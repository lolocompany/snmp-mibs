OneAccess-R1646v2-3132-Zbf DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2Zbf OBJECT IDENTIFIER ::= {r1646Rootv2 3132}

r1646v2ZbfMOProp OBJECT-TYPE
   SYNTAX      SEQUENCE OF R1646v2ZbfMOPropEntry
   MAX-ACCESS  not-accessible
   STATUS      current
   DESCRIPTION
      ""
   ::= {r1646v2Zbf 1}

r1646v2ZbfMOPropEntry OBJECT-TYPE
   SYNTAX      R1646v2ZbfMOPropEntry
   MAX-ACCESS  not-accessible
   STATUS      current
   DESCRIPTION
      ""
   INDEX      { r1646v2ZbfMOPropGlobalIx }
   ::= {r1646v2ZbfMOProp 1}

R1646v2ZbfMOPropEntry ::=
   SEQUENCE
      {
      r1646v2ZbfMOPropPath
         ContainmentPath,
      r1646v2ZbfMOPropRev
         ObjectRevision,
      r1646v2ZbfMOPropGlobalIx
         GlobalIndex
      }

r1646v2ZbfMOPropPath OBJECT-TYPE
   SYNTAX      ContainmentPath
   MAX-ACCESS  read-only
   STATUS      current
   DESCRIPTION
      "Textual description of the containment tree from the instance of
       the root object down to the instance of the current object."
   ::= {r1646v2ZbfMOPropEntry 3}

r1646v2ZbfMOPropRev OBJECT-TYPE
   SYNTAX      ObjectRevision
   MAX-ACCESS  read-only
   STATUS      current
   DESCRIPTION
      "This value corresponds with the revision of the MANAGED OBJECT."
   ::= {r1646v2ZbfMOPropEntry 4}

r1646v2ZbfMOPropGlobalIx OBJECT-TYPE
   SYNTAX      GlobalIndex
   MAX-ACCESS  read-only
   STATUS      current
   DESCRIPTION
      "The value of the tlsCntTreeGlobalIndex of the MANAGED OBJECT."
   ::= {r1646v2ZbfMOPropEntry 10}



er1646v2Zbf OBJECT IDENTIFIER ::= {r1646v2Zbf 11}


er1646v2ZbfSnmpIndexOffset OBJECT IDENTIFIER ::= {er1646v2Zbf 268}

er1646v2ZbfSnmpIndexOffsetTable OBJECT-TYPE
   SYNTAX      SEQUENCE OF Er1646v2ZbfSnmpIndexOffsetEntry
   MAX-ACCESS  not-accessible
   STATUS      current
   DESCRIPTION
      "Preferred offset in the range of SNMP indices for this SWinst, 0 means automatic"
   ::= {er1646v2ZbfSnmpIndexOffset 1}

er1646v2ZbfSnmpIndexOffsetEntry OBJECT-TYPE
   SYNTAX      Er1646v2ZbfSnmpIndexOffsetEntry
   MAX-ACCESS  not-accessible
   STATUS      current
   DESCRIPTION
      ""
   INDEX      { er1646v2ZbfSnmpIndexOffsetGlobalIx }
   ::= {er1646v2ZbfSnmpIndexOffsetTable 1}

Er1646v2ZbfSnmpIndexOffsetEntry ::=
   SEQUENCE
      {
      er1646v2ZbfSnmpIndexOffsetGlobalIx
         GlobalIndex,
      er1646v2ZbfSnmpIndexOffsetValue
         Integer32
      }

er1646v2ZbfSnmpIndexOffsetGlobalIx OBJECT-TYPE
   SYNTAX      GlobalIndex
   MAX-ACCESS  not-accessible
   STATUS      current
   DESCRIPTION
      "The value of the tlsCntTreeGlobalIndex of the MANAGED OBJECT."
   ::= {er1646v2ZbfSnmpIndexOffsetEntry 10}

er1646v2ZbfSnmpIndexOffsetValue OBJECT-TYPE
   SYNTAX      Integer32
   MAX-ACCESS  read-write
   STATUS      current
   DESCRIPTION
      "Path: filter.editConf.snmpIndexOffset"
   ::= {er1646v2ZbfSnmpIndexOffsetEntry 2147483648}


er1646v2ZbfMatchType OBJECT IDENTIFIER ::= {er1646v2Zbf 2}

er1646v2ZbfMatchTypeTable OBJECT-TYPE
   SYNTAX      SEQUENCE OF Er1646v2ZbfMatchTypeEntry
   MAX-ACCESS  not-accessible
   STATUS      current
   DESCRIPTION
      "matchType"
   ::= {er1646v2ZbfMatchType 1}

er1646v2ZbfMatchTypeEntry OBJECT-TYPE
   SYNTAX      Er1646v2ZbfMatchTypeEntry
   MAX-ACCESS  not-accessible
   STATUS      current
   DESCRIPTION
      ""
   INDEX      { er1646v2ZbfMatchTypeGlobalIx }
   ::= {er1646v2ZbfMatchTypeTable 1}

Er1646v2ZbfMatchTypeEntry ::=
   SEQUENCE
      {
      er1646v2ZbfMatchTypeGlobalIx
         GlobalIndex,
      er1646v2ZbfMatchTypeValue
         INTEGER
      }

er1646v2ZbfMatchTypeGlobalIx OBJECT-TYPE
   SYNTAX      GlobalIndex
   MAX-ACCESS  not-accessible
   STATUS      current
   DESCRIPTION
      "The value of the tlsCntTreeGlobalIndex of the MANAGED OBJECT."
   ::= {er1646v2ZbfMatchTypeEntry 10}

er1646v2ZbfMatchTypeValue OBJECT-TYPE
   SYNTAX      INTEGER
               {
               any (0),
               all (1),
               none (2)
               }
   MAX-ACCESS  read-write
   STATUS      current
   DESCRIPTION
      "Path: filter.editConf.matchType

       Possibilities:
               any   (0)
               all   (1)
               none   (2)"
   ::= {er1646v2ZbfMatchTypeEntry 2147483648}


er1646v2ZbfFilterRules OBJECT IDENTIFIER ::= {er1646v2Zbf 3}

er1646v2ZbfFilterRulesSSCTable OBJECT-TYPE
   SYNTAX      SEQUENCE OF Er1646v2ZbfFilterRulesEntry
   MAX-ACCESS  not-accessible
   STATUS      current
   DESCRIPTION
      "filterRules"
   ::= {er1646v2ZbfFilterRules 1}

er1646v2ZbfFilterRulesEntry OBJECT-TYPE
   SYNTAX      Er1646v2ZbfFilterRulesEntry
   MAX-ACCESS  not-accessible
   STATUS      current
   DESCRIPTION
      ""
   INDEX      { er1646v2ZbfFilterRulesGlobalIx,
                er1646v2ZbfFilterRulesTableIx }
   ::= {er1646v2ZbfFilterRulesSSCTable 1}

Er1646v2ZbfFilterRulesEntry ::=
   SEQUENCE
      {
      er1646v2ZbfFilterRulesActions
         VariableLengthTableActions,
      er1646v2ZbfFilterRulesGlobalIx
         GlobalIndex,
      er1646v2ZbfFilterRulesTableIx
         TableIndex,
      er1646v2ZbfFilterRulesName
         DisplayString,
      er1646v2ZbfFilterRulesSrcIpAddress
         DisplayString,
      er1646v2ZbfFilterRulesDstIpAddress
         DisplayString,
      er1646v2ZbfFilterRulesService
         DisplayString,
      er1646v2ZbfFilterRulesFilter
         DisplayString,
      er1646v2ZbfFilterRulesTosDscp
         Integer32,
      er1646v2ZbfFilterRulesMatching
         Integer32
      }

er1646v2ZbfFilterRulesActions OBJECT-TYPE
   SYNTAX      VariableLengthTableActions
   MAX-ACCESS  read-write
   STATUS      current
   DESCRIPTION
      "By way of this field, some manipulations
       on this table may be performed."
   ::= {er1646v2ZbfFilterRulesEntry 2}

er1646v2ZbfFilterRulesGlobalIx OBJECT-TYPE
   SYNTAX      GlobalIndex
   MAX-ACCESS  not-accessible
   STATUS      current
   DESCRIPTION
      "The value of the tlsCntTreeGlobalIndex of the MANAGED OBJECT."
   ::= {er1646v2ZbfFilterRulesEntry 10}

er1646v2ZbfFilterRulesTableIx OBJECT-TYPE
   SYNTAX      TableIndex
   MAX-ACCESS  not-accessible
   STATUS      current
   DESCRIPTION
      ""
   ::= {er1646v2ZbfFilterRulesEntry 11}

er1646v2ZbfFilterRulesName OBJECT-TYPE
   SYNTAX      DisplayString
   MAX-ACCESS  read-write
   STATUS      current
   DESCRIPTION
      "Path: filter.editConf.filterRules.name"
   ::= {er1646v2ZbfFilterRulesEntry 16777216}

er1646v2ZbfFilterRulesSrcIpAddress OBJECT-TYPE
   SYNTAX      DisplayString
   MAX-ACCESS  read-write
   STATUS      current
   DESCRIPTION
      "Path: filter.editConf.filterRules.srcIpAddress"
   ::= {er1646v2ZbfFilterRulesEntry 33554432}

er1646v2ZbfFilterRulesDstIpAddress OBJECT-TYPE
   SYNTAX      DisplayString
   MAX-ACCESS  read-write
   STATUS      current
   DESCRIPTION
      "Path: filter.editConf.filterRules.dstIpAddress"
   ::= {er1646v2ZbfFilterRulesEntry 50331648}

er1646v2ZbfFilterRulesService OBJECT-TYPE
   SYNTAX      DisplayString
   MAX-ACCESS  read-write
   STATUS      current
   DESCRIPTION
      "Path: filter.editConf.filterRules.service"
   ::= {er1646v2ZbfFilterRulesEntry 67108864}

er1646v2ZbfFilterRulesFilter OBJECT-TYPE
   SYNTAX      DisplayString
   MAX-ACCESS  read-write
   STATUS      current
   DESCRIPTION
      "Path: filter.editConf.filterRules.filter"
   ::= {er1646v2ZbfFilterRulesEntry 83886080}

er1646v2ZbfFilterRulesTosDscp OBJECT-TYPE
   SYNTAX      Integer32
   MAX-ACCESS  read-write
   STATUS      current
   DESCRIPTION
      "Path: filter.editConf.filterRules.tosDscp"
   ::= {er1646v2ZbfFilterRulesEntry 100663296}

er1646v2ZbfFilterRulesMatching OBJECT-TYPE
   SYNTAX      Integer32
   MAX-ACCESS  read-write
   STATUS      current
   DESCRIPTION
      "Path: filter.editConf.filterRules.matching

       Bit meanings:
               bit 0 = srcIpAddress,
               bit 1 = dstIpAddress,
               bit 2 = service,
               bit 3 = filter,
               bit 4 = tosDscp,
               bit 5 = timeConstraint"
   ::= {er1646v2ZbfFilterRulesEntry 134217728}

er1646v2ZbfFilterRulesTct OBJECT-TYPE
   SYNTAX      SEQUENCE OF Er1646v2ZbfFilterRulesTctEntry
   MAX-ACCESS  not-accessible
   STATUS      current
   DESCRIPTION
      ""
   ::= {er1646v2ZbfFilterRules 117440512}

er1646v2ZbfFilterRulesTctEntry OBJECT-TYPE
   SYNTAX      Er1646v2ZbfFilterRulesTctEntry
   MAX-ACCESS  not-accessible
   STATUS      current
   DESCRIPTION
      ""
   INDEX      { er1646v2ZbfFilterRulesTctGlobalIx,
                er1646v2ZbfFilterRulesTableIx,
                er1646v2ZbfFilterRulesTctTableIx }
   ::= {er1646v2ZbfFilterRulesTct 1}

Er1646v2ZbfFilterRulesTctEntry ::=
   SEQUENCE
      {
      er1646v2ZbfFilterRulesTctActions
         VariableLengthTableActions,
      er1646v2ZbfFilterRulesTctGlobalIx
         GlobalIndex,
      er1646v2ZbfFilterRulesTctTableIx
         TableIndex,
      er1646v2ZbfFilterRulesTctDayOfWeek
         Integer32,
      er1646v2ZbfFilterRulesTctStartDate
         DisplayString,
      er1646v2ZbfFilterRulesTctEndDate
         DisplayString,
      er1646v2ZbfFilterRulesTctStartTime
         DisplayString,
      er1646v2ZbfFilterRulesTctEndTime
         DisplayString
      }

er1646v2ZbfFilterRulesTctActions OBJECT-TYPE
   SYNTAX      VariableLengthTableActions
   MAX-ACCESS  read-write
   STATUS      current
   DESCRIPTION
      "By way of this field, some manipulations
       on this table may be performed."
   ::= {er1646v2ZbfFilterRulesTctEntry 2}

er1646v2ZbfFilterRulesTctGlobalIx OBJECT-TYPE
   SYNTAX      GlobalIndex
   MAX-ACCESS  not-accessible
   STATUS      current
   DESCRIPTION
      "The value of the tlsCntTreeGlobalIndex of the MANAGED OBJECT."
   ::= {er1646v2ZbfFilterRulesTctEntry 10}

er1646v2ZbfFilterRulesTctTableIx OBJECT-TYPE
   SYNTAX      TableIndex
   MAX-ACCESS  not-accessible
   STATUS      current
   DESCRIPTION
      ""
   ::= {er1646v2ZbfFilterRulesTctEntry 11}

er1646v2ZbfFilterRulesTctDayOfWeek OBJECT-TYPE
   SYNTAX      Integer32
   MAX-ACCESS  read-write
   STATUS      current
   DESCRIPTION
      "Path: filter.editConf.filterRules.timeConstraintTable.dayOfWeek

       Bit meanings:
               bit 0 = monday,
               bit 1 = tuesday,
               bit 2 = wednesday,
               bit 3 = thursday,
               bit 4 = friday,
               bit 5 = saturday,
               bit 6 = sunday"
   ::= {er1646v2ZbfFilterRulesTctEntry 16777216}

er1646v2ZbfFilterRulesTctStartDate OBJECT-TYPE
   SYNTAX      DisplayString
   MAX-ACCESS  read-write
   STATUS      current
   DESCRIPTION
      "Path: filter.editConf.filterRules.timeConstraintTable.startDate"
   ::= {er1646v2ZbfFilterRulesTctEntry 33554432}

er1646v2ZbfFilterRulesTctEndDate OBJECT-TYPE
   SYNTAX      DisplayString
   MAX-ACCESS  read-write
   STATUS      current
   DESCRIPTION
      "Path: filter.editConf.filterRules.timeConstraintTable.endDate"
   ::= {er1646v2ZbfFilterRulesTctEntry 50331648}

er1646v2ZbfFilterRulesTctStartTime OBJECT-TYPE
   SYNTAX      DisplayString
   MAX-ACCESS  read-write
   STATUS      current
   DESCRIPTION
      "Path: filter.editConf.filterRules.timeConstraintTable.startTime"
   ::= {er1646v2ZbfFilterRulesTctEntry 67108864}

er1646v2ZbfFilterRulesTctEndTime OBJECT-TYPE
   SYNTAX      DisplayString
   MAX-ACCESS  read-write
   STATUS      current
   DESCRIPTION
      "Path: filter.editConf.filterRules.timeConstraintTable.endTime"
   ::= {er1646v2ZbfFilterRulesTctEntry 83886080}



sr1646v2Zbf OBJECT IDENTIFIER ::= {r1646v2Zbf 14}


sr1646v2ZbfSnmpIndex OBJECT IDENTIFIER ::= {sr1646v2Zbf 269}

sr1646v2ZbfSnmpIndexTable OBJECT-TYPE
   SYNTAX      SEQUENCE OF Sr1646v2ZbfSnmpIndexEntry
   MAX-ACCESS  not-accessible
   STATUS      current
   DESCRIPTION
      "SNMP index assigned to this object"
   ::= {sr1646v2ZbfSnmpIndex 1}

sr1646v2ZbfSnmpIndexEntry OBJECT-TYPE
   SYNTAX      Sr1646v2ZbfSnmpIndexEntry
   MAX-ACCESS  not-accessible
   STATUS      current
   DESCRIPTION
      ""
   INDEX      { sr1646v2ZbfSnmpIndexGlobalIx }
   ::= {sr1646v2ZbfSnmpIndexTable 1}

Sr1646v2ZbfSnmpIndexEntry ::=
   SEQUENCE
      {
      sr1646v2ZbfSnmpIndexGlobalIx
         GlobalIndex,
      sr1646v2ZbfSnmpIndexValue
         Integer32
      }

sr1646v2ZbfSnmpIndexGlobalIx OBJECT-TYPE
   SYNTAX      GlobalIndex
   MAX-ACCESS  not-accessible
   STATUS      current
   DESCRIPTION
      "The value of the tlsCntTreeGlobalIndex of the MANAGED OBJECT."
   ::= {sr1646v2ZbfSnmpIndexEntry 10}

sr1646v2ZbfSnmpIndexValue OBJECT-TYPE
   SYNTAX      Integer32
   MAX-ACCESS  read-only
   STATUS      current
   DESCRIPTION
      "Path: filter.status.snmpIndex"
   ::= {sr1646v2ZbfSnmpIndexEntry 2147483648}



END
