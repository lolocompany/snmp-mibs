OneAccess-R1645v2-4835-Line DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Line OBJECT IDENTIFIER ::= {r1645Rootv2 4835}

r1645v2LineMOProp OBJECT-TYPE
   SYNTAX      SEQUENCE OF R1645v2LineMOPropEntry
   MAX-ACCESS  not-accessible
   STATUS      current
   DESCRIPTION
      ""
   ::= {r1645v2Line 1}

r1645v2LineMOPropEntry OBJECT-TYPE
   SYNTAX      R1645v2LineMOPropEntry
   MAX-ACCESS  not-accessible
   STATUS      current
   DESCRIPTION
      ""
   INDEX      { r1645v2LineMOPropGlobalIx }
   ::= {r1645v2LineMOProp 1}

R1645v2LineMOPropEntry ::=
   SEQUENCE
      {
      r1645v2LineMOPropPath
         ContainmentPath,
      r1645v2LineMOPropRev
         ObjectRevision,
      r1645v2LineMOPropGlobalIx
         GlobalIndex
      }

r1645v2LineMOPropPath OBJECT-TYPE
   SYNTAX      ContainmentPath
   MAX-ACCESS  read-only
   STATUS      current
   DESCRIPTION
      "Textual description of the containment tree from the instance of
       the root object down to the instance of the current object."
   ::= {r1645v2LineMOPropEntry 3}

r1645v2LineMOPropRev OBJECT-TYPE
   SYNTAX      ObjectRevision
   MAX-ACCESS  read-only
   STATUS      current
   DESCRIPTION
      "This value corresponds with the revision of the MANAGED OBJECT."
   ::= {r1645v2LineMOPropEntry 4}

r1645v2LineMOPropGlobalIx OBJECT-TYPE
   SYNTAX      GlobalIndex
   MAX-ACCESS  read-only
   STATUS      current
   DESCRIPTION
      "The value of the tlsCntTreeGlobalIndex of the MANAGED OBJECT."
   ::= {r1645v2LineMOPropEntry 10}



er1645v2Line OBJECT IDENTIFIER ::= {r1645v2Line 11}


er1645v2LineLinAlmMsk OBJECT IDENTIFIER ::= {er1645v2Line 70}

er1645v2LineLinAlmMskTable OBJECT-TYPE
   SYNTAX      SEQUENCE OF Er1645v2LineLinAlmMskEntry
   MAX-ACCESS  not-accessible
   STATUS      current
   DESCRIPTION
      "lineAlarmMask"
   ::= {er1645v2LineLinAlmMsk 1}

er1645v2LineLinAlmMskEntry OBJECT-TYPE
   SYNTAX      Er1645v2LineLinAlmMskEntry
   MAX-ACCESS  not-accessible
   STATUS      current
   DESCRIPTION
      ""
   INDEX      { er1645v2LineLinAlmMskGlobalIx }
   ::= {er1645v2LineLinAlmMskTable 1}

Er1645v2LineLinAlmMskEntry ::=
   SEQUENCE
      {
      er1645v2LineLinAlmMskGlobalIx
         GlobalIndex,
      er1645v2LineLinAlmMskValue
         Integer32
      }

er1645v2LineLinAlmMskGlobalIx OBJECT-TYPE
   SYNTAX      GlobalIndex
   MAX-ACCESS  not-accessible
   STATUS      current
   DESCRIPTION
      "The value of the tlsCntTreeGlobalIndex of the MANAGED OBJECT."
   ::= {er1645v2LineLinAlmMskEntry 10}

er1645v2LineLinAlmMskValue OBJECT-TYPE
   SYNTAX      Integer32
   MAX-ACCESS  read-write
   STATUS      current
   DESCRIPTION
      "Path: line.editConf.alarmMask

       Bit meanings:
               bit 0 = linkDown"
   ::= {er1645v2LineLinAlmMskEntry 2147483648}


er1645v2LineLinAlmLev OBJECT IDENTIFIER ::= {er1645v2Line 71}

er1645v2LineLinAlmLevSSCTable OBJECT-TYPE
   SYNTAX      SEQUENCE OF Er1645v2LineLinAlmLevEntry
   MAX-ACCESS  not-accessible
   STATUS      current
   DESCRIPTION
      "lineAlarmLevel"
   ::= {er1645v2LineLinAlmLev 1}

er1645v2LineLinAlmLevEntry OBJECT-TYPE
   SYNTAX      Er1645v2LineLinAlmLevEntry
   MAX-ACCESS  not-accessible
   STATUS      current
   DESCRIPTION
      ""
   INDEX      { er1645v2LineLinAlmLevGlobalIx }
   ::= {er1645v2LineLinAlmLevSSCTable 1}

Er1645v2LineLinAlmLevEntry ::=
   SEQUENCE
      {
      er1645v2LineLinAlmLevGlobalIx
         GlobalIndex,
      er1645v2LineLinAlmLevLnkDwn
         Integer32
      }

er1645v2LineLinAlmLevGlobalIx OBJECT-TYPE
   SYNTAX      GlobalIndex
   MAX-ACCESS  not-accessible
   STATUS      current
   DESCRIPTION
      "The value of the tlsCntTreeGlobalIndex of the MANAGED OBJECT."
   ::= {er1645v2LineLinAlmLevEntry 10}

er1645v2LineLinAlmLevLnkDwn OBJECT-TYPE
   SYNTAX      Integer32
   MAX-ACCESS  read-write
   STATUS      current
   DESCRIPTION
      "Path: line.editConf.alarmLevel.linkDown"
   ::= {er1645v2LineLinAlmLevEntry 16777216}


er1645v2LineLinkAlarmThresholds OBJECT IDENTIFIER ::= {er1645v2Line 65}

er1645v2LineLinkAlarmThresholdsSSCTable OBJECT-TYPE
   SYNTAX      SEQUENCE OF Er1645v2LineLinkAlarmThresholdsEntry
   MAX-ACCESS  not-accessible
   STATUS      current
   DESCRIPTION
      "threshold values for alarm generation"
   ::= {er1645v2LineLinkAlarmThresholds 1}

er1645v2LineLinkAlarmThresholdsEntry OBJECT-TYPE
   SYNTAX      Er1645v2LineLinkAlarmThresholdsEntry
   MAX-ACCESS  not-accessible
   STATUS      current
   DESCRIPTION
      ""
   INDEX      { er1645v2LineLinkAlarmThresholdsGlobalIx }
   ::= {er1645v2LineLinkAlarmThresholdsSSCTable 1}

Er1645v2LineLinkAlarmThresholdsEntry ::=
   SEQUENCE
      {
      er1645v2LineLinkAlarmThresholdsGlobalIx
         GlobalIndex,
      er1645v2LineLinkAlarmThresholdsNoiseMrgn
         Integer32,
      er1645v2LineLinkAlarmThresholdsEsrExc
         Integer32,
      er1645v2LineLinkAlarmThresholdsSesrExc
         Integer32,
      er1645v2LineLinkAlarmThresholdsIfDsSpeed
         INTEGER,
      er1645v2LineLinkAlarmThresholdsIfUsSpeed
         INTEGER,
      er1645v2LineLinkAlarmThresholdsElecLen
         Integer32
      }

er1645v2LineLinkAlarmThresholdsGlobalIx OBJECT-TYPE
   SYNTAX      GlobalIndex
   MAX-ACCESS  not-accessible
   STATUS      current
   DESCRIPTION
      "The value of the tlsCntTreeGlobalIndex of the MANAGED OBJECT."
   ::= {er1645v2LineLinkAlarmThresholdsEntry 10}

er1645v2LineLinkAlarmThresholdsNoiseMrgn OBJECT-TYPE
   SYNTAX      Integer32
   UNITS       "dB"
   MAX-ACCESS  read-write
   STATUS      current
   DESCRIPTION
      "Path: line.editConf.linkAlarmThresholds.noiseMargin

       unit name = dB"
   ::= {er1645v2LineLinkAlarmThresholdsEntry 33554432}

er1645v2LineLinkAlarmThresholdsEsrExc OBJECT-TYPE
   SYNTAX      Integer32
   MAX-ACCESS  read-write
   STATUS      current
   DESCRIPTION
      "Path: line.editConf.linkAlarmThresholds.errSecRatioExceeded

       unit name = ratio
       formula = 1000 / ; 1000 *"
   ::= {er1645v2LineLinkAlarmThresholdsEntry 83886080}

er1645v2LineLinkAlarmThresholdsSesrExc OBJECT-TYPE
   SYNTAX      Integer32
   MAX-ACCESS  read-write
   STATUS      current
   DESCRIPTION
      "Path: line.editConf.linkAlarmThresholds.sevErrSecRatioExceeded

       unit name = ratio
       formula = 1000 / ; 1000 *"
   ::= {er1645v2LineLinkAlarmThresholdsEntry 100663296}

er1645v2LineLinkAlarmThresholdsIfDsSpeed OBJECT-TYPE
   SYNTAX      INTEGER
               {
               disabled (0)
               }
   UNITS       "bps"
   MAX-ACCESS  read-write
   STATUS      current
   DESCRIPTION
      "Path: line.editConf.linkAlarmThresholds.ifDsSpeed

       unit name = bps

       Possibilities:
               disabled   (0)"
   ::= {er1645v2LineLinkAlarmThresholdsEntry 117440512}

er1645v2LineLinkAlarmThresholdsIfUsSpeed OBJECT-TYPE
   SYNTAX      INTEGER
               {
               disabled (0)
               }
   UNITS       "bps"
   MAX-ACCESS  read-write
   STATUS      current
   DESCRIPTION
      "Path: line.editConf.linkAlarmThresholds.ifUsSpeed

       unit name = bps

       Possibilities:
               disabled   (0)"
   ::= {er1645v2LineLinkAlarmThresholdsEntry 134217728}

er1645v2LineLinkAlarmThresholdsElecLen OBJECT-TYPE
   SYNTAX      Integer32
   UNITS       "dB"
   MAX-ACCESS  read-write
   STATUS      current
   DESCRIPTION
      "Path: line.editConf.linkAlarmThresholds.electricalLength

       unit name = dB"
   ::= {er1645v2LineLinkAlarmThresholdsEntry 150994944}



sr1645v2Line OBJECT IDENTIFIER ::= {r1645v2Line 14}


sr1645v2LineIfOperStatus OBJECT IDENTIFIER ::= {sr1645v2Line 107}

sr1645v2LineIfOperStatusTable OBJECT-TYPE
   SYNTAX      SEQUENCE OF Sr1645v2LineIfOperStatusEntry
   MAX-ACCESS  not-accessible
   STATUS      current
   DESCRIPTION
      "ifOperStatus"
   ::= {sr1645v2LineIfOperStatus 1}

sr1645v2LineIfOperStatusEntry OBJECT-TYPE
   SYNTAX      Sr1645v2LineIfOperStatusEntry
   MAX-ACCESS  not-accessible
   STATUS      current
   DESCRIPTION
      ""
   INDEX      { sr1645v2LineIfOperStatusGlobalIx }
   ::= {sr1645v2LineIfOperStatusTable 1}

Sr1645v2LineIfOperStatusEntry ::=
   SEQUENCE
      {
      sr1645v2LineIfOperStatusGlobalIx
         GlobalIndex,
      sr1645v2LineIfOperStatusValue
         INTEGER
      }

sr1645v2LineIfOperStatusGlobalIx OBJECT-TYPE
   SYNTAX      GlobalIndex
   MAX-ACCESS  not-accessible
   STATUS      current
   DESCRIPTION
      "The value of the tlsCntTreeGlobalIndex of the MANAGED OBJECT."
   ::= {sr1645v2LineIfOperStatusEntry 10}

sr1645v2LineIfOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: line.status.ifOperStatus

       Possibilities:
               up   (1)
               down   (2)
               testing   (3)
               unknown   (4)
               dormant   (5)
               notPresent   (6)
               lowerLayerDown   (7)"
   ::= {sr1645v2LineIfOperStatusEntry 2147483648}


sr1645v2LineIfDescr OBJECT IDENTIFIER ::= {sr1645v2Line 101}

sr1645v2LineIfDescrTable OBJECT-TYPE
   SYNTAX      SEQUENCE OF Sr1645v2LineIfDescrEntry
   MAX-ACCESS  not-accessible
   STATUS      current
   DESCRIPTION
      "ifDescr"
   ::= {sr1645v2LineIfDescr 1}

sr1645v2LineIfDescrEntry OBJECT-TYPE
   SYNTAX      Sr1645v2LineIfDescrEntry
   MAX-ACCESS  not-accessible
   STATUS      current
   DESCRIPTION
      ""
   INDEX      { sr1645v2LineIfDescrGlobalIx }
   ::= {sr1645v2LineIfDescrTable 1}

Sr1645v2LineIfDescrEntry ::=
   SEQUENCE
      {
      sr1645v2LineIfDescrGlobalIx
         GlobalIndex,
      sr1645v2LineIfDescrValue
         DisplayString
      }

sr1645v2LineIfDescrGlobalIx OBJECT-TYPE
   SYNTAX      GlobalIndex
   MAX-ACCESS  not-accessible
   STATUS      current
   DESCRIPTION
      "The value of the tlsCntTreeGlobalIndex of the MANAGED OBJECT."
   ::= {sr1645v2LineIfDescrEntry 10}

sr1645v2LineIfDescrValue OBJECT-TYPE
   SYNTAX      DisplayString
   MAX-ACCESS  read-only
   STATUS      current
   DESCRIPTION
      "Path: line.status.ifDescr"
   ::= {sr1645v2LineIfDescrEntry 2147483648}


sr1645v2LineIfType OBJECT IDENTIFIER ::= {sr1645v2Line 102}

sr1645v2LineIfTypeTable OBJECT-TYPE
   SYNTAX      SEQUENCE OF Sr1645v2LineIfTypeEntry
   MAX-ACCESS  not-accessible
   STATUS      current
   DESCRIPTION
      "ifType"
   ::= {sr1645v2LineIfType 1}

sr1645v2LineIfTypeEntry OBJECT-TYPE
   SYNTAX      Sr1645v2LineIfTypeEntry
   MAX-ACCESS  not-accessible
   STATUS      current
   DESCRIPTION
      ""
   INDEX      { sr1645v2LineIfTypeGlobalIx }
   ::= {sr1645v2LineIfTypeTable 1}

Sr1645v2LineIfTypeEntry ::=
   SEQUENCE
      {
      sr1645v2LineIfTypeGlobalIx
         GlobalIndex,
      sr1645v2LineIfTypeValue
         INTEGER
      }

sr1645v2LineIfTypeGlobalIx OBJECT-TYPE
   SYNTAX      GlobalIndex
   MAX-ACCESS  not-accessible
   STATUS      current
   DESCRIPTION
      "The value of the tlsCntTreeGlobalIndex of the MANAGED OBJECT."
   ::= {sr1645v2LineIfTypeEntry 10}

sr1645v2LineIfTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: line.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2LineIfTypeEntry 2147483648}


sr1645v2LineIfUsSpeed OBJECT IDENTIFIER ::= {sr1645v2Line 104}

sr1645v2LineIfUsSpeedTable OBJECT-TYPE
   SYNTAX      SEQUENCE OF Sr1645v2LineIfUsSpeedEntry
   MAX-ACCESS  not-accessible
   STATUS      current
   DESCRIPTION
      "ifSpeed"
   ::= {sr1645v2LineIfUsSpeed 1}

sr1645v2LineIfUsSpeedEntry OBJECT-TYPE
   SYNTAX      Sr1645v2LineIfUsSpeedEntry
   MAX-ACCESS  not-accessible
   STATUS      current
   DESCRIPTION
      ""
   INDEX      { sr1645v2LineIfUsSpeedGlobalIx }
   ::= {sr1645v2LineIfUsSpeedTable 1}

Sr1645v2LineIfUsSpeedEntry ::=
   SEQUENCE
      {
      sr1645v2LineIfUsSpeedGlobalIx
         GlobalIndex,
      sr1645v2LineIfUsSpeedValue
         Gauge32
      }

sr1645v2LineIfUsSpeedGlobalIx OBJECT-TYPE
   SYNTAX      GlobalIndex
   MAX-ACCESS  not-accessible
   STATUS      current
   DESCRIPTION
      "The value of the tlsCntTreeGlobalIndex of the MANAGED OBJECT."
   ::= {sr1645v2LineIfUsSpeedEntry 10}

sr1645v2LineIfUsSpeedValue OBJECT-TYPE
   SYNTAX      Gauge32
   MAX-ACCESS  read-only
   STATUS      current
   DESCRIPTION
      "Path: line.status.ifUsSpeed

       32 bit unsigned gauge value."
   ::= {sr1645v2LineIfUsSpeedEntry 2147483648}


sr1645v2LineIfDsSpeed OBJECT IDENTIFIER ::= {sr1645v2Line 127}

sr1645v2LineIfDsSpeedTable OBJECT-TYPE
   SYNTAX      SEQUENCE OF Sr1645v2LineIfDsSpeedEntry
   MAX-ACCESS  not-accessible
   STATUS      current
   DESCRIPTION
      "ifSpeed"
   ::= {sr1645v2LineIfDsSpeed 1}

sr1645v2LineIfDsSpeedEntry OBJECT-TYPE
   SYNTAX      Sr1645v2LineIfDsSpeedEntry
   MAX-ACCESS  not-accessible
   STATUS      current
   DESCRIPTION
      ""
   INDEX      { sr1645v2LineIfDsSpeedGlobalIx }
   ::= {sr1645v2LineIfDsSpeedTable 1}

Sr1645v2LineIfDsSpeedEntry ::=
   SEQUENCE
      {
      sr1645v2LineIfDsSpeedGlobalIx
         GlobalIndex,
      sr1645v2LineIfDsSpeedValue
         Gauge32
      }

sr1645v2LineIfDsSpeedGlobalIx OBJECT-TYPE
   SYNTAX      GlobalIndex
   MAX-ACCESS  not-accessible
   STATUS      current
   DESCRIPTION
      "The value of the tlsCntTreeGlobalIndex of the MANAGED OBJECT."
   ::= {sr1645v2LineIfDsSpeedEntry 10}

sr1645v2LineIfDsSpeedValue OBJECT-TYPE
   SYNTAX      Gauge32
   MAX-ACCESS  read-only
   STATUS      current
   DESCRIPTION
      "Path: line.status.ifDsSpeed

       32 bit unsigned gauge value."
   ::= {sr1645v2LineIfDsSpeedEntry 2147483648}


sr1645v2LineIfUsNetSpeed OBJECT IDENTIFIER ::= {sr1645v2Line 13}

sr1645v2LineIfUsNetSpeedTable OBJECT-TYPE
   SYNTAX      SEQUENCE OF Sr1645v2LineIfUsNetSpeedEntry
   MAX-ACCESS  not-accessible
   STATUS      current
   DESCRIPTION
      "ifSpeed"
   ::= {sr1645v2LineIfUsNetSpeed 1}

sr1645v2LineIfUsNetSpeedEntry OBJECT-TYPE
   SYNTAX      Sr1645v2LineIfUsNetSpeedEntry
   MAX-ACCESS  not-accessible
   STATUS      current
   DESCRIPTION
      ""
   INDEX      { sr1645v2LineIfUsNetSpeedGlobalIx }
   ::= {sr1645v2LineIfUsNetSpeedTable 1}

Sr1645v2LineIfUsNetSpeedEntry ::=
   SEQUENCE
      {
      sr1645v2LineIfUsNetSpeedGlobalIx
         GlobalIndex,
      sr1645v2LineIfUsNetSpeedValue
         Gauge32
      }

sr1645v2LineIfUsNetSpeedGlobalIx OBJECT-TYPE
   SYNTAX      GlobalIndex
   MAX-ACCESS  not-accessible
   STATUS      current
   DESCRIPTION
      "The value of the tlsCntTreeGlobalIndex of the MANAGED OBJECT."
   ::= {sr1645v2LineIfUsNetSpeedEntry 10}

sr1645v2LineIfUsNetSpeedValue OBJECT-TYPE
   SYNTAX      Gauge32
   MAX-ACCESS  read-only
   STATUS      current
   DESCRIPTION
      "Path: line.status.ifUsNetSpeed

       32 bit unsigned gauge value."
   ::= {sr1645v2LineIfUsNetSpeedEntry 2147483648}


sr1645v2LineIfDsNetSpeed OBJECT IDENTIFIER ::= {sr1645v2Line 12}

sr1645v2LineIfDsNetSpeedTable OBJECT-TYPE
   SYNTAX      SEQUENCE OF Sr1645v2LineIfDsNetSpeedEntry
   MAX-ACCESS  not-accessible
   STATUS      current
   DESCRIPTION
      "ifSpeed"
   ::= {sr1645v2LineIfDsNetSpeed 1}

sr1645v2LineIfDsNetSpeedEntry OBJECT-TYPE
   SYNTAX      Sr1645v2LineIfDsNetSpeedEntry
   MAX-ACCESS  not-accessible
   STATUS      current
   DESCRIPTION
      ""
   INDEX      { sr1645v2LineIfDsNetSpeedGlobalIx }
   ::= {sr1645v2LineIfDsNetSpeedTable 1}

Sr1645v2LineIfDsNetSpeedEntry ::=
   SEQUENCE
      {
      sr1645v2LineIfDsNetSpeedGlobalIx
         GlobalIndex,
      sr1645v2LineIfDsNetSpeedValue
         Gauge32
      }

sr1645v2LineIfDsNetSpeedGlobalIx OBJECT-TYPE
   SYNTAX      GlobalIndex
   MAX-ACCESS  not-accessible
   STATUS      current
   DESCRIPTION
      "The value of the tlsCntTreeGlobalIndex of the MANAGED OBJECT."
   ::= {sr1645v2LineIfDsNetSpeedEntry 10}

sr1645v2LineIfDsNetSpeedValue OBJECT-TYPE
   SYNTAX      Gauge32
   MAX-ACCESS  read-only
   STATUS      current
   DESCRIPTION
      "Path: line.status.ifDsNetSpeed

       32 bit unsigned gauge value."
   ::= {sr1645v2LineIfDsNetSpeedEntry 2147483648}


sr1645v2LineIfUsAttNetSpeed OBJECT IDENTIFIER ::= {sr1645v2Line 19}

sr1645v2LineIfUsAttNetSpeedTable OBJECT-TYPE
   SYNTAX      SEQUENCE OF Sr1645v2LineIfUsAttNetSpeedEntry
   MAX-ACCESS  not-accessible
   STATUS      current
   DESCRIPTION
      "ifSpeed"
   ::= {sr1645v2LineIfUsAttNetSpeed 1}

sr1645v2LineIfUsAttNetSpeedEntry OBJECT-TYPE
   SYNTAX      Sr1645v2LineIfUsAttNetSpeedEntry
   MAX-ACCESS  not-accessible
   STATUS      current
   DESCRIPTION
      ""
   INDEX      { sr1645v2LineIfUsAttNetSpeedGlobalIx }
   ::= {sr1645v2LineIfUsAttNetSpeedTable 1}

Sr1645v2LineIfUsAttNetSpeedEntry ::=
   SEQUENCE
      {
      sr1645v2LineIfUsAttNetSpeedGlobalIx
         GlobalIndex,
      sr1645v2LineIfUsAttNetSpeedValue
         Gauge32
      }

sr1645v2LineIfUsAttNetSpeedGlobalIx OBJECT-TYPE
   SYNTAX      GlobalIndex
   MAX-ACCESS  not-accessible
   STATUS      current
   DESCRIPTION
      "The value of the tlsCntTreeGlobalIndex of the MANAGED OBJECT."
   ::= {sr1645v2LineIfUsAttNetSpeedEntry 10}

sr1645v2LineIfUsAttNetSpeedValue OBJECT-TYPE
   SYNTAX      Gauge32
   MAX-ACCESS  read-only
   STATUS      current
   DESCRIPTION
      "Path: line.status.ifUsAttNetSpeed

       32 bit unsigned gauge value."
   ::= {sr1645v2LineIfUsAttNetSpeedEntry 2147483648}


sr1645v2LineIfDsAttNetSpeed OBJECT IDENTIFIER ::= {sr1645v2Line 18}

sr1645v2LineIfDsAttNetSpeedTable OBJECT-TYPE
   SYNTAX      SEQUENCE OF Sr1645v2LineIfDsAttNetSpeedEntry
   MAX-ACCESS  not-accessible
   STATUS      current
   DESCRIPTION
      "ifSpeed"
   ::= {sr1645v2LineIfDsAttNetSpeed 1}

sr1645v2LineIfDsAttNetSpeedEntry OBJECT-TYPE
   SYNTAX      Sr1645v2LineIfDsAttNetSpeedEntry
   MAX-ACCESS  not-accessible
   STATUS      current
   DESCRIPTION
      ""
   INDEX      { sr1645v2LineIfDsAttNetSpeedGlobalIx }
   ::= {sr1645v2LineIfDsAttNetSpeedTable 1}

Sr1645v2LineIfDsAttNetSpeedEntry ::=
   SEQUENCE
      {
      sr1645v2LineIfDsAttNetSpeedGlobalIx
         GlobalIndex,
      sr1645v2LineIfDsAttNetSpeedValue
         Gauge32
      }

sr1645v2LineIfDsAttNetSpeedGlobalIx OBJECT-TYPE
   SYNTAX      GlobalIndex
   MAX-ACCESS  not-accessible
   STATUS      current
   DESCRIPTION
      "The value of the tlsCntTreeGlobalIndex of the MANAGED OBJECT."
   ::= {sr1645v2LineIfDsAttNetSpeedEntry 10}

sr1645v2LineIfDsAttNetSpeedValue OBJECT-TYPE
   SYNTAX      Gauge32
   MAX-ACCESS  read-only
   STATUS      current
   DESCRIPTION
      "Path: line.status.ifDsAttNetSpeed

       32 bit unsigned gauge value."
   ::= {sr1645v2LineIfDsAttNetSpeedEntry 2147483648}


sr1645v2LineG997VendorID OBJECT IDENTIFIER ::= {sr1645v2Line 24}

sr1645v2LineG997VendorIDTable OBJECT-TYPE
   SYNTAX      SEQUENCE OF Sr1645v2LineG997VendorIDEntry
   MAX-ACCESS  not-accessible
   STATUS      current
   DESCRIPTION
      "GFast vendor ID"
   ::= {sr1645v2LineG997VendorID 1}

sr1645v2LineG997VendorIDEntry OBJECT-TYPE
   SYNTAX      Sr1645v2LineG997VendorIDEntry
   MAX-ACCESS  not-accessible
   STATUS      current
   DESCRIPTION
      ""
   INDEX      { sr1645v2LineG997VendorIDGlobalIx }
   ::= {sr1645v2LineG997VendorIDTable 1}

Sr1645v2LineG997VendorIDEntry ::=
   SEQUENCE
      {
      sr1645v2LineG997VendorIDGlobalIx
         GlobalIndex,
      sr1645v2LineG997VendorIDValue
         OCTET STRING
      }

sr1645v2LineG997VendorIDGlobalIx OBJECT-TYPE
   SYNTAX      GlobalIndex
   MAX-ACCESS  not-accessible
   STATUS      current
   DESCRIPTION
      "The value of the tlsCntTreeGlobalIndex of the MANAGED OBJECT."
   ::= {sr1645v2LineG997VendorIDEntry 10}

sr1645v2LineG997VendorIDValue OBJECT-TYPE
   SYNTAX      OCTET STRING
   MAX-ACCESS  read-only
   STATUS      current
   DESCRIPTION
      "Path: line.status.g997VendorID"
   ::= {sr1645v2LineG997VendorIDEntry 2147483648}


sr1645v2LineSnmpIndex OBJECT IDENTIFIER ::= {sr1645v2Line 269}

sr1645v2LineSnmpIndexTable OBJECT-TYPE
   SYNTAX      SEQUENCE OF Sr1645v2LineSnmpIndexEntry
   MAX-ACCESS  not-accessible
   STATUS      current
   DESCRIPTION
      "SNMP index assigned to this object"
   ::= {sr1645v2LineSnmpIndex 1}

sr1645v2LineSnmpIndexEntry OBJECT-TYPE
   SYNTAX      Sr1645v2LineSnmpIndexEntry
   MAX-ACCESS  not-accessible
   STATUS      current
   DESCRIPTION
      ""
   INDEX      { sr1645v2LineSnmpIndexGlobalIx }
   ::= {sr1645v2LineSnmpIndexTable 1}

Sr1645v2LineSnmpIndexEntry ::=
   SEQUENCE
      {
      sr1645v2LineSnmpIndexGlobalIx
         GlobalIndex,
      sr1645v2LineSnmpIndexValue
         Integer32
      }

sr1645v2LineSnmpIndexGlobalIx OBJECT-TYPE
   SYNTAX      GlobalIndex
   MAX-ACCESS  not-accessible
   STATUS      current
   DESCRIPTION
      "The value of the tlsCntTreeGlobalIndex of the MANAGED OBJECT."
   ::= {sr1645v2LineSnmpIndexEntry 10}

sr1645v2LineSnmpIndexValue OBJECT-TYPE
   SYNTAX      Integer32
   MAX-ACCESS  read-only
   STATUS      current
   DESCRIPTION
      "Path: line.status.snmpIndex"
   ::= {sr1645v2LineSnmpIndexEntry 2147483648}



pr1645v2Line OBJECT IDENTIFIER ::= {r1645v2Line 12}


pr1645v2LineH2 OBJECT IDENTIFIER ::= {pr1645v2Line 21}

pr1645v2LineH2SSCTable OBJECT-TYPE
   SYNTAX      SEQUENCE OF Pr1645v2LineH2Entry
   MAX-ACCESS  not-accessible
   STATUS      current
   DESCRIPTION
      "h2Line"
   ::= {pr1645v2LineH2 1}

pr1645v2LineH2Entry OBJECT-TYPE
   SYNTAX      Pr1645v2LineH2Entry
   MAX-ACCESS  not-accessible
   STATUS      current
   DESCRIPTION
      ""
   INDEX      { pr1645v2LineH2GlobalIx,
                pr1645v2LineH2TableIx }
   ::= {pr1645v2LineH2SSCTable 1}

Pr1645v2LineH2Entry ::=
   SEQUENCE
      {
      pr1645v2LineH2GlobalIx
         GlobalIndex,
      pr1645v2LineH2TableIx
         TableIndex,
      pr1645v2LineH2SysUpTime
         TimeTicks,
      pr1645v2LineH2LDownCnt
         Counter32,
      pr1645v2LineH2LDownTme
         TimeTicks,
      pr1645v2LineH2UsSpdMin
         Integer32,
      pr1645v2LineH2UsSpdAvrg
         Integer32,
      pr1645v2LineH2UsSpdMax
         Integer32,
      pr1645v2LineH2DsSpdMin
         Integer32,
      pr1645v2LineH2DsSpdAvrg
         Integer32,
      pr1645v2LineH2DsSpdMax
         Integer32
      }

pr1645v2LineH2GlobalIx OBJECT-TYPE
   SYNTAX      GlobalIndex
   MAX-ACCESS  not-accessible
   STATUS      current
   DESCRIPTION
      "The value of the tlsCntTreeGlobalIndex of the MANAGED OBJECT."
   ::= {pr1645v2LineH2Entry 10}

pr1645v2LineH2TableIx OBJECT-TYPE
   SYNTAX      TableIndex
   MAX-ACCESS  not-accessible
   STATUS      current
   DESCRIPTION
      ""
   ::= {pr1645v2LineH2Entry 11}

pr1645v2LineH2SysUpTime OBJECT-TYPE
   SYNTAX      TimeTicks
   MAX-ACCESS  read-only
   STATUS      current
   DESCRIPTION
      "Path: line.performance.h2Line.sysUpTime

       Time in centi-second."
   ::= {pr1645v2LineH2Entry 16777216}

pr1645v2LineH2LDownCnt OBJECT-TYPE
   SYNTAX      Counter32
   MAX-ACCESS  read-only
   STATUS      current
   DESCRIPTION
      "Path: line.performance.h2Line.linkDownCount

       32 bit unsigned wrappable counter."
   ::= {pr1645v2LineH2Entry 33554432}

pr1645v2LineH2LDownTme OBJECT-TYPE
   SYNTAX      TimeTicks
   MAX-ACCESS  read-only
   STATUS      current
   DESCRIPTION
      "Path: line.performance.h2Line.linkDownTime

       Time in centi-second."
   ::= {pr1645v2LineH2Entry 50331648}

pr1645v2LineH2UsSpdMin OBJECT-TYPE
   SYNTAX      Integer32
   MAX-ACCESS  read-only
   STATUS      current
   DESCRIPTION
      "Path: line.performance.h2Line.usSpeedMin

       formula = 32000 * ; 32000 /"
   ::= {pr1645v2LineH2Entry 67108864}

pr1645v2LineH2UsSpdAvrg OBJECT-TYPE
   SYNTAX      Integer32
   MAX-ACCESS  read-only
   STATUS      current
   DESCRIPTION
      "Path: line.performance.h2Line.usSpeedAvrg

       formula = 32000 * ; 32000 /"
   ::= {pr1645v2LineH2Entry 83886080}

pr1645v2LineH2UsSpdMax OBJECT-TYPE
   SYNTAX      Integer32
   MAX-ACCESS  read-only
   STATUS      current
   DESCRIPTION
      "Path: line.performance.h2Line.usSpeedMax

       formula = 32000 * ; 32000 /"
   ::= {pr1645v2LineH2Entry 100663296}

pr1645v2LineH2DsSpdMin OBJECT-TYPE
   SYNTAX      Integer32
   MAX-ACCESS  read-only
   STATUS      current
   DESCRIPTION
      "Path: line.performance.h2Line.dsSpeedMin

       formula = 32000 * ; 32000 /"
   ::= {pr1645v2LineH2Entry 117440512}

pr1645v2LineH2DsSpdAvrg OBJECT-TYPE
   SYNTAX      Integer32
   MAX-ACCESS  read-only
   STATUS      current
   DESCRIPTION
      "Path: line.performance.h2Line.dsSpeedAvrg

       formula = 32000 * ; 32000 /"
   ::= {pr1645v2LineH2Entry 134217728}

pr1645v2LineH2DsSpdMax OBJECT-TYPE
   SYNTAX      Integer32
   MAX-ACCESS  read-only
   STATUS      current
   DESCRIPTION
      "Path: line.performance.h2Line.dsSpeedMax

       formula = 32000 * ; 32000 /"
   ::= {pr1645v2LineH2Entry 150994944}


pr1645v2LineH24 OBJECT IDENTIFIER ::= {pr1645v2Line 23}

pr1645v2LineH24SSCTable OBJECT-TYPE
   SYNTAX      SEQUENCE OF Pr1645v2LineH24Entry
   MAX-ACCESS  not-accessible
   STATUS      current
   DESCRIPTION
      "h24Line"
   ::= {pr1645v2LineH24 1}

pr1645v2LineH24Entry OBJECT-TYPE
   SYNTAX      Pr1645v2LineH24Entry
   MAX-ACCESS  not-accessible
   STATUS      current
   DESCRIPTION
      ""
   INDEX      { pr1645v2LineH24GlobalIx,
                pr1645v2LineH24TableIx }
   ::= {pr1645v2LineH24SSCTable 1}

Pr1645v2LineH24Entry ::=
   SEQUENCE
      {
      pr1645v2LineH24GlobalIx
         GlobalIndex,
      pr1645v2LineH24TableIx
         TableIndex,
      pr1645v2LineH24SysUpTime
         TimeTicks,
      pr1645v2LineH24LDownCnt
         Counter32,
      pr1645v2LineH24LDownTme
         TimeTicks,
      pr1645v2LineH24UsSpdMin
         Integer32,
      pr1645v2LineH24UsSpdAvrg
         Integer32,
      pr1645v2LineH24UsSpdMax
         Integer32,
      pr1645v2LineH24DsSpdMin
         Integer32,
      pr1645v2LineH24DsSpdAvrg
         Integer32,
      pr1645v2LineH24DsSpdMax
         Integer32
      }

pr1645v2LineH24GlobalIx OBJECT-TYPE
   SYNTAX      GlobalIndex
   MAX-ACCESS  not-accessible
   STATUS      current
   DESCRIPTION
      "The value of the tlsCntTreeGlobalIndex of the MANAGED OBJECT."
   ::= {pr1645v2LineH24Entry 10}

pr1645v2LineH24TableIx OBJECT-TYPE
   SYNTAX      TableIndex
   MAX-ACCESS  not-accessible
   STATUS      current
   DESCRIPTION
      ""
   ::= {pr1645v2LineH24Entry 11}

pr1645v2LineH24SysUpTime OBJECT-TYPE
   SYNTAX      TimeTicks
   MAX-ACCESS  read-only
   STATUS      current
   DESCRIPTION
      "Path: line.performance.h24Line.sysUpTime

       Time in centi-second."
   ::= {pr1645v2LineH24Entry 16777216}

pr1645v2LineH24LDownCnt OBJECT-TYPE
   SYNTAX      Counter32
   MAX-ACCESS  read-only
   STATUS      current
   DESCRIPTION
      "Path: line.performance.h24Line.linkDownCount

       32 bit unsigned wrappable counter."
   ::= {pr1645v2LineH24Entry 33554432}

pr1645v2LineH24LDownTme OBJECT-TYPE
   SYNTAX      TimeTicks
   MAX-ACCESS  read-only
   STATUS      current
   DESCRIPTION
      "Path: line.performance.h24Line.linkDownTime

       Time in centi-second."
   ::= {pr1645v2LineH24Entry 50331648}

pr1645v2LineH24UsSpdMin OBJECT-TYPE
   SYNTAX      Integer32
   MAX-ACCESS  read-only
   STATUS      current
   DESCRIPTION
      "Path: line.performance.h24Line.usSpeedMin

       formula = 32000 * ; 32000 /"
   ::= {pr1645v2LineH24Entry 67108864}

pr1645v2LineH24UsSpdAvrg OBJECT-TYPE
   SYNTAX      Integer32
   MAX-ACCESS  read-only
   STATUS      current
   DESCRIPTION
      "Path: line.performance.h24Line.usSpeedAvrg

       formula = 32000 * ; 32000 /"
   ::= {pr1645v2LineH24Entry 83886080}

pr1645v2LineH24UsSpdMax OBJECT-TYPE
   SYNTAX      Integer32
   MAX-ACCESS  read-only
   STATUS      current
   DESCRIPTION
      "Path: line.performance.h24Line.usSpeedMax

       formula = 32000 * ; 32000 /"
   ::= {pr1645v2LineH24Entry 100663296}

pr1645v2LineH24DsSpdMin OBJECT-TYPE
   SYNTAX      Integer32
   MAX-ACCESS  read-only
   STATUS      current
   DESCRIPTION
      "Path: line.performance.h24Line.dsSpeedMin

       formula = 32000 * ; 32000 /"
   ::= {pr1645v2LineH24Entry 117440512}

pr1645v2LineH24DsSpdAvrg OBJECT-TYPE
   SYNTAX      Integer32
   MAX-ACCESS  read-only
   STATUS      current
   DESCRIPTION
      "Path: line.performance.h24Line.dsSpeedAvrg

       formula = 32000 * ; 32000 /"
   ::= {pr1645v2LineH24Entry 134217728}

pr1645v2LineH24DsSpdMax OBJECT-TYPE
   SYNTAX      Integer32
   MAX-ACCESS  read-only
   STATUS      current
   DESCRIPTION
      "Path: line.performance.h24Line.dsSpeedMax

       formula = 32000 * ; 32000 /"
   ::= {pr1645v2LineH24Entry 150994944}


pr1645v2LineD7 OBJECT IDENTIFIER ::= {pr1645v2Line 26}

pr1645v2LineD7SSCTable OBJECT-TYPE
   SYNTAX      SEQUENCE OF Pr1645v2LineD7Entry
   MAX-ACCESS  not-accessible
   STATUS      current
   DESCRIPTION
      "d7Line"
   ::= {pr1645v2LineD7 1}

pr1645v2LineD7Entry OBJECT-TYPE
   SYNTAX      Pr1645v2LineD7Entry
   MAX-ACCESS  not-accessible
   STATUS      current
   DESCRIPTION
      ""
   INDEX      { pr1645v2LineD7GlobalIx,
                pr1645v2LineD7TableIx }
   ::= {pr1645v2LineD7SSCTable 1}

Pr1645v2LineD7Entry ::=
   SEQUENCE
      {
      pr1645v2LineD7GlobalIx
         GlobalIndex,
      pr1645v2LineD7TableIx
         TableIndex,
      pr1645v2LineD7SysUpTime
         TimeTicks,
      pr1645v2LineD7LDownCnt
         Counter32,
      pr1645v2LineD7LDownTme
         TimeTicks,
      pr1645v2LineD7UsSpdMin
         Integer32,
      pr1645v2LineD7UsSpdAvrg
         Integer32,
      pr1645v2LineD7UsSpdMax
         Integer32,
      pr1645v2LineD7DsSpdMin
         Integer32,
      pr1645v2LineD7DsSpdAvrg
         Integer32,
      pr1645v2LineD7DsSpdMax
         Integer32
      }

pr1645v2LineD7GlobalIx OBJECT-TYPE
   SYNTAX      GlobalIndex
   MAX-ACCESS  not-accessible
   STATUS      current
   DESCRIPTION
      "The value of the tlsCntTreeGlobalIndex of the MANAGED OBJECT."
   ::= {pr1645v2LineD7Entry 10}

pr1645v2LineD7TableIx OBJECT-TYPE
   SYNTAX      TableIndex
   MAX-ACCESS  not-accessible
   STATUS      current
   DESCRIPTION
      ""
   ::= {pr1645v2LineD7Entry 11}

pr1645v2LineD7SysUpTime OBJECT-TYPE
   SYNTAX      TimeTicks
   MAX-ACCESS  read-only
   STATUS      current
   DESCRIPTION
      "Path: line.performance.d7Line.sysUpTime

       Time in centi-second."
   ::= {pr1645v2LineD7Entry 16777216}

pr1645v2LineD7LDownCnt OBJECT-TYPE
   SYNTAX      Counter32
   MAX-ACCESS  read-only
   STATUS      current
   DESCRIPTION
      "Path: line.performance.d7Line.linkDownCount

       32 bit unsigned wrappable counter."
   ::= {pr1645v2LineD7Entry 33554432}

pr1645v2LineD7LDownTme OBJECT-TYPE
   SYNTAX      TimeTicks
   MAX-ACCESS  read-only
   STATUS      current
   DESCRIPTION
      "Path: line.performance.d7Line.linkDownTime

       Time in centi-second."
   ::= {pr1645v2LineD7Entry 50331648}

pr1645v2LineD7UsSpdMin OBJECT-TYPE
   SYNTAX      Integer32
   MAX-ACCESS  read-only
   STATUS      current
   DESCRIPTION
      "Path: line.performance.d7Line.usSpeedMin

       formula = 32000 * ; 32000 /"
   ::= {pr1645v2LineD7Entry 67108864}

pr1645v2LineD7UsSpdAvrg OBJECT-TYPE
   SYNTAX      Integer32
   MAX-ACCESS  read-only
   STATUS      current
   DESCRIPTION
      "Path: line.performance.d7Line.usSpeedAvrg

       formula = 32000 * ; 32000 /"
   ::= {pr1645v2LineD7Entry 83886080}

pr1645v2LineD7UsSpdMax OBJECT-TYPE
   SYNTAX      Integer32
   MAX-ACCESS  read-only
   STATUS      current
   DESCRIPTION
      "Path: line.performance.d7Line.usSpeedMax

       formula = 32000 * ; 32000 /"
   ::= {pr1645v2LineD7Entry 100663296}

pr1645v2LineD7DsSpdMin OBJECT-TYPE
   SYNTAX      Integer32
   MAX-ACCESS  read-only
   STATUS      current
   DESCRIPTION
      "Path: line.performance.d7Line.dsSpeedMin

       formula = 32000 * ; 32000 /"
   ::= {pr1645v2LineD7Entry 117440512}

pr1645v2LineD7DsSpdAvrg OBJECT-TYPE
   SYNTAX      Integer32
   MAX-ACCESS  read-only
   STATUS      current
   DESCRIPTION
      "Path: line.performance.d7Line.dsSpeedAvrg

       formula = 32000 * ; 32000 /"
   ::= {pr1645v2LineD7Entry 134217728}

pr1645v2LineD7DsSpdMax OBJECT-TYPE
   SYNTAX      Integer32
   MAX-ACCESS  read-only
   STATUS      current
   DESCRIPTION
      "Path: line.performance.d7Line.dsSpeedMax

       formula = 32000 * ; 32000 /"
   ::= {pr1645v2LineD7Entry 150994944}


pr1645v2LineRel OBJECT IDENTIFIER ::= {pr1645v2Line 30}

pr1645v2LineRelSSCTable OBJECT-TYPE
   SYNTAX      SEQUENCE OF Pr1645v2LineRelEntry
   MAX-ACCESS  not-accessible
   STATUS      current
   DESCRIPTION
      "relLine"
   ::= {pr1645v2LineRel 1}

pr1645v2LineRelEntry OBJECT-TYPE
   SYNTAX      Pr1645v2LineRelEntry
   MAX-ACCESS  not-accessible
   STATUS      current
   DESCRIPTION
      ""
   INDEX      { pr1645v2LineRelGlobalIx }
   ::= {pr1645v2LineRelSSCTable 1}

Pr1645v2LineRelEntry ::=
   SEQUENCE
      {
      pr1645v2LineRelGlobalIx
         GlobalIndex,
      pr1645v2LineRelLDownCnt
         Counter32,
      pr1645v2LineRelLDownTme
         TimeTicks
      }

pr1645v2LineRelGlobalIx OBJECT-TYPE
   SYNTAX      GlobalIndex
   MAX-ACCESS  not-accessible
   STATUS      current
   DESCRIPTION
      "The value of the tlsCntTreeGlobalIndex of the MANAGED OBJECT."
   ::= {pr1645v2LineRelEntry 10}

pr1645v2LineRelLDownCnt OBJECT-TYPE
   SYNTAX      Counter32
   MAX-ACCESS  read-only
   STATUS      current
   DESCRIPTION
      "Path: line.performance.line.linkDownCount

       32 bit unsigned wrappable counter."
   ::= {pr1645v2LineRelEntry 16777216}

pr1645v2LineRelLDownTme OBJECT-TYPE
   SYNTAX      TimeTicks
   MAX-ACCESS  read-only
   STATUS      current
   DESCRIPTION
      "Path: line.performance.line.linkDownTime

       Time in centi-second."
   ::= {pr1645v2LineRelEntry 33554432}



fr1645v2Line OBJECT IDENTIFIER ::= {r1645v2Line 13}


fr1645v2LineAlInfo OBJECT IDENTIFIER ::= {fr1645v2Line 207}

fr1645v2LineAlInfoSSCTable OBJECT-TYPE
   SYNTAX      SEQUENCE OF Fr1645v2LineAlInfoEntry
   MAX-ACCESS  not-accessible
   STATUS      current
   DESCRIPTION
      "lineAlarmInfo"
   ::= {fr1645v2LineAlInfo 1}

fr1645v2LineAlInfoEntry OBJECT-TYPE
   SYNTAX      Fr1645v2LineAlInfoEntry
   MAX-ACCESS  not-accessible
   STATUS      current
   DESCRIPTION
      ""
   INDEX      { fr1645v2LineAlInfoGlobalIx }
   ::= {fr1645v2LineAlInfoSSCTable 1}

Fr1645v2LineAlInfoEntry ::=
   SEQUENCE
      {
      fr1645v2LineAlInfoGlobalIx
         GlobalIndex,
      fr1645v2LineAlInfoDiscr
         Integer32,
      fr1645v2LineAlInfoCurrAlms
         Integer32,
      fr1645v2LineAlInfoPrevAlms
         Integer32,
      fr1645v2LineAlInfoAlMask
         Integer32,
      fr1645v2LineAlInfoAlLvlLnkDwn
         Integer32
      }

fr1645v2LineAlInfoGlobalIx OBJECT-TYPE
   SYNTAX      GlobalIndex
   MAX-ACCESS  not-accessible
   STATUS      current
   DESCRIPTION
      "The value of the tlsCntTreeGlobalIndex of the MANAGED OBJECT."
   ::= {fr1645v2LineAlInfoEntry 10}

fr1645v2LineAlInfoDiscr OBJECT-TYPE
   SYNTAX      Integer32
   MAX-ACCESS  read-only
   STATUS      current
   DESCRIPTION
      "Path: line.alarms.alarmInfo.discriminator"
   ::= {fr1645v2LineAlInfoEntry 16777216}

fr1645v2LineAlInfoCurrAlms OBJECT-TYPE
   SYNTAX      Integer32
   MAX-ACCESS  read-only
   STATUS      current
   DESCRIPTION
      "Path: line.alarms.alarmInfo.currentAlarms

       Bit meanings:
               bit 0 = linkDown"
   ::= {fr1645v2LineAlInfoEntry 33554432}

fr1645v2LineAlInfoPrevAlms OBJECT-TYPE
   SYNTAX      Integer32
   MAX-ACCESS  read-only
   STATUS      current
   DESCRIPTION
      "Path: line.alarms.alarmInfo.previousAlarms

       Bit meanings:
               bit 0 = linkDown"
   ::= {fr1645v2LineAlInfoEntry 50331648}

fr1645v2LineAlInfoAlMask OBJECT-TYPE
   SYNTAX      Integer32
   MAX-ACCESS  read-only
   STATUS      current
   DESCRIPTION
      "Path: line.alarms.alarmInfo.alarmMask

       Bit meanings:
               bit 0 = linkDown"
   ::= {fr1645v2LineAlInfoEntry 67108864}

fr1645v2LineAlInfoAlLvlLnkDwn OBJECT-TYPE
   SYNTAX      Integer32
   MAX-ACCESS  read-only
   STATUS      current
   DESCRIPTION
      "Path: line.alarms.alarmInfo.alarmLevel.linkDown"
   ::= {fr1645v2LineAlInfoEntry 83951616}


fr1645v2LineAlInfoE2 OBJECT IDENTIFIER ::= {fr1645v2LineAlInfo 2}

fr1645v2LineAlInfoE2Entry OBJECT IDENTIFIER ::= {fr1645v2LineAlInfoE2 1}

fr1645v2LineAlInfoE2LnkDwn OBJECT IDENTIFIER ::= {fr1645v2LineAlInfoE2Entry 10}

fr1645v2LineAlInfoE2LnkDwnPfx OBJECT IDENTIFIER ::= {fr1645v2LineAlInfoE2LnkDwn 0}

fr1645v2LineAlInfoE2LnkDwnOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'mtGFastLine'
                (root='router1645') has changed from the ON to the OFF state."
   ::= {fr1645v2LineAlInfoE2LnkDwnPfx 1}

fr1645v2LineAlInfoE2LnkDwnOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'mtGFastLine'
                (root='router1645') has changed from the OFF to the ON state."
   ::= {fr1645v2LineAlInfoE2LnkDwnPfx 2}



ar1645v2Line OBJECT IDENTIFIER ::= {r1645v2Line 16}


ar1645v2LineClearCounters OBJECT IDENTIFIER ::= {ar1645v2Line 263}

ar1645v2LineClearCountersTable OBJECT-TYPE
   SYNTAX      SEQUENCE OF Ar1645v2LineClearCountersEntry
   MAX-ACCESS  not-accessible
   STATUS      current
   DESCRIPTION
      "reset counters"
   ::= {ar1645v2LineClearCounters 1}

ar1645v2LineClearCountersEntry OBJECT-TYPE
   SYNTAX      Ar1645v2LineClearCountersEntry
   MAX-ACCESS  not-accessible
   STATUS      current
   DESCRIPTION
      ""
   INDEX      { ar1645v2LineClearCountersGlobalIx }
   ::= {ar1645v2LineClearCountersTable 1}

Ar1645v2LineClearCountersEntry ::=
   SEQUENCE
      {
      ar1645v2LineClearCountersGlobalIx
         GlobalIndex,
      ar1645v2LineClearCountersValue
         Integer32
      }

ar1645v2LineClearCountersGlobalIx OBJECT-TYPE
   SYNTAX      GlobalIndex
   MAX-ACCESS  not-accessible
   STATUS      current
   DESCRIPTION
      "The value of the tlsCntTreeGlobalIndex of the MANAGED OBJECT."
   ::= {ar1645v2LineClearCountersEntry 10}

ar1645v2LineClearCountersValue OBJECT-TYPE
   SYNTAX      Integer32
   MAX-ACCESS  read-write
   STATUS      current
   DESCRIPTION
      "Path: line.actions.clearCounters"
   ::= {ar1645v2LineClearCountersEntry 2147483648}



END
