OneAccess-R1646v2-4735-EthPortSwIXt2 DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2EthPortSwIXt2 OBJECT IDENTIFIER ::= {r1646Rootv2 4735}

r1646v2EthPortSwIXt2MOProp OBJECT-TYPE
   SYNTAX      SEQUENCE OF R1646v2EthPortSwIXt2MOPropEntry
   MAX-ACCESS  not-accessible
   STATUS      current
   DESCRIPTION
      ""
   ::= {r1646v2EthPortSwIXt2 1}

r1646v2EthPortSwIXt2MOPropEntry OBJECT-TYPE
   SYNTAX      R1646v2EthPortSwIXt2MOPropEntry
   MAX-ACCESS  not-accessible
   STATUS      current
   DESCRIPTION
      ""
   INDEX      { r1646v2EthPortSwIXt2MOPropGlobalIx }
   ::= {r1646v2EthPortSwIXt2MOProp 1}

R1646v2EthPortSwIXt2MOPropEntry ::=
   SEQUENCE
      {
      r1646v2EthPortSwIXt2MOPropPath
         ContainmentPath,
      r1646v2EthPortSwIXt2MOPropRev
         ObjectRevision,
      r1646v2EthPortSwIXt2MOPropGlobalIx
         GlobalIndex
      }

r1646v2EthPortSwIXt2MOPropPath OBJECT-TYPE
   SYNTAX      ContainmentPath
   MAX-ACCESS  read-only
   STATUS      current
   DESCRIPTION
      "Textual description of the containment tree from the instance of
       the root object down to the instance of the current object."
   ::= {r1646v2EthPortSwIXt2MOPropEntry 3}

r1646v2EthPortSwIXt2MOPropRev OBJECT-TYPE
   SYNTAX      ObjectRevision
   MAX-ACCESS  read-only
   STATUS      current
   DESCRIPTION
      "This value corresponds with the revision of the MANAGED OBJECT."
   ::= {r1646v2EthPortSwIXt2MOPropEntry 4}

r1646v2EthPortSwIXt2MOPropGlobalIx OBJECT-TYPE
   SYNTAX      GlobalIndex
   MAX-ACCESS  read-only
   STATUS      current
   DESCRIPTION
      "The value of the tlsCntTreeGlobalIndex of the MANAGED OBJECT."
   ::= {r1646v2EthPortSwIXt2MOPropEntry 10}



er1646v2EthPortSwIXt2 OBJECT IDENTIFIER ::= {r1646v2EthPortSwIXt2 11}


er1646v2EthPortSwIXt2Remark OBJECT IDENTIFIER ::= {er1646v2EthPortSwIXt2 321}

er1646v2EthPortSwIXt2RemarkTable OBJECT-TYPE
   SYNTAX      SEQUENCE OF Er1646v2EthPortSwIXt2RemarkEntry
   MAX-ACCESS  not-accessible
   STATUS      current
   DESCRIPTION
      "intfRemark"
   ::= {er1646v2EthPortSwIXt2Remark 1}

er1646v2EthPortSwIXt2RemarkEntry OBJECT-TYPE
   SYNTAX      Er1646v2EthPortSwIXt2RemarkEntry
   MAX-ACCESS  not-accessible
   STATUS      current
   DESCRIPTION
      ""
   INDEX      { er1646v2EthPortSwIXt2RemarkGlobalIx }
   ::= {er1646v2EthPortSwIXt2RemarkTable 1}

Er1646v2EthPortSwIXt2RemarkEntry ::=
   SEQUENCE
      {
      er1646v2EthPortSwIXt2RemarkGlobalIx
         GlobalIndex,
      er1646v2EthPortSwIXt2RemarkValue
         DisplayString
      }

er1646v2EthPortSwIXt2RemarkGlobalIx OBJECT-TYPE
   SYNTAX      GlobalIndex
   MAX-ACCESS  not-accessible
   STATUS      current
   DESCRIPTION
      "The value of the tlsCntTreeGlobalIndex of the MANAGED OBJECT."
   ::= {er1646v2EthPortSwIXt2RemarkEntry 10}

er1646v2EthPortSwIXt2RemarkValue OBJECT-TYPE
   SYNTAX      DisplayString
   MAX-ACCESS  read-write
   STATUS      current
   DESCRIPTION
      "Path: swPort.editConf.remark"
   ::= {er1646v2EthPortSwIXt2RemarkEntry 2147483648}


er1646v2EthPortSwIXt2Arp OBJECT IDENTIFIER ::= {er1646v2EthPortSwIXt2 19}

er1646v2EthPortSwIXt2ArpSSCTable OBJECT-TYPE
   SYNTAX      SEQUENCE OF Er1646v2EthPortSwIXt2ArpEntry
   MAX-ACCESS  not-accessible
   STATUS      current
   DESCRIPTION
      "ethernet related config parameters"
   ::= {er1646v2EthPortSwIXt2Arp 1}

er1646v2EthPortSwIXt2ArpEntry OBJECT-TYPE
   SYNTAX      Er1646v2EthPortSwIXt2ArpEntry
   MAX-ACCESS  not-accessible
   STATUS      current
   DESCRIPTION
      ""
   INDEX      { er1646v2EthPortSwIXt2ArpGlobalIx }
   ::= {er1646v2EthPortSwIXt2ArpSSCTable 1}

Er1646v2EthPortSwIXt2ArpEntry ::=
   SEQUENCE
      {
      er1646v2EthPortSwIXt2ArpGlobalIx
         GlobalIndex,
      er1646v2EthPortSwIXt2ArpTimeOut
         TimeTicks,
      er1646v2EthPortSwIXt2ArpProxyArp
         INTEGER
      }

er1646v2EthPortSwIXt2ArpGlobalIx OBJECT-TYPE
   SYNTAX      GlobalIndex
   MAX-ACCESS  not-accessible
   STATUS      current
   DESCRIPTION
      "The value of the tlsCntTreeGlobalIndex of the MANAGED OBJECT."
   ::= {er1646v2EthPortSwIXt2ArpEntry 10}

er1646v2EthPortSwIXt2ArpTimeOut OBJECT-TYPE
   SYNTAX      TimeTicks
   MAX-ACCESS  read-write
   STATUS      current
   DESCRIPTION
      "Path: swPort.editConf.arp.timeOut

       Time in centi-second."
   ::= {er1646v2EthPortSwIXt2ArpEntry 201326592}

er1646v2EthPortSwIXt2ArpProxyArp OBJECT-TYPE
   SYNTAX      INTEGER
               {
               disabled (0),
               enabled (1)
               }
   MAX-ACCESS  read-write
   STATUS      current
   DESCRIPTION
      "Path: swPort.editConf.arp.proxyArp

       Possibilities:
               disabled   (0)
               enabled   (1)"
   ::= {er1646v2EthPortSwIXt2ArpEntry 838860800}

er1646v2EthPortSwIXt2ArpStaticArp OBJECT-TYPE
   SYNTAX      SEQUENCE OF Er1646v2EthPortSwIXt2ArpStaticArpEntry
   MAX-ACCESS  not-accessible
   STATUS      current
   DESCRIPTION
      ""
   ::= {er1646v2EthPortSwIXt2Arp 50331648}

er1646v2EthPortSwIXt2ArpStaticArpEntry OBJECT-TYPE
   SYNTAX      Er1646v2EthPortSwIXt2ArpStaticArpEntry
   MAX-ACCESS  not-accessible
   STATUS      current
   DESCRIPTION
      ""
   INDEX      { er1646v2EthPortSwIXt2ArpStaticArpGlobalIx,
                er1646v2EthPortSwIXt2ArpStaticArpTableIx }
   ::= {er1646v2EthPortSwIXt2ArpStaticArp 1}

Er1646v2EthPortSwIXt2ArpStaticArpEntry ::=
   SEQUENCE
      {
      er1646v2EthPortSwIXt2ArpStaticArpActions
         VariableLengthTableActions,
      er1646v2EthPortSwIXt2ArpStaticArpGlobalIx
         GlobalIndex,
      er1646v2EthPortSwIXt2ArpStaticArpTableIx
         TableIndex,
      er1646v2EthPortSwIXt2ArpStaticArpMacAddress
         OCTET STRING,
      er1646v2EthPortSwIXt2ArpStaticArpIpAddress
         IpAddress
      }

er1646v2EthPortSwIXt2ArpStaticArpActions OBJECT-TYPE
   SYNTAX      VariableLengthTableActions
   MAX-ACCESS  read-write
   STATUS      current
   DESCRIPTION
      "By way of this field, some manipulations
       on this table may be performed."
   ::= {er1646v2EthPortSwIXt2ArpStaticArpEntry 2}

er1646v2EthPortSwIXt2ArpStaticArpGlobalIx OBJECT-TYPE
   SYNTAX      GlobalIndex
   MAX-ACCESS  not-accessible
   STATUS      current
   DESCRIPTION
      "The value of the tlsCntTreeGlobalIndex of the MANAGED OBJECT."
   ::= {er1646v2EthPortSwIXt2ArpStaticArpEntry 10}

er1646v2EthPortSwIXt2ArpStaticArpTableIx OBJECT-TYPE
   SYNTAX      TableIndex
   MAX-ACCESS  not-accessible
   STATUS      current
   DESCRIPTION
      ""
   ::= {er1646v2EthPortSwIXt2ArpStaticArpEntry 11}

er1646v2EthPortSwIXt2ArpStaticArpMacAddress OBJECT-TYPE
   SYNTAX      OCTET STRING
   MAX-ACCESS  read-write
   STATUS      current
   DESCRIPTION
      "Path: swPort.editConf.arp.staticArp.macAddress

       MAC address."
   ::= {er1646v2EthPortSwIXt2ArpStaticArpEntry 16777216}

er1646v2EthPortSwIXt2ArpStaticArpIpAddress OBJECT-TYPE
   SYNTAX      IpAddress
   MAX-ACCESS  read-write
   STATUS      current
   DESCRIPTION
      "Path: swPort.editConf.arp.staticArp.ipAddress"
   ::= {er1646v2EthPortSwIXt2ArpStaticArpEntry 33554432}


er1646v2EthPortSwIXt2BrC OBJECT IDENTIFIER ::= {er1646v2EthPortSwIXt2 27}

er1646v2EthPortSwIXt2BrCSSCTable OBJECT-TYPE
   SYNTAX      SEQUENCE OF Er1646v2EthPortSwIXt2BrCEntry
   MAX-ACCESS  not-accessible
   STATUS      current
   DESCRIPTION
      "Set bridging parameters"
   ::= {er1646v2EthPortSwIXt2BrC 1}

er1646v2EthPortSwIXt2BrCEntry OBJECT-TYPE
   SYNTAX      Er1646v2EthPortSwIXt2BrCEntry
   MAX-ACCESS  not-accessible
   STATUS      current
   DESCRIPTION
      ""
   INDEX      { er1646v2EthPortSwIXt2BrCGlobalIx }
   ::= {er1646v2EthPortSwIXt2BrCSSCTable 1}

Er1646v2EthPortSwIXt2BrCEntry ::=
   SEQUENCE
      {
      er1646v2EthPortSwIXt2BrCGlobalIx
         GlobalIndex,
      er1646v2EthPortSwIXt2BrCAccessList
         DisplayString,
      er1646v2EthPortSwIXt2BrCInAccessList
         DisplayString,
      er1646v2EthPortSwIXt2BrCTp
         DisplayString,
      er1646v2EthPortSwIXt2BrCBridgeGroup
         DisplayString,
      er1646v2EthPortSwIXt2BrCLimBC
         INTEGER,
      er1646v2EthPortSwIXt2BrCPrivateMode
         INTEGER,
      er1646v2EthPortSwIXt2BrCLearning
         INTEGER,
      er1646v2EthPortSwIXt2BrCMaxCacheSize
         INTEGER,
      er1646v2EthPortSwIXt2BrCRelearnDropOnRelearn
         INTEGER,
      er1646v2EthPortSwIXt2BrCRelearnShutdownThreshold
         Integer32,
      er1646v2EthPortSwIXt2BrCRelearnShutdownTime
         TimeTicks,
      er1646v2EthPortSwIXt2BrCRelearnLoopDetection
         INTEGER,
      er1646v2EthPortSwIXt2BrCRelearnLoopDetectionInterval
         TimeTicks,
      er1646v2EthPortSwIXt2BrCVlanMemberShip
         INTEGER,
      er1646v2EthPortSwIXt2BrCDot1adType
         INTEGER,
      er1646v2EthPortSwIXt2BrCPriority
         Integer32,
      er1646v2EthPortSwIXt2BrCPathCost
         Integer32,
      er1646v2EthPortSwIXt2BrCInternalPathCost
         Integer32,
      er1646v2EthPortSwIXt2BrCTCD
         INTEGER,
      er1646v2EthPortSwIXt2BrCRestrictedRole
         INTEGER,
      er1646v2EthPortSwIXt2BrCAdminEdge
         INTEGER,
      er1646v2EthPortSwIXt2BrCMgmtInline
         INTEGER,
      er1646v2EthPortSwIXt2BrCL2ptMode
         INTEGER,
      er1646v2EthPortSwIXt2BrCL2ptProtocols
         Integer32,
      er1646v2EthPortSwIXt2BrCL2ptDestMac
         OCTET STRING,
      er1646v2EthPortSwIXt2BrCL2ptCos
         INTEGER,
      er1646v2EthPortSwIXt2BrCL2ptDropThrStp
         INTEGER,
      er1646v2EthPortSwIXt2BrCL2ptDropThrLldp
         INTEGER,
      er1646v2EthPortSwIXt2BrCL2ptDropThrOam
         INTEGER,
      er1646v2EthPortSwIXt2BrCL2ptDropThrCdp
         INTEGER,
      er1646v2EthPortSwIXt2BrCL2ptDropThrVtp
         INTEGER,
      er1646v2EthPortSwIXt2BrCL2ptDropThrLacp
         INTEGER,
      er1646v2EthPortSwIXt2BrCL2ptDropThrEfmOam
         INTEGER,
      er1646v2EthPortSwIXt2BrCL2ptDropThrPvst
         INTEGER,
      er1646v2EthPortSwIXt2BrCL2ptDropThrMmrp
         INTEGER,
      er1646v2EthPortSwIXt2BrCL2ptDropThrMvrp
         INTEGER,
      er1646v2EthPortSwIXt2BrCL2ptDropThrGvrp
         INTEGER,
      er1646v2EthPortSwIXt2BrCL2ptDropThrGmrp
         INTEGER,
      er1646v2EthPortSwIXt2BrCL2ptDropThrDtp
         INTEGER,
      er1646v2EthPortSwIXt2BrCL2ptDropThrPagp
         INTEGER,
      er1646v2EthPortSwIXt2BrCL2ptDropThrUdld
         INTEGER
      }

er1646v2EthPortSwIXt2BrCGlobalIx OBJECT-TYPE
   SYNTAX      GlobalIndex
   MAX-ACCESS  not-accessible
   STATUS      current
   DESCRIPTION
      "The value of the tlsCntTreeGlobalIndex of the MANAGED OBJECT."
   ::= {er1646v2EthPortSwIXt2BrCEntry 10}

er1646v2EthPortSwIXt2BrCAccessList OBJECT-TYPE
   SYNTAX      DisplayString
   MAX-ACCESS  read-write
   STATUS      current
   DESCRIPTION
      "Path: swPort.editConf.bridging.accessList"
   ::= {er1646v2EthPortSwIXt2BrCEntry 83886080}

er1646v2EthPortSwIXt2BrCInAccessList OBJECT-TYPE
   SYNTAX      DisplayString
   MAX-ACCESS  read-write
   STATUS      current
   DESCRIPTION
      "Path: swPort.editConf.bridging.inAccessList"
   ::= {er1646v2EthPortSwIXt2BrCEntry 251658240}

er1646v2EthPortSwIXt2BrCTp OBJECT-TYPE
   SYNTAX      DisplayString
   MAX-ACCESS  read-write
   STATUS      current
   DESCRIPTION
      "Path: swPort.editConf.bridging.trafficPolicy"
   ::= {er1646v2EthPortSwIXt2BrCEntry 100663296}

er1646v2EthPortSwIXt2BrCBridgeGroup OBJECT-TYPE
   SYNTAX      DisplayString
   MAX-ACCESS  read-write
   STATUS      current
   DESCRIPTION
      "Path: swPort.editConf.bridging.bridgeGroup"
   ::= {er1646v2EthPortSwIXt2BrCEntry 117440512}

er1646v2EthPortSwIXt2BrCLimBC OBJECT-TYPE
   SYNTAX      INTEGER
               {
               disabled (0),
               enabled (1)
               }
   MAX-ACCESS  read-write
   STATUS      current
   DESCRIPTION
      "Path: swPort.editConf.bridging.limitBroadcasts

       Possibilities:
               disabled   (0)
               enabled   (1)"
   ::= {er1646v2EthPortSwIXt2BrCEntry 134217728}

er1646v2EthPortSwIXt2BrCPrivateMode OBJECT-TYPE
   SYNTAX      INTEGER
               {
               disabled (0),
               enabled (1)
               }
   MAX-ACCESS  read-write
   STATUS      current
   DESCRIPTION
      "Path: swPort.editConf.bridging.privateMode

       Possibilities:
               disabled   (0)
               enabled   (1)"
   ::= {er1646v2EthPortSwIXt2BrCEntry 419430400}

er1646v2EthPortSwIXt2BrCLearning OBJECT-TYPE
   SYNTAX      INTEGER
               {
               disabled (0),
               enabled (1)
               }
   MAX-ACCESS  read-write
   STATUS      current
   DESCRIPTION
      "Path: swPort.editConf.bridging.learning

       Possibilities:
               disabled   (0)
               enabled   (1)"
   ::= {er1646v2EthPortSwIXt2BrCEntry 201326592}

er1646v2EthPortSwIXt2BrCMaxCacheSize OBJECT-TYPE
   SYNTAX      INTEGER
               {
               unlimited (0)
               }
   MAX-ACCESS  read-write
   STATUS      current
   DESCRIPTION
      "Path: swPort.editConf.bridging.maxCacheSize

       Possibilities:
               unlimited   (0)"
   ::= {er1646v2EthPortSwIXt2BrCEntry 218103808}

er1646v2EthPortSwIXt2BrCRelearnDropOnRelearn OBJECT-TYPE
   SYNTAX      INTEGER
               {
               disabled (0),
               enabled (1)
               }
   MAX-ACCESS  read-write
   STATUS      current
   DESCRIPTION
      "Path: swPort.editConf.bridging.relearn.dropOnRelearn

       Possibilities:
               disabled   (0)
               enabled   (1)"
   ::= {er1646v2EthPortSwIXt2BrCEntry 234946560}

er1646v2EthPortSwIXt2BrCRelearnShutdownThreshold OBJECT-TYPE
   SYNTAX      Integer32
   MAX-ACCESS  read-write
   STATUS      current
   DESCRIPTION
      "Path: swPort.editConf.bridging.relearn.shutdownThreshold"
   ::= {er1646v2EthPortSwIXt2BrCEntry 235012096}

er1646v2EthPortSwIXt2BrCRelearnShutdownTime OBJECT-TYPE
   SYNTAX      TimeTicks
   MAX-ACCESS  read-write
   STATUS      current
   DESCRIPTION
      "Path: swPort.editConf.bridging.relearn.shutdownTime

       Time in centi-second."
   ::= {er1646v2EthPortSwIXt2BrCEntry 235077632}

er1646v2EthPortSwIXt2BrCRelearnLoopDetection OBJECT-TYPE
   SYNTAX      INTEGER
               {
               disabled (0),
               passive (1),
               active (2)
               }
   MAX-ACCESS  read-write
   STATUS      current
   DESCRIPTION
      "Path: swPort.editConf.bridging.relearn.loopDetection

       Possibilities:
               disabled   (0)
               passive   (1)
               active   (2)"
   ::= {er1646v2EthPortSwIXt2BrCEntry 235143168}

er1646v2EthPortSwIXt2BrCRelearnLoopDetectionInterval OBJECT-TYPE
   SYNTAX      TimeTicks
   MAX-ACCESS  read-write
   STATUS      current
   DESCRIPTION
      "Path: swPort.editConf.bridging.relearn.loopDetectionInterval

       Time in centi-second."
   ::= {er1646v2EthPortSwIXt2BrCEntry 235208704}

er1646v2EthPortSwIXt2BrCVlanMemberShip OBJECT-TYPE
   SYNTAX      INTEGER
               {
               all (0),
               none (1),
               grouped (2)
               }
   MAX-ACCESS  read-write
   STATUS      current
   DESCRIPTION
      "Path: swPort.editConf.bridging.vlanMemberShip

       Possibilities:
               all   (0)
               none   (1)
               grouped   (2)"
   ::= {er1646v2EthPortSwIXt2BrCEntry 318767104}

er1646v2EthPortSwIXt2BrCDot1adType OBJECT-TYPE
   SYNTAX      INTEGER
               {
               slOPTg (0),
               cPort (4),
               sPort (1),
               nni (2)
               }
   MAX-ACCESS  read-write
   STATUS      current
   DESCRIPTION
      "Path: swPort.editConf.bridging.dot1ad.type

       Possibilities:
               <OPT>   (0)
               cPort   (4)
               sPort   (1)
               nni   (2)"
   ::= {er1646v2EthPortSwIXt2BrCEntry 503382016}

er1646v2EthPortSwIXt2BrCPriority OBJECT-TYPE
   SYNTAX      Integer32
   MAX-ACCESS  read-write
   STATUS      current
   DESCRIPTION
      "Path: swPort.editConf.bridging.priority"
   ::= {er1646v2EthPortSwIXt2BrCEntry 33554432}

er1646v2EthPortSwIXt2BrCPathCost OBJECT-TYPE
   SYNTAX      Integer32
   MAX-ACCESS  read-write
   STATUS      current
   DESCRIPTION
      "Path: swPort.editConf.bridging.pathCost"
   ::= {er1646v2EthPortSwIXt2BrCEntry 50331648}

er1646v2EthPortSwIXt2BrCInternalPathCost OBJECT-TYPE
   SYNTAX      Integer32
   MAX-ACCESS  read-write
   STATUS      current
   DESCRIPTION
      "Path: swPort.editConf.bridging.internalPathCost"
   ::= {er1646v2EthPortSwIXt2BrCEntry 301989888}

er1646v2EthPortSwIXt2BrCTCD OBJECT-TYPE
   SYNTAX      INTEGER
               {
               disabled (0),
               enabled (1)
               }
   MAX-ACCESS  read-write
   STATUS      current
   DESCRIPTION
      "Path: swPort.editConf.bridging.topologyChangeDetection

       Possibilities:
               disabled   (0)
               enabled   (1)"
   ::= {er1646v2EthPortSwIXt2BrCEntry 67108864}

er1646v2EthPortSwIXt2BrCRestrictedRole OBJECT-TYPE
   SYNTAX      INTEGER
               {
               disabled (0),
               enabled (1)
               }
   MAX-ACCESS  read-write
   STATUS      current
   DESCRIPTION
      "Path: swPort.editConf.bridging.restrictedRole

       Possibilities:
               disabled   (0)
               enabled   (1)"
   ::= {er1646v2EthPortSwIXt2BrCEntry 335544320}

er1646v2EthPortSwIXt2BrCAdminEdge OBJECT-TYPE
   SYNTAX      INTEGER
               {
               disabled (0),
               enabled (1)
               }
   MAX-ACCESS  read-write
   STATUS      current
   DESCRIPTION
      "Path: swPort.editConf.bridging.adminEdge

       Possibilities:
               disabled   (0)
               enabled   (1)"
   ::= {er1646v2EthPortSwIXt2BrCEntry 268435456}

er1646v2EthPortSwIXt2BrCMgmtInline OBJECT-TYPE
   SYNTAX      INTEGER
               {
               disabled (0),
               enabled (1)
               }
   MAX-ACCESS  read-write
   STATUS      current
   DESCRIPTION
      "Path: swPort.editConf.bridging.mgmtInline

       Possibilities:
               disabled   (0)
               enabled   (1)"
   ::= {er1646v2EthPortSwIXt2BrCEntry 369098752}

er1646v2EthPortSwIXt2BrCL2ptMode OBJECT-TYPE
   SYNTAX      INTEGER
               {
               disabled (0),
               enabled (1)
               }
   MAX-ACCESS  read-write
   STATUS      current
   DESCRIPTION
      "Path: swPort.editConf.bridging.l2ProtTunnel.mode

       Possibilities:
               disabled   (0)
               enabled   (1)"
   ::= {er1646v2EthPortSwIXt2BrCEntry 403701760}

er1646v2EthPortSwIXt2BrCL2ptProtocols OBJECT-TYPE
   SYNTAX      Integer32
   MAX-ACCESS  read-write
   STATUS      current
   DESCRIPTION
      "Path: swPort.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2EthPortSwIXt2BrCEntry 404750336}

er1646v2EthPortSwIXt2BrCL2ptDestMac OBJECT-TYPE
   SYNTAX      OCTET STRING
   MAX-ACCESS  read-write
   STATUS      current
   DESCRIPTION
      "Path: swPort.editConf.bridging.l2ProtTunnel.destinationMac

       MAC address."
   ::= {er1646v2EthPortSwIXt2BrCEntry 405798912}

er1646v2EthPortSwIXt2BrCL2ptCos OBJECT-TYPE
   SYNTAX      INTEGER
               {
               unchanged (255)
               }
   MAX-ACCESS  read-write
   STATUS      current
   DESCRIPTION
      "Path: swPort.editConf.bridging.l2ProtTunnel.cos

       Possibilities:
               unchanged   (255)"
   ::= {er1646v2EthPortSwIXt2BrCEntry 406847488}

er1646v2EthPortSwIXt2BrCL2ptDropThrStp OBJECT-TYPE
   SYNTAX      INTEGER
               {
               unlimited (0)
               }
   UNITS       "packets/sec"
   MAX-ACCESS  read-write
   STATUS      current
   DESCRIPTION
      "Path: swPort.editConf.bridging.l2ProtTunnel.dropThresholds.stp

       unit name = packets/sec

       Possibilities:
               unlimited   (0)"
   ::= {er1646v2EthPortSwIXt2BrCEntry 407900160}

er1646v2EthPortSwIXt2BrCL2ptDropThrLldp OBJECT-TYPE
   SYNTAX      INTEGER
               {
               unlimited (0)
               }
   UNITS       "packets/sec"
   MAX-ACCESS  read-write
   STATUS      current
   DESCRIPTION
      "Path: swPort.editConf.bridging.l2ProtTunnel.dropThresholds.lldp

       unit name = packets/sec

       Possibilities:
               unlimited   (0)"
   ::= {er1646v2EthPortSwIXt2BrCEntry 407904256}

er1646v2EthPortSwIXt2BrCL2ptDropThrOam OBJECT-TYPE
   SYNTAX      INTEGER
               {
               unlimited (0)
               }
   UNITS       "packets/sec"
   MAX-ACCESS  read-write
   STATUS      current
   DESCRIPTION
      "Path: swPort.editConf.bridging.l2ProtTunnel.dropThresholds.oam

       unit name = packets/sec

       Possibilities:
               unlimited   (0)"
   ::= {er1646v2EthPortSwIXt2BrCEntry 407908352}

er1646v2EthPortSwIXt2BrCL2ptDropThrCdp OBJECT-TYPE
   SYNTAX      INTEGER
               {
               unlimited (0)
               }
   UNITS       "packets/sec"
   MAX-ACCESS  read-write
   STATUS      current
   DESCRIPTION
      "Path: swPort.editConf.bridging.l2ProtTunnel.dropThresholds.cdp

       unit name = packets/sec

       Possibilities:
               unlimited   (0)"
   ::= {er1646v2EthPortSwIXt2BrCEntry 407912448}

er1646v2EthPortSwIXt2BrCL2ptDropThrVtp OBJECT-TYPE
   SYNTAX      INTEGER
               {
               unlimited (0)
               }
   UNITS       "packets/sec"
   MAX-ACCESS  read-write
   STATUS      current
   DESCRIPTION
      "Path: swPort.editConf.bridging.l2ProtTunnel.dropThresholds.vtp

       unit name = packets/sec

       Possibilities:
               unlimited   (0)"
   ::= {er1646v2EthPortSwIXt2BrCEntry 407916544}

er1646v2EthPortSwIXt2BrCL2ptDropThrLacp OBJECT-TYPE
   SYNTAX      INTEGER
               {
               unlimited (0)
               }
   UNITS       "packets/sec"
   MAX-ACCESS  read-write
   STATUS      current
   DESCRIPTION
      "Path: swPort.editConf.bridging.l2ProtTunnel.dropThresholds.lacp

       unit name = packets/sec

       Possibilities:
               unlimited   (0)"
   ::= {er1646v2EthPortSwIXt2BrCEntry 407920640}

er1646v2EthPortSwIXt2BrCL2ptDropThrEfmOam OBJECT-TYPE
   SYNTAX      INTEGER
               {
               unlimited (0)
               }
   UNITS       "packets/sec"
   MAX-ACCESS  read-write
   STATUS      current
   DESCRIPTION
      "Path: swPort.editConf.bridging.l2ProtTunnel.dropThresholds.efmOam

       unit name = packets/sec

       Possibilities:
               unlimited   (0)"
   ::= {er1646v2EthPortSwIXt2BrCEntry 407924736}

er1646v2EthPortSwIXt2BrCL2ptDropThrPvst OBJECT-TYPE
   SYNTAX      INTEGER
               {
               unlimited (0)
               }
   UNITS       "packets/sec"
   MAX-ACCESS  read-write
   STATUS      current
   DESCRIPTION
      "Path: swPort.editConf.bridging.l2ProtTunnel.dropThresholds.pvst

       unit name = packets/sec

       Possibilities:
               unlimited   (0)"
   ::= {er1646v2EthPortSwIXt2BrCEntry 407928832}

er1646v2EthPortSwIXt2BrCL2ptDropThrMmrp OBJECT-TYPE
   SYNTAX      INTEGER
               {
               unlimited (0)
               }
   UNITS       "packets/sec"
   MAX-ACCESS  read-write
   STATUS      current
   DESCRIPTION
      "Path: swPort.editConf.bridging.l2ProtTunnel.dropThresholds.mmrp

       unit name = packets/sec

       Possibilities:
               unlimited   (0)"
   ::= {er1646v2EthPortSwIXt2BrCEntry 407932928}

er1646v2EthPortSwIXt2BrCL2ptDropThrMvrp OBJECT-TYPE
   SYNTAX      INTEGER
               {
               unlimited (0)
               }
   UNITS       "packets/sec"
   MAX-ACCESS  read-write
   STATUS      current
   DESCRIPTION
      "Path: swPort.editConf.bridging.l2ProtTunnel.dropThresholds.mvrp

       unit name = packets/sec

       Possibilities:
               unlimited   (0)"
   ::= {er1646v2EthPortSwIXt2BrCEntry 407937024}

er1646v2EthPortSwIXt2BrCL2ptDropThrGvrp OBJECT-TYPE
   SYNTAX      INTEGER
               {
               unlimited (0)
               }
   UNITS       "packets/sec"
   MAX-ACCESS  read-write
   STATUS      current
   DESCRIPTION
      "Path: swPort.editConf.bridging.l2ProtTunnel.dropThresholds.gvrp

       unit name = packets/sec

       Possibilities:
               unlimited   (0)"
   ::= {er1646v2EthPortSwIXt2BrCEntry 407941120}

er1646v2EthPortSwIXt2BrCL2ptDropThrGmrp OBJECT-TYPE
   SYNTAX      INTEGER
               {
               unlimited (0)
               }
   UNITS       "packets/sec"
   MAX-ACCESS  read-write
   STATUS      current
   DESCRIPTION
      "Path: swPort.editConf.bridging.l2ProtTunnel.dropThresholds.gmrp

       unit name = packets/sec

       Possibilities:
               unlimited   (0)"
   ::= {er1646v2EthPortSwIXt2BrCEntry 407945216}

er1646v2EthPortSwIXt2BrCL2ptDropThrDtp OBJECT-TYPE
   SYNTAX      INTEGER
               {
               unlimited (0)
               }
   UNITS       "packets/sec"
   MAX-ACCESS  read-write
   STATUS      current
   DESCRIPTION
      "Path: swPort.editConf.bridging.l2ProtTunnel.dropThresholds.dtp

       unit name = packets/sec

       Possibilities:
               unlimited   (0)"
   ::= {er1646v2EthPortSwIXt2BrCEntry 407949312}

er1646v2EthPortSwIXt2BrCL2ptDropThrPagp OBJECT-TYPE
   SYNTAX      INTEGER
               {
               unlimited (0)
               }
   UNITS       "packets/sec"
   MAX-ACCESS  read-write
   STATUS      current
   DESCRIPTION
      "Path: swPort.editConf.bridging.l2ProtTunnel.dropThresholds.pagp

       unit name = packets/sec

       Possibilities:
               unlimited   (0)"
   ::= {er1646v2EthPortSwIXt2BrCEntry 407953408}

er1646v2EthPortSwIXt2BrCL2ptDropThrUdld OBJECT-TYPE
   SYNTAX      INTEGER
               {
               unlimited (0)
               }
   UNITS       "packets/sec"
   MAX-ACCESS  read-write
   STATUS      current
   DESCRIPTION
      "Path: swPort.editConf.bridging.l2ProtTunnel.dropThresholds.udld

       unit name = packets/sec

       Possibilities:
               unlimited   (0)"
   ::= {er1646v2EthPortSwIXt2BrCEntry 407957504}


er1646v2EthPortSwIXt2VlanTagging OBJECT IDENTIFIER ::= {er1646v2EthPortSwIXt2 14}

er1646v2EthPortSwIXt2VlanTaggingSSCTable OBJECT-TYPE
   SYNTAX      SEQUENCE OF Er1646v2EthPortSwIXt2VlanTaggingEntry
   MAX-ACCESS  not-accessible
   STATUS      current
   DESCRIPTION
      "vlan tagging config"
   ::= {er1646v2EthPortSwIXt2VlanTagging 1}

er1646v2EthPortSwIXt2VlanTaggingEntry OBJECT-TYPE
   SYNTAX      Er1646v2EthPortSwIXt2VlanTaggingEntry
   MAX-ACCESS  not-accessible
   STATUS      current
   DESCRIPTION
      ""
   INDEX      { er1646v2EthPortSwIXt2VlanTaggingGlobalIx }
   ::= {er1646v2EthPortSwIXt2VlanTaggingSSCTable 1}

Er1646v2EthPortSwIXt2VlanTaggingEntry ::=
   SEQUENCE
      {
      er1646v2EthPortSwIXt2VlanTaggingGlobalIx
         GlobalIndex,
      er1646v2EthPortSwIXt2VlanTaggingUntaggedAction
         INTEGER,
      er1646v2EthPortSwIXt2VlanTaggingUntaggedTagInfoTpid
         INTEGER,
      er1646v2EthPortSwIXt2VlanTaggingUntaggedTagInfoVid
         Integer32,
      er1646v2EthPortSwIXt2VlanTaggingUnknownVlansAction
         INTEGER,
      er1646v2EthPortSwIXt2VlanTaggingUnknownVlansTagInfoTpid
         INTEGER,
      er1646v2EthPortSwIXt2VlanTaggingUnknownVlansTagInfoVid
         Integer32
      }

er1646v2EthPortSwIXt2VlanTaggingGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanTaggingEntry 10}

er1646v2EthPortSwIXt2VlanTaggingUntaggedAction OBJECT-TYPE
   SYNTAX      INTEGER
               {
               discard (0),
               accept (1),
               tag (2)
               }
   MAX-ACCESS  read-write
   STATUS      current
   DESCRIPTION
      "Path: swPort.editConf.vlanTagging.untagged.action

       Possibilities:
               discard   (0)
               accept   (1)
               tag   (2)"
   ::= {er1646v2EthPortSwIXt2VlanTaggingEntry 671088640}

er1646v2EthPortSwIXt2VlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.untagged.tagInfo.tpid

       Possibilities:
               dot1Q   (33024)
               dot1ad   (34984)
               0x9100   (37120)
               0x9200   (37376)
               0x9300   (37632)"
   ::= {er1646v2EthPortSwIXt2VlanTaggingEntry 746586112}

er1646v2EthPortSwIXt2VlanTaggingUntaggedTagInfoVid OBJECT-TYPE
   SYNTAX      Integer32
   MAX-ACCESS  read-write
   STATUS      current
   DESCRIPTION
      "Path: swPort.editConf.vlanTagging.untagged.tagInfo.vid"
   ::= {er1646v2EthPortSwIXt2VlanTaggingEntry 754974720}

er1646v2EthPortSwIXt2VlanTaggingUnknownVlansAction OBJECT-TYPE
   SYNTAX      INTEGER
               {
               discard (0),
               accept (1),
               tag (2)
               }
   MAX-ACCESS  read-write
   STATUS      current
   DESCRIPTION
      "Path: swPort.editConf.vlanTagging.unknownVlans.action

       Possibilities:
               discard   (0)
               accept   (1)
               tag   (2)"
   ::= {er1646v2EthPortSwIXt2VlanTaggingEntry 1744830464}

er1646v2EthPortSwIXt2VlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.unknownVlans.tagInfo.tpid

       Possibilities:
               dot1Q   (33024)
               dot1ad   (34984)
               0x9100   (37120)
               0x9200   (37376)
               0x9300   (37632)"
   ::= {er1646v2EthPortSwIXt2VlanTaggingEntry 1820327936}

er1646v2EthPortSwIXt2VlanTaggingUnknownVlansTagInfoVid OBJECT-TYPE
   SYNTAX      Integer32
   MAX-ACCESS  read-write
   STATUS      current
   DESCRIPTION
      "Path: swPort.editConf.vlanTagging.unknownVlans.tagInfo.vid"
   ::= {er1646v2EthPortSwIXt2VlanTaggingEntry 1828716544}

er1646v2EthPortSwIXt2VlanTaggingVlans OBJECT-TYPE
   SYNTAX      SEQUENCE OF Er1646v2EthPortSwIXt2VlanTaggingVlansEntry
   MAX-ACCESS  not-accessible
   STATUS      current
   DESCRIPTION
      ""
   ::= {er1646v2EthPortSwIXt2VlanTagging 1073741824}

er1646v2EthPortSwIXt2VlanTaggingVlansEntry OBJECT-TYPE
   SYNTAX      Er1646v2EthPortSwIXt2VlanTaggingVlansEntry
   MAX-ACCESS  not-accessible
   STATUS      current
   DESCRIPTION
      ""
   INDEX      { er1646v2EthPortSwIXt2VlanTaggingVlansGlobalIx,
                er1646v2EthPortSwIXt2VlanTaggingVlansTableIx }
   ::= {er1646v2EthPortSwIXt2VlanTaggingVlans 1}

Er1646v2EthPortSwIXt2VlanTaggingVlansEntry ::=
   SEQUENCE
      {
      er1646v2EthPortSwIXt2VlanTaggingVlansActions
         VariableLengthTableActions,
      er1646v2EthPortSwIXt2VlanTaggingVlansGlobalIx
         GlobalIndex,
      er1646v2EthPortSwIXt2VlanTaggingVlansTableIx
         TableIndex,
      er1646v2EthPortSwIXt2VlanTaggingVlansVid
         Integer32,
      er1646v2EthPortSwIXt2VlanTaggingVlansEndVid
         Integer32,
      er1646v2EthPortSwIXt2VlanTaggingVlansAction
         INTEGER,
      er1646v2EthPortSwIXt2VlanTaggingVlansTagInfoTpid
         INTEGER,
      er1646v2EthPortSwIXt2VlanTaggingVlansTagInfoVid
         Integer32
      }

er1646v2EthPortSwIXt2VlanTaggingVlansActions OBJECT-TYPE
   SYNTAX      VariableLengthTableActions
   MAX-ACCESS  read-write
   STATUS      current
   DESCRIPTION
      "By way of this field, some manipulations
       on this table may be performed."
   ::= {er1646v2EthPortSwIXt2VlanTaggingVlansEntry 2}

er1646v2EthPortSwIXt2VlanTaggingVlansGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanTaggingVlansEntry 10}

er1646v2EthPortSwIXt2VlanTaggingVlansTableIx OBJECT-TYPE
   SYNTAX      TableIndex
   MAX-ACCESS  not-accessible
   STATUS      current
   DESCRIPTION
      ""
   ::= {er1646v2EthPortSwIXt2VlanTaggingVlansEntry 11}

er1646v2EthPortSwIXt2VlanTaggingVlansVid OBJECT-TYPE
   SYNTAX      Integer32
   MAX-ACCESS  read-write
   STATUS      current
   DESCRIPTION
      "Path: swPort.editConf.vlanTagging.vlans.vid"
   ::= {er1646v2EthPortSwIXt2VlanTaggingVlansEntry 536870912}

er1646v2EthPortSwIXt2VlanTaggingVlansEndVid OBJECT-TYPE
   SYNTAX      Integer32
   MAX-ACCESS  read-write
   STATUS      current
   DESCRIPTION
      "Path: swPort.editConf.vlanTagging.vlans.endVid"
   ::= {er1646v2EthPortSwIXt2VlanTaggingVlansEntry 2147483648}

er1646v2EthPortSwIXt2VlanTaggingVlansAction OBJECT-TYPE
   SYNTAX      INTEGER
               {
               discard (0),
               accept (1),
               tag (2)
               }
   MAX-ACCESS  read-write
   STATUS      current
   DESCRIPTION
      "Path: swPort.editConf.vlanTagging.vlans.action

       Possibilities:
               discard   (0)
               accept   (1)
               tag   (2)"
   ::= {er1646v2EthPortSwIXt2VlanTaggingVlansEntry 1073741824}

er1646v2EthPortSwIXt2VlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlanTagging.vlans.tagInfo.tpid

       Possibilities:
               dot1Q   (33024)
               dot1ad   (34984)
               0x9100   (37120)
               0x9200   (37376)
               0x9300   (37632)"
   ::= {er1646v2EthPortSwIXt2VlanTaggingVlansEntry 1677721600}

er1646v2EthPortSwIXt2VlanTaggingVlansTagInfoVid OBJECT-TYPE
   SYNTAX      Integer32
   MAX-ACCESS  read-write
   STATUS      current
   DESCRIPTION
      "Path: swPort.editConf.vlanTagging.vlans.tagInfo.vid"
   ::= {er1646v2EthPortSwIXt2VlanTaggingVlansEntry 1744830464}


er1646v2EthPortSwIXt2Oam OBJECT IDENTIFIER ::= {er1646v2EthPortSwIXt2 900}

er1646v2EthPortSwIXt2OamSSCTable OBJECT-TYPE
   SYNTAX      SEQUENCE OF Er1646v2EthPortSwIXt2OamEntry
   MAX-ACCESS  not-accessible
   STATUS      current
   DESCRIPTION
      "OAM mode"
   ::= {er1646v2EthPortSwIXt2Oam 1}

er1646v2EthPortSwIXt2OamEntry OBJECT-TYPE
   SYNTAX      Er1646v2EthPortSwIXt2OamEntry
   MAX-ACCESS  not-accessible
   STATUS      current
   DESCRIPTION
      ""
   INDEX      { er1646v2EthPortSwIXt2OamGlobalIx }
   ::= {er1646v2EthPortSwIXt2OamSSCTable 1}

Er1646v2EthPortSwIXt2OamEntry ::=
   SEQUENCE
      {
      er1646v2EthPortSwIXt2OamGlobalIx
         GlobalIndex,
      er1646v2EthPortSwIXt2OamMode
         INTEGER,
      er1646v2EthPortSwIXt2OamLpbkLocalParAction
         INTEGER,
      er1646v2EthPortSwIXt2OamLpbkSwapMacAddr
         INTEGER,
      er1646v2EthPortSwIXt2OamLoopbackIgnoreRx
         INTEGER,
      er1646v2EthPortSwIXt2OamEventsErroredSymbolEnabled
         INTEGER,
      er1646v2EthPortSwIXt2OamEventsErroredSymbolWindowHi
         INTEGER,
      er1646v2EthPortSwIXt2OamEventsErroredSymbolWindowLo
         INTEGER,
      er1646v2EthPortSwIXt2OamEventsErroredSymbolThresholdHi
         Integer32,
      er1646v2EthPortSwIXt2OamEventsErroredSymbolThresholdLo
         Integer32,
      er1646v2EthPortSwIXt2OamEventsErroredFramePeriodEnabled
         INTEGER,
      er1646v2EthPortSwIXt2OamEventsErroredFramePeriodWindow
         INTEGER,
      er1646v2EthPortSwIXt2OamEventsErroredFramePeriodThreshold
         Integer32,
      er1646v2EthPortSwIXt2OamEventsErroredFrameEnabled
         INTEGER,
      er1646v2EthPortSwIXt2OamEventsErroredFrameWindow
         Integer32,
      er1646v2EthPortSwIXt2OamEventsErroredFrameThreshold
         Integer32,
      er1646v2EthPortSwIXt2OamEventsErroredFrameSecondsEnabled
         INTEGER,
      er1646v2EthPortSwIXt2OamEventsErroredFrameSecondsWindow
         Integer32,
      er1646v2EthPortSwIXt2OamEventsErroredFrameSecondsThreshold
         Integer32,
      er1646v2EthPortSwIXt2OamEventsDyingGasp
         INTEGER,
      er1646v2EthPortSwIXt2OamEventsCriticalEvent
         INTEGER
      }

er1646v2EthPortSwIXt2OamGlobalIx OBJECT-TYPE
   SYNTAX      GlobalIndex
   MAX-ACCESS  not-accessible
   STATUS      current
   DESCRIPTION
      "The value of the tlsCntTreeGlobalIndex of the MANAGED OBJECT."
   ::= {er1646v2EthPortSwIXt2OamEntry 10}

er1646v2EthPortSwIXt2OamMode OBJECT-TYPE
   SYNTAX      INTEGER
               {
               disabled (0),
               passive (3),
               active (2)
               }
   MAX-ACCESS  read-write
   STATUS      current
   DESCRIPTION
      "Path: swPort.editConf.oam.mode

       Possibilities:
               disabled   (0)
               passive   (3)
               active   (2)"
   ::= {er1646v2EthPortSwIXt2OamEntry 16777216}

er1646v2EthPortSwIXt2OamLpbkLocalParAction OBJECT-TYPE
   SYNTAX      INTEGER
               {
               discard (0),
               forward (1)
               }
   MAX-ACCESS  read-write
   STATUS      current
   DESCRIPTION
      "Path: swPort.editConf.oam.loopbackLocalParserAction

       Possibilities:
               discard   (0)
               forward   (1)"
   ::= {er1646v2EthPortSwIXt2OamEntry 33554432}

er1646v2EthPortSwIXt2OamLpbkSwapMacAddr OBJECT-TYPE
   SYNTAX      INTEGER
               {
               disabled (0),
               enabled (1)
               }
   MAX-ACCESS  read-write
   STATUS      current
   DESCRIPTION
      "Path: swPort.editConf.oam.loopbackSwapMacAddresses

       Possibilities:
               disabled   (0)
               enabled   (1)"
   ::= {er1646v2EthPortSwIXt2OamEntry 50331648}

er1646v2EthPortSwIXt2OamLoopbackIgnoreRx OBJECT-TYPE
   SYNTAX      INTEGER
               {
               no (0),
               yes (1)
               }
   MAX-ACCESS  read-write
   STATUS      current
   DESCRIPTION
      "Path: swPort.editConf.oam.loopbackIgnoreRx

       Possibilities:
               no   (0)
               yes   (1)"
   ::= {er1646v2EthPortSwIXt2OamEntry 67108864}

er1646v2EthPortSwIXt2OamEventsErroredSymbolEnabled OBJECT-TYPE
   SYNTAX      INTEGER
               {
               no (0),
               yes (1)
               }
   MAX-ACCESS  read-write
   STATUS      current
   DESCRIPTION
      "Path: swPort.editConf.oam.events.erroredSymbol.enabled

       Possibilities:
               no   (0)
               yes   (1)"
   ::= {er1646v2EthPortSwIXt2OamEntry 83951872}

er1646v2EthPortSwIXt2OamEventsErroredSymbolWindowHi OBJECT-TYPE
   SYNTAX      INTEGER
               {
               default (0)
               }
   UNITS       "symbols"
   MAX-ACCESS  read-write
   STATUS      current
   DESCRIPTION
      "Path: swPort.editConf.oam.events.erroredSymbol.windowHi

       unit name = symbols

       Possibilities:
               default   (0)"
   ::= {er1646v2EthPortSwIXt2OamEntry 83952128}

er1646v2EthPortSwIXt2OamEventsErroredSymbolWindowLo OBJECT-TYPE
   SYNTAX      INTEGER
               {
               default (0)
               }
   UNITS       "symbols"
   MAX-ACCESS  read-write
   STATUS      current
   DESCRIPTION
      "Path: swPort.editConf.oam.events.erroredSymbol.windowLo

       unit name = symbols

       Possibilities:
               default   (0)"
   ::= {er1646v2EthPortSwIXt2OamEntry 83952384}

er1646v2EthPortSwIXt2OamEventsErroredSymbolThresholdHi OBJECT-TYPE
   SYNTAX      Integer32
   UNITS       "symbols"
   MAX-ACCESS  read-write
   STATUS      current
   DESCRIPTION
      "Path: swPort.editConf.oam.events.erroredSymbol.thresholdHi

       unit name = symbols"
   ::= {er1646v2EthPortSwIXt2OamEntry 83952640}

er1646v2EthPortSwIXt2OamEventsErroredSymbolThresholdLo OBJECT-TYPE
   SYNTAX      Integer32
   UNITS       "symbols"
   MAX-ACCESS  read-write
   STATUS      current
   DESCRIPTION
      "Path: swPort.editConf.oam.events.erroredSymbol.thresholdLo

       unit name = symbols"
   ::= {er1646v2EthPortSwIXt2OamEntry 83952896}

er1646v2EthPortSwIXt2OamEventsErroredFramePeriodEnabled OBJECT-TYPE
   SYNTAX      INTEGER
               {
               no (0),
               yes (1)
               }
   MAX-ACCESS  read-write
   STATUS      current
   DESCRIPTION
      "Path: swPort.editConf.oam.events.erroredFramePeriod.enabled

       Possibilities:
               no   (0)
               yes   (1)"
   ::= {er1646v2EthPortSwIXt2OamEntry 84017408}

er1646v2EthPortSwIXt2OamEventsErroredFramePeriodWindow OBJECT-TYPE
   SYNTAX      INTEGER
               {
               default (0)
               }
   UNITS       "frames"
   MAX-ACCESS  read-write
   STATUS      current
   DESCRIPTION
      "Path: swPort.editConf.oam.events.erroredFramePeriod.window

       unit name = frames

       Possibilities:
               default   (0)"
   ::= {er1646v2EthPortSwIXt2OamEntry 84017664}

er1646v2EthPortSwIXt2OamEventsErroredFramePeriodThreshold OBJECT-TYPE
   SYNTAX      Integer32
   UNITS       "frames"
   MAX-ACCESS  read-write
   STATUS      current
   DESCRIPTION
      "Path: swPort.editConf.oam.events.erroredFramePeriod.threshold

       unit name = frames"
   ::= {er1646v2EthPortSwIXt2OamEntry 84017920}

er1646v2EthPortSwIXt2OamEventsErroredFrameEnabled OBJECT-TYPE
   SYNTAX      INTEGER
               {
               no (0),
               yes (1)
               }
   MAX-ACCESS  read-write
   STATUS      current
   DESCRIPTION
      "Path: swPort.editConf.oam.events.erroredFrame.enabled

       Possibilities:
               no   (0)
               yes   (1)"
   ::= {er1646v2EthPortSwIXt2OamEntry 84082944}

er1646v2EthPortSwIXt2OamEventsErroredFrameWindow OBJECT-TYPE
   SYNTAX      Integer32
   UNITS       "100msec"
   MAX-ACCESS  read-write
   STATUS      current
   DESCRIPTION
      "Path: swPort.editConf.oam.events.erroredFrame.window

       unit name = 100msec"
   ::= {er1646v2EthPortSwIXt2OamEntry 84083200}

er1646v2EthPortSwIXt2OamEventsErroredFrameThreshold OBJECT-TYPE
   SYNTAX      Integer32
   UNITS       "frames"
   MAX-ACCESS  read-write
   STATUS      current
   DESCRIPTION
      "Path: swPort.editConf.oam.events.erroredFrame.threshold

       unit name = frames"
   ::= {er1646v2EthPortSwIXt2OamEntry 84083456}

er1646v2EthPortSwIXt2OamEventsErroredFrameSecondsEnabled OBJECT-TYPE
   SYNTAX      INTEGER
               {
               no (0),
               yes (1)
               }
   MAX-ACCESS  read-write
   STATUS      current
   DESCRIPTION
      "Path: swPort.editConf.oam.events.erroredFrameSeconds.enabled

       Possibilities:
               no   (0)
               yes   (1)"
   ::= {er1646v2EthPortSwIXt2OamEntry 84148480}

er1646v2EthPortSwIXt2OamEventsErroredFrameSecondsWindow OBJECT-TYPE
   SYNTAX      Integer32
   UNITS       "100msec"
   MAX-ACCESS  read-write
   STATUS      current
   DESCRIPTION
      "Path: swPort.editConf.oam.events.erroredFrameSeconds.window

       unit name = 100msec"
   ::= {er1646v2EthPortSwIXt2OamEntry 84148736}

er1646v2EthPortSwIXt2OamEventsErroredFrameSecondsThreshold OBJECT-TYPE
   SYNTAX      Integer32
   UNITS       "frames"
   MAX-ACCESS  read-write
   STATUS      current
   DESCRIPTION
      "Path: swPort.editConf.oam.events.erroredFrameSeconds.threshold

       unit name = frames"
   ::= {er1646v2EthPortSwIXt2OamEntry 84148992}

er1646v2EthPortSwIXt2OamEventsDyingGasp OBJECT-TYPE
   SYNTAX      INTEGER
               {
               disabled (0),
               enabled (1)
               }
   MAX-ACCESS  read-write
   STATUS      current
   DESCRIPTION
      "Path: swPort.editConf.oam.events.dyingGasp

       Possibilities:
               disabled   (0)
               enabled   (1)"
   ::= {er1646v2EthPortSwIXt2OamEntry 84213760}

er1646v2EthPortSwIXt2OamEventsCriticalEvent OBJECT-TYPE
   SYNTAX      INTEGER
               {
               disabled (0),
               enabled (1)
               }
   MAX-ACCESS  read-write
   STATUS      current
   DESCRIPTION
      "Path: swPort.editConf.oam.events.criticalEvent

       Possibilities:
               disabled   (0)
               enabled   (1)"
   ::= {er1646v2EthPortSwIXt2OamEntry 84279296}


er1646v2EthPortSwIXt2Dot1x OBJECT IDENTIFIER ::= {er1646v2EthPortSwIXt2 191}

er1646v2EthPortSwIXt2Dot1xSSCTable OBJECT-TYPE
   SYNTAX      SEQUENCE OF Er1646v2EthPortSwIXt2Dot1xEntry
   MAX-ACCESS  not-accessible
   STATUS      current
   DESCRIPTION
      "ppp server name on interface"
   ::= {er1646v2EthPortSwIXt2Dot1x 1}

er1646v2EthPortSwIXt2Dot1xEntry OBJECT-TYPE
   SYNTAX      Er1646v2EthPortSwIXt2Dot1xEntry
   MAX-ACCESS  not-accessible
   STATUS      current
   DESCRIPTION
      ""
   INDEX      { er1646v2EthPortSwIXt2Dot1xGlobalIx }
   ::= {er1646v2EthPortSwIXt2Dot1xSSCTable 1}

Er1646v2EthPortSwIXt2Dot1xEntry ::=
   SEQUENCE
      {
      er1646v2EthPortSwIXt2Dot1xGlobalIx
         GlobalIndex,
      er1646v2EthPortSwIXt2Dot1xMode
         INTEGER,
      er1646v2EthPortSwIXt2Dot1xMaxHosts
         Integer32,
      er1646v2EthPortSwIXt2Dot1xReAuthentication
         INTEGER,
      er1646v2EthPortSwIXt2Dot1xReAuthPeriod
         TimeTicks,
      er1646v2EthPortSwIXt2Dot1xQuietPeriod
         TimeTicks,
      er1646v2EthPortSwIXt2Dot1xSupplTimeout
         TimeTicks,
      er1646v2EthPortSwIXt2Dot1xServerTimeout
         TimeTicks,
      er1646v2EthPortSwIXt2Dot1xMaxReqCount
         Integer32
      }

er1646v2EthPortSwIXt2Dot1xGlobalIx OBJECT-TYPE
   SYNTAX      GlobalIndex
   MAX-ACCESS  not-accessible
   STATUS      current
   DESCRIPTION
      "The value of the tlsCntTreeGlobalIndex of the MANAGED OBJECT."
   ::= {er1646v2EthPortSwIXt2Dot1xEntry 10}

er1646v2EthPortSwIXt2Dot1xMode OBJECT-TYPE
   SYNTAX      INTEGER
               {
               inactive (0),
               auto (1)
               }
   MAX-ACCESS  read-write
   STATUS      current
   DESCRIPTION
      "Path: swPort.editConf.dot1x.mode

       Possibilities:
               inactive   (0)
               auto   (1)"
   ::= {er1646v2EthPortSwIXt2Dot1xEntry 16777216}

er1646v2EthPortSwIXt2Dot1xMaxHosts OBJECT-TYPE
   SYNTAX      Integer32
   MAX-ACCESS  read-write
   STATUS      current
   DESCRIPTION
      "Path: swPort.editConf.dot1x.maxHosts"
   ::= {er1646v2EthPortSwIXt2Dot1xEntry 33554432}

er1646v2EthPortSwIXt2Dot1xReAuthentication OBJECT-TYPE
   SYNTAX      INTEGER
               {
               disabled (0),
               enabled (1)
               }
   MAX-ACCESS  read-write
   STATUS      current
   DESCRIPTION
      "Path: swPort.editConf.dot1x.reAuthentication

       Possibilities:
               disabled   (0)
               enabled   (1)"
   ::= {er1646v2EthPortSwIXt2Dot1xEntry 50331648}

er1646v2EthPortSwIXt2Dot1xReAuthPeriod OBJECT-TYPE
   SYNTAX      TimeTicks
   MAX-ACCESS  read-write
   STATUS      current
   DESCRIPTION
      "Path: swPort.editConf.dot1x.reAuthPeriod

       Time in centi-second."
   ::= {er1646v2EthPortSwIXt2Dot1xEntry 67108864}

er1646v2EthPortSwIXt2Dot1xQuietPeriod OBJECT-TYPE
   SYNTAX      TimeTicks
   MAX-ACCESS  read-write
   STATUS      current
   DESCRIPTION
      "Path: swPort.editConf.dot1x.quietPeriod

       Time in centi-second."
   ::= {er1646v2EthPortSwIXt2Dot1xEntry 83886080}

er1646v2EthPortSwIXt2Dot1xSupplTimeout OBJECT-TYPE
   SYNTAX      TimeTicks
   MAX-ACCESS  read-write
   STATUS      current
   DESCRIPTION
      "Path: swPort.editConf.dot1x.supplTimeout

       Time in centi-second."
   ::= {er1646v2EthPortSwIXt2Dot1xEntry 100663296}

er1646v2EthPortSwIXt2Dot1xServerTimeout OBJECT-TYPE
   SYNTAX      TimeTicks
   MAX-ACCESS  read-write
   STATUS      current
   DESCRIPTION
      "Path: swPort.editConf.dot1x.serverTimeout

       Time in centi-second."
   ::= {er1646v2EthPortSwIXt2Dot1xEntry 117440512}

er1646v2EthPortSwIXt2Dot1xMaxReqCount OBJECT-TYPE
   SYNTAX      Integer32
   MAX-ACCESS  read-write
   STATUS      current
   DESCRIPTION
      "Path: swPort.editConf.dot1x.maxReqCount"
   ::= {er1646v2EthPortSwIXt2Dot1xEntry 134217728}


er1646v2EthPortSwIXt2IpV6 OBJECT IDENTIFIER ::= {er1646v2EthPortSwIXt2 15}

er1646v2EthPortSwIXt2IpV6SSCTable OBJECT-TYPE
   SYNTAX      SEQUENCE OF Er1646v2EthPortSwIXt2IpV6Entry
   MAX-ACCESS  not-accessible
   STATUS      current
   DESCRIPTION
      "IPv6 interface config parameters"
   ::= {er1646v2EthPortSwIXt2IpV6 1}

er1646v2EthPortSwIXt2IpV6Entry OBJECT-TYPE
   SYNTAX      Er1646v2EthPortSwIXt2IpV6Entry
   MAX-ACCESS  not-accessible
   STATUS      current
   DESCRIPTION
      ""
   INDEX      { er1646v2EthPortSwIXt2IpV6GlobalIx }
   ::= {er1646v2EthPortSwIXt2IpV6SSCTable 1}

Er1646v2EthPortSwIXt2IpV6Entry ::=
   SEQUENCE
      {
      er1646v2EthPortSwIXt2IpV6GlobalIx
         GlobalIndex,
      er1646v2EthPortSwIXt2IpV6VrfRouter
         DisplayString,
      er1646v2EthPortSwIXt2IpV6AddrAutoConfigNrDupAddrDetects
         Integer32,
      er1646v2EthPortSwIXt2IpV6AddrAutoConfigAcceptRa
         INTEGER,
      er1646v2EthPortSwIXt2IpV6AddrAutoConfigAcceptRaRdnss
         INTEGER,
      er1646v2EthPortSwIXt2IpV6AddrAutoConfigAcceptRaDnssl
         INTEGER,
      er1646v2EthPortSwIXt2IpV6DefaultRoute
         INTEGER,
      er1646v2EthPortSwIXt2IpV6RaSend
         INTEGER,
      er1646v2EthPortSwIXt2IpV6RaMinInterval
         TimeTicks,
      er1646v2EthPortSwIXt2IpV6RaMaxInterval
         TimeTicks,
      er1646v2EthPortSwIXt2IpV6RaManagedFlag
         INTEGER,
      er1646v2EthPortSwIXt2IpV6RaOtherConfFlag
         INTEGER,
      er1646v2EthPortSwIXt2IpV6RaLinkMtu
         Integer32,
      er1646v2EthPortSwIXt2IpV6RaReachableTime
         TimeTicks,
      er1646v2EthPortSwIXt2IpV6RaRetransmitTime
         TimeTicks,
      er1646v2EthPortSwIXt2IpV6RaHopLimit
         Integer32,
      er1646v2EthPortSwIXt2IpV6RaDefaultLifeTime
         TimeTicks,
      er1646v2EthPortSwIXt2IpV6RaDnsOptionsRdnssLifeTime
         TimeTicks,
      er1646v2EthPortSwIXt2IpV6RaDnsOptionsRdnssImportServers
         INTEGER,
      er1646v2EthPortSwIXt2IpV6RaDnsOptionsDnsslLifeTime
         TimeTicks,
      er1646v2EthPortSwIXt2IpV6RaDnsOptionsDnsslImportDomains
         INTEGER,
      er1646v2EthPortSwIXt2IpV6RsSend
         INTEGER,
      er1646v2EthPortSwIXt2IpV6RsMaxRandomDelay
         TimeTicks,
      er1646v2EthPortSwIXt2IpV6RsInterval
         TimeTicks,
      er1646v2EthPortSwIXt2IpV6RsMaxSolicitations
         Integer32,
      er1646v2EthPortSwIXt2IpV6TrafficPolicyInbound
         DisplayString,
      er1646v2EthPortSwIXt2IpV6TrafficPolicyOutbound
         DisplayString,
      er1646v2EthPortSwIXt2IpV6FirewallZone
         DisplayString,
      er1646v2EthPortSwIXt2IpV6DhcpClientAddrAC
         INTEGER,
      er1646v2EthPortSwIXt2IpV6DhcpClientPrDelMode
         INTEGER,
      er1646v2EthPortSwIXt2IpV6DhcpClientPrDelPool
         DisplayString,
      er1646v2EthPortSwIXt2IpV6DhcpClientPrDelPdExclOpt
         INTEGER,
      er1646v2EthPortSwIXt2IpV6DhcpClientDnsServerPref
         Integer32,
      er1646v2EthPortSwIXt2IpV6DhcpClientRapidCommit
         INTEGER,
      er1646v2EthPortSwIXt2IpV6DhcpClientTimersSolTimeOut
         TimeTicks,
      er1646v2EthPortSwIXt2IpV6DhcpClientTimersSolMaxRt
         TimeTicks,
      er1646v2EthPortSwIXt2IpV6DhcpClientTimersInfoRefresh
         TimeTicks,
      er1646v2EthPortSwIXt2IpV6DhcpServerMode
         INTEGER,
      er1646v2EthPortSwIXt2IpV6DhcpServerPreference
         Integer32,
      er1646v2EthPortSwIXt2IpV6DhcpServerPool
         DisplayString,
      er1646v2EthPortSwIXt2IpV6DhcpServerRapidCommit
         INTEGER,
      er1646v2EthPortSwIXt2IpV6DhcpServerTimersInfoRefresh
         TimeTicks,
      er1646v2EthPortSwIXt2IpV6DhcpRelayMode
         INTEGER,
      er1646v2EthPortSwIXt2IpV6SendRedirect
         INTEGER,
      er1646v2EthPortSwIXt2IpV6LinkMtu
         Integer32,
      er1646v2EthPortSwIXt2IpV6InterfaceId
         OCTET STRING,
      er1646v2EthPortSwIXt2IpV6MF
         Integer32,
      er1646v2EthPortSwIXt2IpV6IcmpMessagesNoRoute
         INTEGER,
      er1646v2EthPortSwIXt2IpV6IcmpMessagesBeyondScope
         INTEGER,
      er1646v2EthPortSwIXt2IpV6IcmpMessagesAddressUnreachable
         INTEGER,
      er1646v2EthPortSwIXt2IpV6IcmpMessagesPortUnreachable
         INTEGER,
      er1646v2EthPortSwIXt2IpV6IcmpMessagesPacketTooBig
         INTEGER,
      er1646v2EthPortSwIXt2IpV6IcmpMessagesHopLimitExceeded
         INTEGER,
      er1646v2EthPortSwIXt2IpV6IcmpMessagesFragTimeExceeded
         INTEGER,
      er1646v2EthPortSwIXt2IpV6IcmpMessagesHeaderFieldErr
         INTEGER,
      er1646v2EthPortSwIXt2IpV6IcmpMessagesOptionUnrecognized
         INTEGER,
      er1646v2EthPortSwIXt2IpV6IcmpMessagesRedirect
         INTEGER
      }

er1646v2EthPortSwIXt2IpV6GlobalIx OBJECT-TYPE
   SYNTAX      GlobalIndex
   MAX-ACCESS  not-accessible
   STATUS      current
   DESCRIPTION
      "The value of the tlsCntTreeGlobalIndex of the MANAGED OBJECT."
   ::= {er1646v2EthPortSwIXt2IpV6Entry 10}

er1646v2EthPortSwIXt2IpV6VrfRouter OBJECT-TYPE
   SYNTAX      DisplayString
   MAX-ACCESS  read-write
   STATUS      current
   DESCRIPTION
      "Path: swPort.editConf.ipV6.vrfRouter"
   ::= {er1646v2EthPortSwIXt2IpV6Entry 16777216}

er1646v2EthPortSwIXt2IpV6AddrAutoConfigNrDupAddrDetects OBJECT-TYPE
   SYNTAX      Integer32
   MAX-ACCESS  read-write
   STATUS      current
   DESCRIPTION
      "Path: swPort.editConf.ipV6.addrAutoConfig.nrDupAddrDetects"
   ::= {er1646v2EthPortSwIXt2IpV6Entry 67174400}

er1646v2EthPortSwIXt2IpV6AddrAutoConfigAcceptRa OBJECT-TYPE
   SYNTAX      INTEGER
               {
               disabled (0),
               enabled (1)
               }
   MAX-ACCESS  read-write
   STATUS      current
   DESCRIPTION
      "Path: swPort.editConf.ipV6.addrAutoConfig.acceptRa

       Possibilities:
               disabled   (0)
               enabled   (1)"
   ::= {er1646v2EthPortSwIXt2IpV6Entry 67239936}

er1646v2EthPortSwIXt2IpV6AddrAutoConfigAcceptRaRdnss OBJECT-TYPE
   SYNTAX      INTEGER
               {
               disabled (0),
               enabled (1)
               }
   MAX-ACCESS  read-write
   STATUS      current
   DESCRIPTION
      "Path: swPort.editConf.ipV6.addrAutoConfig.acceptRaRdnss

       Possibilities:
               disabled   (0)
               enabled   (1)"
   ::= {er1646v2EthPortSwIXt2IpV6Entry 67305472}

er1646v2EthPortSwIXt2IpV6AddrAutoConfigAcceptRaDnssl OBJECT-TYPE
   SYNTAX      INTEGER
               {
               disabled (0),
               enabled (1)
               }
   MAX-ACCESS  read-write
   STATUS      current
   DESCRIPTION
      "Path: swPort.editConf.ipV6.addrAutoConfig.acceptRaDnssl

       Possibilities:
               disabled   (0)
               enabled   (1)"
   ::= {er1646v2EthPortSwIXt2IpV6Entry 67371008}

er1646v2EthPortSwIXt2IpV6DefaultRoute OBJECT-TYPE
   SYNTAX      INTEGER
               {
               disabled (0),
               enabled (1)
               }
   MAX-ACCESS  read-write
   STATUS      current
   DESCRIPTION
      "Path: swPort.editConf.ipV6.defaultRoute

       Possibilities:
               disabled   (0)
               enabled   (1)"
   ::= {er1646v2EthPortSwIXt2IpV6Entry 83886080}

er1646v2EthPortSwIXt2IpV6RaSend OBJECT-TYPE
   SYNTAX      INTEGER
               {
               disabled (0),
               enabled (1)
               }
   MAX-ACCESS  read-write
   STATUS      current
   DESCRIPTION
      "Path: swPort.editConf.ipV6.ra.send

       Possibilities:
               disabled   (0)
               enabled   (1)"
   ::= {er1646v2EthPortSwIXt2IpV6Entry 100728832}

er1646v2EthPortSwIXt2IpV6RaMinInterval OBJECT-TYPE
   SYNTAX      TimeTicks
   MAX-ACCESS  read-write
   STATUS      current
   DESCRIPTION
      "Path: swPort.editConf.ipV6.ra.minInterval

       Time in centi-second."
   ::= {er1646v2EthPortSwIXt2IpV6Entry 100794368}

er1646v2EthPortSwIXt2IpV6RaMaxInterval OBJECT-TYPE
   SYNTAX      TimeTicks
   MAX-ACCESS  read-write
   STATUS      current
   DESCRIPTION
      "Path: swPort.editConf.ipV6.ra.maxInterval

       Time in centi-second."
   ::= {er1646v2EthPortSwIXt2IpV6Entry 100859904}

er1646v2EthPortSwIXt2IpV6RaManagedFlag OBJECT-TYPE
   SYNTAX      INTEGER
               {
               disabled (0),
               enabled (1)
               }
   MAX-ACCESS  read-write
   STATUS      current
   DESCRIPTION
      "Path: swPort.editConf.ipV6.ra.managedFlag

       Possibilities:
               disabled   (0)
               enabled   (1)"
   ::= {er1646v2EthPortSwIXt2IpV6Entry 100925440}

er1646v2EthPortSwIXt2IpV6RaOtherConfFlag OBJECT-TYPE
   SYNTAX      INTEGER
               {
               disabled (0),
               enabled (1)
               }
   MAX-ACCESS  read-write
   STATUS      current
   DESCRIPTION
      "Path: swPort.editConf.ipV6.ra.otherConfFlag

       Possibilities:
               disabled   (0)
               enabled   (1)"
   ::= {er1646v2EthPortSwIXt2IpV6Entry 100990976}

er1646v2EthPortSwIXt2IpV6RaLinkMtu OBJECT-TYPE
   SYNTAX      Integer32
   MAX-ACCESS  read-write
   STATUS      current
   DESCRIPTION
      "Path: swPort.editConf.ipV6.ra.linkMtu"
   ::= {er1646v2EthPortSwIXt2IpV6Entry 101056512}

er1646v2EthPortSwIXt2IpV6RaReachableTime OBJECT-TYPE
   SYNTAX      TimeTicks
   MAX-ACCESS  read-write
   STATUS      current
   DESCRIPTION
      "Path: swPort.editConf.ipV6.ra.reachableTime

       Time in centi-second."
   ::= {er1646v2EthPortSwIXt2IpV6Entry 101122048}

er1646v2EthPortSwIXt2IpV6RaRetransmitTime OBJECT-TYPE
   SYNTAX      TimeTicks
   MAX-ACCESS  read-write
   STATUS      current
   DESCRIPTION
      "Path: swPort.editConf.ipV6.ra.retransmitTime

       Time in centi-second."
   ::= {er1646v2EthPortSwIXt2IpV6Entry 101187584}

er1646v2EthPortSwIXt2IpV6RaHopLimit OBJECT-TYPE
   SYNTAX      Integer32
   MAX-ACCESS  read-write
   STATUS      current
   DESCRIPTION
      "Path: swPort.editConf.ipV6.ra.hopLimit"
   ::= {er1646v2EthPortSwIXt2IpV6Entry 101253120}

er1646v2EthPortSwIXt2IpV6RaDefaultLifeTime OBJECT-TYPE
   SYNTAX      TimeTicks
   MAX-ACCESS  read-write
   STATUS      current
   DESCRIPTION
      "Path: swPort.editConf.ipV6.ra.defaultLifeTime

       Time in centi-second."
   ::= {er1646v2EthPortSwIXt2IpV6Entry 101318656}

er1646v2EthPortSwIXt2IpV6RaDnsOptionsRdnssLifeTime OBJECT-TYPE
   SYNTAX      TimeTicks
   MAX-ACCESS  read-write
   STATUS      current
   DESCRIPTION
      "Path: swPort.editConf.ipV6.ra.dnsOptions.rdnss.lifeTime

       Time in centi-second."
   ::= {er1646v2EthPortSwIXt2IpV6Entry 101393408}

er1646v2EthPortSwIXt2IpV6RaDnsOptionsRdnssImportServers OBJECT-TYPE
   SYNTAX      INTEGER
               {
               disabled (0),
               enabled (1)
               }
   MAX-ACCESS  read-write
   STATUS      current
   DESCRIPTION
      "Path: swPort.editConf.ipV6.ra.dnsOptions.rdnss.importServers

       Possibilities:
               disabled   (0)
               enabled   (1)"
   ::= {er1646v2EthPortSwIXt2IpV6Entry 101395456}

er1646v2EthPortSwIXt2IpV6RaDnsOptionsDnsslLifeTime OBJECT-TYPE
   SYNTAX      TimeTicks
   MAX-ACCESS  read-write
   STATUS      current
   DESCRIPTION
      "Path: swPort.editConf.ipV6.ra.dnsOptions.dnssl.lifeTime

       Time in centi-second."
   ::= {er1646v2EthPortSwIXt2IpV6Entry 101401600}

er1646v2EthPortSwIXt2IpV6RaDnsOptionsDnsslImportDomains OBJECT-TYPE
   SYNTAX      INTEGER
               {
               disabled (0),
               enabled (1)
               }
   MAX-ACCESS  read-write
   STATUS      current
   DESCRIPTION
      "Path: swPort.editConf.ipV6.ra.dnsOptions.dnssl.importDomains

       Possibilities:
               disabled   (0)
               enabled   (1)"
   ::= {er1646v2EthPortSwIXt2IpV6Entry 101403648}

er1646v2EthPortSwIXt2IpV6RsSend OBJECT-TYPE
   SYNTAX      INTEGER
               {
               disabled (0),
               enabled (1)
               }
   MAX-ACCESS  read-write
   STATUS      current
   DESCRIPTION
      "Path: swPort.editConf.ipV6.rs.send

       Possibilities:
               disabled   (0)
               enabled   (1)"
   ::= {er1646v2EthPortSwIXt2IpV6Entry 335609856}

er1646v2EthPortSwIXt2IpV6RsMaxRandomDelay OBJECT-TYPE
   SYNTAX      TimeTicks
   MAX-ACCESS  read-write
   STATUS      current
   DESCRIPTION
      "Path: swPort.editConf.ipV6.rs.maxRandomDelay

       Time in centi-second."
   ::= {er1646v2EthPortSwIXt2IpV6Entry 335675392}

er1646v2EthPortSwIXt2IpV6RsInterval OBJECT-TYPE
   SYNTAX      TimeTicks
   MAX-ACCESS  read-write
   STATUS      current
   DESCRIPTION
      "Path: swPort.editConf.ipV6.rs.interval

       Time in centi-second."
   ::= {er1646v2EthPortSwIXt2IpV6Entry 335740928}

er1646v2EthPortSwIXt2IpV6RsMaxSolicitations OBJECT-TYPE
   SYNTAX      Integer32
   MAX-ACCESS  read-write
   STATUS      current
   DESCRIPTION
      "Path: swPort.editConf.ipV6.rs.maxSolicitations"
   ::= {er1646v2EthPortSwIXt2IpV6Entry 335806464}

er1646v2EthPortSwIXt2IpV6TrafficPolicyInbound OBJECT-TYPE
   SYNTAX      DisplayString
   MAX-ACCESS  read-write
   STATUS      current
   DESCRIPTION
      "Path: swPort.editConf.ipV6.trafficPolicy.inbound"
   ::= {er1646v2EthPortSwIXt2IpV6Entry 184614912}

er1646v2EthPortSwIXt2IpV6TrafficPolicyOutbound OBJECT-TYPE
   SYNTAX      DisplayString
   MAX-ACCESS  read-write
   STATUS      current
   DESCRIPTION
      "Path: swPort.editConf.ipV6.trafficPolicy.outbound"
   ::= {er1646v2EthPortSwIXt2IpV6Entry 184680448}

er1646v2EthPortSwIXt2IpV6FirewallZone OBJECT-TYPE
   SYNTAX      DisplayString
   MAX-ACCESS  read-write
   STATUS      current
   DESCRIPTION
      "Path: swPort.editConf.ipV6.firewall.zone"
   ::= {er1646v2EthPortSwIXt2IpV6Entry 201392128}

er1646v2EthPortSwIXt2IpV6DhcpClientAddrAC OBJECT-TYPE
   SYNTAX      INTEGER
               {
               disabled (0),
               enabled (1)
               }
   MAX-ACCESS  read-write
   STATUS      current
   DESCRIPTION
      "Path: swPort.editConf.ipV6.dhcp.client.addrAutoConfig

       Possibilities:
               disabled   (0)
               enabled   (1)"
   ::= {er1646v2EthPortSwIXt2IpV6Entry 170131456}

er1646v2EthPortSwIXt2IpV6DhcpClientPrDelMode OBJECT-TYPE
   SYNTAX      INTEGER
               {
               disabled (0),
               enabled (1)
               }
   MAX-ACCESS  read-write
   STATUS      current
   DESCRIPTION
      "Path: swPort.editConf.ipV6.dhcp.client.pd.mode

       Possibilities:
               disabled   (0)
               enabled   (1)"
   ::= {er1646v2EthPortSwIXt2IpV6Entry 170394624}

er1646v2EthPortSwIXt2IpV6DhcpClientPrDelPool OBJECT-TYPE
   SYNTAX      DisplayString
   MAX-ACCESS  read-write
   STATUS      current
   DESCRIPTION
      "Path: swPort.editConf.ipV6.dhcp.client.pd.pool"
   ::= {er1646v2EthPortSwIXt2IpV6Entry 170395648}

er1646v2EthPortSwIXt2IpV6DhcpClientPrDelPdExclOpt OBJECT-TYPE
   SYNTAX      INTEGER
               {
               disabled (0),
               enabled (1)
               }
   MAX-ACCESS  read-write
   STATUS      current
   DESCRIPTION
      "Path: swPort.editConf.ipV6.dhcp.client.pd.pdExclOpt

       Possibilities:
               disabled   (0)
               enabled   (1)"
   ::= {er1646v2EthPortSwIXt2IpV6Entry 170396672}

er1646v2EthPortSwIXt2IpV6DhcpClientDnsServerPref OBJECT-TYPE
   SYNTAX      Integer32
   MAX-ACCESS  read-write
   STATUS      current
   DESCRIPTION
      "Path: swPort.editConf.ipV6.dhcp.client.dns.serverPref"
   ::= {er1646v2EthPortSwIXt2IpV6Entry 170918912}

er1646v2EthPortSwIXt2IpV6DhcpClientRapidCommit OBJECT-TYPE
   SYNTAX      INTEGER
               {
               disabled (0),
               enabled (1)
               }
   MAX-ACCESS  read-write
   STATUS      current
   DESCRIPTION
      "Path: swPort.editConf.ipV6.dhcp.client.rapidCommit

       Possibilities:
               disabled   (0)
               enabled   (1)"
   ::= {er1646v2EthPortSwIXt2IpV6Entry 170655744}

er1646v2EthPortSwIXt2IpV6DhcpClientTimersSolTimeOut OBJECT-TYPE
   SYNTAX      TimeTicks
   MAX-ACCESS  read-write
   STATUS      current
   DESCRIPTION
      "Path: swPort.editConf.ipV6.dhcp.client.timers.solTimeOut

       Time in centi-second."
   ::= {er1646v2EthPortSwIXt2IpV6Entry 171181056}

er1646v2EthPortSwIXt2IpV6DhcpClientTimersSolMaxRt OBJECT-TYPE
   SYNTAX      TimeTicks
   MAX-ACCESS  read-write
   STATUS      current
   DESCRIPTION
      "Path: swPort.editConf.ipV6.dhcp.client.timers.solMaxRt

       Time in centi-second."
   ::= {er1646v2EthPortSwIXt2IpV6Entry 171182080}

er1646v2EthPortSwIXt2IpV6DhcpClientTimersInfoRefresh OBJECT-TYPE
   SYNTAX      TimeTicks
   MAX-ACCESS  read-write
   STATUS      current
   DESCRIPTION
      "Path: swPort.editConf.ipV6.dhcp.client.timers.infoRefresh

       Time in centi-second."
   ::= {er1646v2EthPortSwIXt2IpV6Entry 171183104}

er1646v2EthPortSwIXt2IpV6DhcpServerMode OBJECT-TYPE
   SYNTAX      INTEGER
               {
               disabled (0),
               enabled (1)
               }
   MAX-ACCESS  read-write
   STATUS      current
   DESCRIPTION
      "Path: swPort.editConf.ipV6.dhcp.server.mode

       Possibilities:
               disabled   (0)
               enabled   (1)"
   ::= {er1646v2EthPortSwIXt2IpV6Entry 172228608}

er1646v2EthPortSwIXt2IpV6DhcpServerPreference OBJECT-TYPE
   SYNTAX      Integer32
   MAX-ACCESS  read-write
   STATUS      current
   DESCRIPTION
      "Path: swPort.editConf.ipV6.dhcp.server.preference"
   ::= {er1646v2EthPortSwIXt2IpV6Entry 172490752}

er1646v2EthPortSwIXt2IpV6DhcpServerPool OBJECT-TYPE
   SYNTAX      DisplayString
   MAX-ACCESS  read-write
   STATUS      current
   DESCRIPTION
      "Path: swPort.editConf.ipV6.dhcp.server.pool"
   ::= {er1646v2EthPortSwIXt2IpV6Entry 172752896}

er1646v2EthPortSwIXt2IpV6DhcpServerRapidCommit OBJECT-TYPE
   SYNTAX      INTEGER
               {
               disabled (0),
               enabled (1)
               }
   MAX-ACCESS  read-write
   STATUS      current
   DESCRIPTION
      "Path: swPort.editConf.ipV6.dhcp.server.rapidCommit

       Possibilities:
               disabled   (0)
               enabled   (1)"
   ::= {er1646v2EthPortSwIXt2IpV6Entry 173015040}

er1646v2EthPortSwIXt2IpV6DhcpServerTimersInfoRefresh OBJECT-TYPE
   SYNTAX      TimeTicks
   MAX-ACCESS  read-write
   STATUS      current
   DESCRIPTION
      "Path: swPort.editConf.ipV6.dhcp.server.timers.infoRefresh

       Time in centi-second."
   ::= {er1646v2EthPortSwIXt2IpV6Entry 173278208}

er1646v2EthPortSwIXt2IpV6DhcpRelayMode OBJECT-TYPE
   SYNTAX      INTEGER
               {
               disabled (0),
               enabled (1)
               }
   MAX-ACCESS  read-write
   STATUS      current
   DESCRIPTION
      "Path: swPort.editConf.ipV6.dhcp.relay.mode

       Possibilities:
               disabled   (0)
               enabled   (1)"
   ::= {er1646v2EthPortSwIXt2IpV6Entry 174071808}

er1646v2EthPortSwIXt2IpV6SendRedirect OBJECT-TYPE
   SYNTAX      INTEGER
               {
               disabled (0),
               enabled (1)
               }
   MAX-ACCESS  read-write
   STATUS      current
   DESCRIPTION
      "Path: swPort.editConf.ipV6.sendRedirect

       Possibilities:
               disabled   (0)
               enabled   (1)"
   ::= {er1646v2EthPortSwIXt2IpV6Entry 117440512}

er1646v2EthPortSwIXt2IpV6LinkMtu OBJECT-TYPE
   SYNTAX      Integer32
   MAX-ACCESS  read-write
   STATUS      current
   DESCRIPTION
      "Path: swPort.editConf.ipV6.linkMtu"
   ::= {er1646v2EthPortSwIXt2IpV6Entry 134217728}

er1646v2EthPortSwIXt2IpV6InterfaceId OBJECT-TYPE
   SYNTAX      OCTET STRING
   MAX-ACCESS  read-write
   STATUS      current
   DESCRIPTION
      "Path: swPort.editConf.ipV6.interfaceId"
   ::= {er1646v2EthPortSwIXt2IpV6Entry 150994944}

er1646v2EthPortSwIXt2IpV6MF OBJECT-TYPE
   SYNTAX      Integer32
   MAX-ACCESS  read-write
   STATUS      current
   DESCRIPTION
      "Path: swPort.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EthPortSwIXt2IpV6Entry 285212672}

er1646v2EthPortSwIXt2IpV6IcmpMessagesNoRoute OBJECT-TYPE
   SYNTAX      INTEGER
               {
               disabled (0),
               enabled (1)
               }
   MAX-ACCESS  read-write
   STATUS      current
   DESCRIPTION
      "Path: swPort.editConf.ipV6.icmpMessages.noRoute

       Possibilities:
               disabled   (0)
               enabled   (1)"
   ::= {er1646v2EthPortSwIXt2IpV6Entry 302055424}

er1646v2EthPortSwIXt2IpV6IcmpMessagesBeyondScope OBJECT-TYPE
   SYNTAX      INTEGER
               {
               disabled (0),
               enabled (1)
               }
   MAX-ACCESS  read-write
   STATUS      current
   DESCRIPTION
      "Path: swPort.editConf.ipV6.icmpMessages.beyondScope

       Possibilities:
               disabled   (0)
               enabled   (1)"
   ::= {er1646v2EthPortSwIXt2IpV6Entry 302186496}

er1646v2EthPortSwIXt2IpV6IcmpMessagesAddressUnreachable OBJECT-TYPE
   SYNTAX      INTEGER
               {
               disabled (0),
               enabled (1)
               }
   MAX-ACCESS  read-write
   STATUS      current
   DESCRIPTION
      "Path: swPort.editConf.ipV6.icmpMessages.addressUnreachable

       Possibilities:
               disabled   (0)
               enabled   (1)"
   ::= {er1646v2EthPortSwIXt2IpV6Entry 302252032}

er1646v2EthPortSwIXt2IpV6IcmpMessagesPortUnreachable OBJECT-TYPE
   SYNTAX      INTEGER
               {
               disabled (0),
               enabled (1)
               }
   MAX-ACCESS  read-write
   STATUS      current
   DESCRIPTION
      "Path: swPort.editConf.ipV6.icmpMessages.portUnreachable

       Possibilities:
               disabled   (0)
               enabled   (1)"
   ::= {er1646v2EthPortSwIXt2IpV6Entry 302317568}

er1646v2EthPortSwIXt2IpV6IcmpMessagesPacketTooBig OBJECT-TYPE
   SYNTAX      INTEGER
               {
               disabled (0),
               enabled (1)
               }
   MAX-ACCESS  read-write
   STATUS      current
   DESCRIPTION
      "Path: swPort.editConf.ipV6.icmpMessages.packetTooBig

       Possibilities:
               disabled   (0)
               enabled   (1)"
   ::= {er1646v2EthPortSwIXt2IpV6Entry 302645248}

er1646v2EthPortSwIXt2IpV6IcmpMessagesHopLimitExceeded OBJECT-TYPE
   SYNTAX      INTEGER
               {
               disabled (0),
               enabled (1)
               }
   MAX-ACCESS  read-write
   STATUS      current
   DESCRIPTION
      "Path: swPort.editConf.ipV6.icmpMessages.hopLimitExceeded

       Possibilities:
               disabled   (0)
               enabled   (1)"
   ::= {er1646v2EthPortSwIXt2IpV6Entry 303300608}

er1646v2EthPortSwIXt2IpV6IcmpMessagesFragTimeExceeded OBJECT-TYPE
   SYNTAX      INTEGER
               {
               disabled (0),
               enabled (1)
               }
   MAX-ACCESS  read-write
   STATUS      current
   DESCRIPTION
      "Path: swPort.editConf.ipV6.icmpMessages.fragTimeExceeded

       Possibilities:
               disabled   (0)
               enabled   (1)"
   ::= {er1646v2EthPortSwIXt2IpV6Entry 303366144}

er1646v2EthPortSwIXt2IpV6IcmpMessagesHeaderFieldErr OBJECT-TYPE
   SYNTAX      INTEGER
               {
               disabled (0),
               enabled (1)
               }
   MAX-ACCESS  read-write
   STATUS      current
   DESCRIPTION
      "Path: swPort.editConf.ipV6.icmpMessages.headerFieldErr

       Possibilities:
               disabled   (0)
               enabled   (1)"
   ::= {er1646v2EthPortSwIXt2IpV6Entry 303955968}

er1646v2EthPortSwIXt2IpV6IcmpMessagesOptionUnrecognized OBJECT-TYPE
   SYNTAX      INTEGER
               {
               disabled (0),
               enabled (1)
               }
   MAX-ACCESS  read-write
   STATUS      current
   DESCRIPTION
      "Path: swPort.editConf.ipV6.icmpMessages.optionUnrecognized

       Possibilities:
               disabled   (0)
               enabled   (1)"
   ::= {er1646v2EthPortSwIXt2IpV6Entry 304087040}

er1646v2EthPortSwIXt2IpV6IcmpMessagesRedirect OBJECT-TYPE
   SYNTAX      INTEGER
               {
               disabled (0),
               enabled (1)
               }
   MAX-ACCESS  read-write
   STATUS      current
   DESCRIPTION
      "Path: swPort.editConf.ipV6.icmpMessages.redirect

       Possibilities:
               disabled   (0)
               enabled   (1)"
   ::= {er1646v2EthPortSwIXt2IpV6Entry 304611328}

er1646v2EthPortSwIXt2IpV6Addresses OBJECT-TYPE
   SYNTAX      SEQUENCE OF Er1646v2EthPortSwIXt2IpV6AddressesEntry
   MAX-ACCESS  not-accessible
   STATUS      current
   DESCRIPTION
      ""
   ::= {er1646v2EthPortSwIXt2IpV6 50331648}

er1646v2EthPortSwIXt2IpV6AddressesEntry OBJECT-TYPE
   SYNTAX      Er1646v2EthPortSwIXt2IpV6AddressesEntry
   MAX-ACCESS  not-accessible
   STATUS      current
   DESCRIPTION
      ""
   INDEX      { er1646v2EthPortSwIXt2IpV6AddressesGlobalIx,
                er1646v2EthPortSwIXt2IpV6AddressesTableIx }
   ::= {er1646v2EthPortSwIXt2IpV6Addresses 1}

Er1646v2EthPortSwIXt2IpV6AddressesEntry ::=
   SEQUENCE
      {
      er1646v2EthPortSwIXt2IpV6AddressesActions
         VariableLengthTableActions,
      er1646v2EthPortSwIXt2IpV6AddressesGlobalIx
         GlobalIndex,
      er1646v2EthPortSwIXt2IpV6AddressesTableIx
         TableIndex,
      er1646v2EthPortSwIXt2IpV6AddressesType
         INTEGER,
      er1646v2EthPortSwIXt2IpV6AddressesAddress
         Ipv6Address,
      er1646v2EthPortSwIXt2IpV6AddressesPrefixLength
         Integer32,
      er1646v2EthPortSwIXt2IpV6AddressesGeneralPrefix
         DisplayString,
      er1646v2EthPortSwIXt2IpV6AddressesRaSend
         INTEGER,
      er1646v2EthPortSwIXt2IpV6AddressesRaOnLinkFlag
         INTEGER,
      er1646v2EthPortSwIXt2IpV6AddressesRaAutoFlag
         INTEGER,
      er1646v2EthPortSwIXt2IpV6AddressesRaValidLifeTime
         TimeTicks,
      er1646v2EthPortSwIXt2IpV6AddressesRaValidLTMode
         INTEGER,
      er1646v2EthPortSwIXt2IpV6AddressesRaPrefLifeTime
         TimeTicks,
      er1646v2EthPortSwIXt2IpV6AddressesRaPrefLTMode
         INTEGER
      }

er1646v2EthPortSwIXt2IpV6AddressesActions OBJECT-TYPE
   SYNTAX      VariableLengthTableActions
   MAX-ACCESS  read-write
   STATUS      current
   DESCRIPTION
      "By way of this field, some manipulations
       on this table may be performed."
   ::= {er1646v2EthPortSwIXt2IpV6AddressesEntry 2}

er1646v2EthPortSwIXt2IpV6AddressesGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpV6AddressesEntry 10}

er1646v2EthPortSwIXt2IpV6AddressesTableIx OBJECT-TYPE
   SYNTAX      TableIndex
   MAX-ACCESS  not-accessible
   STATUS      current
   DESCRIPTION
      ""
   ::= {er1646v2EthPortSwIXt2IpV6AddressesEntry 11}

er1646v2EthPortSwIXt2IpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.ipV6.addresses.type

       Possibilities:
               unicast   (0)
               eui64   (1)
               anycast   (2)
               linkLocal   (3)
               generalPrefix   (4)"
   ::= {er1646v2EthPortSwIXt2IpV6AddressesEntry 50331648}

er1646v2EthPortSwIXt2IpV6AddressesAddress OBJECT-TYPE
   SYNTAX      Ipv6Address
   MAX-ACCESS  read-write
   STATUS      current
   DESCRIPTION
      "Path: swPort.editConf.ipV6.addresses.address

       ipv6 address"
   ::= {er1646v2EthPortSwIXt2IpV6AddressesEntry 16777216}

er1646v2EthPortSwIXt2IpV6AddressesPrefixLength OBJECT-TYPE
   SYNTAX      Integer32
   MAX-ACCESS  read-write
   STATUS      current
   DESCRIPTION
      "Path: swPort.editConf.ipV6.addresses.prefixLength"
   ::= {er1646v2EthPortSwIXt2IpV6AddressesEntry 33554432}

er1646v2EthPortSwIXt2IpV6AddressesGeneralPrefix OBJECT-TYPE
   SYNTAX      DisplayString
   MAX-ACCESS  read-write
   STATUS      current
   DESCRIPTION
      "Path: swPort.editConf.ipV6.addresses.generalPrefix"
   ::= {er1646v2EthPortSwIXt2IpV6AddressesEntry 83886080}

er1646v2EthPortSwIXt2IpV6AddressesRaSend OBJECT-TYPE
   SYNTAX      INTEGER
               {
               disabled (0),
               enabled (1)
               }
   MAX-ACCESS  read-write
   STATUS      current
   DESCRIPTION
      "Path: swPort.editConf.ipV6.addresses.ra.send

       Possibilities:
               disabled   (0)
               enabled   (1)"
   ::= {er1646v2EthPortSwIXt2IpV6AddressesEntry 67174400}

er1646v2EthPortSwIXt2IpV6AddressesRaOnLinkFlag OBJECT-TYPE
   SYNTAX      INTEGER
               {
               disabled (0),
               enabled (1)
               }
   MAX-ACCESS  read-write
   STATUS      current
   DESCRIPTION
      "Path: swPort.editConf.ipV6.addresses.ra.onLinkFlag

       Possibilities:
               disabled   (0)
               enabled   (1)"
   ::= {er1646v2EthPortSwIXt2IpV6AddressesEntry 67371008}

er1646v2EthPortSwIXt2IpV6AddressesRaAutoFlag OBJECT-TYPE
   SYNTAX      INTEGER
               {
               disabled (0),
               enabled (1)
               }
   MAX-ACCESS  read-write
   STATUS      current
   DESCRIPTION
      "Path: swPort.editConf.ipV6.addresses.ra.autonomousFlag

       Possibilities:
               disabled   (0)
               enabled   (1)"
   ::= {er1646v2EthPortSwIXt2IpV6AddressesEntry 67567616}

er1646v2EthPortSwIXt2IpV6AddressesRaValidLifeTime OBJECT-TYPE
   SYNTAX      TimeTicks
   MAX-ACCESS  read-write
   STATUS      current
   DESCRIPTION
      "Path: swPort.editConf.ipV6.addresses.ra.validLifeTime

       Time in centi-second."
   ::= {er1646v2EthPortSwIXt2IpV6AddressesEntry 67239936}

er1646v2EthPortSwIXt2IpV6AddressesRaValidLTMode OBJECT-TYPE
   SYNTAX      INTEGER
               {
               fixed (0),
               infinite (2)
               }
   MAX-ACCESS  read-write
   STATUS      current
   DESCRIPTION
      "Path: swPort.editConf.ipV6.addresses.ra.validLifeTimeMode

       Possibilities:
               fixed   (0)
               infinite   (2)"
   ::= {er1646v2EthPortSwIXt2IpV6AddressesEntry 67305472}

er1646v2EthPortSwIXt2IpV6AddressesRaPrefLifeTime OBJECT-TYPE
   SYNTAX      TimeTicks
   MAX-ACCESS  read-write
   STATUS      current
   DESCRIPTION
      "Path: swPort.editConf.ipV6.addresses.ra.prefLifeTime

       Time in centi-second."
   ::= {er1646v2EthPortSwIXt2IpV6AddressesEntry 67436544}

er1646v2EthPortSwIXt2IpV6AddressesRaPrefLTMode OBJECT-TYPE
   SYNTAX      INTEGER
               {
               fixed (0),
               infinite (2)
               }
   MAX-ACCESS  read-write
   STATUS      current
   DESCRIPTION
      "Path: swPort.editConf.ipV6.addresses.ra.prefLifeTimeMode

       Possibilities:
               fixed   (0)
               infinite   (2)"
   ::= {er1646v2EthPortSwIXt2IpV6AddressesEntry 67502080}

er1646v2EthPortSwIXt2IpV6RaDnsOptionsRdnssServers OBJECT-TYPE
   SYNTAX      SEQUENCE OF Er1646v2EthPortSwIXt2IpV6RaDnsOptionsRdnssServersEntry
   MAX-ACCESS  not-accessible
   STATUS      current
   DESCRIPTION
      ""
   ::= {er1646v2EthPortSwIXt2IpV6 101394432}

er1646v2EthPortSwIXt2IpV6RaDnsOptionsRdnssServersEntry OBJECT-TYPE
   SYNTAX      Er1646v2EthPortSwIXt2IpV6RaDnsOptionsRdnssServersEntry
   MAX-ACCESS  not-accessible
   STATUS      current
   DESCRIPTION
      ""
   INDEX      { er1646v2EthPortSwIXt2IpV6RaDnsOptionsRdnssServersGlobalIx,
                er1646v2EthPortSwIXt2IpV6RaDnsOptionsRdnssServersTableIx }
   ::= {er1646v2EthPortSwIXt2IpV6RaDnsOptionsRdnssServers 1}

Er1646v2EthPortSwIXt2IpV6RaDnsOptionsRdnssServersEntry ::=
   SEQUENCE
      {
      er1646v2EthPortSwIXt2IpV6RaDnsOptionsRdnssServersActions
         VariableLengthTableActions,
      er1646v2EthPortSwIXt2IpV6RaDnsOptionsRdnssServersGlobalIx
         GlobalIndex,
      er1646v2EthPortSwIXt2IpV6RaDnsOptionsRdnssServersTableIx
         TableIndex,
      er1646v2EthPortSwIXt2IpV6RaDnsOptionsRdnssServersAddress
         Ipv6Address
      }

er1646v2EthPortSwIXt2IpV6RaDnsOptionsRdnssServersActions OBJECT-TYPE
   SYNTAX      VariableLengthTableActions
   MAX-ACCESS  read-write
   STATUS      current
   DESCRIPTION
      "By way of this field, some manipulations
       on this table may be performed."
   ::= {er1646v2EthPortSwIXt2IpV6RaDnsOptionsRdnssServersEntry 2}

er1646v2EthPortSwIXt2IpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpV6RaDnsOptionsRdnssServersEntry 10}

er1646v2EthPortSwIXt2IpV6RaDnsOptionsRdnssServersTableIx OBJECT-TYPE
   SYNTAX      TableIndex
   MAX-ACCESS  not-accessible
   STATUS      current
   DESCRIPTION
      ""
   ::= {er1646v2EthPortSwIXt2IpV6RaDnsOptionsRdnssServersEntry 11}

er1646v2EthPortSwIXt2IpV6RaDnsOptionsRdnssServersAddress OBJECT-TYPE
   SYNTAX      Ipv6Address
   MAX-ACCESS  read-write
   STATUS      current
   DESCRIPTION
      "Path: swPort.editConf.ipV6.ra.dnsOptions.rdnss.servers.address

       ipv6 address"
   ::= {er1646v2EthPortSwIXt2IpV6RaDnsOptionsRdnssServersEntry 16777216}

er1646v2EthPortSwIXt2IpV6RaDnsOptionsDnsslDomains OBJECT-TYPE
   SYNTAX      SEQUENCE OF Er1646v2EthPortSwIXt2IpV6RaDnsOptionsDnsslDomainsEntry
   MAX-ACCESS  not-accessible
   STATUS      current
   DESCRIPTION
      ""
   ::= {er1646v2EthPortSwIXt2IpV6 101402624}

er1646v2EthPortSwIXt2IpV6RaDnsOptionsDnsslDomainsEntry OBJECT-TYPE
   SYNTAX      Er1646v2EthPortSwIXt2IpV6RaDnsOptionsDnsslDomainsEntry
   MAX-ACCESS  not-accessible
   STATUS      current
   DESCRIPTION
      ""
   INDEX      { er1646v2EthPortSwIXt2IpV6RaDnsOptionsDnsslDomainsGlobalIx,
                er1646v2EthPortSwIXt2IpV6RaDnsOptionsDnsslDomainsTableIx }
   ::= {er1646v2EthPortSwIXt2IpV6RaDnsOptionsDnsslDomains 1}

Er1646v2EthPortSwIXt2IpV6RaDnsOptionsDnsslDomainsEntry ::=
   SEQUENCE
      {
      er1646v2EthPortSwIXt2IpV6RaDnsOptionsDnsslDomainsActions
         VariableLengthTableActions,
      er1646v2EthPortSwIXt2IpV6RaDnsOptionsDnsslDomainsGlobalIx
         GlobalIndex,
      er1646v2EthPortSwIXt2IpV6RaDnsOptionsDnsslDomainsTableIx
         TableIndex,
      er1646v2EthPortSwIXt2IpV6RaDnsOptionsDnsslDomainsName
         DisplayString
      }

er1646v2EthPortSwIXt2IpV6RaDnsOptionsDnsslDomainsActions OBJECT-TYPE
   SYNTAX      VariableLengthTableActions
   MAX-ACCESS  read-write
   STATUS      current
   DESCRIPTION
      "By way of this field, some manipulations
       on this table may be performed."
   ::= {er1646v2EthPortSwIXt2IpV6RaDnsOptionsDnsslDomainsEntry 2}

er1646v2EthPortSwIXt2IpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpV6RaDnsOptionsDnsslDomainsEntry 10}

er1646v2EthPortSwIXt2IpV6RaDnsOptionsDnsslDomainsTableIx OBJECT-TYPE
   SYNTAX      TableIndex
   MAX-ACCESS  not-accessible
   STATUS      current
   DESCRIPTION
      ""
   ::= {er1646v2EthPortSwIXt2IpV6RaDnsOptionsDnsslDomainsEntry 11}

er1646v2EthPortSwIXt2IpV6RaDnsOptionsDnsslDomainsName OBJECT-TYPE
   SYNTAX      DisplayString
   MAX-ACCESS  read-write
   STATUS      current
   DESCRIPTION
      "Path: swPort.editConf.ipV6.ra.dnsOptions.dnssl.domains.name"
   ::= {er1646v2EthPortSwIXt2IpV6RaDnsOptionsDnsslDomainsEntry 16777216}

er1646v2EthPortSwIXt2IpV6DhcpClientUserClassOpt OBJECT-TYPE
   SYNTAX      SEQUENCE OF Er1646v2EthPortSwIXt2IpV6DhcpClientUserClassOptEntry
   MAX-ACCESS  not-accessible
   STATUS      current
   DESCRIPTION
      ""
   ::= {er1646v2EthPortSwIXt2IpV6 171442176}

er1646v2EthPortSwIXt2IpV6DhcpClientUserClassOptEntry OBJECT-TYPE
   SYNTAX      Er1646v2EthPortSwIXt2IpV6DhcpClientUserClassOptEntry
   MAX-ACCESS  not-accessible
   STATUS      current
   DESCRIPTION
      ""
   INDEX      { er1646v2EthPortSwIXt2IpV6DhcpClientUserClassOptGlobalIx,
                er1646v2EthPortSwIXt2IpV6DhcpClientUserClassOptTableIx }
   ::= {er1646v2EthPortSwIXt2IpV6DhcpClientUserClassOpt 1}

Er1646v2EthPortSwIXt2IpV6DhcpClientUserClassOptEntry ::=
   SEQUENCE
      {
      er1646v2EthPortSwIXt2IpV6DhcpClientUserClassOptActions
         VariableLengthTableActions,
      er1646v2EthPortSwIXt2IpV6DhcpClientUserClassOptGlobalIx
         GlobalIndex,
      er1646v2EthPortSwIXt2IpV6DhcpClientUserClassOptTableIx
         TableIndex,
      er1646v2EthPortSwIXt2IpV6DhcpClientUserClassOptValueAscii
         DisplayString,
      er1646v2EthPortSwIXt2IpV6DhcpClientUserClassOptValueDecimal
         Integer32,
      er1646v2EthPortSwIXt2IpV6DhcpClientUserClassOptValueHexData
         OCTET STRING
      }

er1646v2EthPortSwIXt2IpV6DhcpClientUserClassOptActions OBJECT-TYPE
   SYNTAX      VariableLengthTableActions
   MAX-ACCESS  read-write
   STATUS      current
   DESCRIPTION
      "By way of this field, some manipulations
       on this table may be performed."
   ::= {er1646v2EthPortSwIXt2IpV6DhcpClientUserClassOptEntry 2}

er1646v2EthPortSwIXt2IpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpV6DhcpClientUserClassOptEntry 10}

er1646v2EthPortSwIXt2IpV6DhcpClientUserClassOptTableIx OBJECT-TYPE
   SYNTAX      TableIndex
   MAX-ACCESS  not-accessible
   STATUS      current
   DESCRIPTION
      ""
   ::= {er1646v2EthPortSwIXt2IpV6DhcpClientUserClassOptEntry 11}

er1646v2EthPortSwIXt2IpV6DhcpClientUserClassOptValueAscii OBJECT-TYPE
   SYNTAX      DisplayString
   MAX-ACCESS  read-write
   STATUS      current
   DESCRIPTION
      "Path: swPort.editConf.ipV6.dhcp.client.userClassOpt.value.ascii"
   ::= {er1646v2EthPortSwIXt2IpV6DhcpClientUserClassOptEntry 16842752}

er1646v2EthPortSwIXt2IpV6DhcpClientUserClassOptValueDecimal OBJECT-TYPE
   SYNTAX      Integer32
   MAX-ACCESS  read-write
   STATUS      current
   DESCRIPTION
      "Path: swPort.editConf.ipV6.dhcp.client.userClassOpt.value.decimal"
   ::= {er1646v2EthPortSwIXt2IpV6DhcpClientUserClassOptEntry 16908288}

er1646v2EthPortSwIXt2IpV6DhcpClientUserClassOptValueHexData OBJECT-TYPE
   SYNTAX      OCTET STRING
   MAX-ACCESS  read-write
   STATUS      current
   DESCRIPTION
      "Path: swPort.editConf.ipV6.dhcp.client.userClassOpt.value.hexData"
   ::= {er1646v2EthPortSwIXt2IpV6DhcpClientUserClassOptEntry 16973824}

er1646v2EthPortSwIXt2IpV6DhcpClientVendorCl OBJECT-TYPE
   SYNTAX      SEQUENCE OF Er1646v2EthPortSwIXt2IpV6DhcpClientVendorClEntry
   MAX-ACCESS  not-accessible
   STATUS      current
   DESCRIPTION
      ""
   ::= {er1646v2EthPortSwIXt2IpV6 171704320}

er1646v2EthPortSwIXt2IpV6DhcpClientVendorClEntry OBJECT-TYPE
   SYNTAX      Er1646v2EthPortSwIXt2IpV6DhcpClientVendorClEntry
   MAX-ACCESS  not-accessible
   STATUS      current
   DESCRIPTION
      ""
   INDEX      { er1646v2EthPortSwIXt2IpV6DhcpClientVendorClGlobalIx,
                er1646v2EthPortSwIXt2IpV6DhcpClientVendorClTableIx }
   ::= {er1646v2EthPortSwIXt2IpV6DhcpClientVendorCl 1}

Er1646v2EthPortSwIXt2IpV6DhcpClientVendorClEntry ::=
   SEQUENCE
      {
      er1646v2EthPortSwIXt2IpV6DhcpClientVendorClActions
         VariableLengthTableActions,
      er1646v2EthPortSwIXt2IpV6DhcpClientVendorClGlobalIx
         GlobalIndex,
      er1646v2EthPortSwIXt2IpV6DhcpClientVendorClTableIx
         TableIndex,
      er1646v2EthPortSwIXt2IpV6DhcpClientVendorClValueAscii
         DisplayString,
      er1646v2EthPortSwIXt2IpV6DhcpClientVendorClValueDecimal
         Integer32,
      er1646v2EthPortSwIXt2IpV6DhcpClientVendorClValueHexData
         OCTET STRING
      }

er1646v2EthPortSwIXt2IpV6DhcpClientVendorClActions OBJECT-TYPE
   SYNTAX      VariableLengthTableActions
   MAX-ACCESS  read-write
   STATUS      current
   DESCRIPTION
      "By way of this field, some manipulations
       on this table may be performed."
   ::= {er1646v2EthPortSwIXt2IpV6DhcpClientVendorClEntry 2}

er1646v2EthPortSwIXt2IpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpV6DhcpClientVendorClEntry 10}

er1646v2EthPortSwIXt2IpV6DhcpClientVendorClTableIx OBJECT-TYPE
   SYNTAX      TableIndex
   MAX-ACCESS  not-accessible
   STATUS      current
   DESCRIPTION
      ""
   ::= {er1646v2EthPortSwIXt2IpV6DhcpClientVendorClEntry 11}

er1646v2EthPortSwIXt2IpV6DhcpClientVendorClValueAscii OBJECT-TYPE
   SYNTAX      DisplayString
   MAX-ACCESS  read-write
   STATUS      current
   DESCRIPTION
      "Path: swPort.editConf.ipV6.dhcp.client.vendorClassOpt.value.ascii"
   ::= {er1646v2EthPortSwIXt2IpV6DhcpClientVendorClEntry 16842752}

er1646v2EthPortSwIXt2IpV6DhcpClientVendorClValueDecimal OBJECT-TYPE
   SYNTAX      Integer32
   MAX-ACCESS  read-write
   STATUS      current
   DESCRIPTION
      "Path: swPort.editConf.ipV6.dhcp.client.vendorClassOpt.value.decimal"
   ::= {er1646v2EthPortSwIXt2IpV6DhcpClientVendorClEntry 16908288}

er1646v2EthPortSwIXt2IpV6DhcpClientVendorClValueHexData OBJECT-TYPE
   SYNTAX      OCTET STRING
   MAX-ACCESS  read-write
   STATUS      current
   DESCRIPTION
      "Path: swPort.editConf.ipV6.dhcp.client.vendorClassOpt.value.hexData"
   ::= {er1646v2EthPortSwIXt2IpV6DhcpClientVendorClEntry 16973824}

er1646v2EthPortSwIXt2IpV6DhcpRelayDestinations OBJECT-TYPE
   SYNTAX      SEQUENCE OF Er1646v2EthPortSwIXt2IpV6DhcpRelayDestinationsEntry
   MAX-ACCESS  not-accessible
   STATUS      current
   DESCRIPTION
      ""
   ::= {er1646v2EthPortSwIXt2IpV6 174080000}

er1646v2EthPortSwIXt2IpV6DhcpRelayDestinationsEntry OBJECT-TYPE
   SYNTAX      Er1646v2EthPortSwIXt2IpV6DhcpRelayDestinationsEntry
   MAX-ACCESS  not-accessible
   STATUS      current
   DESCRIPTION
      ""
   INDEX      { er1646v2EthPortSwIXt2IpV6DhcpRelayDestinationsGlobalIx,
                er1646v2EthPortSwIXt2IpV6DhcpRelayDestinationsTableIx }
   ::= {er1646v2EthPortSwIXt2IpV6DhcpRelayDestinations 1}

Er1646v2EthPortSwIXt2IpV6DhcpRelayDestinationsEntry ::=
   SEQUENCE
      {
      er1646v2EthPortSwIXt2IpV6DhcpRelayDestinationsActions
         VariableLengthTableActions,
      er1646v2EthPortSwIXt2IpV6DhcpRelayDestinationsGlobalIx
         GlobalIndex,
      er1646v2EthPortSwIXt2IpV6DhcpRelayDestinationsTableIx
         TableIndex,
      er1646v2EthPortSwIXt2IpV6DhcpRelayDestinationsAddress
         Ipv6Address,
      er1646v2EthPortSwIXt2IpV6DhcpRelayDestinationsInterface
         DisplayString
      }

er1646v2EthPortSwIXt2IpV6DhcpRelayDestinationsActions OBJECT-TYPE
   SYNTAX      VariableLengthTableActions
   MAX-ACCESS  read-write
   STATUS      current
   DESCRIPTION
      "By way of this field, some manipulations
       on this table may be performed."
   ::= {er1646v2EthPortSwIXt2IpV6DhcpRelayDestinationsEntry 2}

er1646v2EthPortSwIXt2IpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpV6DhcpRelayDestinationsEntry 10}

er1646v2EthPortSwIXt2IpV6DhcpRelayDestinationsTableIx OBJECT-TYPE
   SYNTAX      TableIndex
   MAX-ACCESS  not-accessible
   STATUS      current
   DESCRIPTION
      ""
   ::= {er1646v2EthPortSwIXt2IpV6DhcpRelayDestinationsEntry 11}

er1646v2EthPortSwIXt2IpV6DhcpRelayDestinationsAddress OBJECT-TYPE
   SYNTAX      Ipv6Address
   MAX-ACCESS  read-write
   STATUS      current
   DESCRIPTION
      "Path: swPort.editConf.ipV6.dhcp.relay.destinations.address

       ipv6 address"
   ::= {er1646v2EthPortSwIXt2IpV6DhcpRelayDestinationsEntry 16777216}

er1646v2EthPortSwIXt2IpV6DhcpRelayDestinationsInterface OBJECT-TYPE
   SYNTAX      DisplayString
   MAX-ACCESS  read-write
   STATUS      current
   DESCRIPTION
      "Path: swPort.editConf.ipV6.dhcp.relay.destinations.interface"
   ::= {er1646v2EthPortSwIXt2IpV6DhcpRelayDestinationsEntry 33554432}


er1646v2EthPortSwIXt2Mode OBJECT IDENTIFIER ::= {er1646v2EthPortSwIXt2 29}

er1646v2EthPortSwIXt2ModeTable OBJECT-TYPE
   SYNTAX      SEQUENCE OF Er1646v2EthPortSwIXt2ModeEntry
   MAX-ACCESS  not-accessible
   STATUS      current
   DESCRIPTION
      "routing and/or bridging or ipV6 or multilink selection"
   ::= {er1646v2EthPortSwIXt2Mode 1}

er1646v2EthPortSwIXt2ModeEntry OBJECT-TYPE
   SYNTAX      Er1646v2EthPortSwIXt2ModeEntry
   MAX-ACCESS  not-accessible
   STATUS      current
   DESCRIPTION
      ""
   INDEX      { er1646v2EthPortSwIXt2ModeGlobalIx }
   ::= {er1646v2EthPortSwIXt2ModeTable 1}

Er1646v2EthPortSwIXt2ModeEntry ::=
   SEQUENCE
      {
      er1646v2EthPortSwIXt2ModeGlobalIx
         GlobalIndex,
      er1646v2EthPortSwIXt2ModeValue
         INTEGER
      }

er1646v2EthPortSwIXt2ModeGlobalIx OBJECT-TYPE
   SYNTAX      GlobalIndex
   MAX-ACCESS  not-accessible
   STATUS      current
   DESCRIPTION
      "The value of the tlsCntTreeGlobalIndex of the MANAGED OBJECT."
   ::= {er1646v2EthPortSwIXt2ModeEntry 10}

er1646v2EthPortSwIXt2ModeValue OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: swPort.editConf.mode

       Possibilities:
               bridging   (0)
               routing   (1)
               routingAndBridging   (2)
               ipV6   (3)
               ipV6/ipV4   (4)
               multilink   (5)"
   ::= {er1646v2EthPortSwIXt2ModeEntry 2147483648}


er1646v2EthPortSwIXt2Ip OBJECT IDENTIFIER ::= {er1646v2EthPortSwIXt2 1}

er1646v2EthPortSwIXt2IpSSCTable OBJECT-TYPE
   SYNTAX      SEQUENCE OF Er1646v2EthPortSwIXt2IpEntry
   MAX-ACCESS  not-accessible
   STATUS      current
   DESCRIPTION
      "ip interface config parameters"
   ::= {er1646v2EthPortSwIXt2Ip 1}

er1646v2EthPortSwIXt2IpEntry OBJECT-TYPE
   SYNTAX      Er1646v2EthPortSwIXt2IpEntry
   MAX-ACCESS  not-accessible
   STATUS      current
   DESCRIPTION
      ""
   INDEX      { er1646v2EthPortSwIXt2IpGlobalIx }
   ::= {er1646v2EthPortSwIXt2IpSSCTable 1}

Er1646v2EthPortSwIXt2IpEntry ::=
   SEQUENCE
      {
      er1646v2EthPortSwIXt2IpGlobalIx
         GlobalIndex,
      er1646v2EthPortSwIXt2IpVrfRouter
         DisplayString,
      er1646v2EthPortSwIXt2IpAdr
         IpAddress,
      er1646v2EthPortSwIXt2IpNetm
         IpAddress,
      er1646v2EthPortSwIXt2IpSNetName
         INTEGER,
      er1646v2EthPortSwIXt2IpSNetCust
         DisplayString,
      er1646v2EthPortSwIXt2IpDhcpC
         INTEGER,
      er1646v2EthPortSwIXt2IpDhcpGatewayPreference
         Integer32,
      er1646v2EthPortSwIXt2IpDhcpRoutePreference
         Integer32,
      er1646v2EthPortSwIXt2IpDhcpDnsPreference
         Integer32,
      er1646v2EthPortSwIXt2IpMtu
         Integer32,
      er1646v2EthPortSwIXt2IpMssAdjust
         INTEGER,
      er1646v2EthPortSwIXt2IpRipMetric
         Integer32,
      er1646v2EthPortSwIXt2IpRipMetricOut
         Integer32,
      er1646v2EthPortSwIXt2IpRipMode
         INTEGER,
      er1646v2EthPortSwIXt2IpRipTxVer
         INTEGER,
      er1646v2EthPortSwIXt2IpRipRxVer
         INTEGER,
      er1646v2EthPortSwIXt2IpRipSplitH
         INTEGER,
      er1646v2EthPortSwIXt2IpRipAuth
         INTEGER,
      er1646v2EthPortSwIXt2IpRipFilter
         DisplayString,
      er1646v2EthPortSwIXt2IpRipFilterIn
         DisplayString,
      er1646v2EthPortSwIXt2IpRipClearNextHop
         INTEGER,
      er1646v2EthPortSwIXt2IpAccPol
         DisplayString,
      er1646v2EthPortSwIXt2IpAB
         DisplayString,
      er1646v2EthPortSwIXt2IpMA
         INTEGER,
      er1646v2EthPortSwIXt2IpMF
         Integer32,
      er1646v2EthPortSwIXt2IpDB
         INTEGER,
      er1646v2EthPortSwIXt2IpIR
         INTEGER,
      er1646v2EthPortSwIXt2IpIgmp
         INTEGER,
      er1646v2EthPortSwIXt2IpNN
         DisplayString,
      er1646v2EthPortSwIXt2IpVrrp
         INTEGER,
      er1646v2EthPortSwIXt2IpPimMode
         INTEGER,
      er1646v2EthPortSwIXt2IpPimDrPriority
         Counter32,
      er1646v2EthPortSwIXt2IpPimHelloTime
         TimeTicks,
      er1646v2EthPortSwIXt2IpPimPropagationDelay
         TimeTicks,
      er1646v2EthPortSwIXt2IpPimOverrideInterval
         TimeTicks,
      er1646v2EthPortSwIXt2IpPimBsrBorder
         INTEGER,
      er1646v2EthPortSwIXt2IpPimTtlThreshold
         Integer32,
      er1646v2EthPortSwIXt2IpIMNetworkUnreachable
         INTEGER,
      er1646v2EthPortSwIXt2IpIMHostUnreachable
         INTEGER,
      er1646v2EthPortSwIXt2IpIMProtocolUnreachable
         INTEGER,
      er1646v2EthPortSwIXt2IpIMPortUnreachable
         INTEGER,
      er1646v2EthPortSwIXt2IpIMMtuExceeded
         INTEGER,
      er1646v2EthPortSwIXt2IpIMAdminProhibited
         INTEGER,
      er1646v2EthPortSwIXt2IpIMTtlExceeded
         INTEGER,
      er1646v2EthPortSwIXt2IpIMRedirect
         INTEGER
      }

er1646v2EthPortSwIXt2IpGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpEntry 10}

er1646v2EthPortSwIXt2IpVrfRouter OBJECT-TYPE
   SYNTAX      DisplayString
   MAX-ACCESS  read-write
   STATUS      current
   DESCRIPTION
      "Path: swPort.editConf.ip.vrfRouter"
   ::= {er1646v2EthPortSwIXt2IpEntry 738197504}

er1646v2EthPortSwIXt2IpAdr OBJECT-TYPE
   SYNTAX      IpAddress
   MAX-ACCESS  read-write
   STATUS      current
   DESCRIPTION
      "Path: swPort.editConf.ip.address"
   ::= {er1646v2EthPortSwIXt2IpEntry 2030043136}

er1646v2EthPortSwIXt2IpNetm OBJECT-TYPE
   SYNTAX      IpAddress
   MAX-ACCESS  read-write
   STATUS      current
   DESCRIPTION
      "Path: swPort.editConf.ip.netMask"
   ::= {er1646v2EthPortSwIXt2IpEntry 2063597568}

er1646v2EthPortSwIXt2IpSNetName OBJECT-TYPE
   SYNTAX      INTEGER
               {
               slOPTg (0),
               corp (2),
               dmz (3),
               internet (1)
               }
   MAX-ACCESS  read-write
   STATUS      current
   DESCRIPTION
      "Path: swPort.editConf.ip.sNet.name

       Possibilities:
               <OPT>   (0)
               corp   (2)
               dmz   (3)
               internet   (1)"
   ::= {er1646v2EthPortSwIXt2IpEntry 855703552}

er1646v2EthPortSwIXt2IpSNetCust OBJECT-TYPE
   SYNTAX      DisplayString
   MAX-ACCESS  read-write
   STATUS      current
   DESCRIPTION
      "Path: swPort.editConf.ip.sNet.custom"
   ::= {er1646v2EthPortSwIXt2IpEntry 855769088}

er1646v2EthPortSwIXt2IpDhcpC OBJECT-TYPE
   SYNTAX      INTEGER
               {
               disabled (0),
               enabled (1)
               }
   MAX-ACCESS  read-write
   STATUS      current
   DESCRIPTION
      "Path: swPort.editConf.ip.dhcpClient

       Possibilities:
               disabled   (0)
               enabled   (1)"
   ::= {er1646v2EthPortSwIXt2IpEntry 838860800}

er1646v2EthPortSwIXt2IpDhcpGatewayPreference OBJECT-TYPE
   SYNTAX      Integer32
   MAX-ACCESS  read-write
   STATUS      current
   DESCRIPTION
      "Path: swPort.editConf.ip.dhcp.gatewayPreference"
   ::= {er1646v2EthPortSwIXt2IpEntry 872480768}

er1646v2EthPortSwIXt2IpDhcpRoutePreference OBJECT-TYPE
   SYNTAX      Integer32
   MAX-ACCESS  read-write
   STATUS      current
   DESCRIPTION
      "Path: swPort.editConf.ip.dhcp.routePreference"
   ::= {er1646v2EthPortSwIXt2IpEntry 872546304}

er1646v2EthPortSwIXt2IpDhcpDnsPreference OBJECT-TYPE
   SYNTAX      Integer32
   MAX-ACCESS  read-write
   STATUS      current
   DESCRIPTION
      "Path: swPort.editConf.ip.dhcp.dnsPreference"
   ::= {er1646v2EthPortSwIXt2IpEntry 872611840}

er1646v2EthPortSwIXt2IpMtu OBJECT-TYPE
   SYNTAX      Integer32
   MAX-ACCESS  read-write
   STATUS      current
   DESCRIPTION
      "Path: swPort.editConf.ip.mtu"
   ::= {er1646v2EthPortSwIXt2IpEntry 671088640}

er1646v2EthPortSwIXt2IpMssAdjust OBJECT-TYPE
   SYNTAX      INTEGER
               {
               disabled (0),
               auto (65536)
               }
   MAX-ACCESS  read-write
   STATUS      current
   DESCRIPTION
      "Path: swPort.editConf.ip.mssAdjust

       Possibilities:
               disabled   (0)
               auto   (65536)"
   ::= {er1646v2EthPortSwIXt2IpEntry 754974720}

er1646v2EthPortSwIXt2IpRipMetric OBJECT-TYPE
   SYNTAX      Integer32
   MAX-ACCESS  read-write
   STATUS      current
   DESCRIPTION
      "Path: swPort.editConf.ip.rip.metric"
   ::= {er1646v2EthPortSwIXt2IpEntry 353566720}

er1646v2EthPortSwIXt2IpRipMetricOut OBJECT-TYPE
   SYNTAX      Integer32
   MAX-ACCESS  read-write
   STATUS      current
   DESCRIPTION
      "Path: swPort.editConf.ip.rip.metricOut"
   ::= {er1646v2EthPortSwIXt2IpEntry 353632256}

er1646v2EthPortSwIXt2IpRipMode OBJECT-TYPE
   SYNTAX      INTEGER
               {
               disabled (0),
               passive (1),
               active (2)
               }
   MAX-ACCESS  read-write
   STATUS      current
   DESCRIPTION
      "Path: swPort.editConf.ip.rip.mode

       Possibilities:
               disabled   (0)
               passive   (1)
               active   (2)"
   ::= {er1646v2EthPortSwIXt2IpEntry 353697792}

er1646v2EthPortSwIXt2IpRipTxVer OBJECT-TYPE
   SYNTAX      INTEGER
               {
               rip1 (0),
               rip2 (1),
               rip1mcompatible (2)
               }
   MAX-ACCESS  read-write
   STATUS      current
   DESCRIPTION
      "Path: swPort.editConf.ip.rip.txVersion

       Possibilities:
               rip1   (0)
               rip2   (1)
               rip1-compatible   (2)"
   ::= {er1646v2EthPortSwIXt2IpEntry 354615296}

er1646v2EthPortSwIXt2IpRipRxVer OBJECT-TYPE
   SYNTAX      INTEGER
               {
               rip1only (0),
               rip2only (1),
               rip12 (2)
               }
   MAX-ACCESS  read-write
   STATUS      current
   DESCRIPTION
      "Path: swPort.editConf.ip.rip.rxVersion

       Possibilities:
               rip1only   (0)
               rip2only   (1)
               rip1&2   (2)"
   ::= {er1646v2EthPortSwIXt2IpEntry 354680832}

er1646v2EthPortSwIXt2IpRipSplitH OBJECT-TYPE
   SYNTAX      INTEGER
               {
               disabled (0),
               enabled (1),
               poisonedReverse (2)
               }
   MAX-ACCESS  read-write
   STATUS      current
   DESCRIPTION
      "Path: swPort.editConf.ip.rip.splitHorizon

       Possibilities:
               disabled   (0)
               enabled   (1)
               poisonedReverse   (2)"
   ::= {er1646v2EthPortSwIXt2IpEntry 353828864}

er1646v2EthPortSwIXt2IpRipAuth OBJECT-TYPE
   SYNTAX      INTEGER
               {
               disabled (0),
               texts (1),
               md5 (2)
               }
   MAX-ACCESS  read-write
   STATUS      current
   DESCRIPTION
      "Path: swPort.editConf.ip.rip.authentication

       Possibilities:
               disabled   (0)
               text    (1)
               md5   (2)"
   ::= {er1646v2EthPortSwIXt2IpEntry 353501184}

er1646v2EthPortSwIXt2IpRipFilter OBJECT-TYPE
   SYNTAX      DisplayString
   MAX-ACCESS  read-write
   STATUS      current
   DESCRIPTION
      "Path: swPort.editConf.ip.rip.filter"
   ::= {er1646v2EthPortSwIXt2IpEntry 354418688}

er1646v2EthPortSwIXt2IpRipFilterIn OBJECT-TYPE
   SYNTAX      DisplayString
   MAX-ACCESS  read-write
   STATUS      current
   DESCRIPTION
      "Path: swPort.editConf.ip.rip.filterIn"
   ::= {er1646v2EthPortSwIXt2IpEntry 354484224}

er1646v2EthPortSwIXt2IpRipClearNextHop OBJECT-TYPE
   SYNTAX      INTEGER
               {
               disabled (0),
               enabled (1)
               }
   MAX-ACCESS  read-write
   STATUS      current
   DESCRIPTION
      "Path: swPort.editConf.ip.rip.clearNextHop

       Possibilities:
               disabled   (0)
               enabled   (1)"
   ::= {er1646v2EthPortSwIXt2IpEntry 352452608}

er1646v2EthPortSwIXt2IpAccPol OBJECT-TYPE
   SYNTAX      DisplayString
   MAX-ACCESS  read-write
   STATUS      current
   DESCRIPTION
      "Path: swPort.editConf.ip.accessPolicy"
   ::= {er1646v2EthPortSwIXt2IpEntry 704643072}

er1646v2EthPortSwIXt2IpAB OBJECT-TYPE
   SYNTAX      DisplayString
   MAX-ACCESS  read-write
   STATUS      current
   DESCRIPTION
      "Path: swPort.editConf.ip.trafficPolicy"
   ::= {er1646v2EthPortSwIXt2IpEntry 234881024}

er1646v2EthPortSwIXt2IpMA OBJECT-TYPE
   SYNTAX      INTEGER
               {
               disabled (0),
               enabled (1)
               }
   MAX-ACCESS  read-write
   STATUS      current
   DESCRIPTION
      "Path: swPort.editConf.ip.mgmtAccess

       Possibilities:
               disabled   (0)
               enabled   (1)"
   ::= {er1646v2EthPortSwIXt2IpEntry 268435456}

er1646v2EthPortSwIXt2IpMF OBJECT-TYPE
   SYNTAX      Integer32
   MAX-ACCESS  read-write
   STATUS      current
   DESCRIPTION
      "Path: swPort.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EthPortSwIXt2IpEntry 285212672}

er1646v2EthPortSwIXt2IpDB OBJECT-TYPE
   SYNTAX      INTEGER
               {
               disabled (0),
               enabled (1)
               }
   MAX-ACCESS  read-write
   STATUS      current
   DESCRIPTION
      "Path: swPort.editConf.ip.directedBroadcasts

       Possibilities:
               disabled   (0)
               enabled   (1)"
   ::= {er1646v2EthPortSwIXt2IpEntry 369098752}

er1646v2EthPortSwIXt2IpIR OBJECT-TYPE
   SYNTAX      INTEGER
               {
               disabled (0),
               enabled (1)
               }
   MAX-ACCESS  read-write
   STATUS      current
   DESCRIPTION
      "Path: swPort.editConf.ip.icmpRedirects

       Possibilities:
               disabled   (0)
               enabled   (1)"
   ::= {er1646v2EthPortSwIXt2IpEntry 436207616}

er1646v2EthPortSwIXt2IpIgmp OBJECT-TYPE
   SYNTAX      INTEGER
               {
               disabled (0),
               proxy (1),
               router (2),
               v3Router (5)
               }
   MAX-ACCESS  read-write
   STATUS      current
   DESCRIPTION
      "Path: swPort.editConf.ip.igmp

       Possibilities:
               disabled   (0)
               proxy   (1)
               router   (2)
               v3Router   (5)"
   ::= {er1646v2EthPortSwIXt2IpEntry 536870912}

er1646v2EthPortSwIXt2IpNN OBJECT-TYPE
   SYNTAX      DisplayString
   MAX-ACCESS  read-write
   STATUS      current
   DESCRIPTION
      "Path: swPort.editConf.ip.nat"
   ::= {er1646v2EthPortSwIXt2IpEntry 452984832}

er1646v2EthPortSwIXt2IpVrrp OBJECT-TYPE
   SYNTAX      INTEGER
               {
               disabled (0),
               enabled (1)
               }
   MAX-ACCESS  read-write
   STATUS      current
   DESCRIPTION
      "Path: swPort.editConf.ip.vrrp

       Possibilities:
               disabled   (0)
               enabled   (1)"
   ::= {er1646v2EthPortSwIXt2IpEntry 721420288}

er1646v2EthPortSwIXt2IpPimMode OBJECT-TYPE
   SYNTAX      INTEGER
               {
               disabled (0),
               sparse (1),
               passive (2)
               }
   MAX-ACCESS  read-write
   STATUS      current
   DESCRIPTION
      "Path: swPort.editConf.ip.pim.mode

       Possibilities:
               disabled   (0)
               sparse   (1)
               passive   (2)"
   ::= {er1646v2EthPortSwIXt2IpEntry 771817472}

er1646v2EthPortSwIXt2IpPimDrPriority OBJECT-TYPE
   SYNTAX      Counter32
   MAX-ACCESS  read-write
   STATUS      current
   DESCRIPTION
      "Path: swPort.editConf.ip.pim.drPriority

       32 bit unsigned wrappable counter."
   ::= {er1646v2EthPortSwIXt2IpEntry 771883008}

er1646v2EthPortSwIXt2IpPimHelloTime OBJECT-TYPE
   SYNTAX      TimeTicks
   MAX-ACCESS  read-write
   STATUS      current
   DESCRIPTION
      "Path: swPort.editConf.ip.pim.helloTime

       Time in centi-second."
   ::= {er1646v2EthPortSwIXt2IpEntry 771948544}

er1646v2EthPortSwIXt2IpPimPropagationDelay OBJECT-TYPE
   SYNTAX      TimeTicks
   MAX-ACCESS  read-write
   STATUS      current
   DESCRIPTION
      "Path: swPort.editConf.ip.pim.propagationDelay

       Time in centi-second."
   ::= {er1646v2EthPortSwIXt2IpEntry 772014080}

er1646v2EthPortSwIXt2IpPimOverrideInterval OBJECT-TYPE
   SYNTAX      TimeTicks
   MAX-ACCESS  read-write
   STATUS      current
   DESCRIPTION
      "Path: swPort.editConf.ip.pim.overrideInterval

       Time in centi-second."
   ::= {er1646v2EthPortSwIXt2IpEntry 772079616}

er1646v2EthPortSwIXt2IpPimBsrBorder OBJECT-TYPE
   SYNTAX      INTEGER
               {
               disabled (0),
               enabled (1)
               }
   MAX-ACCESS  read-write
   STATUS      current
   DESCRIPTION
      "Path: swPort.editConf.ip.pim.bsrBorder

       Possibilities:
               disabled   (0)
               enabled   (1)"
   ::= {er1646v2EthPortSwIXt2IpEntry 772145152}

er1646v2EthPortSwIXt2IpPimTtlThreshold OBJECT-TYPE
   SYNTAX      Integer32
   MAX-ACCESS  read-write
   STATUS      current
   DESCRIPTION
      "Path: swPort.editConf.ip.pim.ttlThreshold"
   ::= {er1646v2EthPortSwIXt2IpEntry 772210688}

er1646v2EthPortSwIXt2IpIMNetworkUnreachable OBJECT-TYPE
   SYNTAX      INTEGER
               {
               disabled (0),
               enabled (1)
               }
   MAX-ACCESS  read-write
   STATUS      current
   DESCRIPTION
      "Path: swPort.editConf.ip.icmpMessages.networkUnreachable

       Possibilities:
               disabled   (0)
               enabled   (1)"
   ::= {er1646v2EthPortSwIXt2IpEntry 788594688}

er1646v2EthPortSwIXt2IpIMHostUnreachable OBJECT-TYPE
   SYNTAX      INTEGER
               {
               disabled (0),
               enabled (1)
               }
   MAX-ACCESS  read-write
   STATUS      current
   DESCRIPTION
      "Path: swPort.editConf.ip.icmpMessages.hostUnreachable

       Possibilities:
               disabled   (0)
               enabled   (1)"
   ::= {er1646v2EthPortSwIXt2IpEntry 788660224}

er1646v2EthPortSwIXt2IpIMProtocolUnreachable OBJECT-TYPE
   SYNTAX      INTEGER
               {
               disabled (0),
               enabled (1)
               }
   MAX-ACCESS  read-write
   STATUS      current
   DESCRIPTION
      "Path: swPort.editConf.ip.icmpMessages.protocolUnreachable

       Possibilities:
               disabled   (0)
               enabled   (1)"
   ::= {er1646v2EthPortSwIXt2IpEntry 788725760}

er1646v2EthPortSwIXt2IpIMPortUnreachable OBJECT-TYPE
   SYNTAX      INTEGER
               {
               disabled (0),
               enabled (1)
               }
   MAX-ACCESS  read-write
   STATUS      current
   DESCRIPTION
      "Path: swPort.editConf.ip.icmpMessages.portUnreachable

       Possibilities:
               disabled   (0)
               enabled   (1)"
   ::= {er1646v2EthPortSwIXt2IpEntry 788791296}

er1646v2EthPortSwIXt2IpIMMtuExceeded OBJECT-TYPE
   SYNTAX      INTEGER
               {
               disabled (0),
               enabled (1)
               }
   MAX-ACCESS  read-write
   STATUS      current
   DESCRIPTION
      "Path: swPort.editConf.ip.icmpMessages.mtuExceeded

       Possibilities:
               disabled   (0)
               enabled   (1)"
   ::= {er1646v2EthPortSwIXt2IpEntry 788856832}

er1646v2EthPortSwIXt2IpIMAdminProhibited OBJECT-TYPE
   SYNTAX      INTEGER
               {
               disabled (0),
               enabled (1)
               }
   MAX-ACCESS  read-write
   STATUS      current
   DESCRIPTION
      "Path: swPort.editConf.ip.icmpMessages.adminProhibited

       Possibilities:
               disabled   (0)
               enabled   (1)"
   ::= {er1646v2EthPortSwIXt2IpEntry 788922368}

er1646v2EthPortSwIXt2IpIMTtlExceeded OBJECT-TYPE
   SYNTAX      INTEGER
               {
               disabled (0),
               enabled (1)
               }
   MAX-ACCESS  read-write
   STATUS      current
   DESCRIPTION
      "Path: swPort.editConf.ip.icmpMessages.ttlExceeded

       Possibilities:
               disabled   (0)
               enabled   (1)"
   ::= {er1646v2EthPortSwIXt2IpEntry 788987904}

er1646v2EthPortSwIXt2IpIMRedirect OBJECT-TYPE
   SYNTAX      INTEGER
               {
               disabled (0),
               enabled (1)
               }
   MAX-ACCESS  read-write
   STATUS      current
   DESCRIPTION
      "Path: swPort.editConf.ip.icmpMessages.redirect

       Possibilities:
               disabled   (0)
               enabled   (1)"
   ::= {er1646v2EthPortSwIXt2IpEntry 789053440}

er1646v2EthPortSwIXt2IpSaddr OBJECT-TYPE
   SYNTAX      SEQUENCE OF Er1646v2EthPortSwIXt2IpSaddrEntry
   MAX-ACCESS  not-accessible
   STATUS      current
   DESCRIPTION
      ""
   ::= {er1646v2EthPortSwIXt2Ip 385875968}

er1646v2EthPortSwIXt2IpSaddrEntry OBJECT-TYPE
   SYNTAX      Er1646v2EthPortSwIXt2IpSaddrEntry
   MAX-ACCESS  not-accessible
   STATUS      current
   DESCRIPTION
      ""
   INDEX      { er1646v2EthPortSwIXt2IpSaddrGlobalIx,
                er1646v2EthPortSwIXt2IpSaddrTableIx }
   ::= {er1646v2EthPortSwIXt2IpSaddr 1}

Er1646v2EthPortSwIXt2IpSaddrEntry ::=
   SEQUENCE
      {
      er1646v2EthPortSwIXt2IpSaddrActions
         VariableLengthTableActions,
      er1646v2EthPortSwIXt2IpSaddrGlobalIx
         GlobalIndex,
      er1646v2EthPortSwIXt2IpSaddrTableIx
         TableIndex,
      er1646v2EthPortSwIXt2IpSaddrAddress
         IpAddress,
      er1646v2EthPortSwIXt2IpSaddrNetMask
         IpAddress
      }

er1646v2EthPortSwIXt2IpSaddrActions OBJECT-TYPE
   SYNTAX      VariableLengthTableActions
   MAX-ACCESS  read-write
   STATUS      current
   DESCRIPTION
      "By way of this field, some manipulations
       on this table may be performed."
   ::= {er1646v2EthPortSwIXt2IpSaddrEntry 2}

er1646v2EthPortSwIXt2IpSaddrGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpSaddrEntry 10}

er1646v2EthPortSwIXt2IpSaddrTableIx OBJECT-TYPE
   SYNTAX      TableIndex
   MAX-ACCESS  not-accessible
   STATUS      current
   DESCRIPTION
      ""
   ::= {er1646v2EthPortSwIXt2IpSaddrEntry 11}

er1646v2EthPortSwIXt2IpSaddrAddress OBJECT-TYPE
   SYNTAX      IpAddress
   MAX-ACCESS  read-write
   STATUS      current
   DESCRIPTION
      "Path: swPort.editConf.ip.secondaryIp.address"
   ::= {er1646v2EthPortSwIXt2IpSaddrEntry 2030043136}

er1646v2EthPortSwIXt2IpSaddrNetMask OBJECT-TYPE
   SYNTAX      IpAddress
   MAX-ACCESS  read-write
   STATUS      current
   DESCRIPTION
      "Path: swPort.editConf.ip.secondaryIp.netMask"
   ::= {er1646v2EthPortSwIXt2IpSaddrEntry 2063597568}

er1646v2EthPortSwIXt2IpH OBJECT-TYPE
   SYNTAX      SEQUENCE OF Er1646v2EthPortSwIXt2IpHEntry
   MAX-ACCESS  not-accessible
   STATUS      current
   DESCRIPTION
      ""
   ::= {er1646v2EthPortSwIXt2Ip 251658240}

er1646v2EthPortSwIXt2IpHEntry OBJECT-TYPE
   SYNTAX      Er1646v2EthPortSwIXt2IpHEntry
   MAX-ACCESS  not-accessible
   STATUS      current
   DESCRIPTION
      ""
   INDEX      { er1646v2EthPortSwIXt2IpHGlobalIx,
                er1646v2EthPortSwIXt2IpHTableIx }
   ::= {er1646v2EthPortSwIXt2IpH 1}

Er1646v2EthPortSwIXt2IpHEntry ::=
   SEQUENCE
      {
      er1646v2EthPortSwIXt2IpHActions
         VariableLengthTableActions,
      er1646v2EthPortSwIXt2IpHGlobalIx
         GlobalIndex,
      er1646v2EthPortSwIXt2IpHTableIx
         TableIndex,
      er1646v2EthPortSwIXt2IpHAddress
         IpAddress,
      er1646v2EthPortSwIXt2IpHDhcpRelayOptionSubscriberId
         DisplayString
      }

er1646v2EthPortSwIXt2IpHActions OBJECT-TYPE
   SYNTAX      VariableLengthTableActions
   MAX-ACCESS  read-write
   STATUS      current
   DESCRIPTION
      "By way of this field, some manipulations
       on this table may be performed."
   ::= {er1646v2EthPortSwIXt2IpHEntry 2}

er1646v2EthPortSwIXt2IpHGlobalIx OBJECT-TYPE
   SYNTAX      GlobalIndex
   MAX-ACCESS  not-accessible
   STATUS      current
   DESCRIPTION
      "The value of the tlsCntTreeGlobalIndex of the MANAGED OBJECT."
   ::= {er1646v2EthPortSwIXt2IpHEntry 10}

er1646v2EthPortSwIXt2IpHTableIx OBJECT-TYPE
   SYNTAX      TableIndex
   MAX-ACCESS  not-accessible
   STATUS      current
   DESCRIPTION
      ""
   ::= {er1646v2EthPortSwIXt2IpHEntry 11}

er1646v2EthPortSwIXt2IpHAddress OBJECT-TYPE
   SYNTAX      IpAddress
   MAX-ACCESS  read-write
   STATUS      current
   DESCRIPTION
      "Path: swPort.editConf.ip.helpers.address"
   ::= {er1646v2EthPortSwIXt2IpHEntry 16777216}

er1646v2EthPortSwIXt2IpHDhcpRelayOptionSubscriberId OBJECT-TYPE
   SYNTAX      DisplayString
   MAX-ACCESS  read-write
   STATUS      current
   DESCRIPTION
      "Path: swPort.editConf.ip.helpers.dhcpRelayOption.subscriberId"
   ::= {er1646v2EthPortSwIXt2IpHEntry 33947648}


er1646v2EthPortSwIXt2Name OBJECT IDENTIFIER ::= {er1646v2EthPortSwIXt2 2}

er1646v2EthPortSwIXt2NameTable OBJECT-TYPE
   SYNTAX      SEQUENCE OF Er1646v2EthPortSwIXt2NameEntry
   MAX-ACCESS  not-accessible
   STATUS      current
   DESCRIPTION
      "config interface name"
   ::= {er1646v2EthPortSwIXt2Name 1}

er1646v2EthPortSwIXt2NameEntry OBJECT-TYPE
   SYNTAX      Er1646v2EthPortSwIXt2NameEntry
   MAX-ACCESS  not-accessible
   STATUS      current
   DESCRIPTION
      ""
   INDEX      { er1646v2EthPortSwIXt2NameGlobalIx }
   ::= {er1646v2EthPortSwIXt2NameTable 1}

Er1646v2EthPortSwIXt2NameEntry ::=
   SEQUENCE
      {
      er1646v2EthPortSwIXt2NameGlobalIx
         GlobalIndex,
      er1646v2EthPortSwIXt2NameValue
         DisplayString
      }

er1646v2EthPortSwIXt2NameGlobalIx OBJECT-TYPE
   SYNTAX      GlobalIndex
   MAX-ACCESS  not-accessible
   STATUS      current
   DESCRIPTION
      "The value of the tlsCntTreeGlobalIndex of the MANAGED OBJECT."
   ::= {er1646v2EthPortSwIXt2NameEntry 10}

er1646v2EthPortSwIXt2NameValue OBJECT-TYPE
   SYNTAX      DisplayString
   MAX-ACCESS  read-write
   STATUS      current
   DESCRIPTION
      "Path: swPort.editConf.name"
   ::= {er1646v2EthPortSwIXt2NameEntry 2147483648}


er1646v2EthPortSwIXt2Bw OBJECT IDENTIFIER ::= {er1646v2EthPortSwIXt2 5}

er1646v2EthPortSwIXt2BwSSCTable OBJECT-TYPE
   SYNTAX      SEQUENCE OF Er1646v2EthPortSwIXt2BwEntry
   MAX-ACCESS  not-accessible
   STATUS      current
   DESCRIPTION
      ""
   ::= {er1646v2EthPortSwIXt2Bw 1}

er1646v2EthPortSwIXt2BwEntry OBJECT-TYPE
   SYNTAX      Er1646v2EthPortSwIXt2BwEntry
   MAX-ACCESS  not-accessible
   STATUS      current
   DESCRIPTION
      ""
   INDEX      { er1646v2EthPortSwIXt2BwGlobalIx }
   ::= {er1646v2EthPortSwIXt2BwSSCTable 1}

Er1646v2EthPortSwIXt2BwEntry ::=
   SEQUENCE
      {
      er1646v2EthPortSwIXt2BwGlobalIx
         GlobalIndex,
      er1646v2EthPortSwIXt2BwMode
         INTEGER,
      er1646v2EthPortSwIXt2BwCir
         Integer32,
      er1646v2EthPortSwIXt2BwEir
         Integer32,
      er1646v2EthPortSwIXt2BwUnit
         INTEGER,
      er1646v2EthPortSwIXt2BwTc
         INTEGER,
      er1646v2EthPortSwIXt2BwTcFactor
         INTEGER,
      er1646v2EthPortSwIXt2BwCorrType
         INTEGER,
      er1646v2EthPortSwIXt2BwCorrPredefEncapsFrameRelay
         DisplayString,
      er1646v2EthPortSwIXt2BwCorrPredefEncapsPpp
         DisplayString,
      er1646v2EthPortSwIXt2BwCorrPredefEncapsAtmHl
         INTEGER,
      er1646v2EthPortSwIXt2BwCorrPredefEncapsAtmMp
         INTEGER,
      er1646v2EthPortSwIXt2BwCorrPredefEncapsHdlc
         DisplayString,
      er1646v2EthPortSwIXt2BwCorrPredefEncapsEfmFs
         Integer32,
      er1646v2EthPortSwIXt2BwCorrPredefEncapsEfmIb
         Integer32,
      er1646v2EthPortSwIXt2BwCorrPredefMode
         INTEGER,
      er1646v2EthPortSwIXt2BwCorrManualOverhead
         Integer32,
      er1646v2EthPortSwIXt2BwCorrManualFrameData
         Counter32,
      er1646v2EthPortSwIXt2BwCorrManualFrameHeader
         Counter32,
      er1646v2EthPortSwIXt2BwMaxFifoQLen
         Integer32,
      er1646v2EthPortSwIXt2BwDeFlagCir
         INTEGER,
      er1646v2EthPortSwIXt2BwDeFlagEir
         INTEGER,
      er1646v2EthPortSwIXt2BwDeFlagViolate
         INTEGER,
      er1646v2EthPortSwIXt2BwActCirActNone
         OCTET STRING,
      er1646v2EthPortSwIXt2BwActCirActEthCos1
         INTEGER,
      er1646v2EthPortSwIXt2BwActCirActEthDei1
         INTEGER,
      er1646v2EthPortSwIXt2BwActCirActEthCos2
         INTEGER,
      er1646v2EthPortSwIXt2BwActCirActEthDei2
         INTEGER,
      er1646v2EthPortSwIXt2BwActCirActEthCos3
         INTEGER,
      er1646v2EthPortSwIXt2BwActCirActEthDei3
         INTEGER,
      er1646v2EthPortSwIXt2BwActCirActEthCos4
         INTEGER,
      er1646v2EthPortSwIXt2BwActCirActEthDei4
         INTEGER,
      er1646v2EthPortSwIXt2BwActCirActEthCos5
         INTEGER,
      er1646v2EthPortSwIXt2BwActCirActEthDei5
         INTEGER,
      er1646v2EthPortSwIXt2BwActCirActEthCos6
         INTEGER,
      er1646v2EthPortSwIXt2BwActCirActEthDei6
         INTEGER,
      er1646v2EthPortSwIXt2BwActCirActEthCos7
         INTEGER,
      er1646v2EthPortSwIXt2BwActCirActEthDei7
         INTEGER,
      er1646v2EthPortSwIXt2BwActCirActEthCos8
         INTEGER,
      er1646v2EthPortSwIXt2BwActCirActEthDei8
         INTEGER,
      er1646v2EthPortSwIXt2BwActCirActEthTos
         INTEGER,
      er1646v2EthPortSwIXt2BwActCirActEthQueue
         INTEGER,
      er1646v2EthPortSwIXt2BwActCirActEthDrpLev
         INTEGER,
      er1646v2EthPortSwIXt2BwActCirActEthDeFlag
         INTEGER,
      er1646v2EthPortSwIXt2BwActCirActIpTos
         INTEGER,
      er1646v2EthPortSwIXt2BwActCirActIpQueue
         INTEGER,
      er1646v2EthPortSwIXt2BwActCirActIpDrpLev
         INTEGER,
      er1646v2EthPortSwIXt2BwActCirActIpDeFlag
         INTEGER,
      er1646v2EthPortSwIXt2BwActEirActNone
         OCTET STRING,
      er1646v2EthPortSwIXt2BwActEirActEthCos1
         INTEGER,
      er1646v2EthPortSwIXt2BwActEirActEthDei1
         INTEGER,
      er1646v2EthPortSwIXt2BwActEirActEthCos2
         INTEGER,
      er1646v2EthPortSwIXt2BwActEirActEthDei2
         INTEGER,
      er1646v2EthPortSwIXt2BwActEirActEthCos3
         INTEGER,
      er1646v2EthPortSwIXt2BwActEirActEthDei3
         INTEGER,
      er1646v2EthPortSwIXt2BwActEirActEthCos4
         INTEGER,
      er1646v2EthPortSwIXt2BwActEirActEthDei4
         INTEGER,
      er1646v2EthPortSwIXt2BwActEirActEthCos5
         INTEGER,
      er1646v2EthPortSwIXt2BwActEirActEthDei5
         INTEGER,
      er1646v2EthPortSwIXt2BwActEirActEthCos6
         INTEGER,
      er1646v2EthPortSwIXt2BwActEirActEthDei6
         INTEGER,
      er1646v2EthPortSwIXt2BwActEirActEthCos7
         INTEGER,
      er1646v2EthPortSwIXt2BwActEirActEthDei7
         INTEGER,
      er1646v2EthPortSwIXt2BwActEirActEthCos8
         INTEGER,
      er1646v2EthPortSwIXt2BwActEirActEthDei8
         INTEGER,
      er1646v2EthPortSwIXt2BwActEirActEthTos
         INTEGER,
      er1646v2EthPortSwIXt2BwActEirActEthQueue
         INTEGER,
      er1646v2EthPortSwIXt2BwActEirActEthDrpLev
         INTEGER,
      er1646v2EthPortSwIXt2BwActEirActEthDeFlag
         INTEGER,
      er1646v2EthPortSwIXt2BwActEirActIpTos
         INTEGER,
      er1646v2EthPortSwIXt2BwActEirActIpQueue
         INTEGER,
      er1646v2EthPortSwIXt2BwActEirActIpDrpLev
         INTEGER,
      er1646v2EthPortSwIXt2BwActEirActIpDeFlag
         INTEGER,
      er1646v2EthPortSwIXt2BwActViolActNone
         OCTET STRING,
      er1646v2EthPortSwIXt2BwActViolActDrop
         OCTET STRING,
      er1646v2EthPortSwIXt2BwActViolActEthCos1
         INTEGER,
      er1646v2EthPortSwIXt2BwActViolActEthDei1
         INTEGER,
      er1646v2EthPortSwIXt2BwActViolActEthCos2
         INTEGER,
      er1646v2EthPortSwIXt2BwActViolActEthDei2
         INTEGER,
      er1646v2EthPortSwIXt2BwActViolActEthCos3
         INTEGER,
      er1646v2EthPortSwIXt2BwActViolActEthDei3
         INTEGER,
      er1646v2EthPortSwIXt2BwActViolActEthCos4
         INTEGER,
      er1646v2EthPortSwIXt2BwActViolActEthDei4
         INTEGER,
      er1646v2EthPortSwIXt2BwActViolActEthCos5
         INTEGER,
      er1646v2EthPortSwIXt2BwActViolActEthDei5
         INTEGER,
      er1646v2EthPortSwIXt2BwActViolActEthCos6
         INTEGER,
      er1646v2EthPortSwIXt2BwActViolActEthDei6
         INTEGER,
      er1646v2EthPortSwIXt2BwActViolActEthCos7
         INTEGER,
      er1646v2EthPortSwIXt2BwActViolActEthDei7
         INTEGER,
      er1646v2EthPortSwIXt2BwActViolActEthCos8
         INTEGER,
      er1646v2EthPortSwIXt2BwActViolActEthDei8
         INTEGER,
      er1646v2EthPortSwIXt2BwActViolActEthTos
         INTEGER,
      er1646v2EthPortSwIXt2BwActViolActEthQueue
         INTEGER,
      er1646v2EthPortSwIXt2BwActViolActEthDrpLev
         INTEGER,
      er1646v2EthPortSwIXt2BwActViolActEthDeFlag
         INTEGER,
      er1646v2EthPortSwIXt2BwActViolActIpTos
         INTEGER,
      er1646v2EthPortSwIXt2BwActViolActIpQueue
         INTEGER,
      er1646v2EthPortSwIXt2BwActViolActIpDrpLev
         INTEGER,
      er1646v2EthPortSwIXt2BwActViolActIpDeFlag
         INTEGER
      }

er1646v2EthPortSwIXt2BwGlobalIx OBJECT-TYPE
   SYNTAX      GlobalIndex
   MAX-ACCESS  not-accessible
   STATUS      current
   DESCRIPTION
      "The value of the tlsCntTreeGlobalIndex of the MANAGED OBJECT."
   ::= {er1646v2EthPortSwIXt2BwEntry 10}

er1646v2EthPortSwIXt2BwMode OBJECT-TYPE
   SYNTAX      INTEGER
               {
               reshaping (1),
               policing (2),
               policingReshape (3)
               }
   MAX-ACCESS  read-write
   STATUS      current
   DESCRIPTION
      "Path: swPort.editConf.bandwidth.mode

       Possibilities:
               reshaping   (1)
               policing   (2)
               policingReshape   (3)"
   ::= {er1646v2EthPortSwIXt2BwEntry 3758096384}

er1646v2EthPortSwIXt2BwCir OBJECT-TYPE
   SYNTAX      Integer32
   MAX-ACCESS  read-write
   STATUS      current
   DESCRIPTION
      "Path: swPort.editConf.bandwidth.cir"
   ::= {er1646v2EthPortSwIXt2BwEntry 268435456}

er1646v2EthPortSwIXt2BwEir OBJECT-TYPE
   SYNTAX      Integer32
   MAX-ACCESS  read-write
   STATUS      current
   DESCRIPTION
      "Path: swPort.editConf.bandwidth.eir"
   ::= {er1646v2EthPortSwIXt2BwEntry 1879048192}

er1646v2EthPortSwIXt2BwUnit OBJECT-TYPE
   SYNTAX      INTEGER
               {
               bitssec (1),
               percent (2)
               }
   MAX-ACCESS  read-write
   STATUS      current
   DESCRIPTION
      "Path: swPort.editConf.bandwidth.unit

       Possibilities:
               bits/sec   (1)
               percent   (2)"
   ::= {er1646v2EthPortSwIXt2BwEntry 1342177280}

er1646v2EthPortSwIXt2BwTc OBJECT-TYPE
   SYNTAX      INTEGER
               {
               auto (0)
               }
   MAX-ACCESS  read-write
   STATUS      current
   DESCRIPTION
      "Path: swPort.editConf.bandwidth.tc

       Possibilities:
               auto   (0)"
   ::= {er1646v2EthPortSwIXt2BwEntry 1610612736}

er1646v2EthPortSwIXt2BwTcFactor OBJECT-TYPE
   SYNTAX      INTEGER
               {
               ms (10),
               s100us (1)
               }
   MAX-ACCESS  read-write
   STATUS      current
   DESCRIPTION
      "Path: swPort.editConf.bandwidth.tcFactor

       Possibilities:
               ms   (10)
               *100us   (1)"
   ::= {er1646v2EthPortSwIXt2BwEntry 2147483648}

er1646v2EthPortSwIXt2BwCorrType OBJECT-TYPE
   SYNTAX      INTEGER
               {
               noCorrection (0),
               predefined (1),
               manual (2)
               }
   MAX-ACCESS  read-write
   STATUS      current
   DESCRIPTION
      "Path: swPort.editConf.bandwidth.correction.type

       Possibilities:
               noCorrection   (0)
               predefined   (1)
               manual   (2)"
   ::= {er1646v2EthPortSwIXt2BwEntry 570425344}

er1646v2EthPortSwIXt2BwCorrPredefEncapsFrameRelay OBJECT-TYPE
   SYNTAX      DisplayString
   MAX-ACCESS  read-write
   STATUS      current
   DESCRIPTION
      "Path: swPort.editConf.bandwidth.correction.predefined.encapsulation.frameRelay"
   ::= {er1646v2EthPortSwIXt2BwEntry 608436224}

er1646v2EthPortSwIXt2BwCorrPredefEncapsPpp OBJECT-TYPE
   SYNTAX      DisplayString
   MAX-ACCESS  read-write
   STATUS      current
   DESCRIPTION
      "Path: swPort.editConf.bandwidth.correction.predefined.encapsulation.ppp"
   ::= {er1646v2EthPortSwIXt2BwEntry 608698368}

er1646v2EthPortSwIXt2BwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.bandwidth.correction.predefined.encapsulation.atm.higherLayer

       Possibilities:
               rfc2684   (0)
               ppp   (1)
               pppOverEthernet   (2)"
   ::= {er1646v2EthPortSwIXt2BwEntry 608993280}

er1646v2EthPortSwIXt2BwCorrPredefEncapsAtmMp OBJECT-TYPE
   SYNTAX      INTEGER
               {
               llcEncapsulation (0),
               vcMultiplexing (1)
               }
   MAX-ACCESS  read-write
   STATUS      current
   DESCRIPTION
      "Path: swPort.editConf.bandwidth.correction.predefined.encapsulation.atm.multiProtocol

       Possibilities:
               llcEncapsulation   (0)
               vcMultiplexing   (1)"
   ::= {er1646v2EthPortSwIXt2BwEntry 609026048}

er1646v2EthPortSwIXt2BwCorrPredefEncapsHdlc OBJECT-TYPE
   SYNTAX      DisplayString
   MAX-ACCESS  read-write
   STATUS      current
   DESCRIPTION
      "Path: swPort.editConf.bandwidth.correction.predefined.encapsulation.hdlc"
   ::= {er1646v2EthPortSwIXt2BwEntry 609222656}

er1646v2EthPortSwIXt2BwCorrPredefEncapsEfmFs OBJECT-TYPE
   SYNTAX      Integer32
   MAX-ACCESS  read-write
   STATUS      current
   DESCRIPTION
      "Path: swPort.editConf.bandwidth.correction.predefined.encapsulation.efm.fragmentSize"
   ::= {er1646v2EthPortSwIXt2BwEntry 609517568}

er1646v2EthPortSwIXt2BwCorrPredefEncapsEfmIb OBJECT-TYPE
   SYNTAX      Integer32
   MAX-ACCESS  read-write
   STATUS      current
   DESCRIPTION
      "Path: swPort.editConf.bandwidth.correction.predefined.encapsulation.efm.idleBytes"
   ::= {er1646v2EthPortSwIXt2BwEntry 609550336}

er1646v2EthPortSwIXt2BwCorrPredefMode OBJECT-TYPE
   SYNTAX      INTEGER
               {
               routing (0),
               bridging (1)
               }
   MAX-ACCESS  read-write
   STATUS      current
   DESCRIPTION
      "Path: swPort.editConf.bandwidth.correction.predefined.mode

       Possibilities:
               routing   (0)
               bridging   (1)"
   ::= {er1646v2EthPortSwIXt2BwEntry 612368384}

er1646v2EthPortSwIXt2BwCorrManualOverhead OBJECT-TYPE
   SYNTAX      Integer32
   MAX-ACCESS  read-write
   STATUS      current
   DESCRIPTION
      "Path: swPort.editConf.bandwidth.correction.manual.overhead"
   ::= {er1646v2EthPortSwIXt2BwEntry 637665280}

er1646v2EthPortSwIXt2BwCorrManualFrameData OBJECT-TYPE
   SYNTAX      Counter32
   MAX-ACCESS  read-write
   STATUS      current
   DESCRIPTION
      "Path: swPort.editConf.bandwidth.correction.manual.frameData

       32 bit unsigned wrappable counter."
   ::= {er1646v2EthPortSwIXt2BwEntry 637796352}

er1646v2EthPortSwIXt2BwCorrManualFrameHeader OBJECT-TYPE
   SYNTAX      Counter32
   MAX-ACCESS  read-write
   STATUS      current
   DESCRIPTION
      "Path: swPort.editConf.bandwidth.correction.manual.frameHeader

       32 bit unsigned wrappable counter."
   ::= {er1646v2EthPortSwIXt2BwEntry 637927424}

er1646v2EthPortSwIXt2BwMaxFifoQLen OBJECT-TYPE
   SYNTAX      Integer32
   MAX-ACCESS  read-write
   STATUS      current
   DESCRIPTION
      "Path: swPort.editConf.bandwidth.maxFifoQLen"
   ::= {er1646v2EthPortSwIXt2BwEntry 805306368}

er1646v2EthPortSwIXt2BwDeFlagCir OBJECT-TYPE
   SYNTAX      INTEGER
               {
               allowed (1),
               notAllowed (2)
               }
   MAX-ACCESS  read-write
   STATUS      current
   DESCRIPTION
      "Path: swPort.editConf.bandwidth.deFlag.cir

       Possibilities:
               allowed   (1)
               notAllowed   (2)"
   ::= {er1646v2EthPortSwIXt2BwEntry 3490709504}

er1646v2EthPortSwIXt2BwDeFlagEir OBJECT-TYPE
   SYNTAX      INTEGER
               {
               allowed (1),
               notAllowed (2)
               }
   MAX-ACCESS  read-write
   STATUS      current
   DESCRIPTION
      "Path: swPort.editConf.bandwidth.deFlag.eir

       Possibilities:
               allowed   (1)
               notAllowed   (2)"
   ::= {er1646v2EthPortSwIXt2BwEntry 3491758080}

er1646v2EthPortSwIXt2BwDeFlagViolate OBJECT-TYPE
   SYNTAX      INTEGER
               {
               allowed (1),
               notAllowed (2)
               }
   MAX-ACCESS  read-write
   STATUS      current
   DESCRIPTION
      "Path: swPort.editConf.bandwidth.deFlag.violate

       Possibilities:
               allowed   (1)
               notAllowed   (2)"
   ::= {er1646v2EthPortSwIXt2BwEntry 3492806656}

er1646v2EthPortSwIXt2BwActCirActNone OBJECT-TYPE
   SYNTAX      OCTET STRING
   MAX-ACCESS  read-write
   STATUS      current
   DESCRIPTION
      "Path: swPort.editConf.bandwidth.action.cirAction.none"
   ::= {er1646v2EthPortSwIXt2BwEntry 4062183424}

er1646v2EthPortSwIXt2BwActCirActEthCos1 OBJECT-TYPE
   SYNTAX      INTEGER
               {
               unchanged (256)
               }
   MAX-ACCESS  read-write
   STATUS      current
   DESCRIPTION
      "Path: swPort.editConf.bandwidth.action.cirAction.ethernet.cosDepth1

       Possibilities:
               unchanged   (256)"
   ::= {er1646v2EthPortSwIXt2BwEntry 4064346112}

er1646v2EthPortSwIXt2BwActCirActEthDei1 OBJECT-TYPE
   SYNTAX      INTEGER
               {
               unchanged (255),
               clear (0),
               set (1)
               }
   MAX-ACCESS  read-write
   STATUS      current
   DESCRIPTION
      "Path: swPort.editConf.bandwidth.action.cirAction.ethernet.deiDepth1

       Possibilities:
               unchanged   (255)
               clear   (0)
               set   (1)"
   ::= {er1646v2EthPortSwIXt2BwEntry 4065656832}

er1646v2EthPortSwIXt2BwActCirActEthCos2 OBJECT-TYPE
   SYNTAX      INTEGER
               {
               unchanged (256)
               }
   MAX-ACCESS  read-write
   STATUS      current
   DESCRIPTION
      "Path: swPort.editConf.bandwidth.action.cirAction.ethernet.cosDepth2

       Possibilities:
               unchanged   (256)"
   ::= {er1646v2EthPortSwIXt2BwEntry 4064411648}

er1646v2EthPortSwIXt2BwActCirActEthDei2 OBJECT-TYPE
   SYNTAX      INTEGER
               {
               unchanged (255),
               clear (0),
               set (1)
               }
   MAX-ACCESS  read-write
   STATUS      current
   DESCRIPTION
      "Path: swPort.editConf.bandwidth.action.cirAction.ethernet.deiDepth2

       Possibilities:
               unchanged   (255)
               clear   (0)
               set   (1)"
   ::= {er1646v2EthPortSwIXt2BwEntry 4065722368}

er1646v2EthPortSwIXt2BwActCirActEthCos3 OBJECT-TYPE
   SYNTAX      INTEGER
               {
               unchanged (256)
               }
   MAX-ACCESS  read-write
   STATUS      current
   DESCRIPTION
      "Path: swPort.editConf.bandwidth.action.cirAction.ethernet.cosDepth3

       Possibilities:
               unchanged   (256)"
   ::= {er1646v2EthPortSwIXt2BwEntry 4064477184}

er1646v2EthPortSwIXt2BwActCirActEthDei3 OBJECT-TYPE
   SYNTAX      INTEGER
               {
               unchanged (255),
               clear (0),
               set (1)
               }
   MAX-ACCESS  read-write
   STATUS      current
   DESCRIPTION
      "Path: swPort.editConf.bandwidth.action.cirAction.ethernet.deiDepth3

       Possibilities:
               unchanged   (255)
               clear   (0)
               set   (1)"
   ::= {er1646v2EthPortSwIXt2BwEntry 4065787904}

er1646v2EthPortSwIXt2BwActCirActEthCos4 OBJECT-TYPE
   SYNTAX      INTEGER
               {
               unchanged (256)
               }
   MAX-ACCESS  read-write
   STATUS      current
   DESCRIPTION
      "Path: swPort.editConf.bandwidth.action.cirAction.ethernet.cosDepth4

       Possibilities:
               unchanged   (256)"
   ::= {er1646v2EthPortSwIXt2BwEntry 4064542720}

er1646v2EthPortSwIXt2BwActCirActEthDei4 OBJECT-TYPE
   SYNTAX      INTEGER
               {
               unchanged (255),
               clear (0),
               set (1)
               }
   MAX-ACCESS  read-write
   STATUS      current
   DESCRIPTION
      "Path: swPort.editConf.bandwidth.action.cirAction.ethernet.deiDepth4

       Possibilities:
               unchanged   (255)
               clear   (0)
               set   (1)"
   ::= {er1646v2EthPortSwIXt2BwEntry 4065853440}

er1646v2EthPortSwIXt2BwActCirActEthCos5 OBJECT-TYPE
   SYNTAX      INTEGER
               {
               unchanged (256)
               }
   MAX-ACCESS  read-write
   STATUS      current
   DESCRIPTION
      "Path: swPort.editConf.bandwidth.action.cirAction.ethernet.cosDepth5

       Possibilities:
               unchanged   (256)"
   ::= {er1646v2EthPortSwIXt2BwEntry 4064608256}

er1646v2EthPortSwIXt2BwActCirActEthDei5 OBJECT-TYPE
   SYNTAX      INTEGER
               {
               unchanged (255),
               clear (0),
               set (1)
               }
   MAX-ACCESS  read-write
   STATUS      current
   DESCRIPTION
      "Path: swPort.editConf.bandwidth.action.cirAction.ethernet.deiDepth5

       Possibilities:
               unchanged   (255)
               clear   (0)
               set   (1)"
   ::= {er1646v2EthPortSwIXt2BwEntry 4065918976}

er1646v2EthPortSwIXt2BwActCirActEthCos6 OBJECT-TYPE
   SYNTAX      INTEGER
               {
               unchanged (256)
               }
   MAX-ACCESS  read-write
   STATUS      current
   DESCRIPTION
      "Path: swPort.editConf.bandwidth.action.cirAction.ethernet.cosDepth6

       Possibilities:
               unchanged   (256)"
   ::= {er1646v2EthPortSwIXt2BwEntry 4064673792}

er1646v2EthPortSwIXt2BwActCirActEthDei6 OBJECT-TYPE
   SYNTAX      INTEGER
               {
               unchanged (255),
               clear (0),
               set (1)
               }
   MAX-ACCESS  read-write
   STATUS      current
   DESCRIPTION
      "Path: swPort.editConf.bandwidth.action.cirAction.ethernet.deiDepth6

       Possibilities:
               unchanged   (255)
               clear   (0)
               set   (1)"
   ::= {er1646v2EthPortSwIXt2BwEntry 4065984512}

er1646v2EthPortSwIXt2BwActCirActEthCos7 OBJECT-TYPE
   SYNTAX      INTEGER
               {
               unchanged (256)
               }
   MAX-ACCESS  read-write
   STATUS      current
   DESCRIPTION
      "Path: swPort.editConf.bandwidth.action.cirAction.ethernet.cosDepth7

       Possibilities:
               unchanged   (256)"
   ::= {er1646v2EthPortSwIXt2BwEntry 4064739328}

er1646v2EthPortSwIXt2BwActCirActEthDei7 OBJECT-TYPE
   SYNTAX      INTEGER
               {
               unchanged (255),
               clear (0),
               set (1)
               }
   MAX-ACCESS  read-write
   STATUS      current
   DESCRIPTION
      "Path: swPort.editConf.bandwidth.action.cirAction.ethernet.deiDepth7

       Possibilities:
               unchanged   (255)
               clear   (0)
               set   (1)"
   ::= {er1646v2EthPortSwIXt2BwEntry 4066050048}

er1646v2EthPortSwIXt2BwActCirActEthCos8 OBJECT-TYPE
   SYNTAX      INTEGER
               {
               unchanged (256)
               }
   MAX-ACCESS  read-write
   STATUS      current
   DESCRIPTION
      "Path: swPort.editConf.bandwidth.action.cirAction.ethernet.cosDepth8

       Possibilities:
               unchanged   (256)"
   ::= {er1646v2EthPortSwIXt2BwEntry 4064804864}

er1646v2EthPortSwIXt2BwActCirActEthDei8 OBJECT-TYPE
   SYNTAX      INTEGER
               {
               unchanged (255),
               clear (0),
               set (1)
               }
   MAX-ACCESS  read-write
   STATUS      current
   DESCRIPTION
      "Path: swPort.editConf.bandwidth.action.cirAction.ethernet.deiDepth8

       Possibilities:
               unchanged   (255)
               clear   (0)
               set   (1)"
   ::= {er1646v2EthPortSwIXt2BwEntry 4066115584}

er1646v2EthPortSwIXt2BwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2BwEntry 4064870400}

er1646v2EthPortSwIXt2BwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2BwEntry 4064935936}

er1646v2EthPortSwIXt2BwActCirActEthDrpLev OBJECT-TYPE
   SYNTAX      INTEGER
               {
               unchanged (0)
               }
   MAX-ACCESS  read-write
   STATUS      current
   DESCRIPTION
      "Path: swPort.editConf.bandwidth.action.cirAction.ethernet.dropLevel

       Possibilities:
               unchanged   (0)"
   ::= {er1646v2EthPortSwIXt2BwEntry 4065001472}

er1646v2EthPortSwIXt2BwActCirActEthDeFlag OBJECT-TYPE
   SYNTAX      INTEGER
               {
               unchanged (255),
               clear (0),
               set (1)
               }
   MAX-ACCESS  read-write
   STATUS      current
   DESCRIPTION
      "Path: swPort.editConf.bandwidth.action.cirAction.ethernet.deFlag

       Possibilities:
               unchanged   (255)
               clear   (0)
               set   (1)"
   ::= {er1646v2EthPortSwIXt2BwEntry 4065198080}

er1646v2EthPortSwIXt2BwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2BwEntry 4071161856}

er1646v2EthPortSwIXt2BwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2BwEntry 4071227392}

er1646v2EthPortSwIXt2BwActCirActIpDrpLev OBJECT-TYPE
   SYNTAX      INTEGER
               {
               unchanged (0)
               }
   MAX-ACCESS  read-write
   STATUS      current
   DESCRIPTION
      "Path: swPort.editConf.bandwidth.action.cirAction.ip.dropLevel

       Possibilities:
               unchanged   (0)"
   ::= {er1646v2EthPortSwIXt2BwEntry 4071292928}

er1646v2EthPortSwIXt2BwActCirActIpDeFlag OBJECT-TYPE
   SYNTAX      INTEGER
               {
               unchanged (255),
               clear (0),
               set (1)
               }
   MAX-ACCESS  read-write
   STATUS      current
   DESCRIPTION
      "Path: swPort.editConf.bandwidth.action.cirAction.ip.deFlag

       Possibilities:
               unchanged   (255)
               clear   (0)
               set   (1)"
   ::= {er1646v2EthPortSwIXt2BwEntry 4071489536}

er1646v2EthPortSwIXt2BwActEirActNone OBJECT-TYPE
   SYNTAX      OCTET STRING
   MAX-ACCESS  read-write
   STATUS      current
   DESCRIPTION
      "Path: swPort.editConf.bandwidth.action.eirAction.none"
   ::= {er1646v2EthPortSwIXt2BwEntry 4095737856}

er1646v2EthPortSwIXt2BwActEirActEthCos1 OBJECT-TYPE
   SYNTAX      INTEGER
               {
               unchanged (256)
               }
   MAX-ACCESS  read-write
   STATUS      current
   DESCRIPTION
      "Path: swPort.editConf.bandwidth.action.eirAction.ethernet.cosDepth1

       Possibilities:
               unchanged   (256)"
   ::= {er1646v2EthPortSwIXt2BwEntry 4097900544}

er1646v2EthPortSwIXt2BwActEirActEthDei1 OBJECT-TYPE
   SYNTAX      INTEGER
               {
               unchanged (255),
               clear (0),
               set (1)
               }
   MAX-ACCESS  read-write
   STATUS      current
   DESCRIPTION
      "Path: swPort.editConf.bandwidth.action.eirAction.ethernet.deiDepth1

       Possibilities:
               unchanged   (255)
               clear   (0)
               set   (1)"
   ::= {er1646v2EthPortSwIXt2BwEntry 4099211264}

er1646v2EthPortSwIXt2BwActEirActEthCos2 OBJECT-TYPE
   SYNTAX      INTEGER
               {
               unchanged (256)
               }
   MAX-ACCESS  read-write
   STATUS      current
   DESCRIPTION
      "Path: swPort.editConf.bandwidth.action.eirAction.ethernet.cosDepth2

       Possibilities:
               unchanged   (256)"
   ::= {er1646v2EthPortSwIXt2BwEntry 4097966080}

er1646v2EthPortSwIXt2BwActEirActEthDei2 OBJECT-TYPE
   SYNTAX      INTEGER
               {
               unchanged (255),
               clear (0),
               set (1)
               }
   MAX-ACCESS  read-write
   STATUS      current
   DESCRIPTION
      "Path: swPort.editConf.bandwidth.action.eirAction.ethernet.deiDepth2

       Possibilities:
               unchanged   (255)
               clear   (0)
               set   (1)"
   ::= {er1646v2EthPortSwIXt2BwEntry 4099276800}

er1646v2EthPortSwIXt2BwActEirActEthCos3 OBJECT-TYPE
   SYNTAX      INTEGER
               {
               unchanged (256)
               }
   MAX-ACCESS  read-write
   STATUS      current
   DESCRIPTION
      "Path: swPort.editConf.bandwidth.action.eirAction.ethernet.cosDepth3

       Possibilities:
               unchanged   (256)"
   ::= {er1646v2EthPortSwIXt2BwEntry 4098031616}

er1646v2EthPortSwIXt2BwActEirActEthDei3 OBJECT-TYPE
   SYNTAX      INTEGER
               {
               unchanged (255),
               clear (0),
               set (1)
               }
   MAX-ACCESS  read-write
   STATUS      current
   DESCRIPTION
      "Path: swPort.editConf.bandwidth.action.eirAction.ethernet.deiDepth3

       Possibilities:
               unchanged   (255)
               clear   (0)
               set   (1)"
   ::= {er1646v2EthPortSwIXt2BwEntry 4099342336}

er1646v2EthPortSwIXt2BwActEirActEthCos4 OBJECT-TYPE
   SYNTAX      INTEGER
               {
               unchanged (256)
               }
   MAX-ACCESS  read-write
   STATUS      current
   DESCRIPTION
      "Path: swPort.editConf.bandwidth.action.eirAction.ethernet.cosDepth4

       Possibilities:
               unchanged   (256)"
   ::= {er1646v2EthPortSwIXt2BwEntry 4098097152}

er1646v2EthPortSwIXt2BwActEirActEthDei4 OBJECT-TYPE
   SYNTAX      INTEGER
               {
               unchanged (255),
               clear (0),
               set (1)
               }
   MAX-ACCESS  read-write
   STATUS      current
   DESCRIPTION
      "Path: swPort.editConf.bandwidth.action.eirAction.ethernet.deiDepth4

       Possibilities:
               unchanged   (255)
               clear   (0)
               set   (1)"
   ::= {er1646v2EthPortSwIXt2BwEntry 4099407872}

er1646v2EthPortSwIXt2BwActEirActEthCos5 OBJECT-TYPE
   SYNTAX      INTEGER
               {
               unchanged (256)
               }
   MAX-ACCESS  read-write
   STATUS      current
   DESCRIPTION
      "Path: swPort.editConf.bandwidth.action.eirAction.ethernet.cosDepth5

       Possibilities:
               unchanged   (256)"
   ::= {er1646v2EthPortSwIXt2BwEntry 4098162688}

er1646v2EthPortSwIXt2BwActEirActEthDei5 OBJECT-TYPE
   SYNTAX      INTEGER
               {
               unchanged (255),
               clear (0),
               set (1)
               }
   MAX-ACCESS  read-write
   STATUS      current
   DESCRIPTION
      "Path: swPort.editConf.bandwidth.action.eirAction.ethernet.deiDepth5

       Possibilities:
               unchanged   (255)
               clear   (0)
               set   (1)"
   ::= {er1646v2EthPortSwIXt2BwEntry 4099473408}

er1646v2EthPortSwIXt2BwActEirActEthCos6 OBJECT-TYPE
   SYNTAX      INTEGER
               {
               unchanged (256)
               }
   MAX-ACCESS  read-write
   STATUS      current
   DESCRIPTION
      "Path: swPort.editConf.bandwidth.action.eirAction.ethernet.cosDepth6

       Possibilities:
               unchanged   (256)"
   ::= {er1646v2EthPortSwIXt2BwEntry 4098228224}

er1646v2EthPortSwIXt2BwActEirActEthDei6 OBJECT-TYPE
   SYNTAX      INTEGER
               {
               unchanged (255),
               clear (0),
               set (1)
               }
   MAX-ACCESS  read-write
   STATUS      current
   DESCRIPTION
      "Path: swPort.editConf.bandwidth.action.eirAction.ethernet.deiDepth6

       Possibilities:
               unchanged   (255)
               clear   (0)
               set   (1)"
   ::= {er1646v2EthPortSwIXt2BwEntry 4099538944}

er1646v2EthPortSwIXt2BwActEirActEthCos7 OBJECT-TYPE
   SYNTAX      INTEGER
               {
               unchanged (256)
               }
   MAX-ACCESS  read-write
   STATUS      current
   DESCRIPTION
      "Path: swPort.editConf.bandwidth.action.eirAction.ethernet.cosDepth7

       Possibilities:
               unchanged   (256)"
   ::= {er1646v2EthPortSwIXt2BwEntry 4098293760}

er1646v2EthPortSwIXt2BwActEirActEthDei7 OBJECT-TYPE
   SYNTAX      INTEGER
               {
               unchanged (255),
               clear (0),
               set (1)
               }
   MAX-ACCESS  read-write
   STATUS      current
   DESCRIPTION
      "Path: swPort.editConf.bandwidth.action.eirAction.ethernet.deiDepth7

       Possibilities:
               unchanged   (255)
               clear   (0)
               set   (1)"
   ::= {er1646v2EthPortSwIXt2BwEntry 4099604480}

er1646v2EthPortSwIXt2BwActEirActEthCos8 OBJECT-TYPE
   SYNTAX      INTEGER
               {
               unchanged (256)
               }
   MAX-ACCESS  read-write
   STATUS      current
   DESCRIPTION
      "Path: swPort.editConf.bandwidth.action.eirAction.ethernet.cosDepth8

       Possibilities:
               unchanged   (256)"
   ::= {er1646v2EthPortSwIXt2BwEntry 4098359296}

er1646v2EthPortSwIXt2BwActEirActEthDei8 OBJECT-TYPE
   SYNTAX      INTEGER
               {
               unchanged (255),
               clear (0),
               set (1)
               }
   MAX-ACCESS  read-write
   STATUS      current
   DESCRIPTION
      "Path: swPort.editConf.bandwidth.action.eirAction.ethernet.deiDepth8

       Possibilities:
               unchanged   (255)
               clear   (0)
               set   (1)"
   ::= {er1646v2EthPortSwIXt2BwEntry 4099670016}

er1646v2EthPortSwIXt2BwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2BwEntry 4098424832}

er1646v2EthPortSwIXt2BwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2BwEntry 4098490368}

er1646v2EthPortSwIXt2BwActEirActEthDrpLev OBJECT-TYPE
   SYNTAX      INTEGER
               {
               unchanged (0)
               }
   MAX-ACCESS  read-write
   STATUS      current
   DESCRIPTION
      "Path: swPort.editConf.bandwidth.action.eirAction.ethernet.dropLevel

       Possibilities:
               unchanged   (0)"
   ::= {er1646v2EthPortSwIXt2BwEntry 4098555904}

er1646v2EthPortSwIXt2BwActEirActEthDeFlag OBJECT-TYPE
   SYNTAX      INTEGER
               {
               unchanged (255),
               clear (0),
               set (1)
               }
   MAX-ACCESS  read-write
   STATUS      current
   DESCRIPTION
      "Path: swPort.editConf.bandwidth.action.eirAction.ethernet.deFlag

       Possibilities:
               unchanged   (255)
               clear   (0)
               set   (1)"
   ::= {er1646v2EthPortSwIXt2BwEntry 4098752512}

er1646v2EthPortSwIXt2BwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2BwEntry 4104716288}

er1646v2EthPortSwIXt2BwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2BwEntry 4104781824}

er1646v2EthPortSwIXt2BwActEirActIpDrpLev OBJECT-TYPE
   SYNTAX      INTEGER
               {
               unchanged (0)
               }
   MAX-ACCESS  read-write
   STATUS      current
   DESCRIPTION
      "Path: swPort.editConf.bandwidth.action.eirAction.ip.dropLevel

       Possibilities:
               unchanged   (0)"
   ::= {er1646v2EthPortSwIXt2BwEntry 4104847360}

er1646v2EthPortSwIXt2BwActEirActIpDeFlag OBJECT-TYPE
   SYNTAX      INTEGER
               {
               unchanged (255),
               clear (0),
               set (1)
               }
   MAX-ACCESS  read-write
   STATUS      current
   DESCRIPTION
      "Path: swPort.editConf.bandwidth.action.eirAction.ip.deFlag

       Possibilities:
               unchanged   (255)
               clear   (0)
               set   (1)"
   ::= {er1646v2EthPortSwIXt2BwEntry 4105043968}

er1646v2EthPortSwIXt2BwActViolActNone OBJECT-TYPE
   SYNTAX      OCTET STRING
   MAX-ACCESS  read-write
   STATUS      current
   DESCRIPTION
      "Path: swPort.editConf.bandwidth.action.violateAction.none"
   ::= {er1646v2EthPortSwIXt2BwEntry 4129292288}

er1646v2EthPortSwIXt2BwActViolActDrop OBJECT-TYPE
   SYNTAX      OCTET STRING
   MAX-ACCESS  read-write
   STATUS      current
   DESCRIPTION
      "Path: swPort.editConf.bandwidth.action.violateAction.drop"
   ::= {er1646v2EthPortSwIXt2BwEntry 4133486592}

er1646v2EthPortSwIXt2BwActViolActEthCos1 OBJECT-TYPE
   SYNTAX      INTEGER
               {
               unchanged (256)
               }
   MAX-ACCESS  read-write
   STATUS      current
   DESCRIPTION
      "Path: swPort.editConf.bandwidth.action.violateAction.ethernet.cosDepth1

       Possibilities:
               unchanged   (256)"
   ::= {er1646v2EthPortSwIXt2BwEntry 4131454976}

er1646v2EthPortSwIXt2BwActViolActEthDei1 OBJECT-TYPE
   SYNTAX      INTEGER
               {
               unchanged (255),
               clear (0),
               set (1)
               }
   MAX-ACCESS  read-write
   STATUS      current
   DESCRIPTION
      "Path: swPort.editConf.bandwidth.action.violateAction.ethernet.deiDepth1

       Possibilities:
               unchanged   (255)
               clear   (0)
               set   (1)"
   ::= {er1646v2EthPortSwIXt2BwEntry 4132765696}

er1646v2EthPortSwIXt2BwActViolActEthCos2 OBJECT-TYPE
   SYNTAX      INTEGER
               {
               unchanged (256)
               }
   MAX-ACCESS  read-write
   STATUS      current
   DESCRIPTION
      "Path: swPort.editConf.bandwidth.action.violateAction.ethernet.cosDepth2

       Possibilities:
               unchanged   (256)"
   ::= {er1646v2EthPortSwIXt2BwEntry 4131520512}

er1646v2EthPortSwIXt2BwActViolActEthDei2 OBJECT-TYPE
   SYNTAX      INTEGER
               {
               unchanged (255),
               clear (0),
               set (1)
               }
   MAX-ACCESS  read-write
   STATUS      current
   DESCRIPTION
      "Path: swPort.editConf.bandwidth.action.violateAction.ethernet.deiDepth2

       Possibilities:
               unchanged   (255)
               clear   (0)
               set   (1)"
   ::= {er1646v2EthPortSwIXt2BwEntry 4132831232}

er1646v2EthPortSwIXt2BwActViolActEthCos3 OBJECT-TYPE
   SYNTAX      INTEGER
               {
               unchanged (256)
               }
   MAX-ACCESS  read-write
   STATUS      current
   DESCRIPTION
      "Path: swPort.editConf.bandwidth.action.violateAction.ethernet.cosDepth3

       Possibilities:
               unchanged   (256)"
   ::= {er1646v2EthPortSwIXt2BwEntry 4131586048}

er1646v2EthPortSwIXt2BwActViolActEthDei3 OBJECT-TYPE
   SYNTAX      INTEGER
               {
               unchanged (255),
               clear (0),
               set (1)
               }
   MAX-ACCESS  read-write
   STATUS      current
   DESCRIPTION
      "Path: swPort.editConf.bandwidth.action.violateAction.ethernet.deiDepth3

       Possibilities:
               unchanged   (255)
               clear   (0)
               set   (1)"
   ::= {er1646v2EthPortSwIXt2BwEntry 4132896768}

er1646v2EthPortSwIXt2BwActViolActEthCos4 OBJECT-TYPE
   SYNTAX      INTEGER
               {
               unchanged (256)
               }
   MAX-ACCESS  read-write
   STATUS      current
   DESCRIPTION
      "Path: swPort.editConf.bandwidth.action.violateAction.ethernet.cosDepth4

       Possibilities:
               unchanged   (256)"
   ::= {er1646v2EthPortSwIXt2BwEntry 4131651584}

er1646v2EthPortSwIXt2BwActViolActEthDei4 OBJECT-TYPE
   SYNTAX      INTEGER
               {
               unchanged (255),
               clear (0),
               set (1)
               }
   MAX-ACCESS  read-write
   STATUS      current
   DESCRIPTION
      "Path: swPort.editConf.bandwidth.action.violateAction.ethernet.deiDepth4

       Possibilities:
               unchanged   (255)
               clear   (0)
               set   (1)"
   ::= {er1646v2EthPortSwIXt2BwEntry 4132962304}

er1646v2EthPortSwIXt2BwActViolActEthCos5 OBJECT-TYPE
   SYNTAX      INTEGER
               {
               unchanged (256)
               }
   MAX-ACCESS  read-write
   STATUS      current
   DESCRIPTION
      "Path: swPort.editConf.bandwidth.action.violateAction.ethernet.cosDepth5

       Possibilities:
               unchanged   (256)"
   ::= {er1646v2EthPortSwIXt2BwEntry 4131717120}

er1646v2EthPortSwIXt2BwActViolActEthDei5 OBJECT-TYPE
   SYNTAX      INTEGER
               {
               unchanged (255),
               clear (0),
               set (1)
               }
   MAX-ACCESS  read-write
   STATUS      current
   DESCRIPTION
      "Path: swPort.editConf.bandwidth.action.violateAction.ethernet.deiDepth5

       Possibilities:
               unchanged   (255)
               clear   (0)
               set   (1)"
   ::= {er1646v2EthPortSwIXt2BwEntry 4133027840}

er1646v2EthPortSwIXt2BwActViolActEthCos6 OBJECT-TYPE
   SYNTAX      INTEGER
               {
               unchanged (256)
               }
   MAX-ACCESS  read-write
   STATUS      current
   DESCRIPTION
      "Path: swPort.editConf.bandwidth.action.violateAction.ethernet.cosDepth6

       Possibilities:
               unchanged   (256)"
   ::= {er1646v2EthPortSwIXt2BwEntry 4131782656}

er1646v2EthPortSwIXt2BwActViolActEthDei6 OBJECT-TYPE
   SYNTAX      INTEGER
               {
               unchanged (255),
               clear (0),
               set (1)
               }
   MAX-ACCESS  read-write
   STATUS      current
   DESCRIPTION
      "Path: swPort.editConf.bandwidth.action.violateAction.ethernet.deiDepth6

       Possibilities:
               unchanged   (255)
               clear   (0)
               set   (1)"
   ::= {er1646v2EthPortSwIXt2BwEntry 4133093376}

er1646v2EthPortSwIXt2BwActViolActEthCos7 OBJECT-TYPE
   SYNTAX      INTEGER
               {
               unchanged (256)
               }
   MAX-ACCESS  read-write
   STATUS      current
   DESCRIPTION
      "Path: swPort.editConf.bandwidth.action.violateAction.ethernet.cosDepth7

       Possibilities:
               unchanged   (256)"
   ::= {er1646v2EthPortSwIXt2BwEntry 4131848192}

er1646v2EthPortSwIXt2BwActViolActEthDei7 OBJECT-TYPE
   SYNTAX      INTEGER
               {
               unchanged (255),
               clear (0),
               set (1)
               }
   MAX-ACCESS  read-write
   STATUS      current
   DESCRIPTION
      "Path: swPort.editConf.bandwidth.action.violateAction.ethernet.deiDepth7

       Possibilities:
               unchanged   (255)
               clear   (0)
               set   (1)"
   ::= {er1646v2EthPortSwIXt2BwEntry 4133158912}

er1646v2EthPortSwIXt2BwActViolActEthCos8 OBJECT-TYPE
   SYNTAX      INTEGER
               {
               unchanged (256)
               }
   MAX-ACCESS  read-write
   STATUS      current
   DESCRIPTION
      "Path: swPort.editConf.bandwidth.action.violateAction.ethernet.cosDepth8

       Possibilities:
               unchanged   (256)"
   ::= {er1646v2EthPortSwIXt2BwEntry 4131913728}

er1646v2EthPortSwIXt2BwActViolActEthDei8 OBJECT-TYPE
   SYNTAX      INTEGER
               {
               unchanged (255),
               clear (0),
               set (1)
               }
   MAX-ACCESS  read-write
   STATUS      current
   DESCRIPTION
      "Path: swPort.editConf.bandwidth.action.violateAction.ethernet.deiDepth8

       Possibilities:
               unchanged   (255)
               clear   (0)
               set   (1)"
   ::= {er1646v2EthPortSwIXt2BwEntry 4133224448}

er1646v2EthPortSwIXt2BwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2BwEntry 4131979264}

er1646v2EthPortSwIXt2BwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2BwEntry 4132044800}

er1646v2EthPortSwIXt2BwActViolActEthDrpLev OBJECT-TYPE
   SYNTAX      INTEGER
               {
               unchanged (0)
               }
   MAX-ACCESS  read-write
   STATUS      current
   DESCRIPTION
      "Path: swPort.editConf.bandwidth.action.violateAction.ethernet.dropLevel

       Possibilities:
               unchanged   (0)"
   ::= {er1646v2EthPortSwIXt2BwEntry 4132110336}

er1646v2EthPortSwIXt2BwActViolActEthDeFlag OBJECT-TYPE
   SYNTAX      INTEGER
               {
               unchanged (255),
               clear (0),
               set (1)
               }
   MAX-ACCESS  read-write
   STATUS      current
   DESCRIPTION
      "Path: swPort.editConf.bandwidth.action.violateAction.ethernet.deFlag

       Possibilities:
               unchanged   (255)
               clear   (0)
               set   (1)"
   ::= {er1646v2EthPortSwIXt2BwEntry 4132306944}

er1646v2EthPortSwIXt2BwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2BwEntry 4138270720}

er1646v2EthPortSwIXt2BwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2BwEntry 4138336256}

er1646v2EthPortSwIXt2BwActViolActIpDrpLev OBJECT-TYPE
   SYNTAX      INTEGER
               {
               unchanged (0)
               }
   MAX-ACCESS  read-write
   STATUS      current
   DESCRIPTION
      "Path: swPort.editConf.bandwidth.action.violateAction.ip.dropLevel

       Possibilities:
               unchanged   (0)"
   ::= {er1646v2EthPortSwIXt2BwEntry 4138401792}

er1646v2EthPortSwIXt2BwActViolActIpDeFlag OBJECT-TYPE
   SYNTAX      INTEGER
               {
               unchanged (255),
               clear (0),
               set (1)
               }
   MAX-ACCESS  read-write
   STATUS      current
   DESCRIPTION
      "Path: swPort.editConf.bandwidth.action.violateAction.ip.deFlag

       Possibilities:
               unchanged   (255)
               clear   (0)
               set   (1)"
   ::= {er1646v2EthPortSwIXt2BwEntry 4138598400}


er1646v2EthPortSwIXt2Ibw OBJECT IDENTIFIER ::= {er1646v2EthPortSwIXt2 13}

er1646v2EthPortSwIXt2IbwSSCTable OBJECT-TYPE
   SYNTAX      SEQUENCE OF Er1646v2EthPortSwIXt2IbwEntry
   MAX-ACCESS  not-accessible
   STATUS      current
   DESCRIPTION
      ""
   ::= {er1646v2EthPortSwIXt2Ibw 1}

er1646v2EthPortSwIXt2IbwEntry OBJECT-TYPE
   SYNTAX      Er1646v2EthPortSwIXt2IbwEntry
   MAX-ACCESS  not-accessible
   STATUS      current
   DESCRIPTION
      ""
   INDEX      { er1646v2EthPortSwIXt2IbwGlobalIx }
   ::= {er1646v2EthPortSwIXt2IbwSSCTable 1}

Er1646v2EthPortSwIXt2IbwEntry ::=
   SEQUENCE
      {
      er1646v2EthPortSwIXt2IbwGlobalIx
         GlobalIndex,
      er1646v2EthPortSwIXt2IbwMode
         INTEGER,
      er1646v2EthPortSwIXt2IbwCir
         Integer32,
      er1646v2EthPortSwIXt2IbwEir
         Integer32,
      er1646v2EthPortSwIXt2IbwUnit
         INTEGER,
      er1646v2EthPortSwIXt2IbwTc
         INTEGER,
      er1646v2EthPortSwIXt2IbwTcFactor
         INTEGER,
      er1646v2EthPortSwIXt2IbwCorrType
         INTEGER,
      er1646v2EthPortSwIXt2IbwCorrPredefEncapsFrameRelay
         DisplayString,
      er1646v2EthPortSwIXt2IbwCorrPredefEncapsPpp
         DisplayString,
      er1646v2EthPortSwIXt2IbwCorrPredefEncapsAtmHl
         INTEGER,
      er1646v2EthPortSwIXt2IbwCorrPredefEncapsAtmMp
         INTEGER,
      er1646v2EthPortSwIXt2IbwCorrPredefEncapsHdlc
         DisplayString,
      er1646v2EthPortSwIXt2IbwCorrPredefEncapsEfmFs
         Integer32,
      er1646v2EthPortSwIXt2IbwCorrPredefEncapsEfmIb
         Integer32,
      er1646v2EthPortSwIXt2IbwCorrPredefMode
         INTEGER,
      er1646v2EthPortSwIXt2IbwCorrManualOverhead
         Integer32,
      er1646v2EthPortSwIXt2IbwCorrManualFrameData
         Counter32,
      er1646v2EthPortSwIXt2IbwCorrManualFrameHeader
         Counter32,
      er1646v2EthPortSwIXt2IbwMaxFifoQLen
         Integer32,
      er1646v2EthPortSwIXt2IbwPriorityPolicy
         DisplayString,
      er1646v2EthPortSwIXt2IbwDeFlagCir
         INTEGER,
      er1646v2EthPortSwIXt2IbwDeFlagEir
         INTEGER,
      er1646v2EthPortSwIXt2IbwDeFlagViolate
         INTEGER,
      er1646v2EthPortSwIXt2IbwActCirActNone
         OCTET STRING,
      er1646v2EthPortSwIXt2IbwActCirActEthCos1
         INTEGER,
      er1646v2EthPortSwIXt2IbwActCirActEthDei1
         INTEGER,
      er1646v2EthPortSwIXt2IbwActCirActEthCos2
         INTEGER,
      er1646v2EthPortSwIXt2IbwActCirActEthDei2
         INTEGER,
      er1646v2EthPortSwIXt2IbwActCirActEthCos3
         INTEGER,
      er1646v2EthPortSwIXt2IbwActCirActEthDei3
         INTEGER,
      er1646v2EthPortSwIXt2IbwActCirActEthCos4
         INTEGER,
      er1646v2EthPortSwIXt2IbwActCirActEthDei4
         INTEGER,
      er1646v2EthPortSwIXt2IbwActCirActEthCos5
         INTEGER,
      er1646v2EthPortSwIXt2IbwActCirActEthDei5
         INTEGER,
      er1646v2EthPortSwIXt2IbwActCirActEthCos6
         INTEGER,
      er1646v2EthPortSwIXt2IbwActCirActEthDei6
         INTEGER,
      er1646v2EthPortSwIXt2IbwActCirActEthCos7
         INTEGER,
      er1646v2EthPortSwIXt2IbwActCirActEthDei7
         INTEGER,
      er1646v2EthPortSwIXt2IbwActCirActEthCos8
         INTEGER,
      er1646v2EthPortSwIXt2IbwActCirActEthDei8
         INTEGER,
      er1646v2EthPortSwIXt2IbwActCirActEthTos
         INTEGER,
      er1646v2EthPortSwIXt2IbwActCirActEthQueue
         INTEGER,
      er1646v2EthPortSwIXt2IbwActCirActEthDrpLev
         INTEGER,
      er1646v2EthPortSwIXt2IbwActCirActEthDeFlag
         INTEGER,
      er1646v2EthPortSwIXt2IbwActCirActIpTos
         INTEGER,
      er1646v2EthPortSwIXt2IbwActCirActIpQueue
         INTEGER,
      er1646v2EthPortSwIXt2IbwActCirActIpDrpLev
         INTEGER,
      er1646v2EthPortSwIXt2IbwActCirActIpDeFlag
         INTEGER,
      er1646v2EthPortSwIXt2IbwActEirActNone
         OCTET STRING,
      er1646v2EthPortSwIXt2IbwActEirActEthCos1
         INTEGER,
      er1646v2EthPortSwIXt2IbwActEirActEthDei1
         INTEGER,
      er1646v2EthPortSwIXt2IbwActEirActEthCos2
         INTEGER,
      er1646v2EthPortSwIXt2IbwActEirActEthDei2
         INTEGER,
      er1646v2EthPortSwIXt2IbwActEirActEthCos3
         INTEGER,
      er1646v2EthPortSwIXt2IbwActEirActEthDei3
         INTEGER,
      er1646v2EthPortSwIXt2IbwActEirActEthCos4
         INTEGER,
      er1646v2EthPortSwIXt2IbwActEirActEthDei4
         INTEGER,
      er1646v2EthPortSwIXt2IbwActEirActEthCos5
         INTEGER,
      er1646v2EthPortSwIXt2IbwActEirActEthDei5
         INTEGER,
      er1646v2EthPortSwIXt2IbwActEirActEthCos6
         INTEGER,
      er1646v2EthPortSwIXt2IbwActEirActEthDei6
         INTEGER,
      er1646v2EthPortSwIXt2IbwActEirActEthCos7
         INTEGER,
      er1646v2EthPortSwIXt2IbwActEirActEthDei7
         INTEGER,
      er1646v2EthPortSwIXt2IbwActEirActEthCos8
         INTEGER,
      er1646v2EthPortSwIXt2IbwActEirActEthDei8
         INTEGER,
      er1646v2EthPortSwIXt2IbwActEirActEthTos
         INTEGER,
      er1646v2EthPortSwIXt2IbwActEirActEthQueue
         INTEGER,
      er1646v2EthPortSwIXt2IbwActEirActEthDrpLev
         INTEGER,
      er1646v2EthPortSwIXt2IbwActEirActEthDeFlag
         INTEGER,
      er1646v2EthPortSwIXt2IbwActEirActIpTos
         INTEGER,
      er1646v2EthPortSwIXt2IbwActEirActIpQueue
         INTEGER,
      er1646v2EthPortSwIXt2IbwActEirActIpDrpLev
         INTEGER,
      er1646v2EthPortSwIXt2IbwActEirActIpDeFlag
         INTEGER,
      er1646v2EthPortSwIXt2IbwActViolActNone
         OCTET STRING,
      er1646v2EthPortSwIXt2IbwActViolActDrop
         OCTET STRING,
      er1646v2EthPortSwIXt2IbwActViolActEthCos1
         INTEGER,
      er1646v2EthPortSwIXt2IbwActViolActEthDei1
         INTEGER,
      er1646v2EthPortSwIXt2IbwActViolActEthCos2
         INTEGER,
      er1646v2EthPortSwIXt2IbwActViolActEthDei2
         INTEGER,
      er1646v2EthPortSwIXt2IbwActViolActEthCos3
         INTEGER,
      er1646v2EthPortSwIXt2IbwActViolActEthDei3
         INTEGER,
      er1646v2EthPortSwIXt2IbwActViolActEthCos4
         INTEGER,
      er1646v2EthPortSwIXt2IbwActViolActEthDei4
         INTEGER,
      er1646v2EthPortSwIXt2IbwActViolActEthCos5
         INTEGER,
      er1646v2EthPortSwIXt2IbwActViolActEthDei5
         INTEGER,
      er1646v2EthPortSwIXt2IbwActViolActEthCos6
         INTEGER,
      er1646v2EthPortSwIXt2IbwActViolActEthDei6
         INTEGER,
      er1646v2EthPortSwIXt2IbwActViolActEthCos7
         INTEGER,
      er1646v2EthPortSwIXt2IbwActViolActEthDei7
         INTEGER,
      er1646v2EthPortSwIXt2IbwActViolActEthCos8
         INTEGER,
      er1646v2EthPortSwIXt2IbwActViolActEthDei8
         INTEGER,
      er1646v2EthPortSwIXt2IbwActViolActEthTos
         INTEGER,
      er1646v2EthPortSwIXt2IbwActViolActEthQueue
         INTEGER,
      er1646v2EthPortSwIXt2IbwActViolActEthDrpLev
         INTEGER,
      er1646v2EthPortSwIXt2IbwActViolActEthDeFlag
         INTEGER,
      er1646v2EthPortSwIXt2IbwActViolActIpTos
         INTEGER,
      er1646v2EthPortSwIXt2IbwActViolActIpQueue
         INTEGER,
      er1646v2EthPortSwIXt2IbwActViolActIpDrpLev
         INTEGER,
      er1646v2EthPortSwIXt2IbwActViolActIpDeFlag
         INTEGER,
      er1646v2EthPortSwIXt2IbwSubInterfacesExcluded
         INTEGER,
      er1646v2EthPortSwIXt2IbwSubInterfacesIncludedInAccessList
         DisplayString
      }

er1646v2EthPortSwIXt2IbwGlobalIx OBJECT-TYPE
   SYNTAX      GlobalIndex
   MAX-ACCESS  not-accessible
   STATUS      current
   DESCRIPTION
      "The value of the tlsCntTreeGlobalIndex of the MANAGED OBJECT."
   ::= {er1646v2EthPortSwIXt2IbwEntry 10}

er1646v2EthPortSwIXt2IbwMode OBJECT-TYPE
   SYNTAX      INTEGER
               {
               reshaping (1),
               policing (2)
               }
   MAX-ACCESS  read-write
   STATUS      current
   DESCRIPTION
      "Path: swPort.editConf.inboundBandwidth.mode

       Possibilities:
               reshaping   (1)
               policing   (2)"
   ::= {er1646v2EthPortSwIXt2IbwEntry 3758096384}

er1646v2EthPortSwIXt2IbwCir OBJECT-TYPE
   SYNTAX      Integer32
   MAX-ACCESS  read-write
   STATUS      current
   DESCRIPTION
      "Path: swPort.editConf.inboundBandwidth.cir"
   ::= {er1646v2EthPortSwIXt2IbwEntry 268435456}

er1646v2EthPortSwIXt2IbwEir OBJECT-TYPE
   SYNTAX      Integer32
   MAX-ACCESS  read-write
   STATUS      current
   DESCRIPTION
      "Path: swPort.editConf.inboundBandwidth.eir"
   ::= {er1646v2EthPortSwIXt2IbwEntry 1879048192}

er1646v2EthPortSwIXt2IbwUnit OBJECT-TYPE
   SYNTAX      INTEGER
               {
               bitssec (1),
               percent (2)
               }
   MAX-ACCESS  read-write
   STATUS      current
   DESCRIPTION
      "Path: swPort.editConf.inboundBandwidth.unit

       Possibilities:
               bits/sec   (1)
               percent   (2)"
   ::= {er1646v2EthPortSwIXt2IbwEntry 1342177280}

er1646v2EthPortSwIXt2IbwTc OBJECT-TYPE
   SYNTAX      INTEGER
               {
               auto (0)
               }
   MAX-ACCESS  read-write
   STATUS      current
   DESCRIPTION
      "Path: swPort.editConf.inboundBandwidth.tc

       Possibilities:
               auto   (0)"
   ::= {er1646v2EthPortSwIXt2IbwEntry 1610612736}

er1646v2EthPortSwIXt2IbwTcFactor OBJECT-TYPE
   SYNTAX      INTEGER
               {
               ms (10),
               s100us (1)
               }
   MAX-ACCESS  read-write
   STATUS      current
   DESCRIPTION
      "Path: swPort.editConf.inboundBandwidth.tcFactor

       Possibilities:
               ms   (10)
               *100us   (1)"
   ::= {er1646v2EthPortSwIXt2IbwEntry 2147483648}

er1646v2EthPortSwIXt2IbwCorrType OBJECT-TYPE
   SYNTAX      INTEGER
               {
               noCorrection (0),
               predefined (1),
               manual (2)
               }
   MAX-ACCESS  read-write
   STATUS      current
   DESCRIPTION
      "Path: swPort.editConf.inboundBandwidth.correction.type

       Possibilities:
               noCorrection   (0)
               predefined   (1)
               manual   (2)"
   ::= {er1646v2EthPortSwIXt2IbwEntry 570425344}

er1646v2EthPortSwIXt2IbwCorrPredefEncapsFrameRelay OBJECT-TYPE
   SYNTAX      DisplayString
   MAX-ACCESS  read-write
   STATUS      current
   DESCRIPTION
      "Path: swPort.editConf.inboundBandwidth.correction.predefined.encapsulation.frameRelay"
   ::= {er1646v2EthPortSwIXt2IbwEntry 608436224}

er1646v2EthPortSwIXt2IbwCorrPredefEncapsPpp OBJECT-TYPE
   SYNTAX      DisplayString
   MAX-ACCESS  read-write
   STATUS      current
   DESCRIPTION
      "Path: swPort.editConf.inboundBandwidth.correction.predefined.encapsulation.ppp"
   ::= {er1646v2EthPortSwIXt2IbwEntry 608698368}

er1646v2EthPortSwIXt2IbwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.inboundBandwidth.correction.predefined.encapsulation.atm.higherLayer

       Possibilities:
               rfc2684   (0)
               ppp   (1)
               pppOverEthernet   (2)"
   ::= {er1646v2EthPortSwIXt2IbwEntry 608993280}

er1646v2EthPortSwIXt2IbwCorrPredefEncapsAtmMp OBJECT-TYPE
   SYNTAX      INTEGER
               {
               llcEncapsulation (0),
               vcMultiplexing (1)
               }
   MAX-ACCESS  read-write
   STATUS      current
   DESCRIPTION
      "Path: swPort.editConf.inboundBandwidth.correction.predefined.encapsulation.atm.multiProtocol

       Possibilities:
               llcEncapsulation   (0)
               vcMultiplexing   (1)"
   ::= {er1646v2EthPortSwIXt2IbwEntry 609026048}

er1646v2EthPortSwIXt2IbwCorrPredefEncapsHdlc OBJECT-TYPE
   SYNTAX      DisplayString
   MAX-ACCESS  read-write
   STATUS      current
   DESCRIPTION
      "Path: swPort.editConf.inboundBandwidth.correction.predefined.encapsulation.hdlc"
   ::= {er1646v2EthPortSwIXt2IbwEntry 609222656}

er1646v2EthPortSwIXt2IbwCorrPredefEncapsEfmFs OBJECT-TYPE
   SYNTAX      Integer32
   MAX-ACCESS  read-write
   STATUS      current
   DESCRIPTION
      "Path: swPort.editConf.inboundBandwidth.correction.predefined.encapsulation.efm.fragmentSize"
   ::= {er1646v2EthPortSwIXt2IbwEntry 609517568}

er1646v2EthPortSwIXt2IbwCorrPredefEncapsEfmIb OBJECT-TYPE
   SYNTAX      Integer32
   MAX-ACCESS  read-write
   STATUS      current
   DESCRIPTION
      "Path: swPort.editConf.inboundBandwidth.correction.predefined.encapsulation.efm.idleBytes"
   ::= {er1646v2EthPortSwIXt2IbwEntry 609550336}

er1646v2EthPortSwIXt2IbwCorrPredefMode OBJECT-TYPE
   SYNTAX      INTEGER
               {
               routing (0),
               bridging (1)
               }
   MAX-ACCESS  read-write
   STATUS      current
   DESCRIPTION
      "Path: swPort.editConf.inboundBandwidth.correction.predefined.mode

       Possibilities:
               routing   (0)
               bridging   (1)"
   ::= {er1646v2EthPortSwIXt2IbwEntry 612368384}

er1646v2EthPortSwIXt2IbwCorrManualOverhead OBJECT-TYPE
   SYNTAX      Integer32
   MAX-ACCESS  read-write
   STATUS      current
   DESCRIPTION
      "Path: swPort.editConf.inboundBandwidth.correction.manual.overhead"
   ::= {er1646v2EthPortSwIXt2IbwEntry 637665280}

er1646v2EthPortSwIXt2IbwCorrManualFrameData OBJECT-TYPE
   SYNTAX      Counter32
   MAX-ACCESS  read-write
   STATUS      current
   DESCRIPTION
      "Path: swPort.editConf.inboundBandwidth.correction.manual.frameData

       32 bit unsigned wrappable counter."
   ::= {er1646v2EthPortSwIXt2IbwEntry 637796352}

er1646v2EthPortSwIXt2IbwCorrManualFrameHeader OBJECT-TYPE
   SYNTAX      Counter32
   MAX-ACCESS  read-write
   STATUS      current
   DESCRIPTION
      "Path: swPort.editConf.inboundBandwidth.correction.manual.frameHeader

       32 bit unsigned wrappable counter."
   ::= {er1646v2EthPortSwIXt2IbwEntry 637927424}

er1646v2EthPortSwIXt2IbwMaxFifoQLen OBJECT-TYPE
   SYNTAX      Integer32
   MAX-ACCESS  read-write
   STATUS      current
   DESCRIPTION
      "Path: swPort.editConf.inboundBandwidth.maxFifoQLen"
   ::= {er1646v2EthPortSwIXt2IbwEntry 805306368}

er1646v2EthPortSwIXt2IbwPriorityPolicy OBJECT-TYPE
   SYNTAX      DisplayString
   MAX-ACCESS  read-write
   STATUS      current
   DESCRIPTION
      "Path: swPort.editConf.inboundBandwidth.priorityPolicy"
   ::= {er1646v2EthPortSwIXt2IbwEntry 1073741824}

er1646v2EthPortSwIXt2IbwDeFlagCir OBJECT-TYPE
   SYNTAX      INTEGER
               {
               allowed (1),
               notAllowed (2)
               }
   MAX-ACCESS  read-write
   STATUS      current
   DESCRIPTION
      "Path: swPort.editConf.inboundBandwidth.deFlag.cir

       Possibilities:
               allowed   (1)
               notAllowed   (2)"
   ::= {er1646v2EthPortSwIXt2IbwEntry 3490709504}

er1646v2EthPortSwIXt2IbwDeFlagEir OBJECT-TYPE
   SYNTAX      INTEGER
               {
               allowed (1),
               notAllowed (2)
               }
   MAX-ACCESS  read-write
   STATUS      current
   DESCRIPTION
      "Path: swPort.editConf.inboundBandwidth.deFlag.eir

       Possibilities:
               allowed   (1)
               notAllowed   (2)"
   ::= {er1646v2EthPortSwIXt2IbwEntry 3491758080}

er1646v2EthPortSwIXt2IbwDeFlagViolate OBJECT-TYPE
   SYNTAX      INTEGER
               {
               allowed (1),
               notAllowed (2)
               }
   MAX-ACCESS  read-write
   STATUS      current
   DESCRIPTION
      "Path: swPort.editConf.inboundBandwidth.deFlag.violate

       Possibilities:
               allowed   (1)
               notAllowed   (2)"
   ::= {er1646v2EthPortSwIXt2IbwEntry 3492806656}

er1646v2EthPortSwIXt2IbwActCirActNone OBJECT-TYPE
   SYNTAX      OCTET STRING
   MAX-ACCESS  read-write
   STATUS      current
   DESCRIPTION
      "Path: swPort.editConf.inboundBandwidth.action.cirAction.none"
   ::= {er1646v2EthPortSwIXt2IbwEntry 4062183424}

er1646v2EthPortSwIXt2IbwActCirActEthCos1 OBJECT-TYPE
   SYNTAX      INTEGER
               {
               unchanged (256)
               }
   MAX-ACCESS  read-write
   STATUS      current
   DESCRIPTION
      "Path: swPort.editConf.inboundBandwidth.action.cirAction.ethernet.cosDepth1

       Possibilities:
               unchanged   (256)"
   ::= {er1646v2EthPortSwIXt2IbwEntry 4064346112}

er1646v2EthPortSwIXt2IbwActCirActEthDei1 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth1

       Possibilities:
               unchanged   (255)
               clear   (0)
               set   (1)"
   ::= {er1646v2EthPortSwIXt2IbwEntry 4065656832}

er1646v2EthPortSwIXt2IbwActCirActEthCos2 OBJECT-TYPE
   SYNTAX      INTEGER
               {
               unchanged (256)
               }
   MAX-ACCESS  read-write
   STATUS      current
   DESCRIPTION
      "Path: swPort.editConf.inboundBandwidth.action.cirAction.ethernet.cosDepth2

       Possibilities:
               unchanged   (256)"
   ::= {er1646v2EthPortSwIXt2IbwEntry 4064411648}

er1646v2EthPortSwIXt2IbwActCirActEthDei2 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth2

       Possibilities:
               unchanged   (255)
               clear   (0)
               set   (1)"
   ::= {er1646v2EthPortSwIXt2IbwEntry 4065722368}

er1646v2EthPortSwIXt2IbwActCirActEthCos3 OBJECT-TYPE
   SYNTAX      INTEGER
               {
               unchanged (256)
               }
   MAX-ACCESS  read-write
   STATUS      current
   DESCRIPTION
      "Path: swPort.editConf.inboundBandwidth.action.cirAction.ethernet.cosDepth3

       Possibilities:
               unchanged   (256)"
   ::= {er1646v2EthPortSwIXt2IbwEntry 4064477184}

er1646v2EthPortSwIXt2IbwActCirActEthDei3 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth3

       Possibilities:
               unchanged   (255)
               clear   (0)
               set   (1)"
   ::= {er1646v2EthPortSwIXt2IbwEntry 4065787904}

er1646v2EthPortSwIXt2IbwActCirActEthCos4 OBJECT-TYPE
   SYNTAX      INTEGER
               {
               unchanged (256)
               }
   MAX-ACCESS  read-write
   STATUS      current
   DESCRIPTION
      "Path: swPort.editConf.inboundBandwidth.action.cirAction.ethernet.cosDepth4

       Possibilities:
               unchanged   (256)"
   ::= {er1646v2EthPortSwIXt2IbwEntry 4064542720}

er1646v2EthPortSwIXt2IbwActCirActEthDei4 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth4

       Possibilities:
               unchanged   (255)
               clear   (0)
               set   (1)"
   ::= {er1646v2EthPortSwIXt2IbwEntry 4065853440}

er1646v2EthPortSwIXt2IbwActCirActEthCos5 OBJECT-TYPE
   SYNTAX      INTEGER
               {
               unchanged (256)
               }
   MAX-ACCESS  read-write
   STATUS      current
   DESCRIPTION
      "Path: swPort.editConf.inboundBandwidth.action.cirAction.ethernet.cosDepth5

       Possibilities:
               unchanged   (256)"
   ::= {er1646v2EthPortSwIXt2IbwEntry 4064608256}

er1646v2EthPortSwIXt2IbwActCirActEthDei5 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth5

       Possibilities:
               unchanged   (255)
               clear   (0)
               set   (1)"
   ::= {er1646v2EthPortSwIXt2IbwEntry 4065918976}

er1646v2EthPortSwIXt2IbwActCirActEthCos6 OBJECT-TYPE
   SYNTAX      INTEGER
               {
               unchanged (256)
               }
   MAX-ACCESS  read-write
   STATUS      current
   DESCRIPTION
      "Path: swPort.editConf.inboundBandwidth.action.cirAction.ethernet.cosDepth6

       Possibilities:
               unchanged   (256)"
   ::= {er1646v2EthPortSwIXt2IbwEntry 4064673792}

er1646v2EthPortSwIXt2IbwActCirActEthDei6 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth6

       Possibilities:
               unchanged   (255)
               clear   (0)
               set   (1)"
   ::= {er1646v2EthPortSwIXt2IbwEntry 4065984512}

er1646v2EthPortSwIXt2IbwActCirActEthCos7 OBJECT-TYPE
   SYNTAX      INTEGER
               {
               unchanged (256)
               }
   MAX-ACCESS  read-write
   STATUS      current
   DESCRIPTION
      "Path: swPort.editConf.inboundBandwidth.action.cirAction.ethernet.cosDepth7

       Possibilities:
               unchanged   (256)"
   ::= {er1646v2EthPortSwIXt2IbwEntry 4064739328}

er1646v2EthPortSwIXt2IbwActCirActEthDei7 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth7

       Possibilities:
               unchanged   (255)
               clear   (0)
               set   (1)"
   ::= {er1646v2EthPortSwIXt2IbwEntry 4066050048}

er1646v2EthPortSwIXt2IbwActCirActEthCos8 OBJECT-TYPE
   SYNTAX      INTEGER
               {
               unchanged (256)
               }
   MAX-ACCESS  read-write
   STATUS      current
   DESCRIPTION
      "Path: swPort.editConf.inboundBandwidth.action.cirAction.ethernet.cosDepth8

       Possibilities:
               unchanged   (256)"
   ::= {er1646v2EthPortSwIXt2IbwEntry 4064804864}

er1646v2EthPortSwIXt2IbwActCirActEthDei8 OBJECT-TYPE
   SYNTAX      INTEGER
               {
               unchanged (255),
               clear (0),
               set (1)
               }
   MAX-ACCESS  read-write
   STATUS      current
   DESCRIPTION
      "Path: swPort.editConf.inboundBandwidth.action.cirAction.ethernet.deiDepth8

       Possibilities:
               unchanged   (255)
               clear   (0)
               set   (1)"
   ::= {er1646v2EthPortSwIXt2IbwEntry 4066115584}

er1646v2EthPortSwIXt2IbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2IbwEntry 4064870400}

er1646v2EthPortSwIXt2IbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2IbwEntry 4064935936}

er1646v2EthPortSwIXt2IbwActCirActEthDrpLev OBJECT-TYPE
   SYNTAX      INTEGER
               {
               unchanged (0)
               }
   MAX-ACCESS  read-write
   STATUS      current
   DESCRIPTION
      "Path: swPort.editConf.inboundBandwidth.action.cirAction.ethernet.dropLevel

       Possibilities:
               unchanged   (0)"
   ::= {er1646v2EthPortSwIXt2IbwEntry 4065001472}

er1646v2EthPortSwIXt2IbwActCirActEthDeFlag OBJECT-TYPE
   SYNTAX      INTEGER
               {
               unchanged (255),
               clear (0),
               set (1)
               }
   MAX-ACCESS  read-write
   STATUS      current
   DESCRIPTION
      "Path: swPort.editConf.inboundBandwidth.action.cirAction.ethernet.deFlag

       Possibilities:
               unchanged   (255)
               clear   (0)
               set   (1)"
   ::= {er1646v2EthPortSwIXt2IbwEntry 4065198080}

er1646v2EthPortSwIXt2IbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2IbwEntry 4071161856}

er1646v2EthPortSwIXt2IbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2IbwEntry 4071227392}

er1646v2EthPortSwIXt2IbwActCirActIpDrpLev OBJECT-TYPE
   SYNTAX      INTEGER
               {
               unchanged (0)
               }
   MAX-ACCESS  read-write
   STATUS      current
   DESCRIPTION
      "Path: swPort.editConf.inboundBandwidth.action.cirAction.ip.dropLevel

       Possibilities:
               unchanged   (0)"
   ::= {er1646v2EthPortSwIXt2IbwEntry 4071292928}

er1646v2EthPortSwIXt2IbwActCirActIpDeFlag OBJECT-TYPE
   SYNTAX      INTEGER
               {
               unchanged (255),
               clear (0),
               set (1)
               }
   MAX-ACCESS  read-write
   STATUS      current
   DESCRIPTION
      "Path: swPort.editConf.inboundBandwidth.action.cirAction.ip.deFlag

       Possibilities:
               unchanged   (255)
               clear   (0)
               set   (1)"
   ::= {er1646v2EthPortSwIXt2IbwEntry 4071489536}

er1646v2EthPortSwIXt2IbwActEirActNone OBJECT-TYPE
   SYNTAX      OCTET STRING
   MAX-ACCESS  read-write
   STATUS      current
   DESCRIPTION
      "Path: swPort.editConf.inboundBandwidth.action.eirAction.none"
   ::= {er1646v2EthPortSwIXt2IbwEntry 4095737856}

er1646v2EthPortSwIXt2IbwActEirActEthCos1 OBJECT-TYPE
   SYNTAX      INTEGER
               {
               unchanged (256)
               }
   MAX-ACCESS  read-write
   STATUS      current
   DESCRIPTION
      "Path: swPort.editConf.inboundBandwidth.action.eirAction.ethernet.cosDepth1

       Possibilities:
               unchanged   (256)"
   ::= {er1646v2EthPortSwIXt2IbwEntry 4097900544}

er1646v2EthPortSwIXt2IbwActEirActEthDei1 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth1

       Possibilities:
               unchanged   (255)
               clear   (0)
               set   (1)"
   ::= {er1646v2EthPortSwIXt2IbwEntry 4099211264}

er1646v2EthPortSwIXt2IbwActEirActEthCos2 OBJECT-TYPE
   SYNTAX      INTEGER
               {
               unchanged (256)
               }
   MAX-ACCESS  read-write
   STATUS      current
   DESCRIPTION
      "Path: swPort.editConf.inboundBandwidth.action.eirAction.ethernet.cosDepth2

       Possibilities:
               unchanged   (256)"
   ::= {er1646v2EthPortSwIXt2IbwEntry 4097966080}

er1646v2EthPortSwIXt2IbwActEirActEthDei2 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth2

       Possibilities:
               unchanged   (255)
               clear   (0)
               set   (1)"
   ::= {er1646v2EthPortSwIXt2IbwEntry 4099276800}

er1646v2EthPortSwIXt2IbwActEirActEthCos3 OBJECT-TYPE
   SYNTAX      INTEGER
               {
               unchanged (256)
               }
   MAX-ACCESS  read-write
   STATUS      current
   DESCRIPTION
      "Path: swPort.editConf.inboundBandwidth.action.eirAction.ethernet.cosDepth3

       Possibilities:
               unchanged   (256)"
   ::= {er1646v2EthPortSwIXt2IbwEntry 4098031616}

er1646v2EthPortSwIXt2IbwActEirActEthDei3 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth3

       Possibilities:
               unchanged   (255)
               clear   (0)
               set   (1)"
   ::= {er1646v2EthPortSwIXt2IbwEntry 4099342336}

er1646v2EthPortSwIXt2IbwActEirActEthCos4 OBJECT-TYPE
   SYNTAX      INTEGER
               {
               unchanged (256)
               }
   MAX-ACCESS  read-write
   STATUS      current
   DESCRIPTION
      "Path: swPort.editConf.inboundBandwidth.action.eirAction.ethernet.cosDepth4

       Possibilities:
               unchanged   (256)"
   ::= {er1646v2EthPortSwIXt2IbwEntry 4098097152}

er1646v2EthPortSwIXt2IbwActEirActEthDei4 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth4

       Possibilities:
               unchanged   (255)
               clear   (0)
               set   (1)"
   ::= {er1646v2EthPortSwIXt2IbwEntry 4099407872}

er1646v2EthPortSwIXt2IbwActEirActEthCos5 OBJECT-TYPE
   SYNTAX      INTEGER
               {
               unchanged (256)
               }
   MAX-ACCESS  read-write
   STATUS      current
   DESCRIPTION
      "Path: swPort.editConf.inboundBandwidth.action.eirAction.ethernet.cosDepth5

       Possibilities:
               unchanged   (256)"
   ::= {er1646v2EthPortSwIXt2IbwEntry 4098162688}

er1646v2EthPortSwIXt2IbwActEirActEthDei5 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth5

       Possibilities:
               unchanged   (255)
               clear   (0)
               set   (1)"
   ::= {er1646v2EthPortSwIXt2IbwEntry 4099473408}

er1646v2EthPortSwIXt2IbwActEirActEthCos6 OBJECT-TYPE
   SYNTAX      INTEGER
               {
               unchanged (256)
               }
   MAX-ACCESS  read-write
   STATUS      current
   DESCRIPTION
      "Path: swPort.editConf.inboundBandwidth.action.eirAction.ethernet.cosDepth6

       Possibilities:
               unchanged   (256)"
   ::= {er1646v2EthPortSwIXt2IbwEntry 4098228224}

er1646v2EthPortSwIXt2IbwActEirActEthDei6 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth6

       Possibilities:
               unchanged   (255)
               clear   (0)
               set   (1)"
   ::= {er1646v2EthPortSwIXt2IbwEntry 4099538944}

er1646v2EthPortSwIXt2IbwActEirActEthCos7 OBJECT-TYPE
   SYNTAX      INTEGER
               {
               unchanged (256)
               }
   MAX-ACCESS  read-write
   STATUS      current
   DESCRIPTION
      "Path: swPort.editConf.inboundBandwidth.action.eirAction.ethernet.cosDepth7

       Possibilities:
               unchanged   (256)"
   ::= {er1646v2EthPortSwIXt2IbwEntry 4098293760}

er1646v2EthPortSwIXt2IbwActEirActEthDei7 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth7

       Possibilities:
               unchanged   (255)
               clear   (0)
               set   (1)"
   ::= {er1646v2EthPortSwIXt2IbwEntry 4099604480}

er1646v2EthPortSwIXt2IbwActEirActEthCos8 OBJECT-TYPE
   SYNTAX      INTEGER
               {
               unchanged (256)
               }
   MAX-ACCESS  read-write
   STATUS      current
   DESCRIPTION
      "Path: swPort.editConf.inboundBandwidth.action.eirAction.ethernet.cosDepth8

       Possibilities:
               unchanged   (256)"
   ::= {er1646v2EthPortSwIXt2IbwEntry 4098359296}

er1646v2EthPortSwIXt2IbwActEirActEthDei8 OBJECT-TYPE
   SYNTAX      INTEGER
               {
               unchanged (255),
               clear (0),
               set (1)
               }
   MAX-ACCESS  read-write
   STATUS      current
   DESCRIPTION
      "Path: swPort.editConf.inboundBandwidth.action.eirAction.ethernet.deiDepth8

       Possibilities:
               unchanged   (255)
               clear   (0)
               set   (1)"
   ::= {er1646v2EthPortSwIXt2IbwEntry 4099670016}

er1646v2EthPortSwIXt2IbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2IbwEntry 4098424832}

er1646v2EthPortSwIXt2IbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2IbwEntry 4098490368}

er1646v2EthPortSwIXt2IbwActEirActEthDrpLev OBJECT-TYPE
   SYNTAX      INTEGER
               {
               unchanged (0)
               }
   MAX-ACCESS  read-write
   STATUS      current
   DESCRIPTION
      "Path: swPort.editConf.inboundBandwidth.action.eirAction.ethernet.dropLevel

       Possibilities:
               unchanged   (0)"
   ::= {er1646v2EthPortSwIXt2IbwEntry 4098555904}

er1646v2EthPortSwIXt2IbwActEirActEthDeFlag OBJECT-TYPE
   SYNTAX      INTEGER
               {
               unchanged (255),
               clear (0),
               set (1)
               }
   MAX-ACCESS  read-write
   STATUS      current
   DESCRIPTION
      "Path: swPort.editConf.inboundBandwidth.action.eirAction.ethernet.deFlag

       Possibilities:
               unchanged   (255)
               clear   (0)
               set   (1)"
   ::= {er1646v2EthPortSwIXt2IbwEntry 4098752512}

er1646v2EthPortSwIXt2IbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2IbwEntry 4104716288}

er1646v2EthPortSwIXt2IbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2IbwEntry 4104781824}

er1646v2EthPortSwIXt2IbwActEirActIpDrpLev OBJECT-TYPE
   SYNTAX      INTEGER
               {
               unchanged (0)
               }
   MAX-ACCESS  read-write
   STATUS      current
   DESCRIPTION
      "Path: swPort.editConf.inboundBandwidth.action.eirAction.ip.dropLevel

       Possibilities:
               unchanged   (0)"
   ::= {er1646v2EthPortSwIXt2IbwEntry 4104847360}

er1646v2EthPortSwIXt2IbwActEirActIpDeFlag OBJECT-TYPE
   SYNTAX      INTEGER
               {
               unchanged (255),
               clear (0),
               set (1)
               }
   MAX-ACCESS  read-write
   STATUS      current
   DESCRIPTION
      "Path: swPort.editConf.inboundBandwidth.action.eirAction.ip.deFlag

       Possibilities:
               unchanged   (255)
               clear   (0)
               set   (1)"
   ::= {er1646v2EthPortSwIXt2IbwEntry 4105043968}

er1646v2EthPortSwIXt2IbwActViolActNone OBJECT-TYPE
   SYNTAX      OCTET STRING
   MAX-ACCESS  read-write
   STATUS      current
   DESCRIPTION
      "Path: swPort.editConf.inboundBandwidth.action.violateAction.none"
   ::= {er1646v2EthPortSwIXt2IbwEntry 4129292288}

er1646v2EthPortSwIXt2IbwActViolActDrop OBJECT-TYPE
   SYNTAX      OCTET STRING
   MAX-ACCESS  read-write
   STATUS      current
   DESCRIPTION
      "Path: swPort.editConf.inboundBandwidth.action.violateAction.drop"
   ::= {er1646v2EthPortSwIXt2IbwEntry 4133486592}

er1646v2EthPortSwIXt2IbwActViolActEthCos1 OBJECT-TYPE
   SYNTAX      INTEGER
               {
               unchanged (256)
               }
   MAX-ACCESS  read-write
   STATUS      current
   DESCRIPTION
      "Path: swPort.editConf.inboundBandwidth.action.violateAction.ethernet.cosDepth1

       Possibilities:
               unchanged   (256)"
   ::= {er1646v2EthPortSwIXt2IbwEntry 4131454976}

er1646v2EthPortSwIXt2IbwActViolActEthDei1 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth1

       Possibilities:
               unchanged   (255)
               clear   (0)
               set   (1)"
   ::= {er1646v2EthPortSwIXt2IbwEntry 4132765696}

er1646v2EthPortSwIXt2IbwActViolActEthCos2 OBJECT-TYPE
   SYNTAX      INTEGER
               {
               unchanged (256)
               }
   MAX-ACCESS  read-write
   STATUS      current
   DESCRIPTION
      "Path: swPort.editConf.inboundBandwidth.action.violateAction.ethernet.cosDepth2

       Possibilities:
               unchanged   (256)"
   ::= {er1646v2EthPortSwIXt2IbwEntry 4131520512}

er1646v2EthPortSwIXt2IbwActViolActEthDei2 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth2

       Possibilities:
               unchanged   (255)
               clear   (0)
               set   (1)"
   ::= {er1646v2EthPortSwIXt2IbwEntry 4132831232}

er1646v2EthPortSwIXt2IbwActViolActEthCos3 OBJECT-TYPE
   SYNTAX      INTEGER
               {
               unchanged (256)
               }
   MAX-ACCESS  read-write
   STATUS      current
   DESCRIPTION
      "Path: swPort.editConf.inboundBandwidth.action.violateAction.ethernet.cosDepth3

       Possibilities:
               unchanged   (256)"
   ::= {er1646v2EthPortSwIXt2IbwEntry 4131586048}

er1646v2EthPortSwIXt2IbwActViolActEthDei3 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth3

       Possibilities:
               unchanged   (255)
               clear   (0)
               set   (1)"
   ::= {er1646v2EthPortSwIXt2IbwEntry 4132896768}

er1646v2EthPortSwIXt2IbwActViolActEthCos4 OBJECT-TYPE
   SYNTAX      INTEGER
               {
               unchanged (256)
               }
   MAX-ACCESS  read-write
   STATUS      current
   DESCRIPTION
      "Path: swPort.editConf.inboundBandwidth.action.violateAction.ethernet.cosDepth4

       Possibilities:
               unchanged   (256)"
   ::= {er1646v2EthPortSwIXt2IbwEntry 4131651584}

er1646v2EthPortSwIXt2IbwActViolActEthDei4 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth4

       Possibilities:
               unchanged   (255)
               clear   (0)
               set   (1)"
   ::= {er1646v2EthPortSwIXt2IbwEntry 4132962304}

er1646v2EthPortSwIXt2IbwActViolActEthCos5 OBJECT-TYPE
   SYNTAX      INTEGER
               {
               unchanged (256)
               }
   MAX-ACCESS  read-write
   STATUS      current
   DESCRIPTION
      "Path: swPort.editConf.inboundBandwidth.action.violateAction.ethernet.cosDepth5

       Possibilities:
               unchanged   (256)"
   ::= {er1646v2EthPortSwIXt2IbwEntry 4131717120}

er1646v2EthPortSwIXt2IbwActViolActEthDei5 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth5

       Possibilities:
               unchanged   (255)
               clear   (0)
               set   (1)"
   ::= {er1646v2EthPortSwIXt2IbwEntry 4133027840}

er1646v2EthPortSwIXt2IbwActViolActEthCos6 OBJECT-TYPE
   SYNTAX      INTEGER
               {
               unchanged (256)
               }
   MAX-ACCESS  read-write
   STATUS      current
   DESCRIPTION
      "Path: swPort.editConf.inboundBandwidth.action.violateAction.ethernet.cosDepth6

       Possibilities:
               unchanged   (256)"
   ::= {er1646v2EthPortSwIXt2IbwEntry 4131782656}

er1646v2EthPortSwIXt2IbwActViolActEthDei6 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth6

       Possibilities:
               unchanged   (255)
               clear   (0)
               set   (1)"
   ::= {er1646v2EthPortSwIXt2IbwEntry 4133093376}

er1646v2EthPortSwIXt2IbwActViolActEthCos7 OBJECT-TYPE
   SYNTAX      INTEGER
               {
               unchanged (256)
               }
   MAX-ACCESS  read-write
   STATUS      current
   DESCRIPTION
      "Path: swPort.editConf.inboundBandwidth.action.violateAction.ethernet.cosDepth7

       Possibilities:
               unchanged   (256)"
   ::= {er1646v2EthPortSwIXt2IbwEntry 4131848192}

er1646v2EthPortSwIXt2IbwActViolActEthDei7 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth7

       Possibilities:
               unchanged   (255)
               clear   (0)
               set   (1)"
   ::= {er1646v2EthPortSwIXt2IbwEntry 4133158912}

er1646v2EthPortSwIXt2IbwActViolActEthCos8 OBJECT-TYPE
   SYNTAX      INTEGER
               {
               unchanged (256)
               }
   MAX-ACCESS  read-write
   STATUS      current
   DESCRIPTION
      "Path: swPort.editConf.inboundBandwidth.action.violateAction.ethernet.cosDepth8

       Possibilities:
               unchanged   (256)"
   ::= {er1646v2EthPortSwIXt2IbwEntry 4131913728}

er1646v2EthPortSwIXt2IbwActViolActEthDei8 OBJECT-TYPE
   SYNTAX      INTEGER
               {
               unchanged (255),
               clear (0),
               set (1)
               }
   MAX-ACCESS  read-write
   STATUS      current
   DESCRIPTION
      "Path: swPort.editConf.inboundBandwidth.action.violateAction.ethernet.deiDepth8

       Possibilities:
               unchanged   (255)
               clear   (0)
               set   (1)"
   ::= {er1646v2EthPortSwIXt2IbwEntry 4133224448}

er1646v2EthPortSwIXt2IbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2IbwEntry 4131979264}

er1646v2EthPortSwIXt2IbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2IbwEntry 4132044800}

er1646v2EthPortSwIXt2IbwActViolActEthDrpLev OBJECT-TYPE
   SYNTAX      INTEGER
               {
               unchanged (0)
               }
   MAX-ACCESS  read-write
   STATUS      current
   DESCRIPTION
      "Path: swPort.editConf.inboundBandwidth.action.violateAction.ethernet.dropLevel

       Possibilities:
               unchanged   (0)"
   ::= {er1646v2EthPortSwIXt2IbwEntry 4132110336}

er1646v2EthPortSwIXt2IbwActViolActEthDeFlag OBJECT-TYPE
   SYNTAX      INTEGER
               {
               unchanged (255),
               clear (0),
               set (1)
               }
   MAX-ACCESS  read-write
   STATUS      current
   DESCRIPTION
      "Path: swPort.editConf.inboundBandwidth.action.violateAction.ethernet.deFlag

       Possibilities:
               unchanged   (255)
               clear   (0)
               set   (1)"
   ::= {er1646v2EthPortSwIXt2IbwEntry 4132306944}

er1646v2EthPortSwIXt2IbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2IbwEntry 4138270720}

er1646v2EthPortSwIXt2IbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2IbwEntry 4138336256}

er1646v2EthPortSwIXt2IbwActViolActIpDrpLev OBJECT-TYPE
   SYNTAX      INTEGER
               {
               unchanged (0)
               }
   MAX-ACCESS  read-write
   STATUS      current
   DESCRIPTION
      "Path: swPort.editConf.inboundBandwidth.action.violateAction.ip.dropLevel

       Possibilities:
               unchanged   (0)"
   ::= {er1646v2EthPortSwIXt2IbwEntry 4138401792}

er1646v2EthPortSwIXt2IbwActViolActIpDeFlag OBJECT-TYPE
   SYNTAX      INTEGER
               {
               unchanged (255),
               clear (0),
               set (1)
               }
   MAX-ACCESS  read-write
   STATUS      current
   DESCRIPTION
      "Path: swPort.editConf.inboundBandwidth.action.violateAction.ip.deFlag

       Possibilities:
               unchanged   (255)
               clear   (0)
               set   (1)"
   ::= {er1646v2EthPortSwIXt2IbwEntry 4138598400}

er1646v2EthPortSwIXt2IbwSubInterfacesExcluded OBJECT-TYPE
   SYNTAX      INTEGER
               {
               s (1)
               }
   MAX-ACCESS  read-write
   STATUS      current
   DESCRIPTION
      "Path: swPort.editConf.inboundBandwidth.subInterfaces.excluded

       Possibilities:
                  (1)"
   ::= {er1646v2EthPortSwIXt2IbwEntry 2416967680}

er1646v2EthPortSwIXt2IbwSubInterfacesIncludedInAccessList OBJECT-TYPE
   SYNTAX      DisplayString
   MAX-ACCESS  read-write
   STATUS      current
   DESCRIPTION
      "Path: swPort.editConf.inboundBandwidth.subInterfaces.included.inAccessList"
   ::= {er1646v2EthPortSwIXt2IbwEntry 2418020352}


er1646v2EthPortSwIXt2Vlan OBJECT IDENTIFIER ::= {er1646v2EthPortSwIXt2 33}

er1646v2EthPortSwIXt2VlanSSCTable OBJECT-TYPE
   SYNTAX      SEQUENCE OF Er1646v2EthPortSwIXt2VlanEntry
   MAX-ACCESS  not-accessible
   STATUS      current
   DESCRIPTION
      ""
   ::= {er1646v2EthPortSwIXt2Vlan 1}

er1646v2EthPortSwIXt2VlanEntry OBJECT-TYPE
   SYNTAX      Er1646v2EthPortSwIXt2VlanEntry
   MAX-ACCESS  not-accessible
   STATUS      current
   DESCRIPTION
      ""
   INDEX      { er1646v2EthPortSwIXt2VlanGlobalIx,
                er1646v2EthPortSwIXt2VlanTableIx }
   ::= {er1646v2EthPortSwIXt2VlanSSCTable 1}

Er1646v2EthPortSwIXt2VlanEntry ::=
   SEQUENCE
      {
      er1646v2EthPortSwIXt2VlanActions
         VariableLengthTableActions,
      er1646v2EthPortSwIXt2VlanGlobalIx
         GlobalIndex,
      er1646v2EthPortSwIXt2VlanTableIx
         TableIndex,
      er1646v2EthPortSwIXt2VlanName
         DisplayString,
      er1646v2EthPortSwIXt2VlanRemark
         DisplayString,
      er1646v2EthPortSwIXt2VlanAdminStatus
         INTEGER,
      er1646v2EthPortSwIXt2VlanMode
         INTEGER,
      er1646v2EthPortSwIXt2VlanPriorityPolicy
         DisplayString,
      er1646v2EthPortSwIXt2VlanIpVrfRouter
         DisplayString,
      er1646v2EthPortSwIXt2VlanIpAdr
         IpAddress,
      er1646v2EthPortSwIXt2VlanIpNetm
         IpAddress,
      er1646v2EthPortSwIXt2VlanIpSNetName
         INTEGER,
      er1646v2EthPortSwIXt2VlanIpSNetCust
         DisplayString,
      er1646v2EthPortSwIXt2VlanIpDhcpC
         INTEGER,
      er1646v2EthPortSwIXt2VlanIpDhcpGatewayPreference
         Integer32,
      er1646v2EthPortSwIXt2VlanIpDhcpRoutePreference
         Integer32,
      er1646v2EthPortSwIXt2VlanIpDhcpDnsPreference
         Integer32,
      er1646v2EthPortSwIXt2VlanIpMtu
         Integer32,
      er1646v2EthPortSwIXt2VlanIpMssAdjust
         INTEGER,
      er1646v2EthPortSwIXt2VlanIpRipMetric
         Integer32,
      er1646v2EthPortSwIXt2VlanIpRipMetricOut
         Integer32,
      er1646v2EthPortSwIXt2VlanIpRipMode
         INTEGER,
      er1646v2EthPortSwIXt2VlanIpRipTxVer
         INTEGER,
      er1646v2EthPortSwIXt2VlanIpRipRxVer
         INTEGER,
      er1646v2EthPortSwIXt2VlanIpRipSplitH
         INTEGER,
      er1646v2EthPortSwIXt2VlanIpRipAuth
         INTEGER,
      er1646v2EthPortSwIXt2VlanIpRipFilter
         DisplayString,
      er1646v2EthPortSwIXt2VlanIpRipFilterIn
         DisplayString,
      er1646v2EthPortSwIXt2VlanIpRipClearNextHop
         INTEGER,
      er1646v2EthPortSwIXt2VlanIpAccPol
         DisplayString,
      er1646v2EthPortSwIXt2VlanIpAB
         DisplayString,
      er1646v2EthPortSwIXt2VlanIpMA
         INTEGER,
      er1646v2EthPortSwIXt2VlanIpMF
         Integer32,
      er1646v2EthPortSwIXt2VlanIpDB
         INTEGER,
      er1646v2EthPortSwIXt2VlanIpIR
         INTEGER,
      er1646v2EthPortSwIXt2VlanIpIgmp
         INTEGER,
      er1646v2EthPortSwIXt2VlanIpNN
         DisplayString,
      er1646v2EthPortSwIXt2VlanIpVrrp
         INTEGER,
      er1646v2EthPortSwIXt2VlanIpPimMode
         INTEGER,
      er1646v2EthPortSwIXt2VlanIpPimDrPriority
         Counter32,
      er1646v2EthPortSwIXt2VlanIpPimHelloTime
         TimeTicks,
      er1646v2EthPortSwIXt2VlanIpPimPropagationDelay
         TimeTicks,
      er1646v2EthPortSwIXt2VlanIpPimOverrideInterval
         TimeTicks,
      er1646v2EthPortSwIXt2VlanIpPimBsrBorder
         INTEGER,
      er1646v2EthPortSwIXt2VlanIpPimTtlThreshold
         Integer32,
      er1646v2EthPortSwIXt2VlanIpIMNetworkUnreachable
         INTEGER,
      er1646v2EthPortSwIXt2VlanIpIMHostUnreachable
         INTEGER,
      er1646v2EthPortSwIXt2VlanIpIMProtocolUnreachable
         INTEGER,
      er1646v2EthPortSwIXt2VlanIpIMPortUnreachable
         INTEGER,
      er1646v2EthPortSwIXt2VlanIpIMMtuExceeded
         INTEGER,
      er1646v2EthPortSwIXt2VlanIpIMAdminProhibited
         INTEGER,
      er1646v2EthPortSwIXt2VlanIpIMTtlExceeded
         INTEGER,
      er1646v2EthPortSwIXt2VlanIpIMRedirect
         INTEGER,
      er1646v2EthPortSwIXt2VlanIpV6VrfRouter
         DisplayString,
      er1646v2EthPortSwIXt2VlanIpV6AddrAutoConfigNrDupAddrDetects
         Integer32,
      er1646v2EthPortSwIXt2VlanIpV6AddrAutoConfigAcceptRa
         INTEGER,
      er1646v2EthPortSwIXt2VlanIpV6AddrAutoConfigAcceptRaRdnss
         INTEGER,
      er1646v2EthPortSwIXt2VlanIpV6AddrAutoConfigAcceptRaDnssl
         INTEGER,
      er1646v2EthPortSwIXt2VlanIpV6DefaultRoute
         INTEGER,
      er1646v2EthPortSwIXt2VlanIpV6RaSend
         INTEGER,
      er1646v2EthPortSwIXt2VlanIpV6RaMinInterval
         TimeTicks,
      er1646v2EthPortSwIXt2VlanIpV6RaMaxInterval
         TimeTicks,
      er1646v2EthPortSwIXt2VlanIpV6RaManagedFlag
         INTEGER,
      er1646v2EthPortSwIXt2VlanIpV6RaOtherConfFlag
         INTEGER,
      er1646v2EthPortSwIXt2VlanIpV6RaLinkMtu
         Integer32,
      er1646v2EthPortSwIXt2VlanIpV6RaReachableTime
         TimeTicks,
      er1646v2EthPortSwIXt2VlanIpV6RaRetransmitTime
         TimeTicks,
      er1646v2EthPortSwIXt2VlanIpV6RaHopLimit
         Integer32,
      er1646v2EthPortSwIXt2VlanIpV6RaDefaultLifeTime
         TimeTicks,
      er1646v2EthPortSwIXt2VlanIpV6RaDnsOptionsRdnssLifeTime
         TimeTicks,
      er1646v2EthPortSwIXt2VlanIpV6RaDnsOptionsRdnssImportServers
         INTEGER,
      er1646v2EthPortSwIXt2VlanIpV6RaDnsOptionsDnsslLifeTime
         TimeTicks,
      er1646v2EthPortSwIXt2VlanIpV6RaDnsOptionsDnsslImportDomains
         INTEGER,
      er1646v2EthPortSwIXt2VlanIpV6RsSend
         INTEGER,
      er1646v2EthPortSwIXt2VlanIpV6RsMaxRandomDelay
         TimeTicks,
      er1646v2EthPortSwIXt2VlanIpV6RsInterval
         TimeTicks,
      er1646v2EthPortSwIXt2VlanIpV6RsMaxSolicitations
         Integer32,
      er1646v2EthPortSwIXt2VlanIpV6TrafficPolicyInbound
         DisplayString,
      er1646v2EthPortSwIXt2VlanIpV6TrafficPolicyOutbound
         DisplayString,
      er1646v2EthPortSwIXt2VlanIpV6FirewallZone
         DisplayString,
      er1646v2EthPortSwIXt2VlanIpV6DhcpClientAddrAC
         INTEGER,
      er1646v2EthPortSwIXt2VlanIpV6DhcpClientPrDelMode
         INTEGER,
      er1646v2EthPortSwIXt2VlanIpV6DhcpClientPrDelPool
         DisplayString,
      er1646v2EthPortSwIXt2VlanIpV6DhcpClientPrDelPdExclOpt
         INTEGER,
      er1646v2EthPortSwIXt2VlanIpV6DhcpClientDnsServerPref
         Integer32,
      er1646v2EthPortSwIXt2VlanIpV6DhcpClientRapidCommit
         INTEGER,
      er1646v2EthPortSwIXt2VlanIpV6DhcpClientTimersSolTimeOut
         TimeTicks,
      er1646v2EthPortSwIXt2VlanIpV6DhcpClientTimersSolMaxRt
         TimeTicks,
      er1646v2EthPortSwIXt2VlanIpV6DhcpClientTimersInfoRefresh
         TimeTicks,
      er1646v2EthPortSwIXt2VlanIpV6DhcpServerMode
         INTEGER,
      er1646v2EthPortSwIXt2VlanIpV6DhcpServerPreference
         Integer32,
      er1646v2EthPortSwIXt2VlanIpV6DhcpServerPool
         DisplayString,
      er1646v2EthPortSwIXt2VlanIpV6DhcpServerRapidCommit
         INTEGER,
      er1646v2EthPortSwIXt2VlanIpV6DhcpServerTimersInfoRefresh
         TimeTicks,
      er1646v2EthPortSwIXt2VlanIpV6DhcpRelayMode
         INTEGER,
      er1646v2EthPortSwIXt2VlanIpV6SendRedirect
         INTEGER,
      er1646v2EthPortSwIXt2VlanIpV6LinkMtu
         Integer32,
      er1646v2EthPortSwIXt2VlanIpV6InterfaceId
         OCTET STRING,
      er1646v2EthPortSwIXt2VlanIpV6MF
         Integer32,
      er1646v2EthPortSwIXt2VlanIpV6IcmpMessagesNoRoute
         INTEGER,
      er1646v2EthPortSwIXt2VlanIpV6IcmpMessagesBeyondScope
         INTEGER,
      er1646v2EthPortSwIXt2VlanIpV6IcmpMessagesAddressUnreachable
         INTEGER,
      er1646v2EthPortSwIXt2VlanIpV6IcmpMessagesPortUnreachable
         INTEGER,
      er1646v2EthPortSwIXt2VlanIpV6IcmpMessagesPacketTooBig
         INTEGER,
      er1646v2EthPortSwIXt2VlanIpV6IcmpMessagesHopLimitExceeded
         INTEGER,
      er1646v2EthPortSwIXt2VlanIpV6IcmpMessagesFragTimeExceeded
         INTEGER,
      er1646v2EthPortSwIXt2VlanIpV6IcmpMessagesHeaderFieldErr
         INTEGER,
      er1646v2EthPortSwIXt2VlanIpV6IcmpMessagesOptionUnrecognized
         INTEGER,
      er1646v2EthPortSwIXt2VlanIpV6IcmpMessagesRedirect
         INTEGER,
      er1646v2EthPortSwIXt2VlanBridgingAccList
         DisplayString,
      er1646v2EthPortSwIXt2VlanBridgingInACL
         DisplayString,
      er1646v2EthPortSwIXt2VlanBridgingTp
         DisplayString,
      er1646v2EthPortSwIXt2VlanBridgingBrGrp
         DisplayString,
      er1646v2EthPortSwIXt2VlanBridgingLimBC
         INTEGER,
      er1646v2EthPortSwIXt2VlanBridgingPrivateMode
         INTEGER,
      er1646v2EthPortSwIXt2VlanBridgingLearning
         INTEGER,
      er1646v2EthPortSwIXt2VlanBridgingMaxCacheSize
         INTEGER,
      er1646v2EthPortSwIXt2VlanBridgingRelearnDropOnRelearn
         INTEGER,
      er1646v2EthPortSwIXt2VlanBridgingRelearnShutdownThreshold
         Integer32,
      er1646v2EthPortSwIXt2VlanBridgingRelearnShutdownTime
         TimeTicks,
      er1646v2EthPortSwIXt2VlanBridgingRelearnLoopDetection
         INTEGER,
      er1646v2EthPortSwIXt2VlanBridgingRelearnLoopDetectionInterval
         TimeTicks,
      er1646v2EthPortSwIXt2VlanBridgingVlanMemberShip
         INTEGER,
      er1646v2EthPortSwIXt2VlanBridgingVlTUntaggedAction
         INTEGER,
      er1646v2EthPortSwIXt2VlanBridgingVlTUntaggedTagInfoTpid
         INTEGER,
      er1646v2EthPortSwIXt2VlanBridgingVlTUntaggedTagInfoVid
         Integer32,
      er1646v2EthPortSwIXt2VlanBridgingVlTUnknownVlansAction
         INTEGER,
      er1646v2EthPortSwIXt2VlanBridgingVlTUnknownVlansTagInfoTpid
         INTEGER,
      er1646v2EthPortSwIXt2VlanBridgingVlTUnknownVlansTagInfoVid
         Integer32,
      er1646v2EthPortSwIXt2VlanBridgingDot1adType
         INTEGER,
      er1646v2EthPortSwIXt2VlanBridgingPriority
         Integer32,
      er1646v2EthPortSwIXt2VlanBridgingPathCost
         Integer32,
      er1646v2EthPortSwIXt2VlanBridgingInternalPathCost
         Integer32,
      er1646v2EthPortSwIXt2VlanBridgingTCD
         INTEGER,
      er1646v2EthPortSwIXt2VlanBridgingRestrictedRole
         INTEGER,
      er1646v2EthPortSwIXt2VlanBridgingAdminEdge
         INTEGER,
      er1646v2EthPortSwIXt2VlanBridgingOamMacDeviceMac
         DisplayString,
      er1646v2EthPortSwIXt2VlanBridgingOamMacUserMac
         OCTET STRING,
      er1646v2EthPortSwIXt2VlanBridgingOamMacBridgeMac
         DisplayString,
      er1646v2EthPortSwIXt2VlanBridgingMgmtInline
         INTEGER,
      er1646v2EthPortSwIXt2VlanBridgingL2ptMode
         INTEGER,
      er1646v2EthPortSwIXt2VlanBridgingL2ptProtocols
         Integer32,
      er1646v2EthPortSwIXt2VlanBridgingL2ptDestMac
         OCTET STRING,
      er1646v2EthPortSwIXt2VlanBridgingL2ptCos
         INTEGER,
      er1646v2EthPortSwIXt2VlanBridgingL2ptDropThrStp
         INTEGER,
      er1646v2EthPortSwIXt2VlanBridgingL2ptDropThrLldp
         INTEGER,
      er1646v2EthPortSwIXt2VlanBridgingL2ptDropThrOam
         INTEGER,
      er1646v2EthPortSwIXt2VlanBridgingL2ptDropThrCdp
         INTEGER,
      er1646v2EthPortSwIXt2VlanBridgingL2ptDropThrVtp
         INTEGER,
      er1646v2EthPortSwIXt2VlanBridgingL2ptDropThrLacp
         INTEGER,
      er1646v2EthPortSwIXt2VlanBridgingL2ptDropThrEfmOam
         INTEGER,
      er1646v2EthPortSwIXt2VlanBridgingL2ptDropThrPvst
         INTEGER,
      er1646v2EthPortSwIXt2VlanBridgingL2ptDropThrMmrp
         INTEGER,
      er1646v2EthPortSwIXt2VlanBridgingL2ptDropThrMvrp
         INTEGER,
      er1646v2EthPortSwIXt2VlanBridgingL2ptDropThrGvrp
         INTEGER,
      er1646v2EthPortSwIXt2VlanBridgingL2ptDropThrGmrp
         INTEGER,
      er1646v2EthPortSwIXt2VlanBridgingL2ptDropThrDtp
         INTEGER,
      er1646v2EthPortSwIXt2VlanBridgingL2ptDropThrPagp
         INTEGER,
      er1646v2EthPortSwIXt2VlanBridgingL2ptDropThrUdld
         INTEGER,
      er1646v2EthPortSwIXt2VlanVlanVid
         INTEGER,
      er1646v2EthPortSwIXt2VlanVlanVidExtensionSingle
         OCTET STRING,
      er1646v2EthPortSwIXt2VlanVlanVidExtensionEndVid
         Integer32,
      er1646v2EthPortSwIXt2VlanVlanTpid
         INTEGER,
      er1646v2EthPortSwIXt2VlanVlanTagSign
         INTEGER,
      er1646v2EthPortSwIXt2VlanVlanChTos
         INTEGER,
      er1646v2EthPortSwIXt2VlanVlanCTMapP0
         INTEGER,
      er1646v2EthPortSwIXt2VlanVlanCTMapP1
         INTEGER,
      er1646v2EthPortSwIXt2VlanVlanCTMapP2
         INTEGER,
      er1646v2EthPortSwIXt2VlanVlanCTMapP3
         INTEGER,
      er1646v2EthPortSwIXt2VlanVlanCTMapP4
         INTEGER,
      er1646v2EthPortSwIXt2VlanVlanCTMapP5
         INTEGER,
      er1646v2EthPortSwIXt2VlanVlanCTMapP6
         INTEGER,
      er1646v2EthPortSwIXt2VlanVlanCTMapP7
         INTEGER,
      er1646v2EthPortSwIXt2VlanVlanTxCos
         INTEGER,
      er1646v2EthPortSwIXt2VlanVlanCCMapP0
         Integer32,
      er1646v2EthPortSwIXt2VlanVlanCCMapP1
         Integer32,
      er1646v2EthPortSwIXt2VlanVlanCCMapP2
         Integer32,
      er1646v2EthPortSwIXt2VlanVlanCCMapP3
         Integer32,
      er1646v2EthPortSwIXt2VlanVlanCCMapP4
         Integer32,
      er1646v2EthPortSwIXt2VlanVlanCCMapP5
         Integer32,
      er1646v2EthPortSwIXt2VlanVlanCCMapP6
         Integer32,
      er1646v2EthPortSwIXt2VlanVlanCCMapP7
         Integer32,
      er1646v2EthPortSwIXt2VlanVlanQCMapQueue1
         Integer32,
      er1646v2EthPortSwIXt2VlanVlanQCMapQueue2
         Integer32,
      er1646v2EthPortSwIXt2VlanVlanQCMapQueue3
         Integer32,
      er1646v2EthPortSwIXt2VlanVlanQCMapQueue4
         Integer32,
      er1646v2EthPortSwIXt2VlanVlanQCMapQueue5
         Integer32,
      er1646v2EthPortSwIXt2VlanVlanQCMapLowDelayQueue
         Integer32,
      er1646v2EthPortSwIXt2VlanVlanQCMapLowDelay2Queue
         Integer32,
      er1646v2EthPortSwIXt2VlanVlanQCMapSystemQueue
         Integer32,
      er1646v2EthPortSwIXt2VlanVlanQinQSVid
         Integer32,
      er1646v2EthPortSwIXt2VlanVlanQinQSTpid
         INTEGER,
      er1646v2EthPortSwIXt2VlanVlanArpTimeOut
         TimeTicks,
      er1646v2EthPortSwIXt2VlanVlanArpProxyArp
         INTEGER,
      er1646v2EthPortSwIXt2VlanBandwidthMode
         INTEGER,
      er1646v2EthPortSwIXt2VlanBandwidthCir
         Integer32,
      er1646v2EthPortSwIXt2VlanBandwidthEir
         Integer32,
      er1646v2EthPortSwIXt2VlanBandwidthUnit
         INTEGER,
      er1646v2EthPortSwIXt2VlanBandwidthTc
         INTEGER,
      er1646v2EthPortSwIXt2VlanBandwidthTcFactor
         INTEGER,
      er1646v2EthPortSwIXt2VlanBandwidthCorrType
         INTEGER,
      er1646v2EthPortSwIXt2VlanBandwidthCorrPredefEncapsFrameRelay
         DisplayString,
      er1646v2EthPortSwIXt2VlanBandwidthCorrPredefEncapsPpp
         DisplayString,
      er1646v2EthPortSwIXt2VlanBandwidthCorrPredefEncapsAtmHl
         INTEGER,
      er1646v2EthPortSwIXt2VlanBandwidthCorrPredefEncapsAtmMp
         INTEGER,
      er1646v2EthPortSwIXt2VlanBandwidthCorrPredefEncapsHdlc
         DisplayString,
      er1646v2EthPortSwIXt2VlanBandwidthCorrPredefEncapsEfmFs
         Integer32,
      er1646v2EthPortSwIXt2VlanBandwidthCorrPredefEncapsEfmIb
         Integer32,
      er1646v2EthPortSwIXt2VlanBandwidthCorrPredefMode
         INTEGER,
      er1646v2EthPortSwIXt2VlanBandwidthCorrManualOverhead
         Integer32,
      er1646v2EthPortSwIXt2VlanBandwidthCorrManualFrameData
         Counter32,
      er1646v2EthPortSwIXt2VlanBandwidthCorrManualFrameHeader
         Counter32,
      er1646v2EthPortSwIXt2VlanBandwidthMaxFifoQLen
         Integer32,
      er1646v2EthPortSwIXt2VlanBandwidthDeFlagCir
         INTEGER,
      er1646v2EthPortSwIXt2VlanBandwidthDeFlagEir
         INTEGER,
      er1646v2EthPortSwIXt2VlanBandwidthDeFlagViolate
         INTEGER,
      er1646v2EthPortSwIXt2VlanBandwidthActCirActNone
         OCTET STRING,
      er1646v2EthPortSwIXt2VlanBandwidthActCirActEthCos1
         INTEGER,
      er1646v2EthPortSwIXt2VlanBandwidthActCirActEthDei1
         INTEGER,
      er1646v2EthPortSwIXt2VlanBandwidthActCirActEthCos2
         INTEGER,
      er1646v2EthPortSwIXt2VlanBandwidthActCirActEthDei2
         INTEGER,
      er1646v2EthPortSwIXt2VlanBandwidthActCirActEthCos3
         INTEGER,
      er1646v2EthPortSwIXt2VlanBandwidthActCirActEthDei3
         INTEGER,
      er1646v2EthPortSwIXt2VlanBandwidthActCirActEthCos4
         INTEGER,
      er1646v2EthPortSwIXt2VlanBandwidthActCirActEthDei4
         INTEGER,
      er1646v2EthPortSwIXt2VlanBandwidthActCirActEthCos5
         INTEGER,
      er1646v2EthPortSwIXt2VlanBandwidthActCirActEthDei5
         INTEGER,
      er1646v2EthPortSwIXt2VlanBandwidthActCirActEthCos6
         INTEGER,
      er1646v2EthPortSwIXt2VlanBandwidthActCirActEthDei6
         INTEGER,
      er1646v2EthPortSwIXt2VlanBandwidthActCirActEthCos7
         INTEGER,
      er1646v2EthPortSwIXt2VlanBandwidthActCirActEthDei7
         INTEGER,
      er1646v2EthPortSwIXt2VlanBandwidthActCirActEthCos8
         INTEGER,
      er1646v2EthPortSwIXt2VlanBandwidthActCirActEthDei8
         INTEGER,
      er1646v2EthPortSwIXt2VlanBandwidthActCirActEthTos
         INTEGER,
      er1646v2EthPortSwIXt2VlanBandwidthActCirActEthQueue
         INTEGER,
      er1646v2EthPortSwIXt2VlanBandwidthActCirActEthDrpLev
         INTEGER,
      er1646v2EthPortSwIXt2VlanBandwidthActCirActEthDeFlag
         INTEGER,
      er1646v2EthPortSwIXt2VlanBandwidthActCirActIpTos
         INTEGER,
      er1646v2EthPortSwIXt2VlanBandwidthActCirActIpQueue
         INTEGER,
      er1646v2EthPortSwIXt2VlanBandwidthActCirActIpDrpLev
         INTEGER,
      er1646v2EthPortSwIXt2VlanBandwidthActCirActIpDeFlag
         INTEGER,
      er1646v2EthPortSwIXt2VlanBandwidthActEirActNone
         OCTET STRING,
      er1646v2EthPortSwIXt2VlanBandwidthActEirActEthCos1
         INTEGER,
      er1646v2EthPortSwIXt2VlanBandwidthActEirActEthDei1
         INTEGER,
      er1646v2EthPortSwIXt2VlanBandwidthActEirActEthCos2
         INTEGER,
      er1646v2EthPortSwIXt2VlanBandwidthActEirActEthDei2
         INTEGER,
      er1646v2EthPortSwIXt2VlanBandwidthActEirActEthCos3
         INTEGER,
      er1646v2EthPortSwIXt2VlanBandwidthActEirActEthDei3
         INTEGER,
      er1646v2EthPortSwIXt2VlanBandwidthActEirActEthCos4
         INTEGER,
      er1646v2EthPortSwIXt2VlanBandwidthActEirActEthDei4
         INTEGER,
      er1646v2EthPortSwIXt2VlanBandwidthActEirActEthCos5
         INTEGER,
      er1646v2EthPortSwIXt2VlanBandwidthActEirActEthDei5
         INTEGER,
      er1646v2EthPortSwIXt2VlanBandwidthActEirActEthCos6
         INTEGER,
      er1646v2EthPortSwIXt2VlanBandwidthActEirActEthDei6
         INTEGER,
      er1646v2EthPortSwIXt2VlanBandwidthActEirActEthCos7
         INTEGER,
      er1646v2EthPortSwIXt2VlanBandwidthActEirActEthDei7
         INTEGER,
      er1646v2EthPortSwIXt2VlanBandwidthActEirActEthCos8
         INTEGER,
      er1646v2EthPortSwIXt2VlanBandwidthActEirActEthDei8
         INTEGER,
      er1646v2EthPortSwIXt2VlanBandwidthActEirActEthTos
         INTEGER,
      er1646v2EthPortSwIXt2VlanBandwidthActEirActEthQueue
         INTEGER,
      er1646v2EthPortSwIXt2VlanBandwidthActEirActEthDrpLev
         INTEGER,
      er1646v2EthPortSwIXt2VlanBandwidthActEirActEthDeFlag
         INTEGER,
      er1646v2EthPortSwIXt2VlanBandwidthActEirActIpTos
         INTEGER,
      er1646v2EthPortSwIXt2VlanBandwidthActEirActIpQueue
         INTEGER,
      er1646v2EthPortSwIXt2VlanBandwidthActEirActIpDrpLev
         INTEGER,
      er1646v2EthPortSwIXt2VlanBandwidthActEirActIpDeFlag
         INTEGER,
      er1646v2EthPortSwIXt2VlanBandwidthActViolActNone
         OCTET STRING,
      er1646v2EthPortSwIXt2VlanBandwidthActViolActDrop
         OCTET STRING,
      er1646v2EthPortSwIXt2VlanBandwidthActViolActEthCos1
         INTEGER,
      er1646v2EthPortSwIXt2VlanBandwidthActViolActEthDei1
         INTEGER,
      er1646v2EthPortSwIXt2VlanBandwidthActViolActEthCos2
         INTEGER,
      er1646v2EthPortSwIXt2VlanBandwidthActViolActEthDei2
         INTEGER,
      er1646v2EthPortSwIXt2VlanBandwidthActViolActEthCos3
         INTEGER,
      er1646v2EthPortSwIXt2VlanBandwidthActViolActEthDei3
         INTEGER,
      er1646v2EthPortSwIXt2VlanBandwidthActViolActEthCos4
         INTEGER,
      er1646v2EthPortSwIXt2VlanBandwidthActViolActEthDei4
         INTEGER,
      er1646v2EthPortSwIXt2VlanBandwidthActViolActEthCos5
         INTEGER,
      er1646v2EthPortSwIXt2VlanBandwidthActViolActEthDei5
         INTEGER,
      er1646v2EthPortSwIXt2VlanBandwidthActViolActEthCos6
         INTEGER,
      er1646v2EthPortSwIXt2VlanBandwidthActViolActEthDei6
         INTEGER,
      er1646v2EthPortSwIXt2VlanBandwidthActViolActEthCos7
         INTEGER,
      er1646v2EthPortSwIXt2VlanBandwidthActViolActEthDei7
         INTEGER,
      er1646v2EthPortSwIXt2VlanBandwidthActViolActEthCos8
         INTEGER,
      er1646v2EthPortSwIXt2VlanBandwidthActViolActEthDei8
         INTEGER,
      er1646v2EthPortSwIXt2VlanBandwidthActViolActEthTos
         INTEGER,
      er1646v2EthPortSwIXt2VlanBandwidthActViolActEthQueue
         INTEGER,
      er1646v2EthPortSwIXt2VlanBandwidthActViolActEthDrpLev
         INTEGER,
      er1646v2EthPortSwIXt2VlanBandwidthActViolActEthDeFlag
         INTEGER,
      er1646v2EthPortSwIXt2VlanBandwidthActViolActIpTos
         INTEGER,
      er1646v2EthPortSwIXt2VlanBandwidthActViolActIpQueue
         INTEGER,
      er1646v2EthPortSwIXt2VlanBandwidthActViolActIpDrpLev
         INTEGER,
      er1646v2EthPortSwIXt2VlanBandwidthActViolActIpDeFlag
         INTEGER,
      er1646v2EthPortSwIXt2VlanInbBwMode
         INTEGER,
      er1646v2EthPortSwIXt2VlanInbBwCir
         Integer32,
      er1646v2EthPortSwIXt2VlanInbBwEir
         Integer32,
      er1646v2EthPortSwIXt2VlanInbBwUnit
         INTEGER,
      er1646v2EthPortSwIXt2VlanInbBwTc
         INTEGER,
      er1646v2EthPortSwIXt2VlanInbBwTcFactor
         INTEGER,
      er1646v2EthPortSwIXt2VlanInbBwCorrType
         INTEGER,
      er1646v2EthPortSwIXt2VlanInbBwCorrPredefEncapsFrameRelay
         DisplayString,
      er1646v2EthPortSwIXt2VlanInbBwCorrPredefEncapsPpp
         DisplayString,
      er1646v2EthPortSwIXt2VlanInbBwCorrPredefEncapsAtmHl
         INTEGER,
      er1646v2EthPortSwIXt2VlanInbBwCorrPredefEncapsAtmMp
         INTEGER,
      er1646v2EthPortSwIXt2VlanInbBwCorrPredefEncapsHdlc
         DisplayString,
      er1646v2EthPortSwIXt2VlanInbBwCorrPredefEncapsEfmFs
         Integer32,
      er1646v2EthPortSwIXt2VlanInbBwCorrPredefEncapsEfmIb
         Integer32,
      er1646v2EthPortSwIXt2VlanInbBwCorrPredefMode
         INTEGER,
      er1646v2EthPortSwIXt2VlanInbBwCorrManualOverhead
         Integer32,
      er1646v2EthPortSwIXt2VlanInbBwCorrManualFrameData
         Counter32,
      er1646v2EthPortSwIXt2VlanInbBwCorrManualFrameHeader
         Counter32,
      er1646v2EthPortSwIXt2VlanInbBwMaxFifoQLen
         Integer32,
      er1646v2EthPortSwIXt2VlanInbBwPriorityPolicy
         DisplayString,
      er1646v2EthPortSwIXt2VlanInbBwDeFlagCir
         INTEGER,
      er1646v2EthPortSwIXt2VlanInbBwDeFlagEir
         INTEGER,
      er1646v2EthPortSwIXt2VlanInbBwDeFlagViolate
         INTEGER,
      er1646v2EthPortSwIXt2VlanInbBwActCirActNone
         OCTET STRING,
      er1646v2EthPortSwIXt2VlanInbBwActCirActEthCos1
         INTEGER,
      er1646v2EthPortSwIXt2VlanInbBwActCirActEthDei1
         INTEGER,
      er1646v2EthPortSwIXt2VlanInbBwActCirActEthCos2
         INTEGER,
      er1646v2EthPortSwIXt2VlanInbBwActCirActEthDei2
         INTEGER,
      er1646v2EthPortSwIXt2VlanInbBwActCirActEthCos3
         INTEGER,
      er1646v2EthPortSwIXt2VlanInbBwActCirActEthDei3
         INTEGER,
      er1646v2EthPortSwIXt2VlanInbBwActCirActEthCos4
         INTEGER,
      er1646v2EthPortSwIXt2VlanInbBwActCirActEthDei4
         INTEGER,
      er1646v2EthPortSwIXt2VlanInbBwActCirActEthCos5
         INTEGER,
      er1646v2EthPortSwIXt2VlanInbBwActCirActEthDei5
         INTEGER,
      er1646v2EthPortSwIXt2VlanInbBwActCirActEthCos6
         INTEGER,
      er1646v2EthPortSwIXt2VlanInbBwActCirActEthDei6
         INTEGER,
      er1646v2EthPortSwIXt2VlanInbBwActCirActEthCos7
         INTEGER,
      er1646v2EthPortSwIXt2VlanInbBwActCirActEthDei7
         INTEGER,
      er1646v2EthPortSwIXt2VlanInbBwActCirActEthCos8
         INTEGER,
      er1646v2EthPortSwIXt2VlanInbBwActCirActEthDei8
         INTEGER,
      er1646v2EthPortSwIXt2VlanInbBwActCirActEthTos
         INTEGER,
      er1646v2EthPortSwIXt2VlanInbBwActCirActEthQueue
         INTEGER,
      er1646v2EthPortSwIXt2VlanInbBwActCirActEthDrpLev
         INTEGER,
      er1646v2EthPortSwIXt2VlanInbBwActCirActEthDeFlag
         INTEGER,
      er1646v2EthPortSwIXt2VlanInbBwActCirActIpTos
         INTEGER,
      er1646v2EthPortSwIXt2VlanInbBwActCirActIpQueue
         INTEGER,
      er1646v2EthPortSwIXt2VlanInbBwActCirActIpDrpLev
         INTEGER,
      er1646v2EthPortSwIXt2VlanInbBwActCirActIpDeFlag
         INTEGER,
      er1646v2EthPortSwIXt2VlanInbBwActEirActNone
         OCTET STRING,
      er1646v2EthPortSwIXt2VlanInbBwActEirActEthCos1
         INTEGER,
      er1646v2EthPortSwIXt2VlanInbBwActEirActEthDei1
         INTEGER,
      er1646v2EthPortSwIXt2VlanInbBwActEirActEthCos2
         INTEGER,
      er1646v2EthPortSwIXt2VlanInbBwActEirActEthDei2
         INTEGER,
      er1646v2EthPortSwIXt2VlanInbBwActEirActEthCos3
         INTEGER,
      er1646v2EthPortSwIXt2VlanInbBwActEirActEthDei3
         INTEGER,
      er1646v2EthPortSwIXt2VlanInbBwActEirActEthCos4
         INTEGER,
      er1646v2EthPortSwIXt2VlanInbBwActEirActEthDei4
         INTEGER,
      er1646v2EthPortSwIXt2VlanInbBwActEirActEthCos5
         INTEGER,
      er1646v2EthPortSwIXt2VlanInbBwActEirActEthDei5
         INTEGER,
      er1646v2EthPortSwIXt2VlanInbBwActEirActEthCos6
         INTEGER,
      er1646v2EthPortSwIXt2VlanInbBwActEirActEthDei6
         INTEGER,
      er1646v2EthPortSwIXt2VlanInbBwActEirActEthCos7
         INTEGER,
      er1646v2EthPortSwIXt2VlanInbBwActEirActEthDei7
         INTEGER,
      er1646v2EthPortSwIXt2VlanInbBwActEirActEthCos8
         INTEGER,
      er1646v2EthPortSwIXt2VlanInbBwActEirActEthDei8
         INTEGER,
      er1646v2EthPortSwIXt2VlanInbBwActEirActEthTos
         INTEGER,
      er1646v2EthPortSwIXt2VlanInbBwActEirActEthQueue
         INTEGER,
      er1646v2EthPortSwIXt2VlanInbBwActEirActEthDrpLev
         INTEGER,
      er1646v2EthPortSwIXt2VlanInbBwActEirActEthDeFlag
         INTEGER,
      er1646v2EthPortSwIXt2VlanInbBwActEirActIpTos
         INTEGER,
      er1646v2EthPortSwIXt2VlanInbBwActEirActIpQueue
         INTEGER,
      er1646v2EthPortSwIXt2VlanInbBwActEirActIpDrpLev
         INTEGER,
      er1646v2EthPortSwIXt2VlanInbBwActEirActIpDeFlag
         INTEGER,
      er1646v2EthPortSwIXt2VlanInbBwActViolActNone
         OCTET STRING,
      er1646v2EthPortSwIXt2VlanInbBwActViolActDrop
         OCTET STRING,
      er1646v2EthPortSwIXt2VlanInbBwActViolActEthCos1
         INTEGER,
      er1646v2EthPortSwIXt2VlanInbBwActViolActEthDei1
         INTEGER,
      er1646v2EthPortSwIXt2VlanInbBwActViolActEthCos2
         INTEGER,
      er1646v2EthPortSwIXt2VlanInbBwActViolActEthDei2
         INTEGER,
      er1646v2EthPortSwIXt2VlanInbBwActViolActEthCos3
         INTEGER,
      er1646v2EthPortSwIXt2VlanInbBwActViolActEthDei3
         INTEGER,
      er1646v2EthPortSwIXt2VlanInbBwActViolActEthCos4
         INTEGER,
      er1646v2EthPortSwIXt2VlanInbBwActViolActEthDei4
         INTEGER,
      er1646v2EthPortSwIXt2VlanInbBwActViolActEthCos5
         INTEGER,
      er1646v2EthPortSwIXt2VlanInbBwActViolActEthDei5
         INTEGER,
      er1646v2EthPortSwIXt2VlanInbBwActViolActEthCos6
         INTEGER,
      er1646v2EthPortSwIXt2VlanInbBwActViolActEthDei6
         INTEGER,
      er1646v2EthPortSwIXt2VlanInbBwActViolActEthCos7
         INTEGER,
      er1646v2EthPortSwIXt2VlanInbBwActViolActEthDei7
         INTEGER,
      er1646v2EthPortSwIXt2VlanInbBwActViolActEthCos8
         INTEGER,
      er1646v2EthPortSwIXt2VlanInbBwActViolActEthDei8
         INTEGER,
      er1646v2EthPortSwIXt2VlanInbBwActViolActEthTos
         INTEGER,
      er1646v2EthPortSwIXt2VlanInbBwActViolActEthQueue
         INTEGER,
      er1646v2EthPortSwIXt2VlanInbBwActViolActEthDrpLev
         INTEGER,
      er1646v2EthPortSwIXt2VlanInbBwActViolActEthDeFlag
         INTEGER,
      er1646v2EthPortSwIXt2VlanInbBwActViolActIpTos
         INTEGER,
      er1646v2EthPortSwIXt2VlanInbBwActViolActIpQueue
         INTEGER,
      er1646v2EthPortSwIXt2VlanInbBwActViolActIpDrpLev
         INTEGER,
      er1646v2EthPortSwIXt2VlanInbBwActViolActIpDeFlag
         INTEGER,
      er1646v2EthPortSwIXt2VlanPppoE
         INTEGER,
      er1646v2EthPortSwIXt2VlanPppLnkMOperation
         INTEGER,
      er1646v2EthPortSwIXt2VlanPppLnkMInterval
         TimeTicks,
      er1646v2EthPortSwIXt2VlanPppLnkMRepTimeOut
         TimeTicks,
      er1646v2EthPortSwIXt2VlanPppLnkMFailsPrmt
         Integer32,
      er1646v2EthPortSwIXt2VlanPppAuthentication
         INTEGER,
      er1646v2EthPortSwIXt2VlanPppAuthenPeriod
         TimeTicks,
      er1646v2EthPortSwIXt2VlanPppSessionName
         DisplayString,
      er1646v2EthPortSwIXt2VlanPppSessionSecret
         DisplayString,
      er1646v2EthPortSwIXt2VlanPppEncModeSessionSecret
         INTEGER,
      er1646v2EthPortSwIXt2VlanPppEncSessionSecret
         DisplayString,
      er1646v2EthPortSwIXt2VlanPppServiceName
         DisplayString,
      er1646v2EthPortSwIXt2VlanPbbMode
         INTEGER,
      er1646v2EthPortSwIXt2VlanPbbTxCos
         Integer32,
      er1646v2EthPortSwIXt2VlanPbbIsid
         Integer32,
      er1646v2EthPortSwIXt2VlanPbbDestMac
         OCTET STRING,
      er1646v2EthPortSwIXt2VlanPbbCustomGroupMac
         OCTET STRING
      }

er1646v2EthPortSwIXt2VlanActions OBJECT-TYPE
   SYNTAX      VariableLengthTableActions
   MAX-ACCESS  read-write
   STATUS      current
   DESCRIPTION
      "By way of this field, some manipulations
       on this table may be performed."
   ::= {er1646v2EthPortSwIXt2VlanEntry 2}

er1646v2EthPortSwIXt2VlanGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanEntry 10}

er1646v2EthPortSwIXt2VlanTableIx OBJECT-TYPE
   SYNTAX      TableIndex
   MAX-ACCESS  not-accessible
   STATUS      current
   DESCRIPTION
      ""
   ::= {er1646v2EthPortSwIXt2VlanEntry 11}

er1646v2EthPortSwIXt2VlanName OBJECT-TYPE
   SYNTAX      DisplayString
   MAX-ACCESS  read-write
   STATUS      current
   DESCRIPTION
      "Path: swPort.editConf.vlan.name"
   ::= {er1646v2EthPortSwIXt2VlanEntry 16777216}

er1646v2EthPortSwIXt2VlanRemark OBJECT-TYPE
   SYNTAX      DisplayString
   MAX-ACCESS  read-write
   STATUS      current
   DESCRIPTION
      "Path: swPort.editConf.vlan.remark"
   ::= {er1646v2EthPortSwIXt2VlanEntry 1157627904}

er1646v2EthPortSwIXt2VlanAdminStatus OBJECT-TYPE
   SYNTAX      INTEGER
               {
               up (1),
               down (2)
               }
   MAX-ACCESS  read-write
   STATUS      current
   DESCRIPTION
      "Path: swPort.editConf.vlan.adminStatus

       Possibilities:
               up   (1)
               down   (2)"
   ::= {er1646v2EthPortSwIXt2VlanEntry 33554432}

er1646v2EthPortSwIXt2VlanMode OBJECT-TYPE
   SYNTAX      INTEGER
               {
               routing (1),
               bridging (2),
               ipV6 (16),
               ipV6ipV4 (17),
               multilink (8)
               }
   MAX-ACCESS  read-write
   STATUS      current
   DESCRIPTION
      "Path: swPort.editConf.vlan.mode

       Possibilities:
               routing   (1)
               bridging   (2)
               ipV6   (16)
               ipV6/ipV4   (17)
               multilink   (8)"
   ::= {er1646v2EthPortSwIXt2VlanEntry 67108864}

er1646v2EthPortSwIXt2VlanPriorityPolicy OBJECT-TYPE
   SYNTAX      DisplayString
   MAX-ACCESS  read-write
   STATUS      current
   DESCRIPTION
      "Path: swPort.editConf.vlan.priorityPolicy"
   ::= {er1646v2EthPortSwIXt2VlanEntry 83886080}

er1646v2EthPortSwIXt2VlanIpVrfRouter OBJECT-TYPE
   SYNTAX      DisplayString
   MAX-ACCESS  read-write
   STATUS      current
   DESCRIPTION
      "Path: swPort.editConf.vlan.ip.vrfRouter"
   ::= {er1646v2EthPortSwIXt2VlanEntry 53215232}

er1646v2EthPortSwIXt2VlanIpAdr OBJECT-TYPE
   SYNTAX      IpAddress
   MAX-ACCESS  read-write
   STATUS      current
   DESCRIPTION
      "Path: swPort.editConf.vlan.ip.address"
   ::= {er1646v2EthPortSwIXt2VlanEntry 58261504}

er1646v2EthPortSwIXt2VlanIpNetm OBJECT-TYPE
   SYNTAX      IpAddress
   MAX-ACCESS  read-write
   STATUS      current
   DESCRIPTION
      "Path: swPort.editConf.vlan.ip.netMask"
   ::= {er1646v2EthPortSwIXt2VlanEntry 58392576}

er1646v2EthPortSwIXt2VlanIpSNetName OBJECT-TYPE
   SYNTAX      INTEGER
               {
               slOPTg (0),
               corp (2),
               dmz (3),
               internet (1)
               }
   MAX-ACCESS  read-write
   STATUS      current
   DESCRIPTION
      "Path: swPort.editConf.vlan.ip.sNet.name

       Possibilities:
               <OPT>   (0)
               corp   (2)
               dmz   (3)
               internet   (1)"
   ::= {er1646v2EthPortSwIXt2VlanEntry 53674240}

er1646v2EthPortSwIXt2VlanIpSNetCust OBJECT-TYPE
   SYNTAX      DisplayString
   MAX-ACCESS  read-write
   STATUS      current
   DESCRIPTION
      "Path: swPort.editConf.vlan.ip.sNet.custom"
   ::= {er1646v2EthPortSwIXt2VlanEntry 53674496}

er1646v2EthPortSwIXt2VlanIpDhcpC OBJECT-TYPE
   SYNTAX      INTEGER
               {
               disabled (0),
               enabled (1)
               }
   MAX-ACCESS  read-write
   STATUS      current
   DESCRIPTION
      "Path: swPort.editConf.vlan.ip.dhcpClient

       Possibilities:
               disabled   (0)
               enabled   (1)"
   ::= {er1646v2EthPortSwIXt2VlanEntry 53608448}

er1646v2EthPortSwIXt2VlanIpDhcpGatewayPreference OBJECT-TYPE
   SYNTAX      Integer32
   MAX-ACCESS  read-write
   STATUS      current
   DESCRIPTION
      "Path: swPort.editConf.vlan.ip.dhcp.gatewayPreference"
   ::= {er1646v2EthPortSwIXt2VlanEntry 53739776}

er1646v2EthPortSwIXt2VlanIpDhcpRoutePreference OBJECT-TYPE
   SYNTAX      Integer32
   MAX-ACCESS  read-write
   STATUS      current
   DESCRIPTION
      "Path: swPort.editConf.vlan.ip.dhcp.routePreference"
   ::= {er1646v2EthPortSwIXt2VlanEntry 53740032}

er1646v2EthPortSwIXt2VlanIpDhcpDnsPreference OBJECT-TYPE
   SYNTAX      Integer32
   MAX-ACCESS  read-write
   STATUS      current
   DESCRIPTION
      "Path: swPort.editConf.vlan.ip.dhcp.dnsPreference"
   ::= {er1646v2EthPortSwIXt2VlanEntry 53740288}

er1646v2EthPortSwIXt2VlanIpMtu OBJECT-TYPE
   SYNTAX      Integer32
   MAX-ACCESS  read-write
   STATUS      current
   DESCRIPTION
      "Path: swPort.editConf.vlan.ip.mtu"
   ::= {er1646v2EthPortSwIXt2VlanEntry 52953088}

er1646v2EthPortSwIXt2VlanIpMssAdjust OBJECT-TYPE
   SYNTAX      INTEGER
               {
               disabled (0),
               auto (65536)
               }
   MAX-ACCESS  read-write
   STATUS      current
   DESCRIPTION
      "Path: swPort.editConf.vlan.ip.mssAdjust

       Possibilities:
               disabled   (0)
               auto   (65536)"
   ::= {er1646v2EthPortSwIXt2VlanEntry 53280768}

er1646v2EthPortSwIXt2VlanIpRipMetric OBJECT-TYPE
   SYNTAX      Integer32
   MAX-ACCESS  read-write
   STATUS      current
   DESCRIPTION
      "Path: swPort.editConf.vlan.ip.rip.metric"
   ::= {er1646v2EthPortSwIXt2VlanEntry 51712768}

er1646v2EthPortSwIXt2VlanIpRipMetricOut OBJECT-TYPE
   SYNTAX      Integer32
   MAX-ACCESS  read-write
   STATUS      current
   DESCRIPTION
      "Path: swPort.editConf.vlan.ip.rip.metricOut"
   ::= {er1646v2EthPortSwIXt2VlanEntry 51713024}

er1646v2EthPortSwIXt2VlanIpRipMode OBJECT-TYPE
   SYNTAX      INTEGER
               {
               disabled (0),
               passive (1),
               active (2)
               }
   MAX-ACCESS  read-write
   STATUS      current
   DESCRIPTION
      "Path: swPort.editConf.vlan.ip.rip.mode

       Possibilities:
               disabled   (0)
               passive   (1)
               active   (2)"
   ::= {er1646v2EthPortSwIXt2VlanEntry 51713280}

er1646v2EthPortSwIXt2VlanIpRipTxVer OBJECT-TYPE
   SYNTAX      INTEGER
               {
               rip1 (0),
               rip2 (1),
               rip1mcompatible (2)
               }
   MAX-ACCESS  read-write
   STATUS      current
   DESCRIPTION
      "Path: swPort.editConf.vlan.ip.rip.txVersion

       Possibilities:
               rip1   (0)
               rip2   (1)
               rip1-compatible   (2)"
   ::= {er1646v2EthPortSwIXt2VlanEntry 51716864}

er1646v2EthPortSwIXt2VlanIpRipRxVer OBJECT-TYPE
   SYNTAX      INTEGER
               {
               rip1only (0),
               rip2only (1),
               rip12 (2)
               }
   MAX-ACCESS  read-write
   STATUS      current
   DESCRIPTION
      "Path: swPort.editConf.vlan.ip.rip.rxVersion

       Possibilities:
               rip1only   (0)
               rip2only   (1)
               rip1&2   (2)"
   ::= {er1646v2EthPortSwIXt2VlanEntry 51717120}

er1646v2EthPortSwIXt2VlanIpRipSplitH OBJECT-TYPE
   SYNTAX      INTEGER
               {
               disabled (0),
               enabled (1),
               poisonedReverse (2)
               }
   MAX-ACCESS  read-write
   STATUS      current
   DESCRIPTION
      "Path: swPort.editConf.vlan.ip.rip.splitHorizon

       Possibilities:
               disabled   (0)
               enabled   (1)
               poisonedReverse   (2)"
   ::= {er1646v2EthPortSwIXt2VlanEntry 51713792}

er1646v2EthPortSwIXt2VlanIpRipAuth OBJECT-TYPE
   SYNTAX      INTEGER
               {
               disabled (0),
               texts (1),
               md5 (2)
               }
   MAX-ACCESS  read-write
   STATUS      current
   DESCRIPTION
      "Path: swPort.editConf.vlan.ip.rip.authentication

       Possibilities:
               disabled   (0)
               text    (1)
               md5   (2)"
   ::= {er1646v2EthPortSwIXt2VlanEntry 51712512}

er1646v2EthPortSwIXt2VlanIpRipFilter OBJECT-TYPE
   SYNTAX      DisplayString
   MAX-ACCESS  read-write
   STATUS      current
   DESCRIPTION
      "Path: swPort.editConf.vlan.ip.rip.filter"
   ::= {er1646v2EthPortSwIXt2VlanEntry 51716096}

er1646v2EthPortSwIXt2VlanIpRipFilterIn OBJECT-TYPE
   SYNTAX      DisplayString
   MAX-ACCESS  read-write
   STATUS      current
   DESCRIPTION
      "Path: swPort.editConf.vlan.ip.rip.filterIn"
   ::= {er1646v2EthPortSwIXt2VlanEntry 51716352}

er1646v2EthPortSwIXt2VlanIpRipClearNextHop OBJECT-TYPE
   SYNTAX      INTEGER
               {
               disabled (0),
               enabled (1)
               }
   MAX-ACCESS  read-write
   STATUS      current
   DESCRIPTION
      "Path: swPort.editConf.vlan.ip.rip.clearNextHop

       Possibilities:
               disabled   (0)
               enabled   (1)"
   ::= {er1646v2EthPortSwIXt2VlanEntry 51708416}

er1646v2EthPortSwIXt2VlanIpAccPol OBJECT-TYPE
   SYNTAX      DisplayString
   MAX-ACCESS  read-write
   STATUS      current
   DESCRIPTION
      "Path: swPort.editConf.vlan.ip.accessPolicy"
   ::= {er1646v2EthPortSwIXt2VlanEntry 53084160}

er1646v2EthPortSwIXt2VlanIpAB OBJECT-TYPE
   SYNTAX      DisplayString
   MAX-ACCESS  read-write
   STATUS      current
   DESCRIPTION
      "Path: swPort.editConf.vlan.ip.trafficPolicy"
   ::= {er1646v2EthPortSwIXt2VlanEntry 51249152}

er1646v2EthPortSwIXt2VlanIpMA OBJECT-TYPE
   SYNTAX      INTEGER
               {
               disabled (0),
               enabled (1)
               }
   MAX-ACCESS  read-write
   STATUS      current
   DESCRIPTION
      "Path: swPort.editConf.vlan.ip.mgmtAccess

       Possibilities:
               disabled   (0)
               enabled   (1)"
   ::= {er1646v2EthPortSwIXt2VlanEntry 51380224}

er1646v2EthPortSwIXt2VlanIpMF OBJECT-TYPE
   SYNTAX      Integer32
   MAX-ACCESS  read-write
   STATUS      current
   DESCRIPTION
      "Path: swPort.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EthPortSwIXt2VlanEntry 51445760}

er1646v2EthPortSwIXt2VlanIpDB OBJECT-TYPE
   SYNTAX      INTEGER
               {
               disabled (0),
               enabled (1)
               }
   MAX-ACCESS  read-write
   STATUS      current
   DESCRIPTION
      "Path: swPort.editConf.vlan.ip.directedBroadcasts

       Possibilities:
               disabled   (0)
               enabled   (1)"
   ::= {er1646v2EthPortSwIXt2VlanEntry 51773440}

er1646v2EthPortSwIXt2VlanIpIR OBJECT-TYPE
   SYNTAX      INTEGER
               {
               disabled (0),
               enabled (1)
               }
   MAX-ACCESS  read-write
   STATUS      current
   DESCRIPTION
      "Path: swPort.editConf.vlan.ip.icmpRedirects

       Possibilities:
               disabled   (0)
               enabled   (1)"
   ::= {er1646v2EthPortSwIXt2VlanEntry 52035584}

er1646v2EthPortSwIXt2VlanIpIgmp OBJECT-TYPE
   SYNTAX      INTEGER
               {
               disabled (0),
               proxy (1),
               router (2),
               v3Router (5)
               }
   MAX-ACCESS  read-write
   STATUS      current
   DESCRIPTION
      "Path: swPort.editConf.vlan.ip.igmp

       Possibilities:
               disabled   (0)
               proxy   (1)
               router   (2)
               v3Router   (5)"
   ::= {er1646v2EthPortSwIXt2VlanEntry 52428800}

er1646v2EthPortSwIXt2VlanIpNN OBJECT-TYPE
   SYNTAX      DisplayString
   MAX-ACCESS  read-write
   STATUS      current
   DESCRIPTION
      "Path: swPort.editConf.vlan.ip.nat"
   ::= {er1646v2EthPortSwIXt2VlanEntry 52101120}

er1646v2EthPortSwIXt2VlanIpVrrp OBJECT-TYPE
   SYNTAX      INTEGER
               {
               disabled (0),
               enabled (1)
               }
   MAX-ACCESS  read-write
   STATUS      current
   DESCRIPTION
      "Path: swPort.editConf.vlan.ip.vrrp

       Possibilities:
               disabled   (0)
               enabled   (1)"
   ::= {er1646v2EthPortSwIXt2VlanEntry 53149696}

er1646v2EthPortSwIXt2VlanIpPimMode OBJECT-TYPE
   SYNTAX      INTEGER
               {
               disabled (0),
               sparse (1),
               passive (2)
               }
   MAX-ACCESS  read-write
   STATUS      current
   DESCRIPTION
      "Path: swPort.editConf.vlan.ip.pim.mode

       Possibilities:
               disabled   (0)
               sparse   (1)
               passive   (2)"
   ::= {er1646v2EthPortSwIXt2VlanEntry 53346560}

er1646v2EthPortSwIXt2VlanIpPimDrPriority OBJECT-TYPE
   SYNTAX      Counter32
   MAX-ACCESS  read-write
   STATUS      current
   DESCRIPTION
      "Path: swPort.editConf.vlan.ip.pim.drPriority

       32 bit unsigned wrappable counter."
   ::= {er1646v2EthPortSwIXt2VlanEntry 53346816}

er1646v2EthPortSwIXt2VlanIpPimHelloTime OBJECT-TYPE
   SYNTAX      TimeTicks
   MAX-ACCESS  read-write
   STATUS      current
   DESCRIPTION
      "Path: swPort.editConf.vlan.ip.pim.helloTime

       Time in centi-second."
   ::= {er1646v2EthPortSwIXt2VlanEntry 53347072}

er1646v2EthPortSwIXt2VlanIpPimPropagationDelay OBJECT-TYPE
   SYNTAX      TimeTicks
   MAX-ACCESS  read-write
   STATUS      current
   DESCRIPTION
      "Path: swPort.editConf.vlan.ip.pim.propagationDelay

       Time in centi-second."
   ::= {er1646v2EthPortSwIXt2VlanEntry 53347328}

er1646v2EthPortSwIXt2VlanIpPimOverrideInterval OBJECT-TYPE
   SYNTAX      TimeTicks
   MAX-ACCESS  read-write
   STATUS      current
   DESCRIPTION
      "Path: swPort.editConf.vlan.ip.pim.overrideInterval

       Time in centi-second."
   ::= {er1646v2EthPortSwIXt2VlanEntry 53347584}

er1646v2EthPortSwIXt2VlanIpPimBsrBorder OBJECT-TYPE
   SYNTAX      INTEGER
               {
               disabled (0),
               enabled (1)
               }
   MAX-ACCESS  read-write
   STATUS      current
   DESCRIPTION
      "Path: swPort.editConf.vlan.ip.pim.bsrBorder

       Possibilities:
               disabled   (0)
               enabled   (1)"
   ::= {er1646v2EthPortSwIXt2VlanEntry 53347840}

er1646v2EthPortSwIXt2VlanIpPimTtlThreshold OBJECT-TYPE
   SYNTAX      Integer32
   MAX-ACCESS  read-write
   STATUS      current
   DESCRIPTION
      "Path: swPort.editConf.vlan.ip.pim.ttlThreshold"
   ::= {er1646v2EthPortSwIXt2VlanEntry 53348096}

er1646v2EthPortSwIXt2VlanIpIMNetworkUnreachable OBJECT-TYPE
   SYNTAX      INTEGER
               {
               disabled (0),
               enabled (1)
               }
   MAX-ACCESS  read-write
   STATUS      current
   DESCRIPTION
      "Path: swPort.editConf.vlan.ip.icmpMessages.networkUnreachable

       Possibilities:
               disabled   (0)
               enabled   (1)"
   ::= {er1646v2EthPortSwIXt2VlanEntry 53412096}

er1646v2EthPortSwIXt2VlanIpIMHostUnreachable OBJECT-TYPE
   SYNTAX      INTEGER
               {
               disabled (0),
               enabled (1)
               }
   MAX-ACCESS  read-write
   STATUS      current
   DESCRIPTION
      "Path: swPort.editConf.vlan.ip.icmpMessages.hostUnreachable

       Possibilities:
               disabled   (0)
               enabled   (1)"
   ::= {er1646v2EthPortSwIXt2VlanEntry 53412352}

er1646v2EthPortSwIXt2VlanIpIMProtocolUnreachable OBJECT-TYPE
   SYNTAX      INTEGER
               {
               disabled (0),
               enabled (1)
               }
   MAX-ACCESS  read-write
   STATUS      current
   DESCRIPTION
      "Path: swPort.editConf.vlan.ip.icmpMessages.protocolUnreachable

       Possibilities:
               disabled   (0)
               enabled   (1)"
   ::= {er1646v2EthPortSwIXt2VlanEntry 53412608}

er1646v2EthPortSwIXt2VlanIpIMPortUnreachable OBJECT-TYPE
   SYNTAX      INTEGER
               {
               disabled (0),
               enabled (1)
               }
   MAX-ACCESS  read-write
   STATUS      current
   DESCRIPTION
      "Path: swPort.editConf.vlan.ip.icmpMessages.portUnreachable

       Possibilities:
               disabled   (0)
               enabled   (1)"
   ::= {er1646v2EthPortSwIXt2VlanEntry 53412864}

er1646v2EthPortSwIXt2VlanIpIMMtuExceeded OBJECT-TYPE
   SYNTAX      INTEGER
               {
               disabled (0),
               enabled (1)
               }
   MAX-ACCESS  read-write
   STATUS      current
   DESCRIPTION
      "Path: swPort.editConf.vlan.ip.icmpMessages.mtuExceeded

       Possibilities:
               disabled   (0)
               enabled   (1)"
   ::= {er1646v2EthPortSwIXt2VlanEntry 53413120}

er1646v2EthPortSwIXt2VlanIpIMAdminProhibited OBJECT-TYPE
   SYNTAX      INTEGER
               {
               disabled (0),
               enabled (1)
               }
   MAX-ACCESS  read-write
   STATUS      current
   DESCRIPTION
      "Path: swPort.editConf.vlan.ip.icmpMessages.adminProhibited

       Possibilities:
               disabled   (0)
               enabled   (1)"
   ::= {er1646v2EthPortSwIXt2VlanEntry 53413376}

er1646v2EthPortSwIXt2VlanIpIMTtlExceeded OBJECT-TYPE
   SYNTAX      INTEGER
               {
               disabled (0),
               enabled (1)
               }
   MAX-ACCESS  read-write
   STATUS      current
   DESCRIPTION
      "Path: swPort.editConf.vlan.ip.icmpMessages.ttlExceeded

       Possibilities:
               disabled   (0)
               enabled   (1)"
   ::= {er1646v2EthPortSwIXt2VlanEntry 53413632}

er1646v2EthPortSwIXt2VlanIpIMRedirect OBJECT-TYPE
   SYNTAX      INTEGER
               {
               disabled (0),
               enabled (1)
               }
   MAX-ACCESS  read-write
   STATUS      current
   DESCRIPTION
      "Path: swPort.editConf.vlan.ip.icmpMessages.redirect

       Possibilities:
               disabled   (0)
               enabled   (1)"
   ::= {er1646v2EthPortSwIXt2VlanEntry 53413888}

er1646v2EthPortSwIXt2VlanIpV6VrfRouter OBJECT-TYPE
   SYNTAX      DisplayString
   MAX-ACCESS  read-write
   STATUS      current
   DESCRIPTION
      "Path: swPort.editConf.vlan.ipV6.vrfRouter"
   ::= {er1646v2EthPortSwIXt2VlanEntry 704708608}

er1646v2EthPortSwIXt2VlanIpV6AddrAutoConfigNrDupAddrDetects OBJECT-TYPE
   SYNTAX      Integer32
   MAX-ACCESS  read-write
   STATUS      current
   DESCRIPTION
      "Path: swPort.editConf.vlan.ipV6.addrAutoConfig.nrDupAddrDetects"
   ::= {er1646v2EthPortSwIXt2VlanEntry 704905472}

er1646v2EthPortSwIXt2VlanIpV6AddrAutoConfigAcceptRa OBJECT-TYPE
   SYNTAX      INTEGER
               {
               disabled (0),
               enabled (1)
               }
   MAX-ACCESS  read-write
   STATUS      current
   DESCRIPTION
      "Path: swPort.editConf.vlan.ipV6.addrAutoConfig.acceptRa

       Possibilities:
               disabled   (0)
               enabled   (1)"
   ::= {er1646v2EthPortSwIXt2VlanEntry 704905728}

er1646v2EthPortSwIXt2VlanIpV6AddrAutoConfigAcceptRaRdnss OBJECT-TYPE
   SYNTAX      INTEGER
               {
               disabled (0),
               enabled (1)
               }
   MAX-ACCESS  read-write
   STATUS      current
   DESCRIPTION
      "Path: swPort.editConf.vlan.ipV6.addrAutoConfig.acceptRaRdnss

       Possibilities:
               disabled   (0)
               enabled   (1)"
   ::= {er1646v2EthPortSwIXt2VlanEntry 704905984}

er1646v2EthPortSwIXt2VlanIpV6AddrAutoConfigAcceptRaDnssl OBJECT-TYPE
   SYNTAX      INTEGER
               {
               disabled (0),
               enabled (1)
               }
   MAX-ACCESS  read-write
   STATUS      current
   DESCRIPTION
      "Path: swPort.editConf.vlan.ipV6.addrAutoConfig.acceptRaDnssl

       Possibilities:
               disabled   (0)
               enabled   (1)"
   ::= {er1646v2EthPortSwIXt2VlanEntry 704906240}

er1646v2EthPortSwIXt2VlanIpV6DefaultRoute OBJECT-TYPE
   SYNTAX      INTEGER
               {
               disabled (0),
               enabled (1)
               }
   MAX-ACCESS  read-write
   STATUS      current
   DESCRIPTION
      "Path: swPort.editConf.vlan.ipV6.defaultRoute

       Possibilities:
               disabled   (0)
               enabled   (1)"
   ::= {er1646v2EthPortSwIXt2VlanEntry 704970752}

er1646v2EthPortSwIXt2VlanIpV6RaSend OBJECT-TYPE
   SYNTAX      INTEGER
               {
               disabled (0),
               enabled (1)
               }
   MAX-ACCESS  read-write
   STATUS      current
   DESCRIPTION
      "Path: swPort.editConf.vlan.ipV6.ra.send

       Possibilities:
               disabled   (0)
               enabled   (1)"
   ::= {er1646v2EthPortSwIXt2VlanEntry 705036544}

er1646v2EthPortSwIXt2VlanIpV6RaMinInterval OBJECT-TYPE
   SYNTAX      TimeTicks
   MAX-ACCESS  read-write
   STATUS      current
   DESCRIPTION
      "Path: swPort.editConf.vlan.ipV6.ra.minInterval

       Time in centi-second."
   ::= {er1646v2EthPortSwIXt2VlanEntry 705036800}

er1646v2EthPortSwIXt2VlanIpV6RaMaxInterval OBJECT-TYPE
   SYNTAX      TimeTicks
   MAX-ACCESS  read-write
   STATUS      current
   DESCRIPTION
      "Path: swPort.editConf.vlan.ipV6.ra.maxInterval

       Time in centi-second."
   ::= {er1646v2EthPortSwIXt2VlanEntry 705037056}

er1646v2EthPortSwIXt2VlanIpV6RaManagedFlag OBJECT-TYPE
   SYNTAX      INTEGER
               {
               disabled (0),
               enabled (1)
               }
   MAX-ACCESS  read-write
   STATUS      current
   DESCRIPTION
      "Path: swPort.editConf.vlan.ipV6.ra.managedFlag

       Possibilities:
               disabled   (0)
               enabled   (1)"
   ::= {er1646v2EthPortSwIXt2VlanEntry 705037312}

er1646v2EthPortSwIXt2VlanIpV6RaOtherConfFlag OBJECT-TYPE
   SYNTAX      INTEGER
               {
               disabled (0),
               enabled (1)
               }
   MAX-ACCESS  read-write
   STATUS      current
   DESCRIPTION
      "Path: swPort.editConf.vlan.ipV6.ra.otherConfFlag

       Possibilities:
               disabled   (0)
               enabled   (1)"
   ::= {er1646v2EthPortSwIXt2VlanEntry 705037568}

er1646v2EthPortSwIXt2VlanIpV6RaLinkMtu OBJECT-TYPE
   SYNTAX      Integer32
   MAX-ACCESS  read-write
   STATUS      current
   DESCRIPTION
      "Path: swPort.editConf.vlan.ipV6.ra.linkMtu"
   ::= {er1646v2EthPortSwIXt2VlanEntry 705037824}

er1646v2EthPortSwIXt2VlanIpV6RaReachableTime OBJECT-TYPE
   SYNTAX      TimeTicks
   MAX-ACCESS  read-write
   STATUS      current
   DESCRIPTION
      "Path: swPort.editConf.vlan.ipV6.ra.reachableTime

       Time in centi-second."
   ::= {er1646v2EthPortSwIXt2VlanEntry 705038080}

er1646v2EthPortSwIXt2VlanIpV6RaRetransmitTime OBJECT-TYPE
   SYNTAX      TimeTicks
   MAX-ACCESS  read-write
   STATUS      current
   DESCRIPTION
      "Path: swPort.editConf.vlan.ipV6.ra.retransmitTime

       Time in centi-second."
   ::= {er1646v2EthPortSwIXt2VlanEntry 705038336}

er1646v2EthPortSwIXt2VlanIpV6RaHopLimit OBJECT-TYPE
   SYNTAX      Integer32
   MAX-ACCESS  read-write
   STATUS      current
   DESCRIPTION
      "Path: swPort.editConf.vlan.ipV6.ra.hopLimit"
   ::= {er1646v2EthPortSwIXt2VlanEntry 705038592}

er1646v2EthPortSwIXt2VlanIpV6RaDefaultLifeTime OBJECT-TYPE
   SYNTAX      TimeTicks
   MAX-ACCESS  read-write
   STATUS      current
   DESCRIPTION
      "Path: swPort.editConf.vlan.ipV6.ra.defaultLifeTime

       Time in centi-second."
   ::= {er1646v2EthPortSwIXt2VlanEntry 705038848}

er1646v2EthPortSwIXt2VlanIpV6RaDnsOptionsRdnssLifeTime OBJECT-TYPE
   SYNTAX      TimeTicks
   MAX-ACCESS  read-write
   STATUS      current
   DESCRIPTION
      "Path: swPort.editConf.vlan.ipV6.ra.dnsOptions.rdnss.lifeTime

       Time in centi-second."
   ::= {er1646v2EthPortSwIXt2VlanEntry 705039140}

er1646v2EthPortSwIXt2VlanIpV6RaDnsOptionsRdnssImportServers OBJECT-TYPE
   SYNTAX      INTEGER
               {
               disabled (0),
               enabled (1)
               }
   MAX-ACCESS  read-write
   STATUS      current
   DESCRIPTION
      "Path: swPort.editConf.vlan.ipV6.ra.dnsOptions.rdnss.importServers

       Possibilities:
               disabled   (0)
               enabled   (1)"
   ::= {er1646v2EthPortSwIXt2VlanEntry 705039148}

er1646v2EthPortSwIXt2VlanIpV6RaDnsOptionsDnsslLifeTime OBJECT-TYPE
   SYNTAX      TimeTicks
   MAX-ACCESS  read-write
   STATUS      current
   DESCRIPTION
      "Path: swPort.editConf.vlan.ipV6.ra.dnsOptions.dnssl.lifeTime

       Time in centi-second."
   ::= {er1646v2EthPortSwIXt2VlanEntry 705039172}

er1646v2EthPortSwIXt2VlanIpV6RaDnsOptionsDnsslImportDomains OBJECT-TYPE
   SYNTAX      INTEGER
               {
               disabled (0),
               enabled (1)
               }
   MAX-ACCESS  read-write
   STATUS      current
   DESCRIPTION
      "Path: swPort.editConf.vlan.ipV6.ra.dnsOptions.dnssl.importDomains

       Possibilities:
               disabled   (0)
               enabled   (1)"
   ::= {er1646v2EthPortSwIXt2VlanEntry 705039180}

er1646v2EthPortSwIXt2VlanIpV6RsSend OBJECT-TYPE
   SYNTAX      INTEGER
               {
               disabled (0),
               enabled (1)
               }
   MAX-ACCESS  read-write
   STATUS      current
   DESCRIPTION
      "Path: swPort.editConf.vlan.ipV6.rs.send

       Possibilities:
               disabled   (0)
               enabled   (1)"
   ::= {er1646v2EthPortSwIXt2VlanEntry 705954048}

er1646v2EthPortSwIXt2VlanIpV6RsMaxRandomDelay OBJECT-TYPE
   SYNTAX      TimeTicks
   MAX-ACCESS  read-write
   STATUS      current
   DESCRIPTION
      "Path: swPort.editConf.vlan.ipV6.rs.maxRandomDelay

       Time in centi-second."
   ::= {er1646v2EthPortSwIXt2VlanEntry 705954304}

er1646v2EthPortSwIXt2VlanIpV6RsInterval OBJECT-TYPE
   SYNTAX      TimeTicks
   MAX-ACCESS  read-write
   STATUS      current
   DESCRIPTION
      "Path: swPort.editConf.vlan.ipV6.rs.interval

       Time in centi-second."
   ::= {er1646v2EthPortSwIXt2VlanEntry 705954560}

er1646v2EthPortSwIXt2VlanIpV6RsMaxSolicitations OBJECT-TYPE
   SYNTAX      Integer32
   MAX-ACCESS  read-write
   STATUS      current
   DESCRIPTION
      "Path: swPort.editConf.vlan.ipV6.rs.maxSolicitations"
   ::= {er1646v2EthPortSwIXt2VlanEntry 705954816}

er1646v2EthPortSwIXt2VlanIpV6TrafficPolicyInbound OBJECT-TYPE
   SYNTAX      DisplayString
   MAX-ACCESS  read-write
   STATUS      current
   DESCRIPTION
      "Path: swPort.editConf.vlan.ipV6.trafficPolicy.inbound"
   ::= {er1646v2EthPortSwIXt2VlanEntry 705364224}

er1646v2EthPortSwIXt2VlanIpV6TrafficPolicyOutbound OBJECT-TYPE
   SYNTAX      DisplayString
   MAX-ACCESS  read-write
   STATUS      current
   DESCRIPTION
      "Path: swPort.editConf.vlan.ipV6.trafficPolicy.outbound"
   ::= {er1646v2EthPortSwIXt2VlanEntry 705364480}

er1646v2EthPortSwIXt2VlanIpV6FirewallZone OBJECT-TYPE
   SYNTAX      DisplayString
   MAX-ACCESS  read-write
   STATUS      current
   DESCRIPTION
      "Path: swPort.editConf.vlan.ipV6.firewall.zone"
   ::= {er1646v2EthPortSwIXt2VlanEntry 705429760}

er1646v2EthPortSwIXt2VlanIpV6DhcpClientAddrAC OBJECT-TYPE
   SYNTAX      INTEGER
               {
               disabled (0),
               enabled (1)
               }
   MAX-ACCESS  read-write
   STATUS      current
   DESCRIPTION
      "Path: swPort.editConf.vlan.ipV6.dhcp.client.addrAutoConfig

       Possibilities:
               disabled   (0)
               enabled   (1)"
   ::= {er1646v2EthPortSwIXt2VlanEntry 705307648}

er1646v2EthPortSwIXt2VlanIpV6DhcpClientPrDelMode OBJECT-TYPE
   SYNTAX      INTEGER
               {
               disabled (0),
               enabled (1)
               }
   MAX-ACCESS  read-write
   STATUS      current
   DESCRIPTION
      "Path: swPort.editConf.vlan.ipV6.dhcp.client.pd.mode

       Possibilities:
               disabled   (0)
               enabled   (1)"
   ::= {er1646v2EthPortSwIXt2VlanEntry 705308676}

er1646v2EthPortSwIXt2VlanIpV6DhcpClientPrDelPool OBJECT-TYPE
   SYNTAX      DisplayString
   MAX-ACCESS  read-write
   STATUS      current
   DESCRIPTION
      "Path: swPort.editConf.vlan.ipV6.dhcp.client.pd.pool"
   ::= {er1646v2EthPortSwIXt2VlanEntry 705308680}

er1646v2EthPortSwIXt2VlanIpV6DhcpClientPrDelPdExclOpt OBJECT-TYPE
   SYNTAX      INTEGER
               {
               disabled (0),
               enabled (1)
               }
   MAX-ACCESS  read-write
   STATUS      current
   DESCRIPTION
      "Path: swPort.editConf.vlan.ipV6.dhcp.client.pd.pdExclOpt

       Possibilities:
               disabled   (0)
               enabled   (1)"
   ::= {er1646v2EthPortSwIXt2VlanEntry 705308684}

er1646v2EthPortSwIXt2VlanIpV6DhcpClientDnsServerPref OBJECT-TYPE
   SYNTAX      Integer32
   MAX-ACCESS  read-write
   STATUS      current
   DESCRIPTION
      "Path: swPort.editConf.vlan.ipV6.dhcp.client.dns.serverPref"
   ::= {er1646v2EthPortSwIXt2VlanEntry 705310724}

er1646v2EthPortSwIXt2VlanIpV6DhcpClientRapidCommit OBJECT-TYPE
   SYNTAX      INTEGER
               {
               disabled (0),
               enabled (1)
               }
   MAX-ACCESS  read-write
   STATUS      current
   DESCRIPTION
      "Path: swPort.editConf.vlan.ipV6.dhcp.client.rapidCommit

       Possibilities:
               disabled   (0)
               enabled   (1)"
   ::= {er1646v2EthPortSwIXt2VlanEntry 705309696}

er1646v2EthPortSwIXt2VlanIpV6DhcpClientTimersSolTimeOut OBJECT-TYPE
   SYNTAX      TimeTicks
   MAX-ACCESS  read-write
   STATUS      current
   DESCRIPTION
      "Path: swPort.editConf.vlan.ipV6.dhcp.client.timers.solTimeOut

       Time in centi-second."
   ::= {er1646v2EthPortSwIXt2VlanEntry 705311748}

er1646v2EthPortSwIXt2VlanIpV6DhcpClientTimersSolMaxRt OBJECT-TYPE
   SYNTAX      TimeTicks
   MAX-ACCESS  read-write
   STATUS      current
   DESCRIPTION
      "Path: swPort.editConf.vlan.ipV6.dhcp.client.timers.solMaxRt

       Time in centi-second."
   ::= {er1646v2EthPortSwIXt2VlanEntry 705311752}

er1646v2EthPortSwIXt2VlanIpV6DhcpClientTimersInfoRefresh OBJECT-TYPE
   SYNTAX      TimeTicks
   MAX-ACCESS  read-write
   STATUS      current
   DESCRIPTION
      "Path: swPort.editConf.vlan.ipV6.dhcp.client.timers.infoRefresh

       Time in centi-second."
   ::= {er1646v2EthPortSwIXt2VlanEntry 705311756}

er1646v2EthPortSwIXt2VlanIpV6DhcpServerMode OBJECT-TYPE
   SYNTAX      INTEGER
               {
               disabled (0),
               enabled (1)
               }
   MAX-ACCESS  read-write
   STATUS      current
   DESCRIPTION
      "Path: swPort.editConf.vlan.ipV6.dhcp.server.mode

       Possibilities:
               disabled   (0)
               enabled   (1)"
   ::= {er1646v2EthPortSwIXt2VlanEntry 705315840}

er1646v2EthPortSwIXt2VlanIpV6DhcpServerPreference OBJECT-TYPE
   SYNTAX      Integer32
   MAX-ACCESS  read-write
   STATUS      current
   DESCRIPTION
      "Path: swPort.editConf.vlan.ipV6.dhcp.server.preference"
   ::= {er1646v2EthPortSwIXt2VlanEntry 705316864}

er1646v2EthPortSwIXt2VlanIpV6DhcpServerPool OBJECT-TYPE
   SYNTAX      DisplayString
   MAX-ACCESS  read-write
   STATUS      current
   DESCRIPTION
      "Path: swPort.editConf.vlan.ipV6.dhcp.server.pool"
   ::= {er1646v2EthPortSwIXt2VlanEntry 705317888}

er1646v2EthPortSwIXt2VlanIpV6DhcpServerRapidCommit OBJECT-TYPE
   SYNTAX      INTEGER
               {
               disabled (0),
               enabled (1)
               }
   MAX-ACCESS  read-write
   STATUS      current
   DESCRIPTION
      "Path: swPort.editConf.vlan.ipV6.dhcp.server.rapidCommit

       Possibilities:
               disabled   (0)
               enabled   (1)"
   ::= {er1646v2EthPortSwIXt2VlanEntry 705318912}

er1646v2EthPortSwIXt2VlanIpV6DhcpServerTimersInfoRefresh OBJECT-TYPE
   SYNTAX      TimeTicks
   MAX-ACCESS  read-write
   STATUS      current
   DESCRIPTION
      "Path: swPort.editConf.vlan.ipV6.dhcp.server.timers.infoRefresh

       Time in centi-second."
   ::= {er1646v2EthPortSwIXt2VlanEntry 705319940}

er1646v2EthPortSwIXt2VlanIpV6DhcpRelayMode OBJECT-TYPE
   SYNTAX      INTEGER
               {
               disabled (0),
               enabled (1)
               }
   MAX-ACCESS  read-write
   STATUS      current
   DESCRIPTION
      "Path: swPort.editConf.vlan.ipV6.dhcp.relay.mode

       Possibilities:
               disabled   (0)
               enabled   (1)"
   ::= {er1646v2EthPortSwIXt2VlanEntry 705323040}

er1646v2EthPortSwIXt2VlanIpV6SendRedirect OBJECT-TYPE
   SYNTAX      INTEGER
               {
               disabled (0),
               enabled (1)
               }
   MAX-ACCESS  read-write
   STATUS      current
   DESCRIPTION
      "Path: swPort.editConf.vlan.ipV6.sendRedirect

       Possibilities:
               disabled   (0)
               enabled   (1)"
   ::= {er1646v2EthPortSwIXt2VlanEntry 705101824}

er1646v2EthPortSwIXt2VlanIpV6LinkMtu OBJECT-TYPE
   SYNTAX      Integer32
   MAX-ACCESS  read-write
   STATUS      current
   DESCRIPTION
      "Path: swPort.editConf.vlan.ipV6.linkMtu"
   ::= {er1646v2EthPortSwIXt2VlanEntry 705167360}

er1646v2EthPortSwIXt2VlanIpV6InterfaceId OBJECT-TYPE
   SYNTAX      OCTET STRING
   MAX-ACCESS  read-write
   STATUS      current
   DESCRIPTION
      "Path: swPort.editConf.vlan.ipV6.interfaceId"
   ::= {er1646v2EthPortSwIXt2VlanEntry 705232896}

er1646v2EthPortSwIXt2VlanIpV6MF OBJECT-TYPE
   SYNTAX      Integer32
   MAX-ACCESS  read-write
   STATUS      current
   DESCRIPTION
      "Path: swPort.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EthPortSwIXt2VlanEntry 705757184}

er1646v2EthPortSwIXt2VlanIpV6IcmpMessagesNoRoute OBJECT-TYPE
   SYNTAX      INTEGER
               {
               disabled (0),
               enabled (1)
               }
   MAX-ACCESS  read-write
   STATUS      current
   DESCRIPTION
      "Path: swPort.editConf.vlan.ipV6.icmpMessages.noRoute

       Possibilities:
               disabled   (0)
               enabled   (1)"
   ::= {er1646v2EthPortSwIXt2VlanEntry 705822976}

er1646v2EthPortSwIXt2VlanIpV6IcmpMessagesBeyondScope OBJECT-TYPE
   SYNTAX      INTEGER
               {
               disabled (0),
               enabled (1)
               }
   MAX-ACCESS  read-write
   STATUS      current
   DESCRIPTION
      "Path: swPort.editConf.vlan.ipV6.icmpMessages.beyondScope

       Possibilities:
               disabled   (0)
               enabled   (1)"
   ::= {er1646v2EthPortSwIXt2VlanEntry 705823488}

er1646v2EthPortSwIXt2VlanIpV6IcmpMessagesAddressUnreachable OBJECT-TYPE
   SYNTAX      INTEGER
               {
               disabled (0),
               enabled (1)
               }
   MAX-ACCESS  read-write
   STATUS      current
   DESCRIPTION
      "Path: swPort.editConf.vlan.ipV6.icmpMessages.addressUnreachable

       Possibilities:
               disabled   (0)
               enabled   (1)"
   ::= {er1646v2EthPortSwIXt2VlanEntry 705823744}

er1646v2EthPortSwIXt2VlanIpV6IcmpMessagesPortUnreachable OBJECT-TYPE
   SYNTAX      INTEGER
               {
               disabled (0),
               enabled (1)
               }
   MAX-ACCESS  read-write
   STATUS      current
   DESCRIPTION
      "Path: swPort.editConf.vlan.ipV6.icmpMessages.portUnreachable

       Possibilities:
               disabled   (0)
               enabled   (1)"
   ::= {er1646v2EthPortSwIXt2VlanEntry 705824000}

er1646v2EthPortSwIXt2VlanIpV6IcmpMessagesPacketTooBig OBJECT-TYPE
   SYNTAX      INTEGER
               {
               disabled (0),
               enabled (1)
               }
   MAX-ACCESS  read-write
   STATUS      current
   DESCRIPTION
      "Path: swPort.editConf.vlan.ipV6.icmpMessages.packetTooBig

       Possibilities:
               disabled   (0)
               enabled   (1)"
   ::= {er1646v2EthPortSwIXt2VlanEntry 705825280}

er1646v2EthPortSwIXt2VlanIpV6IcmpMessagesHopLimitExceeded OBJECT-TYPE
   SYNTAX      INTEGER
               {
               disabled (0),
               enabled (1)
               }
   MAX-ACCESS  read-write
   STATUS      current
   DESCRIPTION
      "Path: swPort.editConf.vlan.ipV6.icmpMessages.hopLimitExceeded

       Possibilities:
               disabled   (0)
               enabled   (1)"
   ::= {er1646v2EthPortSwIXt2VlanEntry 705827840}

er1646v2EthPortSwIXt2VlanIpV6IcmpMessagesFragTimeExceeded OBJECT-TYPE
   SYNTAX      INTEGER
               {
               disabled (0),
               enabled (1)
               }
   MAX-ACCESS  read-write
   STATUS      current
   DESCRIPTION
      "Path: swPort.editConf.vlan.ipV6.icmpMessages.fragTimeExceeded

       Possibilities:
               disabled   (0)
               enabled   (1)"
   ::= {er1646v2EthPortSwIXt2VlanEntry 705828096}

er1646v2EthPortSwIXt2VlanIpV6IcmpMessagesHeaderFieldErr OBJECT-TYPE
   SYNTAX      INTEGER
               {
               disabled (0),
               enabled (1)
               }
   MAX-ACCESS  read-write
   STATUS      current
   DESCRIPTION
      "Path: swPort.editConf.vlan.ipV6.icmpMessages.headerFieldErr

       Possibilities:
               disabled   (0)
               enabled   (1)"
   ::= {er1646v2EthPortSwIXt2VlanEntry 705830400}

er1646v2EthPortSwIXt2VlanIpV6IcmpMessagesOptionUnrecognized OBJECT-TYPE
   SYNTAX      INTEGER
               {
               disabled (0),
               enabled (1)
               }
   MAX-ACCESS  read-write
   STATUS      current
   DESCRIPTION
      "Path: swPort.editConf.vlan.ipV6.icmpMessages.optionUnrecognized

       Possibilities:
               disabled   (0)
               enabled   (1)"
   ::= {er1646v2EthPortSwIXt2VlanEntry 705830912}

er1646v2EthPortSwIXt2VlanIpV6IcmpMessagesRedirect OBJECT-TYPE
   SYNTAX      INTEGER
               {
               disabled (0),
               enabled (1)
               }
   MAX-ACCESS  read-write
   STATUS      current
   DESCRIPTION
      "Path: swPort.editConf.vlan.ipV6.icmpMessages.redirect

       Possibilities:
               disabled   (0)
               enabled   (1)"
   ::= {er1646v2EthPortSwIXt2VlanEntry 705832960}

er1646v2EthPortSwIXt2VlanBridgingAccList OBJECT-TYPE
   SYNTAX      DisplayString
   MAX-ACCESS  read-write
   STATUS      current
   DESCRIPTION
      "Path: swPort.editConf.vlan.bridging.accessList"
   ::= {er1646v2EthPortSwIXt2VlanEntry 453246976}

er1646v2EthPortSwIXt2VlanBridgingInACL OBJECT-TYPE
   SYNTAX      DisplayString
   MAX-ACCESS  read-write
   STATUS      current
   DESCRIPTION
      "Path: swPort.editConf.vlan.bridging.inAccessList"
   ::= {er1646v2EthPortSwIXt2VlanEntry 456916992}

er1646v2EthPortSwIXt2VlanBridgingTp OBJECT-TYPE
   SYNTAX      DisplayString
   MAX-ACCESS  read-write
   STATUS      current
   DESCRIPTION
      "Path: swPort.editConf.vlan.bridging.trafficPolicy"
   ::= {er1646v2EthPortSwIXt2VlanEntry 454295552}

er1646v2EthPortSwIXt2VlanBridgingBrGrp OBJECT-TYPE
   SYNTAX      DisplayString
   MAX-ACCESS  read-write
   STATUS      current
   DESCRIPTION
      "Path: swPort.editConf.vlan.bridging.bridgeGroup"
   ::= {er1646v2EthPortSwIXt2VlanEntry 454819840}

er1646v2EthPortSwIXt2VlanBridgingLimBC OBJECT-TYPE
   SYNTAX      INTEGER
               {
               disabled (0),
               enabled (1)
               }
   MAX-ACCESS  read-write
   STATUS      current
   DESCRIPTION
      "Path: swPort.editConf.vlan.bridging.limitBroadcasts

       Possibilities:
               disabled   (0)
               enabled   (1)"
   ::= {er1646v2EthPortSwIXt2VlanEntry 455081984}

er1646v2EthPortSwIXt2VlanBridgingPrivateMode OBJECT-TYPE
   SYNTAX      INTEGER
               {
               disabled (0),
               enabled (1)
               }
   MAX-ACCESS  read-write
   STATUS      current
   DESCRIPTION
      "Path: swPort.editConf.vlan.bridging.privateMode

       Possibilities:
               disabled   (0)
               enabled   (1)"
   ::= {er1646v2EthPortSwIXt2VlanEntry 459538432}

er1646v2EthPortSwIXt2VlanBridgingLearning OBJECT-TYPE
   SYNTAX      INTEGER
               {
               disabled (0),
               enabled (1)
               }
   MAX-ACCESS  read-write
   STATUS      current
   DESCRIPTION
      "Path: swPort.editConf.vlan.bridging.learning

       Possibilities:
               disabled   (0)
               enabled   (1)"
   ::= {er1646v2EthPortSwIXt2VlanEntry 456130560}

er1646v2EthPortSwIXt2VlanBridgingMaxCacheSize OBJECT-TYPE
   SYNTAX      INTEGER
               {
               unlimited (0)
               }
   MAX-ACCESS  read-write
   STATUS      current
   DESCRIPTION
      "Path: swPort.editConf.vlan.bridging.maxCacheSize

       Possibilities:
               unlimited   (0)"
   ::= {er1646v2EthPortSwIXt2VlanEntry 456392704}

er1646v2EthPortSwIXt2VlanBridgingRelearnDropOnRelearn OBJECT-TYPE
   SYNTAX      INTEGER
               {
               disabled (0),
               enabled (1)
               }
   MAX-ACCESS  read-write
   STATUS      current
   DESCRIPTION
      "Path: swPort.editConf.vlan.bridging.relearn.dropOnRelearn

       Possibilities:
               disabled   (0)
               enabled   (1)"
   ::= {er1646v2EthPortSwIXt2VlanEntry 456655872}

er1646v2EthPortSwIXt2VlanBridgingRelearnShutdownThreshold OBJECT-TYPE
   SYNTAX      Integer32
   MAX-ACCESS  read-write
   STATUS      current
   DESCRIPTION
      "Path: swPort.editConf.vlan.bridging.relearn.shutdownThreshold"
   ::= {er1646v2EthPortSwIXt2VlanEntry 456656896}

er1646v2EthPortSwIXt2VlanBridgingRelearnShutdownTime OBJECT-TYPE
   SYNTAX      TimeTicks
   MAX-ACCESS  read-write
   STATUS      current
   DESCRIPTION
      "Path: swPort.editConf.vlan.bridging.relearn.shutdownTime

       Time in centi-second."
   ::= {er1646v2EthPortSwIXt2VlanEntry 456657920}

er1646v2EthPortSwIXt2VlanBridgingRelearnLoopDetection OBJECT-TYPE
   SYNTAX      INTEGER
               {
               disabled (0),
               passive (1),
               active (2)
               }
   MAX-ACCESS  read-write
   STATUS      current
   DESCRIPTION
      "Path: swPort.editConf.vlan.bridging.relearn.loopDetection

       Possibilities:
               disabled   (0)
               passive   (1)
               active   (2)"
   ::= {er1646v2EthPortSwIXt2VlanEntry 456658944}

er1646v2EthPortSwIXt2VlanBridgingRelearnLoopDetectionInterval OBJECT-TYPE
   SYNTAX      TimeTicks
   MAX-ACCESS  read-write
   STATUS      current
   DESCRIPTION
      "Path: swPort.editConf.vlan.bridging.relearn.loopDetectionInterval

       Time in centi-second."
   ::= {er1646v2EthPortSwIXt2VlanEntry 456659968}

er1646v2EthPortSwIXt2VlanBridgingVlanMemberShip OBJECT-TYPE
   SYNTAX      INTEGER
               {
               all (0),
               none (1),
               grouped (2)
               }
   MAX-ACCESS  read-write
   STATUS      current
   DESCRIPTION
      "Path: swPort.editConf.vlan.bridging.vlanMemberShip

       Possibilities:
               all   (0)
               none   (1)
               grouped   (2)"
   ::= {er1646v2EthPortSwIXt2VlanEntry 457965568}

er1646v2EthPortSwIXt2VlanBridgingVlTUntaggedAction OBJECT-TYPE
   SYNTAX      INTEGER
               {
               discard (0),
               accept (1),
               tag (2)
               }
   MAX-ACCESS  read-write
   STATUS      current
   DESCRIPTION
      "Path: swPort.editConf.vlan.bridging.vlanTagging.untagged.action

       Possibilities:
               discard   (0)
               accept   (1)
               tag   (2)"
   ::= {er1646v2EthPortSwIXt2VlanEntry 459055104}

er1646v2EthPortSwIXt2VlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.untagged.tagInfo.tpid

       Possibilities:
               dot1Q   (33024)
               dot1ad   (34984)
               0x9100   (37120)
               0x9200   (37376)
               0x9300   (37632)"
   ::= {er1646v2EthPortSwIXt2VlanEntry 459059712}

er1646v2EthPortSwIXt2VlanBridgingVlTUntaggedTagInfoVid OBJECT-TYPE
   SYNTAX      Integer32
   MAX-ACCESS  read-write
   STATUS      current
   DESCRIPTION
      "Path: swPort.editConf.vlan.bridging.vlanTagging.untagged.tagInfo.vid"
   ::= {er1646v2EthPortSwIXt2VlanEntry 459060224}

er1646v2EthPortSwIXt2VlanBridgingVlTUnknownVlansAction OBJECT-TYPE
   SYNTAX      INTEGER
               {
               discard (0),
               accept (1),
               tag (2)
               }
   MAX-ACCESS  read-write
   STATUS      current
   DESCRIPTION
      "Path: swPort.editConf.vlan.bridging.vlanTagging.unknownVlans.action

       Possibilities:
               discard   (0)
               accept   (1)
               tag   (2)"
   ::= {er1646v2EthPortSwIXt2VlanEntry 459120640}

er1646v2EthPortSwIXt2VlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.unknownVlans.tagInfo.tpid

       Possibilities:
               dot1Q   (33024)
               dot1ad   (34984)
               0x9100   (37120)
               0x9200   (37376)
               0x9300   (37632)"
   ::= {er1646v2EthPortSwIXt2VlanEntry 459125248}

er1646v2EthPortSwIXt2VlanBridgingVlTUnknownVlansTagInfoVid OBJECT-TYPE
   SYNTAX      Integer32
   MAX-ACCESS  read-write
   STATUS      current
   DESCRIPTION
      "Path: swPort.editConf.vlan.bridging.vlanTagging.unknownVlans.tagInfo.vid"
   ::= {er1646v2EthPortSwIXt2VlanEntry 459125760}

er1646v2EthPortSwIXt2VlanBridgingDot1adType OBJECT-TYPE
   SYNTAX      INTEGER
               {
               slOPTg (0),
               cPort (4),
               sPort (1),
               nni (2)
               }
   MAX-ACCESS  read-write
   STATUS      current
   DESCRIPTION
      "Path: swPort.editConf.vlan.bridging.dot1ad.type

       Possibilities:
               <OPT>   (0)
               cPort   (4)
               sPort   (1)
               nni   (2)"
   ::= {er1646v2EthPortSwIXt2VlanEntry 460850176}

er1646v2EthPortSwIXt2VlanBridgingPriority OBJECT-TYPE
   SYNTAX      Integer32
   MAX-ACCESS  read-write
   STATUS      current
   DESCRIPTION
      "Path: swPort.editConf.vlan.bridging.priority"
   ::= {er1646v2EthPortSwIXt2VlanEntry 453509120}

er1646v2EthPortSwIXt2VlanBridgingPathCost OBJECT-TYPE
   SYNTAX      Integer32
   MAX-ACCESS  read-write
   STATUS      current
   DESCRIPTION
      "Path: swPort.editConf.vlan.bridging.pathCost"
   ::= {er1646v2EthPortSwIXt2VlanEntry 453771264}

er1646v2EthPortSwIXt2VlanBridgingInternalPathCost OBJECT-TYPE
   SYNTAX      Integer32
   MAX-ACCESS  read-write
   STATUS      current
   DESCRIPTION
      "Path: swPort.editConf.vlan.bridging.internalPathCost"
   ::= {er1646v2EthPortSwIXt2VlanEntry 457703424}

er1646v2EthPortSwIXt2VlanBridgingTCD OBJECT-TYPE
   SYNTAX      INTEGER
               {
               disabled (0),
               enabled (1)
               }
   MAX-ACCESS  read-write
   STATUS      current
   DESCRIPTION
      "Path: swPort.editConf.vlan.bridging.topologyChangeDetection

       Possibilities:
               disabled   (0)
               enabled   (1)"
   ::= {er1646v2EthPortSwIXt2VlanEntry 454033408}

er1646v2EthPortSwIXt2VlanBridgingRestrictedRole OBJECT-TYPE
   SYNTAX      INTEGER
               {
               disabled (0),
               enabled (1)
               }
   MAX-ACCESS  read-write
   STATUS      current
   DESCRIPTION
      "Path: swPort.editConf.vlan.bridging.restrictedRole

       Possibilities:
               disabled   (0)
               enabled   (1)"
   ::= {er1646v2EthPortSwIXt2VlanEntry 458227712}

er1646v2EthPortSwIXt2VlanBridgingAdminEdge OBJECT-TYPE
   SYNTAX      INTEGER
               {
               disabled (0),
               enabled (1)
               }
   MAX-ACCESS  read-write
   STATUS      current
   DESCRIPTION
      "Path: swPort.editConf.vlan.bridging.adminEdge

       Possibilities:
               disabled   (0)
               enabled   (1)"
   ::= {er1646v2EthPortSwIXt2VlanEntry 457179136}

er1646v2EthPortSwIXt2VlanBridgingOamMacDeviceMac OBJECT-TYPE
   SYNTAX      DisplayString
   MAX-ACCESS  read-write
   STATUS      current
   DESCRIPTION
      "Path: swPort.editConf.vlan.bridging.ethOam.macAddress.deviceMac"
   ::= {er1646v2EthPortSwIXt2VlanEntry 458506496}

er1646v2EthPortSwIXt2VlanBridgingOamMacUserMac OBJECT-TYPE
   SYNTAX      OCTET STRING
   MAX-ACCESS  read-write
   STATUS      current
   DESCRIPTION
      "Path: swPort.editConf.vlan.bridging.ethOam.macAddress.userMac

       MAC address."
   ::= {er1646v2EthPortSwIXt2VlanEntry 458506368}

er1646v2EthPortSwIXt2VlanBridgingOamMacBridgeMac OBJECT-TYPE
   SYNTAX      DisplayString
   MAX-ACCESS  read-write
   STATUS      current
   DESCRIPTION
      "Path: swPort.editConf.vlan.bridging.ethOam.macAddress.bridgeMac"
   ::= {er1646v2EthPortSwIXt2VlanEntry 458506432}

er1646v2EthPortSwIXt2VlanBridgingMgmtInline OBJECT-TYPE
   SYNTAX      INTEGER
               {
               disabled (0),
               enabled (1)
               }
   MAX-ACCESS  read-write
   STATUS      current
   DESCRIPTION
      "Path: swPort.editConf.vlan.bridging.mgmtInline

       Possibilities:
               disabled   (0)
               enabled   (1)"
   ::= {er1646v2EthPortSwIXt2VlanEntry 458752000}

er1646v2EthPortSwIXt2VlanBridgingL2ptMode OBJECT-TYPE
   SYNTAX      INTEGER
               {
               disabled (0),
               enabled (1)
               }
   MAX-ACCESS  read-write
   STATUS      current
   DESCRIPTION
      "Path: swPort.editConf.vlan.bridging.l2ProtTunnel.mode

       Possibilities:
               disabled   (0)
               enabled   (1)"
   ::= {er1646v2EthPortSwIXt2VlanEntry 459292672}

er1646v2EthPortSwIXt2VlanBridgingL2ptProtocols OBJECT-TYPE
   SYNTAX      Integer32
   MAX-ACCESS  read-write
   STATUS      current
   DESCRIPTION
      "Path: swPort.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2EthPortSwIXt2VlanEntry 459309056}

er1646v2EthPortSwIXt2VlanBridgingL2ptDestMac OBJECT-TYPE
   SYNTAX      OCTET STRING
   MAX-ACCESS  read-write
   STATUS      current
   DESCRIPTION
      "Path: swPort.editConf.vlan.bridging.l2ProtTunnel.destinationMac

       MAC address."
   ::= {er1646v2EthPortSwIXt2VlanEntry 459325440}

er1646v2EthPortSwIXt2VlanBridgingL2ptCos OBJECT-TYPE
   SYNTAX      INTEGER
               {
               unchanged (255)
               }
   MAX-ACCESS  read-write
   STATUS      current
   DESCRIPTION
      "Path: swPort.editConf.vlan.bridging.l2ProtTunnel.cos

       Possibilities:
               unchanged   (255)"
   ::= {er1646v2EthPortSwIXt2VlanEntry 459341824}

er1646v2EthPortSwIXt2VlanBridgingL2ptDropThrStp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.stp

       unit name = packets/sec

       Possibilities:
               unlimited   (0)"
   ::= {er1646v2EthPortSwIXt2VlanEntry 459358272}

er1646v2EthPortSwIXt2VlanBridgingL2ptDropThrLldp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lldp

       unit name = packets/sec

       Possibilities:
               unlimited   (0)"
   ::= {er1646v2EthPortSwIXt2VlanEntry 459358336}

er1646v2EthPortSwIXt2VlanBridgingL2ptDropThrOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.oam

       unit name = packets/sec

       Possibilities:
               unlimited   (0)"
   ::= {er1646v2EthPortSwIXt2VlanEntry 459358400}

er1646v2EthPortSwIXt2VlanBridgingL2ptDropThrCdp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.cdp

       unit name = packets/sec

       Possibilities:
               unlimited   (0)"
   ::= {er1646v2EthPortSwIXt2VlanEntry 459358464}

er1646v2EthPortSwIXt2VlanBridgingL2ptDropThrVtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.vtp

       unit name = packets/sec

       Possibilities:
               unlimited   (0)"
   ::= {er1646v2EthPortSwIXt2VlanEntry 459358528}

er1646v2EthPortSwIXt2VlanBridgingL2ptDropThrLacp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.lacp

       unit name = packets/sec

       Possibilities:
               unlimited   (0)"
   ::= {er1646v2EthPortSwIXt2VlanEntry 459358592}

er1646v2EthPortSwIXt2VlanBridgingL2ptDropThrEfmOam OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.efmOam

       unit name = packets/sec

       Possibilities:
               unlimited   (0)"
   ::= {er1646v2EthPortSwIXt2VlanEntry 459358656}

er1646v2EthPortSwIXt2VlanBridgingL2ptDropThrPvst OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pvst

       unit name = packets/sec

       Possibilities:
               unlimited   (0)"
   ::= {er1646v2EthPortSwIXt2VlanEntry 459358720}

er1646v2EthPortSwIXt2VlanBridgingL2ptDropThrMmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mmrp

       unit name = packets/sec

       Possibilities:
               unlimited   (0)"
   ::= {er1646v2EthPortSwIXt2VlanEntry 459358784}

er1646v2EthPortSwIXt2VlanBridgingL2ptDropThrMvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.mvrp

       unit name = packets/sec

       Possibilities:
               unlimited   (0)"
   ::= {er1646v2EthPortSwIXt2VlanEntry 459358848}

er1646v2EthPortSwIXt2VlanBridgingL2ptDropThrGvrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gvrp

       unit name = packets/sec

       Possibilities:
               unlimited   (0)"
   ::= {er1646v2EthPortSwIXt2VlanEntry 459358912}

er1646v2EthPortSwIXt2VlanBridgingL2ptDropThrGmrp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.gmrp

       unit name = packets/sec

       Possibilities:
               unlimited   (0)"
   ::= {er1646v2EthPortSwIXt2VlanEntry 459358976}

er1646v2EthPortSwIXt2VlanBridgingL2ptDropThrDtp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.dtp

       unit name = packets/sec

       Possibilities:
               unlimited   (0)"
   ::= {er1646v2EthPortSwIXt2VlanEntry 459359040}

er1646v2EthPortSwIXt2VlanBridgingL2ptDropThrPagp OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.pagp

       unit name = packets/sec

       Possibilities:
               unlimited   (0)"
   ::= {er1646v2EthPortSwIXt2VlanEntry 459359104}

er1646v2EthPortSwIXt2VlanBridgingL2ptDropThrUdld OBJECT-TYPE
   SYNTAX      INTEGER
               {
               unlimited (0)
               }
   UNITS       "packets/sec"
   MAX-ACCESS  read-write
   STATUS      current
   DESCRIPTION
      "Path: swPort.editConf.vlan.bridging.l2ProtTunnel.dropThresholds.udld

       unit name = packets/sec

       Possibilities:
               unlimited   (0)"
   ::= {er1646v2EthPortSwIXt2VlanEntry 459359168}

er1646v2EthPortSwIXt2VlanVlanVid OBJECT-TYPE
   SYNTAX      INTEGER
               {
               untagged (0),
               prioTagged (4096),
               notUsed (4097)
               }
   MAX-ACCESS  read-write
   STATUS      current
   DESCRIPTION
      "Path: swPort.editConf.vlan.vlan.vid

       Possibilities:
               untagged   (0)
               prioTagged   (4096)
               notUsed   (4097)"
   ::= {er1646v2EthPortSwIXt2VlanEntry 234946560}

er1646v2EthPortSwIXt2VlanVlanVidExtensionSingle OBJECT-TYPE
   SYNTAX      OCTET STRING
   MAX-ACCESS  read-write
   STATUS      current
   DESCRIPTION
      "Path: swPort.editConf.vlan.vlan.vidExtension.single"
   ::= {er1646v2EthPortSwIXt2VlanEntry 235340032}

er1646v2EthPortSwIXt2VlanVlanVidExtensionEndVid OBJECT-TYPE
   SYNTAX      Integer32
   MAX-ACCESS  read-write
   STATUS      current
   DESCRIPTION
      "Path: swPort.editConf.vlan.vlan.vidExtension.endVid"
   ::= {er1646v2EthPortSwIXt2VlanEntry 235340288}

er1646v2EthPortSwIXt2VlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tpid

       Possibilities:
               dot1Q   (33024)
               dot1ad   (34984)
               0x9100   (37120)
               0x9200   (37376)
               0x9300   (37632)"
   ::= {er1646v2EthPortSwIXt2VlanEntry 241238016}

er1646v2EthPortSwIXt2VlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: swPort.editConf.vlan.vlan.tagSignificance

       Possibilities:
               global   (0)
               local   (1)
               sVlan   (2)
               sVlanGlobal   (6)
               cVlan   (3)
               scVlan   (5)
               cVlanLocal   (4)"
   ::= {er1646v2EthPortSwIXt2VlanEntry 235012096}

er1646v2EthPortSwIXt2VlanVlanChTos OBJECT-TYPE
   SYNTAX      INTEGER
               {
               disabled (0),
               enabled (1)
               }
   MAX-ACCESS  read-write
   STATUS      current
   DESCRIPTION
      "Path: swPort.editConf.vlan.vlan.changeTos

       Possibilities:
               disabled   (0)
               enabled   (1)"
   ::= {er1646v2EthPortSwIXt2VlanEntry 235208704}

er1646v2EthPortSwIXt2VlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235143424}

er1646v2EthPortSwIXt2VlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235143680}

er1646v2EthPortSwIXt2VlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235143936}

er1646v2EthPortSwIXt2VlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235144192}

er1646v2EthPortSwIXt2VlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235144448}

er1646v2EthPortSwIXt2VlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235144704}

er1646v2EthPortSwIXt2VlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235144960}

er1646v2EthPortSwIXt2VlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: swPort.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2EthPortSwIXt2VlanEntry 235145216}

er1646v2EthPortSwIXt2VlanVlanTxCos OBJECT-TYPE
   SYNTAX      INTEGER
               {
               tosCosMap (8),
               queueCosMap (16)
               }
   MAX-ACCESS  read-write
   STATUS      current
   DESCRIPTION
      "Path: swPort.editConf.vlan.vlan.txCos

       Possibilities:
               tosCosMap   (8)
               queueCosMap   (16)"
   ::= {er1646v2EthPortSwIXt2VlanEntry 235077632}

er1646v2EthPortSwIXt2VlanVlanCCMapP0 OBJECT-TYPE
   SYNTAX      Integer32
   MAX-ACCESS  read-write
   STATUS      current
   DESCRIPTION
      "Path: swPort.editConf.vlan.vlan.cosCosMap.p0"
   ::= {er1646v2EthPortSwIXt2VlanEntry 241303808}

er1646v2EthPortSwIXt2VlanVlanCCMapP1 OBJECT-TYPE
   SYNTAX      Integer32
   MAX-ACCESS  read-write
   STATUS      current
   DESCRIPTION
      "Path: swPort.editConf.vlan.vlan.cosCosMap.p1"
   ::= {er1646v2EthPortSwIXt2VlanEntry 241304064}

er1646v2EthPortSwIXt2VlanVlanCCMapP2 OBJECT-TYPE
   SYNTAX      Integer32
   MAX-ACCESS  read-write
   STATUS      current
   DESCRIPTION
      "Path: swPort.editConf.vlan.vlan.cosCosMap.p2"
   ::= {er1646v2EthPortSwIXt2VlanEntry 241304320}

er1646v2EthPortSwIXt2VlanVlanCCMapP3 OBJECT-TYPE
   SYNTAX      Integer32
   MAX-ACCESS  read-write
   STATUS      current
   DESCRIPTION
      "Path: swPort.editConf.vlan.vlan.cosCosMap.p3"
   ::= {er1646v2EthPortSwIXt2VlanEntry 241304576}

er1646v2EthPortSwIXt2VlanVlanCCMapP4 OBJECT-TYPE
   SYNTAX      Integer32
   MAX-ACCESS  read-write
   STATUS      current
   DESCRIPTION
      "Path: swPort.editConf.vlan.vlan.cosCosMap.p4"
   ::= {er1646v2EthPortSwIXt2VlanEntry 241304832}

er1646v2EthPortSwIXt2VlanVlanCCMapP5 OBJECT-TYPE
   SYNTAX      Integer32
   MAX-ACCESS  read-write
   STATUS      current
   DESCRIPTION
      "Path: swPort.editConf.vlan.vlan.cosCosMap.p5"
   ::= {er1646v2EthPortSwIXt2VlanEntry 241305088}

er1646v2EthPortSwIXt2VlanVlanCCMapP6 OBJECT-TYPE
   SYNTAX      Integer32
   MAX-ACCESS  read-write
   STATUS      current
   DESCRIPTION
      "Path: swPort.editConf.vlan.vlan.cosCosMap.p6"
   ::= {er1646v2EthPortSwIXt2VlanEntry 241305344}

er1646v2EthPortSwIXt2VlanVlanCCMapP7 OBJECT-TYPE
   SYNTAX      Integer32
   MAX-ACCESS  read-write
   STATUS      current
   DESCRIPTION
      "Path: swPort.editConf.vlan.vlan.cosCosMap.p7"
   ::= {er1646v2EthPortSwIXt2VlanEntry 241305600}

er1646v2EthPortSwIXt2VlanVlanQCMapQueue1 OBJECT-TYPE
   SYNTAX      Integer32
   MAX-ACCESS  read-write
   STATUS      current
   DESCRIPTION
      "Path: swPort.editConf.vlan.vlan.queueCosMap.queue1"
   ::= {er1646v2EthPortSwIXt2VlanEntry 241434880}

er1646v2EthPortSwIXt2VlanVlanQCMapQueue2 OBJECT-TYPE
   SYNTAX      Integer32
   MAX-ACCESS  read-write
   STATUS      current
   DESCRIPTION
      "Path: swPort.editConf.vlan.vlan.queueCosMap.queue2"
   ::= {er1646v2EthPortSwIXt2VlanEntry 241435136}

er1646v2EthPortSwIXt2VlanVlanQCMapQueue3 OBJECT-TYPE
   SYNTAX      Integer32
   MAX-ACCESS  read-write
   STATUS      current
   DESCRIPTION
      "Path: swPort.editConf.vlan.vlan.queueCosMap.queue3"
   ::= {er1646v2EthPortSwIXt2VlanEntry 241435392}

er1646v2EthPortSwIXt2VlanVlanQCMapQueue4 OBJECT-TYPE
   SYNTAX      Integer32
   MAX-ACCESS  read-write
   STATUS      current
   DESCRIPTION
      "Path: swPort.editConf.vlan.vlan.queueCosMap.queue4"
   ::= {er1646v2EthPortSwIXt2VlanEntry 241435648}

er1646v2EthPortSwIXt2VlanVlanQCMapQueue5 OBJECT-TYPE
   SYNTAX      Integer32
   MAX-ACCESS  read-write
   STATUS      current
   DESCRIPTION
      "Path: swPort.editConf.vlan.vlan.queueCosMap.queue5"
   ::= {er1646v2EthPortSwIXt2VlanEntry 241435904}

er1646v2EthPortSwIXt2VlanVlanQCMapLowDelayQueue OBJECT-TYPE
   SYNTAX      Integer32
   MAX-ACCESS  read-write
   STATUS      current
   DESCRIPTION
      "Path: swPort.editConf.vlan.vlan.queueCosMap.lowDelayQueue"
   ::= {er1646v2EthPortSwIXt2VlanEntry 241436160}

er1646v2EthPortSwIXt2VlanVlanQCMapLowDelay2Queue OBJECT-TYPE
   SYNTAX      Integer32
   MAX-ACCESS  read-write
   STATUS      current
   DESCRIPTION
      "Path: swPort.editConf.vlan.vlan.queueCosMap.lowDelay2Queue"
   ::= {er1646v2EthPortSwIXt2VlanEntry 241436416}

er1646v2EthPortSwIXt2VlanVlanQCMapSystemQueue OBJECT-TYPE
   SYNTAX      Integer32
   MAX-ACCESS  read-write
   STATUS      current
   DESCRIPTION
      "Path: swPort.editConf.vlan.vlan.queueCosMap.systemQueue"
   ::= {er1646v2EthPortSwIXt2VlanEntry 241436672}

er1646v2EthPortSwIXt2VlanVlanQinQSVid OBJECT-TYPE
   SYNTAX      Integer32
   MAX-ACCESS  read-write
   STATUS      current
   DESCRIPTION
      "Path: swPort.editConf.vlan.vlan.tunnel.sVid"
   ::= {er1646v2EthPortSwIXt2VlanEntry 241172736}

er1646v2EthPortSwIXt2VlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.tunnel.sTpid

       Possibilities:
               dot1Q   (33024)
               dot1ad   (34984)
               0x9100   (37120)
               0x9200   (37376)
               0x9300   (37632)"
   ::= {er1646v2EthPortSwIXt2VlanEntry 241172992}

er1646v2EthPortSwIXt2VlanVlanArpTimeOut OBJECT-TYPE
   SYNTAX      TimeTicks
   MAX-ACCESS  read-write
   STATUS      current
   DESCRIPTION
      "Path: swPort.editConf.vlan.vlan.arp.timeOut

       Time in centi-second."
   ::= {er1646v2EthPortSwIXt2VlanEntry 235277312}

er1646v2EthPortSwIXt2VlanVlanArpProxyArp OBJECT-TYPE
   SYNTAX      INTEGER
               {
               disabled (0),
               enabled (1)
               }
   MAX-ACCESS  read-write
   STATUS      current
   DESCRIPTION
      "Path: swPort.editConf.vlan.vlan.arp.proxyArp

       Possibilities:
               disabled   (0)
               enabled   (1)"
   ::= {er1646v2EthPortSwIXt2VlanEntry 235287040}

er1646v2EthPortSwIXt2VlanBandwidthMode OBJECT-TYPE
   SYNTAX      INTEGER
               {
               reshaping (1),
               policing (2),
               policingReshape (3)
               }
   MAX-ACCESS  read-write
   STATUS      current
   DESCRIPTION
      "Path: swPort.editConf.vlan.bandwidth.mode

       Possibilities:
               reshaping   (1)
               policing   (2)
               policingReshape   (3)"
   ::= {er1646v2EthPortSwIXt2VlanEntry 148897792}

er1646v2EthPortSwIXt2VlanBandwidthCir OBJECT-TYPE
   SYNTAX      Integer32
   MAX-ACCESS  read-write
   STATUS      current
   DESCRIPTION
      "Path: swPort.editConf.vlan.bandwidth.cir"
   ::= {er1646v2EthPortSwIXt2VlanEntry 135266304}

er1646v2EthPortSwIXt2VlanBandwidthEir OBJECT-TYPE
   SYNTAX      Integer32
   MAX-ACCESS  read-write
   STATUS      current
   DESCRIPTION
      "Path: swPort.editConf.vlan.bandwidth.eir"
   ::= {er1646v2EthPortSwIXt2VlanEntry 141557760}

er1646v2EthPortSwIXt2VlanBandwidthUnit OBJECT-TYPE
   SYNTAX      INTEGER
               {
               bitssec (1),
               percent (2)
               }
   MAX-ACCESS  read-write
   STATUS      current
   DESCRIPTION
      "Path: swPort.editConf.vlan.bandwidth.unit

       Possibilities:
               bits/sec   (1)
               percent   (2)"
   ::= {er1646v2EthPortSwIXt2VlanEntry 139460608}

er1646v2EthPortSwIXt2VlanBandwidthTc OBJECT-TYPE
   SYNTAX      INTEGER
               {
               auto (0)
               }
   MAX-ACCESS  read-write
   STATUS      current
   DESCRIPTION
      "Path: swPort.editConf.vlan.bandwidth.tc

       Possibilities:
               auto   (0)"
   ::= {er1646v2EthPortSwIXt2VlanEntry 140509184}

er1646v2EthPortSwIXt2VlanBandwidthTcFactor OBJECT-TYPE
   SYNTAX      INTEGER
               {
               ms (10),
               s100us (1)
               }
   MAX-ACCESS  read-write
   STATUS      current
   DESCRIPTION
      "Path: swPort.editConf.vlan.bandwidth.tcFactor

       Possibilities:
               ms   (10)
               *100us   (1)"
   ::= {er1646v2EthPortSwIXt2VlanEntry 142606336}

er1646v2EthPortSwIXt2VlanBandwidthCorrType OBJECT-TYPE
   SYNTAX      INTEGER
               {
               noCorrection (0),
               predefined (1),
               manual (2)
               }
   MAX-ACCESS  read-write
   STATUS      current
   DESCRIPTION
      "Path: swPort.editConf.vlan.bandwidth.correction.type

       Possibilities:
               noCorrection   (0)
               predefined   (1)
               manual   (2)"
   ::= {er1646v2EthPortSwIXt2VlanEntry 136445952}

er1646v2EthPortSwIXt2VlanBandwidthCorrPredefEncapsFrameRelay OBJECT-TYPE
   SYNTAX      DisplayString
   MAX-ACCESS  read-write
   STATUS      current
   DESCRIPTION
      "Path: swPort.editConf.vlan.bandwidth.correction.predefined.encapsulation.frameRelay"
   ::= {er1646v2EthPortSwIXt2VlanEntry 136594432}

er1646v2EthPortSwIXt2VlanBandwidthCorrPredefEncapsPpp OBJECT-TYPE
   SYNTAX      DisplayString
   MAX-ACCESS  read-write
   STATUS      current
   DESCRIPTION
      "Path: swPort.editConf.vlan.bandwidth.correction.predefined.encapsulation.ppp"
   ::= {er1646v2EthPortSwIXt2VlanEntry 136595456}

er1646v2EthPortSwIXt2VlanBandwidthCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.bandwidth.correction.predefined.encapsulation.atm.higherLayer

       Possibilities:
               rfc2684   (0)
               ppp   (1)
               pppOverEthernet   (2)"
   ::= {er1646v2EthPortSwIXt2VlanEntry 136596608}

er1646v2EthPortSwIXt2VlanBandwidthCorrPredefEncapsAtmMp OBJECT-TYPE
   SYNTAX      INTEGER
               {
               llcEncapsulation (0),
               vcMultiplexing (1)
               }
   MAX-ACCESS  read-write
   STATUS      current
   DESCRIPTION
      "Path: swPort.editConf.vlan.bandwidth.correction.predefined.encapsulation.atm.multiProtocol

       Possibilities:
               llcEncapsulation   (0)
               vcMultiplexing   (1)"
   ::= {er1646v2EthPortSwIXt2VlanEntry 136596736}

er1646v2EthPortSwIXt2VlanBandwidthCorrPredefEncapsHdlc OBJECT-TYPE
   SYNTAX      DisplayString
   MAX-ACCESS  read-write
   STATUS      current
   DESCRIPTION
      "Path: swPort.editConf.vlan.bandwidth.correction.predefined.encapsulation.hdlc"
   ::= {er1646v2EthPortSwIXt2VlanEntry 136597504}

er1646v2EthPortSwIXt2VlanBandwidthCorrPredefEncapsEfmFs OBJECT-TYPE
   SYNTAX      Integer32
   MAX-ACCESS  read-write
   STATUS      current
   DESCRIPTION
      "Path: swPort.editConf.vlan.bandwidth.correction.predefined.encapsulation.efm.fragmentSize"
   ::= {er1646v2EthPortSwIXt2VlanEntry 136598656}

er1646v2EthPortSwIXt2VlanBandwidthCorrPredefEncapsEfmIb OBJECT-TYPE
   SYNTAX      Integer32
   MAX-ACCESS  read-write
   STATUS      current
   DESCRIPTION
      "Path: swPort.editConf.vlan.bandwidth.correction.predefined.encapsulation.efm.idleBytes"
   ::= {er1646v2EthPortSwIXt2VlanEntry 136598784}

er1646v2EthPortSwIXt2VlanBandwidthCorrPredefMode OBJECT-TYPE
   SYNTAX      INTEGER
               {
               routing (0),
               bridging (1)
               }
   MAX-ACCESS  read-write
   STATUS      current
   DESCRIPTION
      "Path: swPort.editConf.vlan.bandwidth.correction.predefined.mode

       Possibilities:
               routing   (0)
               bridging   (1)"
   ::= {er1646v2EthPortSwIXt2VlanEntry 136609792}

er1646v2EthPortSwIXt2VlanBandwidthCorrManualOverhead OBJECT-TYPE
   SYNTAX      Integer32
   MAX-ACCESS  read-write
   STATUS      current
   DESCRIPTION
      "Path: swPort.editConf.vlan.bandwidth.correction.manual.overhead"
   ::= {er1646v2EthPortSwIXt2VlanEntry 136708608}

er1646v2EthPortSwIXt2VlanBandwidthCorrManualFrameData OBJECT-TYPE
   SYNTAX      Counter32
   MAX-ACCESS  read-write
   STATUS      current
   DESCRIPTION
      "Path: swPort.editConf.vlan.bandwidth.correction.manual.frameData

       32 bit unsigned wrappable counter."
   ::= {er1646v2EthPortSwIXt2VlanEntry 136709120}

er1646v2EthPortSwIXt2VlanBandwidthCorrManualFrameHeader OBJECT-TYPE
   SYNTAX      Counter32
   MAX-ACCESS  read-write
   STATUS      current
   DESCRIPTION
      "Path: swPort.editConf.vlan.bandwidth.correction.manual.frameHeader

       32 bit unsigned wrappable counter."
   ::= {er1646v2EthPortSwIXt2VlanEntry 136709632}

er1646v2EthPortSwIXt2VlanBandwidthMaxFifoQLen OBJECT-TYPE
   SYNTAX      Integer32
   MAX-ACCESS  read-write
   STATUS      current
   DESCRIPTION
      "Path: swPort.editConf.vlan.bandwidth.maxFifoQLen"
   ::= {er1646v2EthPortSwIXt2VlanEntry 137363456}

er1646v2EthPortSwIXt2VlanBandwidthDeFlagCir OBJECT-TYPE
   SYNTAX      INTEGER
               {
               allowed (1),
               notAllowed (2)
               }
   MAX-ACCESS  read-write
   STATUS      current
   DESCRIPTION
      "Path: swPort.editConf.vlan.bandwidth.deFlag.cir

       Possibilities:
               allowed   (1)
               notAllowed   (2)"
   ::= {er1646v2EthPortSwIXt2VlanEntry 147853312}

er1646v2EthPortSwIXt2VlanBandwidthDeFlagEir OBJECT-TYPE
   SYNTAX      INTEGER
               {
               allowed (1),
               notAllowed (2)
               }
   MAX-ACCESS  read-write
   STATUS      current
   DESCRIPTION
      "Path: swPort.editConf.vlan.bandwidth.deFlag.eir

       Possibilities:
               allowed   (1)
               notAllowed   (2)"
   ::= {er1646v2EthPortSwIXt2VlanEntry 147857408}

er1646v2EthPortSwIXt2VlanBandwidthDeFlagViolate OBJECT-TYPE
   SYNTAX      INTEGER
               {
               allowed (1),
               notAllowed (2)
               }
   MAX-ACCESS  read-write
   STATUS      current
   DESCRIPTION
      "Path: swPort.editConf.vlan.bandwidth.deFlag.violate

       Possibilities:
               allowed   (1)
               notAllowed   (2)"
   ::= {er1646v2EthPortSwIXt2VlanEntry 147861504}

er1646v2EthPortSwIXt2VlanBandwidthActCirActNone OBJECT-TYPE
   SYNTAX      OCTET STRING
   MAX-ACCESS  read-write
   STATUS      current
   DESCRIPTION
      "Path: swPort.editConf.vlan.bandwidth.action.cirAction.none"
   ::= {er1646v2EthPortSwIXt2VlanEntry 150085632}

er1646v2EthPortSwIXt2VlanBandwidthActCirActEthCos1 OBJECT-TYPE
   SYNTAX      INTEGER
               {
               unchanged (256)
               }
   MAX-ACCESS  read-write
   STATUS      current
   DESCRIPTION
      "Path: swPort.editConf.vlan.bandwidth.action.cirAction.ethernet.cosDepth1

       Possibilities:
               unchanged   (256)"
   ::= {er1646v2EthPortSwIXt2VlanEntry 150094080}

er1646v2EthPortSwIXt2VlanBandwidthActCirActEthDei1 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth1

       Possibilities:
               unchanged   (255)
               clear   (0)
               set   (1)"
   ::= {er1646v2EthPortSwIXt2VlanEntry 150099200}

er1646v2EthPortSwIXt2VlanBandwidthActCirActEthCos2 OBJECT-TYPE
   SYNTAX      INTEGER
               {
               unchanged (256)
               }
   MAX-ACCESS  read-write
   STATUS      current
   DESCRIPTION
      "Path: swPort.editConf.vlan.bandwidth.action.cirAction.ethernet.cosDepth2

       Possibilities:
               unchanged   (256)"
   ::= {er1646v2EthPortSwIXt2VlanEntry 150094336}

er1646v2EthPortSwIXt2VlanBandwidthActCirActEthDei2 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth2

       Possibilities:
               unchanged   (255)
               clear   (0)
               set   (1)"
   ::= {er1646v2EthPortSwIXt2VlanEntry 150099456}

er1646v2EthPortSwIXt2VlanBandwidthActCirActEthCos3 OBJECT-TYPE
   SYNTAX      INTEGER
               {
               unchanged (256)
               }
   MAX-ACCESS  read-write
   STATUS      current
   DESCRIPTION
      "Path: swPort.editConf.vlan.bandwidth.action.cirAction.ethernet.cosDepth3

       Possibilities:
               unchanged   (256)"
   ::= {er1646v2EthPortSwIXt2VlanEntry 150094592}

er1646v2EthPortSwIXt2VlanBandwidthActCirActEthDei3 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth3

       Possibilities:
               unchanged   (255)
               clear   (0)
               set   (1)"
   ::= {er1646v2EthPortSwIXt2VlanEntry 150099712}

er1646v2EthPortSwIXt2VlanBandwidthActCirActEthCos4 OBJECT-TYPE
   SYNTAX      INTEGER
               {
               unchanged (256)
               }
   MAX-ACCESS  read-write
   STATUS      current
   DESCRIPTION
      "Path: swPort.editConf.vlan.bandwidth.action.cirAction.ethernet.cosDepth4

       Possibilities:
               unchanged   (256)"
   ::= {er1646v2EthPortSwIXt2VlanEntry 150094848}

er1646v2EthPortSwIXt2VlanBandwidthActCirActEthDei4 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth4

       Possibilities:
               unchanged   (255)
               clear   (0)
               set   (1)"
   ::= {er1646v2EthPortSwIXt2VlanEntry 150099968}

er1646v2EthPortSwIXt2VlanBandwidthActCirActEthCos5 OBJECT-TYPE
   SYNTAX      INTEGER
               {
               unchanged (256)
               }
   MAX-ACCESS  read-write
   STATUS      current
   DESCRIPTION
      "Path: swPort.editConf.vlan.bandwidth.action.cirAction.ethernet.cosDepth5

       Possibilities:
               unchanged   (256)"
   ::= {er1646v2EthPortSwIXt2VlanEntry 150095104}

er1646v2EthPortSwIXt2VlanBandwidthActCirActEthDei5 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth5

       Possibilities:
               unchanged   (255)
               clear   (0)
               set   (1)"
   ::= {er1646v2EthPortSwIXt2VlanEntry 150100224}

er1646v2EthPortSwIXt2VlanBandwidthActCirActEthCos6 OBJECT-TYPE
   SYNTAX      INTEGER
               {
               unchanged (256)
               }
   MAX-ACCESS  read-write
   STATUS      current
   DESCRIPTION
      "Path: swPort.editConf.vlan.bandwidth.action.cirAction.ethernet.cosDepth6

       Possibilities:
               unchanged   (256)"
   ::= {er1646v2EthPortSwIXt2VlanEntry 150095360}

er1646v2EthPortSwIXt2VlanBandwidthActCirActEthDei6 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth6

       Possibilities:
               unchanged   (255)
               clear   (0)
               set   (1)"
   ::= {er1646v2EthPortSwIXt2VlanEntry 150100480}

er1646v2EthPortSwIXt2VlanBandwidthActCirActEthCos7 OBJECT-TYPE
   SYNTAX      INTEGER
               {
               unchanged (256)
               }
   MAX-ACCESS  read-write
   STATUS      current
   DESCRIPTION
      "Path: swPort.editConf.vlan.bandwidth.action.cirAction.ethernet.cosDepth7

       Possibilities:
               unchanged   (256)"
   ::= {er1646v2EthPortSwIXt2VlanEntry 150095616}

er1646v2EthPortSwIXt2VlanBandwidthActCirActEthDei7 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth7

       Possibilities:
               unchanged   (255)
               clear   (0)
               set   (1)"
   ::= {er1646v2EthPortSwIXt2VlanEntry 150100736}

er1646v2EthPortSwIXt2VlanBandwidthActCirActEthCos8 OBJECT-TYPE
   SYNTAX      INTEGER
               {
               unchanged (256)
               }
   MAX-ACCESS  read-write
   STATUS      current
   DESCRIPTION
      "Path: swPort.editConf.vlan.bandwidth.action.cirAction.ethernet.cosDepth8

       Possibilities:
               unchanged   (256)"
   ::= {er1646v2EthPortSwIXt2VlanEntry 150095872}

er1646v2EthPortSwIXt2VlanBandwidthActCirActEthDei8 OBJECT-TYPE
   SYNTAX      INTEGER
               {
               unchanged (255),
               clear (0),
               set (1)
               }
   MAX-ACCESS  read-write
   STATUS      current
   DESCRIPTION
      "Path: swPort.editConf.vlan.bandwidth.action.cirAction.ethernet.deiDepth8

       Possibilities:
               unchanged   (255)
               clear   (0)
               set   (1)"
   ::= {er1646v2EthPortSwIXt2VlanEntry 150100992}

er1646v2EthPortSwIXt2VlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 150096128}

er1646v2EthPortSwIXt2VlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 150096384}

er1646v2EthPortSwIXt2VlanBandwidthActCirActEthDrpLev OBJECT-TYPE
   SYNTAX      INTEGER
               {
               unchanged (0)
               }
   MAX-ACCESS  read-write
   STATUS      current
   DESCRIPTION
      "Path: swPort.editConf.vlan.bandwidth.action.cirAction.ethernet.dropLevel

       Possibilities:
               unchanged   (0)"
   ::= {er1646v2EthPortSwIXt2VlanEntry 150096640}

er1646v2EthPortSwIXt2VlanBandwidthActCirActEthDeFlag OBJECT-TYPE
   SYNTAX      INTEGER
               {
               unchanged (255),
               clear (0),
               set (1)
               }
   MAX-ACCESS  read-write
   STATUS      current
   DESCRIPTION
      "Path: swPort.editConf.vlan.bandwidth.action.cirAction.ethernet.deFlag

       Possibilities:
               unchanged   (255)
               clear   (0)
               set   (1)"
   ::= {er1646v2EthPortSwIXt2VlanEntry 150097408}

er1646v2EthPortSwIXt2VlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 150120704}

er1646v2EthPortSwIXt2VlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 150120960}

er1646v2EthPortSwIXt2VlanBandwidthActCirActIpDrpLev OBJECT-TYPE
   SYNTAX      INTEGER
               {
               unchanged (0)
               }
   MAX-ACCESS  read-write
   STATUS      current
   DESCRIPTION
      "Path: swPort.editConf.vlan.bandwidth.action.cirAction.ip.dropLevel

       Possibilities:
               unchanged   (0)"
   ::= {er1646v2EthPortSwIXt2VlanEntry 150121216}

er1646v2EthPortSwIXt2VlanBandwidthActCirActIpDeFlag OBJECT-TYPE
   SYNTAX      INTEGER
               {
               unchanged (255),
               clear (0),
               set (1)
               }
   MAX-ACCESS  read-write
   STATUS      current
   DESCRIPTION
      "Path: swPort.editConf.vlan.bandwidth.action.cirAction.ip.deFlag

       Possibilities:
               unchanged   (255)
               clear   (0)
               set   (1)"
   ::= {er1646v2EthPortSwIXt2VlanEntry 150121984}

er1646v2EthPortSwIXt2VlanBandwidthActEirActNone OBJECT-TYPE
   SYNTAX      OCTET STRING
   MAX-ACCESS  read-write
   STATUS      current
   DESCRIPTION
      "Path: swPort.editConf.vlan.bandwidth.action.eirAction.none"
   ::= {er1646v2EthPortSwIXt2VlanEntry 150216704}

er1646v2EthPortSwIXt2VlanBandwidthActEirActEthCos1 OBJECT-TYPE
   SYNTAX      INTEGER
               {
               unchanged (256)
               }
   MAX-ACCESS  read-write
   STATUS      current
   DESCRIPTION
      "Path: swPort.editConf.vlan.bandwidth.action.eirAction.ethernet.cosDepth1

       Possibilities:
               unchanged   (256)"
   ::= {er1646v2EthPortSwIXt2VlanEntry 150225152}

er1646v2EthPortSwIXt2VlanBandwidthActEirActEthDei1 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth1

       Possibilities:
               unchanged   (255)
               clear   (0)
               set   (1)"
   ::= {er1646v2EthPortSwIXt2VlanEntry 150230272}

er1646v2EthPortSwIXt2VlanBandwidthActEirActEthCos2 OBJECT-TYPE
   SYNTAX      INTEGER
               {
               unchanged (256)
               }
   MAX-ACCESS  read-write
   STATUS      current
   DESCRIPTION
      "Path: swPort.editConf.vlan.bandwidth.action.eirAction.ethernet.cosDepth2

       Possibilities:
               unchanged   (256)"
   ::= {er1646v2EthPortSwIXt2VlanEntry 150225408}

er1646v2EthPortSwIXt2VlanBandwidthActEirActEthDei2 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth2

       Possibilities:
               unchanged   (255)
               clear   (0)
               set   (1)"
   ::= {er1646v2EthPortSwIXt2VlanEntry 150230528}

er1646v2EthPortSwIXt2VlanBandwidthActEirActEthCos3 OBJECT-TYPE
   SYNTAX      INTEGER
               {
               unchanged (256)
               }
   MAX-ACCESS  read-write
   STATUS      current
   DESCRIPTION
      "Path: swPort.editConf.vlan.bandwidth.action.eirAction.ethernet.cosDepth3

       Possibilities:
               unchanged   (256)"
   ::= {er1646v2EthPortSwIXt2VlanEntry 150225664}

er1646v2EthPortSwIXt2VlanBandwidthActEirActEthDei3 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth3

       Possibilities:
               unchanged   (255)
               clear   (0)
               set   (1)"
   ::= {er1646v2EthPortSwIXt2VlanEntry 150230784}

er1646v2EthPortSwIXt2VlanBandwidthActEirActEthCos4 OBJECT-TYPE
   SYNTAX      INTEGER
               {
               unchanged (256)
               }
   MAX-ACCESS  read-write
   STATUS      current
   DESCRIPTION
      "Path: swPort.editConf.vlan.bandwidth.action.eirAction.ethernet.cosDepth4

       Possibilities:
               unchanged   (256)"
   ::= {er1646v2EthPortSwIXt2VlanEntry 150225920}

er1646v2EthPortSwIXt2VlanBandwidthActEirActEthDei4 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth4

       Possibilities:
               unchanged   (255)
               clear   (0)
               set   (1)"
   ::= {er1646v2EthPortSwIXt2VlanEntry 150231040}

er1646v2EthPortSwIXt2VlanBandwidthActEirActEthCos5 OBJECT-TYPE
   SYNTAX      INTEGER
               {
               unchanged (256)
               }
   MAX-ACCESS  read-write
   STATUS      current
   DESCRIPTION
      "Path: swPort.editConf.vlan.bandwidth.action.eirAction.ethernet.cosDepth5

       Possibilities:
               unchanged   (256)"
   ::= {er1646v2EthPortSwIXt2VlanEntry 150226176}

er1646v2EthPortSwIXt2VlanBandwidthActEirActEthDei5 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth5

       Possibilities:
               unchanged   (255)
               clear   (0)
               set   (1)"
   ::= {er1646v2EthPortSwIXt2VlanEntry 150231296}

er1646v2EthPortSwIXt2VlanBandwidthActEirActEthCos6 OBJECT-TYPE
   SYNTAX      INTEGER
               {
               unchanged (256)
               }
   MAX-ACCESS  read-write
   STATUS      current
   DESCRIPTION
      "Path: swPort.editConf.vlan.bandwidth.action.eirAction.ethernet.cosDepth6

       Possibilities:
               unchanged   (256)"
   ::= {er1646v2EthPortSwIXt2VlanEntry 150226432}

er1646v2EthPortSwIXt2VlanBandwidthActEirActEthDei6 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth6

       Possibilities:
               unchanged   (255)
               clear   (0)
               set   (1)"
   ::= {er1646v2EthPortSwIXt2VlanEntry 150231552}

er1646v2EthPortSwIXt2VlanBandwidthActEirActEthCos7 OBJECT-TYPE
   SYNTAX      INTEGER
               {
               unchanged (256)
               }
   MAX-ACCESS  read-write
   STATUS      current
   DESCRIPTION
      "Path: swPort.editConf.vlan.bandwidth.action.eirAction.ethernet.cosDepth7

       Possibilities:
               unchanged   (256)"
   ::= {er1646v2EthPortSwIXt2VlanEntry 150226688}

er1646v2EthPortSwIXt2VlanBandwidthActEirActEthDei7 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth7

       Possibilities:
               unchanged   (255)
               clear   (0)
               set   (1)"
   ::= {er1646v2EthPortSwIXt2VlanEntry 150231808}

er1646v2EthPortSwIXt2VlanBandwidthActEirActEthCos8 OBJECT-TYPE
   SYNTAX      INTEGER
               {
               unchanged (256)
               }
   MAX-ACCESS  read-write
   STATUS      current
   DESCRIPTION
      "Path: swPort.editConf.vlan.bandwidth.action.eirAction.ethernet.cosDepth8

       Possibilities:
               unchanged   (256)"
   ::= {er1646v2EthPortSwIXt2VlanEntry 150226944}

er1646v2EthPortSwIXt2VlanBandwidthActEirActEthDei8 OBJECT-TYPE
   SYNTAX      INTEGER
               {
               unchanged (255),
               clear (0),
               set (1)
               }
   MAX-ACCESS  read-write
   STATUS      current
   DESCRIPTION
      "Path: swPort.editConf.vlan.bandwidth.action.eirAction.ethernet.deiDepth8

       Possibilities:
               unchanged   (255)
               clear   (0)
               set   (1)"
   ::= {er1646v2EthPortSwIXt2VlanEntry 150232064}

er1646v2EthPortSwIXt2VlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 150227200}

er1646v2EthPortSwIXt2VlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 150227456}

er1646v2EthPortSwIXt2VlanBandwidthActEirActEthDrpLev OBJECT-TYPE
   SYNTAX      INTEGER
               {
               unchanged (0)
               }
   MAX-ACCESS  read-write
   STATUS      current
   DESCRIPTION
      "Path: swPort.editConf.vlan.bandwidth.action.eirAction.ethernet.dropLevel

       Possibilities:
               unchanged   (0)"
   ::= {er1646v2EthPortSwIXt2VlanEntry 150227712}

er1646v2EthPortSwIXt2VlanBandwidthActEirActEthDeFlag OBJECT-TYPE
   SYNTAX      INTEGER
               {
               unchanged (255),
               clear (0),
               set (1)
               }
   MAX-ACCESS  read-write
   STATUS      current
   DESCRIPTION
      "Path: swPort.editConf.vlan.bandwidth.action.eirAction.ethernet.deFlag

       Possibilities:
               unchanged   (255)
               clear   (0)
               set   (1)"
   ::= {er1646v2EthPortSwIXt2VlanEntry 150228480}

er1646v2EthPortSwIXt2VlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 150251776}

er1646v2EthPortSwIXt2VlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 150252032}

er1646v2EthPortSwIXt2VlanBandwidthActEirActIpDrpLev OBJECT-TYPE
   SYNTAX      INTEGER
               {
               unchanged (0)
               }
   MAX-ACCESS  read-write
   STATUS      current
   DESCRIPTION
      "Path: swPort.editConf.vlan.bandwidth.action.eirAction.ip.dropLevel

       Possibilities:
               unchanged   (0)"
   ::= {er1646v2EthPortSwIXt2VlanEntry 150252288}

er1646v2EthPortSwIXt2VlanBandwidthActEirActIpDeFlag OBJECT-TYPE
   SYNTAX      INTEGER
               {
               unchanged (255),
               clear (0),
               set (1)
               }
   MAX-ACCESS  read-write
   STATUS      current
   DESCRIPTION
      "Path: swPort.editConf.vlan.bandwidth.action.eirAction.ip.deFlag

       Possibilities:
               unchanged   (255)
               clear   (0)
               set   (1)"
   ::= {er1646v2EthPortSwIXt2VlanEntry 150253056}

er1646v2EthPortSwIXt2VlanBandwidthActViolActNone OBJECT-TYPE
   SYNTAX      OCTET STRING
   MAX-ACCESS  read-write
   STATUS      current
   DESCRIPTION
      "Path: swPort.editConf.vlan.bandwidth.action.violateAction.none"
   ::= {er1646v2EthPortSwIXt2VlanEntry 150347776}

er1646v2EthPortSwIXt2VlanBandwidthActViolActDrop OBJECT-TYPE
   SYNTAX      OCTET STRING
   MAX-ACCESS  read-write
   STATUS      current
   DESCRIPTION
      "Path: swPort.editConf.vlan.bandwidth.action.violateAction.drop"
   ::= {er1646v2EthPortSwIXt2VlanEntry 150364160}

er1646v2EthPortSwIXt2VlanBandwidthActViolActEthCos1 OBJECT-TYPE
   SYNTAX      INTEGER
               {
               unchanged (256)
               }
   MAX-ACCESS  read-write
   STATUS      current
   DESCRIPTION
      "Path: swPort.editConf.vlan.bandwidth.action.violateAction.ethernet.cosDepth1

       Possibilities:
               unchanged   (256)"
   ::= {er1646v2EthPortSwIXt2VlanEntry 150356224}

er1646v2EthPortSwIXt2VlanBandwidthActViolActEthDei1 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth1

       Possibilities:
               unchanged   (255)
               clear   (0)
               set   (1)"
   ::= {er1646v2EthPortSwIXt2VlanEntry 150361344}

er1646v2EthPortSwIXt2VlanBandwidthActViolActEthCos2 OBJECT-TYPE
   SYNTAX      INTEGER
               {
               unchanged (256)
               }
   MAX-ACCESS  read-write
   STATUS      current
   DESCRIPTION
      "Path: swPort.editConf.vlan.bandwidth.action.violateAction.ethernet.cosDepth2

       Possibilities:
               unchanged   (256)"
   ::= {er1646v2EthPortSwIXt2VlanEntry 150356480}

er1646v2EthPortSwIXt2VlanBandwidthActViolActEthDei2 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth2

       Possibilities:
               unchanged   (255)
               clear   (0)
               set   (1)"
   ::= {er1646v2EthPortSwIXt2VlanEntry 150361600}

er1646v2EthPortSwIXt2VlanBandwidthActViolActEthCos3 OBJECT-TYPE
   SYNTAX      INTEGER
               {
               unchanged (256)
               }
   MAX-ACCESS  read-write
   STATUS      current
   DESCRIPTION
      "Path: swPort.editConf.vlan.bandwidth.action.violateAction.ethernet.cosDepth3

       Possibilities:
               unchanged   (256)"
   ::= {er1646v2EthPortSwIXt2VlanEntry 150356736}

er1646v2EthPortSwIXt2VlanBandwidthActViolActEthDei3 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth3

       Possibilities:
               unchanged   (255)
               clear   (0)
               set   (1)"
   ::= {er1646v2EthPortSwIXt2VlanEntry 150361856}

er1646v2EthPortSwIXt2VlanBandwidthActViolActEthCos4 OBJECT-TYPE
   SYNTAX      INTEGER
               {
               unchanged (256)
               }
   MAX-ACCESS  read-write
   STATUS      current
   DESCRIPTION
      "Path: swPort.editConf.vlan.bandwidth.action.violateAction.ethernet.cosDepth4

       Possibilities:
               unchanged   (256)"
   ::= {er1646v2EthPortSwIXt2VlanEntry 150356992}

er1646v2EthPortSwIXt2VlanBandwidthActViolActEthDei4 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth4

       Possibilities:
               unchanged   (255)
               clear   (0)
               set   (1)"
   ::= {er1646v2EthPortSwIXt2VlanEntry 150362112}

er1646v2EthPortSwIXt2VlanBandwidthActViolActEthCos5 OBJECT-TYPE
   SYNTAX      INTEGER
               {
               unchanged (256)
               }
   MAX-ACCESS  read-write
   STATUS      current
   DESCRIPTION
      "Path: swPort.editConf.vlan.bandwidth.action.violateAction.ethernet.cosDepth5

       Possibilities:
               unchanged   (256)"
   ::= {er1646v2EthPortSwIXt2VlanEntry 150357248}

er1646v2EthPortSwIXt2VlanBandwidthActViolActEthDei5 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth5

       Possibilities:
               unchanged   (255)
               clear   (0)
               set   (1)"
   ::= {er1646v2EthPortSwIXt2VlanEntry 150362368}

er1646v2EthPortSwIXt2VlanBandwidthActViolActEthCos6 OBJECT-TYPE
   SYNTAX      INTEGER
               {
               unchanged (256)
               }
   MAX-ACCESS  read-write
   STATUS      current
   DESCRIPTION
      "Path: swPort.editConf.vlan.bandwidth.action.violateAction.ethernet.cosDepth6

       Possibilities:
               unchanged   (256)"
   ::= {er1646v2EthPortSwIXt2VlanEntry 150357504}

er1646v2EthPortSwIXt2VlanBandwidthActViolActEthDei6 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth6

       Possibilities:
               unchanged   (255)
               clear   (0)
               set   (1)"
   ::= {er1646v2EthPortSwIXt2VlanEntry 150362624}

er1646v2EthPortSwIXt2VlanBandwidthActViolActEthCos7 OBJECT-TYPE
   SYNTAX      INTEGER
               {
               unchanged (256)
               }
   MAX-ACCESS  read-write
   STATUS      current
   DESCRIPTION
      "Path: swPort.editConf.vlan.bandwidth.action.violateAction.ethernet.cosDepth7

       Possibilities:
               unchanged   (256)"
   ::= {er1646v2EthPortSwIXt2VlanEntry 150357760}

er1646v2EthPortSwIXt2VlanBandwidthActViolActEthDei7 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth7

       Possibilities:
               unchanged   (255)
               clear   (0)
               set   (1)"
   ::= {er1646v2EthPortSwIXt2VlanEntry 150362880}

er1646v2EthPortSwIXt2VlanBandwidthActViolActEthCos8 OBJECT-TYPE
   SYNTAX      INTEGER
               {
               unchanged (256)
               }
   MAX-ACCESS  read-write
   STATUS      current
   DESCRIPTION
      "Path: swPort.editConf.vlan.bandwidth.action.violateAction.ethernet.cosDepth8

       Possibilities:
               unchanged   (256)"
   ::= {er1646v2EthPortSwIXt2VlanEntry 150358016}

er1646v2EthPortSwIXt2VlanBandwidthActViolActEthDei8 OBJECT-TYPE
   SYNTAX      INTEGER
               {
               unchanged (255),
               clear (0),
               set (1)
               }
   MAX-ACCESS  read-write
   STATUS      current
   DESCRIPTION
      "Path: swPort.editConf.vlan.bandwidth.action.violateAction.ethernet.deiDepth8

       Possibilities:
               unchanged   (255)
               clear   (0)
               set   (1)"
   ::= {er1646v2EthPortSwIXt2VlanEntry 150363136}

er1646v2EthPortSwIXt2VlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 150358272}

er1646v2EthPortSwIXt2VlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 150358528}

er1646v2EthPortSwIXt2VlanBandwidthActViolActEthDrpLev OBJECT-TYPE
   SYNTAX      INTEGER
               {
               unchanged (0)
               }
   MAX-ACCESS  read-write
   STATUS      current
   DESCRIPTION
      "Path: swPort.editConf.vlan.bandwidth.action.violateAction.ethernet.dropLevel

       Possibilities:
               unchanged   (0)"
   ::= {er1646v2EthPortSwIXt2VlanEntry 150358784}

er1646v2EthPortSwIXt2VlanBandwidthActViolActEthDeFlag OBJECT-TYPE
   SYNTAX      INTEGER
               {
               unchanged (255),
               clear (0),
               set (1)
               }
   MAX-ACCESS  read-write
   STATUS      current
   DESCRIPTION
      "Path: swPort.editConf.vlan.bandwidth.action.violateAction.ethernet.deFlag

       Possibilities:
               unchanged   (255)
               clear   (0)
               set   (1)"
   ::= {er1646v2EthPortSwIXt2VlanEntry 150359552}

er1646v2EthPortSwIXt2VlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 150382848}

er1646v2EthPortSwIXt2VlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 150383104}

er1646v2EthPortSwIXt2VlanBandwidthActViolActIpDrpLev OBJECT-TYPE
   SYNTAX      INTEGER
               {
               unchanged (0)
               }
   MAX-ACCESS  read-write
   STATUS      current
   DESCRIPTION
      "Path: swPort.editConf.vlan.bandwidth.action.violateAction.ip.dropLevel

       Possibilities:
               unchanged   (0)"
   ::= {er1646v2EthPortSwIXt2VlanEntry 150383360}

er1646v2EthPortSwIXt2VlanBandwidthActViolActIpDeFlag OBJECT-TYPE
   SYNTAX      INTEGER
               {
               unchanged (255),
               clear (0),
               set (1)
               }
   MAX-ACCESS  read-write
   STATUS      current
   DESCRIPTION
      "Path: swPort.editConf.vlan.bandwidth.action.violateAction.ip.deFlag

       Possibilities:
               unchanged   (255)
               clear   (0)
               set   (1)"
   ::= {er1646v2EthPortSwIXt2VlanEntry 150384128}

er1646v2EthPortSwIXt2VlanInbBwMode OBJECT-TYPE
   SYNTAX      INTEGER
               {
               reshaping (1),
               policing (2)
               }
   MAX-ACCESS  read-write
   STATUS      current
   DESCRIPTION
      "Path: swPort.editConf.vlan.inboundBandwidth.mode

       Possibilities:
               reshaping   (1)
               policing   (2)"
   ::= {er1646v2EthPortSwIXt2VlanEntry 132120576}

er1646v2EthPortSwIXt2VlanInbBwCir OBJECT-TYPE
   SYNTAX      Integer32
   MAX-ACCESS  read-write
   STATUS      current
   DESCRIPTION
      "Path: swPort.editConf.vlan.inboundBandwidth.cir"
   ::= {er1646v2EthPortSwIXt2VlanEntry 118489088}

er1646v2EthPortSwIXt2VlanInbBwEir OBJECT-TYPE
   SYNTAX      Integer32
   MAX-ACCESS  read-write
   STATUS      current
   DESCRIPTION
      "Path: swPort.editConf.vlan.inboundBandwidth.eir"
   ::= {er1646v2EthPortSwIXt2VlanEntry 124780544}

er1646v2EthPortSwIXt2VlanInbBwUnit OBJECT-TYPE
   SYNTAX      INTEGER
               {
               bitssec (1),
               percent (2)
               }
   MAX-ACCESS  read-write
   STATUS      current
   DESCRIPTION
      "Path: swPort.editConf.vlan.inboundBandwidth.unit

       Possibilities:
               bits/sec   (1)
               percent   (2)"
   ::= {er1646v2EthPortSwIXt2VlanEntry 122683392}

er1646v2EthPortSwIXt2VlanInbBwTc OBJECT-TYPE
   SYNTAX      INTEGER
               {
               auto (0)
               }
   MAX-ACCESS  read-write
   STATUS      current
   DESCRIPTION
      "Path: swPort.editConf.vlan.inboundBandwidth.tc

       Possibilities:
               auto   (0)"
   ::= {er1646v2EthPortSwIXt2VlanEntry 123731968}

er1646v2EthPortSwIXt2VlanInbBwTcFactor OBJECT-TYPE
   SYNTAX      INTEGER
               {
               ms (10),
               s100us (1)
               }
   MAX-ACCESS  read-write
   STATUS      current
   DESCRIPTION
      "Path: swPort.editConf.vlan.inboundBandwidth.tcFactor

       Possibilities:
               ms   (10)
               *100us   (1)"
   ::= {er1646v2EthPortSwIXt2VlanEntry 125829120}

er1646v2EthPortSwIXt2VlanInbBwCorrType OBJECT-TYPE
   SYNTAX      INTEGER
               {
               noCorrection (0),
               predefined (1),
               manual (2)
               }
   MAX-ACCESS  read-write
   STATUS      current
   DESCRIPTION
      "Path: swPort.editConf.vlan.inboundBandwidth.correction.type

       Possibilities:
               noCorrection   (0)
               predefined   (1)
               manual   (2)"
   ::= {er1646v2EthPortSwIXt2VlanEntry 119668736}

er1646v2EthPortSwIXt2VlanInbBwCorrPredefEncapsFrameRelay OBJECT-TYPE
   SYNTAX      DisplayString
   MAX-ACCESS  read-write
   STATUS      current
   DESCRIPTION
      "Path: swPort.editConf.vlan.inboundBandwidth.correction.predefined.encapsulation.frameRelay"
   ::= {er1646v2EthPortSwIXt2VlanEntry 119817216}

er1646v2EthPortSwIXt2VlanInbBwCorrPredefEncapsPpp OBJECT-TYPE
   SYNTAX      DisplayString
   MAX-ACCESS  read-write
   STATUS      current
   DESCRIPTION
      "Path: swPort.editConf.vlan.inboundBandwidth.correction.predefined.encapsulation.ppp"
   ::= {er1646v2EthPortSwIXt2VlanEntry 119818240}

er1646v2EthPortSwIXt2VlanInbBwCorrPredefEncapsAtmHl OBJECT-TYPE
   SYNTAX      INTEGER
               {
               rfc2684 (0),
               ppp (1),
               pppOverEthernet (2)
               }
   MAX-ACCESS  read-write
   STATUS      current
   DESCRIPTION
      "Path: swPort.editConf.vlan.inboundBandwidth.correction.predefined.encapsulation.atm.higherLayer

       Possibilities:
               rfc2684   (0)
               ppp   (1)
               pppOverEthernet   (2)"
   ::= {er1646v2EthPortSwIXt2VlanEntry 119819392}

er1646v2EthPortSwIXt2VlanInbBwCorrPredefEncapsAtmMp OBJECT-TYPE
   SYNTAX      INTEGER
               {
               llcEncapsulation (0),
               vcMultiplexing (1)
               }
   MAX-ACCESS  read-write
   STATUS      current
   DESCRIPTION
      "Path: swPort.editConf.vlan.inboundBandwidth.correction.predefined.encapsulation.atm.multiProtocol

       Possibilities:
               llcEncapsulation   (0)
               vcMultiplexing   (1)"
   ::= {er1646v2EthPortSwIXt2VlanEntry 119819520}

er1646v2EthPortSwIXt2VlanInbBwCorrPredefEncapsHdlc OBJECT-TYPE
   SYNTAX      DisplayString
   MAX-ACCESS  read-write
   STATUS      current
   DESCRIPTION
      "Path: swPort.editConf.vlan.inboundBandwidth.correction.predefined.encapsulation.hdlc"
   ::= {er1646v2EthPortSwIXt2VlanEntry 119820288}

er1646v2EthPortSwIXt2VlanInbBwCorrPredefEncapsEfmFs OBJECT-TYPE
   SYNTAX      Integer32
   MAX-ACCESS  read-write
   STATUS      current
   DESCRIPTION
      "Path: swPort.editConf.vlan.inboundBandwidth.correction.predefined.encapsulation.efm.fragmentSize"
   ::= {er1646v2EthPortSwIXt2VlanEntry 119821440}

er1646v2EthPortSwIXt2VlanInbBwCorrPredefEncapsEfmIb OBJECT-TYPE
   SYNTAX      Integer32
   MAX-ACCESS  read-write
   STATUS      current
   DESCRIPTION
      "Path: swPort.editConf.vlan.inboundBandwidth.correction.predefined.encapsulation.efm.idleBytes"
   ::= {er1646v2EthPortSwIXt2VlanEntry 119821568}

er1646v2EthPortSwIXt2VlanInbBwCorrPredefMode OBJECT-TYPE
   SYNTAX      INTEGER
               {
               routing (0),
               bridging (1)
               }
   MAX-ACCESS  read-write
   STATUS      current
   DESCRIPTION
      "Path: swPort.editConf.vlan.inboundBandwidth.correction.predefined.mode

       Possibilities:
               routing   (0)
               bridging   (1)"
   ::= {er1646v2EthPortSwIXt2VlanEntry 119832576}

er1646v2EthPortSwIXt2VlanInbBwCorrManualOverhead OBJECT-TYPE
   SYNTAX      Integer32
   MAX-ACCESS  read-write
   STATUS      current
   DESCRIPTION
      "Path: swPort.editConf.vlan.inboundBandwidth.correction.manual.overhead"
   ::= {er1646v2EthPortSwIXt2VlanEntry 119931392}

er1646v2EthPortSwIXt2VlanInbBwCorrManualFrameData OBJECT-TYPE
   SYNTAX      Counter32
   MAX-ACCESS  read-write
   STATUS      current
   DESCRIPTION
      "Path: swPort.editConf.vlan.inboundBandwidth.correction.manual.frameData

       32 bit unsigned wrappable counter."
   ::= {er1646v2EthPortSwIXt2VlanEntry 119931904}

er1646v2EthPortSwIXt2VlanInbBwCorrManualFrameHeader OBJECT-TYPE
   SYNTAX      Counter32
   MAX-ACCESS  read-write
   STATUS      current
   DESCRIPTION
      "Path: swPort.editConf.vlan.inboundBandwidth.correction.manual.frameHeader

       32 bit unsigned wrappable counter."
   ::= {er1646v2EthPortSwIXt2VlanEntry 119932416}

er1646v2EthPortSwIXt2VlanInbBwMaxFifoQLen OBJECT-TYPE
   SYNTAX      Integer32
   MAX-ACCESS  read-write
   STATUS      current
   DESCRIPTION
      "Path: swPort.editConf.vlan.inboundBandwidth.maxFifoQLen"
   ::= {er1646v2EthPortSwIXt2VlanEntry 120586240}

er1646v2EthPortSwIXt2VlanInbBwPriorityPolicy OBJECT-TYPE
   SYNTAX      DisplayString
   MAX-ACCESS  read-write
   STATUS      current
   DESCRIPTION
      "Path: swPort.editConf.vlan.inboundBandwidth.priorityPolicy"
   ::= {er1646v2EthPortSwIXt2VlanEntry 121634816}

er1646v2EthPortSwIXt2VlanInbBwDeFlagCir OBJECT-TYPE
   SYNTAX      INTEGER
               {
               allowed (1),
               notAllowed (2)
               }
   MAX-ACCESS  read-write
   STATUS      current
   DESCRIPTION
      "Path: swPort.editConf.vlan.inboundBandwidth.deFlag.cir

       Possibilities:
               allowed   (1)
               notAllowed   (2)"
   ::= {er1646v2EthPortSwIXt2VlanEntry 131076096}

er1646v2EthPortSwIXt2VlanInbBwDeFlagEir OBJECT-TYPE
   SYNTAX      INTEGER
               {
               allowed (1),
               notAllowed (2)
               }
   MAX-ACCESS  read-write
   STATUS      current
   DESCRIPTION
      "Path: swPort.editConf.vlan.inboundBandwidth.deFlag.eir

       Possibilities:
               allowed   (1)
               notAllowed   (2)"
   ::= {er1646v2EthPortSwIXt2VlanEntry 131080192}

er1646v2EthPortSwIXt2VlanInbBwDeFlagViolate OBJECT-TYPE
   SYNTAX      INTEGER
               {
               allowed (1),
               notAllowed (2)
               }
   MAX-ACCESS  read-write
   STATUS      current
   DESCRIPTION
      "Path: swPort.editConf.vlan.inboundBandwidth.deFlag.violate

       Possibilities:
               allowed   (1)
               notAllowed   (2)"
   ::= {er1646v2EthPortSwIXt2VlanEntry 131084288}

er1646v2EthPortSwIXt2VlanInbBwActCirActNone OBJECT-TYPE
   SYNTAX      OCTET STRING
   MAX-ACCESS  read-write
   STATUS      current
   DESCRIPTION
      "Path: swPort.editConf.vlan.inboundBandwidth.action.cirAction.none"
   ::= {er1646v2EthPortSwIXt2VlanEntry 133308416}

er1646v2EthPortSwIXt2VlanInbBwActCirActEthCos1 OBJECT-TYPE
   SYNTAX      INTEGER
               {
               unchanged (256)
               }
   MAX-ACCESS  read-write
   STATUS      current
   DESCRIPTION
      "Path: swPort.editConf.vlan.inboundBandwidth.action.cirAction.ethernet.cosDepth1

       Possibilities:
               unchanged   (256)"
   ::= {er1646v2EthPortSwIXt2VlanEntry 133316864}

er1646v2EthPortSwIXt2VlanInbBwActCirActEthDei1 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth1

       Possibilities:
               unchanged   (255)
               clear   (0)
               set   (1)"
   ::= {er1646v2EthPortSwIXt2VlanEntry 133321984}

er1646v2EthPortSwIXt2VlanInbBwActCirActEthCos2 OBJECT-TYPE
   SYNTAX      INTEGER
               {
               unchanged (256)
               }
   MAX-ACCESS  read-write
   STATUS      current
   DESCRIPTION
      "Path: swPort.editConf.vlan.inboundBandwidth.action.cirAction.ethernet.cosDepth2

       Possibilities:
               unchanged   (256)"
   ::= {er1646v2EthPortSwIXt2VlanEntry 133317120}

er1646v2EthPortSwIXt2VlanInbBwActCirActEthDei2 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth2

       Possibilities:
               unchanged   (255)
               clear   (0)
               set   (1)"
   ::= {er1646v2EthPortSwIXt2VlanEntry 133322240}

er1646v2EthPortSwIXt2VlanInbBwActCirActEthCos3 OBJECT-TYPE
   SYNTAX      INTEGER
               {
               unchanged (256)
               }
   MAX-ACCESS  read-write
   STATUS      current
   DESCRIPTION
      "Path: swPort.editConf.vlan.inboundBandwidth.action.cirAction.ethernet.cosDepth3

       Possibilities:
               unchanged   (256)"
   ::= {er1646v2EthPortSwIXt2VlanEntry 133317376}

er1646v2EthPortSwIXt2VlanInbBwActCirActEthDei3 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth3

       Possibilities:
               unchanged   (255)
               clear   (0)
               set   (1)"
   ::= {er1646v2EthPortSwIXt2VlanEntry 133322496}

er1646v2EthPortSwIXt2VlanInbBwActCirActEthCos4 OBJECT-TYPE
   SYNTAX      INTEGER
               {
               unchanged (256)
               }
   MAX-ACCESS  read-write
   STATUS      current
   DESCRIPTION
      "Path: swPort.editConf.vlan.inboundBandwidth.action.cirAction.ethernet.cosDepth4

       Possibilities:
               unchanged   (256)"
   ::= {er1646v2EthPortSwIXt2VlanEntry 133317632}

er1646v2EthPortSwIXt2VlanInbBwActCirActEthDei4 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth4

       Possibilities:
               unchanged   (255)
               clear   (0)
               set   (1)"
   ::= {er1646v2EthPortSwIXt2VlanEntry 133322752}

er1646v2EthPortSwIXt2VlanInbBwActCirActEthCos5 OBJECT-TYPE
   SYNTAX      INTEGER
               {
               unchanged (256)
               }
   MAX-ACCESS  read-write
   STATUS      current
   DESCRIPTION
      "Path: swPort.editConf.vlan.inboundBandwidth.action.cirAction.ethernet.cosDepth5

       Possibilities:
               unchanged   (256)"
   ::= {er1646v2EthPortSwIXt2VlanEntry 133317888}

er1646v2EthPortSwIXt2VlanInbBwActCirActEthDei5 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth5

       Possibilities:
               unchanged   (255)
               clear   (0)
               set   (1)"
   ::= {er1646v2EthPortSwIXt2VlanEntry 133323008}

er1646v2EthPortSwIXt2VlanInbBwActCirActEthCos6 OBJECT-TYPE
   SYNTAX      INTEGER
               {
               unchanged (256)
               }
   MAX-ACCESS  read-write
   STATUS      current
   DESCRIPTION
      "Path: swPort.editConf.vlan.inboundBandwidth.action.cirAction.ethernet.cosDepth6

       Possibilities:
               unchanged   (256)"
   ::= {er1646v2EthPortSwIXt2VlanEntry 133318144}

er1646v2EthPortSwIXt2VlanInbBwActCirActEthDei6 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth6

       Possibilities:
               unchanged   (255)
               clear   (0)
               set   (1)"
   ::= {er1646v2EthPortSwIXt2VlanEntry 133323264}

er1646v2EthPortSwIXt2VlanInbBwActCirActEthCos7 OBJECT-TYPE
   SYNTAX      INTEGER
               {
               unchanged (256)
               }
   MAX-ACCESS  read-write
   STATUS      current
   DESCRIPTION
      "Path: swPort.editConf.vlan.inboundBandwidth.action.cirAction.ethernet.cosDepth7

       Possibilities:
               unchanged   (256)"
   ::= {er1646v2EthPortSwIXt2VlanEntry 133318400}

er1646v2EthPortSwIXt2VlanInbBwActCirActEthDei7 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth7

       Possibilities:
               unchanged   (255)
               clear   (0)
               set   (1)"
   ::= {er1646v2EthPortSwIXt2VlanEntry 133323520}

er1646v2EthPortSwIXt2VlanInbBwActCirActEthCos8 OBJECT-TYPE
   SYNTAX      INTEGER
               {
               unchanged (256)
               }
   MAX-ACCESS  read-write
   STATUS      current
   DESCRIPTION
      "Path: swPort.editConf.vlan.inboundBandwidth.action.cirAction.ethernet.cosDepth8

       Possibilities:
               unchanged   (256)"
   ::= {er1646v2EthPortSwIXt2VlanEntry 133318656}

er1646v2EthPortSwIXt2VlanInbBwActCirActEthDei8 OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deiDepth8

       Possibilities:
               unchanged   (255)
               clear   (0)
               set   (1)"
   ::= {er1646v2EthPortSwIXt2VlanEntry 133323776}

er1646v2EthPortSwIXt2VlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 133318912}

er1646v2EthPortSwIXt2VlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 133319168}

er1646v2EthPortSwIXt2VlanInbBwActCirActEthDrpLev OBJECT-TYPE
   SYNTAX      INTEGER
               {
               unchanged (0)
               }
   MAX-ACCESS  read-write
   STATUS      current
   DESCRIPTION
      "Path: swPort.editConf.vlan.inboundBandwidth.action.cirAction.ethernet.dropLevel

       Possibilities:
               unchanged   (0)"
   ::= {er1646v2EthPortSwIXt2VlanEntry 133319424}

er1646v2EthPortSwIXt2VlanInbBwActCirActEthDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ethernet.deFlag

       Possibilities:
               unchanged   (255)
               clear   (0)
               set   (1)"
   ::= {er1646v2EthPortSwIXt2VlanEntry 133320192}

er1646v2EthPortSwIXt2VlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 133343488}

er1646v2EthPortSwIXt2VlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 133343744}

er1646v2EthPortSwIXt2VlanInbBwActCirActIpDrpLev OBJECT-TYPE
   SYNTAX      INTEGER
               {
               unchanged (0)
               }
   MAX-ACCESS  read-write
   STATUS      current
   DESCRIPTION
      "Path: swPort.editConf.vlan.inboundBandwidth.action.cirAction.ip.dropLevel

       Possibilities:
               unchanged   (0)"
   ::= {er1646v2EthPortSwIXt2VlanEntry 133344000}

er1646v2EthPortSwIXt2VlanInbBwActCirActIpDeFlag OBJECT-TYPE
   SYNTAX      INTEGER
               {
               unchanged (255),
               clear (0),
               set (1)
               }
   MAX-ACCESS  read-write
   STATUS      current
   DESCRIPTION
      "Path: swPort.editConf.vlan.inboundBandwidth.action.cirAction.ip.deFlag

       Possibilities:
               unchanged   (255)
               clear   (0)
               set   (1)"
   ::= {er1646v2EthPortSwIXt2VlanEntry 133344768}

er1646v2EthPortSwIXt2VlanInbBwActEirActNone OBJECT-TYPE
   SYNTAX      OCTET STRING
   MAX-ACCESS  read-write
   STATUS      current
   DESCRIPTION
      "Path: swPort.editConf.vlan.inboundBandwidth.action.eirAction.none"
   ::= {er1646v2EthPortSwIXt2VlanEntry 133439488}

er1646v2EthPortSwIXt2VlanInbBwActEirActEthCos1 OBJECT-TYPE
   SYNTAX      INTEGER
               {
               unchanged (256)
               }
   MAX-ACCESS  read-write
   STATUS      current
   DESCRIPTION
      "Path: swPort.editConf.vlan.inboundBandwidth.action.eirAction.ethernet.cosDepth1

       Possibilities:
               unchanged   (256)"
   ::= {er1646v2EthPortSwIXt2VlanEntry 133447936}

er1646v2EthPortSwIXt2VlanInbBwActEirActEthDei1 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth1

       Possibilities:
               unchanged   (255)
               clear   (0)
               set   (1)"
   ::= {er1646v2EthPortSwIXt2VlanEntry 133453056}

er1646v2EthPortSwIXt2VlanInbBwActEirActEthCos2 OBJECT-TYPE
   SYNTAX      INTEGER
               {
               unchanged (256)
               }
   MAX-ACCESS  read-write
   STATUS      current
   DESCRIPTION
      "Path: swPort.editConf.vlan.inboundBandwidth.action.eirAction.ethernet.cosDepth2

       Possibilities:
               unchanged   (256)"
   ::= {er1646v2EthPortSwIXt2VlanEntry 133448192}

er1646v2EthPortSwIXt2VlanInbBwActEirActEthDei2 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth2

       Possibilities:
               unchanged   (255)
               clear   (0)
               set   (1)"
   ::= {er1646v2EthPortSwIXt2VlanEntry 133453312}

er1646v2EthPortSwIXt2VlanInbBwActEirActEthCos3 OBJECT-TYPE
   SYNTAX      INTEGER
               {
               unchanged (256)
               }
   MAX-ACCESS  read-write
   STATUS      current
   DESCRIPTION
      "Path: swPort.editConf.vlan.inboundBandwidth.action.eirAction.ethernet.cosDepth3

       Possibilities:
               unchanged   (256)"
   ::= {er1646v2EthPortSwIXt2VlanEntry 133448448}

er1646v2EthPortSwIXt2VlanInbBwActEirActEthDei3 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth3

       Possibilities:
               unchanged   (255)
               clear   (0)
               set   (1)"
   ::= {er1646v2EthPortSwIXt2VlanEntry 133453568}

er1646v2EthPortSwIXt2VlanInbBwActEirActEthCos4 OBJECT-TYPE
   SYNTAX      INTEGER
               {
               unchanged (256)
               }
   MAX-ACCESS  read-write
   STATUS      current
   DESCRIPTION
      "Path: swPort.editConf.vlan.inboundBandwidth.action.eirAction.ethernet.cosDepth4

       Possibilities:
               unchanged   (256)"
   ::= {er1646v2EthPortSwIXt2VlanEntry 133448704}

er1646v2EthPortSwIXt2VlanInbBwActEirActEthDei4 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth4

       Possibilities:
               unchanged   (255)
               clear   (0)
               set   (1)"
   ::= {er1646v2EthPortSwIXt2VlanEntry 133453824}

er1646v2EthPortSwIXt2VlanInbBwActEirActEthCos5 OBJECT-TYPE
   SYNTAX      INTEGER
               {
               unchanged (256)
               }
   MAX-ACCESS  read-write
   STATUS      current
   DESCRIPTION
      "Path: swPort.editConf.vlan.inboundBandwidth.action.eirAction.ethernet.cosDepth5

       Possibilities:
               unchanged   (256)"
   ::= {er1646v2EthPortSwIXt2VlanEntry 133448960}

er1646v2EthPortSwIXt2VlanInbBwActEirActEthDei5 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth5

       Possibilities:
               unchanged   (255)
               clear   (0)
               set   (1)"
   ::= {er1646v2EthPortSwIXt2VlanEntry 133454080}

er1646v2EthPortSwIXt2VlanInbBwActEirActEthCos6 OBJECT-TYPE
   SYNTAX      INTEGER
               {
               unchanged (256)
               }
   MAX-ACCESS  read-write
   STATUS      current
   DESCRIPTION
      "Path: swPort.editConf.vlan.inboundBandwidth.action.eirAction.ethernet.cosDepth6

       Possibilities:
               unchanged   (256)"
   ::= {er1646v2EthPortSwIXt2VlanEntry 133449216}

er1646v2EthPortSwIXt2VlanInbBwActEirActEthDei6 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth6

       Possibilities:
               unchanged   (255)
               clear   (0)
               set   (1)"
   ::= {er1646v2EthPortSwIXt2VlanEntry 133454336}

er1646v2EthPortSwIXt2VlanInbBwActEirActEthCos7 OBJECT-TYPE
   SYNTAX      INTEGER
               {
               unchanged (256)
               }
   MAX-ACCESS  read-write
   STATUS      current
   DESCRIPTION
      "Path: swPort.editConf.vlan.inboundBandwidth.action.eirAction.ethernet.cosDepth7

       Possibilities:
               unchanged   (256)"
   ::= {er1646v2EthPortSwIXt2VlanEntry 133449472}

er1646v2EthPortSwIXt2VlanInbBwActEirActEthDei7 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth7

       Possibilities:
               unchanged   (255)
               clear   (0)
               set   (1)"
   ::= {er1646v2EthPortSwIXt2VlanEntry 133454592}

er1646v2EthPortSwIXt2VlanInbBwActEirActEthCos8 OBJECT-TYPE
   SYNTAX      INTEGER
               {
               unchanged (256)
               }
   MAX-ACCESS  read-write
   STATUS      current
   DESCRIPTION
      "Path: swPort.editConf.vlan.inboundBandwidth.action.eirAction.ethernet.cosDepth8

       Possibilities:
               unchanged   (256)"
   ::= {er1646v2EthPortSwIXt2VlanEntry 133449728}

er1646v2EthPortSwIXt2VlanInbBwActEirActEthDei8 OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deiDepth8

       Possibilities:
               unchanged   (255)
               clear   (0)
               set   (1)"
   ::= {er1646v2EthPortSwIXt2VlanEntry 133454848}

er1646v2EthPortSwIXt2VlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 133449984}

er1646v2EthPortSwIXt2VlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 133450240}

er1646v2EthPortSwIXt2VlanInbBwActEirActEthDrpLev OBJECT-TYPE
   SYNTAX      INTEGER
               {
               unchanged (0)
               }
   MAX-ACCESS  read-write
   STATUS      current
   DESCRIPTION
      "Path: swPort.editConf.vlan.inboundBandwidth.action.eirAction.ethernet.dropLevel

       Possibilities:
               unchanged   (0)"
   ::= {er1646v2EthPortSwIXt2VlanEntry 133450496}

er1646v2EthPortSwIXt2VlanInbBwActEirActEthDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ethernet.deFlag

       Possibilities:
               unchanged   (255)
               clear   (0)
               set   (1)"
   ::= {er1646v2EthPortSwIXt2VlanEntry 133451264}

er1646v2EthPortSwIXt2VlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 133474560}

er1646v2EthPortSwIXt2VlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 133474816}

er1646v2EthPortSwIXt2VlanInbBwActEirActIpDrpLev OBJECT-TYPE
   SYNTAX      INTEGER
               {
               unchanged (0)
               }
   MAX-ACCESS  read-write
   STATUS      current
   DESCRIPTION
      "Path: swPort.editConf.vlan.inboundBandwidth.action.eirAction.ip.dropLevel

       Possibilities:
               unchanged   (0)"
   ::= {er1646v2EthPortSwIXt2VlanEntry 133475072}

er1646v2EthPortSwIXt2VlanInbBwActEirActIpDeFlag OBJECT-TYPE
   SYNTAX      INTEGER
               {
               unchanged (255),
               clear (0),
               set (1)
               }
   MAX-ACCESS  read-write
   STATUS      current
   DESCRIPTION
      "Path: swPort.editConf.vlan.inboundBandwidth.action.eirAction.ip.deFlag

       Possibilities:
               unchanged   (255)
               clear   (0)
               set   (1)"
   ::= {er1646v2EthPortSwIXt2VlanEntry 133475840}

er1646v2EthPortSwIXt2VlanInbBwActViolActNone OBJECT-TYPE
   SYNTAX      OCTET STRING
   MAX-ACCESS  read-write
   STATUS      current
   DESCRIPTION
      "Path: swPort.editConf.vlan.inboundBandwidth.action.violateAction.none"
   ::= {er1646v2EthPortSwIXt2VlanEntry 133570560}

er1646v2EthPortSwIXt2VlanInbBwActViolActDrop OBJECT-TYPE
   SYNTAX      OCTET STRING
   MAX-ACCESS  read-write
   STATUS      current
   DESCRIPTION
      "Path: swPort.editConf.vlan.inboundBandwidth.action.violateAction.drop"
   ::= {er1646v2EthPortSwIXt2VlanEntry 133586944}

er1646v2EthPortSwIXt2VlanInbBwActViolActEthCos1 OBJECT-TYPE
   SYNTAX      INTEGER
               {
               unchanged (256)
               }
   MAX-ACCESS  read-write
   STATUS      current
   DESCRIPTION
      "Path: swPort.editConf.vlan.inboundBandwidth.action.violateAction.ethernet.cosDepth1

       Possibilities:
               unchanged   (256)"
   ::= {er1646v2EthPortSwIXt2VlanEntry 133579008}

er1646v2EthPortSwIXt2VlanInbBwActViolActEthDei1 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth1

       Possibilities:
               unchanged   (255)
               clear   (0)
               set   (1)"
   ::= {er1646v2EthPortSwIXt2VlanEntry 133584128}

er1646v2EthPortSwIXt2VlanInbBwActViolActEthCos2 OBJECT-TYPE
   SYNTAX      INTEGER
               {
               unchanged (256)
               }
   MAX-ACCESS  read-write
   STATUS      current
   DESCRIPTION
      "Path: swPort.editConf.vlan.inboundBandwidth.action.violateAction.ethernet.cosDepth2

       Possibilities:
               unchanged   (256)"
   ::= {er1646v2EthPortSwIXt2VlanEntry 133579264}

er1646v2EthPortSwIXt2VlanInbBwActViolActEthDei2 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth2

       Possibilities:
               unchanged   (255)
               clear   (0)
               set   (1)"
   ::= {er1646v2EthPortSwIXt2VlanEntry 133584384}

er1646v2EthPortSwIXt2VlanInbBwActViolActEthCos3 OBJECT-TYPE
   SYNTAX      INTEGER
               {
               unchanged (256)
               }
   MAX-ACCESS  read-write
   STATUS      current
   DESCRIPTION
      "Path: swPort.editConf.vlan.inboundBandwidth.action.violateAction.ethernet.cosDepth3

       Possibilities:
               unchanged   (256)"
   ::= {er1646v2EthPortSwIXt2VlanEntry 133579520}

er1646v2EthPortSwIXt2VlanInbBwActViolActEthDei3 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth3

       Possibilities:
               unchanged   (255)
               clear   (0)
               set   (1)"
   ::= {er1646v2EthPortSwIXt2VlanEntry 133584640}

er1646v2EthPortSwIXt2VlanInbBwActViolActEthCos4 OBJECT-TYPE
   SYNTAX      INTEGER
               {
               unchanged (256)
               }
   MAX-ACCESS  read-write
   STATUS      current
   DESCRIPTION
      "Path: swPort.editConf.vlan.inboundBandwidth.action.violateAction.ethernet.cosDepth4

       Possibilities:
               unchanged   (256)"
   ::= {er1646v2EthPortSwIXt2VlanEntry 133579776}

er1646v2EthPortSwIXt2VlanInbBwActViolActEthDei4 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth4

       Possibilities:
               unchanged   (255)
               clear   (0)
               set   (1)"
   ::= {er1646v2EthPortSwIXt2VlanEntry 133584896}

er1646v2EthPortSwIXt2VlanInbBwActViolActEthCos5 OBJECT-TYPE
   SYNTAX      INTEGER
               {
               unchanged (256)
               }
   MAX-ACCESS  read-write
   STATUS      current
   DESCRIPTION
      "Path: swPort.editConf.vlan.inboundBandwidth.action.violateAction.ethernet.cosDepth5

       Possibilities:
               unchanged   (256)"
   ::= {er1646v2EthPortSwIXt2VlanEntry 133580032}

er1646v2EthPortSwIXt2VlanInbBwActViolActEthDei5 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth5

       Possibilities:
               unchanged   (255)
               clear   (0)
               set   (1)"
   ::= {er1646v2EthPortSwIXt2VlanEntry 133585152}

er1646v2EthPortSwIXt2VlanInbBwActViolActEthCos6 OBJECT-TYPE
   SYNTAX      INTEGER
               {
               unchanged (256)
               }
   MAX-ACCESS  read-write
   STATUS      current
   DESCRIPTION
      "Path: swPort.editConf.vlan.inboundBandwidth.action.violateAction.ethernet.cosDepth6

       Possibilities:
               unchanged   (256)"
   ::= {er1646v2EthPortSwIXt2VlanEntry 133580288}

er1646v2EthPortSwIXt2VlanInbBwActViolActEthDei6 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth6

       Possibilities:
               unchanged   (255)
               clear   (0)
               set   (1)"
   ::= {er1646v2EthPortSwIXt2VlanEntry 133585408}

er1646v2EthPortSwIXt2VlanInbBwActViolActEthCos7 OBJECT-TYPE
   SYNTAX      INTEGER
               {
               unchanged (256)
               }
   MAX-ACCESS  read-write
   STATUS      current
   DESCRIPTION
      "Path: swPort.editConf.vlan.inboundBandwidth.action.violateAction.ethernet.cosDepth7

       Possibilities:
               unchanged   (256)"
   ::= {er1646v2EthPortSwIXt2VlanEntry 133580544}

er1646v2EthPortSwIXt2VlanInbBwActViolActEthDei7 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth7

       Possibilities:
               unchanged   (255)
               clear   (0)
               set   (1)"
   ::= {er1646v2EthPortSwIXt2VlanEntry 133585664}

er1646v2EthPortSwIXt2VlanInbBwActViolActEthCos8 OBJECT-TYPE
   SYNTAX      INTEGER
               {
               unchanged (256)
               }
   MAX-ACCESS  read-write
   STATUS      current
   DESCRIPTION
      "Path: swPort.editConf.vlan.inboundBandwidth.action.violateAction.ethernet.cosDepth8

       Possibilities:
               unchanged   (256)"
   ::= {er1646v2EthPortSwIXt2VlanEntry 133580800}

er1646v2EthPortSwIXt2VlanInbBwActViolActEthDei8 OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deiDepth8

       Possibilities:
               unchanged   (255)
               clear   (0)
               set   (1)"
   ::= {er1646v2EthPortSwIXt2VlanEntry 133585920}

er1646v2EthPortSwIXt2VlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 133581056}

er1646v2EthPortSwIXt2VlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 133581312}

er1646v2EthPortSwIXt2VlanInbBwActViolActEthDrpLev OBJECT-TYPE
   SYNTAX      INTEGER
               {
               unchanged (0)
               }
   MAX-ACCESS  read-write
   STATUS      current
   DESCRIPTION
      "Path: swPort.editConf.vlan.inboundBandwidth.action.violateAction.ethernet.dropLevel

       Possibilities:
               unchanged   (0)"
   ::= {er1646v2EthPortSwIXt2VlanEntry 133581568}

er1646v2EthPortSwIXt2VlanInbBwActViolActEthDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ethernet.deFlag

       Possibilities:
               unchanged   (255)
               clear   (0)
               set   (1)"
   ::= {er1646v2EthPortSwIXt2VlanEntry 133582336}

er1646v2EthPortSwIXt2VlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanEntry 133605632}

er1646v2EthPortSwIXt2VlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanEntry 133605888}

er1646v2EthPortSwIXt2VlanInbBwActViolActIpDrpLev OBJECT-TYPE
   SYNTAX      INTEGER
               {
               unchanged (0)
               }
   MAX-ACCESS  read-write
   STATUS      current
   DESCRIPTION
      "Path: swPort.editConf.vlan.inboundBandwidth.action.violateAction.ip.dropLevel

       Possibilities:
               unchanged   (0)"
   ::= {er1646v2EthPortSwIXt2VlanEntry 133606144}

er1646v2EthPortSwIXt2VlanInbBwActViolActIpDeFlag OBJECT-TYPE
   SYNTAX      INTEGER
               {
               unchanged (255),
               clear (0),
               set (1)
               }
   MAX-ACCESS  read-write
   STATUS      current
   DESCRIPTION
      "Path: swPort.editConf.vlan.inboundBandwidth.action.violateAction.ip.deFlag

       Possibilities:
               unchanged   (255)
               clear   (0)
               set   (1)"
   ::= {er1646v2EthPortSwIXt2VlanEntry 133606912}

er1646v2EthPortSwIXt2VlanPppoE OBJECT-TYPE
   SYNTAX      INTEGER
               {
               disabled (0),
               enabled (1)
               }
   MAX-ACCESS  read-write
   STATUS      current
   DESCRIPTION
      "Path: swPort.editConf.vlan.pppoE

       Possibilities:
               disabled   (0)
               enabled   (1)"
   ::= {er1646v2EthPortSwIXt2VlanEntry 838860800}

er1646v2EthPortSwIXt2VlanPppLnkMOperation OBJECT-TYPE
   SYNTAX      INTEGER
               {
               disabled (0),
               enabled (1)
               }
   MAX-ACCESS  read-write
   STATUS      current
   DESCRIPTION
      "Path: swPort.editConf.vlan.ppp.linkMonitoring.operation

       Possibilities:
               disabled   (0)
               enabled   (1)"
   ::= {er1646v2EthPortSwIXt2VlanEntry 251724032}

er1646v2EthPortSwIXt2VlanPppLnkMInterval OBJECT-TYPE
   SYNTAX      TimeTicks
   MAX-ACCESS  read-write
   STATUS      current
   DESCRIPTION
      "Path: swPort.editConf.vlan.ppp.linkMonitoring.interval

       Time in centi-second."
   ::= {er1646v2EthPortSwIXt2VlanEntry 251724288}

er1646v2EthPortSwIXt2VlanPppLnkMRepTimeOut OBJECT-TYPE
   SYNTAX      TimeTicks
   MAX-ACCESS  read-write
   STATUS      current
   DESCRIPTION
      "Path: swPort.editConf.vlan.ppp.linkMonitoring.replyTimeOut

       Time in centi-second."
   ::= {er1646v2EthPortSwIXt2VlanEntry 251724544}

er1646v2EthPortSwIXt2VlanPppLnkMFailsPrmt OBJECT-TYPE
   SYNTAX      Integer32
   MAX-ACCESS  read-write
   STATUS      current
   DESCRIPTION
      "Path: swPort.editConf.vlan.ppp.linkMonitoring.failsPermitted"
   ::= {er1646v2EthPortSwIXt2VlanEntry 251724800}

er1646v2EthPortSwIXt2VlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.vlan.ppp.authentication

       Possibilities:
               disabled   (0)
               chap   (1)
               pap   (2)
               chapOrPap   (3)
               msChap   (4)
               msChapV2   (5)"
   ::= {er1646v2EthPortSwIXt2VlanEntry 251789312}

er1646v2EthPortSwIXt2VlanPppAuthenPeriod OBJECT-TYPE
   SYNTAX      TimeTicks
   MAX-ACCESS  read-write
   STATUS      current
   DESCRIPTION
      "Path: swPort.editConf.vlan.ppp.authenPeriod

       Time in centi-second."
   ::= {er1646v2EthPortSwIXt2VlanEntry 251854848}

er1646v2EthPortSwIXt2VlanPppSessionName OBJECT-TYPE
   SYNTAX      DisplayString
   MAX-ACCESS  read-write
   STATUS      current
   DESCRIPTION
      "Path: swPort.editConf.vlan.ppp.sessionName"
   ::= {er1646v2EthPortSwIXt2VlanEntry 251985920}

er1646v2EthPortSwIXt2VlanPppSessionSecret OBJECT-TYPE
   SYNTAX      DisplayString
   MAX-ACCESS  read-write
   STATUS      current
   DESCRIPTION
      "Path: swPort.editConf.vlan.ppp.sessionSecret"
   ::= {er1646v2EthPortSwIXt2VlanEntry 252051456}

er1646v2EthPortSwIXt2VlanPppEncModeSessionSecret OBJECT-TYPE
   SYNTAX      INTEGER
               {
               none (1),
               encrypt (2),
               encType1 (3),
               invalid (128)
               }
   MAX-ACCESS  read-write
   STATUS      current
   DESCRIPTION
      "Path: swPort.editConf.vlan.ppp.encModeSessionSecret

       Possibilities:
               none   (1)
               encrypt   (2)
               encType1   (3)
               invalid   (128)"
   ::= {er1646v2EthPortSwIXt2VlanEntry 252182528}

er1646v2EthPortSwIXt2VlanPppEncSessionSecret OBJECT-TYPE
   SYNTAX      DisplayString
   MAX-ACCESS  read-write
   STATUS      current
   DESCRIPTION
      "Path: swPort.editConf.vlan.ppp.encSessionSecret"
   ::= {er1646v2EthPortSwIXt2VlanEntry 252248064}

er1646v2EthPortSwIXt2VlanPppServiceName OBJECT-TYPE
   SYNTAX      DisplayString
   MAX-ACCESS  read-write
   STATUS      current
   DESCRIPTION
      "Path: swPort.editConf.vlan.ppp.serviceName"
   ::= {er1646v2EthPortSwIXt2VlanEntry 252116992}

er1646v2EthPortSwIXt2VlanPbbMode OBJECT-TYPE
   SYNTAX      INTEGER
               {
               disabled (0),
               static (1),
               dynamicPtp (2),
               dynamicPtmp (3)
               }
   MAX-ACCESS  read-write
   STATUS      current
   DESCRIPTION
      "Path: swPort.editConf.vlan.pbb.mode

       Possibilities:
               disabled   (0)
               static   (1)
               dynamicPtp   (2)
               dynamicPtmp   (3)"
   ::= {er1646v2EthPortSwIXt2VlanEntry 1174667264}

er1646v2EthPortSwIXt2VlanPbbTxCos OBJECT-TYPE
   SYNTAX      Integer32
   MAX-ACCESS  read-write
   STATUS      current
   DESCRIPTION
      "Path: swPort.editConf.vlan.pbb.txCos"
   ::= {er1646v2EthPortSwIXt2VlanEntry 1175191552}

er1646v2EthPortSwIXt2VlanPbbIsid OBJECT-TYPE
   SYNTAX      Integer32
   MAX-ACCESS  read-write
   STATUS      current
   DESCRIPTION
      "Path: swPort.editConf.vlan.pbb.isid"
   ::= {er1646v2EthPortSwIXt2VlanEntry 1175453696}

er1646v2EthPortSwIXt2VlanPbbDestMac OBJECT-TYPE
   SYNTAX      OCTET STRING
   MAX-ACCESS  read-write
   STATUS      current
   DESCRIPTION
      "Path: swPort.editConf.vlan.pbb.destMac

       MAC address."
   ::= {er1646v2EthPortSwIXt2VlanEntry 1175715840}

er1646v2EthPortSwIXt2VlanPbbCustomGroupMac OBJECT-TYPE
   SYNTAX      OCTET STRING
   MAX-ACCESS  read-write
   STATUS      current
   DESCRIPTION
      "Path: swPort.editConf.vlan.pbb.customGroupMac

       MAC address."
   ::= {er1646v2EthPortSwIXt2VlanEntry 1175977984}

er1646v2EthPortSwIXt2VlanIpSaddr OBJECT-TYPE
   SYNTAX      SEQUENCE OF Er1646v2EthPortSwIXt2VlanIpSaddrEntry
   MAX-ACCESS  not-accessible
   STATUS      current
   DESCRIPTION
      ""
   ::= {er1646v2EthPortSwIXt2Vlan 51838976}

er1646v2EthPortSwIXt2VlanIpSaddrEntry OBJECT-TYPE
   SYNTAX      Er1646v2EthPortSwIXt2VlanIpSaddrEntry
   MAX-ACCESS  not-accessible
   STATUS      current
   DESCRIPTION
      ""
   INDEX      { er1646v2EthPortSwIXt2VlanIpSaddrGlobalIx,
                er1646v2EthPortSwIXt2VlanTableIx,
                er1646v2EthPortSwIXt2VlanIpSaddrTableIx }
   ::= {er1646v2EthPortSwIXt2VlanIpSaddr 1}

Er1646v2EthPortSwIXt2VlanIpSaddrEntry ::=
   SEQUENCE
      {
      er1646v2EthPortSwIXt2VlanIpSaddrActions
         VariableLengthTableActions,
      er1646v2EthPortSwIXt2VlanIpSaddrGlobalIx
         GlobalIndex,
      er1646v2EthPortSwIXt2VlanIpSaddrTableIx
         TableIndex,
      er1646v2EthPortSwIXt2VlanIpSaddrAddress
         IpAddress,
      er1646v2EthPortSwIXt2VlanIpSaddrNetMask
         IpAddress
      }

er1646v2EthPortSwIXt2VlanIpSaddrActions OBJECT-TYPE
   SYNTAX      VariableLengthTableActions
   MAX-ACCESS  read-write
   STATUS      current
   DESCRIPTION
      "By way of this field, some manipulations
       on this table may be performed."
   ::= {er1646v2EthPortSwIXt2VlanIpSaddrEntry 2}

er1646v2EthPortSwIXt2VlanIpSaddrGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpSaddrEntry 10}

er1646v2EthPortSwIXt2VlanIpSaddrTableIx OBJECT-TYPE
   SYNTAX      TableIndex
   MAX-ACCESS  not-accessible
   STATUS      current
   DESCRIPTION
      ""
   ::= {er1646v2EthPortSwIXt2VlanIpSaddrEntry 11}

er1646v2EthPortSwIXt2VlanIpSaddrAddress OBJECT-TYPE
   SYNTAX      IpAddress
   MAX-ACCESS  read-write
   STATUS      current
   DESCRIPTION
      "Path: swPort.editConf.vlan.ip.secondaryIp.address"
   ::= {er1646v2EthPortSwIXt2VlanIpSaddrEntry 2030043136}

er1646v2EthPortSwIXt2VlanIpSaddrNetMask OBJECT-TYPE
   SYNTAX      IpAddress
   MAX-ACCESS  read-write
   STATUS      current
   DESCRIPTION
      "Path: swPort.editConf.vlan.ip.secondaryIp.netMask"
   ::= {er1646v2EthPortSwIXt2VlanIpSaddrEntry 2063597568}

er1646v2EthPortSwIXt2VlanIpH OBJECT-TYPE
   SYNTAX      SEQUENCE OF Er1646v2EthPortSwIXt2VlanIpHEntry
   MAX-ACCESS  not-accessible
   STATUS      current
   DESCRIPTION
      ""
   ::= {er1646v2EthPortSwIXt2Vlan 51314688}

er1646v2EthPortSwIXt2VlanIpHEntry OBJECT-TYPE
   SYNTAX      Er1646v2EthPortSwIXt2VlanIpHEntry
   MAX-ACCESS  not-accessible
   STATUS      current
   DESCRIPTION
      ""
   INDEX      { er1646v2EthPortSwIXt2VlanIpHGlobalIx,
                er1646v2EthPortSwIXt2VlanTableIx,
                er1646v2EthPortSwIXt2VlanIpHTableIx }
   ::= {er1646v2EthPortSwIXt2VlanIpH 1}

Er1646v2EthPortSwIXt2VlanIpHEntry ::=
   SEQUENCE
      {
      er1646v2EthPortSwIXt2VlanIpHActions
         VariableLengthTableActions,
      er1646v2EthPortSwIXt2VlanIpHGlobalIx
         GlobalIndex,
      er1646v2EthPortSwIXt2VlanIpHTableIx
         TableIndex,
      er1646v2EthPortSwIXt2VlanIpHAddress
         IpAddress,
      er1646v2EthPortSwIXt2VlanIpHDhcpRelayOptionSubscriberId
         DisplayString
      }

er1646v2EthPortSwIXt2VlanIpHActions OBJECT-TYPE
   SYNTAX      VariableLengthTableActions
   MAX-ACCESS  read-write
   STATUS      current
   DESCRIPTION
      "By way of this field, some manipulations
       on this table may be performed."
   ::= {er1646v2EthPortSwIXt2VlanIpHEntry 2}

er1646v2EthPortSwIXt2VlanIpHGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpHEntry 10}

er1646v2EthPortSwIXt2VlanIpHTableIx OBJECT-TYPE
   SYNTAX      TableIndex
   MAX-ACCESS  not-accessible
   STATUS      current
   DESCRIPTION
      ""
   ::= {er1646v2EthPortSwIXt2VlanIpHEntry 11}

er1646v2EthPortSwIXt2VlanIpHAddress OBJECT-TYPE
   SYNTAX      IpAddress
   MAX-ACCESS  read-write
   STATUS      current
   DESCRIPTION
      "Path: swPort.editConf.vlan.ip.helpers.address"
   ::= {er1646v2EthPortSwIXt2VlanIpHEntry 16777216}

er1646v2EthPortSwIXt2VlanIpHDhcpRelayOptionSubscriberId OBJECT-TYPE
   SYNTAX      DisplayString
   MAX-ACCESS  read-write
   STATUS      current
   DESCRIPTION
      "Path: swPort.editConf.vlan.ip.helpers.dhcpRelayOption.subscriberId"
   ::= {er1646v2EthPortSwIXt2VlanIpHEntry 33947648}

er1646v2EthPortSwIXt2VlanIpV6Addresses OBJECT-TYPE
   SYNTAX      SEQUENCE OF Er1646v2EthPortSwIXt2VlanIpV6AddressesEntry
   MAX-ACCESS  not-accessible
   STATUS      current
   DESCRIPTION
      ""
   ::= {er1646v2EthPortSwIXt2Vlan 704839680}

er1646v2EthPortSwIXt2VlanIpV6AddressesEntry OBJECT-TYPE
   SYNTAX      Er1646v2EthPortSwIXt2VlanIpV6AddressesEntry
   MAX-ACCESS  not-accessible
   STATUS      current
   DESCRIPTION
      ""
   INDEX      { er1646v2EthPortSwIXt2VlanIpV6AddressesGlobalIx,
                er1646v2EthPortSwIXt2VlanTableIx,
                er1646v2EthPortSwIXt2VlanIpV6AddressesTableIx }
   ::= {er1646v2EthPortSwIXt2VlanIpV6Addresses 1}

Er1646v2EthPortSwIXt2VlanIpV6AddressesEntry ::=
   SEQUENCE
      {
      er1646v2EthPortSwIXt2VlanIpV6AddressesActions
         VariableLengthTableActions,
      er1646v2EthPortSwIXt2VlanIpV6AddressesGlobalIx
         GlobalIndex,
      er1646v2EthPortSwIXt2VlanIpV6AddressesTableIx
         TableIndex,
      er1646v2EthPortSwIXt2VlanIpV6AddressesType
         INTEGER,
      er1646v2EthPortSwIXt2VlanIpV6AddressesAddress
         Ipv6Address,
      er1646v2EthPortSwIXt2VlanIpV6AddressesPrefixLength
         Integer32,
      er1646v2EthPortSwIXt2VlanIpV6AddressesGeneralPrefix
         DisplayString,
      er1646v2EthPortSwIXt2VlanIpV6AddressesRaSend
         INTEGER,
      er1646v2EthPortSwIXt2VlanIpV6AddressesRaOnLinkFlag
         INTEGER,
      er1646v2EthPortSwIXt2VlanIpV6AddressesRaAutoFlag
         INTEGER,
      er1646v2EthPortSwIXt2VlanIpV6AddressesRaValidLifeTime
         TimeTicks,
      er1646v2EthPortSwIXt2VlanIpV6AddressesRaValidLTMode
         INTEGER,
      er1646v2EthPortSwIXt2VlanIpV6AddressesRaPrefLifeTime
         TimeTicks,
      er1646v2EthPortSwIXt2VlanIpV6AddressesRaPrefLTMode
         INTEGER
      }

er1646v2EthPortSwIXt2VlanIpV6AddressesActions OBJECT-TYPE
   SYNTAX      VariableLengthTableActions
   MAX-ACCESS  read-write
   STATUS      current
   DESCRIPTION
      "By way of this field, some manipulations
       on this table may be performed."
   ::= {er1646v2EthPortSwIXt2VlanIpV6AddressesEntry 2}

er1646v2EthPortSwIXt2VlanIpV6AddressesGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpV6AddressesEntry 10}

er1646v2EthPortSwIXt2VlanIpV6AddressesTableIx OBJECT-TYPE
   SYNTAX      TableIndex
   MAX-ACCESS  not-accessible
   STATUS      current
   DESCRIPTION
      ""
   ::= {er1646v2EthPortSwIXt2VlanIpV6AddressesEntry 11}

er1646v2EthPortSwIXt2VlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.vlan.ipV6.addresses.type

       Possibilities:
               unicast   (0)
               eui64   (1)
               anycast   (2)
               linkLocal   (3)
               generalPrefix   (4)"
   ::= {er1646v2EthPortSwIXt2VlanIpV6AddressesEntry 50331648}

er1646v2EthPortSwIXt2VlanIpV6AddressesAddress OBJECT-TYPE
   SYNTAX      Ipv6Address
   MAX-ACCESS  read-write
   STATUS      current
   DESCRIPTION
      "Path: swPort.editConf.vlan.ipV6.addresses.address

       ipv6 address"
   ::= {er1646v2EthPortSwIXt2VlanIpV6AddressesEntry 16777216}

er1646v2EthPortSwIXt2VlanIpV6AddressesPrefixLength OBJECT-TYPE
   SYNTAX      Integer32
   MAX-ACCESS  read-write
   STATUS      current
   DESCRIPTION
      "Path: swPort.editConf.vlan.ipV6.addresses.prefixLength"
   ::= {er1646v2EthPortSwIXt2VlanIpV6AddressesEntry 33554432}

er1646v2EthPortSwIXt2VlanIpV6AddressesGeneralPrefix OBJECT-TYPE
   SYNTAX      DisplayString
   MAX-ACCESS  read-write
   STATUS      current
   DESCRIPTION
      "Path: swPort.editConf.vlan.ipV6.addresses.generalPrefix"
   ::= {er1646v2EthPortSwIXt2VlanIpV6AddressesEntry 83886080}

er1646v2EthPortSwIXt2VlanIpV6AddressesRaSend OBJECT-TYPE
   SYNTAX      INTEGER
               {
               disabled (0),
               enabled (1)
               }
   MAX-ACCESS  read-write
   STATUS      current
   DESCRIPTION
      "Path: swPort.editConf.vlan.ipV6.addresses.ra.send

       Possibilities:
               disabled   (0)
               enabled   (1)"
   ::= {er1646v2EthPortSwIXt2VlanIpV6AddressesEntry 67174400}

er1646v2EthPortSwIXt2VlanIpV6AddressesRaOnLinkFlag OBJECT-TYPE
   SYNTAX      INTEGER
               {
               disabled (0),
               enabled (1)
               }
   MAX-ACCESS  read-write
   STATUS      current
   DESCRIPTION
      "Path: swPort.editConf.vlan.ipV6.addresses.ra.onLinkFlag

       Possibilities:
               disabled   (0)
               enabled   (1)"
   ::= {er1646v2EthPortSwIXt2VlanIpV6AddressesEntry 67371008}

er1646v2EthPortSwIXt2VlanIpV6AddressesRaAutoFlag OBJECT-TYPE
   SYNTAX      INTEGER
               {
               disabled (0),
               enabled (1)
               }
   MAX-ACCESS  read-write
   STATUS      current
   DESCRIPTION
      "Path: swPort.editConf.vlan.ipV6.addresses.ra.autonomousFlag

       Possibilities:
               disabled   (0)
               enabled   (1)"
   ::= {er1646v2EthPortSwIXt2VlanIpV6AddressesEntry 67567616}

er1646v2EthPortSwIXt2VlanIpV6AddressesRaValidLifeTime OBJECT-TYPE
   SYNTAX      TimeTicks
   MAX-ACCESS  read-write
   STATUS      current
   DESCRIPTION
      "Path: swPort.editConf.vlan.ipV6.addresses.ra.validLifeTime

       Time in centi-second."
   ::= {er1646v2EthPortSwIXt2VlanIpV6AddressesEntry 67239936}

er1646v2EthPortSwIXt2VlanIpV6AddressesRaValidLTMode OBJECT-TYPE
   SYNTAX      INTEGER
               {
               fixed (0),
               infinite (2)
               }
   MAX-ACCESS  read-write
   STATUS      current
   DESCRIPTION
      "Path: swPort.editConf.vlan.ipV6.addresses.ra.validLifeTimeMode

       Possibilities:
               fixed   (0)
               infinite   (2)"
   ::= {er1646v2EthPortSwIXt2VlanIpV6AddressesEntry 67305472}

er1646v2EthPortSwIXt2VlanIpV6AddressesRaPrefLifeTime OBJECT-TYPE
   SYNTAX      TimeTicks
   MAX-ACCESS  read-write
   STATUS      current
   DESCRIPTION
      "Path: swPort.editConf.vlan.ipV6.addresses.ra.prefLifeTime

       Time in centi-second."
   ::= {er1646v2EthPortSwIXt2VlanIpV6AddressesEntry 67436544}

er1646v2EthPortSwIXt2VlanIpV6AddressesRaPrefLTMode OBJECT-TYPE
   SYNTAX      INTEGER
               {
               fixed (0),
               infinite (2)
               }
   MAX-ACCESS  read-write
   STATUS      current
   DESCRIPTION
      "Path: swPort.editConf.vlan.ipV6.addresses.ra.prefLifeTimeMode

       Possibilities:
               fixed   (0)
               infinite   (2)"
   ::= {er1646v2EthPortSwIXt2VlanIpV6AddressesEntry 67502080}

er1646v2EthPortSwIXt2VlanIpV6RaDnsOptionsRdnssServers OBJECT-TYPE
   SYNTAX      SEQUENCE OF Er1646v2EthPortSwIXt2VlanIpV6RaDnsOptionsRdnssServersEntry
   MAX-ACCESS  not-accessible
   STATUS      current
   DESCRIPTION
      ""
   ::= {er1646v2EthPortSwIXt2Vlan 705039144}

er1646v2EthPortSwIXt2VlanIpV6RaDnsOptionsRdnssServersEntry OBJECT-TYPE
   SYNTAX      Er1646v2EthPortSwIXt2VlanIpV6RaDnsOptionsRdnssServersEntry
   MAX-ACCESS  not-accessible
   STATUS      current
   DESCRIPTION
      ""
   INDEX      { er1646v2EthPortSwIXt2VlanIpV6RaDnsOptionsRdnssServersGlobalIx,
                er1646v2EthPortSwIXt2VlanTableIx,
                er1646v2EthPortSwIXt2VlanIpV6RaDnsOptionsRdnssServersTableIx }
   ::= {er1646v2EthPortSwIXt2VlanIpV6RaDnsOptionsRdnssServers 1}

Er1646v2EthPortSwIXt2VlanIpV6RaDnsOptionsRdnssServersEntry ::=
   SEQUENCE
      {
      er1646v2EthPortSwIXt2VlanIpV6RaDnsOptionsRdnssServersActions
         VariableLengthTableActions,
      er1646v2EthPortSwIXt2VlanIpV6RaDnsOptionsRdnssServersGlobalIx
         GlobalIndex,
      er1646v2EthPortSwIXt2VlanIpV6RaDnsOptionsRdnssServersTableIx
         TableIndex,
      er1646v2EthPortSwIXt2VlanIpV6RaDnsOptionsRdnssServersAddress
         Ipv6Address
      }

er1646v2EthPortSwIXt2VlanIpV6RaDnsOptionsRdnssServersActions OBJECT-TYPE
   SYNTAX      VariableLengthTableActions
   MAX-ACCESS  read-write
   STATUS      current
   DESCRIPTION
      "By way of this field, some manipulations
       on this table may be performed."
   ::= {er1646v2EthPortSwIXt2VlanIpV6RaDnsOptionsRdnssServersEntry 2}

er1646v2EthPortSwIXt2VlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpV6RaDnsOptionsRdnssServersEntry 10}

er1646v2EthPortSwIXt2VlanIpV6RaDnsOptionsRdnssServersTableIx OBJECT-TYPE
   SYNTAX      TableIndex
   MAX-ACCESS  not-accessible
   STATUS      current
   DESCRIPTION
      ""
   ::= {er1646v2EthPortSwIXt2VlanIpV6RaDnsOptionsRdnssServersEntry 11}

er1646v2EthPortSwIXt2VlanIpV6RaDnsOptionsRdnssServersAddress OBJECT-TYPE
   SYNTAX      Ipv6Address
   MAX-ACCESS  read-write
   STATUS      current
   DESCRIPTION
      "Path: swPort.editConf.vlan.ipV6.ra.dnsOptions.rdnss.servers.address

       ipv6 address"
   ::= {er1646v2EthPortSwIXt2VlanIpV6RaDnsOptionsRdnssServersEntry 16777216}

er1646v2EthPortSwIXt2VlanIpV6RaDnsOptionsDnsslDomains OBJECT-TYPE
   SYNTAX      SEQUENCE OF Er1646v2EthPortSwIXt2VlanIpV6RaDnsOptionsDnsslDomainsEntry
   MAX-ACCESS  not-accessible
   STATUS      current
   DESCRIPTION
      ""
   ::= {er1646v2EthPortSwIXt2Vlan 705039176}

er1646v2EthPortSwIXt2VlanIpV6RaDnsOptionsDnsslDomainsEntry OBJECT-TYPE
   SYNTAX      Er1646v2EthPortSwIXt2VlanIpV6RaDnsOptionsDnsslDomainsEntry
   MAX-ACCESS  not-accessible
   STATUS      current
   DESCRIPTION
      ""
   INDEX      { er1646v2EthPortSwIXt2VlanIpV6RaDnsOptionsDnsslDomainsGlobalIx,
                er1646v2EthPortSwIXt2VlanTableIx,
                er1646v2EthPortSwIXt2VlanIpV6RaDnsOptionsDnsslDomainsTableIx }
   ::= {er1646v2EthPortSwIXt2VlanIpV6RaDnsOptionsDnsslDomains 1}

Er1646v2EthPortSwIXt2VlanIpV6RaDnsOptionsDnsslDomainsEntry ::=
   SEQUENCE
      {
      er1646v2EthPortSwIXt2VlanIpV6RaDnsOptionsDnsslDomainsActions
         VariableLengthTableActions,
      er1646v2EthPortSwIXt2VlanIpV6RaDnsOptionsDnsslDomainsGlobalIx
         GlobalIndex,
      er1646v2EthPortSwIXt2VlanIpV6RaDnsOptionsDnsslDomainsTableIx
         TableIndex,
      er1646v2EthPortSwIXt2VlanIpV6RaDnsOptionsDnsslDomainsName
         DisplayString
      }

er1646v2EthPortSwIXt2VlanIpV6RaDnsOptionsDnsslDomainsActions OBJECT-TYPE
   SYNTAX      VariableLengthTableActions
   MAX-ACCESS  read-write
   STATUS      current
   DESCRIPTION
      "By way of this field, some manipulations
       on this table may be performed."
   ::= {er1646v2EthPortSwIXt2VlanIpV6RaDnsOptionsDnsslDomainsEntry 2}

er1646v2EthPortSwIXt2VlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpV6RaDnsOptionsDnsslDomainsEntry 10}

er1646v2EthPortSwIXt2VlanIpV6RaDnsOptionsDnsslDomainsTableIx OBJECT-TYPE
   SYNTAX      TableIndex
   MAX-ACCESS  not-accessible
   STATUS      current
   DESCRIPTION
      ""
   ::= {er1646v2EthPortSwIXt2VlanIpV6RaDnsOptionsDnsslDomainsEntry 11}

er1646v2EthPortSwIXt2VlanIpV6RaDnsOptionsDnsslDomainsName OBJECT-TYPE
   SYNTAX      DisplayString
   MAX-ACCESS  read-write
   STATUS      current
   DESCRIPTION
      "Path: swPort.editConf.vlan.ipV6.ra.dnsOptions.dnssl.domains.name"
   ::= {er1646v2EthPortSwIXt2VlanIpV6RaDnsOptionsDnsslDomainsEntry 16777216}

er1646v2EthPortSwIXt2VlanIpV6DhcpClientUserClassOpt OBJECT-TYPE
   SYNTAX      SEQUENCE OF Er1646v2EthPortSwIXt2VlanIpV6DhcpClientUserClassOptEntry
   MAX-ACCESS  not-accessible
   STATUS      current
   DESCRIPTION
      ""
   ::= {er1646v2EthPortSwIXt2Vlan 705312768}

er1646v2EthPortSwIXt2VlanIpV6DhcpClientUserClassOptEntry OBJECT-TYPE
   SYNTAX      Er1646v2EthPortSwIXt2VlanIpV6DhcpClientUserClassOptEntry
   MAX-ACCESS  not-accessible
   STATUS      current
   DESCRIPTION
      ""
   INDEX      { er1646v2EthPortSwIXt2VlanIpV6DhcpClientUserClassOptGlobalIx,
                er1646v2EthPortSwIXt2VlanTableIx,
                er1646v2EthPortSwIXt2VlanIpV6DhcpClientUserClassOptTableIx }
   ::= {er1646v2EthPortSwIXt2VlanIpV6DhcpClientUserClassOpt 1}

Er1646v2EthPortSwIXt2VlanIpV6DhcpClientUserClassOptEntry ::=
   SEQUENCE
      {
      er1646v2EthPortSwIXt2VlanIpV6DhcpClientUserClassOptActions
         VariableLengthTableActions,
      er1646v2EthPortSwIXt2VlanIpV6DhcpClientUserClassOptGlobalIx
         GlobalIndex,
      er1646v2EthPortSwIXt2VlanIpV6DhcpClientUserClassOptTableIx
         TableIndex,
      er1646v2EthPortSwIXt2VlanIpV6DhcpClientUserClassOptValueAscii
         DisplayString,
      er1646v2EthPortSwIXt2VlanIpV6DhcpClientUserClassOptValueDecimal
         Integer32,
      er1646v2EthPortSwIXt2VlanIpV6DhcpClientUserClassOptValueHexData
         OCTET STRING
      }

er1646v2EthPortSwIXt2VlanIpV6DhcpClientUserClassOptActions OBJECT-TYPE
   SYNTAX      VariableLengthTableActions
   MAX-ACCESS  read-write
   STATUS      current
   DESCRIPTION
      "By way of this field, some manipulations
       on this table may be performed."
   ::= {er1646v2EthPortSwIXt2VlanIpV6DhcpClientUserClassOptEntry 2}

er1646v2EthPortSwIXt2VlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpV6DhcpClientUserClassOptEntry 10}

er1646v2EthPortSwIXt2VlanIpV6DhcpClientUserClassOptTableIx OBJECT-TYPE
   SYNTAX      TableIndex
   MAX-ACCESS  not-accessible
   STATUS      current
   DESCRIPTION
      ""
   ::= {er1646v2EthPortSwIXt2VlanIpV6DhcpClientUserClassOptEntry 11}

er1646v2EthPortSwIXt2VlanIpV6DhcpClientUserClassOptValueAscii OBJECT-TYPE
   SYNTAX      DisplayString
   MAX-ACCESS  read-write
   STATUS      current
   DESCRIPTION
      "Path: swPort.editConf.vlan.ipV6.dhcp.client.userClassOpt.value.ascii"
   ::= {er1646v2EthPortSwIXt2VlanIpV6DhcpClientUserClassOptEntry 16842752}

er1646v2EthPortSwIXt2VlanIpV6DhcpClientUserClassOptValueDecimal OBJECT-TYPE
   SYNTAX      Integer32
   MAX-ACCESS  read-write
   STATUS      current
   DESCRIPTION
      "Path: swPort.editConf.vlan.ipV6.dhcp.client.userClassOpt.value.decimal"
   ::= {er1646v2EthPortSwIXt2VlanIpV6DhcpClientUserClassOptEntry 16908288}

er1646v2EthPortSwIXt2VlanIpV6DhcpClientUserClassOptValueHexData OBJECT-TYPE
   SYNTAX      OCTET STRING
   MAX-ACCESS  read-write
   STATUS      current
   DESCRIPTION
      "Path: swPort.editConf.vlan.ipV6.dhcp.client.userClassOpt.value.hexData"
   ::= {er1646v2EthPortSwIXt2VlanIpV6DhcpClientUserClassOptEntry 16973824}

er1646v2EthPortSwIXt2VlanIpV6DhcpClientVendorCl OBJECT-TYPE
   SYNTAX      SEQUENCE OF Er1646v2EthPortSwIXt2VlanIpV6DhcpClientVendorClEntry
   MAX-ACCESS  not-accessible
   STATUS      current
   DESCRIPTION
      ""
   ::= {er1646v2EthPortSwIXt2Vlan 705313792}

er1646v2EthPortSwIXt2VlanIpV6DhcpClientVendorClEntry OBJECT-TYPE
   SYNTAX      Er1646v2EthPortSwIXt2VlanIpV6DhcpClientVendorClEntry
   MAX-ACCESS  not-accessible
   STATUS      current
   DESCRIPTION
      ""
   INDEX      { er1646v2EthPortSwIXt2VlanIpV6DhcpClientVendorClGlobalIx,
                er1646v2EthPortSwIXt2VlanTableIx,
                er1646v2EthPortSwIXt2VlanIpV6DhcpClientVendorClTableIx }
   ::= {er1646v2EthPortSwIXt2VlanIpV6DhcpClientVendorCl 1}

Er1646v2EthPortSwIXt2VlanIpV6DhcpClientVendorClEntry ::=
   SEQUENCE
      {
      er1646v2EthPortSwIXt2VlanIpV6DhcpClientVendorClActions
         VariableLengthTableActions,
      er1646v2EthPortSwIXt2VlanIpV6DhcpClientVendorClGlobalIx
         GlobalIndex,
      er1646v2EthPortSwIXt2VlanIpV6DhcpClientVendorClTableIx
         TableIndex,
      er1646v2EthPortSwIXt2VlanIpV6DhcpClientVendorClValueAscii
         DisplayString,
      er1646v2EthPortSwIXt2VlanIpV6DhcpClientVendorClValueDecimal
         Integer32,
      er1646v2EthPortSwIXt2VlanIpV6DhcpClientVendorClValueHexData
         OCTET STRING
      }

er1646v2EthPortSwIXt2VlanIpV6DhcpClientVendorClActions OBJECT-TYPE
   SYNTAX      VariableLengthTableActions
   MAX-ACCESS  read-write
   STATUS      current
   DESCRIPTION
      "By way of this field, some manipulations
       on this table may be performed."
   ::= {er1646v2EthPortSwIXt2VlanIpV6DhcpClientVendorClEntry 2}

er1646v2EthPortSwIXt2VlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpV6DhcpClientVendorClEntry 10}

er1646v2EthPortSwIXt2VlanIpV6DhcpClientVendorClTableIx OBJECT-TYPE
   SYNTAX      TableIndex
   MAX-ACCESS  not-accessible
   STATUS      current
   DESCRIPTION
      ""
   ::= {er1646v2EthPortSwIXt2VlanIpV6DhcpClientVendorClEntry 11}

er1646v2EthPortSwIXt2VlanIpV6DhcpClientVendorClValueAscii OBJECT-TYPE
   SYNTAX      DisplayString
   MAX-ACCESS  read-write
   STATUS      current
   DESCRIPTION
      "Path: swPort.editConf.vlan.ipV6.dhcp.client.vendorClassOpt.value.ascii"
   ::= {er1646v2EthPortSwIXt2VlanIpV6DhcpClientVendorClEntry 16842752}

er1646v2EthPortSwIXt2VlanIpV6DhcpClientVendorClValueDecimal OBJECT-TYPE
   SYNTAX      Integer32
   MAX-ACCESS  read-write
   STATUS      current
   DESCRIPTION
      "Path: swPort.editConf.vlan.ipV6.dhcp.client.vendorClassOpt.value.decimal"
   ::= {er1646v2EthPortSwIXt2VlanIpV6DhcpClientVendorClEntry 16908288}

er1646v2EthPortSwIXt2VlanIpV6DhcpClientVendorClValueHexData OBJECT-TYPE
   SYNTAX      OCTET STRING
   MAX-ACCESS  read-write
   STATUS      current
   DESCRIPTION
      "Path: swPort.editConf.vlan.ipV6.dhcp.client.vendorClassOpt.value.hexData"
   ::= {er1646v2EthPortSwIXt2VlanIpV6DhcpClientVendorClEntry 16973824}

er1646v2EthPortSwIXt2VlanIpV6DhcpRelayDestinations OBJECT-TYPE
   SYNTAX      SEQUENCE OF Er1646v2EthPortSwIXt2VlanIpV6DhcpRelayDestinationsEntry
   MAX-ACCESS  not-accessible
   STATUS      current
   DESCRIPTION
      ""
   ::= {er1646v2EthPortSwIXt2Vlan 705323072}

er1646v2EthPortSwIXt2VlanIpV6DhcpRelayDestinationsEntry OBJECT-TYPE
   SYNTAX      Er1646v2EthPortSwIXt2VlanIpV6DhcpRelayDestinationsEntry
   MAX-ACCESS  not-accessible
   STATUS      current
   DESCRIPTION
      ""
   INDEX      { er1646v2EthPortSwIXt2VlanIpV6DhcpRelayDestinationsGlobalIx,
                er1646v2EthPortSwIXt2VlanTableIx,
                er1646v2EthPortSwIXt2VlanIpV6DhcpRelayDestinationsTableIx }
   ::= {er1646v2EthPortSwIXt2VlanIpV6DhcpRelayDestinations 1}

Er1646v2EthPortSwIXt2VlanIpV6DhcpRelayDestinationsEntry ::=
   SEQUENCE
      {
      er1646v2EthPortSwIXt2VlanIpV6DhcpRelayDestinationsActions
         VariableLengthTableActions,
      er1646v2EthPortSwIXt2VlanIpV6DhcpRelayDestinationsGlobalIx
         GlobalIndex,
      er1646v2EthPortSwIXt2VlanIpV6DhcpRelayDestinationsTableIx
         TableIndex,
      er1646v2EthPortSwIXt2VlanIpV6DhcpRelayDestinationsAddress
         Ipv6Address,
      er1646v2EthPortSwIXt2VlanIpV6DhcpRelayDestinationsInterface
         DisplayString
      }

er1646v2EthPortSwIXt2VlanIpV6DhcpRelayDestinationsActions OBJECT-TYPE
   SYNTAX      VariableLengthTableActions
   MAX-ACCESS  read-write
   STATUS      current
   DESCRIPTION
      "By way of this field, some manipulations
       on this table may be performed."
   ::= {er1646v2EthPortSwIXt2VlanIpV6DhcpRelayDestinationsEntry 2}

er1646v2EthPortSwIXt2VlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanIpV6DhcpRelayDestinationsEntry 10}

er1646v2EthPortSwIXt2VlanIpV6DhcpRelayDestinationsTableIx OBJECT-TYPE
   SYNTAX      TableIndex
   MAX-ACCESS  not-accessible
   STATUS      current
   DESCRIPTION
      ""
   ::= {er1646v2EthPortSwIXt2VlanIpV6DhcpRelayDestinationsEntry 11}

er1646v2EthPortSwIXt2VlanIpV6DhcpRelayDestinationsAddress OBJECT-TYPE
   SYNTAX      Ipv6Address
   MAX-ACCESS  read-write
   STATUS      current
   DESCRIPTION
      "Path: swPort.editConf.vlan.ipV6.dhcp.relay.destinations.address

       ipv6 address"
   ::= {er1646v2EthPortSwIXt2VlanIpV6DhcpRelayDestinationsEntry 16777216}

er1646v2EthPortSwIXt2VlanIpV6DhcpRelayDestinationsInterface OBJECT-TYPE
   SYNTAX      DisplayString
   MAX-ACCESS  read-write
   STATUS      current
   DESCRIPTION
      "Path: swPort.editConf.vlan.ipV6.dhcp.relay.destinations.interface"
   ::= {er1646v2EthPortSwIXt2VlanIpV6DhcpRelayDestinationsEntry 33554432}

er1646v2EthPortSwIXt2VlanBridgingVlTVlans OBJECT-TYPE
   SYNTAX      SEQUENCE OF Er1646v2EthPortSwIXt2VlanBridgingVlTVlansEntry
   MAX-ACCESS  not-accessible
   STATUS      current
   DESCRIPTION
      ""
   ::= {er1646v2EthPortSwIXt2Vlan 459079680}

er1646v2EthPortSwIXt2VlanBridgingVlTVlansEntry OBJECT-TYPE
   SYNTAX      Er1646v2EthPortSwIXt2VlanBridgingVlTVlansEntry
   MAX-ACCESS  not-accessible
   STATUS      current
   DESCRIPTION
      ""
   INDEX      { er1646v2EthPortSwIXt2VlanBridgingVlTVlansGlobalIx,
                er1646v2EthPortSwIXt2VlanTableIx,
                er1646v2EthPortSwIXt2VlanBridgingVlTVlansTableIx }
   ::= {er1646v2EthPortSwIXt2VlanBridgingVlTVlans 1}

Er1646v2EthPortSwIXt2VlanBridgingVlTVlansEntry ::=
   SEQUENCE
      {
      er1646v2EthPortSwIXt2VlanBridgingVlTVlansActions
         VariableLengthTableActions,
      er1646v2EthPortSwIXt2VlanBridgingVlTVlansGlobalIx
         GlobalIndex,
      er1646v2EthPortSwIXt2VlanBridgingVlTVlansTableIx
         TableIndex,
      er1646v2EthPortSwIXt2VlanBridgingVlTVlansVid
         Integer32,
      er1646v2EthPortSwIXt2VlanBridgingVlTVlansEndVid
         Integer32,
      er1646v2EthPortSwIXt2VlanBridgingVlTVlansAction
         INTEGER,
      er1646v2EthPortSwIXt2VlanBridgingVlTVlansTagInfoTpid
         INTEGER,
      er1646v2EthPortSwIXt2VlanBridgingVlTVlansTagInfoVid
         Integer32
      }

er1646v2EthPortSwIXt2VlanBridgingVlTVlansActions OBJECT-TYPE
   SYNTAX      VariableLengthTableActions
   MAX-ACCESS  read-write
   STATUS      current
   DESCRIPTION
      "By way of this field, some manipulations
       on this table may be performed."
   ::= {er1646v2EthPortSwIXt2VlanBridgingVlTVlansEntry 2}

er1646v2EthPortSwIXt2VlanBridgingVlTVlansGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanBridgingVlTVlansEntry 10}

er1646v2EthPortSwIXt2VlanBridgingVlTVlansTableIx OBJECT-TYPE
   SYNTAX      TableIndex
   MAX-ACCESS  not-accessible
   STATUS      current
   DESCRIPTION
      ""
   ::= {er1646v2EthPortSwIXt2VlanBridgingVlTVlansEntry 11}

er1646v2EthPortSwIXt2VlanBridgingVlTVlansVid OBJECT-TYPE
   SYNTAX      Integer32
   MAX-ACCESS  read-write
   STATUS      current
   DESCRIPTION
      "Path: swPort.editConf.vlan.bridging.vlanTagging.vlans.vid"
   ::= {er1646v2EthPortSwIXt2VlanBridgingVlTVlansEntry 536870912}

er1646v2EthPortSwIXt2VlanBridgingVlTVlansEndVid OBJECT-TYPE
   SYNTAX      Integer32
   MAX-ACCESS  read-write
   STATUS      current
   DESCRIPTION
      "Path: swPort.editConf.vlan.bridging.vlanTagging.vlans.endVid"
   ::= {er1646v2EthPortSwIXt2VlanBridgingVlTVlansEntry 2147483648}

er1646v2EthPortSwIXt2VlanBridgingVlTVlansAction OBJECT-TYPE
   SYNTAX      INTEGER
               {
               discard (0),
               accept (1),
               tag (2)
               }
   MAX-ACCESS  read-write
   STATUS      current
   DESCRIPTION
      "Path: swPort.editConf.vlan.bridging.vlanTagging.vlans.action

       Possibilities:
               discard   (0)
               accept   (1)
               tag   (2)"
   ::= {er1646v2EthPortSwIXt2VlanBridgingVlTVlansEntry 1073741824}

er1646v2EthPortSwIXt2VlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.bridging.vlanTagging.vlans.tagInfo.tpid

       Possibilities:
               dot1Q   (33024)
               dot1ad   (34984)
               0x9100   (37120)
               0x9200   (37376)
               0x9300   (37632)"
   ::= {er1646v2EthPortSwIXt2VlanBridgingVlTVlansEntry 1677721600}

er1646v2EthPortSwIXt2VlanBridgingVlTVlansTagInfoVid OBJECT-TYPE
   SYNTAX      Integer32
   MAX-ACCESS  read-write
   STATUS      current
   DESCRIPTION
      "Path: swPort.editConf.vlan.bridging.vlanTagging.vlans.tagInfo.vid"
   ::= {er1646v2EthPortSwIXt2VlanBridgingVlTVlansEntry 1744830464}

er1646v2EthPortSwIXt2VlanVlanVidExtensionTable OBJECT-TYPE
   SYNTAX      SEQUENCE OF Er1646v2EthPortSwIXt2VlanVlanVidExtensionTableEntry
   MAX-ACCESS  not-accessible
   STATUS      current
   DESCRIPTION
      ""
   ::= {er1646v2EthPortSwIXt2Vlan 235340544}

er1646v2EthPortSwIXt2VlanVlanVidExtensionTableEntry OBJECT-TYPE
   SYNTAX      Er1646v2EthPortSwIXt2VlanVlanVidExtensionTableEntry
   MAX-ACCESS  not-accessible
   STATUS      current
   DESCRIPTION
      ""
   INDEX      { er1646v2EthPortSwIXt2VlanVlanVidExtensionTableGlobalIx,
                er1646v2EthPortSwIXt2VlanTableIx,
                er1646v2EthPortSwIXt2VlanVlanVidExtensionTableTableIx }
   ::= {er1646v2EthPortSwIXt2VlanVlanVidExtensionTable 1}

Er1646v2EthPortSwIXt2VlanVlanVidExtensionTableEntry ::=
   SEQUENCE
      {
      er1646v2EthPortSwIXt2VlanVlanVidExtensionTableActions
         VariableLengthTableActions,
      er1646v2EthPortSwIXt2VlanVlanVidExtensionTableGlobalIx
         GlobalIndex,
      er1646v2EthPortSwIXt2VlanVlanVidExtensionTableTableIx
         TableIndex,
      er1646v2EthPortSwIXt2VlanVlanVidExtensionTableTpid
         INTEGER,
      er1646v2EthPortSwIXt2VlanVlanVidExtensionTableVid
         Integer32,
      er1646v2EthPortSwIXt2VlanVlanVidExtensionTableEndVid
         Integer32
      }

er1646v2EthPortSwIXt2VlanVlanVidExtensionTableActions OBJECT-TYPE
   SYNTAX      VariableLengthTableActions
   MAX-ACCESS  read-write
   STATUS      current
   DESCRIPTION
      "By way of this field, some manipulations
       on this table may be performed."
   ::= {er1646v2EthPortSwIXt2VlanVlanVidExtensionTableEntry 2}

er1646v2EthPortSwIXt2VlanVlanVidExtensionTableGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanVlanVidExtensionTableEntry 10}

er1646v2EthPortSwIXt2VlanVlanVidExtensionTableTableIx OBJECT-TYPE
   SYNTAX      TableIndex
   MAX-ACCESS  not-accessible
   STATUS      current
   DESCRIPTION
      ""
   ::= {er1646v2EthPortSwIXt2VlanVlanVidExtensionTableEntry 11}

er1646v2EthPortSwIXt2VlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: swPort.editConf.vlan.vlan.vidExtension.table.tpid

       Possibilities:
               dot1Q   (33024)
               dot1ad   (34984)
               0x9100   (37120)
               0x9200   (37376)
               0x9300   (37632)"
   ::= {er1646v2EthPortSwIXt2VlanVlanVidExtensionTableEntry 16777216}

er1646v2EthPortSwIXt2VlanVlanVidExtensionTableVid OBJECT-TYPE
   SYNTAX      Integer32
   MAX-ACCESS  read-write
   STATUS      current
   DESCRIPTION
      "Path: swPort.editConf.vlan.vlan.vidExtension.table.vid"
   ::= {er1646v2EthPortSwIXt2VlanVlanVidExtensionTableEntry 33554432}

er1646v2EthPortSwIXt2VlanVlanVidExtensionTableEndVid OBJECT-TYPE
   SYNTAX      Integer32
   MAX-ACCESS  read-write
   STATUS      current
   DESCRIPTION
      "Path: swPort.editConf.vlan.vlan.vidExtension.table.endVid"
   ::= {er1646v2EthPortSwIXt2VlanVlanVidExtensionTableEntry 50331648}

er1646v2EthPortSwIXt2VlanVlanCSMap OBJECT-TYPE
   SYNTAX      SEQUENCE OF Er1646v2EthPortSwIXt2VlanVlanCSMapEntry
   MAX-ACCESS  not-accessible
   STATUS      current
   DESCRIPTION
      ""
   ::= {er1646v2EthPortSwIXt2Vlan 235405312}

er1646v2EthPortSwIXt2VlanVlanCSMapEntry OBJECT-TYPE
   SYNTAX      Er1646v2EthPortSwIXt2VlanVlanCSMapEntry
   MAX-ACCESS  not-accessible
   STATUS      current
   DESCRIPTION
      ""
   INDEX      { er1646v2EthPortSwIXt2VlanVlanCSMapGlobalIx,
                er1646v2EthPortSwIXt2VlanTableIx,
                er1646v2EthPortSwIXt2VlanVlanCSMapTableIx }
   ::= {er1646v2EthPortSwIXt2VlanVlanCSMap 1}

Er1646v2EthPortSwIXt2VlanVlanCSMapEntry ::=
   SEQUENCE
      {
      er1646v2EthPortSwIXt2VlanVlanCSMapActions
         VariableLengthTableActions,
      er1646v2EthPortSwIXt2VlanVlanCSMapGlobalIx
         GlobalIndex,
      er1646v2EthPortSwIXt2VlanVlanCSMapTableIx
         TableIndex,
      er1646v2EthPortSwIXt2VlanVlanCSMapCos
         INTEGER,
      er1646v2EthPortSwIXt2VlanVlanCSMapDei
         INTEGER,
      er1646v2EthPortSwIXt2VlanVlanCSMapTos
         INTEGER,
      er1646v2EthPortSwIXt2VlanVlanCSMapQueue
         INTEGER,
      er1646v2EthPortSwIXt2VlanVlanCSMapDropLevel
         INTEGER,
      er1646v2EthPortSwIXt2VlanVlanCSMapDeFlag
         INTEGER
      }

er1646v2EthPortSwIXt2VlanVlanCSMapActions OBJECT-TYPE
   SYNTAX      VariableLengthTableActions
   MAX-ACCESS  read-write
   STATUS      current
   DESCRIPTION
      "By way of this field, some manipulations
       on this table may be performed."
   ::= {er1646v2EthPortSwIXt2VlanVlanCSMapEntry 2}

er1646v2EthPortSwIXt2VlanVlanCSMapGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanVlanCSMapEntry 10}

er1646v2EthPortSwIXt2VlanVlanCSMapTableIx OBJECT-TYPE
   SYNTAX      TableIndex
   MAX-ACCESS  not-accessible
   STATUS      current
   DESCRIPTION
      ""
   ::= {er1646v2EthPortSwIXt2VlanVlanCSMapEntry 11}

er1646v2EthPortSwIXt2VlanVlanCSMapCos OBJECT-TYPE
   SYNTAX      INTEGER
               {
               any (8)
               }
   MAX-ACCESS  read-write
   STATUS      current
   DESCRIPTION
      "Path: swPort.editConf.vlan.vlan.cosMap.cos

       Possibilities:
               any   (8)"
   ::= {er1646v2EthPortSwIXt2VlanVlanCSMapEntry 16777216}

er1646v2EthPortSwIXt2VlanVlanCSMapDei OBJECT-TYPE
   SYNTAX      INTEGER
               {
               clear (0),
               set (1),
               any (2)
               }
   MAX-ACCESS  read-write
   STATUS      current
   DESCRIPTION
      "Path: swPort.editConf.vlan.vlan.cosMap.dei

       Possibilities:
               clear   (0)
               set   (1)
               any   (2)"
   ::= {er1646v2EthPortSwIXt2VlanVlanCSMapEntry 33554432}

er1646v2EthPortSwIXt2VlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: swPort.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2EthPortSwIXt2VlanVlanCSMapEntry 50331648}

er1646v2EthPortSwIXt2VlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: swPort.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1646v2EthPortSwIXt2VlanVlanCSMapEntry 67108864}

er1646v2EthPortSwIXt2VlanVlanCSMapDropLevel OBJECT-TYPE
   SYNTAX      INTEGER
               {
               unchanged (-1),
               dropOnQueue (0)
               }
   MAX-ACCESS  read-write
   STATUS      current
   DESCRIPTION
      "Path: swPort.editConf.vlan.vlan.cosMap.dropLevel

       Possibilities:
               unchanged   (-1)
               dropOnQueue   (0)"
   ::= {er1646v2EthPortSwIXt2VlanVlanCSMapEntry 83886080}

er1646v2EthPortSwIXt2VlanVlanCSMapDeFlag OBJECT-TYPE
   SYNTAX      INTEGER
               {
               unchanged (255),
               clear (0),
               set (1)
               }
   MAX-ACCESS  read-write
   STATUS      current
   DESCRIPTION
      "Path: swPort.editConf.vlan.vlan.cosMap.deFlag

       Possibilities:
               unchanged   (255)
               clear   (0)
               set   (1)"
   ::= {er1646v2EthPortSwIXt2VlanVlanCSMapEntry 117440512}

er1646v2EthPortSwIXt2VlanVlanTCMap OBJECT-TYPE
   SYNTAX      SEQUENCE OF Er1646v2EthPortSwIXt2VlanVlanTCMapEntry
   MAX-ACCESS  not-accessible
   STATUS      current
   DESCRIPTION
      ""
   ::= {er1646v2EthPortSwIXt2Vlan 241369088}

er1646v2EthPortSwIXt2VlanVlanTCMapEntry OBJECT-TYPE
   SYNTAX      Er1646v2EthPortSwIXt2VlanVlanTCMapEntry
   MAX-ACCESS  not-accessible
   STATUS      current
   DESCRIPTION
      ""
   INDEX      { er1646v2EthPortSwIXt2VlanVlanTCMapGlobalIx,
                er1646v2EthPortSwIXt2VlanTableIx,
                er1646v2EthPortSwIXt2VlanVlanTCMapTableIx }
   ::= {er1646v2EthPortSwIXt2VlanVlanTCMap 1}

Er1646v2EthPortSwIXt2VlanVlanTCMapEntry ::=
   SEQUENCE
      {
      er1646v2EthPortSwIXt2VlanVlanTCMapActions
         VariableLengthTableActions,
      er1646v2EthPortSwIXt2VlanVlanTCMapGlobalIx
         GlobalIndex,
      er1646v2EthPortSwIXt2VlanVlanTCMapTableIx
         TableIndex,
      er1646v2EthPortSwIXt2VlanVlanTCMapStartTos
         INTEGER,
      er1646v2EthPortSwIXt2VlanVlanTCMapEndTos
         INTEGER,
      er1646v2EthPortSwIXt2VlanVlanTCMapCos
         INTEGER
      }

er1646v2EthPortSwIXt2VlanVlanTCMapActions OBJECT-TYPE
   SYNTAX      VariableLengthTableActions
   MAX-ACCESS  read-write
   STATUS      current
   DESCRIPTION
      "By way of this field, some manipulations
       on this table may be performed."
   ::= {er1646v2EthPortSwIXt2VlanVlanTCMapEntry 2}

er1646v2EthPortSwIXt2VlanVlanTCMapGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanVlanTCMapEntry 10}

er1646v2EthPortSwIXt2VlanVlanTCMapTableIx OBJECT-TYPE
   SYNTAX      TableIndex
   MAX-ACCESS  not-accessible
   STATUS      current
   DESCRIPTION
      ""
   ::= {er1646v2EthPortSwIXt2VlanVlanTCMapEntry 11}

er1646v2EthPortSwIXt2VlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2EthPortSwIXt2VlanVlanTCMapEntry 16777216}

er1646v2EthPortSwIXt2VlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: swPort.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2EthPortSwIXt2VlanVlanTCMapEntry 33554432}

er1646v2EthPortSwIXt2VlanVlanTCMapCos OBJECT-TYPE
   SYNTAX      INTEGER
               {
               queueCosMap (8)
               }
   MAX-ACCESS  read-write
   STATUS      current
   DESCRIPTION
      "Path: swPort.editConf.vlan.vlan.tosCosMap.cos

       Possibilities:
               queueCosMap   (8)"
   ::= {er1646v2EthPortSwIXt2VlanVlanTCMapEntry 50331648}

er1646v2EthPortSwIXt2VlanVlanArpStaticArp OBJECT-TYPE
   SYNTAX      SEQUENCE OF Er1646v2EthPortSwIXt2VlanVlanArpStaticArpEntry
   MAX-ACCESS  not-accessible
   STATUS      current
   DESCRIPTION
      ""
   ::= {er1646v2EthPortSwIXt2Vlan 235275008}

er1646v2EthPortSwIXt2VlanVlanArpStaticArpEntry OBJECT-TYPE
   SYNTAX      Er1646v2EthPortSwIXt2VlanVlanArpStaticArpEntry
   MAX-ACCESS  not-accessible
   STATUS      current
   DESCRIPTION
      ""
   INDEX      { er1646v2EthPortSwIXt2VlanVlanArpStaticArpGlobalIx,
                er1646v2EthPortSwIXt2VlanTableIx,
                er1646v2EthPortSwIXt2VlanVlanArpStaticArpTableIx }
   ::= {er1646v2EthPortSwIXt2VlanVlanArpStaticArp 1}

Er1646v2EthPortSwIXt2VlanVlanArpStaticArpEntry ::=
   SEQUENCE
      {
      er1646v2EthPortSwIXt2VlanVlanArpStaticArpActions
         VariableLengthTableActions,
      er1646v2EthPortSwIXt2VlanVlanArpStaticArpGlobalIx
         GlobalIndex,
      er1646v2EthPortSwIXt2VlanVlanArpStaticArpTableIx
         TableIndex,
      er1646v2EthPortSwIXt2VlanVlanArpStaticArpMacAddress
         OCTET STRING,
      er1646v2EthPortSwIXt2VlanVlanArpStaticArpIpAddress
         IpAddress
      }

er1646v2EthPortSwIXt2VlanVlanArpStaticArpActions OBJECT-TYPE
   SYNTAX      VariableLengthTableActions
   MAX-ACCESS  read-write
   STATUS      current
   DESCRIPTION
      "By way of this field, some manipulations
       on this table may be performed."
   ::= {er1646v2EthPortSwIXt2VlanVlanArpStaticArpEntry 2}

er1646v2EthPortSwIXt2VlanVlanArpStaticArpGlobalIx OBJECT-TYPE
   SYNTAX      GlobalIndex
   MAX-ACCESS  not-accessible
   STATUS      current
   DESCRIPTION
      "The value of the tlsCntTreeGlobalIndex of the MANAGED OBJECT."
   ::= {er1646v2EthPortSwIXt2VlanVlanArpStaticArpEntry 10}

er1646v2EthPortSwIXt2VlanVlanArpStaticArpTableIx OBJECT-TYPE
   SYNTAX      TableIndex
   MAX-ACCESS  not-accessible
   STATUS      current
   DESCRIPTION
      ""
   ::= {er1646v2EthPortSwIXt2VlanVlanArpStaticArpEntry 11}

er1646v2EthPortSwIXt2VlanVlanArpStaticArpMacAddress OBJECT-TYPE
   SYNTAX      OCTET STRING
   MAX-ACCESS  read-write
   STATUS      current
   DESCRIPTION
      "Path: swPort.editConf.vlan.vlan.arp.staticArp.macAddress

       MAC address."
   ::= {er1646v2EthPortSwIXt2VlanVlanArpStaticArpEntry 16777216}

er1646v2EthPortSwIXt2VlanVlanArpStaticArpIpAddress OBJECT-TYPE
   SYNTAX      IpAddress
   MAX-ACCESS  read-write
   STATUS      current
   DESCRIPTION
      "Path: swPort.editConf.vlan.vlan.arp.staticArp.ipAddress"
   ::= {er1646v2EthPortSwIXt2VlanVlanArpStaticArpEntry 33554432}


er1646v2EthPortSwIXt2PppOE OBJECT IDENTIFIER ::= {er1646v2EthPortSwIXt2 35}

er1646v2EthPortSwIXt2PppOESSCTable OBJECT-TYPE
   SYNTAX      SEQUENCE OF Er1646v2EthPortSwIXt2PppOEEntry
   MAX-ACCESS  not-accessible
   STATUS      current
   DESCRIPTION
      ""
   ::= {er1646v2EthPortSwIXt2PppOE 1}

er1646v2EthPortSwIXt2PppOEEntry OBJECT-TYPE
   SYNTAX      Er1646v2EthPortSwIXt2PppOEEntry
   MAX-ACCESS  not-accessible
   STATUS      current
   DESCRIPTION
      ""
   INDEX      { er1646v2EthPortSwIXt2PppOEGlobalIx,
                er1646v2EthPortSwIXt2PppOETableIx }
   ::= {er1646v2EthPortSwIXt2PppOESSCTable 1}

Er1646v2EthPortSwIXt2PppOEEntry ::=
   SEQUENCE
      {
      er1646v2EthPortSwIXt2PppOEActions
         VariableLengthTableActions,
      er1646v2EthPortSwIXt2PppOEGlobalIx
         GlobalIndex,
      er1646v2EthPortSwIXt2PppOETableIx
         TableIndex,
      er1646v2EthPortSwIXt2PppOEName
         DisplayString,
      er1646v2EthPortSwIXt2PppOERemark
         DisplayString,
      er1646v2EthPortSwIXt2PppOEAdminStatus
         INTEGER,
      er1646v2EthPortSwIXt2PppOEMode
         INTEGER,
      er1646v2EthPortSwIXt2PppOEIpVrfRouter
         DisplayString,
      er1646v2EthPortSwIXt2PppOEIpAdr
         IpAddress,
      er1646v2EthPortSwIXt2PppOEIpNetm
         IpAddress,
      er1646v2EthPortSwIXt2PppOEIpSNetName
         INTEGER,
      er1646v2EthPortSwIXt2PppOEIpSNetCust
         DisplayString,
      er1646v2EthPortSwIXt2PppOEIpRem
         IpAddress,
      er1646v2EthPortSwIXt2PppOEIpUnnumbered
         DisplayString,
      er1646v2EthPortSwIXt2PppOEIpGwPref
         Integer32,
      er1646v2EthPortSwIXt2PppOEIpRsn
         INTEGER,
      er1646v2EthPortSwIXt2PppOEIpMtu
         Integer32,
      er1646v2EthPortSwIXt2PppOEIpMssAdjust
         INTEGER,
      er1646v2EthPortSwIXt2PppOEIpRipMetric
         Integer32,
      er1646v2EthPortSwIXt2PppOEIpRipMetricOut
         Integer32,
      er1646v2EthPortSwIXt2PppOEIpRipMode
         INTEGER,
      er1646v2EthPortSwIXt2PppOEIpRipTxVer
         INTEGER,
      er1646v2EthPortSwIXt2PppOEIpRipRxVer
         INTEGER,
      er1646v2EthPortSwIXt2PppOEIpRipSplitH
         INTEGER,
      er1646v2EthPortSwIXt2PppOEIpRipAuth
         INTEGER,
      er1646v2EthPortSwIXt2PppOEIpRipFilter
         DisplayString,
      er1646v2EthPortSwIXt2PppOEIpRipFilterIn
         DisplayString,
      er1646v2EthPortSwIXt2PppOEIpRipClearNextHop
         INTEGER,
      er1646v2EthPortSwIXt2PppOEIpAccPol
         DisplayString,
      er1646v2EthPortSwIXt2PppOEIpAB
         DisplayString,
      er1646v2EthPortSwIXt2PppOEIpMA
         INTEGER,
      er1646v2EthPortSwIXt2PppOEIpMF
         Integer32,
      er1646v2EthPortSwIXt2PppOEIpDB
         INTEGER,
      er1646v2EthPortSwIXt2PppOEIpIR
         INTEGER,
      er1646v2EthPortSwIXt2PppOEIpIgmp
         INTEGER,
      er1646v2EthPortSwIXt2PppOEIpNN
         DisplayString,
      er1646v2EthPortSwIXt2PppOEIpPimMode
         INTEGER,
      er1646v2EthPortSwIXt2PppOEIpPimDrPriority
         Counter32,
      er1646v2EthPortSwIXt2PppOEIpPimHelloTime
         TimeTicks,
      er1646v2EthPortSwIXt2PppOEIpPimPropagationDelay
         TimeTicks,
      er1646v2EthPortSwIXt2PppOEIpPimOverrideInterval
         TimeTicks,
      er1646v2EthPortSwIXt2PppOEIpPimBsrBorder
         INTEGER,
      er1646v2EthPortSwIXt2PppOEIpPimTtlThreshold
         Integer32,
      er1646v2EthPortSwIXt2PppOEIpIMNetworkUnreachable
         INTEGER,
      er1646v2EthPortSwIXt2PppOEIpIMHostUnreachable
         INTEGER,
      er1646v2EthPortSwIXt2PppOEIpIMProtocolUnreachable
         INTEGER,
      er1646v2EthPortSwIXt2PppOEIpIMPortUnreachable
         INTEGER,
      er1646v2EthPortSwIXt2PppOEIpIMMtuExceeded
         INTEGER,
      er1646v2EthPortSwIXt2PppOEIpIMAdminProhibited
         INTEGER,
      er1646v2EthPortSwIXt2PppOEIpIMTtlExceeded
         INTEGER,
      er1646v2EthPortSwIXt2PppOEIpIMRedirect
         INTEGER,
      er1646v2EthPortSwIXt2PppOEIpV6VrfRouter
         DisplayString,
      er1646v2EthPortSwIXt2PppOEIpV6AddrAutoConfigNrDupAddrDetects
         Integer32,
      er1646v2EthPortSwIXt2PppOEIpV6AddrAutoConfigAcceptRa
         INTEGER,
      er1646v2EthPortSwIXt2PppOEIpV6AddrAutoConfigAcceptRaRdnss
         INTEGER,
      er1646v2EthPortSwIXt2PppOEIpV6AddrAutoConfigAcceptRaDnssl
         INTEGER,
      er1646v2EthPortSwIXt2PppOEIpV6DefaultRoute
         INTEGER,
      er1646v2EthPortSwIXt2PppOEIpV6RaSend
         INTEGER,
      er1646v2EthPortSwIXt2PppOEIpV6RaMinInterval
         TimeTicks,
      er1646v2EthPortSwIXt2PppOEIpV6RaMaxInterval
         TimeTicks,
      er1646v2EthPortSwIXt2PppOEIpV6RaManagedFlag
         INTEGER,
      er1646v2EthPortSwIXt2PppOEIpV6RaOtherConfFlag
         INTEGER,
      er1646v2EthPortSwIXt2PppOEIpV6RaLinkMtu
         Integer32,
      er1646v2EthPortSwIXt2PppOEIpV6RaReachableTime
         TimeTicks,
      er1646v2EthPortSwIXt2PppOEIpV6RaRetransmitTime
         TimeTicks,
      er1646v2EthPortSwIXt2PppOEIpV6RaHopLimit
         Integer32,
      er1646v2EthPortSwIXt2PppOEIpV6RaDefaultLifeTime
         TimeTicks,
      er1646v2EthPortSwIXt2PppOEIpV6RaDnsOptionsRdnssLifeTime
         TimeTicks,
      er1646v2EthPortSwIXt2PppOEIpV6RaDnsOptionsRdnssImportServers
         INTEGER,
      er1646v2EthPortSwIXt2PppOEIpV6RaDnsOptionsDnsslLifeTime
         TimeTicks,
      er1646v2EthPortSwIXt2PppOEIpV6RaDnsOptionsDnsslImportDomains
         INTEGER,
      er1646v2EthPortSwIXt2PppOEIpV6RsSend
         INTEGER,
      er1646v2EthPortSwIXt2PppOEIpV6RsMaxRandomDelay
         TimeTicks,
      er1646v2EthPortSwIXt2PppOEIpV6RsInterval
         TimeTicks,
      er1646v2EthPortSwIXt2PppOEIpV6RsMaxSolicitations
         Integer32,
      er1646v2EthPortSwIXt2PppOEIpV6TrafficPolicyInbound
         DisplayString,
      er1646v2EthPortSwIXt2PppOEIpV6TrafficPolicyOutbound
         DisplayString,
      er1646v2EthPortSwIXt2PppOEIpV6FirewallZone
         DisplayString,
      er1646v2EthPortSwIXt2PppOEIpV6DhcpClientAddrAC
         INTEGER,
      er1646v2EthPortSwIXt2PppOEIpV6DhcpClientPrDelMode
         INTEGER,
      er1646v2EthPortSwIXt2PppOEIpV6DhcpClientPrDelPool
         DisplayString,
      er1646v2EthPortSwIXt2PppOEIpV6DhcpClientPrDelPdExclOpt
         INTEGER,
      er1646v2EthPortSwIXt2PppOEIpV6DhcpClientDnsServerPref
         Integer32,
      er1646v2EthPortSwIXt2PppOEIpV6DhcpClientRapidCommit
         INTEGER,
      er1646v2EthPortSwIXt2PppOEIpV6DhcpClientTimersSolTimeOut
         TimeTicks,
      er1646v2EthPortSwIXt2PppOEIpV6DhcpClientTimersSolMaxRt
         TimeTicks,
      er1646v2EthPortSwIXt2PppOEIpV6DhcpClientTimersInfoRefresh
         TimeTicks,
      er1646v2EthPortSwIXt2PppOEIpV6DhcpServerMode
         INTEGER,
      er1646v2EthPortSwIXt2PppOEIpV6DhcpServerPreference
         Integer32,
      er1646v2EthPortSwIXt2PppOEIpV6DhcpServerPool
         DisplayString,
      er1646v2EthPortSwIXt2PppOEIpV6DhcpServerRapidCommit
         INTEGER,
      er1646v2EthPortSwIXt2PppOEIpV6DhcpServerTimersInfoRefresh
         TimeTicks,
      er1646v2EthPortSwIXt2PppOEIpV6DhcpRelayMode
         INTEGER,
      er1646v2EthPortSwIXt2PppOEIpV6SendRedirect
         INTEGER,
      er1646v2EthPortSwIXt2PppOEIpV6LinkMtu
         Integer32,
      er1646v2EthPortSwIXt2PppOEIpV6InterfaceId
         OCTET STRING,
      er1646v2EthPortSwIXt2PppOEIpV6MF
         Integer32,
      er1646v2EthPortSwIXt2PppOEIpV6IcmpMessagesNoRoute
         INTEGER,
      er1646v2EthPortSwIXt2PppOEIpV6IcmpMessagesBeyondScope
         INTEGER,
      er1646v2EthPortSwIXt2PppOEIpV6IcmpMessagesAddressUnreachable
         INTEGER,
      er1646v2EthPortSwIXt2PppOEIpV6IcmpMessagesPortUnreachable
         INTEGER,
      er1646v2EthPortSwIXt2PppOEIpV6IcmpMessagesPacketTooBig
         INTEGER,
      er1646v2EthPortSwIXt2PppOEIpV6IcmpMessagesHopLimitExceeded
         INTEGER,
      er1646v2EthPortSwIXt2PppOEIpV6IcmpMessagesFragTimeExceeded
         INTEGER,
      er1646v2EthPortSwIXt2PppOEIpV6IcmpMessagesHeaderFieldErr
         INTEGER,
      er1646v2EthPortSwIXt2PppOEIpV6IcmpMessagesOptionUnrecognized
         INTEGER,
      er1646v2EthPortSwIXt2PppOEIpV6IcmpMessagesRedirect
         INTEGER,
      er1646v2EthPortSwIXt2PppOEPppLnkMOperation
         INTEGER,
      er1646v2EthPortSwIXt2PppOEPppLnkMInterval
         TimeTicks,
      er1646v2EthPortSwIXt2PppOEPppLnkMRepTimeOut
         TimeTicks,
      er1646v2EthPortSwIXt2PppOEPppLnkMFailsPrmt
         Integer32,
      er1646v2EthPortSwIXt2PppOEPppAuthentication
         INTEGER,
      er1646v2EthPortSwIXt2PppOEPppAuthenPeriod
         TimeTicks,
      er1646v2EthPortSwIXt2PppOEPppSessionName
         DisplayString,
      er1646v2EthPortSwIXt2PppOEPppSessionSecret
         DisplayString,
      er1646v2EthPortSwIXt2PppOEPppEncModeSessionSecret
         INTEGER,
      er1646v2EthPortSwIXt2PppOEPppEncSessionSecret
         DisplayString,
      er1646v2EthPortSwIXt2PppOEPppServiceName
         DisplayString
      }

er1646v2EthPortSwIXt2PppOEActions OBJECT-TYPE
   SYNTAX      VariableLengthTableActions
   MAX-ACCESS  read-write
   STATUS      current
   DESCRIPTION
      "By way of this field, some manipulations
       on this table may be performed."
   ::= {er1646v2EthPortSwIXt2PppOEEntry 2}

er1646v2EthPortSwIXt2PppOEGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEEntry 10}

er1646v2EthPortSwIXt2PppOETableIx OBJECT-TYPE
   SYNTAX      TableIndex
   MAX-ACCESS  not-accessible
   STATUS      current
   DESCRIPTION
      ""
   ::= {er1646v2EthPortSwIXt2PppOEEntry 11}

er1646v2EthPortSwIXt2PppOEName OBJECT-TYPE
   SYNTAX      DisplayString
   MAX-ACCESS  read-write
   STATUS      current
   DESCRIPTION
      "Path: swPort.editConf.pppoEClient.name"
   ::= {er1646v2EthPortSwIXt2PppOEEntry 16777216}

er1646v2EthPortSwIXt2PppOERemark OBJECT-TYPE
   SYNTAX      DisplayString
   MAX-ACCESS  read-write
   STATUS      current
   DESCRIPTION
      "Path: swPort.editConf.pppoEClient.remark"
   ::= {er1646v2EthPortSwIXt2PppOEEntry 1157627904}

er1646v2EthPortSwIXt2PppOEAdminStatus OBJECT-TYPE
   SYNTAX      INTEGER
               {
               up (1),
               down (2)
               }
   MAX-ACCESS  read-write
   STATUS      current
   DESCRIPTION
      "Path: swPort.editConf.pppoEClient.adminStatus

       Possibilities:
               up   (1)
               down   (2)"
   ::= {er1646v2EthPortSwIXt2PppOEEntry 33554432}

er1646v2EthPortSwIXt2PppOEMode OBJECT-TYPE
   SYNTAX      INTEGER
               {
               routing (1),
               multilink (8),
               ipV6 (16),
               ipV6ipV4 (17)
               }
   MAX-ACCESS  read-write
   STATUS      current
   DESCRIPTION
      "Path: swPort.editConf.pppoEClient.mode

       Possibilities:
               routing   (1)
               multilink   (8)
               ipV6   (16)
               ipV6/ipV4   (17)"
   ::= {er1646v2EthPortSwIXt2PppOEEntry 67108864}

er1646v2EthPortSwIXt2PppOEIpVrfRouter OBJECT-TYPE
   SYNTAX      DisplayString
   MAX-ACCESS  read-write
   STATUS      current
   DESCRIPTION
      "Path: swPort.editConf.pppoEClient.ip.vrfRouter"
   ::= {er1646v2EthPortSwIXt2PppOEEntry 53215232}

er1646v2EthPortSwIXt2PppOEIpAdr OBJECT-TYPE
   SYNTAX      IpAddress
   MAX-ACCESS  read-write
   STATUS      current
   DESCRIPTION
      "Path: swPort.editConf.pppoEClient.ip.address"
   ::= {er1646v2EthPortSwIXt2PppOEEntry 58261504}

er1646v2EthPortSwIXt2PppOEIpNetm OBJECT-TYPE
   SYNTAX      IpAddress
   MAX-ACCESS  read-write
   STATUS      current
   DESCRIPTION
      "Path: swPort.editConf.pppoEClient.ip.netMask"
   ::= {er1646v2EthPortSwIXt2PppOEEntry 58392576}

er1646v2EthPortSwIXt2PppOEIpSNetName OBJECT-TYPE
   SYNTAX      INTEGER
               {
               slOPTg (0),
               corp (2),
               dmz (3),
               internet (1)
               }
   MAX-ACCESS  read-write
   STATUS      current
   DESCRIPTION
      "Path: swPort.editConf.pppoEClient.ip.sNet.name

       Possibilities:
               <OPT>   (0)
               corp   (2)
               dmz   (3)
               internet   (1)"
   ::= {er1646v2EthPortSwIXt2PppOEEntry 53674240}

er1646v2EthPortSwIXt2PppOEIpSNetCust OBJECT-TYPE
   SYNTAX      DisplayString
   MAX-ACCESS  read-write
   STATUS      current
   DESCRIPTION
      "Path: swPort.editConf.pppoEClient.ip.sNet.custom"
   ::= {er1646v2EthPortSwIXt2PppOEEntry 53674496}

er1646v2EthPortSwIXt2PppOEIpRem OBJECT-TYPE
   SYNTAX      IpAddress
   MAX-ACCESS  read-write
   STATUS      current
   DESCRIPTION
      "Path: swPort.editConf.pppoEClient.ip.remote"
   ::= {er1646v2EthPortSwIXt2PppOEEntry 58458112}

er1646v2EthPortSwIXt2PppOEIpUnnumbered OBJECT-TYPE
   SYNTAX      DisplayString
   MAX-ACCESS  read-write
   STATUS      current
   DESCRIPTION
      "Path: swPort.editConf.pppoEClient.ip.unnumbered"
   ::= {er1646v2EthPortSwIXt2PppOEEntry 52625408}

er1646v2EthPortSwIXt2PppOEIpGwPref OBJECT-TYPE
   SYNTAX      Integer32
   MAX-ACCESS  read-write
   STATUS      current
   DESCRIPTION
      "Path: swPort.editConf.pppoEClient.ip.gatewayPreference"
   ::= {er1646v2EthPortSwIXt2PppOEEntry 52690944}

er1646v2EthPortSwIXt2PppOEIpRsn OBJECT-TYPE
   SYNTAX      INTEGER
               {
               disabled (0),
               enabled (1)
               }
   MAX-ACCESS  read-write
   STATUS      current
   DESCRIPTION
      "Path: swPort.editConf.pppoEClient.ip.requestSubnet

       Possibilities:
               disabled   (0)
               enabled   (1)"
   ::= {er1646v2EthPortSwIXt2PppOEEntry 56688640}

er1646v2EthPortSwIXt2PppOEIpMtu OBJECT-TYPE
   SYNTAX      Integer32
   MAX-ACCESS  read-write
   STATUS      current
   DESCRIPTION
      "Path: swPort.editConf.pppoEClient.ip.mtu"
   ::= {er1646v2EthPortSwIXt2PppOEEntry 52953088}

er1646v2EthPortSwIXt2PppOEIpMssAdjust OBJECT-TYPE
   SYNTAX      INTEGER
               {
               disabled (0),
               auto (65536)
               }
   MAX-ACCESS  read-write
   STATUS      current
   DESCRIPTION
      "Path: swPort.editConf.pppoEClient.ip.mssAdjust

       Possibilities:
               disabled   (0)
               auto   (65536)"
   ::= {er1646v2EthPortSwIXt2PppOEEntry 53280768}

er1646v2EthPortSwIXt2PppOEIpRipMetric OBJECT-TYPE
   SYNTAX      Integer32
   MAX-ACCESS  read-write
   STATUS      current
   DESCRIPTION
      "Path: swPort.editConf.pppoEClient.ip.rip.metric"
   ::= {er1646v2EthPortSwIXt2PppOEEntry 51712768}

er1646v2EthPortSwIXt2PppOEIpRipMetricOut OBJECT-TYPE
   SYNTAX      Integer32
   MAX-ACCESS  read-write
   STATUS      current
   DESCRIPTION
      "Path: swPort.editConf.pppoEClient.ip.rip.metricOut"
   ::= {er1646v2EthPortSwIXt2PppOEEntry 51713024}

er1646v2EthPortSwIXt2PppOEIpRipMode OBJECT-TYPE
   SYNTAX      INTEGER
               {
               disabled (0),
               passive (1),
               active (2)
               }
   MAX-ACCESS  read-write
   STATUS      current
   DESCRIPTION
      "Path: swPort.editConf.pppoEClient.ip.rip.mode

       Possibilities:
               disabled   (0)
               passive   (1)
               active   (2)"
   ::= {er1646v2EthPortSwIXt2PppOEEntry 51713280}

er1646v2EthPortSwIXt2PppOEIpRipTxVer OBJECT-TYPE
   SYNTAX      INTEGER
               {
               rip1 (0),
               rip2 (1),
               rip1mcompatible (2)
               }
   MAX-ACCESS  read-write
   STATUS      current
   DESCRIPTION
      "Path: swPort.editConf.pppoEClient.ip.rip.txVersion

       Possibilities:
               rip1   (0)
               rip2   (1)
               rip1-compatible   (2)"
   ::= {er1646v2EthPortSwIXt2PppOEEntry 51716864}

er1646v2EthPortSwIXt2PppOEIpRipRxVer OBJECT-TYPE
   SYNTAX      INTEGER
               {
               rip1only (0),
               rip2only (1),
               rip12 (2)
               }
   MAX-ACCESS  read-write
   STATUS      current
   DESCRIPTION
      "Path: swPort.editConf.pppoEClient.ip.rip.rxVersion

       Possibilities:
               rip1only   (0)
               rip2only   (1)
               rip1&2   (2)"
   ::= {er1646v2EthPortSwIXt2PppOEEntry 51717120}

er1646v2EthPortSwIXt2PppOEIpRipSplitH OBJECT-TYPE
   SYNTAX      INTEGER
               {
               disabled (0),
               enabled (1),
               poisonedReverse (2)
               }
   MAX-ACCESS  read-write
   STATUS      current
   DESCRIPTION
      "Path: swPort.editConf.pppoEClient.ip.rip.splitHorizon

       Possibilities:
               disabled   (0)
               enabled   (1)
               poisonedReverse   (2)"
   ::= {er1646v2EthPortSwIXt2PppOEEntry 51713792}

er1646v2EthPortSwIXt2PppOEIpRipAuth OBJECT-TYPE
   SYNTAX      INTEGER
               {
               disabled (0),
               texts (1),
               md5 (2)
               }
   MAX-ACCESS  read-write
   STATUS      current
   DESCRIPTION
      "Path: swPort.editConf.pppoEClient.ip.rip.authentication

       Possibilities:
               disabled   (0)
               text    (1)
               md5   (2)"
   ::= {er1646v2EthPortSwIXt2PppOEEntry 51712512}

er1646v2EthPortSwIXt2PppOEIpRipFilter OBJECT-TYPE
   SYNTAX      DisplayString
   MAX-ACCESS  read-write
   STATUS      current
   DESCRIPTION
      "Path: swPort.editConf.pppoEClient.ip.rip.filter"
   ::= {er1646v2EthPortSwIXt2PppOEEntry 51716096}

er1646v2EthPortSwIXt2PppOEIpRipFilterIn OBJECT-TYPE
   SYNTAX      DisplayString
   MAX-ACCESS  read-write
   STATUS      current
   DESCRIPTION
      "Path: swPort.editConf.pppoEClient.ip.rip.filterIn"
   ::= {er1646v2EthPortSwIXt2PppOEEntry 51716352}

er1646v2EthPortSwIXt2PppOEIpRipClearNextHop OBJECT-TYPE
   SYNTAX      INTEGER
               {
               disabled (0),
               enabled (1)
               }
   MAX-ACCESS  read-write
   STATUS      current
   DESCRIPTION
      "Path: swPort.editConf.pppoEClient.ip.rip.clearNextHop

       Possibilities:
               disabled   (0)
               enabled   (1)"
   ::= {er1646v2EthPortSwIXt2PppOEEntry 51708416}

er1646v2EthPortSwIXt2PppOEIpAccPol OBJECT-TYPE
   SYNTAX      DisplayString
   MAX-ACCESS  read-write
   STATUS      current
   DESCRIPTION
      "Path: swPort.editConf.pppoEClient.ip.accessPolicy"
   ::= {er1646v2EthPortSwIXt2PppOEEntry 53084160}

er1646v2EthPortSwIXt2PppOEIpAB OBJECT-TYPE
   SYNTAX      DisplayString
   MAX-ACCESS  read-write
   STATUS      current
   DESCRIPTION
      "Path: swPort.editConf.pppoEClient.ip.trafficPolicy"
   ::= {er1646v2EthPortSwIXt2PppOEEntry 51249152}

er1646v2EthPortSwIXt2PppOEIpMA OBJECT-TYPE
   SYNTAX      INTEGER
               {
               disabled (0),
               enabled (1)
               }
   MAX-ACCESS  read-write
   STATUS      current
   DESCRIPTION
      "Path: swPort.editConf.pppoEClient.ip.mgmtAccess

       Possibilities:
               disabled   (0)
               enabled   (1)"
   ::= {er1646v2EthPortSwIXt2PppOEEntry 51380224}

er1646v2EthPortSwIXt2PppOEIpMF OBJECT-TYPE
   SYNTAX      Integer32
   MAX-ACCESS  read-write
   STATUS      current
   DESCRIPTION
      "Path: swPort.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2EthPortSwIXt2PppOEEntry 51445760}

er1646v2EthPortSwIXt2PppOEIpDB OBJECT-TYPE
   SYNTAX      INTEGER
               {
               disabled (0),
               enabled (1)
               }
   MAX-ACCESS  read-write
   STATUS      current
   DESCRIPTION
      "Path: swPort.editConf.pppoEClient.ip.directedBroadcasts

       Possibilities:
               disabled   (0)
               enabled   (1)"
   ::= {er1646v2EthPortSwIXt2PppOEEntry 51773440}

er1646v2EthPortSwIXt2PppOEIpIR OBJECT-TYPE
   SYNTAX      INTEGER
               {
               disabled (0),
               enabled (1)
               }
   MAX-ACCESS  read-write
   STATUS      current
   DESCRIPTION
      "Path: swPort.editConf.pppoEClient.ip.icmpRedirects

       Possibilities:
               disabled   (0)
               enabled   (1)"
   ::= {er1646v2EthPortSwIXt2PppOEEntry 52035584}

er1646v2EthPortSwIXt2PppOEIpIgmp OBJECT-TYPE
   SYNTAX      INTEGER
               {
               disabled (0),
               proxy (1),
               router (2),
               v3Router (5)
               }
   MAX-ACCESS  read-write
   STATUS      current
   DESCRIPTION
      "Path: swPort.editConf.pppoEClient.ip.igmp

       Possibilities:
               disabled   (0)
               proxy   (1)
               router   (2)
               v3Router   (5)"
   ::= {er1646v2EthPortSwIXt2PppOEEntry 52428800}

er1646v2EthPortSwIXt2PppOEIpNN OBJECT-TYPE
   SYNTAX      DisplayString
   MAX-ACCESS  read-write
   STATUS      current
   DESCRIPTION
      "Path: swPort.editConf.pppoEClient.ip.nat"
   ::= {er1646v2EthPortSwIXt2PppOEEntry 52101120}

er1646v2EthPortSwIXt2PppOEIpPimMode OBJECT-TYPE
   SYNTAX      INTEGER
               {
               disabled (0),
               sparse (1),
               passive (2)
               }
   MAX-ACCESS  read-write
   STATUS      current
   DESCRIPTION
      "Path: swPort.editConf.pppoEClient.ip.pim.mode

       Possibilities:
               disabled   (0)
               sparse   (1)
               passive   (2)"
   ::= {er1646v2EthPortSwIXt2PppOEEntry 53346560}

er1646v2EthPortSwIXt2PppOEIpPimDrPriority OBJECT-TYPE
   SYNTAX      Counter32
   MAX-ACCESS  read-write
   STATUS      current
   DESCRIPTION
      "Path: swPort.editConf.pppoEClient.ip.pim.drPriority

       32 bit unsigned wrappable counter."
   ::= {er1646v2EthPortSwIXt2PppOEEntry 53346816}

er1646v2EthPortSwIXt2PppOEIpPimHelloTime OBJECT-TYPE
   SYNTAX      TimeTicks
   MAX-ACCESS  read-write
   STATUS      current
   DESCRIPTION
      "Path: swPort.editConf.pppoEClient.ip.pim.helloTime

       Time in centi-second."
   ::= {er1646v2EthPortSwIXt2PppOEEntry 53347072}

er1646v2EthPortSwIXt2PppOEIpPimPropagationDelay OBJECT-TYPE
   SYNTAX      TimeTicks
   MAX-ACCESS  read-write
   STATUS      current
   DESCRIPTION
      "Path: swPort.editConf.pppoEClient.ip.pim.propagationDelay

       Time in centi-second."
   ::= {er1646v2EthPortSwIXt2PppOEEntry 53347328}

er1646v2EthPortSwIXt2PppOEIpPimOverrideInterval OBJECT-TYPE
   SYNTAX      TimeTicks
   MAX-ACCESS  read-write
   STATUS      current
   DESCRIPTION
      "Path: swPort.editConf.pppoEClient.ip.pim.overrideInterval

       Time in centi-second."
   ::= {er1646v2EthPortSwIXt2PppOEEntry 53347584}

er1646v2EthPortSwIXt2PppOEIpPimBsrBorder OBJECT-TYPE
   SYNTAX      INTEGER
               {
               disabled (0),
               enabled (1)
               }
   MAX-ACCESS  read-write
   STATUS      current
   DESCRIPTION
      "Path: swPort.editConf.pppoEClient.ip.pim.bsrBorder

       Possibilities:
               disabled   (0)
               enabled   (1)"
   ::= {er1646v2EthPortSwIXt2PppOEEntry 53347840}

er1646v2EthPortSwIXt2PppOEIpPimTtlThreshold OBJECT-TYPE
   SYNTAX      Integer32
   MAX-ACCESS  read-write
   STATUS      current
   DESCRIPTION
      "Path: swPort.editConf.pppoEClient.ip.pim.ttlThreshold"
   ::= {er1646v2EthPortSwIXt2PppOEEntry 53348096}

er1646v2EthPortSwIXt2PppOEIpIMNetworkUnreachable OBJECT-TYPE
   SYNTAX      INTEGER
               {
               disabled (0),
               enabled (1)
               }
   MAX-ACCESS  read-write
   STATUS      current
   DESCRIPTION
      "Path: swPort.editConf.pppoEClient.ip.icmpMessages.networkUnreachable

       Possibilities:
               disabled   (0)
               enabled   (1)"
   ::= {er1646v2EthPortSwIXt2PppOEEntry 53412096}

er1646v2EthPortSwIXt2PppOEIpIMHostUnreachable OBJECT-TYPE
   SYNTAX      INTEGER
               {
               disabled (0),
               enabled (1)
               }
   MAX-ACCESS  read-write
   STATUS      current
   DESCRIPTION
      "Path: swPort.editConf.pppoEClient.ip.icmpMessages.hostUnreachable

       Possibilities:
               disabled   (0)
               enabled   (1)"
   ::= {er1646v2EthPortSwIXt2PppOEEntry 53412352}

er1646v2EthPortSwIXt2PppOEIpIMProtocolUnreachable OBJECT-TYPE
   SYNTAX      INTEGER
               {
               disabled (0),
               enabled (1)
               }
   MAX-ACCESS  read-write
   STATUS      current
   DESCRIPTION
      "Path: swPort.editConf.pppoEClient.ip.icmpMessages.protocolUnreachable

       Possibilities:
               disabled   (0)
               enabled   (1)"
   ::= {er1646v2EthPortSwIXt2PppOEEntry 53412608}

er1646v2EthPortSwIXt2PppOEIpIMPortUnreachable OBJECT-TYPE
   SYNTAX      INTEGER
               {
               disabled (0),
               enabled (1)
               }
   MAX-ACCESS  read-write
   STATUS      current
   DESCRIPTION
      "Path: swPort.editConf.pppoEClient.ip.icmpMessages.portUnreachable

       Possibilities:
               disabled   (0)
               enabled   (1)"
   ::= {er1646v2EthPortSwIXt2PppOEEntry 53412864}

er1646v2EthPortSwIXt2PppOEIpIMMtuExceeded OBJECT-TYPE
   SYNTAX      INTEGER
               {
               disabled (0),
               enabled (1)
               }
   MAX-ACCESS  read-write
   STATUS      current
   DESCRIPTION
      "Path: swPort.editConf.pppoEClient.ip.icmpMessages.mtuExceeded

       Possibilities:
               disabled   (0)
               enabled   (1)"
   ::= {er1646v2EthPortSwIXt2PppOEEntry 53413120}

er1646v2EthPortSwIXt2PppOEIpIMAdminProhibited OBJECT-TYPE
   SYNTAX      INTEGER
               {
               disabled (0),
               enabled (1)
               }
   MAX-ACCESS  read-write
   STATUS      current
   DESCRIPTION
      "Path: swPort.editConf.pppoEClient.ip.icmpMessages.adminProhibited

       Possibilities:
               disabled   (0)
               enabled   (1)"
   ::= {er1646v2EthPortSwIXt2PppOEEntry 53413376}

er1646v2EthPortSwIXt2PppOEIpIMTtlExceeded OBJECT-TYPE
   SYNTAX      INTEGER
               {
               disabled (0),
               enabled (1)
               }
   MAX-ACCESS  read-write
   STATUS      current
   DESCRIPTION
      "Path: swPort.editConf.pppoEClient.ip.icmpMessages.ttlExceeded

       Possibilities:
               disabled   (0)
               enabled   (1)"
   ::= {er1646v2EthPortSwIXt2PppOEEntry 53413632}

er1646v2EthPortSwIXt2PppOEIpIMRedirect OBJECT-TYPE
   SYNTAX      INTEGER
               {
               disabled (0),
               enabled (1)
               }
   MAX-ACCESS  read-write
   STATUS      current
   DESCRIPTION
      "Path: swPort.editConf.pppoEClient.ip.icmpMessages.redirect

       Possibilities:
               disabled   (0)
               enabled   (1)"
   ::= {er1646v2EthPortSwIXt2PppOEEntry 53413888}

er1646v2EthPortSwIXt2PppOEIpV6VrfRouter OBJECT-TYPE
   SYNTAX      DisplayString
   MAX-ACCESS  read-write
   STATUS      current
   DESCRIPTION
      "Path: swPort.editConf.pppoEClient.ipV6.vrfRouter"
   ::= {er1646v2EthPortSwIXt2PppOEEntry 704708608}

er1646v2EthPortSwIXt2PppOEIpV6AddrAutoConfigNrDupAddrDetects OBJECT-TYPE
   SYNTAX      Integer32
   MAX-ACCESS  read-write
   STATUS      current
   DESCRIPTION
      "Path: swPort.editConf.pppoEClient.ipV6.addrAutoConfig.nrDupAddrDetects"
   ::= {er1646v2EthPortSwIXt2PppOEEntry 704905472}

er1646v2EthPortSwIXt2PppOEIpV6AddrAutoConfigAcceptRa OBJECT-TYPE
   SYNTAX      INTEGER
               {
               disabled (0),
               enabled (1)
               }
   MAX-ACCESS  read-write
   STATUS      current
   DESCRIPTION
      "Path: swPort.editConf.pppoEClient.ipV6.addrAutoConfig.acceptRa

       Possibilities:
               disabled   (0)
               enabled   (1)"
   ::= {er1646v2EthPortSwIXt2PppOEEntry 704905728}

er1646v2EthPortSwIXt2PppOEIpV6AddrAutoConfigAcceptRaRdnss OBJECT-TYPE
   SYNTAX      INTEGER
               {
               disabled (0),
               enabled (1)
               }
   MAX-ACCESS  read-write
   STATUS      current
   DESCRIPTION
      "Path: swPort.editConf.pppoEClient.ipV6.addrAutoConfig.acceptRaRdnss

       Possibilities:
               disabled   (0)
               enabled   (1)"
   ::= {er1646v2EthPortSwIXt2PppOEEntry 704905984}

er1646v2EthPortSwIXt2PppOEIpV6AddrAutoConfigAcceptRaDnssl OBJECT-TYPE
   SYNTAX      INTEGER
               {
               disabled (0),
               enabled (1)
               }
   MAX-ACCESS  read-write
   STATUS      current
   DESCRIPTION
      "Path: swPort.editConf.pppoEClient.ipV6.addrAutoConfig.acceptRaDnssl

       Possibilities:
               disabled   (0)
               enabled   (1)"
   ::= {er1646v2EthPortSwIXt2PppOEEntry 704906240}

er1646v2EthPortSwIXt2PppOEIpV6DefaultRoute OBJECT-TYPE
   SYNTAX      INTEGER
               {
               disabled (0),
               enabled (1)
               }
   MAX-ACCESS  read-write
   STATUS      current
   DESCRIPTION
      "Path: swPort.editConf.pppoEClient.ipV6.defaultRoute

       Possibilities:
               disabled   (0)
               enabled   (1)"
   ::= {er1646v2EthPortSwIXt2PppOEEntry 704970752}

er1646v2EthPortSwIXt2PppOEIpV6RaSend OBJECT-TYPE
   SYNTAX      INTEGER
               {
               disabled (0),
               enabled (1)
               }
   MAX-ACCESS  read-write
   STATUS      current
   DESCRIPTION
      "Path: swPort.editConf.pppoEClient.ipV6.ra.send

       Possibilities:
               disabled   (0)
               enabled   (1)"
   ::= {er1646v2EthPortSwIXt2PppOEEntry 705036544}

er1646v2EthPortSwIXt2PppOEIpV6RaMinInterval OBJECT-TYPE
   SYNTAX      TimeTicks
   MAX-ACCESS  read-write
   STATUS      current
   DESCRIPTION
      "Path: swPort.editConf.pppoEClient.ipV6.ra.minInterval

       Time in centi-second."
   ::= {er1646v2EthPortSwIXt2PppOEEntry 705036800}

er1646v2EthPortSwIXt2PppOEIpV6RaMaxInterval OBJECT-TYPE
   SYNTAX      TimeTicks
   MAX-ACCESS  read-write
   STATUS      current
   DESCRIPTION
      "Path: swPort.editConf.pppoEClient.ipV6.ra.maxInterval

       Time in centi-second."
   ::= {er1646v2EthPortSwIXt2PppOEEntry 705037056}

er1646v2EthPortSwIXt2PppOEIpV6RaManagedFlag OBJECT-TYPE
   SYNTAX      INTEGER
               {
               disabled (0),
               enabled (1)
               }
   MAX-ACCESS  read-write
   STATUS      current
   DESCRIPTION
      "Path: swPort.editConf.pppoEClient.ipV6.ra.managedFlag

       Possibilities:
               disabled   (0)
               enabled   (1)"
   ::= {er1646v2EthPortSwIXt2PppOEEntry 705037312}

er1646v2EthPortSwIXt2PppOEIpV6RaOtherConfFlag OBJECT-TYPE
   SYNTAX      INTEGER
               {
               disabled (0),
               enabled (1)
               }
   MAX-ACCESS  read-write
   STATUS      current
   DESCRIPTION
      "Path: swPort.editConf.pppoEClient.ipV6.ra.otherConfFlag

       Possibilities:
               disabled   (0)
               enabled   (1)"
   ::= {er1646v2EthPortSwIXt2PppOEEntry 705037568}

er1646v2EthPortSwIXt2PppOEIpV6RaLinkMtu OBJECT-TYPE
   SYNTAX      Integer32
   MAX-ACCESS  read-write
   STATUS      current
   DESCRIPTION
      "Path: swPort.editConf.pppoEClient.ipV6.ra.linkMtu"
   ::= {er1646v2EthPortSwIXt2PppOEEntry 705037824}

er1646v2EthPortSwIXt2PppOEIpV6RaReachableTime OBJECT-TYPE
   SYNTAX      TimeTicks
   MAX-ACCESS  read-write
   STATUS      current
   DESCRIPTION
      "Path: swPort.editConf.pppoEClient.ipV6.ra.reachableTime

       Time in centi-second."
   ::= {er1646v2EthPortSwIXt2PppOEEntry 705038080}

er1646v2EthPortSwIXt2PppOEIpV6RaRetransmitTime OBJECT-TYPE
   SYNTAX      TimeTicks
   MAX-ACCESS  read-write
   STATUS      current
   DESCRIPTION
      "Path: swPort.editConf.pppoEClient.ipV6.ra.retransmitTime

       Time in centi-second."
   ::= {er1646v2EthPortSwIXt2PppOEEntry 705038336}

er1646v2EthPortSwIXt2PppOEIpV6RaHopLimit OBJECT-TYPE
   SYNTAX      Integer32
   MAX-ACCESS  read-write
   STATUS      current
   DESCRIPTION
      "Path: swPort.editConf.pppoEClient.ipV6.ra.hopLimit"
   ::= {er1646v2EthPortSwIXt2PppOEEntry 705038592}

er1646v2EthPortSwIXt2PppOEIpV6RaDefaultLifeTime OBJECT-TYPE
   SYNTAX      TimeTicks
   MAX-ACCESS  read-write
   STATUS      current
   DESCRIPTION
      "Path: swPort.editConf.pppoEClient.ipV6.ra.defaultLifeTime

       Time in centi-second."
   ::= {er1646v2EthPortSwIXt2PppOEEntry 705038848}

er1646v2EthPortSwIXt2PppOEIpV6RaDnsOptionsRdnssLifeTime OBJECT-TYPE
   SYNTAX      TimeTicks
   MAX-ACCESS  read-write
   STATUS      current
   DESCRIPTION
      "Path: swPort.editConf.pppoEClient.ipV6.ra.dnsOptions.rdnss.lifeTime

       Time in centi-second."
   ::= {er1646v2EthPortSwIXt2PppOEEntry 705039140}

er1646v2EthPortSwIXt2PppOEIpV6RaDnsOptionsRdnssImportServers OBJECT-TYPE
   SYNTAX      INTEGER
               {
               disabled (0),
               enabled (1)
               }
   MAX-ACCESS  read-write
   STATUS      current
   DESCRIPTION
      "Path: swPort.editConf.pppoEClient.ipV6.ra.dnsOptions.rdnss.importServers

       Possibilities:
               disabled   (0)
               enabled   (1)"
   ::= {er1646v2EthPortSwIXt2PppOEEntry 705039148}

er1646v2EthPortSwIXt2PppOEIpV6RaDnsOptionsDnsslLifeTime OBJECT-TYPE
   SYNTAX      TimeTicks
   MAX-ACCESS  read-write
   STATUS      current
   DESCRIPTION
      "Path: swPort.editConf.pppoEClient.ipV6.ra.dnsOptions.dnssl.lifeTime

       Time in centi-second."
   ::= {er1646v2EthPortSwIXt2PppOEEntry 705039172}

er1646v2EthPortSwIXt2PppOEIpV6RaDnsOptionsDnsslImportDomains OBJECT-TYPE
   SYNTAX      INTEGER
               {
               disabled (0),
               enabled (1)
               }
   MAX-ACCESS  read-write
   STATUS      current
   DESCRIPTION
      "Path: swPort.editConf.pppoEClient.ipV6.ra.dnsOptions.dnssl.importDomains

       Possibilities:
               disabled   (0)
               enabled   (1)"
   ::= {er1646v2EthPortSwIXt2PppOEEntry 705039180}

er1646v2EthPortSwIXt2PppOEIpV6RsSend OBJECT-TYPE
   SYNTAX      INTEGER
               {
               disabled (0),
               enabled (1)
               }
   MAX-ACCESS  read-write
   STATUS      current
   DESCRIPTION
      "Path: swPort.editConf.pppoEClient.ipV6.rs.send

       Possibilities:
               disabled   (0)
               enabled   (1)"
   ::= {er1646v2EthPortSwIXt2PppOEEntry 705954048}

er1646v2EthPortSwIXt2PppOEIpV6RsMaxRandomDelay OBJECT-TYPE
   SYNTAX      TimeTicks
   MAX-ACCESS  read-write
   STATUS      current
   DESCRIPTION
      "Path: swPort.editConf.pppoEClient.ipV6.rs.maxRandomDelay

       Time in centi-second."
   ::= {er1646v2EthPortSwIXt2PppOEEntry 705954304}

er1646v2EthPortSwIXt2PppOEIpV6RsInterval OBJECT-TYPE
   SYNTAX      TimeTicks
   MAX-ACCESS  read-write
   STATUS      current
   DESCRIPTION
      "Path: swPort.editConf.pppoEClient.ipV6.rs.interval

       Time in centi-second."
   ::= {er1646v2EthPortSwIXt2PppOEEntry 705954560}

er1646v2EthPortSwIXt2PppOEIpV6RsMaxSolicitations OBJECT-TYPE
   SYNTAX      Integer32
   MAX-ACCESS  read-write
   STATUS      current
   DESCRIPTION
      "Path: swPort.editConf.pppoEClient.ipV6.rs.maxSolicitations"
   ::= {er1646v2EthPortSwIXt2PppOEEntry 705954816}

er1646v2EthPortSwIXt2PppOEIpV6TrafficPolicyInbound OBJECT-TYPE
   SYNTAX      DisplayString
   MAX-ACCESS  read-write
   STATUS      current
   DESCRIPTION
      "Path: swPort.editConf.pppoEClient.ipV6.trafficPolicy.inbound"
   ::= {er1646v2EthPortSwIXt2PppOEEntry 705364224}

er1646v2EthPortSwIXt2PppOEIpV6TrafficPolicyOutbound OBJECT-TYPE
   SYNTAX      DisplayString
   MAX-ACCESS  read-write
   STATUS      current
   DESCRIPTION
      "Path: swPort.editConf.pppoEClient.ipV6.trafficPolicy.outbound"
   ::= {er1646v2EthPortSwIXt2PppOEEntry 705364480}

er1646v2EthPortSwIXt2PppOEIpV6FirewallZone OBJECT-TYPE
   SYNTAX      DisplayString
   MAX-ACCESS  read-write
   STATUS      current
   DESCRIPTION
      "Path: swPort.editConf.pppoEClient.ipV6.firewall.zone"
   ::= {er1646v2EthPortSwIXt2PppOEEntry 705429760}

er1646v2EthPortSwIXt2PppOEIpV6DhcpClientAddrAC OBJECT-TYPE
   SYNTAX      INTEGER
               {
               disabled (0),
               enabled (1)
               }
   MAX-ACCESS  read-write
   STATUS      current
   DESCRIPTION
      "Path: swPort.editConf.pppoEClient.ipV6.dhcp.client.addrAutoConfig

       Possibilities:
               disabled   (0)
               enabled   (1)"
   ::= {er1646v2EthPortSwIXt2PppOEEntry 705307648}

er1646v2EthPortSwIXt2PppOEIpV6DhcpClientPrDelMode OBJECT-TYPE
   SYNTAX      INTEGER
               {
               disabled (0),
               enabled (1)
               }
   MAX-ACCESS  read-write
   STATUS      current
   DESCRIPTION
      "Path: swPort.editConf.pppoEClient.ipV6.dhcp.client.pd.mode

       Possibilities:
               disabled   (0)
               enabled   (1)"
   ::= {er1646v2EthPortSwIXt2PppOEEntry 705308676}

er1646v2EthPortSwIXt2PppOEIpV6DhcpClientPrDelPool OBJECT-TYPE
   SYNTAX      DisplayString
   MAX-ACCESS  read-write
   STATUS      current
   DESCRIPTION
      "Path: swPort.editConf.pppoEClient.ipV6.dhcp.client.pd.pool"
   ::= {er1646v2EthPortSwIXt2PppOEEntry 705308680}

er1646v2EthPortSwIXt2PppOEIpV6DhcpClientPrDelPdExclOpt OBJECT-TYPE
   SYNTAX      INTEGER
               {
               disabled (0),
               enabled (1)
               }
   MAX-ACCESS  read-write
   STATUS      current
   DESCRIPTION
      "Path: swPort.editConf.pppoEClient.ipV6.dhcp.client.pd.pdExclOpt

       Possibilities:
               disabled   (0)
               enabled   (1)"
   ::= {er1646v2EthPortSwIXt2PppOEEntry 705308684}

er1646v2EthPortSwIXt2PppOEIpV6DhcpClientDnsServerPref OBJECT-TYPE
   SYNTAX      Integer32
   MAX-ACCESS  read-write
   STATUS      current
   DESCRIPTION
      "Path: swPort.editConf.pppoEClient.ipV6.dhcp.client.dns.serverPref"
   ::= {er1646v2EthPortSwIXt2PppOEEntry 705310724}

er1646v2EthPortSwIXt2PppOEIpV6DhcpClientRapidCommit OBJECT-TYPE
   SYNTAX      INTEGER
               {
               disabled (0),
               enabled (1)
               }
   MAX-ACCESS  read-write
   STATUS      current
   DESCRIPTION
      "Path: swPort.editConf.pppoEClient.ipV6.dhcp.client.rapidCommit

       Possibilities:
               disabled   (0)
               enabled   (1)"
   ::= {er1646v2EthPortSwIXt2PppOEEntry 705309696}

er1646v2EthPortSwIXt2PppOEIpV6DhcpClientTimersSolTimeOut OBJECT-TYPE
   SYNTAX      TimeTicks
   MAX-ACCESS  read-write
   STATUS      current
   DESCRIPTION
      "Path: swPort.editConf.pppoEClient.ipV6.dhcp.client.timers.solTimeOut

       Time in centi-second."
   ::= {er1646v2EthPortSwIXt2PppOEEntry 705311748}

er1646v2EthPortSwIXt2PppOEIpV6DhcpClientTimersSolMaxRt OBJECT-TYPE
   SYNTAX      TimeTicks
   MAX-ACCESS  read-write
   STATUS      current
   DESCRIPTION
      "Path: swPort.editConf.pppoEClient.ipV6.dhcp.client.timers.solMaxRt

       Time in centi-second."
   ::= {er1646v2EthPortSwIXt2PppOEEntry 705311752}

er1646v2EthPortSwIXt2PppOEIpV6DhcpClientTimersInfoRefresh OBJECT-TYPE
   SYNTAX      TimeTicks
   MAX-ACCESS  read-write
   STATUS      current
   DESCRIPTION
      "Path: swPort.editConf.pppoEClient.ipV6.dhcp.client.timers.infoRefresh

       Time in centi-second."
   ::= {er1646v2EthPortSwIXt2PppOEEntry 705311756}

er1646v2EthPortSwIXt2PppOEIpV6DhcpServerMode OBJECT-TYPE
   SYNTAX      INTEGER
               {
               disabled (0),
               enabled (1)
               }
   MAX-ACCESS  read-write
   STATUS      current
   DESCRIPTION
      "Path: swPort.editConf.pppoEClient.ipV6.dhcp.server.mode

       Possibilities:
               disabled   (0)
               enabled   (1)"
   ::= {er1646v2EthPortSwIXt2PppOEEntry 705315840}

er1646v2EthPortSwIXt2PppOEIpV6DhcpServerPreference OBJECT-TYPE
   SYNTAX      Integer32
   MAX-ACCESS  read-write
   STATUS      current
   DESCRIPTION
      "Path: swPort.editConf.pppoEClient.ipV6.dhcp.server.preference"
   ::= {er1646v2EthPortSwIXt2PppOEEntry 705316864}

er1646v2EthPortSwIXt2PppOEIpV6DhcpServerPool OBJECT-TYPE
   SYNTAX      DisplayString
   MAX-ACCESS  read-write
   STATUS      current
   DESCRIPTION
      "Path: swPort.editConf.pppoEClient.ipV6.dhcp.server.pool"
   ::= {er1646v2EthPortSwIXt2PppOEEntry 705317888}

er1646v2EthPortSwIXt2PppOEIpV6DhcpServerRapidCommit OBJECT-TYPE
   SYNTAX      INTEGER
               {
               disabled (0),
               enabled (1)
               }
   MAX-ACCESS  read-write
   STATUS      current
   DESCRIPTION
      "Path: swPort.editConf.pppoEClient.ipV6.dhcp.server.rapidCommit

       Possibilities:
               disabled   (0)
               enabled   (1)"
   ::= {er1646v2EthPortSwIXt2PppOEEntry 705318912}

er1646v2EthPortSwIXt2PppOEIpV6DhcpServerTimersInfoRefresh OBJECT-TYPE
   SYNTAX      TimeTicks
   MAX-ACCESS  read-write
   STATUS      current
   DESCRIPTION
      "Path: swPort.editConf.pppoEClient.ipV6.dhcp.server.timers.infoRefresh

       Time in centi-second."
   ::= {er1646v2EthPortSwIXt2PppOEEntry 705319940}

er1646v2EthPortSwIXt2PppOEIpV6DhcpRelayMode OBJECT-TYPE
   SYNTAX      INTEGER
               {
               disabled (0),
               enabled (1)
               }
   MAX-ACCESS  read-write
   STATUS      current
   DESCRIPTION
      "Path: swPort.editConf.pppoEClient.ipV6.dhcp.relay.mode

       Possibilities:
               disabled   (0)
               enabled   (1)"
   ::= {er1646v2EthPortSwIXt2PppOEEntry 705323040}

er1646v2EthPortSwIXt2PppOEIpV6SendRedirect OBJECT-TYPE
   SYNTAX      INTEGER
               {
               disabled (0),
               enabled (1)
               }
   MAX-ACCESS  read-write
   STATUS      current
   DESCRIPTION
      "Path: swPort.editConf.pppoEClient.ipV6.sendRedirect

       Possibilities:
               disabled   (0)
               enabled   (1)"
   ::= {er1646v2EthPortSwIXt2PppOEEntry 705101824}

er1646v2EthPortSwIXt2PppOEIpV6LinkMtu OBJECT-TYPE
   SYNTAX      Integer32
   MAX-ACCESS  read-write
   STATUS      current
   DESCRIPTION
      "Path: swPort.editConf.pppoEClient.ipV6.linkMtu"
   ::= {er1646v2EthPortSwIXt2PppOEEntry 705167360}

er1646v2EthPortSwIXt2PppOEIpV6InterfaceId OBJECT-TYPE
   SYNTAX      OCTET STRING
   MAX-ACCESS  read-write
   STATUS      current
   DESCRIPTION
      "Path: swPort.editConf.pppoEClient.ipV6.interfaceId"
   ::= {er1646v2EthPortSwIXt2PppOEEntry 705232896}

er1646v2EthPortSwIXt2PppOEIpV6MF OBJECT-TYPE
   SYNTAX      Integer32
   MAX-ACCESS  read-write
   STATUS      current
   DESCRIPTION
      "Path: swPort.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2EthPortSwIXt2PppOEEntry 705757184}

er1646v2EthPortSwIXt2PppOEIpV6IcmpMessagesNoRoute OBJECT-TYPE
   SYNTAX      INTEGER
               {
               disabled (0),
               enabled (1)
               }
   MAX-ACCESS  read-write
   STATUS      current
   DESCRIPTION
      "Path: swPort.editConf.pppoEClient.ipV6.icmpMessages.noRoute

       Possibilities:
               disabled   (0)
               enabled   (1)"
   ::= {er1646v2EthPortSwIXt2PppOEEntry 705822976}

er1646v2EthPortSwIXt2PppOEIpV6IcmpMessagesBeyondScope OBJECT-TYPE
   SYNTAX      INTEGER
               {
               disabled (0),
               enabled (1)
               }
   MAX-ACCESS  read-write
   STATUS      current
   DESCRIPTION
      "Path: swPort.editConf.pppoEClient.ipV6.icmpMessages.beyondScope

       Possibilities:
               disabled   (0)
               enabled   (1)"
   ::= {er1646v2EthPortSwIXt2PppOEEntry 705823488}

er1646v2EthPortSwIXt2PppOEIpV6IcmpMessagesAddressUnreachable OBJECT-TYPE
   SYNTAX      INTEGER
               {
               disabled (0),
               enabled (1)
               }
   MAX-ACCESS  read-write
   STATUS      current
   DESCRIPTION
      "Path: swPort.editConf.pppoEClient.ipV6.icmpMessages.addressUnreachable

       Possibilities:
               disabled   (0)
               enabled   (1)"
   ::= {er1646v2EthPortSwIXt2PppOEEntry 705823744}

er1646v2EthPortSwIXt2PppOEIpV6IcmpMessagesPortUnreachable OBJECT-TYPE
   SYNTAX      INTEGER
               {
               disabled (0),
               enabled (1)
               }
   MAX-ACCESS  read-write
   STATUS      current
   DESCRIPTION
      "Path: swPort.editConf.pppoEClient.ipV6.icmpMessages.portUnreachable

       Possibilities:
               disabled   (0)
               enabled   (1)"
   ::= {er1646v2EthPortSwIXt2PppOEEntry 705824000}

er1646v2EthPortSwIXt2PppOEIpV6IcmpMessagesPacketTooBig OBJECT-TYPE
   SYNTAX      INTEGER
               {
               disabled (0),
               enabled (1)
               }
   MAX-ACCESS  read-write
   STATUS      current
   DESCRIPTION
      "Path: swPort.editConf.pppoEClient.ipV6.icmpMessages.packetTooBig

       Possibilities:
               disabled   (0)
               enabled   (1)"
   ::= {er1646v2EthPortSwIXt2PppOEEntry 705825280}

er1646v2EthPortSwIXt2PppOEIpV6IcmpMessagesHopLimitExceeded OBJECT-TYPE
   SYNTAX      INTEGER
               {
               disabled (0),
               enabled (1)
               }
   MAX-ACCESS  read-write
   STATUS      current
   DESCRIPTION
      "Path: swPort.editConf.pppoEClient.ipV6.icmpMessages.hopLimitExceeded

       Possibilities:
               disabled   (0)
               enabled   (1)"
   ::= {er1646v2EthPortSwIXt2PppOEEntry 705827840}

er1646v2EthPortSwIXt2PppOEIpV6IcmpMessagesFragTimeExceeded OBJECT-TYPE
   SYNTAX      INTEGER
               {
               disabled (0),
               enabled (1)
               }
   MAX-ACCESS  read-write
   STATUS      current
   DESCRIPTION
      "Path: swPort.editConf.pppoEClient.ipV6.icmpMessages.fragTimeExceeded

       Possibilities:
               disabled   (0)
               enabled   (1)"
   ::= {er1646v2EthPortSwIXt2PppOEEntry 705828096}

er1646v2EthPortSwIXt2PppOEIpV6IcmpMessagesHeaderFieldErr OBJECT-TYPE
   SYNTAX      INTEGER
               {
               disabled (0),
               enabled (1)
               }
   MAX-ACCESS  read-write
   STATUS      current
   DESCRIPTION
      "Path: swPort.editConf.pppoEClient.ipV6.icmpMessages.headerFieldErr

       Possibilities:
               disabled   (0)
               enabled   (1)"
   ::= {er1646v2EthPortSwIXt2PppOEEntry 705830400}

er1646v2EthPortSwIXt2PppOEIpV6IcmpMessagesOptionUnrecognized OBJECT-TYPE
   SYNTAX      INTEGER
               {
               disabled (0),
               enabled (1)
               }
   MAX-ACCESS  read-write
   STATUS      current
   DESCRIPTION
      "Path: swPort.editConf.pppoEClient.ipV6.icmpMessages.optionUnrecognized

       Possibilities:
               disabled   (0)
               enabled   (1)"
   ::= {er1646v2EthPortSwIXt2PppOEEntry 705830912}

er1646v2EthPortSwIXt2PppOEIpV6IcmpMessagesRedirect OBJECT-TYPE
   SYNTAX      INTEGER
               {
               disabled (0),
               enabled (1)
               }
   MAX-ACCESS  read-write
   STATUS      current
   DESCRIPTION
      "Path: swPort.editConf.pppoEClient.ipV6.icmpMessages.redirect

       Possibilities:
               disabled   (0)
               enabled   (1)"
   ::= {er1646v2EthPortSwIXt2PppOEEntry 705832960}

er1646v2EthPortSwIXt2PppOEPppLnkMOperation OBJECT-TYPE
   SYNTAX      INTEGER
               {
               disabled (0),
               enabled (1)
               }
   MAX-ACCESS  read-write
   STATUS      current
   DESCRIPTION
      "Path: swPort.editConf.pppoEClient.ppp.linkMonitoring.operation

       Possibilities:
               disabled   (0)
               enabled   (1)"
   ::= {er1646v2EthPortSwIXt2PppOEEntry 251724032}

er1646v2EthPortSwIXt2PppOEPppLnkMInterval OBJECT-TYPE
   SYNTAX      TimeTicks
   MAX-ACCESS  read-write
   STATUS      current
   DESCRIPTION
      "Path: swPort.editConf.pppoEClient.ppp.linkMonitoring.interval

       Time in centi-second."
   ::= {er1646v2EthPortSwIXt2PppOEEntry 251724288}

er1646v2EthPortSwIXt2PppOEPppLnkMRepTimeOut OBJECT-TYPE
   SYNTAX      TimeTicks
   MAX-ACCESS  read-write
   STATUS      current
   DESCRIPTION
      "Path: swPort.editConf.pppoEClient.ppp.linkMonitoring.replyTimeOut

       Time in centi-second."
   ::= {er1646v2EthPortSwIXt2PppOEEntry 251724544}

er1646v2EthPortSwIXt2PppOEPppLnkMFailsPrmt OBJECT-TYPE
   SYNTAX      Integer32
   MAX-ACCESS  read-write
   STATUS      current
   DESCRIPTION
      "Path: swPort.editConf.pppoEClient.ppp.linkMonitoring.failsPermitted"
   ::= {er1646v2EthPortSwIXt2PppOEEntry 251724800}

er1646v2EthPortSwIXt2PppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: swPort.editConf.pppoEClient.ppp.authentication

       Possibilities:
               disabled   (0)
               chap   (1)
               pap   (2)
               chapOrPap   (3)
               msChap   (4)
               msChapV2   (5)"
   ::= {er1646v2EthPortSwIXt2PppOEEntry 251789312}

er1646v2EthPortSwIXt2PppOEPppAuthenPeriod OBJECT-TYPE
   SYNTAX      TimeTicks
   MAX-ACCESS  read-write
   STATUS      current
   DESCRIPTION
      "Path: swPort.editConf.pppoEClient.ppp.authenPeriod

       Time in centi-second."
   ::= {er1646v2EthPortSwIXt2PppOEEntry 251854848}

er1646v2EthPortSwIXt2PppOEPppSessionName OBJECT-TYPE
   SYNTAX      DisplayString
   MAX-ACCESS  read-write
   STATUS      current
   DESCRIPTION
      "Path: swPort.editConf.pppoEClient.ppp.sessionName"
   ::= {er1646v2EthPortSwIXt2PppOEEntry 251985920}

er1646v2EthPortSwIXt2PppOEPppSessionSecret OBJECT-TYPE
   SYNTAX      DisplayString
   MAX-ACCESS  read-write
   STATUS      current
   DESCRIPTION
      "Path: swPort.editConf.pppoEClient.ppp.sessionSecret"
   ::= {er1646v2EthPortSwIXt2PppOEEntry 252051456}

er1646v2EthPortSwIXt2PppOEPppEncModeSessionSecret OBJECT-TYPE
   SYNTAX      INTEGER
               {
               none (1),
               encrypt (2),
               encType1 (3),
               invalid (128)
               }
   MAX-ACCESS  read-write
   STATUS      current
   DESCRIPTION
      "Path: swPort.editConf.pppoEClient.ppp.encModeSessionSecret

       Possibilities:
               none   (1)
               encrypt   (2)
               encType1   (3)
               invalid   (128)"
   ::= {er1646v2EthPortSwIXt2PppOEEntry 252182528}

er1646v2EthPortSwIXt2PppOEPppEncSessionSecret OBJECT-TYPE
   SYNTAX      DisplayString
   MAX-ACCESS  read-write
   STATUS      current
   DESCRIPTION
      "Path: swPort.editConf.pppoEClient.ppp.encSessionSecret"
   ::= {er1646v2EthPortSwIXt2PppOEEntry 252248064}

er1646v2EthPortSwIXt2PppOEPppServiceName OBJECT-TYPE
   SYNTAX      DisplayString
   MAX-ACCESS  read-write
   STATUS      current
   DESCRIPTION
      "Path: swPort.editConf.pppoEClient.ppp.serviceName"
   ::= {er1646v2EthPortSwIXt2PppOEEntry 252116992}

er1646v2EthPortSwIXt2PppOEIpH OBJECT-TYPE
   SYNTAX      SEQUENCE OF Er1646v2EthPortSwIXt2PppOEIpHEntry
   MAX-ACCESS  not-accessible
   STATUS      current
   DESCRIPTION
      ""
   ::= {er1646v2EthPortSwIXt2PppOE 51314688}

er1646v2EthPortSwIXt2PppOEIpHEntry OBJECT-TYPE
   SYNTAX      Er1646v2EthPortSwIXt2PppOEIpHEntry
   MAX-ACCESS  not-accessible
   STATUS      current
   DESCRIPTION
      ""
   INDEX      { er1646v2EthPortSwIXt2PppOEIpHGlobalIx,
                er1646v2EthPortSwIXt2PppOETableIx,
                er1646v2EthPortSwIXt2PppOEIpHTableIx }
   ::= {er1646v2EthPortSwIXt2PppOEIpH 1}

Er1646v2EthPortSwIXt2PppOEIpHEntry ::=
   SEQUENCE
      {
      er1646v2EthPortSwIXt2PppOEIpHActions
         VariableLengthTableActions,
      er1646v2EthPortSwIXt2PppOEIpHGlobalIx
         GlobalIndex,
      er1646v2EthPortSwIXt2PppOEIpHTableIx
         TableIndex,
      er1646v2EthPortSwIXt2PppOEIpHAddress
         IpAddress,
      er1646v2EthPortSwIXt2PppOEIpHDhcpRelayOptionSubscriberId
         DisplayString
      }

er1646v2EthPortSwIXt2PppOEIpHActions OBJECT-TYPE
   SYNTAX      VariableLengthTableActions
   MAX-ACCESS  read-write
   STATUS      current
   DESCRIPTION
      "By way of this field, some manipulations
       on this table may be performed."
   ::= {er1646v2EthPortSwIXt2PppOEIpHEntry 2}

er1646v2EthPortSwIXt2PppOEIpHGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEIpHEntry 10}

er1646v2EthPortSwIXt2PppOEIpHTableIx OBJECT-TYPE
   SYNTAX      TableIndex
   MAX-ACCESS  not-accessible
   STATUS      current
   DESCRIPTION
      ""
   ::= {er1646v2EthPortSwIXt2PppOEIpHEntry 11}

er1646v2EthPortSwIXt2PppOEIpHAddress OBJECT-TYPE
   SYNTAX      IpAddress
   MAX-ACCESS  read-write
   STATUS      current
   DESCRIPTION
      "Path: swPort.editConf.pppoEClient.ip.helpers.address"
   ::= {er1646v2EthPortSwIXt2PppOEIpHEntry 16777216}

er1646v2EthPortSwIXt2PppOEIpHDhcpRelayOptionSubscriberId OBJECT-TYPE
   SYNTAX      DisplayString
   MAX-ACCESS  read-write
   STATUS      current
   DESCRIPTION
      "Path: swPort.editConf.pppoEClient.ip.helpers.dhcpRelayOption.subscriberId"
   ::= {er1646v2EthPortSwIXt2PppOEIpHEntry 33947648}

er1646v2EthPortSwIXt2PppOEIpV6Addresses OBJECT-TYPE
   SYNTAX      SEQUENCE OF Er1646v2EthPortSwIXt2PppOEIpV6AddressesEntry
   MAX-ACCESS  not-accessible
   STATUS      current
   DESCRIPTION
      ""
   ::= {er1646v2EthPortSwIXt2PppOE 704839680}

er1646v2EthPortSwIXt2PppOEIpV6AddressesEntry OBJECT-TYPE
   SYNTAX      Er1646v2EthPortSwIXt2PppOEIpV6AddressesEntry
   MAX-ACCESS  not-accessible
   STATUS      current
   DESCRIPTION
      ""
   INDEX      { er1646v2EthPortSwIXt2PppOEIpV6AddressesGlobalIx,
                er1646v2EthPortSwIXt2PppOETableIx,
                er1646v2EthPortSwIXt2PppOEIpV6AddressesTableIx }
   ::= {er1646v2EthPortSwIXt2PppOEIpV6Addresses 1}

Er1646v2EthPortSwIXt2PppOEIpV6AddressesEntry ::=
   SEQUENCE
      {
      er1646v2EthPortSwIXt2PppOEIpV6AddressesActions
         VariableLengthTableActions,
      er1646v2EthPortSwIXt2PppOEIpV6AddressesGlobalIx
         GlobalIndex,
      er1646v2EthPortSwIXt2PppOEIpV6AddressesTableIx
         TableIndex,
      er1646v2EthPortSwIXt2PppOEIpV6AddressesType
         INTEGER,
      er1646v2EthPortSwIXt2PppOEIpV6AddressesAddress
         Ipv6Address,
      er1646v2EthPortSwIXt2PppOEIpV6AddressesPrefixLength
         Integer32,
      er1646v2EthPortSwIXt2PppOEIpV6AddressesGeneralPrefix
         DisplayString,
      er1646v2EthPortSwIXt2PppOEIpV6AddressesRaSend
         INTEGER,
      er1646v2EthPortSwIXt2PppOEIpV6AddressesRaOnLinkFlag
         INTEGER,
      er1646v2EthPortSwIXt2PppOEIpV6AddressesRaAutoFlag
         INTEGER,
      er1646v2EthPortSwIXt2PppOEIpV6AddressesRaValidLifeTime
         TimeTicks,
      er1646v2EthPortSwIXt2PppOEIpV6AddressesRaValidLTMode
         INTEGER,
      er1646v2EthPortSwIXt2PppOEIpV6AddressesRaPrefLifeTime
         TimeTicks,
      er1646v2EthPortSwIXt2PppOEIpV6AddressesRaPrefLTMode
         INTEGER
      }

er1646v2EthPortSwIXt2PppOEIpV6AddressesActions OBJECT-TYPE
   SYNTAX      VariableLengthTableActions
   MAX-ACCESS  read-write
   STATUS      current
   DESCRIPTION
      "By way of this field, some manipulations
       on this table may be performed."
   ::= {er1646v2EthPortSwIXt2PppOEIpV6AddressesEntry 2}

er1646v2EthPortSwIXt2PppOEIpV6AddressesGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEIpV6AddressesEntry 10}

er1646v2EthPortSwIXt2PppOEIpV6AddressesTableIx OBJECT-TYPE
   SYNTAX      TableIndex
   MAX-ACCESS  not-accessible
   STATUS      current
   DESCRIPTION
      ""
   ::= {er1646v2EthPortSwIXt2PppOEIpV6AddressesEntry 11}

er1646v2EthPortSwIXt2PppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: swPort.editConf.pppoEClient.ipV6.addresses.type

       Possibilities:
               unicast   (0)
               eui64   (1)
               anycast   (2)
               linkLocal   (3)
               generalPrefix   (4)"
   ::= {er1646v2EthPortSwIXt2PppOEIpV6AddressesEntry 50331648}

er1646v2EthPortSwIXt2PppOEIpV6AddressesAddress OBJECT-TYPE
   SYNTAX      Ipv6Address
   MAX-ACCESS  read-write
   STATUS      current
   DESCRIPTION
      "Path: swPort.editConf.pppoEClient.ipV6.addresses.address

       ipv6 address"
   ::= {er1646v2EthPortSwIXt2PppOEIpV6AddressesEntry 16777216}

er1646v2EthPortSwIXt2PppOEIpV6AddressesPrefixLength OBJECT-TYPE
   SYNTAX      Integer32
   MAX-ACCESS  read-write
   STATUS      current
   DESCRIPTION
      "Path: swPort.editConf.pppoEClient.ipV6.addresses.prefixLength"
   ::= {er1646v2EthPortSwIXt2PppOEIpV6AddressesEntry 33554432}

er1646v2EthPortSwIXt2PppOEIpV6AddressesGeneralPrefix OBJECT-TYPE
   SYNTAX      DisplayString
   MAX-ACCESS  read-write
   STATUS      current
   DESCRIPTION
      "Path: swPort.editConf.pppoEClient.ipV6.addresses.generalPrefix"
   ::= {er1646v2EthPortSwIXt2PppOEIpV6AddressesEntry 83886080}

er1646v2EthPortSwIXt2PppOEIpV6AddressesRaSend OBJECT-TYPE
   SYNTAX      INTEGER
               {
               disabled (0),
               enabled (1)
               }
   MAX-ACCESS  read-write
   STATUS      current
   DESCRIPTION
      "Path: swPort.editConf.pppoEClient.ipV6.addresses.ra.send

       Possibilities:
               disabled   (0)
               enabled   (1)"
   ::= {er1646v2EthPortSwIXt2PppOEIpV6AddressesEntry 67174400}

er1646v2EthPortSwIXt2PppOEIpV6AddressesRaOnLinkFlag OBJECT-TYPE
   SYNTAX      INTEGER
               {
               disabled (0),
               enabled (1)
               }
   MAX-ACCESS  read-write
   STATUS      current
   DESCRIPTION
      "Path: swPort.editConf.pppoEClient.ipV6.addresses.ra.onLinkFlag

       Possibilities:
               disabled   (0)
               enabled   (1)"
   ::= {er1646v2EthPortSwIXt2PppOEIpV6AddressesEntry 67371008}

er1646v2EthPortSwIXt2PppOEIpV6AddressesRaAutoFlag OBJECT-TYPE
   SYNTAX      INTEGER
               {
               disabled (0),
               enabled (1)
               }
   MAX-ACCESS  read-write
   STATUS      current
   DESCRIPTION
      "Path: swPort.editConf.pppoEClient.ipV6.addresses.ra.autonomousFlag

       Possibilities:
               disabled   (0)
               enabled   (1)"
   ::= {er1646v2EthPortSwIXt2PppOEIpV6AddressesEntry 67567616}

er1646v2EthPortSwIXt2PppOEIpV6AddressesRaValidLifeTime OBJECT-TYPE
   SYNTAX      TimeTicks
   MAX-ACCESS  read-write
   STATUS      current
   DESCRIPTION
      "Path: swPort.editConf.pppoEClient.ipV6.addresses.ra.validLifeTime

       Time in centi-second."
   ::= {er1646v2EthPortSwIXt2PppOEIpV6AddressesEntry 67239936}

er1646v2EthPortSwIXt2PppOEIpV6AddressesRaValidLTMode OBJECT-TYPE
   SYNTAX      INTEGER
               {
               fixed (0),
               infinite (2)
               }
   MAX-ACCESS  read-write
   STATUS      current
   DESCRIPTION
      "Path: swPort.editConf.pppoEClient.ipV6.addresses.ra.validLifeTimeMode

       Possibilities:
               fixed   (0)
               infinite   (2)"
   ::= {er1646v2EthPortSwIXt2PppOEIpV6AddressesEntry 67305472}

er1646v2EthPortSwIXt2PppOEIpV6AddressesRaPrefLifeTime OBJECT-TYPE
   SYNTAX      TimeTicks
   MAX-ACCESS  read-write
   STATUS      current
   DESCRIPTION
      "Path: swPort.editConf.pppoEClient.ipV6.addresses.ra.prefLifeTime

       Time in centi-second."
   ::= {er1646v2EthPortSwIXt2PppOEIpV6AddressesEntry 67436544}

er1646v2EthPortSwIXt2PppOEIpV6AddressesRaPrefLTMode OBJECT-TYPE
   SYNTAX      INTEGER
               {
               fixed (0),
               infinite (2)
               }
   MAX-ACCESS  read-write
   STATUS      current
   DESCRIPTION
      "Path: swPort.editConf.pppoEClient.ipV6.addresses.ra.prefLifeTimeMode

       Possibilities:
               fixed   (0)
               infinite   (2)"
   ::= {er1646v2EthPortSwIXt2PppOEIpV6AddressesEntry 67502080}

er1646v2EthPortSwIXt2PppOEIpV6RaDnsOptionsRdnssServers OBJECT-TYPE
   SYNTAX      SEQUENCE OF Er1646v2EthPortSwIXt2PppOEIpV6RaDnsOptionsRdnssServersEntry
   MAX-ACCESS  not-accessible
   STATUS      current
   DESCRIPTION
      ""
   ::= {er1646v2EthPortSwIXt2PppOE 705039144}

er1646v2EthPortSwIXt2PppOEIpV6RaDnsOptionsRdnssServersEntry OBJECT-TYPE
   SYNTAX      Er1646v2EthPortSwIXt2PppOEIpV6RaDnsOptionsRdnssServersEntry
   MAX-ACCESS  not-accessible
   STATUS      current
   DESCRIPTION
      ""
   INDEX      { er1646v2EthPortSwIXt2PppOEIpV6RaDnsOptionsRdnssServersGlobalIx,
                er1646v2EthPortSwIXt2PppOETableIx,
                er1646v2EthPortSwIXt2PppOEIpV6RaDnsOptionsRdnssServersTableIx }
   ::= {er1646v2EthPortSwIXt2PppOEIpV6RaDnsOptionsRdnssServers 1}

Er1646v2EthPortSwIXt2PppOEIpV6RaDnsOptionsRdnssServersEntry ::=
   SEQUENCE
      {
      er1646v2EthPortSwIXt2PppOEIpV6RaDnsOptionsRdnssServersActions
         VariableLengthTableActions,
      er1646v2EthPortSwIXt2PppOEIpV6RaDnsOptionsRdnssServersGlobalIx
         GlobalIndex,
      er1646v2EthPortSwIXt2PppOEIpV6RaDnsOptionsRdnssServersTableIx
         TableIndex,
      er1646v2EthPortSwIXt2PppOEIpV6RaDnsOptionsRdnssServersAddress
         Ipv6Address
      }

er1646v2EthPortSwIXt2PppOEIpV6RaDnsOptionsRdnssServersActions OBJECT-TYPE
   SYNTAX      VariableLengthTableActions
   MAX-ACCESS  read-write
   STATUS      current
   DESCRIPTION
      "By way of this field, some manipulations
       on this table may be performed."
   ::= {er1646v2EthPortSwIXt2PppOEIpV6RaDnsOptionsRdnssServersEntry 2}

er1646v2EthPortSwIXt2PppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEIpV6RaDnsOptionsRdnssServersEntry 10}

er1646v2EthPortSwIXt2PppOEIpV6RaDnsOptionsRdnssServersTableIx OBJECT-TYPE
   SYNTAX      TableIndex
   MAX-ACCESS  not-accessible
   STATUS      current
   DESCRIPTION
      ""
   ::= {er1646v2EthPortSwIXt2PppOEIpV6RaDnsOptionsRdnssServersEntry 11}

er1646v2EthPortSwIXt2PppOEIpV6RaDnsOptionsRdnssServersAddress OBJECT-TYPE
   SYNTAX      Ipv6Address
   MAX-ACCESS  read-write
   STATUS      current
   DESCRIPTION
      "Path: swPort.editConf.pppoEClient.ipV6.ra.dnsOptions.rdnss.servers.address

       ipv6 address"
   ::= {er1646v2EthPortSwIXt2PppOEIpV6RaDnsOptionsRdnssServersEntry 16777216}

er1646v2EthPortSwIXt2PppOEIpV6RaDnsOptionsDnsslDomains OBJECT-TYPE
   SYNTAX      SEQUENCE OF Er1646v2EthPortSwIXt2PppOEIpV6RaDnsOptionsDnsslDomainsEntry
   MAX-ACCESS  not-accessible
   STATUS      current
   DESCRIPTION
      ""
   ::= {er1646v2EthPortSwIXt2PppOE 705039176}

er1646v2EthPortSwIXt2PppOEIpV6RaDnsOptionsDnsslDomainsEntry OBJECT-TYPE
   SYNTAX      Er1646v2EthPortSwIXt2PppOEIpV6RaDnsOptionsDnsslDomainsEntry
   MAX-ACCESS  not-accessible
   STATUS      current
   DESCRIPTION
      ""
   INDEX      { er1646v2EthPortSwIXt2PppOEIpV6RaDnsOptionsDnsslDomainsGlobalIx,
                er1646v2EthPortSwIXt2PppOETableIx,
                er1646v2EthPortSwIXt2PppOEIpV6RaDnsOptionsDnsslDomainsTableIx }
   ::= {er1646v2EthPortSwIXt2PppOEIpV6RaDnsOptionsDnsslDomains 1}

Er1646v2EthPortSwIXt2PppOEIpV6RaDnsOptionsDnsslDomainsEntry ::=
   SEQUENCE
      {
      er1646v2EthPortSwIXt2PppOEIpV6RaDnsOptionsDnsslDomainsActions
         VariableLengthTableActions,
      er1646v2EthPortSwIXt2PppOEIpV6RaDnsOptionsDnsslDomainsGlobalIx
         GlobalIndex,
      er1646v2EthPortSwIXt2PppOEIpV6RaDnsOptionsDnsslDomainsTableIx
         TableIndex,
      er1646v2EthPortSwIXt2PppOEIpV6RaDnsOptionsDnsslDomainsName
         DisplayString
      }

er1646v2EthPortSwIXt2PppOEIpV6RaDnsOptionsDnsslDomainsActions OBJECT-TYPE
   SYNTAX      VariableLengthTableActions
   MAX-ACCESS  read-write
   STATUS      current
   DESCRIPTION
      "By way of this field, some manipulations
       on this table may be performed."
   ::= {er1646v2EthPortSwIXt2PppOEIpV6RaDnsOptionsDnsslDomainsEntry 2}

er1646v2EthPortSwIXt2PppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEIpV6RaDnsOptionsDnsslDomainsEntry 10}

er1646v2EthPortSwIXt2PppOEIpV6RaDnsOptionsDnsslDomainsTableIx OBJECT-TYPE
   SYNTAX      TableIndex
   MAX-ACCESS  not-accessible
   STATUS      current
   DESCRIPTION
      ""
   ::= {er1646v2EthPortSwIXt2PppOEIpV6RaDnsOptionsDnsslDomainsEntry 11}

er1646v2EthPortSwIXt2PppOEIpV6RaDnsOptionsDnsslDomainsName OBJECT-TYPE
   SYNTAX      DisplayString
   MAX-ACCESS  read-write
   STATUS      current
   DESCRIPTION
      "Path: swPort.editConf.pppoEClient.ipV6.ra.dnsOptions.dnssl.domains.name"
   ::= {er1646v2EthPortSwIXt2PppOEIpV6RaDnsOptionsDnsslDomainsEntry 16777216}

er1646v2EthPortSwIXt2PppOEIpV6DhcpClientUserClassOpt OBJECT-TYPE
   SYNTAX      SEQUENCE OF Er1646v2EthPortSwIXt2PppOEIpV6DhcpClientUserClassOptEntry
   MAX-ACCESS  not-accessible
   STATUS      current
   DESCRIPTION
      ""
   ::= {er1646v2EthPortSwIXt2PppOE 705312768}

er1646v2EthPortSwIXt2PppOEIpV6DhcpClientUserClassOptEntry OBJECT-TYPE
   SYNTAX      Er1646v2EthPortSwIXt2PppOEIpV6DhcpClientUserClassOptEntry
   MAX-ACCESS  not-accessible
   STATUS      current
   DESCRIPTION
      ""
   INDEX      { er1646v2EthPortSwIXt2PppOEIpV6DhcpClientUserClassOptGlobalIx,
                er1646v2EthPortSwIXt2PppOETableIx,
                er1646v2EthPortSwIXt2PppOEIpV6DhcpClientUserClassOptTableIx }
   ::= {er1646v2EthPortSwIXt2PppOEIpV6DhcpClientUserClassOpt 1}

Er1646v2EthPortSwIXt2PppOEIpV6DhcpClientUserClassOptEntry ::=
   SEQUENCE
      {
      er1646v2EthPortSwIXt2PppOEIpV6DhcpClientUserClassOptActions
         VariableLengthTableActions,
      er1646v2EthPortSwIXt2PppOEIpV6DhcpClientUserClassOptGlobalIx
         GlobalIndex,
      er1646v2EthPortSwIXt2PppOEIpV6DhcpClientUserClassOptTableIx
         TableIndex,
      er1646v2EthPortSwIXt2PppOEIpV6DhcpClientUserClassOptValueAscii
         DisplayString,
      er1646v2EthPortSwIXt2PppOEIpV6DhcpClientUserClassOptValueDecimal
         Integer32,
      er1646v2EthPortSwIXt2PppOEIpV6DhcpClientUserClassOptValueHexData
         OCTET STRING
      }

er1646v2EthPortSwIXt2PppOEIpV6DhcpClientUserClassOptActions OBJECT-TYPE
   SYNTAX      VariableLengthTableActions
   MAX-ACCESS  read-write
   STATUS      current
   DESCRIPTION
      "By way of this field, some manipulations
       on this table may be performed."
   ::= {er1646v2EthPortSwIXt2PppOEIpV6DhcpClientUserClassOptEntry 2}

er1646v2EthPortSwIXt2PppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEIpV6DhcpClientUserClassOptEntry 10}

er1646v2EthPortSwIXt2PppOEIpV6DhcpClientUserClassOptTableIx OBJECT-TYPE
   SYNTAX      TableIndex
   MAX-ACCESS  not-accessible
   STATUS      current
   DESCRIPTION
      ""
   ::= {er1646v2EthPortSwIXt2PppOEIpV6DhcpClientUserClassOptEntry 11}

er1646v2EthPortSwIXt2PppOEIpV6DhcpClientUserClassOptValueAscii OBJECT-TYPE
   SYNTAX      DisplayString
   MAX-ACCESS  read-write
   STATUS      current
   DESCRIPTION
      "Path: swPort.editConf.pppoEClient.ipV6.dhcp.client.userClassOpt.value.ascii"
   ::= {er1646v2EthPortSwIXt2PppOEIpV6DhcpClientUserClassOptEntry 16842752}

er1646v2EthPortSwIXt2PppOEIpV6DhcpClientUserClassOptValueDecimal OBJECT-TYPE
   SYNTAX      Integer32
   MAX-ACCESS  read-write
   STATUS      current
   DESCRIPTION
      "Path: swPort.editConf.pppoEClient.ipV6.dhcp.client.userClassOpt.value.decimal"
   ::= {er1646v2EthPortSwIXt2PppOEIpV6DhcpClientUserClassOptEntry 16908288}

er1646v2EthPortSwIXt2PppOEIpV6DhcpClientUserClassOptValueHexData OBJECT-TYPE
   SYNTAX      OCTET STRING
   MAX-ACCESS  read-write
   STATUS      current
   DESCRIPTION
      "Path: swPort.editConf.pppoEClient.ipV6.dhcp.client.userClassOpt.value.hexData"
   ::= {er1646v2EthPortSwIXt2PppOEIpV6DhcpClientUserClassOptEntry 16973824}

er1646v2EthPortSwIXt2PppOEIpV6DhcpClientVendorCl OBJECT-TYPE
   SYNTAX      SEQUENCE OF Er1646v2EthPortSwIXt2PppOEIpV6DhcpClientVendorClEntry
   MAX-ACCESS  not-accessible
   STATUS      current
   DESCRIPTION
      ""
   ::= {er1646v2EthPortSwIXt2PppOE 705313792}

er1646v2EthPortSwIXt2PppOEIpV6DhcpClientVendorClEntry OBJECT-TYPE
   SYNTAX      Er1646v2EthPortSwIXt2PppOEIpV6DhcpClientVendorClEntry
   MAX-ACCESS  not-accessible
   STATUS      current
   DESCRIPTION
      ""
   INDEX      { er1646v2EthPortSwIXt2PppOEIpV6DhcpClientVendorClGlobalIx,
                er1646v2EthPortSwIXt2PppOETableIx,
                er1646v2EthPortSwIXt2PppOEIpV6DhcpClientVendorClTableIx }
   ::= {er1646v2EthPortSwIXt2PppOEIpV6DhcpClientVendorCl 1}

Er1646v2EthPortSwIXt2PppOEIpV6DhcpClientVendorClEntry ::=
   SEQUENCE
      {
      er1646v2EthPortSwIXt2PppOEIpV6DhcpClientVendorClActions
         VariableLengthTableActions,
      er1646v2EthPortSwIXt2PppOEIpV6DhcpClientVendorClGlobalIx
         GlobalIndex,
      er1646v2EthPortSwIXt2PppOEIpV6DhcpClientVendorClTableIx
         TableIndex,
      er1646v2EthPortSwIXt2PppOEIpV6DhcpClientVendorClValueAscii
         DisplayString,
      er1646v2EthPortSwIXt2PppOEIpV6DhcpClientVendorClValueDecimal
         Integer32,
      er1646v2EthPortSwIXt2PppOEIpV6DhcpClientVendorClValueHexData
         OCTET STRING
      }

er1646v2EthPortSwIXt2PppOEIpV6DhcpClientVendorClActions OBJECT-TYPE
   SYNTAX      VariableLengthTableActions
   MAX-ACCESS  read-write
   STATUS      current
   DESCRIPTION
      "By way of this field, some manipulations
       on this table may be performed."
   ::= {er1646v2EthPortSwIXt2PppOEIpV6DhcpClientVendorClEntry 2}

er1646v2EthPortSwIXt2PppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEIpV6DhcpClientVendorClEntry 10}

er1646v2EthPortSwIXt2PppOEIpV6DhcpClientVendorClTableIx OBJECT-TYPE
   SYNTAX      TableIndex
   MAX-ACCESS  not-accessible
   STATUS      current
   DESCRIPTION
      ""
   ::= {er1646v2EthPortSwIXt2PppOEIpV6DhcpClientVendorClEntry 11}

er1646v2EthPortSwIXt2PppOEIpV6DhcpClientVendorClValueAscii OBJECT-TYPE
   SYNTAX      DisplayString
   MAX-ACCESS  read-write
   STATUS      current
   DESCRIPTION
      "Path: swPort.editConf.pppoEClient.ipV6.dhcp.client.vendorClassOpt.value.ascii"
   ::= {er1646v2EthPortSwIXt2PppOEIpV6DhcpClientVendorClEntry 16842752}

er1646v2EthPortSwIXt2PppOEIpV6DhcpClientVendorClValueDecimal OBJECT-TYPE
   SYNTAX      Integer32
   MAX-ACCESS  read-write
   STATUS      current
   DESCRIPTION
      "Path: swPort.editConf.pppoEClient.ipV6.dhcp.client.vendorClassOpt.value.decimal"
   ::= {er1646v2EthPortSwIXt2PppOEIpV6DhcpClientVendorClEntry 16908288}

er1646v2EthPortSwIXt2PppOEIpV6DhcpClientVendorClValueHexData OBJECT-TYPE
   SYNTAX      OCTET STRING
   MAX-ACCESS  read-write
   STATUS      current
   DESCRIPTION
      "Path: swPort.editConf.pppoEClient.ipV6.dhcp.client.vendorClassOpt.value.hexData"
   ::= {er1646v2EthPortSwIXt2PppOEIpV6DhcpClientVendorClEntry 16973824}

er1646v2EthPortSwIXt2PppOEIpV6DhcpRelayDestinations OBJECT-TYPE
   SYNTAX      SEQUENCE OF Er1646v2EthPortSwIXt2PppOEIpV6DhcpRelayDestinationsEntry
   MAX-ACCESS  not-accessible
   STATUS      current
   DESCRIPTION
      ""
   ::= {er1646v2EthPortSwIXt2PppOE 705323072}

er1646v2EthPortSwIXt2PppOEIpV6DhcpRelayDestinationsEntry OBJECT-TYPE
   SYNTAX      Er1646v2EthPortSwIXt2PppOEIpV6DhcpRelayDestinationsEntry
   MAX-ACCESS  not-accessible
   STATUS      current
   DESCRIPTION
      ""
   INDEX      { er1646v2EthPortSwIXt2PppOEIpV6DhcpRelayDestinationsGlobalIx,
                er1646v2EthPortSwIXt2PppOETableIx,
                er1646v2EthPortSwIXt2PppOEIpV6DhcpRelayDestinationsTableIx }
   ::= {er1646v2EthPortSwIXt2PppOEIpV6DhcpRelayDestinations 1}

Er1646v2EthPortSwIXt2PppOEIpV6DhcpRelayDestinationsEntry ::=
   SEQUENCE
      {
      er1646v2EthPortSwIXt2PppOEIpV6DhcpRelayDestinationsActions
         VariableLengthTableActions,
      er1646v2EthPortSwIXt2PppOEIpV6DhcpRelayDestinationsGlobalIx
         GlobalIndex,
      er1646v2EthPortSwIXt2PppOEIpV6DhcpRelayDestinationsTableIx
         TableIndex,
      er1646v2EthPortSwIXt2PppOEIpV6DhcpRelayDestinationsAddress
         Ipv6Address,
      er1646v2EthPortSwIXt2PppOEIpV6DhcpRelayDestinationsInterface
         DisplayString
      }

er1646v2EthPortSwIXt2PppOEIpV6DhcpRelayDestinationsActions OBJECT-TYPE
   SYNTAX      VariableLengthTableActions
   MAX-ACCESS  read-write
   STATUS      current
   DESCRIPTION
      "By way of this field, some manipulations
       on this table may be performed."
   ::= {er1646v2EthPortSwIXt2PppOEIpV6DhcpRelayDestinationsEntry 2}

er1646v2EthPortSwIXt2PppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOEIpV6DhcpRelayDestinationsEntry 10}

er1646v2EthPortSwIXt2PppOEIpV6DhcpRelayDestinationsTableIx OBJECT-TYPE
   SYNTAX      TableIndex
   MAX-ACCESS  not-accessible
   STATUS      current
   DESCRIPTION
      ""
   ::= {er1646v2EthPortSwIXt2PppOEIpV6DhcpRelayDestinationsEntry 11}

er1646v2EthPortSwIXt2PppOEIpV6DhcpRelayDestinationsAddress OBJECT-TYPE
   SYNTAX      Ipv6Address
   MAX-ACCESS  read-write
   STATUS      current
   DESCRIPTION
      "Path: swPort.editConf.pppoEClient.ipV6.dhcp.relay.destinations.address

       ipv6 address"
   ::= {er1646v2EthPortSwIXt2PppOEIpV6DhcpRelayDestinationsEntry 16777216}

er1646v2EthPortSwIXt2PppOEIpV6DhcpRelayDestinationsInterface OBJECT-TYPE
   SYNTAX      DisplayString
   MAX-ACCESS  read-write
   STATUS      current
   DESCRIPTION
      "Path: swPort.editConf.pppoEClient.ipV6.dhcp.relay.destinations.interface"
   ::= {er1646v2EthPortSwIXt2PppOEIpV6DhcpRelayDestinationsEntry 33554432}


er1646v2EthPortSwIXt2PppOES OBJECT IDENTIFIER ::= {er1646v2EthPortSwIXt2 37}

er1646v2EthPortSwIXt2PppOESTable OBJECT-TYPE
   SYNTAX      SEQUENCE OF Er1646v2EthPortSwIXt2PppOESEntry
   MAX-ACCESS  not-accessible
   STATUS      current
   DESCRIPTION
      "ppp server name on interface"
   ::= {er1646v2EthPortSwIXt2PppOES 1}

er1646v2EthPortSwIXt2PppOESEntry OBJECT-TYPE
   SYNTAX      Er1646v2EthPortSwIXt2PppOESEntry
   MAX-ACCESS  not-accessible
   STATUS      current
   DESCRIPTION
      ""
   INDEX      { er1646v2EthPortSwIXt2PppOESGlobalIx }
   ::= {er1646v2EthPortSwIXt2PppOESTable 1}

Er1646v2EthPortSwIXt2PppOESEntry ::=
   SEQUENCE
      {
      er1646v2EthPortSwIXt2PppOESGlobalIx
         GlobalIndex,
      er1646v2EthPortSwIXt2PppOESValue
         DisplayString
      }

er1646v2EthPortSwIXt2PppOESGlobalIx OBJECT-TYPE
   SYNTAX      GlobalIndex
   MAX-ACCESS  not-accessible
   STATUS      current
   DESCRIPTION
      "The value of the tlsCntTreeGlobalIndex of the MANAGED OBJECT."
   ::= {er1646v2EthPortSwIXt2PppOESEntry 10}

er1646v2EthPortSwIXt2PppOESValue OBJECT-TYPE
   SYNTAX      DisplayString
   MAX-ACCESS  read-write
   STATUS      current
   DESCRIPTION
      "Path: swPort.editConf.pppoEServer"
   ::= {er1646v2EthPortSwIXt2PppOESEntry 2147483648}


er1646v2EthPortSwIXt2AdminStatus OBJECT IDENTIFIER ::= {er1646v2EthPortSwIXt2 106}

er1646v2EthPortSwIXt2AdminStatusTable OBJECT-TYPE
   SYNTAX      SEQUENCE OF Er1646v2EthPortSwIXt2AdminStatusEntry
   MAX-ACCESS  not-accessible
   STATUS      current
   DESCRIPTION
      "ifAdminStatus"
   ::= {er1646v2EthPortSwIXt2AdminStatus 1}

er1646v2EthPortSwIXt2AdminStatusEntry OBJECT-TYPE
   SYNTAX      Er1646v2EthPortSwIXt2AdminStatusEntry
   MAX-ACCESS  not-accessible
   STATUS      current
   DESCRIPTION
      ""
   INDEX      { er1646v2EthPortSwIXt2AdminStatusGlobalIx }
   ::= {er1646v2EthPortSwIXt2AdminStatusTable 1}

Er1646v2EthPortSwIXt2AdminStatusEntry ::=
   SEQUENCE
      {
      er1646v2EthPortSwIXt2AdminStatusGlobalIx
         GlobalIndex,
      er1646v2EthPortSwIXt2AdminStatusValue
         INTEGER
      }

er1646v2EthPortSwIXt2AdminStatusGlobalIx OBJECT-TYPE
   SYNTAX      GlobalIndex
   MAX-ACCESS  not-accessible
   STATUS      current
   DESCRIPTION
      "The value of the tlsCntTreeGlobalIndex of the MANAGED OBJECT."
   ::= {er1646v2EthPortSwIXt2AdminStatusEntry 10}

er1646v2EthPortSwIXt2AdminStatusValue OBJECT-TYPE
   SYNTAX      INTEGER
               {
               up (1),
               down (2)
               }
   MAX-ACCESS  read-write
   STATUS      current
   DESCRIPTION
      "Path: swPort.editConf.adminStatus

       Possibilities:
               up   (1)
               down   (2)"
   ::= {er1646v2EthPortSwIXt2AdminStatusEntry 2147483648}


er1646v2EthPortSwIXt2AlarmMask OBJECT IDENTIFIER ::= {er1646v2EthPortSwIXt2 135}

er1646v2EthPortSwIXt2AlarmMaskTable OBJECT-TYPE
   SYNTAX      SEQUENCE OF Er1646v2EthPortSwIXt2AlarmMaskEntry
   MAX-ACCESS  not-accessible
   STATUS      current
   DESCRIPTION
      "ifAlarmMask"
   ::= {er1646v2EthPortSwIXt2AlarmMask 1}

er1646v2EthPortSwIXt2AlarmMaskEntry OBJECT-TYPE
   SYNTAX      Er1646v2EthPortSwIXt2AlarmMaskEntry
   MAX-ACCESS  not-accessible
   STATUS      current
   DESCRIPTION
      ""
   INDEX      { er1646v2EthPortSwIXt2AlarmMaskGlobalIx }
   ::= {er1646v2EthPortSwIXt2AlarmMaskTable 1}

Er1646v2EthPortSwIXt2AlarmMaskEntry ::=
   SEQUENCE
      {
      er1646v2EthPortSwIXt2AlarmMaskGlobalIx
         GlobalIndex,
      er1646v2EthPortSwIXt2AlarmMaskValue
         Integer32
      }

er1646v2EthPortSwIXt2AlarmMaskGlobalIx OBJECT-TYPE
   SYNTAX      GlobalIndex
   MAX-ACCESS  not-accessible
   STATUS      current
   DESCRIPTION
      "The value of the tlsCntTreeGlobalIndex of the MANAGED OBJECT."
   ::= {er1646v2EthPortSwIXt2AlarmMaskEntry 10}

er1646v2EthPortSwIXt2AlarmMaskValue OBJECT-TYPE
   SYNTAX      Integer32
   MAX-ACCESS  read-write
   STATUS      current
   DESCRIPTION
      "Path: swPort.editConf.alarmMask

       Bit meanings:
               bit 0 = linkDown,
               bit 9 = pppoEDown"
   ::= {er1646v2EthPortSwIXt2AlarmMaskEntry 2147483648}


er1646v2EthPortSwIXt2AlarmLev OBJECT IDENTIFIER ::= {er1646v2EthPortSwIXt2 170}

er1646v2EthPortSwIXt2AlarmLevSSCTable OBJECT-TYPE
   SYNTAX      SEQUENCE OF Er1646v2EthPortSwIXt2AlarmLevEntry
   MAX-ACCESS  not-accessible
   STATUS      current
   DESCRIPTION
      "IfAlarmLevels"
   ::= {er1646v2EthPortSwIXt2AlarmLev 1}

er1646v2EthPortSwIXt2AlarmLevEntry OBJECT-TYPE
   SYNTAX      Er1646v2EthPortSwIXt2AlarmLevEntry
   MAX-ACCESS  not-accessible
   STATUS      current
   DESCRIPTION
      ""
   INDEX      { er1646v2EthPortSwIXt2AlarmLevGlobalIx }
   ::= {er1646v2EthPortSwIXt2AlarmLevSSCTable 1}

Er1646v2EthPortSwIXt2AlarmLevEntry ::=
   SEQUENCE
      {
      er1646v2EthPortSwIXt2AlarmLevGlobalIx
         GlobalIndex,
      er1646v2EthPortSwIXt2AlarmLevLinkDown
         Integer32,
      er1646v2EthPortSwIXt2AlarmLevPppoEDown
         Integer32
      }

er1646v2EthPortSwIXt2AlarmLevGlobalIx OBJECT-TYPE
   SYNTAX      GlobalIndex
   MAX-ACCESS  not-accessible
   STATUS      current
   DESCRIPTION
      "The value of the tlsCntTreeGlobalIndex of the MANAGED OBJECT."
   ::= {er1646v2EthPortSwIXt2AlarmLevEntry 10}

er1646v2EthPortSwIXt2AlarmLevLinkDown OBJECT-TYPE
   SYNTAX      Integer32
   MAX-ACCESS  read-write
   STATUS      current
   DESCRIPTION
      "Path: swPort.editConf.alarmLevel.linkDown"
   ::= {er1646v2EthPortSwIXt2AlarmLevEntry 16777216}

er1646v2EthPortSwIXt2AlarmLevPppoEDown OBJECT-TYPE
   SYNTAX      Integer32
   MAX-ACCESS  read-write
   STATUS      current
   DESCRIPTION
      "Path: swPort.editConf.alarmLevel.pppoEDown"
   ::= {er1646v2EthPortSwIXt2AlarmLevEntry 167772160}


er1646v2EthPortSwIXt2PriorityPolicy OBJECT IDENTIFIER ::= {er1646v2EthPortSwIXt2 39}

er1646v2EthPortSwIXt2PriorityPolicyTable OBJECT-TYPE
   SYNTAX      SEQUENCE OF Er1646v2EthPortSwIXt2PriorityPolicyEntry
   MAX-ACCESS  not-accessible
   STATUS      current
   DESCRIPTION
      "Preferred Policy"
   ::= {er1646v2EthPortSwIXt2PriorityPolicy 1}

er1646v2EthPortSwIXt2PriorityPolicyEntry OBJECT-TYPE
   SYNTAX      Er1646v2EthPortSwIXt2PriorityPolicyEntry
   MAX-ACCESS  not-accessible
   STATUS      current
   DESCRIPTION
      ""
   INDEX      { er1646v2EthPortSwIXt2PriorityPolicyGlobalIx }
   ::= {er1646v2EthPortSwIXt2PriorityPolicyTable 1}

Er1646v2EthPortSwIXt2PriorityPolicyEntry ::=
   SEQUENCE
      {
      er1646v2EthPortSwIXt2PriorityPolicyGlobalIx
         GlobalIndex,
      er1646v2EthPortSwIXt2PriorityPolicyValue
         DisplayString
      }

er1646v2EthPortSwIXt2PriorityPolicyGlobalIx OBJECT-TYPE
   SYNTAX      GlobalIndex
   MAX-ACCESS  not-accessible
   STATUS      current
   DESCRIPTION
      "The value of the tlsCntTreeGlobalIndex of the MANAGED OBJECT."
   ::= {er1646v2EthPortSwIXt2PriorityPolicyEntry 10}

er1646v2EthPortSwIXt2PriorityPolicyValue OBJECT-TYPE
   SYNTAX      DisplayString
   MAX-ACCESS  read-write
   STATUS      current
   DESCRIPTION
      "Path: swPort.editConf.priorityPolicy"
   ::= {er1646v2EthPortSwIXt2PriorityPolicyEntry 2147483648}


er1646v2EthPortSwIXt2Lst OBJECT IDENTIFIER ::= {er1646v2EthPortSwIXt2 12}

er1646v2EthPortSwIXt2LstSSCTable OBJECT-TYPE
   SYNTAX      SEQUENCE OF Er1646v2EthPortSwIXt2LstEntry
   MAX-ACCESS  not-accessible
   STATUS      current
   DESCRIPTION
      ""
   ::= {er1646v2EthPortSwIXt2Lst 1}

er1646v2EthPortSwIXt2LstEntry OBJECT-TYPE
   SYNTAX      Er1646v2EthPortSwIXt2LstEntry
   MAX-ACCESS  not-accessible
   STATUS      current
   DESCRIPTION
      ""
   INDEX      { er1646v2EthPortSwIXt2LstGlobalIx }
   ::= {er1646v2EthPortSwIXt2LstSSCTable 1}

Er1646v2EthPortSwIXt2LstEntry ::=
   SEQUENCE
      {
      er1646v2EthPortSwIXt2LstGlobalIx
         GlobalIndex,
      er1646v2EthPortSwIXt2LstTrackedInterface
         DisplayString
      }

er1646v2EthPortSwIXt2LstGlobalIx OBJECT-TYPE
   SYNTAX      GlobalIndex
   MAX-ACCESS  not-accessible
   STATUS      current
   DESCRIPTION
      "The value of the tlsCntTreeGlobalIndex of the MANAGED OBJECT."
   ::= {er1646v2EthPortSwIXt2LstEntry 10}

er1646v2EthPortSwIXt2LstTrackedInterface OBJECT-TYPE
   SYNTAX      DisplayString
   MAX-ACCESS  read-write
   STATUS      current
   DESCRIPTION
      "Path: swPort.editConf.linkStateTracking.trackedInterface"
   ::= {er1646v2EthPortSwIXt2LstEntry 16777216}


er1646v2EthPortSwIXt2SnmpIndexOffset OBJECT IDENTIFIER ::= {er1646v2EthPortSwIXt2 268}

er1646v2EthPortSwIXt2SnmpIndexOffsetTable OBJECT-TYPE
   SYNTAX      SEQUENCE OF Er1646v2EthPortSwIXt2SnmpIndexOffsetEntry
   MAX-ACCESS  not-accessible
   STATUS      current
   DESCRIPTION
      "Preferred offset in the range of SNMP indices for this SWinst, 0 means automatic"
   ::= {er1646v2EthPortSwIXt2SnmpIndexOffset 1}

er1646v2EthPortSwIXt2SnmpIndexOffsetEntry OBJECT-TYPE
   SYNTAX      Er1646v2EthPortSwIXt2SnmpIndexOffsetEntry
   MAX-ACCESS  not-accessible
   STATUS      current
   DESCRIPTION
      ""
   INDEX      { er1646v2EthPortSwIXt2SnmpIndexOffsetGlobalIx }
   ::= {er1646v2EthPortSwIXt2SnmpIndexOffsetTable 1}

Er1646v2EthPortSwIXt2SnmpIndexOffsetEntry ::=
   SEQUENCE
      {
      er1646v2EthPortSwIXt2SnmpIndexOffsetGlobalIx
         GlobalIndex,
      er1646v2EthPortSwIXt2SnmpIndexOffsetValue
         Integer32
      }

er1646v2EthPortSwIXt2SnmpIndexOffsetGlobalIx OBJECT-TYPE
   SYNTAX      GlobalIndex
   MAX-ACCESS  not-accessible
   STATUS      current
   DESCRIPTION
      "The value of the tlsCntTreeGlobalIndex of the MANAGED OBJECT."
   ::= {er1646v2EthPortSwIXt2SnmpIndexOffsetEntry 10}

er1646v2EthPortSwIXt2SnmpIndexOffsetValue OBJECT-TYPE
   SYNTAX      Integer32
   MAX-ACCESS  read-write
   STATUS      current
   DESCRIPTION
      "Path: swPort.editConf.snmpIndexOffset"
   ::= {er1646v2EthPortSwIXt2SnmpIndexOffsetEntry 2147483648}



sr1646v2EthPortSwIXt2 OBJECT IDENTIFIER ::= {r1646v2EthPortSwIXt2 14}


sr1646v2EthPortSwIXt2Descr OBJECT IDENTIFIER ::= {sr1646v2EthPortSwIXt2 101}

sr1646v2EthPortSwIXt2DescrTable OBJECT-TYPE
   SYNTAX      SEQUENCE OF Sr1646v2EthPortSwIXt2DescrEntry
   MAX-ACCESS  not-accessible
   STATUS      current
   DESCRIPTION
      "ifDescr"
   ::= {sr1646v2EthPortSwIXt2Descr 1}

sr1646v2EthPortSwIXt2DescrEntry OBJECT-TYPE
   SYNTAX      Sr1646v2EthPortSwIXt2DescrEntry
   MAX-ACCESS  not-accessible
   STATUS      current
   DESCRIPTION
      ""
   INDEX      { sr1646v2EthPortSwIXt2DescrGlobalIx }
   ::= {sr1646v2EthPortSwIXt2DescrTable 1}

Sr1646v2EthPortSwIXt2DescrEntry ::=
   SEQUENCE
      {
      sr1646v2EthPortSwIXt2DescrGlobalIx
         GlobalIndex,
      sr1646v2EthPortSwIXt2DescrValue
         DisplayString
      }

sr1646v2EthPortSwIXt2DescrGlobalIx OBJECT-TYPE
   SYNTAX      GlobalIndex
   MAX-ACCESS  not-accessible
   STATUS      current
   DESCRIPTION
      "The value of the tlsCntTreeGlobalIndex of the MANAGED OBJECT."
   ::= {sr1646v2EthPortSwIXt2DescrEntry 10}

sr1646v2EthPortSwIXt2DescrValue OBJECT-TYPE
   SYNTAX      DisplayString
   MAX-ACCESS  read-only
   STATUS      current
   DESCRIPTION
      "Path: swPort.status.ifDescr"
   ::= {sr1646v2EthPortSwIXt2DescrEntry 2147483648}


sr1646v2EthPortSwIXt2Type OBJECT IDENTIFIER ::= {sr1646v2EthPortSwIXt2 102}

sr1646v2EthPortSwIXt2TypeTable OBJECT-TYPE
   SYNTAX      SEQUENCE OF Sr1646v2EthPortSwIXt2TypeEntry
   MAX-ACCESS  not-accessible
   STATUS      current
   DESCRIPTION
      "ifType"
   ::= {sr1646v2EthPortSwIXt2Type 1}

sr1646v2EthPortSwIXt2TypeEntry OBJECT-TYPE
   SYNTAX      Sr1646v2EthPortSwIXt2TypeEntry
   MAX-ACCESS  not-accessible
   STATUS      current
   DESCRIPTION
      ""
   INDEX      { sr1646v2EthPortSwIXt2TypeGlobalIx }
   ::= {sr1646v2EthPortSwIXt2TypeTable 1}

Sr1646v2EthPortSwIXt2TypeEntry ::=
   SEQUENCE
      {
      sr1646v2EthPortSwIXt2TypeGlobalIx
         GlobalIndex,
      sr1646v2EthPortSwIXt2TypeValue
         INTEGER
      }

sr1646v2EthPortSwIXt2TypeGlobalIx OBJECT-TYPE
   SYNTAX      GlobalIndex
   MAX-ACCESS  not-accessible
   STATUS      current
   DESCRIPTION
      "The value of the tlsCntTreeGlobalIndex of the MANAGED OBJECT."
   ::= {sr1646v2EthPortSwIXt2TypeEntry 10}

sr1646v2EthPortSwIXt2TypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: swPort.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2EthPortSwIXt2TypeEntry 2147483648}


sr1646v2EthPortSwIXt2Mtu OBJECT IDENTIFIER ::= {sr1646v2EthPortSwIXt2 103}

sr1646v2EthPortSwIXt2MtuTable OBJECT-TYPE
   SYNTAX      SEQUENCE OF Sr1646v2EthPortSwIXt2MtuEntry
   MAX-ACCESS  not-accessible
   STATUS      current
   DESCRIPTION
      "ifMtu"
   ::= {sr1646v2EthPortSwIXt2Mtu 1}

sr1646v2EthPortSwIXt2MtuEntry OBJECT-TYPE
   SYNTAX      Sr1646v2EthPortSwIXt2MtuEntry
   MAX-ACCESS  not-accessible
   STATUS      current
   DESCRIPTION
      ""
   INDEX      { sr1646v2EthPortSwIXt2MtuGlobalIx }
   ::= {sr1646v2EthPortSwIXt2MtuTable 1}

Sr1646v2EthPortSwIXt2MtuEntry ::=
   SEQUENCE
      {
      sr1646v2EthPortSwIXt2MtuGlobalIx
         GlobalIndex,
      sr1646v2EthPortSwIXt2MtuValue
         Integer32
      }

sr1646v2EthPortSwIXt2MtuGlobalIx OBJECT-TYPE
   SYNTAX      GlobalIndex
   MAX-ACCESS  not-accessible
   STATUS      current
   DESCRIPTION
      "The value of the tlsCntTreeGlobalIndex of the MANAGED OBJECT."
   ::= {sr1646v2EthPortSwIXt2MtuEntry 10}

sr1646v2EthPortSwIXt2MtuValue OBJECT-TYPE
   SYNTAX      Integer32
   MAX-ACCESS  read-only
   STATUS      current
   DESCRIPTION
      "Path: swPort.status.ifMtu"
   ::= {sr1646v2EthPortSwIXt2MtuEntry 2147483648}


sr1646v2EthPortSwIXt2OperStatus OBJECT IDENTIFIER ::= {sr1646v2EthPortSwIXt2 107}

sr1646v2EthPortSwIXt2OperStatusTable OBJECT-TYPE
   SYNTAX      SEQUENCE OF Sr1646v2EthPortSwIXt2OperStatusEntry
   MAX-ACCESS  not-accessible
   STATUS      current
   DESCRIPTION
      "ifOperStatus"
   ::= {sr1646v2EthPortSwIXt2OperStatus 1}

sr1646v2EthPortSwIXt2OperStatusEntry OBJECT-TYPE
   SYNTAX      Sr1646v2EthPortSwIXt2OperStatusEntry
   MAX-ACCESS  not-accessible
   STATUS      current
   DESCRIPTION
      ""
   INDEX      { sr1646v2EthPortSwIXt2OperStatusGlobalIx }
   ::= {sr1646v2EthPortSwIXt2OperStatusTable 1}

Sr1646v2EthPortSwIXt2OperStatusEntry ::=
   SEQUENCE
      {
      sr1646v2EthPortSwIXt2OperStatusGlobalIx
         GlobalIndex,
      sr1646v2EthPortSwIXt2OperStatusValue
         INTEGER
      }

sr1646v2EthPortSwIXt2OperStatusGlobalIx OBJECT-TYPE
   SYNTAX      GlobalIndex
   MAX-ACCESS  not-accessible
   STATUS      current
   DESCRIPTION
      "The value of the tlsCntTreeGlobalIndex of the MANAGED OBJECT."
   ::= {sr1646v2EthPortSwIXt2OperStatusEntry 10}

sr1646v2EthPortSwIXt2OperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ifOperStatus

       Possibilities:
               up   (1)
               down   (2)
               testing   (3)
               unknown   (4)
               dormant   (5)
               notPresent   (6)
               lowerLayerDown   (7)"
   ::= {sr1646v2EthPortSwIXt2OperStatusEntry 2147483648}


sr1646v2EthPortSwIXt2LastChange OBJECT IDENTIFIER ::= {sr1646v2EthPortSwIXt2 108}

sr1646v2EthPortSwIXt2LastChangeTable OBJECT-TYPE
   SYNTAX      SEQUENCE OF Sr1646v2EthPortSwIXt2LastChangeEntry
   MAX-ACCESS  not-accessible
   STATUS      current
   DESCRIPTION
      "ifLastChange"
   ::= {sr1646v2EthPortSwIXt2LastChange 1}

sr1646v2EthPortSwIXt2LastChangeEntry OBJECT-TYPE
   SYNTAX      Sr1646v2EthPortSwIXt2LastChangeEntry
   MAX-ACCESS  not-accessible
   STATUS      current
   DESCRIPTION
      ""
   INDEX      { sr1646v2EthPortSwIXt2LastChangeGlobalIx }
   ::= {sr1646v2EthPortSwIXt2LastChangeTable 1}

Sr1646v2EthPortSwIXt2LastChangeEntry ::=
   SEQUENCE
      {
      sr1646v2EthPortSwIXt2LastChangeGlobalIx
         GlobalIndex,
      sr1646v2EthPortSwIXt2LastChangeValue
         TimeTicks
      }

sr1646v2EthPortSwIXt2LastChangeGlobalIx OBJECT-TYPE
   SYNTAX      GlobalIndex
   MAX-ACCESS  not-accessible
   STATUS      current
   DESCRIPTION
      "The value of the tlsCntTreeGlobalIndex of the MANAGED OBJECT."
   ::= {sr1646v2EthPortSwIXt2LastChangeEntry 10}

sr1646v2EthPortSwIXt2LastChangeValue OBJECT-TYPE
   SYNTAX      TimeTicks
   MAX-ACCESS  read-only
   STATUS      current
   DESCRIPTION
      "Path: swPort.status.ifLastChange

       Time in centi-second."
   ::= {sr1646v2EthPortSwIXt2LastChangeEntry 2147483648}


sr1646v2EthPortSwIXt2LastChangeD OBJECT IDENTIFIER ::= {sr1646v2EthPortSwIXt2 183}

sr1646v2EthPortSwIXt2LastChangeDTable OBJECT-TYPE
   SYNTAX      SEQUENCE OF Sr1646v2EthPortSwIXt2LastChangeDEntry
   MAX-ACCESS  not-accessible
   STATUS      current
   DESCRIPTION
      "ifLastChangeDate"
   ::= {sr1646v2EthPortSwIXt2LastChangeD 1}

sr1646v2EthPortSwIXt2LastChangeDEntry OBJECT-TYPE
   SYNTAX      Sr1646v2EthPortSwIXt2LastChangeDEntry
   MAX-ACCESS  not-accessible
   STATUS      current
   DESCRIPTION
      ""
   INDEX      { sr1646v2EthPortSwIXt2LastChangeDGlobalIx }
   ::= {sr1646v2EthPortSwIXt2LastChangeDTable 1}

Sr1646v2EthPortSwIXt2LastChangeDEntry ::=
   SEQUENCE
      {
      sr1646v2EthPortSwIXt2LastChangeDGlobalIx
         GlobalIndex,
      sr1646v2EthPortSwIXt2LastChangeDValue
         DisplayString
      }

sr1646v2EthPortSwIXt2LastChangeDGlobalIx OBJECT-TYPE
   SYNTAX      GlobalIndex
   MAX-ACCESS  not-accessible
   STATUS      current
   DESCRIPTION
      "The value of the tlsCntTreeGlobalIndex of the MANAGED OBJECT."
   ::= {sr1646v2EthPortSwIXt2LastChangeDEntry 10}

sr1646v2EthPortSwIXt2LastChangeDValue OBJECT-TYPE
   SYNTAX      DisplayString
   MAX-ACCESS  read-only
   STATUS      current
   DESCRIPTION
      "Path: swPort.status.ifLastChangeDate"
   ::= {sr1646v2EthPortSwIXt2LastChangeDEntry 2147483648}


sr1646v2EthPortSwIXt2Speed OBJECT IDENTIFIER ::= {sr1646v2EthPortSwIXt2 104}

sr1646v2EthPortSwIXt2SpeedTable OBJECT-TYPE
   SYNTAX      SEQUENCE OF Sr1646v2EthPortSwIXt2SpeedEntry
   MAX-ACCESS  not-accessible
   STATUS      current
   DESCRIPTION
      "ifSpeed"
   ::= {sr1646v2EthPortSwIXt2Speed 1}

sr1646v2EthPortSwIXt2SpeedEntry OBJECT-TYPE
   SYNTAX      Sr1646v2EthPortSwIXt2SpeedEntry
   MAX-ACCESS  not-accessible
   STATUS      current
   DESCRIPTION
      ""
   INDEX      { sr1646v2EthPortSwIXt2SpeedGlobalIx }
   ::= {sr1646v2EthPortSwIXt2SpeedTable 1}

Sr1646v2EthPortSwIXt2SpeedEntry ::=
   SEQUENCE
      {
      sr1646v2EthPortSwIXt2SpeedGlobalIx
         GlobalIndex,
      sr1646v2EthPortSwIXt2SpeedValue
         Gauge32
      }

sr1646v2EthPortSwIXt2SpeedGlobalIx OBJECT-TYPE
   SYNTAX      GlobalIndex
   MAX-ACCESS  not-accessible
   STATUS      current
   DESCRIPTION
      "The value of the tlsCntTreeGlobalIndex of the MANAGED OBJECT."
   ::= {sr1646v2EthPortSwIXt2SpeedEntry 10}

sr1646v2EthPortSwIXt2SpeedValue OBJECT-TYPE
   SYNTAX      Gauge32
   MAX-ACCESS  read-only
   STATUS      current
   DESCRIPTION
      "Path: swPort.status.ifSpeed

       32 bit unsigned gauge value."
   ::= {sr1646v2EthPortSwIXt2SpeedEntry 2147483648}


sr1646v2EthPortSwIXt2Ip OBJECT IDENTIFIER ::= {sr1646v2EthPortSwIXt2 16}

sr1646v2EthPortSwIXt2IpSSCTable OBJECT-TYPE
   SYNTAX      SEQUENCE OF Sr1646v2EthPortSwIXt2IpEntry
   MAX-ACCESS  not-accessible
   STATUS      current
   DESCRIPTION
      "ip interface status parameters"
   ::= {sr1646v2EthPortSwIXt2Ip 1}

sr1646v2EthPortSwIXt2IpEntry OBJECT-TYPE
   SYNTAX      Sr1646v2EthPortSwIXt2IpEntry
   MAX-ACCESS  not-accessible
   STATUS      current
   DESCRIPTION
      ""
   INDEX      { sr1646v2EthPortSwIXt2IpGlobalIx }
   ::= {sr1646v2EthPortSwIXt2IpSSCTable 1}

Sr1646v2EthPortSwIXt2IpEntry ::=
   SEQUENCE
      {
      sr1646v2EthPortSwIXt2IpGlobalIx
         GlobalIndex,
      sr1646v2EthPortSwIXt2IpStatus
         INTEGER,
      sr1646v2EthPortSwIXt2IpAddress
         IpAddress,
      sr1646v2EthPortSwIXt2IpNetMask
         IpAddress,
      sr1646v2EthPortSwIXt2IpDhcpStatus
         INTEGER,
      sr1646v2EthPortSwIXt2IpDhcpLeaseTime
         TimeTicks
      }

sr1646v2EthPortSwIXt2IpGlobalIx OBJECT-TYPE
   SYNTAX      GlobalIndex
   MAX-ACCESS  not-accessible
   STATUS      current
   DESCRIPTION
      "The value of the tlsCntTreeGlobalIndex of the MANAGED OBJECT."
   ::= {sr1646v2EthPortSwIXt2IpEntry 10}

sr1646v2EthPortSwIXt2IpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.ip.status

       Possibilities:
               up   (1)
               down   (2)
               testing   (3)
               unknown   (4)
               dormant   (5)
               notPresent   (6)
               lowerLayerDown   (7)"
   ::= {sr1646v2EthPortSwIXt2IpEntry 1795162112}

sr1646v2EthPortSwIXt2IpAddress OBJECT-TYPE
   SYNTAX      IpAddress
   MAX-ACCESS  read-only
   STATUS      current
   DESCRIPTION
      "Path: swPort.status.ip.address"
   ::= {sr1646v2EthPortSwIXt2IpEntry 2030043136}

sr1646v2EthPortSwIXt2IpNetMask OBJECT-TYPE
   SYNTAX      IpAddress
   MAX-ACCESS  read-only
   STATUS      current
   DESCRIPTION
      "Path: swPort.status.ip.netMask"
   ::= {sr1646v2EthPortSwIXt2IpEntry 2063597568}

sr1646v2EthPortSwIXt2IpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.ip.dhcp.status

       Possibilities:
               none   (0)
               selecting   (1)
               requesting   (2)
               rebinding   (3)
               bound   (4)
               renewing   (5)
               rebooting   (6)
               initreboot   (7)"
   ::= {sr1646v2EthPortSwIXt2IpEntry 402718720}

sr1646v2EthPortSwIXt2IpDhcpLeaseTime OBJECT-TYPE
   SYNTAX      TimeTicks
   MAX-ACCESS  read-only
   STATUS      current
   DESCRIPTION
      "Path: swPort.status.ip.dhcp.leaseTime

       Time in centi-second."
   ::= {sr1646v2EthPortSwIXt2IpEntry 402784256}

sr1646v2EthPortSwIXt2IpSecondaryIp OBJECT-TYPE
   SYNTAX      SEQUENCE OF Sr1646v2EthPortSwIXt2IpSecondaryIpEntry
   MAX-ACCESS  not-accessible
   STATUS      current
   DESCRIPTION
      ""
   ::= {sr1646v2EthPortSwIXt2Ip 385875968}

sr1646v2EthPortSwIXt2IpSecondaryIpEntry OBJECT-TYPE
   SYNTAX      Sr1646v2EthPortSwIXt2IpSecondaryIpEntry
   MAX-ACCESS  not-accessible
   STATUS      current
   DESCRIPTION
      ""
   INDEX      { sr1646v2EthPortSwIXt2IpSecondaryIpGlobalIx,
                sr1646v2EthPortSwIXt2IpSecondaryIpTableIx }
   ::= {sr1646v2EthPortSwIXt2IpSecondaryIp 1}

Sr1646v2EthPortSwIXt2IpSecondaryIpEntry ::=
   SEQUENCE
      {
      sr1646v2EthPortSwIXt2IpSecondaryIpGlobalIx
         GlobalIndex,
      sr1646v2EthPortSwIXt2IpSecondaryIpTableIx
         TableIndex,
      sr1646v2EthPortSwIXt2IpSecondaryIpAddress
         IpAddress,
      sr1646v2EthPortSwIXt2IpSecondaryIpNetMask
         IpAddress
      }

sr1646v2EthPortSwIXt2IpSecondaryIpGlobalIx OBJECT-TYPE
   SYNTAX      GlobalIndex
   MAX-ACCESS  not-accessible
   STATUS      current
   DESCRIPTION
      "The value of the tlsCntTreeGlobalIndex of the MANAGED OBJECT."
   ::= {sr1646v2EthPortSwIXt2IpSecondaryIpEntry 10}

sr1646v2EthPortSwIXt2IpSecondaryIpTableIx OBJECT-TYPE
   SYNTAX      TableIndex
   MAX-ACCESS  not-accessible
   STATUS      current
   DESCRIPTION
      ""
   ::= {sr1646v2EthPortSwIXt2IpSecondaryIpEntry 11}

sr1646v2EthPortSwIXt2IpSecondaryIpAddress OBJECT-TYPE
   SYNTAX      IpAddress
   MAX-ACCESS  read-only
   STATUS      current
   DESCRIPTION
      "Path: swPort.status.ip.secondaryIp.address"
   ::= {sr1646v2EthPortSwIXt2IpSecondaryIpEntry 2030043136}

sr1646v2EthPortSwIXt2IpSecondaryIpNetMask OBJECT-TYPE
   SYNTAX      IpAddress
   MAX-ACCESS  read-only
   STATUS      current
   DESCRIPTION
      "Path: swPort.status.ip.secondaryIp.netMask"
   ::= {sr1646v2EthPortSwIXt2IpSecondaryIpEntry 2063597568}


sr1646v2EthPortSwIXt2ArpCache OBJECT IDENTIFIER ::= {sr1646v2EthPortSwIXt2 11}

sr1646v2EthPortSwIXt2ArpCacheSSCTable OBJECT-TYPE
   SYNTAX      SEQUENCE OF Sr1646v2EthPortSwIXt2ArpCacheEntry
   MAX-ACCESS  not-accessible
   STATUS      current
   DESCRIPTION
      "arp cache of ethernet interface"
   ::= {sr1646v2EthPortSwIXt2ArpCache 1}

sr1646v2EthPortSwIXt2ArpCacheEntry OBJECT-TYPE
   SYNTAX      Sr1646v2EthPortSwIXt2ArpCacheEntry
   MAX-ACCESS  not-accessible
   STATUS      current
   DESCRIPTION
      ""
   INDEX      { sr1646v2EthPortSwIXt2ArpCacheGlobalIx,
                sr1646v2EthPortSwIXt2ArpCacheTableIx }
   ::= {sr1646v2EthPortSwIXt2ArpCacheSSCTable 1}

Sr1646v2EthPortSwIXt2ArpCacheEntry ::=
   SEQUENCE
      {
      sr1646v2EthPortSwIXt2ArpCacheGlobalIx
         GlobalIndex,
      sr1646v2EthPortSwIXt2ArpCacheTableIx
         TableIndex,
      sr1646v2EthPortSwIXt2ArpCacheMacAddress
         OCTET STRING,
      sr1646v2EthPortSwIXt2ArpCacheIpAddress
         IpAddress,
      sr1646v2EthPortSwIXt2ArpCacheType
         INTEGER,
      sr1646v2EthPortSwIXt2ArpCacheTimeOut
         TimeTicks
      }

sr1646v2EthPortSwIXt2ArpCacheGlobalIx OBJECT-TYPE
   SYNTAX      GlobalIndex
   MAX-ACCESS  not-accessible
   STATUS      current
   DESCRIPTION
      "The value of the tlsCntTreeGlobalIndex of the MANAGED OBJECT."
   ::= {sr1646v2EthPortSwIXt2ArpCacheEntry 10}

sr1646v2EthPortSwIXt2ArpCacheTableIx OBJECT-TYPE
   SYNTAX      TableIndex
   MAX-ACCESS  not-accessible
   STATUS      current
   DESCRIPTION
      ""
   ::= {sr1646v2EthPortSwIXt2ArpCacheEntry 11}

sr1646v2EthPortSwIXt2ArpCacheMacAddress OBJECT-TYPE
   SYNTAX      OCTET STRING
   MAX-ACCESS  read-only
   STATUS      current
   DESCRIPTION
      "Path: swPort.status.arpCache.macAddress

       MAC address."
   ::= {sr1646v2EthPortSwIXt2ArpCacheEntry 16777216}

sr1646v2EthPortSwIXt2ArpCacheIpAddress OBJECT-TYPE
   SYNTAX      IpAddress
   MAX-ACCESS  read-only
   STATUS      current
   DESCRIPTION
      "Path: swPort.status.arpCache.ipAddress"
   ::= {sr1646v2EthPortSwIXt2ArpCacheEntry 33554432}

sr1646v2EthPortSwIXt2ArpCacheType OBJECT-TYPE
   SYNTAX      INTEGER
               {
               static (0),
               dynamic (1)
               }
   MAX-ACCESS  read-only
   STATUS      current
   DESCRIPTION
      "Path: swPort.status.arpCache.type

       Possibilities:
               static   (0)
               dynamic   (1)"
   ::= {sr1646v2EthPortSwIXt2ArpCacheEntry 50331648}

sr1646v2EthPortSwIXt2ArpCacheTimeOut OBJECT-TYPE
   SYNTAX      TimeTicks
   MAX-ACCESS  read-only
   STATUS      current
   DESCRIPTION
      "Path: swPort.status.arpCache.timeOut

       Time in centi-second."
   ::= {sr1646v2EthPortSwIXt2ArpCacheEntry 67108864}


sr1646v2EthPortSwIXt2BrS OBJECT IDENTIFIER ::= {sr1646v2EthPortSwIXt2 28}

sr1646v2EthPortSwIXt2BrSSSCTable OBJECT-TYPE
   SYNTAX      SEQUENCE OF Sr1646v2EthPortSwIXt2BrSEntry
   MAX-ACCESS  not-accessible
   STATUS      current
   DESCRIPTION
      "spanning tree status ethernet interface"
   ::= {sr1646v2EthPortSwIXt2BrS 1}

sr1646v2EthPortSwIXt2BrSEntry OBJECT-TYPE
   SYNTAX      Sr1646v2EthPortSwIXt2BrSEntry
   MAX-ACCESS  not-accessible
   STATUS      current
   DESCRIPTION
      ""
   INDEX      { sr1646v2EthPortSwIXt2BrSGlobalIx }
   ::= {sr1646v2EthPortSwIXt2BrSSSCTable 1}

Sr1646v2EthPortSwIXt2BrSEntry ::=
   SEQUENCE
      {
      sr1646v2EthPortSwIXt2BrSGlobalIx
         GlobalIndex,
      sr1646v2EthPortSwIXt2BrSStatus
         INTEGER,
      sr1646v2EthPortSwIXt2BrSStPortRole
         INTEGER,
      sr1646v2EthPortSwIXt2BrSStPortId
         Integer32,
      sr1646v2EthPortSwIXt2BrSStPpCostExtPathCost
         Integer32,
      sr1646v2EthPortSwIXt2BrSStPpCostIntPathCost
         Integer32,
      sr1646v2EthPortSwIXt2BrSStExtRpCost
         Integer32,
      sr1646v2EthPortSwIXt2BrSStIntRpCost
         Integer32,
      sr1646v2EthPortSwIXt2BrSStDesBrIdPriority
         Integer32,
      sr1646v2EthPortSwIXt2BrSStDesBrIdMacAddress
         OCTET STRING,
      sr1646v2EthPortSwIXt2BrSStDesPrtId
         Integer32,
      sr1646v2EthPortSwIXt2BrSStDesInt
         INTEGER,
      sr1646v2EthPortSwIXt2BrSStEdgeDetection
         INTEGER
      }

sr1646v2EthPortSwIXt2BrSGlobalIx OBJECT-TYPE
   SYNTAX      GlobalIndex
   MAX-ACCESS  not-accessible
   STATUS      current
   DESCRIPTION
      "The value of the tlsCntTreeGlobalIndex of the MANAGED OBJECT."
   ::= {sr1646v2EthPortSwIXt2BrSEntry 10}

sr1646v2EthPortSwIXt2BrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.bridging.status

       Possibilities:
               disabled   (0)
               discarding   (1)
               learning   (2)
               forwarding   (3)
               backupBlockedIntfDown   (256)
               backupBlockedIntfUp   (259)
               shutdown   (255)"
   ::= {sr1646v2EthPortSwIXt2BrSEntry 16777216}

sr1646v2EthPortSwIXt2BrSStPortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.bridging.spanningTree.portRole

       Possibilities:
               none   (0)
               root   (1)
               designated   (2)
               alternate   (3)
               backup   (4)
               disabled   (5)
               master   (6)"
   ::= {sr1646v2EthPortSwIXt2BrSEntry 33619968}

sr1646v2EthPortSwIXt2BrSStPortId OBJECT-TYPE
   SYNTAX      Integer32
   MAX-ACCESS  read-only
   STATUS      current
   DESCRIPTION
      "Path: swPort.status.bridging.spanningTree.portId"
   ::= {sr1646v2EthPortSwIXt2BrSEntry 33685504}

sr1646v2EthPortSwIXt2BrSStPpCostExtPathCost OBJECT-TYPE
   SYNTAX      Integer32
   MAX-ACCESS  read-only
   STATUS      current
   DESCRIPTION
      "Path: swPort.status.bridging.spanningTree.portPathCosts.extPathCost"
   ::= {sr1646v2EthPortSwIXt2BrSEntry 33751296}

sr1646v2EthPortSwIXt2BrSStPpCostIntPathCost OBJECT-TYPE
   SYNTAX      Integer32
   MAX-ACCESS  read-only
   STATUS      current
   DESCRIPTION
      "Path: swPort.status.bridging.spanningTree.portPathCosts.intPathCost"
   ::= {sr1646v2EthPortSwIXt2BrSEntry 33751552}

sr1646v2EthPortSwIXt2BrSStExtRpCost OBJECT-TYPE
   SYNTAX      Integer32
   MAX-ACCESS  read-only
   STATUS      current
   DESCRIPTION
      "Path: swPort.status.bridging.spanningTree.extRootPathCost"
   ::= {sr1646v2EthPortSwIXt2BrSEntry 33816576}

sr1646v2EthPortSwIXt2BrSStIntRpCost OBJECT-TYPE
   SYNTAX      Integer32
   MAX-ACCESS  read-only
   STATUS      current
   DESCRIPTION
      "Path: swPort.status.bridging.spanningTree.intRootPathCost"
   ::= {sr1646v2EthPortSwIXt2BrSEntry 33882112}

sr1646v2EthPortSwIXt2BrSStDesBrIdPriority OBJECT-TYPE
   SYNTAX      Integer32
   MAX-ACCESS  read-only
   STATUS      current
   DESCRIPTION
      "Path: swPort.status.bridging.spanningTree.designatedBridgeId.priority"
   ::= {sr1646v2EthPortSwIXt2BrSEntry 33947904}

sr1646v2EthPortSwIXt2BrSStDesBrIdMacAddress OBJECT-TYPE
   SYNTAX      OCTET STRING
   MAX-ACCESS  read-only
   STATUS      current
   DESCRIPTION
      "Path: swPort.status.bridging.spanningTree.designatedBridgeId.macAddress

       MAC address."
   ::= {sr1646v2EthPortSwIXt2BrSEntry 33948160}

sr1646v2EthPortSwIXt2BrSStDesPrtId OBJECT-TYPE
   SYNTAX      Integer32
   MAX-ACCESS  read-only
   STATUS      current
   DESCRIPTION
      "Path: swPort.status.bridging.spanningTree.designatedPortId"
   ::= {sr1646v2EthPortSwIXt2BrSEntry 34013184}

sr1646v2EthPortSwIXt2BrSStDesInt OBJECT-TYPE
   SYNTAX      INTEGER
               {
               no (0),
               yes (1)
               }
   MAX-ACCESS  read-only
   STATUS      current
   DESCRIPTION
      "Path: swPort.status.bridging.spanningTree.designatedOrInternal

       Possibilities:
               no   (0)
               yes   (1)"
   ::= {sr1646v2EthPortSwIXt2BrSEntry 34078720}

sr1646v2EthPortSwIXt2BrSStEdgeDetection OBJECT-TYPE
   SYNTAX      INTEGER
               {
               none (0),
               edge (1),
               notEdge (2)
               }
   MAX-ACCESS  read-only
   STATUS      current
   DESCRIPTION
      "Path: swPort.status.bridging.spanningTree.edgeDetection

       Possibilities:
               none   (0)
               edge   (1)
               notEdge   (2)"
   ::= {sr1646v2EthPortSwIXt2BrSEntry 34144256}


sr1646v2EthPortSwIXt2MacAddress OBJECT IDENTIFIER ::= {sr1646v2EthPortSwIXt2 105}

sr1646v2EthPortSwIXt2MacAddressTable OBJECT-TYPE
   SYNTAX      SEQUENCE OF Sr1646v2EthPortSwIXt2MacAddressEntry
   MAX-ACCESS  not-accessible
   STATUS      current
   DESCRIPTION
      "ifPhysAddress"
   ::= {sr1646v2EthPortSwIXt2MacAddress 1}

sr1646v2EthPortSwIXt2MacAddressEntry OBJECT-TYPE
   SYNTAX      Sr1646v2EthPortSwIXt2MacAddressEntry
   MAX-ACCESS  not-accessible
   STATUS      current
   DESCRIPTION
      ""
   INDEX      { sr1646v2EthPortSwIXt2MacAddressGlobalIx }
   ::= {sr1646v2EthPortSwIXt2MacAddressTable 1}

Sr1646v2EthPortSwIXt2MacAddressEntry ::=
   SEQUENCE
      {
      sr1646v2EthPortSwIXt2MacAddressGlobalIx
         GlobalIndex,
      sr1646v2EthPortSwIXt2MacAddressValue
         OCTET STRING
      }

sr1646v2EthPortSwIXt2MacAddressGlobalIx OBJECT-TYPE
   SYNTAX      GlobalIndex
   MAX-ACCESS  not-accessible
   STATUS      current
   DESCRIPTION
      "The value of the tlsCntTreeGlobalIndex of the MANAGED OBJECT."
   ::= {sr1646v2EthPortSwIXt2MacAddressEntry 10}

sr1646v2EthPortSwIXt2MacAddressValue OBJECT-TYPE
   SYNTAX      OCTET STRING
   MAX-ACCESS  read-only
   STATUS      current
   DESCRIPTION
      "Path: swPort.status.macAddress

       MAC address."
   ::= {sr1646v2EthPortSwIXt2MacAddressEntry 2147483648}


sr1646v2EthPortSwIXt2IpAdEntBcastAddr OBJECT IDENTIFIER ::= {sr1646v2EthPortSwIXt2 124}

sr1646v2EthPortSwIXt2IpAdEntBcastAddrTable OBJECT-TYPE
   SYNTAX      SEQUENCE OF Sr1646v2EthPortSwIXt2IpAdEntBcastAddrEntry
   MAX-ACCESS  not-accessible
   STATUS      current
   DESCRIPTION
      "ipAdEntBcastAddr"
   ::= {sr1646v2EthPortSwIXt2IpAdEntBcastAddr 1}

sr1646v2EthPortSwIXt2IpAdEntBcastAddrEntry OBJECT-TYPE
   SYNTAX      Sr1646v2EthPortSwIXt2IpAdEntBcastAddrEntry
   MAX-ACCESS  not-accessible
   STATUS      current
   DESCRIPTION
      ""
   INDEX      { sr1646v2EthPortSwIXt2IpAdEntBcastAddrGlobalIx }
   ::= {sr1646v2EthPortSwIXt2IpAdEntBcastAddrTable 1}

Sr1646v2EthPortSwIXt2IpAdEntBcastAddrEntry ::=
   SEQUENCE
      {
      sr1646v2EthPortSwIXt2IpAdEntBcastAddrGlobalIx
         GlobalIndex,
      sr1646v2EthPortSwIXt2IpAdEntBcastAddrValue
         Integer32
      }

sr1646v2EthPortSwIXt2IpAdEntBcastAddrGlobalIx OBJECT-TYPE
   SYNTAX      GlobalIndex
   MAX-ACCESS  not-accessible
   STATUS      current
   DESCRIPTION
      "The value of the tlsCntTreeGlobalIndex of the MANAGED OBJECT."
   ::= {sr1646v2EthPortSwIXt2IpAdEntBcastAddrEntry 10}

sr1646v2EthPortSwIXt2IpAdEntBcastAddrValue OBJECT-TYPE
   SYNTAX      Integer32
   MAX-ACCESS  read-only
   STATUS      current
   DESCRIPTION
      "Path: swPort.status.ipAdEntBcastAddr"
   ::= {sr1646v2EthPortSwIXt2IpAdEntBcastAddrEntry 2147483648}


sr1646v2EthPortSwIXt2IpAdEntReasmMaxSize OBJECT IDENTIFIER ::= {sr1646v2EthPortSwIXt2 125}

sr1646v2EthPortSwIXt2IpAdEntReasmMaxSizeTable OBJECT-TYPE
   SYNTAX      SEQUENCE OF Sr1646v2EthPortSwIXt2IpAdEntReasmMaxSizeEntry
   MAX-ACCESS  not-accessible
   STATUS      current
   DESCRIPTION
      "ipAdEntReasmMaxSize"
   ::= {sr1646v2EthPortSwIXt2IpAdEntReasmMaxSize 1}

sr1646v2EthPortSwIXt2IpAdEntReasmMaxSizeEntry OBJECT-TYPE
   SYNTAX      Sr1646v2EthPortSwIXt2IpAdEntReasmMaxSizeEntry
   MAX-ACCESS  not-accessible
   STATUS      current
   DESCRIPTION
      ""
   INDEX      { sr1646v2EthPortSwIXt2IpAdEntReasmMaxSizeGlobalIx }
   ::= {sr1646v2EthPortSwIXt2IpAdEntReasmMaxSizeTable 1}

Sr1646v2EthPortSwIXt2IpAdEntReasmMaxSizeEntry ::=
   SEQUENCE
      {
      sr1646v2EthPortSwIXt2IpAdEntReasmMaxSizeGlobalIx
         GlobalIndex,
      sr1646v2EthPortSwIXt2IpAdEntReasmMaxSizeValue
         Integer32
      }

sr1646v2EthPortSwIXt2IpAdEntReasmMaxSizeGlobalIx OBJECT-TYPE
   SYNTAX      GlobalIndex
   MAX-ACCESS  not-accessible
   STATUS      current
   DESCRIPTION
      "The value of the tlsCntTreeGlobalIndex of the MANAGED OBJECT."
   ::= {sr1646v2EthPortSwIXt2IpAdEntReasmMaxSizeEntry 10}

sr1646v2EthPortSwIXt2IpAdEntReasmMaxSizeValue OBJECT-TYPE
   SYNTAX      Integer32
   MAX-ACCESS  read-only
   STATUS      current
   DESCRIPTION
      "Path: swPort.status.ipAdEntReasmMaxSize"
   ::= {sr1646v2EthPortSwIXt2IpAdEntReasmMaxSizeEntry 2147483648}


sr1646v2EthPortSwIXt2Oam OBJECT IDENTIFIER ::= {sr1646v2EthPortSwIXt2 901}

sr1646v2EthPortSwIXt2OamSSCTable OBJECT-TYPE
   SYNTAX      SEQUENCE OF Sr1646v2EthPortSwIXt2OamEntry
   MAX-ACCESS  not-accessible
   STATUS      current
   DESCRIPTION
      "OAM discovery state"
   ::= {sr1646v2EthPortSwIXt2Oam 1}

sr1646v2EthPortSwIXt2OamEntry OBJECT-TYPE
   SYNTAX      Sr1646v2EthPortSwIXt2OamEntry
   MAX-ACCESS  not-accessible
   STATUS      current
   DESCRIPTION
      ""
   INDEX      { sr1646v2EthPortSwIXt2OamGlobalIx }
   ::= {sr1646v2EthPortSwIXt2OamSSCTable 1}

Sr1646v2EthPortSwIXt2OamEntry ::=
   SEQUENCE
      {
      sr1646v2EthPortSwIXt2OamGlobalIx
         GlobalIndex,
      sr1646v2EthPortSwIXt2OamDiscovery
         INTEGER,
      sr1646v2EthPortSwIXt2OamLoopback
         INTEGER,
      sr1646v2EthPortSwIXt2OamLocalInfoVersion
         Integer32,
      sr1646v2EthPortSwIXt2OamLocalInfoRevision
         Integer32,
      sr1646v2EthPortSwIXt2OamLocalInfoStateMuxAction
         INTEGER,
      sr1646v2EthPortSwIXt2OamLocalInfoStateParserAction
         INTEGER,
      sr1646v2EthPortSwIXt2OamLocalInfoOui
         OCTET STRING,
      sr1646v2EthPortSwIXt2OamLocalInfoVendorInfo
         OCTET STRING,
      sr1646v2EthPortSwIXt2OamLocalInfoVarRetrieval
         INTEGER,
      sr1646v2EthPortSwIXt2OamLocalInfoLinkEvents
         INTEGER,
      sr1646v2EthPortSwIXt2OamLocalInfoLoopback
         INTEGER,
      sr1646v2EthPortSwIXt2OamLocalInfoUnidirectional
         INTEGER,
      sr1646v2EthPortSwIXt2OamLocalInfoMode
         INTEGER,
      sr1646v2EthPortSwIXt2OamLocalInfoMaxPduSize
         Integer32,
      sr1646v2EthPortSwIXt2OamRemoteInfoVersion
         Integer32,
      sr1646v2EthPortSwIXt2OamRemoteInfoRevision
         Integer32,
      sr1646v2EthPortSwIXt2OamRemoteInfoStateMuxAction
         INTEGER,
      sr1646v2EthPortSwIXt2OamRemoteInfoStateParserAction
         INTEGER,
      sr1646v2EthPortSwIXt2OamRemoteInfoOui
         OCTET STRING,
      sr1646v2EthPortSwIXt2OamRemoteInfoVendorInfo
         OCTET STRING,
      sr1646v2EthPortSwIXt2OamRemoteInfoVarRetrieval
         INTEGER,
      sr1646v2EthPortSwIXt2OamRemoteInfoLinkEvents
         INTEGER,
      sr1646v2EthPortSwIXt2OamRemoteInfoLoopback
         INTEGER,
      sr1646v2EthPortSwIXt2OamRemoteInfoUnidirectional
         INTEGER,
      sr1646v2EthPortSwIXt2OamRemoteInfoMode
         INTEGER,
      sr1646v2EthPortSwIXt2OamRemoteInfoMaxPduSize
         Integer32,
      sr1646v2EthPortSwIXt2OamEventsErroredSymbolWindow
         Integer32,
      sr1646v2EthPortSwIXt2OamEventsErroredSymbolThreshold
         OCTET STRING,
      sr1646v2EthPortSwIXt2OamEventsErroredFramePeriodWindow
         INTEGER,
      sr1646v2EthPortSwIXt2OamEventsErroredFramePeriodThreshold
         Integer32,
      sr1646v2EthPortSwIXt2OamEventsErroredFrameWindow
         Integer32,
      sr1646v2EthPortSwIXt2OamEventsErroredFrameThreshold
         Integer32,
      sr1646v2EthPortSwIXt2OamEventsErroredFrameSecondsWindow
         Integer32,
      sr1646v2EthPortSwIXt2OamEventsErroredFrameSecondsThreshold
         Integer32
      }

sr1646v2EthPortSwIXt2OamGlobalIx OBJECT-TYPE
   SYNTAX      GlobalIndex
   MAX-ACCESS  not-accessible
   STATUS      current
   DESCRIPTION
      "The value of the tlsCntTreeGlobalIndex of the MANAGED OBJECT."
   ::= {sr1646v2EthPortSwIXt2OamEntry 10}

sr1646v2EthPortSwIXt2OamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: swPort.status.oam.discovery

       Possibilities:
               fault   (0)
               sendLocal   (1)
               passiveWait   (2)
               sendLocalRemote   (3)
               sendLocalRemoteOk   (4)
               sendAny   (5)"
   ::= {sr1646v2EthPortSwIXt2OamEntry 16777216}

sr1646v2EthPortSwIXt2OamLoopback OBJECT-TYPE
   SYNTAX      INTEGER
               {
               idle (0),
               waiting (1),
               localRunning (2),
               remoteRunning (3)
               }
   MAX-ACCESS  read-only
   STATUS      current
   DESCRIPTION
      "Path: swPort.status.oam.loopback

       Possibilities:
               idle   (0)
               waiting   (1)
               localRunning   (2)
               remoteRunning   (3)"
   ::= {sr1646v2EthPortSwIXt2OamEntry 33554432}

sr1646v2EthPortSwIXt2OamLocalInfoVersion OBJECT-TYPE
   SYNTAX      Integer32
   MAX-ACCESS  read-only
   STATUS      current
   DESCRIPTION
      "Path: swPort.status.oam.localInfo.version"
   ::= {sr1646v2EthPortSwIXt2OamEntry 50397184}

sr1646v2EthPortSwIXt2OamLocalInfoRevision OBJECT-TYPE
   SYNTAX      Integer32
   MAX-ACCESS  read-only
   STATUS      current
   DESCRIPTION
      "Path: swPort.status.oam.localInfo.revision"
   ::= {sr1646v2EthPortSwIXt2OamEntry 50462720}

sr1646v2EthPortSwIXt2OamLocalInfoStateMuxAction OBJECT-TYPE
   SYNTAX      INTEGER
               {
               forwarding (0),
               discarding (1)
               }
   MAX-ACCESS  read-only
   STATUS      current
   DESCRIPTION
      "Path: swPort.status.oam.localInfo.state.muxAction

       Possibilities:
               forwarding   (0)
               discarding   (1)"
   ::= {sr1646v2EthPortSwIXt2OamEntry 50528512}

sr1646v2EthPortSwIXt2OamLocalInfoStateParserAction OBJECT-TYPE
   SYNTAX      INTEGER
               {
               forwarding (0),
               loopback (1),
               discarding (2),
               reserved (3)
               }
   MAX-ACCESS  read-only
   STATUS      current
   DESCRIPTION
      "Path: swPort.status.oam.localInfo.state.parserAction

       Possibilities:
               forwarding   (0)
               loopback   (1)
               discarding   (2)
               reserved   (3)"
   ::= {sr1646v2EthPortSwIXt2OamEntry 50528768}

sr1646v2EthPortSwIXt2OamLocalInfoOui OBJECT-TYPE
   SYNTAX      OCTET STRING
   MAX-ACCESS  read-only
   STATUS      current
   DESCRIPTION
      "Path: swPort.status.oam.localInfo.oui"
   ::= {sr1646v2EthPortSwIXt2OamEntry 50593792}

sr1646v2EthPortSwIXt2OamLocalInfoVendorInfo OBJECT-TYPE
   SYNTAX      OCTET STRING
   MAX-ACCESS  read-only
   STATUS      current
   DESCRIPTION
      "Path: swPort.status.oam.localInfo.vendorInfo"
   ::= {sr1646v2EthPortSwIXt2OamEntry 50659328}

sr1646v2EthPortSwIXt2OamLocalInfoVarRetrieval OBJECT-TYPE
   SYNTAX      INTEGER
               {
               notSupported (0),
               supported (1)
               }
   MAX-ACCESS  read-only
   STATUS      current
   DESCRIPTION
      "Path: swPort.status.oam.localInfo.varRetrieval

       Possibilities:
               notSupported   (0)
               supported   (1)"
   ::= {sr1646v2EthPortSwIXt2OamEntry 50724864}

sr1646v2EthPortSwIXt2OamLocalInfoLinkEvents OBJECT-TYPE
   SYNTAX      INTEGER
               {
               ignored (0),
               interpreted (1)
               }
   MAX-ACCESS  read-only
   STATUS      current
   DESCRIPTION
      "Path: swPort.status.oam.localInfo.linkEvents

       Possibilities:
               ignored   (0)
               interpreted   (1)"
   ::= {sr1646v2EthPortSwIXt2OamEntry 50790400}

sr1646v2EthPortSwIXt2OamLocalInfoLoopback OBJECT-TYPE
   SYNTAX      INTEGER
               {
               notSupported (0),
               supported (1)
               }
   MAX-ACCESS  read-only
   STATUS      current
   DESCRIPTION
      "Path: swPort.status.oam.localInfo.loopback

       Possibilities:
               notSupported   (0)
               supported   (1)"
   ::= {sr1646v2EthPortSwIXt2OamEntry 50855936}

sr1646v2EthPortSwIXt2OamLocalInfoUnidirectional OBJECT-TYPE
   SYNTAX      INTEGER
               {
               notSupported (0),
               supported (1)
               }
   MAX-ACCESS  read-only
   STATUS      current
   DESCRIPTION
      "Path: swPort.status.oam.localInfo.unidirectional

       Possibilities:
               notSupported   (0)
               supported   (1)"
   ::= {sr1646v2EthPortSwIXt2OamEntry 50921472}

sr1646v2EthPortSwIXt2OamLocalInfoMode OBJECT-TYPE
   SYNTAX      INTEGER
               {
               passive (0),
               active (1)
               }
   MAX-ACCESS  read-only
   STATUS      current
   DESCRIPTION
      "Path: swPort.status.oam.localInfo.mode

       Possibilities:
               passive   (0)
               active   (1)"
   ::= {sr1646v2EthPortSwIXt2OamEntry 50987008}

sr1646v2EthPortSwIXt2OamLocalInfoMaxPduSize OBJECT-TYPE
   SYNTAX      Integer32
   MAX-ACCESS  read-only
   STATUS      current
   DESCRIPTION
      "Path: swPort.status.oam.localInfo.maxPduSize"
   ::= {sr1646v2EthPortSwIXt2OamEntry 51052544}

sr1646v2EthPortSwIXt2OamRemoteInfoVersion OBJECT-TYPE
   SYNTAX      Integer32
   MAX-ACCESS  read-only
   STATUS      current
   DESCRIPTION
      "Path: swPort.status.oam.remoteInfo.version"
   ::= {sr1646v2EthPortSwIXt2OamEntry 67174400}

sr1646v2EthPortSwIXt2OamRemoteInfoRevision OBJECT-TYPE
   SYNTAX      Integer32
   MAX-ACCESS  read-only
   STATUS      current
   DESCRIPTION
      "Path: swPort.status.oam.remoteInfo.revision"
   ::= {sr1646v2EthPortSwIXt2OamEntry 67239936}

sr1646v2EthPortSwIXt2OamRemoteInfoStateMuxAction OBJECT-TYPE
   SYNTAX      INTEGER
               {
               forwarding (0),
               discarding (1)
               }
   MAX-ACCESS  read-only
   STATUS      current
   DESCRIPTION
      "Path: swPort.status.oam.remoteInfo.state.muxAction

       Possibilities:
               forwarding   (0)
               discarding   (1)"
   ::= {sr1646v2EthPortSwIXt2OamEntry 67305728}

sr1646v2EthPortSwIXt2OamRemoteInfoStateParserAction OBJECT-TYPE
   SYNTAX      INTEGER
               {
               forwarding (0),
               loopback (1),
               discarding (2),
               reserved (3)
               }
   MAX-ACCESS  read-only
   STATUS      current
   DESCRIPTION
      "Path: swPort.status.oam.remoteInfo.state.parserAction

       Possibilities:
               forwarding   (0)
               loopback   (1)
               discarding   (2)
               reserved   (3)"
   ::= {sr1646v2EthPortSwIXt2OamEntry 67305984}

sr1646v2EthPortSwIXt2OamRemoteInfoOui OBJECT-TYPE
   SYNTAX      OCTET STRING
   MAX-ACCESS  read-only
   STATUS      current
   DESCRIPTION
      "Path: swPort.status.oam.remoteInfo.oui"
   ::= {sr1646v2EthPortSwIXt2OamEntry 67371008}

sr1646v2EthPortSwIXt2OamRemoteInfoVendorInfo OBJECT-TYPE
   SYNTAX      OCTET STRING
   MAX-ACCESS  read-only
   STATUS      current
   DESCRIPTION
      "Path: swPort.status.oam.remoteInfo.vendorInfo"
   ::= {sr1646v2EthPortSwIXt2OamEntry 67436544}

sr1646v2EthPortSwIXt2OamRemoteInfoVarRetrieval OBJECT-TYPE
   SYNTAX      INTEGER
               {
               notSupported (0),
               supported (1)
               }
   MAX-ACCESS  read-only
   STATUS      current
   DESCRIPTION
      "Path: swPort.status.oam.remoteInfo.varRetrieval

       Possibilities:
               notSupported   (0)
               supported   (1)"
   ::= {sr1646v2EthPortSwIXt2OamEntry 67502080}

sr1646v2EthPortSwIXt2OamRemoteInfoLinkEvents OBJECT-TYPE
   SYNTAX      INTEGER
               {
               ignored (0),
               interpreted (1)
               }
   MAX-ACCESS  read-only
   STATUS      current
   DESCRIPTION
      "Path: swPort.status.oam.remoteInfo.linkEvents

       Possibilities:
               ignored   (0)
               interpreted   (1)"
   ::= {sr1646v2EthPortSwIXt2OamEntry 67567616}

sr1646v2EthPortSwIXt2OamRemoteInfoLoopback OBJECT-TYPE
   SYNTAX      INTEGER
               {
               notSupported (0),
               supported (1)
               }
   MAX-ACCESS  read-only
   STATUS      current
   DESCRIPTION
      "Path: swPort.status.oam.remoteInfo.loopback

       Possibilities:
               notSupported   (0)
               supported   (1)"
   ::= {sr1646v2EthPortSwIXt2OamEntry 67633152}

sr1646v2EthPortSwIXt2OamRemoteInfoUnidirectional OBJECT-TYPE
   SYNTAX      INTEGER
               {
               notSupported (0),
               supported (1)
               }
   MAX-ACCESS  read-only
   STATUS      current
   DESCRIPTION
      "Path: swPort.status.oam.remoteInfo.unidirectional

       Possibilities:
               notSupported   (0)
               supported   (1)"
   ::= {sr1646v2EthPortSwIXt2OamEntry 67698688}

sr1646v2EthPortSwIXt2OamRemoteInfoMode OBJECT-TYPE
   SYNTAX      INTEGER
               {
               passive (0),
               active (1)
               }
   MAX-ACCESS  read-only
   STATUS      current
   DESCRIPTION
      "Path: swPort.status.oam.remoteInfo.mode

       Possibilities:
               passive   (0)
               active   (1)"
   ::= {sr1646v2EthPortSwIXt2OamEntry 67764224}

sr1646v2EthPortSwIXt2OamRemoteInfoMaxPduSize OBJECT-TYPE
   SYNTAX      Integer32
   MAX-ACCESS  read-only
   STATUS      current
   DESCRIPTION
      "Path: swPort.status.oam.remoteInfo.maxPduSize"
   ::= {sr1646v2EthPortSwIXt2OamEntry 67829760}

sr1646v2EthPortSwIXt2OamEventsErroredSymbolWindow OBJECT-TYPE
   SYNTAX      Integer32
   UNITS       "symbols"
   MAX-ACCESS  read-only
   STATUS      current
   DESCRIPTION
      "Path: swPort.status.oam.events.erroredSymbol.window

       unit name = symbols"
   ::= {sr1646v2EthPortSwIXt2OamEntry 83951872}

sr1646v2EthPortSwIXt2OamEventsErroredSymbolThreshold OBJECT-TYPE
   SYNTAX      OCTET STRING
   UNITS       "symbols"
   MAX-ACCESS  read-only
   STATUS      current
   DESCRIPTION
      "Path: swPort.status.oam.events.erroredSymbol.threshold

       unit name = symbols"
   ::= {sr1646v2EthPortSwIXt2OamEntry 83952128}

sr1646v2EthPortSwIXt2OamEventsErroredFramePeriodWindow OBJECT-TYPE
   SYNTAX      INTEGER
               {
               default (0)
               }
   UNITS       "frames"
   MAX-ACCESS  read-only
   STATUS      current
   DESCRIPTION
      "Path: swPort.status.oam.events.erroredFramePeriod.window

       unit name = frames

       Possibilities:
               default   (0)"
   ::= {sr1646v2EthPortSwIXt2OamEntry 84017408}

sr1646v2EthPortSwIXt2OamEventsErroredFramePeriodThreshold OBJECT-TYPE
   SYNTAX      Integer32
   UNITS       "frames"
   MAX-ACCESS  read-only
   STATUS      current
   DESCRIPTION
      "Path: swPort.status.oam.events.erroredFramePeriod.threshold

       unit name = frames"
   ::= {sr1646v2EthPortSwIXt2OamEntry 84017664}

sr1646v2EthPortSwIXt2OamEventsErroredFrameWindow OBJECT-TYPE
   SYNTAX      Integer32
   UNITS       "100msec"
   MAX-ACCESS  read-only
   STATUS      current
   DESCRIPTION
      "Path: swPort.status.oam.events.erroredFrame.window

       unit name = 100msec"
   ::= {sr1646v2EthPortSwIXt2OamEntry 84082944}

sr1646v2EthPortSwIXt2OamEventsErroredFrameThreshold OBJECT-TYPE
   SYNTAX      Integer32
   UNITS       "frames"
   MAX-ACCESS  read-only
   STATUS      current
   DESCRIPTION
      "Path: swPort.status.oam.events.erroredFrame.threshold

       unit name = frames"
   ::= {sr1646v2EthPortSwIXt2OamEntry 84083200}

sr1646v2EthPortSwIXt2OamEventsErroredFrameSecondsWindow OBJECT-TYPE
   SYNTAX      Integer32
   UNITS       "100msec"
   MAX-ACCESS  read-only
   STATUS      current
   DESCRIPTION
      "Path: swPort.status.oam.events.erroredFrameSeconds.window

       unit name = 100msec"
   ::= {sr1646v2EthPortSwIXt2OamEntry 84148480}

sr1646v2EthPortSwIXt2OamEventsErroredFrameSecondsThreshold OBJECT-TYPE
   SYNTAX      Integer32
   UNITS       "frames"
   MAX-ACCESS  read-only
   STATUS      current
   DESCRIPTION
      "Path: swPort.status.oam.events.erroredFrameSeconds.threshold

       unit name = frames"
   ::= {sr1646v2EthPortSwIXt2OamEntry 84148736}


sr1646v2EthPortSwIXt2OamEventLog OBJECT IDENTIFIER ::= {sr1646v2EthPortSwIXt2 911}

sr1646v2EthPortSwIXt2OamEventLogSSCTable OBJECT-TYPE
   SYNTAX      SEQUENCE OF Sr1646v2EthPortSwIXt2OamEventLogEntry
   MAX-ACCESS  not-accessible
   STATUS      current
   DESCRIPTION
      "OAM event log"
   ::= {sr1646v2EthPortSwIXt2OamEventLog 1}

sr1646v2EthPortSwIXt2OamEventLogEntry OBJECT-TYPE
   SYNTAX      Sr1646v2EthPortSwIXt2OamEventLogEntry
   MAX-ACCESS  not-accessible
   STATUS      current
   DESCRIPTION
      ""
   INDEX      { sr1646v2EthPortSwIXt2OamEventLogGlobalIx,
                sr1646v2EthPortSwIXt2OamEventLogTableIx }
   ::= {sr1646v2EthPortSwIXt2OamEventLogSSCTable 1}

Sr1646v2EthPortSwIXt2OamEventLogEntry ::=
   SEQUENCE
      {
      sr1646v2EthPortSwIXt2OamEventLogGlobalIx
         GlobalIndex,
      sr1646v2EthPortSwIXt2OamEventLogTableIx
         TableIndex,
      sr1646v2EthPortSwIXt2OamEventLogSysUpTime
         TimeTicks,
      sr1646v2EthPortSwIXt2OamEventLogLocation
         INTEGER,
      sr1646v2EthPortSwIXt2OamEventLogType
         INTEGER,
      sr1646v2EthPortSwIXt2OamEventLogOui
         OCTET STRING,
      sr1646v2EthPortSwIXt2OamEventLogWindow
         Counter64,
      sr1646v2EthPortSwIXt2OamEventLogThreshold
         Counter64,
      sr1646v2EthPortSwIXt2OamEventLogTotal
         Counter32,
      sr1646v2EthPortSwIXt2OamEventLogValue
         Counter64,
      sr1646v2EthPortSwIXt2OamEventLogRunningTotal
         Counter64
      }

sr1646v2EthPortSwIXt2OamEventLogGlobalIx OBJECT-TYPE
   SYNTAX      GlobalIndex
   MAX-ACCESS  not-accessible
   STATUS      current
   DESCRIPTION
      "The value of the tlsCntTreeGlobalIndex of the MANAGED OBJECT."
   ::= {sr1646v2EthPortSwIXt2OamEventLogEntry 10}

sr1646v2EthPortSwIXt2OamEventLogTableIx OBJECT-TYPE
   SYNTAX      TableIndex
   MAX-ACCESS  not-accessible
   STATUS      current
   DESCRIPTION
      ""
   ::= {sr1646v2EthPortSwIXt2OamEventLogEntry 11}

sr1646v2EthPortSwIXt2OamEventLogSysUpTime OBJECT-TYPE
   SYNTAX      TimeTicks
   MAX-ACCESS  read-only
   STATUS      current
   DESCRIPTION
      "Path: swPort.status.oamEventLog.sysUpTime

       Time in centi-second."
   ::= {sr1646v2EthPortSwIXt2OamEventLogEntry 16777216}

sr1646v2EthPortSwIXt2OamEventLogLocation OBJECT-TYPE
   SYNTAX      INTEGER
               {
               local (1),
               remote (2)
               }
   MAX-ACCESS  read-only
   STATUS      current
   DESCRIPTION
      "Path: swPort.status.oamEventLog.location

       Possibilities:
               local   (1)
               remote   (2)"
   ::= {sr1646v2EthPortSwIXt2OamEventLogEntry 33554432}

sr1646v2EthPortSwIXt2OamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: swPort.status.oamEventLog.type

       Possibilities:
               erroredSymbols   (1)
               erroredFramePeriod   (2)
               erroredFrame   (3)
               erroredFrameSeconds   (4)
               linkFault   (256)
               dyingGasp   (257)
               criticalLink   (258)"
   ::= {sr1646v2EthPortSwIXt2OamEventLogEntry 50331648}

sr1646v2EthPortSwIXt2OamEventLogOui OBJECT-TYPE
   SYNTAX      OCTET STRING
   MAX-ACCESS  read-only
   STATUS      current
   DESCRIPTION
      "Path: swPort.status.oamEventLog.oui"
   ::= {sr1646v2EthPortSwIXt2OamEventLogEntry 67108864}

sr1646v2EthPortSwIXt2OamEventLogWindow OBJECT-TYPE
   SYNTAX      Counter64
   MAX-ACCESS  read-only
   STATUS      current
   DESCRIPTION
      "Path: swPort.status.oamEventLog.window

       64 bit unsigned wrappable counter."
   ::= {sr1646v2EthPortSwIXt2OamEventLogEntry 83886080}

sr1646v2EthPortSwIXt2OamEventLogThreshold OBJECT-TYPE
   SYNTAX      Counter64
   MAX-ACCESS  read-only
   STATUS      current
   DESCRIPTION
      "Path: swPort.status.oamEventLog.threshold

       64 bit unsigned wrappable counter."
   ::= {sr1646v2EthPortSwIXt2OamEventLogEntry 100663296}

sr1646v2EthPortSwIXt2OamEventLogTotal OBJECT-TYPE
   SYNTAX      Counter32
   MAX-ACCESS  read-only
   STATUS      current
   DESCRIPTION
      "Path: swPort.status.oamEventLog.total

       32 bit unsigned wrappable counter."
   ::= {sr1646v2EthPortSwIXt2OamEventLogEntry 117440512}

sr1646v2EthPortSwIXt2OamEventLogValue OBJECT-TYPE
   SYNTAX      Counter64
   MAX-ACCESS  read-only
   STATUS      current
   DESCRIPTION
      "Path: swPort.status.oamEventLog.value

       64 bit unsigned wrappable counter."
   ::= {sr1646v2EthPortSwIXt2OamEventLogEntry 134217728}

sr1646v2EthPortSwIXt2OamEventLogRunningTotal OBJECT-TYPE
   SYNTAX      Counter64
   MAX-ACCESS  read-only
   STATUS      current
   DESCRIPTION
      "Path: swPort.status.oamEventLog.runningTotal

       64 bit unsigned wrappable counter."
   ::= {sr1646v2EthPortSwIXt2OamEventLogEntry 150994944}


sr1646v2EthPortSwIXt2Vlan OBJECT IDENTIFIER ::= {sr1646v2EthPortSwIXt2 34}

sr1646v2EthPortSwIXt2VlanSSCTable OBJECT-TYPE
   SYNTAX      SEQUENCE OF Sr1646v2EthPortSwIXt2VlanEntry
   MAX-ACCESS  not-accessible
   STATUS      current
   DESCRIPTION
      ""
   ::= {sr1646v2EthPortSwIXt2Vlan 1}

sr1646v2EthPortSwIXt2VlanEntry OBJECT-TYPE
   SYNTAX      Sr1646v2EthPortSwIXt2VlanEntry
   MAX-ACCESS  not-accessible
   STATUS      current
   DESCRIPTION
      ""
   INDEX      { sr1646v2EthPortSwIXt2VlanGlobalIx,
                sr1646v2EthPortSwIXt2VlanTableIx }
   ::= {sr1646v2EthPortSwIXt2VlanSSCTable 1}

Sr1646v2EthPortSwIXt2VlanEntry ::=
   SEQUENCE
      {
      sr1646v2EthPortSwIXt2VlanGlobalIx
         GlobalIndex,
      sr1646v2EthPortSwIXt2VlanTableIx
         TableIndex,
      sr1646v2EthPortSwIXt2VlanName
         DisplayString,
      sr1646v2EthPortSwIXt2VlanMode
         INTEGER,
      sr1646v2EthPortSwIXt2VlanIfOperStatus
         INTEGER,
      sr1646v2EthPortSwIXt2VlanIfLastChange
         TimeTicks,
      sr1646v2EthPortSwIXt2VlanIfLastChangeDate
         DisplayString,
      sr1646v2EthPortSwIXt2VlanIpAddress
         IpAddress,
      sr1646v2EthPortSwIXt2VlanIpNetMask
         IpAddress,
      sr1646v2EthPortSwIXt2VlanIpRemote
         IpAddress,
      sr1646v2EthPortSwIXt2VlanIpDhcpStatus
         INTEGER,
      sr1646v2EthPortSwIXt2VlanIpDhcpLeaseTime
         TimeTicks,
      sr1646v2EthPortSwIXt2VlanIpV6State
         INTEGER,
      sr1646v2EthPortSwIXt2VlanIpV6InterfaceId
         OCTET STRING,
      sr1646v2EthPortSwIXt2VlanIpV6LinkMtu
         Integer32,
      sr1646v2EthPortSwIXt2VlanIpV6HopLimit
         Integer32,
      sr1646v2EthPortSwIXt2VlanIpV6DhcpIaid
         Counter32,
      sr1646v2EthPortSwIXt2VlanIpV6RaRcvOption
         Integer32,
      sr1646v2EthPortSwIXt2VlanBridgingStatus
         INTEGER,
      sr1646v2EthPortSwIXt2VlanBridgingSpanningTreePortRole
         INTEGER,
      sr1646v2EthPortSwIXt2VlanBridgingSpanningTreePortId
         Integer32,
      sr1646v2EthPortSwIXt2VlanBridgingSpanningTreePpCostExtPathCost
         Integer32,
      sr1646v2EthPortSwIXt2VlanBridgingSpanningTreePpCostIntPathCost
         Integer32,
      sr1646v2EthPortSwIXt2VlanBridgingSpanningTreeExtRpCost
         Integer32,
      sr1646v2EthPortSwIXt2VlanBridgingSpanningTreeIntRpCost
         Integer32,
      sr1646v2EthPortSwIXt2VlanBridgingSpanningTreeDesBrIdPriority
         Integer32,
      sr1646v2EthPortSwIXt2VlanBridgingSpanningTreeDesBrIdMacAddress
         OCTET STRING,
      sr1646v2EthPortSwIXt2VlanBridgingSpanningTreeDesPrtId
         Integer32,
      sr1646v2EthPortSwIXt2VlanBridgingSpanningTreeDesInt
         INTEGER,
      sr1646v2EthPortSwIXt2VlanBridgingSpanningTreeEdgeDetection
         INTEGER,
      sr1646v2EthPortSwIXt2VlanVlanVid
         Integer32,
      sr1646v2EthPortSwIXt2VlanPppOEthDiscState
         INTEGER,
      sr1646v2EthPortSwIXt2VlanPppOEthPeerMac
         OCTET STRING,
      sr1646v2EthPortSwIXt2VlanPppOEthServiceName
         DisplayString,
      sr1646v2EthPortSwIXt2VlanPppLcpState
         INTEGER,
      sr1646v2EthPortSwIXt2VlanPppIpcpState
         INTEGER,
      sr1646v2EthPortSwIXt2VlanPppIp6cpState
         INTEGER,
      sr1646v2EthPortSwIXt2VlanPppMyAutSt
         INTEGER,
      sr1646v2EthPortSwIXt2VlanPppHisAutSt
         INTEGER,
      sr1646v2EthPortSwIXt2VlanPppMru
         Integer32
      }

sr1646v2EthPortSwIXt2VlanGlobalIx OBJECT-TYPE
   SYNTAX      GlobalIndex
   MAX-ACCESS  not-accessible
   STATUS      current
   DESCRIPTION
      "The value of the tlsCntTreeGlobalIndex of the MANAGED OBJECT."
   ::= {sr1646v2EthPortSwIXt2VlanEntry 10}

sr1646v2EthPortSwIXt2VlanTableIx OBJECT-TYPE
   SYNTAX      TableIndex
   MAX-ACCESS  not-accessible
   STATUS      current
   DESCRIPTION
      ""
   ::= {sr1646v2EthPortSwIXt2VlanEntry 11}

sr1646v2EthPortSwIXt2VlanName OBJECT-TYPE
   SYNTAX      DisplayString
   MAX-ACCESS  read-only
   STATUS      current
   DESCRIPTION
      "Path: swPort.status.vlan.name"
   ::= {sr1646v2EthPortSwIXt2VlanEntry 16777216}

sr1646v2EthPortSwIXt2VlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2EthPortSwIXt2VlanEntry 335544320}

sr1646v2EthPortSwIXt2VlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.vlan.ifOperStatus

       Possibilities:
               up   (1)
               down   (2)
               testing   (3)
               unknown   (4)
               dormant   (5)
               notPresent   (6)
               lowerLayerDown   (7)"
   ::= {sr1646v2EthPortSwIXt2VlanEntry 1795162112}

sr1646v2EthPortSwIXt2VlanIfLastChange OBJECT-TYPE
   SYNTAX      TimeTicks
   MAX-ACCESS  read-only
   STATUS      current
   DESCRIPTION
      "Path: swPort.status.vlan.ifLastChange

       Time in centi-second."
   ::= {sr1646v2EthPortSwIXt2VlanEntry 1811939328}

sr1646v2EthPortSwIXt2VlanIfLastChangeDate OBJECT-TYPE
   SYNTAX      DisplayString
   MAX-ACCESS  read-only
   STATUS      current
   DESCRIPTION
      "Path: swPort.status.vlan.ifLastChangeDate"
   ::= {sr1646v2EthPortSwIXt2VlanEntry 3070230528}

sr1646v2EthPortSwIXt2VlanIpAddress OBJECT-TYPE
   SYNTAX      IpAddress
   MAX-ACCESS  read-only
   STATUS      current
   DESCRIPTION
      "Path: swPort.status.vlan.ip.address"
   ::= {sr1646v2EthPortSwIXt2VlanEntry 51380224}

sr1646v2EthPortSwIXt2VlanIpNetMask OBJECT-TYPE
   SYNTAX      IpAddress
   MAX-ACCESS  read-only
   STATUS      current
   DESCRIPTION
      "Path: swPort.status.vlan.ip.netMask"
   ::= {sr1646v2EthPortSwIXt2VlanEntry 51445760}

sr1646v2EthPortSwIXt2VlanIpRemote OBJECT-TYPE
   SYNTAX      IpAddress
   MAX-ACCESS  read-only
   STATUS      current
   DESCRIPTION
      "Path: swPort.status.vlan.ip.remote"
   ::= {sr1646v2EthPortSwIXt2VlanEntry 51511296}

sr1646v2EthPortSwIXt2VlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: swPort.status.vlan.ip.dhcp.status

       Possibilities:
               none   (0)
               selecting   (1)
               requesting   (2)
               rebinding   (3)
               bound   (4)
               renewing   (5)
               rebooting   (6)
               initreboot   (7)"
   ::= {sr1646v2EthPortSwIXt2VlanEntry 51904768}

sr1646v2EthPortSwIXt2VlanIpDhcpLeaseTime OBJECT-TYPE
   SYNTAX      TimeTicks
   MAX-ACCESS  read-only
   STATUS      current
   DESCRIPTION
      "Path: swPort.status.vlan.ip.dhcp.leaseTime

       Time in centi-second."
   ::= {sr1646v2EthPortSwIXt2VlanEntry 51905024}

sr1646v2EthPortSwIXt2VlanIpV6State OBJECT-TYPE
   SYNTAX      INTEGER
               {
               disabled (0),
               enabled (1)
               }
   MAX-ACCESS  read-only
   STATUS      current
   DESCRIPTION
      "Path: swPort.status.vlan.ipV6.state

       Possibilities:
               disabled   (0)
               enabled   (1)"
   ::= {sr1646v2EthPortSwIXt2VlanEntry 100728832}

sr1646v2EthPortSwIXt2VlanIpV6InterfaceId OBJECT-TYPE
   SYNTAX      OCTET STRING
   MAX-ACCESS  read-only
   STATUS      current
   DESCRIPTION
      "Path: swPort.status.vlan.ipV6.interfaceId"
   ::= {sr1646v2EthPortSwIXt2VlanEntry 100794368}

sr1646v2EthPortSwIXt2VlanIpV6LinkMtu OBJECT-TYPE
   SYNTAX      Integer32
   MAX-ACCESS  read-only
   STATUS      current
   DESCRIPTION
      "Path: swPort.status.vlan.ipV6.linkMtu"
   ::= {sr1646v2EthPortSwIXt2VlanEntry 100925440}

sr1646v2EthPortSwIXt2VlanIpV6HopLimit OBJECT-TYPE
   SYNTAX      Integer32
   MAX-ACCESS  read-only
   STATUS      current
   DESCRIPTION
      "Path: swPort.status.vlan.ipV6.hopLimit"
   ::= {sr1646v2EthPortSwIXt2VlanEntry 100990976}

sr1646v2EthPortSwIXt2VlanIpV6DhcpIaid OBJECT-TYPE
   SYNTAX      Counter32
   MAX-ACCESS  read-only
   STATUS      current
   DESCRIPTION
      "Path: swPort.status.vlan.ipV6.dhcp.iaid

       32 bit unsigned wrappable counter."
   ::= {sr1646v2EthPortSwIXt2VlanEntry 101056768}

sr1646v2EthPortSwIXt2VlanIpV6RaRcvOption OBJECT-TYPE
   SYNTAX      Integer32
   MAX-ACCESS  read-only
   STATUS      current
   DESCRIPTION
      "Path: swPort.status.vlan.ipV6.raRcvOption

       Bit meanings:
               bit 0 = linkMtu,
               bit 1 = srcLinkLayer,
               bit 2 = prefixInfo,
               bit 3 = rdnss,
               bit 4 = dnssl"
   ::= {sr1646v2EthPortSwIXt2VlanEntry 101122048}

sr1646v2EthPortSwIXt2VlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: swPort.status.vlan.bridging.status

       Possibilities:
               disabled   (0)
               discarding   (1)
               learning   (2)
               forwarding   (3)
               backupBlockedIntfDown   (256)
               backupBlockedIntfUp   (259)
               shutdown   (255)"
   ::= {sr1646v2EthPortSwIXt2VlanEntry 453050368}

sr1646v2EthPortSwIXt2VlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: swPort.status.vlan.bridging.spanningTree.portRole

       Possibilities:
               none   (0)
               root   (1)
               designated   (2)
               alternate   (3)
               backup   (4)
               disabled   (5)
               master   (6)"
   ::= {sr1646v2EthPortSwIXt2VlanEntry 453116160}

sr1646v2EthPortSwIXt2VlanBridgingSpanningTreePortId OBJECT-TYPE
   SYNTAX      Integer32
   MAX-ACCESS  read-only
   STATUS      current
   DESCRIPTION
      "Path: swPort.status.vlan.bridging.spanningTree.portId"
   ::= {sr1646v2EthPortSwIXt2VlanEntry 453116416}

sr1646v2EthPortSwIXt2VlanBridgingSpanningTreePpCostExtPathCost OBJECT-TYPE
   SYNTAX      Integer32
   MAX-ACCESS  read-only
   STATUS      current
   DESCRIPTION
      "Path: swPort.status.vlan.bridging.spanningTree.portPathCosts.extPathCost"
   ::= {sr1646v2EthPortSwIXt2VlanEntry 453116673}

sr1646v2EthPortSwIXt2VlanBridgingSpanningTreePpCostIntPathCost OBJECT-TYPE
   SYNTAX      Integer32
   MAX-ACCESS  read-only
   STATUS      current
   DESCRIPTION
      "Path: swPort.status.vlan.bridging.spanningTree.portPathCosts.intPathCost"
   ::= {sr1646v2EthPortSwIXt2VlanEntry 453116674}

sr1646v2EthPortSwIXt2VlanBridgingSpanningTreeExtRpCost OBJECT-TYPE
   SYNTAX      Integer32
   MAX-ACCESS  read-only
   STATUS      current
   DESCRIPTION
      "Path: swPort.status.vlan.bridging.spanningTree.extRootPathCost"
   ::= {sr1646v2EthPortSwIXt2VlanEntry 453116928}

sr1646v2EthPortSwIXt2VlanBridgingSpanningTreeIntRpCost OBJECT-TYPE
   SYNTAX      Integer32
   MAX-ACCESS  read-only
   STATUS      current
   DESCRIPTION
      "Path: swPort.status.vlan.bridging.spanningTree.intRootPathCost"
   ::= {sr1646v2EthPortSwIXt2VlanEntry 453117184}

sr1646v2EthPortSwIXt2VlanBridgingSpanningTreeDesBrIdPriority OBJECT-TYPE
   SYNTAX      Integer32
   MAX-ACCESS  read-only
   STATUS      current
   DESCRIPTION
      "Path: swPort.status.vlan.bridging.spanningTree.designatedBridgeId.priority"
   ::= {sr1646v2EthPortSwIXt2VlanEntry 453117441}

sr1646v2EthPortSwIXt2VlanBridgingSpanningTreeDesBrIdMacAddress OBJECT-TYPE
   SYNTAX      OCTET STRING
   MAX-ACCESS  read-only
   STATUS      current
   DESCRIPTION
      "Path: swPort.status.vlan.bridging.spanningTree.designatedBridgeId.macAddress

       MAC address."
   ::= {sr1646v2EthPortSwIXt2VlanEntry 453117442}

sr1646v2EthPortSwIXt2VlanBridgingSpanningTreeDesPrtId OBJECT-TYPE
   SYNTAX      Integer32
   MAX-ACCESS  read-only
   STATUS      current
   DESCRIPTION
      "Path: swPort.status.vlan.bridging.spanningTree.designatedPortId"
   ::= {sr1646v2EthPortSwIXt2VlanEntry 453117696}

sr1646v2EthPortSwIXt2VlanBridgingSpanningTreeDesInt OBJECT-TYPE
   SYNTAX      INTEGER
               {
               no (0),
               yes (1)
               }
   MAX-ACCESS  read-only
   STATUS      current
   DESCRIPTION
      "Path: swPort.status.vlan.bridging.spanningTree.designatedOrInternal

       Possibilities:
               no   (0)
               yes   (1)"
   ::= {sr1646v2EthPortSwIXt2VlanEntry 453117952}

sr1646v2EthPortSwIXt2VlanBridgingSpanningTreeEdgeDetection OBJECT-TYPE
   SYNTAX      INTEGER
               {
               none (0),
               edge (1),
               notEdge (2)
               }
   MAX-ACCESS  read-only
   STATUS      current
   DESCRIPTION
      "Path: swPort.status.vlan.bridging.spanningTree.edgeDetection

       Possibilities:
               none   (0)
               edge   (1)
               notEdge   (2)"
   ::= {sr1646v2EthPortSwIXt2VlanEntry 453118208}

sr1646v2EthPortSwIXt2VlanVlanVid OBJECT-TYPE
   SYNTAX      Integer32
   MAX-ACCESS  read-only
   STATUS      current
   DESCRIPTION
      "Path: swPort.status.vlan.vlan.vid"
   ::= {sr1646v2EthPortSwIXt2VlanEntry 234946560}

sr1646v2EthPortSwIXt2VlanPppOEthDiscState OBJECT-TYPE
   SYNTAX      INTEGER
               {
               idle (0),
               waitForPADO (1),
               waitForPADS (2),
               established (3)
               }
   MAX-ACCESS  read-only
   STATUS      current
   DESCRIPTION
      "Path: swPort.status.vlan.pppOverEth.discState

       Possibilities:
               idle   (0)
               waitForPADO   (1)
               waitForPADS   (2)
               established   (3)"
   ::= {sr1646v2EthPortSwIXt2VlanEntry 67174400}

sr1646v2EthPortSwIXt2VlanPppOEthPeerMac OBJECT-TYPE
   SYNTAX      OCTET STRING
   MAX-ACCESS  read-only
   STATUS      current
   DESCRIPTION
      "Path: swPort.status.vlan.pppOverEth.remoteMacAddress

       MAC address."
   ::= {sr1646v2EthPortSwIXt2VlanEntry 67239936}

sr1646v2EthPortSwIXt2VlanPppOEthServiceName OBJECT-TYPE
   SYNTAX      DisplayString
   MAX-ACCESS  read-only
   STATUS      current
   DESCRIPTION
      "Path: swPort.status.vlan.pppOverEth.serviceName"
   ::= {sr1646v2EthPortSwIXt2VlanEntry 67305472}

sr1646v2EthPortSwIXt2VlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwIXt2VlanEntry 83951616}

sr1646v2EthPortSwIXt2VlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwIXt2VlanEntry 84017152}

sr1646v2EthPortSwIXt2VlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwIXt2VlanEntry 84869120}

sr1646v2EthPortSwIXt2VlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2EthPortSwIXt2VlanEntry 84541440}

sr1646v2EthPortSwIXt2VlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2EthPortSwIXt2VlanEntry 84606976}

sr1646v2EthPortSwIXt2VlanPppMru OBJECT-TYPE
   SYNTAX      Integer32
   MAX-ACCESS  read-only
   STATUS      current
   DESCRIPTION
      "Path: swPort.status.vlan.ppp.mru"
   ::= {sr1646v2EthPortSwIXt2VlanEntry 84934656}

sr1646v2EthPortSwIXt2VlanIpSecondaryIp OBJECT-TYPE
   SYNTAX      SEQUENCE OF Sr1646v2EthPortSwIXt2VlanIpSecondaryIpEntry
   MAX-ACCESS  not-accessible
   STATUS      current
   DESCRIPTION
      ""
   ::= {sr1646v2EthPortSwIXt2Vlan 51838976}

sr1646v2EthPortSwIXt2VlanIpSecondaryIpEntry OBJECT-TYPE
   SYNTAX      Sr1646v2EthPortSwIXt2VlanIpSecondaryIpEntry
   MAX-ACCESS  not-accessible
   STATUS      current
   DESCRIPTION
      ""
   INDEX      { sr1646v2EthPortSwIXt2VlanIpSecondaryIpGlobalIx,
                sr1646v2EthPortSwIXt2VlanTableIx,
                sr1646v2EthPortSwIXt2VlanIpSecondaryIpTableIx }
   ::= {sr1646v2EthPortSwIXt2VlanIpSecondaryIp 1}

Sr1646v2EthPortSwIXt2VlanIpSecondaryIpEntry ::=
   SEQUENCE
      {
      sr1646v2EthPortSwIXt2VlanIpSecondaryIpGlobalIx
         GlobalIndex,
      sr1646v2EthPortSwIXt2VlanIpSecondaryIpTableIx
         TableIndex,
      sr1646v2EthPortSwIXt2VlanIpSecondaryIpAddress
         IpAddress,
      sr1646v2EthPortSwIXt2VlanIpSecondaryIpNetMask
         IpAddress
      }

sr1646v2EthPortSwIXt2VlanIpSecondaryIpGlobalIx OBJECT-TYPE
   SYNTAX      GlobalIndex
   MAX-ACCESS  not-accessible
   STATUS      current
   DESCRIPTION
      "The value of the tlsCntTreeGlobalIndex of the MANAGED OBJECT."
   ::= {sr1646v2EthPortSwIXt2VlanIpSecondaryIpEntry 10}

sr1646v2EthPortSwIXt2VlanIpSecondaryIpTableIx OBJECT-TYPE
   SYNTAX      TableIndex
   MAX-ACCESS  not-accessible
   STATUS      current
   DESCRIPTION
      ""
   ::= {sr1646v2EthPortSwIXt2VlanIpSecondaryIpEntry 11}

sr1646v2EthPortSwIXt2VlanIpSecondaryIpAddress OBJECT-TYPE
   SYNTAX      IpAddress
   MAX-ACCESS  read-only
   STATUS      current
   DESCRIPTION
      "Path: swPort.status.vlan.ip.secondaryIp.address"
   ::= {sr1646v2EthPortSwIXt2VlanIpSecondaryIpEntry 2030043136}

sr1646v2EthPortSwIXt2VlanIpSecondaryIpNetMask OBJECT-TYPE
   SYNTAX      IpAddress
   MAX-ACCESS  read-only
   STATUS      current
   DESCRIPTION
      "Path: swPort.status.vlan.ip.secondaryIp.netMask"
   ::= {sr1646v2EthPortSwIXt2VlanIpSecondaryIpEntry 2063597568}

sr1646v2EthPortSwIXt2VlanIpV6Addresses OBJECT-TYPE
   SYNTAX      SEQUENCE OF Sr1646v2EthPortSwIXt2VlanIpV6AddressesEntry
   MAX-ACCESS  not-accessible
   STATUS      current
   DESCRIPTION
      ""
   ::= {sr1646v2EthPortSwIXt2Vlan 100859904}

sr1646v2EthPortSwIXt2VlanIpV6AddressesEntry OBJECT-TYPE
   SYNTAX      Sr1646v2EthPortSwIXt2VlanIpV6AddressesEntry
   MAX-ACCESS  not-accessible
   STATUS      current
   DESCRIPTION
      ""
   INDEX      { sr1646v2EthPortSwIXt2VlanIpV6AddressesGlobalIx,
                sr1646v2EthPortSwIXt2VlanTableIx,
                sr1646v2EthPortSwIXt2VlanIpV6AddressesTableIx }
   ::= {sr1646v2EthPortSwIXt2VlanIpV6Addresses 1}

Sr1646v2EthPortSwIXt2VlanIpV6AddressesEntry ::=
   SEQUENCE
      {
      sr1646v2EthPortSwIXt2VlanIpV6AddressesGlobalIx
         GlobalIndex,
      sr1646v2EthPortSwIXt2VlanIpV6AddressesTableIx
         TableIndex,
      sr1646v2EthPortSwIXt2VlanIpV6AddressesAddress
         Ipv6Address,
      sr1646v2EthPortSwIXt2VlanIpV6AddressesPrefixLength
         Integer32,
      sr1646v2EthPortSwIXt2VlanIpV6AddressesStatus
         INTEGER,
      sr1646v2EthPortSwIXt2VlanIpV6AddressesOrigin
         INTEGER,
      sr1646v2EthPortSwIXt2VlanIpV6AddressesFlagsInterfaceId
         INTEGER,
      sr1646v2EthPortSwIXt2VlanIpV6AddressesFlagsAnycast
         INTEGER,
      sr1646v2EthPortSwIXt2VlanIpV6AddressesTimersValidLifeTime
         TimeTicks,
      sr1646v2EthPortSwIXt2VlanIpV6AddressesTimersPrefLifeTime
         TimeTicks
      }

sr1646v2EthPortSwIXt2VlanIpV6AddressesGlobalIx OBJECT-TYPE
   SYNTAX      GlobalIndex
   MAX-ACCESS  not-accessible
   STATUS      current
   DESCRIPTION
      "The value of the tlsCntTreeGlobalIndex of the MANAGED OBJECT."
   ::= {sr1646v2EthPortSwIXt2VlanIpV6AddressesEntry 10}

sr1646v2EthPortSwIXt2VlanIpV6AddressesTableIx OBJECT-TYPE
   SYNTAX      TableIndex
   MAX-ACCESS  not-accessible
   STATUS      current
   DESCRIPTION
      ""
   ::= {sr1646v2EthPortSwIXt2VlanIpV6AddressesEntry 11}

sr1646v2EthPortSwIXt2VlanIpV6AddressesAddress OBJECT-TYPE
   SYNTAX      Ipv6Address
   MAX-ACCESS  read-only
   STATUS      current
   DESCRIPTION
      "Path: swPort.status.vlan.ipV6.addresses.address

       ipv6 address"
   ::= {sr1646v2EthPortSwIXt2VlanIpV6AddressesEntry 16777216}

sr1646v2EthPortSwIXt2VlanIpV6AddressesPrefixLength OBJECT-TYPE
   SYNTAX      Integer32
   MAX-ACCESS  read-only
   STATUS      current
   DESCRIPTION
      "Path: swPort.status.vlan.ipV6.addresses.prefixLength"
   ::= {sr1646v2EthPortSwIXt2VlanIpV6AddressesEntry 33554432}

sr1646v2EthPortSwIXt2VlanIpV6AddressesStatus OBJECT-TYPE
   SYNTAX      INTEGER
               {
               invalid (0),
               tentative (1),
               deprecated (2),
               preferred (3)
               }
   MAX-ACCESS  read-only
   STATUS      current
   DESCRIPTION
      "Path: swPort.status.vlan.ipV6.addresses.status

       Possibilities:
               invalid   (0)
               tentative   (1)
               deprecated   (2)
               preferred   (3)"
   ::= {sr1646v2EthPortSwIXt2VlanIpV6AddressesEntry 50331648}

sr1646v2EthPortSwIXt2VlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.vlan.ipV6.addresses.origin

       Possibilities:
               unknown   (0)
               manual   (1)
               generalPrefix   (2)
               statelessAuto   (3)
               statefullAuto   (4)"
   ::= {sr1646v2EthPortSwIXt2VlanIpV6AddressesEntry 67108864}

sr1646v2EthPortSwIXt2VlanIpV6AddressesFlagsInterfaceId OBJECT-TYPE
   SYNTAX      INTEGER
               {
               no (0),
               yes (1)
               }
   MAX-ACCESS  read-only
   STATUS      current
   DESCRIPTION
      "Path: swPort.status.vlan.ipV6.addresses.flags.interfaceId

       Possibilities:
               no   (0)
               yes   (1)"
   ::= {sr1646v2EthPortSwIXt2VlanIpV6AddressesEntry 83951616}

sr1646v2EthPortSwIXt2VlanIpV6AddressesFlagsAnycast OBJECT-TYPE
   SYNTAX      INTEGER
               {
               no (0),
               yes (1)
               }
   MAX-ACCESS  read-only
   STATUS      current
   DESCRIPTION
      "Path: swPort.status.vlan.ipV6.addresses.flags.anycast

       Possibilities:
               no   (0)
               yes   (1)"
   ::= {sr1646v2EthPortSwIXt2VlanIpV6AddressesEntry 84017152}

sr1646v2EthPortSwIXt2VlanIpV6AddressesTimersValidLifeTime OBJECT-TYPE
   SYNTAX      TimeTicks
   MAX-ACCESS  read-only
   STATUS      current
   DESCRIPTION
      "Path: swPort.status.vlan.ipV6.addresses.timers.validLifeTime

       Time in centi-second."
   ::= {sr1646v2EthPortSwIXt2VlanIpV6AddressesEntry 100794368}

sr1646v2EthPortSwIXt2VlanIpV6AddressesTimersPrefLifeTime OBJECT-TYPE
   SYNTAX      TimeTicks
   MAX-ACCESS  read-only
   STATUS      current
   DESCRIPTION
      "Path: swPort.status.vlan.ipV6.addresses.timers.prefLifeTime

       Time in centi-second."
   ::= {sr1646v2EthPortSwIXt2VlanIpV6AddressesEntry 100728832}

sr1646v2EthPortSwIXt2VlanVlanArpCache OBJECT-TYPE
   SYNTAX      SEQUENCE OF Sr1646v2EthPortSwIXt2VlanVlanArpCacheEntry
   MAX-ACCESS  not-accessible
   STATUS      current
   DESCRIPTION
      ""
   ::= {sr1646v2EthPortSwIXt2Vlan 235601920}

sr1646v2EthPortSwIXt2VlanVlanArpCacheEntry OBJECT-TYPE
   SYNTAX      Sr1646v2EthPortSwIXt2VlanVlanArpCacheEntry
   MAX-ACCESS  not-accessible
   STATUS      current
   DESCRIPTION
      ""
   INDEX      { sr1646v2EthPortSwIXt2VlanVlanArpCacheGlobalIx,
                sr1646v2EthPortSwIXt2VlanTableIx,
                sr1646v2EthPortSwIXt2VlanVlanArpCacheTableIx }
   ::= {sr1646v2EthPortSwIXt2VlanVlanArpCache 1}

Sr1646v2EthPortSwIXt2VlanVlanArpCacheEntry ::=
   SEQUENCE
      {
      sr1646v2EthPortSwIXt2VlanVlanArpCacheGlobalIx
         GlobalIndex,
      sr1646v2EthPortSwIXt2VlanVlanArpCacheTableIx
         TableIndex,
      sr1646v2EthPortSwIXt2VlanVlanArpCacheMacAddress
         OCTET STRING,
      sr1646v2EthPortSwIXt2VlanVlanArpCacheIpAddress
         IpAddress,
      sr1646v2EthPortSwIXt2VlanVlanArpCacheType
         INTEGER,
      sr1646v2EthPortSwIXt2VlanVlanArpCacheTimeOut
         TimeTicks
      }

sr1646v2EthPortSwIXt2VlanVlanArpCacheGlobalIx OBJECT-TYPE
   SYNTAX      GlobalIndex
   MAX-ACCESS  not-accessible
   STATUS      current
   DESCRIPTION
      "The value of the tlsCntTreeGlobalIndex of the MANAGED OBJECT."
   ::= {sr1646v2EthPortSwIXt2VlanVlanArpCacheEntry 10}

sr1646v2EthPortSwIXt2VlanVlanArpCacheTableIx OBJECT-TYPE
   SYNTAX      TableIndex
   MAX-ACCESS  not-accessible
   STATUS      current
   DESCRIPTION
      ""
   ::= {sr1646v2EthPortSwIXt2VlanVlanArpCacheEntry 11}

sr1646v2EthPortSwIXt2VlanVlanArpCacheMacAddress OBJECT-TYPE
   SYNTAX      OCTET STRING
   MAX-ACCESS  read-only
   STATUS      current
   DESCRIPTION
      "Path: swPort.status.vlan.vlan.arpCache.macAddress

       MAC address."
   ::= {sr1646v2EthPortSwIXt2VlanVlanArpCacheEntry 16777216}

sr1646v2EthPortSwIXt2VlanVlanArpCacheIpAddress OBJECT-TYPE
   SYNTAX      IpAddress
   MAX-ACCESS  read-only
   STATUS      current
   DESCRIPTION
      "Path: swPort.status.vlan.vlan.arpCache.ipAddress"
   ::= {sr1646v2EthPortSwIXt2VlanVlanArpCacheEntry 33554432}

sr1646v2EthPortSwIXt2VlanVlanArpCacheType OBJECT-TYPE
   SYNTAX      INTEGER
               {
               static (0),
               dynamic (1)
               }
   MAX-ACCESS  read-only
   STATUS      current
   DESCRIPTION
      "Path: swPort.status.vlan.vlan.arpCache.type

       Possibilities:
               static   (0)
               dynamic   (1)"
   ::= {sr1646v2EthPortSwIXt2VlanVlanArpCacheEntry 50331648}

sr1646v2EthPortSwIXt2VlanVlanArpCacheTimeOut OBJECT-TYPE
   SYNTAX      TimeTicks
   MAX-ACCESS  read-only
   STATUS      current
   DESCRIPTION
      "Path: swPort.status.vlan.vlan.arpCache.timeOut

       Time in centi-second."
   ::= {sr1646v2EthPortSwIXt2VlanVlanArpCacheEntry 67108864}


sr1646v2EthPortSwIXt2PppOE OBJECT IDENTIFIER ::= {sr1646v2EthPortSwIXt2 36}

sr1646v2EthPortSwIXt2PppOESSCTable OBJECT-TYPE
   SYNTAX      SEQUENCE OF Sr1646v2EthPortSwIXt2PppOEEntry
   MAX-ACCESS  not-accessible
   STATUS      current
   DESCRIPTION
      ""
   ::= {sr1646v2EthPortSwIXt2PppOE 1}

sr1646v2EthPortSwIXt2PppOEEntry OBJECT-TYPE
   SYNTAX      Sr1646v2EthPortSwIXt2PppOEEntry
   MAX-ACCESS  not-accessible
   STATUS      current
   DESCRIPTION
      ""
   INDEX      { sr1646v2EthPortSwIXt2PppOEGlobalIx,
                sr1646v2EthPortSwIXt2PppOETableIx }
   ::= {sr1646v2EthPortSwIXt2PppOESSCTable 1}

Sr1646v2EthPortSwIXt2PppOEEntry ::=
   SEQUENCE
      {
      sr1646v2EthPortSwIXt2PppOEGlobalIx
         GlobalIndex,
      sr1646v2EthPortSwIXt2PppOETableIx
         TableIndex,
      sr1646v2EthPortSwIXt2PppOEName
         DisplayString,
      sr1646v2EthPortSwIXt2PppOEMode
         INTEGER,
      sr1646v2EthPortSwIXt2PppOEIfOperStatus
         INTEGER,
      sr1646v2EthPortSwIXt2PppOEIfLastChange
         TimeTicks,
      sr1646v2EthPortSwIXt2PppOEIfLastChangeDate
         DisplayString,
      sr1646v2EthPortSwIXt2PppOEIpAddress
         IpAddress,
      sr1646v2EthPortSwIXt2PppOEIpNetMask
         IpAddress,
      sr1646v2EthPortSwIXt2PppOEIpRemote
         IpAddress,
      sr1646v2EthPortSwIXt2PppOEPppOEthDiscState
         INTEGER,
      sr1646v2EthPortSwIXt2PppOEPppOEthPeerMac
         OCTET STRING,
      sr1646v2EthPortSwIXt2PppOEPppOEthServiceName
         DisplayString,
      sr1646v2EthPortSwIXt2PppOEPppLcpState
         INTEGER,
      sr1646v2EthPortSwIXt2PppOEPppIpcpState
         INTEGER,
      sr1646v2EthPortSwIXt2PppOEPppIp6cpState
         INTEGER,
      sr1646v2EthPortSwIXt2PppOEPppMyAutSt
         INTEGER,
      sr1646v2EthPortSwIXt2PppOEPppHisAutSt
         INTEGER,
      sr1646v2EthPortSwIXt2PppOEPppMru
         Integer32,
      sr1646v2EthPortSwIXt2PppOEIpV6State
         INTEGER,
      sr1646v2EthPortSwIXt2PppOEIpV6InterfaceId
         OCTET STRING,
      sr1646v2EthPortSwIXt2PppOEIpV6LinkMtu
         Integer32,
      sr1646v2EthPortSwIXt2PppOEIpV6HopLimit
         Integer32,
      sr1646v2EthPortSwIXt2PppOEIpV6DhcpIaid
         Counter32,
      sr1646v2EthPortSwIXt2PppOEIpV6RaRcvOption
         Integer32
      }

sr1646v2EthPortSwIXt2PppOEGlobalIx OBJECT-TYPE
   SYNTAX      GlobalIndex
   MAX-ACCESS  not-accessible
   STATUS      current
   DESCRIPTION
      "The value of the tlsCntTreeGlobalIndex of the MANAGED OBJECT."
   ::= {sr1646v2EthPortSwIXt2PppOEEntry 10}

sr1646v2EthPortSwIXt2PppOETableIx OBJECT-TYPE
   SYNTAX      TableIndex
   MAX-ACCESS  not-accessible
   STATUS      current
   DESCRIPTION
      ""
   ::= {sr1646v2EthPortSwIXt2PppOEEntry 11}

sr1646v2EthPortSwIXt2PppOEName OBJECT-TYPE
   SYNTAX      DisplayString
   MAX-ACCESS  read-only
   STATUS      current
   DESCRIPTION
      "Path: swPort.status.pppoEClient.name"
   ::= {sr1646v2EthPortSwIXt2PppOEEntry 16777216}

sr1646v2EthPortSwIXt2PppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: swPort.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2EthPortSwIXt2PppOEEntry 335544320}

sr1646v2EthPortSwIXt2PppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.pppoEClient.ifOperStatus

       Possibilities:
               up   (1)
               down   (2)
               testing   (3)
               unknown   (4)
               dormant   (5)
               notPresent   (6)
               lowerLayerDown   (7)"
   ::= {sr1646v2EthPortSwIXt2PppOEEntry 1795162112}

sr1646v2EthPortSwIXt2PppOEIfLastChange OBJECT-TYPE
   SYNTAX      TimeTicks
   MAX-ACCESS  read-only
   STATUS      current
   DESCRIPTION
      "Path: swPort.status.pppoEClient.ifLastChange

       Time in centi-second."
   ::= {sr1646v2EthPortSwIXt2PppOEEntry 1811939328}

sr1646v2EthPortSwIXt2PppOEIfLastChangeDate OBJECT-TYPE
   SYNTAX      DisplayString
   MAX-ACCESS  read-only
   STATUS      current
   DESCRIPTION
      "Path: swPort.status.pppoEClient.ifLastChangeDate"
   ::= {sr1646v2EthPortSwIXt2PppOEEntry 3070230528}

sr1646v2EthPortSwIXt2PppOEIpAddress OBJECT-TYPE
   SYNTAX      IpAddress
   MAX-ACCESS  read-only
   STATUS      current
   DESCRIPTION
      "Path: swPort.status.pppoEClient.ip.address"
   ::= {sr1646v2EthPortSwIXt2PppOEEntry 51380224}

sr1646v2EthPortSwIXt2PppOEIpNetMask OBJECT-TYPE
   SYNTAX      IpAddress
   MAX-ACCESS  read-only
   STATUS      current
   DESCRIPTION
      "Path: swPort.status.pppoEClient.ip.netMask"
   ::= {sr1646v2EthPortSwIXt2PppOEEntry 51445760}

sr1646v2EthPortSwIXt2PppOEIpRemote OBJECT-TYPE
   SYNTAX      IpAddress
   MAX-ACCESS  read-only
   STATUS      current
   DESCRIPTION
      "Path: swPort.status.pppoEClient.ip.remote"
   ::= {sr1646v2EthPortSwIXt2PppOEEntry 51511296}

sr1646v2EthPortSwIXt2PppOEPppOEthDiscState OBJECT-TYPE
   SYNTAX      INTEGER
               {
               idle (0),
               waitForPADO (1),
               waitForPADS (2),
               established (3)
               }
   MAX-ACCESS  read-only
   STATUS      current
   DESCRIPTION
      "Path: swPort.status.pppoEClient.pppOverEth.discState

       Possibilities:
               idle   (0)
               waitForPADO   (1)
               waitForPADS   (2)
               established   (3)"
   ::= {sr1646v2EthPortSwIXt2PppOEEntry 67174400}

sr1646v2EthPortSwIXt2PppOEPppOEthPeerMac OBJECT-TYPE
   SYNTAX      OCTET STRING
   MAX-ACCESS  read-only
   STATUS      current
   DESCRIPTION
      "Path: swPort.status.pppoEClient.pppOverEth.remoteMacAddress

       MAC address."
   ::= {sr1646v2EthPortSwIXt2PppOEEntry 67239936}

sr1646v2EthPortSwIXt2PppOEPppOEthServiceName OBJECT-TYPE
   SYNTAX      DisplayString
   MAX-ACCESS  read-only
   STATUS      current
   DESCRIPTION
      "Path: swPort.status.pppoEClient.pppOverEth.serviceName"
   ::= {sr1646v2EthPortSwIXt2PppOEEntry 67305472}

sr1646v2EthPortSwIXt2PppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwIXt2PppOEEntry 83951616}

sr1646v2EthPortSwIXt2PppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwIXt2PppOEEntry 84017152}

sr1646v2EthPortSwIXt2PppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: swPort.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2EthPortSwIXt2PppOEEntry 84869120}

sr1646v2EthPortSwIXt2PppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: swPort.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2EthPortSwIXt2PppOEEntry 84541440}

sr1646v2EthPortSwIXt2PppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: swPort.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2EthPortSwIXt2PppOEEntry 84606976}

sr1646v2EthPortSwIXt2PppOEPppMru OBJECT-TYPE
   SYNTAX      Integer32
   MAX-ACCESS  read-only
   STATUS      current
   DESCRIPTION
      "Path: swPort.status.pppoEClient.ppp.mru"
   ::= {sr1646v2EthPortSwIXt2PppOEEntry 84934656}

sr1646v2EthPortSwIXt2PppOEIpV6State OBJECT-TYPE
   SYNTAX      INTEGER
               {
               disabled (0),
               enabled (1)
               }
   MAX-ACCESS  read-only
   STATUS      current
   DESCRIPTION
      "Path: swPort.status.pppoEClient.ipV6.state

       Possibilities:
               disabled   (0)
               enabled   (1)"
   ::= {sr1646v2EthPortSwIXt2PppOEEntry 100728832}

sr1646v2EthPortSwIXt2PppOEIpV6InterfaceId OBJECT-TYPE
   SYNTAX      OCTET STRING
   MAX-ACCESS  read-only
   STATUS      current
   DESCRIPTION
      "Path: swPort.status.pppoEClient.ipV6.interfaceId"
   ::= {sr1646v2EthPortSwIXt2PppOEEntry 100794368}

sr1646v2EthPortSwIXt2PppOEIpV6LinkMtu OBJECT-TYPE
   SYNTAX      Integer32
   MAX-ACCESS  read-only
   STATUS      current
   DESCRIPTION
      "Path: swPort.status.pppoEClient.ipV6.linkMtu"
   ::= {sr1646v2EthPortSwIXt2PppOEEntry 100925440}

sr1646v2EthPortSwIXt2PppOEIpV6HopLimit OBJECT-TYPE
   SYNTAX      Integer32
   MAX-ACCESS  read-only
   STATUS      current
   DESCRIPTION
      "Path: swPort.status.pppoEClient.ipV6.hopLimit"
   ::= {sr1646v2EthPortSwIXt2PppOEEntry 100990976}

sr1646v2EthPortSwIXt2PppOEIpV6DhcpIaid OBJECT-TYPE
   SYNTAX      Counter32
   MAX-ACCESS  read-only
   STATUS      current
   DESCRIPTION
      "Path: swPort.status.pppoEClient.ipV6.dhcp.iaid

       32 bit unsigned wrappable counter."
   ::= {sr1646v2EthPortSwIXt2PppOEEntry 101056768}

sr1646v2EthPortSwIXt2PppOEIpV6RaRcvOption OBJECT-TYPE
   SYNTAX      Integer32
   MAX-ACCESS  read-only
   STATUS      current
   DESCRIPTION
      "Path: swPort.status.pppoEClient.ipV6.raRcvOption

       Bit meanings:
               bit 0 = linkMtu,
               bit 1 = srcLinkLayer,
               bit 2 = prefixInfo,
               bit 3 = rdnss,
               bit 4 = dnssl"
   ::= {sr1646v2EthPortSwIXt2PppOEEntry 101122048}

sr1646v2EthPortSwIXt2PppOEIpV6Addresses OBJECT-TYPE
   SYNTAX      SEQUENCE OF Sr1646v2EthPortSwIXt2PppOEIpV6AddressesEntry
   MAX-ACCESS  not-accessible
   STATUS      current
   DESCRIPTION
      ""
   ::= {sr1646v2EthPortSwIXt2PppOE 100859904}

sr1646v2EthPortSwIXt2PppOEIpV6AddressesEntry OBJECT-TYPE
   SYNTAX      Sr1646v2EthPortSwIXt2PppOEIpV6AddressesEntry
   MAX-ACCESS  not-accessible
   STATUS      current
   DESCRIPTION
      ""
   INDEX      { sr1646v2EthPortSwIXt2PppOEIpV6AddressesGlobalIx,
                sr1646v2EthPortSwIXt2PppOETableIx,
                sr1646v2EthPortSwIXt2PppOEIpV6AddressesTableIx }
   ::= {sr1646v2EthPortSwIXt2PppOEIpV6Addresses 1}

Sr1646v2EthPortSwIXt2PppOEIpV6AddressesEntry ::=
   SEQUENCE
      {
      sr1646v2EthPortSwIXt2PppOEIpV6AddressesGlobalIx
         GlobalIndex,
      sr1646v2EthPortSwIXt2PppOEIpV6AddressesTableIx
         TableIndex,
      sr1646v2EthPortSwIXt2PppOEIpV6AddressesAddress
         Ipv6Address,
      sr1646v2EthPortSwIXt2PppOEIpV6AddressesPrefixLength
         Integer32,
      sr1646v2EthPortSwIXt2PppOEIpV6AddressesStatus
         INTEGER,
      sr1646v2EthPortSwIXt2PppOEIpV6AddressesOrigin
         INTEGER,
      sr1646v2EthPortSwIXt2PppOEIpV6AddressesFlagsInterfaceId
         INTEGER,
      sr1646v2EthPortSwIXt2PppOEIpV6AddressesFlagsAnycast
         INTEGER,
      sr1646v2EthPortSwIXt2PppOEIpV6AddressesTimersValidLifeTime
         TimeTicks,
      sr1646v2EthPortSwIXt2PppOEIpV6AddressesTimersPrefLifeTime
         TimeTicks
      }

sr1646v2EthPortSwIXt2PppOEIpV6AddressesGlobalIx OBJECT-TYPE
   SYNTAX      GlobalIndex
   MAX-ACCESS  not-accessible
   STATUS      current
   DESCRIPTION
      "The value of the tlsCntTreeGlobalIndex of the MANAGED OBJECT."
   ::= {sr1646v2EthPortSwIXt2PppOEIpV6AddressesEntry 10}

sr1646v2EthPortSwIXt2PppOEIpV6AddressesTableIx OBJECT-TYPE
   SYNTAX      TableIndex
   MAX-ACCESS  not-accessible
   STATUS      current
   DESCRIPTION
      ""
   ::= {sr1646v2EthPortSwIXt2PppOEIpV6AddressesEntry 11}

sr1646v2EthPortSwIXt2PppOEIpV6AddressesAddress OBJECT-TYPE
   SYNTAX      Ipv6Address
   MAX-ACCESS  read-only
   STATUS      current
   DESCRIPTION
      "Path: swPort.status.pppoEClient.ipV6.addresses.address

       ipv6 address"
   ::= {sr1646v2EthPortSwIXt2PppOEIpV6AddressesEntry 16777216}

sr1646v2EthPortSwIXt2PppOEIpV6AddressesPrefixLength OBJECT-TYPE
   SYNTAX      Integer32
   MAX-ACCESS  read-only
   STATUS      current
   DESCRIPTION
      "Path: swPort.status.pppoEClient.ipV6.addresses.prefixLength"
   ::= {sr1646v2EthPortSwIXt2PppOEIpV6AddressesEntry 33554432}

sr1646v2EthPortSwIXt2PppOEIpV6AddressesStatus OBJECT-TYPE
   SYNTAX      INTEGER
               {
               invalid (0),
               tentative (1),
               deprecated (2),
               preferred (3)
               }
   MAX-ACCESS  read-only
   STATUS      current
   DESCRIPTION
      "Path: swPort.status.pppoEClient.ipV6.addresses.status

       Possibilities:
               invalid   (0)
               tentative   (1)
               deprecated   (2)
               preferred   (3)"
   ::= {sr1646v2EthPortSwIXt2PppOEIpV6AddressesEntry 50331648}

sr1646v2EthPortSwIXt2PppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.pppoEClient.ipV6.addresses.origin

       Possibilities:
               unknown   (0)
               manual   (1)
               generalPrefix   (2)
               statelessAuto   (3)
               statefullAuto   (4)"
   ::= {sr1646v2EthPortSwIXt2PppOEIpV6AddressesEntry 67108864}

sr1646v2EthPortSwIXt2PppOEIpV6AddressesFlagsInterfaceId OBJECT-TYPE
   SYNTAX      INTEGER
               {
               no (0),
               yes (1)
               }
   MAX-ACCESS  read-only
   STATUS      current
   DESCRIPTION
      "Path: swPort.status.pppoEClient.ipV6.addresses.flags.interfaceId

       Possibilities:
               no   (0)
               yes   (1)"
   ::= {sr1646v2EthPortSwIXt2PppOEIpV6AddressesEntry 83951616}

sr1646v2EthPortSwIXt2PppOEIpV6AddressesFlagsAnycast OBJECT-TYPE
   SYNTAX      INTEGER
               {
               no (0),
               yes (1)
               }
   MAX-ACCESS  read-only
   STATUS      current
   DESCRIPTION
      "Path: swPort.status.pppoEClient.ipV6.addresses.flags.anycast

       Possibilities:
               no   (0)
               yes   (1)"
   ::= {sr1646v2EthPortSwIXt2PppOEIpV6AddressesEntry 84017152}

sr1646v2EthPortSwIXt2PppOEIpV6AddressesTimersValidLifeTime OBJECT-TYPE
   SYNTAX      TimeTicks
   MAX-ACCESS  read-only
   STATUS      current
   DESCRIPTION
      "Path: swPort.status.pppoEClient.ipV6.addresses.timers.validLifeTime

       Time in centi-second."
   ::= {sr1646v2EthPortSwIXt2PppOEIpV6AddressesEntry 100794368}

sr1646v2EthPortSwIXt2PppOEIpV6AddressesTimersPrefLifeTime OBJECT-TYPE
   SYNTAX      TimeTicks
   MAX-ACCESS  read-only
   STATUS      current
   DESCRIPTION
      "Path: swPort.status.pppoEClient.ipV6.addresses.timers.prefLifeTime

       Time in centi-second."
   ::= {sr1646v2EthPortSwIXt2PppOEIpV6AddressesEntry 100728832}


sr1646v2EthPortSwIXt2Dot1x OBJECT IDENTIFIER ::= {sr1646v2EthPortSwIXt2 190}

sr1646v2EthPortSwIXt2Dot1xSSCTable OBJECT-TYPE
   SYNTAX      SEQUENCE OF Sr1646v2EthPortSwIXt2Dot1xEntry
   MAX-ACCESS  not-accessible
   STATUS      current
   DESCRIPTION
      "Ethernet Switch VLAN Table"
   ::= {sr1646v2EthPortSwIXt2Dot1x 1}

sr1646v2EthPortSwIXt2Dot1xEntry OBJECT-TYPE
   SYNTAX      Sr1646v2EthPortSwIXt2Dot1xEntry
   MAX-ACCESS  not-accessible
   STATUS      current
   DESCRIPTION
      ""
   INDEX      { sr1646v2EthPortSwIXt2Dot1xGlobalIx,
                sr1646v2EthPortSwIXt2Dot1xTableIx }
   ::= {sr1646v2EthPortSwIXt2Dot1xSSCTable 1}

Sr1646v2EthPortSwIXt2Dot1xEntry ::=
   SEQUENCE
      {
      sr1646v2EthPortSwIXt2Dot1xGlobalIx
         GlobalIndex,
      sr1646v2EthPortSwIXt2Dot1xTableIx
         TableIndex,
      sr1646v2EthPortSwIXt2Dot1xRemote
         OCTET STRING,
      sr1646v2EthPortSwIXt2Dot1xAuthorized
         INTEGER,
      sr1646v2EthPortSwIXt2Dot1xAuthenticator
         INTEGER,
      sr1646v2EthPortSwIXt2Dot1xBackEnd
         INTEGER,
      sr1646v2EthPortSwIXt2Dot1xRetries
         Integer32,
      sr1646v2EthPortSwIXt2Dot1xReAuthTime
         TimeTicks,
      sr1646v2EthPortSwIXt2Dot1xHoldTime
         TimeTicks
      }

sr1646v2EthPortSwIXt2Dot1xGlobalIx OBJECT-TYPE
   SYNTAX      GlobalIndex
   MAX-ACCESS  not-accessible
   STATUS      current
   DESCRIPTION
      "The value of the tlsCntTreeGlobalIndex of the MANAGED OBJECT."
   ::= {sr1646v2EthPortSwIXt2Dot1xEntry 10}

sr1646v2EthPortSwIXt2Dot1xTableIx OBJECT-TYPE
   SYNTAX      TableIndex
   MAX-ACCESS  not-accessible
   STATUS      current
   DESCRIPTION
      ""
   ::= {sr1646v2EthPortSwIXt2Dot1xEntry 11}

sr1646v2EthPortSwIXt2Dot1xRemote OBJECT-TYPE
   SYNTAX      OCTET STRING
   MAX-ACCESS  read-only
   STATUS      current
   DESCRIPTION
      "Path: swPort.status.dot1x.remote

       MAC address."
   ::= {sr1646v2EthPortSwIXt2Dot1xEntry 16777216}

sr1646v2EthPortSwIXt2Dot1xAuthorized OBJECT-TYPE
   SYNTAX      INTEGER
               {
               no (0),
               yes (1)
               }
   MAX-ACCESS  read-only
   STATUS      current
   DESCRIPTION
      "Path: swPort.status.dot1x.authorized

       Possibilities:
               no   (0)
               yes   (1)"
   ::= {sr1646v2EthPortSwIXt2Dot1xEntry 33554432}

sr1646v2EthPortSwIXt2Dot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: swPort.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1646v2EthPortSwIXt2Dot1xEntry 50331648}

sr1646v2EthPortSwIXt2Dot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: swPort.status.dot1x.backEnd

       Possibilities:
               preInit   (0)
               initialize   (1)
               idle   (2)
               request   (3)
               response   (4)
               success   (5)
               failure   (6)
               radiusTimeout   (7)
               timeout   (8)"
   ::= {sr1646v2EthPortSwIXt2Dot1xEntry 67108864}

sr1646v2EthPortSwIXt2Dot1xRetries OBJECT-TYPE
   SYNTAX      Integer32
   MAX-ACCESS  read-only
   STATUS      current
   DESCRIPTION
      "Path: swPort.status.dot1x.retries"
   ::= {sr1646v2EthPortSwIXt2Dot1xEntry 83886080}

sr1646v2EthPortSwIXt2Dot1xReAuthTime OBJECT-TYPE
   SYNTAX      TimeTicks
   MAX-ACCESS  read-only
   STATUS      current
   DESCRIPTION
      "Path: swPort.status.dot1x.reAuthTime

       Time in centi-second."
   ::= {sr1646v2EthPortSwIXt2Dot1xEntry 100663296}

sr1646v2EthPortSwIXt2Dot1xHoldTime OBJECT-TYPE
   SYNTAX      TimeTicks
   MAX-ACCESS  read-only
   STATUS      current
   DESCRIPTION
      "Path: swPort.status.dot1x.holdTime

       Time in centi-second."
   ::= {sr1646v2EthPortSwIXt2Dot1xEntry 117440512}


sr1646v2EthPortSwIXt2IpV6 OBJECT IDENTIFIER ::= {sr1646v2EthPortSwIXt2 17}

sr1646v2EthPortSwIXt2IpV6SSCTable OBJECT-TYPE
   SYNTAX      SEQUENCE OF Sr1646v2EthPortSwIXt2IpV6Entry
   MAX-ACCESS  not-accessible
   STATUS      current
   DESCRIPTION
      "IPv6 interface config parameters"
   ::= {sr1646v2EthPortSwIXt2IpV6 1}

sr1646v2EthPortSwIXt2IpV6Entry OBJECT-TYPE
   SYNTAX      Sr1646v2EthPortSwIXt2IpV6Entry
   MAX-ACCESS  not-accessible
   STATUS      current
   DESCRIPTION
      ""
   INDEX      { sr1646v2EthPortSwIXt2IpV6GlobalIx }
   ::= {sr1646v2EthPortSwIXt2IpV6SSCTable 1}

Sr1646v2EthPortSwIXt2IpV6Entry ::=
   SEQUENCE
      {
      sr1646v2EthPortSwIXt2IpV6GlobalIx
         GlobalIndex,
      sr1646v2EthPortSwIXt2IpV6State
         INTEGER,
      sr1646v2EthPortSwIXt2IpV6InterfaceId
         OCTET STRING,
      sr1646v2EthPortSwIXt2IpV6LinkMtu
         Integer32,
      sr1646v2EthPortSwIXt2IpV6HopLimit
         Integer32,
      sr1646v2EthPortSwIXt2IpV6DhcpIaid
         Counter32,
      sr1646v2EthPortSwIXt2IpV6RaRcvOption
         Integer32
      }

sr1646v2EthPortSwIXt2IpV6GlobalIx OBJECT-TYPE
   SYNTAX      GlobalIndex
   MAX-ACCESS  not-accessible
   STATUS      current
   DESCRIPTION
      "The value of the tlsCntTreeGlobalIndex of the MANAGED OBJECT."
   ::= {sr1646v2EthPortSwIXt2IpV6Entry 10}

sr1646v2EthPortSwIXt2IpV6State OBJECT-TYPE
   SYNTAX      INTEGER
               {
               disabled (0),
               enabled (1)
               }
   MAX-ACCESS  read-only
   STATUS      current
   DESCRIPTION
      "Path: swPort.status.ipV6.state

       Possibilities:
               disabled   (0)
               enabled   (1)"
   ::= {sr1646v2EthPortSwIXt2IpV6Entry 16777216}

sr1646v2EthPortSwIXt2IpV6InterfaceId OBJECT-TYPE
   SYNTAX      OCTET STRING
   MAX-ACCESS  read-only
   STATUS      current
   DESCRIPTION
      "Path: swPort.status.ipV6.interfaceId"
   ::= {sr1646v2EthPortSwIXt2IpV6Entry 33554432}

sr1646v2EthPortSwIXt2IpV6LinkMtu OBJECT-TYPE
   SYNTAX      Integer32
   MAX-ACCESS  read-only
   STATUS      current
   DESCRIPTION
      "Path: swPort.status.ipV6.linkMtu"
   ::= {sr1646v2EthPortSwIXt2IpV6Entry 67108864}

sr1646v2EthPortSwIXt2IpV6HopLimit OBJECT-TYPE
   SYNTAX      Integer32
   MAX-ACCESS  read-only
   STATUS      current
   DESCRIPTION
      "Path: swPort.status.ipV6.hopLimit"
   ::= {sr1646v2EthPortSwIXt2IpV6Entry 83886080}

sr1646v2EthPortSwIXt2IpV6DhcpIaid OBJECT-TYPE
   SYNTAX      Counter32
   MAX-ACCESS  read-only
   STATUS      current
   DESCRIPTION
      "Path: swPort.status.ipV6.dhcp.iaid

       32 bit unsigned wrappable counter."
   ::= {sr1646v2EthPortSwIXt2IpV6Entry 100728832}

sr1646v2EthPortSwIXt2IpV6RaRcvOption OBJECT-TYPE
   SYNTAX      Integer32
   MAX-ACCESS  read-only
   STATUS      current
   DESCRIPTION
      "Path: swPort.status.ipV6.raRcvOption

       Bit meanings:
               bit 0 = linkMtu,
               bit 1 = srcLinkLayer,
               bit 2 = prefixInfo,
               bit 3 = rdnss,
               bit 4 = dnssl"
   ::= {sr1646v2EthPortSwIXt2IpV6Entry 117440512}

sr1646v2EthPortSwIXt2IpV6Addresses OBJECT-TYPE
   SYNTAX      SEQUENCE OF Sr1646v2EthPortSwIXt2IpV6AddressesEntry
   MAX-ACCESS  not-accessible
   STATUS      current
   DESCRIPTION
      ""
   ::= {sr1646v2EthPortSwIXt2IpV6 50331648}

sr1646v2EthPortSwIXt2IpV6AddressesEntry OBJECT-TYPE
   SYNTAX      Sr1646v2EthPortSwIXt2IpV6AddressesEntry
   MAX-ACCESS  not-accessible
   STATUS      current
   DESCRIPTION
      ""
   INDEX      { sr1646v2EthPortSwIXt2IpV6AddressesGlobalIx,
                sr1646v2EthPortSwIXt2IpV6AddressesTableIx }
   ::= {sr1646v2EthPortSwIXt2IpV6Addresses 1}

Sr1646v2EthPortSwIXt2IpV6AddressesEntry ::=
   SEQUENCE
      {
      sr1646v2EthPortSwIXt2IpV6AddressesGlobalIx
         GlobalIndex,
      sr1646v2EthPortSwIXt2IpV6AddressesTableIx
         TableIndex,
      sr1646v2EthPortSwIXt2IpV6AddressesAddress
         Ipv6Address,
      sr1646v2EthPortSwIXt2IpV6AddressesPrefixLength
         Integer32,
      sr1646v2EthPortSwIXt2IpV6AddressesStatus
         INTEGER,
      sr1646v2EthPortSwIXt2IpV6AddressesOrigin
         INTEGER,
      sr1646v2EthPortSwIXt2IpV6AddressesFlagsInterfaceId
         INTEGER,
      sr1646v2EthPortSwIXt2IpV6AddressesFlagsAnycast
         INTEGER,
      sr1646v2EthPortSwIXt2IpV6AddressesTimersValidLifeTime
         TimeTicks,
      sr1646v2EthPortSwIXt2IpV6AddressesTimersPrefLifeTime
         TimeTicks
      }

sr1646v2EthPortSwIXt2IpV6AddressesGlobalIx OBJECT-TYPE
   SYNTAX      GlobalIndex
   MAX-ACCESS  not-accessible
   STATUS      current
   DESCRIPTION
      "The value of the tlsCntTreeGlobalIndex of the MANAGED OBJECT."
   ::= {sr1646v2EthPortSwIXt2IpV6AddressesEntry 10}

sr1646v2EthPortSwIXt2IpV6AddressesTableIx OBJECT-TYPE
   SYNTAX      TableIndex
   MAX-ACCESS  not-accessible
   STATUS      current
   DESCRIPTION
      ""
   ::= {sr1646v2EthPortSwIXt2IpV6AddressesEntry 11}

sr1646v2EthPortSwIXt2IpV6AddressesAddress OBJECT-TYPE
   SYNTAX      Ipv6Address
   MAX-ACCESS  read-only
   STATUS      current
   DESCRIPTION
      "Path: swPort.status.ipV6.addresses.address

       ipv6 address"
   ::= {sr1646v2EthPortSwIXt2IpV6AddressesEntry 16777216}

sr1646v2EthPortSwIXt2IpV6AddressesPrefixLength OBJECT-TYPE
   SYNTAX      Integer32
   MAX-ACCESS  read-only
   STATUS      current
   DESCRIPTION
      "Path: swPort.status.ipV6.addresses.prefixLength"
   ::= {sr1646v2EthPortSwIXt2IpV6AddressesEntry 33554432}

sr1646v2EthPortSwIXt2IpV6AddressesStatus OBJECT-TYPE
   SYNTAX      INTEGER
               {
               invalid (0),
               tentative (1),
               deprecated (2),
               preferred (3)
               }
   MAX-ACCESS  read-only
   STATUS      current
   DESCRIPTION
      "Path: swPort.status.ipV6.addresses.status

       Possibilities:
               invalid   (0)
               tentative   (1)
               deprecated   (2)
               preferred   (3)"
   ::= {sr1646v2EthPortSwIXt2IpV6AddressesEntry 50331648}

sr1646v2EthPortSwIXt2IpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: swPort.status.ipV6.addresses.origin

       Possibilities:
               unknown   (0)
               manual   (1)
               generalPrefix   (2)
               statelessAuto   (3)
               statefullAuto   (4)"
   ::= {sr1646v2EthPortSwIXt2IpV6AddressesEntry 67108864}

sr1646v2EthPortSwIXt2IpV6AddressesFlagsInterfaceId OBJECT-TYPE
   SYNTAX      INTEGER
               {
               no (0),
               yes (1)
               }
   MAX-ACCESS  read-only
   STATUS      current
   DESCRIPTION
      "Path: swPort.status.ipV6.addresses.flags.interfaceId

       Possibilities:
               no   (0)
               yes   (1)"
   ::= {sr1646v2EthPortSwIXt2IpV6AddressesEntry 83951616}

sr1646v2EthPortSwIXt2IpV6AddressesFlagsAnycast OBJECT-TYPE
   SYNTAX      INTEGER
               {
               no (0),
               yes (1)
               }
   MAX-ACCESS  read-only
   STATUS      current
   DESCRIPTION
      "Path: swPort.status.ipV6.addresses.flags.anycast

       Possibilities:
               no   (0)
               yes   (1)"
   ::= {sr1646v2EthPortSwIXt2IpV6AddressesEntry 84017152}

sr1646v2EthPortSwIXt2IpV6AddressesTimersValidLifeTime OBJECT-TYPE
   SYNTAX      TimeTicks
   MAX-ACCESS  read-only
   STATUS      current
   DESCRIPTION
      "Path: swPort.status.ipV6.addresses.timers.validLifeTime

       Time in centi-second."
   ::= {sr1646v2EthPortSwIXt2IpV6AddressesEntry 100794368}

sr1646v2EthPortSwIXt2IpV6AddressesTimersPrefLifeTime OBJECT-TYPE
   SYNTAX      TimeTicks
   MAX-ACCESS  read-only
   STATUS      current
   DESCRIPTION
      "Path: swPort.status.ipV6.addresses.timers.prefLifeTime

       Time in centi-second."
   ::= {sr1646v2EthPortSwIXt2IpV6AddressesEntry 100728832}


sr1646v2EthPortSwIXt2SnmpIndex OBJECT IDENTIFIER ::= {sr1646v2EthPortSwIXt2 269}

sr1646v2EthPortSwIXt2SnmpIndexTable OBJECT-TYPE
   SYNTAX      SEQUENCE OF Sr1646v2EthPortSwIXt2SnmpIndexEntry
   MAX-ACCESS  not-accessible
   STATUS      current
   DESCRIPTION
      "SNMP index assigned to this object"
   ::= {sr1646v2EthPortSwIXt2SnmpIndex 1}

sr1646v2EthPortSwIXt2SnmpIndexEntry OBJECT-TYPE
   SYNTAX      Sr1646v2EthPortSwIXt2SnmpIndexEntry
   MAX-ACCESS  not-accessible
   STATUS      current
   DESCRIPTION
      ""
   INDEX      { sr1646v2EthPortSwIXt2SnmpIndexGlobalIx }
   ::= {sr1646v2EthPortSwIXt2SnmpIndexTable 1}

Sr1646v2EthPortSwIXt2SnmpIndexEntry ::=
   SEQUENCE
      {
      sr1646v2EthPortSwIXt2SnmpIndexGlobalIx
         GlobalIndex,
      sr1646v2EthPortSwIXt2SnmpIndexValue
         Integer32
      }

sr1646v2EthPortSwIXt2SnmpIndexGlobalIx OBJECT-TYPE
   SYNTAX      GlobalIndex
   MAX-ACCESS  not-accessible
   STATUS      current
   DESCRIPTION
      "The value of the tlsCntTreeGlobalIndex of the MANAGED OBJECT."
   ::= {sr1646v2EthPortSwIXt2SnmpIndexEntry 10}

sr1646v2EthPortSwIXt2SnmpIndexValue OBJECT-TYPE
   SYNTAX      Integer32
   MAX-ACCESS  read-only
   STATUS      current
   DESCRIPTION
      "Path: swPort.status.snmpIndex"
   ::= {sr1646v2EthPortSwIXt2SnmpIndexEntry 2147483648}


sr1646v2EthPortSwIXt2Lst OBJECT IDENTIFIER ::= {sr1646v2EthPortSwIXt2 18}

sr1646v2EthPortSwIXt2LstSSCTable OBJECT-TYPE
   SYNTAX      SEQUENCE OF Sr1646v2EthPortSwIXt2LstEntry
   MAX-ACCESS  not-accessible
   STATUS      current
   DESCRIPTION
      ""
   ::= {sr1646v2EthPortSwIXt2Lst 1}

sr1646v2EthPortSwIXt2LstEntry OBJECT-TYPE
   SYNTAX      Sr1646v2EthPortSwIXt2LstEntry
   MAX-ACCESS  not-accessible
   STATUS      current
   DESCRIPTION
      ""
   INDEX      { sr1646v2EthPortSwIXt2LstGlobalIx }
   ::= {sr1646v2EthPortSwIXt2LstSSCTable 1}

Sr1646v2EthPortSwIXt2LstEntry ::=
   SEQUENCE
      {
      sr1646v2EthPortSwIXt2LstGlobalIx
         GlobalIndex,
      sr1646v2EthPortSwIXt2LstTrackedInterface
         DisplayString,
      sr1646v2EthPortSwIXt2LstIfOperStatus
         INTEGER
      }

sr1646v2EthPortSwIXt2LstGlobalIx OBJECT-TYPE
   SYNTAX      GlobalIndex
   MAX-ACCESS  not-accessible
   STATUS      current
   DESCRIPTION
      "The value of the tlsCntTreeGlobalIndex of the MANAGED OBJECT."
   ::= {sr1646v2EthPortSwIXt2LstEntry 10}

sr1646v2EthPortSwIXt2LstTrackedInterface OBJECT-TYPE
   SYNTAX      DisplayString
   MAX-ACCESS  read-only
   STATUS      current
   DESCRIPTION
      "Path: swPort.status.linkStateTracking.trackedInterface"
   ::= {sr1646v2EthPortSwIXt2LstEntry 16777216}

sr1646v2EthPortSwIXt2LstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: swPort.status.linkStateTracking.ifOperStatus

       Possibilities:
               up   (1)
               down   (2)
               testing   (3)
               unknown   (4)
               dormant   (5)
               notPresent   (6)
               lowerLayerDown   (7)
                  (255)"
   ::= {sr1646v2EthPortSwIXt2LstEntry 50331648}


sr1646v2EthPortSwIXt2HwPorts OBJECT IDENTIFIER ::= {sr1646v2EthPortSwIXt2 270}

sr1646v2EthPortSwIXt2HwPortsSSCTable OBJECT-TYPE
   SYNTAX      SEQUENCE OF Sr1646v2EthPortSwIXt2HwPortsEntry
   MAX-ACCESS  not-accessible
   STATUS      current
   DESCRIPTION
      ""
   ::= {sr1646v2EthPortSwIXt2HwPorts 1}

sr1646v2EthPortSwIXt2HwPortsEntry OBJECT-TYPE
   SYNTAX      Sr1646v2EthPortSwIXt2HwPortsEntry
   MAX-ACCESS  not-accessible
   STATUS      current
   DESCRIPTION
      ""
   INDEX      { sr1646v2EthPortSwIXt2HwPortsGlobalIx,
                sr1646v2EthPortSwIXt2HwPortsTableIx }
   ::= {sr1646v2EthPortSwIXt2HwPortsSSCTable 1}

Sr1646v2EthPortSwIXt2HwPortsEntry ::=
   SEQUENCE
      {
      sr1646v2EthPortSwIXt2HwPortsGlobalIx
         GlobalIndex,
      sr1646v2EthPortSwIXt2HwPortsTableIx
         TableIndex,
      sr1646v2EthPortSwIXt2HwPortsHwPort
         INTEGER,
      sr1646v2EthPortSwIXt2HwPortsStatus
         INTEGER
      }

sr1646v2EthPortSwIXt2HwPortsGlobalIx OBJECT-TYPE
   SYNTAX      GlobalIndex
   MAX-ACCESS  not-accessible
   STATUS      current
   DESCRIPTION
      "The value of the tlsCntTreeGlobalIndex of the MANAGED OBJECT."
   ::= {sr1646v2EthPortSwIXt2HwPortsEntry 10}

sr1646v2EthPortSwIXt2HwPortsTableIx OBJECT-TYPE
   SYNTAX      TableIndex
   MAX-ACCESS  not-accessible
   STATUS      current
   DESCRIPTION
      ""
   ::= {sr1646v2EthPortSwIXt2HwPortsEntry 11}

sr1646v2EthPortSwIXt2HwPortsHwPort OBJECT-TYPE
   SYNTAX      INTEGER
               {
               hwPortu1 (1),
               hwPortu2 (2),
               hwPortu3 (3),
               hwPortu4 (4),
               hwPortu5 (5),
               hwPortu6 (6),
               hwPortu7 (7),
               hwPortu8 (8),
               hwPortuLocalPort (65535)
               }
   MAX-ACCESS  read-only
   STATUS      current
   DESCRIPTION
      "Path: swPort.status.hwPorts.hwPort

       Possibilities:
               hwPort_1   (1)
               hwPort_2   (2)
               hwPort_3   (3)
               hwPort_4   (4)
               hwPort_5   (5)
               hwPort_6   (6)
               hwPort_7   (7)
               hwPort_8   (8)
               hwPort_LocalPort   (65535)"
   ::= {sr1646v2EthPortSwIXt2HwPortsEntry 16777216}

sr1646v2EthPortSwIXt2HwPortsStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: swPort.status.hwPorts.status

       Possibilities:
               up   (1)
               down   (2)
               testing   (3)
               unknown   (4)
               dormant   (5)
               notPresent   (6)
               lowerLayerDown   (7)"
   ::= {sr1646v2EthPortSwIXt2HwPortsEntry 33554432}



pr1646v2EthPortSwIXt2 OBJECT IDENTIFIER ::= {r1646v2EthPortSwIXt2 12}


pr1646v2EthPortSwIXt2InOctets OBJECT IDENTIFIER ::= {pr1646v2EthPortSwIXt2 109}

pr1646v2EthPortSwIXt2InOctetsTable OBJECT-TYPE
   SYNTAX      SEQUENCE OF Pr1646v2EthPortSwIXt2InOctetsEntry
   MAX-ACCESS  not-accessible
   STATUS      current
   DESCRIPTION
      "ifInOctets"
   ::= {pr1646v2EthPortSwIXt2InOctets 1}

pr1646v2EthPortSwIXt2InOctetsEntry OBJECT-TYPE
   SYNTAX      Pr1646v2EthPortSwIXt2InOctetsEntry
   MAX-ACCESS  not-accessible
   STATUS      current
   DESCRIPTION
      ""
   INDEX      { pr1646v2EthPortSwIXt2InOctetsGlobalIx }
   ::= {pr1646v2EthPortSwIXt2InOctetsTable 1}

Pr1646v2EthPortSwIXt2InOctetsEntry ::=
   SEQUENCE
      {
      pr1646v2EthPortSwIXt2InOctetsGlobalIx
         GlobalIndex,
      pr1646v2EthPortSwIXt2InOctetsValue
         Counter64
      }

pr1646v2EthPortSwIXt2InOctetsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InOctetsEntry 10}

pr1646v2EthPortSwIXt2InOctetsValue OBJECT-TYPE
   SYNTAX      Counter64
   MAX-ACCESS  read-only
   STATUS      current
   DESCRIPTION
      "Path: swPort.performance.ifInOctets

       64 bit unsigned wrappable counter."
   ::= {pr1646v2EthPortSwIXt2InOctetsEntry 2147483648}


pr1646v2EthPortSwIXt2InUcast OBJECT IDENTIFIER ::= {pr1646v2EthPortSwIXt2 110}

pr1646v2EthPortSwIXt2InUcastTable OBJECT-TYPE
   SYNTAX      SEQUENCE OF Pr1646v2EthPortSwIXt2InUcastEntry
   MAX-ACCESS  not-accessible
   STATUS      current
   DESCRIPTION
      "ifInUcastPkts"
   ::= {pr1646v2EthPortSwIXt2InUcast 1}

pr1646v2EthPortSwIXt2InUcastEntry OBJECT-TYPE
   SYNTAX      Pr1646v2EthPortSwIXt2InUcastEntry
   MAX-ACCESS  not-accessible
   STATUS      current
   DESCRIPTION
      ""
   INDEX      { pr1646v2EthPortSwIXt2InUcastGlobalIx }
   ::= {pr1646v2EthPortSwIXt2InUcastTable 1}

Pr1646v2EthPortSwIXt2InUcastEntry ::=
   SEQUENCE
      {
      pr1646v2EthPortSwIXt2InUcastGlobalIx
         GlobalIndex,
      pr1646v2EthPortSwIXt2InUcastValue
         Counter64
      }

pr1646v2EthPortSwIXt2InUcastGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InUcastEntry 10}

pr1646v2EthPortSwIXt2InUcastValue OBJECT-TYPE
   SYNTAX      Counter64
   MAX-ACCESS  read-only
   STATUS      current
   DESCRIPTION
      "Path: swPort.performance.ifInUcastPkts

       64 bit unsigned wrappable counter."
   ::= {pr1646v2EthPortSwIXt2InUcastEntry 2147483648}


pr1646v2EthPortSwIXt2InNUcastPkts OBJECT IDENTIFIER ::= {pr1646v2EthPortSwIXt2 111}

pr1646v2EthPortSwIXt2InNUcastPktsTable OBJECT-TYPE
   SYNTAX      SEQUENCE OF Pr1646v2EthPortSwIXt2InNUcastPktsEntry
   MAX-ACCESS  not-accessible
   STATUS      current
   DESCRIPTION
      "ifInNUcastPkts"
   ::= {pr1646v2EthPortSwIXt2InNUcastPkts 1}

pr1646v2EthPortSwIXt2InNUcastPktsEntry OBJECT-TYPE
   SYNTAX      Pr1646v2EthPortSwIXt2InNUcastPktsEntry
   MAX-ACCESS  not-accessible
   STATUS      current
   DESCRIPTION
      ""
   INDEX      { pr1646v2EthPortSwIXt2InNUcastPktsGlobalIx }
   ::= {pr1646v2EthPortSwIXt2InNUcastPktsTable 1}

Pr1646v2EthPortSwIXt2InNUcastPktsEntry ::=
   SEQUENCE
      {
      pr1646v2EthPortSwIXt2InNUcastPktsGlobalIx
         GlobalIndex,
      pr1646v2EthPortSwIXt2InNUcastPktsValue
         Counter64
      }

pr1646v2EthPortSwIXt2InNUcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InNUcastPktsEntry 10}

pr1646v2EthPortSwIXt2InNUcastPktsValue OBJECT-TYPE
   SYNTAX      Counter64
   MAX-ACCESS  read-only
   STATUS      current
   DESCRIPTION
      "Path: swPort.performance.ifInNUcastPkts

       64 bit unsigned wrappable counter."
   ::= {pr1646v2EthPortSwIXt2InNUcastPktsEntry 2147483648}


pr1646v2EthPortSwIXt2InBcastPkts OBJECT IDENTIFIER ::= {pr1646v2EthPortSwIXt2 211}

pr1646v2EthPortSwIXt2InBcastPktsTable OBJECT-TYPE
   SYNTAX      SEQUENCE OF Pr1646v2EthPortSwIXt2InBcastPktsEntry
   MAX-ACCESS  not-accessible
   STATUS      current
   DESCRIPTION
      "ifInBcastPkts"
   ::= {pr1646v2EthPortSwIXt2InBcastPkts 1}

pr1646v2EthPortSwIXt2InBcastPktsEntry OBJECT-TYPE
   SYNTAX      Pr1646v2EthPortSwIXt2InBcastPktsEntry
   MAX-ACCESS  not-accessible
   STATUS      current
   DESCRIPTION
      ""
   INDEX      { pr1646v2EthPortSwIXt2InBcastPktsGlobalIx }
   ::= {pr1646v2EthPortSwIXt2InBcastPktsTable 1}

Pr1646v2EthPortSwIXt2InBcastPktsEntry ::=
   SEQUENCE
      {
      pr1646v2EthPortSwIXt2InBcastPktsGlobalIx
         GlobalIndex,
      pr1646v2EthPortSwIXt2InBcastPktsValue
         Counter64
      }

pr1646v2EthPortSwIXt2InBcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InBcastPktsEntry 10}

pr1646v2EthPortSwIXt2InBcastPktsValue OBJECT-TYPE
   SYNTAX      Counter64
   MAX-ACCESS  read-only
   STATUS      current
   DESCRIPTION
      "Path: swPort.performance.ifInBcastPkts

       64 bit unsigned wrappable counter."
   ::= {pr1646v2EthPortSwIXt2InBcastPktsEntry 2147483648}


pr1646v2EthPortSwIXt2InMcastPkts OBJECT IDENTIFIER ::= {pr1646v2EthPortSwIXt2 221}

pr1646v2EthPortSwIXt2InMcastPktsTable OBJECT-TYPE
   SYNTAX      SEQUENCE OF Pr1646v2EthPortSwIXt2InMcastPktsEntry
   MAX-ACCESS  not-accessible
   STATUS      current
   DESCRIPTION
      "ifInNUcastPkts"
   ::= {pr1646v2EthPortSwIXt2InMcastPkts 1}

pr1646v2EthPortSwIXt2InMcastPktsEntry OBJECT-TYPE
   SYNTAX      Pr1646v2EthPortSwIXt2InMcastPktsEntry
   MAX-ACCESS  not-accessible
   STATUS      current
   DESCRIPTION
      ""
   INDEX      { pr1646v2EthPortSwIXt2InMcastPktsGlobalIx }
   ::= {pr1646v2EthPortSwIXt2InMcastPktsTable 1}

Pr1646v2EthPortSwIXt2InMcastPktsEntry ::=
   SEQUENCE
      {
      pr1646v2EthPortSwIXt2InMcastPktsGlobalIx
         GlobalIndex,
      pr1646v2EthPortSwIXt2InMcastPktsValue
         Counter64
      }

pr1646v2EthPortSwIXt2InMcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InMcastPktsEntry 10}

pr1646v2EthPortSwIXt2InMcastPktsValue OBJECT-TYPE
   SYNTAX      Counter64
   MAX-ACCESS  read-only
   STATUS      current
   DESCRIPTION
      "Path: swPort.performance.ifInMcastPkts

       64 bit unsigned wrappable counter."
   ::= {pr1646v2EthPortSwIXt2InMcastPktsEntry 2147483648}


pr1646v2EthPortSwIXt2InDiscards OBJECT IDENTIFIER ::= {pr1646v2EthPortSwIXt2 112}

pr1646v2EthPortSwIXt2InDiscardsTable OBJECT-TYPE
   SYNTAX      SEQUENCE OF Pr1646v2EthPortSwIXt2InDiscardsEntry
   MAX-ACCESS  not-accessible
   STATUS      current
   DESCRIPTION
      "ifInDiscards"
   ::= {pr1646v2EthPortSwIXt2InDiscards 1}

pr1646v2EthPortSwIXt2InDiscardsEntry OBJECT-TYPE
   SYNTAX      Pr1646v2EthPortSwIXt2InDiscardsEntry
   MAX-ACCESS  not-accessible
   STATUS      current
   DESCRIPTION
      ""
   INDEX      { pr1646v2EthPortSwIXt2InDiscardsGlobalIx }
   ::= {pr1646v2EthPortSwIXt2InDiscardsTable 1}

Pr1646v2EthPortSwIXt2InDiscardsEntry ::=
   SEQUENCE
      {
      pr1646v2EthPortSwIXt2InDiscardsGlobalIx
         GlobalIndex,
      pr1646v2EthPortSwIXt2InDiscardsValue
         Counter64
      }

pr1646v2EthPortSwIXt2InDiscardsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InDiscardsEntry 10}

pr1646v2EthPortSwIXt2InDiscardsValue OBJECT-TYPE
   SYNTAX      Counter64
   MAX-ACCESS  read-only
   STATUS      current
   DESCRIPTION
      "Path: swPort.performance.ifInDiscards

       64 bit unsigned wrappable counter."
   ::= {pr1646v2EthPortSwIXt2InDiscardsEntry 2147483648}


pr1646v2EthPortSwIXt2InErrors OBJECT IDENTIFIER ::= {pr1646v2EthPortSwIXt2 113}

pr1646v2EthPortSwIXt2InErrorsTable OBJECT-TYPE
   SYNTAX      SEQUENCE OF Pr1646v2EthPortSwIXt2InErrorsEntry
   MAX-ACCESS  not-accessible
   STATUS      current
   DESCRIPTION
      "ifInErrors"
   ::= {pr1646v2EthPortSwIXt2InErrors 1}

pr1646v2EthPortSwIXt2InErrorsEntry OBJECT-TYPE
   SYNTAX      Pr1646v2EthPortSwIXt2InErrorsEntry
   MAX-ACCESS  not-accessible
   STATUS      current
   DESCRIPTION
      ""
   INDEX      { pr1646v2EthPortSwIXt2InErrorsGlobalIx }
   ::= {pr1646v2EthPortSwIXt2InErrorsTable 1}

Pr1646v2EthPortSwIXt2InErrorsEntry ::=
   SEQUENCE
      {
      pr1646v2EthPortSwIXt2InErrorsGlobalIx
         GlobalIndex,
      pr1646v2EthPortSwIXt2InErrorsValue
         Counter64
      }

pr1646v2EthPortSwIXt2InErrorsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InErrorsEntry 10}

pr1646v2EthPortSwIXt2InErrorsValue OBJECT-TYPE
   SYNTAX      Counter64
   MAX-ACCESS  read-only
   STATUS      current
   DESCRIPTION
      "Path: swPort.performance.ifInErrors

       64 bit unsigned wrappable counter."
   ::= {pr1646v2EthPortSwIXt2InErrorsEntry 2147483648}


pr1646v2EthPortSwIXt2InUnknownProtos OBJECT IDENTIFIER ::= {pr1646v2EthPortSwIXt2 114}

pr1646v2EthPortSwIXt2InUnknownProtosTable OBJECT-TYPE
   SYNTAX      SEQUENCE OF Pr1646v2EthPortSwIXt2InUnknownProtosEntry
   MAX-ACCESS  not-accessible
   STATUS      current
   DESCRIPTION
      "ifInUnknownprotos"
   ::= {pr1646v2EthPortSwIXt2InUnknownProtos 1}

pr1646v2EthPortSwIXt2InUnknownProtosEntry OBJECT-TYPE
   SYNTAX      Pr1646v2EthPortSwIXt2InUnknownProtosEntry
   MAX-ACCESS  not-accessible
   STATUS      current
   DESCRIPTION
      ""
   INDEX      { pr1646v2EthPortSwIXt2InUnknownProtosGlobalIx }
   ::= {pr1646v2EthPortSwIXt2InUnknownProtosTable 1}

Pr1646v2EthPortSwIXt2InUnknownProtosEntry ::=
   SEQUENCE
      {
      pr1646v2EthPortSwIXt2InUnknownProtosGlobalIx
         GlobalIndex,
      pr1646v2EthPortSwIXt2InUnknownProtosValue
         Counter64
      }

pr1646v2EthPortSwIXt2InUnknownProtosGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InUnknownProtosEntry 10}

pr1646v2EthPortSwIXt2InUnknownProtosValue OBJECT-TYPE
   SYNTAX      Counter64
   MAX-ACCESS  read-only
   STATUS      current
   DESCRIPTION
      "Path: swPort.performance.ifInUnknownProtos

       64 bit unsigned wrappable counter."
   ::= {pr1646v2EthPortSwIXt2InUnknownProtosEntry 2147483648}


pr1646v2EthPortSwIXt2InDropEx OBJECT IDENTIFIER ::= {pr1646v2EthPortSwIXt2 130}

pr1646v2EthPortSwIXt2InDropExTable OBJECT-TYPE
   SYNTAX      SEQUENCE OF Pr1646v2EthPortSwIXt2InDropExEntry
   MAX-ACCESS  not-accessible
   STATUS      current
   DESCRIPTION
      "ifInDiscards"
   ::= {pr1646v2EthPortSwIXt2InDropEx 1}

pr1646v2EthPortSwIXt2InDropExEntry OBJECT-TYPE
   SYNTAX      Pr1646v2EthPortSwIXt2InDropExEntry
   MAX-ACCESS  not-accessible
   STATUS      current
   DESCRIPTION
      ""
   INDEX      { pr1646v2EthPortSwIXt2InDropExGlobalIx }
   ::= {pr1646v2EthPortSwIXt2InDropExTable 1}

Pr1646v2EthPortSwIXt2InDropExEntry ::=
   SEQUENCE
      {
      pr1646v2EthPortSwIXt2InDropExGlobalIx
         GlobalIndex,
      pr1646v2EthPortSwIXt2InDropExValue
         Counter64
      }

pr1646v2EthPortSwIXt2InDropExGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InDropExEntry 10}

pr1646v2EthPortSwIXt2InDropExValue OBJECT-TYPE
   SYNTAX      Counter64
   MAX-ACCESS  read-only
   STATUS      current
   DESCRIPTION
      "Path: swPort.performance.ifInDropLevelExceeded

       64 bit unsigned wrappable counter."
   ::= {pr1646v2EthPortSwIXt2InDropExEntry 2147483648}


pr1646v2EthPortSwIXt2InDropNoMac OBJECT IDENTIFIER ::= {pr1646v2EthPortSwIXt2 133}

pr1646v2EthPortSwIXt2InDropNoMacTable OBJECT-TYPE
   SYNTAX      SEQUENCE OF Pr1646v2EthPortSwIXt2InDropNoMacEntry
   MAX-ACCESS  not-accessible
   STATUS      current
   DESCRIPTION
      "ifInDiscards"
   ::= {pr1646v2EthPortSwIXt2InDropNoMac 1}

pr1646v2EthPortSwIXt2InDropNoMacEntry OBJECT-TYPE
   SYNTAX      Pr1646v2EthPortSwIXt2InDropNoMacEntry
   MAX-ACCESS  not-accessible
   STATUS      current
   DESCRIPTION
      ""
   INDEX      { pr1646v2EthPortSwIXt2InDropNoMacGlobalIx }
   ::= {pr1646v2EthPortSwIXt2InDropNoMacTable 1}

Pr1646v2EthPortSwIXt2InDropNoMacEntry ::=
   SEQUENCE
      {
      pr1646v2EthPortSwIXt2InDropNoMacGlobalIx
         GlobalIndex,
      pr1646v2EthPortSwIXt2InDropNoMacValue
         Counter64
      }

pr1646v2EthPortSwIXt2InDropNoMacGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InDropNoMacEntry 10}

pr1646v2EthPortSwIXt2InDropNoMacValue OBJECT-TYPE
   SYNTAX      Counter64
   MAX-ACCESS  read-only
   STATUS      current
   DESCRIPTION
      "Path: swPort.performance.ifInDiscardsNoMacFit

       64 bit unsigned wrappable counter."
   ::= {pr1646v2EthPortSwIXt2InDropNoMacEntry 2147483648}


pr1646v2EthPortSwIXt2InDropNUCast OBJECT IDENTIFIER ::= {pr1646v2EthPortSwIXt2 136}

pr1646v2EthPortSwIXt2InDropNUCastTable OBJECT-TYPE
   SYNTAX      SEQUENCE OF Pr1646v2EthPortSwIXt2InDropNUCastEntry
   MAX-ACCESS  not-accessible
   STATUS      current
   DESCRIPTION
      "ifInDiscards"
   ::= {pr1646v2EthPortSwIXt2InDropNUCast 1}

pr1646v2EthPortSwIXt2InDropNUCastEntry OBJECT-TYPE
   SYNTAX      Pr1646v2EthPortSwIXt2InDropNUCastEntry
   MAX-ACCESS  not-accessible
   STATUS      current
   DESCRIPTION
      ""
   INDEX      { pr1646v2EthPortSwIXt2InDropNUCastGlobalIx }
   ::= {pr1646v2EthPortSwIXt2InDropNUCastTable 1}

Pr1646v2EthPortSwIXt2InDropNUCastEntry ::=
   SEQUENCE
      {
      pr1646v2EthPortSwIXt2InDropNUCastGlobalIx
         GlobalIndex,
      pr1646v2EthPortSwIXt2InDropNUCastValue
         Counter64
      }

pr1646v2EthPortSwIXt2InDropNUCastGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InDropNUCastEntry 10}

pr1646v2EthPortSwIXt2InDropNUCastValue OBJECT-TYPE
   SYNTAX      Counter64
   MAX-ACCESS  read-only
   STATUS      current
   DESCRIPTION
      "Path: swPort.performance.ifInDiscardsNUCast

       64 bit unsigned wrappable counter."
   ::= {pr1646v2EthPortSwIXt2InDropNUCastEntry 2147483648}


pr1646v2EthPortSwIXt2InDropFilter OBJECT IDENTIFIER ::= {pr1646v2EthPortSwIXt2 137}

pr1646v2EthPortSwIXt2InDropFilterTable OBJECT-TYPE
   SYNTAX      SEQUENCE OF Pr1646v2EthPortSwIXt2InDropFilterEntry
   MAX-ACCESS  not-accessible
   STATUS      current
   DESCRIPTION
      "ifInDiscards"
   ::= {pr1646v2EthPortSwIXt2InDropFilter 1}

pr1646v2EthPortSwIXt2InDropFilterEntry OBJECT-TYPE
   SYNTAX      Pr1646v2EthPortSwIXt2InDropFilterEntry
   MAX-ACCESS  not-accessible
   STATUS      current
   DESCRIPTION
      ""
   INDEX      { pr1646v2EthPortSwIXt2InDropFilterGlobalIx }
   ::= {pr1646v2EthPortSwIXt2InDropFilterTable 1}

Pr1646v2EthPortSwIXt2InDropFilterEntry ::=
   SEQUENCE
      {
      pr1646v2EthPortSwIXt2InDropFilterGlobalIx
         GlobalIndex,
      pr1646v2EthPortSwIXt2InDropFilterValue
         Counter64
      }

pr1646v2EthPortSwIXt2InDropFilterGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InDropFilterEntry 10}

pr1646v2EthPortSwIXt2InDropFilterValue OBJECT-TYPE
   SYNTAX      Counter64
   MAX-ACCESS  read-only
   STATUS      current
   DESCRIPTION
      "Path: swPort.performance.ifInDiscardsFilter

       64 bit unsigned wrappable counter."
   ::= {pr1646v2EthPortSwIXt2InDropFilterEntry 2147483648}


pr1646v2EthPortSwIXt2InQueues OBJECT IDENTIFIER ::= {pr1646v2EthPortSwIXt2 131}

pr1646v2EthPortSwIXt2InQueuesSSCTable OBJECT-TYPE
   SYNTAX      SEQUENCE OF Pr1646v2EthPortSwIXt2InQueuesEntry
   MAX-ACCESS  not-accessible
   STATUS      current
   DESCRIPTION
      "Queue Lengths"
   ::= {pr1646v2EthPortSwIXt2InQueues 1}

pr1646v2EthPortSwIXt2InQueuesEntry OBJECT-TYPE
   SYNTAX      Pr1646v2EthPortSwIXt2InQueuesEntry
   MAX-ACCESS  not-accessible
   STATUS      current
   DESCRIPTION
      ""
   INDEX      { pr1646v2EthPortSwIXt2InQueuesGlobalIx,
                pr1646v2EthPortSwIXt2InQueuesTableIx }
   ::= {pr1646v2EthPortSwIXt2InQueuesSSCTable 1}

Pr1646v2EthPortSwIXt2InQueuesEntry ::=
   SEQUENCE
      {
      pr1646v2EthPortSwIXt2InQueuesGlobalIx
         GlobalIndex,
      pr1646v2EthPortSwIXt2InQueuesTableIx
         TableIndex,
      pr1646v2EthPortSwIXt2InQueuesName
         INTEGER,
      pr1646v2EthPortSwIXt2InQueuesLength
         Integer32,
      pr1646v2EthPortSwIXt2InQueuesOctetLength
         Integer32,
      pr1646v2EthPortSwIXt2InQueuesRedLength
         Integer32,
      pr1646v2EthPortSwIXt2InQueuesPacketsTotal
         Counter64,
      pr1646v2EthPortSwIXt2InQueuesPacketsDirectTx
         Counter64,
      pr1646v2EthPortSwIXt2InQueuesPacketsQueued
         Counter64,
      pr1646v2EthPortSwIXt2InQueuesPacketsDropped
         Counter64,
      pr1646v2EthPortSwIXt2InQueuesPacketsRedDropped
         Counter64,
      pr1646v2EthPortSwIXt2InQueuesPacketsCirTx
         Counter64,
      pr1646v2EthPortSwIXt2InQueuesPacketsEirTx
         Counter64,
      pr1646v2EthPortSwIXt2InQueuesPacketsViolateTx
         Counter64,
      pr1646v2EthPortSwIXt2InQueuesOctetsTotal
         Counter64,
      pr1646v2EthPortSwIXt2InQueuesOctetsDirectTx
         Counter64,
      pr1646v2EthPortSwIXt2InQueuesOctetsQueued
         Counter64,
      pr1646v2EthPortSwIXt2InQueuesOctetsDropped
         Counter64,
      pr1646v2EthPortSwIXt2InQueuesOctetsRedDropped
         Counter64,
      pr1646v2EthPortSwIXt2InQueuesOctetsCirTx
         Counter64,
      pr1646v2EthPortSwIXt2InQueuesOctetsEirTx
         Counter64,
      pr1646v2EthPortSwIXt2InQueuesOctetsViolateTx
         Counter64,
      pr1646v2EthPortSwIXt2InQueuesOctetsBandwidth15sec
         Integer32,
      pr1646v2EthPortSwIXt2InQueuesOctetsBandwidth30sec
         Integer32,
      pr1646v2EthPortSwIXt2InQueuesOctetsBandwidth1min
         Integer32,
      pr1646v2EthPortSwIXt2InQueuesOctetsBandwidth2min
         Integer32,
      pr1646v2EthPortSwIXt2InQueuesOctetsBandwidth5min
         Integer32
      }

pr1646v2EthPortSwIXt2InQueuesGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InQueuesEntry 10}

pr1646v2EthPortSwIXt2InQueuesTableIx OBJECT-TYPE
   SYNTAX      TableIndex
   MAX-ACCESS  not-accessible
   STATUS      current
   DESCRIPTION
      ""
   ::= {pr1646v2EthPortSwIXt2InQueuesEntry 11}

pr1646v2EthPortSwIXt2InQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwIXt2InQueuesEntry 16777216}

pr1646v2EthPortSwIXt2InQueuesLength OBJECT-TYPE
   SYNTAX      Integer32
   MAX-ACCESS  read-only
   STATUS      current
   DESCRIPTION
      "Path: swPort.performance.ifInPriorityQueues.length"
   ::= {pr1646v2EthPortSwIXt2InQueuesEntry 33554432}

pr1646v2EthPortSwIXt2InQueuesOctetLength OBJECT-TYPE
   SYNTAX      Integer32
   MAX-ACCESS  read-only
   STATUS      current
   DESCRIPTION
      "Path: swPort.performance.ifInPriorityQueues.octetLength"
   ::= {pr1646v2EthPortSwIXt2InQueuesEntry 150994944}

pr1646v2EthPortSwIXt2InQueuesRedLength OBJECT-TYPE
   SYNTAX      Integer32
   MAX-ACCESS  read-only
   STATUS      current
   DESCRIPTION
      "Path: swPort.performance.ifInPriorityQueues.redLength"
   ::= {pr1646v2EthPortSwIXt2InQueuesEntry 134217728}

pr1646v2EthPortSwIXt2InQueuesPacketsTotal OBJECT-TYPE
   SYNTAX      Counter64
   MAX-ACCESS  read-only
   STATUS      current
   DESCRIPTION
      "Path: swPort.performance.ifInPriorityQueues.packets.total

       64 bit unsigned wrappable counter."
   ::= {pr1646v2EthPortSwIXt2InQueuesEntry 50790400}

pr1646v2EthPortSwIXt2InQueuesPacketsDirectTx OBJECT-TYPE
   SYNTAX      Counter64
   MAX-ACCESS  read-only
   STATUS      current
   DESCRIPTION
      "Path: swPort.performance.ifInPriorityQueues.packets.directTx

       64 bit unsigned wrappable counter."
   ::= {pr1646v2EthPortSwIXt2InQueuesEntry 50397184}

pr1646v2EthPortSwIXt2InQueuesPacketsQueued OBJECT-TYPE
   SYNTAX      Counter64
   MAX-ACCESS  read-only
   STATUS      current
   DESCRIPTION
      "Path: swPort.performance.ifInPriorityQueues.packets.queued

       64 bit unsigned wrappable counter."
   ::= {pr1646v2EthPortSwIXt2InQueuesEntry 50462720}

pr1646v2EthPortSwIXt2InQueuesPacketsDropped OBJECT-TYPE
   SYNTAX      Counter64
   MAX-ACCESS  read-only
   STATUS      current
   DESCRIPTION
      "Path: swPort.performance.ifInPriorityQueues.packets.dropped

       64 bit unsigned wrappable counter."
   ::= {pr1646v2EthPortSwIXt2InQueuesEntry 50528256}

pr1646v2EthPortSwIXt2InQueuesPacketsRedDropped OBJECT-TYPE
   SYNTAX      Counter64
   MAX-ACCESS  read-only
   STATUS      current
   DESCRIPTION
      "Path: swPort.performance.ifInPriorityQueues.packets.redDropped

       64 bit unsigned wrappable counter."
   ::= {pr1646v2EthPortSwIXt2InQueuesEntry 50724864}

pr1646v2EthPortSwIXt2InQueuesPacketsCirTx OBJECT-TYPE
   SYNTAX      Counter64
   MAX-ACCESS  read-only
   STATUS      current
   DESCRIPTION
      "Path: swPort.performance.ifInPriorityQueues.packets.cirTx

       64 bit unsigned wrappable counter."
   ::= {pr1646v2EthPortSwIXt2InQueuesEntry 50593792}

pr1646v2EthPortSwIXt2InQueuesPacketsEirTx OBJECT-TYPE
   SYNTAX      Counter64
   MAX-ACCESS  read-only
   STATUS      current
   DESCRIPTION
      "Path: swPort.performance.ifInPriorityQueues.packets.eirTx

       64 bit unsigned wrappable counter."
   ::= {pr1646v2EthPortSwIXt2InQueuesEntry 50659328}

pr1646v2EthPortSwIXt2InQueuesPacketsViolateTx OBJECT-TYPE
   SYNTAX      Counter64
   MAX-ACCESS  read-only
   STATUS      current
   DESCRIPTION
      "Path: swPort.performance.ifInPriorityQueues.packets.violateTx

       64 bit unsigned wrappable counter."
   ::= {pr1646v2EthPortSwIXt2InQueuesEntry 50855936}

pr1646v2EthPortSwIXt2InQueuesOctetsTotal OBJECT-TYPE
   SYNTAX      Counter64
   MAX-ACCESS  read-only
   STATUS      current
   DESCRIPTION
      "Path: swPort.performance.ifInPriorityQueues.octets.total

       64 bit unsigned wrappable counter."
   ::= {pr1646v2EthPortSwIXt2InQueuesEntry 67567616}

pr1646v2EthPortSwIXt2InQueuesOctetsDirectTx OBJECT-TYPE
   SYNTAX      Counter64
   MAX-ACCESS  read-only
   STATUS      current
   DESCRIPTION
      "Path: swPort.performance.ifInPriorityQueues.octets.directTx

       64 bit unsigned wrappable counter."
   ::= {pr1646v2EthPortSwIXt2InQueuesEntry 67174400}

pr1646v2EthPortSwIXt2InQueuesOctetsQueued OBJECT-TYPE
   SYNTAX      Counter64
   MAX-ACCESS  read-only
   STATUS      current
   DESCRIPTION
      "Path: swPort.performance.ifInPriorityQueues.octets.queued

       64 bit unsigned wrappable counter."
   ::= {pr1646v2EthPortSwIXt2InQueuesEntry 67239936}

pr1646v2EthPortSwIXt2InQueuesOctetsDropped OBJECT-TYPE
   SYNTAX      Counter64
   MAX-ACCESS  read-only
   STATUS      current
   DESCRIPTION
      "Path: swPort.performance.ifInPriorityQueues.octets.dropped

       64 bit unsigned wrappable counter."
   ::= {pr1646v2EthPortSwIXt2InQueuesEntry 67305472}

pr1646v2EthPortSwIXt2InQueuesOctetsRedDropped OBJECT-TYPE
   SYNTAX      Counter64
   MAX-ACCESS  read-only
   STATUS      current
   DESCRIPTION
      "Path: swPort.performance.ifInPriorityQueues.octets.redDropped

       64 bit unsigned wrappable counter."
   ::= {pr1646v2EthPortSwIXt2InQueuesEntry 67502080}

pr1646v2EthPortSwIXt2InQueuesOctetsCirTx OBJECT-TYPE
   SYNTAX      Counter64
   MAX-ACCESS  read-only
   STATUS      current
   DESCRIPTION
      "Path: swPort.performance.ifInPriorityQueues.octets.cirTx

       64 bit unsigned wrappable counter."
   ::= {pr1646v2EthPortSwIXt2InQueuesEntry 67371008}

pr1646v2EthPortSwIXt2InQueuesOctetsEirTx OBJECT-TYPE
   SYNTAX      Counter64
   MAX-ACCESS  read-only
   STATUS      current
   DESCRIPTION
      "Path: swPort.performance.ifInPriorityQueues.octets.eirTx

       64 bit unsigned wrappable counter."
   ::= {pr1646v2EthPortSwIXt2InQueuesEntry 67436544}

pr1646v2EthPortSwIXt2InQueuesOctetsViolateTx OBJECT-TYPE
   SYNTAX      Counter64
   MAX-ACCESS  read-only
   STATUS      current
   DESCRIPTION
      "Path: swPort.performance.ifInPriorityQueues.octets.violateTx

       64 bit unsigned wrappable counter."
   ::= {pr1646v2EthPortSwIXt2InQueuesEntry 67633152}

pr1646v2EthPortSwIXt2InQueuesOctetsBandwidth15sec OBJECT-TYPE
   SYNTAX      Integer32
   MAX-ACCESS  read-only
   STATUS      current
   DESCRIPTION
      "Path: swPort.performance.ifInPriorityQueues.octets.bandwidth.15sec

       unit name = bps
       formula = 8 * ; 8 /"
   ::= {pr1646v2EthPortSwIXt2InQueuesEntry 70386944}

pr1646v2EthPortSwIXt2InQueuesOctetsBandwidth30sec OBJECT-TYPE
   SYNTAX      Integer32
   MAX-ACCESS  read-only
   STATUS      current
   DESCRIPTION
      "Path: swPort.performance.ifInPriorityQueues.octets.bandwidth.30sec

       unit name = bps
       formula = 8 * ; 8 /"
   ::= {pr1646v2EthPortSwIXt2InQueuesEntry 70388224}

pr1646v2EthPortSwIXt2InQueuesOctetsBandwidth1min OBJECT-TYPE
   SYNTAX      Integer32
   MAX-ACCESS  read-only
   STATUS      current
   DESCRIPTION
      "Path: swPort.performance.ifInPriorityQueues.octets.bandwidth.1min

       unit name = bps
       formula = 8 * ; 8 /"
   ::= {pr1646v2EthPortSwIXt2InQueuesEntry 70390784}

pr1646v2EthPortSwIXt2InQueuesOctetsBandwidth2min OBJECT-TYPE
   SYNTAX      Integer32
   MAX-ACCESS  read-only
   STATUS      current
   DESCRIPTION
      "Path: swPort.performance.ifInPriorityQueues.octets.bandwidth.2min

       unit name = bps
       formula = 8 * ; 8 /"
   ::= {pr1646v2EthPortSwIXt2InQueuesEntry 70395904}

pr1646v2EthPortSwIXt2InQueuesOctetsBandwidth5min OBJECT-TYPE
   SYNTAX      Integer32
   MAX-ACCESS  read-only
   STATUS      current
   DESCRIPTION
      "Path: swPort.performance.ifInPriorityQueues.octets.bandwidth.5min

       unit name = bps
       formula = 8 * ; 8 /"
   ::= {pr1646v2EthPortSwIXt2InQueuesEntry 70411264}

pr1646v2EthPortSwIXt2InQueuesH2Performance OBJECT-TYPE
   SYNTAX      SEQUENCE OF Pr1646v2EthPortSwIXt2InQueuesH2PerformanceEntry
   MAX-ACCESS  not-accessible
   STATUS      current
   DESCRIPTION
      ""
   ::= {pr1646v2EthPortSwIXt2InQueues 83886080}

pr1646v2EthPortSwIXt2InQueuesH2PerformanceEntry OBJECT-TYPE
   SYNTAX      Pr1646v2EthPortSwIXt2InQueuesH2PerformanceEntry
   MAX-ACCESS  not-accessible
   STATUS      current
   DESCRIPTION
      ""
   INDEX      { pr1646v2EthPortSwIXt2InQueuesH2PerformanceGlobalIx,
                pr1646v2EthPortSwIXt2InQueuesTableIx,
                pr1646v2EthPortSwIXt2InQueuesH2PerformanceTableIx }
   ::= {pr1646v2EthPortSwIXt2InQueuesH2Performance 1}

Pr1646v2EthPortSwIXt2InQueuesH2PerformanceEntry ::=
   SEQUENCE
      {
      pr1646v2EthPortSwIXt2InQueuesH2PerformanceGlobalIx
         GlobalIndex,
      pr1646v2EthPortSwIXt2InQueuesH2PerformanceTableIx
         TableIndex,
      pr1646v2EthPortSwIXt2InQueuesH2PerformanceSysUpTime
         TimeTicks,
      pr1646v2EthPortSwIXt2InQueuesH2PerformanceTotPkts
         Counter64,
      pr1646v2EthPortSwIXt2InQueuesH2PerformanceDirTxPkts
         Counter64,
      pr1646v2EthPortSwIXt2InQueuesH2PerformanceQdPkts
         Counter64,
      pr1646v2EthPortSwIXt2InQueuesH2PerformanceDropPkts
         Counter64,
      pr1646v2EthPortSwIXt2InQueuesH2PerformanceRDropPkts
         Counter64,
      pr1646v2EthPortSwIXt2InQueuesH2PerformanceCirTxPkts
         Counter64,
      pr1646v2EthPortSwIXt2InQueuesH2PerformanceEirTxPkts
         Counter64,
      pr1646v2EthPortSwIXt2InQueuesH2PerformanceViolTxPkts
         Counter64,
      pr1646v2EthPortSwIXt2InQueuesH2PerformanceTotOcts
         Counter64,
      pr1646v2EthPortSwIXt2InQueuesH2PerformanceDirTxOcts
         Counter64,
      pr1646v2EthPortSwIXt2InQueuesH2PerformanceQdOcts
         Counter64,
      pr1646v2EthPortSwIXt2InQueuesH2PerformanceDropOcts
         Counter64,
      pr1646v2EthPortSwIXt2InQueuesH2PerformanceRDropOcts
         Counter64,
      pr1646v2EthPortSwIXt2InQueuesH2PerformanceCirTxOcts
         Counter64,
      pr1646v2EthPortSwIXt2InQueuesH2PerformanceEirTxOcts
         Counter64,
      pr1646v2EthPortSwIXt2InQueuesH2PerformanceViolTxOcts
         Counter64,
      pr1646v2EthPortSwIXt2InQueuesH2PerformanceBandwidth
         Integer32
      }

pr1646v2EthPortSwIXt2InQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InQueuesH2PerformanceEntry 10}

pr1646v2EthPortSwIXt2InQueuesH2PerformanceTableIx OBJECT-TYPE
   SYNTAX      TableIndex
   MAX-ACCESS  not-accessible
   STATUS      current
   DESCRIPTION
      ""
   ::= {pr1646v2EthPortSwIXt2InQueuesH2PerformanceEntry 11}

pr1646v2EthPortSwIXt2InQueuesH2PerformanceSysUpTime OBJECT-TYPE
   SYNTAX      TimeTicks
   MAX-ACCESS  read-only
   STATUS      current
   DESCRIPTION
      "Path: swPort.performance.ifInPriorityQueues.h2Performance.sysUpTime

       Time in centi-second."
   ::= {pr1646v2EthPortSwIXt2InQueuesH2PerformanceEntry 16777216}

pr1646v2EthPortSwIXt2InQueuesH2PerformanceTotPkts OBJECT-TYPE
   SYNTAX      Counter64
   MAX-ACCESS  read-only
   STATUS      current
   DESCRIPTION
      "Path: swPort.performance.ifInPriorityQueues.h2Performance.totalPkts

       64 bit unsigned wrappable counter."
   ::= {pr1646v2EthPortSwIXt2InQueuesH2PerformanceEntry 234881024}

pr1646v2EthPortSwIXt2InQueuesH2PerformanceDirTxPkts OBJECT-TYPE
   SYNTAX      Counter64
   MAX-ACCESS  read-only
   STATUS      current
   DESCRIPTION
      "Path: swPort.performance.ifInPriorityQueues.h2Performance.directTxPkts

       64 bit unsigned wrappable counter."
   ::= {pr1646v2EthPortSwIXt2InQueuesH2PerformanceEntry 33554432}

pr1646v2EthPortSwIXt2InQueuesH2PerformanceQdPkts OBJECT-TYPE
   SYNTAX      Counter64
   MAX-ACCESS  read-only
   STATUS      current
   DESCRIPTION
      "Path: swPort.performance.ifInPriorityQueues.h2Performance.queuedPkts

       64 bit unsigned wrappable counter."
   ::= {pr1646v2EthPortSwIXt2InQueuesH2PerformanceEntry 50331648}

pr1646v2EthPortSwIXt2InQueuesH2PerformanceDropPkts OBJECT-TYPE
   SYNTAX      Counter64
   MAX-ACCESS  read-only
   STATUS      current
   DESCRIPTION
      "Path: swPort.performance.ifInPriorityQueues.h2Performance.droppedPkts

       64 bit unsigned wrappable counter."
   ::= {pr1646v2EthPortSwIXt2InQueuesH2PerformanceEntry 67108864}

pr1646v2EthPortSwIXt2InQueuesH2PerformanceRDropPkts OBJECT-TYPE
   SYNTAX      Counter64
   MAX-ACCESS  read-only
   STATUS      current
   DESCRIPTION
      "Path: swPort.performance.ifInPriorityQueues.h2Performance.redDroppedPkts

       64 bit unsigned wrappable counter."
   ::= {pr1646v2EthPortSwIXt2InQueuesH2PerformanceEntry 201326592}

pr1646v2EthPortSwIXt2InQueuesH2PerformanceCirTxPkts OBJECT-TYPE
   SYNTAX      Counter64
   MAX-ACCESS  read-only
   STATUS      current
   DESCRIPTION
      "Path: swPort.performance.ifInPriorityQueues.h2Performance.cirTxPkts

       64 bit unsigned wrappable counter."
   ::= {pr1646v2EthPortSwIXt2InQueuesH2PerformanceEntry 83886080}

pr1646v2EthPortSwIXt2InQueuesH2PerformanceEirTxPkts OBJECT-TYPE
   SYNTAX      Counter64
   MAX-ACCESS  read-only
   STATUS      current
   DESCRIPTION
      "Path: swPort.performance.ifInPriorityQueues.h2Performance.eirTxPkts

       64 bit unsigned wrappable counter."
   ::= {pr1646v2EthPortSwIXt2InQueuesH2PerformanceEntry 100663296}

pr1646v2EthPortSwIXt2InQueuesH2PerformanceViolTxPkts OBJECT-TYPE
   SYNTAX      Counter64
   MAX-ACCESS  read-only
   STATUS      current
   DESCRIPTION
      "Path: swPort.performance.ifInPriorityQueues.h2Performance.violateTxPkts

       64 bit unsigned wrappable counter."
   ::= {pr1646v2EthPortSwIXt2InQueuesH2PerformanceEntry 301989888}

pr1646v2EthPortSwIXt2InQueuesH2PerformanceTotOcts OBJECT-TYPE
   SYNTAX      Counter64
   MAX-ACCESS  read-only
   STATUS      current
   DESCRIPTION
      "Path: swPort.performance.ifInPriorityQueues.h2Performance.totalOctets

       64 bit unsigned wrappable counter."
   ::= {pr1646v2EthPortSwIXt2InQueuesH2PerformanceEntry 251658240}

pr1646v2EthPortSwIXt2InQueuesH2PerformanceDirTxOcts OBJECT-TYPE
   SYNTAX      Counter64
   MAX-ACCESS  read-only
   STATUS      current
   DESCRIPTION
      "Path: swPort.performance.ifInPriorityQueues.h2Performance.directTxOctets

       64 bit unsigned wrappable counter."
   ::= {pr1646v2EthPortSwIXt2InQueuesH2PerformanceEntry 117440512}

pr1646v2EthPortSwIXt2InQueuesH2PerformanceQdOcts OBJECT-TYPE
   SYNTAX      Counter64
   MAX-ACCESS  read-only
   STATUS      current
   DESCRIPTION
      "Path: swPort.performance.ifInPriorityQueues.h2Performance.queuedOctets

       64 bit unsigned wrappable counter."
   ::= {pr1646v2EthPortSwIXt2InQueuesH2PerformanceEntry 134217728}

pr1646v2EthPortSwIXt2InQueuesH2PerformanceDropOcts OBJECT-TYPE
   SYNTAX      Counter64
   MAX-ACCESS  read-only
   STATUS      current
   DESCRIPTION
      "Path: swPort.performance.ifInPriorityQueues.h2Performance.droppedOctets

       64 bit unsigned wrappable counter."
   ::= {pr1646v2EthPortSwIXt2InQueuesH2PerformanceEntry 150994944}

pr1646v2EthPortSwIXt2InQueuesH2PerformanceRDropOcts OBJECT-TYPE
   SYNTAX      Counter64
   MAX-ACCESS  read-only
   STATUS      current
   DESCRIPTION
      "Path: swPort.performance.ifInPriorityQueues.h2Performance.redDroppedOctets

       64 bit unsigned wrappable counter."
   ::= {pr1646v2EthPortSwIXt2InQueuesH2PerformanceEntry 218103808}

pr1646v2EthPortSwIXt2InQueuesH2PerformanceCirTxOcts OBJECT-TYPE
   SYNTAX      Counter64
   MAX-ACCESS  read-only
   STATUS      current
   DESCRIPTION
      "Path: swPort.performance.ifInPriorityQueues.h2Performance.cirTxOctets

       64 bit unsigned wrappable counter."
   ::= {pr1646v2EthPortSwIXt2InQueuesH2PerformanceEntry 167772160}

pr1646v2EthPortSwIXt2InQueuesH2PerformanceEirTxOcts OBJECT-TYPE
   SYNTAX      Counter64
   MAX-ACCESS  read-only
   STATUS      current
   DESCRIPTION
      "Path: swPort.performance.ifInPriorityQueues.h2Performance.eirTxOctets

       64 bit unsigned wrappable counter."
   ::= {pr1646v2EthPortSwIXt2InQueuesH2PerformanceEntry 184549376}

pr1646v2EthPortSwIXt2InQueuesH2PerformanceViolTxOcts OBJECT-TYPE
   SYNTAX      Counter64
   MAX-ACCESS  read-only
   STATUS      current
   DESCRIPTION
      "Path: swPort.performance.ifInPriorityQueues.h2Performance.violateTxOctets

       64 bit unsigned wrappable counter."
   ::= {pr1646v2EthPortSwIXt2InQueuesH2PerformanceEntry 318767104}

pr1646v2EthPortSwIXt2InQueuesH2PerformanceBandwidth OBJECT-TYPE
   SYNTAX      Integer32
   MAX-ACCESS  read-only
   STATUS      current
   DESCRIPTION
      "Path: swPort.performance.ifInPriorityQueues.h2Performance.bandwidth

       unit name = bps
       formula = 8 * ; 8 /"
   ::= {pr1646v2EthPortSwIXt2InQueuesH2PerformanceEntry 268435456}

pr1646v2EthPortSwIXt2InQueuesH24Performance OBJECT-TYPE
   SYNTAX      SEQUENCE OF Pr1646v2EthPortSwIXt2InQueuesH24PerformanceEntry
   MAX-ACCESS  not-accessible
   STATUS      current
   DESCRIPTION
      ""
   ::= {pr1646v2EthPortSwIXt2InQueues 100663296}

pr1646v2EthPortSwIXt2InQueuesH24PerformanceEntry OBJECT-TYPE
   SYNTAX      Pr1646v2EthPortSwIXt2InQueuesH24PerformanceEntry
   MAX-ACCESS  not-accessible
   STATUS      current
   DESCRIPTION
      ""
   INDEX      { pr1646v2EthPortSwIXt2InQueuesH24PerformanceGlobalIx,
                pr1646v2EthPortSwIXt2InQueuesTableIx,
                pr1646v2EthPortSwIXt2InQueuesH24PerformanceTableIx }
   ::= {pr1646v2EthPortSwIXt2InQueuesH24Performance 1}

Pr1646v2EthPortSwIXt2InQueuesH24PerformanceEntry ::=
   SEQUENCE
      {
      pr1646v2EthPortSwIXt2InQueuesH24PerformanceGlobalIx
         GlobalIndex,
      pr1646v2EthPortSwIXt2InQueuesH24PerformanceTableIx
         TableIndex,
      pr1646v2EthPortSwIXt2InQueuesH24PerformanceSysUpTime
         TimeTicks,
      pr1646v2EthPortSwIXt2InQueuesH24PerformanceTotPkts
         Counter64,
      pr1646v2EthPortSwIXt2InQueuesH24PerformanceDirTxPkts
         Counter64,
      pr1646v2EthPortSwIXt2InQueuesH24PerformanceQdPkts
         Counter64,
      pr1646v2EthPortSwIXt2InQueuesH24PerformanceDropPkts
         Counter64,
      pr1646v2EthPortSwIXt2InQueuesH24PerformanceRDropPkts
         Counter64,
      pr1646v2EthPortSwIXt2InQueuesH24PerformanceCirTxPkts
         Counter64,
      pr1646v2EthPortSwIXt2InQueuesH24PerformanceEirTxPkts
         Counter64,
      pr1646v2EthPortSwIXt2InQueuesH24PerformanceViolTxPkts
         Counter64,
      pr1646v2EthPortSwIXt2InQueuesH24PerformanceTotOcts
         Counter64,
      pr1646v2EthPortSwIXt2InQueuesH24PerformanceDirTxOcts
         Counter64,
      pr1646v2EthPortSwIXt2InQueuesH24PerformanceQdOcts
         Counter64,
      pr1646v2EthPortSwIXt2InQueuesH24PerformanceDropOcts
         Counter64,
      pr1646v2EthPortSwIXt2InQueuesH24PerformanceRDropOcts
         Counter64,
      pr1646v2EthPortSwIXt2InQueuesH24PerformanceCirTxOcts
         Counter64,
      pr1646v2EthPortSwIXt2InQueuesH24PerformanceEirTxOcts
         Counter64,
      pr1646v2EthPortSwIXt2InQueuesH24PerformanceViolTxOcts
         Counter64,
      pr1646v2EthPortSwIXt2InQueuesH24PerformanceBandwidth
         Integer32
      }

pr1646v2EthPortSwIXt2InQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InQueuesH24PerformanceEntry 10}

pr1646v2EthPortSwIXt2InQueuesH24PerformanceTableIx OBJECT-TYPE
   SYNTAX      TableIndex
   MAX-ACCESS  not-accessible
   STATUS      current
   DESCRIPTION
      ""
   ::= {pr1646v2EthPortSwIXt2InQueuesH24PerformanceEntry 11}

pr1646v2EthPortSwIXt2InQueuesH24PerformanceSysUpTime OBJECT-TYPE
   SYNTAX      TimeTicks
   MAX-ACCESS  read-only
   STATUS      current
   DESCRIPTION
      "Path: swPort.performance.ifInPriorityQueues.h24Performance.sysUpTime

       Time in centi-second."
   ::= {pr1646v2EthPortSwIXt2InQueuesH24PerformanceEntry 16777216}

pr1646v2EthPortSwIXt2InQueuesH24PerformanceTotPkts OBJECT-TYPE
   SYNTAX      Counter64
   MAX-ACCESS  read-only
   STATUS      current
   DESCRIPTION
      "Path: swPort.performance.ifInPriorityQueues.h24Performance.totalPkts

       64 bit unsigned wrappable counter."
   ::= {pr1646v2EthPortSwIXt2InQueuesH24PerformanceEntry 234881024}

pr1646v2EthPortSwIXt2InQueuesH24PerformanceDirTxPkts OBJECT-TYPE
   SYNTAX      Counter64
   MAX-ACCESS  read-only
   STATUS      current
   DESCRIPTION
      "Path: swPort.performance.ifInPriorityQueues.h24Performance.directTxPkts

       64 bit unsigned wrappable counter."
   ::= {pr1646v2EthPortSwIXt2InQueuesH24PerformanceEntry 33554432}

pr1646v2EthPortSwIXt2InQueuesH24PerformanceQdPkts OBJECT-TYPE
   SYNTAX      Counter64
   MAX-ACCESS  read-only
   STATUS      current
   DESCRIPTION
      "Path: swPort.performance.ifInPriorityQueues.h24Performance.queuedPkts

       64 bit unsigned wrappable counter."
   ::= {pr1646v2EthPortSwIXt2InQueuesH24PerformanceEntry 50331648}

pr1646v2EthPortSwIXt2InQueuesH24PerformanceDropPkts OBJECT-TYPE
   SYNTAX      Counter64
   MAX-ACCESS  read-only
   STATUS      current
   DESCRIPTION
      "Path: swPort.performance.ifInPriorityQueues.h24Performance.droppedPkts

       64 bit unsigned wrappable counter."
   ::= {pr1646v2EthPortSwIXt2InQueuesH24PerformanceEntry 67108864}

pr1646v2EthPortSwIXt2InQueuesH24PerformanceRDropPkts OBJECT-TYPE
   SYNTAX      Counter64
   MAX-ACCESS  read-only
   STATUS      current
   DESCRIPTION
      "Path: swPort.performance.ifInPriorityQueues.h24Performance.redDroppedPkts

       64 bit unsigned wrappable counter."
   ::= {pr1646v2EthPortSwIXt2InQueuesH24PerformanceEntry 201326592}

pr1646v2EthPortSwIXt2InQueuesH24PerformanceCirTxPkts OBJECT-TYPE
   SYNTAX      Counter64
   MAX-ACCESS  read-only
   STATUS      current
   DESCRIPTION
      "Path: swPort.performance.ifInPriorityQueues.h24Performance.cirTxPkts

       64 bit unsigned wrappable counter."
   ::= {pr1646v2EthPortSwIXt2InQueuesH24PerformanceEntry 83886080}

pr1646v2EthPortSwIXt2InQueuesH24PerformanceEirTxPkts OBJECT-TYPE
   SYNTAX      Counter64
   MAX-ACCESS  read-only
   STATUS      current
   DESCRIPTION
      "Path: swPort.performance.ifInPriorityQueues.h24Performance.eirTxPkts

       64 bit unsigned wrappable counter."
   ::= {pr1646v2EthPortSwIXt2InQueuesH24PerformanceEntry 100663296}

pr1646v2EthPortSwIXt2InQueuesH24PerformanceViolTxPkts OBJECT-TYPE
   SYNTAX      Counter64
   MAX-ACCESS  read-only
   STATUS      current
   DESCRIPTION
      "Path: swPort.performance.ifInPriorityQueues.h24Performance.violateTxPkts

       64 bit unsigned wrappable counter."
   ::= {pr1646v2EthPortSwIXt2InQueuesH24PerformanceEntry 301989888}

pr1646v2EthPortSwIXt2InQueuesH24PerformanceTotOcts OBJECT-TYPE
   SYNTAX      Counter64
   MAX-ACCESS  read-only
   STATUS      current
   DESCRIPTION
      "Path: swPort.performance.ifInPriorityQueues.h24Performance.totalOctets

       64 bit unsigned wrappable counter."
   ::= {pr1646v2EthPortSwIXt2InQueuesH24PerformanceEntry 251658240}

pr1646v2EthPortSwIXt2InQueuesH24PerformanceDirTxOcts OBJECT-TYPE
   SYNTAX      Counter64
   MAX-ACCESS  read-only
   STATUS      current
   DESCRIPTION
      "Path: swPort.performance.ifInPriorityQueues.h24Performance.directTxOctets

       64 bit unsigned wrappable counter."
   ::= {pr1646v2EthPortSwIXt2InQueuesH24PerformanceEntry 117440512}

pr1646v2EthPortSwIXt2InQueuesH24PerformanceQdOcts OBJECT-TYPE
   SYNTAX      Counter64
   MAX-ACCESS  read-only
   STATUS      current
   DESCRIPTION
      "Path: swPort.performance.ifInPriorityQueues.h24Performance.queuedOctets

       64 bit unsigned wrappable counter."
   ::= {pr1646v2EthPortSwIXt2InQueuesH24PerformanceEntry 134217728}

pr1646v2EthPortSwIXt2InQueuesH24PerformanceDropOcts OBJECT-TYPE
   SYNTAX      Counter64
   MAX-ACCESS  read-only
   STATUS      current
   DESCRIPTION
      "Path: swPort.performance.ifInPriorityQueues.h24Performance.droppedOctets

       64 bit unsigned wrappable counter."
   ::= {pr1646v2EthPortSwIXt2InQueuesH24PerformanceEntry 150994944}

pr1646v2EthPortSwIXt2InQueuesH24PerformanceRDropOcts OBJECT-TYPE
   SYNTAX      Counter64
   MAX-ACCESS  read-only
   STATUS      current
   DESCRIPTION
      "Path: swPort.performance.ifInPriorityQueues.h24Performance.redDroppedOctets

       64 bit unsigned wrappable counter."
   ::= {pr1646v2EthPortSwIXt2InQueuesH24PerformanceEntry 218103808}

pr1646v2EthPortSwIXt2InQueuesH24PerformanceCirTxOcts OBJECT-TYPE
   SYNTAX      Counter64
   MAX-ACCESS  read-only
   STATUS      current
   DESCRIPTION
      "Path: swPort.performance.ifInPriorityQueues.h24Performance.cirTxOctets

       64 bit unsigned wrappable counter."
   ::= {pr1646v2EthPortSwIXt2InQueuesH24PerformanceEntry 167772160}

pr1646v2EthPortSwIXt2InQueuesH24PerformanceEirTxOcts OBJECT-TYPE
   SYNTAX      Counter64
   MAX-ACCESS  read-only
   STATUS      current
   DESCRIPTION
      "Path: swPort.performance.ifInPriorityQueues.h24Performance.eirTxOctets

       64 bit unsigned wrappable counter."
   ::= {pr1646v2EthPortSwIXt2InQueuesH24PerformanceEntry 184549376}

pr1646v2EthPortSwIXt2InQueuesH24PerformanceViolTxOcts OBJECT-TYPE
   SYNTAX      Counter64
   MAX-ACCESS  read-only
   STATUS      current
   DESCRIPTION
      "Path: swPort.performance.ifInPriorityQueues.h24Performance.violateTxOctets

       64 bit unsigned wrappable counter."
   ::= {pr1646v2EthPortSwIXt2InQueuesH24PerformanceEntry 318767104}

pr1646v2EthPortSwIXt2InQueuesH24PerformanceBandwidth OBJECT-TYPE
   SYNTAX      Integer32
   MAX-ACCESS  read-only
   STATUS      current
   DESCRIPTION
      "Path: swPort.performance.ifInPriorityQueues.h24Performance.bandwidth

       unit name = bps
       formula = 8 * ; 8 /"
   ::= {pr1646v2EthPortSwIXt2InQueuesH24PerformanceEntry 268435456}

pr1646v2EthPortSwIXt2InQueuesD7Performance OBJECT-TYPE
   SYNTAX      SEQUENCE OF Pr1646v2EthPortSwIXt2InQueuesD7PerformanceEntry
   MAX-ACCESS  not-accessible
   STATUS      current
   DESCRIPTION
      ""
   ::= {pr1646v2EthPortSwIXt2InQueues 117440512}

pr1646v2EthPortSwIXt2InQueuesD7PerformanceEntry OBJECT-TYPE
   SYNTAX      Pr1646v2EthPortSwIXt2InQueuesD7PerformanceEntry
   MAX-ACCESS  not-accessible
   STATUS      current
   DESCRIPTION
      ""
   INDEX      { pr1646v2EthPortSwIXt2InQueuesD7PerformanceGlobalIx,
                pr1646v2EthPortSwIXt2InQueuesTableIx,
                pr1646v2EthPortSwIXt2InQueuesD7PerformanceTableIx }
   ::= {pr1646v2EthPortSwIXt2InQueuesD7Performance 1}

Pr1646v2EthPortSwIXt2InQueuesD7PerformanceEntry ::=
   SEQUENCE
      {
      pr1646v2EthPortSwIXt2InQueuesD7PerformanceGlobalIx
         GlobalIndex,
      pr1646v2EthPortSwIXt2InQueuesD7PerformanceTableIx
         TableIndex,
      pr1646v2EthPortSwIXt2InQueuesD7PerformanceSysUpTime
         TimeTicks,
      pr1646v2EthPortSwIXt2InQueuesD7PerformanceTotPkts
         Counter64,
      pr1646v2EthPortSwIXt2InQueuesD7PerformanceDirTxPkts
         Counter64,
      pr1646v2EthPortSwIXt2InQueuesD7PerformanceQdPkts
         Counter64,
      pr1646v2EthPortSwIXt2InQueuesD7PerformanceDropPkts
         Counter64,
      pr1646v2EthPortSwIXt2InQueuesD7PerformanceRDropPkts
         Counter64,
      pr1646v2EthPortSwIXt2InQueuesD7PerformanceCirTxPkts
         Counter64,
      pr1646v2EthPortSwIXt2InQueuesD7PerformanceEirTxPkts
         Counter64,
      pr1646v2EthPortSwIXt2InQueuesD7PerformanceViolTxPkts
         Counter64,
      pr1646v2EthPortSwIXt2InQueuesD7PerformanceTotOcts
         Counter64,
      pr1646v2EthPortSwIXt2InQueuesD7PerformanceDirTxOcts
         Counter64,
      pr1646v2EthPortSwIXt2InQueuesD7PerformanceQdOcts
         Counter64,
      pr1646v2EthPortSwIXt2InQueuesD7PerformanceDropOcts
         Counter64,
      pr1646v2EthPortSwIXt2InQueuesD7PerformanceRDropOcts
         Counter64,
      pr1646v2EthPortSwIXt2InQueuesD7PerformanceCirTxOcts
         Counter64,
      pr1646v2EthPortSwIXt2InQueuesD7PerformanceEirTxOcts
         Counter64,
      pr1646v2EthPortSwIXt2InQueuesD7PerformanceViolTxOcts
         Counter64,
      pr1646v2EthPortSwIXt2InQueuesD7PerformanceBandwidth
         Integer32
      }

pr1646v2EthPortSwIXt2InQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InQueuesD7PerformanceEntry 10}

pr1646v2EthPortSwIXt2InQueuesD7PerformanceTableIx OBJECT-TYPE
   SYNTAX      TableIndex
   MAX-ACCESS  not-accessible
   STATUS      current
   DESCRIPTION
      ""
   ::= {pr1646v2EthPortSwIXt2InQueuesD7PerformanceEntry 11}

pr1646v2EthPortSwIXt2InQueuesD7PerformanceSysUpTime OBJECT-TYPE
   SYNTAX      TimeTicks
   MAX-ACCESS  read-only
   STATUS      current
   DESCRIPTION
      "Path: swPort.performance.ifInPriorityQueues.d7Performance.sysUpTime

       Time in centi-second."
   ::= {pr1646v2EthPortSwIXt2InQueuesD7PerformanceEntry 16777216}

pr1646v2EthPortSwIXt2InQueuesD7PerformanceTotPkts OBJECT-TYPE
   SYNTAX      Counter64
   MAX-ACCESS  read-only
   STATUS      current
   DESCRIPTION
      "Path: swPort.performance.ifInPriorityQueues.d7Performance.totalPkts

       64 bit unsigned wrappable counter."
   ::= {pr1646v2EthPortSwIXt2InQueuesD7PerformanceEntry 234881024}

pr1646v2EthPortSwIXt2InQueuesD7PerformanceDirTxPkts OBJECT-TYPE
   SYNTAX      Counter64
   MAX-ACCESS  read-only
   STATUS      current
   DESCRIPTION
      "Path: swPort.performance.ifInPriorityQueues.d7Performance.directTxPkts

       64 bit unsigned wrappable counter."
   ::= {pr1646v2EthPortSwIXt2InQueuesD7PerformanceEntry 33554432}

pr1646v2EthPortSwIXt2InQueuesD7PerformanceQdPkts OBJECT-TYPE
   SYNTAX      Counter64
   MAX-ACCESS  read-only
   STATUS      current
   DESCRIPTION
      "Path: swPort.performance.ifInPriorityQueues.d7Performance.queuedPkts

       64 bit unsigned wrappable counter."
   ::= {pr1646v2EthPortSwIXt2InQueuesD7PerformanceEntry 50331648}

pr1646v2EthPortSwIXt2InQueuesD7PerformanceDropPkts OBJECT-TYPE
   SYNTAX      Counter64
   MAX-ACCESS  read-only
   STATUS      current
   DESCRIPTION
      "Path: swPort.performance.ifInPriorityQueues.d7Performance.droppedPkts

       64 bit unsigned wrappable counter."
   ::= {pr1646v2EthPortSwIXt2InQueuesD7PerformanceEntry 67108864}

pr1646v2EthPortSwIXt2InQueuesD7PerformanceRDropPkts OBJECT-TYPE
   SYNTAX      Counter64
   MAX-ACCESS  read-only
   STATUS      current
   DESCRIPTION
      "Path: swPort.performance.ifInPriorityQueues.d7Performance.redDroppedPkts

       64 bit unsigned wrappable counter."
   ::= {pr1646v2EthPortSwIXt2InQueuesD7PerformanceEntry 201326592}

pr1646v2EthPortSwIXt2InQueuesD7PerformanceCirTxPkts OBJECT-TYPE
   SYNTAX      Counter64
   MAX-ACCESS  read-only
   STATUS      current
   DESCRIPTION
      "Path: swPort.performance.ifInPriorityQueues.d7Performance.cirTxPkts

       64 bit unsigned wrappable counter."
   ::= {pr1646v2EthPortSwIXt2InQueuesD7PerformanceEntry 83886080}

pr1646v2EthPortSwIXt2InQueuesD7PerformanceEirTxPkts OBJECT-TYPE
   SYNTAX      Counter64
   MAX-ACCESS  read-only
   STATUS      current
   DESCRIPTION
      "Path: swPort.performance.ifInPriorityQueues.d7Performance.eirTxPkts

       64 bit unsigned wrappable counter."
   ::= {pr1646v2EthPortSwIXt2InQueuesD7PerformanceEntry 100663296}

pr1646v2EthPortSwIXt2InQueuesD7PerformanceViolTxPkts OBJECT-TYPE
   SYNTAX      Counter64
   MAX-ACCESS  read-only
   STATUS      current
   DESCRIPTION
      "Path: swPort.performance.ifInPriorityQueues.d7Performance.violateTxPkts

       64 bit unsigned wrappable counter."
   ::= {pr1646v2EthPortSwIXt2InQueuesD7PerformanceEntry 301989888}

pr1646v2EthPortSwIXt2InQueuesD7PerformanceTotOcts OBJECT-TYPE
   SYNTAX      Counter64
   MAX-ACCESS  read-only
   STATUS      current
   DESCRIPTION
      "Path: swPort.performance.ifInPriorityQueues.d7Performance.totalOctets

       64 bit unsigned wrappable counter."
   ::= {pr1646v2EthPortSwIXt2InQueuesD7PerformanceEntry 251658240}

pr1646v2EthPortSwIXt2InQueuesD7PerformanceDirTxOcts OBJECT-TYPE
   SYNTAX      Counter64
   MAX-ACCESS  read-only
   STATUS      current
   DESCRIPTION
      "Path: swPort.performance.ifInPriorityQueues.d7Performance.directTxOctets

       64 bit unsigned wrappable counter."
   ::= {pr1646v2EthPortSwIXt2InQueuesD7PerformanceEntry 117440512}

pr1646v2EthPortSwIXt2InQueuesD7PerformanceQdOcts OBJECT-TYPE
   SYNTAX      Counter64
   MAX-ACCESS  read-only
   STATUS      current
   DESCRIPTION
      "Path: swPort.performance.ifInPriorityQueues.d7Performance.queuedOctets

       64 bit unsigned wrappable counter."
   ::= {pr1646v2EthPortSwIXt2InQueuesD7PerformanceEntry 134217728}

pr1646v2EthPortSwIXt2InQueuesD7PerformanceDropOcts OBJECT-TYPE
   SYNTAX      Counter64
   MAX-ACCESS  read-only
   STATUS      current
   DESCRIPTION
      "Path: swPort.performance.ifInPriorityQueues.d7Performance.droppedOctets

       64 bit unsigned wrappable counter."
   ::= {pr1646v2EthPortSwIXt2InQueuesD7PerformanceEntry 150994944}

pr1646v2EthPortSwIXt2InQueuesD7PerformanceRDropOcts OBJECT-TYPE
   SYNTAX      Counter64
   MAX-ACCESS  read-only
   STATUS      current
   DESCRIPTION
      "Path: swPort.performance.ifInPriorityQueues.d7Performance.redDroppedOctets

       64 bit unsigned wrappable counter."
   ::= {pr1646v2EthPortSwIXt2InQueuesD7PerformanceEntry 218103808}

pr1646v2EthPortSwIXt2InQueuesD7PerformanceCirTxOcts OBJECT-TYPE
   SYNTAX      Counter64
   MAX-ACCESS  read-only
   STATUS      current
   DESCRIPTION
      "Path: swPort.performance.ifInPriorityQueues.d7Performance.cirTxOctets

       64 bit unsigned wrappable counter."
   ::= {pr1646v2EthPortSwIXt2InQueuesD7PerformanceEntry 167772160}

pr1646v2EthPortSwIXt2InQueuesD7PerformanceEirTxOcts OBJECT-TYPE
   SYNTAX      Counter64
   MAX-ACCESS  read-only
   STATUS      current
   DESCRIPTION
      "Path: swPort.performance.ifInPriorityQueues.d7Performance.eirTxOctets

       64 bit unsigned wrappable counter."
   ::= {pr1646v2EthPortSwIXt2InQueuesD7PerformanceEntry 184549376}

pr1646v2EthPortSwIXt2InQueuesD7PerformanceViolTxOcts OBJECT-TYPE
   SYNTAX      Counter64
   MAX-ACCESS  read-only
   STATUS      current
   DESCRIPTION
      "Path: swPort.performance.ifInPriorityQueues.d7Performance.violateTxOctets

       64 bit unsigned wrappable counter."
   ::= {pr1646v2EthPortSwIXt2InQueuesD7PerformanceEntry 318767104}

pr1646v2EthPortSwIXt2InQueuesD7PerformanceBandwidth OBJECT-TYPE
   SYNTAX      Integer32
   MAX-ACCESS  read-only
   STATUS      current
   DESCRIPTION
      "Path: swPort.performance.ifInPriorityQueues.d7Performance.bandwidth

       unit name = bps
       formula = 8 * ; 8 /"
   ::= {pr1646v2EthPortSwIXt2InQueuesD7PerformanceEntry 268435456}


pr1646v2EthPortSwIXt2InBandwidth OBJECT IDENTIFIER ::= {pr1646v2EthPortSwIXt2 181}

pr1646v2EthPortSwIXt2InBandwidthSSCTable OBJECT-TYPE
   SYNTAX      SEQUENCE OF Pr1646v2EthPortSwIXt2InBandwidthEntry
   MAX-ACCESS  not-accessible
   STATUS      current
   DESCRIPTION
      "bandwidth"
   ::= {pr1646v2EthPortSwIXt2InBandwidth 1}

pr1646v2EthPortSwIXt2InBandwidthEntry OBJECT-TYPE
   SYNTAX      Pr1646v2EthPortSwIXt2InBandwidthEntry
   MAX-ACCESS  not-accessible
   STATUS      current
   DESCRIPTION
      ""
   INDEX      { pr1646v2EthPortSwIXt2InBandwidthGlobalIx }
   ::= {pr1646v2EthPortSwIXt2InBandwidthSSCTable 1}

Pr1646v2EthPortSwIXt2InBandwidthEntry ::=
   SEQUENCE
      {
      pr1646v2EthPortSwIXt2InBandwidthGlobalIx
         GlobalIndex,
      pr1646v2EthPortSwIXt2InBandwidth15sec
         Integer32,
      pr1646v2EthPortSwIXt2InBandwidth30sec
         Integer32,
      pr1646v2EthPortSwIXt2InBandwidth1min
         Integer32,
      pr1646v2EthPortSwIXt2InBandwidth2min
         Integer32,
      pr1646v2EthPortSwIXt2InBandwidth5min
         Integer32
      }

pr1646v2EthPortSwIXt2InBandwidthGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InBandwidthEntry 10}

pr1646v2EthPortSwIXt2InBandwidth15sec OBJECT-TYPE
   SYNTAX      Integer32
   MAX-ACCESS  read-only
   STATUS      current
   DESCRIPTION
      "Path: swPort.performance.ifInBandwidth.15sec

       unit name = bps
       formula = 8 * ; 8 /"
   ::= {pr1646v2EthPortSwIXt2InBandwidthEntry 83886080}

pr1646v2EthPortSwIXt2InBandwidth30sec OBJECT-TYPE
   SYNTAX      Integer32
   MAX-ACCESS  read-only
   STATUS      current
   DESCRIPTION
      "Path: swPort.performance.ifInBandwidth.30sec

       unit name = bps
       formula = 8 * ; 8 /"
   ::= {pr1646v2EthPortSwIXt2InBandwidthEntry 167772160}

pr1646v2EthPortSwIXt2InBandwidth1min OBJECT-TYPE
   SYNTAX      Integer32
   MAX-ACCESS  read-only
   STATUS      current
   DESCRIPTION
      "Path: swPort.performance.ifInBandwidth.1min

       unit name = bps
       formula = 8 * ; 8 /"
   ::= {pr1646v2EthPortSwIXt2InBandwidthEntry 335544320}

pr1646v2EthPortSwIXt2InBandwidth2min OBJECT-TYPE
   SYNTAX      Integer32
   MAX-ACCESS  read-only
   STATUS      current
   DESCRIPTION
      "Path: swPort.performance.ifInBandwidth.2min

       unit name = bps
       formula = 8 * ; 8 /"
   ::= {pr1646v2EthPortSwIXt2InBandwidthEntry 671088640}

pr1646v2EthPortSwIXt2InBandwidth5min OBJECT-TYPE
   SYNTAX      Integer32
   MAX-ACCESS  read-only
   STATUS      current
   DESCRIPTION
      "Path: swPort.performance.ifInBandwidth.5min

       unit name = bps
       formula = 8 * ; 8 /"
   ::= {pr1646v2EthPortSwIXt2InBandwidthEntry 1677721600}


pr1646v2EthPortSwIXt2OutOctets OBJECT IDENTIFIER ::= {pr1646v2EthPortSwIXt2 115}

pr1646v2EthPortSwIXt2OutOctetsTable OBJECT-TYPE
   SYNTAX      SEQUENCE OF Pr1646v2EthPortSwIXt2OutOctetsEntry
   MAX-ACCESS  not-accessible
   STATUS      current
   DESCRIPTION
      "ifOutOctets"
   ::= {pr1646v2EthPortSwIXt2OutOctets 1}

pr1646v2EthPortSwIXt2OutOctetsEntry OBJECT-TYPE
   SYNTAX      Pr1646v2EthPortSwIXt2OutOctetsEntry
   MAX-ACCESS  not-accessible
   STATUS      current
   DESCRIPTION
      ""
   INDEX      { pr1646v2EthPortSwIXt2OutOctetsGlobalIx }
   ::= {pr1646v2EthPortSwIXt2OutOctetsTable 1}

Pr1646v2EthPortSwIXt2OutOctetsEntry ::=
   SEQUENCE
      {
      pr1646v2EthPortSwIXt2OutOctetsGlobalIx
         GlobalIndex,
      pr1646v2EthPortSwIXt2OutOctetsValue
         Counter64
      }

pr1646v2EthPortSwIXt2OutOctetsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutOctetsEntry 10}

pr1646v2EthPortSwIXt2OutOctetsValue OBJECT-TYPE
   SYNTAX      Counter64
   MAX-ACCESS  read-only
   STATUS      current
   DESCRIPTION
      "Path: swPort.performance.ifOutOctets

       64 bit unsigned wrappable counter."
   ::= {pr1646v2EthPortSwIXt2OutOctetsEntry 2147483648}


pr1646v2EthPortSwIXt2OutUcastPkts OBJECT IDENTIFIER ::= {pr1646v2EthPortSwIXt2 116}

pr1646v2EthPortSwIXt2OutUcastPktsTable OBJECT-TYPE
   SYNTAX      SEQUENCE OF Pr1646v2EthPortSwIXt2OutUcastPktsEntry
   MAX-ACCESS  not-accessible
   STATUS      current
   DESCRIPTION
      "ifOutUcastPkts"
   ::= {pr1646v2EthPortSwIXt2OutUcastPkts 1}

pr1646v2EthPortSwIXt2OutUcastPktsEntry OBJECT-TYPE
   SYNTAX      Pr1646v2EthPortSwIXt2OutUcastPktsEntry
   MAX-ACCESS  not-accessible
   STATUS      current
   DESCRIPTION
      ""
   INDEX      { pr1646v2EthPortSwIXt2OutUcastPktsGlobalIx }
   ::= {pr1646v2EthPortSwIXt2OutUcastPktsTable 1}

Pr1646v2EthPortSwIXt2OutUcastPktsEntry ::=
   SEQUENCE
      {
      pr1646v2EthPortSwIXt2OutUcastPktsGlobalIx
         GlobalIndex,
      pr1646v2EthPortSwIXt2OutUcastPktsValue
         Counter64
      }

pr1646v2EthPortSwIXt2OutUcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutUcastPktsEntry 10}

pr1646v2EthPortSwIXt2OutUcastPktsValue OBJECT-TYPE
   SYNTAX      Counter64
   MAX-ACCESS  read-only
   STATUS      current
   DESCRIPTION
      "Path: swPort.performance.ifOutUcastPkts

       64 bit unsigned wrappable counter."
   ::= {pr1646v2EthPortSwIXt2OutUcastPktsEntry 2147483648}


pr1646v2EthPortSwIXt2OutNUcastPkts OBJECT IDENTIFIER ::= {pr1646v2EthPortSwIXt2 117}

pr1646v2EthPortSwIXt2OutNUcastPktsTable OBJECT-TYPE
   SYNTAX      SEQUENCE OF Pr1646v2EthPortSwIXt2OutNUcastPktsEntry
   MAX-ACCESS  not-accessible
   STATUS      current
   DESCRIPTION
      "ifOutNUcastPkts"
   ::= {pr1646v2EthPortSwIXt2OutNUcastPkts 1}

pr1646v2EthPortSwIXt2OutNUcastPktsEntry OBJECT-TYPE
   SYNTAX      Pr1646v2EthPortSwIXt2OutNUcastPktsEntry
   MAX-ACCESS  not-accessible
   STATUS      current
   DESCRIPTION
      ""
   INDEX      { pr1646v2EthPortSwIXt2OutNUcastPktsGlobalIx }
   ::= {pr1646v2EthPortSwIXt2OutNUcastPktsTable 1}

Pr1646v2EthPortSwIXt2OutNUcastPktsEntry ::=
   SEQUENCE
      {
      pr1646v2EthPortSwIXt2OutNUcastPktsGlobalIx
         GlobalIndex,
      pr1646v2EthPortSwIXt2OutNUcastPktsValue
         Counter64
      }

pr1646v2EthPortSwIXt2OutNUcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutNUcastPktsEntry 10}

pr1646v2EthPortSwIXt2OutNUcastPktsValue OBJECT-TYPE
   SYNTAX      Counter64
   MAX-ACCESS  read-only
   STATUS      current
   DESCRIPTION
      "Path: swPort.performance.ifOutNUcastPkts

       64 bit unsigned wrappable counter."
   ::= {pr1646v2EthPortSwIXt2OutNUcastPktsEntry 2147483648}


pr1646v2EthPortSwIXt2OutBcastPkts OBJECT IDENTIFIER ::= {pr1646v2EthPortSwIXt2 217}

pr1646v2EthPortSwIXt2OutBcastPktsTable OBJECT-TYPE
   SYNTAX      SEQUENCE OF Pr1646v2EthPortSwIXt2OutBcastPktsEntry
   MAX-ACCESS  not-accessible
   STATUS      current
   DESCRIPTION
      "ifOutBcastPkts"
   ::= {pr1646v2EthPortSwIXt2OutBcastPkts 1}

pr1646v2EthPortSwIXt2OutBcastPktsEntry OBJECT-TYPE
   SYNTAX      Pr1646v2EthPortSwIXt2OutBcastPktsEntry
   MAX-ACCESS  not-accessible
   STATUS      current
   DESCRIPTION
      ""
   INDEX      { pr1646v2EthPortSwIXt2OutBcastPktsGlobalIx }
   ::= {pr1646v2EthPortSwIXt2OutBcastPktsTable 1}

Pr1646v2EthPortSwIXt2OutBcastPktsEntry ::=
   SEQUENCE
      {
      pr1646v2EthPortSwIXt2OutBcastPktsGlobalIx
         GlobalIndex,
      pr1646v2EthPortSwIXt2OutBcastPktsValue
         Counter64
      }

pr1646v2EthPortSwIXt2OutBcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutBcastPktsEntry 10}

pr1646v2EthPortSwIXt2OutBcastPktsValue OBJECT-TYPE
   SYNTAX      Counter64
   MAX-ACCESS  read-only
   STATUS      current
   DESCRIPTION
      "Path: swPort.performance.ifOutBcastPkts

       64 bit unsigned wrappable counter."
   ::= {pr1646v2EthPortSwIXt2OutBcastPktsEntry 2147483648}


pr1646v2EthPortSwIXt2OutMcastPkts OBJECT IDENTIFIER ::= {pr1646v2EthPortSwIXt2 227}

pr1646v2EthPortSwIXt2OutMcastPktsTable OBJECT-TYPE
   SYNTAX      SEQUENCE OF Pr1646v2EthPortSwIXt2OutMcastPktsEntry
   MAX-ACCESS  not-accessible
   STATUS      current
   DESCRIPTION
      "ifOutMcastPkts"
   ::= {pr1646v2EthPortSwIXt2OutMcastPkts 1}

pr1646v2EthPortSwIXt2OutMcastPktsEntry OBJECT-TYPE
   SYNTAX      Pr1646v2EthPortSwIXt2OutMcastPktsEntry
   MAX-ACCESS  not-accessible
   STATUS      current
   DESCRIPTION
      ""
   INDEX      { pr1646v2EthPortSwIXt2OutMcastPktsGlobalIx }
   ::= {pr1646v2EthPortSwIXt2OutMcastPktsTable 1}

Pr1646v2EthPortSwIXt2OutMcastPktsEntry ::=
   SEQUENCE
      {
      pr1646v2EthPortSwIXt2OutMcastPktsGlobalIx
         GlobalIndex,
      pr1646v2EthPortSwIXt2OutMcastPktsValue
         Counter64
      }

pr1646v2EthPortSwIXt2OutMcastPktsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutMcastPktsEntry 10}

pr1646v2EthPortSwIXt2OutMcastPktsValue OBJECT-TYPE
   SYNTAX      Counter64
   MAX-ACCESS  read-only
   STATUS      current
   DESCRIPTION
      "Path: swPort.performance.ifOutMcastPkts

       64 bit unsigned wrappable counter."
   ::= {pr1646v2EthPortSwIXt2OutMcastPktsEntry 2147483648}


pr1646v2EthPortSwIXt2OutDiscards OBJECT IDENTIFIER ::= {pr1646v2EthPortSwIXt2 118}

pr1646v2EthPortSwIXt2OutDiscardsTable OBJECT-TYPE
   SYNTAX      SEQUENCE OF Pr1646v2EthPortSwIXt2OutDiscardsEntry
   MAX-ACCESS  not-accessible
   STATUS      current
   DESCRIPTION
      "ifOutDiscards"
   ::= {pr1646v2EthPortSwIXt2OutDiscards 1}

pr1646v2EthPortSwIXt2OutDiscardsEntry OBJECT-TYPE
   SYNTAX      Pr1646v2EthPortSwIXt2OutDiscardsEntry
   MAX-ACCESS  not-accessible
   STATUS      current
   DESCRIPTION
      ""
   INDEX      { pr1646v2EthPortSwIXt2OutDiscardsGlobalIx }
   ::= {pr1646v2EthPortSwIXt2OutDiscardsTable 1}

Pr1646v2EthPortSwIXt2OutDiscardsEntry ::=
   SEQUENCE
      {
      pr1646v2EthPortSwIXt2OutDiscardsGlobalIx
         GlobalIndex,
      pr1646v2EthPortSwIXt2OutDiscardsValue
         Counter64
      }

pr1646v2EthPortSwIXt2OutDiscardsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutDiscardsEntry 10}

pr1646v2EthPortSwIXt2OutDiscardsValue OBJECT-TYPE
   SYNTAX      Counter64
   MAX-ACCESS  read-only
   STATUS      current
   DESCRIPTION
      "Path: swPort.performance.ifOutDiscards

       64 bit unsigned wrappable counter."
   ::= {pr1646v2EthPortSwIXt2OutDiscardsEntry 2147483648}


pr1646v2EthPortSwIXt2OutErrors OBJECT IDENTIFIER ::= {pr1646v2EthPortSwIXt2 119}

pr1646v2EthPortSwIXt2OutErrorsTable OBJECT-TYPE
   SYNTAX      SEQUENCE OF Pr1646v2EthPortSwIXt2OutErrorsEntry
   MAX-ACCESS  not-accessible
   STATUS      current
   DESCRIPTION
      "ifOutErrors"
   ::= {pr1646v2EthPortSwIXt2OutErrors 1}

pr1646v2EthPortSwIXt2OutErrorsEntry OBJECT-TYPE
   SYNTAX      Pr1646v2EthPortSwIXt2OutErrorsEntry
   MAX-ACCESS  not-accessible
   STATUS      current
   DESCRIPTION
      ""
   INDEX      { pr1646v2EthPortSwIXt2OutErrorsGlobalIx }
   ::= {pr1646v2EthPortSwIXt2OutErrorsTable 1}

Pr1646v2EthPortSwIXt2OutErrorsEntry ::=
   SEQUENCE
      {
      pr1646v2EthPortSwIXt2OutErrorsGlobalIx
         GlobalIndex,
      pr1646v2EthPortSwIXt2OutErrorsValue
         Counter64
      }

pr1646v2EthPortSwIXt2OutErrorsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutErrorsEntry 10}

pr1646v2EthPortSwIXt2OutErrorsValue OBJECT-TYPE
   SYNTAX      Counter64
   MAX-ACCESS  read-only
   STATUS      current
   DESCRIPTION
      "Path: swPort.performance.ifOutErrors

       64 bit unsigned wrappable counter."
   ::= {pr1646v2EthPortSwIXt2OutErrorsEntry 2147483648}


pr1646v2EthPortSwIXt2OutQLen OBJECT IDENTIFIER ::= {pr1646v2EthPortSwIXt2 120}

pr1646v2EthPortSwIXt2OutQLenTable OBJECT-TYPE
   SYNTAX      SEQUENCE OF Pr1646v2EthPortSwIXt2OutQLenEntry
   MAX-ACCESS  not-accessible
   STATUS      current
   DESCRIPTION
      "ifOutQLen"
   ::= {pr1646v2EthPortSwIXt2OutQLen 1}

pr1646v2EthPortSwIXt2OutQLenEntry OBJECT-TYPE
   SYNTAX      Pr1646v2EthPortSwIXt2OutQLenEntry
   MAX-ACCESS  not-accessible
   STATUS      current
   DESCRIPTION
      ""
   INDEX      { pr1646v2EthPortSwIXt2OutQLenGlobalIx }
   ::= {pr1646v2EthPortSwIXt2OutQLenTable 1}

Pr1646v2EthPortSwIXt2OutQLenEntry ::=
   SEQUENCE
      {
      pr1646v2EthPortSwIXt2OutQLenGlobalIx
         GlobalIndex,
      pr1646v2EthPortSwIXt2OutQLenValue
         Gauge32
      }

pr1646v2EthPortSwIXt2OutQLenGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutQLenEntry 10}

pr1646v2EthPortSwIXt2OutQLenValue OBJECT-TYPE
   SYNTAX      Gauge32
   MAX-ACCESS  read-only
   STATUS      current
   DESCRIPTION
      "Path: swPort.performance.ifOutQLen

       32 bit unsigned gauge value."
   ::= {pr1646v2EthPortSwIXt2OutQLenEntry 2147483648}


pr1646v2EthPortSwIXt2OutDropEx OBJECT IDENTIFIER ::= {pr1646v2EthPortSwIXt2 127}

pr1646v2EthPortSwIXt2OutDropExTable OBJECT-TYPE
   SYNTAX      SEQUENCE OF Pr1646v2EthPortSwIXt2OutDropExEntry
   MAX-ACCESS  not-accessible
   STATUS      current
   DESCRIPTION
      "ifOutDiscards"
   ::= {pr1646v2EthPortSwIXt2OutDropEx 1}

pr1646v2EthPortSwIXt2OutDropExEntry OBJECT-TYPE
   SYNTAX      Pr1646v2EthPortSwIXt2OutDropExEntry
   MAX-ACCESS  not-accessible
   STATUS      current
   DESCRIPTION
      ""
   INDEX      { pr1646v2EthPortSwIXt2OutDropExGlobalIx }
   ::= {pr1646v2EthPortSwIXt2OutDropExTable 1}

Pr1646v2EthPortSwIXt2OutDropExEntry ::=
   SEQUENCE
      {
      pr1646v2EthPortSwIXt2OutDropExGlobalIx
         GlobalIndex,
      pr1646v2EthPortSwIXt2OutDropExValue
         Counter64
      }

pr1646v2EthPortSwIXt2OutDropExGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutDropExEntry 10}

pr1646v2EthPortSwIXt2OutDropExValue OBJECT-TYPE
   SYNTAX      Counter64
   MAX-ACCESS  read-only
   STATUS      current
   DESCRIPTION
      "Path: swPort.performance.ifOutDropLevelExceeded

       64 bit unsigned wrappable counter."
   ::= {pr1646v2EthPortSwIXt2OutDropExEntry 2147483648}


pr1646v2EthPortSwIXt2OutDropNoArp OBJECT IDENTIFIER ::= {pr1646v2EthPortSwIXt2 134}

pr1646v2EthPortSwIXt2OutDropNoArpTable OBJECT-TYPE
   SYNTAX      SEQUENCE OF Pr1646v2EthPortSwIXt2OutDropNoArpEntry
   MAX-ACCESS  not-accessible
   STATUS      current
   DESCRIPTION
      "ifOutDiscards"
   ::= {pr1646v2EthPortSwIXt2OutDropNoArp 1}

pr1646v2EthPortSwIXt2OutDropNoArpEntry OBJECT-TYPE
   SYNTAX      Pr1646v2EthPortSwIXt2OutDropNoArpEntry
   MAX-ACCESS  not-accessible
   STATUS      current
   DESCRIPTION
      ""
   INDEX      { pr1646v2EthPortSwIXt2OutDropNoArpGlobalIx }
   ::= {pr1646v2EthPortSwIXt2OutDropNoArpTable 1}

Pr1646v2EthPortSwIXt2OutDropNoArpEntry ::=
   SEQUENCE
      {
      pr1646v2EthPortSwIXt2OutDropNoArpGlobalIx
         GlobalIndex,
      pr1646v2EthPortSwIXt2OutDropNoArpValue
         Counter64
      }

pr1646v2EthPortSwIXt2OutDropNoArpGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutDropNoArpEntry 10}

pr1646v2EthPortSwIXt2OutDropNoArpValue OBJECT-TYPE
   SYNTAX      Counter64
   MAX-ACCESS  read-only
   STATUS      current
   DESCRIPTION
      "Path: swPort.performance.ifOutDiscardsNoArp

       64 bit unsigned wrappable counter."
   ::= {pr1646v2EthPortSwIXt2OutDropNoArpEntry 2147483648}


pr1646v2EthPortSwIXt2OutDropFilter OBJECT IDENTIFIER ::= {pr1646v2EthPortSwIXt2 138}

pr1646v2EthPortSwIXt2OutDropFilterTable OBJECT-TYPE
   SYNTAX      SEQUENCE OF Pr1646v2EthPortSwIXt2OutDropFilterEntry
   MAX-ACCESS  not-accessible
   STATUS      current
   DESCRIPTION
      "ifOutDiscards"
   ::= {pr1646v2EthPortSwIXt2OutDropFilter 1}

pr1646v2EthPortSwIXt2OutDropFilterEntry OBJECT-TYPE
   SYNTAX      Pr1646v2EthPortSwIXt2OutDropFilterEntry
   MAX-ACCESS  not-accessible
   STATUS      current
   DESCRIPTION
      ""
   INDEX      { pr1646v2EthPortSwIXt2OutDropFilterGlobalIx }
   ::= {pr1646v2EthPortSwIXt2OutDropFilterTable 1}

Pr1646v2EthPortSwIXt2OutDropFilterEntry ::=
   SEQUENCE
      {
      pr1646v2EthPortSwIXt2OutDropFilterGlobalIx
         GlobalIndex,
      pr1646v2EthPortSwIXt2OutDropFilterValue
         Counter64
      }

pr1646v2EthPortSwIXt2OutDropFilterGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutDropFilterEntry 10}

pr1646v2EthPortSwIXt2OutDropFilterValue OBJECT-TYPE
   SYNTAX      Counter64
   MAX-ACCESS  read-only
   STATUS      current
   DESCRIPTION
      "Path: swPort.performance.ifOutDiscardsFilter

       64 bit unsigned wrappable counter."
   ::= {pr1646v2EthPortSwIXt2OutDropFilterEntry 2147483648}


pr1646v2EthPortSwIXt2OutQueues OBJECT IDENTIFIER ::= {pr1646v2EthPortSwIXt2 129}

pr1646v2EthPortSwIXt2OutQueuesSSCTable OBJECT-TYPE
   SYNTAX      SEQUENCE OF Pr1646v2EthPortSwIXt2OutQueuesEntry
   MAX-ACCESS  not-accessible
   STATUS      current
   DESCRIPTION
      "Queue Lengths"
   ::= {pr1646v2EthPortSwIXt2OutQueues 1}

pr1646v2EthPortSwIXt2OutQueuesEntry OBJECT-TYPE
   SYNTAX      Pr1646v2EthPortSwIXt2OutQueuesEntry
   MAX-ACCESS  not-accessible
   STATUS      current
   DESCRIPTION
      ""
   INDEX      { pr1646v2EthPortSwIXt2OutQueuesGlobalIx,
                pr1646v2EthPortSwIXt2OutQueuesTableIx }
   ::= {pr1646v2EthPortSwIXt2OutQueuesSSCTable 1}

Pr1646v2EthPortSwIXt2OutQueuesEntry ::=
   SEQUENCE
      {
      pr1646v2EthPortSwIXt2OutQueuesGlobalIx
         GlobalIndex,
      pr1646v2EthPortSwIXt2OutQueuesTableIx
         TableIndex,
      pr1646v2EthPortSwIXt2OutQueuesName
         INTEGER,
      pr1646v2EthPortSwIXt2OutQueuesLength
         Integer32,
      pr1646v2EthPortSwIXt2OutQueuesOctetLength
         Integer32,
      pr1646v2EthPortSwIXt2OutQueuesRedLength
         Integer32,
      pr1646v2EthPortSwIXt2OutQueuesPacketsTotal
         Counter64,
      pr1646v2EthPortSwIXt2OutQueuesPacketsDirectTx
         Counter64,
      pr1646v2EthPortSwIXt2OutQueuesPacketsQueued
         Counter64,
      pr1646v2EthPortSwIXt2OutQueuesPacketsDropped
         Counter64,
      pr1646v2EthPortSwIXt2OutQueuesPacketsRedDropped
         Counter64,
      pr1646v2EthPortSwIXt2OutQueuesPacketsCirTx
         Counter64,
      pr1646v2EthPortSwIXt2OutQueuesPacketsEirTx
         Counter64,
      pr1646v2EthPortSwIXt2OutQueuesPacketsViolateTx
         Counter64,
      pr1646v2EthPortSwIXt2OutQueuesOctetsTotal
         Counter64,
      pr1646v2EthPortSwIXt2OutQueuesOctetsDirectTx
         Counter64,
      pr1646v2EthPortSwIXt2OutQueuesOctetsQueued
         Counter64,
      pr1646v2EthPortSwIXt2OutQueuesOctetsDropped
         Counter64,
      pr1646v2EthPortSwIXt2OutQueuesOctetsRedDropped
         Counter64,
      pr1646v2EthPortSwIXt2OutQueuesOctetsCirTx
         Counter64,
      pr1646v2EthPortSwIXt2OutQueuesOctetsEirTx
         Counter64,
      pr1646v2EthPortSwIXt2OutQueuesOctetsViolateTx
         Counter64,
      pr1646v2EthPortSwIXt2OutQueuesOctetsBandwidth15sec
         Integer32,
      pr1646v2EthPortSwIXt2OutQueuesOctetsBandwidth30sec
         Integer32,
      pr1646v2EthPortSwIXt2OutQueuesOctetsBandwidth1min
         Integer32,
      pr1646v2EthPortSwIXt2OutQueuesOctetsBandwidth2min
         Integer32,
      pr1646v2EthPortSwIXt2OutQueuesOctetsBandwidth5min
         Integer32
      }

pr1646v2EthPortSwIXt2OutQueuesGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutQueuesEntry 10}

pr1646v2EthPortSwIXt2OutQueuesTableIx OBJECT-TYPE
   SYNTAX      TableIndex
   MAX-ACCESS  not-accessible
   STATUS      current
   DESCRIPTION
      ""
   ::= {pr1646v2EthPortSwIXt2OutQueuesEntry 11}

pr1646v2EthPortSwIXt2OutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwIXt2OutQueuesEntry 16777216}

pr1646v2EthPortSwIXt2OutQueuesLength OBJECT-TYPE
   SYNTAX      Integer32
   MAX-ACCESS  read-only
   STATUS      current
   DESCRIPTION
      "Path: swPort.performance.ifOutPriorityQueues.length"
   ::= {pr1646v2EthPortSwIXt2OutQueuesEntry 33554432}

pr1646v2EthPortSwIXt2OutQueuesOctetLength OBJECT-TYPE
   SYNTAX      Integer32
   MAX-ACCESS  read-only
   STATUS      current
   DESCRIPTION
      "Path: swPort.performance.ifOutPriorityQueues.octetLength"
   ::= {pr1646v2EthPortSwIXt2OutQueuesEntry 150994944}

pr1646v2EthPortSwIXt2OutQueuesRedLength OBJECT-TYPE
   SYNTAX      Integer32
   MAX-ACCESS  read-only
   STATUS      current
   DESCRIPTION
      "Path: swPort.performance.ifOutPriorityQueues.redLength"
   ::= {pr1646v2EthPortSwIXt2OutQueuesEntry 134217728}

pr1646v2EthPortSwIXt2OutQueuesPacketsTotal OBJECT-TYPE
   SYNTAX      Counter64
   MAX-ACCESS  read-only
   STATUS      current
   DESCRIPTION
      "Path: swPort.performance.ifOutPriorityQueues.packets.total

       64 bit unsigned wrappable counter."
   ::= {pr1646v2EthPortSwIXt2OutQueuesEntry 50790400}

pr1646v2EthPortSwIXt2OutQueuesPacketsDirectTx OBJECT-TYPE
   SYNTAX      Counter64
   MAX-ACCESS  read-only
   STATUS      current
   DESCRIPTION
      "Path: swPort.performance.ifOutPriorityQueues.packets.directTx

       64 bit unsigned wrappable counter."
   ::= {pr1646v2EthPortSwIXt2OutQueuesEntry 50397184}

pr1646v2EthPortSwIXt2OutQueuesPacketsQueued OBJECT-TYPE
   SYNTAX      Counter64
   MAX-ACCESS  read-only
   STATUS      current
   DESCRIPTION
      "Path: swPort.performance.ifOutPriorityQueues.packets.queued

       64 bit unsigned wrappable counter."
   ::= {pr1646v2EthPortSwIXt2OutQueuesEntry 50462720}

pr1646v2EthPortSwIXt2OutQueuesPacketsDropped OBJECT-TYPE
   SYNTAX      Counter64
   MAX-ACCESS  read-only
   STATUS      current
   DESCRIPTION
      "Path: swPort.performance.ifOutPriorityQueues.packets.dropped

       64 bit unsigned wrappable counter."
   ::= {pr1646v2EthPortSwIXt2OutQueuesEntry 50528256}

pr1646v2EthPortSwIXt2OutQueuesPacketsRedDropped OBJECT-TYPE
   SYNTAX      Counter64
   MAX-ACCESS  read-only
   STATUS      current
   DESCRIPTION
      "Path: swPort.performance.ifOutPriorityQueues.packets.redDropped

       64 bit unsigned wrappable counter."
   ::= {pr1646v2EthPortSwIXt2OutQueuesEntry 50724864}

pr1646v2EthPortSwIXt2OutQueuesPacketsCirTx OBJECT-TYPE
   SYNTAX      Counter64
   MAX-ACCESS  read-only
   STATUS      current
   DESCRIPTION
      "Path: swPort.performance.ifOutPriorityQueues.packets.cirTx

       64 bit unsigned wrappable counter."
   ::= {pr1646v2EthPortSwIXt2OutQueuesEntry 50593792}

pr1646v2EthPortSwIXt2OutQueuesPacketsEirTx OBJECT-TYPE
   SYNTAX      Counter64
   MAX-ACCESS  read-only
   STATUS      current
   DESCRIPTION
      "Path: swPort.performance.ifOutPriorityQueues.packets.eirTx

       64 bit unsigned wrappable counter."
   ::= {pr1646v2EthPortSwIXt2OutQueuesEntry 50659328}

pr1646v2EthPortSwIXt2OutQueuesPacketsViolateTx OBJECT-TYPE
   SYNTAX      Counter64
   MAX-ACCESS  read-only
   STATUS      current
   DESCRIPTION
      "Path: swPort.performance.ifOutPriorityQueues.packets.violateTx

       64 bit unsigned wrappable counter."
   ::= {pr1646v2EthPortSwIXt2OutQueuesEntry 50855936}

pr1646v2EthPortSwIXt2OutQueuesOctetsTotal OBJECT-TYPE
   SYNTAX      Counter64
   MAX-ACCESS  read-only
   STATUS      current
   DESCRIPTION
      "Path: swPort.performance.ifOutPriorityQueues.octets.total

       64 bit unsigned wrappable counter."
   ::= {pr1646v2EthPortSwIXt2OutQueuesEntry 67567616}

pr1646v2EthPortSwIXt2OutQueuesOctetsDirectTx OBJECT-TYPE
   SYNTAX      Counter64
   MAX-ACCESS  read-only
   STATUS      current
   DESCRIPTION
      "Path: swPort.performance.ifOutPriorityQueues.octets.directTx

       64 bit unsigned wrappable counter."
   ::= {pr1646v2EthPortSwIXt2OutQueuesEntry 67174400}

pr1646v2EthPortSwIXt2OutQueuesOctetsQueued OBJECT-TYPE
   SYNTAX      Counter64
   MAX-ACCESS  read-only
   STATUS      current
   DESCRIPTION
      "Path: swPort.performance.ifOutPriorityQueues.octets.queued

       64 bit unsigned wrappable counter."
   ::= {pr1646v2EthPortSwIXt2OutQueuesEntry 67239936}

pr1646v2EthPortSwIXt2OutQueuesOctetsDropped OBJECT-TYPE
   SYNTAX      Counter64
   MAX-ACCESS  read-only
   STATUS      current
   DESCRIPTION
      "Path: swPort.performance.ifOutPriorityQueues.octets.dropped

       64 bit unsigned wrappable counter."
   ::= {pr1646v2EthPortSwIXt2OutQueuesEntry 67305472}

pr1646v2EthPortSwIXt2OutQueuesOctetsRedDropped OBJECT-TYPE
   SYNTAX      Counter64
   MAX-ACCESS  read-only
   STATUS      current
   DESCRIPTION
      "Path: swPort.performance.ifOutPriorityQueues.octets.redDropped

       64 bit unsigned wrappable counter."
   ::= {pr1646v2EthPortSwIXt2OutQueuesEntry 67502080}

pr1646v2EthPortSwIXt2OutQueuesOctetsCirTx OBJECT-TYPE
   SYNTAX      Counter64
   MAX-ACCESS  read-only
   STATUS      current
   DESCRIPTION
      "Path: swPort.performance.ifOutPriorityQueues.octets.cirTx

       64 bit unsigned wrappable counter."
   ::= {pr1646v2EthPortSwIXt2OutQueuesEntry 67371008}

pr1646v2EthPortSwIXt2OutQueuesOctetsEirTx OBJECT-TYPE
   SYNTAX      Counter64
   MAX-ACCESS  read-only
   STATUS      current
   DESCRIPTION
      "Path: swPort.performance.ifOutPriorityQueues.octets.eirTx

       64 bit unsigned wrappable counter."
   ::= {pr1646v2EthPortSwIXt2OutQueuesEntry 67436544}

pr1646v2EthPortSwIXt2OutQueuesOctetsViolateTx OBJECT-TYPE
   SYNTAX      Counter64
   MAX-ACCESS  read-only
   STATUS      current
   DESCRIPTION
      "Path: swPort.performance.ifOutPriorityQueues.octets.violateTx

       64 bit unsigned wrappable counter."
   ::= {pr1646v2EthPortSwIXt2OutQueuesEntry 67633152}

pr1646v2EthPortSwIXt2OutQueuesOctetsBandwidth15sec OBJECT-TYPE
   SYNTAX      Integer32
   MAX-ACCESS  read-only
   STATUS      current
   DESCRIPTION
      "Path: swPort.performance.ifOutPriorityQueues.octets.bandwidth.15sec

       unit name = bps
       formula = 8 * ; 8 /"
   ::= {pr1646v2EthPortSwIXt2OutQueuesEntry 70386944}

pr1646v2EthPortSwIXt2OutQueuesOctetsBandwidth30sec OBJECT-TYPE
   SYNTAX      Integer32
   MAX-ACCESS  read-only
   STATUS      current
   DESCRIPTION
      "Path: swPort.performance.ifOutPriorityQueues.octets.bandwidth.30sec

       unit name = bps
       formula = 8 * ; 8 /"
   ::= {pr1646v2EthPortSwIXt2OutQueuesEntry 70388224}

pr1646v2EthPortSwIXt2OutQueuesOctetsBandwidth1min OBJECT-TYPE
   SYNTAX      Integer32
   MAX-ACCESS  read-only
   STATUS      current
   DESCRIPTION
      "Path: swPort.performance.ifOutPriorityQueues.octets.bandwidth.1min

       unit name = bps
       formula = 8 * ; 8 /"
   ::= {pr1646v2EthPortSwIXt2OutQueuesEntry 70390784}

pr1646v2EthPortSwIXt2OutQueuesOctetsBandwidth2min OBJECT-TYPE
   SYNTAX      Integer32
   MAX-ACCESS  read-only
   STATUS      current
   DESCRIPTION
      "Path: swPort.performance.ifOutPriorityQueues.octets.bandwidth.2min

       unit name = bps
       formula = 8 * ; 8 /"
   ::= {pr1646v2EthPortSwIXt2OutQueuesEntry 70395904}

pr1646v2EthPortSwIXt2OutQueuesOctetsBandwidth5min OBJECT-TYPE
   SYNTAX      Integer32
   MAX-ACCESS  read-only
   STATUS      current
   DESCRIPTION
      "Path: swPort.performance.ifOutPriorityQueues.octets.bandwidth.5min

       unit name = bps
       formula = 8 * ; 8 /"
   ::= {pr1646v2EthPortSwIXt2OutQueuesEntry 70411264}

pr1646v2EthPortSwIXt2OutQueuesH2Performance OBJECT-TYPE
   SYNTAX      SEQUENCE OF Pr1646v2EthPortSwIXt2OutQueuesH2PerformanceEntry
   MAX-ACCESS  not-accessible
   STATUS      current
   DESCRIPTION
      ""
   ::= {pr1646v2EthPortSwIXt2OutQueues 83886080}

pr1646v2EthPortSwIXt2OutQueuesH2PerformanceEntry OBJECT-TYPE
   SYNTAX      Pr1646v2EthPortSwIXt2OutQueuesH2PerformanceEntry
   MAX-ACCESS  not-accessible
   STATUS      current
   DESCRIPTION
      ""
   INDEX      { pr1646v2EthPortSwIXt2OutQueuesH2PerformanceGlobalIx,
                pr1646v2EthPortSwIXt2OutQueuesTableIx,
                pr1646v2EthPortSwIXt2OutQueuesH2PerformanceTableIx }
   ::= {pr1646v2EthPortSwIXt2OutQueuesH2Performance 1}

Pr1646v2EthPortSwIXt2OutQueuesH2PerformanceEntry ::=
   SEQUENCE
      {
      pr1646v2EthPortSwIXt2OutQueuesH2PerformanceGlobalIx
         GlobalIndex,
      pr1646v2EthPortSwIXt2OutQueuesH2PerformanceTableIx
         TableIndex,
      pr1646v2EthPortSwIXt2OutQueuesH2PerformanceSysUpTime
         TimeTicks,
      pr1646v2EthPortSwIXt2OutQueuesH2PerformanceTotPkts
         Counter64,
      pr1646v2EthPortSwIXt2OutQueuesH2PerformanceDirTxPkts
         Counter64,
      pr1646v2EthPortSwIXt2OutQueuesH2PerformanceQdPkts
         Counter64,
      pr1646v2EthPortSwIXt2OutQueuesH2PerformanceDropPkts
         Counter64,
      pr1646v2EthPortSwIXt2OutQueuesH2PerformanceRDropPkts
         Counter64,
      pr1646v2EthPortSwIXt2OutQueuesH2PerformanceCirTxPkts
         Counter64,
      pr1646v2EthPortSwIXt2OutQueuesH2PerformanceEirTxPkts
         Counter64,
      pr1646v2EthPortSwIXt2OutQueuesH2PerformanceViolTxPkts
         Counter64,
      pr1646v2EthPortSwIXt2OutQueuesH2PerformanceTotOcts
         Counter64,
      pr1646v2EthPortSwIXt2OutQueuesH2PerformanceDirTxOcts
         Counter64,
      pr1646v2EthPortSwIXt2OutQueuesH2PerformanceQdOcts
         Counter64,
      pr1646v2EthPortSwIXt2OutQueuesH2PerformanceDropOcts
         Counter64,
      pr1646v2EthPortSwIXt2OutQueuesH2PerformanceRDropOcts
         Counter64,
      pr1646v2EthPortSwIXt2OutQueuesH2PerformanceCirTxOcts
         Counter64,
      pr1646v2EthPortSwIXt2OutQueuesH2PerformanceEirTxOcts
         Counter64,
      pr1646v2EthPortSwIXt2OutQueuesH2PerformanceViolTxOcts
         Counter64,
      pr1646v2EthPortSwIXt2OutQueuesH2PerformanceBandwidth
         Integer32
      }

pr1646v2EthPortSwIXt2OutQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutQueuesH2PerformanceEntry 10}

pr1646v2EthPortSwIXt2OutQueuesH2PerformanceTableIx OBJECT-TYPE
   SYNTAX      TableIndex
   MAX-ACCESS  not-accessible
   STATUS      current
   DESCRIPTION
      ""
   ::= {pr1646v2EthPortSwIXt2OutQueuesH2PerformanceEntry 11}

pr1646v2EthPortSwIXt2OutQueuesH2PerformanceSysUpTime OBJECT-TYPE
   SYNTAX      TimeTicks
   MAX-ACCESS  read-only
   STATUS      current
   DESCRIPTION
      "Path: swPort.performance.ifOutPriorityQueues.h2Performance.sysUpTime

       Time in centi-second."
   ::= {pr1646v2EthPortSwIXt2OutQueuesH2PerformanceEntry 16777216}

pr1646v2EthPortSwIXt2OutQueuesH2PerformanceTotPkts OBJECT-TYPE
   SYNTAX      Counter64
   MAX-ACCESS  read-only
   STATUS      current
   DESCRIPTION
      "Path: swPort.performance.ifOutPriorityQueues.h2Performance.totalPkts

       64 bit unsigned wrappable counter."
   ::= {pr1646v2EthPortSwIXt2OutQueuesH2PerformanceEntry 234881024}

pr1646v2EthPortSwIXt2OutQueuesH2PerformanceDirTxPkts OBJECT-TYPE
   SYNTAX      Counter64
   MAX-ACCESS  read-only
   STATUS      current
   DESCRIPTION
      "Path: swPort.performance.ifOutPriorityQueues.h2Performance.directTxPkts

       64 bit unsigned wrappable counter."
   ::= {pr1646v2EthPortSwIXt2OutQueuesH2PerformanceEntry 33554432}

pr1646v2EthPortSwIXt2OutQueuesH2PerformanceQdPkts OBJECT-TYPE
   SYNTAX      Counter64
   MAX-ACCESS  read-only
   STATUS      current
   DESCRIPTION
      "Path: swPort.performance.ifOutPriorityQueues.h2Performance.queuedPkts

       64 bit unsigned wrappable counter."
   ::= {pr1646v2EthPortSwIXt2OutQueuesH2PerformanceEntry 50331648}

pr1646v2EthPortSwIXt2OutQueuesH2PerformanceDropPkts OBJECT-TYPE
   SYNTAX      Counter64
   MAX-ACCESS  read-only
   STATUS      current
   DESCRIPTION
      "Path: swPort.performance.ifOutPriorityQueues.h2Performance.droppedPkts

       64 bit unsigned wrappable counter."
   ::= {pr1646v2EthPortSwIXt2OutQueuesH2PerformanceEntry 67108864}

pr1646v2EthPortSwIXt2OutQueuesH2PerformanceRDropPkts OBJECT-TYPE
   SYNTAX      Counter64
   MAX-ACCESS  read-only
   STATUS      current
   DESCRIPTION
      "Path: swPort.performance.ifOutPriorityQueues.h2Performance.redDroppedPkts

       64 bit unsigned wrappable counter."
   ::= {pr1646v2EthPortSwIXt2OutQueuesH2PerformanceEntry 201326592}

pr1646v2EthPortSwIXt2OutQueuesH2PerformanceCirTxPkts OBJECT-TYPE
   SYNTAX      Counter64
   MAX-ACCESS  read-only
   STATUS      current
   DESCRIPTION
      "Path: swPort.performance.ifOutPriorityQueues.h2Performance.cirTxPkts

       64 bit unsigned wrappable counter."
   ::= {pr1646v2EthPortSwIXt2OutQueuesH2PerformanceEntry 83886080}

pr1646v2EthPortSwIXt2OutQueuesH2PerformanceEirTxPkts OBJECT-TYPE
   SYNTAX      Counter64
   MAX-ACCESS  read-only
   STATUS      current
   DESCRIPTION
      "Path: swPort.performance.ifOutPriorityQueues.h2Performance.eirTxPkts

       64 bit unsigned wrappable counter."
   ::= {pr1646v2EthPortSwIXt2OutQueuesH2PerformanceEntry 100663296}

pr1646v2EthPortSwIXt2OutQueuesH2PerformanceViolTxPkts OBJECT-TYPE
   SYNTAX      Counter64
   MAX-ACCESS  read-only
   STATUS      current
   DESCRIPTION
      "Path: swPort.performance.ifOutPriorityQueues.h2Performance.violateTxPkts

       64 bit unsigned wrappable counter."
   ::= {pr1646v2EthPortSwIXt2OutQueuesH2PerformanceEntry 301989888}

pr1646v2EthPortSwIXt2OutQueuesH2PerformanceTotOcts OBJECT-TYPE
   SYNTAX      Counter64
   MAX-ACCESS  read-only
   STATUS      current
   DESCRIPTION
      "Path: swPort.performance.ifOutPriorityQueues.h2Performance.totalOctets

       64 bit unsigned wrappable counter."
   ::= {pr1646v2EthPortSwIXt2OutQueuesH2PerformanceEntry 251658240}

pr1646v2EthPortSwIXt2OutQueuesH2PerformanceDirTxOcts OBJECT-TYPE
   SYNTAX      Counter64
   MAX-ACCESS  read-only
   STATUS      current
   DESCRIPTION
      "Path: swPort.performance.ifOutPriorityQueues.h2Performance.directTxOctets

       64 bit unsigned wrappable counter."
   ::= {pr1646v2EthPortSwIXt2OutQueuesH2PerformanceEntry 117440512}

pr1646v2EthPortSwIXt2OutQueuesH2PerformanceQdOcts OBJECT-TYPE
   SYNTAX      Counter64
   MAX-ACCESS  read-only
   STATUS      current
   DESCRIPTION
      "Path: swPort.performance.ifOutPriorityQueues.h2Performance.queuedOctets

       64 bit unsigned wrappable counter."
   ::= {pr1646v2EthPortSwIXt2OutQueuesH2PerformanceEntry 134217728}

pr1646v2EthPortSwIXt2OutQueuesH2PerformanceDropOcts OBJECT-TYPE
   SYNTAX      Counter64
   MAX-ACCESS  read-only
   STATUS      current
   DESCRIPTION
      "Path: swPort.performance.ifOutPriorityQueues.h2Performance.droppedOctets

       64 bit unsigned wrappable counter."
   ::= {pr1646v2EthPortSwIXt2OutQueuesH2PerformanceEntry 150994944}

pr1646v2EthPortSwIXt2OutQueuesH2PerformanceRDropOcts OBJECT-TYPE
   SYNTAX      Counter64
   MAX-ACCESS  read-only
   STATUS      current
   DESCRIPTION
      "Path: swPort.performance.ifOutPriorityQueues.h2Performance.redDroppedOctets

       64 bit unsigned wrappable counter."
   ::= {pr1646v2EthPortSwIXt2OutQueuesH2PerformanceEntry 218103808}

pr1646v2EthPortSwIXt2OutQueuesH2PerformanceCirTxOcts OBJECT-TYPE
   SYNTAX      Counter64
   MAX-ACCESS  read-only
   STATUS      current
   DESCRIPTION
      "Path: swPort.performance.ifOutPriorityQueues.h2Performance.cirTxOctets

       64 bit unsigned wrappable counter."
   ::= {pr1646v2EthPortSwIXt2OutQueuesH2PerformanceEntry 167772160}

pr1646v2EthPortSwIXt2OutQueuesH2PerformanceEirTxOcts OBJECT-TYPE
   SYNTAX      Counter64
   MAX-ACCESS  read-only
   STATUS      current
   DESCRIPTION
      "Path: swPort.performance.ifOutPriorityQueues.h2Performance.eirTxOctets

       64 bit unsigned wrappable counter."
   ::= {pr1646v2EthPortSwIXt2OutQueuesH2PerformanceEntry 184549376}

pr1646v2EthPortSwIXt2OutQueuesH2PerformanceViolTxOcts OBJECT-TYPE
   SYNTAX      Counter64
   MAX-ACCESS  read-only
   STATUS      current
   DESCRIPTION
      "Path: swPort.performance.ifOutPriorityQueues.h2Performance.violateTxOctets

       64 bit unsigned wrappable counter."
   ::= {pr1646v2EthPortSwIXt2OutQueuesH2PerformanceEntry 318767104}

pr1646v2EthPortSwIXt2OutQueuesH2PerformanceBandwidth OBJECT-TYPE
   SYNTAX      Integer32
   MAX-ACCESS  read-only
   STATUS      current
   DESCRIPTION
      "Path: swPort.performance.ifOutPriorityQueues.h2Performance.bandwidth

       unit name = bps
       formula = 8 * ; 8 /"
   ::= {pr1646v2EthPortSwIXt2OutQueuesH2PerformanceEntry 268435456}

pr1646v2EthPortSwIXt2OutQueuesH24Performance OBJECT-TYPE
   SYNTAX      SEQUENCE OF Pr1646v2EthPortSwIXt2OutQueuesH24PerformanceEntry
   MAX-ACCESS  not-accessible
   STATUS      current
   DESCRIPTION
      ""
   ::= {pr1646v2EthPortSwIXt2OutQueues 100663296}

pr1646v2EthPortSwIXt2OutQueuesH24PerformanceEntry OBJECT-TYPE
   SYNTAX      Pr1646v2EthPortSwIXt2OutQueuesH24PerformanceEntry
   MAX-ACCESS  not-accessible
   STATUS      current
   DESCRIPTION
      ""
   INDEX      { pr1646v2EthPortSwIXt2OutQueuesH24PerformanceGlobalIx,
                pr1646v2EthPortSwIXt2OutQueuesTableIx,
                pr1646v2EthPortSwIXt2OutQueuesH24PerformanceTableIx }
   ::= {pr1646v2EthPortSwIXt2OutQueuesH24Performance 1}

Pr1646v2EthPortSwIXt2OutQueuesH24PerformanceEntry ::=
   SEQUENCE
      {
      pr1646v2EthPortSwIXt2OutQueuesH24PerformanceGlobalIx
         GlobalIndex,
      pr1646v2EthPortSwIXt2OutQueuesH24PerformanceTableIx
         TableIndex,
      pr1646v2EthPortSwIXt2OutQueuesH24PerformanceSysUpTime
         TimeTicks,
      pr1646v2EthPortSwIXt2OutQueuesH24PerformanceTotPkts
         Counter64,
      pr1646v2EthPortSwIXt2OutQueuesH24PerformanceDirTxPkts
         Counter64,
      pr1646v2EthPortSwIXt2OutQueuesH24PerformanceQdPkts
         Counter64,
      pr1646v2EthPortSwIXt2OutQueuesH24PerformanceDropPkts
         Counter64,
      pr1646v2EthPortSwIXt2OutQueuesH24PerformanceRDropPkts
         Counter64,
      pr1646v2EthPortSwIXt2OutQueuesH24PerformanceCirTxPkts
         Counter64,
      pr1646v2EthPortSwIXt2OutQueuesH24PerformanceEirTxPkts
         Counter64,
      pr1646v2EthPortSwIXt2OutQueuesH24PerformanceViolTxPkts
         Counter64,
      pr1646v2EthPortSwIXt2OutQueuesH24PerformanceTotOcts
         Counter64,
      pr1646v2EthPortSwIXt2OutQueuesH24PerformanceDirTxOcts
         Counter64,
      pr1646v2EthPortSwIXt2OutQueuesH24PerformanceQdOcts
         Counter64,
      pr1646v2EthPortSwIXt2OutQueuesH24PerformanceDropOcts
         Counter64,
      pr1646v2EthPortSwIXt2OutQueuesH24PerformanceRDropOcts
         Counter64,
      pr1646v2EthPortSwIXt2OutQueuesH24PerformanceCirTxOcts
         Counter64,
      pr1646v2EthPortSwIXt2OutQueuesH24PerformanceEirTxOcts
         Counter64,
      pr1646v2EthPortSwIXt2OutQueuesH24PerformanceViolTxOcts
         Counter64,
      pr1646v2EthPortSwIXt2OutQueuesH24PerformanceBandwidth
         Integer32
      }

pr1646v2EthPortSwIXt2OutQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutQueuesH24PerformanceEntry 10}

pr1646v2EthPortSwIXt2OutQueuesH24PerformanceTableIx OBJECT-TYPE
   SYNTAX      TableIndex
   MAX-ACCESS  not-accessible
   STATUS      current
   DESCRIPTION
      ""
   ::= {pr1646v2EthPortSwIXt2OutQueuesH24PerformanceEntry 11}

pr1646v2EthPortSwIXt2OutQueuesH24PerformanceSysUpTime OBJECT-TYPE
   SYNTAX      TimeTicks
   MAX-ACCESS  read-only
   STATUS      current
   DESCRIPTION
      "Path: swPort.performance.ifOutPriorityQueues.h24Performance.sysUpTime

       Time in centi-second."
   ::= {pr1646v2EthPortSwIXt2OutQueuesH24PerformanceEntry 16777216}

pr1646v2EthPortSwIXt2OutQueuesH24PerformanceTotPkts OBJECT-TYPE
   SYNTAX      Counter64
   MAX-ACCESS  read-only
   STATUS      current
   DESCRIPTION
      "Path: swPort.performance.ifOutPriorityQueues.h24Performance.totalPkts

       64 bit unsigned wrappable counter."
   ::= {pr1646v2EthPortSwIXt2OutQueuesH24PerformanceEntry 234881024}

pr1646v2EthPortSwIXt2OutQueuesH24PerformanceDirTxPkts OBJECT-TYPE
   SYNTAX      Counter64
   MAX-ACCESS  read-only
   STATUS      current
   DESCRIPTION
      "Path: swPort.performance.ifOutPriorityQueues.h24Performance.directTxPkts

       64 bit unsigned wrappable counter."
   ::= {pr1646v2EthPortSwIXt2OutQueuesH24PerformanceEntry 33554432}

pr1646v2EthPortSwIXt2OutQueuesH24PerformanceQdPkts OBJECT-TYPE
   SYNTAX      Counter64
   MAX-ACCESS  read-only
   STATUS      current
   DESCRIPTION
      "Path: swPort.performance.ifOutPriorityQueues.h24Performance.queuedPkts

       64 bit unsigned wrappable counter."
   ::= {pr1646v2EthPortSwIXt2OutQueuesH24PerformanceEntry 50331648}

pr1646v2EthPortSwIXt2OutQueuesH24PerformanceDropPkts OBJECT-TYPE
   SYNTAX      Counter64
   MAX-ACCESS  read-only
   STATUS      current
   DESCRIPTION
      "Path: swPort.performance.ifOutPriorityQueues.h24Performance.droppedPkts

       64 bit unsigned wrappable counter."
   ::= {pr1646v2EthPortSwIXt2OutQueuesH24PerformanceEntry 67108864}

pr1646v2EthPortSwIXt2OutQueuesH24PerformanceRDropPkts OBJECT-TYPE
   SYNTAX      Counter64
   MAX-ACCESS  read-only
   STATUS      current
   DESCRIPTION
      "Path: swPort.performance.ifOutPriorityQueues.h24Performance.redDroppedPkts

       64 bit unsigned wrappable counter."
   ::= {pr1646v2EthPortSwIXt2OutQueuesH24PerformanceEntry 201326592}

pr1646v2EthPortSwIXt2OutQueuesH24PerformanceCirTxPkts OBJECT-TYPE
   SYNTAX      Counter64
   MAX-ACCESS  read-only
   STATUS      current
   DESCRIPTION
      "Path: swPort.performance.ifOutPriorityQueues.h24Performance.cirTxPkts

       64 bit unsigned wrappable counter."
   ::= {pr1646v2EthPortSwIXt2OutQueuesH24PerformanceEntry 83886080}

pr1646v2EthPortSwIXt2OutQueuesH24PerformanceEirTxPkts OBJECT-TYPE
   SYNTAX      Counter64
   MAX-ACCESS  read-only
   STATUS      current
   DESCRIPTION
      "Path: swPort.performance.ifOutPriorityQueues.h24Performance.eirTxPkts

       64 bit unsigned wrappable counter."
   ::= {pr1646v2EthPortSwIXt2OutQueuesH24PerformanceEntry 100663296}

pr1646v2EthPortSwIXt2OutQueuesH24PerformanceViolTxPkts OBJECT-TYPE
   SYNTAX      Counter64
   MAX-ACCESS  read-only
   STATUS      current
   DESCRIPTION
      "Path: swPort.performance.ifOutPriorityQueues.h24Performance.violateTxPkts

       64 bit unsigned wrappable counter."
   ::= {pr1646v2EthPortSwIXt2OutQueuesH24PerformanceEntry 301989888}

pr1646v2EthPortSwIXt2OutQueuesH24PerformanceTotOcts OBJECT-TYPE
   SYNTAX      Counter64
   MAX-ACCESS  read-only
   STATUS      current
   DESCRIPTION
      "Path: swPort.performance.ifOutPriorityQueues.h24Performance.totalOctets

       64 bit unsigned wrappable counter."
   ::= {pr1646v2EthPortSwIXt2OutQueuesH24PerformanceEntry 251658240}

pr1646v2EthPortSwIXt2OutQueuesH24PerformanceDirTxOcts OBJECT-TYPE
   SYNTAX      Counter64
   MAX-ACCESS  read-only
   STATUS      current
   DESCRIPTION
      "Path: swPort.performance.ifOutPriorityQueues.h24Performance.directTxOctets

       64 bit unsigned wrappable counter."
   ::= {pr1646v2EthPortSwIXt2OutQueuesH24PerformanceEntry 117440512}

pr1646v2EthPortSwIXt2OutQueuesH24PerformanceQdOcts OBJECT-TYPE
   SYNTAX      Counter64
   MAX-ACCESS  read-only
   STATUS      current
   DESCRIPTION
      "Path: swPort.performance.ifOutPriorityQueues.h24Performance.queuedOctets

       64 bit unsigned wrappable counter."
   ::= {pr1646v2EthPortSwIXt2OutQueuesH24PerformanceEntry 134217728}

pr1646v2EthPortSwIXt2OutQueuesH24PerformanceDropOcts OBJECT-TYPE
   SYNTAX      Counter64
   MAX-ACCESS  read-only
   STATUS      current
   DESCRIPTION
      "Path: swPort.performance.ifOutPriorityQueues.h24Performance.droppedOctets

       64 bit unsigned wrappable counter."
   ::= {pr1646v2EthPortSwIXt2OutQueuesH24PerformanceEntry 150994944}

pr1646v2EthPortSwIXt2OutQueuesH24PerformanceRDropOcts OBJECT-TYPE
   SYNTAX      Counter64
   MAX-ACCESS  read-only
   STATUS      current
   DESCRIPTION
      "Path: swPort.performance.ifOutPriorityQueues.h24Performance.redDroppedOctets

       64 bit unsigned wrappable counter."
   ::= {pr1646v2EthPortSwIXt2OutQueuesH24PerformanceEntry 218103808}

pr1646v2EthPortSwIXt2OutQueuesH24PerformanceCirTxOcts OBJECT-TYPE
   SYNTAX      Counter64
   MAX-ACCESS  read-only
   STATUS      current
   DESCRIPTION
      "Path: swPort.performance.ifOutPriorityQueues.h24Performance.cirTxOctets

       64 bit unsigned wrappable counter."
   ::= {pr1646v2EthPortSwIXt2OutQueuesH24PerformanceEntry 167772160}

pr1646v2EthPortSwIXt2OutQueuesH24PerformanceEirTxOcts OBJECT-TYPE
   SYNTAX      Counter64
   MAX-ACCESS  read-only
   STATUS      current
   DESCRIPTION
      "Path: swPort.performance.ifOutPriorityQueues.h24Performance.eirTxOctets

       64 bit unsigned wrappable counter."
   ::= {pr1646v2EthPortSwIXt2OutQueuesH24PerformanceEntry 184549376}

pr1646v2EthPortSwIXt2OutQueuesH24PerformanceViolTxOcts OBJECT-TYPE
   SYNTAX      Counter64
   MAX-ACCESS  read-only
   STATUS      current
   DESCRIPTION
      "Path: swPort.performance.ifOutPriorityQueues.h24Performance.violateTxOctets

       64 bit unsigned wrappable counter."
   ::= {pr1646v2EthPortSwIXt2OutQueuesH24PerformanceEntry 318767104}

pr1646v2EthPortSwIXt2OutQueuesH24PerformanceBandwidth OBJECT-TYPE
   SYNTAX      Integer32
   MAX-ACCESS  read-only
   STATUS      current
   DESCRIPTION
      "Path: swPort.performance.ifOutPriorityQueues.h24Performance.bandwidth

       unit name = bps
       formula = 8 * ; 8 /"
   ::= {pr1646v2EthPortSwIXt2OutQueuesH24PerformanceEntry 268435456}

pr1646v2EthPortSwIXt2OutQueuesD7Performance OBJECT-TYPE
   SYNTAX      SEQUENCE OF Pr1646v2EthPortSwIXt2OutQueuesD7PerformanceEntry
   MAX-ACCESS  not-accessible
   STATUS      current
   DESCRIPTION
      ""
   ::= {pr1646v2EthPortSwIXt2OutQueues 117440512}

pr1646v2EthPortSwIXt2OutQueuesD7PerformanceEntry OBJECT-TYPE
   SYNTAX      Pr1646v2EthPortSwIXt2OutQueuesD7PerformanceEntry
   MAX-ACCESS  not-accessible
   STATUS      current
   DESCRIPTION
      ""
   INDEX      { pr1646v2EthPortSwIXt2OutQueuesD7PerformanceGlobalIx,
                pr1646v2EthPortSwIXt2OutQueuesTableIx,
                pr1646v2EthPortSwIXt2OutQueuesD7PerformanceTableIx }
   ::= {pr1646v2EthPortSwIXt2OutQueuesD7Performance 1}

Pr1646v2EthPortSwIXt2OutQueuesD7PerformanceEntry ::=
   SEQUENCE
      {
      pr1646v2EthPortSwIXt2OutQueuesD7PerformanceGlobalIx
         GlobalIndex,
      pr1646v2EthPortSwIXt2OutQueuesD7PerformanceTableIx
         TableIndex,
      pr1646v2EthPortSwIXt2OutQueuesD7PerformanceSysUpTime
         TimeTicks,
      pr1646v2EthPortSwIXt2OutQueuesD7PerformanceTotPkts
         Counter64,
      pr1646v2EthPortSwIXt2OutQueuesD7PerformanceDirTxPkts
         Counter64,
      pr1646v2EthPortSwIXt2OutQueuesD7PerformanceQdPkts
         Counter64,
      pr1646v2EthPortSwIXt2OutQueuesD7PerformanceDropPkts
         Counter64,
      pr1646v2EthPortSwIXt2OutQueuesD7PerformanceRDropPkts
         Counter64,
      pr1646v2EthPortSwIXt2OutQueuesD7PerformanceCirTxPkts
         Counter64,
      pr1646v2EthPortSwIXt2OutQueuesD7PerformanceEirTxPkts
         Counter64,
      pr1646v2EthPortSwIXt2OutQueuesD7PerformanceViolTxPkts
         Counter64,
      pr1646v2EthPortSwIXt2OutQueuesD7PerformanceTotOcts
         Counter64,
      pr1646v2EthPortSwIXt2OutQueuesD7PerformanceDirTxOcts
         Counter64,
      pr1646v2EthPortSwIXt2OutQueuesD7PerformanceQdOcts
         Counter64,
      pr1646v2EthPortSwIXt2OutQueuesD7PerformanceDropOcts
         Counter64,
      pr1646v2EthPortSwIXt2OutQueuesD7PerformanceRDropOcts
         Counter64,
      pr1646v2EthPortSwIXt2OutQueuesD7PerformanceCirTxOcts
         Counter64,
      pr1646v2EthPortSwIXt2OutQueuesD7PerformanceEirTxOcts
         Counter64,
      pr1646v2EthPortSwIXt2OutQueuesD7PerformanceViolTxOcts
         Counter64,
      pr1646v2EthPortSwIXt2OutQueuesD7PerformanceBandwidth
         Integer32
      }

pr1646v2EthPortSwIXt2OutQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutQueuesD7PerformanceEntry 10}

pr1646v2EthPortSwIXt2OutQueuesD7PerformanceTableIx OBJECT-TYPE
   SYNTAX      TableIndex
   MAX-ACCESS  not-accessible
   STATUS      current
   DESCRIPTION
      ""
   ::= {pr1646v2EthPortSwIXt2OutQueuesD7PerformanceEntry 11}

pr1646v2EthPortSwIXt2OutQueuesD7PerformanceSysUpTime OBJECT-TYPE
   SYNTAX      TimeTicks
   MAX-ACCESS  read-only
   STATUS      current
   DESCRIPTION
      "Path: swPort.performance.ifOutPriorityQueues.d7Performance.sysUpTime

       Time in centi-second."
   ::= {pr1646v2EthPortSwIXt2OutQueuesD7PerformanceEntry 16777216}

pr1646v2EthPortSwIXt2OutQueuesD7PerformanceTotPkts OBJECT-TYPE
   SYNTAX      Counter64
   MAX-ACCESS  read-only
   STATUS      current
   DESCRIPTION
      "Path: swPort.performance.ifOutPriorityQueues.d7Performance.totalPkts

       64 bit unsigned wrappable counter."
   ::= {pr1646v2EthPortSwIXt2OutQueuesD7PerformanceEntry 234881024}

pr1646v2EthPortSwIXt2OutQueuesD7PerformanceDirTxPkts OBJECT-TYPE
   SYNTAX      Counter64
   MAX-ACCESS  read-only
   STATUS      current
   DESCRIPTION
      "Path: swPort.performance.ifOutPriorityQueues.d7Performance.directTxPkts

       64 bit unsigned wrappable counter."
   ::= {pr1646v2EthPortSwIXt2OutQueuesD7PerformanceEntry 33554432}

pr1646v2EthPortSwIXt2OutQueuesD7PerformanceQdPkts OBJECT-TYPE
   SYNTAX      Counter64
   MAX-ACCESS  read-only
   STATUS      current
   DESCRIPTION
      "Path: swPort.performance.ifOutPriorityQueues.d7Performance.queuedPkts

       64 bit unsigned wrappable counter."
   ::= {pr1646v2EthPortSwIXt2OutQueuesD7PerformanceEntry 50331648}

pr1646v2EthPortSwIXt2OutQueuesD7PerformanceDropPkts OBJECT-TYPE
   SYNTAX      Counter64
   MAX-ACCESS  read-only
   STATUS      current
   DESCRIPTION
      "Path: swPort.performance.ifOutPriorityQueues.d7Performance.droppedPkts

       64 bit unsigned wrappable counter."
   ::= {pr1646v2EthPortSwIXt2OutQueuesD7PerformanceEntry 67108864}

pr1646v2EthPortSwIXt2OutQueuesD7PerformanceRDropPkts OBJECT-TYPE
   SYNTAX      Counter64
   MAX-ACCESS  read-only
   STATUS      current
   DESCRIPTION
      "Path: swPort.performance.ifOutPriorityQueues.d7Performance.redDroppedPkts

       64 bit unsigned wrappable counter."
   ::= {pr1646v2EthPortSwIXt2OutQueuesD7PerformanceEntry 201326592}

pr1646v2EthPortSwIXt2OutQueuesD7PerformanceCirTxPkts OBJECT-TYPE
   SYNTAX      Counter64
   MAX-ACCESS  read-only
   STATUS      current
   DESCRIPTION
      "Path: swPort.performance.ifOutPriorityQueues.d7Performance.cirTxPkts

       64 bit unsigned wrappable counter."
   ::= {pr1646v2EthPortSwIXt2OutQueuesD7PerformanceEntry 83886080}

pr1646v2EthPortSwIXt2OutQueuesD7PerformanceEirTxPkts OBJECT-TYPE
   SYNTAX      Counter64
   MAX-ACCESS  read-only
   STATUS      current
   DESCRIPTION
      "Path: swPort.performance.ifOutPriorityQueues.d7Performance.eirTxPkts

       64 bit unsigned wrappable counter."
   ::= {pr1646v2EthPortSwIXt2OutQueuesD7PerformanceEntry 100663296}

pr1646v2EthPortSwIXt2OutQueuesD7PerformanceViolTxPkts OBJECT-TYPE
   SYNTAX      Counter64
   MAX-ACCESS  read-only
   STATUS      current
   DESCRIPTION
      "Path: swPort.performance.ifOutPriorityQueues.d7Performance.violateTxPkts

       64 bit unsigned wrappable counter."
   ::= {pr1646v2EthPortSwIXt2OutQueuesD7PerformanceEntry 301989888}

pr1646v2EthPortSwIXt2OutQueuesD7PerformanceTotOcts OBJECT-TYPE
   SYNTAX      Counter64
   MAX-ACCESS  read-only
   STATUS      current
   DESCRIPTION
      "Path: swPort.performance.ifOutPriorityQueues.d7Performance.totalOctets

       64 bit unsigned wrappable counter."
   ::= {pr1646v2EthPortSwIXt2OutQueuesD7PerformanceEntry 251658240}

pr1646v2EthPortSwIXt2OutQueuesD7PerformanceDirTxOcts OBJECT-TYPE
   SYNTAX      Counter64
   MAX-ACCESS  read-only
   STATUS      current
   DESCRIPTION
      "Path: swPort.performance.ifOutPriorityQueues.d7Performance.directTxOctets

       64 bit unsigned wrappable counter."
   ::= {pr1646v2EthPortSwIXt2OutQueuesD7PerformanceEntry 117440512}

pr1646v2EthPortSwIXt2OutQueuesD7PerformanceQdOcts OBJECT-TYPE
   SYNTAX      Counter64
   MAX-ACCESS  read-only
   STATUS      current
   DESCRIPTION
      "Path: swPort.performance.ifOutPriorityQueues.d7Performance.queuedOctets

       64 bit unsigned wrappable counter."
   ::= {pr1646v2EthPortSwIXt2OutQueuesD7PerformanceEntry 134217728}

pr1646v2EthPortSwIXt2OutQueuesD7PerformanceDropOcts OBJECT-TYPE
   SYNTAX      Counter64
   MAX-ACCESS  read-only
   STATUS      current
   DESCRIPTION
      "Path: swPort.performance.ifOutPriorityQueues.d7Performance.droppedOctets

       64 bit unsigned wrappable counter."
   ::= {pr1646v2EthPortSwIXt2OutQueuesD7PerformanceEntry 150994944}

pr1646v2EthPortSwIXt2OutQueuesD7PerformanceRDropOcts OBJECT-TYPE
   SYNTAX      Counter64
   MAX-ACCESS  read-only
   STATUS      current
   DESCRIPTION
      "Path: swPort.performance.ifOutPriorityQueues.d7Performance.redDroppedOctets

       64 bit unsigned wrappable counter."
   ::= {pr1646v2EthPortSwIXt2OutQueuesD7PerformanceEntry 218103808}

pr1646v2EthPortSwIXt2OutQueuesD7PerformanceCirTxOcts OBJECT-TYPE
   SYNTAX      Counter64
   MAX-ACCESS  read-only
   STATUS      current
   DESCRIPTION
      "Path: swPort.performance.ifOutPriorityQueues.d7Performance.cirTxOctets

       64 bit unsigned wrappable counter."
   ::= {pr1646v2EthPortSwIXt2OutQueuesD7PerformanceEntry 167772160}

pr1646v2EthPortSwIXt2OutQueuesD7PerformanceEirTxOcts OBJECT-TYPE
   SYNTAX      Counter64
   MAX-ACCESS  read-only
   STATUS      current
   DESCRIPTION
      "Path: swPort.performance.ifOutPriorityQueues.d7Performance.eirTxOctets

       64 bit unsigned wrappable counter."
   ::= {pr1646v2EthPortSwIXt2OutQueuesD7PerformanceEntry 184549376}

pr1646v2EthPortSwIXt2OutQueuesD7PerformanceViolTxOcts OBJECT-TYPE
   SYNTAX      Counter64
   MAX-ACCESS  read-only
   STATUS      current
   DESCRIPTION
      "Path: swPort.performance.ifOutPriorityQueues.d7Performance.violateTxOctets

       64 bit unsigned wrappable counter."
   ::= {pr1646v2EthPortSwIXt2OutQueuesD7PerformanceEntry 318767104}

pr1646v2EthPortSwIXt2OutQueuesD7PerformanceBandwidth OBJECT-TYPE
   SYNTAX      Integer32
   MAX-ACCESS  read-only
   STATUS      current
   DESCRIPTION
      "Path: swPort.performance.ifOutPriorityQueues.d7Performance.bandwidth

       unit name = bps
       formula = 8 * ; 8 /"
   ::= {pr1646v2EthPortSwIXt2OutQueuesD7PerformanceEntry 268435456}


pr1646v2EthPortSwIXt2OutBandwidth OBJECT IDENTIFIER ::= {pr1646v2EthPortSwIXt2 182}

pr1646v2EthPortSwIXt2OutBandwidthSSCTable OBJECT-TYPE
   SYNTAX      SEQUENCE OF Pr1646v2EthPortSwIXt2OutBandwidthEntry
   MAX-ACCESS  not-accessible
   STATUS      current
   DESCRIPTION
      "bandwidth"
   ::= {pr1646v2EthPortSwIXt2OutBandwidth 1}

pr1646v2EthPortSwIXt2OutBandwidthEntry OBJECT-TYPE
   SYNTAX      Pr1646v2EthPortSwIXt2OutBandwidthEntry
   MAX-ACCESS  not-accessible
   STATUS      current
   DESCRIPTION
      ""
   INDEX      { pr1646v2EthPortSwIXt2OutBandwidthGlobalIx }
   ::= {pr1646v2EthPortSwIXt2OutBandwidthSSCTable 1}

Pr1646v2EthPortSwIXt2OutBandwidthEntry ::=
   SEQUENCE
      {
      pr1646v2EthPortSwIXt2OutBandwidthGlobalIx
         GlobalIndex,
      pr1646v2EthPortSwIXt2OutBandwidth15sec
         Integer32,
      pr1646v2EthPortSwIXt2OutBandwidth30sec
         Integer32,
      pr1646v2EthPortSwIXt2OutBandwidth1min
         Integer32,
      pr1646v2EthPortSwIXt2OutBandwidth2min
         Integer32,
      pr1646v2EthPortSwIXt2OutBandwidth5min
         Integer32
      }

pr1646v2EthPortSwIXt2OutBandwidthGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OutBandwidthEntry 10}

pr1646v2EthPortSwIXt2OutBandwidth15sec OBJECT-TYPE
   SYNTAX      Integer32
   MAX-ACCESS  read-only
   STATUS      current
   DESCRIPTION
      "Path: swPort.performance.ifOutBandwidth.15sec

       unit name = bps
       formula = 8 * ; 8 /"
   ::= {pr1646v2EthPortSwIXt2OutBandwidthEntry 83886080}

pr1646v2EthPortSwIXt2OutBandwidth30sec OBJECT-TYPE
   SYNTAX      Integer32
   MAX-ACCESS  read-only
   STATUS      current
   DESCRIPTION
      "Path: swPort.performance.ifOutBandwidth.30sec

       unit name = bps
       formula = 8 * ; 8 /"
   ::= {pr1646v2EthPortSwIXt2OutBandwidthEntry 167772160}

pr1646v2EthPortSwIXt2OutBandwidth1min OBJECT-TYPE
   SYNTAX      Integer32
   MAX-ACCESS  read-only
   STATUS      current
   DESCRIPTION
      "Path: swPort.performance.ifOutBandwidth.1min

       unit name = bps
       formula = 8 * ; 8 /"
   ::= {pr1646v2EthPortSwIXt2OutBandwidthEntry 335544320}

pr1646v2EthPortSwIXt2OutBandwidth2min OBJECT-TYPE
   SYNTAX      Integer32
   MAX-ACCESS  read-only
   STATUS      current
   DESCRIPTION
      "Path: swPort.performance.ifOutBandwidth.2min

       unit name = bps
       formula = 8 * ; 8 /"
   ::= {pr1646v2EthPortSwIXt2OutBandwidthEntry 671088640}

pr1646v2EthPortSwIXt2OutBandwidth5min OBJECT-TYPE
   SYNTAX      Integer32
   MAX-ACCESS  read-only
   STATUS      current
   DESCRIPTION
      "Path: swPort.performance.ifOutBandwidth.5min

       unit name = bps
       formula = 8 * ; 8 /"
   ::= {pr1646v2EthPortSwIXt2OutBandwidthEntry 1677721600}


pr1646v2EthPortSwIXt2InP OBJECT IDENTIFIER ::= {pr1646v2EthPortSwIXt2 307}

pr1646v2EthPortSwIXt2InPSSCTable OBJECT-TYPE
   SYNTAX      SEQUENCE OF Pr1646v2EthPortSwIXt2InPEntry
   MAX-ACCESS  not-accessible
   STATUS      current
   DESCRIPTION
      "h2IfInPerformance"
   ::= {pr1646v2EthPortSwIXt2InP 1}

pr1646v2EthPortSwIXt2InPEntry OBJECT-TYPE
   SYNTAX      Pr1646v2EthPortSwIXt2InPEntry
   MAX-ACCESS  not-accessible
   STATUS      current
   DESCRIPTION
      ""
   INDEX      { pr1646v2EthPortSwIXt2InPGlobalIx,
                pr1646v2EthPortSwIXt2InPTableIx }
   ::= {pr1646v2EthPortSwIXt2InPSSCTable 1}

Pr1646v2EthPortSwIXt2InPEntry ::=
   SEQUENCE
      {
      pr1646v2EthPortSwIXt2InPGlobalIx
         GlobalIndex,
      pr1646v2EthPortSwIXt2InPTableIx
         TableIndex,
      pr1646v2EthPortSwIXt2InPSysUpTime
         TimeTicks,
      pr1646v2EthPortSwIXt2InPIfUpTime
         TimeTicks,
      pr1646v2EthPortSwIXt2InPIfStatChanges
         Counter32,
      pr1646v2EthPortSwIXt2InPIfInOctets
         Counter64,
      pr1646v2EthPortSwIXt2InPIfInUCPkts
         Counter64,
      pr1646v2EthPortSwIXt2InPIfInNUCPkts
         Counter64,
      pr1646v2EthPortSwIXt2InPIfInBCPkts
         Counter64,
      pr1646v2EthPortSwIXt2InPIfInMCPkts
         Counter64,
      pr1646v2EthPortSwIXt2InPIfInDiscards
         Counter64,
      pr1646v2EthPortSwIXt2InPIfInErrors
         Counter64,
      pr1646v2EthPortSwIXt2InPIfInUnkwn
         Counter64,
      pr1646v2EthPortSwIXt2InPInDropEx
         Counter64,
      pr1646v2EthPortSwIXt2InPInDropNoMac
         Counter64,
      pr1646v2EthPortSwIXt2InPInDropNUCast
         Counter64,
      pr1646v2EthPortSwIXt2InPInDropFilter
         Counter64,
      pr1646v2EthPortSwIXt2InPIfInBandwidth
         Integer32,
      pr1646v2EthPortSwIXt2InPIfOutOctets
         Counter64,
      pr1646v2EthPortSwIXt2InPIfOutUCPkts
         Counter64,
      pr1646v2EthPortSwIXt2InPIfOutNUCPkts
         Counter64,
      pr1646v2EthPortSwIXt2InPIfOutBCPkts
         Counter64,
      pr1646v2EthPortSwIXt2InPIfOutMCPkts
         Counter64,
      pr1646v2EthPortSwIXt2InPIfOutDiscards
         Counter64,
      pr1646v2EthPortSwIXt2InPIfOutErrors
         Counter64,
      pr1646v2EthPortSwIXt2InPOutDropEx
         Counter64,
      pr1646v2EthPortSwIXt2InPOutDropNoArp
         Counter64,
      pr1646v2EthPortSwIXt2InPOutDropFilter
         Counter64,
      pr1646v2EthPortSwIXt2InPIfOutBandwidth
         Integer32,
      pr1646v2EthPortSwIXt2InPIfErrSec
         Counter32
      }

pr1646v2EthPortSwIXt2InPGlobalIx OBJECT-TYPE
   SYNTAX      GlobalIndex
   MAX-ACCESS  not-accessible
   STATUS      current
   DESCRIPTION
      "The value of the tlsCntTreeGlobalIndex of the MANAGED OBJECT."
   ::= {pr1646v2EthPortSwIXt2InPEntry 10}

pr1646v2EthPortSwIXt2InPTableIx OBJECT-TYPE
   SYNTAX      TableIndex
   MAX-ACCESS  not-accessible
   STATUS      current
   DESCRIPTION
      ""
   ::= {pr1646v2EthPortSwIXt2InPEntry 11}

pr1646v2EthPortSwIXt2InPSysUpTime OBJECT-TYPE
   SYNTAX      TimeTicks
   MAX-ACCESS  read-only
   STATUS      current
   DESCRIPTION
      "Path: swPort.performance.h2Performance.sysUpTime

       Time in centi-second."
   ::= {pr1646v2EthPortSwIXt2InPEntry 16777216}

pr1646v2EthPortSwIXt2InPIfUpTime OBJECT-TYPE
   SYNTAX      TimeTicks
   MAX-ACCESS  read-only
   STATUS      current
   DESCRIPTION
      "Path: swPort.performance.h2Performance.ifUpTime

       Time in centi-second."
   ::= {pr1646v2EthPortSwIXt2InPEntry 33554432}

pr1646v2EthPortSwIXt2InPIfStatChanges OBJECT-TYPE
   SYNTAX      Counter32
   MAX-ACCESS  read-only
   STATUS      current
   DESCRIPTION
      "Path: swPort.performance.h2Performance.ifStatusChanges

       32 bit unsigned wrappable counter."
   ::= {pr1646v2EthPortSwIXt2InPEntry 50331648}

pr1646v2EthPortSwIXt2InPIfInOctets OBJECT-TYPE
   SYNTAX      Counter64
   MAX-ACCESS  read-only
   STATUS      current
   DESCRIPTION
      "Path: swPort.performance.h2Performance.ifInOctets

       64 bit unsigned wrappable counter."
   ::= {pr1646v2EthPortSwIXt2InPEntry 67108864}

pr1646v2EthPortSwIXt2InPIfInUCPkts OBJECT-TYPE
   SYNTAX      Counter64
   MAX-ACCESS  read-only
   STATUS      current
   DESCRIPTION
      "Path: swPort.performance.h2Performance.ifInUcastPkts

       64 bit unsigned wrappable counter."
   ::= {pr1646v2EthPortSwIXt2InPEntry 83886080}

pr1646v2EthPortSwIXt2InPIfInNUCPkts OBJECT-TYPE
   SYNTAX      Counter64
   MAX-ACCESS  read-only
   STATUS      current
   DESCRIPTION
      "Path: swPort.performance.h2Performance.ifInNUcastPkts

       64 bit unsigned wrappable counter."
   ::= {pr1646v2EthPortSwIXt2InPEntry 100663296}

pr1646v2EthPortSwIXt2InPIfInBCPkts OBJECT-TYPE
   SYNTAX      Counter64
   MAX-ACCESS  read-only
   STATUS      current
   DESCRIPTION
      "Path: swPort.performance.h2Performance.ifInBcastPkts

       64 bit unsigned wrappable counter."
   ::= {pr1646v2EthPortSwIXt2InPEntry 419430400}

pr1646v2EthPortSwIXt2InPIfInMCPkts OBJECT-TYPE
   SYNTAX      Counter64
   MAX-ACCESS  read-only
   STATUS      current
   DESCRIPTION
      "Path: swPort.performance.h2Performance.ifInMcastPkts

       64 bit unsigned wrappable counter."
   ::= {pr1646v2EthPortSwIXt2InPEntry 436207616}

pr1646v2EthPortSwIXt2InPIfInDiscards OBJECT-TYPE
   SYNTAX      Counter64
   MAX-ACCESS  read-only
   STATUS      current
   DESCRIPTION
      "Path: swPort.performance.h2Performance.ifInDiscards

       64 bit unsigned wrappable counter."
   ::= {pr1646v2EthPortSwIXt2InPEntry 117440512}

pr1646v2EthPortSwIXt2InPIfInErrors OBJECT-TYPE
   SYNTAX      Counter64
   MAX-ACCESS  read-only
   STATUS      current
   DESCRIPTION
      "Path: swPort.performance.h2Performance.ifInErrors

       64 bit unsigned wrappable counter."
   ::= {pr1646v2EthPortSwIXt2InPEntry 134217728}

pr1646v2EthPortSwIXt2InPIfInUnkwn OBJECT-TYPE
   SYNTAX      Counter64
   MAX-ACCESS  read-only
   STATUS      current
   DESCRIPTION
      "Path: swPort.performance.h2Performance.ifInUnknownProtos

       64 bit unsigned wrappable counter."
   ::= {pr1646v2EthPortSwIXt2InPEntry 150994944}

pr1646v2EthPortSwIXt2InPInDropEx OBJECT-TYPE
   SYNTAX      Counter64
   MAX-ACCESS  read-only
   STATUS      current
   DESCRIPTION
      "Path: swPort.performance.h2Performance.ifInDropLevelExceeded

       64 bit unsigned wrappable counter."
   ::= {pr1646v2EthPortSwIXt2InPEntry 335544320}

pr1646v2EthPortSwIXt2InPInDropNoMac OBJECT-TYPE
   SYNTAX      Counter64
   MAX-ACCESS  read-only
   STATUS      current
   DESCRIPTION
      "Path: swPort.performance.h2Performance.fInDiscardsNoMacFit

       64 bit unsigned wrappable counter."
   ::= {pr1646v2EthPortSwIXt2InPEntry 301989888}

pr1646v2EthPortSwIXt2InPInDropNUCast OBJECT-TYPE
   SYNTAX      Counter64
   MAX-ACCESS  read-only
   STATUS      current
   DESCRIPTION
      "Path: swPort.performance.h2Performance.fInDiscardsNUCast

       64 bit unsigned wrappable counter."
   ::= {pr1646v2EthPortSwIXt2InPEntry 318767104}

pr1646v2EthPortSwIXt2InPInDropFilter OBJECT-TYPE
   SYNTAX      Counter64
   MAX-ACCESS  read-only
   STATUS      current
   DESCRIPTION
      "Path: swPort.performance.h2Performance.fInDiscardsFilter

       64 bit unsigned wrappable counter."
   ::= {pr1646v2EthPortSwIXt2InPEntry 385875968}

pr1646v2EthPortSwIXt2InPIfInBandwidth OBJECT-TYPE
   SYNTAX      Integer32
   MAX-ACCESS  read-only
   STATUS      current
   DESCRIPTION
      "Path: swPort.performance.h2Performance.ifInBandwidth

       unit name = bps
       formula = 8 * ; 8 /"
   ::= {pr1646v2EthPortSwIXt2InPEntry 268435456}

pr1646v2EthPortSwIXt2InPIfOutOctets OBJECT-TYPE
   SYNTAX      Counter64
   MAX-ACCESS  read-only
   STATUS      current
   DESCRIPTION
      "Path: swPort.performance.h2Performance.ifOutOctets

       64 bit unsigned wrappable counter."
   ::= {pr1646v2EthPortSwIXt2InPEntry 167772160}

pr1646v2EthPortSwIXt2InPIfOutUCPkts OBJECT-TYPE
   SYNTAX      Counter64
   MAX-ACCESS  read-only
   STATUS      current
   DESCRIPTION
      "Path: swPort.performance.h2Performance.ifOutUcastPkts

       64 bit unsigned wrappable counter."
   ::= {pr1646v2EthPortSwIXt2InPEntry 184549376}

pr1646v2EthPortSwIXt2InPIfOutNUCPkts OBJECT-TYPE
   SYNTAX      Counter64
   MAX-ACCESS  read-only
   STATUS      current
   DESCRIPTION
      "Path: swPort.performance.h2Performance.ifOutNUcastPkts

       64 bit unsigned wrappable counter."
   ::= {pr1646v2EthPortSwIXt2InPEntry 201326592}

pr1646v2EthPortSwIXt2InPIfOutBCPkts OBJECT-TYPE
   SYNTAX      Counter64
   MAX-ACCESS  read-only
   STATUS      current
   DESCRIPTION
      "Path: swPort.performance.h2Performance.ifOutBcastPkts

       64 bit unsigned wrappable counter."
   ::= {pr1646v2EthPortSwIXt2InPEntry 452984832}

pr1646v2EthPortSwIXt2InPIfOutMCPkts OBJECT-TYPE
   SYNTAX      Counter64
   MAX-ACCESS  read-only
   STATUS      current
   DESCRIPTION
      "Path: swPort.performance.h2Performance.ifOutMcastPkts

       64 bit unsigned wrappable counter."
   ::= {pr1646v2EthPortSwIXt2InPEntry 469762048}

pr1646v2EthPortSwIXt2InPIfOutDiscards OBJECT-TYPE
   SYNTAX      Counter64
   MAX-ACCESS  read-only
   STATUS      current
   DESCRIPTION
      "Path: swPort.performance.h2Performance.ifOutDiscards

       64 bit unsigned wrappable counter."
   ::= {pr1646v2EthPortSwIXt2InPEntry 218103808}

pr1646v2EthPortSwIXt2InPIfOutErrors OBJECT-TYPE
   SYNTAX      Counter64
   MAX-ACCESS  read-only
   STATUS      current
   DESCRIPTION
      "Path: swPort.performance.h2Performance.ifOutErrors

       64 bit unsigned wrappable counter."
   ::= {pr1646v2EthPortSwIXt2InPEntry 234881024}

pr1646v2EthPortSwIXt2InPOutDropEx OBJECT-TYPE
   SYNTAX      Counter64
   MAX-ACCESS  read-only
   STATUS      current
   DESCRIPTION
      "Path: swPort.performance.h2Performance.ifOutDropLevelExceeded

       64 bit unsigned wrappable counter."
   ::= {pr1646v2EthPortSwIXt2InPEntry 352321536}

pr1646v2EthPortSwIXt2InPOutDropNoArp OBJECT-TYPE
   SYNTAX      Counter64
   MAX-ACCESS  read-only
   STATUS      current
   DESCRIPTION
      "Path: swPort.performance.h2Performance.ifOutDiscardsNoArp

       64 bit unsigned wrappable counter."
   ::= {pr1646v2EthPortSwIXt2InPEntry 369098752}

pr1646v2EthPortSwIXt2InPOutDropFilter OBJECT-TYPE
   SYNTAX      Counter64
   MAX-ACCESS  read-only
   STATUS      current
   DESCRIPTION
      "Path: swPort.performance.h2Performance.ifOutDiscardsFilter

       64 bit unsigned wrappable counter."
   ::= {pr1646v2EthPortSwIXt2InPEntry 402653184}

pr1646v2EthPortSwIXt2InPIfOutBandwidth OBJECT-TYPE
   SYNTAX      Integer32
   MAX-ACCESS  read-only
   STATUS      current
   DESCRIPTION
      "Path: swPort.performance.h2Performance.ifOutBandwidth

       unit name = bps
       formula = 8 * ; 8 /"
   ::= {pr1646v2EthPortSwIXt2InPEntry 285212672}

pr1646v2EthPortSwIXt2InPIfErrSec OBJECT-TYPE
   SYNTAX      Counter32
   MAX-ACCESS  read-only
   STATUS      current
   DESCRIPTION
      "Path: swPort.performance.h2Performance.ifErrSec

       32 bit unsigned wrappable counter."
   ::= {pr1646v2EthPortSwIXt2InPEntry 251658240}


pr1646v2EthPortSwIXt2H24InP OBJECT IDENTIFIER ::= {pr1646v2EthPortSwIXt2 308}

pr1646v2EthPortSwIXt2H24InPSSCTable OBJECT-TYPE
   SYNTAX      SEQUENCE OF Pr1646v2EthPortSwIXt2H24InPEntry
   MAX-ACCESS  not-accessible
   STATUS      current
   DESCRIPTION
      "h24IfInPerformance"
   ::= {pr1646v2EthPortSwIXt2H24InP 1}

pr1646v2EthPortSwIXt2H24InPEntry OBJECT-TYPE
   SYNTAX      Pr1646v2EthPortSwIXt2H24InPEntry
   MAX-ACCESS  not-accessible
   STATUS      current
   DESCRIPTION
      ""
   INDEX      { pr1646v2EthPortSwIXt2H24InPGlobalIx,
                pr1646v2EthPortSwIXt2H24InPTableIx }
   ::= {pr1646v2EthPortSwIXt2H24InPSSCTable 1}

Pr1646v2EthPortSwIXt2H24InPEntry ::=
   SEQUENCE
      {
      pr1646v2EthPortSwIXt2H24InPGlobalIx
         GlobalIndex,
      pr1646v2EthPortSwIXt2H24InPTableIx
         TableIndex,
      pr1646v2EthPortSwIXt2H24InPSysUpTime
         TimeTicks,
      pr1646v2EthPortSwIXt2H24InPIfUpTime
         TimeTicks,
      pr1646v2EthPortSwIXt2H24InPIfStatChanges
         Counter32,
      pr1646v2EthPortSwIXt2H24InPIfInOctets
         Counter64,
      pr1646v2EthPortSwIXt2H24InPIfInUCPkts
         Counter64,
      pr1646v2EthPortSwIXt2H24InPIfInNUCPkts
         Counter64,
      pr1646v2EthPortSwIXt2H24InPIfInBCPkts
         Counter64,
      pr1646v2EthPortSwIXt2H24InPIfInMCPkts
         Counter64,
      pr1646v2EthPortSwIXt2H24InPIfInDiscards
         Counter64,
      pr1646v2EthPortSwIXt2H24InPIfInErrors
         Counter64,
      pr1646v2EthPortSwIXt2H24InPIfInUnkwn
         Counter64,
      pr1646v2EthPortSwIXt2H24InPInDropEx
         Counter64,
      pr1646v2EthPortSwIXt2H24InPInDropNoMac
         Counter64,
      pr1646v2EthPortSwIXt2H24InPInDropNUCast
         Counter64,
      pr1646v2EthPortSwIXt2H24InPInDropFilter
         Counter64,
      pr1646v2EthPortSwIXt2H24InPIfInBandwidth
         Integer32,
      pr1646v2EthPortSwIXt2H24InPIfOutOctets
         Counter64,
      pr1646v2EthPortSwIXt2H24InPIfOutUCPkts
         Counter64,
      pr1646v2EthPortSwIXt2H24InPIfOutNUCPkts
         Counter64,
      pr1646v2EthPortSwIXt2H24InPIfOutBCPkts
         Counter64,
      pr1646v2EthPortSwIXt2H24InPIfOutMCPkts
         Counter64,
      pr1646v2EthPortSwIXt2H24InPIfOutDiscards
         Counter64,
      pr1646v2EthPortSwIXt2H24InPIfOutErrors
         Counter64,
      pr1646v2EthPortSwIXt2H24InPOutDropEx
         Counter64,
      pr1646v2EthPortSwIXt2H24InPOutDropNoArp
         Counter64,
      pr1646v2EthPortSwIXt2H24InPOutDropFilter
         Counter64,
      pr1646v2EthPortSwIXt2H24InPIfOutBandwidth
         Integer32,
      pr1646v2EthPortSwIXt2H24InPIfErrSec
         Counter32
      }

pr1646v2EthPortSwIXt2H24InPGlobalIx OBJECT-TYPE
   SYNTAX      GlobalIndex
   MAX-ACCESS  not-accessible
   STATUS      current
   DESCRIPTION
      "The value of the tlsCntTreeGlobalIndex of the MANAGED OBJECT."
   ::= {pr1646v2EthPortSwIXt2H24InPEntry 10}

pr1646v2EthPortSwIXt2H24InPTableIx OBJECT-TYPE
   SYNTAX      TableIndex
   MAX-ACCESS  not-accessible
   STATUS      current
   DESCRIPTION
      ""
   ::= {pr1646v2EthPortSwIXt2H24InPEntry 11}

pr1646v2EthPortSwIXt2H24InPSysUpTime OBJECT-TYPE
   SYNTAX      TimeTicks
   MAX-ACCESS  read-only
   STATUS      current
   DESCRIPTION
      "Path: swPort.performance.h24Performance.sysUpTime

       Time in centi-second."
   ::= {pr1646v2EthPortSwIXt2H24InPEntry 16777216}

pr1646v2EthPortSwIXt2H24InPIfUpTime OBJECT-TYPE
   SYNTAX      TimeTicks
   MAX-ACCESS  read-only
   STATUS      current
   DESCRIPTION
      "Path: swPort.performance.h24Performance.ifUpTime

       Time in centi-second."
   ::= {pr1646v2EthPortSwIXt2H24InPEntry 33554432}

pr1646v2EthPortSwIXt2H24InPIfStatChanges OBJECT-TYPE
   SYNTAX      Counter32
   MAX-ACCESS  read-only
   STATUS      current
   DESCRIPTION
      "Path: swPort.performance.h24Performance.ifStatusChanges

       32 bit unsigned wrappable counter."
   ::= {pr1646v2EthPortSwIXt2H24InPEntry 50331648}

pr1646v2EthPortSwIXt2H24InPIfInOctets OBJECT-TYPE
   SYNTAX      Counter64
   MAX-ACCESS  read-only
   STATUS      current
   DESCRIPTION
      "Path: swPort.performance.h24Performance.ifInOctets

       64 bit unsigned wrappable counter."
   ::= {pr1646v2EthPortSwIXt2H24InPEntry 67108864}

pr1646v2EthPortSwIXt2H24InPIfInUCPkts OBJECT-TYPE
   SYNTAX      Counter64
   MAX-ACCESS  read-only
   STATUS      current
   DESCRIPTION
      "Path: swPort.performance.h24Performance.ifInUcastPkts

       64 bit unsigned wrappable counter."
   ::= {pr1646v2EthPortSwIXt2H24InPEntry 83886080}

pr1646v2EthPortSwIXt2H24InPIfInNUCPkts OBJECT-TYPE
   SYNTAX      Counter64
   MAX-ACCESS  read-only
   STATUS      current
   DESCRIPTION
      "Path: swPort.performance.h24Performance.ifInNUcastPkts

       64 bit unsigned wrappable counter."
   ::= {pr1646v2EthPortSwIXt2H24InPEntry 100663296}

pr1646v2EthPortSwIXt2H24InPIfInBCPkts OBJECT-TYPE
   SYNTAX      Counter64
   MAX-ACCESS  read-only
   STATUS      current
   DESCRIPTION
      "Path: swPort.performance.h24Performance.ifInBcastPkts

       64 bit unsigned wrappable counter."
   ::= {pr1646v2EthPortSwIXt2H24InPEntry 419430400}

pr1646v2EthPortSwIXt2H24InPIfInMCPkts OBJECT-TYPE
   SYNTAX      Counter64
   MAX-ACCESS  read-only
   STATUS      current
   DESCRIPTION
      "Path: swPort.performance.h24Performance.ifInMcastPkts

       64 bit unsigned wrappable counter."
   ::= {pr1646v2EthPortSwIXt2H24InPEntry 436207616}

pr1646v2EthPortSwIXt2H24InPIfInDiscards OBJECT-TYPE
   SYNTAX      Counter64
   MAX-ACCESS  read-only
   STATUS      current
   DESCRIPTION
      "Path: swPort.performance.h24Performance.ifInDiscards

       64 bit unsigned wrappable counter."
   ::= {pr1646v2EthPortSwIXt2H24InPEntry 117440512}

pr1646v2EthPortSwIXt2H24InPIfInErrors OBJECT-TYPE
   SYNTAX      Counter64
   MAX-ACCESS  read-only
   STATUS      current
   DESCRIPTION
      "Path: swPort.performance.h24Performance.ifInErrors

       64 bit unsigned wrappable counter."
   ::= {pr1646v2EthPortSwIXt2H24InPEntry 134217728}

pr1646v2EthPortSwIXt2H24InPIfInUnkwn OBJECT-TYPE
   SYNTAX      Counter64
   MAX-ACCESS  read-only
   STATUS      current
   DESCRIPTION
      "Path: swPort.performance.h24Performance.ifInUnknownProtos

       64 bit unsigned wrappable counter."
   ::= {pr1646v2EthPortSwIXt2H24InPEntry 150994944}

pr1646v2EthPortSwIXt2H24InPInDropEx OBJECT-TYPE
   SYNTAX      Counter64
   MAX-ACCESS  read-only
   STATUS      current
   DESCRIPTION
      "Path: swPort.performance.h24Performance.ifInDropLevelExceeded

       64 bit unsigned wrappable counter."
   ::= {pr1646v2EthPortSwIXt2H24InPEntry 335544320}

pr1646v2EthPortSwIXt2H24InPInDropNoMac OBJECT-TYPE
   SYNTAX      Counter64
   MAX-ACCESS  read-only
   STATUS      current
   DESCRIPTION
      "Path: swPort.performance.h24Performance.fInDiscardsNoMacFit

       64 bit unsigned wrappable counter."
   ::= {pr1646v2EthPortSwIXt2H24InPEntry 301989888}

pr1646v2EthPortSwIXt2H24InPInDropNUCast OBJECT-TYPE
   SYNTAX      Counter64
   MAX-ACCESS  read-only
   STATUS      current
   DESCRIPTION
      "Path: swPort.performance.h24Performance.fInDiscardsNUCast

       64 bit unsigned wrappable counter."
   ::= {pr1646v2EthPortSwIXt2H24InPEntry 318767104}

pr1646v2EthPortSwIXt2H24InPInDropFilter OBJECT-TYPE
   SYNTAX      Counter64
   MAX-ACCESS  read-only
   STATUS      current
   DESCRIPTION
      "Path: swPort.performance.h24Performance.fInDiscardsFilter

       64 bit unsigned wrappable counter."
   ::= {pr1646v2EthPortSwIXt2H24InPEntry 385875968}

pr1646v2EthPortSwIXt2H24InPIfInBandwidth OBJECT-TYPE
   SYNTAX      Integer32
   MAX-ACCESS  read-only
   STATUS      current
   DESCRIPTION
      "Path: swPort.performance.h24Performance.ifInBandwidth

       unit name = bps
       formula = 8 * ; 8 /"
   ::= {pr1646v2EthPortSwIXt2H24InPEntry 268435456}

pr1646v2EthPortSwIXt2H24InPIfOutOctets OBJECT-TYPE
   SYNTAX      Counter64
   MAX-ACCESS  read-only
   STATUS      current
   DESCRIPTION
      "Path: swPort.performance.h24Performance.ifOutOctets

       64 bit unsigned wrappable counter."
   ::= {pr1646v2EthPortSwIXt2H24InPEntry 167772160}

pr1646v2EthPortSwIXt2H24InPIfOutUCPkts OBJECT-TYPE
   SYNTAX      Counter64
   MAX-ACCESS  read-only
   STATUS      current
   DESCRIPTION
      "Path: swPort.performance.h24Performance.ifOutUcastPkts

       64 bit unsigned wrappable counter."
   ::= {pr1646v2EthPortSwIXt2H24InPEntry 184549376}

pr1646v2EthPortSwIXt2H24InPIfOutNUCPkts OBJECT-TYPE
   SYNTAX      Counter64
   MAX-ACCESS  read-only
   STATUS      current
   DESCRIPTION
      "Path: swPort.performance.h24Performance.ifOutNUcastPkts

       64 bit unsigned wrappable counter."
   ::= {pr1646v2EthPortSwIXt2H24InPEntry 201326592}

pr1646v2EthPortSwIXt2H24InPIfOutBCPkts OBJECT-TYPE
   SYNTAX      Counter64
   MAX-ACCESS  read-only
   STATUS      current
   DESCRIPTION
      "Path: swPort.performance.h24Performance.ifOutBcastPkts

       64 bit unsigned wrappable counter."
   ::= {pr1646v2EthPortSwIXt2H24InPEntry 452984832}

pr1646v2EthPortSwIXt2H24InPIfOutMCPkts OBJECT-TYPE
   SYNTAX      Counter64
   MAX-ACCESS  read-only
   STATUS      current
   DESCRIPTION
      "Path: swPort.performance.h24Performance.ifOutMcastPkts

       64 bit unsigned wrappable counter."
   ::= {pr1646v2EthPortSwIXt2H24InPEntry 469762048}

pr1646v2EthPortSwIXt2H24InPIfOutDiscards OBJECT-TYPE
   SYNTAX      Counter64
   MAX-ACCESS  read-only
   STATUS      current
   DESCRIPTION
      "Path: swPort.performance.h24Performance.ifOutDiscards

       64 bit unsigned wrappable counter."
   ::= {pr1646v2EthPortSwIXt2H24InPEntry 218103808}

pr1646v2EthPortSwIXt2H24InPIfOutErrors OBJECT-TYPE
   SYNTAX      Counter64
   MAX-ACCESS  read-only
   STATUS      current
   DESCRIPTION
      "Path: swPort.performance.h24Performance.ifOutErrors

       64 bit unsigned wrappable counter."
   ::= {pr1646v2EthPortSwIXt2H24InPEntry 234881024}

pr1646v2EthPortSwIXt2H24InPOutDropEx OBJECT-TYPE
   SYNTAX      Counter64
   MAX-ACCESS  read-only
   STATUS      current
   DESCRIPTION
      "Path: swPort.performance.h24Performance.ifOutDropLevelExceeded

       64 bit unsigned wrappable counter."
   ::= {pr1646v2EthPortSwIXt2H24InPEntry 352321536}

pr1646v2EthPortSwIXt2H24InPOutDropNoArp OBJECT-TYPE
   SYNTAX      Counter64
   MAX-ACCESS  read-only
   STATUS      current
   DESCRIPTION
      "Path: swPort.performance.h24Performance.ifOutDiscardsNoArp

       64 bit unsigned wrappable counter."
   ::= {pr1646v2EthPortSwIXt2H24InPEntry 369098752}

pr1646v2EthPortSwIXt2H24InPOutDropFilter OBJECT-TYPE
   SYNTAX      Counter64
   MAX-ACCESS  read-only
   STATUS      current
   DESCRIPTION
      "Path: swPort.performance.h24Performance.ifOutDiscardsFilter

       64 bit unsigned wrappable counter."
   ::= {pr1646v2EthPortSwIXt2H24InPEntry 402653184}

pr1646v2EthPortSwIXt2H24InPIfOutBandwidth OBJECT-TYPE
   SYNTAX      Integer32
   MAX-ACCESS  read-only
   STATUS      current
   DESCRIPTION
      "Path: swPort.performance.h24Performance.ifOutBandwidth

       unit name = bps
       formula = 8 * ; 8 /"
   ::= {pr1646v2EthPortSwIXt2H24InPEntry 285212672}

pr1646v2EthPortSwIXt2H24InPIfErrSec OBJECT-TYPE
   SYNTAX      Counter32
   MAX-ACCESS  read-only
   STATUS      current
   DESCRIPTION
      "Path: swPort.performance.h24Performance.ifErrSec

       32 bit unsigned wrappable counter."
   ::= {pr1646v2EthPortSwIXt2H24InPEntry 251658240}


pr1646v2EthPortSwIXt2D7InP OBJECT IDENTIFIER ::= {pr1646v2EthPortSwIXt2 309}

pr1646v2EthPortSwIXt2D7InPSSCTable OBJECT-TYPE
   SYNTAX      SEQUENCE OF Pr1646v2EthPortSwIXt2D7InPEntry
   MAX-ACCESS  not-accessible
   STATUS      current
   DESCRIPTION
      "d7IfInPerformance"
   ::= {pr1646v2EthPortSwIXt2D7InP 1}

pr1646v2EthPortSwIXt2D7InPEntry OBJECT-TYPE
   SYNTAX      Pr1646v2EthPortSwIXt2D7InPEntry
   MAX-ACCESS  not-accessible
   STATUS      current
   DESCRIPTION
      ""
   INDEX      { pr1646v2EthPortSwIXt2D7InPGlobalIx,
                pr1646v2EthPortSwIXt2D7InPTableIx }
   ::= {pr1646v2EthPortSwIXt2D7InPSSCTable 1}

Pr1646v2EthPortSwIXt2D7InPEntry ::=
   SEQUENCE
      {
      pr1646v2EthPortSwIXt2D7InPGlobalIx
         GlobalIndex,
      pr1646v2EthPortSwIXt2D7InPTableIx
         TableIndex,
      pr1646v2EthPortSwIXt2D7InPSysUpTime
         TimeTicks,
      pr1646v2EthPortSwIXt2D7InPIfUpTime
         TimeTicks,
      pr1646v2EthPortSwIXt2D7InPIfStatChanges
         Counter32,
      pr1646v2EthPortSwIXt2D7InPIfInOctets
         Counter64,
      pr1646v2EthPortSwIXt2D7InPIfInUCPkts
         Counter64,
      pr1646v2EthPortSwIXt2D7InPIfInNUCPkts
         Counter64,
      pr1646v2EthPortSwIXt2D7InPIfInBCPkts
         Counter64,
      pr1646v2EthPortSwIXt2D7InPIfInMCPkts
         Counter64,
      pr1646v2EthPortSwIXt2D7InPIfInDiscards
         Counter64,
      pr1646v2EthPortSwIXt2D7InPIfInErrors
         Counter64,
      pr1646v2EthPortSwIXt2D7InPIfInUnkwn
         Counter64,
      pr1646v2EthPortSwIXt2D7InPInDropEx
         Counter64,
      pr1646v2EthPortSwIXt2D7InPInDropNoMac
         Counter64,
      pr1646v2EthPortSwIXt2D7InPInDropNUCast
         Counter64,
      pr1646v2EthPortSwIXt2D7InPInDropFilter
         Counter64,
      pr1646v2EthPortSwIXt2D7InPIfInBandwidth
         Integer32,
      pr1646v2EthPortSwIXt2D7InPIfOutOctets
         Counter64,
      pr1646v2EthPortSwIXt2D7InPIfOutUCPkts
         Counter64,
      pr1646v2EthPortSwIXt2D7InPIfOutNUCPkts
         Counter64,
      pr1646v2EthPortSwIXt2D7InPIfOutBCPkts
         Counter64,
      pr1646v2EthPortSwIXt2D7InPIfOutMCPkts
         Counter64,
      pr1646v2EthPortSwIXt2D7InPIfOutDiscards
         Counter64,
      pr1646v2EthPortSwIXt2D7InPIfOutErrors
         Counter64,
      pr1646v2EthPortSwIXt2D7InPOutDropEx
         Counter64,
      pr1646v2EthPortSwIXt2D7InPOutDropNoArp
         Counter64,
      pr1646v2EthPortSwIXt2D7InPOutDropFilter
         Counter64,
      pr1646v2EthPortSwIXt2D7InPIfOutBandwidth
         Integer32,
      pr1646v2EthPortSwIXt2D7InPIfErrSec
         Counter32
      }

pr1646v2EthPortSwIXt2D7InPGlobalIx OBJECT-TYPE
   SYNTAX      GlobalIndex
   MAX-ACCESS  not-accessible
   STATUS      current
   DESCRIPTION
      "The value of the tlsCntTreeGlobalIndex of the MANAGED OBJECT."
   ::= {pr1646v2EthPortSwIXt2D7InPEntry 10}

pr1646v2EthPortSwIXt2D7InPTableIx OBJECT-TYPE
   SYNTAX      TableIndex
   MAX-ACCESS  not-accessible
   STATUS      current
   DESCRIPTION
      ""
   ::= {pr1646v2EthPortSwIXt2D7InPEntry 11}

pr1646v2EthPortSwIXt2D7InPSysUpTime OBJECT-TYPE
   SYNTAX      TimeTicks
   MAX-ACCESS  read-only
   STATUS      current
   DESCRIPTION
      "Path: swPort.performance.d7Performance.sysUpTime

       Time in centi-second."
   ::= {pr1646v2EthPortSwIXt2D7InPEntry 16777216}

pr1646v2EthPortSwIXt2D7InPIfUpTime OBJECT-TYPE
   SYNTAX      TimeTicks
   MAX-ACCESS  read-only
   STATUS      current
   DESCRIPTION
      "Path: swPort.performance.d7Performance.ifUpTime

       Time in centi-second."
   ::= {pr1646v2EthPortSwIXt2D7InPEntry 33554432}

pr1646v2EthPortSwIXt2D7InPIfStatChanges OBJECT-TYPE
   SYNTAX      Counter32
   MAX-ACCESS  read-only
   STATUS      current
   DESCRIPTION
      "Path: swPort.performance.d7Performance.ifStatusChanges

       32 bit unsigned wrappable counter."
   ::= {pr1646v2EthPortSwIXt2D7InPEntry 50331648}

pr1646v2EthPortSwIXt2D7InPIfInOctets OBJECT-TYPE
   SYNTAX      Counter64
   MAX-ACCESS  read-only
   STATUS      current
   DESCRIPTION
      "Path: swPort.performance.d7Performance.ifInOctets

       64 bit unsigned wrappable counter."
   ::= {pr1646v2EthPortSwIXt2D7InPEntry 67108864}

pr1646v2EthPortSwIXt2D7InPIfInUCPkts OBJECT-TYPE
   SYNTAX      Counter64
   MAX-ACCESS  read-only
   STATUS      current
   DESCRIPTION
      "Path: swPort.performance.d7Performance.ifInUcastPkts

       64 bit unsigned wrappable counter."
   ::= {pr1646v2EthPortSwIXt2D7InPEntry 83886080}

pr1646v2EthPortSwIXt2D7InPIfInNUCPkts OBJECT-TYPE
   SYNTAX      Counter64
   MAX-ACCESS  read-only
   STATUS      current
   DESCRIPTION
      "Path: swPort.performance.d7Performance.ifInNUcastPkts

       64 bit unsigned wrappable counter."
   ::= {pr1646v2EthPortSwIXt2D7InPEntry 100663296}

pr1646v2EthPortSwIXt2D7InPIfInBCPkts OBJECT-TYPE
   SYNTAX      Counter64
   MAX-ACCESS  read-only
   STATUS      current
   DESCRIPTION
      "Path: swPort.performance.d7Performance.ifInBcastPkts

       64 bit unsigned wrappable counter."
   ::= {pr1646v2EthPortSwIXt2D7InPEntry 419430400}

pr1646v2EthPortSwIXt2D7InPIfInMCPkts OBJECT-TYPE
   SYNTAX      Counter64
   MAX-ACCESS  read-only
   STATUS      current
   DESCRIPTION
      "Path: swPort.performance.d7Performance.ifInMcastPkts

       64 bit unsigned wrappable counter."
   ::= {pr1646v2EthPortSwIXt2D7InPEntry 436207616}

pr1646v2EthPortSwIXt2D7InPIfInDiscards OBJECT-TYPE
   SYNTAX      Counter64
   MAX-ACCESS  read-only
   STATUS      current
   DESCRIPTION
      "Path: swPort.performance.d7Performance.ifInDiscards

       64 bit unsigned wrappable counter."
   ::= {pr1646v2EthPortSwIXt2D7InPEntry 117440512}

pr1646v2EthPortSwIXt2D7InPIfInErrors OBJECT-TYPE
   SYNTAX      Counter64
   MAX-ACCESS  read-only
   STATUS      current
   DESCRIPTION
      "Path: swPort.performance.d7Performance.ifInErrors

       64 bit unsigned wrappable counter."
   ::= {pr1646v2EthPortSwIXt2D7InPEntry 134217728}

pr1646v2EthPortSwIXt2D7InPIfInUnkwn OBJECT-TYPE
   SYNTAX      Counter64
   MAX-ACCESS  read-only
   STATUS      current
   DESCRIPTION
      "Path: swPort.performance.d7Performance.ifInUnknownProtos

       64 bit unsigned wrappable counter."
   ::= {pr1646v2EthPortSwIXt2D7InPEntry 150994944}

pr1646v2EthPortSwIXt2D7InPInDropEx OBJECT-TYPE
   SYNTAX      Counter64
   MAX-ACCESS  read-only
   STATUS      current
   DESCRIPTION
      "Path: swPort.performance.d7Performance.ifInDropLevelExceeded

       64 bit unsigned wrappable counter."
   ::= {pr1646v2EthPortSwIXt2D7InPEntry 335544320}

pr1646v2EthPortSwIXt2D7InPInDropNoMac OBJECT-TYPE
   SYNTAX      Counter64
   MAX-ACCESS  read-only
   STATUS      current
   DESCRIPTION
      "Path: swPort.performance.d7Performance.fInDiscardsNoMacFit

       64 bit unsigned wrappable counter."
   ::= {pr1646v2EthPortSwIXt2D7InPEntry 301989888}

pr1646v2EthPortSwIXt2D7InPInDropNUCast OBJECT-TYPE
   SYNTAX      Counter64
   MAX-ACCESS  read-only
   STATUS      current
   DESCRIPTION
      "Path: swPort.performance.d7Performance.fInDiscardsNUCast

       64 bit unsigned wrappable counter."
   ::= {pr1646v2EthPortSwIXt2D7InPEntry 318767104}

pr1646v2EthPortSwIXt2D7InPInDropFilter OBJECT-TYPE
   SYNTAX      Counter64
   MAX-ACCESS  read-only
   STATUS      current
   DESCRIPTION
      "Path: swPort.performance.d7Performance.fInDiscardsFilter

       64 bit unsigned wrappable counter."
   ::= {pr1646v2EthPortSwIXt2D7InPEntry 385875968}

pr1646v2EthPortSwIXt2D7InPIfInBandwidth OBJECT-TYPE
   SYNTAX      Integer32
   MAX-ACCESS  read-only
   STATUS      current
   DESCRIPTION
      "Path: swPort.performance.d7Performance.ifInBandwidth

       unit name = bps
       formula = 8 * ; 8 /"
   ::= {pr1646v2EthPortSwIXt2D7InPEntry 268435456}

pr1646v2EthPortSwIXt2D7InPIfOutOctets OBJECT-TYPE
   SYNTAX      Counter64
   MAX-ACCESS  read-only
   STATUS      current
   DESCRIPTION
      "Path: swPort.performance.d7Performance.ifOutOctets

       64 bit unsigned wrappable counter."
   ::= {pr1646v2EthPortSwIXt2D7InPEntry 167772160}

pr1646v2EthPortSwIXt2D7InPIfOutUCPkts OBJECT-TYPE
   SYNTAX      Counter64
   MAX-ACCESS  read-only
   STATUS      current
   DESCRIPTION
      "Path: swPort.performance.d7Performance.ifOutUcastPkts

       64 bit unsigned wrappable counter."
   ::= {pr1646v2EthPortSwIXt2D7InPEntry 184549376}

pr1646v2EthPortSwIXt2D7InPIfOutNUCPkts OBJECT-TYPE
   SYNTAX      Counter64
   MAX-ACCESS  read-only
   STATUS      current
   DESCRIPTION
      "Path: swPort.performance.d7Performance.ifOutNUcastPkts

       64 bit unsigned wrappable counter."
   ::= {pr1646v2EthPortSwIXt2D7InPEntry 201326592}

pr1646v2EthPortSwIXt2D7InPIfOutBCPkts OBJECT-TYPE
   SYNTAX      Counter64
   MAX-ACCESS  read-only
   STATUS      current
   DESCRIPTION
      "Path: swPort.performance.d7Performance.ifOutBcastPkts

       64 bit unsigned wrappable counter."
   ::= {pr1646v2EthPortSwIXt2D7InPEntry 452984832}

pr1646v2EthPortSwIXt2D7InPIfOutMCPkts OBJECT-TYPE
   SYNTAX      Counter64
   MAX-ACCESS  read-only
   STATUS      current
   DESCRIPTION
      "Path: swPort.performance.d7Performance.ifOutMcastPkts

       64 bit unsigned wrappable counter."
   ::= {pr1646v2EthPortSwIXt2D7InPEntry 469762048}

pr1646v2EthPortSwIXt2D7InPIfOutDiscards OBJECT-TYPE
   SYNTAX      Counter64
   MAX-ACCESS  read-only
   STATUS      current
   DESCRIPTION
      "Path: swPort.performance.d7Performance.ifOutDiscards

       64 bit unsigned wrappable counter."
   ::= {pr1646v2EthPortSwIXt2D7InPEntry 218103808}

pr1646v2EthPortSwIXt2D7InPIfOutErrors OBJECT-TYPE
   SYNTAX      Counter64
   MAX-ACCESS  read-only
   STATUS      current
   DESCRIPTION
      "Path: swPort.performance.d7Performance.ifOutErrors

       64 bit unsigned wrappable counter."
   ::= {pr1646v2EthPortSwIXt2D7InPEntry 234881024}

pr1646v2EthPortSwIXt2D7InPOutDropEx OBJECT-TYPE
   SYNTAX      Counter64
   MAX-ACCESS  read-only
   STATUS      current
   DESCRIPTION
      "Path: swPort.performance.d7Performance.ifOutDropLevelExceeded

       64 bit unsigned wrappable counter."
   ::= {pr1646v2EthPortSwIXt2D7InPEntry 352321536}

pr1646v2EthPortSwIXt2D7InPOutDropNoArp OBJECT-TYPE
   SYNTAX      Counter64
   MAX-ACCESS  read-only
   STATUS      current
   DESCRIPTION
      "Path: swPort.performance.d7Performance.ifOutDiscardsNoArp

       64 bit unsigned wrappable counter."
   ::= {pr1646v2EthPortSwIXt2D7InPEntry 369098752}

pr1646v2EthPortSwIXt2D7InPOutDropFilter OBJECT-TYPE
   SYNTAX      Counter64
   MAX-ACCESS  read-only
   STATUS      current
   DESCRIPTION
      "Path: swPort.performance.d7Performance.ifOutDiscardsFilter

       64 bit unsigned wrappable counter."
   ::= {pr1646v2EthPortSwIXt2D7InPEntry 402653184}

pr1646v2EthPortSwIXt2D7InPIfOutBandwidth OBJECT-TYPE
   SYNTAX      Integer32
   MAX-ACCESS  read-only
   STATUS      current
   DESCRIPTION
      "Path: swPort.performance.d7Performance.ifOutBandwidth

       unit name = bps
       formula = 8 * ; 8 /"
   ::= {pr1646v2EthPortSwIXt2D7InPEntry 285212672}

pr1646v2EthPortSwIXt2D7InPIfErrSec OBJECT-TYPE
   SYNTAX      Counter32
   MAX-ACCESS  read-only
   STATUS      current
   DESCRIPTION
      "Path: swPort.performance.d7Performance.ifErrSec

       32 bit unsigned wrappable counter."
   ::= {pr1646v2EthPortSwIXt2D7InPEntry 251658240}


pr1646v2EthPortSwIXt2Oam OBJECT IDENTIFIER ::= {pr1646v2EthPortSwIXt2 910}

pr1646v2EthPortSwIXt2OamSSCTable OBJECT-TYPE
   SYNTAX      SEQUENCE OF Pr1646v2EthPortSwIXt2OamEntry
   MAX-ACCESS  not-accessible
   STATUS      current
   DESCRIPTION
      "OAM statistics"
   ::= {pr1646v2EthPortSwIXt2Oam 1}

pr1646v2EthPortSwIXt2OamEntry OBJECT-TYPE
   SYNTAX      Pr1646v2EthPortSwIXt2OamEntry
   MAX-ACCESS  not-accessible
   STATUS      current
   DESCRIPTION
      ""
   INDEX      { pr1646v2EthPortSwIXt2OamGlobalIx }
   ::= {pr1646v2EthPortSwIXt2OamSSCTable 1}

Pr1646v2EthPortSwIXt2OamEntry ::=
   SEQUENCE
      {
      pr1646v2EthPortSwIXt2OamGlobalIx
         GlobalIndex,
      pr1646v2EthPortSwIXt2OamInformationTx
         Counter32,
      pr1646v2EthPortSwIXt2OamInformationRx
         Counter32,
      pr1646v2EthPortSwIXt2OamUniqueEventNotifTx
         Counter32,
      pr1646v2EthPortSwIXt2OamUniqueEventNotifRx
         Counter32,
      pr1646v2EthPortSwIXt2OamLoopbackCtrlTx
         Counter32,
      pr1646v2EthPortSwIXt2OamLoopbackCtrlRx
         Counter32,
      pr1646v2EthPortSwIXt2OamVarReqTx
         Counter32,
      pr1646v2EthPortSwIXt2OamVarReqRx
         Counter32,
      pr1646v2EthPortSwIXt2OamVarRespTx
         Counter32,
      pr1646v2EthPortSwIXt2OamVarRespRx
         Counter32,
      pr1646v2EthPortSwIXt2OamOrgSpecificTx
         Counter32,
      pr1646v2EthPortSwIXt2OamOrgSpecificRx
         Counter32,
      pr1646v2EthPortSwIXt2OamUnsupportedCodesTx
         Counter32,
      pr1646v2EthPortSwIXt2OamUnsupportedCodesRx
         Counter32,
      pr1646v2EthPortSwIXt2OamPduDiscardRx
         Counter32,
      pr1646v2EthPortSwIXt2OamDataDiscardTx
         Counter32,
      pr1646v2EthPortSwIXt2OamDataDiscardRx
         Counter32
      }

pr1646v2EthPortSwIXt2OamGlobalIx OBJECT-TYPE
   SYNTAX      GlobalIndex
   MAX-ACCESS  not-accessible
   STATUS      current
   DESCRIPTION
      "The value of the tlsCntTreeGlobalIndex of the MANAGED OBJECT."
   ::= {pr1646v2EthPortSwIXt2OamEntry 10}

pr1646v2EthPortSwIXt2OamInformationTx OBJECT-TYPE
   SYNTAX      Counter32
   MAX-ACCESS  read-only
   STATUS      current
   DESCRIPTION
      "Path: swPort.performance.oam.informationTx

       32 bit unsigned wrappable counter."
   ::= {pr1646v2EthPortSwIXt2OamEntry 16777216}

pr1646v2EthPortSwIXt2OamInformationRx OBJECT-TYPE
   SYNTAX      Counter32
   MAX-ACCESS  read-only
   STATUS      current
   DESCRIPTION
      "Path: swPort.performance.oam.informationRx

       32 bit unsigned wrappable counter."
   ::= {pr1646v2EthPortSwIXt2OamEntry 33554432}

pr1646v2EthPortSwIXt2OamUniqueEventNotifTx OBJECT-TYPE
   SYNTAX      Counter32
   MAX-ACCESS  read-only
   STATUS      current
   DESCRIPTION
      "Path: swPort.performance.oam.uniqueEventNotifTx

       32 bit unsigned wrappable counter."
   ::= {pr1646v2EthPortSwIXt2OamEntry 50331648}

pr1646v2EthPortSwIXt2OamUniqueEventNotifRx OBJECT-TYPE
   SYNTAX      Counter32
   MAX-ACCESS  read-only
   STATUS      current
   DESCRIPTION
      "Path: swPort.performance.oam.uniqueEventNotifRx

       32 bit unsigned wrappable counter."
   ::= {pr1646v2EthPortSwIXt2OamEntry 67108864}

pr1646v2EthPortSwIXt2OamLoopbackCtrlTx OBJECT-TYPE
   SYNTAX      Counter32
   MAX-ACCESS  read-only
   STATUS      current
   DESCRIPTION
      "Path: swPort.performance.oam.loopbackCtrlTx

       32 bit unsigned wrappable counter."
   ::= {pr1646v2EthPortSwIXt2OamEntry 117440512}

pr1646v2EthPortSwIXt2OamLoopbackCtrlRx OBJECT-TYPE
   SYNTAX      Counter32
   MAX-ACCESS  read-only
   STATUS      current
   DESCRIPTION
      "Path: swPort.performance.oam.loopbackCtrlRx

       32 bit unsigned wrappable counter."
   ::= {pr1646v2EthPortSwIXt2OamEntry 134217728}

pr1646v2EthPortSwIXt2OamVarReqTx OBJECT-TYPE
   SYNTAX      Counter32
   MAX-ACCESS  read-only
   STATUS      current
   DESCRIPTION
      "Path: swPort.performance.oam.varReqTx

       32 bit unsigned wrappable counter."
   ::= {pr1646v2EthPortSwIXt2OamEntry 150994944}

pr1646v2EthPortSwIXt2OamVarReqRx OBJECT-TYPE
   SYNTAX      Counter32
   MAX-ACCESS  read-only
   STATUS      current
   DESCRIPTION
      "Path: swPort.performance.oam.varReqRx

       32 bit unsigned wrappable counter."
   ::= {pr1646v2EthPortSwIXt2OamEntry 167772160}

pr1646v2EthPortSwIXt2OamVarRespTx OBJECT-TYPE
   SYNTAX      Counter32
   MAX-ACCESS  read-only
   STATUS      current
   DESCRIPTION
      "Path: swPort.performance.oam.varRespTx

       32 bit unsigned wrappable counter."
   ::= {pr1646v2EthPortSwIXt2OamEntry 184549376}

pr1646v2EthPortSwIXt2OamVarRespRx OBJECT-TYPE
   SYNTAX      Counter32
   MAX-ACCESS  read-only
   STATUS      current
   DESCRIPTION
      "Path: swPort.performance.oam.varRespRx

       32 bit unsigned wrappable counter."
   ::= {pr1646v2EthPortSwIXt2OamEntry 201326592}

pr1646v2EthPortSwIXt2OamOrgSpecificTx OBJECT-TYPE
   SYNTAX      Counter32
   MAX-ACCESS  read-only
   STATUS      current
   DESCRIPTION
      "Path: swPort.performance.oam.orgSpecificTx

       32 bit unsigned wrappable counter."
   ::= {pr1646v2EthPortSwIXt2OamEntry 218103808}

pr1646v2EthPortSwIXt2OamOrgSpecificRx OBJECT-TYPE
   SYNTAX      Counter32
   MAX-ACCESS  read-only
   STATUS      current
   DESCRIPTION
      "Path: swPort.performance.oam.orgSpecificRx

       32 bit unsigned wrappable counter."
   ::= {pr1646v2EthPortSwIXt2OamEntry 234881024}

pr1646v2EthPortSwIXt2OamUnsupportedCodesTx OBJECT-TYPE
   SYNTAX      Counter32
   MAX-ACCESS  read-only
   STATUS      current
   DESCRIPTION
      "Path: swPort.performance.oam.unsupportedCodesTx

       32 bit unsigned wrappable counter."
   ::= {pr1646v2EthPortSwIXt2OamEntry 251658240}

pr1646v2EthPortSwIXt2OamUnsupportedCodesRx OBJECT-TYPE
   SYNTAX      Counter32
   MAX-ACCESS  read-only
   STATUS      current
   DESCRIPTION
      "Path: swPort.performance.oam.unsupportedCodesRx

       32 bit unsigned wrappable counter."
   ::= {pr1646v2EthPortSwIXt2OamEntry 268435456}

pr1646v2EthPortSwIXt2OamPduDiscardRx OBJECT-TYPE
   SYNTAX      Counter32
   MAX-ACCESS  read-only
   STATUS      current
   DESCRIPTION
      "Path: swPort.performance.oam.pduDiscardRx

       32 bit unsigned wrappable counter."
   ::= {pr1646v2EthPortSwIXt2OamEntry 1694498816}

pr1646v2EthPortSwIXt2OamDataDiscardTx OBJECT-TYPE
   SYNTAX      Counter32
   MAX-ACCESS  read-only
   STATUS      current
   DESCRIPTION
      "Path: swPort.performance.oam.dataDiscardTx

       32 bit unsigned wrappable counter."
   ::= {pr1646v2EthPortSwIXt2OamEntry 1711276032}

pr1646v2EthPortSwIXt2OamDataDiscardRx OBJECT-TYPE
   SYNTAX      Counter32
   MAX-ACCESS  read-only
   STATUS      current
   DESCRIPTION
      "Path: swPort.performance.oam.dataDiscardRx

       32 bit unsigned wrappable counter."
   ::= {pr1646v2EthPortSwIXt2OamEntry 1728053248}


pr1646v2EthPortSwIXt2Vlan OBJECT IDENTIFIER ::= {pr1646v2EthPortSwIXt2 310}

pr1646v2EthPortSwIXt2VlanSSCTable OBJECT-TYPE
   SYNTAX      SEQUENCE OF Pr1646v2EthPortSwIXt2VlanEntry
   MAX-ACCESS  not-accessible
   STATUS      current
   DESCRIPTION
      ""
   ::= {pr1646v2EthPortSwIXt2Vlan 1}

pr1646v2EthPortSwIXt2VlanEntry OBJECT-TYPE
   SYNTAX      Pr1646v2EthPortSwIXt2VlanEntry
   MAX-ACCESS  not-accessible
   STATUS      current
   DESCRIPTION
      ""
   INDEX      { pr1646v2EthPortSwIXt2VlanGlobalIx,
                pr1646v2EthPortSwIXt2VlanTableIx }
   ::= {pr1646v2EthPortSwIXt2VlanSSCTable 1}

Pr1646v2EthPortSwIXt2VlanEntry ::=
   SEQUENCE
      {
      pr1646v2EthPortSwIXt2VlanGlobalIx
         GlobalIndex,
      pr1646v2EthPortSwIXt2VlanTableIx
         TableIndex,
      pr1646v2EthPortSwIXt2VlanName
         DisplayString,
      pr1646v2EthPortSwIXt2VlanMCInOctets
         Counter64,
      pr1646v2EthPortSwIXt2VlanMCInUcast
         Counter64,
      pr1646v2EthPortSwIXt2VlanMCInNUcastPkts
         Counter64,
      pr1646v2EthPortSwIXt2VlanMCInBcastPkts
         Counter64,
      pr1646v2EthPortSwIXt2VlanMCInMcastPkts
         Counter64,
      pr1646v2EthPortSwIXt2VlanMCInDiscards
         Counter64,
      pr1646v2EthPortSwIXt2VlanMCInErrors
         Counter64,
      pr1646v2EthPortSwIXt2VlanMCInUnknownProtos
         Counter64,
      pr1646v2EthPortSwIXt2VlanMCInDropEx
         Counter64,
      pr1646v2EthPortSwIXt2VlanMCInDropNoMac
         Counter64,
      pr1646v2EthPortSwIXt2VlanMCInDropNUCast
         Counter64,
      pr1646v2EthPortSwIXt2VlanMCInDropFilter
         Counter64,
      pr1646v2EthPortSwIXt2VlanMCInBandwidth15sec
         Integer32,
      pr1646v2EthPortSwIXt2VlanMCInBandwidth30sec
         Integer32,
      pr1646v2EthPortSwIXt2VlanMCInBandwidth1min
         Integer32,
      pr1646v2EthPortSwIXt2VlanMCInBandwidth2min
         Integer32,
      pr1646v2EthPortSwIXt2VlanMCInBandwidth5min
         Integer32,
      pr1646v2EthPortSwIXt2VlanMCOutOctets
         Counter64,
      pr1646v2EthPortSwIXt2VlanMCOutUcastPkts
         Counter64,
      pr1646v2EthPortSwIXt2VlanMCOutNUcastPkts
         Counter64,
      pr1646v2EthPortSwIXt2VlanMCOutBcastPkts
         Counter64,
      pr1646v2EthPortSwIXt2VlanMCOutMcastPkts
         Counter64,
      pr1646v2EthPortSwIXt2VlanMCOutDiscards
         Counter64,
      pr1646v2EthPortSwIXt2VlanMCOutErrors
         Counter64,
      pr1646v2EthPortSwIXt2VlanMCOutQLen
         Counter32,
      pr1646v2EthPortSwIXt2VlanMCOutDropEx
         Counter64,
      pr1646v2EthPortSwIXt2VlanMCOutDropNoArp
         Counter64,
      pr1646v2EthPortSwIXt2VlanMCOutDropFilter
         Counter64,
      pr1646v2EthPortSwIXt2VlanMCOutBandwidth15sec
         Integer32,
      pr1646v2EthPortSwIXt2VlanMCOutBandwidth30sec
         Integer32,
      pr1646v2EthPortSwIXt2VlanMCOutBandwidth1min
         Integer32,
      pr1646v2EthPortSwIXt2VlanMCOutBandwidth2min
         Integer32,
      pr1646v2EthPortSwIXt2VlanMCOutBandwidth5min
         Integer32,
      pr1646v2EthPortSwIXt2VlanVlanVid
         Integer32,
      pr1646v2EthPortSwIXt2VlanPppLinkMonitoringRequestsSent
         Gauge32,
      pr1646v2EthPortSwIXt2VlanPppLinkMonitoringRepliesRcvd
         Gauge32,
      pr1646v2EthPortSwIXt2VlanPppLinkMonitoringRequestsRcvd
         Gauge32,
      pr1646v2EthPortSwIXt2VlanPppLinkMonitoringRepliesSent
         Gauge32
      }

pr1646v2EthPortSwIXt2VlanGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanEntry 10}

pr1646v2EthPortSwIXt2VlanTableIx OBJECT-TYPE
   SYNTAX      TableIndex
   MAX-ACCESS  not-accessible
   STATUS      current
   DESCRIPTION
      ""
   ::= {pr1646v2EthPortSwIXt2VlanEntry 11}

pr1646v2EthPortSwIXt2VlanName OBJECT-TYPE
   SYNTAX      DisplayString
   MAX-ACCESS  read-only
   STATUS      current
   DESCRIPTION
      "Path: swPort.performance.vlan.name"
   ::= {pr1646v2EthPortSwIXt2VlanEntry 16777216}

pr1646v2EthPortSwIXt2VlanMCInOctets OBJECT-TYPE
   SYNTAX      Counter64
   MAX-ACCESS  read-only
   STATUS      current
   DESCRIPTION
      "Path: swPort.performance.vlan.mibCounters.ifInOctets

       64 bit unsigned wrappable counter."
   ::= {pr1646v2EthPortSwIXt2VlanEntry 40697856}

pr1646v2EthPortSwIXt2VlanMCInUcast OBJECT-TYPE
   SYNTAX      Counter64
   MAX-ACCESS  read-only
   STATUS      current
   DESCRIPTION
      "Path: swPort.performance.vlan.mibCounters.ifInUcastPkts

       64 bit unsigned wrappable counter."
   ::= {pr1646v2EthPortSwIXt2VlanEntry 40763392}

pr1646v2EthPortSwIXt2VlanMCInNUcastPkts OBJECT-TYPE
   SYNTAX      Counter64
   MAX-ACCESS  read-only
   STATUS      current
   DESCRIPTION
      "Path: swPort.performance.vlan.mibCounters.ifInNUcastPkts

       64 bit unsigned wrappable counter."
   ::= {pr1646v2EthPortSwIXt2VlanEntry 40828928}

pr1646v2EthPortSwIXt2VlanMCInBcastPkts OBJECT-TYPE
   SYNTAX      Counter64
   MAX-ACCESS  read-only
   STATUS      current
   DESCRIPTION
      "Path: swPort.performance.vlan.mibCounters.ifInBcastPkts

       64 bit unsigned wrappable counter."
   ::= {pr1646v2EthPortSwIXt2VlanEntry 47382528}

pr1646v2EthPortSwIXt2VlanMCInMcastPkts OBJECT-TYPE
   SYNTAX      Counter64
   MAX-ACCESS  read-only
   STATUS      current
   DESCRIPTION
      "Path: swPort.performance.vlan.mibCounters.ifInMcastPkts

       64 bit unsigned wrappable counter."
   ::= {pr1646v2EthPortSwIXt2VlanEntry 48037888}

pr1646v2EthPortSwIXt2VlanMCInDiscards OBJECT-TYPE
   SYNTAX      Counter64
   MAX-ACCESS  read-only
   STATUS      current
   DESCRIPTION
      "Path: swPort.performance.vlan.mibCounters.ifInDiscards

       64 bit unsigned wrappable counter."
   ::= {pr1646v2EthPortSwIXt2VlanEntry 40894464}

pr1646v2EthPortSwIXt2VlanMCInErrors OBJECT-TYPE
   SYNTAX      Counter64
   MAX-ACCESS  read-only
   STATUS      current
   DESCRIPTION
      "Path: swPort.performance.vlan.mibCounters.ifInErrors

       64 bit unsigned wrappable counter."
   ::= {pr1646v2EthPortSwIXt2VlanEntry 40960000}

pr1646v2EthPortSwIXt2VlanMCInUnknownProtos OBJECT-TYPE
   SYNTAX      Counter64
   MAX-ACCESS  read-only
   STATUS      current
   DESCRIPTION
      "Path: swPort.performance.vlan.mibCounters.ifInUnknownProtos

       64 bit unsigned wrappable counter."
   ::= {pr1646v2EthPortSwIXt2VlanEntry 41025536}

pr1646v2EthPortSwIXt2VlanMCInDropEx OBJECT-TYPE
   SYNTAX      Counter64
   MAX-ACCESS  read-only
   STATUS      current
   DESCRIPTION
      "Path: swPort.performance.vlan.mibCounters.ifInDropLevelExceeded

       64 bit unsigned wrappable counter."
   ::= {pr1646v2EthPortSwIXt2VlanEntry 42074112}

pr1646v2EthPortSwIXt2VlanMCInDropNoMac OBJECT-TYPE
   SYNTAX      Counter64
   MAX-ACCESS  read-only
   STATUS      current
   DESCRIPTION
      "Path: swPort.performance.vlan.mibCounters.ifInDiscardsNoMacFit

       64 bit unsigned wrappable counter."
   ::= {pr1646v2EthPortSwIXt2VlanEntry 42270720}

pr1646v2EthPortSwIXt2VlanMCInDropNUCast OBJECT-TYPE
   SYNTAX      Counter64
   MAX-ACCESS  read-only
   STATUS      current
   DESCRIPTION
      "Path: swPort.performance.vlan.mibCounters.ifInDiscardsNUCast

       64 bit unsigned wrappable counter."
   ::= {pr1646v2EthPortSwIXt2VlanEntry 42467328}

pr1646v2EthPortSwIXt2VlanMCInDropFilter OBJECT-TYPE
   SYNTAX      Counter64
   MAX-ACCESS  read-only
   STATUS      current
   DESCRIPTION
      "Path: swPort.performance.vlan.mibCounters.ifInDiscardsFilter

       64 bit unsigned wrappable counter."
   ::= {pr1646v2EthPortSwIXt2VlanEntry 42532864}

pr1646v2EthPortSwIXt2VlanMCInBandwidth15sec OBJECT-TYPE
   SYNTAX      Integer32
   MAX-ACCESS  read-only
   STATUS      current
   DESCRIPTION
      "Path: swPort.performance.vlan.mibCounters.ifInBandwidth.15sec

       unit name = bps
       formula = 8 * ; 8 /"
   ::= {pr1646v2EthPortSwIXt2VlanEntry 45417728}

pr1646v2EthPortSwIXt2VlanMCInBandwidth30sec OBJECT-TYPE
   SYNTAX      Integer32
   MAX-ACCESS  read-only
   STATUS      current
   DESCRIPTION
      "Path: swPort.performance.vlan.mibCounters.ifInBandwidth.30sec

       unit name = bps
       formula = 8 * ; 8 /"
   ::= {pr1646v2EthPortSwIXt2VlanEntry 45419008}

pr1646v2EthPortSwIXt2VlanMCInBandwidth1min OBJECT-TYPE
   SYNTAX      Integer32
   MAX-ACCESS  read-only
   STATUS      current
   DESCRIPTION
      "Path: swPort.performance.vlan.mibCounters.ifInBandwidth.1min

       unit name = bps
       formula = 8 * ; 8 /"
   ::= {pr1646v2EthPortSwIXt2VlanEntry 45421568}

pr1646v2EthPortSwIXt2VlanMCInBandwidth2min OBJECT-TYPE
   SYNTAX      Integer32
   MAX-ACCESS  read-only
   STATUS      current
   DESCRIPTION
      "Path: swPort.performance.vlan.mibCounters.ifInBandwidth.2min

       unit name = bps
       formula = 8 * ; 8 /"
   ::= {pr1646v2EthPortSwIXt2VlanEntry 45426688}

pr1646v2EthPortSwIXt2VlanMCInBandwidth5min OBJECT-TYPE
   SYNTAX      Integer32
   MAX-ACCESS  read-only
   STATUS      current
   DESCRIPTION
      "Path: swPort.performance.vlan.mibCounters.ifInBandwidth.5min

       unit name = bps
       formula = 8 * ; 8 /"
   ::= {pr1646v2EthPortSwIXt2VlanEntry 45442048}

pr1646v2EthPortSwIXt2VlanMCOutOctets OBJECT-TYPE
   SYNTAX      Counter64
   MAX-ACCESS  read-only
   STATUS      current
   DESCRIPTION
      "Path: swPort.performance.vlan.mibCounters.ifOutOctets

       64 bit unsigned wrappable counter."
   ::= {pr1646v2EthPortSwIXt2VlanEntry 41091072}

pr1646v2EthPortSwIXt2VlanMCOutUcastPkts OBJECT-TYPE
   SYNTAX      Counter64
   MAX-ACCESS  read-only
   STATUS      current
   DESCRIPTION
      "Path: swPort.performance.vlan.mibCounters.ifOutUcastPkts

       64 bit unsigned wrappable counter."
   ::= {pr1646v2EthPortSwIXt2VlanEntry 41156608}

pr1646v2EthPortSwIXt2VlanMCOutNUcastPkts OBJECT-TYPE
   SYNTAX      Counter64
   MAX-ACCESS  read-only
   STATUS      current
   DESCRIPTION
      "Path: swPort.performance.vlan.mibCounters.ifOutNUcastPkts

       64 bit unsigned wrappable counter."
   ::= {pr1646v2EthPortSwIXt2VlanEntry 41222144}

pr1646v2EthPortSwIXt2VlanMCOutBcastPkts OBJECT-TYPE
   SYNTAX      Counter64
   MAX-ACCESS  read-only
   STATUS      current
   DESCRIPTION
      "Path: swPort.performance.vlan.mibCounters.ifOutBcastPkts

       64 bit unsigned wrappable counter."
   ::= {pr1646v2EthPortSwIXt2VlanEntry 47775744}

pr1646v2EthPortSwIXt2VlanMCOutMcastPkts OBJECT-TYPE
   SYNTAX      Counter64
   MAX-ACCESS  read-only
   STATUS      current
   DESCRIPTION
      "Path: swPort.performance.vlan.mibCounters.ifOutMcastPkts

       64 bit unsigned wrappable counter."
   ::= {pr1646v2EthPortSwIXt2VlanEntry 48431104}

pr1646v2EthPortSwIXt2VlanMCOutDiscards OBJECT-TYPE
   SYNTAX      Counter64
   MAX-ACCESS  read-only
   STATUS      current
   DESCRIPTION
      "Path: swPort.performance.vlan.mibCounters.ifOutDiscards

       64 bit unsigned wrappable counter."
   ::= {pr1646v2EthPortSwIXt2VlanEntry 41287680}

pr1646v2EthPortSwIXt2VlanMCOutErrors OBJECT-TYPE
   SYNTAX      Counter64
   MAX-ACCESS  read-only
   STATUS      current
   DESCRIPTION
      "Path: swPort.performance.vlan.mibCounters.ifOutErrors

       64 bit unsigned wrappable counter."
   ::= {pr1646v2EthPortSwIXt2VlanEntry 41353216}

pr1646v2EthPortSwIXt2VlanMCOutQLen OBJECT-TYPE
   SYNTAX      Counter32
   MAX-ACCESS  read-only
   STATUS      current
   DESCRIPTION
      "Path: swPort.performance.vlan.mibCounters.ifOutQLen

       32 bit unsigned wrappable counter."
   ::= {pr1646v2EthPortSwIXt2VlanEntry 41418752}

pr1646v2EthPortSwIXt2VlanMCOutDropEx OBJECT-TYPE
   SYNTAX      Counter64
   MAX-ACCESS  read-only
   STATUS      current
   DESCRIPTION
      "Path: swPort.performance.vlan.mibCounters.ifOutDropLevelExceeded

       64 bit unsigned wrappable counter."
   ::= {pr1646v2EthPortSwIXt2VlanEntry 41484288}

pr1646v2EthPortSwIXt2VlanMCOutDropNoArp OBJECT-TYPE
   SYNTAX      Counter64
   MAX-ACCESS  read-only
   STATUS      current
   DESCRIPTION
      "Path: swPort.performance.vlan.mibCounters.ifOutDiscardsNoArp

       64 bit unsigned wrappable counter."
   ::= {pr1646v2EthPortSwIXt2VlanEntry 42336256}

pr1646v2EthPortSwIXt2VlanMCOutDropFilter OBJECT-TYPE
   SYNTAX      Counter64
   MAX-ACCESS  read-only
   STATUS      current
   DESCRIPTION
      "Path: swPort.performance.vlan.mibCounters.ifOutDiscardsFilter

       64 bit unsigned wrappable counter."
   ::= {pr1646v2EthPortSwIXt2VlanEntry 42598400}

pr1646v2EthPortSwIXt2VlanMCOutBandwidth15sec OBJECT-TYPE
   SYNTAX      Integer32
   MAX-ACCESS  read-only
   STATUS      current
   DESCRIPTION
      "Path: swPort.performance.vlan.mibCounters.ifOutBandwidth.15sec

       unit name = bps
       formula = 8 * ; 8 /"
   ::= {pr1646v2EthPortSwIXt2VlanEntry 45483264}

pr1646v2EthPortSwIXt2VlanMCOutBandwidth30sec OBJECT-TYPE
   SYNTAX      Integer32
   MAX-ACCESS  read-only
   STATUS      current
   DESCRIPTION
      "Path: swPort.performance.vlan.mibCounters.ifOutBandwidth.30sec

       unit name = bps
       formula = 8 * ; 8 /"
   ::= {pr1646v2EthPortSwIXt2VlanEntry 45484544}

pr1646v2EthPortSwIXt2VlanMCOutBandwidth1min OBJECT-TYPE
   SYNTAX      Integer32
   MAX-ACCESS  read-only
   STATUS      current
   DESCRIPTION
      "Path: swPort.performance.vlan.mibCounters.ifOutBandwidth.1min

       unit name = bps
       formula = 8 * ; 8 /"
   ::= {pr1646v2EthPortSwIXt2VlanEntry 45487104}

pr1646v2EthPortSwIXt2VlanMCOutBandwidth2min OBJECT-TYPE
   SYNTAX      Integer32
   MAX-ACCESS  read-only
   STATUS      current
   DESCRIPTION
      "Path: swPort.performance.vlan.mibCounters.ifOutBandwidth.2min

       unit name = bps
       formula = 8 * ; 8 /"
   ::= {pr1646v2EthPortSwIXt2VlanEntry 45492224}

pr1646v2EthPortSwIXt2VlanMCOutBandwidth5min OBJECT-TYPE
   SYNTAX      Integer32
   MAX-ACCESS  read-only
   STATUS      current
   DESCRIPTION
      "Path: swPort.performance.vlan.mibCounters.ifOutBandwidth.5min

       unit name = bps
       formula = 8 * ; 8 /"
   ::= {pr1646v2EthPortSwIXt2VlanEntry 45507584}

pr1646v2EthPortSwIXt2VlanVlanVid OBJECT-TYPE
   SYNTAX      Integer32
   MAX-ACCESS  read-only
   STATUS      current
   DESCRIPTION
      "Path: swPort.performance.vlan.vlan.vid"
   ::= {pr1646v2EthPortSwIXt2VlanEntry 234946560}

pr1646v2EthPortSwIXt2VlanPppLinkMonitoringRequestsSent OBJECT-TYPE
   SYNTAX      Gauge32
   MAX-ACCESS  read-only
   STATUS      current
   DESCRIPTION
      "Path: swPort.performance.vlan.ppp.linkMonitoring.requestsSent

       32 bit unsigned gauge value."
   ::= {pr1646v2EthPortSwIXt2VlanEntry 50397440}

pr1646v2EthPortSwIXt2VlanPppLinkMonitoringRepliesRcvd OBJECT-TYPE
   SYNTAX      Gauge32
   MAX-ACCESS  read-only
   STATUS      current
   DESCRIPTION
      "Path: swPort.performance.vlan.ppp.linkMonitoring.repliesRcvd

       32 bit unsigned gauge value."
   ::= {pr1646v2EthPortSwIXt2VlanEntry 50397696}

pr1646v2EthPortSwIXt2VlanPppLinkMonitoringRequestsRcvd OBJECT-TYPE
   SYNTAX      Gauge32
   MAX-ACCESS  read-only
   STATUS      current
   DESCRIPTION
      "Path: swPort.performance.vlan.ppp.linkMonitoring.requestsRcvd

       32 bit unsigned gauge value."
   ::= {pr1646v2EthPortSwIXt2VlanEntry 50397952}

pr1646v2EthPortSwIXt2VlanPppLinkMonitoringRepliesSent OBJECT-TYPE
   SYNTAX      Gauge32
   MAX-ACCESS  read-only
   STATUS      current
   DESCRIPTION
      "Path: swPort.performance.vlan.ppp.linkMonitoring.repliesSent

       32 bit unsigned gauge value."
   ::= {pr1646v2EthPortSwIXt2VlanEntry 50398208}

pr1646v2EthPortSwIXt2VlanMCH2P OBJECT-TYPE
   SYNTAX      SEQUENCE OF Pr1646v2EthPortSwIXt2VlanMCH2PEntry
   MAX-ACCESS  not-accessible
   STATUS      current
   DESCRIPTION
      ""
   ::= {pr1646v2EthPortSwIXt2Vlan 41549824}

pr1646v2EthPortSwIXt2VlanMCH2PEntry OBJECT-TYPE
   SYNTAX      Pr1646v2EthPortSwIXt2VlanMCH2PEntry
   MAX-ACCESS  not-accessible
   STATUS      current
   DESCRIPTION
      ""
   INDEX      { pr1646v2EthPortSwIXt2VlanMCH2PGlobalIx,
                pr1646v2EthPortSwIXt2VlanTableIx,
                pr1646v2EthPortSwIXt2VlanMCH2PTableIx }
   ::= {pr1646v2EthPortSwIXt2VlanMCH2P 1}

Pr1646v2EthPortSwIXt2VlanMCH2PEntry ::=
   SEQUENCE
      {
      pr1646v2EthPortSwIXt2VlanMCH2PGlobalIx
         GlobalIndex,
      pr1646v2EthPortSwIXt2VlanMCH2PTableIx
         TableIndex,
      pr1646v2EthPortSwIXt2VlanMCH2PSysUpTime
         TimeTicks,
      pr1646v2EthPortSwIXt2VlanMCH2PIfUpTime
         TimeTicks,
      pr1646v2EthPortSwIXt2VlanMCH2PIfStatChanges
         Counter32,
      pr1646v2EthPortSwIXt2VlanMCH2PIfInOctets
         Counter64,
      pr1646v2EthPortSwIXt2VlanMCH2PIfInUCPkts
         Counter64,
      pr1646v2EthPortSwIXt2VlanMCH2PIfInNUCPkts
         Counter64,
      pr1646v2EthPortSwIXt2VlanMCH2PIfInBCPkts
         Counter64,
      pr1646v2EthPortSwIXt2VlanMCH2PIfInMCPkts
         Counter64,
      pr1646v2EthPortSwIXt2VlanMCH2PIfInDiscards
         Counter64,
      pr1646v2EthPortSwIXt2VlanMCH2PIfInErrors
         Counter64,
      pr1646v2EthPortSwIXt2VlanMCH2PIfInUnkwn
         Counter64,
      pr1646v2EthPortSwIXt2VlanMCH2PInDropEx
         Counter64,
      pr1646v2EthPortSwIXt2VlanMCH2PInDropNoMac
         Counter64,
      pr1646v2EthPortSwIXt2VlanMCH2PInDropNUCast
         Counter64,
      pr1646v2EthPortSwIXt2VlanMCH2PInDropFilter
         Counter64,
      pr1646v2EthPortSwIXt2VlanMCH2PIfInBandwidth
         Integer32,
      pr1646v2EthPortSwIXt2VlanMCH2PIfOutOctets
         Counter64,
      pr1646v2EthPortSwIXt2VlanMCH2PIfOutUCPkts
         Counter64,
      pr1646v2EthPortSwIXt2VlanMCH2PIfOutNUCPkts
         Counter64,
      pr1646v2EthPortSwIXt2VlanMCH2PIfOutBCPkts
         Counter64,
      pr1646v2EthPortSwIXt2VlanMCH2PIfOutMCPkts
         Counter64,
      pr1646v2EthPortSwIXt2VlanMCH2PIfOutDiscards
         Counter64,
      pr1646v2EthPortSwIXt2VlanMCH2PIfOutErrors
         Counter64,
      pr1646v2EthPortSwIXt2VlanMCH2POutDropEx
         Counter64,
      pr1646v2EthPortSwIXt2VlanMCH2POutDropNoArp
         Counter64,
      pr1646v2EthPortSwIXt2VlanMCH2POutDropFilter
         Counter64,
      pr1646v2EthPortSwIXt2VlanMCH2PIfOutBandwidth
         Integer32,
      pr1646v2EthPortSwIXt2VlanMCH2PIfErrSec
         Counter32
      }

pr1646v2EthPortSwIXt2VlanMCH2PGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanMCH2PEntry 10}

pr1646v2EthPortSwIXt2VlanMCH2PTableIx OBJECT-TYPE
   SYNTAX      TableIndex
   MAX-ACCESS  not-accessible
   STATUS      current
   DESCRIPTION
      ""
   ::= {pr1646v2EthPortSwIXt2VlanMCH2PEntry 11}

pr1646v2EthPortSwIXt2VlanMCH2PSysUpTime OBJECT-TYPE
   SYNTAX      TimeTicks
   MAX-ACCESS  read-only
   STATUS      current
   DESCRIPTION
      "Path: swPort.performance.vlan.mibCounters.h2Performance.sysUpTime

       Time in centi-second."
   ::= {pr1646v2EthPortSwIXt2VlanMCH2PEntry 16777216}

pr1646v2EthPortSwIXt2VlanMCH2PIfUpTime OBJECT-TYPE
   SYNTAX      TimeTicks
   MAX-ACCESS  read-only
   STATUS      current
   DESCRIPTION
      "Path: swPort.performance.vlan.mibCounters.h2Performance.ifUpTime

       Time in centi-second."
   ::= {pr1646v2EthPortSwIXt2VlanMCH2PEntry 33554432}

pr1646v2EthPortSwIXt2VlanMCH2PIfStatChanges OBJECT-TYPE
   SYNTAX      Counter32
   MAX-ACCESS  read-only
   STATUS      current
   DESCRIPTION
      "Path: swPort.performance.vlan.mibCounters.h2Performance.ifStatusChanges

       32 bit unsigned wrappable counter."
   ::= {pr1646v2EthPortSwIXt2VlanMCH2PEntry 50331648}

pr1646v2EthPortSwIXt2VlanMCH2PIfInOctets OBJECT-TYPE
   SYNTAX      Counter64
   MAX-ACCESS  read-only
   STATUS      current
   DESCRIPTION
      "Path: swPort.performance.vlan.mibCounters.h2Performance.ifInOctets

       64 bit unsigned wrappable counter."
   ::= {pr1646v2EthPortSwIXt2VlanMCH2PEntry 67108864}

pr1646v2EthPortSwIXt2VlanMCH2PIfInUCPkts OBJECT-TYPE
   SYNTAX      Counter64
   MAX-ACCESS  read-only
   STATUS      current
   DESCRIPTION
      "Path: swPort.performance.vlan.mibCounters.h2Performance.ifInUcastPkts

       64 bit unsigned wrappable counter."
   ::= {pr1646v2EthPortSwIXt2VlanMCH2PEntry 83886080}

pr1646v2EthPortSwIXt2VlanMCH2PIfInNUCPkts OBJECT-TYPE
   SYNTAX      Counter64
   MAX-ACCESS  read-only
   STATUS      current
   DESCRIPTION
      "Path: swPort.performance.vlan.mibCounters.h2Performance.ifInNUcastPkts

       64 bit unsigned wrappable counter."
   ::= {pr1646v2EthPortSwIXt2VlanMCH2PEntry 100663296}

pr1646v2EthPortSwIXt2VlanMCH2PIfInBCPkts OBJECT-TYPE
   SYNTAX      Counter64
   MAX-ACCESS  read-only
   STATUS      current
   DESCRIPTION
      "Path: swPort.performance.vlan.mibCounters.h2Performance.ifInBcastPkts

       64 bit unsigned wrappable counter."
   ::= {pr1646v2EthPortSwIXt2VlanMCH2PEntry 419430400}

pr1646v2EthPortSwIXt2VlanMCH2PIfInMCPkts OBJECT-TYPE
   SYNTAX      Counter64
   MAX-ACCESS  read-only
   STATUS      current
   DESCRIPTION
      "Path: swPort.performance.vlan.mibCounters.h2Performance.ifInMcastPkts

       64 bit unsigned wrappable counter."
   ::= {pr1646v2EthPortSwIXt2VlanMCH2PEntry 436207616}

pr1646v2EthPortSwIXt2VlanMCH2PIfInDiscards OBJECT-TYPE
   SYNTAX      Counter64
   MAX-ACCESS  read-only
   STATUS      current
   DESCRIPTION
      "Path: swPort.performance.vlan.mibCounters.h2Performance.ifInDiscards

       64 bit unsigned wrappable counter."
   ::= {pr1646v2EthPortSwIXt2VlanMCH2PEntry 117440512}

pr1646v2EthPortSwIXt2VlanMCH2PIfInErrors OBJECT-TYPE
   SYNTAX      Counter64
   MAX-ACCESS  read-only
   STATUS      current
   DESCRIPTION
      "Path: swPort.performance.vlan.mibCounters.h2Performance.ifInErrors

       64 bit unsigned wrappable counter."
   ::= {pr1646v2EthPortSwIXt2VlanMCH2PEntry 134217728}

pr1646v2EthPortSwIXt2VlanMCH2PIfInUnkwn OBJECT-TYPE
   SYNTAX      Counter64
   MAX-ACCESS  read-only
   STATUS      current
   DESCRIPTION
      "Path: swPort.performance.vlan.mibCounters.h2Performance.ifInUnknownProtos

       64 bit unsigned wrappable counter."
   ::= {pr1646v2EthPortSwIXt2VlanMCH2PEntry 150994944}

pr1646v2EthPortSwIXt2VlanMCH2PInDropEx OBJECT-TYPE
   SYNTAX      Counter64
   MAX-ACCESS  read-only
   STATUS      current
   DESCRIPTION
      "Path: swPort.performance.vlan.mibCounters.h2Performance.ifInDropLevelExceeded

       64 bit unsigned wrappable counter."
   ::= {pr1646v2EthPortSwIXt2VlanMCH2PEntry 335544320}

pr1646v2EthPortSwIXt2VlanMCH2PInDropNoMac OBJECT-TYPE
   SYNTAX      Counter64
   MAX-ACCESS  read-only
   STATUS      current
   DESCRIPTION
      "Path: swPort.performance.vlan.mibCounters.h2Performance.fInDiscardsNoMacFit

       64 bit unsigned wrappable counter."
   ::= {pr1646v2EthPortSwIXt2VlanMCH2PEntry 301989888}

pr1646v2EthPortSwIXt2VlanMCH2PInDropNUCast OBJECT-TYPE
   SYNTAX      Counter64
   MAX-ACCESS  read-only
   STATUS      current
   DESCRIPTION
      "Path: swPort.performance.vlan.mibCounters.h2Performance.fInDiscardsNUCast

       64 bit unsigned wrappable counter."
   ::= {pr1646v2EthPortSwIXt2VlanMCH2PEntry 318767104}

pr1646v2EthPortSwIXt2VlanMCH2PInDropFilter OBJECT-TYPE
   SYNTAX      Counter64
   MAX-ACCESS  read-only
   STATUS      current
   DESCRIPTION
      "Path: swPort.performance.vlan.mibCounters.h2Performance.fInDiscardsFilter

       64 bit unsigned wrappable counter."
   ::= {pr1646v2EthPortSwIXt2VlanMCH2PEntry 385875968}

pr1646v2EthPortSwIXt2VlanMCH2PIfInBandwidth OBJECT-TYPE
   SYNTAX      Integer32
   MAX-ACCESS  read-only
   STATUS      current
   DESCRIPTION
      "Path: swPort.performance.vlan.mibCounters.h2Performance.ifInBandwidth

       unit name = bps
       formula = 8 * ; 8 /"
   ::= {pr1646v2EthPortSwIXt2VlanMCH2PEntry 268435456}

pr1646v2EthPortSwIXt2VlanMCH2PIfOutOctets OBJECT-TYPE
   SYNTAX      Counter64
   MAX-ACCESS  read-only
   STATUS      current
   DESCRIPTION
      "Path: swPort.performance.vlan.mibCounters.h2Performance.ifOutOctets

       64 bit unsigned wrappable counter."
   ::= {pr1646v2EthPortSwIXt2VlanMCH2PEntry 167772160}

pr1646v2EthPortSwIXt2VlanMCH2PIfOutUCPkts OBJECT-TYPE
   SYNTAX      Counter64
   MAX-ACCESS  read-only
   STATUS      current
   DESCRIPTION
      "Path: swPort.performance.vlan.mibCounters.h2Performance.ifOutUcastPkts

       64 bit unsigned wrappable counter."
   ::= {pr1646v2EthPortSwIXt2VlanMCH2PEntry 184549376}

pr1646v2EthPortSwIXt2VlanMCH2PIfOutNUCPkts OBJECT-TYPE
   SYNTAX      Counter64
   MAX-ACCESS  read-only
   STATUS      current
   DESCRIPTION
      "Path: swPort.performance.vlan.mibCounters.h2Performance.ifOutNUcastPkts

       64 bit unsigned wrappable counter."
   ::= {pr1646v2EthPortSwIXt2VlanMCH2PEntry 201326592}

pr1646v2EthPortSwIXt2VlanMCH2PIfOutBCPkts OBJECT-TYPE
   SYNTAX      Counter64
   MAX-ACCESS  read-only
   STATUS      current
   DESCRIPTION
      "Path: swPort.performance.vlan.mibCounters.h2Performance.ifOutBcastPkts

       64 bit unsigned wrappable counter."
   ::= {pr1646v2EthPortSwIXt2VlanMCH2PEntry 452984832}

pr1646v2EthPortSwIXt2VlanMCH2PIfOutMCPkts OBJECT-TYPE
   SYNTAX      Counter64
   MAX-ACCESS  read-only
   STATUS      current
   DESCRIPTION
      "Path: swPort.performance.vlan.mibCounters.h2Performance.ifOutMcastPkts

       64 bit unsigned wrappable counter."
   ::= {pr1646v2EthPortSwIXt2VlanMCH2PEntry 469762048}

pr1646v2EthPortSwIXt2VlanMCH2PIfOutDiscards OBJECT-TYPE
   SYNTAX      Counter64
   MAX-ACCESS  read-only
   STATUS      current
   DESCRIPTION
      "Path: swPort.performance.vlan.mibCounters.h2Performance.ifOutDiscards

       64 bit unsigned wrappable counter."
   ::= {pr1646v2EthPortSwIXt2VlanMCH2PEntry 218103808}

pr1646v2EthPortSwIXt2VlanMCH2PIfOutErrors OBJECT-TYPE
   SYNTAX      Counter64
   MAX-ACCESS  read-only
   STATUS      current
   DESCRIPTION
      "Path: swPort.performance.vlan.mibCounters.h2Performance.ifOutErrors

       64 bit unsigned wrappable counter."
   ::= {pr1646v2EthPortSwIXt2VlanMCH2PEntry 234881024}

pr1646v2EthPortSwIXt2VlanMCH2POutDropEx OBJECT-TYPE
   SYNTAX      Counter64
   MAX-ACCESS  read-only
   STATUS      current
   DESCRIPTION
      "Path: swPort.performance.vlan.mibCounters.h2Performance.ifOutDropLevelExceeded

       64 bit unsigned wrappable counter."
   ::= {pr1646v2EthPortSwIXt2VlanMCH2PEntry 352321536}

pr1646v2EthPortSwIXt2VlanMCH2POutDropNoArp OBJECT-TYPE
   SYNTAX      Counter64
   MAX-ACCESS  read-only
   STATUS      current
   DESCRIPTION
      "Path: swPort.performance.vlan.mibCounters.h2Performance.ifOutDiscardsNoArp

       64 bit unsigned wrappable counter."
   ::= {pr1646v2EthPortSwIXt2VlanMCH2PEntry 369098752}

pr1646v2EthPortSwIXt2VlanMCH2POutDropFilter OBJECT-TYPE
   SYNTAX      Counter64
   MAX-ACCESS  read-only
   STATUS      current
   DESCRIPTION
      "Path: swPort.performance.vlan.mibCounters.h2Performance.ifOutDiscardsFilter

       64 bit unsigned wrappable counter."
   ::= {pr1646v2EthPortSwIXt2VlanMCH2PEntry 402653184}

pr1646v2EthPortSwIXt2VlanMCH2PIfOutBandwidth OBJECT-TYPE
   SYNTAX      Integer32
   MAX-ACCESS  read-only
   STATUS      current
   DESCRIPTION
      "Path: swPort.performance.vlan.mibCounters.h2Performance.ifOutBandwidth

       unit name = bps
       formula = 8 * ; 8 /"
   ::= {pr1646v2EthPortSwIXt2VlanMCH2PEntry 285212672}

pr1646v2EthPortSwIXt2VlanMCH2PIfErrSec OBJECT-TYPE
   SYNTAX      Counter32
   MAX-ACCESS  read-only
   STATUS      current
   DESCRIPTION
      "Path: swPort.performance.vlan.mibCounters.h2Performance.ifErrSec

       32 bit unsigned wrappable counter."
   ::= {pr1646v2EthPortSwIXt2VlanMCH2PEntry 251658240}

pr1646v2EthPortSwIXt2VlanMCH24P OBJECT-TYPE
   SYNTAX      SEQUENCE OF Pr1646v2EthPortSwIXt2VlanMCH24PEntry
   MAX-ACCESS  not-accessible
   STATUS      current
   DESCRIPTION
      ""
   ::= {pr1646v2EthPortSwIXt2Vlan 41615360}

pr1646v2EthPortSwIXt2VlanMCH24PEntry OBJECT-TYPE
   SYNTAX      Pr1646v2EthPortSwIXt2VlanMCH24PEntry
   MAX-ACCESS  not-accessible
   STATUS      current
   DESCRIPTION
      ""
   INDEX      { pr1646v2EthPortSwIXt2VlanMCH24PGlobalIx,
                pr1646v2EthPortSwIXt2VlanTableIx,
                pr1646v2EthPortSwIXt2VlanMCH24PTableIx }
   ::= {pr1646v2EthPortSwIXt2VlanMCH24P 1}

Pr1646v2EthPortSwIXt2VlanMCH24PEntry ::=
   SEQUENCE
      {
      pr1646v2EthPortSwIXt2VlanMCH24PGlobalIx
         GlobalIndex,
      pr1646v2EthPortSwIXt2VlanMCH24PTableIx
         TableIndex,
      pr1646v2EthPortSwIXt2VlanMCH24PSysUpTime
         TimeTicks,
      pr1646v2EthPortSwIXt2VlanMCH24PIfUpTime
         TimeTicks,
      pr1646v2EthPortSwIXt2VlanMCH24PIfStatChanges
         Counter32,
      pr1646v2EthPortSwIXt2VlanMCH24PIfInOctets
         Counter64,
      pr1646v2EthPortSwIXt2VlanMCH24PIfInUCPkts
         Counter64,
      pr1646v2EthPortSwIXt2VlanMCH24PIfInNUCPkts
         Counter64,
      pr1646v2EthPortSwIXt2VlanMCH24PIfInBCPkts
         Counter64,
      pr1646v2EthPortSwIXt2VlanMCH24PIfInMCPkts
         Counter64,
      pr1646v2EthPortSwIXt2VlanMCH24PIfInDiscards
         Counter64,
      pr1646v2EthPortSwIXt2VlanMCH24PIfInErrors
         Counter64,
      pr1646v2EthPortSwIXt2VlanMCH24PIfInUnkwn
         Counter64,
      pr1646v2EthPortSwIXt2VlanMCH24PInDropEx
         Counter64,
      pr1646v2EthPortSwIXt2VlanMCH24PInDropNoMac
         Counter64,
      pr1646v2EthPortSwIXt2VlanMCH24PInDropNUCast
         Counter64,
      pr1646v2EthPortSwIXt2VlanMCH24PInDropFilter
         Counter64,
      pr1646v2EthPortSwIXt2VlanMCH24PIfInBandwidth
         Integer32,
      pr1646v2EthPortSwIXt2VlanMCH24PIfOutOctets
         Counter64,
      pr1646v2EthPortSwIXt2VlanMCH24PIfOutUCPkts
         Counter64,
      pr1646v2EthPortSwIXt2VlanMCH24PIfOutNUCPkts
         Counter64,
      pr1646v2EthPortSwIXt2VlanMCH24PIfOutBCPkts
         Counter64,
      pr1646v2EthPortSwIXt2VlanMCH24PIfOutMCPkts
         Counter64,
      pr1646v2EthPortSwIXt2VlanMCH24PIfOutDiscards
         Counter64,
      pr1646v2EthPortSwIXt2VlanMCH24PIfOutErrors
         Counter64,
      pr1646v2EthPortSwIXt2VlanMCH24POutDropEx
         Counter64,
      pr1646v2EthPortSwIXt2VlanMCH24POutDropNoArp
         Counter64,
      pr1646v2EthPortSwIXt2VlanMCH24POutDropFilter
         Counter64,
      pr1646v2EthPortSwIXt2VlanMCH24PIfOutBandwidth
         Integer32,
      pr1646v2EthPortSwIXt2VlanMCH24PIfErrSec
         Counter32
      }

pr1646v2EthPortSwIXt2VlanMCH24PGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanMCH24PEntry 10}

pr1646v2EthPortSwIXt2VlanMCH24PTableIx OBJECT-TYPE
   SYNTAX      TableIndex
   MAX-ACCESS  not-accessible
   STATUS      current
   DESCRIPTION
      ""
   ::= {pr1646v2EthPortSwIXt2VlanMCH24PEntry 11}

pr1646v2EthPortSwIXt2VlanMCH24PSysUpTime OBJECT-TYPE
   SYNTAX      TimeTicks
   MAX-ACCESS  read-only
   STATUS      current
   DESCRIPTION
      "Path: swPort.performance.vlan.mibCounters.h24Performance.sysUpTime

       Time in centi-second."
   ::= {pr1646v2EthPortSwIXt2VlanMCH24PEntry 16777216}

pr1646v2EthPortSwIXt2VlanMCH24PIfUpTime OBJECT-TYPE
   SYNTAX      TimeTicks
   MAX-ACCESS  read-only
   STATUS      current
   DESCRIPTION
      "Path: swPort.performance.vlan.mibCounters.h24Performance.ifUpTime

       Time in centi-second."
   ::= {pr1646v2EthPortSwIXt2VlanMCH24PEntry 33554432}

pr1646v2EthPortSwIXt2VlanMCH24PIfStatChanges OBJECT-TYPE
   SYNTAX      Counter32
   MAX-ACCESS  read-only
   STATUS      current
   DESCRIPTION
      "Path: swPort.performance.vlan.mibCounters.h24Performance.ifStatusChanges

       32 bit unsigned wrappable counter."
   ::= {pr1646v2EthPortSwIXt2VlanMCH24PEntry 50331648}

pr1646v2EthPortSwIXt2VlanMCH24PIfInOctets OBJECT-TYPE
   SYNTAX      Counter64
   MAX-ACCESS  read-only
   STATUS      current
   DESCRIPTION
      "Path: swPort.performance.vlan.mibCounters.h24Performance.ifInOctets

       64 bit unsigned wrappable counter."
   ::= {pr1646v2EthPortSwIXt2VlanMCH24PEntry 67108864}

pr1646v2EthPortSwIXt2VlanMCH24PIfInUCPkts OBJECT-TYPE
   SYNTAX      Counter64
   MAX-ACCESS  read-only
   STATUS      current
   DESCRIPTION
      "Path: swPort.performance.vlan.mibCounters.h24Performance.ifInUcastPkts

       64 bit unsigned wrappable counter."
   ::= {pr1646v2EthPortSwIXt2VlanMCH24PEntry 83886080}

pr1646v2EthPortSwIXt2VlanMCH24PIfInNUCPkts OBJECT-TYPE
   SYNTAX      Counter64
   MAX-ACCESS  read-only
   STATUS      current
   DESCRIPTION
      "Path: swPort.performance.vlan.mibCounters.h24Performance.ifInNUcastPkts

       64 bit unsigned wrappable counter."
   ::= {pr1646v2EthPortSwIXt2VlanMCH24PEntry 100663296}

pr1646v2EthPortSwIXt2VlanMCH24PIfInBCPkts OBJECT-TYPE
   SYNTAX      Counter64
   MAX-ACCESS  read-only
   STATUS      current
   DESCRIPTION
      "Path: swPort.performance.vlan.mibCounters.h24Performance.ifInBcastPkts

       64 bit unsigned wrappable counter."
   ::= {pr1646v2EthPortSwIXt2VlanMCH24PEntry 419430400}

pr1646v2EthPortSwIXt2VlanMCH24PIfInMCPkts OBJECT-TYPE
   SYNTAX      Counter64
   MAX-ACCESS  read-only
   STATUS      current
   DESCRIPTION
      "Path: swPort.performance.vlan.mibCounters.h24Performance.ifInMcastPkts

       64 bit unsigned wrappable counter."
   ::= {pr1646v2EthPortSwIXt2VlanMCH24PEntry 436207616}

pr1646v2EthPortSwIXt2VlanMCH24PIfInDiscards OBJECT-TYPE
   SYNTAX      Counter64
   MAX-ACCESS  read-only
   STATUS      current
   DESCRIPTION
      "Path: swPort.performance.vlan.mibCounters.h24Performance.ifInDiscards

       64 bit unsigned wrappable counter."
   ::= {pr1646v2EthPortSwIXt2VlanMCH24PEntry 117440512}

pr1646v2EthPortSwIXt2VlanMCH24PIfInErrors OBJECT-TYPE
   SYNTAX      Counter64
   MAX-ACCESS  read-only
   STATUS      current
   DESCRIPTION
      "Path: swPort.performance.vlan.mibCounters.h24Performance.ifInErrors

       64 bit unsigned wrappable counter."
   ::= {pr1646v2EthPortSwIXt2VlanMCH24PEntry 134217728}

pr1646v2EthPortSwIXt2VlanMCH24PIfInUnkwn OBJECT-TYPE
   SYNTAX      Counter64
   MAX-ACCESS  read-only
   STATUS      current
   DESCRIPTION
      "Path: swPort.performance.vlan.mibCounters.h24Performance.ifInUnknownProtos

       64 bit unsigned wrappable counter."
   ::= {pr1646v2EthPortSwIXt2VlanMCH24PEntry 150994944}

pr1646v2EthPortSwIXt2VlanMCH24PInDropEx OBJECT-TYPE
   SYNTAX      Counter64
   MAX-ACCESS  read-only
   STATUS      current
   DESCRIPTION
      "Path: swPort.performance.vlan.mibCounters.h24Performance.ifInDropLevelExceeded

       64 bit unsigned wrappable counter."
   ::= {pr1646v2EthPortSwIXt2VlanMCH24PEntry 335544320}

pr1646v2EthPortSwIXt2VlanMCH24PInDropNoMac OBJECT-TYPE
   SYNTAX      Counter64
   MAX-ACCESS  read-only
   STATUS      current
   DESCRIPTION
      "Path: swPort.performance.vlan.mibCounters.h24Performance.fInDiscardsNoMacFit

       64 bit unsigned wrappable counter."
   ::= {pr1646v2EthPortSwIXt2VlanMCH24PEntry 301989888}

pr1646v2EthPortSwIXt2VlanMCH24PInDropNUCast OBJECT-TYPE
   SYNTAX      Counter64
   MAX-ACCESS  read-only
   STATUS      current
   DESCRIPTION
      "Path: swPort.performance.vlan.mibCounters.h24Performance.fInDiscardsNUCast

       64 bit unsigned wrappable counter."
   ::= {pr1646v2EthPortSwIXt2VlanMCH24PEntry 318767104}

pr1646v2EthPortSwIXt2VlanMCH24PInDropFilter OBJECT-TYPE
   SYNTAX      Counter64
   MAX-ACCESS  read-only
   STATUS      current
   DESCRIPTION
      "Path: swPort.performance.vlan.mibCounters.h24Performance.fInDiscardsFilter

       64 bit unsigned wrappable counter."
   ::= {pr1646v2EthPortSwIXt2VlanMCH24PEntry 385875968}

pr1646v2EthPortSwIXt2VlanMCH24PIfInBandwidth OBJECT-TYPE
   SYNTAX      Integer32
   MAX-ACCESS  read-only
   STATUS      current
   DESCRIPTION
      "Path: swPort.performance.vlan.mibCounters.h24Performance.ifInBandwidth

       unit name = bps
       formula = 8 * ; 8 /"
   ::= {pr1646v2EthPortSwIXt2VlanMCH24PEntry 268435456}

pr1646v2EthPortSwIXt2VlanMCH24PIfOutOctets OBJECT-TYPE
   SYNTAX      Counter64
   MAX-ACCESS  read-only
   STATUS      current
   DESCRIPTION
      "Path: swPort.performance.vlan.mibCounters.h24Performance.ifOutOctets

       64 bit unsigned wrappable counter."
   ::= {pr1646v2EthPortSwIXt2VlanMCH24PEntry 167772160}

pr1646v2EthPortSwIXt2VlanMCH24PIfOutUCPkts OBJECT-TYPE
   SYNTAX      Counter64
   MAX-ACCESS  read-only
   STATUS      current
   DESCRIPTION
      "Path: swPort.performance.vlan.mibCounters.h24Performance.ifOutUcastPkts

       64 bit unsigned wrappable counter."
   ::= {pr1646v2EthPortSwIXt2VlanMCH24PEntry 184549376}

pr1646v2EthPortSwIXt2VlanMCH24PIfOutNUCPkts OBJECT-TYPE
   SYNTAX      Counter64
   MAX-ACCESS  read-only
   STATUS      current
   DESCRIPTION
      "Path: swPort.performance.vlan.mibCounters.h24Performance.ifOutNUcastPkts

       64 bit unsigned wrappable counter."
   ::= {pr1646v2EthPortSwIXt2VlanMCH24PEntry 201326592}

pr1646v2EthPortSwIXt2VlanMCH24PIfOutBCPkts OBJECT-TYPE
   SYNTAX      Counter64
   MAX-ACCESS  read-only
   STATUS      current
   DESCRIPTION
      "Path: swPort.performance.vlan.mibCounters.h24Performance.ifOutBcastPkts

       64 bit unsigned wrappable counter."
   ::= {pr1646v2EthPortSwIXt2VlanMCH24PEntry 452984832}

pr1646v2EthPortSwIXt2VlanMCH24PIfOutMCPkts OBJECT-TYPE
   SYNTAX      Counter64
   MAX-ACCESS  read-only
   STATUS      current
   DESCRIPTION
      "Path: swPort.performance.vlan.mibCounters.h24Performance.ifOutMcastPkts

       64 bit unsigned wrappable counter."
   ::= {pr1646v2EthPortSwIXt2VlanMCH24PEntry 469762048}

pr1646v2EthPortSwIXt2VlanMCH24PIfOutDiscards OBJECT-TYPE
   SYNTAX      Counter64
   MAX-ACCESS  read-only
   STATUS      current
   DESCRIPTION
      "Path: swPort.performance.vlan.mibCounters.h24Performance.ifOutDiscards

       64 bit unsigned wrappable counter."
   ::= {pr1646v2EthPortSwIXt2VlanMCH24PEntry 218103808}

pr1646v2EthPortSwIXt2VlanMCH24PIfOutErrors OBJECT-TYPE
   SYNTAX      Counter64
   MAX-ACCESS  read-only
   STATUS      current
   DESCRIPTION
      "Path: swPort.performance.vlan.mibCounters.h24Performance.ifOutErrors

       64 bit unsigned wrappable counter."
   ::= {pr1646v2EthPortSwIXt2VlanMCH24PEntry 234881024}

pr1646v2EthPortSwIXt2VlanMCH24POutDropEx OBJECT-TYPE
   SYNTAX      Counter64
   MAX-ACCESS  read-only
   STATUS      current
   DESCRIPTION
      "Path: swPort.performance.vlan.mibCounters.h24Performance.ifOutDropLevelExceeded

       64 bit unsigned wrappable counter."
   ::= {pr1646v2EthPortSwIXt2VlanMCH24PEntry 352321536}

pr1646v2EthPortSwIXt2VlanMCH24POutDropNoArp OBJECT-TYPE
   SYNTAX      Counter64
   MAX-ACCESS  read-only
   STATUS      current
   DESCRIPTION
      "Path: swPort.performance.vlan.mibCounters.h24Performance.ifOutDiscardsNoArp

       64 bit unsigned wrappable counter."
   ::= {pr1646v2EthPortSwIXt2VlanMCH24PEntry 369098752}

pr1646v2EthPortSwIXt2VlanMCH24POutDropFilter OBJECT-TYPE
   SYNTAX      Counter64
   MAX-ACCESS  read-only
   STATUS      current
   DESCRIPTION
      "Path: swPort.performance.vlan.mibCounters.h24Performance.ifOutDiscardsFilter

       64 bit unsigned wrappable counter."
   ::= {pr1646v2EthPortSwIXt2VlanMCH24PEntry 402653184}

pr1646v2EthPortSwIXt2VlanMCH24PIfOutBandwidth OBJECT-TYPE
   SYNTAX      Integer32
   MAX-ACCESS  read-only
   STATUS      current
   DESCRIPTION
      "Path: swPort.performance.vlan.mibCounters.h24Performance.ifOutBandwidth

       unit name = bps
       formula = 8 * ; 8 /"
   ::= {pr1646v2EthPortSwIXt2VlanMCH24PEntry 285212672}

pr1646v2EthPortSwIXt2VlanMCH24PIfErrSec OBJECT-TYPE
   SYNTAX      Counter32
   MAX-ACCESS  read-only
   STATUS      current
   DESCRIPTION
      "Path: swPort.performance.vlan.mibCounters.h24Performance.ifErrSec

       32 bit unsigned wrappable counter."
   ::= {pr1646v2EthPortSwIXt2VlanMCH24PEntry 251658240}

pr1646v2EthPortSwIXt2VlanMCD7P OBJECT-TYPE
   SYNTAX      SEQUENCE OF Pr1646v2EthPortSwIXt2VlanMCD7PEntry
   MAX-ACCESS  not-accessible
   STATUS      current
   DESCRIPTION
      ""
   ::= {pr1646v2EthPortSwIXt2Vlan 41680896}

pr1646v2EthPortSwIXt2VlanMCD7PEntry OBJECT-TYPE
   SYNTAX      Pr1646v2EthPortSwIXt2VlanMCD7PEntry
   MAX-ACCESS  not-accessible
   STATUS      current
   DESCRIPTION
      ""
   INDEX      { pr1646v2EthPortSwIXt2VlanMCD7PGlobalIx,
                pr1646v2EthPortSwIXt2VlanTableIx,
                pr1646v2EthPortSwIXt2VlanMCD7PTableIx }
   ::= {pr1646v2EthPortSwIXt2VlanMCD7P 1}

Pr1646v2EthPortSwIXt2VlanMCD7PEntry ::=
   SEQUENCE
      {
      pr1646v2EthPortSwIXt2VlanMCD7PGlobalIx
         GlobalIndex,
      pr1646v2EthPortSwIXt2VlanMCD7PTableIx
         TableIndex,
      pr1646v2EthPortSwIXt2VlanMCD7PSysUpTime
         TimeTicks,
      pr1646v2EthPortSwIXt2VlanMCD7PIfUpTime
         TimeTicks,
      pr1646v2EthPortSwIXt2VlanMCD7PIfStatChanges
         Counter32,
      pr1646v2EthPortSwIXt2VlanMCD7PIfInOctets
         Counter64,
      pr1646v2EthPortSwIXt2VlanMCD7PIfInUCPkts
         Counter64,
      pr1646v2EthPortSwIXt2VlanMCD7PIfInNUCPkts
         Counter64,
      pr1646v2EthPortSwIXt2VlanMCD7PIfInBCPkts
         Counter64,
      pr1646v2EthPortSwIXt2VlanMCD7PIfInMCPkts
         Counter64,
      pr1646v2EthPortSwIXt2VlanMCD7PIfInDiscards
         Counter64,
      pr1646v2EthPortSwIXt2VlanMCD7PIfInErrors
         Counter64,
      pr1646v2EthPortSwIXt2VlanMCD7PIfInUnkwn
         Counter64,
      pr1646v2EthPortSwIXt2VlanMCD7PInDropEx
         Counter64,
      pr1646v2EthPortSwIXt2VlanMCD7PInDropNoMac
         Counter64,
      pr1646v2EthPortSwIXt2VlanMCD7PInDropNUCast
         Counter64,
      pr1646v2EthPortSwIXt2VlanMCD7PInDropFilter
         Counter64,
      pr1646v2EthPortSwIXt2VlanMCD7PIfInBandwidth
         Integer32,
      pr1646v2EthPortSwIXt2VlanMCD7PIfOutOctets
         Counter64,
      pr1646v2EthPortSwIXt2VlanMCD7PIfOutUCPkts
         Counter64,
      pr1646v2EthPortSwIXt2VlanMCD7PIfOutNUCPkts
         Counter64,
      pr1646v2EthPortSwIXt2VlanMCD7PIfOutBCPkts
         Counter64,
      pr1646v2EthPortSwIXt2VlanMCD7PIfOutMCPkts
         Counter64,
      pr1646v2EthPortSwIXt2VlanMCD7PIfOutDiscards
         Counter64,
      pr1646v2EthPortSwIXt2VlanMCD7PIfOutErrors
         Counter64,
      pr1646v2EthPortSwIXt2VlanMCD7POutDropEx
         Counter64,
      pr1646v2EthPortSwIXt2VlanMCD7POutDropNoArp
         Counter64,
      pr1646v2EthPortSwIXt2VlanMCD7POutDropFilter
         Counter64,
      pr1646v2EthPortSwIXt2VlanMCD7PIfOutBandwidth
         Integer32,
      pr1646v2EthPortSwIXt2VlanMCD7PIfErrSec
         Counter32
      }

pr1646v2EthPortSwIXt2VlanMCD7PGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanMCD7PEntry 10}

pr1646v2EthPortSwIXt2VlanMCD7PTableIx OBJECT-TYPE
   SYNTAX      TableIndex
   MAX-ACCESS  not-accessible
   STATUS      current
   DESCRIPTION
      ""
   ::= {pr1646v2EthPortSwIXt2VlanMCD7PEntry 11}

pr1646v2EthPortSwIXt2VlanMCD7PSysUpTime OBJECT-TYPE
   SYNTAX      TimeTicks
   MAX-ACCESS  read-only
   STATUS      current
   DESCRIPTION
      "Path: swPort.performance.vlan.mibCounters.d7Performance.sysUpTime

       Time in centi-second."
   ::= {pr1646v2EthPortSwIXt2VlanMCD7PEntry 16777216}

pr1646v2EthPortSwIXt2VlanMCD7PIfUpTime OBJECT-TYPE
   SYNTAX      TimeTicks
   MAX-ACCESS  read-only
   STATUS      current
   DESCRIPTION
      "Path: swPort.performance.vlan.mibCounters.d7Performance.ifUpTime

       Time in centi-second."
   ::= {pr1646v2EthPortSwIXt2VlanMCD7PEntry 33554432}

pr1646v2EthPortSwIXt2VlanMCD7PIfStatChanges OBJECT-TYPE
   SYNTAX      Counter32
   MAX-ACCESS  read-only
   STATUS      current
   DESCRIPTION
      "Path: swPort.performance.vlan.mibCounters.d7Performance.ifStatusChanges

       32 bit unsigned wrappable counter."
   ::= {pr1646v2EthPortSwIXt2VlanMCD7PEntry 50331648}

pr1646v2EthPortSwIXt2VlanMCD7PIfInOctets OBJECT-TYPE
   SYNTAX      Counter64
   MAX-ACCESS  read-only
   STATUS      current
   DESCRIPTION
      "Path: swPort.performance.vlan.mibCounters.d7Performance.ifInOctets

       64 bit unsigned wrappable counter."
   ::= {pr1646v2EthPortSwIXt2VlanMCD7PEntry 67108864}

pr1646v2EthPortSwIXt2VlanMCD7PIfInUCPkts OBJECT-TYPE
   SYNTAX      Counter64
   MAX-ACCESS  read-only
   STATUS      current
   DESCRIPTION
      "Path: swPort.performance.vlan.mibCounters.d7Performance.ifInUcastPkts

       64 bit unsigned wrappable counter."
   ::= {pr1646v2EthPortSwIXt2VlanMCD7PEntry 83886080}

pr1646v2EthPortSwIXt2VlanMCD7PIfInNUCPkts OBJECT-TYPE
   SYNTAX      Counter64
   MAX-ACCESS  read-only
   STATUS      current
   DESCRIPTION
      "Path: swPort.performance.vlan.mibCounters.d7Performance.ifInNUcastPkts

       64 bit unsigned wrappable counter."
   ::= {pr1646v2EthPortSwIXt2VlanMCD7PEntry 100663296}

pr1646v2EthPortSwIXt2VlanMCD7PIfInBCPkts OBJECT-TYPE
   SYNTAX      Counter64
   MAX-ACCESS  read-only
   STATUS      current
   DESCRIPTION
      "Path: swPort.performance.vlan.mibCounters.d7Performance.ifInBcastPkts

       64 bit unsigned wrappable counter."
   ::= {pr1646v2EthPortSwIXt2VlanMCD7PEntry 419430400}

pr1646v2EthPortSwIXt2VlanMCD7PIfInMCPkts OBJECT-TYPE
   SYNTAX      Counter64
   MAX-ACCESS  read-only
   STATUS      current
   DESCRIPTION
      "Path: swPort.performance.vlan.mibCounters.d7Performance.ifInMcastPkts

       64 bit unsigned wrappable counter."
   ::= {pr1646v2EthPortSwIXt2VlanMCD7PEntry 436207616}

pr1646v2EthPortSwIXt2VlanMCD7PIfInDiscards OBJECT-TYPE
   SYNTAX      Counter64
   MAX-ACCESS  read-only
   STATUS      current
   DESCRIPTION
      "Path: swPort.performance.vlan.mibCounters.d7Performance.ifInDiscards

       64 bit unsigned wrappable counter."
   ::= {pr1646v2EthPortSwIXt2VlanMCD7PEntry 117440512}

pr1646v2EthPortSwIXt2VlanMCD7PIfInErrors OBJECT-TYPE
   SYNTAX      Counter64
   MAX-ACCESS  read-only
   STATUS      current
   DESCRIPTION
      "Path: swPort.performance.vlan.mibCounters.d7Performance.ifInErrors

       64 bit unsigned wrappable counter."
   ::= {pr1646v2EthPortSwIXt2VlanMCD7PEntry 134217728}

pr1646v2EthPortSwIXt2VlanMCD7PIfInUnkwn OBJECT-TYPE
   SYNTAX      Counter64
   MAX-ACCESS  read-only
   STATUS      current
   DESCRIPTION
      "Path: swPort.performance.vlan.mibCounters.d7Performance.ifInUnknownProtos

       64 bit unsigned wrappable counter."
   ::= {pr1646v2EthPortSwIXt2VlanMCD7PEntry 150994944}

pr1646v2EthPortSwIXt2VlanMCD7PInDropEx OBJECT-TYPE
   SYNTAX      Counter64
   MAX-ACCESS  read-only
   STATUS      current
   DESCRIPTION
      "Path: swPort.performance.vlan.mibCounters.d7Performance.ifInDropLevelExceeded

       64 bit unsigned wrappable counter."
   ::= {pr1646v2EthPortSwIXt2VlanMCD7PEntry 335544320}

pr1646v2EthPortSwIXt2VlanMCD7PInDropNoMac OBJECT-TYPE
   SYNTAX      Counter64
   MAX-ACCESS  read-only
   STATUS      current
   DESCRIPTION
      "Path: swPort.performance.vlan.mibCounters.d7Performance.fInDiscardsNoMacFit

       64 bit unsigned wrappable counter."
   ::= {pr1646v2EthPortSwIXt2VlanMCD7PEntry 301989888}

pr1646v2EthPortSwIXt2VlanMCD7PInDropNUCast OBJECT-TYPE
   SYNTAX      Counter64
   MAX-ACCESS  read-only
   STATUS      current
   DESCRIPTION
      "Path: swPort.performance.vlan.mibCounters.d7Performance.fInDiscardsNUCast

       64 bit unsigned wrappable counter."
   ::= {pr1646v2EthPortSwIXt2VlanMCD7PEntry 318767104}

pr1646v2EthPortSwIXt2VlanMCD7PInDropFilter OBJECT-TYPE
   SYNTAX      Counter64
   MAX-ACCESS  read-only
   STATUS      current
   DESCRIPTION
      "Path: swPort.performance.vlan.mibCounters.d7Performance.fInDiscardsFilter

       64 bit unsigned wrappable counter."
   ::= {pr1646v2EthPortSwIXt2VlanMCD7PEntry 385875968}

pr1646v2EthPortSwIXt2VlanMCD7PIfInBandwidth OBJECT-TYPE
   SYNTAX      Integer32
   MAX-ACCESS  read-only
   STATUS      current
   DESCRIPTION
      "Path: swPort.performance.vlan.mibCounters.d7Performance.ifInBandwidth

       unit name = bps
       formula = 8 * ; 8 /"
   ::= {pr1646v2EthPortSwIXt2VlanMCD7PEntry 268435456}

pr1646v2EthPortSwIXt2VlanMCD7PIfOutOctets OBJECT-TYPE
   SYNTAX      Counter64
   MAX-ACCESS  read-only
   STATUS      current
   DESCRIPTION
      "Path: swPort.performance.vlan.mibCounters.d7Performance.ifOutOctets

       64 bit unsigned wrappable counter."
   ::= {pr1646v2EthPortSwIXt2VlanMCD7PEntry 167772160}

pr1646v2EthPortSwIXt2VlanMCD7PIfOutUCPkts OBJECT-TYPE
   SYNTAX      Counter64
   MAX-ACCESS  read-only
   STATUS      current
   DESCRIPTION
      "Path: swPort.performance.vlan.mibCounters.d7Performance.ifOutUcastPkts

       64 bit unsigned wrappable counter."
   ::= {pr1646v2EthPortSwIXt2VlanMCD7PEntry 184549376}

pr1646v2EthPortSwIXt2VlanMCD7PIfOutNUCPkts OBJECT-TYPE
   SYNTAX      Counter64
   MAX-ACCESS  read-only
   STATUS      current
   DESCRIPTION
      "Path: swPort.performance.vlan.mibCounters.d7Performance.ifOutNUcastPkts

       64 bit unsigned wrappable counter."
   ::= {pr1646v2EthPortSwIXt2VlanMCD7PEntry 201326592}

pr1646v2EthPortSwIXt2VlanMCD7PIfOutBCPkts OBJECT-TYPE
   SYNTAX      Counter64
   MAX-ACCESS  read-only
   STATUS      current
   DESCRIPTION
      "Path: swPort.performance.vlan.mibCounters.d7Performance.ifOutBcastPkts

       64 bit unsigned wrappable counter."
   ::= {pr1646v2EthPortSwIXt2VlanMCD7PEntry 452984832}

pr1646v2EthPortSwIXt2VlanMCD7PIfOutMCPkts OBJECT-TYPE
   SYNTAX      Counter64
   MAX-ACCESS  read-only
   STATUS      current
   DESCRIPTION
      "Path: swPort.performance.vlan.mibCounters.d7Performance.ifOutMcastPkts

       64 bit unsigned wrappable counter."
   ::= {pr1646v2EthPortSwIXt2VlanMCD7PEntry 469762048}

pr1646v2EthPortSwIXt2VlanMCD7PIfOutDiscards OBJECT-TYPE
   SYNTAX      Counter64
   MAX-ACCESS  read-only
   STATUS      current
   DESCRIPTION
      "Path: swPort.performance.vlan.mibCounters.d7Performance.ifOutDiscards

       64 bit unsigned wrappable counter."
   ::= {pr1646v2EthPortSwIXt2VlanMCD7PEntry 218103808}

pr1646v2EthPortSwIXt2VlanMCD7PIfOutErrors OBJECT-TYPE
   SYNTAX      Counter64
   MAX-ACCESS  read-only
   STATUS      current
   DESCRIPTION
      "Path: swPort.performance.vlan.mibCounters.d7Performance.ifOutErrors

       64 bit unsigned wrappable counter."
   ::= {pr1646v2EthPortSwIXt2VlanMCD7PEntry 234881024}

pr1646v2EthPortSwIXt2VlanMCD7POutDropEx OBJECT-TYPE
   SYNTAX      Counter64
   MAX-ACCESS  read-only
   STATUS      current
   DESCRIPTION
      "Path: swPort.performance.vlan.mibCounters.d7Performance.ifOutDropLevelExceeded

       64 bit unsigned wrappable counter."
   ::= {pr1646v2EthPortSwIXt2VlanMCD7PEntry 352321536}

pr1646v2EthPortSwIXt2VlanMCD7POutDropNoArp OBJECT-TYPE
   SYNTAX      Counter64
   MAX-ACCESS  read-only
   STATUS      current
   DESCRIPTION
      "Path: swPort.performance.vlan.mibCounters.d7Performance.ifOutDiscardsNoArp

       64 bit unsigned wrappable counter."
   ::= {pr1646v2EthPortSwIXt2VlanMCD7PEntry 369098752}

pr1646v2EthPortSwIXt2VlanMCD7POutDropFilter OBJECT-TYPE
   SYNTAX      Counter64
   MAX-ACCESS  read-only
   STATUS      current
   DESCRIPTION
      "Path: swPort.performance.vlan.mibCounters.d7Performance.ifOutDiscardsFilter

       64 bit unsigned wrappable counter."
   ::= {pr1646v2EthPortSwIXt2VlanMCD7PEntry 402653184}

pr1646v2EthPortSwIXt2VlanMCD7PIfOutBandwidth OBJECT-TYPE
   SYNTAX      Integer32
   MAX-ACCESS  read-only
   STATUS      current
   DESCRIPTION
      "Path: swPort.performance.vlan.mibCounters.d7Performance.ifOutBandwidth

       unit name = bps
       formula = 8 * ; 8 /"
   ::= {pr1646v2EthPortSwIXt2VlanMCD7PEntry 285212672}

pr1646v2EthPortSwIXt2VlanMCD7PIfErrSec OBJECT-TYPE
   SYNTAX      Counter32
   MAX-ACCESS  read-only
   STATUS      current
   DESCRIPTION
      "Path: swPort.performance.vlan.mibCounters.d7Performance.ifErrSec

       32 bit unsigned wrappable counter."
   ::= {pr1646v2EthPortSwIXt2VlanMCD7PEntry 251658240}

pr1646v2EthPortSwIXt2VlanInPQs OBJECT-TYPE
   SYNTAX      SEQUENCE OF Pr1646v2EthPortSwIXt2VlanInPQsEntry
   MAX-ACCESS  not-accessible
   STATUS      current
   DESCRIPTION
      ""
   ::= {pr1646v2EthPortSwIXt2Vlan 100663296}

pr1646v2EthPortSwIXt2VlanInPQsEntry OBJECT-TYPE
   SYNTAX      Pr1646v2EthPortSwIXt2VlanInPQsEntry
   MAX-ACCESS  not-accessible
   STATUS      current
   DESCRIPTION
      ""
   INDEX      { pr1646v2EthPortSwIXt2VlanInPQsGlobalIx,
                pr1646v2EthPortSwIXt2VlanTableIx,
                pr1646v2EthPortSwIXt2VlanInPQsTableIx }
   ::= {pr1646v2EthPortSwIXt2VlanInPQs 1}

Pr1646v2EthPortSwIXt2VlanInPQsEntry ::=
   SEQUENCE
      {
      pr1646v2EthPortSwIXt2VlanInPQsGlobalIx
         GlobalIndex,
      pr1646v2EthPortSwIXt2VlanInPQsTableIx
         TableIndex,
      pr1646v2EthPortSwIXt2VlanInPQsName
         INTEGER,
      pr1646v2EthPortSwIXt2VlanInPQsLength
         Integer32,
      pr1646v2EthPortSwIXt2VlanInPQsOctetLength
         Integer32,
      pr1646v2EthPortSwIXt2VlanInPQsRedLength
         Integer32,
      pr1646v2EthPortSwIXt2VlanInPQsPacketsTotal
         Counter64,
      pr1646v2EthPortSwIXt2VlanInPQsPacketsDirectTx
         Counter64,
      pr1646v2EthPortSwIXt2VlanInPQsPacketsQueued
         Counter64,
      pr1646v2EthPortSwIXt2VlanInPQsPacketsDropped
         Counter64,
      pr1646v2EthPortSwIXt2VlanInPQsPacketsRedDropped
         Counter64,
      pr1646v2EthPortSwIXt2VlanInPQsPacketsCirTx
         Counter64,
      pr1646v2EthPortSwIXt2VlanInPQsPacketsEirTx
         Counter64,
      pr1646v2EthPortSwIXt2VlanInPQsPacketsViolateTx
         Counter64,
      pr1646v2EthPortSwIXt2VlanInPQsOctetsTotal
         Counter64,
      pr1646v2EthPortSwIXt2VlanInPQsOctetsDirectTx
         Counter64,
      pr1646v2EthPortSwIXt2VlanInPQsOctetsQueued
         Counter64,
      pr1646v2EthPortSwIXt2VlanInPQsOctetsDropped
         Counter64,
      pr1646v2EthPortSwIXt2VlanInPQsOctetsRedDropped
         Counter64,
      pr1646v2EthPortSwIXt2VlanInPQsOctetsCirTx
         Counter64,
      pr1646v2EthPortSwIXt2VlanInPQsOctetsEirTx
         Counter64,
      pr1646v2EthPortSwIXt2VlanInPQsOctetsViolateTx
         Counter64,
      pr1646v2EthPortSwIXt2VlanInPQsOctetsBandwidth15sec
         Integer32,
      pr1646v2EthPortSwIXt2VlanInPQsOctetsBandwidth30sec
         Integer32,
      pr1646v2EthPortSwIXt2VlanInPQsOctetsBandwidth1min
         Integer32,
      pr1646v2EthPortSwIXt2VlanInPQsOctetsBandwidth2min
         Integer32,
      pr1646v2EthPortSwIXt2VlanInPQsOctetsBandwidth5min
         Integer32
      }

pr1646v2EthPortSwIXt2VlanInPQsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanInPQsEntry 10}

pr1646v2EthPortSwIXt2VlanInPQsTableIx OBJECT-TYPE
   SYNTAX      TableIndex
   MAX-ACCESS  not-accessible
   STATUS      current
   DESCRIPTION
      ""
   ::= {pr1646v2EthPortSwIXt2VlanInPQsEntry 11}

pr1646v2EthPortSwIXt2VlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwIXt2VlanInPQsEntry 16777216}

pr1646v2EthPortSwIXt2VlanInPQsLength OBJECT-TYPE
   SYNTAX      Integer32
   MAX-ACCESS  read-only
   STATUS      current
   DESCRIPTION
      "Path: swPort.performance.vlan.inPriorityQueues.length"
   ::= {pr1646v2EthPortSwIXt2VlanInPQsEntry 33554432}

pr1646v2EthPortSwIXt2VlanInPQsOctetLength OBJECT-TYPE
   SYNTAX      Integer32
   MAX-ACCESS  read-only
   STATUS      current
   DESCRIPTION
      "Path: swPort.performance.vlan.inPriorityQueues.octetLength"
   ::= {pr1646v2EthPortSwIXt2VlanInPQsEntry 150994944}

pr1646v2EthPortSwIXt2VlanInPQsRedLength OBJECT-TYPE
   SYNTAX      Integer32
   MAX-ACCESS  read-only
   STATUS      current
   DESCRIPTION
      "Path: swPort.performance.vlan.inPriorityQueues.redLength"
   ::= {pr1646v2EthPortSwIXt2VlanInPQsEntry 134217728}

pr1646v2EthPortSwIXt2VlanInPQsPacketsTotal OBJECT-TYPE
   SYNTAX      Counter64
   MAX-ACCESS  read-only
   STATUS      current
   DESCRIPTION
      "Path: swPort.performance.vlan.inPriorityQueues.packets.total

       64 bit unsigned wrappable counter."
   ::= {pr1646v2EthPortSwIXt2VlanInPQsEntry 50790400}

pr1646v2EthPortSwIXt2VlanInPQsPacketsDirectTx OBJECT-TYPE
   SYNTAX      Counter64
   MAX-ACCESS  read-only
   STATUS      current
   DESCRIPTION
      "Path: swPort.performance.vlan.inPriorityQueues.packets.directTx

       64 bit unsigned wrappable counter."
   ::= {pr1646v2EthPortSwIXt2VlanInPQsEntry 50397184}

pr1646v2EthPortSwIXt2VlanInPQsPacketsQueued OBJECT-TYPE
   SYNTAX      Counter64
   MAX-ACCESS  read-only
   STATUS      current
   DESCRIPTION
      "Path: swPort.performance.vlan.inPriorityQueues.packets.queued

       64 bit unsigned wrappable counter."
   ::= {pr1646v2EthPortSwIXt2VlanInPQsEntry 50462720}

pr1646v2EthPortSwIXt2VlanInPQsPacketsDropped OBJECT-TYPE
   SYNTAX      Counter64
   MAX-ACCESS  read-only
   STATUS      current
   DESCRIPTION
      "Path: swPort.performance.vlan.inPriorityQueues.packets.dropped

       64 bit unsigned wrappable counter."
   ::= {pr1646v2EthPortSwIXt2VlanInPQsEntry 50528256}

pr1646v2EthPortSwIXt2VlanInPQsPacketsRedDropped OBJECT-TYPE
   SYNTAX      Counter64
   MAX-ACCESS  read-only
   STATUS      current
   DESCRIPTION
      "Path: swPort.performance.vlan.inPriorityQueues.packets.redDropped

       64 bit unsigned wrappable counter."
   ::= {pr1646v2EthPortSwIXt2VlanInPQsEntry 50724864}

pr1646v2EthPortSwIXt2VlanInPQsPacketsCirTx OBJECT-TYPE
   SYNTAX      Counter64
   MAX-ACCESS  read-only
   STATUS      current
   DESCRIPTION
      "Path: swPort.performance.vlan.inPriorityQueues.packets.cirTx

       64 bit unsigned wrappable counter."
   ::= {pr1646v2EthPortSwIXt2VlanInPQsEntry 50593792}

pr1646v2EthPortSwIXt2VlanInPQsPacketsEirTx OBJECT-TYPE
   SYNTAX      Counter64
   MAX-ACCESS  read-only
   STATUS      current
   DESCRIPTION
      "Path: swPort.performance.vlan.inPriorityQueues.packets.eirTx

       64 bit unsigned wrappable counter."
   ::= {pr1646v2EthPortSwIXt2VlanInPQsEntry 50659328}

pr1646v2EthPortSwIXt2VlanInPQsPacketsViolateTx OBJECT-TYPE
   SYNTAX      Counter64
   MAX-ACCESS  read-only
   STATUS      current
   DESCRIPTION
      "Path: swPort.performance.vlan.inPriorityQueues.packets.violateTx

       64 bit unsigned wrappable counter."
   ::= {pr1646v2EthPortSwIXt2VlanInPQsEntry 50855936}

pr1646v2EthPortSwIXt2VlanInPQsOctetsTotal OBJECT-TYPE
   SYNTAX      Counter64
   MAX-ACCESS  read-only
   STATUS      current
   DESCRIPTION
      "Path: swPort.performance.vlan.inPriorityQueues.octets.total

       64 bit unsigned wrappable counter."
   ::= {pr1646v2EthPortSwIXt2VlanInPQsEntry 67567616}

pr1646v2EthPortSwIXt2VlanInPQsOctetsDirectTx OBJECT-TYPE
   SYNTAX      Counter64
   MAX-ACCESS  read-only
   STATUS      current
   DESCRIPTION
      "Path: swPort.performance.vlan.inPriorityQueues.octets.directTx

       64 bit unsigned wrappable counter."
   ::= {pr1646v2EthPortSwIXt2VlanInPQsEntry 67174400}

pr1646v2EthPortSwIXt2VlanInPQsOctetsQueued OBJECT-TYPE
   SYNTAX      Counter64
   MAX-ACCESS  read-only
   STATUS      current
   DESCRIPTION
      "Path: swPort.performance.vlan.inPriorityQueues.octets.queued

       64 bit unsigned wrappable counter."
   ::= {pr1646v2EthPortSwIXt2VlanInPQsEntry 67239936}

pr1646v2EthPortSwIXt2VlanInPQsOctetsDropped OBJECT-TYPE
   SYNTAX      Counter64
   MAX-ACCESS  read-only
   STATUS      current
   DESCRIPTION
      "Path: swPort.performance.vlan.inPriorityQueues.octets.dropped

       64 bit unsigned wrappable counter."
   ::= {pr1646v2EthPortSwIXt2VlanInPQsEntry 67305472}

pr1646v2EthPortSwIXt2VlanInPQsOctetsRedDropped OBJECT-TYPE
   SYNTAX      Counter64
   MAX-ACCESS  read-only
   STATUS      current
   DESCRIPTION
      "Path: swPort.performance.vlan.inPriorityQueues.octets.redDropped

       64 bit unsigned wrappable counter."
   ::= {pr1646v2EthPortSwIXt2VlanInPQsEntry 67502080}

pr1646v2EthPortSwIXt2VlanInPQsOctetsCirTx OBJECT-TYPE
   SYNTAX      Counter64
   MAX-ACCESS  read-only
   STATUS      current
   DESCRIPTION
      "Path: swPort.performance.vlan.inPriorityQueues.octets.cirTx

       64 bit unsigned wrappable counter."
   ::= {pr1646v2EthPortSwIXt2VlanInPQsEntry 67371008}

pr1646v2EthPortSwIXt2VlanInPQsOctetsEirTx OBJECT-TYPE
   SYNTAX      Counter64
   MAX-ACCESS  read-only
   STATUS      current
   DESCRIPTION
      "Path: swPort.performance.vlan.inPriorityQueues.octets.eirTx

       64 bit unsigned wrappable counter."
   ::= {pr1646v2EthPortSwIXt2VlanInPQsEntry 67436544}

pr1646v2EthPortSwIXt2VlanInPQsOctetsViolateTx OBJECT-TYPE
   SYNTAX      Counter64
   MAX-ACCESS  read-only
   STATUS      current
   DESCRIPTION
      "Path: swPort.performance.vlan.inPriorityQueues.octets.violateTx

       64 bit unsigned wrappable counter."
   ::= {pr1646v2EthPortSwIXt2VlanInPQsEntry 67633152}

pr1646v2EthPortSwIXt2VlanInPQsOctetsBandwidth15sec OBJECT-TYPE
   SYNTAX      Integer32
   MAX-ACCESS  read-only
   STATUS      current
   DESCRIPTION
      "Path: swPort.performance.vlan.inPriorityQueues.octets.bandwidth.15sec

       unit name = bps
       formula = 8 * ; 8 /"
   ::= {pr1646v2EthPortSwIXt2VlanInPQsEntry 70386944}

pr1646v2EthPortSwIXt2VlanInPQsOctetsBandwidth30sec OBJECT-TYPE
   SYNTAX      Integer32
   MAX-ACCESS  read-only
   STATUS      current
   DESCRIPTION
      "Path: swPort.performance.vlan.inPriorityQueues.octets.bandwidth.30sec

       unit name = bps
       formula = 8 * ; 8 /"
   ::= {pr1646v2EthPortSwIXt2VlanInPQsEntry 70388224}

pr1646v2EthPortSwIXt2VlanInPQsOctetsBandwidth1min OBJECT-TYPE
   SYNTAX      Integer32
   MAX-ACCESS  read-only
   STATUS      current
   DESCRIPTION
      "Path: swPort.performance.vlan.inPriorityQueues.octets.bandwidth.1min

       unit name = bps
       formula = 8 * ; 8 /"
   ::= {pr1646v2EthPortSwIXt2VlanInPQsEntry 70390784}

pr1646v2EthPortSwIXt2VlanInPQsOctetsBandwidth2min OBJECT-TYPE
   SYNTAX      Integer32
   MAX-ACCESS  read-only
   STATUS      current
   DESCRIPTION
      "Path: swPort.performance.vlan.inPriorityQueues.octets.bandwidth.2min

       unit name = bps
       formula = 8 * ; 8 /"
   ::= {pr1646v2EthPortSwIXt2VlanInPQsEntry 70395904}

pr1646v2EthPortSwIXt2VlanInPQsOctetsBandwidth5min OBJECT-TYPE
   SYNTAX      Integer32
   MAX-ACCESS  read-only
   STATUS      current
   DESCRIPTION
      "Path: swPort.performance.vlan.inPriorityQueues.octets.bandwidth.5min

       unit name = bps
       formula = 8 * ; 8 /"
   ::= {pr1646v2EthPortSwIXt2VlanInPQsEntry 70411264}

pr1646v2EthPortSwIXt2VlanInPQsH2Performance OBJECT-TYPE
   SYNTAX      SEQUENCE OF Pr1646v2EthPortSwIXt2VlanInPQsH2PerformanceEntry
   MAX-ACCESS  not-accessible
   STATUS      current
   DESCRIPTION
      ""
   ::= {pr1646v2EthPortSwIXt2Vlan 100990976}

pr1646v2EthPortSwIXt2VlanInPQsH2PerformanceEntry OBJECT-TYPE
   SYNTAX      Pr1646v2EthPortSwIXt2VlanInPQsH2PerformanceEntry
   MAX-ACCESS  not-accessible
   STATUS      current
   DESCRIPTION
      ""
   INDEX      { pr1646v2EthPortSwIXt2VlanInPQsH2PerformanceGlobalIx,
                pr1646v2EthPortSwIXt2VlanTableIx,
                pr1646v2EthPortSwIXt2VlanInPQsTableIx,
                pr1646v2EthPortSwIXt2VlanInPQsH2PerformanceTableIx }
   ::= {pr1646v2EthPortSwIXt2VlanInPQsH2Performance 1}

Pr1646v2EthPortSwIXt2VlanInPQsH2PerformanceEntry ::=
   SEQUENCE
      {
      pr1646v2EthPortSwIXt2VlanInPQsH2PerformanceGlobalIx
         GlobalIndex,
      pr1646v2EthPortSwIXt2VlanInPQsH2PerformanceTableIx
         TableIndex,
      pr1646v2EthPortSwIXt2VlanInPQsH2PerformanceSysUpTime
         TimeTicks,
      pr1646v2EthPortSwIXt2VlanInPQsH2PerformanceTotPkts
         Counter64,
      pr1646v2EthPortSwIXt2VlanInPQsH2PerformanceDirTxPkts
         Counter64,
      pr1646v2EthPortSwIXt2VlanInPQsH2PerformanceQdPkts
         Counter64,
      pr1646v2EthPortSwIXt2VlanInPQsH2PerformanceDropPkts
         Counter64,
      pr1646v2EthPortSwIXt2VlanInPQsH2PerformanceRDropPkts
         Counter64,
      pr1646v2EthPortSwIXt2VlanInPQsH2PerformanceCirTxPkts
         Counter64,
      pr1646v2EthPortSwIXt2VlanInPQsH2PerformanceEirTxPkts
         Counter64,
      pr1646v2EthPortSwIXt2VlanInPQsH2PerformanceViolTxPkts
         Counter64,
      pr1646v2EthPortSwIXt2VlanInPQsH2PerformanceTotOcts
         Counter64,
      pr1646v2EthPortSwIXt2VlanInPQsH2PerformanceDirTxOcts
         Counter64,
      pr1646v2EthPortSwIXt2VlanInPQsH2PerformanceQdOcts
         Counter64,
      pr1646v2EthPortSwIXt2VlanInPQsH2PerformanceDropOcts
         Counter64,
      pr1646v2EthPortSwIXt2VlanInPQsH2PerformanceRDropOcts
         Counter64,
      pr1646v2EthPortSwIXt2VlanInPQsH2PerformanceCirTxOcts
         Counter64,
      pr1646v2EthPortSwIXt2VlanInPQsH2PerformanceEirTxOcts
         Counter64,
      pr1646v2EthPortSwIXt2VlanInPQsH2PerformanceViolTxOcts
         Counter64,
      pr1646v2EthPortSwIXt2VlanInPQsH2PerformanceBandwidth
         Integer32
      }

pr1646v2EthPortSwIXt2VlanInPQsH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanInPQsH2PerformanceEntry 10}

pr1646v2EthPortSwIXt2VlanInPQsH2PerformanceTableIx OBJECT-TYPE
   SYNTAX      TableIndex
   MAX-ACCESS  not-accessible
   STATUS      current
   DESCRIPTION
      ""
   ::= {pr1646v2EthPortSwIXt2VlanInPQsH2PerformanceEntry 11}

pr1646v2EthPortSwIXt2VlanInPQsH2PerformanceSysUpTime OBJECT-TYPE
   SYNTAX      TimeTicks
   MAX-ACCESS  read-only
   STATUS      current
   DESCRIPTION
      "Path: swPort.performance.vlan.inPriorityQueues.h2Performance.sysUpTime

       Time in centi-second."
   ::= {pr1646v2EthPortSwIXt2VlanInPQsH2PerformanceEntry 16777216}

pr1646v2EthPortSwIXt2VlanInPQsH2PerformanceTotPkts OBJECT-TYPE
   SYNTAX      Counter64
   MAX-ACCESS  read-only
   STATUS      current
   DESCRIPTION
      "Path: swPort.performance.vlan.inPriorityQueues.h2Performance.totalPkts

       64 bit unsigned wrappable counter."
   ::= {pr1646v2EthPortSwIXt2VlanInPQsH2PerformanceEntry 234881024}

pr1646v2EthPortSwIXt2VlanInPQsH2PerformanceDirTxPkts OBJECT-TYPE
   SYNTAX      Counter64
   MAX-ACCESS  read-only
   STATUS      current
   DESCRIPTION
      "Path: swPort.performance.vlan.inPriorityQueues.h2Performance.directTxPkts

       64 bit unsigned wrappable counter."
   ::= {pr1646v2EthPortSwIXt2VlanInPQsH2PerformanceEntry 33554432}

pr1646v2EthPortSwIXt2VlanInPQsH2PerformanceQdPkts OBJECT-TYPE
   SYNTAX      Counter64
   MAX-ACCESS  read-only
   STATUS      current
   DESCRIPTION
      "Path: swPort.performance.vlan.inPriorityQueues.h2Performance.queuedPkts

       64 bit unsigned wrappable counter."
   ::= {pr1646v2EthPortSwIXt2VlanInPQsH2PerformanceEntry 50331648}

pr1646v2EthPortSwIXt2VlanInPQsH2PerformanceDropPkts OBJECT-TYPE
   SYNTAX      Counter64
   MAX-ACCESS  read-only
   STATUS      current
   DESCRIPTION
      "Path: swPort.performance.vlan.inPriorityQueues.h2Performance.droppedPkts

       64 bit unsigned wrappable counter."
   ::= {pr1646v2EthPortSwIXt2VlanInPQsH2PerformanceEntry 67108864}

pr1646v2EthPortSwIXt2VlanInPQsH2PerformanceRDropPkts OBJECT-TYPE
   SYNTAX      Counter64
   MAX-ACCESS  read-only
   STATUS      current
   DESCRIPTION
      "Path: swPort.performance.vlan.inPriorityQueues.h2Performance.redDroppedPkts

       64 bit unsigned wrappable counter."
   ::= {pr1646v2EthPortSwIXt2VlanInPQsH2PerformanceEntry 201326592}

pr1646v2EthPortSwIXt2VlanInPQsH2PerformanceCirTxPkts OBJECT-TYPE
   SYNTAX      Counter64
   MAX-ACCESS  read-only
   STATUS      current
   DESCRIPTION
      "Path: swPort.performance.vlan.inPriorityQueues.h2Performance.cirTxPkts

       64 bit unsigned wrappable counter."
   ::= {pr1646v2EthPortSwIXt2VlanInPQsH2PerformanceEntry 83886080}

pr1646v2EthPortSwIXt2VlanInPQsH2PerformanceEirTxPkts OBJECT-TYPE
   SYNTAX      Counter64
   MAX-ACCESS  read-only
   STATUS      current
   DESCRIPTION
      "Path: swPort.performance.vlan.inPriorityQueues.h2Performance.eirTxPkts

       64 bit unsigned wrappable counter."
   ::= {pr1646v2EthPortSwIXt2VlanInPQsH2PerformanceEntry 100663296}

pr1646v2EthPortSwIXt2VlanInPQsH2PerformanceViolTxPkts OBJECT-TYPE
   SYNTAX      Counter64
   MAX-ACCESS  read-only
   STATUS      current
   DESCRIPTION
      "Path: swPort.performance.vlan.inPriorityQueues.h2Performance.violateTxPkts

       64 bit unsigned wrappable counter."
   ::= {pr1646v2EthPortSwIXt2VlanInPQsH2PerformanceEntry 301989888}

pr1646v2EthPortSwIXt2VlanInPQsH2PerformanceTotOcts OBJECT-TYPE
   SYNTAX      Counter64
   MAX-ACCESS  read-only
   STATUS      current
   DESCRIPTION
      "Path: swPort.performance.vlan.inPriorityQueues.h2Performance.totalOctets

       64 bit unsigned wrappable counter."
   ::= {pr1646v2EthPortSwIXt2VlanInPQsH2PerformanceEntry 251658240}

pr1646v2EthPortSwIXt2VlanInPQsH2PerformanceDirTxOcts OBJECT-TYPE
   SYNTAX      Counter64
   MAX-ACCESS  read-only
   STATUS      current
   DESCRIPTION
      "Path: swPort.performance.vlan.inPriorityQueues.h2Performance.directTxOctets

       64 bit unsigned wrappable counter."
   ::= {pr1646v2EthPortSwIXt2VlanInPQsH2PerformanceEntry 117440512}

pr1646v2EthPortSwIXt2VlanInPQsH2PerformanceQdOcts OBJECT-TYPE
   SYNTAX      Counter64
   MAX-ACCESS  read-only
   STATUS      current
   DESCRIPTION
      "Path: swPort.performance.vlan.inPriorityQueues.h2Performance.queuedOctets

       64 bit unsigned wrappable counter."
   ::= {pr1646v2EthPortSwIXt2VlanInPQsH2PerformanceEntry 134217728}

pr1646v2EthPortSwIXt2VlanInPQsH2PerformanceDropOcts OBJECT-TYPE
   SYNTAX      Counter64
   MAX-ACCESS  read-only
   STATUS      current
   DESCRIPTION
      "Path: swPort.performance.vlan.inPriorityQueues.h2Performance.droppedOctets

       64 bit unsigned wrappable counter."
   ::= {pr1646v2EthPortSwIXt2VlanInPQsH2PerformanceEntry 150994944}

pr1646v2EthPortSwIXt2VlanInPQsH2PerformanceRDropOcts OBJECT-TYPE
   SYNTAX      Counter64
   MAX-ACCESS  read-only
   STATUS      current
   DESCRIPTION
      "Path: swPort.performance.vlan.inPriorityQueues.h2Performance.redDroppedOctets

       64 bit unsigned wrappable counter."
   ::= {pr1646v2EthPortSwIXt2VlanInPQsH2PerformanceEntry 218103808}

pr1646v2EthPortSwIXt2VlanInPQsH2PerformanceCirTxOcts OBJECT-TYPE
   SYNTAX      Counter64
   MAX-ACCESS  read-only
   STATUS      current
   DESCRIPTION
      "Path: swPort.performance.vlan.inPriorityQueues.h2Performance.cirTxOctets

       64 bit unsigned wrappable counter."
   ::= {pr1646v2EthPortSwIXt2VlanInPQsH2PerformanceEntry 167772160}

pr1646v2EthPortSwIXt2VlanInPQsH2PerformanceEirTxOcts OBJECT-TYPE
   SYNTAX      Counter64
   MAX-ACCESS  read-only
   STATUS      current
   DESCRIPTION
      "Path: swPort.performance.vlan.inPriorityQueues.h2Performance.eirTxOctets

       64 bit unsigned wrappable counter."
   ::= {pr1646v2EthPortSwIXt2VlanInPQsH2PerformanceEntry 184549376}

pr1646v2EthPortSwIXt2VlanInPQsH2PerformanceViolTxOcts OBJECT-TYPE
   SYNTAX      Counter64
   MAX-ACCESS  read-only
   STATUS      current
   DESCRIPTION
      "Path: swPort.performance.vlan.inPriorityQueues.h2Performance.violateTxOctets

       64 bit unsigned wrappable counter."
   ::= {pr1646v2EthPortSwIXt2VlanInPQsH2PerformanceEntry 318767104}

pr1646v2EthPortSwIXt2VlanInPQsH2PerformanceBandwidth OBJECT-TYPE
   SYNTAX      Integer32
   MAX-ACCESS  read-only
   STATUS      current
   DESCRIPTION
      "Path: swPort.performance.vlan.inPriorityQueues.h2Performance.bandwidth

       unit name = bps
       formula = 8 * ; 8 /"
   ::= {pr1646v2EthPortSwIXt2VlanInPQsH2PerformanceEntry 268435456}

pr1646v2EthPortSwIXt2VlanInPQsH24Performance OBJECT-TYPE
   SYNTAX      SEQUENCE OF Pr1646v2EthPortSwIXt2VlanInPQsH24PerformanceEntry
   MAX-ACCESS  not-accessible
   STATUS      current
   DESCRIPTION
      ""
   ::= {pr1646v2EthPortSwIXt2Vlan 101056512}

pr1646v2EthPortSwIXt2VlanInPQsH24PerformanceEntry OBJECT-TYPE
   SYNTAX      Pr1646v2EthPortSwIXt2VlanInPQsH24PerformanceEntry
   MAX-ACCESS  not-accessible
   STATUS      current
   DESCRIPTION
      ""
   INDEX      { pr1646v2EthPortSwIXt2VlanInPQsH24PerformanceGlobalIx,
                pr1646v2EthPortSwIXt2VlanTableIx,
                pr1646v2EthPortSwIXt2VlanInPQsTableIx,
                pr1646v2EthPortSwIXt2VlanInPQsH24PerformanceTableIx }
   ::= {pr1646v2EthPortSwIXt2VlanInPQsH24Performance 1}

Pr1646v2EthPortSwIXt2VlanInPQsH24PerformanceEntry ::=
   SEQUENCE
      {
      pr1646v2EthPortSwIXt2VlanInPQsH24PerformanceGlobalIx
         GlobalIndex,
      pr1646v2EthPortSwIXt2VlanInPQsH24PerformanceTableIx
         TableIndex,
      pr1646v2EthPortSwIXt2VlanInPQsH24PerformanceSysUpTime
         TimeTicks,
      pr1646v2EthPortSwIXt2VlanInPQsH24PerformanceTotPkts
         Counter64,
      pr1646v2EthPortSwIXt2VlanInPQsH24PerformanceDirTxPkts
         Counter64,
      pr1646v2EthPortSwIXt2VlanInPQsH24PerformanceQdPkts
         Counter64,
      pr1646v2EthPortSwIXt2VlanInPQsH24PerformanceDropPkts
         Counter64,
      pr1646v2EthPortSwIXt2VlanInPQsH24PerformanceRDropPkts
         Counter64,
      pr1646v2EthPortSwIXt2VlanInPQsH24PerformanceCirTxPkts
         Counter64,
      pr1646v2EthPortSwIXt2VlanInPQsH24PerformanceEirTxPkts
         Counter64,
      pr1646v2EthPortSwIXt2VlanInPQsH24PerformanceViolTxPkts
         Counter64,
      pr1646v2EthPortSwIXt2VlanInPQsH24PerformanceTotOcts
         Counter64,
      pr1646v2EthPortSwIXt2VlanInPQsH24PerformanceDirTxOcts
         Counter64,
      pr1646v2EthPortSwIXt2VlanInPQsH24PerformanceQdOcts
         Counter64,
      pr1646v2EthPortSwIXt2VlanInPQsH24PerformanceDropOcts
         Counter64,
      pr1646v2EthPortSwIXt2VlanInPQsH24PerformanceRDropOcts
         Counter64,
      pr1646v2EthPortSwIXt2VlanInPQsH24PerformanceCirTxOcts
         Counter64,
      pr1646v2EthPortSwIXt2VlanInPQsH24PerformanceEirTxOcts
         Counter64,
      pr1646v2EthPortSwIXt2VlanInPQsH24PerformanceViolTxOcts
         Counter64,
      pr1646v2EthPortSwIXt2VlanInPQsH24PerformanceBandwidth
         Integer32
      }

pr1646v2EthPortSwIXt2VlanInPQsH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanInPQsH24PerformanceEntry 10}

pr1646v2EthPortSwIXt2VlanInPQsH24PerformanceTableIx OBJECT-TYPE
   SYNTAX      TableIndex
   MAX-ACCESS  not-accessible
   STATUS      current
   DESCRIPTION
      ""
   ::= {pr1646v2EthPortSwIXt2VlanInPQsH24PerformanceEntry 11}

pr1646v2EthPortSwIXt2VlanInPQsH24PerformanceSysUpTime OBJECT-TYPE
   SYNTAX      TimeTicks
   MAX-ACCESS  read-only
   STATUS      current
   DESCRIPTION
      "Path: swPort.performance.vlan.inPriorityQueues.h24Performance.sysUpTime

       Time in centi-second."
   ::= {pr1646v2EthPortSwIXt2VlanInPQsH24PerformanceEntry 16777216}

pr1646v2EthPortSwIXt2VlanInPQsH24PerformanceTotPkts OBJECT-TYPE
   SYNTAX      Counter64
   MAX-ACCESS  read-only
   STATUS      current
   DESCRIPTION
      "Path: swPort.performance.vlan.inPriorityQueues.h24Performance.totalPkts

       64 bit unsigned wrappable counter."
   ::= {pr1646v2EthPortSwIXt2VlanInPQsH24PerformanceEntry 234881024}

pr1646v2EthPortSwIXt2VlanInPQsH24PerformanceDirTxPkts OBJECT-TYPE
   SYNTAX      Counter64
   MAX-ACCESS  read-only
   STATUS      current
   DESCRIPTION
      "Path: swPort.performance.vlan.inPriorityQueues.h24Performance.directTxPkts

       64 bit unsigned wrappable counter."
   ::= {pr1646v2EthPortSwIXt2VlanInPQsH24PerformanceEntry 33554432}

pr1646v2EthPortSwIXt2VlanInPQsH24PerformanceQdPkts OBJECT-TYPE
   SYNTAX      Counter64
   MAX-ACCESS  read-only
   STATUS      current
   DESCRIPTION
      "Path: swPort.performance.vlan.inPriorityQueues.h24Performance.queuedPkts

       64 bit unsigned wrappable counter."
   ::= {pr1646v2EthPortSwIXt2VlanInPQsH24PerformanceEntry 50331648}

pr1646v2EthPortSwIXt2VlanInPQsH24PerformanceDropPkts OBJECT-TYPE
   SYNTAX      Counter64
   MAX-ACCESS  read-only
   STATUS      current
   DESCRIPTION
      "Path: swPort.performance.vlan.inPriorityQueues.h24Performance.droppedPkts

       64 bit unsigned wrappable counter."
   ::= {pr1646v2EthPortSwIXt2VlanInPQsH24PerformanceEntry 67108864}

pr1646v2EthPortSwIXt2VlanInPQsH24PerformanceRDropPkts OBJECT-TYPE
   SYNTAX      Counter64
   MAX-ACCESS  read-only
   STATUS      current
   DESCRIPTION
      "Path: swPort.performance.vlan.inPriorityQueues.h24Performance.redDroppedPkts

       64 bit unsigned wrappable counter."
   ::= {pr1646v2EthPortSwIXt2VlanInPQsH24PerformanceEntry 201326592}

pr1646v2EthPortSwIXt2VlanInPQsH24PerformanceCirTxPkts OBJECT-TYPE
   SYNTAX      Counter64
   MAX-ACCESS  read-only
   STATUS      current
   DESCRIPTION
      "Path: swPort.performance.vlan.inPriorityQueues.h24Performance.cirTxPkts

       64 bit unsigned wrappable counter."
   ::= {pr1646v2EthPortSwIXt2VlanInPQsH24PerformanceEntry 83886080}

pr1646v2EthPortSwIXt2VlanInPQsH24PerformanceEirTxPkts OBJECT-TYPE
   SYNTAX      Counter64
   MAX-ACCESS  read-only
   STATUS      current
   DESCRIPTION
      "Path: swPort.performance.vlan.inPriorityQueues.h24Performance.eirTxPkts

       64 bit unsigned wrappable counter."
   ::= {pr1646v2EthPortSwIXt2VlanInPQsH24PerformanceEntry 100663296}

pr1646v2EthPortSwIXt2VlanInPQsH24PerformanceViolTxPkts OBJECT-TYPE
   SYNTAX      Counter64
   MAX-ACCESS  read-only
   STATUS      current
   DESCRIPTION
      "Path: swPort.performance.vlan.inPriorityQueues.h24Performance.violateTxPkts

       64 bit unsigned wrappable counter."
   ::= {pr1646v2EthPortSwIXt2VlanInPQsH24PerformanceEntry 301989888}

pr1646v2EthPortSwIXt2VlanInPQsH24PerformanceTotOcts OBJECT-TYPE
   SYNTAX      Counter64
   MAX-ACCESS  read-only
   STATUS      current
   DESCRIPTION
      "Path: swPort.performance.vlan.inPriorityQueues.h24Performance.totalOctets

       64 bit unsigned wrappable counter."
   ::= {pr1646v2EthPortSwIXt2VlanInPQsH24PerformanceEntry 251658240}

pr1646v2EthPortSwIXt2VlanInPQsH24PerformanceDirTxOcts OBJECT-TYPE
   SYNTAX      Counter64
   MAX-ACCESS  read-only
   STATUS      current
   DESCRIPTION
      "Path: swPort.performance.vlan.inPriorityQueues.h24Performance.directTxOctets

       64 bit unsigned wrappable counter."
   ::= {pr1646v2EthPortSwIXt2VlanInPQsH24PerformanceEntry 117440512}

pr1646v2EthPortSwIXt2VlanInPQsH24PerformanceQdOcts OBJECT-TYPE
   SYNTAX      Counter64
   MAX-ACCESS  read-only
   STATUS      current
   DESCRIPTION
      "Path: swPort.performance.vlan.inPriorityQueues.h24Performance.queuedOctets

       64 bit unsigned wrappable counter."
   ::= {pr1646v2EthPortSwIXt2VlanInPQsH24PerformanceEntry 134217728}

pr1646v2EthPortSwIXt2VlanInPQsH24PerformanceDropOcts OBJECT-TYPE
   SYNTAX      Counter64
   MAX-ACCESS  read-only
   STATUS      current
   DESCRIPTION
      "Path: swPort.performance.vlan.inPriorityQueues.h24Performance.droppedOctets

       64 bit unsigned wrappable counter."
   ::= {pr1646v2EthPortSwIXt2VlanInPQsH24PerformanceEntry 150994944}

pr1646v2EthPortSwIXt2VlanInPQsH24PerformanceRDropOcts OBJECT-TYPE
   SYNTAX      Counter64
   MAX-ACCESS  read-only
   STATUS      current
   DESCRIPTION
      "Path: swPort.performance.vlan.inPriorityQueues.h24Performance.redDroppedOctets

       64 bit unsigned wrappable counter."
   ::= {pr1646v2EthPortSwIXt2VlanInPQsH24PerformanceEntry 218103808}

pr1646v2EthPortSwIXt2VlanInPQsH24PerformanceCirTxOcts OBJECT-TYPE
   SYNTAX      Counter64
   MAX-ACCESS  read-only
   STATUS      current
   DESCRIPTION
      "Path: swPort.performance.vlan.inPriorityQueues.h24Performance.cirTxOctets

       64 bit unsigned wrappable counter."
   ::= {pr1646v2EthPortSwIXt2VlanInPQsH24PerformanceEntry 167772160}

pr1646v2EthPortSwIXt2VlanInPQsH24PerformanceEirTxOcts OBJECT-TYPE
   SYNTAX      Counter64
   MAX-ACCESS  read-only
   STATUS      current
   DESCRIPTION
      "Path: swPort.performance.vlan.inPriorityQueues.h24Performance.eirTxOctets

       64 bit unsigned wrappable counter."
   ::= {pr1646v2EthPortSwIXt2VlanInPQsH24PerformanceEntry 184549376}

pr1646v2EthPortSwIXt2VlanInPQsH24PerformanceViolTxOcts OBJECT-TYPE
   SYNTAX      Counter64
   MAX-ACCESS  read-only
   STATUS      current
   DESCRIPTION
      "Path: swPort.performance.vlan.inPriorityQueues.h24Performance.violateTxOctets

       64 bit unsigned wrappable counter."
   ::= {pr1646v2EthPortSwIXt2VlanInPQsH24PerformanceEntry 318767104}

pr1646v2EthPortSwIXt2VlanInPQsH24PerformanceBandwidth OBJECT-TYPE
   SYNTAX      Integer32
   MAX-ACCESS  read-only
   STATUS      current
   DESCRIPTION
      "Path: swPort.performance.vlan.inPriorityQueues.h24Performance.bandwidth

       unit name = bps
       formula = 8 * ; 8 /"
   ::= {pr1646v2EthPortSwIXt2VlanInPQsH24PerformanceEntry 268435456}

pr1646v2EthPortSwIXt2VlanInPQsD7Performance OBJECT-TYPE
   SYNTAX      SEQUENCE OF Pr1646v2EthPortSwIXt2VlanInPQsD7PerformanceEntry
   MAX-ACCESS  not-accessible
   STATUS      current
   DESCRIPTION
      ""
   ::= {pr1646v2EthPortSwIXt2Vlan 101122048}

pr1646v2EthPortSwIXt2VlanInPQsD7PerformanceEntry OBJECT-TYPE
   SYNTAX      Pr1646v2EthPortSwIXt2VlanInPQsD7PerformanceEntry
   MAX-ACCESS  not-accessible
   STATUS      current
   DESCRIPTION
      ""
   INDEX      { pr1646v2EthPortSwIXt2VlanInPQsD7PerformanceGlobalIx,
                pr1646v2EthPortSwIXt2VlanTableIx,
                pr1646v2EthPortSwIXt2VlanInPQsTableIx,
                pr1646v2EthPortSwIXt2VlanInPQsD7PerformanceTableIx }
   ::= {pr1646v2EthPortSwIXt2VlanInPQsD7Performance 1}

Pr1646v2EthPortSwIXt2VlanInPQsD7PerformanceEntry ::=
   SEQUENCE
      {
      pr1646v2EthPortSwIXt2VlanInPQsD7PerformanceGlobalIx
         GlobalIndex,
      pr1646v2EthPortSwIXt2VlanInPQsD7PerformanceTableIx
         TableIndex,
      pr1646v2EthPortSwIXt2VlanInPQsD7PerformanceSysUpTime
         TimeTicks,
      pr1646v2EthPortSwIXt2VlanInPQsD7PerformanceTotPkts
         Counter64,
      pr1646v2EthPortSwIXt2VlanInPQsD7PerformanceDirTxPkts
         Counter64,
      pr1646v2EthPortSwIXt2VlanInPQsD7PerformanceQdPkts
         Counter64,
      pr1646v2EthPortSwIXt2VlanInPQsD7PerformanceDropPkts
         Counter64,
      pr1646v2EthPortSwIXt2VlanInPQsD7PerformanceRDropPkts
         Counter64,
      pr1646v2EthPortSwIXt2VlanInPQsD7PerformanceCirTxPkts
         Counter64,
      pr1646v2EthPortSwIXt2VlanInPQsD7PerformanceEirTxPkts
         Counter64,
      pr1646v2EthPortSwIXt2VlanInPQsD7PerformanceViolTxPkts
         Counter64,
      pr1646v2EthPortSwIXt2VlanInPQsD7PerformanceTotOcts
         Counter64,
      pr1646v2EthPortSwIXt2VlanInPQsD7PerformanceDirTxOcts
         Counter64,
      pr1646v2EthPortSwIXt2VlanInPQsD7PerformanceQdOcts
         Counter64,
      pr1646v2EthPortSwIXt2VlanInPQsD7PerformanceDropOcts
         Counter64,
      pr1646v2EthPortSwIXt2VlanInPQsD7PerformanceRDropOcts
         Counter64,
      pr1646v2EthPortSwIXt2VlanInPQsD7PerformanceCirTxOcts
         Counter64,
      pr1646v2EthPortSwIXt2VlanInPQsD7PerformanceEirTxOcts
         Counter64,
      pr1646v2EthPortSwIXt2VlanInPQsD7PerformanceViolTxOcts
         Counter64,
      pr1646v2EthPortSwIXt2VlanInPQsD7PerformanceBandwidth
         Integer32
      }

pr1646v2EthPortSwIXt2VlanInPQsD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanInPQsD7PerformanceEntry 10}

pr1646v2EthPortSwIXt2VlanInPQsD7PerformanceTableIx OBJECT-TYPE
   SYNTAX      TableIndex
   MAX-ACCESS  not-accessible
   STATUS      current
   DESCRIPTION
      ""
   ::= {pr1646v2EthPortSwIXt2VlanInPQsD7PerformanceEntry 11}

pr1646v2EthPortSwIXt2VlanInPQsD7PerformanceSysUpTime OBJECT-TYPE
   SYNTAX      TimeTicks
   MAX-ACCESS  read-only
   STATUS      current
   DESCRIPTION
      "Path: swPort.performance.vlan.inPriorityQueues.d7Performance.sysUpTime

       Time in centi-second."
   ::= {pr1646v2EthPortSwIXt2VlanInPQsD7PerformanceEntry 16777216}

pr1646v2EthPortSwIXt2VlanInPQsD7PerformanceTotPkts OBJECT-TYPE
   SYNTAX      Counter64
   MAX-ACCESS  read-only
   STATUS      current
   DESCRIPTION
      "Path: swPort.performance.vlan.inPriorityQueues.d7Performance.totalPkts

       64 bit unsigned wrappable counter."
   ::= {pr1646v2EthPortSwIXt2VlanInPQsD7PerformanceEntry 234881024}

pr1646v2EthPortSwIXt2VlanInPQsD7PerformanceDirTxPkts OBJECT-TYPE
   SYNTAX      Counter64
   MAX-ACCESS  read-only
   STATUS      current
   DESCRIPTION
      "Path: swPort.performance.vlan.inPriorityQueues.d7Performance.directTxPkts

       64 bit unsigned wrappable counter."
   ::= {pr1646v2EthPortSwIXt2VlanInPQsD7PerformanceEntry 33554432}

pr1646v2EthPortSwIXt2VlanInPQsD7PerformanceQdPkts OBJECT-TYPE
   SYNTAX      Counter64
   MAX-ACCESS  read-only
   STATUS      current
   DESCRIPTION
      "Path: swPort.performance.vlan.inPriorityQueues.d7Performance.queuedPkts

       64 bit unsigned wrappable counter."
   ::= {pr1646v2EthPortSwIXt2VlanInPQsD7PerformanceEntry 50331648}

pr1646v2EthPortSwIXt2VlanInPQsD7PerformanceDropPkts OBJECT-TYPE
   SYNTAX      Counter64
   MAX-ACCESS  read-only
   STATUS      current
   DESCRIPTION
      "Path: swPort.performance.vlan.inPriorityQueues.d7Performance.droppedPkts

       64 bit unsigned wrappable counter."
   ::= {pr1646v2EthPortSwIXt2VlanInPQsD7PerformanceEntry 67108864}

pr1646v2EthPortSwIXt2VlanInPQsD7PerformanceRDropPkts OBJECT-TYPE
   SYNTAX      Counter64
   MAX-ACCESS  read-only
   STATUS      current
   DESCRIPTION
      "Path: swPort.performance.vlan.inPriorityQueues.d7Performance.redDroppedPkts

       64 bit unsigned wrappable counter."
   ::= {pr1646v2EthPortSwIXt2VlanInPQsD7PerformanceEntry 201326592}

pr1646v2EthPortSwIXt2VlanInPQsD7PerformanceCirTxPkts OBJECT-TYPE
   SYNTAX      Counter64
   MAX-ACCESS  read-only
   STATUS      current
   DESCRIPTION
      "Path: swPort.performance.vlan.inPriorityQueues.d7Performance.cirTxPkts

       64 bit unsigned wrappable counter."
   ::= {pr1646v2EthPortSwIXt2VlanInPQsD7PerformanceEntry 83886080}

pr1646v2EthPortSwIXt2VlanInPQsD7PerformanceEirTxPkts OBJECT-TYPE
   SYNTAX      Counter64
   MAX-ACCESS  read-only
   STATUS      current
   DESCRIPTION
      "Path: swPort.performance.vlan.inPriorityQueues.d7Performance.eirTxPkts

       64 bit unsigned wrappable counter."
   ::= {pr1646v2EthPortSwIXt2VlanInPQsD7PerformanceEntry 100663296}

pr1646v2EthPortSwIXt2VlanInPQsD7PerformanceViolTxPkts OBJECT-TYPE
   SYNTAX      Counter64
   MAX-ACCESS  read-only
   STATUS      current
   DESCRIPTION
      "Path: swPort.performance.vlan.inPriorityQueues.d7Performance.violateTxPkts

       64 bit unsigned wrappable counter."
   ::= {pr1646v2EthPortSwIXt2VlanInPQsD7PerformanceEntry 301989888}

pr1646v2EthPortSwIXt2VlanInPQsD7PerformanceTotOcts OBJECT-TYPE
   SYNTAX      Counter64
   MAX-ACCESS  read-only
   STATUS      current
   DESCRIPTION
      "Path: swPort.performance.vlan.inPriorityQueues.d7Performance.totalOctets

       64 bit unsigned wrappable counter."
   ::= {pr1646v2EthPortSwIXt2VlanInPQsD7PerformanceEntry 251658240}

pr1646v2EthPortSwIXt2VlanInPQsD7PerformanceDirTxOcts OBJECT-TYPE
   SYNTAX      Counter64
   MAX-ACCESS  read-only
   STATUS      current
   DESCRIPTION
      "Path: swPort.performance.vlan.inPriorityQueues.d7Performance.directTxOctets

       64 bit unsigned wrappable counter."
   ::= {pr1646v2EthPortSwIXt2VlanInPQsD7PerformanceEntry 117440512}

pr1646v2EthPortSwIXt2VlanInPQsD7PerformanceQdOcts OBJECT-TYPE
   SYNTAX      Counter64
   MAX-ACCESS  read-only
   STATUS      current
   DESCRIPTION
      "Path: swPort.performance.vlan.inPriorityQueues.d7Performance.queuedOctets

       64 bit unsigned wrappable counter."
   ::= {pr1646v2EthPortSwIXt2VlanInPQsD7PerformanceEntry 134217728}

pr1646v2EthPortSwIXt2VlanInPQsD7PerformanceDropOcts OBJECT-TYPE
   SYNTAX      Counter64
   MAX-ACCESS  read-only
   STATUS      current
   DESCRIPTION
      "Path: swPort.performance.vlan.inPriorityQueues.d7Performance.droppedOctets

       64 bit unsigned wrappable counter."
   ::= {pr1646v2EthPortSwIXt2VlanInPQsD7PerformanceEntry 150994944}

pr1646v2EthPortSwIXt2VlanInPQsD7PerformanceRDropOcts OBJECT-TYPE
   SYNTAX      Counter64
   MAX-ACCESS  read-only
   STATUS      current
   DESCRIPTION
      "Path: swPort.performance.vlan.inPriorityQueues.d7Performance.redDroppedOctets

       64 bit unsigned wrappable counter."
   ::= {pr1646v2EthPortSwIXt2VlanInPQsD7PerformanceEntry 218103808}

pr1646v2EthPortSwIXt2VlanInPQsD7PerformanceCirTxOcts OBJECT-TYPE
   SYNTAX      Counter64
   MAX-ACCESS  read-only
   STATUS      current
   DESCRIPTION
      "Path: swPort.performance.vlan.inPriorityQueues.d7Performance.cirTxOctets

       64 bit unsigned wrappable counter."
   ::= {pr1646v2EthPortSwIXt2VlanInPQsD7PerformanceEntry 167772160}

pr1646v2EthPortSwIXt2VlanInPQsD7PerformanceEirTxOcts OBJECT-TYPE
   SYNTAX      Counter64
   MAX-ACCESS  read-only
   STATUS      current
   DESCRIPTION
      "Path: swPort.performance.vlan.inPriorityQueues.d7Performance.eirTxOctets

       64 bit unsigned wrappable counter."
   ::= {pr1646v2EthPortSwIXt2VlanInPQsD7PerformanceEntry 184549376}

pr1646v2EthPortSwIXt2VlanInPQsD7PerformanceViolTxOcts OBJECT-TYPE
   SYNTAX      Counter64
   MAX-ACCESS  read-only
   STATUS      current
   DESCRIPTION
      "Path: swPort.performance.vlan.inPriorityQueues.d7Performance.violateTxOctets

       64 bit unsigned wrappable counter."
   ::= {pr1646v2EthPortSwIXt2VlanInPQsD7PerformanceEntry 318767104}

pr1646v2EthPortSwIXt2VlanInPQsD7PerformanceBandwidth OBJECT-TYPE
   SYNTAX      Integer32
   MAX-ACCESS  read-only
   STATUS      current
   DESCRIPTION
      "Path: swPort.performance.vlan.inPriorityQueues.d7Performance.bandwidth

       unit name = bps
       formula = 8 * ; 8 /"
   ::= {pr1646v2EthPortSwIXt2VlanInPQsD7PerformanceEntry 268435456}

pr1646v2EthPortSwIXt2VlanOutPQs OBJECT-TYPE
   SYNTAX      SEQUENCE OF Pr1646v2EthPortSwIXt2VlanOutPQsEntry
   MAX-ACCESS  not-accessible
   STATUS      current
   DESCRIPTION
      ""
   ::= {pr1646v2EthPortSwIXt2Vlan 83886080}

pr1646v2EthPortSwIXt2VlanOutPQsEntry OBJECT-TYPE
   SYNTAX      Pr1646v2EthPortSwIXt2VlanOutPQsEntry
   MAX-ACCESS  not-accessible
   STATUS      current
   DESCRIPTION
      ""
   INDEX      { pr1646v2EthPortSwIXt2VlanOutPQsGlobalIx,
                pr1646v2EthPortSwIXt2VlanTableIx,
                pr1646v2EthPortSwIXt2VlanOutPQsTableIx }
   ::= {pr1646v2EthPortSwIXt2VlanOutPQs 1}

Pr1646v2EthPortSwIXt2VlanOutPQsEntry ::=
   SEQUENCE
      {
      pr1646v2EthPortSwIXt2VlanOutPQsGlobalIx
         GlobalIndex,
      pr1646v2EthPortSwIXt2VlanOutPQsTableIx
         TableIndex,
      pr1646v2EthPortSwIXt2VlanOutPQsName
         INTEGER,
      pr1646v2EthPortSwIXt2VlanOutPQsLength
         Integer32,
      pr1646v2EthPortSwIXt2VlanOutPQsOctetLength
         Integer32,
      pr1646v2EthPortSwIXt2VlanOutPQsRedLength
         Integer32,
      pr1646v2EthPortSwIXt2VlanOutPQsPacketsTotal
         Counter64,
      pr1646v2EthPortSwIXt2VlanOutPQsPacketsDirectTx
         Counter64,
      pr1646v2EthPortSwIXt2VlanOutPQsPacketsQueued
         Counter64,
      pr1646v2EthPortSwIXt2VlanOutPQsPacketsDropped
         Counter64,
      pr1646v2EthPortSwIXt2VlanOutPQsPacketsRedDropped
         Counter64,
      pr1646v2EthPortSwIXt2VlanOutPQsPacketsCirTx
         Counter64,
      pr1646v2EthPortSwIXt2VlanOutPQsPacketsEirTx
         Counter64,
      pr1646v2EthPortSwIXt2VlanOutPQsPacketsViolateTx
         Counter64,
      pr1646v2EthPortSwIXt2VlanOutPQsOctetsTotal
         Counter64,
      pr1646v2EthPortSwIXt2VlanOutPQsOctetsDirectTx
         Counter64,
      pr1646v2EthPortSwIXt2VlanOutPQsOctetsQueued
         Counter64,
      pr1646v2EthPortSwIXt2VlanOutPQsOctetsDropped
         Counter64,
      pr1646v2EthPortSwIXt2VlanOutPQsOctetsRedDropped
         Counter64,
      pr1646v2EthPortSwIXt2VlanOutPQsOctetsCirTx
         Counter64,
      pr1646v2EthPortSwIXt2VlanOutPQsOctetsEirTx
         Counter64,
      pr1646v2EthPortSwIXt2VlanOutPQsOctetsViolateTx
         Counter64,
      pr1646v2EthPortSwIXt2VlanOutPQsOctetsBandwidth15sec
         Integer32,
      pr1646v2EthPortSwIXt2VlanOutPQsOctetsBandwidth30sec
         Integer32,
      pr1646v2EthPortSwIXt2VlanOutPQsOctetsBandwidth1min
         Integer32,
      pr1646v2EthPortSwIXt2VlanOutPQsOctetsBandwidth2min
         Integer32,
      pr1646v2EthPortSwIXt2VlanOutPQsOctetsBandwidth5min
         Integer32
      }

pr1646v2EthPortSwIXt2VlanOutPQsGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanOutPQsEntry 10}

pr1646v2EthPortSwIXt2VlanOutPQsTableIx OBJECT-TYPE
   SYNTAX      TableIndex
   MAX-ACCESS  not-accessible
   STATUS      current
   DESCRIPTION
      ""
   ::= {pr1646v2EthPortSwIXt2VlanOutPQsEntry 11}

pr1646v2EthPortSwIXt2VlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: swPort.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2EthPortSwIXt2VlanOutPQsEntry 16777216}

pr1646v2EthPortSwIXt2VlanOutPQsLength OBJECT-TYPE
   SYNTAX      Integer32
   MAX-ACCESS  read-only
   STATUS      current
   DESCRIPTION
      "Path: swPort.performance.vlan.outPriorityQueues.length"
   ::= {pr1646v2EthPortSwIXt2VlanOutPQsEntry 33554432}

pr1646v2EthPortSwIXt2VlanOutPQsOctetLength OBJECT-TYPE
   SYNTAX      Integer32
   MAX-ACCESS  read-only
   STATUS      current
   DESCRIPTION
      "Path: swPort.performance.vlan.outPriorityQueues.octetLength"
   ::= {pr1646v2EthPortSwIXt2VlanOutPQsEntry 150994944}

pr1646v2EthPortSwIXt2VlanOutPQsRedLength OBJECT-TYPE
   SYNTAX      Integer32
   MAX-ACCESS  read-only
   STATUS      current
   DESCRIPTION
      "Path: swPort.performance.vlan.outPriorityQueues.redLength"
   ::= {pr1646v2EthPortSwIXt2VlanOutPQsEntry 134217728}

pr1646v2EthPortSwIXt2VlanOutPQsPacketsTotal OBJECT-TYPE
   SYNTAX      Counter64
   MAX-ACCESS  read-only
   STATUS      current
   DESCRIPTION
      "Path: swPort.performance.vlan.outPriorityQueues.packets.total

       64 bit unsigned wrappable counter."
   ::= {pr1646v2EthPortSwIXt2VlanOutPQsEntry 50790400}

pr1646v2EthPortSwIXt2VlanOutPQsPacketsDirectTx OBJECT-TYPE
   SYNTAX      Counter64
   MAX-ACCESS  read-only
   STATUS      current
   DESCRIPTION
      "Path: swPort.performance.vlan.outPriorityQueues.packets.directTx

       64 bit unsigned wrappable counter."
   ::= {pr1646v2EthPortSwIXt2VlanOutPQsEntry 50397184}

pr1646v2EthPortSwIXt2VlanOutPQsPacketsQueued OBJECT-TYPE
   SYNTAX      Counter64
   MAX-ACCESS  read-only
   STATUS      current
   DESCRIPTION
      "Path: swPort.performance.vlan.outPriorityQueues.packets.queued

       64 bit unsigned wrappable counter."
   ::= {pr1646v2EthPortSwIXt2VlanOutPQsEntry 50462720}

pr1646v2EthPortSwIXt2VlanOutPQsPacketsDropped OBJECT-TYPE
   SYNTAX      Counter64
   MAX-ACCESS  read-only
   STATUS      current
   DESCRIPTION
      "Path: swPort.performance.vlan.outPriorityQueues.packets.dropped

       64 bit unsigned wrappable counter."
   ::= {pr1646v2EthPortSwIXt2VlanOutPQsEntry 50528256}

pr1646v2EthPortSwIXt2VlanOutPQsPacketsRedDropped OBJECT-TYPE
   SYNTAX      Counter64
   MAX-ACCESS  read-only
   STATUS      current
   DESCRIPTION
      "Path: swPort.performance.vlan.outPriorityQueues.packets.redDropped

       64 bit unsigned wrappable counter."
   ::= {pr1646v2EthPortSwIXt2VlanOutPQsEntry 50724864}

pr1646v2EthPortSwIXt2VlanOutPQsPacketsCirTx OBJECT-TYPE
   SYNTAX      Counter64
   MAX-ACCESS  read-only
   STATUS      current
   DESCRIPTION
      "Path: swPort.performance.vlan.outPriorityQueues.packets.cirTx

       64 bit unsigned wrappable counter."
   ::= {pr1646v2EthPortSwIXt2VlanOutPQsEntry 50593792}

pr1646v2EthPortSwIXt2VlanOutPQsPacketsEirTx OBJECT-TYPE
   SYNTAX      Counter64
   MAX-ACCESS  read-only
   STATUS      current
   DESCRIPTION
      "Path: swPort.performance.vlan.outPriorityQueues.packets.eirTx

       64 bit unsigned wrappable counter."
   ::= {pr1646v2EthPortSwIXt2VlanOutPQsEntry 50659328}

pr1646v2EthPortSwIXt2VlanOutPQsPacketsViolateTx OBJECT-TYPE
   SYNTAX      Counter64
   MAX-ACCESS  read-only
   STATUS      current
   DESCRIPTION
      "Path: swPort.performance.vlan.outPriorityQueues.packets.violateTx

       64 bit unsigned wrappable counter."
   ::= {pr1646v2EthPortSwIXt2VlanOutPQsEntry 50855936}

pr1646v2EthPortSwIXt2VlanOutPQsOctetsTotal OBJECT-TYPE
   SYNTAX      Counter64
   MAX-ACCESS  read-only
   STATUS      current
   DESCRIPTION
      "Path: swPort.performance.vlan.outPriorityQueues.octets.total

       64 bit unsigned wrappable counter."
   ::= {pr1646v2EthPortSwIXt2VlanOutPQsEntry 67567616}

pr1646v2EthPortSwIXt2VlanOutPQsOctetsDirectTx OBJECT-TYPE
   SYNTAX      Counter64
   MAX-ACCESS  read-only
   STATUS      current
   DESCRIPTION
      "Path: swPort.performance.vlan.outPriorityQueues.octets.directTx

       64 bit unsigned wrappable counter."
   ::= {pr1646v2EthPortSwIXt2VlanOutPQsEntry 67174400}

pr1646v2EthPortSwIXt2VlanOutPQsOctetsQueued OBJECT-TYPE
   SYNTAX      Counter64
   MAX-ACCESS  read-only
   STATUS      current
   DESCRIPTION
      "Path: swPort.performance.vlan.outPriorityQueues.octets.queued

       64 bit unsigned wrappable counter."
   ::= {pr1646v2EthPortSwIXt2VlanOutPQsEntry 67239936}

pr1646v2EthPortSwIXt2VlanOutPQsOctetsDropped OBJECT-TYPE
   SYNTAX      Counter64
   MAX-ACCESS  read-only
   STATUS      current
   DESCRIPTION
      "Path: swPort.performance.vlan.outPriorityQueues.octets.dropped

       64 bit unsigned wrappable counter."
   ::= {pr1646v2EthPortSwIXt2VlanOutPQsEntry 67305472}

pr1646v2EthPortSwIXt2VlanOutPQsOctetsRedDropped OBJECT-TYPE
   SYNTAX      Counter64
   MAX-ACCESS  read-only
   STATUS      current
   DESCRIPTION
      "Path: swPort.performance.vlan.outPriorityQueues.octets.redDropped

       64 bit unsigned wrappable counter."
   ::= {pr1646v2EthPortSwIXt2VlanOutPQsEntry 67502080}

pr1646v2EthPortSwIXt2VlanOutPQsOctetsCirTx OBJECT-TYPE
   SYNTAX      Counter64
   MAX-ACCESS  read-only
   STATUS      current
   DESCRIPTION
      "Path: swPort.performance.vlan.outPriorityQueues.octets.cirTx

       64 bit unsigned wrappable counter."
   ::= {pr1646v2EthPortSwIXt2VlanOutPQsEntry 67371008}

pr1646v2EthPortSwIXt2VlanOutPQsOctetsEirTx OBJECT-TYPE
   SYNTAX      Counter64
   MAX-ACCESS  read-only
   STATUS      current
   DESCRIPTION
      "Path: swPort.performance.vlan.outPriorityQueues.octets.eirTx

       64 bit unsigned wrappable counter."
   ::= {pr1646v2EthPortSwIXt2VlanOutPQsEntry 67436544}

pr1646v2EthPortSwIXt2VlanOutPQsOctetsViolateTx OBJECT-TYPE
   SYNTAX      Counter64
   MAX-ACCESS  read-only
   STATUS      current
   DESCRIPTION
      "Path: swPort.performance.vlan.outPriorityQueues.octets.violateTx

       64 bit unsigned wrappable counter."
   ::= {pr1646v2EthPortSwIXt2VlanOutPQsEntry 67633152}

pr1646v2EthPortSwIXt2VlanOutPQsOctetsBandwidth15sec OBJECT-TYPE
   SYNTAX      Integer32
   MAX-ACCESS  read-only
   STATUS      current
   DESCRIPTION
      "Path: swPort.performance.vlan.outPriorityQueues.octets.bandwidth.15sec

       unit name = bps
       formula = 8 * ; 8 /"
   ::= {pr1646v2EthPortSwIXt2VlanOutPQsEntry 70386944}

pr1646v2EthPortSwIXt2VlanOutPQsOctetsBandwidth30sec OBJECT-TYPE
   SYNTAX      Integer32
   MAX-ACCESS  read-only
   STATUS      current
   DESCRIPTION
      "Path: swPort.performance.vlan.outPriorityQueues.octets.bandwidth.30sec

       unit name = bps
       formula = 8 * ; 8 /"
   ::= {pr1646v2EthPortSwIXt2VlanOutPQsEntry 70388224}

pr1646v2EthPortSwIXt2VlanOutPQsOctetsBandwidth1min OBJECT-TYPE
   SYNTAX      Integer32
   MAX-ACCESS  read-only
   STATUS      current
   DESCRIPTION
      "Path: swPort.performance.vlan.outPriorityQueues.octets.bandwidth.1min

       unit name = bps
       formula = 8 * ; 8 /"
   ::= {pr1646v2EthPortSwIXt2VlanOutPQsEntry 70390784}

pr1646v2EthPortSwIXt2VlanOutPQsOctetsBandwidth2min OBJECT-TYPE
   SYNTAX      Integer32
   MAX-ACCESS  read-only
   STATUS      current
   DESCRIPTION
      "Path: swPort.performance.vlan.outPriorityQueues.octets.bandwidth.2min

       unit name = bps
       formula = 8 * ; 8 /"
   ::= {pr1646v2EthPortSwIXt2VlanOutPQsEntry 70395904}

pr1646v2EthPortSwIXt2VlanOutPQsOctetsBandwidth5min OBJECT-TYPE
   SYNTAX      Integer32
   MAX-ACCESS  read-only
   STATUS      current
   DESCRIPTION
      "Path: swPort.performance.vlan.outPriorityQueues.octets.bandwidth.5min

       unit name = bps
       formula = 8 * ; 8 /"
   ::= {pr1646v2EthPortSwIXt2VlanOutPQsEntry 70411264}

pr1646v2EthPortSwIXt2VlanOutPQsH2Performance OBJECT-TYPE
   SYNTAX      SEQUENCE OF Pr1646v2EthPortSwIXt2VlanOutPQsH2PerformanceEntry
   MAX-ACCESS  not-accessible
   STATUS      current
   DESCRIPTION
      ""
   ::= {pr1646v2EthPortSwIXt2Vlan 84213760}

pr1646v2EthPortSwIXt2VlanOutPQsH2PerformanceEntry OBJECT-TYPE
   SYNTAX      Pr1646v2EthPortSwIXt2VlanOutPQsH2PerformanceEntry
   MAX-ACCESS  not-accessible
   STATUS      current
   DESCRIPTION
      ""
   INDEX      { pr1646v2EthPortSwIXt2VlanOutPQsH2PerformanceGlobalIx,
                pr1646v2EthPortSwIXt2VlanTableIx,
                pr1646v2EthPortSwIXt2VlanOutPQsTableIx,
                pr1646v2EthPortSwIXt2VlanOutPQsH2PerformanceTableIx }
   ::= {pr1646v2EthPortSwIXt2VlanOutPQsH2Performance 1}

Pr1646v2EthPortSwIXt2VlanOutPQsH2PerformanceEntry ::=
   SEQUENCE
      {
      pr1646v2EthPortSwIXt2VlanOutPQsH2PerformanceGlobalIx
         GlobalIndex,
      pr1646v2EthPortSwIXt2VlanOutPQsH2PerformanceTableIx
         TableIndex,
      pr1646v2EthPortSwIXt2VlanOutPQsH2PerformanceSysUpTime
         TimeTicks,
      pr1646v2EthPortSwIXt2VlanOutPQsH2PerformanceTotPkts
         Counter64,
      pr1646v2EthPortSwIXt2VlanOutPQsH2PerformanceDirTxPkts
         Counter64,
      pr1646v2EthPortSwIXt2VlanOutPQsH2PerformanceQdPkts
         Counter64,
      pr1646v2EthPortSwIXt2VlanOutPQsH2PerformanceDropPkts
         Counter64,
      pr1646v2EthPortSwIXt2VlanOutPQsH2PerformanceRDropPkts
         Counter64,
      pr1646v2EthPortSwIXt2VlanOutPQsH2PerformanceCirTxPkts
         Counter64,
      pr1646v2EthPortSwIXt2VlanOutPQsH2PerformanceEirTxPkts
         Counter64,
      pr1646v2EthPortSwIXt2VlanOutPQsH2PerformanceViolTxPkts
         Counter64,
      pr1646v2EthPortSwIXt2VlanOutPQsH2PerformanceTotOcts
         Counter64,
      pr1646v2EthPortSwIXt2VlanOutPQsH2PerformanceDirTxOcts
         Counter64,
      pr1646v2EthPortSwIXt2VlanOutPQsH2PerformanceQdOcts
         Counter64,
      pr1646v2EthPortSwIXt2VlanOutPQsH2PerformanceDropOcts
         Counter64,
      pr1646v2EthPortSwIXt2VlanOutPQsH2PerformanceRDropOcts
         Counter64,
      pr1646v2EthPortSwIXt2VlanOutPQsH2PerformanceCirTxOcts
         Counter64,
      pr1646v2EthPortSwIXt2VlanOutPQsH2PerformanceEirTxOcts
         Counter64,
      pr1646v2EthPortSwIXt2VlanOutPQsH2PerformanceViolTxOcts
         Counter64,
      pr1646v2EthPortSwIXt2VlanOutPQsH2PerformanceBandwidth
         Integer32
      }

pr1646v2EthPortSwIXt2VlanOutPQsH2PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanOutPQsH2PerformanceEntry 10}

pr1646v2EthPortSwIXt2VlanOutPQsH2PerformanceTableIx OBJECT-TYPE
   SYNTAX      TableIndex
   MAX-ACCESS  not-accessible
   STATUS      current
   DESCRIPTION
      ""
   ::= {pr1646v2EthPortSwIXt2VlanOutPQsH2PerformanceEntry 11}

pr1646v2EthPortSwIXt2VlanOutPQsH2PerformanceSysUpTime OBJECT-TYPE
   SYNTAX      TimeTicks
   MAX-ACCESS  read-only
   STATUS      current
   DESCRIPTION
      "Path: swPort.performance.vlan.outPriorityQueues.h2Performance.sysUpTime

       Time in centi-second."
   ::= {pr1646v2EthPortSwIXt2VlanOutPQsH2PerformanceEntry 16777216}

pr1646v2EthPortSwIXt2VlanOutPQsH2PerformanceTotPkts OBJECT-TYPE
   SYNTAX      Counter64
   MAX-ACCESS  read-only
   STATUS      current
   DESCRIPTION
      "Path: swPort.performance.vlan.outPriorityQueues.h2Performance.totalPkts

       64 bit unsigned wrappable counter."
   ::= {pr1646v2EthPortSwIXt2VlanOutPQsH2PerformanceEntry 234881024}

pr1646v2EthPortSwIXt2VlanOutPQsH2PerformanceDirTxPkts OBJECT-TYPE
   SYNTAX      Counter64
   MAX-ACCESS  read-only
   STATUS      current
   DESCRIPTION
      "Path: swPort.performance.vlan.outPriorityQueues.h2Performance.directTxPkts

       64 bit unsigned wrappable counter."
   ::= {pr1646v2EthPortSwIXt2VlanOutPQsH2PerformanceEntry 33554432}

pr1646v2EthPortSwIXt2VlanOutPQsH2PerformanceQdPkts OBJECT-TYPE
   SYNTAX      Counter64
   MAX-ACCESS  read-only
   STATUS      current
   DESCRIPTION
      "Path: swPort.performance.vlan.outPriorityQueues.h2Performance.queuedPkts

       64 bit unsigned wrappable counter."
   ::= {pr1646v2EthPortSwIXt2VlanOutPQsH2PerformanceEntry 50331648}

pr1646v2EthPortSwIXt2VlanOutPQsH2PerformanceDropPkts OBJECT-TYPE
   SYNTAX      Counter64
   MAX-ACCESS  read-only
   STATUS      current
   DESCRIPTION
      "Path: swPort.performance.vlan.outPriorityQueues.h2Performance.droppedPkts

       64 bit unsigned wrappable counter."
   ::= {pr1646v2EthPortSwIXt2VlanOutPQsH2PerformanceEntry 67108864}

pr1646v2EthPortSwIXt2VlanOutPQsH2PerformanceRDropPkts OBJECT-TYPE
   SYNTAX      Counter64
   MAX-ACCESS  read-only
   STATUS      current
   DESCRIPTION
      "Path: swPort.performance.vlan.outPriorityQueues.h2Performance.redDroppedPkts

       64 bit unsigned wrappable counter."
   ::= {pr1646v2EthPortSwIXt2VlanOutPQsH2PerformanceEntry 201326592}

pr1646v2EthPortSwIXt2VlanOutPQsH2PerformanceCirTxPkts OBJECT-TYPE
   SYNTAX      Counter64
   MAX-ACCESS  read-only
   STATUS      current
   DESCRIPTION
      "Path: swPort.performance.vlan.outPriorityQueues.h2Performance.cirTxPkts

       64 bit unsigned wrappable counter."
   ::= {pr1646v2EthPortSwIXt2VlanOutPQsH2PerformanceEntry 83886080}

pr1646v2EthPortSwIXt2VlanOutPQsH2PerformanceEirTxPkts OBJECT-TYPE
   SYNTAX      Counter64
   MAX-ACCESS  read-only
   STATUS      current
   DESCRIPTION
      "Path: swPort.performance.vlan.outPriorityQueues.h2Performance.eirTxPkts

       64 bit unsigned wrappable counter."
   ::= {pr1646v2EthPortSwIXt2VlanOutPQsH2PerformanceEntry 100663296}

pr1646v2EthPortSwIXt2VlanOutPQsH2PerformanceViolTxPkts OBJECT-TYPE
   SYNTAX      Counter64
   MAX-ACCESS  read-only
   STATUS      current
   DESCRIPTION
      "Path: swPort.performance.vlan.outPriorityQueues.h2Performance.violateTxPkts

       64 bit unsigned wrappable counter."
   ::= {pr1646v2EthPortSwIXt2VlanOutPQsH2PerformanceEntry 301989888}

pr1646v2EthPortSwIXt2VlanOutPQsH2PerformanceTotOcts OBJECT-TYPE
   SYNTAX      Counter64
   MAX-ACCESS  read-only
   STATUS      current
   DESCRIPTION
      "Path: swPort.performance.vlan.outPriorityQueues.h2Performance.totalOctets

       64 bit unsigned wrappable counter."
   ::= {pr1646v2EthPortSwIXt2VlanOutPQsH2PerformanceEntry 251658240}

pr1646v2EthPortSwIXt2VlanOutPQsH2PerformanceDirTxOcts OBJECT-TYPE
   SYNTAX      Counter64
   MAX-ACCESS  read-only
   STATUS      current
   DESCRIPTION
      "Path: swPort.performance.vlan.outPriorityQueues.h2Performance.directTxOctets

       64 bit unsigned wrappable counter."
   ::= {pr1646v2EthPortSwIXt2VlanOutPQsH2PerformanceEntry 117440512}

pr1646v2EthPortSwIXt2VlanOutPQsH2PerformanceQdOcts OBJECT-TYPE
   SYNTAX      Counter64
   MAX-ACCESS  read-only
   STATUS      current
   DESCRIPTION
      "Path: swPort.performance.vlan.outPriorityQueues.h2Performance.queuedOctets

       64 bit unsigned wrappable counter."
   ::= {pr1646v2EthPortSwIXt2VlanOutPQsH2PerformanceEntry 134217728}

pr1646v2EthPortSwIXt2VlanOutPQsH2PerformanceDropOcts OBJECT-TYPE
   SYNTAX      Counter64
   MAX-ACCESS  read-only
   STATUS      current
   DESCRIPTION
      "Path: swPort.performance.vlan.outPriorityQueues.h2Performance.droppedOctets

       64 bit unsigned wrappable counter."
   ::= {pr1646v2EthPortSwIXt2VlanOutPQsH2PerformanceEntry 150994944}

pr1646v2EthPortSwIXt2VlanOutPQsH2PerformanceRDropOcts OBJECT-TYPE
   SYNTAX      Counter64
   MAX-ACCESS  read-only
   STATUS      current
   DESCRIPTION
      "Path: swPort.performance.vlan.outPriorityQueues.h2Performance.redDroppedOctets

       64 bit unsigned wrappable counter."
   ::= {pr1646v2EthPortSwIXt2VlanOutPQsH2PerformanceEntry 218103808}

pr1646v2EthPortSwIXt2VlanOutPQsH2PerformanceCirTxOcts OBJECT-TYPE
   SYNTAX      Counter64
   MAX-ACCESS  read-only
   STATUS      current
   DESCRIPTION
      "Path: swPort.performance.vlan.outPriorityQueues.h2Performance.cirTxOctets

       64 bit unsigned wrappable counter."
   ::= {pr1646v2EthPortSwIXt2VlanOutPQsH2PerformanceEntry 167772160}

pr1646v2EthPortSwIXt2VlanOutPQsH2PerformanceEirTxOcts OBJECT-TYPE
   SYNTAX      Counter64
   MAX-ACCESS  read-only
   STATUS      current
   DESCRIPTION
      "Path: swPort.performance.vlan.outPriorityQueues.h2Performance.eirTxOctets

       64 bit unsigned wrappable counter."
   ::= {pr1646v2EthPortSwIXt2VlanOutPQsH2PerformanceEntry 184549376}

pr1646v2EthPortSwIXt2VlanOutPQsH2PerformanceViolTxOcts OBJECT-TYPE
   SYNTAX      Counter64
   MAX-ACCESS  read-only
   STATUS      current
   DESCRIPTION
      "Path: swPort.performance.vlan.outPriorityQueues.h2Performance.violateTxOctets

       64 bit unsigned wrappable counter."
   ::= {pr1646v2EthPortSwIXt2VlanOutPQsH2PerformanceEntry 318767104}

pr1646v2EthPortSwIXt2VlanOutPQsH2PerformanceBandwidth OBJECT-TYPE
   SYNTAX      Integer32
   MAX-ACCESS  read-only
   STATUS      current
   DESCRIPTION
      "Path: swPort.performance.vlan.outPriorityQueues.h2Performance.bandwidth

       unit name = bps
       formula = 8 * ; 8 /"
   ::= {pr1646v2EthPortSwIXt2VlanOutPQsH2PerformanceEntry 268435456}

pr1646v2EthPortSwIXt2VlanOutPQsH24Performance OBJECT-TYPE
   SYNTAX      SEQUENCE OF Pr1646v2EthPortSwIXt2VlanOutPQsH24PerformanceEntry
   MAX-ACCESS  not-accessible
   STATUS      current
   DESCRIPTION
      ""
   ::= {pr1646v2EthPortSwIXt2Vlan 84279296}

pr1646v2EthPortSwIXt2VlanOutPQsH24PerformanceEntry OBJECT-TYPE
   SYNTAX      Pr1646v2EthPortSwIXt2VlanOutPQsH24PerformanceEntry
   MAX-ACCESS  not-accessible
   STATUS      current
   DESCRIPTION
      ""
   INDEX      { pr1646v2EthPortSwIXt2VlanOutPQsH24PerformanceGlobalIx,
                pr1646v2EthPortSwIXt2VlanTableIx,
                pr1646v2EthPortSwIXt2VlanOutPQsTableIx,
                pr1646v2EthPortSwIXt2VlanOutPQsH24PerformanceTableIx }
   ::= {pr1646v2EthPortSwIXt2VlanOutPQsH24Performance 1}

Pr1646v2EthPortSwIXt2VlanOutPQsH24PerformanceEntry ::=
   SEQUENCE
      {
      pr1646v2EthPortSwIXt2VlanOutPQsH24PerformanceGlobalIx
         GlobalIndex,
      pr1646v2EthPortSwIXt2VlanOutPQsH24PerformanceTableIx
         TableIndex,
      pr1646v2EthPortSwIXt2VlanOutPQsH24PerformanceSysUpTime
         TimeTicks,
      pr1646v2EthPortSwIXt2VlanOutPQsH24PerformanceTotPkts
         Counter64,
      pr1646v2EthPortSwIXt2VlanOutPQsH24PerformanceDirTxPkts
         Counter64,
      pr1646v2EthPortSwIXt2VlanOutPQsH24PerformanceQdPkts
         Counter64,
      pr1646v2EthPortSwIXt2VlanOutPQsH24PerformanceDropPkts
         Counter64,
      pr1646v2EthPortSwIXt2VlanOutPQsH24PerformanceRDropPkts
         Counter64,
      pr1646v2EthPortSwIXt2VlanOutPQsH24PerformanceCirTxPkts
         Counter64,
      pr1646v2EthPortSwIXt2VlanOutPQsH24PerformanceEirTxPkts
         Counter64,
      pr1646v2EthPortSwIXt2VlanOutPQsH24PerformanceViolTxPkts
         Counter64,
      pr1646v2EthPortSwIXt2VlanOutPQsH24PerformanceTotOcts
         Counter64,
      pr1646v2EthPortSwIXt2VlanOutPQsH24PerformanceDirTxOcts
         Counter64,
      pr1646v2EthPortSwIXt2VlanOutPQsH24PerformanceQdOcts
         Counter64,
      pr1646v2EthPortSwIXt2VlanOutPQsH24PerformanceDropOcts
         Counter64,
      pr1646v2EthPortSwIXt2VlanOutPQsH24PerformanceRDropOcts
         Counter64,
      pr1646v2EthPortSwIXt2VlanOutPQsH24PerformanceCirTxOcts
         Counter64,
      pr1646v2EthPortSwIXt2VlanOutPQsH24PerformanceEirTxOcts
         Counter64,
      pr1646v2EthPortSwIXt2VlanOutPQsH24PerformanceViolTxOcts
         Counter64,
      pr1646v2EthPortSwIXt2VlanOutPQsH24PerformanceBandwidth
         Integer32
      }

pr1646v2EthPortSwIXt2VlanOutPQsH24PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanOutPQsH24PerformanceEntry 10}

pr1646v2EthPortSwIXt2VlanOutPQsH24PerformanceTableIx OBJECT-TYPE
   SYNTAX      TableIndex
   MAX-ACCESS  not-accessible
   STATUS      current
   DESCRIPTION
      ""
   ::= {pr1646v2EthPortSwIXt2VlanOutPQsH24PerformanceEntry 11}

pr1646v2EthPortSwIXt2VlanOutPQsH24PerformanceSysUpTime OBJECT-TYPE
   SYNTAX      TimeTicks
   MAX-ACCESS  read-only
   STATUS      current
   DESCRIPTION
      "Path: swPort.performance.vlan.outPriorityQueues.h24Performance.sysUpTime

       Time in centi-second."
   ::= {pr1646v2EthPortSwIXt2VlanOutPQsH24PerformanceEntry 16777216}

pr1646v2EthPortSwIXt2VlanOutPQsH24PerformanceTotPkts OBJECT-TYPE
   SYNTAX      Counter64
   MAX-ACCESS  read-only
   STATUS      current
   DESCRIPTION
      "Path: swPort.performance.vlan.outPriorityQueues.h24Performance.totalPkts

       64 bit unsigned wrappable counter."
   ::= {pr1646v2EthPortSwIXt2VlanOutPQsH24PerformanceEntry 234881024}

pr1646v2EthPortSwIXt2VlanOutPQsH24PerformanceDirTxPkts OBJECT-TYPE
   SYNTAX      Counter64
   MAX-ACCESS  read-only
   STATUS      current
   DESCRIPTION
      "Path: swPort.performance.vlan.outPriorityQueues.h24Performance.directTxPkts

       64 bit unsigned wrappable counter."
   ::= {pr1646v2EthPortSwIXt2VlanOutPQsH24PerformanceEntry 33554432}

pr1646v2EthPortSwIXt2VlanOutPQsH24PerformanceQdPkts OBJECT-TYPE
   SYNTAX      Counter64
   MAX-ACCESS  read-only
   STATUS      current
   DESCRIPTION
      "Path: swPort.performance.vlan.outPriorityQueues.h24Performance.queuedPkts

       64 bit unsigned wrappable counter."
   ::= {pr1646v2EthPortSwIXt2VlanOutPQsH24PerformanceEntry 50331648}

pr1646v2EthPortSwIXt2VlanOutPQsH24PerformanceDropPkts OBJECT-TYPE
   SYNTAX      Counter64
   MAX-ACCESS  read-only
   STATUS      current
   DESCRIPTION
      "Path: swPort.performance.vlan.outPriorityQueues.h24Performance.droppedPkts

       64 bit unsigned wrappable counter."
   ::= {pr1646v2EthPortSwIXt2VlanOutPQsH24PerformanceEntry 67108864}

pr1646v2EthPortSwIXt2VlanOutPQsH24PerformanceRDropPkts OBJECT-TYPE
   SYNTAX      Counter64
   MAX-ACCESS  read-only
   STATUS      current
   DESCRIPTION
      "Path: swPort.performance.vlan.outPriorityQueues.h24Performance.redDroppedPkts

       64 bit unsigned wrappable counter."
   ::= {pr1646v2EthPortSwIXt2VlanOutPQsH24PerformanceEntry 201326592}

pr1646v2EthPortSwIXt2VlanOutPQsH24PerformanceCirTxPkts OBJECT-TYPE
   SYNTAX      Counter64
   MAX-ACCESS  read-only
   STATUS      current
   DESCRIPTION
      "Path: swPort.performance.vlan.outPriorityQueues.h24Performance.cirTxPkts

       64 bit unsigned wrappable counter."
   ::= {pr1646v2EthPortSwIXt2VlanOutPQsH24PerformanceEntry 83886080}

pr1646v2EthPortSwIXt2VlanOutPQsH24PerformanceEirTxPkts OBJECT-TYPE
   SYNTAX      Counter64
   MAX-ACCESS  read-only
   STATUS      current
   DESCRIPTION
      "Path: swPort.performance.vlan.outPriorityQueues.h24Performance.eirTxPkts

       64 bit unsigned wrappable counter."
   ::= {pr1646v2EthPortSwIXt2VlanOutPQsH24PerformanceEntry 100663296}

pr1646v2EthPortSwIXt2VlanOutPQsH24PerformanceViolTxPkts OBJECT-TYPE
   SYNTAX      Counter64
   MAX-ACCESS  read-only
   STATUS      current
   DESCRIPTION
      "Path: swPort.performance.vlan.outPriorityQueues.h24Performance.violateTxPkts

       64 bit unsigned wrappable counter."
   ::= {pr1646v2EthPortSwIXt2VlanOutPQsH24PerformanceEntry 301989888}

pr1646v2EthPortSwIXt2VlanOutPQsH24PerformanceTotOcts OBJECT-TYPE
   SYNTAX      Counter64
   MAX-ACCESS  read-only
   STATUS      current
   DESCRIPTION
      "Path: swPort.performance.vlan.outPriorityQueues.h24Performance.totalOctets

       64 bit unsigned wrappable counter."
   ::= {pr1646v2EthPortSwIXt2VlanOutPQsH24PerformanceEntry 251658240}

pr1646v2EthPortSwIXt2VlanOutPQsH24PerformanceDirTxOcts OBJECT-TYPE
   SYNTAX      Counter64
   MAX-ACCESS  read-only
   STATUS      current
   DESCRIPTION
      "Path: swPort.performance.vlan.outPriorityQueues.h24Performance.directTxOctets

       64 bit unsigned wrappable counter."
   ::= {pr1646v2EthPortSwIXt2VlanOutPQsH24PerformanceEntry 117440512}

pr1646v2EthPortSwIXt2VlanOutPQsH24PerformanceQdOcts OBJECT-TYPE
   SYNTAX      Counter64
   MAX-ACCESS  read-only
   STATUS      current
   DESCRIPTION
      "Path: swPort.performance.vlan.outPriorityQueues.h24Performance.queuedOctets

       64 bit unsigned wrappable counter."
   ::= {pr1646v2EthPortSwIXt2VlanOutPQsH24PerformanceEntry 134217728}

pr1646v2EthPortSwIXt2VlanOutPQsH24PerformanceDropOcts OBJECT-TYPE
   SYNTAX      Counter64
   MAX-ACCESS  read-only
   STATUS      current
   DESCRIPTION
      "Path: swPort.performance.vlan.outPriorityQueues.h24Performance.droppedOctets

       64 bit unsigned wrappable counter."
   ::= {pr1646v2EthPortSwIXt2VlanOutPQsH24PerformanceEntry 150994944}

pr1646v2EthPortSwIXt2VlanOutPQsH24PerformanceRDropOcts OBJECT-TYPE
   SYNTAX      Counter64
   MAX-ACCESS  read-only
   STATUS      current
   DESCRIPTION
      "Path: swPort.performance.vlan.outPriorityQueues.h24Performance.redDroppedOctets

       64 bit unsigned wrappable counter."
   ::= {pr1646v2EthPortSwIXt2VlanOutPQsH24PerformanceEntry 218103808}

pr1646v2EthPortSwIXt2VlanOutPQsH24PerformanceCirTxOcts OBJECT-TYPE
   SYNTAX      Counter64
   MAX-ACCESS  read-only
   STATUS      current
   DESCRIPTION
      "Path: swPort.performance.vlan.outPriorityQueues.h24Performance.cirTxOctets

       64 bit unsigned wrappable counter."
   ::= {pr1646v2EthPortSwIXt2VlanOutPQsH24PerformanceEntry 167772160}

pr1646v2EthPortSwIXt2VlanOutPQsH24PerformanceEirTxOcts OBJECT-TYPE
   SYNTAX      Counter64
   MAX-ACCESS  read-only
   STATUS      current
   DESCRIPTION
      "Path: swPort.performance.vlan.outPriorityQueues.h24Performance.eirTxOctets

       64 bit unsigned wrappable counter."
   ::= {pr1646v2EthPortSwIXt2VlanOutPQsH24PerformanceEntry 184549376}

pr1646v2EthPortSwIXt2VlanOutPQsH24PerformanceViolTxOcts OBJECT-TYPE
   SYNTAX      Counter64
   MAX-ACCESS  read-only
   STATUS      current
   DESCRIPTION
      "Path: swPort.performance.vlan.outPriorityQueues.h24Performance.violateTxOctets

       64 bit unsigned wrappable counter."
   ::= {pr1646v2EthPortSwIXt2VlanOutPQsH24PerformanceEntry 318767104}

pr1646v2EthPortSwIXt2VlanOutPQsH24PerformanceBandwidth OBJECT-TYPE
   SYNTAX      Integer32
   MAX-ACCESS  read-only
   STATUS      current
   DESCRIPTION
      "Path: swPort.performance.vlan.outPriorityQueues.h24Performance.bandwidth

       unit name = bps
       formula = 8 * ; 8 /"
   ::= {pr1646v2EthPortSwIXt2VlanOutPQsH24PerformanceEntry 268435456}

pr1646v2EthPortSwIXt2VlanOutPQsD7Performance OBJECT-TYPE
   SYNTAX      SEQUENCE OF Pr1646v2EthPortSwIXt2VlanOutPQsD7PerformanceEntry
   MAX-ACCESS  not-accessible
   STATUS      current
   DESCRIPTION
      ""
   ::= {pr1646v2EthPortSwIXt2Vlan 84344832}

pr1646v2EthPortSwIXt2VlanOutPQsD7PerformanceEntry OBJECT-TYPE
   SYNTAX      Pr1646v2EthPortSwIXt2VlanOutPQsD7PerformanceEntry
   MAX-ACCESS  not-accessible
   STATUS      current
   DESCRIPTION
      ""
   INDEX      { pr1646v2EthPortSwIXt2VlanOutPQsD7PerformanceGlobalIx,
                pr1646v2EthPortSwIXt2VlanTableIx,
                pr1646v2EthPortSwIXt2VlanOutPQsTableIx,
                pr1646v2EthPortSwIXt2VlanOutPQsD7PerformanceTableIx }
   ::= {pr1646v2EthPortSwIXt2VlanOutPQsD7Performance 1}

Pr1646v2EthPortSwIXt2VlanOutPQsD7PerformanceEntry ::=
   SEQUENCE
      {
      pr1646v2EthPortSwIXt2VlanOutPQsD7PerformanceGlobalIx
         GlobalIndex,
      pr1646v2EthPortSwIXt2VlanOutPQsD7PerformanceTableIx
         TableIndex,
      pr1646v2EthPortSwIXt2VlanOutPQsD7PerformanceSysUpTime
         TimeTicks,
      pr1646v2EthPortSwIXt2VlanOutPQsD7PerformanceTotPkts
         Counter64,
      pr1646v2EthPortSwIXt2VlanOutPQsD7PerformanceDirTxPkts
         Counter64,
      pr1646v2EthPortSwIXt2VlanOutPQsD7PerformanceQdPkts
         Counter64,
      pr1646v2EthPortSwIXt2VlanOutPQsD7PerformanceDropPkts
         Counter64,
      pr1646v2EthPortSwIXt2VlanOutPQsD7PerformanceRDropPkts
         Counter64,
      pr1646v2EthPortSwIXt2VlanOutPQsD7PerformanceCirTxPkts
         Counter64,
      pr1646v2EthPortSwIXt2VlanOutPQsD7PerformanceEirTxPkts
         Counter64,
      pr1646v2EthPortSwIXt2VlanOutPQsD7PerformanceViolTxPkts
         Counter64,
      pr1646v2EthPortSwIXt2VlanOutPQsD7PerformanceTotOcts
         Counter64,
      pr1646v2EthPortSwIXt2VlanOutPQsD7PerformanceDirTxOcts
         Counter64,
      pr1646v2EthPortSwIXt2VlanOutPQsD7PerformanceQdOcts
         Counter64,
      pr1646v2EthPortSwIXt2VlanOutPQsD7PerformanceDropOcts
         Counter64,
      pr1646v2EthPortSwIXt2VlanOutPQsD7PerformanceRDropOcts
         Counter64,
      pr1646v2EthPortSwIXt2VlanOutPQsD7PerformanceCirTxOcts
         Counter64,
      pr1646v2EthPortSwIXt2VlanOutPQsD7PerformanceEirTxOcts
         Counter64,
      pr1646v2EthPortSwIXt2VlanOutPQsD7PerformanceViolTxOcts
         Counter64,
      pr1646v2EthPortSwIXt2VlanOutPQsD7PerformanceBandwidth
         Integer32
      }

pr1646v2EthPortSwIXt2VlanOutPQsD7PerformanceGlobalIx OBJECT-TYPE
   SYNTAX      GlobalIndex
   MAX-ACCESS  not-accessible
   STATUS      current
   DESCRIPTION
      "The value of the tlsCntTreeGlobalIndex of the MANAGED OBJECT."
   ::= {pr1646v2EthPortSwIXt2VlanOutPQsD7PerformanceEntry 10}

pr1646v2EthPortSwIXt2VlanOutPQsD7PerformanceTableIx OBJECT-TYPE
   SYNTAX      TableIndex
   MAX-ACCESS  not-accessible
   STATUS      current
   DESCRIPTION
      ""
   ::= {pr1646v2EthPortSwIXt2VlanOutPQsD7PerformanceEntry 11}

pr1646v2EthPortSwIXt2VlanOutPQsD7PerformanceSysUpTime OBJECT-TYPE
   SYNTAX      TimeTicks
   MAX-ACCESS  read-only
   STATUS      current
   DESCRIPTION
      "Path: swPort.performance.vlan.outPriorityQueues.d7Performance.sysUpTime

       Time in centi-second."
   ::= {pr1646v2EthPortSwIXt2VlanOutPQsD7PerformanceEntry 16777216}

pr1646v2EthPortSwIXt2VlanOutPQsD7PerformanceTotPkts OBJECT-TYPE
   SYNTAX      Counter64
   MAX-ACCESS  read-only
   STATUS      current
   DESCRIPTION
      "Path: swPort.performance.vlan.outPriorityQueues.d7Performance.totalPkts

       64 bit unsigned wrappable counter."
   ::= {pr1646v2EthPortSwIXt2VlanOutPQsD7PerformanceEntry 234881024}

pr1646v2EthPortSwIXt2VlanOutPQsD7PerformanceDirTxPkts OBJECT-TYPE
   SYNTAX      Counter64
   MAX-ACCESS  read-only
   STATUS      current
   DESCRIPTION
      "Path: swPort.performance.vlan.outPriorityQueues.d7Performance.directTxPkts

       64 bit unsigned wrappable counter."
   ::= {pr1646v2EthPortSwIXt2VlanOutPQsD7PerformanceEntry 33554432}

pr1646v2EthPortSwIXt2VlanOutPQsD7PerformanceQdPkts OBJECT-TYPE
   SYNTAX      Counter64
   MAX-ACCESS  read-only
   STATUS      current
   DESCRIPTION
      "Path: swPort.performance.vlan.outPriorityQueues.d7Performance.queuedPkts

       64 bit unsigned wrappable counter."
   ::= {pr1646v2EthPortSwIXt2VlanOutPQsD7PerformanceEntry 50331648}

pr1646v2EthPortSwIXt2VlanOutPQsD7PerformanceDropPkts OBJECT-TYPE
   SYNTAX      Counter64
   MAX-ACCESS  read-only
   STATUS      current
   DESCRIPTION
      "Path: swPort.performance.vlan.outPriorityQueues.d7Performance.droppedPkts

       64 bit unsigned wrappable counter."
   ::= {pr1646v2EthPortSwIXt2VlanOutPQsD7PerformanceEntry 67108864}

pr1646v2EthPortSwIXt2VlanOutPQsD7PerformanceRDropPkts OBJECT-TYPE
   SYNTAX      Counter64
   MAX-ACCESS  read-only
   STATUS      current
   DESCRIPTION
      "Path: swPort.performance.vlan.outPriorityQueues.d7Performance.redDroppedPkts

       64 bit unsigned wrappable counter."
   ::= {pr1646v2EthPortSwIXt2VlanOutPQsD7PerformanceEntry 201326592}

pr1646v2EthPortSwIXt2VlanOutPQsD7PerformanceCirTxPkts OBJECT-TYPE
   SYNTAX      Counter64
   MAX-ACCESS  read-only
   STATUS      current
   DESCRIPTION
      "Path: swPort.performance.vlan.outPriorityQueues.d7Performance.cirTxPkts

       64 bit unsigned wrappable counter."
   ::= {pr1646v2EthPortSwIXt2VlanOutPQsD7PerformanceEntry 83886080}

pr1646v2EthPortSwIXt2VlanOutPQsD7PerformanceEirTxPkts OBJECT-TYPE
   SYNTAX      Counter64
   MAX-ACCESS  read-only
   STATUS      current
   DESCRIPTION
      "Path: swPort.performance.vlan.outPriorityQueues.d7Performance.eirTxPkts

       64 bit unsigned wrappable counter."
   ::= {pr1646v2EthPortSwIXt2VlanOutPQsD7PerformanceEntry 100663296}

pr1646v2EthPortSwIXt2VlanOutPQsD7PerformanceViolTxPkts OBJECT-TYPE
   SYNTAX      Counter64
   MAX-ACCESS  read-only
   STATUS      current
   DESCRIPTION
      "Path: swPort.performance.vlan.outPriorityQueues.d7Performance.violateTxPkts

       64 bit unsigned wrappable counter."
   ::= {pr1646v2EthPortSwIXt2VlanOutPQsD7PerformanceEntry 301989888}

pr1646v2EthPortSwIXt2VlanOutPQsD7PerformanceTotOcts OBJECT-TYPE
   SYNTAX      Counter64
   MAX-ACCESS  read-only
   STATUS      current
   DESCRIPTION
      "Path: swPort.performance.vlan.outPriorityQueues.d7Performance.totalOctets

       64 bit unsigned wrappable counter."
   ::= {pr1646v2EthPortSwIXt2VlanOutPQsD7PerformanceEntry 251658240}

pr1646v2EthPortSwIXt2VlanOutPQsD7PerformanceDirTxOcts OBJECT-TYPE
   SYNTAX      Counter64
   MAX-ACCESS  read-only
   STATUS      current
   DESCRIPTION
      "Path: swPort.performance.vlan.outPriorityQueues.d7Performance.directTxOctets

       64 bit unsigned wrappable counter."
   ::= {pr1646v2EthPortSwIXt2VlanOutPQsD7PerformanceEntry 117440512}

pr1646v2EthPortSwIXt2VlanOutPQsD7PerformanceQdOcts OBJECT-TYPE
   SYNTAX      Counter64
   MAX-ACCESS  read-only
   STATUS      current
   DESCRIPTION
      "Path: swPort.performance.vlan.outPriorityQueues.d7Performance.queuedOctets

       64 bit unsigned wrappable counter."
   ::= {pr1646v2EthPortSwIXt2VlanOutPQsD7PerformanceEntry 134217728}

pr1646v2EthPortSwIXt2VlanOutPQsD7PerformanceDropOcts OBJECT-TYPE
   SYNTAX      Counter64
   MAX-ACCESS  read-only
   STATUS      current
   DESCRIPTION
      "Path: swPort.performance.vlan.outPriorityQueues.d7Performance.droppedOctets

       64 bit unsigned wrappable counter."
   ::= {pr1646v2EthPortSwIXt2VlanOutPQsD7PerformanceEntry 150994944}

pr1646v2EthPortSwIXt2VlanOutPQsD7PerformanceRDropOcts OBJECT-TYPE
   SYNTAX      Counter64
   MAX-ACCESS  read-only
   STATUS      current
   DESCRIPTION
      "Path: swPort.performance.vlan.outPriorityQueues.d7Performance.redDroppedOctets

       64 bit unsigned wrappable counter."
   ::= {pr1646v2EthPortSwIXt2VlanOutPQsD7PerformanceEntry 218103808}

pr1646v2EthPortSwIXt2VlanOutPQsD7PerformanceCirTxOcts OBJECT-TYPE
   SYNTAX      Counter64
   MAX-ACCESS  read-only
   STATUS      current
   DESCRIPTION
      "Path: swPort.performance.vlan.outPriorityQueues.d7Performance.cirTxOctets

       64 bit unsigned wrappable counter."
   ::= {pr1646v2EthPortSwIXt2VlanOutPQsD7PerformanceEntry 167772160}

pr1646v2EthPortSwIXt2VlanOutPQsD7PerformanceEirTxOcts OBJECT-TYPE
   SYNTAX      Counter64
   MAX-ACCESS  read-only
   STATUS      current
   DESCRIPTION
      "Path: swPort.performance.vlan.outPriorityQueues.d7Performance.eirTxOctets

       64 bit unsigned wrappable counter."
   ::= {pr1646v2EthPortSwIXt2VlanOutPQsD7PerformanceEntry 184549376}

pr1646v2EthPortSwIXt2VlanOutPQsD7PerformanceViolTxOcts OBJECT-TYPE
   SYNTAX      Counter64
   MAX-ACCESS  read-only
   STATUS      current
   DESCRIPTION
      "Path: swPort.performance.vlan.outPriorityQueues.d7Performance.violateTxOctets

       64 bit unsigned wrappable counter."
   ::= {pr1646v2EthPortSwIXt2VlanOutPQsD7PerformanceEntry 318767104}

pr1646v2EthPortSwIXt2VlanOutPQsD7PerformanceBandwidth OBJECT-TYPE
   SYNTAX      Integer32
   MAX-ACCESS  read-only
   STATUS      current
   DESCRIPTION
      "Path: swPort.performance.vlan.outPriorityQueues.d7Performance.bandwidth

       unit name = bps
       formula = 8 * ; 8 /"
   ::= {pr1646v2EthPortSwIXt2VlanOutPQsD7PerformanceEntry 268435456}


pr1646v2EthPortSwIXt2PPPoE OBJECT IDENTIFIER ::= {pr1646v2EthPortSwIXt2 53}

pr1646v2EthPortSwIXt2PPPoESSCTable OBJECT-TYPE
   SYNTAX      SEQUENCE OF Pr1646v2EthPortSwIXt2PPPoEEntry
   MAX-ACCESS  not-accessible
   STATUS      current
   DESCRIPTION
      ""
   ::= {pr1646v2EthPortSwIXt2PPPoE 1}

pr1646v2EthPortSwIXt2PPPoEEntry OBJECT-TYPE
   SYNTAX      Pr1646v2EthPortSwIXt2PPPoEEntry
   MAX-ACCESS  not-accessible
   STATUS      current
   DESCRIPTION
      ""
   INDEX      { pr1646v2EthPortSwIXt2PPPoEGlobalIx,
                pr1646v2EthPortSwIXt2PPPoETableIx }
   ::= {pr1646v2EthPortSwIXt2PPPoESSCTable 1}

Pr1646v2EthPortSwIXt2PPPoEEntry ::=
   SEQUENCE
      {
      pr1646v2EthPortSwIXt2PPPoEGlobalIx
         GlobalIndex,
      pr1646v2EthPortSwIXt2PPPoETableIx
         TableIndex,
      pr1646v2EthPortSwIXt2PPPoEName
         DisplayString,
      pr1646v2EthPortSwIXt2PPPoEMCInOctets
         Counter64,
      pr1646v2EthPortSwIXt2PPPoEMCInUcast
         Counter64,
      pr1646v2EthPortSwIXt2PPPoEMCInNUcastPkts
         Counter64,
      pr1646v2EthPortSwIXt2PPPoEMCInBcastPkts
         Counter64,
      pr1646v2EthPortSwIXt2PPPoEMCInMcastPkts
         Counter64,
      pr1646v2EthPortSwIXt2PPPoEMCInDiscards
         Counter64,
      pr1646v2EthPortSwIXt2PPPoEMCInErrors
         Counter64,
      pr1646v2EthPortSwIXt2PPPoEMCInUnknownProtos
         Counter64,
      pr1646v2EthPortSwIXt2PPPoEMCInDropEx
         Counter64,
      pr1646v2EthPortSwIXt2PPPoEMCInDropNoMac
         Counter64,
      pr1646v2EthPortSwIXt2PPPoEMCInDropNUCast
         Counter64,
      pr1646v2EthPortSwIXt2PPPoEMCInDropFilter
         Counter64,
      pr1646v2EthPortSwIXt2PPPoEMCInBandwidth15sec
         Integer32,
      pr1646v2EthPortSwIXt2PPPoEMCInBandwidth30sec
         Integer32,
      pr1646v2EthPortSwIXt2PPPoEMCInBandwidth1min
         Integer32,
      pr1646v2EthPortSwIXt2PPPoEMCInBandwidth2min
         Integer32,
      pr1646v2EthPortSwIXt2PPPoEMCInBandwidth5min
         Integer32,
      pr1646v2EthPortSwIXt2PPPoEMCOutOctets
         Counter64,
      pr1646v2EthPortSwIXt2PPPoEMCOutUcastPkts
         Counter64,
      pr1646v2EthPortSwIXt2PPPoEMCOutNUcastPkts
         Counter64,
      pr1646v2EthPortSwIXt2PPPoEMCOutBcastPkts
         Counter64,
      pr1646v2EthPortSwIXt2PPPoEMCOutMcastPkts
         Counter64,
      pr1646v2EthPortSwIXt2PPPoEMCOutDiscards
         Counter64,
      pr1646v2EthPortSwIXt2PPPoEMCOutErrors
         Counter64,
      pr1646v2EthPortSwIXt2PPPoEMCOutQLen
         Counter32,
      pr1646v2EthPortSwIXt2PPPoEMCOutDropEx
         Counter64,
      pr1646v2EthPortSwIXt2PPPoEMCOutDropNoArp
         Counter64,
      pr1646v2EthPortSwIXt2PPPoEMCOutDropFilter
         Counter64,
      pr1646v2EthPortSwIXt2PPPoEMCOutBandwidth15sec
         Integer32,
      pr1646v2EthPortSwIXt2PPPoEMCOutBandwidth30sec
         Integer32,
      pr1646v2EthPortSwIXt2PPPoEMCOutBandwidth1min
         Integer32,
      pr1646v2EthPortSwIXt2PPPoEMCOutBandwidth2min
         Integer32,
      pr1646v2EthPortSwIXt2PPPoEMCOutBandwidth5min
         Integer32,
      pr1646v2EthPortSwIXt2PPPoEPppLinkMonitoringRequestsSent
         Gauge32,
      pr1646v2EthPortSwIXt2PPPoEPppLinkMonitoringRepliesRcvd
         Gauge32,
      pr1646v2EthPortSwIXt2PPPoEPppLinkMonitoringRequestsRcvd
         Gauge32,
      pr1646v2EthPortSwIXt2PPPoEPppLinkMonitoringRepliesSent
         Gauge32
      }

pr1646v2EthPortSwIXt2PPPoEGlobalIx OBJECT-TYPE
   SYNTAX      GlobalIndex
   MAX-ACCESS  not-accessible
   STATUS      current
   DESCRIPTION
      "The value of the tlsCntTreeGlobalIndex of the MANAGED OBJECT."
   ::= {pr1646v2EthPortSwIXt2PPPoEEntry 10}

pr1646v2EthPortSwIXt2PPPoETableIx OBJECT-TYPE
   SYNTAX      TableIndex
   MAX-ACCESS  not-accessible
   STATUS      current
   DESCRIPTION
      ""
   ::= {pr1646v2EthPortSwIXt2PPPoEEntry 11}

pr1646v2EthPortSwIXt2PPPoEName OBJECT-TYPE
   SYNTAX      DisplayString
   MAX-ACCESS  read-only
   STATUS      current
   DESCRIPTION
      "Path: swPort.performance.pppoEClient.name"
   ::= {pr1646v2EthPortSwIXt2PPPoEEntry 16777216}

pr1646v2EthPortSwIXt2PPPoEMCInOctets OBJECT-TYPE
   SYNTAX      Counter64
   MAX-ACCESS  read-only
   STATUS      current
   DESCRIPTION
      "Path: swPort.performance.pppoEClient.mibCounters.ifInOctets

       64 bit unsigned wrappable counter."
   ::= {pr1646v2EthPortSwIXt2PPPoEEntry 40697856}

pr1646v2EthPortSwIXt2PPPoEMCInUcast OBJECT-TYPE
   SYNTAX      Counter64
   MAX-ACCESS  read-only
   STATUS      current
   DESCRIPTION
      "Path: swPort.performance.pppoEClient.mibCounters.ifInUcastPkts

       64 bit unsigned wrappable counter."
   ::= {pr1646v2EthPortSwIXt2PPPoEEntry 40763392}

pr1646v2EthPortSwIXt2PPPoEMCInNUcastPkts OBJECT-TYPE
   SYNTAX      Counter64
   MAX-ACCESS  read-only
   STATUS      current
   DESCRIPTION
      "Path: swPort.performance.pppoEClient.mibCounters.ifInNUcastPkts

       64 bit unsigned wrappable counter."
   ::= {pr1646v2EthPortSwIXt2PPPoEEntry 40828928}

pr1646v2EthPortSwIXt2PPPoEMCInBcastPkts OBJECT-TYPE
   SYNTAX      Counter64
   MAX-ACCESS  read-only
   STATUS      current
   DESCRIPTION
      "Path: swPort.performance.pppoEClient.mibCounters.ifInBcastPkts

       64 bit unsigned wrappable counter."
   ::= {pr1646v2EthPortSwIXt2PPPoEEntry 47382528}

pr1646v2EthPortSwIXt2PPPoEMCInMcastPkts OBJECT-TYPE
   SYNTAX      Counter64
   MAX-ACCESS  read-only
   STATUS      current
   DESCRIPTION
      "Path: swPort.performance.pppoEClient.mibCounters.ifInMcastPkts

       64 bit unsigned wrappable counter."
   ::= {pr1646v2EthPortSwIXt2PPPoEEntry 48037888}

pr1646v2EthPortSwIXt2PPPoEMCInDiscards OBJECT-TYPE
   SYNTAX      Counter64
   MAX-ACCESS  read-only
   STATUS      current
   DESCRIPTION
      "Path: swPort.performance.pppoEClient.mibCounters.ifInDiscards

       64 bit unsigned wrappable counter."
   ::= {pr1646v2EthPortSwIXt2PPPoEEntry 40894464}

pr1646v2EthPortSwIXt2PPPoEMCInErrors OBJECT-TYPE
   SYNTAX      Counter64
   MAX-ACCESS  read-only
   STATUS      current
   DESCRIPTION
      "Path: swPort.performance.pppoEClient.mibCounters.ifInErrors

       64 bit unsigned wrappable counter."
   ::= {pr1646v2EthPortSwIXt2PPPoEEntry 40960000}

pr1646v2EthPortSwIXt2PPPoEMCInUnknownProtos OBJECT-TYPE
   SYNTAX      Counter64
   MAX-ACCESS  read-only
   STATUS      current
   DESCRIPTION
      "Path: swPort.performance.pppoEClient.mibCounters.ifInUnknownProtos

       64 bit unsigned wrappable counter."
   ::= {pr1646v2EthPortSwIXt2PPPoEEntry 41025536}

pr1646v2EthPortSwIXt2PPPoEMCInDropEx OBJECT-TYPE
   SYNTAX      Counter64
   MAX-ACCESS  read-only
   STATUS      current
   DESCRIPTION
      "Path: swPort.performance.pppoEClient.mibCounters.ifInDropLevelExceeded

       64 bit unsigned wrappable counter."
   ::= {pr1646v2EthPortSwIXt2PPPoEEntry 42074112}

pr1646v2EthPortSwIXt2PPPoEMCInDropNoMac OBJECT-TYPE
   SYNTAX      Counter64
   MAX-ACCESS  read-only
   STATUS      current
   DESCRIPTION
      "Path: swPort.performance.pppoEClient.mibCounters.ifInDiscardsNoMacFit

       64 bit unsigned wrappable counter."
   ::= {pr1646v2EthPortSwIXt2PPPoEEntry 42270720}

pr1646v2EthPortSwIXt2PPPoEMCInDropNUCast OBJECT-TYPE
   SYNTAX      Counter64
   MAX-ACCESS  read-only
   STATUS      current
   DESCRIPTION
      "Path: swPort.performance.pppoEClient.mibCounters.ifInDiscardsNUCast

       64 bit unsigned wrappable counter."
   ::= {pr1646v2EthPortSwIXt2PPPoEEntry 42467328}

pr1646v2EthPortSwIXt2PPPoEMCInDropFilter OBJECT-TYPE
   SYNTAX      Counter64
   MAX-ACCESS  read-only
   STATUS      current
   DESCRIPTION
      "Path: swPort.performance.pppoEClient.mibCounters.ifInDiscardsFilter

       64 bit unsigned wrappable counter."
   ::= {pr1646v2EthPortSwIXt2PPPoEEntry 42532864}

pr1646v2EthPortSwIXt2PPPoEMCInBandwidth15sec OBJECT-TYPE
   SYNTAX      Integer32
   MAX-ACCESS  read-only
   STATUS      current
   DESCRIPTION
      "Path: swPort.performance.pppoEClient.mibCounters.ifInBandwidth.15sec

       unit name = bps
       formula = 8 * ; 8 /"
   ::= {pr1646v2EthPortSwIXt2PPPoEEntry 45417728}

pr1646v2EthPortSwIXt2PPPoEMCInBandwidth30sec OBJECT-TYPE
   SYNTAX      Integer32
   MAX-ACCESS  read-only
   STATUS      current
   DESCRIPTION
      "Path: swPort.performance.pppoEClient.mibCounters.ifInBandwidth.30sec

       unit name = bps
       formula = 8 * ; 8 /"
   ::= {pr1646v2EthPortSwIXt2PPPoEEntry 45419008}

pr1646v2EthPortSwIXt2PPPoEMCInBandwidth1min OBJECT-TYPE
   SYNTAX      Integer32
   MAX-ACCESS  read-only
   STATUS      current
   DESCRIPTION
      "Path: swPort.performance.pppoEClient.mibCounters.ifInBandwidth.1min

       unit name = bps
       formula = 8 * ; 8 /"
   ::= {pr1646v2EthPortSwIXt2PPPoEEntry 45421568}

pr1646v2EthPortSwIXt2PPPoEMCInBandwidth2min OBJECT-TYPE
   SYNTAX      Integer32
   MAX-ACCESS  read-only
   STATUS      current
   DESCRIPTION
      "Path: swPort.performance.pppoEClient.mibCounters.ifInBandwidth.2min

       unit name = bps
       formula = 8 * ; 8 /"
   ::= {pr1646v2EthPortSwIXt2PPPoEEntry 45426688}

pr1646v2EthPortSwIXt2PPPoEMCInBandwidth5min OBJECT-TYPE
   SYNTAX      Integer32
   MAX-ACCESS  read-only
   STATUS      current
   DESCRIPTION
      "Path: swPort.performance.pppoEClient.mibCounters.ifInBandwidth.5min

       unit name = bps
       formula = 8 * ; 8 /"
   ::= {pr1646v2EthPortSwIXt2PPPoEEntry 45442048}

pr1646v2EthPortSwIXt2PPPoEMCOutOctets OBJECT-TYPE
   SYNTAX      Counter64
   MAX-ACCESS  read-only
   STATUS      current
   DESCRIPTION
      "Path: swPort.performance.pppoEClient.mibCounters.ifOutOctets

       64 bit unsigned wrappable counter."
   ::= {pr1646v2EthPortSwIXt2PPPoEEntry 41091072}

pr1646v2EthPortSwIXt2PPPoEMCOutUcastPkts OBJECT-TYPE
   SYNTAX      Counter64
   MAX-ACCESS  read-only
   STATUS      current
   DESCRIPTION
      "Path: swPort.performance.pppoEClient.mibCounters.ifOutUcastPkts

       64 bit unsigned wrappable counter."
   ::= {pr1646v2EthPortSwIXt2PPPoEEntry 41156608}

pr1646v2EthPortSwIXt2PPPoEMCOutNUcastPkts OBJECT-TYPE
   SYNTAX      Counter64
   MAX-ACCESS  read-only
   STATUS      current
   DESCRIPTION
      "Path: swPort.performance.pppoEClient.mibCounters.ifOutNUcastPkts

       64 bit unsigned wrappable counter."
   ::= {pr1646v2EthPortSwIXt2PPPoEEntry 41222144}

pr1646v2EthPortSwIXt2PPPoEMCOutBcastPkts OBJECT-TYPE
   SYNTAX      Counter64
   MAX-ACCESS  read-only
   STATUS      current
   DESCRIPTION
      "Path: swPort.performance.pppoEClient.mibCounters.ifOutBcastPkts

       64 bit unsigned wrappable counter."
   ::= {pr1646v2EthPortSwIXt2PPPoEEntry 47775744}

pr1646v2EthPortSwIXt2PPPoEMCOutMcastPkts OBJECT-TYPE
   SYNTAX      Counter64
   MAX-ACCESS  read-only
   STATUS      current
   DESCRIPTION
      "Path: swPort.performance.pppoEClient.mibCounters.ifOutMcastPkts

       64 bit unsigned wrappable counter."
   ::= {pr1646v2EthPortSwIXt2PPPoEEntry 48431104}

pr1646v2EthPortSwIXt2PPPoEMCOutDiscards OBJECT-TYPE
   SYNTAX      Counter64
   MAX-ACCESS  read-only
   STATUS      current
   DESCRIPTION
      "Path: swPort.performance.pppoEClient.mibCounters.ifOutDiscards

       64 bit unsigned wrappable counter."
   ::= {pr1646v2EthPortSwIXt2PPPoEEntry 41287680}

pr1646v2EthPortSwIXt2PPPoEMCOutErrors OBJECT-TYPE
   SYNTAX      Counter64
   MAX-ACCESS  read-only
   STATUS      current
   DESCRIPTION
      "Path: swPort.performance.pppoEClient.mibCounters.ifOutErrors

       64 bit unsigned wrappable counter."
   ::= {pr1646v2EthPortSwIXt2PPPoEEntry 41353216}

pr1646v2EthPortSwIXt2PPPoEMCOutQLen OBJECT-TYPE
   SYNTAX      Counter32
   MAX-ACCESS  read-only
   STATUS      current
   DESCRIPTION
      "Path: swPort.performance.pppoEClient.mibCounters.ifOutQLen

       32 bit unsigned wrappable counter."
   ::= {pr1646v2EthPortSwIXt2PPPoEEntry 41418752}

pr1646v2EthPortSwIXt2PPPoEMCOutDropEx OBJECT-TYPE
   SYNTAX      Counter64
   MAX-ACCESS  read-only
   STATUS      current
   DESCRIPTION
      "Path: swPort.performance.pppoEClient.mibCounters.ifOutDropLevelExceeded

       64 bit unsigned wrappable counter."
   ::= {pr1646v2EthPortSwIXt2PPPoEEntry 41484288}

pr1646v2EthPortSwIXt2PPPoEMCOutDropNoArp OBJECT-TYPE
   SYNTAX      Counter64
   MAX-ACCESS  read-only
   STATUS      current
   DESCRIPTION
      "Path: swPort.performance.pppoEClient.mibCounters.ifOutDiscardsNoArp

       64 bit unsigned wrappable counter."
   ::= {pr1646v2EthPortSwIXt2PPPoEEntry 42336256}

pr1646v2EthPortSwIXt2PPPoEMCOutDropFilter OBJECT-TYPE
   SYNTAX      Counter64
   MAX-ACCESS  read-only
   STATUS      current
   DESCRIPTION
      "Path: swPort.performance.pppoEClient.mibCounters.ifOutDiscardsFilter

       64 bit unsigned wrappable counter."
   ::= {pr1646v2EthPortSwIXt2PPPoEEntry 42598400}

pr1646v2EthPortSwIXt2PPPoEMCOutBandwidth15sec OBJECT-TYPE
   SYNTAX      Integer32
   MAX-ACCESS  read-only
   STATUS      current
   DESCRIPTION
      "Path: swPort.performance.pppoEClient.mibCounters.ifOutBandwidth.15sec

       unit name = bps
       formula = 8 * ; 8 /"
   ::= {pr1646v2EthPortSwIXt2PPPoEEntry 45483264}

pr1646v2EthPortSwIXt2PPPoEMCOutBandwidth30sec OBJECT-TYPE
   SYNTAX      Integer32
   MAX-ACCESS  read-only
   STATUS      current
   DESCRIPTION
      "Path: swPort.performance.pppoEClient.mibCounters.ifOutBandwidth.30sec

       unit name = bps
       formula = 8 * ; 8 /"
   ::= {pr1646v2EthPortSwIXt2PPPoEEntry 45484544}

pr1646v2EthPortSwIXt2PPPoEMCOutBandwidth1min OBJECT-TYPE
   SYNTAX      Integer32
   MAX-ACCESS  read-only
   STATUS      current
   DESCRIPTION
      "Path: swPort.performance.pppoEClient.mibCounters.ifOutBandwidth.1min

       unit name = bps
       formula = 8 * ; 8 /"
   ::= {pr1646v2EthPortSwIXt2PPPoEEntry 45487104}

pr1646v2EthPortSwIXt2PPPoEMCOutBandwidth2min OBJECT-TYPE
   SYNTAX      Integer32
   MAX-ACCESS  read-only
   STATUS      current
   DESCRIPTION
      "Path: swPort.performance.pppoEClient.mibCounters.ifOutBandwidth.2min

       unit name = bps
       formula = 8 * ; 8 /"
   ::= {pr1646v2EthPortSwIXt2PPPoEEntry 45492224}

pr1646v2EthPortSwIXt2PPPoEMCOutBandwidth5min OBJECT-TYPE
   SYNTAX      Integer32
   MAX-ACCESS  read-only
   STATUS      current
   DESCRIPTION
      "Path: swPort.performance.pppoEClient.mibCounters.ifOutBandwidth.5min

       unit name = bps
       formula = 8 * ; 8 /"
   ::= {pr1646v2EthPortSwIXt2PPPoEEntry 45507584}

pr1646v2EthPortSwIXt2PPPoEPppLinkMonitoringRequestsSent OBJECT-TYPE
   SYNTAX      Gauge32
   MAX-ACCESS  read-only
   STATUS      current
   DESCRIPTION
      "Path: swPort.performance.pppoEClient.ppp.linkMonitoring.requestsSent

       32 bit unsigned gauge value."
   ::= {pr1646v2EthPortSwIXt2PPPoEEntry 50397440}

pr1646v2EthPortSwIXt2PPPoEPppLinkMonitoringRepliesRcvd OBJECT-TYPE
   SYNTAX      Gauge32
   MAX-ACCESS  read-only
   STATUS      current
   DESCRIPTION
      "Path: swPort.performance.pppoEClient.ppp.linkMonitoring.repliesRcvd

       32 bit unsigned gauge value."
   ::= {pr1646v2EthPortSwIXt2PPPoEEntry 50397696}

pr1646v2EthPortSwIXt2PPPoEPppLinkMonitoringRequestsRcvd OBJECT-TYPE
   SYNTAX      Gauge32
   MAX-ACCESS  read-only
   STATUS      current
   DESCRIPTION
      "Path: swPort.performance.pppoEClient.ppp.linkMonitoring.requestsRcvd

       32 bit unsigned gauge value."
   ::= {pr1646v2EthPortSwIXt2PPPoEEntry 50397952}

pr1646v2EthPortSwIXt2PPPoEPppLinkMonitoringRepliesSent OBJECT-TYPE
   SYNTAX      Gauge32
   MAX-ACCESS  read-only
   STATUS      current
   DESCRIPTION
      "Path: swPort.performance.pppoEClient.ppp.linkMonitoring.repliesSent

       32 bit unsigned gauge value."
   ::= {pr1646v2EthPortSwIXt2PPPoEEntry 50398208}

pr1646v2EthPortSwIXt2PPPoEMCH2P OBJECT-TYPE
   SYNTAX      SEQUENCE OF Pr1646v2EthPortSwIXt2PPPoEMCH2PEntry
   MAX-ACCESS  not-accessible
   STATUS      current
   DESCRIPTION
      ""
   ::= {pr1646v2EthPortSwIXt2PPPoE 41549824}

pr1646v2EthPortSwIXt2PPPoEMCH2PEntry OBJECT-TYPE
   SYNTAX      Pr1646v2EthPortSwIXt2PPPoEMCH2PEntry
   MAX-ACCESS  not-accessible
   STATUS      current
   DESCRIPTION
      ""
   INDEX      { pr1646v2EthPortSwIXt2PPPoEMCH2PGlobalIx,
                pr1646v2EthPortSwIXt2PPPoETableIx,
                pr1646v2EthPortSwIXt2PPPoEMCH2PTableIx }
   ::= {pr1646v2EthPortSwIXt2PPPoEMCH2P 1}

Pr1646v2EthPortSwIXt2PPPoEMCH2PEntry ::=
   SEQUENCE
      {
      pr1646v2EthPortSwIXt2PPPoEMCH2PGlobalIx
         GlobalIndex,
      pr1646v2EthPortSwIXt2PPPoEMCH2PTableIx
         TableIndex,
      pr1646v2EthPortSwIXt2PPPoEMCH2PSysUpTime
         TimeTicks,
      pr1646v2EthPortSwIXt2PPPoEMCH2PIfUpTime
         TimeTicks,
      pr1646v2EthPortSwIXt2PPPoEMCH2PIfStatChanges
         Counter32,
      pr1646v2EthPortSwIXt2PPPoEMCH2PIfInOctets
         Counter64,
      pr1646v2EthPortSwIXt2PPPoEMCH2PIfInUCPkts
         Counter64,
      pr1646v2EthPortSwIXt2PPPoEMCH2PIfInNUCPkts
         Counter64,
      pr1646v2EthPortSwIXt2PPPoEMCH2PIfInBCPkts
         Counter64,
      pr1646v2EthPortSwIXt2PPPoEMCH2PIfInMCPkts
         Counter64,
      pr1646v2EthPortSwIXt2PPPoEMCH2PIfInDiscards
         Counter64,
      pr1646v2EthPortSwIXt2PPPoEMCH2PIfInErrors
         Counter64,
      pr1646v2EthPortSwIXt2PPPoEMCH2PIfInUnkwn
         Counter64,
      pr1646v2EthPortSwIXt2PPPoEMCH2PInDropEx
         Counter64,
      pr1646v2EthPortSwIXt2PPPoEMCH2PInDropNoMac
         Counter64,
      pr1646v2EthPortSwIXt2PPPoEMCH2PInDropNUCast
         Counter64,
      pr1646v2EthPortSwIXt2PPPoEMCH2PInDropFilter
         Counter64,
      pr1646v2EthPortSwIXt2PPPoEMCH2PIfInBandwidth
         Integer32,
      pr1646v2EthPortSwIXt2PPPoEMCH2PIfOutOctets
         Counter64,
      pr1646v2EthPortSwIXt2PPPoEMCH2PIfOutUCPkts
         Counter64,
      pr1646v2EthPortSwIXt2PPPoEMCH2PIfOutNUCPkts
         Counter64,
      pr1646v2EthPortSwIXt2PPPoEMCH2PIfOutBCPkts
         Counter64,
      pr1646v2EthPortSwIXt2PPPoEMCH2PIfOutMCPkts
         Counter64,
      pr1646v2EthPortSwIXt2PPPoEMCH2PIfOutDiscards
         Counter64,
      pr1646v2EthPortSwIXt2PPPoEMCH2PIfOutErrors
         Counter64,
      pr1646v2EthPortSwIXt2PPPoEMCH2POutDropEx
         Counter64,
      pr1646v2EthPortSwIXt2PPPoEMCH2POutDropNoArp
         Counter64,
      pr1646v2EthPortSwIXt2PPPoEMCH2POutDropFilter
         Counter64,
      pr1646v2EthPortSwIXt2PPPoEMCH2PIfOutBandwidth
         Integer32,
      pr1646v2EthPortSwIXt2PPPoEMCH2PIfErrSec
         Counter32
      }

pr1646v2EthPortSwIXt2PPPoEMCH2PGlobalIx OBJECT-TYPE
   SYNTAX      GlobalIndex
   MAX-ACCESS  not-accessible
   STATUS      current
   DESCRIPTION
      "The value of the tlsCntTreeGlobalIndex of the MANAGED OBJECT."
   ::= {pr1646v2EthPortSwIXt2PPPoEMCH2PEntry 10}

pr1646v2EthPortSwIXt2PPPoEMCH2PTableIx OBJECT-TYPE
   SYNTAX      TableIndex
   MAX-ACCESS  not-accessible
   STATUS      current
   DESCRIPTION
      ""
   ::= {pr1646v2EthPortSwIXt2PPPoEMCH2PEntry 11}

pr1646v2EthPortSwIXt2PPPoEMCH2PSysUpTime OBJECT-TYPE
   SYNTAX      TimeTicks
   MAX-ACCESS  read-only
   STATUS      current
   DESCRIPTION
      "Path: swPort.performance.pppoEClient.mibCounters.h2Performance.sysUpTime

       Time in centi-second."
   ::= {pr1646v2EthPortSwIXt2PPPoEMCH2PEntry 16777216}

pr1646v2EthPortSwIXt2PPPoEMCH2PIfUpTime OBJECT-TYPE
   SYNTAX      TimeTicks
   MAX-ACCESS  read-only
   STATUS      current
   DESCRIPTION
      "Path: swPort.performance.pppoEClient.mibCounters.h2Performance.ifUpTime

       Time in centi-second."
   ::= {pr1646v2EthPortSwIXt2PPPoEMCH2PEntry 33554432}

pr1646v2EthPortSwIXt2PPPoEMCH2PIfStatChanges OBJECT-TYPE
   SYNTAX      Counter32
   MAX-ACCESS  read-only
   STATUS      current
   DESCRIPTION
      "Path: swPort.performance.pppoEClient.mibCounters.h2Performance.ifStatusChanges

       32 bit unsigned wrappable counter."
   ::= {pr1646v2EthPortSwIXt2PPPoEMCH2PEntry 50331648}

pr1646v2EthPortSwIXt2PPPoEMCH2PIfInOctets OBJECT-TYPE
   SYNTAX      Counter64
   MAX-ACCESS  read-only
   STATUS      current
   DESCRIPTION
      "Path: swPort.performance.pppoEClient.mibCounters.h2Performance.ifInOctets

       64 bit unsigned wrappable counter."
   ::= {pr1646v2EthPortSwIXt2PPPoEMCH2PEntry 67108864}

pr1646v2EthPortSwIXt2PPPoEMCH2PIfInUCPkts OBJECT-TYPE
   SYNTAX      Counter64
   MAX-ACCESS  read-only
   STATUS      current
   DESCRIPTION
      "Path: swPort.performance.pppoEClient.mibCounters.h2Performance.ifInUcastPkts

       64 bit unsigned wrappable counter."
   ::= {pr1646v2EthPortSwIXt2PPPoEMCH2PEntry 83886080}

pr1646v2EthPortSwIXt2PPPoEMCH2PIfInNUCPkts OBJECT-TYPE
   SYNTAX      Counter64
   MAX-ACCESS  read-only
   STATUS      current
   DESCRIPTION
      "Path: swPort.performance.pppoEClient.mibCounters.h2Performance.ifInNUcastPkts

       64 bit unsigned wrappable counter."
   ::= {pr1646v2EthPortSwIXt2PPPoEMCH2PEntry 100663296}

pr1646v2EthPortSwIXt2PPPoEMCH2PIfInBCPkts OBJECT-TYPE
   SYNTAX      Counter64
   MAX-ACCESS  read-only
   STATUS      current
   DESCRIPTION
      "Path: swPort.performance.pppoEClient.mibCounters.h2Performance.ifInBcastPkts

       64 bit unsigned wrappable counter."
   ::= {pr1646v2EthPortSwIXt2PPPoEMCH2PEntry 419430400}

pr1646v2EthPortSwIXt2PPPoEMCH2PIfInMCPkts OBJECT-TYPE
   SYNTAX      Counter64
   MAX-ACCESS  read-only
   STATUS      current
   DESCRIPTION
      "Path: swPort.performance.pppoEClient.mibCounters.h2Performance.ifInMcastPkts

       64 bit unsigned wrappable counter."
   ::= {pr1646v2EthPortSwIXt2PPPoEMCH2PEntry 436207616}

pr1646v2EthPortSwIXt2PPPoEMCH2PIfInDiscards OBJECT-TYPE
   SYNTAX      Counter64
   MAX-ACCESS  read-only
   STATUS      current
   DESCRIPTION
      "Path: swPort.performance.pppoEClient.mibCounters.h2Performance.ifInDiscards

       64 bit unsigned wrappable counter."
   ::= {pr1646v2EthPortSwIXt2PPPoEMCH2PEntry 117440512}

pr1646v2EthPortSwIXt2PPPoEMCH2PIfInErrors OBJECT-TYPE
   SYNTAX      Counter64
   MAX-ACCESS  read-only
   STATUS      current
   DESCRIPTION
      "Path: swPort.performance.pppoEClient.mibCounters.h2Performance.ifInErrors

       64 bit unsigned wrappable counter."
   ::= {pr1646v2EthPortSwIXt2PPPoEMCH2PEntry 134217728}

pr1646v2EthPortSwIXt2PPPoEMCH2PIfInUnkwn OBJECT-TYPE
   SYNTAX      Counter64
   MAX-ACCESS  read-only
   STATUS      current
   DESCRIPTION
      "Path: swPort.performance.pppoEClient.mibCounters.h2Performance.ifInUnknownProtos

       64 bit unsigned wrappable counter."
   ::= {pr1646v2EthPortSwIXt2PPPoEMCH2PEntry 150994944}

pr1646v2EthPortSwIXt2PPPoEMCH2PInDropEx OBJECT-TYPE
   SYNTAX      Counter64
   MAX-ACCESS  read-only
   STATUS      current
   DESCRIPTION
      "Path: swPort.performance.pppoEClient.mibCounters.h2Performance.ifInDropLevelExceeded

       64 bit unsigned wrappable counter."
   ::= {pr1646v2EthPortSwIXt2PPPoEMCH2PEntry 335544320}

pr1646v2EthPortSwIXt2PPPoEMCH2PInDropNoMac OBJECT-TYPE
   SYNTAX      Counter64
   MAX-ACCESS  read-only
   STATUS      current
   DESCRIPTION
      "Path: swPort.performance.pppoEClient.mibCounters.h2Performance.fInDiscardsNoMacFit

       64 bit unsigned wrappable counter."
   ::= {pr1646v2EthPortSwIXt2PPPoEMCH2PEntry 301989888}

pr1646v2EthPortSwIXt2PPPoEMCH2PInDropNUCast OBJECT-TYPE
   SYNTAX      Counter64
   MAX-ACCESS  read-only
   STATUS      current
   DESCRIPTION
      "Path: swPort.performance.pppoEClient.mibCounters.h2Performance.fInDiscardsNUCast

       64 bit unsigned wrappable counter."
   ::= {pr1646v2EthPortSwIXt2PPPoEMCH2PEntry 318767104}

pr1646v2EthPortSwIXt2PPPoEMCH2PInDropFilter OBJECT-TYPE
   SYNTAX      Counter64
   MAX-ACCESS  read-only
   STATUS      current
   DESCRIPTION
      "Path: swPort.performance.pppoEClient.mibCounters.h2Performance.fInDiscardsFilter

       64 bit unsigned wrappable counter."
   ::= {pr1646v2EthPortSwIXt2PPPoEMCH2PEntry 385875968}

pr1646v2EthPortSwIXt2PPPoEMCH2PIfInBandwidth OBJECT-TYPE
   SYNTAX      Integer32
   MAX-ACCESS  read-only
   STATUS      current
   DESCRIPTION
      "Path: swPort.performance.pppoEClient.mibCounters.h2Performance.ifInBandwidth

       unit name = bps
       formula = 8 * ; 8 /"
   ::= {pr1646v2EthPortSwIXt2PPPoEMCH2PEntry 268435456}

pr1646v2EthPortSwIXt2PPPoEMCH2PIfOutOctets OBJECT-TYPE
   SYNTAX      Counter64
   MAX-ACCESS  read-only
   STATUS      current
   DESCRIPTION
      "Path: swPort.performance.pppoEClient.mibCounters.h2Performance.ifOutOctets

       64 bit unsigned wrappable counter."
   ::= {pr1646v2EthPortSwIXt2PPPoEMCH2PEntry 167772160}

pr1646v2EthPortSwIXt2PPPoEMCH2PIfOutUCPkts OBJECT-TYPE
   SYNTAX      Counter64
   MAX-ACCESS  read-only
   STATUS      current
   DESCRIPTION
      "Path: swPort.performance.pppoEClient.mibCounters.h2Performance.ifOutUcastPkts

       64 bit unsigned wrappable counter."
   ::= {pr1646v2EthPortSwIXt2PPPoEMCH2PEntry 184549376}

pr1646v2EthPortSwIXt2PPPoEMCH2PIfOutNUCPkts OBJECT-TYPE
   SYNTAX      Counter64
   MAX-ACCESS  read-only
   STATUS      current
   DESCRIPTION
      "Path: swPort.performance.pppoEClient.mibCounters.h2Performance.ifOutNUcastPkts

       64 bit unsigned wrappable counter."
   ::= {pr1646v2EthPortSwIXt2PPPoEMCH2PEntry 201326592}

pr1646v2EthPortSwIXt2PPPoEMCH2PIfOutBCPkts OBJECT-TYPE
   SYNTAX      Counter64
   MAX-ACCESS  read-only
   STATUS      current
   DESCRIPTION
      "Path: swPort.performance.pppoEClient.mibCounters.h2Performance.ifOutBcastPkts

       64 bit unsigned wrappable counter."
   ::= {pr1646v2EthPortSwIXt2PPPoEMCH2PEntry 452984832}

pr1646v2EthPortSwIXt2PPPoEMCH2PIfOutMCPkts OBJECT-TYPE
   SYNTAX      Counter64
   MAX-ACCESS  read-only
   STATUS      current
   DESCRIPTION
      "Path: swPort.performance.pppoEClient.mibCounters.h2Performance.ifOutMcastPkts

       64 bit unsigned wrappable counter."
   ::= {pr1646v2EthPortSwIXt2PPPoEMCH2PEntry 469762048}

pr1646v2EthPortSwIXt2PPPoEMCH2PIfOutDiscards OBJECT-TYPE
   SYNTAX      Counter64
   MAX-ACCESS  read-only
   STATUS      current
   DESCRIPTION
      "Path: swPort.performance.pppoEClient.mibCounters.h2Performance.ifOutDiscards

       64 bit unsigned wrappable counter."
   ::= {pr1646v2EthPortSwIXt2PPPoEMCH2PEntry 218103808}

pr1646v2EthPortSwIXt2PPPoEMCH2PIfOutErrors OBJECT-TYPE
   SYNTAX      Counter64
   MAX-ACCESS  read-only
   STATUS      current
   DESCRIPTION
      "Path: swPort.performance.pppoEClient.mibCounters.h2Performance.ifOutErrors

       64 bit unsigned wrappable counter."
   ::= {pr1646v2EthPortSwIXt2PPPoEMCH2PEntry 234881024}

pr1646v2EthPortSwIXt2PPPoEMCH2POutDropEx OBJECT-TYPE
   SYNTAX      Counter64
   MAX-ACCESS  read-only
   STATUS      current
   DESCRIPTION
      "Path: swPort.performance.pppoEClient.mibCounters.h2Performance.ifOutDropLevelExceeded

       64 bit unsigned wrappable counter."
   ::= {pr1646v2EthPortSwIXt2PPPoEMCH2PEntry 352321536}

pr1646v2EthPortSwIXt2PPPoEMCH2POutDropNoArp OBJECT-TYPE
   SYNTAX      Counter64
   MAX-ACCESS  read-only
   STATUS      current
   DESCRIPTION
      "Path: swPort.performance.pppoEClient.mibCounters.h2Performance.ifOutDiscardsNoArp

       64 bit unsigned wrappable counter."
   ::= {pr1646v2EthPortSwIXt2PPPoEMCH2PEntry 369098752}

pr1646v2EthPortSwIXt2PPPoEMCH2POutDropFilter OBJECT-TYPE
   SYNTAX      Counter64
   MAX-ACCESS  read-only
   STATUS      current
   DESCRIPTION
      "Path: swPort.performance.pppoEClient.mibCounters.h2Performance.ifOutDiscardsFilter

       64 bit unsigned wrappable counter."
   ::= {pr1646v2EthPortSwIXt2PPPoEMCH2PEntry 402653184}

pr1646v2EthPortSwIXt2PPPoEMCH2PIfOutBandwidth OBJECT-TYPE
   SYNTAX      Integer32
   MAX-ACCESS  read-only
   STATUS      current
   DESCRIPTION
      "Path: swPort.performance.pppoEClient.mibCounters.h2Performance.ifOutBandwidth

       unit name = bps
       formula = 8 * ; 8 /"
   ::= {pr1646v2EthPortSwIXt2PPPoEMCH2PEntry 285212672}

pr1646v2EthPortSwIXt2PPPoEMCH2PIfErrSec OBJECT-TYPE
   SYNTAX      Counter32
   MAX-ACCESS  read-only
   STATUS      current
   DESCRIPTION
      "Path: swPort.performance.pppoEClient.mibCounters.h2Performance.ifErrSec

       32 bit unsigned wrappable counter."
   ::= {pr1646v2EthPortSwIXt2PPPoEMCH2PEntry 251658240}

pr1646v2EthPortSwIXt2PPPoEMCH24P OBJECT-TYPE
   SYNTAX      SEQUENCE OF Pr1646v2EthPortSwIXt2PPPoEMCH24PEntry
   MAX-ACCESS  not-accessible
   STATUS      current
   DESCRIPTION
      ""
   ::= {pr1646v2EthPortSwIXt2PPPoE 41615360}

pr1646v2EthPortSwIXt2PPPoEMCH24PEntry OBJECT-TYPE
   SYNTAX      Pr1646v2EthPortSwIXt2PPPoEMCH24PEntry
   MAX-ACCESS  not-accessible
   STATUS      current
   DESCRIPTION
      ""
   INDEX      { pr1646v2EthPortSwIXt2PPPoEMCH24PGlobalIx,
                pr1646v2EthPortSwIXt2PPPoETableIx,
                pr1646v2EthPortSwIXt2PPPoEMCH24PTableIx }
   ::= {pr1646v2EthPortSwIXt2PPPoEMCH24P 1}

Pr1646v2EthPortSwIXt2PPPoEMCH24PEntry ::=
   SEQUENCE
      {
      pr1646v2EthPortSwIXt2PPPoEMCH24PGlobalIx
         GlobalIndex,
      pr1646v2EthPortSwIXt2PPPoEMCH24PTableIx
         TableIndex,
      pr1646v2EthPortSwIXt2PPPoEMCH24PSysUpTime
         TimeTicks,
      pr1646v2EthPortSwIXt2PPPoEMCH24PIfUpTime
         TimeTicks,
      pr1646v2EthPortSwIXt2PPPoEMCH24PIfStatChanges
         Counter32,
      pr1646v2EthPortSwIXt2PPPoEMCH24PIfInOctets
         Counter64,
      pr1646v2EthPortSwIXt2PPPoEMCH24PIfInUCPkts
         Counter64,
      pr1646v2EthPortSwIXt2PPPoEMCH24PIfInNUCPkts
         Counter64,
      pr1646v2EthPortSwIXt2PPPoEMCH24PIfInBCPkts
         Counter64,
      pr1646v2EthPortSwIXt2PPPoEMCH24PIfInMCPkts
         Counter64,
      pr1646v2EthPortSwIXt2PPPoEMCH24PIfInDiscards
         Counter64,
      pr1646v2EthPortSwIXt2PPPoEMCH24PIfInErrors
         Counter64,
      pr1646v2EthPortSwIXt2PPPoEMCH24PIfInUnkwn
         Counter64,
      pr1646v2EthPortSwIXt2PPPoEMCH24PInDropEx
         Counter64,
      pr1646v2EthPortSwIXt2PPPoEMCH24PInDropNoMac
         Counter64,
      pr1646v2EthPortSwIXt2PPPoEMCH24PInDropNUCast
         Counter64,
      pr1646v2EthPortSwIXt2PPPoEMCH24PInDropFilter
         Counter64,
      pr1646v2EthPortSwIXt2PPPoEMCH24PIfInBandwidth
         Integer32,
      pr1646v2EthPortSwIXt2PPPoEMCH24PIfOutOctets
         Counter64,
      pr1646v2EthPortSwIXt2PPPoEMCH24PIfOutUCPkts
         Counter64,
      pr1646v2EthPortSwIXt2PPPoEMCH24PIfOutNUCPkts
         Counter64,
      pr1646v2EthPortSwIXt2PPPoEMCH24PIfOutBCPkts
         Counter64,
      pr1646v2EthPortSwIXt2PPPoEMCH24PIfOutMCPkts
         Counter64,
      pr1646v2EthPortSwIXt2PPPoEMCH24PIfOutDiscards
         Counter64,
      pr1646v2EthPortSwIXt2PPPoEMCH24PIfOutErrors
         Counter64,
      pr1646v2EthPortSwIXt2PPPoEMCH24POutDropEx
         Counter64,
      pr1646v2EthPortSwIXt2PPPoEMCH24POutDropNoArp
         Counter64,
      pr1646v2EthPortSwIXt2PPPoEMCH24POutDropFilter
         Counter64,
      pr1646v2EthPortSwIXt2PPPoEMCH24PIfOutBandwidth
         Integer32,
      pr1646v2EthPortSwIXt2PPPoEMCH24PIfErrSec
         Counter32
      }

pr1646v2EthPortSwIXt2PPPoEMCH24PGlobalIx OBJECT-TYPE
   SYNTAX      GlobalIndex
   MAX-ACCESS  not-accessible
   STATUS      current
   DESCRIPTION
      "The value of the tlsCntTreeGlobalIndex of the MANAGED OBJECT."
   ::= {pr1646v2EthPortSwIXt2PPPoEMCH24PEntry 10}

pr1646v2EthPortSwIXt2PPPoEMCH24PTableIx OBJECT-TYPE
   SYNTAX      TableIndex
   MAX-ACCESS  not-accessible
   STATUS      current
   DESCRIPTION
      ""
   ::= {pr1646v2EthPortSwIXt2PPPoEMCH24PEntry 11}

pr1646v2EthPortSwIXt2PPPoEMCH24PSysUpTime OBJECT-TYPE
   SYNTAX      TimeTicks
   MAX-ACCESS  read-only
   STATUS      current
   DESCRIPTION
      "Path: swPort.performance.pppoEClient.mibCounters.h24Performance.sysUpTime

       Time in centi-second."
   ::= {pr1646v2EthPortSwIXt2PPPoEMCH24PEntry 16777216}

pr1646v2EthPortSwIXt2PPPoEMCH24PIfUpTime OBJECT-TYPE
   SYNTAX      TimeTicks
   MAX-ACCESS  read-only
   STATUS      current
   DESCRIPTION
      "Path: swPort.performance.pppoEClient.mibCounters.h24Performance.ifUpTime

       Time in centi-second."
   ::= {pr1646v2EthPortSwIXt2PPPoEMCH24PEntry 33554432}

pr1646v2EthPortSwIXt2PPPoEMCH24PIfStatChanges OBJECT-TYPE
   SYNTAX      Counter32
   MAX-ACCESS  read-only
   STATUS      current
   DESCRIPTION
      "Path: swPort.performance.pppoEClient.mibCounters.h24Performance.ifStatusChanges

       32 bit unsigned wrappable counter."
   ::= {pr1646v2EthPortSwIXt2PPPoEMCH24PEntry 50331648}

pr1646v2EthPortSwIXt2PPPoEMCH24PIfInOctets OBJECT-TYPE
   SYNTAX      Counter64
   MAX-ACCESS  read-only
   STATUS      current
   DESCRIPTION
      "Path: swPort.performance.pppoEClient.mibCounters.h24Performance.ifInOctets

       64 bit unsigned wrappable counter."
   ::= {pr1646v2EthPortSwIXt2PPPoEMCH24PEntry 67108864}

pr1646v2EthPortSwIXt2PPPoEMCH24PIfInUCPkts OBJECT-TYPE
   SYNTAX      Counter64
   MAX-ACCESS  read-only
   STATUS      current
   DESCRIPTION
      "Path: swPort.performance.pppoEClient.mibCounters.h24Performance.ifInUcastPkts

       64 bit unsigned wrappable counter."
   ::= {pr1646v2EthPortSwIXt2PPPoEMCH24PEntry 83886080}

pr1646v2EthPortSwIXt2PPPoEMCH24PIfInNUCPkts OBJECT-TYPE
   SYNTAX      Counter64
   MAX-ACCESS  read-only
   STATUS      current
   DESCRIPTION
      "Path: swPort.performance.pppoEClient.mibCounters.h24Performance.ifInNUcastPkts

       64 bit unsigned wrappable counter."
   ::= {pr1646v2EthPortSwIXt2PPPoEMCH24PEntry 100663296}

pr1646v2EthPortSwIXt2PPPoEMCH24PIfInBCPkts OBJECT-TYPE
   SYNTAX      Counter64
   MAX-ACCESS  read-only
   STATUS      current
   DESCRIPTION
      "Path: swPort.performance.pppoEClient.mibCounters.h24Performance.ifInBcastPkts

       64 bit unsigned wrappable counter."
   ::= {pr1646v2EthPortSwIXt2PPPoEMCH24PEntry 419430400}

pr1646v2EthPortSwIXt2PPPoEMCH24PIfInMCPkts OBJECT-TYPE
   SYNTAX      Counter64
   MAX-ACCESS  read-only
   STATUS      current
   DESCRIPTION
      "Path: swPort.performance.pppoEClient.mibCounters.h24Performance.ifInMcastPkts

       64 bit unsigned wrappable counter."
   ::= {pr1646v2EthPortSwIXt2PPPoEMCH24PEntry 436207616}

pr1646v2EthPortSwIXt2PPPoEMCH24PIfInDiscards OBJECT-TYPE
   SYNTAX      Counter64
   MAX-ACCESS  read-only
   STATUS      current
   DESCRIPTION
      "Path: swPort.performance.pppoEClient.mibCounters.h24Performance.ifInDiscards

       64 bit unsigned wrappable counter."
   ::= {pr1646v2EthPortSwIXt2PPPoEMCH24PEntry 117440512}

pr1646v2EthPortSwIXt2PPPoEMCH24PIfInErrors OBJECT-TYPE
   SYNTAX      Counter64
   MAX-ACCESS  read-only
   STATUS      current
   DESCRIPTION
      "Path: swPort.performance.pppoEClient.mibCounters.h24Performance.ifInErrors

       64 bit unsigned wrappable counter."
   ::= {pr1646v2EthPortSwIXt2PPPoEMCH24PEntry 134217728}

pr1646v2EthPortSwIXt2PPPoEMCH24PIfInUnkwn OBJECT-TYPE
   SYNTAX      Counter64
   MAX-ACCESS  read-only
   STATUS      current
   DESCRIPTION
      "Path: swPort.performance.pppoEClient.mibCounters.h24Performance.ifInUnknownProtos

       64 bit unsigned wrappable counter."
   ::= {pr1646v2EthPortSwIXt2PPPoEMCH24PEntry 150994944}

pr1646v2EthPortSwIXt2PPPoEMCH24PInDropEx OBJECT-TYPE
   SYNTAX      Counter64
   MAX-ACCESS  read-only
   STATUS      current
   DESCRIPTION
      "Path: swPort.performance.pppoEClient.mibCounters.h24Performance.ifInDropLevelExceeded

       64 bit unsigned wrappable counter."
   ::= {pr1646v2EthPortSwIXt2PPPoEMCH24PEntry 335544320}

pr1646v2EthPortSwIXt2PPPoEMCH24PInDropNoMac OBJECT-TYPE
   SYNTAX      Counter64
   MAX-ACCESS  read-only
   STATUS      current
   DESCRIPTION
      "Path: swPort.performance.pppoEClient.mibCounters.h24Performance.fInDiscardsNoMacFit

       64 bit unsigned wrappable counter."
   ::= {pr1646v2EthPortSwIXt2PPPoEMCH24PEntry 301989888}

pr1646v2EthPortSwIXt2PPPoEMCH24PInDropNUCast OBJECT-TYPE
   SYNTAX      Counter64
   MAX-ACCESS  read-only
   STATUS      current
   DESCRIPTION
      "Path: swPort.performance.pppoEClient.mibCounters.h24Performance.fInDiscardsNUCast

       64 bit unsigned wrappable counter."
   ::= {pr1646v2EthPortSwIXt2PPPoEMCH24PEntry 318767104}

pr1646v2EthPortSwIXt2PPPoEMCH24PInDropFilter OBJECT-TYPE
   SYNTAX      Counter64
   MAX-ACCESS  read-only
   STATUS      current
   DESCRIPTION
      "Path: swPort.performance.pppoEClient.mibCounters.h24Performance.fInDiscardsFilter

       64 bit unsigned wrappable counter."
   ::= {pr1646v2EthPortSwIXt2PPPoEMCH24PEntry 385875968}

pr1646v2EthPortSwIXt2PPPoEMCH24PIfInBandwidth OBJECT-TYPE
   SYNTAX      Integer32
   MAX-ACCESS  read-only
   STATUS      current
   DESCRIPTION
      "Path: swPort.performance.pppoEClient.mibCounters.h24Performance.ifInBandwidth

       unit name = bps
       formula = 8 * ; 8 /"
   ::= {pr1646v2EthPortSwIXt2PPPoEMCH24PEntry 268435456}

pr1646v2EthPortSwIXt2PPPoEMCH24PIfOutOctets OBJECT-TYPE
   SYNTAX      Counter64
   MAX-ACCESS  read-only
   STATUS      current
   DESCRIPTION
      "Path: swPort.performance.pppoEClient.mibCounters.h24Performance.ifOutOctets

       64 bit unsigned wrappable counter."
   ::= {pr1646v2EthPortSwIXt2PPPoEMCH24PEntry 167772160}

pr1646v2EthPortSwIXt2PPPoEMCH24PIfOutUCPkts OBJECT-TYPE
   SYNTAX      Counter64
   MAX-ACCESS  read-only
   STATUS      current
   DESCRIPTION
      "Path: swPort.performance.pppoEClient.mibCounters.h24Performance.ifOutUcastPkts

       64 bit unsigned wrappable counter."
   ::= {pr1646v2EthPortSwIXt2PPPoEMCH24PEntry 184549376}

pr1646v2EthPortSwIXt2PPPoEMCH24PIfOutNUCPkts OBJECT-TYPE
   SYNTAX      Counter64
   MAX-ACCESS  read-only
   STATUS      current
   DESCRIPTION
      "Path: swPort.performance.pppoEClient.mibCounters.h24Performance.ifOutNUcastPkts

       64 bit unsigned wrappable counter."
   ::= {pr1646v2EthPortSwIXt2PPPoEMCH24PEntry 201326592}

pr1646v2EthPortSwIXt2PPPoEMCH24PIfOutBCPkts OBJECT-TYPE
   SYNTAX      Counter64
   MAX-ACCESS  read-only
   STATUS      current
   DESCRIPTION
      "Path: swPort.performance.pppoEClient.mibCounters.h24Performance.ifOutBcastPkts

       64 bit unsigned wrappable counter."
   ::= {pr1646v2EthPortSwIXt2PPPoEMCH24PEntry 452984832}

pr1646v2EthPortSwIXt2PPPoEMCH24PIfOutMCPkts OBJECT-TYPE
   SYNTAX      Counter64
   MAX-ACCESS  read-only
   STATUS      current
   DESCRIPTION
      "Path: swPort.performance.pppoEClient.mibCounters.h24Performance.ifOutMcastPkts

       64 bit unsigned wrappable counter."
   ::= {pr1646v2EthPortSwIXt2PPPoEMCH24PEntry 469762048}

pr1646v2EthPortSwIXt2PPPoEMCH24PIfOutDiscards OBJECT-TYPE
   SYNTAX      Counter64
   MAX-ACCESS  read-only
   STATUS      current
   DESCRIPTION
      "Path: swPort.performance.pppoEClient.mibCounters.h24Performance.ifOutDiscards

       64 bit unsigned wrappable counter."
   ::= {pr1646v2EthPortSwIXt2PPPoEMCH24PEntry 218103808}

pr1646v2EthPortSwIXt2PPPoEMCH24PIfOutErrors OBJECT-TYPE
   SYNTAX      Counter64
   MAX-ACCESS  read-only
   STATUS      current
   DESCRIPTION
      "Path: swPort.performance.pppoEClient.mibCounters.h24Performance.ifOutErrors

       64 bit unsigned wrappable counter."
   ::= {pr1646v2EthPortSwIXt2PPPoEMCH24PEntry 234881024}

pr1646v2EthPortSwIXt2PPPoEMCH24POutDropEx OBJECT-TYPE
   SYNTAX      Counter64
   MAX-ACCESS  read-only
   STATUS      current
   DESCRIPTION
      "Path: swPort.performance.pppoEClient.mibCounters.h24Performance.ifOutDropLevelExceeded

       64 bit unsigned wrappable counter."
   ::= {pr1646v2EthPortSwIXt2PPPoEMCH24PEntry 352321536}

pr1646v2EthPortSwIXt2PPPoEMCH24POutDropNoArp OBJECT-TYPE
   SYNTAX      Counter64
   MAX-ACCESS  read-only
   STATUS      current
   DESCRIPTION
      "Path: swPort.performance.pppoEClient.mibCounters.h24Performance.ifOutDiscardsNoArp

       64 bit unsigned wrappable counter."
   ::= {pr1646v2EthPortSwIXt2PPPoEMCH24PEntry 369098752}

pr1646v2EthPortSwIXt2PPPoEMCH24POutDropFilter OBJECT-TYPE
   SYNTAX      Counter64
   MAX-ACCESS  read-only
   STATUS      current
   DESCRIPTION
      "Path: swPort.performance.pppoEClient.mibCounters.h24Performance.ifOutDiscardsFilter

       64 bit unsigned wrappable counter."
   ::= {pr1646v2EthPortSwIXt2PPPoEMCH24PEntry 402653184}

pr1646v2EthPortSwIXt2PPPoEMCH24PIfOutBandwidth OBJECT-TYPE
   SYNTAX      Integer32
   MAX-ACCESS  read-only
   STATUS      current
   DESCRIPTION
      "Path: swPort.performance.pppoEClient.mibCounters.h24Performance.ifOutBandwidth

       unit name = bps
       formula = 8 * ; 8 /"
   ::= {pr1646v2EthPortSwIXt2PPPoEMCH24PEntry 285212672}

pr1646v2EthPortSwIXt2PPPoEMCH24PIfErrSec OBJECT-TYPE
   SYNTAX      Counter32
   MAX-ACCESS  read-only
   STATUS      current
   DESCRIPTION
      "Path: swPort.performance.pppoEClient.mibCounters.h24Performance.ifErrSec

       32 bit unsigned wrappable counter."
   ::= {pr1646v2EthPortSwIXt2PPPoEMCH24PEntry 251658240}

pr1646v2EthPortSwIXt2PPPoEMCD7P OBJECT-TYPE
   SYNTAX      SEQUENCE OF Pr1646v2EthPortSwIXt2PPPoEMCD7PEntry
   MAX-ACCESS  not-accessible
   STATUS      current
   DESCRIPTION
      ""
   ::= {pr1646v2EthPortSwIXt2PPPoE 41680896}

pr1646v2EthPortSwIXt2PPPoEMCD7PEntry OBJECT-TYPE
   SYNTAX      Pr1646v2EthPortSwIXt2PPPoEMCD7PEntry
   MAX-ACCESS  not-accessible
   STATUS      current
   DESCRIPTION
      ""
   INDEX      { pr1646v2EthPortSwIXt2PPPoEMCD7PGlobalIx,
                pr1646v2EthPortSwIXt2PPPoETableIx,
                pr1646v2EthPortSwIXt2PPPoEMCD7PTableIx }
   ::= {pr1646v2EthPortSwIXt2PPPoEMCD7P 1}

Pr1646v2EthPortSwIXt2PPPoEMCD7PEntry ::=
   SEQUENCE
      {
      pr1646v2EthPortSwIXt2PPPoEMCD7PGlobalIx
         GlobalIndex,
      pr1646v2EthPortSwIXt2PPPoEMCD7PTableIx
         TableIndex,
      pr1646v2EthPortSwIXt2PPPoEMCD7PSysUpTime
         TimeTicks,
      pr1646v2EthPortSwIXt2PPPoEMCD7PIfUpTime
         TimeTicks,
      pr1646v2EthPortSwIXt2PPPoEMCD7PIfStatChanges
         Counter32,
      pr1646v2EthPortSwIXt2PPPoEMCD7PIfInOctets
         Counter64,
      pr1646v2EthPortSwIXt2PPPoEMCD7PIfInUCPkts
         Counter64,
      pr1646v2EthPortSwIXt2PPPoEMCD7PIfInNUCPkts
         Counter64,
      pr1646v2EthPortSwIXt2PPPoEMCD7PIfInBCPkts
         Counter64,
      pr1646v2EthPortSwIXt2PPPoEMCD7PIfInMCPkts
         Counter64,
      pr1646v2EthPortSwIXt2PPPoEMCD7PIfInDiscards
         Counter64,
      pr1646v2EthPortSwIXt2PPPoEMCD7PIfInErrors
         Counter64,
      pr1646v2EthPortSwIXt2PPPoEMCD7PIfInUnkwn
         Counter64,
      pr1646v2EthPortSwIXt2PPPoEMCD7PInDropEx
         Counter64,
      pr1646v2EthPortSwIXt2PPPoEMCD7PInDropNoMac
         Counter64,
      pr1646v2EthPortSwIXt2PPPoEMCD7PInDropNUCast
         Counter64,
      pr1646v2EthPortSwIXt2PPPoEMCD7PInDropFilter
         Counter64,
      pr1646v2EthPortSwIXt2PPPoEMCD7PIfInBandwidth
         Integer32,
      pr1646v2EthPortSwIXt2PPPoEMCD7PIfOutOctets
         Counter64,
      pr1646v2EthPortSwIXt2PPPoEMCD7PIfOutUCPkts
         Counter64,
      pr1646v2EthPortSwIXt2PPPoEMCD7PIfOutNUCPkts
         Counter64,
      pr1646v2EthPortSwIXt2PPPoEMCD7PIfOutBCPkts
         Counter64,
      pr1646v2EthPortSwIXt2PPPoEMCD7PIfOutMCPkts
         Counter64,
      pr1646v2EthPortSwIXt2PPPoEMCD7PIfOutDiscards
         Counter64,
      pr1646v2EthPortSwIXt2PPPoEMCD7PIfOutErrors
         Counter64,
      pr1646v2EthPortSwIXt2PPPoEMCD7POutDropEx
         Counter64,
      pr1646v2EthPortSwIXt2PPPoEMCD7POutDropNoArp
         Counter64,
      pr1646v2EthPortSwIXt2PPPoEMCD7POutDropFilter
         Counter64,
      pr1646v2EthPortSwIXt2PPPoEMCD7PIfOutBandwidth
         Integer32,
      pr1646v2EthPortSwIXt2PPPoEMCD7PIfErrSec
         Counter32
      }

pr1646v2EthPortSwIXt2PPPoEMCD7PGlobalIx OBJECT-TYPE
   SYNTAX      GlobalIndex
   MAX-ACCESS  not-accessible
   STATUS      current
   DESCRIPTION
      "The value of the tlsCntTreeGlobalIndex of the MANAGED OBJECT."
   ::= {pr1646v2EthPortSwIXt2PPPoEMCD7PEntry 10}

pr1646v2EthPortSwIXt2PPPoEMCD7PTableIx OBJECT-TYPE
   SYNTAX      TableIndex
   MAX-ACCESS  not-accessible
   STATUS      current
   DESCRIPTION
      ""
   ::= {pr1646v2EthPortSwIXt2PPPoEMCD7PEntry 11}

pr1646v2EthPortSwIXt2PPPoEMCD7PSysUpTime OBJECT-TYPE
   SYNTAX      TimeTicks
   MAX-ACCESS  read-only
   STATUS      current
   DESCRIPTION
      "Path: swPort.performance.pppoEClient.mibCounters.d7Performance.sysUpTime

       Time in centi-second."
   ::= {pr1646v2EthPortSwIXt2PPPoEMCD7PEntry 16777216}

pr1646v2EthPortSwIXt2PPPoEMCD7PIfUpTime OBJECT-TYPE
   SYNTAX      TimeTicks
   MAX-ACCESS  read-only
   STATUS      current
   DESCRIPTION
      "Path: swPort.performance.pppoEClient.mibCounters.d7Performance.ifUpTime

       Time in centi-second."
   ::= {pr1646v2EthPortSwIXt2PPPoEMCD7PEntry 33554432}

pr1646v2EthPortSwIXt2PPPoEMCD7PIfStatChanges OBJECT-TYPE
   SYNTAX      Counter32
   MAX-ACCESS  read-only
   STATUS      current
   DESCRIPTION
      "Path: swPort.performance.pppoEClient.mibCounters.d7Performance.ifStatusChanges

       32 bit unsigned wrappable counter."
   ::= {pr1646v2EthPortSwIXt2PPPoEMCD7PEntry 50331648}

pr1646v2EthPortSwIXt2PPPoEMCD7PIfInOctets OBJECT-TYPE
   SYNTAX      Counter64
   MAX-ACCESS  read-only
   STATUS      current
   DESCRIPTION
      "Path: swPort.performance.pppoEClient.mibCounters.d7Performance.ifInOctets

       64 bit unsigned wrappable counter."
   ::= {pr1646v2EthPortSwIXt2PPPoEMCD7PEntry 67108864}

pr1646v2EthPortSwIXt2PPPoEMCD7PIfInUCPkts OBJECT-TYPE
   SYNTAX      Counter64
   MAX-ACCESS  read-only
   STATUS      current
   DESCRIPTION
      "Path: swPort.performance.pppoEClient.mibCounters.d7Performance.ifInUcastPkts

       64 bit unsigned wrappable counter."
   ::= {pr1646v2EthPortSwIXt2PPPoEMCD7PEntry 83886080}

pr1646v2EthPortSwIXt2PPPoEMCD7PIfInNUCPkts OBJECT-TYPE
   SYNTAX      Counter64
   MAX-ACCESS  read-only
   STATUS      current
   DESCRIPTION
      "Path: swPort.performance.pppoEClient.mibCounters.d7Performance.ifInNUcastPkts

       64 bit unsigned wrappable counter."
   ::= {pr1646v2EthPortSwIXt2PPPoEMCD7PEntry 100663296}

pr1646v2EthPortSwIXt2PPPoEMCD7PIfInBCPkts OBJECT-TYPE
   SYNTAX      Counter64
   MAX-ACCESS  read-only
   STATUS      current
   DESCRIPTION
      "Path: swPort.performance.pppoEClient.mibCounters.d7Performance.ifInBcastPkts

       64 bit unsigned wrappable counter."
   ::= {pr1646v2EthPortSwIXt2PPPoEMCD7PEntry 419430400}

pr1646v2EthPortSwIXt2PPPoEMCD7PIfInMCPkts OBJECT-TYPE
   SYNTAX      Counter64
   MAX-ACCESS  read-only
   STATUS      current
   DESCRIPTION
      "Path: swPort.performance.pppoEClient.mibCounters.d7Performance.ifInMcastPkts

       64 bit unsigned wrappable counter."
   ::= {pr1646v2EthPortSwIXt2PPPoEMCD7PEntry 436207616}

pr1646v2EthPortSwIXt2PPPoEMCD7PIfInDiscards OBJECT-TYPE
   SYNTAX      Counter64
   MAX-ACCESS  read-only
   STATUS      current
   DESCRIPTION
      "Path: swPort.performance.pppoEClient.mibCounters.d7Performance.ifInDiscards

       64 bit unsigned wrappable counter."
   ::= {pr1646v2EthPortSwIXt2PPPoEMCD7PEntry 117440512}

pr1646v2EthPortSwIXt2PPPoEMCD7PIfInErrors OBJECT-TYPE
   SYNTAX      Counter64
   MAX-ACCESS  read-only
   STATUS      current
   DESCRIPTION
      "Path: swPort.performance.pppoEClient.mibCounters.d7Performance.ifInErrors

       64 bit unsigned wrappable counter."
   ::= {pr1646v2EthPortSwIXt2PPPoEMCD7PEntry 134217728}

pr1646v2EthPortSwIXt2PPPoEMCD7PIfInUnkwn OBJECT-TYPE
   SYNTAX      Counter64
   MAX-ACCESS  read-only
   STATUS      current
   DESCRIPTION
      "Path: swPort.performance.pppoEClient.mibCounters.d7Performance.ifInUnknownProtos

       64 bit unsigned wrappable counter."
   ::= {pr1646v2EthPortSwIXt2PPPoEMCD7PEntry 150994944}

pr1646v2EthPortSwIXt2PPPoEMCD7PInDropEx OBJECT-TYPE
   SYNTAX      Counter64
   MAX-ACCESS  read-only
   STATUS      current
   DESCRIPTION
      "Path: swPort.performance.pppoEClient.mibCounters.d7Performance.ifInDropLevelExceeded

       64 bit unsigned wrappable counter."
   ::= {pr1646v2EthPortSwIXt2PPPoEMCD7PEntry 335544320}

pr1646v2EthPortSwIXt2PPPoEMCD7PInDropNoMac OBJECT-TYPE
   SYNTAX      Counter64
   MAX-ACCESS  read-only
   STATUS      current
   DESCRIPTION
      "Path: swPort.performance.pppoEClient.mibCounters.d7Performance.fInDiscardsNoMacFit

       64 bit unsigned wrappable counter."
   ::= {pr1646v2EthPortSwIXt2PPPoEMCD7PEntry 301989888}

pr1646v2EthPortSwIXt2PPPoEMCD7PInDropNUCast OBJECT-TYPE
   SYNTAX      Counter64
   MAX-ACCESS  read-only
   STATUS      current
   DESCRIPTION
      "Path: swPort.performance.pppoEClient.mibCounters.d7Performance.fInDiscardsNUCast

       64 bit unsigned wrappable counter."
   ::= {pr1646v2EthPortSwIXt2PPPoEMCD7PEntry 318767104}

pr1646v2EthPortSwIXt2PPPoEMCD7PInDropFilter OBJECT-TYPE
   SYNTAX      Counter64
   MAX-ACCESS  read-only
   STATUS      current
   DESCRIPTION
      "Path: swPort.performance.pppoEClient.mibCounters.d7Performance.fInDiscardsFilter

       64 bit unsigned wrappable counter."
   ::= {pr1646v2EthPortSwIXt2PPPoEMCD7PEntry 385875968}

pr1646v2EthPortSwIXt2PPPoEMCD7PIfInBandwidth OBJECT-TYPE
   SYNTAX      Integer32
   MAX-ACCESS  read-only
   STATUS      current
   DESCRIPTION
      "Path: swPort.performance.pppoEClient.mibCounters.d7Performance.ifInBandwidth

       unit name = bps
       formula = 8 * ; 8 /"
   ::= {pr1646v2EthPortSwIXt2PPPoEMCD7PEntry 268435456}

pr1646v2EthPortSwIXt2PPPoEMCD7PIfOutOctets OBJECT-TYPE
   SYNTAX      Counter64
   MAX-ACCESS  read-only
   STATUS      current
   DESCRIPTION
      "Path: swPort.performance.pppoEClient.mibCounters.d7Performance.ifOutOctets

       64 bit unsigned wrappable counter."
   ::= {pr1646v2EthPortSwIXt2PPPoEMCD7PEntry 167772160}

pr1646v2EthPortSwIXt2PPPoEMCD7PIfOutUCPkts OBJECT-TYPE
   SYNTAX      Counter64
   MAX-ACCESS  read-only
   STATUS      current
   DESCRIPTION
      "Path: swPort.performance.pppoEClient.mibCounters.d7Performance.ifOutUcastPkts

       64 bit unsigned wrappable counter."
   ::= {pr1646v2EthPortSwIXt2PPPoEMCD7PEntry 184549376}

pr1646v2EthPortSwIXt2PPPoEMCD7PIfOutNUCPkts OBJECT-TYPE
   SYNTAX      Counter64
   MAX-ACCESS  read-only
   STATUS      current
   DESCRIPTION
      "Path: swPort.performance.pppoEClient.mibCounters.d7Performance.ifOutNUcastPkts

       64 bit unsigned wrappable counter."
   ::= {pr1646v2EthPortSwIXt2PPPoEMCD7PEntry 201326592}

pr1646v2EthPortSwIXt2PPPoEMCD7PIfOutBCPkts OBJECT-TYPE
   SYNTAX      Counter64
   MAX-ACCESS  read-only
   STATUS      current
   DESCRIPTION
      "Path: swPort.performance.pppoEClient.mibCounters.d7Performance.ifOutBcastPkts

       64 bit unsigned wrappable counter."
   ::= {pr1646v2EthPortSwIXt2PPPoEMCD7PEntry 452984832}

pr1646v2EthPortSwIXt2PPPoEMCD7PIfOutMCPkts OBJECT-TYPE
   SYNTAX      Counter64
   MAX-ACCESS  read-only
   STATUS      current
   DESCRIPTION
      "Path: swPort.performance.pppoEClient.mibCounters.d7Performance.ifOutMcastPkts

       64 bit unsigned wrappable counter."
   ::= {pr1646v2EthPortSwIXt2PPPoEMCD7PEntry 469762048}

pr1646v2EthPortSwIXt2PPPoEMCD7PIfOutDiscards OBJECT-TYPE
   SYNTAX      Counter64
   MAX-ACCESS  read-only
   STATUS      current
   DESCRIPTION
      "Path: swPort.performance.pppoEClient.mibCounters.d7Performance.ifOutDiscards

       64 bit unsigned wrappable counter."
   ::= {pr1646v2EthPortSwIXt2PPPoEMCD7PEntry 218103808}

pr1646v2EthPortSwIXt2PPPoEMCD7PIfOutErrors OBJECT-TYPE
   SYNTAX      Counter64
   MAX-ACCESS  read-only
   STATUS      current
   DESCRIPTION
      "Path: swPort.performance.pppoEClient.mibCounters.d7Performance.ifOutErrors

       64 bit unsigned wrappable counter."
   ::= {pr1646v2EthPortSwIXt2PPPoEMCD7PEntry 234881024}

pr1646v2EthPortSwIXt2PPPoEMCD7POutDropEx OBJECT-TYPE
   SYNTAX      Counter64
   MAX-ACCESS  read-only
   STATUS      current
   DESCRIPTION
      "Path: swPort.performance.pppoEClient.mibCounters.d7Performance.ifOutDropLevelExceeded

       64 bit unsigned wrappable counter."
   ::= {pr1646v2EthPortSwIXt2PPPoEMCD7PEntry 352321536}

pr1646v2EthPortSwIXt2PPPoEMCD7POutDropNoArp OBJECT-TYPE
   SYNTAX      Counter64
   MAX-ACCESS  read-only
   STATUS      current
   DESCRIPTION
      "Path: swPort.performance.pppoEClient.mibCounters.d7Performance.ifOutDiscardsNoArp

       64 bit unsigned wrappable counter."
   ::= {pr1646v2EthPortSwIXt2PPPoEMCD7PEntry 369098752}

pr1646v2EthPortSwIXt2PPPoEMCD7POutDropFilter OBJECT-TYPE
   SYNTAX      Counter64
   MAX-ACCESS  read-only
   STATUS      current
   DESCRIPTION
      "Path: swPort.performance.pppoEClient.mibCounters.d7Performance.ifOutDiscardsFilter

       64 bit unsigned wrappable counter."
   ::= {pr1646v2EthPortSwIXt2PPPoEMCD7PEntry 402653184}

pr1646v2EthPortSwIXt2PPPoEMCD7PIfOutBandwidth OBJECT-TYPE
   SYNTAX      Integer32
   MAX-ACCESS  read-only
   STATUS      current
   DESCRIPTION
      "Path: swPort.performance.pppoEClient.mibCounters.d7Performance.ifOutBandwidth

       unit name = bps
       formula = 8 * ; 8 /"
   ::= {pr1646v2EthPortSwIXt2PPPoEMCD7PEntry 285212672}

pr1646v2EthPortSwIXt2PPPoEMCD7PIfErrSec OBJECT-TYPE
   SYNTAX      Counter32
   MAX-ACCESS  read-only
   STATUS      current
   DESCRIPTION
      "Path: swPort.performance.pppoEClient.mibCounters.d7Performance.ifErrSec

       32 bit unsigned wrappable counter."
   ::= {pr1646v2EthPortSwIXt2PPPoEMCD7PEntry 251658240}



ar1646v2EthPortSwIXt2 OBJECT IDENTIFIER ::= {r1646v2EthPortSwIXt2 16}


ar1646v2EthPortSwIXt2ClearCounters OBJECT IDENTIFIER ::= {ar1646v2EthPortSwIXt2 263}

ar1646v2EthPortSwIXt2ClearCountersTable OBJECT-TYPE
   SYNTAX      SEQUENCE OF Ar1646v2EthPortSwIXt2ClearCountersEntry
   MAX-ACCESS  not-accessible
   STATUS      current
   DESCRIPTION
      "reset counters"
   ::= {ar1646v2EthPortSwIXt2ClearCounters 1}

ar1646v2EthPortSwIXt2ClearCountersEntry OBJECT-TYPE
   SYNTAX      Ar1646v2EthPortSwIXt2ClearCountersEntry
   MAX-ACCESS  not-accessible
   STATUS      current
   DESCRIPTION
      ""
   INDEX      { ar1646v2EthPortSwIXt2ClearCountersGlobalIx }
   ::= {ar1646v2EthPortSwIXt2ClearCountersTable 1}

Ar1646v2EthPortSwIXt2ClearCountersEntry ::=
   SEQUENCE
      {
      ar1646v2EthPortSwIXt2ClearCountersGlobalIx
         GlobalIndex,
      ar1646v2EthPortSwIXt2ClearCountersValue
         Integer32
      }

ar1646v2EthPortSwIXt2ClearCountersGlobalIx OBJECT-TYPE
   SYNTAX      GlobalIndex
   MAX-ACCESS  not-accessible
   STATUS      current
   DESCRIPTION
      "The value of the tlsCntTreeGlobalIndex of the MANAGED OBJECT."
   ::= {ar1646v2EthPortSwIXt2ClearCountersEntry 10}

ar1646v2EthPortSwIXt2ClearCountersValue OBJECT-TYPE
   SYNTAX      Integer32
   MAX-ACCESS  read-write
   STATUS      current
   DESCRIPTION
      "Path: swPort.actions.clearCounters"
   ::= {ar1646v2EthPortSwIXt2ClearCountersEntry 2147483648}


ar1646v2EthPortSwIXt2RestartIntf OBJECT IDENTIFIER ::= {ar1646v2EthPortSwIXt2 67}

ar1646v2EthPortSwIXt2RestartIntfTable OBJECT-TYPE
   SYNTAX      SEQUENCE OF Ar1646v2EthPortSwIXt2RestartIntfEntry
   MAX-ACCESS  not-accessible
   STATUS      current
   DESCRIPTION
      "action in the debug group"
   ::= {ar1646v2EthPortSwIXt2RestartIntf 1}

ar1646v2EthPortSwIXt2RestartIntfEntry OBJECT-TYPE
   SYNTAX      Ar1646v2EthPortSwIXt2RestartIntfEntry
   MAX-ACCESS  not-accessible
   STATUS      current
   DESCRIPTION
      ""
   INDEX      { ar1646v2EthPortSwIXt2RestartIntfGlobalIx }
   ::= {ar1646v2EthPortSwIXt2RestartIntfTable 1}

Ar1646v2EthPortSwIXt2RestartIntfEntry ::=
   SEQUENCE
      {
      ar1646v2EthPortSwIXt2RestartIntfGlobalIx
         GlobalIndex,
      ar1646v2EthPortSwIXt2RestartIntfValue
         Integer32
      }

ar1646v2EthPortSwIXt2RestartIntfGlobalIx OBJECT-TYPE
   SYNTAX      GlobalIndex
   MAX-ACCESS  not-accessible
   STATUS      current
   DESCRIPTION
      "The value of the tlsCntTreeGlobalIndex of the MANAGED OBJECT."
   ::= {ar1646v2EthPortSwIXt2RestartIntfEntry 10}

ar1646v2EthPortSwIXt2RestartIntfValue OBJECT-TYPE
   SYNTAX      Integer32
   MAX-ACCESS  read-write
   STATUS      current
   DESCRIPTION
      "Path: swPort.actions.restartIntf"
   ::= {ar1646v2EthPortSwIXt2RestartIntfEntry 2147483648}


ar1646v2EthPortSwIXt2ClearOamEventLog OBJECT IDENTIFIER ::= {ar1646v2EthPortSwIXt2 916}

ar1646v2EthPortSwIXt2ClearOamEventLogTable OBJECT-TYPE
   SYNTAX      SEQUENCE OF Ar1646v2EthPortSwIXt2ClearOamEventLogEntry
   MAX-ACCESS  not-accessible
   STATUS      current
   DESCRIPTION
      "clear the OAM event log"
   ::= {ar1646v2EthPortSwIXt2ClearOamEventLog 1}

ar1646v2EthPortSwIXt2ClearOamEventLogEntry OBJECT-TYPE
   SYNTAX      Ar1646v2EthPortSwIXt2ClearOamEventLogEntry
   MAX-ACCESS  not-accessible
   STATUS      current
   DESCRIPTION
      ""
   INDEX      { ar1646v2EthPortSwIXt2ClearOamEventLogGlobalIx }
   ::= {ar1646v2EthPortSwIXt2ClearOamEventLogTable 1}

Ar1646v2EthPortSwIXt2ClearOamEventLogEntry ::=
   SEQUENCE
      {
      ar1646v2EthPortSwIXt2ClearOamEventLogGlobalIx
         GlobalIndex,
      ar1646v2EthPortSwIXt2ClearOamEventLogValue
         Integer32
      }

ar1646v2EthPortSwIXt2ClearOamEventLogGlobalIx OBJECT-TYPE
   SYNTAX      GlobalIndex
   MAX-ACCESS  not-accessible
   STATUS      current
   DESCRIPTION
      "The value of the tlsCntTreeGlobalIndex of the MANAGED OBJECT."
   ::= {ar1646v2EthPortSwIXt2ClearOamEventLogEntry 10}

ar1646v2EthPortSwIXt2ClearOamEventLogValue OBJECT-TYPE
   SYNTAX      Integer32
   MAX-ACCESS  read-write
   STATUS      current
   DESCRIPTION
      "Path: swPort.actions.clearOamEventLog"
   ::= {ar1646v2EthPortSwIXt2ClearOamEventLogEntry 2147483648}


ar1646v2EthPortSwIXt2Loopback OBJECT IDENTIFIER ::= {ar1646v2EthPortSwIXt2 914}

ar1646v2EthPortSwIXt2LoopbackTable OBJECT-TYPE
   SYNTAX      SEQUENCE OF Ar1646v2EthPortSwIXt2LoopbackEntry
   MAX-ACCESS  not-accessible
   STATUS      current
   DESCRIPTION
      "ethernet loopback"
   ::= {ar1646v2EthPortSwIXt2Loopback 1}

ar1646v2EthPortSwIXt2LoopbackEntry OBJECT-TYPE
   SYNTAX      Ar1646v2EthPortSwIXt2LoopbackEntry
   MAX-ACCESS  not-accessible
   STATUS      current
   DESCRIPTION
      ""
   INDEX      { ar1646v2EthPortSwIXt2LoopbackGlobalIx }
   ::= {ar1646v2EthPortSwIXt2LoopbackTable 1}

Ar1646v2EthPortSwIXt2LoopbackEntry ::=
   SEQUENCE
      {
      ar1646v2EthPortSwIXt2LoopbackGlobalIx
         GlobalIndex,
      ar1646v2EthPortSwIXt2LoopbackValue
         Integer32
      }

ar1646v2EthPortSwIXt2LoopbackGlobalIx OBJECT-TYPE
   SYNTAX      GlobalIndex
   MAX-ACCESS  not-accessible
   STATUS      current
   DESCRIPTION
      "The value of the tlsCntTreeGlobalIndex of the MANAGED OBJECT."
   ::= {ar1646v2EthPortSwIXt2LoopbackEntry 10}

ar1646v2EthPortSwIXt2LoopbackValue OBJECT-TYPE
   SYNTAX      Integer32
   MAX-ACCESS  read-write
   STATUS      current
   DESCRIPTION
      "Path: swPort.actions.loopback"
   ::= {ar1646v2EthPortSwIXt2LoopbackEntry 2147483648}


ar1646v2EthPortSwIXt2Loop OBJECT IDENTIFIER ::= {ar1646v2EthPortSwIXt2 915}

ar1646v2EthPortSwIXt2LoopSSCTable OBJECT-TYPE
   SYNTAX      SEQUENCE OF Ar1646v2EthPortSwIXt2LoopEntry
   MAX-ACCESS  not-accessible
   STATUS      current
   DESCRIPTION
      "ethernet loopback type"
   ::= {ar1646v2EthPortSwIXt2Loop 1}

ar1646v2EthPortSwIXt2LoopEntry OBJECT-TYPE
   SYNTAX      Ar1646v2EthPortSwIXt2LoopEntry
   MAX-ACCESS  not-accessible
   STATUS      current
   DESCRIPTION
      ""
   INDEX      { ar1646v2EthPortSwIXt2LoopGlobalIx }
   ::= {ar1646v2EthPortSwIXt2LoopSSCTable 1}

Ar1646v2EthPortSwIXt2LoopEntry ::=
   SEQUENCE
      {
      ar1646v2EthPortSwIXt2LoopGlobalIx
         GlobalIndex,
      ar1646v2EthPortSwIXt2LoopAction
         INTEGER,
      ar1646v2EthPortSwIXt2LoopTime
         TimeTicks,
      ar1646v2EthPortSwIXt2LoopIntfName
         DisplayString
      }

ar1646v2EthPortSwIXt2LoopGlobalIx OBJECT-TYPE
   SYNTAX      GlobalIndex
   MAX-ACCESS  not-accessible
   STATUS      current
   DESCRIPTION
      "The value of the tlsCntTreeGlobalIndex of the MANAGED OBJECT."
   ::= {ar1646v2EthPortSwIXt2LoopEntry 10}

ar1646v2EthPortSwIXt2LoopAction OBJECT-TYPE
   SYNTAX      INTEGER
               {
               start (1),
               stop (2)
               }
   MAX-ACCESS  read-write
   STATUS      current
   DESCRIPTION
      "Path: swPort.actions.loop.action

       Possibilities:
               start   (1)
               stop   (2)"
   ::= {ar1646v2EthPortSwIXt2LoopEntry 16777216}

ar1646v2EthPortSwIXt2LoopTime OBJECT-TYPE
   SYNTAX      TimeTicks
   MAX-ACCESS  read-write
   STATUS      current
   DESCRIPTION
      "Path: swPort.actions.loop.time

       Time in centi-second."
   ::= {ar1646v2EthPortSwIXt2LoopEntry 50331648}

ar1646v2EthPortSwIXt2LoopIntfName OBJECT-TYPE
   SYNTAX      DisplayString
   MAX-ACCESS  read-write
   STATUS      current
   DESCRIPTION
      "Path: swPort.actions.loop.intfName"
   ::= {ar1646v2EthPortSwIXt2LoopEntry 67108864}


ar1646v2EthPortSwIXt2OamRemLoopback OBJECT IDENTIFIER ::= {ar1646v2EthPortSwIXt2 912}

ar1646v2EthPortSwIXt2OamRemLoopbackTable OBJECT-TYPE
   SYNTAX      SEQUENCE OF Ar1646v2EthPortSwIXt2OamRemLoopbackEntry
   MAX-ACCESS  not-accessible
   STATUS      current
   DESCRIPTION
      "OAM Remote Loopback"
   ::= {ar1646v2EthPortSwIXt2OamRemLoopback 1}

ar1646v2EthPortSwIXt2OamRemLoopbackEntry OBJECT-TYPE
   SYNTAX      Ar1646v2EthPortSwIXt2OamRemLoopbackEntry
   MAX-ACCESS  not-accessible
   STATUS      current
   DESCRIPTION
      ""
   INDEX      { ar1646v2EthPortSwIXt2OamRemLoopbackGlobalIx }
   ::= {ar1646v2EthPortSwIXt2OamRemLoopbackTable 1}

Ar1646v2EthPortSwIXt2OamRemLoopbackEntry ::=
   SEQUENCE
      {
      ar1646v2EthPortSwIXt2OamRemLoopbackGlobalIx
         GlobalIndex,
      ar1646v2EthPortSwIXt2OamRemLoopbackValue
         Integer32
      }

ar1646v2EthPortSwIXt2OamRemLoopbackGlobalIx OBJECT-TYPE
   SYNTAX      GlobalIndex
   MAX-ACCESS  not-accessible
   STATUS      current
   DESCRIPTION
      "The value of the tlsCntTreeGlobalIndex of the MANAGED OBJECT."
   ::= {ar1646v2EthPortSwIXt2OamRemLoopbackEntry 10}

ar1646v2EthPortSwIXt2OamRemLoopbackValue OBJECT-TYPE
   SYNTAX      Integer32
   MAX-ACCESS  read-write
   STATUS      current
   DESCRIPTION
      "Path: swPort.actions.oamRemLoopback"
   ::= {ar1646v2EthPortSwIXt2OamRemLoopbackEntry 2147483648}


ar1646v2EthPortSwIXt2Type OBJECT IDENTIFIER ::= {ar1646v2EthPortSwIXt2 913}

ar1646v2EthPortSwIXt2TypeTable OBJECT-TYPE
   SYNTAX      SEQUENCE OF Ar1646v2EthPortSwIXt2TypeEntry
   MAX-ACCESS  not-accessible
   STATUS      current
   DESCRIPTION
      "OAM Remote Loopback type"
   ::= {ar1646v2EthPortSwIXt2Type 1}

ar1646v2EthPortSwIXt2TypeEntry OBJECT-TYPE
   SYNTAX      Ar1646v2EthPortSwIXt2TypeEntry
   MAX-ACCESS  not-accessible
   STATUS      current
   DESCRIPTION
      ""
   INDEX      { ar1646v2EthPortSwIXt2TypeGlobalIx }
   ::= {ar1646v2EthPortSwIXt2TypeTable 1}

Ar1646v2EthPortSwIXt2TypeEntry ::=
   SEQUENCE
      {
      ar1646v2EthPortSwIXt2TypeGlobalIx
         GlobalIndex,
      ar1646v2EthPortSwIXt2TypeValue
         INTEGER
      }

ar1646v2EthPortSwIXt2TypeGlobalIx OBJECT-TYPE
   SYNTAX      GlobalIndex
   MAX-ACCESS  not-accessible
   STATUS      current
   DESCRIPTION
      "The value of the tlsCntTreeGlobalIndex of the MANAGED OBJECT."
   ::= {ar1646v2EthPortSwIXt2TypeEntry 10}

ar1646v2EthPortSwIXt2TypeValue OBJECT-TYPE
   SYNTAX      INTEGER
               {
               start (0),
               stop (1)
               }
   MAX-ACCESS  read-write
   STATUS      current
   DESCRIPTION
      "Path: swPort.actions.type

       Possibilities:
               start   (0)
               stop   (1)"
   ::= {ar1646v2EthPortSwIXt2TypeEntry 2147483648}


ar1646v2EthPortSwIXt2SendWOL OBJECT IDENTIFIER ::= {ar1646v2EthPortSwIXt2 333}

ar1646v2EthPortSwIXt2SendWOLTable OBJECT-TYPE
   SYNTAX      SEQUENCE OF Ar1646v2EthPortSwIXt2SendWOLEntry
   MAX-ACCESS  not-accessible
   STATUS      current
   DESCRIPTION
      "send a WakeOnLan message on this interface"
   ::= {ar1646v2EthPortSwIXt2SendWOL 1}

ar1646v2EthPortSwIXt2SendWOLEntry OBJECT-TYPE
   SYNTAX      Ar1646v2EthPortSwIXt2SendWOLEntry
   MAX-ACCESS  not-accessible
   STATUS      current
   DESCRIPTION
      ""
   INDEX      { ar1646v2EthPortSwIXt2SendWOLGlobalIx }
   ::= {ar1646v2EthPortSwIXt2SendWOLTable 1}

Ar1646v2EthPortSwIXt2SendWOLEntry ::=
   SEQUENCE
      {
      ar1646v2EthPortSwIXt2SendWOLGlobalIx
         GlobalIndex,
      ar1646v2EthPortSwIXt2SendWOLValue
         Integer32
      }

ar1646v2EthPortSwIXt2SendWOLGlobalIx OBJECT-TYPE
   SYNTAX      GlobalIndex
   MAX-ACCESS  not-accessible
   STATUS      current
   DESCRIPTION
      "The value of the tlsCntTreeGlobalIndex of the MANAGED OBJECT."
   ::= {ar1646v2EthPortSwIXt2SendWOLEntry 10}

ar1646v2EthPortSwIXt2SendWOLValue OBJECT-TYPE
   SYNTAX      Integer32
   MAX-ACCESS  read-write
   STATUS      current
   DESCRIPTION
      "Path: swPort.actions.sendWOL"
   ::= {ar1646v2EthPortSwIXt2SendWOLEntry 2147483648}


ar1646v2EthPortSwIXt2WolInfo OBJECT IDENTIFIER ::= {ar1646v2EthPortSwIXt2 332}

ar1646v2EthPortSwIXt2WolInfoSSCTable OBJECT-TYPE
   SYNTAX      SEQUENCE OF Ar1646v2EthPortSwIXt2WolInfoEntry
   MAX-ACCESS  not-accessible
   STATUS      current
   DESCRIPTION
      "content of a WakeOnLan message"
   ::= {ar1646v2EthPortSwIXt2WolInfo 1}

ar1646v2EthPortSwIXt2WolInfoEntry OBJECT-TYPE
   SYNTAX      Ar1646v2EthPortSwIXt2WolInfoEntry
   MAX-ACCESS  not-accessible
   STATUS      current
   DESCRIPTION
      ""
   INDEX      { ar1646v2EthPortSwIXt2WolInfoGlobalIx }
   ::= {ar1646v2EthPortSwIXt2WolInfoSSCTable 1}

Ar1646v2EthPortSwIXt2WolInfoEntry ::=
   SEQUENCE
      {
      ar1646v2EthPortSwIXt2WolInfoGlobalIx
         GlobalIndex,
      ar1646v2EthPortSwIXt2WolInfoTargetMAC
         OCTET STRING,
      ar1646v2EthPortSwIXt2WolInfoPassword
         OCTET STRING
      }

ar1646v2EthPortSwIXt2WolInfoGlobalIx OBJECT-TYPE
   SYNTAX      GlobalIndex
   MAX-ACCESS  not-accessible
   STATUS      current
   DESCRIPTION
      "The value of the tlsCntTreeGlobalIndex of the MANAGED OBJECT."
   ::= {ar1646v2EthPortSwIXt2WolInfoEntry 10}

ar1646v2EthPortSwIXt2WolInfoTargetMAC OBJECT-TYPE
   SYNTAX      OCTET STRING
   MAX-ACCESS  read-write
   STATUS      current
   DESCRIPTION
      "Path: swPort.actions.wolInfo.targetMAC

       MAC address."
   ::= {ar1646v2EthPortSwIXt2WolInfoEntry 16777216}

ar1646v2EthPortSwIXt2WolInfoPassword OBJECT-TYPE
   SYNTAX      OCTET STRING
   MAX-ACCESS  read-write
   STATUS      current
   DESCRIPTION
      "Path: swPort.actions.wolInfo.password"
   ::= {ar1646v2EthPortSwIXt2WolInfoEntry 33554432}


ar1646v2EthPortSwIXt2ClearArpCache OBJECT IDENTIFIER ::= {ar1646v2EthPortSwIXt2 25}

ar1646v2EthPortSwIXt2ClearArpCacheTable OBJECT-TYPE
   SYNTAX      SEQUENCE OF Ar1646v2EthPortSwIXt2ClearArpCacheEntry
   MAX-ACCESS  not-accessible
   STATUS      current
   DESCRIPTION
      "clear all dynamic enties in ARP cache table"
   ::= {ar1646v2EthPortSwIXt2ClearArpCache 1}

ar1646v2EthPortSwIXt2ClearArpCacheEntry OBJECT-TYPE
   SYNTAX      Ar1646v2EthPortSwIXt2ClearArpCacheEntry
   MAX-ACCESS  not-accessible
   STATUS      current
   DESCRIPTION
      ""
   INDEX      { ar1646v2EthPortSwIXt2ClearArpCacheGlobalIx }
   ::= {ar1646v2EthPortSwIXt2ClearArpCacheTable 1}

Ar1646v2EthPortSwIXt2ClearArpCacheEntry ::=
   SEQUENCE
      {
      ar1646v2EthPortSwIXt2ClearArpCacheGlobalIx
         GlobalIndex,
      ar1646v2EthPortSwIXt2ClearArpCacheValue
         Integer32
      }

ar1646v2EthPortSwIXt2ClearArpCacheGlobalIx OBJECT-TYPE
   SYNTAX      GlobalIndex
   MAX-ACCESS  not-accessible
   STATUS      current
   DESCRIPTION
      "The value of the tlsCntTreeGlobalIndex of the MANAGED OBJECT."
   ::= {ar1646v2EthPortSwIXt2ClearArpCacheEntry 10}

ar1646v2EthPortSwIXt2ClearArpCacheValue OBJECT-TYPE
   SYNTAX      Integer32
   MAX-ACCESS  read-write
   STATUS      current
   DESCRIPTION
      "Path: swPort.actions.clearArpCache"
   ::= {ar1646v2EthPortSwIXt2ClearArpCacheEntry 2147483648}



fr1646v2EthPortSwIXt2 OBJECT IDENTIFIER ::= {r1646v2EthPortSwIXt2 13}


fr1646v2EthPortSwIXt2Alarm OBJECT IDENTIFIER ::= {fr1646v2EthPortSwIXt2 207}

fr1646v2EthPortSwIXt2AlarmSSCTable OBJECT-TYPE
   SYNTAX      SEQUENCE OF Fr1646v2EthPortSwIXt2AlarmEntry
   MAX-ACCESS  not-accessible
   STATUS      current
   DESCRIPTION
      "IfAlarmInfo"
   ::= {fr1646v2EthPortSwIXt2Alarm 1}

fr1646v2EthPortSwIXt2AlarmEntry OBJECT-TYPE
   SYNTAX      Fr1646v2EthPortSwIXt2AlarmEntry
   MAX-ACCESS  not-accessible
   STATUS      current
   DESCRIPTION
      ""
   INDEX      { fr1646v2EthPortSwIXt2AlarmGlobalIx }
   ::= {fr1646v2EthPortSwIXt2AlarmSSCTable 1}

Fr1646v2EthPortSwIXt2AlarmEntry ::=
   SEQUENCE
      {
      fr1646v2EthPortSwIXt2AlarmGlobalIx
         GlobalIndex,
      fr1646v2EthPortSwIXt2AlarmDiscriminator
         Integer32,
      fr1646v2EthPortSwIXt2AlarmCurrent
         Integer32,
      fr1646v2EthPortSwIXt2AlarmPrevious
         Integer32,
      fr1646v2EthPortSwIXt2AlarmMask
         Integer32,
      fr1646v2EthPortSwIXt2AlarmLevLinkDown
         Integer32,
      fr1646v2EthPortSwIXt2AlarmLevPppoEDown
         Integer32
      }

fr1646v2EthPortSwIXt2AlarmGlobalIx OBJECT-TYPE
   SYNTAX      GlobalIndex
   MAX-ACCESS  not-accessible
   STATUS      current
   DESCRIPTION
      "The value of the tlsCntTreeGlobalIndex of the MANAGED OBJECT."
   ::= {fr1646v2EthPortSwIXt2AlarmEntry 10}

fr1646v2EthPortSwIXt2AlarmDiscriminator OBJECT-TYPE
   SYNTAX      Integer32
   MAX-ACCESS  read-only
   STATUS      current
   DESCRIPTION
      "Path: swPort.alarms.alarmInfo.discriminator"
   ::= {fr1646v2EthPortSwIXt2AlarmEntry 16777216}

fr1646v2EthPortSwIXt2AlarmCurrent OBJECT-TYPE
   SYNTAX      Integer32
   MAX-ACCESS  read-only
   STATUS      current
   DESCRIPTION
      "Path: swPort.alarms.alarmInfo.currentAlarms

       Bit meanings:
               bit 0 = linkDown,
               bit 9 = pppoEDown"
   ::= {fr1646v2EthPortSwIXt2AlarmEntry 33554432}

fr1646v2EthPortSwIXt2AlarmPrevious OBJECT-TYPE
   SYNTAX      Integer32
   MAX-ACCESS  read-only
   STATUS      current
   DESCRIPTION
      "Path: swPort.alarms.alarmInfo.previousAlarms

       Bit meanings:
               bit 0 = linkDown,
               bit 9 = pppoEDown"
   ::= {fr1646v2EthPortSwIXt2AlarmEntry 50331648}

fr1646v2EthPortSwIXt2AlarmMask OBJECT-TYPE
   SYNTAX      Integer32
   MAX-ACCESS  read-only
   STATUS      current
   DESCRIPTION
      "Path: swPort.alarms.alarmInfo.alarmMask

       Bit meanings:
               bit 0 = linkDown,
               bit 9 = pppoEDown"
   ::= {fr1646v2EthPortSwIXt2AlarmEntry 67108864}

fr1646v2EthPortSwIXt2AlarmLevLinkDown OBJECT-TYPE
   SYNTAX      Integer32
   MAX-ACCESS  read-only
   STATUS      current
   DESCRIPTION
      "Path: swPort.alarms.alarmInfo.alarmLevel.linkDown"
   ::= {fr1646v2EthPortSwIXt2AlarmEntry 83951616}

fr1646v2EthPortSwIXt2AlarmLevPppoEDown OBJECT-TYPE
   SYNTAX      Integer32
   MAX-ACCESS  read-only
   STATUS      current
   DESCRIPTION
      "Path: swPort.alarms.alarmInfo.alarmLevel.pppoEDown"
   ::= {fr1646v2EthPortSwIXt2AlarmEntry 84541440}


fr1646v2EthPortSwIXt2AlarmE2 OBJECT IDENTIFIER ::= {fr1646v2EthPortSwIXt2Alarm 2}

fr1646v2EthPortSwIXt2AlarmE2Entry OBJECT IDENTIFIER ::= {fr1646v2EthPortSwIXt2AlarmE2 1}

fr1646v2EthPortSwIXt2AlarmE2LinkDown OBJECT IDENTIFIER ::= {fr1646v2EthPortSwIXt2AlarmE2Entry 10}

fr1646v2EthPortSwIXt2AlarmE2LinkDownPfx OBJECT IDENTIFIER ::= {fr1646v2EthPortSwIXt2AlarmE2LinkDown 0}

fr1646v2EthPortSwIXt2AlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwInstExtUpTo8'
                (root='router1646') has changed from the ON to the OFF state."
   ::= {fr1646v2EthPortSwIXt2AlarmE2LinkDownPfx 1}

fr1646v2EthPortSwIXt2AlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'ethPortSwInstExtUpTo8'
                (root='router1646') has changed from the OFF to the ON state."
   ::= {fr1646v2EthPortSwIXt2AlarmE2LinkDownPfx 2}

fr1646v2EthPortSwIXt2AlarmE2PppoEDown OBJECT IDENTIFIER ::= {fr1646v2EthPortSwIXt2AlarmE2Entry 19}

fr1646v2EthPortSwIXt2AlarmE2PppoEDownPfx OBJECT IDENTIFIER ::= {fr1646v2EthPortSwIXt2AlarmE2PppoEDown 0}

fr1646v2EthPortSwIXt2AlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwInstExtUpTo8'
                (root='router1646') has changed from the ON to the OFF state."
   ::= {fr1646v2EthPortSwIXt2AlarmE2PppoEDownPfx 1}

fr1646v2EthPortSwIXt2AlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'ethPortSwInstExtUpTo8'
                (root='router1646') has changed from the OFF to the ON state."
   ::= {fr1646v2EthPortSwIXt2AlarmE2PppoEDownPfx 2}



END
