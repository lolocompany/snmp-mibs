OneAccess-R1646v2-958-OsSch DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2OsSch OBJECT IDENTIFIER ::= {r1646Rootv2 958}

r1646v2OsSchMOProp OBJECT-TYPE
   SYNTAX      SEQUENCE OF R1646v2OsSchMOPropEntry
   MAX-ACCESS  not-accessible
   STATUS      current
   DESCRIPTION
      ""
   ::= {r1646v2OsSch 1}

r1646v2OsSchMOPropEntry OBJECT-TYPE
   SYNTAX      R1646v2OsSchMOPropEntry
   MAX-ACCESS  not-accessible
   STATUS      current
   DESCRIPTION
      ""
   INDEX      { r1646v2OsSchMOPropGlobalIx }
   ::= {r1646v2OsSchMOProp 1}

R1646v2OsSchMOPropEntry ::=
   SEQUENCE
      {
      r1646v2OsSchMOPropPath
         ContainmentPath,
      r1646v2OsSchMOPropRev
         ObjectRevision,
      r1646v2OsSchMOPropGlobalIx
         GlobalIndex
      }

r1646v2OsSchMOPropPath OBJECT-TYPE
   SYNTAX      ContainmentPath
   MAX-ACCESS  read-only
   STATUS      current
   DESCRIPTION
      "Textual description of the containment tree from the instance of
       the root object down to the instance of the current object."
   ::= {r1646v2OsSchMOPropEntry 3}

r1646v2OsSchMOPropRev OBJECT-TYPE
   SYNTAX      ObjectRevision
   MAX-ACCESS  read-only
   STATUS      current
   DESCRIPTION
      "This value corresponds with the revision of the MANAGED OBJECT."
   ::= {r1646v2OsSchMOPropEntry 4}

r1646v2OsSchMOPropGlobalIx OBJECT-TYPE
   SYNTAX      GlobalIndex
   MAX-ACCESS  read-only
   STATUS      current
   DESCRIPTION
      "The value of the tlsCntTreeGlobalIndex of the MANAGED OBJECT."
   ::= {r1646v2OsSchMOPropEntry 10}



pr1646v2OsSch OBJECT IDENTIFIER ::= {r1646v2OsSch 12}


pr1646v2OsSchCurrUsedProcPower OBJECT IDENTIFIER ::= {pr1646v2OsSch 10}

pr1646v2OsSchCurrUsedProcPowerTable OBJECT-TYPE
   SYNTAX      SEQUENCE OF Pr1646v2OsSchCurrUsedProcPowerEntry
   MAX-ACCESS  not-accessible
   STATUS      current
   DESCRIPTION
      "currently used processing power in the system"
   ::= {pr1646v2OsSchCurrUsedProcPower 1}

pr1646v2OsSchCurrUsedProcPowerEntry OBJECT-TYPE
   SYNTAX      Pr1646v2OsSchCurrUsedProcPowerEntry
   MAX-ACCESS  not-accessible
   STATUS      current
   DESCRIPTION
      ""
   INDEX      { pr1646v2OsSchCurrUsedProcPowerGlobalIx }
   ::= {pr1646v2OsSchCurrUsedProcPowerTable 1}

Pr1646v2OsSchCurrUsedProcPowerEntry ::=
   SEQUENCE
      {
      pr1646v2OsSchCurrUsedProcPowerGlobalIx
         GlobalIndex,
      pr1646v2OsSchCurrUsedProcPowerValue
         Integer32
      }

pr1646v2OsSchCurrUsedProcPowerGlobalIx OBJECT-TYPE
   SYNTAX      GlobalIndex
   MAX-ACCESS  not-accessible
   STATUS      current
   DESCRIPTION
      "The value of the tlsCntTreeGlobalIndex of the MANAGED OBJECT."
   ::= {pr1646v2OsSchCurrUsedProcPowerEntry 10}

pr1646v2OsSchCurrUsedProcPowerValue OBJECT-TYPE
   SYNTAX      Integer32
   UNITS       "%"
   MAX-ACCESS  read-only
   STATUS      current
   DESCRIPTION
      "Path: scheduler.performance.currUsedProcPower

       unit name = %"
   ::= {pr1646v2OsSchCurrUsedProcPowerEntry 2147483648}


pr1646v2OsSchUsedProcPower OBJECT IDENTIFIER ::= {pr1646v2OsSch 11}

pr1646v2OsSchUsedProcPowerSSCTable OBJECT-TYPE
   SYNTAX      SEQUENCE OF Pr1646v2OsSchUsedProcPowerEntry
   MAX-ACCESS  not-accessible
   STATUS      current
   DESCRIPTION
      "used processing power 5-minute history"
   ::= {pr1646v2OsSchUsedProcPower 1}

pr1646v2OsSchUsedProcPowerEntry OBJECT-TYPE
   SYNTAX      Pr1646v2OsSchUsedProcPowerEntry
   MAX-ACCESS  not-accessible
   STATUS      current
   DESCRIPTION
      ""
   INDEX      { pr1646v2OsSchUsedProcPowerGlobalIx,
                pr1646v2OsSchUsedProcPowerTableIx }
   ::= {pr1646v2OsSchUsedProcPowerSSCTable 1}

Pr1646v2OsSchUsedProcPowerEntry ::=
   SEQUENCE
      {
      pr1646v2OsSchUsedProcPowerGlobalIx
         GlobalIndex,
      pr1646v2OsSchUsedProcPowerTableIx
         TableIndex,
      pr1646v2OsSchUsedProcPowerSysUpTime
         TimeTicks,
      pr1646v2OsSchUsedProcPowerMin
         Integer32,
      pr1646v2OsSchUsedProcPowerAverage
         Integer32,
      pr1646v2OsSchUsedProcPowerMax
         Integer32
      }

pr1646v2OsSchUsedProcPowerGlobalIx OBJECT-TYPE
   SYNTAX      GlobalIndex
   MAX-ACCESS  not-accessible
   STATUS      current
   DESCRIPTION
      "The value of the tlsCntTreeGlobalIndex of the MANAGED OBJECT."
   ::= {pr1646v2OsSchUsedProcPowerEntry 10}

pr1646v2OsSchUsedProcPowerTableIx OBJECT-TYPE
   SYNTAX      TableIndex
   MAX-ACCESS  not-accessible
   STATUS      current
   DESCRIPTION
      ""
   ::= {pr1646v2OsSchUsedProcPowerEntry 11}

pr1646v2OsSchUsedProcPowerSysUpTime OBJECT-TYPE
   SYNTAX      TimeTicks
   MAX-ACCESS  read-only
   STATUS      current
   DESCRIPTION
      "Path: scheduler.performance.usedProcPower.sysUpTime

       Time in centi-second."
   ::= {pr1646v2OsSchUsedProcPowerEntry 67108864}

pr1646v2OsSchUsedProcPowerMin OBJECT-TYPE
   SYNTAX      Integer32
   UNITS       "%"
   MAX-ACCESS  read-only
   STATUS      current
   DESCRIPTION
      "Path: scheduler.performance.usedProcPower.min

       unit name = %"
   ::= {pr1646v2OsSchUsedProcPowerEntry 50331648}

pr1646v2OsSchUsedProcPowerAverage OBJECT-TYPE
   SYNTAX      Integer32
   UNITS       "%"
   MAX-ACCESS  read-only
   STATUS      current
   DESCRIPTION
      "Path: scheduler.performance.usedProcPower.average

       unit name = %"
   ::= {pr1646v2OsSchUsedProcPowerEntry 16777216}

pr1646v2OsSchUsedProcPowerMax OBJECT-TYPE
   SYNTAX      Integer32
   UNITS       "%"
   MAX-ACCESS  read-only
   STATUS      current
   DESCRIPTION
      "Path: scheduler.performance.usedProcPower.max

       unit name = %"
   ::= {pr1646v2OsSchUsedProcPowerEntry 33554432}


pr1646v2OsSchFreeDataBuffers OBJECT IDENTIFIER ::= {pr1646v2OsSch 12}

pr1646v2OsSchFreeDataBuffersTable OBJECT-TYPE
   SYNTAX      SEQUENCE OF Pr1646v2OsSchFreeDataBuffersEntry
   MAX-ACCESS  not-accessible
   STATUS      current
   DESCRIPTION
      "amount of free databuffers"
   ::= {pr1646v2OsSchFreeDataBuffers 1}

pr1646v2OsSchFreeDataBuffersEntry OBJECT-TYPE
   SYNTAX      Pr1646v2OsSchFreeDataBuffersEntry
   MAX-ACCESS  not-accessible
   STATUS      current
   DESCRIPTION
      ""
   INDEX      { pr1646v2OsSchFreeDataBuffersGlobalIx }
   ::= {pr1646v2OsSchFreeDataBuffersTable 1}

Pr1646v2OsSchFreeDataBuffersEntry ::=
   SEQUENCE
      {
      pr1646v2OsSchFreeDataBuffersGlobalIx
         GlobalIndex,
      pr1646v2OsSchFreeDataBuffersValue
         Gauge32
      }

pr1646v2OsSchFreeDataBuffersGlobalIx OBJECT-TYPE
   SYNTAX      GlobalIndex
   MAX-ACCESS  not-accessible
   STATUS      current
   DESCRIPTION
      "The value of the tlsCntTreeGlobalIndex of the MANAGED OBJECT."
   ::= {pr1646v2OsSchFreeDataBuffersEntry 10}

pr1646v2OsSchFreeDataBuffersValue OBJECT-TYPE
   SYNTAX      Gauge32
   MAX-ACCESS  read-only
   STATUS      current
   DESCRIPTION
      "Path: scheduler.performance.freeDataBuffers

       32 bit unsigned gauge value."
   ::= {pr1646v2OsSchFreeDataBuffersEntry 2147483648}


pr1646v2OsSchTotalDataBuffers OBJECT IDENTIFIER ::= {pr1646v2OsSch 13}

pr1646v2OsSchTotalDataBuffersTable OBJECT-TYPE
   SYNTAX      SEQUENCE OF Pr1646v2OsSchTotalDataBuffersEntry
   MAX-ACCESS  not-accessible
   STATUS      current
   DESCRIPTION
      "total amount of databuffers (= free + used)"
   ::= {pr1646v2OsSchTotalDataBuffers 1}

pr1646v2OsSchTotalDataBuffersEntry OBJECT-TYPE
   SYNTAX      Pr1646v2OsSchTotalDataBuffersEntry
   MAX-ACCESS  not-accessible
   STATUS      current
   DESCRIPTION
      ""
   INDEX      { pr1646v2OsSchTotalDataBuffersGlobalIx }
   ::= {pr1646v2OsSchTotalDataBuffersTable 1}

Pr1646v2OsSchTotalDataBuffersEntry ::=
   SEQUENCE
      {
      pr1646v2OsSchTotalDataBuffersGlobalIx
         GlobalIndex,
      pr1646v2OsSchTotalDataBuffersValue
         Gauge32
      }

pr1646v2OsSchTotalDataBuffersGlobalIx OBJECT-TYPE
   SYNTAX      GlobalIndex
   MAX-ACCESS  not-accessible
   STATUS      current
   DESCRIPTION
      "The value of the tlsCntTreeGlobalIndex of the MANAGED OBJECT."
   ::= {pr1646v2OsSchTotalDataBuffersEntry 10}

pr1646v2OsSchTotalDataBuffersValue OBJECT-TYPE
   SYNTAX      Gauge32
   MAX-ACCESS  read-only
   STATUS      current
   DESCRIPTION
      "Path: scheduler.performance.totalDataBuffers

       32 bit unsigned gauge value."
   ::= {pr1646v2OsSchTotalDataBuffersEntry 2147483648}


pr1646v2OsSchFreeMemory OBJECT IDENTIFIER ::= {pr1646v2OsSch 16}

pr1646v2OsSchFreeMemoryTable OBJECT-TYPE
   SYNTAX      SEQUENCE OF Pr1646v2OsSchFreeMemoryEntry
   MAX-ACCESS  not-accessible
   STATUS      current
   DESCRIPTION
      "free memory in the system in bytes"
   ::= {pr1646v2OsSchFreeMemory 1}

pr1646v2OsSchFreeMemoryEntry OBJECT-TYPE
   SYNTAX      Pr1646v2OsSchFreeMemoryEntry
   MAX-ACCESS  not-accessible
   STATUS      current
   DESCRIPTION
      ""
   INDEX      { pr1646v2OsSchFreeMemoryGlobalIx }
   ::= {pr1646v2OsSchFreeMemoryTable 1}

Pr1646v2OsSchFreeMemoryEntry ::=
   SEQUENCE
      {
      pr1646v2OsSchFreeMemoryGlobalIx
         GlobalIndex,
      pr1646v2OsSchFreeMemoryValue
         Gauge32
      }

pr1646v2OsSchFreeMemoryGlobalIx OBJECT-TYPE
   SYNTAX      GlobalIndex
   MAX-ACCESS  not-accessible
   STATUS      current
   DESCRIPTION
      "The value of the tlsCntTreeGlobalIndex of the MANAGED OBJECT."
   ::= {pr1646v2OsSchFreeMemoryEntry 10}

pr1646v2OsSchFreeMemoryValue OBJECT-TYPE
   SYNTAX      Gauge32
   MAX-ACCESS  read-only
   STATUS      current
   DESCRIPTION
      "Path: scheduler.performance.freeMemory

       32 bit unsigned gauge value."
   ::= {pr1646v2OsSchFreeMemoryEntry 2147483648}


pr1646v2OsSchTotalMemory OBJECT IDENTIFIER ::= {pr1646v2OsSch 17}

pr1646v2OsSchTotalMemoryTable OBJECT-TYPE
   SYNTAX      SEQUENCE OF Pr1646v2OsSchTotalMemoryEntry
   MAX-ACCESS  not-accessible
   STATUS      current
   DESCRIPTION
      "total memory in the system in bytes"
   ::= {pr1646v2OsSchTotalMemory 1}

pr1646v2OsSchTotalMemoryEntry OBJECT-TYPE
   SYNTAX      Pr1646v2OsSchTotalMemoryEntry
   MAX-ACCESS  not-accessible
   STATUS      current
   DESCRIPTION
      ""
   INDEX      { pr1646v2OsSchTotalMemoryGlobalIx }
   ::= {pr1646v2OsSchTotalMemoryTable 1}

Pr1646v2OsSchTotalMemoryEntry ::=
   SEQUENCE
      {
      pr1646v2OsSchTotalMemoryGlobalIx
         GlobalIndex,
      pr1646v2OsSchTotalMemoryValue
         Gauge32
      }

pr1646v2OsSchTotalMemoryGlobalIx OBJECT-TYPE
   SYNTAX      GlobalIndex
   MAX-ACCESS  not-accessible
   STATUS      current
   DESCRIPTION
      "The value of the tlsCntTreeGlobalIndex of the MANAGED OBJECT."
   ::= {pr1646v2OsSchTotalMemoryEntry 10}

pr1646v2OsSchTotalMemoryValue OBJECT-TYPE
   SYNTAX      Gauge32
   MAX-ACCESS  read-only
   STATUS      current
   DESCRIPTION
      "Path: scheduler.performance.totalMemory

       32 bit unsigned gauge value."
   ::= {pr1646v2OsSchTotalMemoryEntry 2147483648}


pr1646v2OsSchMemAllocations OBJECT IDENTIFIER ::= {pr1646v2OsSch 61}

pr1646v2OsSchMemAllocationsTable OBJECT-TYPE
   SYNTAX      SEQUENCE OF Pr1646v2OsSchMemAllocationsEntry
   MAX-ACCESS  not-accessible
   STATUS      current
   DESCRIPTION
      "total number of memory allocations"
   ::= {pr1646v2OsSchMemAllocations 1}

pr1646v2OsSchMemAllocationsEntry OBJECT-TYPE
   SYNTAX      Pr1646v2OsSchMemAllocationsEntry
   MAX-ACCESS  not-accessible
   STATUS      current
   DESCRIPTION
      ""
   INDEX      { pr1646v2OsSchMemAllocationsGlobalIx }
   ::= {pr1646v2OsSchMemAllocationsTable 1}

Pr1646v2OsSchMemAllocationsEntry ::=
   SEQUENCE
      {
      pr1646v2OsSchMemAllocationsGlobalIx
         GlobalIndex,
      pr1646v2OsSchMemAllocationsValue
         Counter32
      }

pr1646v2OsSchMemAllocationsGlobalIx OBJECT-TYPE
   SYNTAX      GlobalIndex
   MAX-ACCESS  not-accessible
   STATUS      current
   DESCRIPTION
      "The value of the tlsCntTreeGlobalIndex of the MANAGED OBJECT."
   ::= {pr1646v2OsSchMemAllocationsEntry 10}

pr1646v2OsSchMemAllocationsValue OBJECT-TYPE
   SYNTAX      Counter32
   MAX-ACCESS  read-only
   STATUS      current
   DESCRIPTION
      "Path: scheduler.performance.memAllocations

       32 bit unsigned wrappable counter."
   ::= {pr1646v2OsSchMemAllocationsEntry 2147483648}


pr1646v2OsSchMemOutstanding OBJECT IDENTIFIER ::= {pr1646v2OsSch 62}

pr1646v2OsSchMemOutstandingTable OBJECT-TYPE
   SYNTAX      SEQUENCE OF Pr1646v2OsSchMemOutstandingEntry
   MAX-ACCESS  not-accessible
   STATUS      current
   DESCRIPTION
      "memory outstanding"
   ::= {pr1646v2OsSchMemOutstanding 1}

pr1646v2OsSchMemOutstandingEntry OBJECT-TYPE
   SYNTAX      Pr1646v2OsSchMemOutstandingEntry
   MAX-ACCESS  not-accessible
   STATUS      current
   DESCRIPTION
      ""
   INDEX      { pr1646v2OsSchMemOutstandingGlobalIx }
   ::= {pr1646v2OsSchMemOutstandingTable 1}

Pr1646v2OsSchMemOutstandingEntry ::=
   SEQUENCE
      {
      pr1646v2OsSchMemOutstandingGlobalIx
         GlobalIndex,
      pr1646v2OsSchMemOutstandingValue
         Gauge32
      }

pr1646v2OsSchMemOutstandingGlobalIx OBJECT-TYPE
   SYNTAX      GlobalIndex
   MAX-ACCESS  not-accessible
   STATUS      current
   DESCRIPTION
      "The value of the tlsCntTreeGlobalIndex of the MANAGED OBJECT."
   ::= {pr1646v2OsSchMemOutstandingEntry 10}

pr1646v2OsSchMemOutstandingValue OBJECT-TYPE
   SYNTAX      Gauge32
   MAX-ACCESS  read-only
   STATUS      current
   DESCRIPTION
      "Path: scheduler.performance.memOutstanding

       32 bit unsigned gauge value."
   ::= {pr1646v2OsSchMemOutstandingEntry 2147483648}


pr1646v2OsSchMemOverview OBJECT IDENTIFIER ::= {pr1646v2OsSch 63}

pr1646v2OsSchMemOverviewSSCTable OBJECT-TYPE
   SYNTAX      SEQUENCE OF Pr1646v2OsSchMemOverviewEntry
   MAX-ACCESS  not-accessible
   STATUS      current
   DESCRIPTION
      ""
   ::= {pr1646v2OsSchMemOverview 1}

pr1646v2OsSchMemOverviewEntry OBJECT-TYPE
   SYNTAX      Pr1646v2OsSchMemOverviewEntry
   MAX-ACCESS  not-accessible
   STATUS      current
   DESCRIPTION
      ""
   INDEX      { pr1646v2OsSchMemOverviewGlobalIx,
                pr1646v2OsSchMemOverviewTableIx }
   ::= {pr1646v2OsSchMemOverviewSSCTable 1}

Pr1646v2OsSchMemOverviewEntry ::=
   SEQUENCE
      {
      pr1646v2OsSchMemOverviewGlobalIx
         GlobalIndex,
      pr1646v2OsSchMemOverviewTableIx
         TableIndex,
      pr1646v2OsSchMemOverviewSize
         INTEGER,
      pr1646v2OsSchMemOverviewAllocations
         Counter32,
      pr1646v2OsSchMemOverviewOutstanding
         Gauge32,
      pr1646v2OsSchMemOverviewPartFreeSegs
         Gauge32,
      pr1646v2OsSchMemOverviewFullFreeSegs
         Gauge32,
      pr1646v2OsSchMemOverviewCompFilledSegs
         Gauge32,
      pr1646v2OsSchMemOverviewFreeMemory
         Gauge32
      }

pr1646v2OsSchMemOverviewGlobalIx OBJECT-TYPE
   SYNTAX      GlobalIndex
   MAX-ACCESS  not-accessible
   STATUS      current
   DESCRIPTION
      "The value of the tlsCntTreeGlobalIndex of the MANAGED OBJECT."
   ::= {pr1646v2OsSchMemOverviewEntry 10}

pr1646v2OsSchMemOverviewTableIx OBJECT-TYPE
   SYNTAX      TableIndex
   MAX-ACCESS  not-accessible
   STATUS      current
   DESCRIPTION
      ""
   ::= {pr1646v2OsSchMemOverviewEntry 11}

pr1646v2OsSchMemOverviewSize OBJECT-TYPE
   SYNTAX      INTEGER
               {
               sg32K (1),
               s1Km32K (2),
               s128m1K (3),
               s0m128 (4),
               s8 (5),
               s16 (6),
               s24 (7),
               s32 (8),
               s48 (9),
               s64 (10),
               s80 (11),
               s96 (12),
               s128 (13),
               s (100)
               }
   MAX-ACCESS  read-only
   STATUS      current
   DESCRIPTION
      "Path: scheduler.performance.memOverview.size

       Possibilities:
               >32K   (1)
               1K-32K   (2)
               128-1K   (3)
               0-128   (4)
               8   (5)
               16   (6)
               24   (7)
               32   (8)
               48   (9)
               64   (10)
               80   (11)
               96   (12)
               128   (13)
                  (100)"
   ::= {pr1646v2OsSchMemOverviewEntry 16777216}

pr1646v2OsSchMemOverviewAllocations OBJECT-TYPE
   SYNTAX      Counter32
   MAX-ACCESS  read-only
   STATUS      current
   DESCRIPTION
      "Path: scheduler.performance.memOverview.allocations

       32 bit unsigned wrappable counter."
   ::= {pr1646v2OsSchMemOverviewEntry 33554432}

pr1646v2OsSchMemOverviewOutstanding OBJECT-TYPE
   SYNTAX      Gauge32
   MAX-ACCESS  read-only
   STATUS      current
   DESCRIPTION
      "Path: scheduler.performance.memOverview.outstanding

       32 bit unsigned gauge value."
   ::= {pr1646v2OsSchMemOverviewEntry 50331648}

pr1646v2OsSchMemOverviewPartFreeSegs OBJECT-TYPE
   SYNTAX      Gauge32
   MAX-ACCESS  read-only
   STATUS      current
   DESCRIPTION
      "Path: scheduler.performance.memOverview.partialFreeSegments

       32 bit unsigned gauge value."
   ::= {pr1646v2OsSchMemOverviewEntry 67108864}

pr1646v2OsSchMemOverviewFullFreeSegs OBJECT-TYPE
   SYNTAX      Gauge32
   MAX-ACCESS  read-only
   STATUS      current
   DESCRIPTION
      "Path: scheduler.performance.memOverview.fullFreeSegments

       32 bit unsigned gauge value."
   ::= {pr1646v2OsSchMemOverviewEntry 83886080}

pr1646v2OsSchMemOverviewCompFilledSegs OBJECT-TYPE
   SYNTAX      Gauge32
   MAX-ACCESS  read-only
   STATUS      current
   DESCRIPTION
      "Path: scheduler.performance.memOverview.completeFilledSegments

       32 bit unsigned gauge value."
   ::= {pr1646v2OsSchMemOverviewEntry 100663296}

pr1646v2OsSchMemOverviewFreeMemory OBJECT-TYPE
   SYNTAX      Gauge32
   MAX-ACCESS  read-only
   STATUS      current
   DESCRIPTION
      "Path: scheduler.performance.memOverview.freeMemory

       32 bit unsigned gauge value."
   ::= {pr1646v2OsSchMemOverviewEntry 117440512}


pr1646v2OsSchFreeShortBuffers OBJECT IDENTIFIER ::= {pr1646v2OsSch 20}

pr1646v2OsSchFreeShortBuffersTable OBJECT-TYPE
   SYNTAX      SEQUENCE OF Pr1646v2OsSchFreeShortBuffersEntry
   MAX-ACCESS  not-accessible
   STATUS      current
   DESCRIPTION
      "amount of free databuffers"
   ::= {pr1646v2OsSchFreeShortBuffers 1}

pr1646v2OsSchFreeShortBuffersEntry OBJECT-TYPE
   SYNTAX      Pr1646v2OsSchFreeShortBuffersEntry
   MAX-ACCESS  not-accessible
   STATUS      current
   DESCRIPTION
      ""
   INDEX      { pr1646v2OsSchFreeShortBuffersGlobalIx }
   ::= {pr1646v2OsSchFreeShortBuffersTable 1}

Pr1646v2OsSchFreeShortBuffersEntry ::=
   SEQUENCE
      {
      pr1646v2OsSchFreeShortBuffersGlobalIx
         GlobalIndex,
      pr1646v2OsSchFreeShortBuffersValue
         Gauge32
      }

pr1646v2OsSchFreeShortBuffersGlobalIx OBJECT-TYPE
   SYNTAX      GlobalIndex
   MAX-ACCESS  not-accessible
   STATUS      current
   DESCRIPTION
      "The value of the tlsCntTreeGlobalIndex of the MANAGED OBJECT."
   ::= {pr1646v2OsSchFreeShortBuffersEntry 10}

pr1646v2OsSchFreeShortBuffersValue OBJECT-TYPE
   SYNTAX      Gauge32
   MAX-ACCESS  read-only
   STATUS      current
   DESCRIPTION
      "Path: scheduler.performance.freeShortBuffers

       32 bit unsigned gauge value."
   ::= {pr1646v2OsSchFreeShortBuffersEntry 2147483648}


pr1646v2OsSchTotalShortBuffers OBJECT IDENTIFIER ::= {pr1646v2OsSch 21}

pr1646v2OsSchTotalShortBuffersTable OBJECT-TYPE
   SYNTAX      SEQUENCE OF Pr1646v2OsSchTotalShortBuffersEntry
   MAX-ACCESS  not-accessible
   STATUS      current
   DESCRIPTION
      "total amount of databuffers (= free + used)"
   ::= {pr1646v2OsSchTotalShortBuffers 1}

pr1646v2OsSchTotalShortBuffersEntry OBJECT-TYPE
   SYNTAX      Pr1646v2OsSchTotalShortBuffersEntry
   MAX-ACCESS  not-accessible
   STATUS      current
   DESCRIPTION
      ""
   INDEX      { pr1646v2OsSchTotalShortBuffersGlobalIx }
   ::= {pr1646v2OsSchTotalShortBuffersTable 1}

Pr1646v2OsSchTotalShortBuffersEntry ::=
   SEQUENCE
      {
      pr1646v2OsSchTotalShortBuffersGlobalIx
         GlobalIndex,
      pr1646v2OsSchTotalShortBuffersValue
         Gauge32
      }

pr1646v2OsSchTotalShortBuffersGlobalIx OBJECT-TYPE
   SYNTAX      GlobalIndex
   MAX-ACCESS  not-accessible
   STATUS      current
   DESCRIPTION
      "The value of the tlsCntTreeGlobalIndex of the MANAGED OBJECT."
   ::= {pr1646v2OsSchTotalShortBuffersEntry 10}

pr1646v2OsSchTotalShortBuffersValue OBJECT-TYPE
   SYNTAX      Gauge32
   MAX-ACCESS  read-only
   STATUS      current
   DESCRIPTION
      "Path: scheduler.performance.totalShortBuffers

       32 bit unsigned gauge value."
   ::= {pr1646v2OsSchTotalShortBuffersEntry 2147483648}


pr1646v2OsSchTaskInfo OBJECT IDENTIFIER ::= {pr1646v2OsSch 32}

pr1646v2OsSchTaskInfoSSCTable OBJECT-TYPE
   SYNTAX      SEQUENCE OF Pr1646v2OsSchTaskInfoEntry
   MAX-ACCESS  not-accessible
   STATUS      current
   DESCRIPTION
      "task-related information"
   ::= {pr1646v2OsSchTaskInfo 1}

pr1646v2OsSchTaskInfoEntry OBJECT-TYPE
   SYNTAX      Pr1646v2OsSchTaskInfoEntry
   MAX-ACCESS  not-accessible
   STATUS      current
   DESCRIPTION
      ""
   INDEX      { pr1646v2OsSchTaskInfoGlobalIx,
                pr1646v2OsSchTaskInfoTableIx }
   ::= {pr1646v2OsSchTaskInfoSSCTable 1}

Pr1646v2OsSchTaskInfoEntry ::=
   SEQUENCE
      {
      pr1646v2OsSchTaskInfoGlobalIx
         GlobalIndex,
      pr1646v2OsSchTaskInfoTableIx
         TableIndex,
      pr1646v2OsSchTaskInfoTaskName
         DisplayString,
      pr1646v2OsSchTaskInfoTaskStatus
         INTEGER,
      pr1646v2OsSchTaskInfoLoad30s
         Integer32,
      pr1646v2OsSchTaskInfoLoad5m
         Integer32,
      pr1646v2OsSchTaskInfoRunningInMedium
         Integer32,
      pr1646v2OsSchTaskInfoRunningInHigh
         Integer32,
      pr1646v2OsSchTaskInfoActivity
         Gauge32
      }

pr1646v2OsSchTaskInfoGlobalIx OBJECT-TYPE
   SYNTAX      GlobalIndex
   MAX-ACCESS  not-accessible
   STATUS      current
   DESCRIPTION
      "The value of the tlsCntTreeGlobalIndex of the MANAGED OBJECT."
   ::= {pr1646v2OsSchTaskInfoEntry 10}

pr1646v2OsSchTaskInfoTableIx OBJECT-TYPE
   SYNTAX      TableIndex
   MAX-ACCESS  not-accessible
   STATUS      current
   DESCRIPTION
      ""
   ::= {pr1646v2OsSchTaskInfoEntry 11}

pr1646v2OsSchTaskInfoTaskName OBJECT-TYPE
   SYNTAX      DisplayString
   MAX-ACCESS  read-only
   STATUS      current
   DESCRIPTION
      "Path: scheduler.performance.taskInfo.taskName"
   ::= {pr1646v2OsSchTaskInfoEntry 16777216}

pr1646v2OsSchTaskInfoTaskStatus OBJECT-TYPE
   SYNTAX      INTEGER
               {
               asleep (1),
               awake (2),
               inactive (3)
               }
   MAX-ACCESS  read-only
   STATUS      current
   DESCRIPTION
      "Path: scheduler.performance.taskInfo.taskStatus

       Possibilities:
               asleep   (1)
               awake   (2)
               inactive   (3)"
   ::= {pr1646v2OsSchTaskInfoEntry 33554432}

pr1646v2OsSchTaskInfoLoad30s OBJECT-TYPE
   SYNTAX      Integer32
   MAX-ACCESS  read-only
   STATUS      current
   DESCRIPTION
      "Path: scheduler.performance.taskInfo.load30s

       unit name = %
       formula = 10 / ; 10 *"
   ::= {pr1646v2OsSchTaskInfoEntry 50331648}

pr1646v2OsSchTaskInfoLoad5m OBJECT-TYPE
   SYNTAX      Integer32
   MAX-ACCESS  read-only
   STATUS      current
   DESCRIPTION
      "Path: scheduler.performance.taskInfo.load5m

       unit name = %
       formula = 10 / ; 10 *"
   ::= {pr1646v2OsSchTaskInfoEntry 67108864}

pr1646v2OsSchTaskInfoRunningInMedium OBJECT-TYPE
   SYNTAX      Integer32
   MAX-ACCESS  read-only
   STATUS      current
   DESCRIPTION
      "Path: scheduler.performance.taskInfo.runningInMedium

       unit name = %
       formula = 10 / ; 10 *"
   ::= {pr1646v2OsSchTaskInfoEntry 100663296}

pr1646v2OsSchTaskInfoRunningInHigh OBJECT-TYPE
   SYNTAX      Integer32
   MAX-ACCESS  read-only
   STATUS      current
   DESCRIPTION
      "Path: scheduler.performance.taskInfo.runningInHigh

       unit name = %
       formula = 10 / ; 10 *"
   ::= {pr1646v2OsSchTaskInfoEntry 117440512}

pr1646v2OsSchTaskInfoActivity OBJECT-TYPE
   SYNTAX      Gauge32
   MAX-ACCESS  read-only
   STATUS      current
   DESCRIPTION
      "Path: scheduler.performance.taskInfo.activity

       32 bit unsigned gauge value."
   ::= {pr1646v2OsSchTaskInfoEntry 419430400}


pr1646v2OsSchProcPower OBJECT IDENTIFIER ::= {pr1646v2OsSch 28}

pr1646v2OsSchProcPowerSSCTable OBJECT-TYPE
   SYNTAX      SEQUENCE OF Pr1646v2OsSchProcPowerEntry
   MAX-ACCESS  not-accessible
   STATUS      current
   DESCRIPTION
      "processing power"
   ::= {pr1646v2OsSchProcPower 1}

pr1646v2OsSchProcPowerEntry OBJECT-TYPE
   SYNTAX      Pr1646v2OsSchProcPowerEntry
   MAX-ACCESS  not-accessible
   STATUS      current
   DESCRIPTION
      ""
   INDEX      { pr1646v2OsSchProcPowerGlobalIx }
   ::= {pr1646v2OsSchProcPowerSSCTable 1}

Pr1646v2OsSchProcPowerEntry ::=
   SEQUENCE
      {
      pr1646v2OsSchProcPowerGlobalIx
         GlobalIndex,
      pr1646v2OsSchProcPower15sec
         Integer32,
      pr1646v2OsSchProcPower30sec
         Integer32,
      pr1646v2OsSchProcPower1min
         Integer32,
      pr1646v2OsSchProcPower2min
         Integer32,
      pr1646v2OsSchProcPower5min
         Integer32
      }

pr1646v2OsSchProcPowerGlobalIx OBJECT-TYPE
   SYNTAX      GlobalIndex
   MAX-ACCESS  not-accessible
   STATUS      current
   DESCRIPTION
      "The value of the tlsCntTreeGlobalIndex of the MANAGED OBJECT."
   ::= {pr1646v2OsSchProcPowerEntry 10}

pr1646v2OsSchProcPower15sec OBJECT-TYPE
   SYNTAX      Integer32
   UNITS       "%"
   MAX-ACCESS  read-only
   STATUS      current
   DESCRIPTION
      "Path: scheduler.performance.procPower.15sec

       unit name = %"
   ::= {pr1646v2OsSchProcPowerEntry 83886080}

pr1646v2OsSchProcPower30sec OBJECT-TYPE
   SYNTAX      Integer32
   UNITS       "%"
   MAX-ACCESS  read-only
   STATUS      current
   DESCRIPTION
      "Path: scheduler.performance.procPower.30sec

       unit name = %"
   ::= {pr1646v2OsSchProcPowerEntry 167772160}

pr1646v2OsSchProcPower1min OBJECT-TYPE
   SYNTAX      Integer32
   UNITS       "%"
   MAX-ACCESS  read-only
   STATUS      current
   DESCRIPTION
      "Path: scheduler.performance.procPower.1min

       unit name = %"
   ::= {pr1646v2OsSchProcPowerEntry 335544320}

pr1646v2OsSchProcPower2min OBJECT-TYPE
   SYNTAX      Integer32
   UNITS       "%"
   MAX-ACCESS  read-only
   STATUS      current
   DESCRIPTION
      "Path: scheduler.performance.procPower.2min

       unit name = %"
   ::= {pr1646v2OsSchProcPowerEntry 671088640}

pr1646v2OsSchProcPower5min OBJECT-TYPE
   SYNTAX      Integer32
   UNITS       "%"
   MAX-ACCESS  read-only
   STATUS      current
   DESCRIPTION
      "Path: scheduler.performance.procPower.5min

       unit name = %"
   ::= {pr1646v2OsSchProcPowerEntry 1677721600}


pr1646v2OsSchH2OperatingSystem OBJECT IDENTIFIER ::= {pr1646v2OsSch 25}

pr1646v2OsSchH2OperatingSystemSSCTable OBJECT-TYPE
   SYNTAX      SEQUENCE OF Pr1646v2OsSchH2OperatingSystemEntry
   MAX-ACCESS  not-accessible
   STATUS      current
   DESCRIPTION
      "os statistics"
   ::= {pr1646v2OsSchH2OperatingSystem 1}

pr1646v2OsSchH2OperatingSystemEntry OBJECT-TYPE
   SYNTAX      Pr1646v2OsSchH2OperatingSystemEntry
   MAX-ACCESS  not-accessible
   STATUS      current
   DESCRIPTION
      ""
   INDEX      { pr1646v2OsSchH2OperatingSystemGlobalIx,
                pr1646v2OsSchH2OperatingSystemTableIx }
   ::= {pr1646v2OsSchH2OperatingSystemSSCTable 1}

Pr1646v2OsSchH2OperatingSystemEntry ::=
   SEQUENCE
      {
      pr1646v2OsSchH2OperatingSystemGlobalIx
         GlobalIndex,
      pr1646v2OsSchH2OperatingSystemTableIx
         TableIndex,
      pr1646v2OsSchH2OperatingSystemSysUpTime
         TimeTicks,
      pr1646v2OsSchH2OperatingSystemUsedProcPowerMin
         Integer32,
      pr1646v2OsSchH2OperatingSystemUsedProcPowerAvrg
         Integer32,
      pr1646v2OsSchH2OperatingSystemUsedProcPowerMax
         Integer32,
      pr1646v2OsSchH2OperatingSystemFreeMemoryMin
         Integer32,
      pr1646v2OsSchH2OperatingSystemFreeMemoryAvrg
         Integer32,
      pr1646v2OsSchH2OperatingSystemFreeMemoryMax
         Integer32,
      pr1646v2OsSchH2OperatingSystemMemOutstanding
         Integer32,
      pr1646v2OsSchH2OperatingSystemFreeDataBuffersMin
         Integer32,
      pr1646v2OsSchH2OperatingSystemFreeDataBuffersAvrg
         Integer32,
      pr1646v2OsSchH2OperatingSystemFreeDataBuffersMax
         Integer32,
      pr1646v2OsSchH2OperatingSystemFreeShortBuffersMin
         Integer32,
      pr1646v2OsSchH2OperatingSystemFreeShortBuffersAvrg
         Integer32,
      pr1646v2OsSchH2OperatingSystemFreeShortBuffersMax
         Integer32,
      pr1646v2OsSchH2OperatingSystemFreeDiskSpaceMin
         Integer32,
      pr1646v2OsSchH2OperatingSystemFreeDiskSpaceAvrg
         Integer32,
      pr1646v2OsSchH2OperatingSystemFreeDiskSpaceMax
         Integer32
      }

pr1646v2OsSchH2OperatingSystemGlobalIx OBJECT-TYPE
   SYNTAX      GlobalIndex
   MAX-ACCESS  not-accessible
   STATUS      current
   DESCRIPTION
      "The value of the tlsCntTreeGlobalIndex of the MANAGED OBJECT."
   ::= {pr1646v2OsSchH2OperatingSystemEntry 10}

pr1646v2OsSchH2OperatingSystemTableIx OBJECT-TYPE
   SYNTAX      TableIndex
   MAX-ACCESS  not-accessible
   STATUS      current
   DESCRIPTION
      ""
   ::= {pr1646v2OsSchH2OperatingSystemEntry 11}

pr1646v2OsSchH2OperatingSystemSysUpTime OBJECT-TYPE
   SYNTAX      TimeTicks
   MAX-ACCESS  read-only
   STATUS      current
   DESCRIPTION
      "Path: scheduler.performance.h2OperatingSystem.sysUpTime

       Time in centi-second."
   ::= {pr1646v2OsSchH2OperatingSystemEntry 16777216}

pr1646v2OsSchH2OperatingSystemUsedProcPowerMin OBJECT-TYPE
   SYNTAX      Integer32
   UNITS       "%"
   MAX-ACCESS  read-only
   STATUS      current
   DESCRIPTION
      "Path: scheduler.performance.h2OperatingSystem.usedProcPowerMin

       unit name = %"
   ::= {pr1646v2OsSchH2OperatingSystemEntry 33554432}

pr1646v2OsSchH2OperatingSystemUsedProcPowerAvrg OBJECT-TYPE
   SYNTAX      Integer32
   UNITS       "%"
   MAX-ACCESS  read-only
   STATUS      current
   DESCRIPTION
      "Path: scheduler.performance.h2OperatingSystem.usedProcPowerAvrg

       unit name = %"
   ::= {pr1646v2OsSchH2OperatingSystemEntry 50331648}

pr1646v2OsSchH2OperatingSystemUsedProcPowerMax OBJECT-TYPE
   SYNTAX      Integer32
   UNITS       "%"
   MAX-ACCESS  read-only
   STATUS      current
   DESCRIPTION
      "Path: scheduler.performance.h2OperatingSystem.usedProcPowerMax

       unit name = %"
   ::= {pr1646v2OsSchH2OperatingSystemEntry 67108864}

pr1646v2OsSchH2OperatingSystemFreeMemoryMin OBJECT-TYPE
   SYNTAX      Integer32
   MAX-ACCESS  read-only
   STATUS      current
   DESCRIPTION
      "Path: scheduler.performance.h2OperatingSystem.freeMemoryMin

       unit name = kbyte
       formula = 16 * ; 16 /"
   ::= {pr1646v2OsSchH2OperatingSystemEntry 83886080}

pr1646v2OsSchH2OperatingSystemFreeMemoryAvrg OBJECT-TYPE
   SYNTAX      Integer32
   MAX-ACCESS  read-only
   STATUS      current
   DESCRIPTION
      "Path: scheduler.performance.h2OperatingSystem.freeMemoryAvrg

       unit name = kbyte
       formula = 16 * ; 16 /"
   ::= {pr1646v2OsSchH2OperatingSystemEntry 100663296}

pr1646v2OsSchH2OperatingSystemFreeMemoryMax OBJECT-TYPE
   SYNTAX      Integer32
   MAX-ACCESS  read-only
   STATUS      current
   DESCRIPTION
      "Path: scheduler.performance.h2OperatingSystem.freeMemoryMax

       unit name = kbyte
       formula = 16 * ; 16 /"
   ::= {pr1646v2OsSchH2OperatingSystemEntry 117440512}

pr1646v2OsSchH2OperatingSystemMemOutstanding OBJECT-TYPE
   SYNTAX      Integer32
   MAX-ACCESS  read-only
   STATUS      current
   DESCRIPTION
      "Path: scheduler.performance.h2OperatingSystem.memOutstanding

       formula = 16 * ; 16 /"
   ::= {pr1646v2OsSchH2OperatingSystemEntry 234881024}

pr1646v2OsSchH2OperatingSystemFreeDataBuffersMin OBJECT-TYPE
   SYNTAX      Integer32
   MAX-ACCESS  read-only
   STATUS      current
   DESCRIPTION
      "Path: scheduler.performance.h2OperatingSystem.freeDataBuffersMin"
   ::= {pr1646v2OsSchH2OperatingSystemEntry 134217728}

pr1646v2OsSchH2OperatingSystemFreeDataBuffersAvrg OBJECT-TYPE
   SYNTAX      Integer32
   MAX-ACCESS  read-only
   STATUS      current
   DESCRIPTION
      "Path: scheduler.performance.h2OperatingSystem.freeDataBuffersAvrg"
   ::= {pr1646v2OsSchH2OperatingSystemEntry 150994944}

pr1646v2OsSchH2OperatingSystemFreeDataBuffersMax OBJECT-TYPE
   SYNTAX      Integer32
   MAX-ACCESS  read-only
   STATUS      current
   DESCRIPTION
      "Path: scheduler.performance.h2OperatingSystem.freeDataBuffersMax"
   ::= {pr1646v2OsSchH2OperatingSystemEntry 167772160}

pr1646v2OsSchH2OperatingSystemFreeShortBuffersMin OBJECT-TYPE
   SYNTAX      Integer32
   MAX-ACCESS  read-only
   STATUS      current
   DESCRIPTION
      "Path: scheduler.performance.h2OperatingSystem.freeShortBuffersMin"
   ::= {pr1646v2OsSchH2OperatingSystemEntry 184549376}

pr1646v2OsSchH2OperatingSystemFreeShortBuffersAvrg OBJECT-TYPE
   SYNTAX      Integer32
   MAX-ACCESS  read-only
   STATUS      current
   DESCRIPTION
      "Path: scheduler.performance.h2OperatingSystem.freeShortBuffersAvrg"
   ::= {pr1646v2OsSchH2OperatingSystemEntry 201326592}

pr1646v2OsSchH2OperatingSystemFreeShortBuffersMax OBJECT-TYPE
   SYNTAX      Integer32
   MAX-ACCESS  read-only
   STATUS      current
   DESCRIPTION
      "Path: scheduler.performance.h2OperatingSystem.freeShortBuffersMax"
   ::= {pr1646v2OsSchH2OperatingSystemEntry 218103808}

pr1646v2OsSchH2OperatingSystemFreeDiskSpaceMin OBJECT-TYPE
   SYNTAX      Integer32
   MAX-ACCESS  read-only
   STATUS      current
   DESCRIPTION
      "Path: scheduler.performance.h2OperatingSystem.freeDiskSpaceMin

       unit name = kbyte
       formula = 16 * ; 16 /"
   ::= {pr1646v2OsSchH2OperatingSystemEntry 251658240}

pr1646v2OsSchH2OperatingSystemFreeDiskSpaceAvrg OBJECT-TYPE
   SYNTAX      Integer32
   MAX-ACCESS  read-only
   STATUS      current
   DESCRIPTION
      "Path: scheduler.performance.h2OperatingSystem.freeDiskSpaceAvrg

       unit name = kbyte
       formula = 16 * ; 16 /"
   ::= {pr1646v2OsSchH2OperatingSystemEntry 268435456}

pr1646v2OsSchH2OperatingSystemFreeDiskSpaceMax OBJECT-TYPE
   SYNTAX      Integer32
   MAX-ACCESS  read-only
   STATUS      current
   DESCRIPTION
      "Path: scheduler.performance.h2OperatingSystem.freeDiskSpaceMax

       unit name = kbyte
       formula = 16 * ; 16 /"
   ::= {pr1646v2OsSchH2OperatingSystemEntry 285212672}


pr1646v2OsSchH24OperatingSystem OBJECT IDENTIFIER ::= {pr1646v2OsSch 26}

pr1646v2OsSchH24OperatingSystemSSCTable OBJECT-TYPE
   SYNTAX      SEQUENCE OF Pr1646v2OsSchH24OperatingSystemEntry
   MAX-ACCESS  not-accessible
   STATUS      current
   DESCRIPTION
      "os statistics"
   ::= {pr1646v2OsSchH24OperatingSystem 1}

pr1646v2OsSchH24OperatingSystemEntry OBJECT-TYPE
   SYNTAX      Pr1646v2OsSchH24OperatingSystemEntry
   MAX-ACCESS  not-accessible
   STATUS      current
   DESCRIPTION
      ""
   INDEX      { pr1646v2OsSchH24OperatingSystemGlobalIx,
                pr1646v2OsSchH24OperatingSystemTableIx }
   ::= {pr1646v2OsSchH24OperatingSystemSSCTable 1}

Pr1646v2OsSchH24OperatingSystemEntry ::=
   SEQUENCE
      {
      pr1646v2OsSchH24OperatingSystemGlobalIx
         GlobalIndex,
      pr1646v2OsSchH24OperatingSystemTableIx
         TableIndex,
      pr1646v2OsSchH24OperatingSystemSysUpTime
         TimeTicks,
      pr1646v2OsSchH24OperatingSystemUsedProcPowerMin
         Integer32,
      pr1646v2OsSchH24OperatingSystemUsedProcPowerAvrg
         Integer32,
      pr1646v2OsSchH24OperatingSystemUsedProcPowerMax
         Integer32,
      pr1646v2OsSchH24OperatingSystemFreeMemoryMin
         Integer32,
      pr1646v2OsSchH24OperatingSystemFreeMemoryAvrg
         Integer32,
      pr1646v2OsSchH24OperatingSystemFreeMemoryMax
         Integer32,
      pr1646v2OsSchH24OperatingSystemMemOutstanding
         Integer32,
      pr1646v2OsSchH24OperatingSystemFreeDataBuffersMin
         Integer32,
      pr1646v2OsSchH24OperatingSystemFreeDataBuffersAvrg
         Integer32,
      pr1646v2OsSchH24OperatingSystemFreeDataBuffersMax
         Integer32,
      pr1646v2OsSchH24OperatingSystemFreeShortBuffersMin
         Integer32,
      pr1646v2OsSchH24OperatingSystemFreeShortBuffersAvrg
         Integer32,
      pr1646v2OsSchH24OperatingSystemFreeShortBuffersMax
         Integer32,
      pr1646v2OsSchH24OperatingSystemFreeDiskSpaceMin
         Integer32,
      pr1646v2OsSchH24OperatingSystemFreeDiskSpaceAvrg
         Integer32,
      pr1646v2OsSchH24OperatingSystemFreeDiskSpaceMax
         Integer32
      }

pr1646v2OsSchH24OperatingSystemGlobalIx OBJECT-TYPE
   SYNTAX      GlobalIndex
   MAX-ACCESS  not-accessible
   STATUS      current
   DESCRIPTION
      "The value of the tlsCntTreeGlobalIndex of the MANAGED OBJECT."
   ::= {pr1646v2OsSchH24OperatingSystemEntry 10}

pr1646v2OsSchH24OperatingSystemTableIx OBJECT-TYPE
   SYNTAX      TableIndex
   MAX-ACCESS  not-accessible
   STATUS      current
   DESCRIPTION
      ""
   ::= {pr1646v2OsSchH24OperatingSystemEntry 11}

pr1646v2OsSchH24OperatingSystemSysUpTime OBJECT-TYPE
   SYNTAX      TimeTicks
   MAX-ACCESS  read-only
   STATUS      current
   DESCRIPTION
      "Path: scheduler.performance.h24OperatingSystem.sysUpTime

       Time in centi-second."
   ::= {pr1646v2OsSchH24OperatingSystemEntry 16777216}

pr1646v2OsSchH24OperatingSystemUsedProcPowerMin OBJECT-TYPE
   SYNTAX      Integer32
   UNITS       "%"
   MAX-ACCESS  read-only
   STATUS      current
   DESCRIPTION
      "Path: scheduler.performance.h24OperatingSystem.usedProcPowerMin

       unit name = %"
   ::= {pr1646v2OsSchH24OperatingSystemEntry 33554432}

pr1646v2OsSchH24OperatingSystemUsedProcPowerAvrg OBJECT-TYPE
   SYNTAX      Integer32
   UNITS       "%"
   MAX-ACCESS  read-only
   STATUS      current
   DESCRIPTION
      "Path: scheduler.performance.h24OperatingSystem.usedProcPowerAvrg

       unit name = %"
   ::= {pr1646v2OsSchH24OperatingSystemEntry 50331648}

pr1646v2OsSchH24OperatingSystemUsedProcPowerMax OBJECT-TYPE
   SYNTAX      Integer32
   UNITS       "%"
   MAX-ACCESS  read-only
   STATUS      current
   DESCRIPTION
      "Path: scheduler.performance.h24OperatingSystem.usedProcPowerMax

       unit name = %"
   ::= {pr1646v2OsSchH24OperatingSystemEntry 67108864}

pr1646v2OsSchH24OperatingSystemFreeMemoryMin OBJECT-TYPE
   SYNTAX      Integer32
   MAX-ACCESS  read-only
   STATUS      current
   DESCRIPTION
      "Path: scheduler.performance.h24OperatingSystem.freeMemoryMin

       unit name = kbyte
       formula = 16 * ; 16 /"
   ::= {pr1646v2OsSchH24OperatingSystemEntry 83886080}

pr1646v2OsSchH24OperatingSystemFreeMemoryAvrg OBJECT-TYPE
   SYNTAX      Integer32
   MAX-ACCESS  read-only
   STATUS      current
   DESCRIPTION
      "Path: scheduler.performance.h24OperatingSystem.freeMemoryAvrg

       unit name = kbyte
       formula = 16 * ; 16 /"
   ::= {pr1646v2OsSchH24OperatingSystemEntry 100663296}

pr1646v2OsSchH24OperatingSystemFreeMemoryMax OBJECT-TYPE
   SYNTAX      Integer32
   MAX-ACCESS  read-only
   STATUS      current
   DESCRIPTION
      "Path: scheduler.performance.h24OperatingSystem.freeMemoryMax

       unit name = kbyte
       formula = 16 * ; 16 /"
   ::= {pr1646v2OsSchH24OperatingSystemEntry 117440512}

pr1646v2OsSchH24OperatingSystemMemOutstanding OBJECT-TYPE
   SYNTAX      Integer32
   MAX-ACCESS  read-only
   STATUS      current
   DESCRIPTION
      "Path: scheduler.performance.h24OperatingSystem.memOutstanding

       formula = 16 * ; 16 /"
   ::= {pr1646v2OsSchH24OperatingSystemEntry 234881024}

pr1646v2OsSchH24OperatingSystemFreeDataBuffersMin OBJECT-TYPE
   SYNTAX      Integer32
   MAX-ACCESS  read-only
   STATUS      current
   DESCRIPTION
      "Path: scheduler.performance.h24OperatingSystem.freeDataBuffersMin"
   ::= {pr1646v2OsSchH24OperatingSystemEntry 134217728}

pr1646v2OsSchH24OperatingSystemFreeDataBuffersAvrg OBJECT-TYPE
   SYNTAX      Integer32
   MAX-ACCESS  read-only
   STATUS      current
   DESCRIPTION
      "Path: scheduler.performance.h24OperatingSystem.freeDataBuffersAvrg"
   ::= {pr1646v2OsSchH24OperatingSystemEntry 150994944}

pr1646v2OsSchH24OperatingSystemFreeDataBuffersMax OBJECT-TYPE
   SYNTAX      Integer32
   MAX-ACCESS  read-only
   STATUS      current
   DESCRIPTION
      "Path: scheduler.performance.h24OperatingSystem.freeDataBuffersMax"
   ::= {pr1646v2OsSchH24OperatingSystemEntry 167772160}

pr1646v2OsSchH24OperatingSystemFreeShortBuffersMin OBJECT-TYPE
   SYNTAX      Integer32
   MAX-ACCESS  read-only
   STATUS      current
   DESCRIPTION
      "Path: scheduler.performance.h24OperatingSystem.freeShortBuffersMin"
   ::= {pr1646v2OsSchH24OperatingSystemEntry 184549376}

pr1646v2OsSchH24OperatingSystemFreeShortBuffersAvrg OBJECT-TYPE
   SYNTAX      Integer32
   MAX-ACCESS  read-only
   STATUS      current
   DESCRIPTION
      "Path: scheduler.performance.h24OperatingSystem.freeShortBuffersAvrg"
   ::= {pr1646v2OsSchH24OperatingSystemEntry 201326592}

pr1646v2OsSchH24OperatingSystemFreeShortBuffersMax OBJECT-TYPE
   SYNTAX      Integer32
   MAX-ACCESS  read-only
   STATUS      current
   DESCRIPTION
      "Path: scheduler.performance.h24OperatingSystem.freeShortBuffersMax"
   ::= {pr1646v2OsSchH24OperatingSystemEntry 218103808}

pr1646v2OsSchH24OperatingSystemFreeDiskSpaceMin OBJECT-TYPE
   SYNTAX      Integer32
   MAX-ACCESS  read-only
   STATUS      current
   DESCRIPTION
      "Path: scheduler.performance.h24OperatingSystem.freeDiskSpaceMin

       unit name = kbyte
       formula = 16 * ; 16 /"
   ::= {pr1646v2OsSchH24OperatingSystemEntry 251658240}

pr1646v2OsSchH24OperatingSystemFreeDiskSpaceAvrg OBJECT-TYPE
   SYNTAX      Integer32
   MAX-ACCESS  read-only
   STATUS      current
   DESCRIPTION
      "Path: scheduler.performance.h24OperatingSystem.freeDiskSpaceAvrg

       unit name = kbyte
       formula = 16 * ; 16 /"
   ::= {pr1646v2OsSchH24OperatingSystemEntry 268435456}

pr1646v2OsSchH24OperatingSystemFreeDiskSpaceMax OBJECT-TYPE
   SYNTAX      Integer32
   MAX-ACCESS  read-only
   STATUS      current
   DESCRIPTION
      "Path: scheduler.performance.h24OperatingSystem.freeDiskSpaceMax

       unit name = kbyte
       formula = 16 * ; 16 /"
   ::= {pr1646v2OsSchH24OperatingSystemEntry 285212672}


pr1646v2OsSchD7OperatingSystem OBJECT IDENTIFIER ::= {pr1646v2OsSch 27}

pr1646v2OsSchD7OperatingSystemSSCTable OBJECT-TYPE
   SYNTAX      SEQUENCE OF Pr1646v2OsSchD7OperatingSystemEntry
   MAX-ACCESS  not-accessible
   STATUS      current
   DESCRIPTION
      "os statistics"
   ::= {pr1646v2OsSchD7OperatingSystem 1}

pr1646v2OsSchD7OperatingSystemEntry OBJECT-TYPE
   SYNTAX      Pr1646v2OsSchD7OperatingSystemEntry
   MAX-ACCESS  not-accessible
   STATUS      current
   DESCRIPTION
      ""
   INDEX      { pr1646v2OsSchD7OperatingSystemGlobalIx,
                pr1646v2OsSchD7OperatingSystemTableIx }
   ::= {pr1646v2OsSchD7OperatingSystemSSCTable 1}

Pr1646v2OsSchD7OperatingSystemEntry ::=
   SEQUENCE
      {
      pr1646v2OsSchD7OperatingSystemGlobalIx
         GlobalIndex,
      pr1646v2OsSchD7OperatingSystemTableIx
         TableIndex,
      pr1646v2OsSchD7OperatingSystemSysUpTime
         TimeTicks,
      pr1646v2OsSchD7OperatingSystemUsedProcPowerMin
         Integer32,
      pr1646v2OsSchD7OperatingSystemUsedProcPowerAvrg
         Integer32,
      pr1646v2OsSchD7OperatingSystemUsedProcPowerMax
         Integer32,
      pr1646v2OsSchD7OperatingSystemFreeMemoryMin
         Integer32,
      pr1646v2OsSchD7OperatingSystemFreeMemoryAvrg
         Integer32,
      pr1646v2OsSchD7OperatingSystemFreeMemoryMax
         Integer32,
      pr1646v2OsSchD7OperatingSystemMemOutstanding
         Integer32,
      pr1646v2OsSchD7OperatingSystemFreeDataBuffersMin
         Integer32,
      pr1646v2OsSchD7OperatingSystemFreeDataBuffersAvrg
         Integer32,
      pr1646v2OsSchD7OperatingSystemFreeDataBuffersMax
         Integer32,
      pr1646v2OsSchD7OperatingSystemFreeShortBuffersMin
         Integer32,
      pr1646v2OsSchD7OperatingSystemFreeShortBuffersAvrg
         Integer32,
      pr1646v2OsSchD7OperatingSystemFreeShortBuffersMax
         Integer32,
      pr1646v2OsSchD7OperatingSystemFreeDiskSpaceMin
         Integer32,
      pr1646v2OsSchD7OperatingSystemFreeDiskSpaceAvrg
         Integer32,
      pr1646v2OsSchD7OperatingSystemFreeDiskSpaceMax
         Integer32
      }

pr1646v2OsSchD7OperatingSystemGlobalIx OBJECT-TYPE
   SYNTAX      GlobalIndex
   MAX-ACCESS  not-accessible
   STATUS      current
   DESCRIPTION
      "The value of the tlsCntTreeGlobalIndex of the MANAGED OBJECT."
   ::= {pr1646v2OsSchD7OperatingSystemEntry 10}

pr1646v2OsSchD7OperatingSystemTableIx OBJECT-TYPE
   SYNTAX      TableIndex
   MAX-ACCESS  not-accessible
   STATUS      current
   DESCRIPTION
      ""
   ::= {pr1646v2OsSchD7OperatingSystemEntry 11}

pr1646v2OsSchD7OperatingSystemSysUpTime OBJECT-TYPE
   SYNTAX      TimeTicks
   MAX-ACCESS  read-only
   STATUS      current
   DESCRIPTION
      "Path: scheduler.performance.d7OperatingSystem.sysUpTime

       Time in centi-second."
   ::= {pr1646v2OsSchD7OperatingSystemEntry 16777216}

pr1646v2OsSchD7OperatingSystemUsedProcPowerMin OBJECT-TYPE
   SYNTAX      Integer32
   UNITS       "%"
   MAX-ACCESS  read-only
   STATUS      current
   DESCRIPTION
      "Path: scheduler.performance.d7OperatingSystem.usedProcPowerMin

       unit name = %"
   ::= {pr1646v2OsSchD7OperatingSystemEntry 33554432}

pr1646v2OsSchD7OperatingSystemUsedProcPowerAvrg OBJECT-TYPE
   SYNTAX      Integer32
   UNITS       "%"
   MAX-ACCESS  read-only
   STATUS      current
   DESCRIPTION
      "Path: scheduler.performance.d7OperatingSystem.usedProcPowerAvrg

       unit name = %"
   ::= {pr1646v2OsSchD7OperatingSystemEntry 50331648}

pr1646v2OsSchD7OperatingSystemUsedProcPowerMax OBJECT-TYPE
   SYNTAX      Integer32
   UNITS       "%"
   MAX-ACCESS  read-only
   STATUS      current
   DESCRIPTION
      "Path: scheduler.performance.d7OperatingSystem.usedProcPowerMax

       unit name = %"
   ::= {pr1646v2OsSchD7OperatingSystemEntry 67108864}

pr1646v2OsSchD7OperatingSystemFreeMemoryMin OBJECT-TYPE
   SYNTAX      Integer32
   MAX-ACCESS  read-only
   STATUS      current
   DESCRIPTION
      "Path: scheduler.performance.d7OperatingSystem.freeMemoryMin

       unit name = kbyte
       formula = 16 * ; 16 /"
   ::= {pr1646v2OsSchD7OperatingSystemEntry 83886080}

pr1646v2OsSchD7OperatingSystemFreeMemoryAvrg OBJECT-TYPE
   SYNTAX      Integer32
   MAX-ACCESS  read-only
   STATUS      current
   DESCRIPTION
      "Path: scheduler.performance.d7OperatingSystem.freeMemoryAvrg

       unit name = kbyte
       formula = 16 * ; 16 /"
   ::= {pr1646v2OsSchD7OperatingSystemEntry 100663296}

pr1646v2OsSchD7OperatingSystemFreeMemoryMax OBJECT-TYPE
   SYNTAX      Integer32
   MAX-ACCESS  read-only
   STATUS      current
   DESCRIPTION
      "Path: scheduler.performance.d7OperatingSystem.freeMemoryMax

       unit name = kbyte
       formula = 16 * ; 16 /"
   ::= {pr1646v2OsSchD7OperatingSystemEntry 117440512}

pr1646v2OsSchD7OperatingSystemMemOutstanding OBJECT-TYPE
   SYNTAX      Integer32
   MAX-ACCESS  read-only
   STATUS      current
   DESCRIPTION
      "Path: scheduler.performance.d7OperatingSystem.memOutstanding

       formula = 16 * ; 16 /"
   ::= {pr1646v2OsSchD7OperatingSystemEntry 234881024}

pr1646v2OsSchD7OperatingSystemFreeDataBuffersMin OBJECT-TYPE
   SYNTAX      Integer32
   MAX-ACCESS  read-only
   STATUS      current
   DESCRIPTION
      "Path: scheduler.performance.d7OperatingSystem.freeDataBuffersMin"
   ::= {pr1646v2OsSchD7OperatingSystemEntry 134217728}

pr1646v2OsSchD7OperatingSystemFreeDataBuffersAvrg OBJECT-TYPE
   SYNTAX      Integer32
   MAX-ACCESS  read-only
   STATUS      current
   DESCRIPTION
      "Path: scheduler.performance.d7OperatingSystem.freeDataBuffersAvrg"
   ::= {pr1646v2OsSchD7OperatingSystemEntry 150994944}

pr1646v2OsSchD7OperatingSystemFreeDataBuffersMax OBJECT-TYPE
   SYNTAX      Integer32
   MAX-ACCESS  read-only
   STATUS      current
   DESCRIPTION
      "Path: scheduler.performance.d7OperatingSystem.freeDataBuffersMax"
   ::= {pr1646v2OsSchD7OperatingSystemEntry 167772160}

pr1646v2OsSchD7OperatingSystemFreeShortBuffersMin OBJECT-TYPE
   SYNTAX      Integer32
   MAX-ACCESS  read-only
   STATUS      current
   DESCRIPTION
      "Path: scheduler.performance.d7OperatingSystem.freeShortBuffersMin"
   ::= {pr1646v2OsSchD7OperatingSystemEntry 184549376}

pr1646v2OsSchD7OperatingSystemFreeShortBuffersAvrg OBJECT-TYPE
   SYNTAX      Integer32
   MAX-ACCESS  read-only
   STATUS      current
   DESCRIPTION
      "Path: scheduler.performance.d7OperatingSystem.freeShortBuffersAvrg"
   ::= {pr1646v2OsSchD7OperatingSystemEntry 201326592}

pr1646v2OsSchD7OperatingSystemFreeShortBuffersMax OBJECT-TYPE
   SYNTAX      Integer32
   MAX-ACCESS  read-only
   STATUS      current
   DESCRIPTION
      "Path: scheduler.performance.d7OperatingSystem.freeShortBuffersMax"
   ::= {pr1646v2OsSchD7OperatingSystemEntry 218103808}

pr1646v2OsSchD7OperatingSystemFreeDiskSpaceMin OBJECT-TYPE
   SYNTAX      Integer32
   MAX-ACCESS  read-only
   STATUS      current
   DESCRIPTION
      "Path: scheduler.performance.d7OperatingSystem.freeDiskSpaceMin

       unit name = kbyte
       formula = 16 * ; 16 /"
   ::= {pr1646v2OsSchD7OperatingSystemEntry 251658240}

pr1646v2OsSchD7OperatingSystemFreeDiskSpaceAvrg OBJECT-TYPE
   SYNTAX      Integer32
   MAX-ACCESS  read-only
   STATUS      current
   DESCRIPTION
      "Path: scheduler.performance.d7OperatingSystem.freeDiskSpaceAvrg

       unit name = kbyte
       formula = 16 * ; 16 /"
   ::= {pr1646v2OsSchD7OperatingSystemEntry 268435456}

pr1646v2OsSchD7OperatingSystemFreeDiskSpaceMax OBJECT-TYPE
   SYNTAX      Integer32
   MAX-ACCESS  read-only
   STATUS      current
   DESCRIPTION
      "Path: scheduler.performance.d7OperatingSystem.freeDiskSpaceMax

       unit name = kbyte
       formula = 16 * ; 16 /"
   ::= {pr1646v2OsSchD7OperatingSystemEntry 285212672}



sr1646v2OsSch OBJECT IDENTIFIER ::= {r1646v2OsSch 14}


sr1646v2OsSchTaskInfo OBJECT IDENTIFIER ::= {sr1646v2OsSch 30}

sr1646v2OsSchTaskInfoSSCTable OBJECT-TYPE
   SYNTAX      SEQUENCE OF Sr1646v2OsSchTaskInfoEntry
   MAX-ACCESS  not-accessible
   STATUS      current
   DESCRIPTION
      "task-related information"
   ::= {sr1646v2OsSchTaskInfo 1}

sr1646v2OsSchTaskInfoEntry OBJECT-TYPE
   SYNTAX      Sr1646v2OsSchTaskInfoEntry
   MAX-ACCESS  not-accessible
   STATUS      current
   DESCRIPTION
      ""
   INDEX      { sr1646v2OsSchTaskInfoGlobalIx,
                sr1646v2OsSchTaskInfoTableIx }
   ::= {sr1646v2OsSchTaskInfoSSCTable 1}

Sr1646v2OsSchTaskInfoEntry ::=
   SEQUENCE
      {
      sr1646v2OsSchTaskInfoGlobalIx
         GlobalIndex,
      sr1646v2OsSchTaskInfoTableIx
         TableIndex,
      sr1646v2OsSchTaskInfoTaskName
         DisplayString,
      sr1646v2OsSchTaskInfoTaskStatus
         INTEGER,
      sr1646v2OsSchTaskInfoTaskId
         Integer32,
      sr1646v2OsSchTaskInfoProgramCounter
         OCTET STRING
      }

sr1646v2OsSchTaskInfoGlobalIx OBJECT-TYPE
   SYNTAX      GlobalIndex
   MAX-ACCESS  not-accessible
   STATUS      current
   DESCRIPTION
      "The value of the tlsCntTreeGlobalIndex of the MANAGED OBJECT."
   ::= {sr1646v2OsSchTaskInfoEntry 10}

sr1646v2OsSchTaskInfoTableIx OBJECT-TYPE
   SYNTAX      TableIndex
   MAX-ACCESS  not-accessible
   STATUS      current
   DESCRIPTION
      ""
   ::= {sr1646v2OsSchTaskInfoEntry 11}

sr1646v2OsSchTaskInfoTaskName OBJECT-TYPE
   SYNTAX      DisplayString
   MAX-ACCESS  read-only
   STATUS      current
   DESCRIPTION
      "Path: scheduler.status.taskInfo.taskName"
   ::= {sr1646v2OsSchTaskInfoEntry 16777216}

sr1646v2OsSchTaskInfoTaskStatus OBJECT-TYPE
   SYNTAX      INTEGER
               {
               asleep (1),
               awake (2),
               inactive (3)
               }
   MAX-ACCESS  read-only
   STATUS      current
   DESCRIPTION
      "Path: scheduler.status.taskInfo.taskStatus

       Possibilities:
               asleep   (1)
               awake   (2)
               inactive   (3)"
   ::= {sr1646v2OsSchTaskInfoEntry 33554432}

sr1646v2OsSchTaskInfoTaskId OBJECT-TYPE
   SYNTAX      Integer32
   MAX-ACCESS  read-only
   STATUS      current
   DESCRIPTION
      "Path: scheduler.status.taskInfo.taskId"
   ::= {sr1646v2OsSchTaskInfoEntry 1778384896}

sr1646v2OsSchTaskInfoProgramCounter OBJECT-TYPE
   SYNTAX      OCTET STRING
   MAX-ACCESS  read-only
   STATUS      current
   DESCRIPTION
      "Path: scheduler.status.taskInfo.programCounter"
   ::= {sr1646v2OsSchTaskInfoEntry 83886080}


sr1646v2OsSchCDump OBJECT IDENTIFIER ::= {sr1646v2OsSch 19}

sr1646v2OsSchCDumpSSCTable OBJECT-TYPE
   SYNTAX      SEQUENCE OF Sr1646v2OsSchCDumpEntry
   MAX-ACCESS  not-accessible
   STATUS      current
   DESCRIPTION
      "coreDump for powerPC2 Pro"
   ::= {sr1646v2OsSchCDump 1}

sr1646v2OsSchCDumpEntry OBJECT-TYPE
   SYNTAX      Sr1646v2OsSchCDumpEntry
   MAX-ACCESS  not-accessible
   STATUS      current
   DESCRIPTION
      ""
   INDEX      { sr1646v2OsSchCDumpGlobalIx }
   ::= {sr1646v2OsSchCDumpSSCTable 1}

Sr1646v2OsSchCDumpEntry ::=
   SEQUENCE
      {
      sr1646v2OsSchCDumpGlobalIx
         GlobalIndex,
      sr1646v2OsSchCDumpExStCType
         INTEGER,
      sr1646v2OsSchCDumpExStCPCnt
         OCTET STRING,
      sr1646v2OsSchCDumpExStCSpRegXER
         OCTET STRING,
      sr1646v2OsSchCDumpExStCSpRegLR
         OCTET STRING,
      sr1646v2OsSchCDumpExStCSpRegCTR
         OCTET STRING,
      sr1646v2OsSchCDumpExStCSpRegSRR0
         OCTET STRING,
      sr1646v2OsSchCDumpExStCSpRegSRR1
         OCTET STRING,
      sr1646v2OsSchCDumpExStCSpRegDAR
         OCTET STRING,
      sr1646v2OsSchCDumpExStCSpRegDSISR
         OCTET STRING,
      sr1646v2OsSchCDumpExStTName
         DisplayString,
      sr1646v2OsSchCDumpExStIntRegSIMSRh
         OCTET STRING,
      sr1646v2OsSchCDumpExStIntRegSIMSRl
         OCTET STRING,
      sr1646v2OsSchCDumpExStIntRegSEMSR
         OCTET STRING,
      sr1646v2OsSchCDumpExStIntRegSEPNR
         OCTET STRING,
      sr1646v2OsSchCDumpExStIntRegSINPRh
         OCTET STRING,
      sr1646v2OsSchCDumpExStIntRegSINPRl
         OCTET STRING,
      sr1646v2OsSchCDumpExStIntRegSICFR
         OCTET STRING,
      sr1646v2OsSchCDumpExStIntRegSIVCR
         OCTET STRING,
      sr1646v2OsSchCDumpExStArbRegAEATR
         OCTET STRING,
      sr1646v2OsSchCDumpExStArbRegAEADR
         OCTET STRING,
      sr1646v2OsSchCDumpWDogTName
         DisplayString,
      sr1646v2OsSchCDumpWDogWdAct
         OCTET STRING,
      sr1646v2OsSchCDumpWDogWdTr
         OCTET STRING,
      sr1646v2OsSchCDumpWDogTStAdd
         OCTET STRING,
      sr1646v2OsSchCDumpRebootReason
         Integer32,
      sr1646v2OsSchCDumpRebootUpTime
         TimeTicks
      }

sr1646v2OsSchCDumpGlobalIx OBJECT-TYPE
   SYNTAX      GlobalIndex
   MAX-ACCESS  not-accessible
   STATUS      current
   DESCRIPTION
      "The value of the tlsCntTreeGlobalIndex of the MANAGED OBJECT."
   ::= {sr1646v2OsSchCDumpEntry 10}

sr1646v2OsSchCDumpExStCType OBJECT-TYPE
   SYNTAX      INTEGER
               {
               res0 (0),
               sysRst (1),
               macChk (2),
               dsi (3),
               isi (4),
               extInt (5),
               align (6),
               prog (7),
               fpuUna (8),
               decr (9),
               critInt (10),
               res1 (11),
               sysCall (12),
               trace (13),
               res2 (14),
               res3 (15),
               iTLB (16),
               dTLB (17),
               dSTLB (18),
               iBrPnt (19),
               sMgm (20),
               res4 (21),
               res5 (22),
               res6 (23),
               res7 (24),
               res8 (25),
               res9 (26),
               res10 (27),
               res11 (28),
               res12 (29),
               res13 (30),
               res14 (31)
               }
   MAX-ACCESS  read-only
   STATUS      current
   DESCRIPTION
      "Path: scheduler.status.coreDump.exceptionStack.coreDump.type

       Possibilities:
               reserved   (0)
               systemReset   (1)
               machineCheck   (2)
               dsiException   (3)
               isiException   (4)
               extIntException   (5)
               alignmentException   (6)
               programException   (7)
               fluUnavailable   (8)
               decrementerException   (9)
               criticalInt   (10)
               reserved1   (11)
               systemCallException   (12)
               traceException   (13)
               reserved2   (14)
               reserved3   (15)
               instructionTranslationMiss   (16)
               dataLoadTranslationMiss   (17)
               dataStoreTranslationMiss   (18)
               instructionBreakpoint   (19)
               systemManagementInt   (20)
               reserved4   (21)
               reserved5   (22)
               reserved6   (23)
               reserved7   (24)
               reserved8   (25)
               reserved9   (26)
               reserved10   (27)
               reserved11   (28)
               reserved12   (29)
               reserved13   (30)
               reserved14   (31)"
   ::= {sr1646v2OsSchCDumpEntry 16843008}

sr1646v2OsSchCDumpExStCPCnt OBJECT-TYPE
   SYNTAX      OCTET STRING
   MAX-ACCESS  read-only
   STATUS      current
   DESCRIPTION
      "Path: scheduler.status.coreDump.exceptionStack.coreDump.programCounter"
   ::= {sr1646v2OsSchCDumpEntry 16843264}

sr1646v2OsSchCDumpExStCSpRegXER OBJECT-TYPE
   SYNTAX      OCTET STRING
   MAX-ACCESS  read-only
   STATUS      current
   DESCRIPTION
      "Path: scheduler.status.coreDump.exceptionStack.coreDump.sPRegisters.XER"
   ::= {sr1646v2OsSchCDumpEntry 16843521}

sr1646v2OsSchCDumpExStCSpRegLR OBJECT-TYPE
   SYNTAX      OCTET STRING
   MAX-ACCESS  read-only
   STATUS      current
   DESCRIPTION
      "Path: scheduler.status.coreDump.exceptionStack.coreDump.sPRegisters.LR"
   ::= {sr1646v2OsSchCDumpEntry 16843522}

sr1646v2OsSchCDumpExStCSpRegCTR OBJECT-TYPE
   SYNTAX      OCTET STRING
   MAX-ACCESS  read-only
   STATUS      current
   DESCRIPTION
      "Path: scheduler.status.coreDump.exceptionStack.coreDump.sPRegisters.CTR"
   ::= {sr1646v2OsSchCDumpEntry 16843523}

sr1646v2OsSchCDumpExStCSpRegSRR0 OBJECT-TYPE
   SYNTAX      OCTET STRING
   MAX-ACCESS  read-only
   STATUS      current
   DESCRIPTION
      "Path: scheduler.status.coreDump.exceptionStack.coreDump.sPRegisters.SRR0"
   ::= {sr1646v2OsSchCDumpEntry 16843524}

sr1646v2OsSchCDumpExStCSpRegSRR1 OBJECT-TYPE
   SYNTAX      OCTET STRING
   MAX-ACCESS  read-only
   STATUS      current
   DESCRIPTION
      "Path: scheduler.status.coreDump.exceptionStack.coreDump.sPRegisters.SRR1"
   ::= {sr1646v2OsSchCDumpEntry 16843525}

sr1646v2OsSchCDumpExStCSpRegDAR OBJECT-TYPE
   SYNTAX      OCTET STRING
   MAX-ACCESS  read-only
   STATUS      current
   DESCRIPTION
      "Path: scheduler.status.coreDump.exceptionStack.coreDump.sPRegisters.DAR"
   ::= {sr1646v2OsSchCDumpEntry 16843526}

sr1646v2OsSchCDumpExStCSpRegDSISR OBJECT-TYPE
   SYNTAX      OCTET STRING
   MAX-ACCESS  read-only
   STATUS      current
   DESCRIPTION
      "Path: scheduler.status.coreDump.exceptionStack.coreDump.sPRegisters.DSISR"
   ::= {sr1646v2OsSchCDumpEntry 16843527}

sr1646v2OsSchCDumpExStTName OBJECT-TYPE
   SYNTAX      DisplayString
   MAX-ACCESS  read-only
   STATUS      current
   DESCRIPTION
      "Path: scheduler.status.coreDump.exceptionStack.currentTaskName"
   ::= {sr1646v2OsSchCDumpEntry 16908288}

sr1646v2OsSchCDumpExStIntRegSIMSRh OBJECT-TYPE
   SYNTAX      OCTET STRING
   MAX-ACCESS  read-only
   STATUS      current
   DESCRIPTION
      "Path: scheduler.status.coreDump.exceptionStack.interruptRegisters.SIMSRh"
   ::= {sr1646v2OsSchCDumpEntry 17105152}

sr1646v2OsSchCDumpExStIntRegSIMSRl OBJECT-TYPE
   SYNTAX      OCTET STRING
   MAX-ACCESS  read-only
   STATUS      current
   DESCRIPTION
      "Path: scheduler.status.coreDump.exceptionStack.interruptRegisters.SIMSRl"
   ::= {sr1646v2OsSchCDumpEntry 17105408}

sr1646v2OsSchCDumpExStIntRegSEMSR OBJECT-TYPE
   SYNTAX      OCTET STRING
   MAX-ACCESS  read-only
   STATUS      current
   DESCRIPTION
      "Path: scheduler.status.coreDump.exceptionStack.interruptRegisters.SEMSR"
   ::= {sr1646v2OsSchCDumpEntry 17105664}

sr1646v2OsSchCDumpExStIntRegSEPNR OBJECT-TYPE
   SYNTAX      OCTET STRING
   MAX-ACCESS  read-only
   STATUS      current
   DESCRIPTION
      "Path: scheduler.status.coreDump.exceptionStack.interruptRegisters.SEPNR"
   ::= {sr1646v2OsSchCDumpEntry 17105920}

sr1646v2OsSchCDumpExStIntRegSINPRh OBJECT-TYPE
   SYNTAX      OCTET STRING
   MAX-ACCESS  read-only
   STATUS      current
   DESCRIPTION
      "Path: scheduler.status.coreDump.exceptionStack.interruptRegisters.SINPRh"
   ::= {sr1646v2OsSchCDumpEntry 17106176}

sr1646v2OsSchCDumpExStIntRegSINPRl OBJECT-TYPE
   SYNTAX      OCTET STRING
   MAX-ACCESS  read-only
   STATUS      current
   DESCRIPTION
      "Path: scheduler.status.coreDump.exceptionStack.interruptRegisters.SINPRl"
   ::= {sr1646v2OsSchCDumpEntry 17106432}

sr1646v2OsSchCDumpExStIntRegSICFR OBJECT-TYPE
   SYNTAX      OCTET STRING
   MAX-ACCESS  read-only
   STATUS      current
   DESCRIPTION
      "Path: scheduler.status.coreDump.exceptionStack.interruptRegisters.SICFR"
   ::= {sr1646v2OsSchCDumpEntry 17106688}

sr1646v2OsSchCDumpExStIntRegSIVCR OBJECT-TYPE
   SYNTAX      OCTET STRING
   MAX-ACCESS  read-only
   STATUS      current
   DESCRIPTION
      "Path: scheduler.status.coreDump.exceptionStack.interruptRegisters.SIVCR"
   ::= {sr1646v2OsSchCDumpEntry 17106944}

sr1646v2OsSchCDumpExStArbRegAEATR OBJECT-TYPE
   SYNTAX      OCTET STRING
   MAX-ACCESS  read-only
   STATUS      current
   DESCRIPTION
      "Path: scheduler.status.coreDump.exceptionStack.arbiterRegisters.AEATR"
   ::= {sr1646v2OsSchCDumpEntry 17170688}

sr1646v2OsSchCDumpExStArbRegAEADR OBJECT-TYPE
   SYNTAX      OCTET STRING
   MAX-ACCESS  read-only
   STATUS      current
   DESCRIPTION
      "Path: scheduler.status.coreDump.exceptionStack.arbiterRegisters.AEADR"
   ::= {sr1646v2OsSchCDumpEntry 17170944}

sr1646v2OsSchCDumpWDogTName OBJECT-TYPE
   SYNTAX      DisplayString
   MAX-ACCESS  read-only
   STATUS      current
   DESCRIPTION
      "Path: scheduler.status.coreDump.watchDog.taskName"
   ::= {sr1646v2OsSchCDumpEntry 50397184}

sr1646v2OsSchCDumpWDogWdAct OBJECT-TYPE
   SYNTAX      OCTET STRING
   MAX-ACCESS  read-only
   STATUS      current
   DESCRIPTION
      "Path: scheduler.status.coreDump.watchDog.watchdogActive"
   ::= {sr1646v2OsSchCDumpEntry 50462720}

sr1646v2OsSchCDumpWDogWdTr OBJECT-TYPE
   SYNTAX      OCTET STRING
   MAX-ACCESS  read-only
   STATUS      current
   DESCRIPTION
      "Path: scheduler.status.coreDump.watchDog.watchdogTrigger"
   ::= {sr1646v2OsSchCDumpEntry 50528256}

sr1646v2OsSchCDumpWDogTStAdd OBJECT-TYPE
   SYNTAX      OCTET STRING
   MAX-ACCESS  read-only
   STATUS      current
   DESCRIPTION
      "Path: scheduler.status.coreDump.watchDog.taskStackAddress"
   ::= {sr1646v2OsSchCDumpEntry 50790400}

sr1646v2OsSchCDumpRebootReason OBJECT-TYPE
   SYNTAX      Integer32
   MAX-ACCESS  read-only
   STATUS      current
   DESCRIPTION
      "Path: scheduler.status.coreDump.reboot.reason

       Bit meanings:
               bit 27 = scheduled,
               bit 26 = warmBoot,
               bit 25 = coldBoot,
               bit 24 = powerDown,
               bit 22 = codeCheck,
               bit 21 = configCheck,
               bit 20 = coreDump"
   ::= {sr1646v2OsSchCDumpEntry 671154176}

sr1646v2OsSchCDumpRebootUpTime OBJECT-TYPE
   SYNTAX      TimeTicks
   MAX-ACCESS  read-only
   STATUS      current
   DESCRIPTION
      "Path: scheduler.status.coreDump.reboot.upTime

       Time in centi-second."
   ::= {sr1646v2OsSchCDumpEntry 671219712}

sr1646v2OsSchCDumpExStStInf OBJECT-TYPE
   SYNTAX      SEQUENCE OF Sr1646v2OsSchCDumpExStStInfEntry
   MAX-ACCESS  not-accessible
   STATUS      current
   DESCRIPTION
      ""
   ::= {sr1646v2OsSchCDump 16973824}

sr1646v2OsSchCDumpExStStInfEntry OBJECT-TYPE
   SYNTAX      Sr1646v2OsSchCDumpExStStInfEntry
   MAX-ACCESS  not-accessible
   STATUS      current
   DESCRIPTION
      ""
   INDEX      { sr1646v2OsSchCDumpExStStInfGlobalIx,
                sr1646v2OsSchCDumpExStStInfTableIx }
   ::= {sr1646v2OsSchCDumpExStStInf 1}

Sr1646v2OsSchCDumpExStStInfEntry ::=
   SEQUENCE
      {
      sr1646v2OsSchCDumpExStStInfGlobalIx
         GlobalIndex,
      sr1646v2OsSchCDumpExStStInfTableIx
         TableIndex,
      sr1646v2OsSchCDumpExStStInfRow
         OCTET STRING
      }

sr1646v2OsSchCDumpExStStInfGlobalIx OBJECT-TYPE
   SYNTAX      GlobalIndex
   MAX-ACCESS  not-accessible
   STATUS      current
   DESCRIPTION
      "The value of the tlsCntTreeGlobalIndex of the MANAGED OBJECT."
   ::= {sr1646v2OsSchCDumpExStStInfEntry 10}

sr1646v2OsSchCDumpExStStInfTableIx OBJECT-TYPE
   SYNTAX      TableIndex
   MAX-ACCESS  not-accessible
   STATUS      current
   DESCRIPTION
      ""
   ::= {sr1646v2OsSchCDumpExStStInfEntry 11}

sr1646v2OsSchCDumpExStStInfRow OBJECT-TYPE
   SYNTAX      OCTET STRING
   MAX-ACCESS  read-only
   STATUS      current
   DESCRIPTION
      "Path: scheduler.status.coreDump.exceptionStack.currentStack.row"
   ::= {sr1646v2OsSchCDumpExStStInfEntry 16777216}

sr1646v2OsSchCDumpExStReg OBJECT-TYPE
   SYNTAX      SEQUENCE OF Sr1646v2OsSchCDumpExStRegEntry
   MAX-ACCESS  not-accessible
   STATUS      current
   DESCRIPTION
      ""
   ::= {sr1646v2OsSchCDump 17039360}

sr1646v2OsSchCDumpExStRegEntry OBJECT-TYPE
   SYNTAX      Sr1646v2OsSchCDumpExStRegEntry
   MAX-ACCESS  not-accessible
   STATUS      current
   DESCRIPTION
      ""
   INDEX      { sr1646v2OsSchCDumpExStRegGlobalIx,
                sr1646v2OsSchCDumpExStRegTableIx }
   ::= {sr1646v2OsSchCDumpExStReg 1}

Sr1646v2OsSchCDumpExStRegEntry ::=
   SEQUENCE
      {
      sr1646v2OsSchCDumpExStRegGlobalIx
         GlobalIndex,
      sr1646v2OsSchCDumpExStRegTableIx
         TableIndex,
      sr1646v2OsSchCDumpExStRegGPR0uGPR31
         OCTET STRING
      }

sr1646v2OsSchCDumpExStRegGlobalIx OBJECT-TYPE
   SYNTAX      GlobalIndex
   MAX-ACCESS  not-accessible
   STATUS      current
   DESCRIPTION
      "The value of the tlsCntTreeGlobalIndex of the MANAGED OBJECT."
   ::= {sr1646v2OsSchCDumpExStRegEntry 10}

sr1646v2OsSchCDumpExStRegTableIx OBJECT-TYPE
   SYNTAX      TableIndex
   MAX-ACCESS  not-accessible
   STATUS      current
   DESCRIPTION
      ""
   ::= {sr1646v2OsSchCDumpExStRegEntry 11}

sr1646v2OsSchCDumpExStRegGPR0uGPR31 OBJECT-TYPE
   SYNTAX      OCTET STRING
   MAX-ACCESS  read-only
   STATUS      current
   DESCRIPTION
      "Path: scheduler.status.coreDump.exceptionStack.gPRegisters.GPR0_GPR31"
   ::= {sr1646v2OsSchCDumpExStRegEntry 16777216}

sr1646v2OsSchCDumpExStSreg OBJECT-TYPE
   SYNTAX      SEQUENCE OF Sr1646v2OsSchCDumpExStSregEntry
   MAX-ACCESS  not-accessible
   STATUS      current
   DESCRIPTION
      ""
   ::= {sr1646v2OsSchCDump 17235968}

sr1646v2OsSchCDumpExStSregEntry OBJECT-TYPE
   SYNTAX      Sr1646v2OsSchCDumpExStSregEntry
   MAX-ACCESS  not-accessible
   STATUS      current
   DESCRIPTION
      ""
   INDEX      { sr1646v2OsSchCDumpExStSregGlobalIx,
                sr1646v2OsSchCDumpExStSregTableIx }
   ::= {sr1646v2OsSchCDumpExStSreg 1}

Sr1646v2OsSchCDumpExStSregEntry ::=
   SEQUENCE
      {
      sr1646v2OsSchCDumpExStSregGlobalIx
         GlobalIndex,
      sr1646v2OsSchCDumpExStSregTableIx
         TableIndex,
      sr1646v2OsSchCDumpExStSregSPR0uSPR7
         OCTET STRING
      }

sr1646v2OsSchCDumpExStSregGlobalIx OBJECT-TYPE
   SYNTAX      GlobalIndex
   MAX-ACCESS  not-accessible
   STATUS      current
   DESCRIPTION
      "The value of the tlsCntTreeGlobalIndex of the MANAGED OBJECT."
   ::= {sr1646v2OsSchCDumpExStSregEntry 10}

sr1646v2OsSchCDumpExStSregTableIx OBJECT-TYPE
   SYNTAX      TableIndex
   MAX-ACCESS  not-accessible
   STATUS      current
   DESCRIPTION
      ""
   ::= {sr1646v2OsSchCDumpExStSregEntry 11}

sr1646v2OsSchCDumpExStSregSPR0uSPR7 OBJECT-TYPE
   SYNTAX      OCTET STRING
   MAX-ACCESS  read-only
   STATUS      current
   DESCRIPTION
      "Path: scheduler.status.coreDump.exceptionStack.sPRegisters.SPR0_SPR7"
   ::= {sr1646v2OsSchCDumpExStSregEntry 16777216}

sr1646v2OsSchCDumpExStCStck OBJECT-TYPE
   SYNTAX      SEQUENCE OF Sr1646v2OsSchCDumpExStCStckEntry
   MAX-ACCESS  not-accessible
   STATUS      current
   DESCRIPTION
      ""
   ::= {sr1646v2OsSchCDump 17301504}

sr1646v2OsSchCDumpExStCStckEntry OBJECT-TYPE
   SYNTAX      Sr1646v2OsSchCDumpExStCStckEntry
   MAX-ACCESS  not-accessible
   STATUS      current
   DESCRIPTION
      ""
   INDEX      { sr1646v2OsSchCDumpExStCStckGlobalIx,
                sr1646v2OsSchCDumpExStCStckTableIx }
   ::= {sr1646v2OsSchCDumpExStCStck 1}

Sr1646v2OsSchCDumpExStCStckEntry ::=
   SEQUENCE
      {
      sr1646v2OsSchCDumpExStCStckGlobalIx
         GlobalIndex,
      sr1646v2OsSchCDumpExStCStckTableIx
         TableIndex,
      sr1646v2OsSchCDumpExStCStckRow
         DisplayString
      }

sr1646v2OsSchCDumpExStCStckGlobalIx OBJECT-TYPE
   SYNTAX      GlobalIndex
   MAX-ACCESS  not-accessible
   STATUS      current
   DESCRIPTION
      "The value of the tlsCntTreeGlobalIndex of the MANAGED OBJECT."
   ::= {sr1646v2OsSchCDumpExStCStckEntry 10}

sr1646v2OsSchCDumpExStCStckTableIx OBJECT-TYPE
   SYNTAX      TableIndex
   MAX-ACCESS  not-accessible
   STATUS      current
   DESCRIPTION
      ""
   ::= {sr1646v2OsSchCDumpExStCStckEntry 11}

sr1646v2OsSchCDumpExStCStckRow OBJECT-TYPE
   SYNTAX      DisplayString
   MAX-ACCESS  read-only
   STATUS      current
   DESCRIPTION
      "Path: scheduler.status.coreDump.exceptionStack.callingStack.row"
   ::= {sr1646v2OsSchCDumpExStCStckEntry 16777216}

sr1646v2OsSchCDumpWDogTStInf OBJECT-TYPE
   SYNTAX      SEQUENCE OF Sr1646v2OsSchCDumpWDogTStInfEntry
   MAX-ACCESS  not-accessible
   STATUS      current
   DESCRIPTION
      ""
   ::= {sr1646v2OsSchCDump 50659328}

sr1646v2OsSchCDumpWDogTStInfEntry OBJECT-TYPE
   SYNTAX      Sr1646v2OsSchCDumpWDogTStInfEntry
   MAX-ACCESS  not-accessible
   STATUS      current
   DESCRIPTION
      ""
   INDEX      { sr1646v2OsSchCDumpWDogTStInfGlobalIx,
                sr1646v2OsSchCDumpWDogTStInfTableIx }
   ::= {sr1646v2OsSchCDumpWDogTStInf 1}

Sr1646v2OsSchCDumpWDogTStInfEntry ::=
   SEQUENCE
      {
      sr1646v2OsSchCDumpWDogTStInfGlobalIx
         GlobalIndex,
      sr1646v2OsSchCDumpWDogTStInfTableIx
         TableIndex,
      sr1646v2OsSchCDumpWDogTStInfRow
         OCTET STRING
      }

sr1646v2OsSchCDumpWDogTStInfGlobalIx OBJECT-TYPE
   SYNTAX      GlobalIndex
   MAX-ACCESS  not-accessible
   STATUS      current
   DESCRIPTION
      "The value of the tlsCntTreeGlobalIndex of the MANAGED OBJECT."
   ::= {sr1646v2OsSchCDumpWDogTStInfEntry 10}

sr1646v2OsSchCDumpWDogTStInfTableIx OBJECT-TYPE
   SYNTAX      TableIndex
   MAX-ACCESS  not-accessible
   STATUS      current
   DESCRIPTION
      ""
   ::= {sr1646v2OsSchCDumpWDogTStInfEntry 11}

sr1646v2OsSchCDumpWDogTStInfRow OBJECT-TYPE
   SYNTAX      OCTET STRING
   MAX-ACCESS  read-only
   STATUS      current
   DESCRIPTION
      "Path: scheduler.status.coreDump.watchDog.taskStackInfo.row"
   ::= {sr1646v2OsSchCDumpWDogTStInfEntry 16777216}

sr1646v2OsSchCDumpWDogCStck OBJECT-TYPE
   SYNTAX      SEQUENCE OF Sr1646v2OsSchCDumpWDogCStckEntry
   MAX-ACCESS  not-accessible
   STATUS      current
   DESCRIPTION
      ""
   ::= {sr1646v2OsSchCDump 50724864}

sr1646v2OsSchCDumpWDogCStckEntry OBJECT-TYPE
   SYNTAX      Sr1646v2OsSchCDumpWDogCStckEntry
   MAX-ACCESS  not-accessible
   STATUS      current
   DESCRIPTION
      ""
   INDEX      { sr1646v2OsSchCDumpWDogCStckGlobalIx,
                sr1646v2OsSchCDumpWDogCStckTableIx }
   ::= {sr1646v2OsSchCDumpWDogCStck 1}

Sr1646v2OsSchCDumpWDogCStckEntry ::=
   SEQUENCE
      {
      sr1646v2OsSchCDumpWDogCStckGlobalIx
         GlobalIndex,
      sr1646v2OsSchCDumpWDogCStckTableIx
         TableIndex,
      sr1646v2OsSchCDumpWDogCStckRow
         DisplayString
      }

sr1646v2OsSchCDumpWDogCStckGlobalIx OBJECT-TYPE
   SYNTAX      GlobalIndex
   MAX-ACCESS  not-accessible
   STATUS      current
   DESCRIPTION
      "The value of the tlsCntTreeGlobalIndex of the MANAGED OBJECT."
   ::= {sr1646v2OsSchCDumpWDogCStckEntry 10}

sr1646v2OsSchCDumpWDogCStckTableIx OBJECT-TYPE
   SYNTAX      TableIndex
   MAX-ACCESS  not-accessible
   STATUS      current
   DESCRIPTION
      ""
   ::= {sr1646v2OsSchCDumpWDogCStckEntry 11}

sr1646v2OsSchCDumpWDogCStckRow OBJECT-TYPE
   SYNTAX      DisplayString
   MAX-ACCESS  read-only
   STATUS      current
   DESCRIPTION
      "Path: scheduler.status.coreDump.watchDog.callingStack.row"
   ::= {sr1646v2OsSchCDumpWDogCStckEntry 16777216}


sr1646v2OsSchSnmpIndex OBJECT IDENTIFIER ::= {sr1646v2OsSch 269}

sr1646v2OsSchSnmpIndexTable OBJECT-TYPE
   SYNTAX      SEQUENCE OF Sr1646v2OsSchSnmpIndexEntry
   MAX-ACCESS  not-accessible
   STATUS      current
   DESCRIPTION
      "SNMP index assigned to this object"
   ::= {sr1646v2OsSchSnmpIndex 1}

sr1646v2OsSchSnmpIndexEntry OBJECT-TYPE
   SYNTAX      Sr1646v2OsSchSnmpIndexEntry
   MAX-ACCESS  not-accessible
   STATUS      current
   DESCRIPTION
      ""
   INDEX      { sr1646v2OsSchSnmpIndexGlobalIx }
   ::= {sr1646v2OsSchSnmpIndexTable 1}

Sr1646v2OsSchSnmpIndexEntry ::=
   SEQUENCE
      {
      sr1646v2OsSchSnmpIndexGlobalIx
         GlobalIndex,
      sr1646v2OsSchSnmpIndexValue
         Integer32
      }

sr1646v2OsSchSnmpIndexGlobalIx OBJECT-TYPE
   SYNTAX      GlobalIndex
   MAX-ACCESS  not-accessible
   STATUS      current
   DESCRIPTION
      "The value of the tlsCntTreeGlobalIndex of the MANAGED OBJECT."
   ::= {sr1646v2OsSchSnmpIndexEntry 10}

sr1646v2OsSchSnmpIndexValue OBJECT-TYPE
   SYNTAX      Integer32
   MAX-ACCESS  read-only
   STATUS      current
   DESCRIPTION
      "Path: scheduler.status.snmpIndex"
   ::= {sr1646v2OsSchSnmpIndexEntry 2147483648}



ar1646v2OsSch OBJECT IDENTIFIER ::= {r1646v2OsSch 16}


ar1646v2OsSchClearICCounters OBJECT IDENTIFIER ::= {ar1646v2OsSch 57}

ar1646v2OsSchClearICCountersTable OBJECT-TYPE
   SYNTAX      SEQUENCE OF Ar1646v2OsSchClearICCountersEntry
   MAX-ACCESS  not-accessible
   STATUS      current
   DESCRIPTION
      "reset counters"
   ::= {ar1646v2OsSchClearICCounters 1}

ar1646v2OsSchClearICCountersEntry OBJECT-TYPE
   SYNTAX      Ar1646v2OsSchClearICCountersEntry
   MAX-ACCESS  not-accessible
   STATUS      current
   DESCRIPTION
      ""
   INDEX      { ar1646v2OsSchClearICCountersGlobalIx }
   ::= {ar1646v2OsSchClearICCountersTable 1}

Ar1646v2OsSchClearICCountersEntry ::=
   SEQUENCE
      {
      ar1646v2OsSchClearICCountersGlobalIx
         GlobalIndex,
      ar1646v2OsSchClearICCountersValue
         Integer32
      }

ar1646v2OsSchClearICCountersGlobalIx OBJECT-TYPE
   SYNTAX      GlobalIndex
   MAX-ACCESS  not-accessible
   STATUS      current
   DESCRIPTION
      "The value of the tlsCntTreeGlobalIndex of the MANAGED OBJECT."
   ::= {ar1646v2OsSchClearICCountersEntry 10}

ar1646v2OsSchClearICCountersValue OBJECT-TYPE
   SYNTAX      Integer32
   MAX-ACCESS  read-write
   STATUS      current
   DESCRIPTION
      "Path: scheduler.actions.clearICCounters"
   ::= {ar1646v2OsSchClearICCountersEntry 2147483648}


ar1646v2OsSchCheckFreeStack OBJECT IDENTIFIER ::= {ar1646v2OsSch 56}

ar1646v2OsSchCheckFreeStackTable OBJECT-TYPE
   SYNTAX      SEQUENCE OF Ar1646v2OsSchCheckFreeStackEntry
   MAX-ACCESS  not-accessible
   STATUS      current
   DESCRIPTION
      "general purpose counter configuration"
   ::= {ar1646v2OsSchCheckFreeStack 1}

ar1646v2OsSchCheckFreeStackEntry OBJECT-TYPE
   SYNTAX      Ar1646v2OsSchCheckFreeStackEntry
   MAX-ACCESS  not-accessible
   STATUS      current
   DESCRIPTION
      ""
   INDEX      { ar1646v2OsSchCheckFreeStackGlobalIx }
   ::= {ar1646v2OsSchCheckFreeStackTable 1}

Ar1646v2OsSchCheckFreeStackEntry ::=
   SEQUENCE
      {
      ar1646v2OsSchCheckFreeStackGlobalIx
         GlobalIndex,
      ar1646v2OsSchCheckFreeStackValue
         Counter32
      }

ar1646v2OsSchCheckFreeStackGlobalIx OBJECT-TYPE
   SYNTAX      GlobalIndex
   MAX-ACCESS  not-accessible
   STATUS      current
   DESCRIPTION
      "The value of the tlsCntTreeGlobalIndex of the MANAGED OBJECT."
   ::= {ar1646v2OsSchCheckFreeStackEntry 10}

ar1646v2OsSchCheckFreeStackValue OBJECT-TYPE
   SYNTAX      Counter32
   MAX-ACCESS  read-write
   STATUS      current
   DESCRIPTION
      "Path: scheduler.actions.checkFreeStack

       32 bit unsigned wrappable counter."
   ::= {ar1646v2OsSchCheckFreeStackEntry 2147483648}


ar1646v2OsSchNoFillMemory OBJECT IDENTIFIER ::= {ar1646v2OsSch 53}

ar1646v2OsSchNoFillMemoryTable OBJECT-TYPE
   SYNTAX      SEQUENCE OF Ar1646v2OsSchNoFillMemoryEntry
   MAX-ACCESS  not-accessible
   STATUS      current
   DESCRIPTION
      "general purpose counter configuration"
   ::= {ar1646v2OsSchNoFillMemory 1}

ar1646v2OsSchNoFillMemoryEntry OBJECT-TYPE
   SYNTAX      Ar1646v2OsSchNoFillMemoryEntry
   MAX-ACCESS  not-accessible
   STATUS      current
   DESCRIPTION
      ""
   INDEX      { ar1646v2OsSchNoFillMemoryGlobalIx }
   ::= {ar1646v2OsSchNoFillMemoryTable 1}

Ar1646v2OsSchNoFillMemoryEntry ::=
   SEQUENCE
      {
      ar1646v2OsSchNoFillMemoryGlobalIx
         GlobalIndex,
      ar1646v2OsSchNoFillMemoryValue
         Counter32
      }

ar1646v2OsSchNoFillMemoryGlobalIx OBJECT-TYPE
   SYNTAX      GlobalIndex
   MAX-ACCESS  not-accessible
   STATUS      current
   DESCRIPTION
      "The value of the tlsCntTreeGlobalIndex of the MANAGED OBJECT."
   ::= {ar1646v2OsSchNoFillMemoryEntry 10}

ar1646v2OsSchNoFillMemoryValue OBJECT-TYPE
   SYNTAX      Counter32
   MAX-ACCESS  read-write
   STATUS      current
   DESCRIPTION
      "Path: scheduler.actions.noFillMemory

       32 bit unsigned wrappable counter."
   ::= {ar1646v2OsSchNoFillMemoryEntry 2147483648}


ar1646v2OsSchFillMemory OBJECT IDENTIFIER ::= {ar1646v2OsSch 52}

ar1646v2OsSchFillMemoryTable OBJECT-TYPE
   SYNTAX      SEQUENCE OF Ar1646v2OsSchFillMemoryEntry
   MAX-ACCESS  not-accessible
   STATUS      current
   DESCRIPTION
      "general purpose counter configuration"
   ::= {ar1646v2OsSchFillMemory 1}

ar1646v2OsSchFillMemoryEntry OBJECT-TYPE
   SYNTAX      Ar1646v2OsSchFillMemoryEntry
   MAX-ACCESS  not-accessible
   STATUS      current
   DESCRIPTION
      ""
   INDEX      { ar1646v2OsSchFillMemoryGlobalIx }
   ::= {ar1646v2OsSchFillMemoryTable 1}

Ar1646v2OsSchFillMemoryEntry ::=
   SEQUENCE
      {
      ar1646v2OsSchFillMemoryGlobalIx
         GlobalIndex,
      ar1646v2OsSchFillMemoryValue
         Counter32
      }

ar1646v2OsSchFillMemoryGlobalIx OBJECT-TYPE
   SYNTAX      GlobalIndex
   MAX-ACCESS  not-accessible
   STATUS      current
   DESCRIPTION
      "The value of the tlsCntTreeGlobalIndex of the MANAGED OBJECT."
   ::= {ar1646v2OsSchFillMemoryEntry 10}

ar1646v2OsSchFillMemoryValue OBJECT-TYPE
   SYNTAX      Counter32
   MAX-ACCESS  read-write
   STATUS      current
   DESCRIPTION
      "Path: scheduler.actions.fillMemory

       32 bit unsigned wrappable counter."
   ::= {ar1646v2OsSchFillMemoryEntry 2147483648}


ar1646v2OsSchStopMbufAllocLoss OBJECT IDENTIFIER ::= {ar1646v2OsSch 55}

ar1646v2OsSchStopMbufAllocLossTable OBJECT-TYPE
   SYNTAX      SEQUENCE OF Ar1646v2OsSchStopMbufAllocLossEntry
   MAX-ACCESS  not-accessible
   STATUS      current
   DESCRIPTION
      "general purpose counter configuration"
   ::= {ar1646v2OsSchStopMbufAllocLoss 1}

ar1646v2OsSchStopMbufAllocLossEntry OBJECT-TYPE
   SYNTAX      Ar1646v2OsSchStopMbufAllocLossEntry
   MAX-ACCESS  not-accessible
   STATUS      current
   DESCRIPTION
      ""
   INDEX      { ar1646v2OsSchStopMbufAllocLossGlobalIx }
   ::= {ar1646v2OsSchStopMbufAllocLossTable 1}

Ar1646v2OsSchStopMbufAllocLossEntry ::=
   SEQUENCE
      {
      ar1646v2OsSchStopMbufAllocLossGlobalIx
         GlobalIndex,
      ar1646v2OsSchStopMbufAllocLossValue
         Counter32
      }

ar1646v2OsSchStopMbufAllocLossGlobalIx OBJECT-TYPE
   SYNTAX      GlobalIndex
   MAX-ACCESS  not-accessible
   STATUS      current
   DESCRIPTION
      "The value of the tlsCntTreeGlobalIndex of the MANAGED OBJECT."
   ::= {ar1646v2OsSchStopMbufAllocLossEntry 10}

ar1646v2OsSchStopMbufAllocLossValue OBJECT-TYPE
   SYNTAX      Counter32
   MAX-ACCESS  read-write
   STATUS      current
   DESCRIPTION
      "Path: scheduler.actions.stopMbufAllocLoss

       32 bit unsigned wrappable counter."
   ::= {ar1646v2OsSchStopMbufAllocLossEntry 2147483648}


ar1646v2OsSchStartMbufAllocLoss OBJECT IDENTIFIER ::= {ar1646v2OsSch 54}

ar1646v2OsSchStartMbufAllocLossTable OBJECT-TYPE
   SYNTAX      SEQUENCE OF Ar1646v2OsSchStartMbufAllocLossEntry
   MAX-ACCESS  not-accessible
   STATUS      current
   DESCRIPTION
      "general purpose counter configuration"
   ::= {ar1646v2OsSchStartMbufAllocLoss 1}

ar1646v2OsSchStartMbufAllocLossEntry OBJECT-TYPE
   SYNTAX      Ar1646v2OsSchStartMbufAllocLossEntry
   MAX-ACCESS  not-accessible
   STATUS      current
   DESCRIPTION
      ""
   INDEX      { ar1646v2OsSchStartMbufAllocLossGlobalIx }
   ::= {ar1646v2OsSchStartMbufAllocLossTable 1}

Ar1646v2OsSchStartMbufAllocLossEntry ::=
   SEQUENCE
      {
      ar1646v2OsSchStartMbufAllocLossGlobalIx
         GlobalIndex,
      ar1646v2OsSchStartMbufAllocLossValue
         Counter32
      }

ar1646v2OsSchStartMbufAllocLossGlobalIx OBJECT-TYPE
   SYNTAX      GlobalIndex
   MAX-ACCESS  not-accessible
   STATUS      current
   DESCRIPTION
      "The value of the tlsCntTreeGlobalIndex of the MANAGED OBJECT."
   ::= {ar1646v2OsSchStartMbufAllocLossEntry 10}

ar1646v2OsSchStartMbufAllocLossValue OBJECT-TYPE
   SYNTAX      Counter32
   MAX-ACCESS  read-write
   STATUS      current
   DESCRIPTION
      "Path: scheduler.actions.startMbufAllocLoss

       32 bit unsigned wrappable counter."
   ::= {ar1646v2OsSchStartMbufAllocLossEntry 2147483648}


ar1646v2OsSchStopMemAllocLoss OBJECT IDENTIFIER ::= {ar1646v2OsSch 51}

ar1646v2OsSchStopMemAllocLossTable OBJECT-TYPE
   SYNTAX      SEQUENCE OF Ar1646v2OsSchStopMemAllocLossEntry
   MAX-ACCESS  not-accessible
   STATUS      current
   DESCRIPTION
      "general purpose counter configuration"
   ::= {ar1646v2OsSchStopMemAllocLoss 1}

ar1646v2OsSchStopMemAllocLossEntry OBJECT-TYPE
   SYNTAX      Ar1646v2OsSchStopMemAllocLossEntry
   MAX-ACCESS  not-accessible
   STATUS      current
   DESCRIPTION
      ""
   INDEX      { ar1646v2OsSchStopMemAllocLossGlobalIx }
   ::= {ar1646v2OsSchStopMemAllocLossTable 1}

Ar1646v2OsSchStopMemAllocLossEntry ::=
   SEQUENCE
      {
      ar1646v2OsSchStopMemAllocLossGlobalIx
         GlobalIndex,
      ar1646v2OsSchStopMemAllocLossValue
         Counter32
      }

ar1646v2OsSchStopMemAllocLossGlobalIx OBJECT-TYPE
   SYNTAX      GlobalIndex
   MAX-ACCESS  not-accessible
   STATUS      current
   DESCRIPTION
      "The value of the tlsCntTreeGlobalIndex of the MANAGED OBJECT."
   ::= {ar1646v2OsSchStopMemAllocLossEntry 10}

ar1646v2OsSchStopMemAllocLossValue OBJECT-TYPE
   SYNTAX      Counter32
   MAX-ACCESS  read-write
   STATUS      current
   DESCRIPTION
      "Path: scheduler.actions.stopMemAllocLoss

       32 bit unsigned wrappable counter."
   ::= {ar1646v2OsSchStopMemAllocLossEntry 2147483648}


ar1646v2OsSchStartMemAllocLoss OBJECT IDENTIFIER ::= {ar1646v2OsSch 50}

ar1646v2OsSchStartMemAllocLossTable OBJECT-TYPE
   SYNTAX      SEQUENCE OF Ar1646v2OsSchStartMemAllocLossEntry
   MAX-ACCESS  not-accessible
   STATUS      current
   DESCRIPTION
      "general purpose counter configuration"
   ::= {ar1646v2OsSchStartMemAllocLoss 1}

ar1646v2OsSchStartMemAllocLossEntry OBJECT-TYPE
   SYNTAX      Ar1646v2OsSchStartMemAllocLossEntry
   MAX-ACCESS  not-accessible
   STATUS      current
   DESCRIPTION
      ""
   INDEX      { ar1646v2OsSchStartMemAllocLossGlobalIx }
   ::= {ar1646v2OsSchStartMemAllocLossTable 1}

Ar1646v2OsSchStartMemAllocLossEntry ::=
   SEQUENCE
      {
      ar1646v2OsSchStartMemAllocLossGlobalIx
         GlobalIndex,
      ar1646v2OsSchStartMemAllocLossValue
         Counter32
      }

ar1646v2OsSchStartMemAllocLossGlobalIx OBJECT-TYPE
   SYNTAX      GlobalIndex
   MAX-ACCESS  not-accessible
   STATUS      current
   DESCRIPTION
      "The value of the tlsCntTreeGlobalIndex of the MANAGED OBJECT."
   ::= {ar1646v2OsSchStartMemAllocLossEntry 10}

ar1646v2OsSchStartMemAllocLossValue OBJECT-TYPE
   SYNTAX      Counter32
   MAX-ACCESS  read-write
   STATUS      current
   DESCRIPTION
      "Path: scheduler.actions.startMemAllocLoss

       32 bit unsigned wrappable counter."
   ::= {ar1646v2OsSchStartMemAllocLossEntry 2147483648}


ar1646v2OsSchTriggerCoredump OBJECT IDENTIFIER ::= {ar1646v2OsSch 800}

ar1646v2OsSchTriggerCoredumpTable OBJECT-TYPE
   SYNTAX      SEQUENCE OF Ar1646v2OsSchTriggerCoredumpEntry
   MAX-ACCESS  not-accessible
   STATUS      current
   DESCRIPTION
      "Trigger Coredump"
   ::= {ar1646v2OsSchTriggerCoredump 1}

ar1646v2OsSchTriggerCoredumpEntry OBJECT-TYPE
   SYNTAX      Ar1646v2OsSchTriggerCoredumpEntry
   MAX-ACCESS  not-accessible
   STATUS      current
   DESCRIPTION
      ""
   INDEX      { ar1646v2OsSchTriggerCoredumpGlobalIx }
   ::= {ar1646v2OsSchTriggerCoredumpTable 1}

Ar1646v2OsSchTriggerCoredumpEntry ::=
   SEQUENCE
      {
      ar1646v2OsSchTriggerCoredumpGlobalIx
         GlobalIndex,
      ar1646v2OsSchTriggerCoredumpValue
         Integer32
      }

ar1646v2OsSchTriggerCoredumpGlobalIx OBJECT-TYPE
   SYNTAX      GlobalIndex
   MAX-ACCESS  not-accessible
   STATUS      current
   DESCRIPTION
      "The value of the tlsCntTreeGlobalIndex of the MANAGED OBJECT."
   ::= {ar1646v2OsSchTriggerCoredumpEntry 10}

ar1646v2OsSchTriggerCoredumpValue OBJECT-TYPE
   SYNTAX      Integer32
   MAX-ACCESS  read-write
   STATUS      current
   DESCRIPTION
      "Path: scheduler.actions.triggerCoredump"
   ::= {ar1646v2OsSchTriggerCoredumpEntry 2147483648}


ar1646v2OsSchTriggerCoredumpType OBJECT IDENTIFIER ::= {ar1646v2OsSch 801}

ar1646v2OsSchTriggerCoredumpTypeTable OBJECT-TYPE
   SYNTAX      SEQUENCE OF Ar1646v2OsSchTriggerCoredumpTypeEntry
   MAX-ACCESS  not-accessible
   STATUS      current
   DESCRIPTION
      "Trigger Coredump"
   ::= {ar1646v2OsSchTriggerCoredumpType 1}

ar1646v2OsSchTriggerCoredumpTypeEntry OBJECT-TYPE
   SYNTAX      Ar1646v2OsSchTriggerCoredumpTypeEntry
   MAX-ACCESS  not-accessible
   STATUS      current
   DESCRIPTION
      ""
   INDEX      { ar1646v2OsSchTriggerCoredumpTypeGlobalIx }
   ::= {ar1646v2OsSchTriggerCoredumpTypeTable 1}

Ar1646v2OsSchTriggerCoredumpTypeEntry ::=
   SEQUENCE
      {
      ar1646v2OsSchTriggerCoredumpTypeGlobalIx
         GlobalIndex,
      ar1646v2OsSchTriggerCoredumpTypeValue
         INTEGER
      }

ar1646v2OsSchTriggerCoredumpTypeGlobalIx OBJECT-TYPE
   SYNTAX      GlobalIndex
   MAX-ACCESS  not-accessible
   STATUS      current
   DESCRIPTION
      "The value of the tlsCntTreeGlobalIndex of the MANAGED OBJECT."
   ::= {ar1646v2OsSchTriggerCoredumpTypeEntry 10}

ar1646v2OsSchTriggerCoredumpTypeValue OBJECT-TYPE
   SYNTAX      INTEGER
               {
               doubleMbufFree (0),
               watchdog (1),
               doubleMemFree (2),
               illegal (3),
               trap (4),
               overwriteHEAP (5),
               null (6),
               alignment (7),
               busError (8),
               powerDown (9)
               }
   MAX-ACCESS  read-write
   STATUS      current
   DESCRIPTION
      "Path: scheduler.actions.triggerCoredumpType

       Possibilities:
               doubleMbufFree   (0)
               watchdog   (1)
               doubleMemFree   (2)
               illegal   (3)
               trap   (4)
               overwriteHEAP   (5)
               null   (6)
               alignment   (7)
               busError   (8)
               powerDown   (9)"
   ::= {ar1646v2OsSchTriggerCoredumpTypeEntry 2147483648}


ar1646v2OsSchClearCounters OBJECT IDENTIFIER ::= {ar1646v2OsSch 263}

ar1646v2OsSchClearCountersTable OBJECT-TYPE
   SYNTAX      SEQUENCE OF Ar1646v2OsSchClearCountersEntry
   MAX-ACCESS  not-accessible
   STATUS      current
   DESCRIPTION
      "reset counters"
   ::= {ar1646v2OsSchClearCounters 1}

ar1646v2OsSchClearCountersEntry OBJECT-TYPE
   SYNTAX      Ar1646v2OsSchClearCountersEntry
   MAX-ACCESS  not-accessible
   STATUS      current
   DESCRIPTION
      ""
   INDEX      { ar1646v2OsSchClearCountersGlobalIx }
   ::= {ar1646v2OsSchClearCountersTable 1}

Ar1646v2OsSchClearCountersEntry ::=
   SEQUENCE
      {
      ar1646v2OsSchClearCountersGlobalIx
         GlobalIndex,
      ar1646v2OsSchClearCountersValue
         Integer32
      }

ar1646v2OsSchClearCountersGlobalIx OBJECT-TYPE
   SYNTAX      GlobalIndex
   MAX-ACCESS  not-accessible
   STATUS      current
   DESCRIPTION
      "The value of the tlsCntTreeGlobalIndex of the MANAGED OBJECT."
   ::= {ar1646v2OsSchClearCountersEntry 10}

ar1646v2OsSchClearCountersValue OBJECT-TYPE
   SYNTAX      Integer32
   MAX-ACCESS  read-write
   STATUS      current
   DESCRIPTION
      "Path: scheduler.actions.clearCounters"
   ::= {ar1646v2OsSchClearCountersEntry 2147483648}



END
