OneAccess-R1645v2-4731-PortSwE DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2PortSwE OBJECT IDENTIFIER ::= {r1645Rootv2 4731}

r1645v2PortSwEMOProp OBJECT IDENTIFIER ::= {r1645v2PortSwE 1}

r1645v2PortSwEMOPropEntry OBJECT IDENTIFIER ::= {r1645v2PortSwEMOProp 1}

r1645v2PortSwEMOPropPath OBJECT-TYPE
   SYNTAX      ContainmentPath
   MAX-ACCESS  read-only
   STATUS      current
   DESCRIPTION
      "Textual description of the containment tree from the instance of
       the root object down to the instance of the current object."
   ::= {r1645v2PortSwEMOPropEntry 3}

r1645v2PortSwEMOPropRev OBJECT-TYPE
   SYNTAX      ObjectRevision
   MAX-ACCESS  read-only
   STATUS      current
   DESCRIPTION
      "This value corresponds with the revision of the MANAGED OBJECT."
   ::= {r1645v2PortSwEMOPropEntry 4}



er1645v2PortSwE OBJECT IDENTIFIER ::= {r1645v2PortSwE 11}


er1645v2PortSwERemark OBJECT-TYPE
   SYNTAX      DisplayString
   MAX-ACCESS  read-write
   STATUS      current
   DESCRIPTION
      "Path: ethernet3.editConf.remark
       Info: intfRemark"
   ::= {er1645v2PortSwE 321}


er1645v2PortSwEAdminStatus OBJECT-TYPE
   SYNTAX      INTEGER
               {
               up (1),
               down (2)
               }
   MAX-ACCESS  read-write
   STATUS      current
   DESCRIPTION
      "Path: ethernet3.editConf.adminStatus
       Info: ifAdminStatus

       Possibilities:
               up   (1)
               down   (2)"
   ::= {er1645v2PortSwE 106}


er1645v2PortSwEAlarmMask OBJECT-TYPE
   SYNTAX      Integer32
   MAX-ACCESS  read-write
   STATUS      current
   DESCRIPTION
      "Path: ethernet3.editConf.alarmMask
       Info: ifAlarmMask

       Bit meanings:
               bit 0 = linkDown"
   ::= {er1645v2PortSwE 135}


er1645v2PortSwEAlarmLev OBJECT IDENTIFIER ::= {er1645v2PortSwE 170}

er1645v2PortSwEAlarmLevSSC OBJECT IDENTIFIER ::= {er1645v2PortSwEAlarmLev 1}

er1645v2PortSwEAlarmLevEntry OBJECT IDENTIFIER ::= {er1645v2PortSwEAlarmLevSSC 1}

er1645v2PortSwEAlarmLevLinkDown OBJECT-TYPE
   SYNTAX      Integer32
   MAX-ACCESS  read-write
   STATUS      current
   DESCRIPTION
      "Path: ethernet3.editConf.alarmLevel.linkDown"
   ::= {er1645v2PortSwEAlarmLevEntry 16777216}


er1645v2PortSwEBw OBJECT IDENTIFIER ::= {er1645v2PortSwE 5}

er1645v2PortSwEBwSSC OBJECT IDENTIFIER ::= {er1645v2PortSwEBw 1}

er1645v2PortSwEBwEntry OBJECT IDENTIFIER ::= {er1645v2PortSwEBwSSC 1}

er1645v2PortSwEBwMode OBJECT-TYPE
   SYNTAX      INTEGER
               {
               reshaping (1),
               policing (2),
               policingReshape (3)
               }
   MAX-ACCESS  read-write
   STATUS      current
   DESCRIPTION
      "Path: ethernet3.editConf.bandwidth.mode

       Possibilities:
               reshaping   (1)
               policing   (2)
               policingReshape   (3)"
   ::= {er1645v2PortSwEBwEntry 3758096384}

er1645v2PortSwEBwCir OBJECT-TYPE
   SYNTAX      Integer32
   MAX-ACCESS  read-write
   STATUS      current
   DESCRIPTION
      "Path: ethernet3.editConf.bandwidth.cir"
   ::= {er1645v2PortSwEBwEntry 268435456}

er1645v2PortSwEBwEir OBJECT-TYPE
   SYNTAX      Integer32
   MAX-ACCESS  read-write
   STATUS      current
   DESCRIPTION
      "Path: ethernet3.editConf.bandwidth.eir"
   ::= {er1645v2PortSwEBwEntry 1879048192}

er1645v2PortSwEBwUnit OBJECT-TYPE
   SYNTAX      INTEGER
               {
               bitssec (1),
               percent (2)
               }
   MAX-ACCESS  read-write
   STATUS      current
   DESCRIPTION
      "Path: ethernet3.editConf.bandwidth.unit

       Possibilities:
               bits/sec   (1)
               percent   (2)"
   ::= {er1645v2PortSwEBwEntry 1342177280}

er1645v2PortSwEBwTc OBJECT-TYPE
   SYNTAX      INTEGER
               {
               auto (0)
               }
   MAX-ACCESS  read-write
   STATUS      current
   DESCRIPTION
      "Path: ethernet3.editConf.bandwidth.tc

       Possibilities:
               auto   (0)"
   ::= {er1645v2PortSwEBwEntry 1610612736}

er1645v2PortSwEBwTcFactor OBJECT-TYPE
   SYNTAX      INTEGER
               {
               ms (10),
               s100us (1)
               }
   MAX-ACCESS  read-write
   STATUS      current
   DESCRIPTION
      "Path: ethernet3.editConf.bandwidth.tcFactor

       Possibilities:
               ms   (10)
               *100us   (1)"
   ::= {er1645v2PortSwEBwEntry 2147483648}

er1645v2PortSwEBwCorrType OBJECT-TYPE
   SYNTAX      INTEGER
               {
               noCorrection (0),
               predefined (1),
               manual (2)
               }
   MAX-ACCESS  read-write
   STATUS      current
   DESCRIPTION
      "Path: ethernet3.editConf.bandwidth.correction.type

       Possibilities:
               noCorrection   (0)
               predefined   (1)
               manual   (2)"
   ::= {er1645v2PortSwEBwEntry 570425344}

er1645v2PortSwEBwCorrPredefEncapsFrameRelay OBJECT-TYPE
   SYNTAX      DisplayString
   MAX-ACCESS  read-write
   STATUS      current
   DESCRIPTION
      "Path: ethernet3.editConf.bandwidth.correction.predefined.encapsulation.frameRelay"
   ::= {er1645v2PortSwEBwEntry 608436224}

er1645v2PortSwEBwCorrPredefEncapsPpp OBJECT-TYPE
   SYNTAX      DisplayString
   MAX-ACCESS  read-write
   STATUS      current
   DESCRIPTION
      "Path: ethernet3.editConf.bandwidth.correction.predefined.encapsulation.ppp"
   ::= {er1645v2PortSwEBwEntry 608698368}

er1645v2PortSwEBwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.bandwidth.correction.predefined.encapsulation.atm.higherLayer

       Possibilities:
               rfc2684   (0)
               ppp   (1)
               pppOverEthernet   (2)"
   ::= {er1645v2PortSwEBwEntry 608993280}

er1645v2PortSwEBwCorrPredefEncapsAtmMp OBJECT-TYPE
   SYNTAX      INTEGER
               {
               llcEncapsulation (0),
               vcMultiplexing (1)
               }
   MAX-ACCESS  read-write
   STATUS      current
   DESCRIPTION
      "Path: ethernet3.editConf.bandwidth.correction.predefined.encapsulation.atm.multiProtocol

       Possibilities:
               llcEncapsulation   (0)
               vcMultiplexing   (1)"
   ::= {er1645v2PortSwEBwEntry 609026048}

er1645v2PortSwEBwCorrPredefEncapsHdlc OBJECT-TYPE
   SYNTAX      DisplayString
   MAX-ACCESS  read-write
   STATUS      current
   DESCRIPTION
      "Path: ethernet3.editConf.bandwidth.correction.predefined.encapsulation.hdlc"
   ::= {er1645v2PortSwEBwEntry 609222656}

er1645v2PortSwEBwCorrPredefEncapsEfmFs OBJECT-TYPE
   SYNTAX      Integer32
   MAX-ACCESS  read-write
   STATUS      current
   DESCRIPTION
      "Path: ethernet3.editConf.bandwidth.correction.predefined.encapsulation.efm.fragmentSize"
   ::= {er1645v2PortSwEBwEntry 609517568}

er1645v2PortSwEBwCorrPredefEncapsEfmIb OBJECT-TYPE
   SYNTAX      Integer32
   MAX-ACCESS  read-write
   STATUS      current
   DESCRIPTION
      "Path: ethernet3.editConf.bandwidth.correction.predefined.encapsulation.efm.idleBytes"
   ::= {er1645v2PortSwEBwEntry 609550336}

er1645v2PortSwEBwCorrPredefMode OBJECT-TYPE
   SYNTAX      INTEGER
               {
               routing (0),
               bridging (1)
               }
   MAX-ACCESS  read-write
   STATUS      current
   DESCRIPTION
      "Path: ethernet3.editConf.bandwidth.correction.predefined.mode

       Possibilities:
               routing   (0)
               bridging   (1)"
   ::= {er1645v2PortSwEBwEntry 612368384}

er1645v2PortSwEBwCorrManualOverhead OBJECT-TYPE
   SYNTAX      Integer32
   MAX-ACCESS  read-write
   STATUS      current
   DESCRIPTION
      "Path: ethernet3.editConf.bandwidth.correction.manual.overhead"
   ::= {er1645v2PortSwEBwEntry 637665280}

er1645v2PortSwEBwCorrManualFrameData OBJECT-TYPE
   SYNTAX      Counter32
   MAX-ACCESS  read-write
   STATUS      current
   DESCRIPTION
      "Path: ethernet3.editConf.bandwidth.correction.manual.frameData

       32 bit unsigned wrappable counter."
   ::= {er1645v2PortSwEBwEntry 637796352}

er1645v2PortSwEBwCorrManualFrameHeader OBJECT-TYPE
   SYNTAX      Counter32
   MAX-ACCESS  read-write
   STATUS      current
   DESCRIPTION
      "Path: ethernet3.editConf.bandwidth.correction.manual.frameHeader

       32 bit unsigned wrappable counter."
   ::= {er1645v2PortSwEBwEntry 637927424}

er1645v2PortSwEBwMaxFifoQLen OBJECT-TYPE
   SYNTAX      Integer32
   MAX-ACCESS  read-write
   STATUS      current
   DESCRIPTION
      "Path: ethernet3.editConf.bandwidth.maxFifoQLen"
   ::= {er1645v2PortSwEBwEntry 805306368}

er1645v2PortSwEBwDeFlagCir OBJECT-TYPE
   SYNTAX      INTEGER
               {
               allowed (1),
               notAllowed (2)
               }
   MAX-ACCESS  read-write
   STATUS      current
   DESCRIPTION
      "Path: ethernet3.editConf.bandwidth.deFlag.cir

       Possibilities:
               allowed   (1)
               notAllowed   (2)"
   ::= {er1645v2PortSwEBwEntry 3490709504}

er1645v2PortSwEBwDeFlagEir OBJECT-TYPE
   SYNTAX      INTEGER
               {
               allowed (1),
               notAllowed (2)
               }
   MAX-ACCESS  read-write
   STATUS      current
   DESCRIPTION
      "Path: ethernet3.editConf.bandwidth.deFlag.eir

       Possibilities:
               allowed   (1)
               notAllowed   (2)"
   ::= {er1645v2PortSwEBwEntry 3491758080}

er1645v2PortSwEBwDeFlagViolate OBJECT-TYPE
   SYNTAX      INTEGER
               {
               allowed (1),
               notAllowed (2)
               }
   MAX-ACCESS  read-write
   STATUS      current
   DESCRIPTION
      "Path: ethernet3.editConf.bandwidth.deFlag.violate

       Possibilities:
               allowed   (1)
               notAllowed   (2)"
   ::= {er1645v2PortSwEBwEntry 3492806656}

er1645v2PortSwEBwActCirActNone OBJECT-TYPE
   SYNTAX      OCTET STRING
   MAX-ACCESS  read-write
   STATUS      current
   DESCRIPTION
      "Path: ethernet3.editConf.bandwidth.action.cirAction.none"
   ::= {er1645v2PortSwEBwEntry 4062183424}

er1645v2PortSwEBwActCirActEthCos1 OBJECT-TYPE
   SYNTAX      INTEGER
               {
               unchanged (256)
               }
   MAX-ACCESS  read-write
   STATUS      current
   DESCRIPTION
      "Path: ethernet3.editConf.bandwidth.action.cirAction.ethernet.cosDepth1

       Possibilities:
               unchanged   (256)"
   ::= {er1645v2PortSwEBwEntry 4064346112}

er1645v2PortSwEBwActCirActEthDei1 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth1

       Possibilities:
               unchanged   (255)
               clear   (0)
               set   (1)"
   ::= {er1645v2PortSwEBwEntry 4065656832}

er1645v2PortSwEBwActCirActEthCos2 OBJECT-TYPE
   SYNTAX      INTEGER
               {
               unchanged (256)
               }
   MAX-ACCESS  read-write
   STATUS      current
   DESCRIPTION
      "Path: ethernet3.editConf.bandwidth.action.cirAction.ethernet.cosDepth2

       Possibilities:
               unchanged   (256)"
   ::= {er1645v2PortSwEBwEntry 4064411648}

er1645v2PortSwEBwActCirActEthDei2 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth2

       Possibilities:
               unchanged   (255)
               clear   (0)
               set   (1)"
   ::= {er1645v2PortSwEBwEntry 4065722368}

er1645v2PortSwEBwActCirActEthCos3 OBJECT-TYPE
   SYNTAX      INTEGER
               {
               unchanged (256)
               }
   MAX-ACCESS  read-write
   STATUS      current
   DESCRIPTION
      "Path: ethernet3.editConf.bandwidth.action.cirAction.ethernet.cosDepth3

       Possibilities:
               unchanged   (256)"
   ::= {er1645v2PortSwEBwEntry 4064477184}

er1645v2PortSwEBwActCirActEthDei3 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth3

       Possibilities:
               unchanged   (255)
               clear   (0)
               set   (1)"
   ::= {er1645v2PortSwEBwEntry 4065787904}

er1645v2PortSwEBwActCirActEthCos4 OBJECT-TYPE
   SYNTAX      INTEGER
               {
               unchanged (256)
               }
   MAX-ACCESS  read-write
   STATUS      current
   DESCRIPTION
      "Path: ethernet3.editConf.bandwidth.action.cirAction.ethernet.cosDepth4

       Possibilities:
               unchanged   (256)"
   ::= {er1645v2PortSwEBwEntry 4064542720}

er1645v2PortSwEBwActCirActEthDei4 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth4

       Possibilities:
               unchanged   (255)
               clear   (0)
               set   (1)"
   ::= {er1645v2PortSwEBwEntry 4065853440}

er1645v2PortSwEBwActCirActEthCos5 OBJECT-TYPE
   SYNTAX      INTEGER
               {
               unchanged (256)
               }
   MAX-ACCESS  read-write
   STATUS      current
   DESCRIPTION
      "Path: ethernet3.editConf.bandwidth.action.cirAction.ethernet.cosDepth5

       Possibilities:
               unchanged   (256)"
   ::= {er1645v2PortSwEBwEntry 4064608256}

er1645v2PortSwEBwActCirActEthDei5 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth5

       Possibilities:
               unchanged   (255)
               clear   (0)
               set   (1)"
   ::= {er1645v2PortSwEBwEntry 4065918976}

er1645v2PortSwEBwActCirActEthCos6 OBJECT-TYPE
   SYNTAX      INTEGER
               {
               unchanged (256)
               }
   MAX-ACCESS  read-write
   STATUS      current
   DESCRIPTION
      "Path: ethernet3.editConf.bandwidth.action.cirAction.ethernet.cosDepth6

       Possibilities:
               unchanged   (256)"
   ::= {er1645v2PortSwEBwEntry 4064673792}

er1645v2PortSwEBwActCirActEthDei6 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth6

       Possibilities:
               unchanged   (255)
               clear   (0)
               set   (1)"
   ::= {er1645v2PortSwEBwEntry 4065984512}

er1645v2PortSwEBwActCirActEthCos7 OBJECT-TYPE
   SYNTAX      INTEGER
               {
               unchanged (256)
               }
   MAX-ACCESS  read-write
   STATUS      current
   DESCRIPTION
      "Path: ethernet3.editConf.bandwidth.action.cirAction.ethernet.cosDepth7

       Possibilities:
               unchanged   (256)"
   ::= {er1645v2PortSwEBwEntry 4064739328}

er1645v2PortSwEBwActCirActEthDei7 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth7

       Possibilities:
               unchanged   (255)
               clear   (0)
               set   (1)"
   ::= {er1645v2PortSwEBwEntry 4066050048}

er1645v2PortSwEBwActCirActEthCos8 OBJECT-TYPE
   SYNTAX      INTEGER
               {
               unchanged (256)
               }
   MAX-ACCESS  read-write
   STATUS      current
   DESCRIPTION
      "Path: ethernet3.editConf.bandwidth.action.cirAction.ethernet.cosDepth8

       Possibilities:
               unchanged   (256)"
   ::= {er1645v2PortSwEBwEntry 4064804864}

er1645v2PortSwEBwActCirActEthDei8 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth8

       Possibilities:
               unchanged   (255)
               clear   (0)
               set   (1)"
   ::= {er1645v2PortSwEBwEntry 4066115584}

er1645v2PortSwEBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEBwEntry 4064870400}

er1645v2PortSwEBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwEBwEntry 4064935936}

er1645v2PortSwEBwActCirActEthDrpLev OBJECT-TYPE
   SYNTAX      INTEGER
               {
               unchanged (0)
               }
   MAX-ACCESS  read-write
   STATUS      current
   DESCRIPTION
      "Path: ethernet3.editConf.bandwidth.action.cirAction.ethernet.dropLevel

       Possibilities:
               unchanged   (0)"
   ::= {er1645v2PortSwEBwEntry 4065001472}

er1645v2PortSwEBwActCirActEthDeFlag OBJECT-TYPE
   SYNTAX      INTEGER
               {
               unchanged (255),
               clear (0),
               set (1)
               }
   MAX-ACCESS  read-write
   STATUS      current
   DESCRIPTION
      "Path: ethernet3.editConf.bandwidth.action.cirAction.ethernet.deFlag

       Possibilities:
               unchanged   (255)
               clear   (0)
               set   (1)"
   ::= {er1645v2PortSwEBwEntry 4065198080}

er1645v2PortSwEBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEBwEntry 4071161856}

er1645v2PortSwEBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwEBwEntry 4071227392}

er1645v2PortSwEBwActCirActIpDrpLev OBJECT-TYPE
   SYNTAX      INTEGER
               {
               unchanged (0)
               }
   MAX-ACCESS  read-write
   STATUS      current
   DESCRIPTION
      "Path: ethernet3.editConf.bandwidth.action.cirAction.ip.dropLevel

       Possibilities:
               unchanged   (0)"
   ::= {er1645v2PortSwEBwEntry 4071292928}

er1645v2PortSwEBwActCirActIpDeFlag OBJECT-TYPE
   SYNTAX      INTEGER
               {
               unchanged (255),
               clear (0),
               set (1)
               }
   MAX-ACCESS  read-write
   STATUS      current
   DESCRIPTION
      "Path: ethernet3.editConf.bandwidth.action.cirAction.ip.deFlag

       Possibilities:
               unchanged   (255)
               clear   (0)
               set   (1)"
   ::= {er1645v2PortSwEBwEntry 4071489536}

er1645v2PortSwEBwActEirActNone OBJECT-TYPE
   SYNTAX      OCTET STRING
   MAX-ACCESS  read-write
   STATUS      current
   DESCRIPTION
      "Path: ethernet3.editConf.bandwidth.action.eirAction.none"
   ::= {er1645v2PortSwEBwEntry 4095737856}

er1645v2PortSwEBwActEirActEthCos1 OBJECT-TYPE
   SYNTAX      INTEGER
               {
               unchanged (256)
               }
   MAX-ACCESS  read-write
   STATUS      current
   DESCRIPTION
      "Path: ethernet3.editConf.bandwidth.action.eirAction.ethernet.cosDepth1

       Possibilities:
               unchanged   (256)"
   ::= {er1645v2PortSwEBwEntry 4097900544}

er1645v2PortSwEBwActEirActEthDei1 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth1

       Possibilities:
               unchanged   (255)
               clear   (0)
               set   (1)"
   ::= {er1645v2PortSwEBwEntry 4099211264}

er1645v2PortSwEBwActEirActEthCos2 OBJECT-TYPE
   SYNTAX      INTEGER
               {
               unchanged (256)
               }
   MAX-ACCESS  read-write
   STATUS      current
   DESCRIPTION
      "Path: ethernet3.editConf.bandwidth.action.eirAction.ethernet.cosDepth2

       Possibilities:
               unchanged   (256)"
   ::= {er1645v2PortSwEBwEntry 4097966080}

er1645v2PortSwEBwActEirActEthDei2 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth2

       Possibilities:
               unchanged   (255)
               clear   (0)
               set   (1)"
   ::= {er1645v2PortSwEBwEntry 4099276800}

er1645v2PortSwEBwActEirActEthCos3 OBJECT-TYPE
   SYNTAX      INTEGER
               {
               unchanged (256)
               }
   MAX-ACCESS  read-write
   STATUS      current
   DESCRIPTION
      "Path: ethernet3.editConf.bandwidth.action.eirAction.ethernet.cosDepth3

       Possibilities:
               unchanged   (256)"
   ::= {er1645v2PortSwEBwEntry 4098031616}

er1645v2PortSwEBwActEirActEthDei3 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth3

       Possibilities:
               unchanged   (255)
               clear   (0)
               set   (1)"
   ::= {er1645v2PortSwEBwEntry 4099342336}

er1645v2PortSwEBwActEirActEthCos4 OBJECT-TYPE
   SYNTAX      INTEGER
               {
               unchanged (256)
               }
   MAX-ACCESS  read-write
   STATUS      current
   DESCRIPTION
      "Path: ethernet3.editConf.bandwidth.action.eirAction.ethernet.cosDepth4

       Possibilities:
               unchanged   (256)"
   ::= {er1645v2PortSwEBwEntry 4098097152}

er1645v2PortSwEBwActEirActEthDei4 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth4

       Possibilities:
               unchanged   (255)
               clear   (0)
               set   (1)"
   ::= {er1645v2PortSwEBwEntry 4099407872}

er1645v2PortSwEBwActEirActEthCos5 OBJECT-TYPE
   SYNTAX      INTEGER
               {
               unchanged (256)
               }
   MAX-ACCESS  read-write
   STATUS      current
   DESCRIPTION
      "Path: ethernet3.editConf.bandwidth.action.eirAction.ethernet.cosDepth5

       Possibilities:
               unchanged   (256)"
   ::= {er1645v2PortSwEBwEntry 4098162688}

er1645v2PortSwEBwActEirActEthDei5 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth5

       Possibilities:
               unchanged   (255)
               clear   (0)
               set   (1)"
   ::= {er1645v2PortSwEBwEntry 4099473408}

er1645v2PortSwEBwActEirActEthCos6 OBJECT-TYPE
   SYNTAX      INTEGER
               {
               unchanged (256)
               }
   MAX-ACCESS  read-write
   STATUS      current
   DESCRIPTION
      "Path: ethernet3.editConf.bandwidth.action.eirAction.ethernet.cosDepth6

       Possibilities:
               unchanged   (256)"
   ::= {er1645v2PortSwEBwEntry 4098228224}

er1645v2PortSwEBwActEirActEthDei6 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth6

       Possibilities:
               unchanged   (255)
               clear   (0)
               set   (1)"
   ::= {er1645v2PortSwEBwEntry 4099538944}

er1645v2PortSwEBwActEirActEthCos7 OBJECT-TYPE
   SYNTAX      INTEGER
               {
               unchanged (256)
               }
   MAX-ACCESS  read-write
   STATUS      current
   DESCRIPTION
      "Path: ethernet3.editConf.bandwidth.action.eirAction.ethernet.cosDepth7

       Possibilities:
               unchanged   (256)"
   ::= {er1645v2PortSwEBwEntry 4098293760}

er1645v2PortSwEBwActEirActEthDei7 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth7

       Possibilities:
               unchanged   (255)
               clear   (0)
               set   (1)"
   ::= {er1645v2PortSwEBwEntry 4099604480}

er1645v2PortSwEBwActEirActEthCos8 OBJECT-TYPE
   SYNTAX      INTEGER
               {
               unchanged (256)
               }
   MAX-ACCESS  read-write
   STATUS      current
   DESCRIPTION
      "Path: ethernet3.editConf.bandwidth.action.eirAction.ethernet.cosDepth8

       Possibilities:
               unchanged   (256)"
   ::= {er1645v2PortSwEBwEntry 4098359296}

er1645v2PortSwEBwActEirActEthDei8 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth8

       Possibilities:
               unchanged   (255)
               clear   (0)
               set   (1)"
   ::= {er1645v2PortSwEBwEntry 4099670016}

er1645v2PortSwEBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEBwEntry 4098424832}

er1645v2PortSwEBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwEBwEntry 4098490368}

er1645v2PortSwEBwActEirActEthDrpLev OBJECT-TYPE
   SYNTAX      INTEGER
               {
               unchanged (0)
               }
   MAX-ACCESS  read-write
   STATUS      current
   DESCRIPTION
      "Path: ethernet3.editConf.bandwidth.action.eirAction.ethernet.dropLevel

       Possibilities:
               unchanged   (0)"
   ::= {er1645v2PortSwEBwEntry 4098555904}

er1645v2PortSwEBwActEirActEthDeFlag OBJECT-TYPE
   SYNTAX      INTEGER
               {
               unchanged (255),
               clear (0),
               set (1)
               }
   MAX-ACCESS  read-write
   STATUS      current
   DESCRIPTION
      "Path: ethernet3.editConf.bandwidth.action.eirAction.ethernet.deFlag

       Possibilities:
               unchanged   (255)
               clear   (0)
               set   (1)"
   ::= {er1645v2PortSwEBwEntry 4098752512}

er1645v2PortSwEBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEBwEntry 4104716288}

er1645v2PortSwEBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwEBwEntry 4104781824}

er1645v2PortSwEBwActEirActIpDrpLev OBJECT-TYPE
   SYNTAX      INTEGER
               {
               unchanged (0)
               }
   MAX-ACCESS  read-write
   STATUS      current
   DESCRIPTION
      "Path: ethernet3.editConf.bandwidth.action.eirAction.ip.dropLevel

       Possibilities:
               unchanged   (0)"
   ::= {er1645v2PortSwEBwEntry 4104847360}

er1645v2PortSwEBwActEirActIpDeFlag OBJECT-TYPE
   SYNTAX      INTEGER
               {
               unchanged (255),
               clear (0),
               set (1)
               }
   MAX-ACCESS  read-write
   STATUS      current
   DESCRIPTION
      "Path: ethernet3.editConf.bandwidth.action.eirAction.ip.deFlag

       Possibilities:
               unchanged   (255)
               clear   (0)
               set   (1)"
   ::= {er1645v2PortSwEBwEntry 4105043968}

er1645v2PortSwEBwActViolActNone OBJECT-TYPE
   SYNTAX      OCTET STRING
   MAX-ACCESS  read-write
   STATUS      current
   DESCRIPTION
      "Path: ethernet3.editConf.bandwidth.action.violateAction.none"
   ::= {er1645v2PortSwEBwEntry 4129292288}

er1645v2PortSwEBwActViolActDrop OBJECT-TYPE
   SYNTAX      OCTET STRING
   MAX-ACCESS  read-write
   STATUS      current
   DESCRIPTION
      "Path: ethernet3.editConf.bandwidth.action.violateAction.drop"
   ::= {er1645v2PortSwEBwEntry 4133486592}

er1645v2PortSwEBwActViolActEthCos1 OBJECT-TYPE
   SYNTAX      INTEGER
               {
               unchanged (256)
               }
   MAX-ACCESS  read-write
   STATUS      current
   DESCRIPTION
      "Path: ethernet3.editConf.bandwidth.action.violateAction.ethernet.cosDepth1

       Possibilities:
               unchanged   (256)"
   ::= {er1645v2PortSwEBwEntry 4131454976}

er1645v2PortSwEBwActViolActEthDei1 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth1

       Possibilities:
               unchanged   (255)
               clear   (0)
               set   (1)"
   ::= {er1645v2PortSwEBwEntry 4132765696}

er1645v2PortSwEBwActViolActEthCos2 OBJECT-TYPE
   SYNTAX      INTEGER
               {
               unchanged (256)
               }
   MAX-ACCESS  read-write
   STATUS      current
   DESCRIPTION
      "Path: ethernet3.editConf.bandwidth.action.violateAction.ethernet.cosDepth2

       Possibilities:
               unchanged   (256)"
   ::= {er1645v2PortSwEBwEntry 4131520512}

er1645v2PortSwEBwActViolActEthDei2 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth2

       Possibilities:
               unchanged   (255)
               clear   (0)
               set   (1)"
   ::= {er1645v2PortSwEBwEntry 4132831232}

er1645v2PortSwEBwActViolActEthCos3 OBJECT-TYPE
   SYNTAX      INTEGER
               {
               unchanged (256)
               }
   MAX-ACCESS  read-write
   STATUS      current
   DESCRIPTION
      "Path: ethernet3.editConf.bandwidth.action.violateAction.ethernet.cosDepth3

       Possibilities:
               unchanged   (256)"
   ::= {er1645v2PortSwEBwEntry 4131586048}

er1645v2PortSwEBwActViolActEthDei3 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth3

       Possibilities:
               unchanged   (255)
               clear   (0)
               set   (1)"
   ::= {er1645v2PortSwEBwEntry 4132896768}

er1645v2PortSwEBwActViolActEthCos4 OBJECT-TYPE
   SYNTAX      INTEGER
               {
               unchanged (256)
               }
   MAX-ACCESS  read-write
   STATUS      current
   DESCRIPTION
      "Path: ethernet3.editConf.bandwidth.action.violateAction.ethernet.cosDepth4

       Possibilities:
               unchanged   (256)"
   ::= {er1645v2PortSwEBwEntry 4131651584}

er1645v2PortSwEBwActViolActEthDei4 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth4

       Possibilities:
               unchanged   (255)
               clear   (0)
               set   (1)"
   ::= {er1645v2PortSwEBwEntry 4132962304}

er1645v2PortSwEBwActViolActEthCos5 OBJECT-TYPE
   SYNTAX      INTEGER
               {
               unchanged (256)
               }
   MAX-ACCESS  read-write
   STATUS      current
   DESCRIPTION
      "Path: ethernet3.editConf.bandwidth.action.violateAction.ethernet.cosDepth5

       Possibilities:
               unchanged   (256)"
   ::= {er1645v2PortSwEBwEntry 4131717120}

er1645v2PortSwEBwActViolActEthDei5 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth5

       Possibilities:
               unchanged   (255)
               clear   (0)
               set   (1)"
   ::= {er1645v2PortSwEBwEntry 4133027840}

er1645v2PortSwEBwActViolActEthCos6 OBJECT-TYPE
   SYNTAX      INTEGER
               {
               unchanged (256)
               }
   MAX-ACCESS  read-write
   STATUS      current
   DESCRIPTION
      "Path: ethernet3.editConf.bandwidth.action.violateAction.ethernet.cosDepth6

       Possibilities:
               unchanged   (256)"
   ::= {er1645v2PortSwEBwEntry 4131782656}

er1645v2PortSwEBwActViolActEthDei6 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth6

       Possibilities:
               unchanged   (255)
               clear   (0)
               set   (1)"
   ::= {er1645v2PortSwEBwEntry 4133093376}

er1645v2PortSwEBwActViolActEthCos7 OBJECT-TYPE
   SYNTAX      INTEGER
               {
               unchanged (256)
               }
   MAX-ACCESS  read-write
   STATUS      current
   DESCRIPTION
      "Path: ethernet3.editConf.bandwidth.action.violateAction.ethernet.cosDepth7

       Possibilities:
               unchanged   (256)"
   ::= {er1645v2PortSwEBwEntry 4131848192}

er1645v2PortSwEBwActViolActEthDei7 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth7

       Possibilities:
               unchanged   (255)
               clear   (0)
               set   (1)"
   ::= {er1645v2PortSwEBwEntry 4133158912}

er1645v2PortSwEBwActViolActEthCos8 OBJECT-TYPE
   SYNTAX      INTEGER
               {
               unchanged (256)
               }
   MAX-ACCESS  read-write
   STATUS      current
   DESCRIPTION
      "Path: ethernet3.editConf.bandwidth.action.violateAction.ethernet.cosDepth8

       Possibilities:
               unchanged   (256)"
   ::= {er1645v2PortSwEBwEntry 4131913728}

er1645v2PortSwEBwActViolActEthDei8 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth8

       Possibilities:
               unchanged   (255)
               clear   (0)
               set   (1)"
   ::= {er1645v2PortSwEBwEntry 4133224448}

er1645v2PortSwEBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEBwEntry 4131979264}

er1645v2PortSwEBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwEBwEntry 4132044800}

er1645v2PortSwEBwActViolActEthDrpLev OBJECT-TYPE
   SYNTAX      INTEGER
               {
               unchanged (0)
               }
   MAX-ACCESS  read-write
   STATUS      current
   DESCRIPTION
      "Path: ethernet3.editConf.bandwidth.action.violateAction.ethernet.dropLevel

       Possibilities:
               unchanged   (0)"
   ::= {er1645v2PortSwEBwEntry 4132110336}

er1645v2PortSwEBwActViolActEthDeFlag OBJECT-TYPE
   SYNTAX      INTEGER
               {
               unchanged (255),
               clear (0),
               set (1)
               }
   MAX-ACCESS  read-write
   STATUS      current
   DESCRIPTION
      "Path: ethernet3.editConf.bandwidth.action.violateAction.ethernet.deFlag

       Possibilities:
               unchanged   (255)
               clear   (0)
               set   (1)"
   ::= {er1645v2PortSwEBwEntry 4132306944}

er1645v2PortSwEBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEBwEntry 4138270720}

er1645v2PortSwEBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwEBwEntry 4138336256}

er1645v2PortSwEBwActViolActIpDrpLev OBJECT-TYPE
   SYNTAX      INTEGER
               {
               unchanged (0)
               }
   MAX-ACCESS  read-write
   STATUS      current
   DESCRIPTION
      "Path: ethernet3.editConf.bandwidth.action.violateAction.ip.dropLevel

       Possibilities:
               unchanged   (0)"
   ::= {er1645v2PortSwEBwEntry 4138401792}

er1645v2PortSwEBwActViolActIpDeFlag OBJECT-TYPE
   SYNTAX      INTEGER
               {
               unchanged (255),
               clear (0),
               set (1)
               }
   MAX-ACCESS  read-write
   STATUS      current
   DESCRIPTION
      "Path: ethernet3.editConf.bandwidth.action.violateAction.ip.deFlag

       Possibilities:
               unchanged   (255)
               clear   (0)
               set   (1)"
   ::= {er1645v2PortSwEBwEntry 4138598400}


er1645v2PortSwEPriorityPolicy OBJECT-TYPE
   SYNTAX      DisplayString
   MAX-ACCESS  read-write
   STATUS      current
   DESCRIPTION
      "Path: ethernet3.editConf.priorityPolicy
       Info: Preferred Policy"
   ::= {er1645v2PortSwE 39}


er1645v2PortSwEMru OBJECT-TYPE
   SYNTAX      Integer32
   MAX-ACCESS  read-write
   STATUS      current
   DESCRIPTION
      "Path: ethernet3.editConf.mru"
   ::= {er1645v2PortSwE 43}


er1645v2PortSwEDelayOptimisation OBJECT-TYPE
   SYNTAX      INTEGER
               {
               disabled (0),
               enabled (1)
               }
   MAX-ACCESS  read-write
   STATUS      current
   DESCRIPTION
      "Path: ethernet3.editConf.delayOptimisation
       Info: optimise delay

       Possibilities:
               disabled   (0)
               enabled   (1)"
   ::= {er1645v2PortSwE 80}


er1645v2PortSwEIbw OBJECT IDENTIFIER ::= {er1645v2PortSwE 13}

er1645v2PortSwEIbwSSC OBJECT IDENTIFIER ::= {er1645v2PortSwEIbw 1}

er1645v2PortSwEIbwEntry OBJECT IDENTIFIER ::= {er1645v2PortSwEIbwSSC 1}

er1645v2PortSwEIbwMode OBJECT-TYPE
   SYNTAX      INTEGER
               {
               reshaping (1),
               policing (2)
               }
   MAX-ACCESS  read-write
   STATUS      current
   DESCRIPTION
      "Path: ethernet3.editConf.inboundBandwidth.mode

       Possibilities:
               reshaping   (1)
               policing   (2)"
   ::= {er1645v2PortSwEIbwEntry 3758096384}

er1645v2PortSwEIbwCir OBJECT-TYPE
   SYNTAX      Integer32
   MAX-ACCESS  read-write
   STATUS      current
   DESCRIPTION
      "Path: ethernet3.editConf.inboundBandwidth.cir"
   ::= {er1645v2PortSwEIbwEntry 268435456}

er1645v2PortSwEIbwEir OBJECT-TYPE
   SYNTAX      Integer32
   MAX-ACCESS  read-write
   STATUS      current
   DESCRIPTION
      "Path: ethernet3.editConf.inboundBandwidth.eir"
   ::= {er1645v2PortSwEIbwEntry 1879048192}

er1645v2PortSwEIbwTc OBJECT-TYPE
   SYNTAX      INTEGER
               {
               auto (0)
               }
   MAX-ACCESS  read-write
   STATUS      current
   DESCRIPTION
      "Path: ethernet3.editConf.inboundBandwidth.tc

       Possibilities:
               auto   (0)"
   ::= {er1645v2PortSwEIbwEntry 1610612736}

er1645v2PortSwEIbwTcFactor OBJECT-TYPE
   SYNTAX      INTEGER
               {
               ms (10),
               s100us (1)
               }
   MAX-ACCESS  read-write
   STATUS      current
   DESCRIPTION
      "Path: ethernet3.editConf.inboundBandwidth.tcFactor

       Possibilities:
               ms   (10)
               *100us   (1)"
   ::= {er1645v2PortSwEIbwEntry 2147483648}

er1645v2PortSwEIbwCorrType OBJECT-TYPE
   SYNTAX      INTEGER
               {
               noCorrection (0),
               predefined (1),
               manual (2)
               }
   MAX-ACCESS  read-write
   STATUS      current
   DESCRIPTION
      "Path: ethernet3.editConf.inboundBandwidth.correction.type

       Possibilities:
               noCorrection   (0)
               predefined   (1)
               manual   (2)"
   ::= {er1645v2PortSwEIbwEntry 570425344}

er1645v2PortSwEIbwCorrPredefEncapsFrameRelay OBJECT-TYPE
   SYNTAX      DisplayString
   MAX-ACCESS  read-write
   STATUS      current
   DESCRIPTION
      "Path: ethernet3.editConf.inboundBandwidth.correction.predefined.encapsulation.frameRelay"
   ::= {er1645v2PortSwEIbwEntry 608436224}

er1645v2PortSwEIbwCorrPredefEncapsPpp OBJECT-TYPE
   SYNTAX      DisplayString
   MAX-ACCESS  read-write
   STATUS      current
   DESCRIPTION
      "Path: ethernet3.editConf.inboundBandwidth.correction.predefined.encapsulation.ppp"
   ::= {er1645v2PortSwEIbwEntry 608698368}

er1645v2PortSwEIbwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.inboundBandwidth.correction.predefined.encapsulation.atm.higherLayer

       Possibilities:
               rfc2684   (0)
               ppp   (1)
               pppOverEthernet   (2)"
   ::= {er1645v2PortSwEIbwEntry 608993280}

er1645v2PortSwEIbwCorrPredefEncapsAtmMp OBJECT-TYPE
   SYNTAX      INTEGER
               {
               llcEncapsulation (0),
               vcMultiplexing (1)
               }
   MAX-ACCESS  read-write
   STATUS      current
   DESCRIPTION
      "Path: ethernet3.editConf.inboundBandwidth.correction.predefined.encapsulation.atm.multiProtocol

       Possibilities:
               llcEncapsulation   (0)
               vcMultiplexing   (1)"
   ::= {er1645v2PortSwEIbwEntry 609026048}

er1645v2PortSwEIbwCorrPredefEncapsHdlc OBJECT-TYPE
   SYNTAX      DisplayString
   MAX-ACCESS  read-write
   STATUS      current
   DESCRIPTION
      "Path: ethernet3.editConf.inboundBandwidth.correction.predefined.encapsulation.hdlc"
   ::= {er1645v2PortSwEIbwEntry 609222656}

er1645v2PortSwEIbwCorrPredefEncapsEfmFs OBJECT-TYPE
   SYNTAX      Integer32
   MAX-ACCESS  read-write
   STATUS      current
   DESCRIPTION
      "Path: ethernet3.editConf.inboundBandwidth.correction.predefined.encapsulation.efm.fragmentSize"
   ::= {er1645v2PortSwEIbwEntry 609517568}

er1645v2PortSwEIbwCorrPredefEncapsEfmIb OBJECT-TYPE
   SYNTAX      Integer32
   MAX-ACCESS  read-write
   STATUS      current
   DESCRIPTION
      "Path: ethernet3.editConf.inboundBandwidth.correction.predefined.encapsulation.efm.idleBytes"
   ::= {er1645v2PortSwEIbwEntry 609550336}

er1645v2PortSwEIbwCorrPredefMode OBJECT-TYPE
   SYNTAX      INTEGER
               {
               routing (0),
               bridging (1)
               }
   MAX-ACCESS  read-write
   STATUS      current
   DESCRIPTION
      "Path: ethernet3.editConf.inboundBandwidth.correction.predefined.mode

       Possibilities:
               routing   (0)
               bridging   (1)"
   ::= {er1645v2PortSwEIbwEntry 612368384}

er1645v2PortSwEIbwCorrManualOverhead OBJECT-TYPE
   SYNTAX      Integer32
   MAX-ACCESS  read-write
   STATUS      current
   DESCRIPTION
      "Path: ethernet3.editConf.inboundBandwidth.correction.manual.overhead"
   ::= {er1645v2PortSwEIbwEntry 637665280}

er1645v2PortSwEIbwCorrManualFrameData OBJECT-TYPE
   SYNTAX      Counter32
   MAX-ACCESS  read-write
   STATUS      current
   DESCRIPTION
      "Path: ethernet3.editConf.inboundBandwidth.correction.manual.frameData

       32 bit unsigned wrappable counter."
   ::= {er1645v2PortSwEIbwEntry 637796352}

er1645v2PortSwEIbwCorrManualFrameHeader OBJECT-TYPE
   SYNTAX      Counter32
   MAX-ACCESS  read-write
   STATUS      current
   DESCRIPTION
      "Path: ethernet3.editConf.inboundBandwidth.correction.manual.frameHeader

       32 bit unsigned wrappable counter."
   ::= {er1645v2PortSwEIbwEntry 637927424}

er1645v2PortSwEIbwMaxFifoQLen OBJECT-TYPE
   SYNTAX      Integer32
   MAX-ACCESS  read-write
   STATUS      current
   DESCRIPTION
      "Path: ethernet3.editConf.inboundBandwidth.maxFifoQLen"
   ::= {er1645v2PortSwEIbwEntry 805306368}

er1645v2PortSwEIbwPriorityPolicy OBJECT-TYPE
   SYNTAX      DisplayString
   MAX-ACCESS  read-write
   STATUS      current
   DESCRIPTION
      "Path: ethernet3.editConf.inboundBandwidth.priorityPolicy"
   ::= {er1645v2PortSwEIbwEntry 1073741824}

er1645v2PortSwEIbwDeFlagCir OBJECT-TYPE
   SYNTAX      INTEGER
               {
               allowed (1),
               notAllowed (2)
               }
   MAX-ACCESS  read-write
   STATUS      current
   DESCRIPTION
      "Path: ethernet3.editConf.inboundBandwidth.deFlag.cir

       Possibilities:
               allowed   (1)
               notAllowed   (2)"
   ::= {er1645v2PortSwEIbwEntry 3490709504}

er1645v2PortSwEIbwDeFlagEir OBJECT-TYPE
   SYNTAX      INTEGER
               {
               allowed (1),
               notAllowed (2)
               }
   MAX-ACCESS  read-write
   STATUS      current
   DESCRIPTION
      "Path: ethernet3.editConf.inboundBandwidth.deFlag.eir

       Possibilities:
               allowed   (1)
               notAllowed   (2)"
   ::= {er1645v2PortSwEIbwEntry 3491758080}

er1645v2PortSwEIbwDeFlagViolate OBJECT-TYPE
   SYNTAX      INTEGER
               {
               allowed (1),
               notAllowed (2)
               }
   MAX-ACCESS  read-write
   STATUS      current
   DESCRIPTION
      "Path: ethernet3.editConf.inboundBandwidth.deFlag.violate

       Possibilities:
               allowed   (1)
               notAllowed   (2)"
   ::= {er1645v2PortSwEIbwEntry 3492806656}

er1645v2PortSwEIbwActCirActNone OBJECT-TYPE
   SYNTAX      OCTET STRING
   MAX-ACCESS  read-write
   STATUS      current
   DESCRIPTION
      "Path: ethernet3.editConf.inboundBandwidth.action.cirAction.none"
   ::= {er1645v2PortSwEIbwEntry 4062183424}

er1645v2PortSwEIbwActCirActEthCos1 OBJECT-TYPE
   SYNTAX      INTEGER
               {
               unchanged (256)
               }
   MAX-ACCESS  read-write
   STATUS      current
   DESCRIPTION
      "Path: ethernet3.editConf.inboundBandwidth.action.cirAction.ethernet.cosDepth1

       Possibilities:
               unchanged   (256)"
   ::= {er1645v2PortSwEIbwEntry 4064346112}

er1645v2PortSwEIbwActCirActEthDei1 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth1

       Possibilities:
               unchanged   (255)
               clear   (0)
               set   (1)"
   ::= {er1645v2PortSwEIbwEntry 4065656832}

er1645v2PortSwEIbwActCirActEthCos2 OBJECT-TYPE
   SYNTAX      INTEGER
               {
               unchanged (256)
               }
   MAX-ACCESS  read-write
   STATUS      current
   DESCRIPTION
      "Path: ethernet3.editConf.inboundBandwidth.action.cirAction.ethernet.cosDepth2

       Possibilities:
               unchanged   (256)"
   ::= {er1645v2PortSwEIbwEntry 4064411648}

er1645v2PortSwEIbwActCirActEthDei2 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth2

       Possibilities:
               unchanged   (255)
               clear   (0)
               set   (1)"
   ::= {er1645v2PortSwEIbwEntry 4065722368}

er1645v2PortSwEIbwActCirActEthCos3 OBJECT-TYPE
   SYNTAX      INTEGER
               {
               unchanged (256)
               }
   MAX-ACCESS  read-write
   STATUS      current
   DESCRIPTION
      "Path: ethernet3.editConf.inboundBandwidth.action.cirAction.ethernet.cosDepth3

       Possibilities:
               unchanged   (256)"
   ::= {er1645v2PortSwEIbwEntry 4064477184}

er1645v2PortSwEIbwActCirActEthDei3 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth3

       Possibilities:
               unchanged   (255)
               clear   (0)
               set   (1)"
   ::= {er1645v2PortSwEIbwEntry 4065787904}

er1645v2PortSwEIbwActCirActEthCos4 OBJECT-TYPE
   SYNTAX      INTEGER
               {
               unchanged (256)
               }
   MAX-ACCESS  read-write
   STATUS      current
   DESCRIPTION
      "Path: ethernet3.editConf.inboundBandwidth.action.cirAction.ethernet.cosDepth4

       Possibilities:
               unchanged   (256)"
   ::= {er1645v2PortSwEIbwEntry 4064542720}

er1645v2PortSwEIbwActCirActEthDei4 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth4

       Possibilities:
               unchanged   (255)
               clear   (0)
               set   (1)"
   ::= {er1645v2PortSwEIbwEntry 4065853440}

er1645v2PortSwEIbwActCirActEthCos5 OBJECT-TYPE
   SYNTAX      INTEGER
               {
               unchanged (256)
               }
   MAX-ACCESS  read-write
   STATUS      current
   DESCRIPTION
      "Path: ethernet3.editConf.inboundBandwidth.action.cirAction.ethernet.cosDepth5

       Possibilities:
               unchanged   (256)"
   ::= {er1645v2PortSwEIbwEntry 4064608256}

er1645v2PortSwEIbwActCirActEthDei5 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth5

       Possibilities:
               unchanged   (255)
               clear   (0)
               set   (1)"
   ::= {er1645v2PortSwEIbwEntry 4065918976}

er1645v2PortSwEIbwActCirActEthCos6 OBJECT-TYPE
   SYNTAX      INTEGER
               {
               unchanged (256)
               }
   MAX-ACCESS  read-write
   STATUS      current
   DESCRIPTION
      "Path: ethernet3.editConf.inboundBandwidth.action.cirAction.ethernet.cosDepth6

       Possibilities:
               unchanged   (256)"
   ::= {er1645v2PortSwEIbwEntry 4064673792}

er1645v2PortSwEIbwActCirActEthDei6 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth6

       Possibilities:
               unchanged   (255)
               clear   (0)
               set   (1)"
   ::= {er1645v2PortSwEIbwEntry 4065984512}

er1645v2PortSwEIbwActCirActEthCos7 OBJECT-TYPE
   SYNTAX      INTEGER
               {
               unchanged (256)
               }
   MAX-ACCESS  read-write
   STATUS      current
   DESCRIPTION
      "Path: ethernet3.editConf.inboundBandwidth.action.cirAction.ethernet.cosDepth7

       Possibilities:
               unchanged   (256)"
   ::= {er1645v2PortSwEIbwEntry 4064739328}

er1645v2PortSwEIbwActCirActEthDei7 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth7

       Possibilities:
               unchanged   (255)
               clear   (0)
               set   (1)"
   ::= {er1645v2PortSwEIbwEntry 4066050048}

er1645v2PortSwEIbwActCirActEthCos8 OBJECT-TYPE
   SYNTAX      INTEGER
               {
               unchanged (256)
               }
   MAX-ACCESS  read-write
   STATUS      current
   DESCRIPTION
      "Path: ethernet3.editConf.inboundBandwidth.action.cirAction.ethernet.cosDepth8

       Possibilities:
               unchanged   (256)"
   ::= {er1645v2PortSwEIbwEntry 4064804864}

er1645v2PortSwEIbwActCirActEthDei8 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth8

       Possibilities:
               unchanged   (255)
               clear   (0)
               set   (1)"
   ::= {er1645v2PortSwEIbwEntry 4066115584}

er1645v2PortSwEIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEIbwEntry 4064870400}

er1645v2PortSwEIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwEIbwEntry 4064935936}

er1645v2PortSwEIbwActCirActEthDrpLev OBJECT-TYPE
   SYNTAX      INTEGER
               {
               unchanged (0)
               }
   MAX-ACCESS  read-write
   STATUS      current
   DESCRIPTION
      "Path: ethernet3.editConf.inboundBandwidth.action.cirAction.ethernet.dropLevel

       Possibilities:
               unchanged   (0)"
   ::= {er1645v2PortSwEIbwEntry 4065001472}

er1645v2PortSwEIbwActCirActEthDeFlag OBJECT-TYPE
   SYNTAX      INTEGER
               {
               unchanged (255),
               clear (0),
               set (1)
               }
   MAX-ACCESS  read-write
   STATUS      current
   DESCRIPTION
      "Path: ethernet3.editConf.inboundBandwidth.action.cirAction.ethernet.deFlag

       Possibilities:
               unchanged   (255)
               clear   (0)
               set   (1)"
   ::= {er1645v2PortSwEIbwEntry 4065198080}

er1645v2PortSwEIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEIbwEntry 4071161856}

er1645v2PortSwEIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwEIbwEntry 4071227392}

er1645v2PortSwEIbwActCirActIpDrpLev OBJECT-TYPE
   SYNTAX      INTEGER
               {
               unchanged (0)
               }
   MAX-ACCESS  read-write
   STATUS      current
   DESCRIPTION
      "Path: ethernet3.editConf.inboundBandwidth.action.cirAction.ip.dropLevel

       Possibilities:
               unchanged   (0)"
   ::= {er1645v2PortSwEIbwEntry 4071292928}

er1645v2PortSwEIbwActCirActIpDeFlag OBJECT-TYPE
   SYNTAX      INTEGER
               {
               unchanged (255),
               clear (0),
               set (1)
               }
   MAX-ACCESS  read-write
   STATUS      current
   DESCRIPTION
      "Path: ethernet3.editConf.inboundBandwidth.action.cirAction.ip.deFlag

       Possibilities:
               unchanged   (255)
               clear   (0)
               set   (1)"
   ::= {er1645v2PortSwEIbwEntry 4071489536}

er1645v2PortSwEIbwActEirActNone OBJECT-TYPE
   SYNTAX      OCTET STRING
   MAX-ACCESS  read-write
   STATUS      current
   DESCRIPTION
      "Path: ethernet3.editConf.inboundBandwidth.action.eirAction.none"
   ::= {er1645v2PortSwEIbwEntry 4095737856}

er1645v2PortSwEIbwActEirActEthCos1 OBJECT-TYPE
   SYNTAX      INTEGER
               {
               unchanged (256)
               }
   MAX-ACCESS  read-write
   STATUS      current
   DESCRIPTION
      "Path: ethernet3.editConf.inboundBandwidth.action.eirAction.ethernet.cosDepth1

       Possibilities:
               unchanged   (256)"
   ::= {er1645v2PortSwEIbwEntry 4097900544}

er1645v2PortSwEIbwActEirActEthDei1 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth1

       Possibilities:
               unchanged   (255)
               clear   (0)
               set   (1)"
   ::= {er1645v2PortSwEIbwEntry 4099211264}

er1645v2PortSwEIbwActEirActEthCos2 OBJECT-TYPE
   SYNTAX      INTEGER
               {
               unchanged (256)
               }
   MAX-ACCESS  read-write
   STATUS      current
   DESCRIPTION
      "Path: ethernet3.editConf.inboundBandwidth.action.eirAction.ethernet.cosDepth2

       Possibilities:
               unchanged   (256)"
   ::= {er1645v2PortSwEIbwEntry 4097966080}

er1645v2PortSwEIbwActEirActEthDei2 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth2

       Possibilities:
               unchanged   (255)
               clear   (0)
               set   (1)"
   ::= {er1645v2PortSwEIbwEntry 4099276800}

er1645v2PortSwEIbwActEirActEthCos3 OBJECT-TYPE
   SYNTAX      INTEGER
               {
               unchanged (256)
               }
   MAX-ACCESS  read-write
   STATUS      current
   DESCRIPTION
      "Path: ethernet3.editConf.inboundBandwidth.action.eirAction.ethernet.cosDepth3

       Possibilities:
               unchanged   (256)"
   ::= {er1645v2PortSwEIbwEntry 4098031616}

er1645v2PortSwEIbwActEirActEthDei3 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth3

       Possibilities:
               unchanged   (255)
               clear   (0)
               set   (1)"
   ::= {er1645v2PortSwEIbwEntry 4099342336}

er1645v2PortSwEIbwActEirActEthCos4 OBJECT-TYPE
   SYNTAX      INTEGER
               {
               unchanged (256)
               }
   MAX-ACCESS  read-write
   STATUS      current
   DESCRIPTION
      "Path: ethernet3.editConf.inboundBandwidth.action.eirAction.ethernet.cosDepth4

       Possibilities:
               unchanged   (256)"
   ::= {er1645v2PortSwEIbwEntry 4098097152}

er1645v2PortSwEIbwActEirActEthDei4 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth4

       Possibilities:
               unchanged   (255)
               clear   (0)
               set   (1)"
   ::= {er1645v2PortSwEIbwEntry 4099407872}

er1645v2PortSwEIbwActEirActEthCos5 OBJECT-TYPE
   SYNTAX      INTEGER
               {
               unchanged (256)
               }
   MAX-ACCESS  read-write
   STATUS      current
   DESCRIPTION
      "Path: ethernet3.editConf.inboundBandwidth.action.eirAction.ethernet.cosDepth5

       Possibilities:
               unchanged   (256)"
   ::= {er1645v2PortSwEIbwEntry 4098162688}

er1645v2PortSwEIbwActEirActEthDei5 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth5

       Possibilities:
               unchanged   (255)
               clear   (0)
               set   (1)"
   ::= {er1645v2PortSwEIbwEntry 4099473408}

er1645v2PortSwEIbwActEirActEthCos6 OBJECT-TYPE
   SYNTAX      INTEGER
               {
               unchanged (256)
               }
   MAX-ACCESS  read-write
   STATUS      current
   DESCRIPTION
      "Path: ethernet3.editConf.inboundBandwidth.action.eirAction.ethernet.cosDepth6

       Possibilities:
               unchanged   (256)"
   ::= {er1645v2PortSwEIbwEntry 4098228224}

er1645v2PortSwEIbwActEirActEthDei6 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth6

       Possibilities:
               unchanged   (255)
               clear   (0)
               set   (1)"
   ::= {er1645v2PortSwEIbwEntry 4099538944}

er1645v2PortSwEIbwActEirActEthCos7 OBJECT-TYPE
   SYNTAX      INTEGER
               {
               unchanged (256)
               }
   MAX-ACCESS  read-write
   STATUS      current
   DESCRIPTION
      "Path: ethernet3.editConf.inboundBandwidth.action.eirAction.ethernet.cosDepth7

       Possibilities:
               unchanged   (256)"
   ::= {er1645v2PortSwEIbwEntry 4098293760}

er1645v2PortSwEIbwActEirActEthDei7 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth7

       Possibilities:
               unchanged   (255)
               clear   (0)
               set   (1)"
   ::= {er1645v2PortSwEIbwEntry 4099604480}

er1645v2PortSwEIbwActEirActEthCos8 OBJECT-TYPE
   SYNTAX      INTEGER
               {
               unchanged (256)
               }
   MAX-ACCESS  read-write
   STATUS      current
   DESCRIPTION
      "Path: ethernet3.editConf.inboundBandwidth.action.eirAction.ethernet.cosDepth8

       Possibilities:
               unchanged   (256)"
   ::= {er1645v2PortSwEIbwEntry 4098359296}

er1645v2PortSwEIbwActEirActEthDei8 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth8

       Possibilities:
               unchanged   (255)
               clear   (0)
               set   (1)"
   ::= {er1645v2PortSwEIbwEntry 4099670016}

er1645v2PortSwEIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEIbwEntry 4098424832}

er1645v2PortSwEIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwEIbwEntry 4098490368}

er1645v2PortSwEIbwActEirActEthDrpLev OBJECT-TYPE
   SYNTAX      INTEGER
               {
               unchanged (0)
               }
   MAX-ACCESS  read-write
   STATUS      current
   DESCRIPTION
      "Path: ethernet3.editConf.inboundBandwidth.action.eirAction.ethernet.dropLevel

       Possibilities:
               unchanged   (0)"
   ::= {er1645v2PortSwEIbwEntry 4098555904}

er1645v2PortSwEIbwActEirActEthDeFlag OBJECT-TYPE
   SYNTAX      INTEGER
               {
               unchanged (255),
               clear (0),
               set (1)
               }
   MAX-ACCESS  read-write
   STATUS      current
   DESCRIPTION
      "Path: ethernet3.editConf.inboundBandwidth.action.eirAction.ethernet.deFlag

       Possibilities:
               unchanged   (255)
               clear   (0)
               set   (1)"
   ::= {er1645v2PortSwEIbwEntry 4098752512}

er1645v2PortSwEIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEIbwEntry 4104716288}

er1645v2PortSwEIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwEIbwEntry 4104781824}

er1645v2PortSwEIbwActEirActIpDrpLev OBJECT-TYPE
   SYNTAX      INTEGER
               {
               unchanged (0)
               }
   MAX-ACCESS  read-write
   STATUS      current
   DESCRIPTION
      "Path: ethernet3.editConf.inboundBandwidth.action.eirAction.ip.dropLevel

       Possibilities:
               unchanged   (0)"
   ::= {er1645v2PortSwEIbwEntry 4104847360}

er1645v2PortSwEIbwActEirActIpDeFlag OBJECT-TYPE
   SYNTAX      INTEGER
               {
               unchanged (255),
               clear (0),
               set (1)
               }
   MAX-ACCESS  read-write
   STATUS      current
   DESCRIPTION
      "Path: ethernet3.editConf.inboundBandwidth.action.eirAction.ip.deFlag

       Possibilities:
               unchanged   (255)
               clear   (0)
               set   (1)"
   ::= {er1645v2PortSwEIbwEntry 4105043968}

er1645v2PortSwEIbwActViolActNone OBJECT-TYPE
   SYNTAX      OCTET STRING
   MAX-ACCESS  read-write
   STATUS      current
   DESCRIPTION
      "Path: ethernet3.editConf.inboundBandwidth.action.violateAction.none"
   ::= {er1645v2PortSwEIbwEntry 4129292288}

er1645v2PortSwEIbwActViolActDrop OBJECT-TYPE
   SYNTAX      OCTET STRING
   MAX-ACCESS  read-write
   STATUS      current
   DESCRIPTION
      "Path: ethernet3.editConf.inboundBandwidth.action.violateAction.drop"
   ::= {er1645v2PortSwEIbwEntry 4133486592}

er1645v2PortSwEIbwActViolActEthCos1 OBJECT-TYPE
   SYNTAX      INTEGER
               {
               unchanged (256)
               }
   MAX-ACCESS  read-write
   STATUS      current
   DESCRIPTION
      "Path: ethernet3.editConf.inboundBandwidth.action.violateAction.ethernet.cosDepth1

       Possibilities:
               unchanged   (256)"
   ::= {er1645v2PortSwEIbwEntry 4131454976}

er1645v2PortSwEIbwActViolActEthDei1 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth1

       Possibilities:
               unchanged   (255)
               clear   (0)
               set   (1)"
   ::= {er1645v2PortSwEIbwEntry 4132765696}

er1645v2PortSwEIbwActViolActEthCos2 OBJECT-TYPE
   SYNTAX      INTEGER
               {
               unchanged (256)
               }
   MAX-ACCESS  read-write
   STATUS      current
   DESCRIPTION
      "Path: ethernet3.editConf.inboundBandwidth.action.violateAction.ethernet.cosDepth2

       Possibilities:
               unchanged   (256)"
   ::= {er1645v2PortSwEIbwEntry 4131520512}

er1645v2PortSwEIbwActViolActEthDei2 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth2

       Possibilities:
               unchanged   (255)
               clear   (0)
               set   (1)"
   ::= {er1645v2PortSwEIbwEntry 4132831232}

er1645v2PortSwEIbwActViolActEthCos3 OBJECT-TYPE
   SYNTAX      INTEGER
               {
               unchanged (256)
               }
   MAX-ACCESS  read-write
   STATUS      current
   DESCRIPTION
      "Path: ethernet3.editConf.inboundBandwidth.action.violateAction.ethernet.cosDepth3

       Possibilities:
               unchanged   (256)"
   ::= {er1645v2PortSwEIbwEntry 4131586048}

er1645v2PortSwEIbwActViolActEthDei3 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth3

       Possibilities:
               unchanged   (255)
               clear   (0)
               set   (1)"
   ::= {er1645v2PortSwEIbwEntry 4132896768}

er1645v2PortSwEIbwActViolActEthCos4 OBJECT-TYPE
   SYNTAX      INTEGER
               {
               unchanged (256)
               }
   MAX-ACCESS  read-write
   STATUS      current
   DESCRIPTION
      "Path: ethernet3.editConf.inboundBandwidth.action.violateAction.ethernet.cosDepth4

       Possibilities:
               unchanged   (256)"
   ::= {er1645v2PortSwEIbwEntry 4131651584}

er1645v2PortSwEIbwActViolActEthDei4 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth4

       Possibilities:
               unchanged   (255)
               clear   (0)
               set   (1)"
   ::= {er1645v2PortSwEIbwEntry 4132962304}

er1645v2PortSwEIbwActViolActEthCos5 OBJECT-TYPE
   SYNTAX      INTEGER
               {
               unchanged (256)
               }
   MAX-ACCESS  read-write
   STATUS      current
   DESCRIPTION
      "Path: ethernet3.editConf.inboundBandwidth.action.violateAction.ethernet.cosDepth5

       Possibilities:
               unchanged   (256)"
   ::= {er1645v2PortSwEIbwEntry 4131717120}

er1645v2PortSwEIbwActViolActEthDei5 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth5

       Possibilities:
               unchanged   (255)
               clear   (0)
               set   (1)"
   ::= {er1645v2PortSwEIbwEntry 4133027840}

er1645v2PortSwEIbwActViolActEthCos6 OBJECT-TYPE
   SYNTAX      INTEGER
               {
               unchanged (256)
               }
   MAX-ACCESS  read-write
   STATUS      current
   DESCRIPTION
      "Path: ethernet3.editConf.inboundBandwidth.action.violateAction.ethernet.cosDepth6

       Possibilities:
               unchanged   (256)"
   ::= {er1645v2PortSwEIbwEntry 4131782656}

er1645v2PortSwEIbwActViolActEthDei6 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth6

       Possibilities:
               unchanged   (255)
               clear   (0)
               set   (1)"
   ::= {er1645v2PortSwEIbwEntry 4133093376}

er1645v2PortSwEIbwActViolActEthCos7 OBJECT-TYPE
   SYNTAX      INTEGER
               {
               unchanged (256)
               }
   MAX-ACCESS  read-write
   STATUS      current
   DESCRIPTION
      "Path: ethernet3.editConf.inboundBandwidth.action.violateAction.ethernet.cosDepth7

       Possibilities:
               unchanged   (256)"
   ::= {er1645v2PortSwEIbwEntry 4131848192}

er1645v2PortSwEIbwActViolActEthDei7 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth7

       Possibilities:
               unchanged   (255)
               clear   (0)
               set   (1)"
   ::= {er1645v2PortSwEIbwEntry 4133158912}

er1645v2PortSwEIbwActViolActEthCos8 OBJECT-TYPE
   SYNTAX      INTEGER
               {
               unchanged (256)
               }
   MAX-ACCESS  read-write
   STATUS      current
   DESCRIPTION
      "Path: ethernet3.editConf.inboundBandwidth.action.violateAction.ethernet.cosDepth8

       Possibilities:
               unchanged   (256)"
   ::= {er1645v2PortSwEIbwEntry 4131913728}

er1645v2PortSwEIbwActViolActEthDei8 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth8

       Possibilities:
               unchanged   (255)
               clear   (0)
               set   (1)"
   ::= {er1645v2PortSwEIbwEntry 4133224448}

er1645v2PortSwEIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEIbwEntry 4131979264}

er1645v2PortSwEIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PortSwEIbwEntry 4132044800}

er1645v2PortSwEIbwActViolActEthDrpLev OBJECT-TYPE
   SYNTAX      INTEGER
               {
               unchanged (0)
               }
   MAX-ACCESS  read-write
   STATUS      current
   DESCRIPTION
      "Path: ethernet3.editConf.inboundBandwidth.action.violateAction.ethernet.dropLevel

       Possibilities:
               unchanged   (0)"
   ::= {er1645v2PortSwEIbwEntry 4132110336}

er1645v2PortSwEIbwActViolActEthDeFlag OBJECT-TYPE
   SYNTAX      INTEGER
               {
               unchanged (255),
               clear (0),
               set (1)
               }
   MAX-ACCESS  read-write
   STATUS      current
   DESCRIPTION
      "Path: ethernet3.editConf.inboundBandwidth.action.violateAction.ethernet.deFlag

       Possibilities:
               unchanged   (255)
               clear   (0)
               set   (1)"
   ::= {er1645v2PortSwEIbwEntry 4132306944}

er1645v2PortSwEIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PortSwEIbwEntry 4138270720}

er1645v2PortSwEIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PortSwEIbwEntry 4138336256}

er1645v2PortSwEIbwActViolActIpDrpLev OBJECT-TYPE
   SYNTAX      INTEGER
               {
               unchanged (0)
               }
   MAX-ACCESS  read-write
   STATUS      current
   DESCRIPTION
      "Path: ethernet3.editConf.inboundBandwidth.action.violateAction.ip.dropLevel

       Possibilities:
               unchanged   (0)"
   ::= {er1645v2PortSwEIbwEntry 4138401792}

er1645v2PortSwEIbwActViolActIpDeFlag OBJECT-TYPE
   SYNTAX      INTEGER
               {
               unchanged (255),
               clear (0),
               set (1)
               }
   MAX-ACCESS  read-write
   STATUS      current
   DESCRIPTION
      "Path: ethernet3.editConf.inboundBandwidth.action.violateAction.ip.deFlag

       Possibilities:
               unchanged   (255)
               clear   (0)
               set   (1)"
   ::= {er1645v2PortSwEIbwEntry 4138598400}

er1645v2PortSwEIbwSubInterfacesExcluded OBJECT-TYPE
   SYNTAX      INTEGER
               {
               s (1)
               }
   MAX-ACCESS  read-write
   STATUS      current
   DESCRIPTION
      "Path: ethernet3.editConf.inboundBandwidth.subInterfaces.excluded

       Possibilities:
                  (1)"
   ::= {er1645v2PortSwEIbwEntry 2416967680}

er1645v2PortSwEIbwSubInterfacesIncludedInAccessList OBJECT-TYPE
   SYNTAX      DisplayString
   MAX-ACCESS  read-write
   STATUS      current
   DESCRIPTION
      "Path: ethernet3.editConf.inboundBandwidth.subInterfaces.included.inAccessList"
   ::= {er1645v2PortSwEIbwEntry 2418020352}


er1645v2PortSwEInboundNUcastPriority OBJECT IDENTIFIER ::= {er1645v2PortSwE 230}

er1645v2PortSwEInboundNUcastPrioritySSC OBJECT IDENTIFIER ::= {er1645v2PortSwEInboundNUcastPriority 1}

er1645v2PortSwEInboundNUcastPriorityEntry OBJECT IDENTIFIER ::= {er1645v2PortSwEInboundNUcastPrioritySSC 1}

er1645v2PortSwEInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.broadcast

       Possibilities:
               queue1   (0)
               queue2   (1)
               queue3   (2)
               queue4   (3)
               queue5   (4)
               lowDelayQueue   (5)
               lowDelay2Queue   (6)
               systemQueue   (7)"
   ::= {er1645v2PortSwEInboundNUcastPriorityEntry 16777216}

er1645v2PortSwEInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.multicast

       Possibilities:
               queue1   (0)
               queue2   (1)
               queue3   (2)
               queue4   (3)
               queue5   (4)
               lowDelayQueue   (5)
               lowDelay2Queue   (6)
               systemQueue   (7)"
   ::= {er1645v2PortSwEInboundNUcastPriorityEntry 33554432}


er1645v2PortSwEInboundHwPriority OBJECT IDENTIFIER ::= {er1645v2PortSwE 231}

er1645v2PortSwEInboundHwPrioritySSC OBJECT IDENTIFIER ::= {er1645v2PortSwEInboundHwPriority 1}

er1645v2PortSwEInboundHwPriorityEntry OBJECT IDENTIFIER ::= {er1645v2PortSwEInboundHwPrioritySSC 1}

er1645v2PortSwEInboundHwPriorityNone OBJECT-TYPE
   SYNTAX      OCTET STRING
   MAX-ACCESS  read-write
   STATUS      current
   DESCRIPTION
      "Path: ethernet3.editConf.inboundHwPriority.none"
   ::= {er1645v2PortSwEInboundHwPriorityEntry 16777216}

er1645v2PortSwEInboundHwPriorityMapCosToQueueP0 OBJECT-TYPE
   SYNTAX      INTEGER
               {
               queue1 (1),
               queue2 (2)
               }
   MAX-ACCESS  read-write
   STATUS      current
   DESCRIPTION
      "Path: ethernet3.editConf.inboundHwPriority.mapCosToQueue.p0

       Possibilities:
               queue1   (1)
               queue2   (2)"
   ::= {er1645v2PortSwEInboundHwPriorityEntry 33619968}

er1645v2PortSwEInboundHwPriorityMapCosToQueueP1 OBJECT-TYPE
   SYNTAX      INTEGER
               {
               queue1 (1),
               queue2 (2)
               }
   MAX-ACCESS  read-write
   STATUS      current
   DESCRIPTION
      "Path: ethernet3.editConf.inboundHwPriority.mapCosToQueue.p1

       Possibilities:
               queue1   (1)
               queue2   (2)"
   ::= {er1645v2PortSwEInboundHwPriorityEntry 33685504}

er1645v2PortSwEInboundHwPriorityMapCosToQueueP2 OBJECT-TYPE
   SYNTAX      INTEGER
               {
               queue1 (1),
               queue2 (2)
               }
   MAX-ACCESS  read-write
   STATUS      current
   DESCRIPTION
      "Path: ethernet3.editConf.inboundHwPriority.mapCosToQueue.p2

       Possibilities:
               queue1   (1)
               queue2   (2)"
   ::= {er1645v2PortSwEInboundHwPriorityEntry 33751040}

er1645v2PortSwEInboundHwPriorityMapCosToQueueP3 OBJECT-TYPE
   SYNTAX      INTEGER
               {
               queue1 (1),
               queue2 (2)
               }
   MAX-ACCESS  read-write
   STATUS      current
   DESCRIPTION
      "Path: ethernet3.editConf.inboundHwPriority.mapCosToQueue.p3

       Possibilities:
               queue1   (1)
               queue2   (2)"
   ::= {er1645v2PortSwEInboundHwPriorityEntry 33816576}

er1645v2PortSwEInboundHwPriorityMapCosToQueueP4 OBJECT-TYPE
   SYNTAX      INTEGER
               {
               queue1 (1),
               queue2 (2)
               }
   MAX-ACCESS  read-write
   STATUS      current
   DESCRIPTION
      "Path: ethernet3.editConf.inboundHwPriority.mapCosToQueue.p4

       Possibilities:
               queue1   (1)
               queue2   (2)"
   ::= {er1645v2PortSwEInboundHwPriorityEntry 33882112}

er1645v2PortSwEInboundHwPriorityMapCosToQueueP5 OBJECT-TYPE
   SYNTAX      INTEGER
               {
               queue1 (1),
               queue2 (2)
               }
   MAX-ACCESS  read-write
   STATUS      current
   DESCRIPTION
      "Path: ethernet3.editConf.inboundHwPriority.mapCosToQueue.p5

       Possibilities:
               queue1   (1)
               queue2   (2)"
   ::= {er1645v2PortSwEInboundHwPriorityEntry 33947648}

er1645v2PortSwEInboundHwPriorityMapCosToQueueP6 OBJECT-TYPE
   SYNTAX      INTEGER
               {
               queue1 (1),
               queue2 (2)
               }
   MAX-ACCESS  read-write
   STATUS      current
   DESCRIPTION
      "Path: ethernet3.editConf.inboundHwPriority.mapCosToQueue.p6

       Possibilities:
               queue1   (1)
               queue2   (2)"
   ::= {er1645v2PortSwEInboundHwPriorityEntry 34013184}

er1645v2PortSwEInboundHwPriorityMapCosToQueueP7 OBJECT-TYPE
   SYNTAX      INTEGER
               {
               queue1 (1),
               queue2 (2)
               }
   MAX-ACCESS  read-write
   STATUS      current
   DESCRIPTION
      "Path: ethernet3.editConf.inboundHwPriority.mapCosToQueue.p7

       Possibilities:
               queue1   (1)
               queue2   (2)"
   ::= {er1645v2PortSwEInboundHwPriorityEntry 34078720}

er1645v2PortSwEInboundHwPriorityMapDscpToQueue OBJECT-TYPE
   SYNTAX      SEQUENCE OF Er1645v2PortSwEInboundHwPriorityMapDscpToQueueEntry
   MAX-ACCESS  not-accessible
   STATUS      current
   DESCRIPTION
      ""
   ::= {er1645v2PortSwEInboundHwPriority 50331648}

er1645v2PortSwEInboundHwPriorityMapDscpToQueueEntry OBJECT-TYPE
   SYNTAX      Er1645v2PortSwEInboundHwPriorityMapDscpToQueueEntry
   MAX-ACCESS  not-accessible
   STATUS      current
   DESCRIPTION
      ""
   INDEX      { er1645v2PortSwEInboundHwPriorityMapDscpToQueueTableIx }
   ::= {er1645v2PortSwEInboundHwPriorityMapDscpToQueue 1}

Er1645v2PortSwEInboundHwPriorityMapDscpToQueueEntry ::=
   SEQUENCE
      {
      er1645v2PortSwEInboundHwPriorityMapDscpToQueueActions
         VariableLengthTableActions,
      er1645v2PortSwEInboundHwPriorityMapDscpToQueueTableIx
         TableIndex,
      er1645v2PortSwEInboundHwPriorityMapDscpToQueueStartDscp
         INTEGER,
      er1645v2PortSwEInboundHwPriorityMapDscpToQueueEndDscp
         INTEGER,
      er1645v2PortSwEInboundHwPriorityMapDscpToQueueQueue
         INTEGER
      }

er1645v2PortSwEInboundHwPriorityMapDscpToQueueActions OBJECT-TYPE
   SYNTAX      VariableLengthTableActions
   MAX-ACCESS  read-write
   STATUS      current
   DESCRIPTION
      "By way of this field, some manipulations
       on this table may be performed."
   ::= {er1645v2PortSwEInboundHwPriorityMapDscpToQueueEntry 2}

er1645v2PortSwEInboundHwPriorityMapDscpToQueueTableIx OBJECT-TYPE
   SYNTAX      TableIndex
   MAX-ACCESS  not-accessible
   STATUS      current
   DESCRIPTION
      ""
   ::= {er1645v2PortSwEInboundHwPriorityMapDscpToQueueEntry 11}

er1645v2PortSwEInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2PortSwEInboundHwPriorityMapDscpToQueueEntry 16777216}

er1645v2PortSwEInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2PortSwEInboundHwPriorityMapDscpToQueueEntry 33554432}

er1645v2PortSwEInboundHwPriorityMapDscpToQueueQueue OBJECT-TYPE
   SYNTAX      INTEGER
               {
               queue1 (1),
               queue2 (2)
               }
   MAX-ACCESS  read-write
   STATUS      current
   DESCRIPTION
      "Path: ethernet3.editConf.inboundHwPriority.mapDscpToQueue.queue

       Possibilities:
               queue1   (1)
               queue2   (2)"
   ::= {er1645v2PortSwEInboundHwPriorityMapDscpToQueueEntry 50331648}


er1645v2PortSwEName OBJECT-TYPE
   SYNTAX      DisplayString
   MAX-ACCESS  read-write
   STATUS      current
   DESCRIPTION
      "Path: ethernet3.editConf.name
       Info: config interface name"
   ::= {er1645v2PortSwE 2}



sr1645v2PortSwE OBJECT IDENTIFIER ::= {r1645v2PortSwE 14}


sr1645v2PortSwEDescr OBJECT-TYPE
   SYNTAX      DisplayString
   MAX-ACCESS  read-only
   STATUS      current
   DESCRIPTION
      "Path: ethernet3.status.ifDescr
       Info: ifDescr"
   ::= {sr1645v2PortSwE 101}


sr1645v2PortSwEType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet3.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2PortSwE 102}


sr1645v2PortSwEMtu OBJECT-TYPE
   SYNTAX      Integer32
   MAX-ACCESS  read-only
   STATUS      current
   DESCRIPTION
      "Path: ethernet3.status.ifMtu
       Info: ifMtu"
   ::= {sr1645v2PortSwE 103}


sr1645v2PortSwEOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ifOperStatus
       Info: ifOperStatus

       Possibilities:
               up   (1)
               down   (2)
               testing   (3)
               unknown   (4)
               dormant   (5)
               notPresent   (6)
               lowerLayerDown   (7)"
   ::= {sr1645v2PortSwE 107}


sr1645v2PortSwELastChange OBJECT-TYPE
   SYNTAX      TimeTicks
   MAX-ACCESS  read-only
   STATUS      current
   DESCRIPTION
      "Path: ethernet3.status.ifLastChange
       Info: ifLastChange

       Time in centi-second."
   ::= {sr1645v2PortSwE 108}


sr1645v2PortSwELastChangeD OBJECT-TYPE
   SYNTAX      DisplayString
   MAX-ACCESS  read-only
   STATUS      current
   DESCRIPTION
      "Path: ethernet3.status.ifLastChangeDate
       Info: ifLastChangeDate"
   ::= {sr1645v2PortSwE 183}


sr1645v2PortSwESpeed OBJECT-TYPE
   SYNTAX      Gauge32
   MAX-ACCESS  read-only
   STATUS      current
   DESCRIPTION
      "Path: ethernet3.status.ifSpeed
       Info: ifSpeed

       32 bit unsigned gauge value."
   ::= {sr1645v2PortSwE 104}


sr1645v2PortSwESnmpIndex OBJECT-TYPE
   SYNTAX      Integer32
   MAX-ACCESS  read-only
   STATUS      current
   DESCRIPTION
      "Path: ethernet3.status.snmpIndex
       Info: SNMP index assigned to this object"
   ::= {sr1645v2PortSwE 269}


sr1645v2PortSwEVtuTable OBJECT IDENTIFIER ::= {sr1645v2PortSwE 89}

sr1645v2PortSwEVtuTableSSCTable OBJECT-TYPE
   SYNTAX      SEQUENCE OF Sr1645v2PortSwEVtuTableEntry
   MAX-ACCESS  not-accessible
   STATUS      current
   DESCRIPTION
      "VTU table"
   ::= {sr1645v2PortSwEVtuTable 1}

sr1645v2PortSwEVtuTableEntry OBJECT-TYPE
   SYNTAX      Sr1645v2PortSwEVtuTableEntry
   MAX-ACCESS  not-accessible
   STATUS      current
   DESCRIPTION
      ""
   INDEX      { sr1645v2PortSwEVtuTableTableIx }
   ::= {sr1645v2PortSwEVtuTableSSCTable 1}

Sr1645v2PortSwEVtuTableEntry ::=
   SEQUENCE
      {
      sr1645v2PortSwEVtuTableTableIx
         TableIndex,
      sr1645v2PortSwEVtuTableVid
         INTEGER,
      sr1645v2PortSwEVtuTableHwPort1
         INTEGER,
      sr1645v2PortSwEVtuTableHwPort2
         INTEGER,
      sr1645v2PortSwEVtuTableHwPort3
         INTEGER,
      sr1645v2PortSwEVtuTableHwPort4
         INTEGER,
      sr1645v2PortSwEVtuTableHwPortLocalPort
         INTEGER,
      sr1645v2PortSwEVtuTableDbNum
         Integer32
      }

sr1645v2PortSwEVtuTableTableIx OBJECT-TYPE
   SYNTAX      TableIndex
   MAX-ACCESS  not-accessible
   STATUS      current
   DESCRIPTION
      ""
   ::= {sr1645v2PortSwEVtuTableEntry 11}

sr1645v2PortSwEVtuTableVid OBJECT-TYPE
   SYNTAX      INTEGER
               {
               untagged (0)
               }
   MAX-ACCESS  read-only
   STATUS      current
   DESCRIPTION
      "Path: ethernet3.status.vtuTable.vid

       Possibilities:
               untagged   (0)"
   ::= {sr1645v2PortSwEVtuTableEntry 16777216}

sr1645v2PortSwEVtuTableHwPort1 OBJECT-TYPE
   SYNTAX      INTEGER
               {
               pass (0),
               untag (1),
               tag (2),
               smm (3)
               }
   MAX-ACCESS  read-only
   STATUS      current
   DESCRIPTION
      "Path: ethernet3.status.vtuTable.hwPort1

       Possibilities:
               pass   (0)
               untag   (1)
               tag   (2)
               --   (3)"
   ::= {sr1645v2PortSwEVtuTableEntry 33554432}

sr1645v2PortSwEVtuTableHwPort2 OBJECT-TYPE
   SYNTAX      INTEGER
               {
               pass (0),
               untag (1),
               tag (2),
               smm (3)
               }
   MAX-ACCESS  read-only
   STATUS      current
   DESCRIPTION
      "Path: ethernet3.status.vtuTable.hwPort2

       Possibilities:
               pass   (0)
               untag   (1)
               tag   (2)
               --   (3)"
   ::= {sr1645v2PortSwEVtuTableEntry 50331648}

sr1645v2PortSwEVtuTableHwPort3 OBJECT-TYPE
   SYNTAX      INTEGER
               {
               pass (0),
               untag (1),
               tag (2),
               smm (3)
               }
   MAX-ACCESS  read-only
   STATUS      current
   DESCRIPTION
      "Path: ethernet3.status.vtuTable.hwPort3

       Possibilities:
               pass   (0)
               untag   (1)
               tag   (2)
               --   (3)"
   ::= {sr1645v2PortSwEVtuTableEntry 67108864}

sr1645v2PortSwEVtuTableHwPort4 OBJECT-TYPE
   SYNTAX      INTEGER
               {
               pass (0),
               untag (1),
               tag (2),
               smm (3)
               }
   MAX-ACCESS  read-only
   STATUS      current
   DESCRIPTION
      "Path: ethernet3.status.vtuTable.hwPort4

       Possibilities:
               pass   (0)
               untag   (1)
               tag   (2)
               --   (3)"
   ::= {sr1645v2PortSwEVtuTableEntry 83886080}

sr1645v2PortSwEVtuTableHwPortLocalPort OBJECT-TYPE
   SYNTAX      INTEGER
               {
               pass (0),
               untag (1),
               tag (2),
               smm (3)
               }
   MAX-ACCESS  read-only
   STATUS      current
   DESCRIPTION
      "Path: ethernet3.status.vtuTable.hwPortLocalPort

       Possibilities:
               pass   (0)
               untag   (1)
               tag   (2)
               --   (3)"
   ::= {sr1645v2PortSwEVtuTableEntry 117440512}

sr1645v2PortSwEVtuTableDbNum OBJECT-TYPE
   SYNTAX      Integer32
   MAX-ACCESS  read-only
   STATUS      current
   DESCRIPTION
      "Path: ethernet3.status.vtuTable.dbNum"
   ::= {sr1645v2PortSwEVtuTableEntry 134217728}


sr1645v2PortSwEPorts OBJECT IDENTIFIER ::= {sr1645v2PortSwE 146}

sr1645v2PortSwEPortsSSCTable OBJECT-TYPE
   SYNTAX      SEQUENCE OF Sr1645v2PortSwEPortsEntry
   MAX-ACCESS  not-accessible
   STATUS      current
   DESCRIPTION
      "Ethernet Switch 8 Gigabit Ports Status without vlan"
   ::= {sr1645v2PortSwEPorts 1}

sr1645v2PortSwEPortsEntry OBJECT-TYPE
   SYNTAX      Sr1645v2PortSwEPortsEntry
   MAX-ACCESS  not-accessible
   STATUS      current
   DESCRIPTION
      ""
   INDEX      { sr1645v2PortSwEPortsTableIx }
   ::= {sr1645v2PortSwEPortsSSCTable 1}

Sr1645v2PortSwEPortsEntry ::=
   SEQUENCE
      {
      sr1645v2PortSwEPortsTableIx
         TableIndex,
      sr1645v2PortSwEPortsPortName
         INTEGER,
      sr1645v2PortSwEPortsOperStatus
         INTEGER,
      sr1645v2PortSwEPortsSpeed
         INTEGER,
      sr1645v2PortSwEPortsDuplex
         INTEGER,
      sr1645v2PortSwEPortsAutoNeg
         INTEGER,
      sr1645v2PortSwEPortsPartnerCapsFlowCtrl
         INTEGER,
      sr1645v2PortSwEPortsPartnerCapsHD10
         INTEGER,
      sr1645v2PortSwEPortsPartnerCapsFD10
         INTEGER,
      sr1645v2PortSwEPortsPartnerCapsHD100
         INTEGER,
      sr1645v2PortSwEPortsPartnerCapsFD100
         INTEGER,
      sr1645v2PortSwEPortsCir
         Integer32,
      sr1645v2PortSwEPortsSwPort
         INTEGER
      }

sr1645v2PortSwEPortsTableIx OBJECT-TYPE
   SYNTAX      TableIndex
   MAX-ACCESS  not-accessible
   STATUS      current
   DESCRIPTION
      ""
   ::= {sr1645v2PortSwEPortsEntry 11}

sr1645v2PortSwEPortsPortName OBJECT-TYPE
   SYNTAX      INTEGER
               {
               hwPortu1 (1),
               hwPortu2 (2),
               hwPortu3 (3),
               hwPortu4 (4),
               hwPortu5 (5),
               hwPortu6 (6),
               hwPortu7 (7),
               hwPortu8 (8),
               hwPortuLocalPort (255)
               }
   MAX-ACCESS  read-only
   STATUS      current
   DESCRIPTION
      "Path: ethernet3.status.ports.portName

       Possibilities:
               hwPort_1   (1)
               hwPort_2   (2)
               hwPort_3   (3)
               hwPort_4   (4)
               hwPort_5   (5)
               hwPort_6   (6)
               hwPort_7   (7)
               hwPort_8   (8)
               hwPort_LocalPort   (255)"
   ::= {sr1645v2PortSwEPortsEntry 16777216}

sr1645v2PortSwEPortsOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ports.ifOperStatus

       Possibilities:
               up   (1)
               down   (2)
               testing   (3)
               unknown   (4)
               dormant   (5)
               notPresent   (6)
               lowerLayerDown   (7)"
   ::= {sr1645v2PortSwEPortsEntry 33554432}

sr1645v2PortSwEPortsSpeed OBJECT-TYPE
   SYNTAX      INTEGER
               {
               s10 (0),
               s100 (1),
               s1000 (2),
               s200 (3)
               }
   MAX-ACCESS  read-only
   STATUS      current
   DESCRIPTION
      "Path: ethernet3.status.ports.speed

       Possibilities:
               10   (0)
               100   (1)
               1000   (2)
               200   (3)"
   ::= {sr1645v2PortSwEPortsEntry 50331648}

sr1645v2PortSwEPortsDuplex OBJECT-TYPE
   SYNTAX      INTEGER
               {
               halfDuplex (0),
               fullDuplex (1)
               }
   MAX-ACCESS  read-only
   STATUS      current
   DESCRIPTION
      "Path: ethernet3.status.ports.duplex

       Possibilities:
               halfDuplex   (0)
               fullDuplex   (1)"
   ::= {sr1645v2PortSwEPortsEntry 67108864}

sr1645v2PortSwEPortsAutoNeg OBJECT-TYPE
   SYNTAX      INTEGER
               {
               disabled (0),
               done (1),
               notDone (2)
               }
   MAX-ACCESS  read-only
   STATUS      current
   DESCRIPTION
      "Path: ethernet3.status.ports.autoNegotiate

       Possibilities:
               disabled   (0)
               done   (1)
               notDone   (2)"
   ::= {sr1645v2PortSwEPortsEntry 83886080}

sr1645v2PortSwEPortsPartnerCapsFlowCtrl OBJECT-TYPE
   SYNTAX      INTEGER
               {
               notCapable (0),
               capable (1),
               unknown (2)
               }
   MAX-ACCESS  read-only
   STATUS      current
   DESCRIPTION
      "Path: ethernet3.status.ports.linkPartnerCaps.flowControl

       Possibilities:
               notCapable   (0)
               capable   (1)
               unknown   (2)"
   ::= {sr1645v2PortSwEPortsEntry 100728832}

sr1645v2PortSwEPortsPartnerCapsHD10 OBJECT-TYPE
   SYNTAX      INTEGER
               {
               notCapable (0),
               capable (1),
               unknown (2)
               }
   MAX-ACCESS  read-only
   STATUS      current
   DESCRIPTION
      "Path: ethernet3.status.ports.linkPartnerCaps.10Mb/halfDuplex

       Possibilities:
               notCapable   (0)
               capable   (1)
               unknown   (2)"
   ::= {sr1645v2PortSwEPortsEntry 100794368}

sr1645v2PortSwEPortsPartnerCapsFD10 OBJECT-TYPE
   SYNTAX      INTEGER
               {
               notCapable (0),
               capable (1),
               unknown (2)
               }
   MAX-ACCESS  read-only
   STATUS      current
   DESCRIPTION
      "Path: ethernet3.status.ports.linkPartnerCaps.10Mb/fullDuplex

       Possibilities:
               notCapable   (0)
               capable   (1)
               unknown   (2)"
   ::= {sr1645v2PortSwEPortsEntry 100859904}

sr1645v2PortSwEPortsPartnerCapsHD100 OBJECT-TYPE
   SYNTAX      INTEGER
               {
               notCapable (0),
               capable (1),
               unknown (2)
               }
   MAX-ACCESS  read-only
   STATUS      current
   DESCRIPTION
      "Path: ethernet3.status.ports.linkPartnerCaps.100Mb/halfDuplex

       Possibilities:
               notCapable   (0)
               capable   (1)
               unknown   (2)"
   ::= {sr1645v2PortSwEPortsEntry 100925440}

sr1645v2PortSwEPortsPartnerCapsFD100 OBJECT-TYPE
   SYNTAX      INTEGER
               {
               notCapable (0),
               capable (1),
               unknown (2)
               }
   MAX-ACCESS  read-only
   STATUS      current
   DESCRIPTION
      "Path: ethernet3.status.ports.linkPartnerCaps.100Mb/fullDuplex

       Possibilities:
               notCapable   (0)
               capable   (1)
               unknown   (2)"
   ::= {sr1645v2PortSwEPortsEntry 100990976}

sr1645v2PortSwEPortsCir OBJECT-TYPE
   SYNTAX      Integer32
   MAX-ACCESS  read-only
   STATUS      current
   DESCRIPTION
      "Path: ethernet3.status.ports.cir"
   ::= {sr1645v2PortSwEPortsEntry 134217728}

sr1645v2PortSwEPortsSwPort OBJECT-TYPE
   SYNTAX      INTEGER
               {
               swPort1 (1),
               swPort2 (2),
               swPort3 (3),
               swPort4 (4),
               swPort5 (5),
               swPort6 (6),
               swPort7 (7),
               swPort8 (8),
               none (255),
               all (65535)
               }
   MAX-ACCESS  read-only
   STATUS      current
   DESCRIPTION
      "Path: ethernet3.status.ports.swPort

       Possibilities:
               swPort[1]   (1)
               swPort[2]   (2)
               swPort[3]   (3)
               swPort[4]   (4)
               swPort[5]   (5)
               swPort[6]   (6)
               swPort[7]   (7)
               swPort[8]   (8)
               none   (255)
               all   (65535)"
   ::= {sr1645v2PortSwEPortsEntry 150994944}


sr1645v2PortSwESwitchCache OBJECT IDENTIFIER ::= {sr1645v2PortSwE 10}

sr1645v2PortSwESwitchCacheSSCTable OBJECT-TYPE
   SYNTAX      SEQUENCE OF Sr1645v2PortSwESwitchCacheEntry
   MAX-ACCESS  not-accessible
   STATUS      current
   DESCRIPTION
      "switch MAC cache"
   ::= {sr1645v2PortSwESwitchCache 1}

sr1645v2PortSwESwitchCacheEntry OBJECT-TYPE
   SYNTAX      Sr1645v2PortSwESwitchCacheEntry
   MAX-ACCESS  not-accessible
   STATUS      current
   DESCRIPTION
      ""
   INDEX      { sr1645v2PortSwESwitchCacheTableIx }
   ::= {sr1645v2PortSwESwitchCacheSSCTable 1}

Sr1645v2PortSwESwitchCacheEntry ::=
   SEQUENCE
      {
      sr1645v2PortSwESwitchCacheTableIx
         TableIndex,
      sr1645v2PortSwESwitchCacheMacAddress
         OCTET STRING,
      sr1645v2PortSwESwitchCachePort
         INTEGER,
      sr1645v2PortSwESwitchCacheType
         INTEGER,
      sr1645v2PortSwESwitchCacheTimeout
         TimeTicks,
      sr1645v2PortSwESwitchCacheDbNum
         Integer32
      }

sr1645v2PortSwESwitchCacheTableIx OBJECT-TYPE
   SYNTAX      TableIndex
   MAX-ACCESS  not-accessible
   STATUS      current
   DESCRIPTION
      ""
   ::= {sr1645v2PortSwESwitchCacheEntry 11}

sr1645v2PortSwESwitchCacheMacAddress OBJECT-TYPE
   SYNTAX      OCTET STRING
   MAX-ACCESS  read-only
   STATUS      current
   DESCRIPTION
      "Path: ethernet3.status.switchCache.macAddress

       MAC address."
   ::= {sr1645v2PortSwESwitchCacheEntry 16777216}

sr1645v2PortSwESwitchCachePort OBJECT-TYPE
   SYNTAX      INTEGER
               {
               none (0),
               hwPortu1 (1),
               hwPortu2 (2),
               hwPortu3 (3),
               hwPortu4 (4),
               hwPortu5 (5),
               hwPortu6 (6),
               hwPortu7 (7),
               hwPortu8 (8),
               hwPortuLocalPort (9)
               }
   MAX-ACCESS  read-only
   STATUS      current
   DESCRIPTION
      "Path: ethernet3.status.switchCache.port

       Possibilities:
               none   (0)
               hwPort_1   (1)
               hwPort_2   (2)
               hwPort_3   (3)
               hwPort_4   (4)
               hwPort_5   (5)
               hwPort_6   (6)
               hwPort_7   (7)
               hwPort_8   (8)
               hwPort_LocalPort   (9)"
   ::= {sr1645v2PortSwESwitchCacheEntry 33554432}

sr1645v2PortSwESwitchCacheType OBJECT-TYPE
   SYNTAX      INTEGER
               {
               static (0),
               dynamic (1)
               }
   MAX-ACCESS  read-only
   STATUS      current
   DESCRIPTION
      "Path: ethernet3.status.switchCache.type

       Possibilities:
               static   (0)
               dynamic   (1)"
   ::= {sr1645v2PortSwESwitchCacheEntry 50331648}

sr1645v2PortSwESwitchCacheTimeout OBJECT-TYPE
   SYNTAX      TimeTicks
   MAX-ACCESS  read-only
   STATUS      current
   DESCRIPTION
      "Path: ethernet3.status.switchCache.timeout

       Time in centi-second."
   ::= {sr1645v2PortSwESwitchCacheEntry 67108864}

sr1645v2PortSwESwitchCacheDbNum OBJECT-TYPE
   SYNTAX      Integer32
   MAX-ACCESS  read-only
   STATUS      current
   DESCRIPTION
      "Path: ethernet3.status.switchCache.dbNum"
   ::= {sr1645v2PortSwESwitchCacheEntry 83886080}



pr1645v2PortSwE OBJECT IDENTIFIER ::= {r1645v2PortSwE 12}


pr1645v2PortSwEInOctets OBJECT-TYPE
   SYNTAX      Counter64
   MAX-ACCESS  read-only
   STATUS      current
   DESCRIPTION
      "Path: ethernet3.performance.ifInOctets
       Info: ifInOctets

       64 bit unsigned wrappable counter."
   ::= {pr1645v2PortSwE 109}


pr1645v2PortSwEInUcast OBJECT-TYPE
   SYNTAX      Counter64
   MAX-ACCESS  read-only
   STATUS      current
   DESCRIPTION
      "Path: ethernet3.performance.ifInUcastPkts
       Info: ifInUcastPkts

       64 bit unsigned wrappable counter."
   ::= {pr1645v2PortSwE 110}


pr1645v2PortSwEInNUcastPkts OBJECT-TYPE
   SYNTAX      Counter64
   MAX-ACCESS  read-only
   STATUS      current
   DESCRIPTION
      "Path: ethernet3.performance.ifInNUcastPkts
       Info: ifInNUcastPkts

       64 bit unsigned wrappable counter."
   ::= {pr1645v2PortSwE 111}


pr1645v2PortSwEInBcastPkts OBJECT-TYPE
   SYNTAX      Counter64
   MAX-ACCESS  read-only
   STATUS      current
   DESCRIPTION
      "Path: ethernet3.performance.ifInBcastPkts
       Info: ifInBcastPkts

       64 bit unsigned wrappable counter."
   ::= {pr1645v2PortSwE 211}


pr1645v2PortSwEInMcastPkts OBJECT-TYPE
   SYNTAX      Counter64
   MAX-ACCESS  read-only
   STATUS      current
   DESCRIPTION
      "Path: ethernet3.performance.ifInMcastPkts
       Info: ifInNUcastPkts

       64 bit unsigned wrappable counter."
   ::= {pr1645v2PortSwE 221}


pr1645v2PortSwEInDiscards OBJECT-TYPE
   SYNTAX      Counter64
   MAX-ACCESS  read-only
   STATUS      current
   DESCRIPTION
      "Path: ethernet3.performance.ifInDiscards
       Info: ifInDiscards

       64 bit unsigned wrappable counter."
   ::= {pr1645v2PortSwE 112}


pr1645v2PortSwEInErrors OBJECT-TYPE
   SYNTAX      Counter64
   MAX-ACCESS  read-only
   STATUS      current
   DESCRIPTION
      "Path: ethernet3.performance.ifInErrors
       Info: ifInErrors

       64 bit unsigned wrappable counter."
   ::= {pr1645v2PortSwE 113}


pr1645v2PortSwEInUnknownProtos OBJECT-TYPE
   SYNTAX      Counter64
   MAX-ACCESS  read-only
   STATUS      current
   DESCRIPTION
      "Path: ethernet3.performance.ifInUnknownProtos
       Info: ifInUnknownprotos

       64 bit unsigned wrappable counter."
   ::= {pr1645v2PortSwE 114}


pr1645v2PortSwEInQLen OBJECT-TYPE
   SYNTAX      Gauge32
   MAX-ACCESS  read-only
   STATUS      current
   DESCRIPTION
      "Path: ethernet3.performance.ifInQLen
       Info: ifInQLen

       32 bit unsigned gauge value."
   ::= {pr1645v2PortSwE 128}


pr1645v2PortSwEInDropEx OBJECT-TYPE
   SYNTAX      Counter64
   MAX-ACCESS  read-only
   STATUS      current
   DESCRIPTION
      "Path: ethernet3.performance.ifInDropLevelExceeded
       Info: ifInDiscards

       64 bit unsigned wrappable counter."
   ::= {pr1645v2PortSwE 130}


pr1645v2PortSwEInDropNoMac OBJECT-TYPE
   SYNTAX      Counter64
   MAX-ACCESS  read-only
   STATUS      current
   DESCRIPTION
      "Path: ethernet3.performance.ifInDiscardsNoMacFit
       Info: ifInDiscards

       64 bit unsigned wrappable counter."
   ::= {pr1645v2PortSwE 133}


pr1645v2PortSwEInDropNUCast OBJECT-TYPE
   SYNTAX      Counter64
   MAX-ACCESS  read-only
   STATUS      current
   DESCRIPTION
      "Path: ethernet3.performance.ifInDiscardsNUCast
       Info: ifInDiscards

       64 bit unsigned wrappable counter."
   ::= {pr1645v2PortSwE 136}


pr1645v2PortSwEInDropFilter OBJECT-TYPE
   SYNTAX      Counter64
   MAX-ACCESS  read-only
   STATUS      current
   DESCRIPTION
      "Path: ethernet3.performance.ifInDiscardsFilter
       Info: ifInDiscards

       64 bit unsigned wrappable counter."
   ::= {pr1645v2PortSwE 137}


pr1645v2PortSwEInBandwidth OBJECT IDENTIFIER ::= {pr1645v2PortSwE 181}

pr1645v2PortSwEInBandwidthSSC OBJECT IDENTIFIER ::= {pr1645v2PortSwEInBandwidth 1}

pr1645v2PortSwEInBandwidthEntry OBJECT IDENTIFIER ::= {pr1645v2PortSwEInBandwidthSSC 1}

pr1645v2PortSwEInBandwidth15sec OBJECT-TYPE
   SYNTAX      Integer32
   MAX-ACCESS  read-only
   STATUS      current
   DESCRIPTION
      "Path: ethernet3.performance.ifInBandwidth.15sec

       unit name = bps
       formula = 8 * ; 8 /"
   ::= {pr1645v2PortSwEInBandwidthEntry 83886080}

pr1645v2PortSwEInBandwidth30sec OBJECT-TYPE
   SYNTAX      Integer32
   MAX-ACCESS  read-only
   STATUS      current
   DESCRIPTION
      "Path: ethernet3.performance.ifInBandwidth.30sec

       unit name = bps
       formula = 8 * ; 8 /"
   ::= {pr1645v2PortSwEInBandwidthEntry 167772160}

pr1645v2PortSwEInBandwidth1min OBJECT-TYPE
   SYNTAX      Integer32
   MAX-ACCESS  read-only
   STATUS      current
   DESCRIPTION
      "Path: ethernet3.performance.ifInBandwidth.1min

       unit name = bps
       formula = 8 * ; 8 /"
   ::= {pr1645v2PortSwEInBandwidthEntry 335544320}

pr1645v2PortSwEInBandwidth2min OBJECT-TYPE
   SYNTAX      Integer32
   MAX-ACCESS  read-only
   STATUS      current
   DESCRIPTION
      "Path: ethernet3.performance.ifInBandwidth.2min

       unit name = bps
       formula = 8 * ; 8 /"
   ::= {pr1645v2PortSwEInBandwidthEntry 671088640}

pr1645v2PortSwEInBandwidth5min OBJECT-TYPE
   SYNTAX      Integer32
   MAX-ACCESS  read-only
   STATUS      current
   DESCRIPTION
      "Path: ethernet3.performance.ifInBandwidth.5min

       unit name = bps
       formula = 8 * ; 8 /"
   ::= {pr1645v2PortSwEInBandwidthEntry 1677721600}


pr1645v2PortSwEOutOctets OBJECT-TYPE
   SYNTAX      Counter64
   MAX-ACCESS  read-only
   STATUS      current
   DESCRIPTION
      "Path: ethernet3.performance.ifOutOctets
       Info: ifOutOctets

       64 bit unsigned wrappable counter."
   ::= {pr1645v2PortSwE 115}


pr1645v2PortSwEOutUcastPkts OBJECT-TYPE
   SYNTAX      Counter64
   MAX-ACCESS  read-only
   STATUS      current
   DESCRIPTION
      "Path: ethernet3.performance.ifOutUcastPkts
       Info: ifOutUcastPkts

       64 bit unsigned wrappable counter."
   ::= {pr1645v2PortSwE 116}


pr1645v2PortSwEOutNUcastPkts OBJECT-TYPE
   SYNTAX      Counter64
   MAX-ACCESS  read-only
   STATUS      current
   DESCRIPTION
      "Path: ethernet3.performance.ifOutNUcastPkts
       Info: ifOutNUcastPkts

       64 bit unsigned wrappable counter."
   ::= {pr1645v2PortSwE 117}


pr1645v2PortSwEOutBcastPkts OBJECT-TYPE
   SYNTAX      Counter64
   MAX-ACCESS  read-only
   STATUS      current
   DESCRIPTION
      "Path: ethernet3.performance.ifOutBcastPkts
       Info: ifOutBcastPkts

       64 bit unsigned wrappable counter."
   ::= {pr1645v2PortSwE 217}


pr1645v2PortSwEOutMcastPkts OBJECT-TYPE
   SYNTAX      Counter64
   MAX-ACCESS  read-only
   STATUS      current
   DESCRIPTION
      "Path: ethernet3.performance.ifOutMcastPkts
       Info: ifOutMcastPkts

       64 bit unsigned wrappable counter."
   ::= {pr1645v2PortSwE 227}


pr1645v2PortSwEOutDiscards OBJECT-TYPE
   SYNTAX      Counter64
   MAX-ACCESS  read-only
   STATUS      current
   DESCRIPTION
      "Path: ethernet3.performance.ifOutDiscards
       Info: ifOutDiscards

       64 bit unsigned wrappable counter."
   ::= {pr1645v2PortSwE 118}


pr1645v2PortSwEOutErrors OBJECT-TYPE
   SYNTAX      Counter64
   MAX-ACCESS  read-only
   STATUS      current
   DESCRIPTION
      "Path: ethernet3.performance.ifOutErrors
       Info: ifOutErrors

       64 bit unsigned wrappable counter."
   ::= {pr1645v2PortSwE 119}


pr1645v2PortSwEOutQLen OBJECT-TYPE
   SYNTAX      Gauge32
   MAX-ACCESS  read-only
   STATUS      current
   DESCRIPTION
      "Path: ethernet3.performance.ifOutQLen
       Info: ifOutQLen

       32 bit unsigned gauge value."
   ::= {pr1645v2PortSwE 120}


pr1645v2PortSwEOutDropEx OBJECT-TYPE
   SYNTAX      Counter64
   MAX-ACCESS  read-only
   STATUS      current
   DESCRIPTION
      "Path: ethernet3.performance.ifOutDropLevelExceeded
       Info: ifOutDiscards

       64 bit unsigned wrappable counter."
   ::= {pr1645v2PortSwE 127}


pr1645v2PortSwEOutDropNoArp OBJECT-TYPE
   SYNTAX      Counter64
   MAX-ACCESS  read-only
   STATUS      current
   DESCRIPTION
      "Path: ethernet3.performance.ifOutDiscardsNoArp
       Info: ifOutDiscards

       64 bit unsigned wrappable counter."
   ::= {pr1645v2PortSwE 134}


pr1645v2PortSwEOutDropFilter OBJECT-TYPE
   SYNTAX      Counter64
   MAX-ACCESS  read-only
   STATUS      current
   DESCRIPTION
      "Path: ethernet3.performance.ifOutDiscardsFilter
       Info: ifOutDiscards

       64 bit unsigned wrappable counter."
   ::= {pr1645v2PortSwE 138}


pr1645v2PortSwEOutQueues OBJECT IDENTIFIER ::= {pr1645v2PortSwE 129}

pr1645v2PortSwEOutQueuesSSCTable OBJECT-TYPE
   SYNTAX      SEQUENCE OF Pr1645v2PortSwEOutQueuesEntry
   MAX-ACCESS  not-accessible
   STATUS      current
   DESCRIPTION
      "Queue Lengths"
   ::= {pr1645v2PortSwEOutQueues 1}

pr1645v2PortSwEOutQueuesEntry OBJECT-TYPE
   SYNTAX      Pr1645v2PortSwEOutQueuesEntry
   MAX-ACCESS  not-accessible
   STATUS      current
   DESCRIPTION
      ""
   INDEX      { pr1645v2PortSwEOutQueuesTableIx }
   ::= {pr1645v2PortSwEOutQueuesSSCTable 1}

Pr1645v2PortSwEOutQueuesEntry ::=
   SEQUENCE
      {
      pr1645v2PortSwEOutQueuesTableIx
         TableIndex,
      pr1645v2PortSwEOutQueuesName
         INTEGER,
      pr1645v2PortSwEOutQueuesLength
         Integer32,
      pr1645v2PortSwEOutQueuesOctetLength
         Integer32,
      pr1645v2PortSwEOutQueuesRedLength
         Integer32,
      pr1645v2PortSwEOutQueuesPacketsTotal
         Counter64,
      pr1645v2PortSwEOutQueuesPacketsDirectTx
         Counter64,
      pr1645v2PortSwEOutQueuesPacketsQueued
         Counter64,
      pr1645v2PortSwEOutQueuesPacketsDropped
         Counter64,
      pr1645v2PortSwEOutQueuesPacketsRedDropped
         Counter64,
      pr1645v2PortSwEOutQueuesPacketsCirTx
         Counter64,
      pr1645v2PortSwEOutQueuesPacketsEirTx
         Counter64,
      pr1645v2PortSwEOutQueuesPacketsViolateTx
         Counter64,
      pr1645v2PortSwEOutQueuesOctetsTotal
         Counter64,
      pr1645v2PortSwEOutQueuesOctetsDirectTx
         Counter64,
      pr1645v2PortSwEOutQueuesOctetsQueued
         Counter64,
      pr1645v2PortSwEOutQueuesOctetsDropped
         Counter64,
      pr1645v2PortSwEOutQueuesOctetsRedDropped
         Counter64,
      pr1645v2PortSwEOutQueuesOctetsCirTx
         Counter64,
      pr1645v2PortSwEOutQueuesOctetsEirTx
         Counter64,
      pr1645v2PortSwEOutQueuesOctetsViolateTx
         Counter64,
      pr1645v2PortSwEOutQueuesOctetsBandwidth15sec
         Integer32,
      pr1645v2PortSwEOutQueuesOctetsBandwidth30sec
         Integer32,
      pr1645v2PortSwEOutQueuesOctetsBandwidth1min
         Integer32,
      pr1645v2PortSwEOutQueuesOctetsBandwidth2min
         Integer32,
      pr1645v2PortSwEOutQueuesOctetsBandwidth5min
         Integer32
      }

pr1645v2PortSwEOutQueuesTableIx OBJECT-TYPE
   SYNTAX      TableIndex
   MAX-ACCESS  not-accessible
   STATUS      current
   DESCRIPTION
      ""
   ::= {pr1645v2PortSwEOutQueuesEntry 11}

pr1645v2PortSwEOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PortSwEOutQueuesEntry 16777216}

pr1645v2PortSwEOutQueuesLength OBJECT-TYPE
   SYNTAX      Integer32
   MAX-ACCESS  read-only
   STATUS      current
   DESCRIPTION
      "Path: ethernet3.performance.ifOutPriorityQueues.length"
   ::= {pr1645v2PortSwEOutQueuesEntry 33554432}

pr1645v2PortSwEOutQueuesOctetLength OBJECT-TYPE
   SYNTAX      Integer32
   MAX-ACCESS  read-only
   STATUS      current
   DESCRIPTION
      "Path: ethernet3.performance.ifOutPriorityQueues.octetLength"
   ::= {pr1645v2PortSwEOutQueuesEntry 150994944}

pr1645v2PortSwEOutQueuesRedLength OBJECT-TYPE
   SYNTAX      Integer32
   MAX-ACCESS  read-only
   STATUS      current
   DESCRIPTION
      "Path: ethernet3.performance.ifOutPriorityQueues.redLength"
   ::= {pr1645v2PortSwEOutQueuesEntry 134217728}

pr1645v2PortSwEOutQueuesPacketsTotal OBJECT-TYPE
   SYNTAX      Counter64
   MAX-ACCESS  read-only
   STATUS      current
   DESCRIPTION
      "Path: ethernet3.performance.ifOutPriorityQueues.packets.total

       64 bit unsigned wrappable counter."
   ::= {pr1645v2PortSwEOutQueuesEntry 50790400}

pr1645v2PortSwEOutQueuesPacketsDirectTx OBJECT-TYPE
   SYNTAX      Counter64
   MAX-ACCESS  read-only
   STATUS      current
   DESCRIPTION
      "Path: ethernet3.performance.ifOutPriorityQueues.packets.directTx

       64 bit unsigned wrappable counter."
   ::= {pr1645v2PortSwEOutQueuesEntry 50397184}

pr1645v2PortSwEOutQueuesPacketsQueued OBJECT-TYPE
   SYNTAX      Counter64
   MAX-ACCESS  read-only
   STATUS      current
   DESCRIPTION
      "Path: ethernet3.performance.ifOutPriorityQueues.packets.queued

       64 bit unsigned wrappable counter."
   ::= {pr1645v2PortSwEOutQueuesEntry 50462720}

pr1645v2PortSwEOutQueuesPacketsDropped OBJECT-TYPE
   SYNTAX      Counter64
   MAX-ACCESS  read-only
   STATUS      current
   DESCRIPTION
      "Path: ethernet3.performance.ifOutPriorityQueues.packets.dropped

       64 bit unsigned wrappable counter."
   ::= {pr1645v2PortSwEOutQueuesEntry 50528256}

pr1645v2PortSwEOutQueuesPacketsRedDropped OBJECT-TYPE
   SYNTAX      Counter64
   MAX-ACCESS  read-only
   STATUS      current
   DESCRIPTION
      "Path: ethernet3.performance.ifOutPriorityQueues.packets.redDropped

       64 bit unsigned wrappable counter."
   ::= {pr1645v2PortSwEOutQueuesEntry 50724864}

pr1645v2PortSwEOutQueuesPacketsCirTx OBJECT-TYPE
   SYNTAX      Counter64
   MAX-ACCESS  read-only
   STATUS      current
   DESCRIPTION
      "Path: ethernet3.performance.ifOutPriorityQueues.packets.cirTx

       64 bit unsigned wrappable counter."
   ::= {pr1645v2PortSwEOutQueuesEntry 50593792}

pr1645v2PortSwEOutQueuesPacketsEirTx OBJECT-TYPE
   SYNTAX      Counter64
   MAX-ACCESS  read-only
   STATUS      current
   DESCRIPTION
      "Path: ethernet3.performance.ifOutPriorityQueues.packets.eirTx

       64 bit unsigned wrappable counter."
   ::= {pr1645v2PortSwEOutQueuesEntry 50659328}

pr1645v2PortSwEOutQueuesPacketsViolateTx OBJECT-TYPE
   SYNTAX      Counter64
   MAX-ACCESS  read-only
   STATUS      current
   DESCRIPTION
      "Path: ethernet3.performance.ifOutPriorityQueues.packets.violateTx

       64 bit unsigned wrappable counter."
   ::= {pr1645v2PortSwEOutQueuesEntry 50855936}

pr1645v2PortSwEOutQueuesOctetsTotal OBJECT-TYPE
   SYNTAX      Counter64
   MAX-ACCESS  read-only
   STATUS      current
   DESCRIPTION
      "Path: ethernet3.performance.ifOutPriorityQueues.octets.total

       64 bit unsigned wrappable counter."
   ::= {pr1645v2PortSwEOutQueuesEntry 67567616}

pr1645v2PortSwEOutQueuesOctetsDirectTx OBJECT-TYPE
   SYNTAX      Counter64
   MAX-ACCESS  read-only
   STATUS      current
   DESCRIPTION
      "Path: ethernet3.performance.ifOutPriorityQueues.octets.directTx

       64 bit unsigned wrappable counter."
   ::= {pr1645v2PortSwEOutQueuesEntry 67174400}

pr1645v2PortSwEOutQueuesOctetsQueued OBJECT-TYPE
   SYNTAX      Counter64
   MAX-ACCESS  read-only
   STATUS      current
   DESCRIPTION
      "Path: ethernet3.performance.ifOutPriorityQueues.octets.queued

       64 bit unsigned wrappable counter."
   ::= {pr1645v2PortSwEOutQueuesEntry 67239936}

pr1645v2PortSwEOutQueuesOctetsDropped OBJECT-TYPE
   SYNTAX      Counter64
   MAX-ACCESS  read-only
   STATUS      current
   DESCRIPTION
      "Path: ethernet3.performance.ifOutPriorityQueues.octets.dropped

       64 bit unsigned wrappable counter."
   ::= {pr1645v2PortSwEOutQueuesEntry 67305472}

pr1645v2PortSwEOutQueuesOctetsRedDropped OBJECT-TYPE
   SYNTAX      Counter64
   MAX-ACCESS  read-only
   STATUS      current
   DESCRIPTION
      "Path: ethernet3.performance.ifOutPriorityQueues.octets.redDropped

       64 bit unsigned wrappable counter."
   ::= {pr1645v2PortSwEOutQueuesEntry 67502080}

pr1645v2PortSwEOutQueuesOctetsCirTx OBJECT-TYPE
   SYNTAX      Counter64
   MAX-ACCESS  read-only
   STATUS      current
   DESCRIPTION
      "Path: ethernet3.performance.ifOutPriorityQueues.octets.cirTx

       64 bit unsigned wrappable counter."
   ::= {pr1645v2PortSwEOutQueuesEntry 67371008}

pr1645v2PortSwEOutQueuesOctetsEirTx OBJECT-TYPE
   SYNTAX      Counter64
   MAX-ACCESS  read-only
   STATUS      current
   DESCRIPTION
      "Path: ethernet3.performance.ifOutPriorityQueues.octets.eirTx

       64 bit unsigned wrappable counter."
   ::= {pr1645v2PortSwEOutQueuesEntry 67436544}

pr1645v2PortSwEOutQueuesOctetsViolateTx OBJECT-TYPE
   SYNTAX      Counter64
   MAX-ACCESS  read-only
   STATUS      current
   DESCRIPTION
      "Path: ethernet3.performance.ifOutPriorityQueues.octets.violateTx

       64 bit unsigned wrappable counter."
   ::= {pr1645v2PortSwEOutQueuesEntry 67633152}

pr1645v2PortSwEOutQueuesOctetsBandwidth15sec OBJECT-TYPE
   SYNTAX      Integer32
   MAX-ACCESS  read-only
   STATUS      current
   DESCRIPTION
      "Path: ethernet3.performance.ifOutPriorityQueues.octets.bandwidth.15sec

       unit name = bps
       formula = 8 * ; 8 /"
   ::= {pr1645v2PortSwEOutQueuesEntry 70386944}

pr1645v2PortSwEOutQueuesOctetsBandwidth30sec OBJECT-TYPE
   SYNTAX      Integer32
   MAX-ACCESS  read-only
   STATUS      current
   DESCRIPTION
      "Path: ethernet3.performance.ifOutPriorityQueues.octets.bandwidth.30sec

       unit name = bps
       formula = 8 * ; 8 /"
   ::= {pr1645v2PortSwEOutQueuesEntry 70388224}

pr1645v2PortSwEOutQueuesOctetsBandwidth1min OBJECT-TYPE
   SYNTAX      Integer32
   MAX-ACCESS  read-only
   STATUS      current
   DESCRIPTION
      "Path: ethernet3.performance.ifOutPriorityQueues.octets.bandwidth.1min

       unit name = bps
       formula = 8 * ; 8 /"
   ::= {pr1645v2PortSwEOutQueuesEntry 70390784}

pr1645v2PortSwEOutQueuesOctetsBandwidth2min OBJECT-TYPE
   SYNTAX      Integer32
   MAX-ACCESS  read-only
   STATUS      current
   DESCRIPTION
      "Path: ethernet3.performance.ifOutPriorityQueues.octets.bandwidth.2min

       unit name = bps
       formula = 8 * ; 8 /"
   ::= {pr1645v2PortSwEOutQueuesEntry 70395904}

pr1645v2PortSwEOutQueuesOctetsBandwidth5min OBJECT-TYPE
   SYNTAX      Integer32
   MAX-ACCESS  read-only
   STATUS      current
   DESCRIPTION
      "Path: ethernet3.performance.ifOutPriorityQueues.octets.bandwidth.5min

       unit name = bps
       formula = 8 * ; 8 /"
   ::= {pr1645v2PortSwEOutQueuesEntry 70411264}

pr1645v2PortSwEOutQueuesH2Performance OBJECT-TYPE
   SYNTAX      SEQUENCE OF Pr1645v2PortSwEOutQueuesH2PerformanceEntry
   MAX-ACCESS  not-accessible
   STATUS      current
   DESCRIPTION
      ""
   ::= {pr1645v2PortSwEOutQueues 83886080}

pr1645v2PortSwEOutQueuesH2PerformanceEntry OBJECT-TYPE
   SYNTAX      Pr1645v2PortSwEOutQueuesH2PerformanceEntry
   MAX-ACCESS  not-accessible
   STATUS      current
   DESCRIPTION
      ""
   INDEX      { pr1645v2PortSwEOutQueuesTableIx,
                pr1645v2PortSwEOutQueuesH2PerformanceTableIx }
   ::= {pr1645v2PortSwEOutQueuesH2Performance 1}

Pr1645v2PortSwEOutQueuesH2PerformanceEntry ::=
   SEQUENCE
      {
      pr1645v2PortSwEOutQueuesH2PerformanceTableIx
         TableIndex,
      pr1645v2PortSwEOutQueuesH2PerformanceSysUpTime
         TimeTicks,
      pr1645v2PortSwEOutQueuesH2PerformanceTotPkts
         Counter64,
      pr1645v2PortSwEOutQueuesH2PerformanceDirTxPkts
         Counter64,
      pr1645v2PortSwEOutQueuesH2PerformanceQdPkts
         Counter64,
      pr1645v2PortSwEOutQueuesH2PerformanceDropPkts
         Counter64,
      pr1645v2PortSwEOutQueuesH2PerformanceRDropPkts
         Counter64,
      pr1645v2PortSwEOutQueuesH2PerformanceCirTxPkts
         Counter64,
      pr1645v2PortSwEOutQueuesH2PerformanceEirTxPkts
         Counter64,
      pr1645v2PortSwEOutQueuesH2PerformanceViolTxPkts
         Counter64,
      pr1645v2PortSwEOutQueuesH2PerformanceTotOcts
         Counter64,
      pr1645v2PortSwEOutQueuesH2PerformanceDirTxOcts
         Counter64,
      pr1645v2PortSwEOutQueuesH2PerformanceQdOcts
         Counter64,
      pr1645v2PortSwEOutQueuesH2PerformanceDropOcts
         Counter64,
      pr1645v2PortSwEOutQueuesH2PerformanceRDropOcts
         Counter64,
      pr1645v2PortSwEOutQueuesH2PerformanceCirTxOcts
         Counter64,
      pr1645v2PortSwEOutQueuesH2PerformanceEirTxOcts
         Counter64,
      pr1645v2PortSwEOutQueuesH2PerformanceViolTxOcts
         Counter64,
      pr1645v2PortSwEOutQueuesH2PerformanceBandwidth
         Integer32
      }

pr1645v2PortSwEOutQueuesH2PerformanceTableIx OBJECT-TYPE
   SYNTAX      TableIndex
   MAX-ACCESS  not-accessible
   STATUS      current
   DESCRIPTION
      ""
   ::= {pr1645v2PortSwEOutQueuesH2PerformanceEntry 11}

pr1645v2PortSwEOutQueuesH2PerformanceSysUpTime OBJECT-TYPE
   SYNTAX      TimeTicks
   MAX-ACCESS  read-only
   STATUS      current
   DESCRIPTION
      "Path: ethernet3.performance.ifOutPriorityQueues.h2Performance.sysUpTime

       Time in centi-second."
   ::= {pr1645v2PortSwEOutQueuesH2PerformanceEntry 16777216}

pr1645v2PortSwEOutQueuesH2PerformanceTotPkts OBJECT-TYPE
   SYNTAX      Counter64
   MAX-ACCESS  read-only
   STATUS      current
   DESCRIPTION
      "Path: ethernet3.performance.ifOutPriorityQueues.h2Performance.totalPkts

       64 bit unsigned wrappable counter."
   ::= {pr1645v2PortSwEOutQueuesH2PerformanceEntry 234881024}

pr1645v2PortSwEOutQueuesH2PerformanceDirTxPkts OBJECT-TYPE
   SYNTAX      Counter64
   MAX-ACCESS  read-only
   STATUS      current
   DESCRIPTION
      "Path: ethernet3.performance.ifOutPriorityQueues.h2Performance.directTxPkts

       64 bit unsigned wrappable counter."
   ::= {pr1645v2PortSwEOutQueuesH2PerformanceEntry 33554432}

pr1645v2PortSwEOutQueuesH2PerformanceQdPkts OBJECT-TYPE
   SYNTAX      Counter64
   MAX-ACCESS  read-only
   STATUS      current
   DESCRIPTION
      "Path: ethernet3.performance.ifOutPriorityQueues.h2Performance.queuedPkts

       64 bit unsigned wrappable counter."
   ::= {pr1645v2PortSwEOutQueuesH2PerformanceEntry 50331648}

pr1645v2PortSwEOutQueuesH2PerformanceDropPkts OBJECT-TYPE
   SYNTAX      Counter64
   MAX-ACCESS  read-only
   STATUS      current
   DESCRIPTION
      "Path: ethernet3.performance.ifOutPriorityQueues.h2Performance.droppedPkts

       64 bit unsigned wrappable counter."
   ::= {pr1645v2PortSwEOutQueuesH2PerformanceEntry 67108864}

pr1645v2PortSwEOutQueuesH2PerformanceRDropPkts OBJECT-TYPE
   SYNTAX      Counter64
   MAX-ACCESS  read-only
   STATUS      current
   DESCRIPTION
      "Path: ethernet3.performance.ifOutPriorityQueues.h2Performance.redDroppedPkts

       64 bit unsigned wrappable counter."
   ::= {pr1645v2PortSwEOutQueuesH2PerformanceEntry 201326592}

pr1645v2PortSwEOutQueuesH2PerformanceCirTxPkts OBJECT-TYPE
   SYNTAX      Counter64
   MAX-ACCESS  read-only
   STATUS      current
   DESCRIPTION
      "Path: ethernet3.performance.ifOutPriorityQueues.h2Performance.cirTxPkts

       64 bit unsigned wrappable counter."
   ::= {pr1645v2PortSwEOutQueuesH2PerformanceEntry 83886080}

pr1645v2PortSwEOutQueuesH2PerformanceEirTxPkts OBJECT-TYPE
   SYNTAX      Counter64
   MAX-ACCESS  read-only
   STATUS      current
   DESCRIPTION
      "Path: ethernet3.performance.ifOutPriorityQueues.h2Performance.eirTxPkts

       64 bit unsigned wrappable counter."
   ::= {pr1645v2PortSwEOutQueuesH2PerformanceEntry 100663296}

pr1645v2PortSwEOutQueuesH2PerformanceViolTxPkts OBJECT-TYPE
   SYNTAX      Counter64
   MAX-ACCESS  read-only
   STATUS      current
   DESCRIPTION
      "Path: ethernet3.performance.ifOutPriorityQueues.h2Performance.violateTxPkts

       64 bit unsigned wrappable counter."
   ::= {pr1645v2PortSwEOutQueuesH2PerformanceEntry 301989888}

pr1645v2PortSwEOutQueuesH2PerformanceTotOcts OBJECT-TYPE
   SYNTAX      Counter64
   MAX-ACCESS  read-only
   STATUS      current
   DESCRIPTION
      "Path: ethernet3.performance.ifOutPriorityQueues.h2Performance.totalOctets

       64 bit unsigned wrappable counter."
   ::= {pr1645v2PortSwEOutQueuesH2PerformanceEntry 251658240}

pr1645v2PortSwEOutQueuesH2PerformanceDirTxOcts OBJECT-TYPE
   SYNTAX      Counter64
   MAX-ACCESS  read-only
   STATUS      current
   DESCRIPTION
      "Path: ethernet3.performance.ifOutPriorityQueues.h2Performance.directTxOctets

       64 bit unsigned wrappable counter."
   ::= {pr1645v2PortSwEOutQueuesH2PerformanceEntry 117440512}

pr1645v2PortSwEOutQueuesH2PerformanceQdOcts OBJECT-TYPE
   SYNTAX      Counter64
   MAX-ACCESS  read-only
   STATUS      current
   DESCRIPTION
      "Path: ethernet3.performance.ifOutPriorityQueues.h2Performance.queuedOctets

       64 bit unsigned wrappable counter."
   ::= {pr1645v2PortSwEOutQueuesH2PerformanceEntry 134217728}

pr1645v2PortSwEOutQueuesH2PerformanceDropOcts OBJECT-TYPE
   SYNTAX      Counter64
   MAX-ACCESS  read-only
   STATUS      current
   DESCRIPTION
      "Path: ethernet3.performance.ifOutPriorityQueues.h2Performance.droppedOctets

       64 bit unsigned wrappable counter."
   ::= {pr1645v2PortSwEOutQueuesH2PerformanceEntry 150994944}

pr1645v2PortSwEOutQueuesH2PerformanceRDropOcts OBJECT-TYPE
   SYNTAX      Counter64
   MAX-ACCESS  read-only
   STATUS      current
   DESCRIPTION
      "Path: ethernet3.performance.ifOutPriorityQueues.h2Performance.redDroppedOctets

       64 bit unsigned wrappable counter."
   ::= {pr1645v2PortSwEOutQueuesH2PerformanceEntry 218103808}

pr1645v2PortSwEOutQueuesH2PerformanceCirTxOcts OBJECT-TYPE
   SYNTAX      Counter64
   MAX-ACCESS  read-only
   STATUS      current
   DESCRIPTION
      "Path: ethernet3.performance.ifOutPriorityQueues.h2Performance.cirTxOctets

       64 bit unsigned wrappable counter."
   ::= {pr1645v2PortSwEOutQueuesH2PerformanceEntry 167772160}

pr1645v2PortSwEOutQueuesH2PerformanceEirTxOcts OBJECT-TYPE
   SYNTAX      Counter64
   MAX-ACCESS  read-only
   STATUS      current
   DESCRIPTION
      "Path: ethernet3.performance.ifOutPriorityQueues.h2Performance.eirTxOctets

       64 bit unsigned wrappable counter."
   ::= {pr1645v2PortSwEOutQueuesH2PerformanceEntry 184549376}

pr1645v2PortSwEOutQueuesH2PerformanceViolTxOcts OBJECT-TYPE
   SYNTAX      Counter64
   MAX-ACCESS  read-only
   STATUS      current
   DESCRIPTION
      "Path: ethernet3.performance.ifOutPriorityQueues.h2Performance.violateTxOctets

       64 bit unsigned wrappable counter."
   ::= {pr1645v2PortSwEOutQueuesH2PerformanceEntry 318767104}

pr1645v2PortSwEOutQueuesH2PerformanceBandwidth OBJECT-TYPE
   SYNTAX      Integer32
   MAX-ACCESS  read-only
   STATUS      current
   DESCRIPTION
      "Path: ethernet3.performance.ifOutPriorityQueues.h2Performance.bandwidth

       unit name = bps
       formula = 8 * ; 8 /"
   ::= {pr1645v2PortSwEOutQueuesH2PerformanceEntry 268435456}

pr1645v2PortSwEOutQueuesH24Performance OBJECT-TYPE
   SYNTAX      SEQUENCE OF Pr1645v2PortSwEOutQueuesH24PerformanceEntry
   MAX-ACCESS  not-accessible
   STATUS      current
   DESCRIPTION
      ""
   ::= {pr1645v2PortSwEOutQueues 100663296}

pr1645v2PortSwEOutQueuesH24PerformanceEntry OBJECT-TYPE
   SYNTAX      Pr1645v2PortSwEOutQueuesH24PerformanceEntry
   MAX-ACCESS  not-accessible
   STATUS      current
   DESCRIPTION
      ""
   INDEX      { pr1645v2PortSwEOutQueuesTableIx,
                pr1645v2PortSwEOutQueuesH24PerformanceTableIx }
   ::= {pr1645v2PortSwEOutQueuesH24Performance 1}

Pr1645v2PortSwEOutQueuesH24PerformanceEntry ::=
   SEQUENCE
      {
      pr1645v2PortSwEOutQueuesH24PerformanceTableIx
         TableIndex,
      pr1645v2PortSwEOutQueuesH24PerformanceSysUpTime
         TimeTicks,
      pr1645v2PortSwEOutQueuesH24PerformanceTotPkts
         Counter64,
      pr1645v2PortSwEOutQueuesH24PerformanceDirTxPkts
         Counter64,
      pr1645v2PortSwEOutQueuesH24PerformanceQdPkts
         Counter64,
      pr1645v2PortSwEOutQueuesH24PerformanceDropPkts
         Counter64,
      pr1645v2PortSwEOutQueuesH24PerformanceRDropPkts
         Counter64,
      pr1645v2PortSwEOutQueuesH24PerformanceCirTxPkts
         Counter64,
      pr1645v2PortSwEOutQueuesH24PerformanceEirTxPkts
         Counter64,
      pr1645v2PortSwEOutQueuesH24PerformanceViolTxPkts
         Counter64,
      pr1645v2PortSwEOutQueuesH24PerformanceTotOcts
         Counter64,
      pr1645v2PortSwEOutQueuesH24PerformanceDirTxOcts
         Counter64,
      pr1645v2PortSwEOutQueuesH24PerformanceQdOcts
         Counter64,
      pr1645v2PortSwEOutQueuesH24PerformanceDropOcts
         Counter64,
      pr1645v2PortSwEOutQueuesH24PerformanceRDropOcts
         Counter64,
      pr1645v2PortSwEOutQueuesH24PerformanceCirTxOcts
         Counter64,
      pr1645v2PortSwEOutQueuesH24PerformanceEirTxOcts
         Counter64,
      pr1645v2PortSwEOutQueuesH24PerformanceViolTxOcts
         Counter64,
      pr1645v2PortSwEOutQueuesH24PerformanceBandwidth
         Integer32
      }

pr1645v2PortSwEOutQueuesH24PerformanceTableIx OBJECT-TYPE
   SYNTAX      TableIndex
   MAX-ACCESS  not-accessible
   STATUS      current
   DESCRIPTION
      ""
   ::= {pr1645v2PortSwEOutQueuesH24PerformanceEntry 11}

pr1645v2PortSwEOutQueuesH24PerformanceSysUpTime OBJECT-TYPE
   SYNTAX      TimeTicks
   MAX-ACCESS  read-only
   STATUS      current
   DESCRIPTION
      "Path: ethernet3.performance.ifOutPriorityQueues.h24Performance.sysUpTime

       Time in centi-second."
   ::= {pr1645v2PortSwEOutQueuesH24PerformanceEntry 16777216}

pr1645v2PortSwEOutQueuesH24PerformanceTotPkts OBJECT-TYPE
   SYNTAX      Counter64
   MAX-ACCESS  read-only
   STATUS      current
   DESCRIPTION
      "Path: ethernet3.performance.ifOutPriorityQueues.h24Performance.totalPkts

       64 bit unsigned wrappable counter."
   ::= {pr1645v2PortSwEOutQueuesH24PerformanceEntry 234881024}

pr1645v2PortSwEOutQueuesH24PerformanceDirTxPkts OBJECT-TYPE
   SYNTAX      Counter64
   MAX-ACCESS  read-only
   STATUS      current
   DESCRIPTION
      "Path: ethernet3.performance.ifOutPriorityQueues.h24Performance.directTxPkts

       64 bit unsigned wrappable counter."
   ::= {pr1645v2PortSwEOutQueuesH24PerformanceEntry 33554432}

pr1645v2PortSwEOutQueuesH24PerformanceQdPkts OBJECT-TYPE
   SYNTAX      Counter64
   MAX-ACCESS  read-only
   STATUS      current
   DESCRIPTION
      "Path: ethernet3.performance.ifOutPriorityQueues.h24Performance.queuedPkts

       64 bit unsigned wrappable counter."
   ::= {pr1645v2PortSwEOutQueuesH24PerformanceEntry 50331648}

pr1645v2PortSwEOutQueuesH24PerformanceDropPkts OBJECT-TYPE
   SYNTAX      Counter64
   MAX-ACCESS  read-only
   STATUS      current
   DESCRIPTION
      "Path: ethernet3.performance.ifOutPriorityQueues.h24Performance.droppedPkts

       64 bit unsigned wrappable counter."
   ::= {pr1645v2PortSwEOutQueuesH24PerformanceEntry 67108864}

pr1645v2PortSwEOutQueuesH24PerformanceRDropPkts OBJECT-TYPE
   SYNTAX      Counter64
   MAX-ACCESS  read-only
   STATUS      current
   DESCRIPTION
      "Path: ethernet3.performance.ifOutPriorityQueues.h24Performance.redDroppedPkts

       64 bit unsigned wrappable counter."
   ::= {pr1645v2PortSwEOutQueuesH24PerformanceEntry 201326592}

pr1645v2PortSwEOutQueuesH24PerformanceCirTxPkts OBJECT-TYPE
   SYNTAX      Counter64
   MAX-ACCESS  read-only
   STATUS      current
   DESCRIPTION
      "Path: ethernet3.performance.ifOutPriorityQueues.h24Performance.cirTxPkts

       64 bit unsigned wrappable counter."
   ::= {pr1645v2PortSwEOutQueuesH24PerformanceEntry 83886080}

pr1645v2PortSwEOutQueuesH24PerformanceEirTxPkts OBJECT-TYPE
   SYNTAX      Counter64
   MAX-ACCESS  read-only
   STATUS      current
   DESCRIPTION
      "Path: ethernet3.performance.ifOutPriorityQueues.h24Performance.eirTxPkts

       64 bit unsigned wrappable counter."
   ::= {pr1645v2PortSwEOutQueuesH24PerformanceEntry 100663296}

pr1645v2PortSwEOutQueuesH24PerformanceViolTxPkts OBJECT-TYPE
   SYNTAX      Counter64
   MAX-ACCESS  read-only
   STATUS      current
   DESCRIPTION
      "Path: ethernet3.performance.ifOutPriorityQueues.h24Performance.violateTxPkts

       64 bit unsigned wrappable counter."
   ::= {pr1645v2PortSwEOutQueuesH24PerformanceEntry 301989888}

pr1645v2PortSwEOutQueuesH24PerformanceTotOcts OBJECT-TYPE
   SYNTAX      Counter64
   MAX-ACCESS  read-only
   STATUS      current
   DESCRIPTION
      "Path: ethernet3.performance.ifOutPriorityQueues.h24Performance.totalOctets

       64 bit unsigned wrappable counter."
   ::= {pr1645v2PortSwEOutQueuesH24PerformanceEntry 251658240}

pr1645v2PortSwEOutQueuesH24PerformanceDirTxOcts OBJECT-TYPE
   SYNTAX      Counter64
   MAX-ACCESS  read-only
   STATUS      current
   DESCRIPTION
      "Path: ethernet3.performance.ifOutPriorityQueues.h24Performance.directTxOctets

       64 bit unsigned wrappable counter."
   ::= {pr1645v2PortSwEOutQueuesH24PerformanceEntry 117440512}

pr1645v2PortSwEOutQueuesH24PerformanceQdOcts OBJECT-TYPE
   SYNTAX      Counter64
   MAX-ACCESS  read-only
   STATUS      current
   DESCRIPTION
      "Path: ethernet3.performance.ifOutPriorityQueues.h24Performance.queuedOctets

       64 bit unsigned wrappable counter."
   ::= {pr1645v2PortSwEOutQueuesH24PerformanceEntry 134217728}

pr1645v2PortSwEOutQueuesH24PerformanceDropOcts OBJECT-TYPE
   SYNTAX      Counter64
   MAX-ACCESS  read-only
   STATUS      current
   DESCRIPTION
      "Path: ethernet3.performance.ifOutPriorityQueues.h24Performance.droppedOctets

       64 bit unsigned wrappable counter."
   ::= {pr1645v2PortSwEOutQueuesH24PerformanceEntry 150994944}

pr1645v2PortSwEOutQueuesH24PerformanceRDropOcts OBJECT-TYPE
   SYNTAX      Counter64
   MAX-ACCESS  read-only
   STATUS      current
   DESCRIPTION
      "Path: ethernet3.performance.ifOutPriorityQueues.h24Performance.redDroppedOctets

       64 bit unsigned wrappable counter."
   ::= {pr1645v2PortSwEOutQueuesH24PerformanceEntry 218103808}

pr1645v2PortSwEOutQueuesH24PerformanceCirTxOcts OBJECT-TYPE
   SYNTAX      Counter64
   MAX-ACCESS  read-only
   STATUS      current
   DESCRIPTION
      "Path: ethernet3.performance.ifOutPriorityQueues.h24Performance.cirTxOctets

       64 bit unsigned wrappable counter."
   ::= {pr1645v2PortSwEOutQueuesH24PerformanceEntry 167772160}

pr1645v2PortSwEOutQueuesH24PerformanceEirTxOcts OBJECT-TYPE
   SYNTAX      Counter64
   MAX-ACCESS  read-only
   STATUS      current
   DESCRIPTION
      "Path: ethernet3.performance.ifOutPriorityQueues.h24Performance.eirTxOctets

       64 bit unsigned wrappable counter."
   ::= {pr1645v2PortSwEOutQueuesH24PerformanceEntry 184549376}

pr1645v2PortSwEOutQueuesH24PerformanceViolTxOcts OBJECT-TYPE
   SYNTAX      Counter64
   MAX-ACCESS  read-only
   STATUS      current
   DESCRIPTION
      "Path: ethernet3.performance.ifOutPriorityQueues.h24Performance.violateTxOctets

       64 bit unsigned wrappable counter."
   ::= {pr1645v2PortSwEOutQueuesH24PerformanceEntry 318767104}

pr1645v2PortSwEOutQueuesH24PerformanceBandwidth OBJECT-TYPE
   SYNTAX      Integer32
   MAX-ACCESS  read-only
   STATUS      current
   DESCRIPTION
      "Path: ethernet3.performance.ifOutPriorityQueues.h24Performance.bandwidth

       unit name = bps
       formula = 8 * ; 8 /"
   ::= {pr1645v2PortSwEOutQueuesH24PerformanceEntry 268435456}

pr1645v2PortSwEOutQueuesD7Performance OBJECT-TYPE
   SYNTAX      SEQUENCE OF Pr1645v2PortSwEOutQueuesD7PerformanceEntry
   MAX-ACCESS  not-accessible
   STATUS      current
   DESCRIPTION
      ""
   ::= {pr1645v2PortSwEOutQueues 117440512}

pr1645v2PortSwEOutQueuesD7PerformanceEntry OBJECT-TYPE
   SYNTAX      Pr1645v2PortSwEOutQueuesD7PerformanceEntry
   MAX-ACCESS  not-accessible
   STATUS      current
   DESCRIPTION
      ""
   INDEX      { pr1645v2PortSwEOutQueuesTableIx,
                pr1645v2PortSwEOutQueuesD7PerformanceTableIx }
   ::= {pr1645v2PortSwEOutQueuesD7Performance 1}

Pr1645v2PortSwEOutQueuesD7PerformanceEntry ::=
   SEQUENCE
      {
      pr1645v2PortSwEOutQueuesD7PerformanceTableIx
         TableIndex,
      pr1645v2PortSwEOutQueuesD7PerformanceSysUpTime
         TimeTicks,
      pr1645v2PortSwEOutQueuesD7PerformanceTotPkts
         Counter64,
      pr1645v2PortSwEOutQueuesD7PerformanceDirTxPkts
         Counter64,
      pr1645v2PortSwEOutQueuesD7PerformanceQdPkts
         Counter64,
      pr1645v2PortSwEOutQueuesD7PerformanceDropPkts
         Counter64,
      pr1645v2PortSwEOutQueuesD7PerformanceRDropPkts
         Counter64,
      pr1645v2PortSwEOutQueuesD7PerformanceCirTxPkts
         Counter64,
      pr1645v2PortSwEOutQueuesD7PerformanceEirTxPkts
         Counter64,
      pr1645v2PortSwEOutQueuesD7PerformanceViolTxPkts
         Counter64,
      pr1645v2PortSwEOutQueuesD7PerformanceTotOcts
         Counter64,
      pr1645v2PortSwEOutQueuesD7PerformanceDirTxOcts
         Counter64,
      pr1645v2PortSwEOutQueuesD7PerformanceQdOcts
         Counter64,
      pr1645v2PortSwEOutQueuesD7PerformanceDropOcts
         Counter64,
      pr1645v2PortSwEOutQueuesD7PerformanceRDropOcts
         Counter64,
      pr1645v2PortSwEOutQueuesD7PerformanceCirTxOcts
         Counter64,
      pr1645v2PortSwEOutQueuesD7PerformanceEirTxOcts
         Counter64,
      pr1645v2PortSwEOutQueuesD7PerformanceViolTxOcts
         Counter64,
      pr1645v2PortSwEOutQueuesD7PerformanceBandwidth
         Integer32
      }

pr1645v2PortSwEOutQueuesD7PerformanceTableIx OBJECT-TYPE
   SYNTAX      TableIndex
   MAX-ACCESS  not-accessible
   STATUS      current
   DESCRIPTION
      ""
   ::= {pr1645v2PortSwEOutQueuesD7PerformanceEntry 11}

pr1645v2PortSwEOutQueuesD7PerformanceSysUpTime OBJECT-TYPE
   SYNTAX      TimeTicks
   MAX-ACCESS  read-only
   STATUS      current
   DESCRIPTION
      "Path: ethernet3.performance.ifOutPriorityQueues.d7Performance.sysUpTime

       Time in centi-second."
   ::= {pr1645v2PortSwEOutQueuesD7PerformanceEntry 16777216}

pr1645v2PortSwEOutQueuesD7PerformanceTotPkts OBJECT-TYPE
   SYNTAX      Counter64
   MAX-ACCESS  read-only
   STATUS      current
   DESCRIPTION
      "Path: ethernet3.performance.ifOutPriorityQueues.d7Performance.totalPkts

       64 bit unsigned wrappable counter."
   ::= {pr1645v2PortSwEOutQueuesD7PerformanceEntry 234881024}

pr1645v2PortSwEOutQueuesD7PerformanceDirTxPkts OBJECT-TYPE
   SYNTAX      Counter64
   MAX-ACCESS  read-only
   STATUS      current
   DESCRIPTION
      "Path: ethernet3.performance.ifOutPriorityQueues.d7Performance.directTxPkts

       64 bit unsigned wrappable counter."
   ::= {pr1645v2PortSwEOutQueuesD7PerformanceEntry 33554432}

pr1645v2PortSwEOutQueuesD7PerformanceQdPkts OBJECT-TYPE
   SYNTAX      Counter64
   MAX-ACCESS  read-only
   STATUS      current
   DESCRIPTION
      "Path: ethernet3.performance.ifOutPriorityQueues.d7Performance.queuedPkts

       64 bit unsigned wrappable counter."
   ::= {pr1645v2PortSwEOutQueuesD7PerformanceEntry 50331648}

pr1645v2PortSwEOutQueuesD7PerformanceDropPkts OBJECT-TYPE
   SYNTAX      Counter64
   MAX-ACCESS  read-only
   STATUS      current
   DESCRIPTION
      "Path: ethernet3.performance.ifOutPriorityQueues.d7Performance.droppedPkts

       64 bit unsigned wrappable counter."
   ::= {pr1645v2PortSwEOutQueuesD7PerformanceEntry 67108864}

pr1645v2PortSwEOutQueuesD7PerformanceRDropPkts OBJECT-TYPE
   SYNTAX      Counter64
   MAX-ACCESS  read-only
   STATUS      current
   DESCRIPTION
      "Path: ethernet3.performance.ifOutPriorityQueues.d7Performance.redDroppedPkts

       64 bit unsigned wrappable counter."
   ::= {pr1645v2PortSwEOutQueuesD7PerformanceEntry 201326592}

pr1645v2PortSwEOutQueuesD7PerformanceCirTxPkts OBJECT-TYPE
   SYNTAX      Counter64
   MAX-ACCESS  read-only
   STATUS      current
   DESCRIPTION
      "Path: ethernet3.performance.ifOutPriorityQueues.d7Performance.cirTxPkts

       64 bit unsigned wrappable counter."
   ::= {pr1645v2PortSwEOutQueuesD7PerformanceEntry 83886080}

pr1645v2PortSwEOutQueuesD7PerformanceEirTxPkts OBJECT-TYPE
   SYNTAX      Counter64
   MAX-ACCESS  read-only
   STATUS      current
   DESCRIPTION
      "Path: ethernet3.performance.ifOutPriorityQueues.d7Performance.eirTxPkts

       64 bit unsigned wrappable counter."
   ::= {pr1645v2PortSwEOutQueuesD7PerformanceEntry 100663296}

pr1645v2PortSwEOutQueuesD7PerformanceViolTxPkts OBJECT-TYPE
   SYNTAX      Counter64
   MAX-ACCESS  read-only
   STATUS      current
   DESCRIPTION
      "Path: ethernet3.performance.ifOutPriorityQueues.d7Performance.violateTxPkts

       64 bit unsigned wrappable counter."
   ::= {pr1645v2PortSwEOutQueuesD7PerformanceEntry 301989888}

pr1645v2PortSwEOutQueuesD7PerformanceTotOcts OBJECT-TYPE
   SYNTAX      Counter64
   MAX-ACCESS  read-only
   STATUS      current
   DESCRIPTION
      "Path: ethernet3.performance.ifOutPriorityQueues.d7Performance.totalOctets

       64 bit unsigned wrappable counter."
   ::= {pr1645v2PortSwEOutQueuesD7PerformanceEntry 251658240}

pr1645v2PortSwEOutQueuesD7PerformanceDirTxOcts OBJECT-TYPE
   SYNTAX      Counter64
   MAX-ACCESS  read-only
   STATUS      current
   DESCRIPTION
      "Path: ethernet3.performance.ifOutPriorityQueues.d7Performance.directTxOctets

       64 bit unsigned wrappable counter."
   ::= {pr1645v2PortSwEOutQueuesD7PerformanceEntry 117440512}

pr1645v2PortSwEOutQueuesD7PerformanceQdOcts OBJECT-TYPE
   SYNTAX      Counter64
   MAX-ACCESS  read-only
   STATUS      current
   DESCRIPTION
      "Path: ethernet3.performance.ifOutPriorityQueues.d7Performance.queuedOctets

       64 bit unsigned wrappable counter."
   ::= {pr1645v2PortSwEOutQueuesD7PerformanceEntry 134217728}

pr1645v2PortSwEOutQueuesD7PerformanceDropOcts OBJECT-TYPE
   SYNTAX      Counter64
   MAX-ACCESS  read-only
   STATUS      current
   DESCRIPTION
      "Path: ethernet3.performance.ifOutPriorityQueues.d7Performance.droppedOctets

       64 bit unsigned wrappable counter."
   ::= {pr1645v2PortSwEOutQueuesD7PerformanceEntry 150994944}

pr1645v2PortSwEOutQueuesD7PerformanceRDropOcts OBJECT-TYPE
   SYNTAX      Counter64
   MAX-ACCESS  read-only
   STATUS      current
   DESCRIPTION
      "Path: ethernet3.performance.ifOutPriorityQueues.d7Performance.redDroppedOctets

       64 bit unsigned wrappable counter."
   ::= {pr1645v2PortSwEOutQueuesD7PerformanceEntry 218103808}

pr1645v2PortSwEOutQueuesD7PerformanceCirTxOcts OBJECT-TYPE
   SYNTAX      Counter64
   MAX-ACCESS  read-only
   STATUS      current
   DESCRIPTION
      "Path: ethernet3.performance.ifOutPriorityQueues.d7Performance.cirTxOctets

       64 bit unsigned wrappable counter."
   ::= {pr1645v2PortSwEOutQueuesD7PerformanceEntry 167772160}

pr1645v2PortSwEOutQueuesD7PerformanceEirTxOcts OBJECT-TYPE
   SYNTAX      Counter64
   MAX-ACCESS  read-only
   STATUS      current
   DESCRIPTION
      "Path: ethernet3.performance.ifOutPriorityQueues.d7Performance.eirTxOctets

       64 bit unsigned wrappable counter."
   ::= {pr1645v2PortSwEOutQueuesD7PerformanceEntry 184549376}

pr1645v2PortSwEOutQueuesD7PerformanceViolTxOcts OBJECT-TYPE
   SYNTAX      Counter64
   MAX-ACCESS  read-only
   STATUS      current
   DESCRIPTION
      "Path: ethernet3.performance.ifOutPriorityQueues.d7Performance.violateTxOctets

       64 bit unsigned wrappable counter."
   ::= {pr1645v2PortSwEOutQueuesD7PerformanceEntry 318767104}

pr1645v2PortSwEOutQueuesD7PerformanceBandwidth OBJECT-TYPE
   SYNTAX      Integer32
   MAX-ACCESS  read-only
   STATUS      current
   DESCRIPTION
      "Path: ethernet3.performance.ifOutPriorityQueues.d7Performance.bandwidth

       unit name = bps
       formula = 8 * ; 8 /"
   ::= {pr1645v2PortSwEOutQueuesD7PerformanceEntry 268435456}


pr1645v2PortSwEOutBandwidth OBJECT IDENTIFIER ::= {pr1645v2PortSwE 182}

pr1645v2PortSwEOutBandwidthSSC OBJECT IDENTIFIER ::= {pr1645v2PortSwEOutBandwidth 1}

pr1645v2PortSwEOutBandwidthEntry OBJECT IDENTIFIER ::= {pr1645v2PortSwEOutBandwidthSSC 1}

pr1645v2PortSwEOutBandwidth15sec OBJECT-TYPE
   SYNTAX      Integer32
   MAX-ACCESS  read-only
   STATUS      current
   DESCRIPTION
      "Path: ethernet3.performance.ifOutBandwidth.15sec

       unit name = bps
       formula = 8 * ; 8 /"
   ::= {pr1645v2PortSwEOutBandwidthEntry 83886080}

pr1645v2PortSwEOutBandwidth30sec OBJECT-TYPE
   SYNTAX      Integer32
   MAX-ACCESS  read-only
   STATUS      current
   DESCRIPTION
      "Path: ethernet3.performance.ifOutBandwidth.30sec

       unit name = bps
       formula = 8 * ; 8 /"
   ::= {pr1645v2PortSwEOutBandwidthEntry 167772160}

pr1645v2PortSwEOutBandwidth1min OBJECT-TYPE
   SYNTAX      Integer32
   MAX-ACCESS  read-only
   STATUS      current
   DESCRIPTION
      "Path: ethernet3.performance.ifOutBandwidth.1min

       unit name = bps
       formula = 8 * ; 8 /"
   ::= {pr1645v2PortSwEOutBandwidthEntry 335544320}

pr1645v2PortSwEOutBandwidth2min OBJECT-TYPE
   SYNTAX      Integer32
   MAX-ACCESS  read-only
   STATUS      current
   DESCRIPTION
      "Path: ethernet3.performance.ifOutBandwidth.2min

       unit name = bps
       formula = 8 * ; 8 /"
   ::= {pr1645v2PortSwEOutBandwidthEntry 671088640}

pr1645v2PortSwEOutBandwidth5min OBJECT-TYPE
   SYNTAX      Integer32
   MAX-ACCESS  read-only
   STATUS      current
   DESCRIPTION
      "Path: ethernet3.performance.ifOutBandwidth.5min

       unit name = bps
       formula = 8 * ; 8 /"
   ::= {pr1645v2PortSwEOutBandwidthEntry 1677721600}


pr1645v2PortSwEInP OBJECT IDENTIFIER ::= {pr1645v2PortSwE 307}

pr1645v2PortSwEInPSSCTable OBJECT-TYPE
   SYNTAX      SEQUENCE OF Pr1645v2PortSwEInPEntry
   MAX-ACCESS  not-accessible
   STATUS      current
   DESCRIPTION
      "h2IfInPerformance"
   ::= {pr1645v2PortSwEInP 1}

pr1645v2PortSwEInPEntry OBJECT-TYPE
   SYNTAX      Pr1645v2PortSwEInPEntry
   MAX-ACCESS  not-accessible
   STATUS      current
   DESCRIPTION
      ""
   INDEX      { pr1645v2PortSwEInPTableIx }
   ::= {pr1645v2PortSwEInPSSCTable 1}

Pr1645v2PortSwEInPEntry ::=
   SEQUENCE
      {
      pr1645v2PortSwEInPTableIx
         TableIndex,
      pr1645v2PortSwEInPSysUpTime
         TimeTicks,
      pr1645v2PortSwEInPIfUpTime
         TimeTicks,
      pr1645v2PortSwEInPIfStatChanges
         Counter32,
      pr1645v2PortSwEInPIfInOctets
         Counter64,
      pr1645v2PortSwEInPIfInUCPkts
         Counter64,
      pr1645v2PortSwEInPIfInNUCPkts
         Counter64,
      pr1645v2PortSwEInPIfInBCPkts
         Counter64,
      pr1645v2PortSwEInPIfInMCPkts
         Counter64,
      pr1645v2PortSwEInPIfInDiscards
         Counter64,
      pr1645v2PortSwEInPIfInErrors
         Counter64,
      pr1645v2PortSwEInPIfInUnkwn
         Counter64,
      pr1645v2PortSwEInPInDropEx
         Counter64,
      pr1645v2PortSwEInPInDropNoMac
         Counter64,
      pr1645v2PortSwEInPInDropNUCast
         Counter64,
      pr1645v2PortSwEInPInDropFilter
         Counter64,
      pr1645v2PortSwEInPIfInBandwidth
         Integer32,
      pr1645v2PortSwEInPIfOutOctets
         Counter64,
      pr1645v2PortSwEInPIfOutUCPkts
         Counter64,
      pr1645v2PortSwEInPIfOutNUCPkts
         Counter64,
      pr1645v2PortSwEInPIfOutBCPkts
         Counter64,
      pr1645v2PortSwEInPIfOutMCPkts
         Counter64,
      pr1645v2PortSwEInPIfOutDiscards
         Counter64,
      pr1645v2PortSwEInPIfOutErrors
         Counter64,
      pr1645v2PortSwEInPOutDropEx
         Counter64,
      pr1645v2PortSwEInPOutDropNoArp
         Counter64,
      pr1645v2PortSwEInPOutDropFilter
         Counter64,
      pr1645v2PortSwEInPIfOutBandwidth
         Integer32,
      pr1645v2PortSwEInPIfErrSec
         Counter32
      }

pr1645v2PortSwEInPTableIx OBJECT-TYPE
   SYNTAX      TableIndex
   MAX-ACCESS  not-accessible
   STATUS      current
   DESCRIPTION
      ""
   ::= {pr1645v2PortSwEInPEntry 11}

pr1645v2PortSwEInPSysUpTime OBJECT-TYPE
   SYNTAX      TimeTicks
   MAX-ACCESS  read-only
   STATUS      current
   DESCRIPTION
      "Path: ethernet3.performance.h2Performance.sysUpTime

       Time in centi-second."
   ::= {pr1645v2PortSwEInPEntry 16777216}

pr1645v2PortSwEInPIfUpTime OBJECT-TYPE
   SYNTAX      TimeTicks
   MAX-ACCESS  read-only
   STATUS      current
   DESCRIPTION
      "Path: ethernet3.performance.h2Performance.ifUpTime

       Time in centi-second."
   ::= {pr1645v2PortSwEInPEntry 33554432}

pr1645v2PortSwEInPIfStatChanges OBJECT-TYPE
   SYNTAX      Counter32
   MAX-ACCESS  read-only
   STATUS      current
   DESCRIPTION
      "Path: ethernet3.performance.h2Performance.ifStatusChanges

       32 bit unsigned wrappable counter."
   ::= {pr1645v2PortSwEInPEntry 50331648}

pr1645v2PortSwEInPIfInOctets OBJECT-TYPE
   SYNTAX      Counter64
   MAX-ACCESS  read-only
   STATUS      current
   DESCRIPTION
      "Path: ethernet3.performance.h2Performance.ifInOctets

       64 bit unsigned wrappable counter."
   ::= {pr1645v2PortSwEInPEntry 67108864}

pr1645v2PortSwEInPIfInUCPkts OBJECT-TYPE
   SYNTAX      Counter64
   MAX-ACCESS  read-only
   STATUS      current
   DESCRIPTION
      "Path: ethernet3.performance.h2Performance.ifInUcastPkts

       64 bit unsigned wrappable counter."
   ::= {pr1645v2PortSwEInPEntry 83886080}

pr1645v2PortSwEInPIfInNUCPkts OBJECT-TYPE
   SYNTAX      Counter64
   MAX-ACCESS  read-only
   STATUS      current
   DESCRIPTION
      "Path: ethernet3.performance.h2Performance.ifInNUcastPkts

       64 bit unsigned wrappable counter."
   ::= {pr1645v2PortSwEInPEntry 100663296}

pr1645v2PortSwEInPIfInBCPkts OBJECT-TYPE
   SYNTAX      Counter64
   MAX-ACCESS  read-only
   STATUS      current
   DESCRIPTION
      "Path: ethernet3.performance.h2Performance.ifInBcastPkts

       64 bit unsigned wrappable counter."
   ::= {pr1645v2PortSwEInPEntry 419430400}

pr1645v2PortSwEInPIfInMCPkts OBJECT-TYPE
   SYNTAX      Counter64
   MAX-ACCESS  read-only
   STATUS      current
   DESCRIPTION
      "Path: ethernet3.performance.h2Performance.ifInMcastPkts

       64 bit unsigned wrappable counter."
   ::= {pr1645v2PortSwEInPEntry 436207616}

pr1645v2PortSwEInPIfInDiscards OBJECT-TYPE
   SYNTAX      Counter64
   MAX-ACCESS  read-only
   STATUS      current
   DESCRIPTION
      "Path: ethernet3.performance.h2Performance.ifInDiscards

       64 bit unsigned wrappable counter."
   ::= {pr1645v2PortSwEInPEntry 117440512}

pr1645v2PortSwEInPIfInErrors OBJECT-TYPE
   SYNTAX      Counter64
   MAX-ACCESS  read-only
   STATUS      current
   DESCRIPTION
      "Path: ethernet3.performance.h2Performance.ifInErrors

       64 bit unsigned wrappable counter."
   ::= {pr1645v2PortSwEInPEntry 134217728}

pr1645v2PortSwEInPIfInUnkwn OBJECT-TYPE
   SYNTAX      Counter64
   MAX-ACCESS  read-only
   STATUS      current
   DESCRIPTION
      "Path: ethernet3.performance.h2Performance.ifInUnknownProtos

       64 bit unsigned wrappable counter."
   ::= {pr1645v2PortSwEInPEntry 150994944}

pr1645v2PortSwEInPInDropEx OBJECT-TYPE
   SYNTAX      Counter64
   MAX-ACCESS  read-only
   STATUS      current
   DESCRIPTION
      "Path: ethernet3.performance.h2Performance.ifInDropLevelExceeded

       64 bit unsigned wrappable counter."
   ::= {pr1645v2PortSwEInPEntry 335544320}

pr1645v2PortSwEInPInDropNoMac OBJECT-TYPE
   SYNTAX      Counter64
   MAX-ACCESS  read-only
   STATUS      current
   DESCRIPTION
      "Path: ethernet3.performance.h2Performance.fInDiscardsNoMacFit

       64 bit unsigned wrappable counter."
   ::= {pr1645v2PortSwEInPEntry 301989888}

pr1645v2PortSwEInPInDropNUCast OBJECT-TYPE
   SYNTAX      Counter64
   MAX-ACCESS  read-only
   STATUS      current
   DESCRIPTION
      "Path: ethernet3.performance.h2Performance.fInDiscardsNUCast

       64 bit unsigned wrappable counter."
   ::= {pr1645v2PortSwEInPEntry 318767104}

pr1645v2PortSwEInPInDropFilter OBJECT-TYPE
   SYNTAX      Counter64
   MAX-ACCESS  read-only
   STATUS      current
   DESCRIPTION
      "Path: ethernet3.performance.h2Performance.fInDiscardsFilter

       64 bit unsigned wrappable counter."
   ::= {pr1645v2PortSwEInPEntry 385875968}

pr1645v2PortSwEInPIfInBandwidth OBJECT-TYPE
   SYNTAX      Integer32
   MAX-ACCESS  read-only
   STATUS      current
   DESCRIPTION
      "Path: ethernet3.performance.h2Performance.ifInBandwidth

       unit name = bps
       formula = 8 * ; 8 /"
   ::= {pr1645v2PortSwEInPEntry 268435456}

pr1645v2PortSwEInPIfOutOctets OBJECT-TYPE
   SYNTAX      Counter64
   MAX-ACCESS  read-only
   STATUS      current
   DESCRIPTION
      "Path: ethernet3.performance.h2Performance.ifOutOctets

       64 bit unsigned wrappable counter."
   ::= {pr1645v2PortSwEInPEntry 167772160}

pr1645v2PortSwEInPIfOutUCPkts OBJECT-TYPE
   SYNTAX      Counter64
   MAX-ACCESS  read-only
   STATUS      current
   DESCRIPTION
      "Path: ethernet3.performance.h2Performance.ifOutUcastPkts

       64 bit unsigned wrappable counter."
   ::= {pr1645v2PortSwEInPEntry 184549376}

pr1645v2PortSwEInPIfOutNUCPkts OBJECT-TYPE
   SYNTAX      Counter64
   MAX-ACCESS  read-only
   STATUS      current
   DESCRIPTION
      "Path: ethernet3.performance.h2Performance.ifOutNUcastPkts

       64 bit unsigned wrappable counter."
   ::= {pr1645v2PortSwEInPEntry 201326592}

pr1645v2PortSwEInPIfOutBCPkts OBJECT-TYPE
   SYNTAX      Counter64
   MAX-ACCESS  read-only
   STATUS      current
   DESCRIPTION
      "Path: ethernet3.performance.h2Performance.ifOutBcastPkts

       64 bit unsigned wrappable counter."
   ::= {pr1645v2PortSwEInPEntry 452984832}

pr1645v2PortSwEInPIfOutMCPkts OBJECT-TYPE
   SYNTAX      Counter64
   MAX-ACCESS  read-only
   STATUS      current
   DESCRIPTION
      "Path: ethernet3.performance.h2Performance.ifOutMcastPkts

       64 bit unsigned wrappable counter."
   ::= {pr1645v2PortSwEInPEntry 469762048}

pr1645v2PortSwEInPIfOutDiscards OBJECT-TYPE
   SYNTAX      Counter64
   MAX-ACCESS  read-only
   STATUS      current
   DESCRIPTION
      "Path: ethernet3.performance.h2Performance.ifOutDiscards

       64 bit unsigned wrappable counter."
   ::= {pr1645v2PortSwEInPEntry 218103808}

pr1645v2PortSwEInPIfOutErrors OBJECT-TYPE
   SYNTAX      Counter64
   MAX-ACCESS  read-only
   STATUS      current
   DESCRIPTION
      "Path: ethernet3.performance.h2Performance.ifOutErrors

       64 bit unsigned wrappable counter."
   ::= {pr1645v2PortSwEInPEntry 234881024}

pr1645v2PortSwEInPOutDropEx OBJECT-TYPE
   SYNTAX      Counter64
   MAX-ACCESS  read-only
   STATUS      current
   DESCRIPTION
      "Path: ethernet3.performance.h2Performance.ifOutDropLevelExceeded

       64 bit unsigned wrappable counter."
   ::= {pr1645v2PortSwEInPEntry 352321536}

pr1645v2PortSwEInPOutDropNoArp OBJECT-TYPE
   SYNTAX      Counter64
   MAX-ACCESS  read-only
   STATUS      current
   DESCRIPTION
      "Path: ethernet3.performance.h2Performance.ifOutDiscardsNoArp

       64 bit unsigned wrappable counter."
   ::= {pr1645v2PortSwEInPEntry 369098752}

pr1645v2PortSwEInPOutDropFilter OBJECT-TYPE
   SYNTAX      Counter64
   MAX-ACCESS  read-only
   STATUS      current
   DESCRIPTION
      "Path: ethernet3.performance.h2Performance.ifOutDiscardsFilter

       64 bit unsigned wrappable counter."
   ::= {pr1645v2PortSwEInPEntry 402653184}

pr1645v2PortSwEInPIfOutBandwidth OBJECT-TYPE
   SYNTAX      Integer32
   MAX-ACCESS  read-only
   STATUS      current
   DESCRIPTION
      "Path: ethernet3.performance.h2Performance.ifOutBandwidth

       unit name = bps
       formula = 8 * ; 8 /"
   ::= {pr1645v2PortSwEInPEntry 285212672}

pr1645v2PortSwEInPIfErrSec OBJECT-TYPE
   SYNTAX      Counter32
   MAX-ACCESS  read-only
   STATUS      current
   DESCRIPTION
      "Path: ethernet3.performance.h2Performance.ifErrSec

       32 bit unsigned wrappable counter."
   ::= {pr1645v2PortSwEInPEntry 251658240}


pr1645v2PortSwEH24InP OBJECT IDENTIFIER ::= {pr1645v2PortSwE 308}

pr1645v2PortSwEH24InPSSCTable OBJECT-TYPE
   SYNTAX      SEQUENCE OF Pr1645v2PortSwEH24InPEntry
   MAX-ACCESS  not-accessible
   STATUS      current
   DESCRIPTION
      "h24IfInPerformance"
   ::= {pr1645v2PortSwEH24InP 1}

pr1645v2PortSwEH24InPEntry OBJECT-TYPE
   SYNTAX      Pr1645v2PortSwEH24InPEntry
   MAX-ACCESS  not-accessible
   STATUS      current
   DESCRIPTION
      ""
   INDEX      { pr1645v2PortSwEH24InPTableIx }
   ::= {pr1645v2PortSwEH24InPSSCTable 1}

Pr1645v2PortSwEH24InPEntry ::=
   SEQUENCE
      {
      pr1645v2PortSwEH24InPTableIx
         TableIndex,
      pr1645v2PortSwEH24InPSysUpTime
         TimeTicks,
      pr1645v2PortSwEH24InPIfUpTime
         TimeTicks,
      pr1645v2PortSwEH24InPIfStatChanges
         Counter32,
      pr1645v2PortSwEH24InPIfInOctets
         Counter64,
      pr1645v2PortSwEH24InPIfInUCPkts
         Counter64,
      pr1645v2PortSwEH24InPIfInNUCPkts
         Counter64,
      pr1645v2PortSwEH24InPIfInBCPkts
         Counter64,
      pr1645v2PortSwEH24InPIfInMCPkts
         Counter64,
      pr1645v2PortSwEH24InPIfInDiscards
         Counter64,
      pr1645v2PortSwEH24InPIfInErrors
         Counter64,
      pr1645v2PortSwEH24InPIfInUnkwn
         Counter64,
      pr1645v2PortSwEH24InPInDropEx
         Counter64,
      pr1645v2PortSwEH24InPInDropNoMac
         Counter64,
      pr1645v2PortSwEH24InPInDropNUCast
         Counter64,
      pr1645v2PortSwEH24InPInDropFilter
         Counter64,
      pr1645v2PortSwEH24InPIfInBandwidth
         Integer32,
      pr1645v2PortSwEH24InPIfOutOctets
         Counter64,
      pr1645v2PortSwEH24InPIfOutUCPkts
         Counter64,
      pr1645v2PortSwEH24InPIfOutNUCPkts
         Counter64,
      pr1645v2PortSwEH24InPIfOutBCPkts
         Counter64,
      pr1645v2PortSwEH24InPIfOutMCPkts
         Counter64,
      pr1645v2PortSwEH24InPIfOutDiscards
         Counter64,
      pr1645v2PortSwEH24InPIfOutErrors
         Counter64,
      pr1645v2PortSwEH24InPOutDropEx
         Counter64,
      pr1645v2PortSwEH24InPOutDropNoArp
         Counter64,
      pr1645v2PortSwEH24InPOutDropFilter
         Counter64,
      pr1645v2PortSwEH24InPIfOutBandwidth
         Integer32,
      pr1645v2PortSwEH24InPIfErrSec
         Counter32
      }

pr1645v2PortSwEH24InPTableIx OBJECT-TYPE
   SYNTAX      TableIndex
   MAX-ACCESS  not-accessible
   STATUS      current
   DESCRIPTION
      ""
   ::= {pr1645v2PortSwEH24InPEntry 11}

pr1645v2PortSwEH24InPSysUpTime OBJECT-TYPE
   SYNTAX      TimeTicks
   MAX-ACCESS  read-only
   STATUS      current
   DESCRIPTION
      "Path: ethernet3.performance.h24Performance.sysUpTime

       Time in centi-second."
   ::= {pr1645v2PortSwEH24InPEntry 16777216}

pr1645v2PortSwEH24InPIfUpTime OBJECT-TYPE
   SYNTAX      TimeTicks
   MAX-ACCESS  read-only
   STATUS      current
   DESCRIPTION
      "Path: ethernet3.performance.h24Performance.ifUpTime

       Time in centi-second."
   ::= {pr1645v2PortSwEH24InPEntry 33554432}

pr1645v2PortSwEH24InPIfStatChanges OBJECT-TYPE
   SYNTAX      Counter32
   MAX-ACCESS  read-only
   STATUS      current
   DESCRIPTION
      "Path: ethernet3.performance.h24Performance.ifStatusChanges

       32 bit unsigned wrappable counter."
   ::= {pr1645v2PortSwEH24InPEntry 50331648}

pr1645v2PortSwEH24InPIfInOctets OBJECT-TYPE
   SYNTAX      Counter64
   MAX-ACCESS  read-only
   STATUS      current
   DESCRIPTION
      "Path: ethernet3.performance.h24Performance.ifInOctets

       64 bit unsigned wrappable counter."
   ::= {pr1645v2PortSwEH24InPEntry 67108864}

pr1645v2PortSwEH24InPIfInUCPkts OBJECT-TYPE
   SYNTAX      Counter64
   MAX-ACCESS  read-only
   STATUS      current
   DESCRIPTION
      "Path: ethernet3.performance.h24Performance.ifInUcastPkts

       64 bit unsigned wrappable counter."
   ::= {pr1645v2PortSwEH24InPEntry 83886080}

pr1645v2PortSwEH24InPIfInNUCPkts OBJECT-TYPE
   SYNTAX      Counter64
   MAX-ACCESS  read-only
   STATUS      current
   DESCRIPTION
      "Path: ethernet3.performance.h24Performance.ifInNUcastPkts

       64 bit unsigned wrappable counter."
   ::= {pr1645v2PortSwEH24InPEntry 100663296}

pr1645v2PortSwEH24InPIfInBCPkts OBJECT-TYPE
   SYNTAX      Counter64
   MAX-ACCESS  read-only
   STATUS      current
   DESCRIPTION
      "Path: ethernet3.performance.h24Performance.ifInBcastPkts

       64 bit unsigned wrappable counter."
   ::= {pr1645v2PortSwEH24InPEntry 419430400}

pr1645v2PortSwEH24InPIfInMCPkts OBJECT-TYPE
   SYNTAX      Counter64
   MAX-ACCESS  read-only
   STATUS      current
   DESCRIPTION
      "Path: ethernet3.performance.h24Performance.ifInMcastPkts

       64 bit unsigned wrappable counter."
   ::= {pr1645v2PortSwEH24InPEntry 436207616}

pr1645v2PortSwEH24InPIfInDiscards OBJECT-TYPE
   SYNTAX      Counter64
   MAX-ACCESS  read-only
   STATUS      current
   DESCRIPTION
      "Path: ethernet3.performance.h24Performance.ifInDiscards

       64 bit unsigned wrappable counter."
   ::= {pr1645v2PortSwEH24InPEntry 117440512}

pr1645v2PortSwEH24InPIfInErrors OBJECT-TYPE
   SYNTAX      Counter64
   MAX-ACCESS  read-only
   STATUS      current
   DESCRIPTION
      "Path: ethernet3.performance.h24Performance.ifInErrors

       64 bit unsigned wrappable counter."
   ::= {pr1645v2PortSwEH24InPEntry 134217728}

pr1645v2PortSwEH24InPIfInUnkwn OBJECT-TYPE
   SYNTAX      Counter64
   MAX-ACCESS  read-only
   STATUS      current
   DESCRIPTION
      "Path: ethernet3.performance.h24Performance.ifInUnknownProtos

       64 bit unsigned wrappable counter."
   ::= {pr1645v2PortSwEH24InPEntry 150994944}

pr1645v2PortSwEH24InPInDropEx OBJECT-TYPE
   SYNTAX      Counter64
   MAX-ACCESS  read-only
   STATUS      current
   DESCRIPTION
      "Path: ethernet3.performance.h24Performance.ifInDropLevelExceeded

       64 bit unsigned wrappable counter."
   ::= {pr1645v2PortSwEH24InPEntry 335544320}

pr1645v2PortSwEH24InPInDropNoMac OBJECT-TYPE
   SYNTAX      Counter64
   MAX-ACCESS  read-only
   STATUS      current
   DESCRIPTION
      "Path: ethernet3.performance.h24Performance.fInDiscardsNoMacFit

       64 bit unsigned wrappable counter."
   ::= {pr1645v2PortSwEH24InPEntry 301989888}

pr1645v2PortSwEH24InPInDropNUCast OBJECT-TYPE
   SYNTAX      Counter64
   MAX-ACCESS  read-only
   STATUS      current
   DESCRIPTION
      "Path: ethernet3.performance.h24Performance.fInDiscardsNUCast

       64 bit unsigned wrappable counter."
   ::= {pr1645v2PortSwEH24InPEntry 318767104}

pr1645v2PortSwEH24InPInDropFilter OBJECT-TYPE
   SYNTAX      Counter64
   MAX-ACCESS  read-only
   STATUS      current
   DESCRIPTION
      "Path: ethernet3.performance.h24Performance.fInDiscardsFilter

       64 bit unsigned wrappable counter."
   ::= {pr1645v2PortSwEH24InPEntry 385875968}

pr1645v2PortSwEH24InPIfInBandwidth OBJECT-TYPE
   SYNTAX      Integer32
   MAX-ACCESS  read-only
   STATUS      current
   DESCRIPTION
      "Path: ethernet3.performance.h24Performance.ifInBandwidth

       unit name = bps
       formula = 8 * ; 8 /"
   ::= {pr1645v2PortSwEH24InPEntry 268435456}

pr1645v2PortSwEH24InPIfOutOctets OBJECT-TYPE
   SYNTAX      Counter64
   MAX-ACCESS  read-only
   STATUS      current
   DESCRIPTION
      "Path: ethernet3.performance.h24Performance.ifOutOctets

       64 bit unsigned wrappable counter."
   ::= {pr1645v2PortSwEH24InPEntry 167772160}

pr1645v2PortSwEH24InPIfOutUCPkts OBJECT-TYPE
   SYNTAX      Counter64
   MAX-ACCESS  read-only
   STATUS      current
   DESCRIPTION
      "Path: ethernet3.performance.h24Performance.ifOutUcastPkts

       64 bit unsigned wrappable counter."
   ::= {pr1645v2PortSwEH24InPEntry 184549376}

pr1645v2PortSwEH24InPIfOutNUCPkts OBJECT-TYPE
   SYNTAX      Counter64
   MAX-ACCESS  read-only
   STATUS      current
   DESCRIPTION
      "Path: ethernet3.performance.h24Performance.ifOutNUcastPkts

       64 bit unsigned wrappable counter."
   ::= {pr1645v2PortSwEH24InPEntry 201326592}

pr1645v2PortSwEH24InPIfOutBCPkts OBJECT-TYPE
   SYNTAX      Counter64
   MAX-ACCESS  read-only
   STATUS      current
   DESCRIPTION
      "Path: ethernet3.performance.h24Performance.ifOutBcastPkts

       64 bit unsigned wrappable counter."
   ::= {pr1645v2PortSwEH24InPEntry 452984832}

pr1645v2PortSwEH24InPIfOutMCPkts OBJECT-TYPE
   SYNTAX      Counter64
   MAX-ACCESS  read-only
   STATUS      current
   DESCRIPTION
      "Path: ethernet3.performance.h24Performance.ifOutMcastPkts

       64 bit unsigned wrappable counter."
   ::= {pr1645v2PortSwEH24InPEntry 469762048}

pr1645v2PortSwEH24InPIfOutDiscards OBJECT-TYPE
   SYNTAX      Counter64
   MAX-ACCESS  read-only
   STATUS      current
   DESCRIPTION
      "Path: ethernet3.performance.h24Performance.ifOutDiscards

       64 bit unsigned wrappable counter."
   ::= {pr1645v2PortSwEH24InPEntry 218103808}

pr1645v2PortSwEH24InPIfOutErrors OBJECT-TYPE
   SYNTAX      Counter64
   MAX-ACCESS  read-only
   STATUS      current
   DESCRIPTION
      "Path: ethernet3.performance.h24Performance.ifOutErrors

       64 bit unsigned wrappable counter."
   ::= {pr1645v2PortSwEH24InPEntry 234881024}

pr1645v2PortSwEH24InPOutDropEx OBJECT-TYPE
   SYNTAX      Counter64
   MAX-ACCESS  read-only
   STATUS      current
   DESCRIPTION
      "Path: ethernet3.performance.h24Performance.ifOutDropLevelExceeded

       64 bit unsigned wrappable counter."
   ::= {pr1645v2PortSwEH24InPEntry 352321536}

pr1645v2PortSwEH24InPOutDropNoArp OBJECT-TYPE
   SYNTAX      Counter64
   MAX-ACCESS  read-only
   STATUS      current
   DESCRIPTION
      "Path: ethernet3.performance.h24Performance.ifOutDiscardsNoArp

       64 bit unsigned wrappable counter."
   ::= {pr1645v2PortSwEH24InPEntry 369098752}

pr1645v2PortSwEH24InPOutDropFilter OBJECT-TYPE
   SYNTAX      Counter64
   MAX-ACCESS  read-only
   STATUS      current
   DESCRIPTION
      "Path: ethernet3.performance.h24Performance.ifOutDiscardsFilter

       64 bit unsigned wrappable counter."
   ::= {pr1645v2PortSwEH24InPEntry 402653184}

pr1645v2PortSwEH24InPIfOutBandwidth OBJECT-TYPE
   SYNTAX      Integer32
   MAX-ACCESS  read-only
   STATUS      current
   DESCRIPTION
      "Path: ethernet3.performance.h24Performance.ifOutBandwidth

       unit name = bps
       formula = 8 * ; 8 /"
   ::= {pr1645v2PortSwEH24InPEntry 285212672}

pr1645v2PortSwEH24InPIfErrSec OBJECT-TYPE
   SYNTAX      Counter32
   MAX-ACCESS  read-only
   STATUS      current
   DESCRIPTION
      "Path: ethernet3.performance.h24Performance.ifErrSec

       32 bit unsigned wrappable counter."
   ::= {pr1645v2PortSwEH24InPEntry 251658240}


pr1645v2PortSwED7InP OBJECT IDENTIFIER ::= {pr1645v2PortSwE 309}

pr1645v2PortSwED7InPSSCTable OBJECT-TYPE
   SYNTAX      SEQUENCE OF Pr1645v2PortSwED7InPEntry
   MAX-ACCESS  not-accessible
   STATUS      current
   DESCRIPTION
      "d7IfInPerformance"
   ::= {pr1645v2PortSwED7InP 1}

pr1645v2PortSwED7InPEntry OBJECT-TYPE
   SYNTAX      Pr1645v2PortSwED7InPEntry
   MAX-ACCESS  not-accessible
   STATUS      current
   DESCRIPTION
      ""
   INDEX      { pr1645v2PortSwED7InPTableIx }
   ::= {pr1645v2PortSwED7InPSSCTable 1}

Pr1645v2PortSwED7InPEntry ::=
   SEQUENCE
      {
      pr1645v2PortSwED7InPTableIx
         TableIndex,
      pr1645v2PortSwED7InPSysUpTime
         TimeTicks,
      pr1645v2PortSwED7InPIfUpTime
         TimeTicks,
      pr1645v2PortSwED7InPIfStatChanges
         Counter32,
      pr1645v2PortSwED7InPIfInOctets
         Counter64,
      pr1645v2PortSwED7InPIfInUCPkts
         Counter64,
      pr1645v2PortSwED7InPIfInNUCPkts
         Counter64,
      pr1645v2PortSwED7InPIfInBCPkts
         Counter64,
      pr1645v2PortSwED7InPIfInMCPkts
         Counter64,
      pr1645v2PortSwED7InPIfInDiscards
         Counter64,
      pr1645v2PortSwED7InPIfInErrors
         Counter64,
      pr1645v2PortSwED7InPIfInUnkwn
         Counter64,
      pr1645v2PortSwED7InPInDropEx
         Counter64,
      pr1645v2PortSwED7InPInDropNoMac
         Counter64,
      pr1645v2PortSwED7InPInDropNUCast
         Counter64,
      pr1645v2PortSwED7InPInDropFilter
         Counter64,
      pr1645v2PortSwED7InPIfInBandwidth
         Integer32,
      pr1645v2PortSwED7InPIfOutOctets
         Counter64,
      pr1645v2PortSwED7InPIfOutUCPkts
         Counter64,
      pr1645v2PortSwED7InPIfOutNUCPkts
         Counter64,
      pr1645v2PortSwED7InPIfOutBCPkts
         Counter64,
      pr1645v2PortSwED7InPIfOutMCPkts
         Counter64,
      pr1645v2PortSwED7InPIfOutDiscards
         Counter64,
      pr1645v2PortSwED7InPIfOutErrors
         Counter64,
      pr1645v2PortSwED7InPOutDropEx
         Counter64,
      pr1645v2PortSwED7InPOutDropNoArp
         Counter64,
      pr1645v2PortSwED7InPOutDropFilter
         Counter64,
      pr1645v2PortSwED7InPIfOutBandwidth
         Integer32,
      pr1645v2PortSwED7InPIfErrSec
         Counter32
      }

pr1645v2PortSwED7InPTableIx OBJECT-TYPE
   SYNTAX      TableIndex
   MAX-ACCESS  not-accessible
   STATUS      current
   DESCRIPTION
      ""
   ::= {pr1645v2PortSwED7InPEntry 11}

pr1645v2PortSwED7InPSysUpTime OBJECT-TYPE
   SYNTAX      TimeTicks
   MAX-ACCESS  read-only
   STATUS      current
   DESCRIPTION
      "Path: ethernet3.performance.d7Performance.sysUpTime

       Time in centi-second."
   ::= {pr1645v2PortSwED7InPEntry 16777216}

pr1645v2PortSwED7InPIfUpTime OBJECT-TYPE
   SYNTAX      TimeTicks
   MAX-ACCESS  read-only
   STATUS      current
   DESCRIPTION
      "Path: ethernet3.performance.d7Performance.ifUpTime

       Time in centi-second."
   ::= {pr1645v2PortSwED7InPEntry 33554432}

pr1645v2PortSwED7InPIfStatChanges OBJECT-TYPE
   SYNTAX      Counter32
   MAX-ACCESS  read-only
   STATUS      current
   DESCRIPTION
      "Path: ethernet3.performance.d7Performance.ifStatusChanges

       32 bit unsigned wrappable counter."
   ::= {pr1645v2PortSwED7InPEntry 50331648}

pr1645v2PortSwED7InPIfInOctets OBJECT-TYPE
   SYNTAX      Counter64
   MAX-ACCESS  read-only
   STATUS      current
   DESCRIPTION
      "Path: ethernet3.performance.d7Performance.ifInOctets

       64 bit unsigned wrappable counter."
   ::= {pr1645v2PortSwED7InPEntry 67108864}

pr1645v2PortSwED7InPIfInUCPkts OBJECT-TYPE
   SYNTAX      Counter64
   MAX-ACCESS  read-only
   STATUS      current
   DESCRIPTION
      "Path: ethernet3.performance.d7Performance.ifInUcastPkts

       64 bit unsigned wrappable counter."
   ::= {pr1645v2PortSwED7InPEntry 83886080}

pr1645v2PortSwED7InPIfInNUCPkts OBJECT-TYPE
   SYNTAX      Counter64
   MAX-ACCESS  read-only
   STATUS      current
   DESCRIPTION
      "Path: ethernet3.performance.d7Performance.ifInNUcastPkts

       64 bit unsigned wrappable counter."
   ::= {pr1645v2PortSwED7InPEntry 100663296}

pr1645v2PortSwED7InPIfInBCPkts OBJECT-TYPE
   SYNTAX      Counter64
   MAX-ACCESS  read-only
   STATUS      current
   DESCRIPTION
      "Path: ethernet3.performance.d7Performance.ifInBcastPkts

       64 bit unsigned wrappable counter."
   ::= {pr1645v2PortSwED7InPEntry 419430400}

pr1645v2PortSwED7InPIfInMCPkts OBJECT-TYPE
   SYNTAX      Counter64
   MAX-ACCESS  read-only
   STATUS      current
   DESCRIPTION
      "Path: ethernet3.performance.d7Performance.ifInMcastPkts

       64 bit unsigned wrappable counter."
   ::= {pr1645v2PortSwED7InPEntry 436207616}

pr1645v2PortSwED7InPIfInDiscards OBJECT-TYPE
   SYNTAX      Counter64
   MAX-ACCESS  read-only
   STATUS      current
   DESCRIPTION
      "Path: ethernet3.performance.d7Performance.ifInDiscards

       64 bit unsigned wrappable counter."
   ::= {pr1645v2PortSwED7InPEntry 117440512}

pr1645v2PortSwED7InPIfInErrors OBJECT-TYPE
   SYNTAX      Counter64
   MAX-ACCESS  read-only
   STATUS      current
   DESCRIPTION
      "Path: ethernet3.performance.d7Performance.ifInErrors

       64 bit unsigned wrappable counter."
   ::= {pr1645v2PortSwED7InPEntry 134217728}

pr1645v2PortSwED7InPIfInUnkwn OBJECT-TYPE
   SYNTAX      Counter64
   MAX-ACCESS  read-only
   STATUS      current
   DESCRIPTION
      "Path: ethernet3.performance.d7Performance.ifInUnknownProtos

       64 bit unsigned wrappable counter."
   ::= {pr1645v2PortSwED7InPEntry 150994944}

pr1645v2PortSwED7InPInDropEx OBJECT-TYPE
   SYNTAX      Counter64
   MAX-ACCESS  read-only
   STATUS      current
   DESCRIPTION
      "Path: ethernet3.performance.d7Performance.ifInDropLevelExceeded

       64 bit unsigned wrappable counter."
   ::= {pr1645v2PortSwED7InPEntry 335544320}

pr1645v2PortSwED7InPInDropNoMac OBJECT-TYPE
   SYNTAX      Counter64
   MAX-ACCESS  read-only
   STATUS      current
   DESCRIPTION
      "Path: ethernet3.performance.d7Performance.fInDiscardsNoMacFit

       64 bit unsigned wrappable counter."
   ::= {pr1645v2PortSwED7InPEntry 301989888}

pr1645v2PortSwED7InPInDropNUCast OBJECT-TYPE
   SYNTAX      Counter64
   MAX-ACCESS  read-only
   STATUS      current
   DESCRIPTION
      "Path: ethernet3.performance.d7Performance.fInDiscardsNUCast

       64 bit unsigned wrappable counter."
   ::= {pr1645v2PortSwED7InPEntry 318767104}

pr1645v2PortSwED7InPInDropFilter OBJECT-TYPE
   SYNTAX      Counter64
   MAX-ACCESS  read-only
   STATUS      current
   DESCRIPTION
      "Path: ethernet3.performance.d7Performance.fInDiscardsFilter

       64 bit unsigned wrappable counter."
   ::= {pr1645v2PortSwED7InPEntry 385875968}

pr1645v2PortSwED7InPIfInBandwidth OBJECT-TYPE
   SYNTAX      Integer32
   MAX-ACCESS  read-only
   STATUS      current
   DESCRIPTION
      "Path: ethernet3.performance.d7Performance.ifInBandwidth

       unit name = bps
       formula = 8 * ; 8 /"
   ::= {pr1645v2PortSwED7InPEntry 268435456}

pr1645v2PortSwED7InPIfOutOctets OBJECT-TYPE
   SYNTAX      Counter64
   MAX-ACCESS  read-only
   STATUS      current
   DESCRIPTION
      "Path: ethernet3.performance.d7Performance.ifOutOctets

       64 bit unsigned wrappable counter."
   ::= {pr1645v2PortSwED7InPEntry 167772160}

pr1645v2PortSwED7InPIfOutUCPkts OBJECT-TYPE
   SYNTAX      Counter64
   MAX-ACCESS  read-only
   STATUS      current
   DESCRIPTION
      "Path: ethernet3.performance.d7Performance.ifOutUcastPkts

       64 bit unsigned wrappable counter."
   ::= {pr1645v2PortSwED7InPEntry 184549376}

pr1645v2PortSwED7InPIfOutNUCPkts OBJECT-TYPE
   SYNTAX      Counter64
   MAX-ACCESS  read-only
   STATUS      current
   DESCRIPTION
      "Path: ethernet3.performance.d7Performance.ifOutNUcastPkts

       64 bit unsigned wrappable counter."
   ::= {pr1645v2PortSwED7InPEntry 201326592}

pr1645v2PortSwED7InPIfOutBCPkts OBJECT-TYPE
   SYNTAX      Counter64
   MAX-ACCESS  read-only
   STATUS      current
   DESCRIPTION
      "Path: ethernet3.performance.d7Performance.ifOutBcastPkts

       64 bit unsigned wrappable counter."
   ::= {pr1645v2PortSwED7InPEntry 452984832}

pr1645v2PortSwED7InPIfOutMCPkts OBJECT-TYPE
   SYNTAX      Counter64
   MAX-ACCESS  read-only
   STATUS      current
   DESCRIPTION
      "Path: ethernet3.performance.d7Performance.ifOutMcastPkts

       64 bit unsigned wrappable counter."
   ::= {pr1645v2PortSwED7InPEntry 469762048}

pr1645v2PortSwED7InPIfOutDiscards OBJECT-TYPE
   SYNTAX      Counter64
   MAX-ACCESS  read-only
   STATUS      current
   DESCRIPTION
      "Path: ethernet3.performance.d7Performance.ifOutDiscards

       64 bit unsigned wrappable counter."
   ::= {pr1645v2PortSwED7InPEntry 218103808}

pr1645v2PortSwED7InPIfOutErrors OBJECT-TYPE
   SYNTAX      Counter64
   MAX-ACCESS  read-only
   STATUS      current
   DESCRIPTION
      "Path: ethernet3.performance.d7Performance.ifOutErrors

       64 bit unsigned wrappable counter."
   ::= {pr1645v2PortSwED7InPEntry 234881024}

pr1645v2PortSwED7InPOutDropEx OBJECT-TYPE
   SYNTAX      Counter64
   MAX-ACCESS  read-only
   STATUS      current
   DESCRIPTION
      "Path: ethernet3.performance.d7Performance.ifOutDropLevelExceeded

       64 bit unsigned wrappable counter."
   ::= {pr1645v2PortSwED7InPEntry 352321536}

pr1645v2PortSwED7InPOutDropNoArp OBJECT-TYPE
   SYNTAX      Counter64
   MAX-ACCESS  read-only
   STATUS      current
   DESCRIPTION
      "Path: ethernet3.performance.d7Performance.ifOutDiscardsNoArp

       64 bit unsigned wrappable counter."
   ::= {pr1645v2PortSwED7InPEntry 369098752}

pr1645v2PortSwED7InPOutDropFilter OBJECT-TYPE
   SYNTAX      Counter64
   MAX-ACCESS  read-only
   STATUS      current
   DESCRIPTION
      "Path: ethernet3.performance.d7Performance.ifOutDiscardsFilter

       64 bit unsigned wrappable counter."
   ::= {pr1645v2PortSwED7InPEntry 402653184}

pr1645v2PortSwED7InPIfOutBandwidth OBJECT-TYPE
   SYNTAX      Integer32
   MAX-ACCESS  read-only
   STATUS      current
   DESCRIPTION
      "Path: ethernet3.performance.d7Performance.ifOutBandwidth

       unit name = bps
       formula = 8 * ; 8 /"
   ::= {pr1645v2PortSwED7InPEntry 285212672}

pr1645v2PortSwED7InPIfErrSec OBJECT-TYPE
   SYNTAX      Counter32
   MAX-ACCESS  read-only
   STATUS      current
   DESCRIPTION
      "Path: ethernet3.performance.d7Performance.ifErrSec

       32 bit unsigned wrappable counter."
   ::= {pr1645v2PortSwED7InPEntry 251658240}


pr1645v2PortSwEIfInPriorityQueues OBJECT IDENTIFIER ::= {pr1645v2PortSwE 131}

pr1645v2PortSwEIfInPriorityQueuesSSCTable OBJECT-TYPE
   SYNTAX      SEQUENCE OF Pr1645v2PortSwEIfInPriorityQueuesEntry
   MAX-ACCESS  not-accessible
   STATUS      current
   DESCRIPTION
      "Queue Lengths"
   ::= {pr1645v2PortSwEIfInPriorityQueues 1}

pr1645v2PortSwEIfInPriorityQueuesEntry OBJECT-TYPE
   SYNTAX      Pr1645v2PortSwEIfInPriorityQueuesEntry
   MAX-ACCESS  not-accessible
   STATUS      current
   DESCRIPTION
      ""
   INDEX      { pr1645v2PortSwEIfInPriorityQueuesTableIx }
   ::= {pr1645v2PortSwEIfInPriorityQueuesSSCTable 1}

Pr1645v2PortSwEIfInPriorityQueuesEntry ::=
   SEQUENCE
      {
      pr1645v2PortSwEIfInPriorityQueuesTableIx
         TableIndex,
      pr1645v2PortSwEIfInPriorityQueuesName
         INTEGER,
      pr1645v2PortSwEIfInPriorityQueuesLength
         Integer32,
      pr1645v2PortSwEIfInPriorityQueuesOctetLength
         Integer32,
      pr1645v2PortSwEIfInPriorityQueuesRedLength
         Integer32,
      pr1645v2PortSwEIfInPriorityQueuesPacketsTotal
         Counter64,
      pr1645v2PortSwEIfInPriorityQueuesPacketsDirectTx
         Counter64,
      pr1645v2PortSwEIfInPriorityQueuesPacketsQueued
         Counter64,
      pr1645v2PortSwEIfInPriorityQueuesPacketsDropped
         Counter64,
      pr1645v2PortSwEIfInPriorityQueuesPacketsRedDropped
         Counter64,
      pr1645v2PortSwEIfInPriorityQueuesPacketsCirTx
         Counter64,
      pr1645v2PortSwEIfInPriorityQueuesPacketsEirTx
         Counter64,
      pr1645v2PortSwEIfInPriorityQueuesPacketsViolateTx
         Counter64,
      pr1645v2PortSwEIfInPriorityQueuesOctetsTotal
         Counter64,
      pr1645v2PortSwEIfInPriorityQueuesOctetsDirectTx
         Counter64,
      pr1645v2PortSwEIfInPriorityQueuesOctetsQueued
         Counter64,
      pr1645v2PortSwEIfInPriorityQueuesOctetsDropped
         Counter64,
      pr1645v2PortSwEIfInPriorityQueuesOctetsRedDropped
         Counter64,
      pr1645v2PortSwEIfInPriorityQueuesOctetsCirTx
         Counter64,
      pr1645v2PortSwEIfInPriorityQueuesOctetsEirTx
         Counter64,
      pr1645v2PortSwEIfInPriorityQueuesOctetsViolateTx
         Counter64,
      pr1645v2PortSwEIfInPriorityQueuesOctetsBandwidth15sec
         Integer32,
      pr1645v2PortSwEIfInPriorityQueuesOctetsBandwidth30sec
         Integer32,
      pr1645v2PortSwEIfInPriorityQueuesOctetsBandwidth1min
         Integer32,
      pr1645v2PortSwEIfInPriorityQueuesOctetsBandwidth2min
         Integer32,
      pr1645v2PortSwEIfInPriorityQueuesOctetsBandwidth5min
         Integer32
      }

pr1645v2PortSwEIfInPriorityQueuesTableIx OBJECT-TYPE
   SYNTAX      TableIndex
   MAX-ACCESS  not-accessible
   STATUS      current
   DESCRIPTION
      ""
   ::= {pr1645v2PortSwEIfInPriorityQueuesEntry 11}

pr1645v2PortSwEIfInPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PortSwEIfInPriorityQueuesEntry 16777216}

pr1645v2PortSwEIfInPriorityQueuesLength OBJECT-TYPE
   SYNTAX      Integer32
   MAX-ACCESS  read-only
   STATUS      current
   DESCRIPTION
      "Path: ethernet3.performance.ifInPriorityQueues.length"
   ::= {pr1645v2PortSwEIfInPriorityQueuesEntry 33554432}

pr1645v2PortSwEIfInPriorityQueuesOctetLength OBJECT-TYPE
   SYNTAX      Integer32
   MAX-ACCESS  read-only
   STATUS      current
   DESCRIPTION
      "Path: ethernet3.performance.ifInPriorityQueues.octetLength"
   ::= {pr1645v2PortSwEIfInPriorityQueuesEntry 150994944}

pr1645v2PortSwEIfInPriorityQueuesRedLength OBJECT-TYPE
   SYNTAX      Integer32
   MAX-ACCESS  read-only
   STATUS      current
   DESCRIPTION
      "Path: ethernet3.performance.ifInPriorityQueues.redLength"
   ::= {pr1645v2PortSwEIfInPriorityQueuesEntry 134217728}

pr1645v2PortSwEIfInPriorityQueuesPacketsTotal OBJECT-TYPE
   SYNTAX      Counter64
   MAX-ACCESS  read-only
   STATUS      current
   DESCRIPTION
      "Path: ethernet3.performance.ifInPriorityQueues.packets.total

       64 bit unsigned wrappable counter."
   ::= {pr1645v2PortSwEIfInPriorityQueuesEntry 50790400}

pr1645v2PortSwEIfInPriorityQueuesPacketsDirectTx OBJECT-TYPE
   SYNTAX      Counter64
   MAX-ACCESS  read-only
   STATUS      current
   DESCRIPTION
      "Path: ethernet3.performance.ifInPriorityQueues.packets.directTx

       64 bit unsigned wrappable counter."
   ::= {pr1645v2PortSwEIfInPriorityQueuesEntry 50397184}

pr1645v2PortSwEIfInPriorityQueuesPacketsQueued OBJECT-TYPE
   SYNTAX      Counter64
   MAX-ACCESS  read-only
   STATUS      current
   DESCRIPTION
      "Path: ethernet3.performance.ifInPriorityQueues.packets.queued

       64 bit unsigned wrappable counter."
   ::= {pr1645v2PortSwEIfInPriorityQueuesEntry 50462720}

pr1645v2PortSwEIfInPriorityQueuesPacketsDropped OBJECT-TYPE
   SYNTAX      Counter64
   MAX-ACCESS  read-only
   STATUS      current
   DESCRIPTION
      "Path: ethernet3.performance.ifInPriorityQueues.packets.dropped

       64 bit unsigned wrappable counter."
   ::= {pr1645v2PortSwEIfInPriorityQueuesEntry 50528256}

pr1645v2PortSwEIfInPriorityQueuesPacketsRedDropped OBJECT-TYPE
   SYNTAX      Counter64
   MAX-ACCESS  read-only
   STATUS      current
   DESCRIPTION
      "Path: ethernet3.performance.ifInPriorityQueues.packets.redDropped

       64 bit unsigned wrappable counter."
   ::= {pr1645v2PortSwEIfInPriorityQueuesEntry 50724864}

pr1645v2PortSwEIfInPriorityQueuesPacketsCirTx OBJECT-TYPE
   SYNTAX      Counter64
   MAX-ACCESS  read-only
   STATUS      current
   DESCRIPTION
      "Path: ethernet3.performance.ifInPriorityQueues.packets.cirTx

       64 bit unsigned wrappable counter."
   ::= {pr1645v2PortSwEIfInPriorityQueuesEntry 50593792}

pr1645v2PortSwEIfInPriorityQueuesPacketsEirTx OBJECT-TYPE
   SYNTAX      Counter64
   MAX-ACCESS  read-only
   STATUS      current
   DESCRIPTION
      "Path: ethernet3.performance.ifInPriorityQueues.packets.eirTx

       64 bit unsigned wrappable counter."
   ::= {pr1645v2PortSwEIfInPriorityQueuesEntry 50659328}

pr1645v2PortSwEIfInPriorityQueuesPacketsViolateTx OBJECT-TYPE
   SYNTAX      Counter64
   MAX-ACCESS  read-only
   STATUS      current
   DESCRIPTION
      "Path: ethernet3.performance.ifInPriorityQueues.packets.violateTx

       64 bit unsigned wrappable counter."
   ::= {pr1645v2PortSwEIfInPriorityQueuesEntry 50855936}

pr1645v2PortSwEIfInPriorityQueuesOctetsTotal OBJECT-TYPE
   SYNTAX      Counter64
   MAX-ACCESS  read-only
   STATUS      current
   DESCRIPTION
      "Path: ethernet3.performance.ifInPriorityQueues.octets.total

       64 bit unsigned wrappable counter."
   ::= {pr1645v2PortSwEIfInPriorityQueuesEntry 67567616}

pr1645v2PortSwEIfInPriorityQueuesOctetsDirectTx OBJECT-TYPE
   SYNTAX      Counter64
   MAX-ACCESS  read-only
   STATUS      current
   DESCRIPTION
      "Path: ethernet3.performance.ifInPriorityQueues.octets.directTx

       64 bit unsigned wrappable counter."
   ::= {pr1645v2PortSwEIfInPriorityQueuesEntry 67174400}

pr1645v2PortSwEIfInPriorityQueuesOctetsQueued OBJECT-TYPE
   SYNTAX      Counter64
   MAX-ACCESS  read-only
   STATUS      current
   DESCRIPTION
      "Path: ethernet3.performance.ifInPriorityQueues.octets.queued

       64 bit unsigned wrappable counter."
   ::= {pr1645v2PortSwEIfInPriorityQueuesEntry 67239936}

pr1645v2PortSwEIfInPriorityQueuesOctetsDropped OBJECT-TYPE
   SYNTAX      Counter64
   MAX-ACCESS  read-only
   STATUS      current
   DESCRIPTION
      "Path: ethernet3.performance.ifInPriorityQueues.octets.dropped

       64 bit unsigned wrappable counter."
   ::= {pr1645v2PortSwEIfInPriorityQueuesEntry 67305472}

pr1645v2PortSwEIfInPriorityQueuesOctetsRedDropped OBJECT-TYPE
   SYNTAX      Counter64
   MAX-ACCESS  read-only
   STATUS      current
   DESCRIPTION
      "Path: ethernet3.performance.ifInPriorityQueues.octets.redDropped

       64 bit unsigned wrappable counter."
   ::= {pr1645v2PortSwEIfInPriorityQueuesEntry 67502080}

pr1645v2PortSwEIfInPriorityQueuesOctetsCirTx OBJECT-TYPE
   SYNTAX      Counter64
   MAX-ACCESS  read-only
   STATUS      current
   DESCRIPTION
      "Path: ethernet3.performance.ifInPriorityQueues.octets.cirTx

       64 bit unsigned wrappable counter."
   ::= {pr1645v2PortSwEIfInPriorityQueuesEntry 67371008}

pr1645v2PortSwEIfInPriorityQueuesOctetsEirTx OBJECT-TYPE
   SYNTAX      Counter64
   MAX-ACCESS  read-only
   STATUS      current
   DESCRIPTION
      "Path: ethernet3.performance.ifInPriorityQueues.octets.eirTx

       64 bit unsigned wrappable counter."
   ::= {pr1645v2PortSwEIfInPriorityQueuesEntry 67436544}

pr1645v2PortSwEIfInPriorityQueuesOctetsViolateTx OBJECT-TYPE
   SYNTAX      Counter64
   MAX-ACCESS  read-only
   STATUS      current
   DESCRIPTION
      "Path: ethernet3.performance.ifInPriorityQueues.octets.violateTx

       64 bit unsigned wrappable counter."
   ::= {pr1645v2PortSwEIfInPriorityQueuesEntry 67633152}

pr1645v2PortSwEIfInPriorityQueuesOctetsBandwidth15sec OBJECT-TYPE
   SYNTAX      Integer32
   MAX-ACCESS  read-only
   STATUS      current
   DESCRIPTION
      "Path: ethernet3.performance.ifInPriorityQueues.octets.bandwidth.15sec

       unit name = bps
       formula = 8 * ; 8 /"
   ::= {pr1645v2PortSwEIfInPriorityQueuesEntry 70386944}

pr1645v2PortSwEIfInPriorityQueuesOctetsBandwidth30sec OBJECT-TYPE
   SYNTAX      Integer32
   MAX-ACCESS  read-only
   STATUS      current
   DESCRIPTION
      "Path: ethernet3.performance.ifInPriorityQueues.octets.bandwidth.30sec

       unit name = bps
       formula = 8 * ; 8 /"
   ::= {pr1645v2PortSwEIfInPriorityQueuesEntry 70388224}

pr1645v2PortSwEIfInPriorityQueuesOctetsBandwidth1min OBJECT-TYPE
   SYNTAX      Integer32
   MAX-ACCESS  read-only
   STATUS      current
   DESCRIPTION
      "Path: ethernet3.performance.ifInPriorityQueues.octets.bandwidth.1min

       unit name = bps
       formula = 8 * ; 8 /"
   ::= {pr1645v2PortSwEIfInPriorityQueuesEntry 70390784}

pr1645v2PortSwEIfInPriorityQueuesOctetsBandwidth2min OBJECT-TYPE
   SYNTAX      Integer32
   MAX-ACCESS  read-only
   STATUS      current
   DESCRIPTION
      "Path: ethernet3.performance.ifInPriorityQueues.octets.bandwidth.2min

       unit name = bps
       formula = 8 * ; 8 /"
   ::= {pr1645v2PortSwEIfInPriorityQueuesEntry 70395904}

pr1645v2PortSwEIfInPriorityQueuesOctetsBandwidth5min OBJECT-TYPE
   SYNTAX      Integer32
   MAX-ACCESS  read-only
   STATUS      current
   DESCRIPTION
      "Path: ethernet3.performance.ifInPriorityQueues.octets.bandwidth.5min

       unit name = bps
       formula = 8 * ; 8 /"
   ::= {pr1645v2PortSwEIfInPriorityQueuesEntry 70411264}

pr1645v2PortSwEIfInPriorityQueuesH2Performance OBJECT-TYPE
   SYNTAX      SEQUENCE OF Pr1645v2PortSwEIfInPriorityQueuesH2PerformanceEntry
   MAX-ACCESS  not-accessible
   STATUS      current
   DESCRIPTION
      ""
   ::= {pr1645v2PortSwEIfInPriorityQueues 83886080}

pr1645v2PortSwEIfInPriorityQueuesH2PerformanceEntry OBJECT-TYPE
   SYNTAX      Pr1645v2PortSwEIfInPriorityQueuesH2PerformanceEntry
   MAX-ACCESS  not-accessible
   STATUS      current
   DESCRIPTION
      ""
   INDEX      { pr1645v2PortSwEIfInPriorityQueuesTableIx,
                pr1645v2PortSwEIfInPriorityQueuesH2PerformanceTableIx }
   ::= {pr1645v2PortSwEIfInPriorityQueuesH2Performance 1}

Pr1645v2PortSwEIfInPriorityQueuesH2PerformanceEntry ::=
   SEQUENCE
      {
      pr1645v2PortSwEIfInPriorityQueuesH2PerformanceTableIx
         TableIndex,
      pr1645v2PortSwEIfInPriorityQueuesH2PerformanceSysUpTime
         TimeTicks,
      pr1645v2PortSwEIfInPriorityQueuesH2PerformanceTotPkts
         Counter64,
      pr1645v2PortSwEIfInPriorityQueuesH2PerformanceDirTxPkts
         Counter64,
      pr1645v2PortSwEIfInPriorityQueuesH2PerformanceQdPkts
         Counter64,
      pr1645v2PortSwEIfInPriorityQueuesH2PerformanceDropPkts
         Counter64,
      pr1645v2PortSwEIfInPriorityQueuesH2PerformanceRDropPkts
         Counter64,
      pr1645v2PortSwEIfInPriorityQueuesH2PerformanceCirTxPkts
         Counter64,
      pr1645v2PortSwEIfInPriorityQueuesH2PerformanceEirTxPkts
         Counter64,
      pr1645v2PortSwEIfInPriorityQueuesH2PerformanceViolTxPkts
         Counter64,
      pr1645v2PortSwEIfInPriorityQueuesH2PerformanceTotOcts
         Counter64,
      pr1645v2PortSwEIfInPriorityQueuesH2PerformanceDirTxOcts
         Counter64,
      pr1645v2PortSwEIfInPriorityQueuesH2PerformanceQdOcts
         Counter64,
      pr1645v2PortSwEIfInPriorityQueuesH2PerformanceDropOcts
         Counter64,
      pr1645v2PortSwEIfInPriorityQueuesH2PerformanceRDropOcts
         Counter64,
      pr1645v2PortSwEIfInPriorityQueuesH2PerformanceCirTxOcts
         Counter64,
      pr1645v2PortSwEIfInPriorityQueuesH2PerformanceEirTxOcts
         Counter64,
      pr1645v2PortSwEIfInPriorityQueuesH2PerformanceViolTxOcts
         Counter64,
      pr1645v2PortSwEIfInPriorityQueuesH2PerformanceBandwidth
         Integer32
      }

pr1645v2PortSwEIfInPriorityQueuesH2PerformanceTableIx OBJECT-TYPE
   SYNTAX      TableIndex
   MAX-ACCESS  not-accessible
   STATUS      current
   DESCRIPTION
      ""
   ::= {pr1645v2PortSwEIfInPriorityQueuesH2PerformanceEntry 11}

pr1645v2PortSwEIfInPriorityQueuesH2PerformanceSysUpTime OBJECT-TYPE
   SYNTAX      TimeTicks
   MAX-ACCESS  read-only
   STATUS      current
   DESCRIPTION
      "Path: ethernet3.performance.ifInPriorityQueues.h2Performance.sysUpTime

       Time in centi-second."
   ::= {pr1645v2PortSwEIfInPriorityQueuesH2PerformanceEntry 16777216}

pr1645v2PortSwEIfInPriorityQueuesH2PerformanceTotPkts OBJECT-TYPE
   SYNTAX      Counter64
   MAX-ACCESS  read-only
   STATUS      current
   DESCRIPTION
      "Path: ethernet3.performance.ifInPriorityQueues.h2Performance.totalPkts

       64 bit unsigned wrappable counter."
   ::= {pr1645v2PortSwEIfInPriorityQueuesH2PerformanceEntry 234881024}

pr1645v2PortSwEIfInPriorityQueuesH2PerformanceDirTxPkts OBJECT-TYPE
   SYNTAX      Counter64
   MAX-ACCESS  read-only
   STATUS      current
   DESCRIPTION
      "Path: ethernet3.performance.ifInPriorityQueues.h2Performance.directTxPkts

       64 bit unsigned wrappable counter."
   ::= {pr1645v2PortSwEIfInPriorityQueuesH2PerformanceEntry 33554432}

pr1645v2PortSwEIfInPriorityQueuesH2PerformanceQdPkts OBJECT-TYPE
   SYNTAX      Counter64
   MAX-ACCESS  read-only
   STATUS      current
   DESCRIPTION
      "Path: ethernet3.performance.ifInPriorityQueues.h2Performance.queuedPkts

       64 bit unsigned wrappable counter."
   ::= {pr1645v2PortSwEIfInPriorityQueuesH2PerformanceEntry 50331648}

pr1645v2PortSwEIfInPriorityQueuesH2PerformanceDropPkts OBJECT-TYPE
   SYNTAX      Counter64
   MAX-ACCESS  read-only
   STATUS      current
   DESCRIPTION
      "Path: ethernet3.performance.ifInPriorityQueues.h2Performance.droppedPkts

       64 bit unsigned wrappable counter."
   ::= {pr1645v2PortSwEIfInPriorityQueuesH2PerformanceEntry 67108864}

pr1645v2PortSwEIfInPriorityQueuesH2PerformanceRDropPkts OBJECT-TYPE
   SYNTAX      Counter64
   MAX-ACCESS  read-only
   STATUS      current
   DESCRIPTION
      "Path: ethernet3.performance.ifInPriorityQueues.h2Performance.redDroppedPkts

       64 bit unsigned wrappable counter."
   ::= {pr1645v2PortSwEIfInPriorityQueuesH2PerformanceEntry 201326592}

pr1645v2PortSwEIfInPriorityQueuesH2PerformanceCirTxPkts OBJECT-TYPE
   SYNTAX      Counter64
   MAX-ACCESS  read-only
   STATUS      current
   DESCRIPTION
      "Path: ethernet3.performance.ifInPriorityQueues.h2Performance.cirTxPkts

       64 bit unsigned wrappable counter."
   ::= {pr1645v2PortSwEIfInPriorityQueuesH2PerformanceEntry 83886080}

pr1645v2PortSwEIfInPriorityQueuesH2PerformanceEirTxPkts OBJECT-TYPE
   SYNTAX      Counter64
   MAX-ACCESS  read-only
   STATUS      current
   DESCRIPTION
      "Path: ethernet3.performance.ifInPriorityQueues.h2Performance.eirTxPkts

       64 bit unsigned wrappable counter."
   ::= {pr1645v2PortSwEIfInPriorityQueuesH2PerformanceEntry 100663296}

pr1645v2PortSwEIfInPriorityQueuesH2PerformanceViolTxPkts OBJECT-TYPE
   SYNTAX      Counter64
   MAX-ACCESS  read-only
   STATUS      current
   DESCRIPTION
      "Path: ethernet3.performance.ifInPriorityQueues.h2Performance.violateTxPkts

       64 bit unsigned wrappable counter."
   ::= {pr1645v2PortSwEIfInPriorityQueuesH2PerformanceEntry 301989888}

pr1645v2PortSwEIfInPriorityQueuesH2PerformanceTotOcts OBJECT-TYPE
   SYNTAX      Counter64
   MAX-ACCESS  read-only
   STATUS      current
   DESCRIPTION
      "Path: ethernet3.performance.ifInPriorityQueues.h2Performance.totalOctets

       64 bit unsigned wrappable counter."
   ::= {pr1645v2PortSwEIfInPriorityQueuesH2PerformanceEntry 251658240}

pr1645v2PortSwEIfInPriorityQueuesH2PerformanceDirTxOcts OBJECT-TYPE
   SYNTAX      Counter64
   MAX-ACCESS  read-only
   STATUS      current
   DESCRIPTION
      "Path: ethernet3.performance.ifInPriorityQueues.h2Performance.directTxOctets

       64 bit unsigned wrappable counter."
   ::= {pr1645v2PortSwEIfInPriorityQueuesH2PerformanceEntry 117440512}

pr1645v2PortSwEIfInPriorityQueuesH2PerformanceQdOcts OBJECT-TYPE
   SYNTAX      Counter64
   MAX-ACCESS  read-only
   STATUS      current
   DESCRIPTION
      "Path: ethernet3.performance.ifInPriorityQueues.h2Performance.queuedOctets

       64 bit unsigned wrappable counter."
   ::= {pr1645v2PortSwEIfInPriorityQueuesH2PerformanceEntry 134217728}

pr1645v2PortSwEIfInPriorityQueuesH2PerformanceDropOcts OBJECT-TYPE
   SYNTAX      Counter64
   MAX-ACCESS  read-only
   STATUS      current
   DESCRIPTION
      "Path: ethernet3.performance.ifInPriorityQueues.h2Performance.droppedOctets

       64 bit unsigned wrappable counter."
   ::= {pr1645v2PortSwEIfInPriorityQueuesH2PerformanceEntry 150994944}

pr1645v2PortSwEIfInPriorityQueuesH2PerformanceRDropOcts OBJECT-TYPE
   SYNTAX      Counter64
   MAX-ACCESS  read-only
   STATUS      current
   DESCRIPTION
      "Path: ethernet3.performance.ifInPriorityQueues.h2Performance.redDroppedOctets

       64 bit unsigned wrappable counter."
   ::= {pr1645v2PortSwEIfInPriorityQueuesH2PerformanceEntry 218103808}

pr1645v2PortSwEIfInPriorityQueuesH2PerformanceCirTxOcts OBJECT-TYPE
   SYNTAX      Counter64
   MAX-ACCESS  read-only
   STATUS      current
   DESCRIPTION
      "Path: ethernet3.performance.ifInPriorityQueues.h2Performance.cirTxOctets

       64 bit unsigned wrappable counter."
   ::= {pr1645v2PortSwEIfInPriorityQueuesH2PerformanceEntry 167772160}

pr1645v2PortSwEIfInPriorityQueuesH2PerformanceEirTxOcts OBJECT-TYPE
   SYNTAX      Counter64
   MAX-ACCESS  read-only
   STATUS      current
   DESCRIPTION
      "Path: ethernet3.performance.ifInPriorityQueues.h2Performance.eirTxOctets

       64 bit unsigned wrappable counter."
   ::= {pr1645v2PortSwEIfInPriorityQueuesH2PerformanceEntry 184549376}

pr1645v2PortSwEIfInPriorityQueuesH2PerformanceViolTxOcts OBJECT-TYPE
   SYNTAX      Counter64
   MAX-ACCESS  read-only
   STATUS      current
   DESCRIPTION
      "Path: ethernet3.performance.ifInPriorityQueues.h2Performance.violateTxOctets

       64 bit unsigned wrappable counter."
   ::= {pr1645v2PortSwEIfInPriorityQueuesH2PerformanceEntry 318767104}

pr1645v2PortSwEIfInPriorityQueuesH2PerformanceBandwidth OBJECT-TYPE
   SYNTAX      Integer32
   MAX-ACCESS  read-only
   STATUS      current
   DESCRIPTION
      "Path: ethernet3.performance.ifInPriorityQueues.h2Performance.bandwidth

       unit name = bps
       formula = 8 * ; 8 /"
   ::= {pr1645v2PortSwEIfInPriorityQueuesH2PerformanceEntry 268435456}

pr1645v2PortSwEIfInPriorityQueuesH24Performance OBJECT-TYPE
   SYNTAX      SEQUENCE OF Pr1645v2PortSwEIfInPriorityQueuesH24PerformanceEntry
   MAX-ACCESS  not-accessible
   STATUS      current
   DESCRIPTION
      ""
   ::= {pr1645v2PortSwEIfInPriorityQueues 100663296}

pr1645v2PortSwEIfInPriorityQueuesH24PerformanceEntry OBJECT-TYPE
   SYNTAX      Pr1645v2PortSwEIfInPriorityQueuesH24PerformanceEntry
   MAX-ACCESS  not-accessible
   STATUS      current
   DESCRIPTION
      ""
   INDEX      { pr1645v2PortSwEIfInPriorityQueuesTableIx,
                pr1645v2PortSwEIfInPriorityQueuesH24PerformanceTableIx }
   ::= {pr1645v2PortSwEIfInPriorityQueuesH24Performance 1}

Pr1645v2PortSwEIfInPriorityQueuesH24PerformanceEntry ::=
   SEQUENCE
      {
      pr1645v2PortSwEIfInPriorityQueuesH24PerformanceTableIx
         TableIndex,
      pr1645v2PortSwEIfInPriorityQueuesH24PerformanceSysUpTime
         TimeTicks,
      pr1645v2PortSwEIfInPriorityQueuesH24PerformanceTotPkts
         Counter64,
      pr1645v2PortSwEIfInPriorityQueuesH24PerformanceDirTxPkts
         Counter64,
      pr1645v2PortSwEIfInPriorityQueuesH24PerformanceQdPkts
         Counter64,
      pr1645v2PortSwEIfInPriorityQueuesH24PerformanceDropPkts
         Counter64,
      pr1645v2PortSwEIfInPriorityQueuesH24PerformanceRDropPkts
         Counter64,
      pr1645v2PortSwEIfInPriorityQueuesH24PerformanceCirTxPkts
         Counter64,
      pr1645v2PortSwEIfInPriorityQueuesH24PerformanceEirTxPkts
         Counter64,
      pr1645v2PortSwEIfInPriorityQueuesH24PerformanceViolTxPkts
         Counter64,
      pr1645v2PortSwEIfInPriorityQueuesH24PerformanceTotOcts
         Counter64,
      pr1645v2PortSwEIfInPriorityQueuesH24PerformanceDirTxOcts
         Counter64,
      pr1645v2PortSwEIfInPriorityQueuesH24PerformanceQdOcts
         Counter64,
      pr1645v2PortSwEIfInPriorityQueuesH24PerformanceDropOcts
         Counter64,
      pr1645v2PortSwEIfInPriorityQueuesH24PerformanceRDropOcts
         Counter64,
      pr1645v2PortSwEIfInPriorityQueuesH24PerformanceCirTxOcts
         Counter64,
      pr1645v2PortSwEIfInPriorityQueuesH24PerformanceEirTxOcts
         Counter64,
      pr1645v2PortSwEIfInPriorityQueuesH24PerformanceViolTxOcts
         Counter64,
      pr1645v2PortSwEIfInPriorityQueuesH24PerformanceBandwidth
         Integer32
      }

pr1645v2PortSwEIfInPriorityQueuesH24PerformanceTableIx OBJECT-TYPE
   SYNTAX      TableIndex
   MAX-ACCESS  not-accessible
   STATUS      current
   DESCRIPTION
      ""
   ::= {pr1645v2PortSwEIfInPriorityQueuesH24PerformanceEntry 11}

pr1645v2PortSwEIfInPriorityQueuesH24PerformanceSysUpTime OBJECT-TYPE
   SYNTAX      TimeTicks
   MAX-ACCESS  read-only
   STATUS      current
   DESCRIPTION
      "Path: ethernet3.performance.ifInPriorityQueues.h24Performance.sysUpTime

       Time in centi-second."
   ::= {pr1645v2PortSwEIfInPriorityQueuesH24PerformanceEntry 16777216}

pr1645v2PortSwEIfInPriorityQueuesH24PerformanceTotPkts OBJECT-TYPE
   SYNTAX      Counter64
   MAX-ACCESS  read-only
   STATUS      current
   DESCRIPTION
      "Path: ethernet3.performance.ifInPriorityQueues.h24Performance.totalPkts

       64 bit unsigned wrappable counter."
   ::= {pr1645v2PortSwEIfInPriorityQueuesH24PerformanceEntry 234881024}

pr1645v2PortSwEIfInPriorityQueuesH24PerformanceDirTxPkts OBJECT-TYPE
   SYNTAX      Counter64
   MAX-ACCESS  read-only
   STATUS      current
   DESCRIPTION
      "Path: ethernet3.performance.ifInPriorityQueues.h24Performance.directTxPkts

       64 bit unsigned wrappable counter."
   ::= {pr1645v2PortSwEIfInPriorityQueuesH24PerformanceEntry 33554432}

pr1645v2PortSwEIfInPriorityQueuesH24PerformanceQdPkts OBJECT-TYPE
   SYNTAX      Counter64
   MAX-ACCESS  read-only
   STATUS      current
   DESCRIPTION
      "Path: ethernet3.performance.ifInPriorityQueues.h24Performance.queuedPkts

       64 bit unsigned wrappable counter."
   ::= {pr1645v2PortSwEIfInPriorityQueuesH24PerformanceEntry 50331648}

pr1645v2PortSwEIfInPriorityQueuesH24PerformanceDropPkts OBJECT-TYPE
   SYNTAX      Counter64
   MAX-ACCESS  read-only
   STATUS      current
   DESCRIPTION
      "Path: ethernet3.performance.ifInPriorityQueues.h24Performance.droppedPkts

       64 bit unsigned wrappable counter."
   ::= {pr1645v2PortSwEIfInPriorityQueuesH24PerformanceEntry 67108864}

pr1645v2PortSwEIfInPriorityQueuesH24PerformanceRDropPkts OBJECT-TYPE
   SYNTAX      Counter64
   MAX-ACCESS  read-only
   STATUS      current
   DESCRIPTION
      "Path: ethernet3.performance.ifInPriorityQueues.h24Performance.redDroppedPkts

       64 bit unsigned wrappable counter."
   ::= {pr1645v2PortSwEIfInPriorityQueuesH24PerformanceEntry 201326592}

pr1645v2PortSwEIfInPriorityQueuesH24PerformanceCirTxPkts OBJECT-TYPE
   SYNTAX      Counter64
   MAX-ACCESS  read-only
   STATUS      current
   DESCRIPTION
      "Path: ethernet3.performance.ifInPriorityQueues.h24Performance.cirTxPkts

       64 bit unsigned wrappable counter."
   ::= {pr1645v2PortSwEIfInPriorityQueuesH24PerformanceEntry 83886080}

pr1645v2PortSwEIfInPriorityQueuesH24PerformanceEirTxPkts OBJECT-TYPE
   SYNTAX      Counter64
   MAX-ACCESS  read-only
   STATUS      current
   DESCRIPTION
      "Path: ethernet3.performance.ifInPriorityQueues.h24Performance.eirTxPkts

       64 bit unsigned wrappable counter."
   ::= {pr1645v2PortSwEIfInPriorityQueuesH24PerformanceEntry 100663296}

pr1645v2PortSwEIfInPriorityQueuesH24PerformanceViolTxPkts OBJECT-TYPE
   SYNTAX      Counter64
   MAX-ACCESS  read-only
   STATUS      current
   DESCRIPTION
      "Path: ethernet3.performance.ifInPriorityQueues.h24Performance.violateTxPkts

       64 bit unsigned wrappable counter."
   ::= {pr1645v2PortSwEIfInPriorityQueuesH24PerformanceEntry 301989888}

pr1645v2PortSwEIfInPriorityQueuesH24PerformanceTotOcts OBJECT-TYPE
   SYNTAX      Counter64
   MAX-ACCESS  read-only
   STATUS      current
   DESCRIPTION
      "Path: ethernet3.performance.ifInPriorityQueues.h24Performance.totalOctets

       64 bit unsigned wrappable counter."
   ::= {pr1645v2PortSwEIfInPriorityQueuesH24PerformanceEntry 251658240}

pr1645v2PortSwEIfInPriorityQueuesH24PerformanceDirTxOcts OBJECT-TYPE
   SYNTAX      Counter64
   MAX-ACCESS  read-only
   STATUS      current
   DESCRIPTION
      "Path: ethernet3.performance.ifInPriorityQueues.h24Performance.directTxOctets

       64 bit unsigned wrappable counter."
   ::= {pr1645v2PortSwEIfInPriorityQueuesH24PerformanceEntry 117440512}

pr1645v2PortSwEIfInPriorityQueuesH24PerformanceQdOcts OBJECT-TYPE
   SYNTAX      Counter64
   MAX-ACCESS  read-only
   STATUS      current
   DESCRIPTION
      "Path: ethernet3.performance.ifInPriorityQueues.h24Performance.queuedOctets

       64 bit unsigned wrappable counter."
   ::= {pr1645v2PortSwEIfInPriorityQueuesH24PerformanceEntry 134217728}

pr1645v2PortSwEIfInPriorityQueuesH24PerformanceDropOcts OBJECT-TYPE
   SYNTAX      Counter64
   MAX-ACCESS  read-only
   STATUS      current
   DESCRIPTION
      "Path: ethernet3.performance.ifInPriorityQueues.h24Performance.droppedOctets

       64 bit unsigned wrappable counter."
   ::= {pr1645v2PortSwEIfInPriorityQueuesH24PerformanceEntry 150994944}

pr1645v2PortSwEIfInPriorityQueuesH24PerformanceRDropOcts OBJECT-TYPE
   SYNTAX      Counter64
   MAX-ACCESS  read-only
   STATUS      current
   DESCRIPTION
      "Path: ethernet3.performance.ifInPriorityQueues.h24Performance.redDroppedOctets

       64 bit unsigned wrappable counter."
   ::= {pr1645v2PortSwEIfInPriorityQueuesH24PerformanceEntry 218103808}

pr1645v2PortSwEIfInPriorityQueuesH24PerformanceCirTxOcts OBJECT-TYPE
   SYNTAX      Counter64
   MAX-ACCESS  read-only
   STATUS      current
   DESCRIPTION
      "Path: ethernet3.performance.ifInPriorityQueues.h24Performance.cirTxOctets

       64 bit unsigned wrappable counter."
   ::= {pr1645v2PortSwEIfInPriorityQueuesH24PerformanceEntry 167772160}

pr1645v2PortSwEIfInPriorityQueuesH24PerformanceEirTxOcts OBJECT-TYPE
   SYNTAX      Counter64
   MAX-ACCESS  read-only
   STATUS      current
   DESCRIPTION
      "Path: ethernet3.performance.ifInPriorityQueues.h24Performance.eirTxOctets

       64 bit unsigned wrappable counter."
   ::= {pr1645v2PortSwEIfInPriorityQueuesH24PerformanceEntry 184549376}

pr1645v2PortSwEIfInPriorityQueuesH24PerformanceViolTxOcts OBJECT-TYPE
   SYNTAX      Counter64
   MAX-ACCESS  read-only
   STATUS      current
   DESCRIPTION
      "Path: ethernet3.performance.ifInPriorityQueues.h24Performance.violateTxOctets

       64 bit unsigned wrappable counter."
   ::= {pr1645v2PortSwEIfInPriorityQueuesH24PerformanceEntry 318767104}

pr1645v2PortSwEIfInPriorityQueuesH24PerformanceBandwidth OBJECT-TYPE
   SYNTAX      Integer32
   MAX-ACCESS  read-only
   STATUS      current
   DESCRIPTION
      "Path: ethernet3.performance.ifInPriorityQueues.h24Performance.bandwidth

       unit name = bps
       formula = 8 * ; 8 /"
   ::= {pr1645v2PortSwEIfInPriorityQueuesH24PerformanceEntry 268435456}

pr1645v2PortSwEIfInPriorityQueuesD7Performance OBJECT-TYPE
   SYNTAX      SEQUENCE OF Pr1645v2PortSwEIfInPriorityQueuesD7PerformanceEntry
   MAX-ACCESS  not-accessible
   STATUS      current
   DESCRIPTION
      ""
   ::= {pr1645v2PortSwEIfInPriorityQueues 117440512}

pr1645v2PortSwEIfInPriorityQueuesD7PerformanceEntry OBJECT-TYPE
   SYNTAX      Pr1645v2PortSwEIfInPriorityQueuesD7PerformanceEntry
   MAX-ACCESS  not-accessible
   STATUS      current
   DESCRIPTION
      ""
   INDEX      { pr1645v2PortSwEIfInPriorityQueuesTableIx,
                pr1645v2PortSwEIfInPriorityQueuesD7PerformanceTableIx }
   ::= {pr1645v2PortSwEIfInPriorityQueuesD7Performance 1}

Pr1645v2PortSwEIfInPriorityQueuesD7PerformanceEntry ::=
   SEQUENCE
      {
      pr1645v2PortSwEIfInPriorityQueuesD7PerformanceTableIx
         TableIndex,
      pr1645v2PortSwEIfInPriorityQueuesD7PerformanceSysUpTime
         TimeTicks,
      pr1645v2PortSwEIfInPriorityQueuesD7PerformanceTotPkts
         Counter64,
      pr1645v2PortSwEIfInPriorityQueuesD7PerformanceDirTxPkts
         Counter64,
      pr1645v2PortSwEIfInPriorityQueuesD7PerformanceQdPkts
         Counter64,
      pr1645v2PortSwEIfInPriorityQueuesD7PerformanceDropPkts
         Counter64,
      pr1645v2PortSwEIfInPriorityQueuesD7PerformanceRDropPkts
         Counter64,
      pr1645v2PortSwEIfInPriorityQueuesD7PerformanceCirTxPkts
         Counter64,
      pr1645v2PortSwEIfInPriorityQueuesD7PerformanceEirTxPkts
         Counter64,
      pr1645v2PortSwEIfInPriorityQueuesD7PerformanceViolTxPkts
         Counter64,
      pr1645v2PortSwEIfInPriorityQueuesD7PerformanceTotOcts
         Counter64,
      pr1645v2PortSwEIfInPriorityQueuesD7PerformanceDirTxOcts
         Counter64,
      pr1645v2PortSwEIfInPriorityQueuesD7PerformanceQdOcts
         Counter64,
      pr1645v2PortSwEIfInPriorityQueuesD7PerformanceDropOcts
         Counter64,
      pr1645v2PortSwEIfInPriorityQueuesD7PerformanceRDropOcts
         Counter64,
      pr1645v2PortSwEIfInPriorityQueuesD7PerformanceCirTxOcts
         Counter64,
      pr1645v2PortSwEIfInPriorityQueuesD7PerformanceEirTxOcts
         Counter64,
      pr1645v2PortSwEIfInPriorityQueuesD7PerformanceViolTxOcts
         Counter64,
      pr1645v2PortSwEIfInPriorityQueuesD7PerformanceBandwidth
         Integer32
      }

pr1645v2PortSwEIfInPriorityQueuesD7PerformanceTableIx OBJECT-TYPE
   SYNTAX      TableIndex
   MAX-ACCESS  not-accessible
   STATUS      current
   DESCRIPTION
      ""
   ::= {pr1645v2PortSwEIfInPriorityQueuesD7PerformanceEntry 11}

pr1645v2PortSwEIfInPriorityQueuesD7PerformanceSysUpTime OBJECT-TYPE
   SYNTAX      TimeTicks
   MAX-ACCESS  read-only
   STATUS      current
   DESCRIPTION
      "Path: ethernet3.performance.ifInPriorityQueues.d7Performance.sysUpTime

       Time in centi-second."
   ::= {pr1645v2PortSwEIfInPriorityQueuesD7PerformanceEntry 16777216}

pr1645v2PortSwEIfInPriorityQueuesD7PerformanceTotPkts OBJECT-TYPE
   SYNTAX      Counter64
   MAX-ACCESS  read-only
   STATUS      current
   DESCRIPTION
      "Path: ethernet3.performance.ifInPriorityQueues.d7Performance.totalPkts

       64 bit unsigned wrappable counter."
   ::= {pr1645v2PortSwEIfInPriorityQueuesD7PerformanceEntry 234881024}

pr1645v2PortSwEIfInPriorityQueuesD7PerformanceDirTxPkts OBJECT-TYPE
   SYNTAX      Counter64
   MAX-ACCESS  read-only
   STATUS      current
   DESCRIPTION
      "Path: ethernet3.performance.ifInPriorityQueues.d7Performance.directTxPkts

       64 bit unsigned wrappable counter."
   ::= {pr1645v2PortSwEIfInPriorityQueuesD7PerformanceEntry 33554432}

pr1645v2PortSwEIfInPriorityQueuesD7PerformanceQdPkts OBJECT-TYPE
   SYNTAX      Counter64
   MAX-ACCESS  read-only
   STATUS      current
   DESCRIPTION
      "Path: ethernet3.performance.ifInPriorityQueues.d7Performance.queuedPkts

       64 bit unsigned wrappable counter."
   ::= {pr1645v2PortSwEIfInPriorityQueuesD7PerformanceEntry 50331648}

pr1645v2PortSwEIfInPriorityQueuesD7PerformanceDropPkts OBJECT-TYPE
   SYNTAX      Counter64
   MAX-ACCESS  read-only
   STATUS      current
   DESCRIPTION
      "Path: ethernet3.performance.ifInPriorityQueues.d7Performance.droppedPkts

       64 bit unsigned wrappable counter."
   ::= {pr1645v2PortSwEIfInPriorityQueuesD7PerformanceEntry 67108864}

pr1645v2PortSwEIfInPriorityQueuesD7PerformanceRDropPkts OBJECT-TYPE
   SYNTAX      Counter64
   MAX-ACCESS  read-only
   STATUS      current
   DESCRIPTION
      "Path: ethernet3.performance.ifInPriorityQueues.d7Performance.redDroppedPkts

       64 bit unsigned wrappable counter."
   ::= {pr1645v2PortSwEIfInPriorityQueuesD7PerformanceEntry 201326592}

pr1645v2PortSwEIfInPriorityQueuesD7PerformanceCirTxPkts OBJECT-TYPE
   SYNTAX      Counter64
   MAX-ACCESS  read-only
   STATUS      current
   DESCRIPTION
      "Path: ethernet3.performance.ifInPriorityQueues.d7Performance.cirTxPkts

       64 bit unsigned wrappable counter."
   ::= {pr1645v2PortSwEIfInPriorityQueuesD7PerformanceEntry 83886080}

pr1645v2PortSwEIfInPriorityQueuesD7PerformanceEirTxPkts OBJECT-TYPE
   SYNTAX      Counter64
   MAX-ACCESS  read-only
   STATUS      current
   DESCRIPTION
      "Path: ethernet3.performance.ifInPriorityQueues.d7Performance.eirTxPkts

       64 bit unsigned wrappable counter."
   ::= {pr1645v2PortSwEIfInPriorityQueuesD7PerformanceEntry 100663296}

pr1645v2PortSwEIfInPriorityQueuesD7PerformanceViolTxPkts OBJECT-TYPE
   SYNTAX      Counter64
   MAX-ACCESS  read-only
   STATUS      current
   DESCRIPTION
      "Path: ethernet3.performance.ifInPriorityQueues.d7Performance.violateTxPkts

       64 bit unsigned wrappable counter."
   ::= {pr1645v2PortSwEIfInPriorityQueuesD7PerformanceEntry 301989888}

pr1645v2PortSwEIfInPriorityQueuesD7PerformanceTotOcts OBJECT-TYPE
   SYNTAX      Counter64
   MAX-ACCESS  read-only
   STATUS      current
   DESCRIPTION
      "Path: ethernet3.performance.ifInPriorityQueues.d7Performance.totalOctets

       64 bit unsigned wrappable counter."
   ::= {pr1645v2PortSwEIfInPriorityQueuesD7PerformanceEntry 251658240}

pr1645v2PortSwEIfInPriorityQueuesD7PerformanceDirTxOcts OBJECT-TYPE
   SYNTAX      Counter64
   MAX-ACCESS  read-only
   STATUS      current
   DESCRIPTION
      "Path: ethernet3.performance.ifInPriorityQueues.d7Performance.directTxOctets

       64 bit unsigned wrappable counter."
   ::= {pr1645v2PortSwEIfInPriorityQueuesD7PerformanceEntry 117440512}

pr1645v2PortSwEIfInPriorityQueuesD7PerformanceQdOcts OBJECT-TYPE
   SYNTAX      Counter64
   MAX-ACCESS  read-only
   STATUS      current
   DESCRIPTION
      "Path: ethernet3.performance.ifInPriorityQueues.d7Performance.queuedOctets

       64 bit unsigned wrappable counter."
   ::= {pr1645v2PortSwEIfInPriorityQueuesD7PerformanceEntry 134217728}

pr1645v2PortSwEIfInPriorityQueuesD7PerformanceDropOcts OBJECT-TYPE
   SYNTAX      Counter64
   MAX-ACCESS  read-only
   STATUS      current
   DESCRIPTION
      "Path: ethernet3.performance.ifInPriorityQueues.d7Performance.droppedOctets

       64 bit unsigned wrappable counter."
   ::= {pr1645v2PortSwEIfInPriorityQueuesD7PerformanceEntry 150994944}

pr1645v2PortSwEIfInPriorityQueuesD7PerformanceRDropOcts OBJECT-TYPE
   SYNTAX      Counter64
   MAX-ACCESS  read-only
   STATUS      current
   DESCRIPTION
      "Path: ethernet3.performance.ifInPriorityQueues.d7Performance.redDroppedOctets

       64 bit unsigned wrappable counter."
   ::= {pr1645v2PortSwEIfInPriorityQueuesD7PerformanceEntry 218103808}

pr1645v2PortSwEIfInPriorityQueuesD7PerformanceCirTxOcts OBJECT-TYPE
   SYNTAX      Counter64
   MAX-ACCESS  read-only
   STATUS      current
   DESCRIPTION
      "Path: ethernet3.performance.ifInPriorityQueues.d7Performance.cirTxOctets

       64 bit unsigned wrappable counter."
   ::= {pr1645v2PortSwEIfInPriorityQueuesD7PerformanceEntry 167772160}

pr1645v2PortSwEIfInPriorityQueuesD7PerformanceEirTxOcts OBJECT-TYPE
   SYNTAX      Counter64
   MAX-ACCESS  read-only
   STATUS      current
   DESCRIPTION
      "Path: ethernet3.performance.ifInPriorityQueues.d7Performance.eirTxOctets

       64 bit unsigned wrappable counter."
   ::= {pr1645v2PortSwEIfInPriorityQueuesD7PerformanceEntry 184549376}

pr1645v2PortSwEIfInPriorityQueuesD7PerformanceViolTxOcts OBJECT-TYPE
   SYNTAX      Counter64
   MAX-ACCESS  read-only
   STATUS      current
   DESCRIPTION
      "Path: ethernet3.performance.ifInPriorityQueues.d7Performance.violateTxOctets

       64 bit unsigned wrappable counter."
   ::= {pr1645v2PortSwEIfInPriorityQueuesD7PerformanceEntry 318767104}

pr1645v2PortSwEIfInPriorityQueuesD7PerformanceBandwidth OBJECT-TYPE
   SYNTAX      Integer32
   MAX-ACCESS  read-only
   STATUS      current
   DESCRIPTION
      "Path: ethernet3.performance.ifInPriorityQueues.d7Performance.bandwidth

       unit name = bps
       formula = 8 * ; 8 /"
   ::= {pr1645v2PortSwEIfInPriorityQueuesD7PerformanceEntry 268435456}


pr1645v2PortSwEIfInHwPriorityQueues OBJECT IDENTIFIER ::= {pr1645v2PortSwE 132}

pr1645v2PortSwEIfInHwPriorityQueuesSSCTable OBJECT-TYPE
   SYNTAX      SEQUENCE OF Pr1645v2PortSwEIfInHwPriorityQueuesEntry
   MAX-ACCESS  not-accessible
   STATUS      current
   DESCRIPTION
      "hwPriorityQueues"
   ::= {pr1645v2PortSwEIfInHwPriorityQueues 1}

pr1645v2PortSwEIfInHwPriorityQueuesEntry OBJECT-TYPE
   SYNTAX      Pr1645v2PortSwEIfInHwPriorityQueuesEntry
   MAX-ACCESS  not-accessible
   STATUS      current
   DESCRIPTION
      ""
   INDEX      { pr1645v2PortSwEIfInHwPriorityQueuesTableIx }
   ::= {pr1645v2PortSwEIfInHwPriorityQueuesSSCTable 1}

Pr1645v2PortSwEIfInHwPriorityQueuesEntry ::=
   SEQUENCE
      {
      pr1645v2PortSwEIfInHwPriorityQueuesTableIx
         TableIndex,
      pr1645v2PortSwEIfInHwPriorityQueuesName
         INTEGER,
      pr1645v2PortSwEIfInHwPriorityQueuesLength
         Integer32,
      pr1645v2PortSwEIfInHwPriorityQueuesPacketsTotal
         Counter64,
      pr1645v2PortSwEIfInHwPriorityQueuesOctetsTotal
         Counter64,
      pr1645v2PortSwEIfInHwPriorityQueuesOctetsBandwidth15sec
         Integer32,
      pr1645v2PortSwEIfInHwPriorityQueuesOctetsBandwidth30sec
         Integer32,
      pr1645v2PortSwEIfInHwPriorityQueuesOctetsBandwidth1min
         Integer32,
      pr1645v2PortSwEIfInHwPriorityQueuesOctetsBandwidth2min
         Integer32,
      pr1645v2PortSwEIfInHwPriorityQueuesOctetsBandwidth5min
         Integer32
      }

pr1645v2PortSwEIfInHwPriorityQueuesTableIx OBJECT-TYPE
   SYNTAX      TableIndex
   MAX-ACCESS  not-accessible
   STATUS      current
   DESCRIPTION
      ""
   ::= {pr1645v2PortSwEIfInHwPriorityQueuesEntry 11}

pr1645v2PortSwEIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PortSwEIfInHwPriorityQueuesEntry 16777216}

pr1645v2PortSwEIfInHwPriorityQueuesLength OBJECT-TYPE
   SYNTAX      Integer32
   MAX-ACCESS  read-only
   STATUS      current
   DESCRIPTION
      "Path: ethernet3.performance.ifInHwPriorityQueues.length"
   ::= {pr1645v2PortSwEIfInHwPriorityQueuesEntry 33554432}

pr1645v2PortSwEIfInHwPriorityQueuesPacketsTotal OBJECT-TYPE
   SYNTAX      Counter64
   MAX-ACCESS  read-only
   STATUS      current
   DESCRIPTION
      "Path: ethernet3.performance.ifInHwPriorityQueues.packets.total

       64 bit unsigned wrappable counter."
   ::= {pr1645v2PortSwEIfInHwPriorityQueuesEntry 50790400}

pr1645v2PortSwEIfInHwPriorityQueuesOctetsTotal OBJECT-TYPE
   SYNTAX      Counter64
   MAX-ACCESS  read-only
   STATUS      current
   DESCRIPTION
      "Path: ethernet3.performance.ifInHwPriorityQueues.octets.total

       64 bit unsigned wrappable counter."
   ::= {pr1645v2PortSwEIfInHwPriorityQueuesEntry 67567616}

pr1645v2PortSwEIfInHwPriorityQueuesOctetsBandwidth15sec OBJECT-TYPE
   SYNTAX      Integer32
   MAX-ACCESS  read-only
   STATUS      current
   DESCRIPTION
      "Path: ethernet3.performance.ifInHwPriorityQueues.octets.bandwidth.15sec

       unit name = bps
       formula = 8 * ; 8 /"
   ::= {pr1645v2PortSwEIfInHwPriorityQueuesEntry 70386944}

pr1645v2PortSwEIfInHwPriorityQueuesOctetsBandwidth30sec OBJECT-TYPE
   SYNTAX      Integer32
   MAX-ACCESS  read-only
   STATUS      current
   DESCRIPTION
      "Path: ethernet3.performance.ifInHwPriorityQueues.octets.bandwidth.30sec

       unit name = bps
       formula = 8 * ; 8 /"
   ::= {pr1645v2PortSwEIfInHwPriorityQueuesEntry 70388224}

pr1645v2PortSwEIfInHwPriorityQueuesOctetsBandwidth1min OBJECT-TYPE
   SYNTAX      Integer32
   MAX-ACCESS  read-only
   STATUS      current
   DESCRIPTION
      "Path: ethernet3.performance.ifInHwPriorityQueues.octets.bandwidth.1min

       unit name = bps
       formula = 8 * ; 8 /"
   ::= {pr1645v2PortSwEIfInHwPriorityQueuesEntry 70390784}

pr1645v2PortSwEIfInHwPriorityQueuesOctetsBandwidth2min OBJECT-TYPE
   SYNTAX      Integer32
   MAX-ACCESS  read-only
   STATUS      current
   DESCRIPTION
      "Path: ethernet3.performance.ifInHwPriorityQueues.octets.bandwidth.2min

       unit name = bps
       formula = 8 * ; 8 /"
   ::= {pr1645v2PortSwEIfInHwPriorityQueuesEntry 70395904}

pr1645v2PortSwEIfInHwPriorityQueuesOctetsBandwidth5min OBJECT-TYPE
   SYNTAX      Integer32
   MAX-ACCESS  read-only
   STATUS      current
   DESCRIPTION
      "Path: ethernet3.performance.ifInHwPriorityQueues.octets.bandwidth.5min

       unit name = bps
       formula = 8 * ; 8 /"
   ::= {pr1645v2PortSwEIfInHwPriorityQueuesEntry 70411264}

pr1645v2PortSwEIfInHwPriorityQueuesH2Performance OBJECT-TYPE
   SYNTAX      SEQUENCE OF Pr1645v2PortSwEIfInHwPriorityQueuesH2PerformanceEntry
   MAX-ACCESS  not-accessible
   STATUS      current
   DESCRIPTION
      ""
   ::= {pr1645v2PortSwEIfInHwPriorityQueues 83886080}

pr1645v2PortSwEIfInHwPriorityQueuesH2PerformanceEntry OBJECT-TYPE
   SYNTAX      Pr1645v2PortSwEIfInHwPriorityQueuesH2PerformanceEntry
   MAX-ACCESS  not-accessible
   STATUS      current
   DESCRIPTION
      ""
   INDEX      { pr1645v2PortSwEIfInHwPriorityQueuesTableIx,
                pr1645v2PortSwEIfInHwPriorityQueuesH2PerformanceTableIx }
   ::= {pr1645v2PortSwEIfInHwPriorityQueuesH2Performance 1}

Pr1645v2PortSwEIfInHwPriorityQueuesH2PerformanceEntry ::=
   SEQUENCE
      {
      pr1645v2PortSwEIfInHwPriorityQueuesH2PerformanceTableIx
         TableIndex,
      pr1645v2PortSwEIfInHwPriorityQueuesH2PerformanceSysUpTime
         TimeTicks,
      pr1645v2PortSwEIfInHwPriorityQueuesH2PerformanceTotPkts
         Counter64,
      pr1645v2PortSwEIfInHwPriorityQueuesH2PerformanceTotOcts
         Counter64,
      pr1645v2PortSwEIfInHwPriorityQueuesH2PerformanceBandwidth
         Integer32
      }

pr1645v2PortSwEIfInHwPriorityQueuesH2PerformanceTableIx OBJECT-TYPE
   SYNTAX      TableIndex
   MAX-ACCESS  not-accessible
   STATUS      current
   DESCRIPTION
      ""
   ::= {pr1645v2PortSwEIfInHwPriorityQueuesH2PerformanceEntry 11}

pr1645v2PortSwEIfInHwPriorityQueuesH2PerformanceSysUpTime OBJECT-TYPE
   SYNTAX      TimeTicks
   MAX-ACCESS  read-only
   STATUS      current
   DESCRIPTION
      "Path: ethernet3.performance.ifInHwPriorityQueues.h2Performance.sysUpTime

       Time in centi-second."
   ::= {pr1645v2PortSwEIfInHwPriorityQueuesH2PerformanceEntry 16777216}

pr1645v2PortSwEIfInHwPriorityQueuesH2PerformanceTotPkts OBJECT-TYPE
   SYNTAX      Counter64
   MAX-ACCESS  read-only
   STATUS      current
   DESCRIPTION
      "Path: ethernet3.performance.ifInHwPriorityQueues.h2Performance.totalPkts

       64 bit unsigned wrappable counter."
   ::= {pr1645v2PortSwEIfInHwPriorityQueuesH2PerformanceEntry 234881024}

pr1645v2PortSwEIfInHwPriorityQueuesH2PerformanceTotOcts OBJECT-TYPE
   SYNTAX      Counter64
   MAX-ACCESS  read-only
   STATUS      current
   DESCRIPTION
      "Path: ethernet3.performance.ifInHwPriorityQueues.h2Performance.totalOctets

       64 bit unsigned wrappable counter."
   ::= {pr1645v2PortSwEIfInHwPriorityQueuesH2PerformanceEntry 251658240}

pr1645v2PortSwEIfInHwPriorityQueuesH2PerformanceBandwidth OBJECT-TYPE
   SYNTAX      Integer32
   MAX-ACCESS  read-only
   STATUS      current
   DESCRIPTION
      "Path: ethernet3.performance.ifInHwPriorityQueues.h2Performance.bandwidth

       unit name = bps
       formula = 8 * ; 8 /"
   ::= {pr1645v2PortSwEIfInHwPriorityQueuesH2PerformanceEntry 268435456}

pr1645v2PortSwEIfInHwPriorityQueuesH24Performance OBJECT-TYPE
   SYNTAX      SEQUENCE OF Pr1645v2PortSwEIfInHwPriorityQueuesH24PerformanceEntry
   MAX-ACCESS  not-accessible
   STATUS      current
   DESCRIPTION
      ""
   ::= {pr1645v2PortSwEIfInHwPriorityQueues 100663296}

pr1645v2PortSwEIfInHwPriorityQueuesH24PerformanceEntry OBJECT-TYPE
   SYNTAX      Pr1645v2PortSwEIfInHwPriorityQueuesH24PerformanceEntry
   MAX-ACCESS  not-accessible
   STATUS      current
   DESCRIPTION
      ""
   INDEX      { pr1645v2PortSwEIfInHwPriorityQueuesTableIx,
                pr1645v2PortSwEIfInHwPriorityQueuesH24PerformanceTableIx }
   ::= {pr1645v2PortSwEIfInHwPriorityQueuesH24Performance 1}

Pr1645v2PortSwEIfInHwPriorityQueuesH24PerformanceEntry ::=
   SEQUENCE
      {
      pr1645v2PortSwEIfInHwPriorityQueuesH24PerformanceTableIx
         TableIndex,
      pr1645v2PortSwEIfInHwPriorityQueuesH24PerformanceSysUpTime
         TimeTicks,
      pr1645v2PortSwEIfInHwPriorityQueuesH24PerformanceTotPkts
         Counter64,
      pr1645v2PortSwEIfInHwPriorityQueuesH24PerformanceTotOcts
         Counter64,
      pr1645v2PortSwEIfInHwPriorityQueuesH24PerformanceBandwidth
         Integer32
      }

pr1645v2PortSwEIfInHwPriorityQueuesH24PerformanceTableIx OBJECT-TYPE
   SYNTAX      TableIndex
   MAX-ACCESS  not-accessible
   STATUS      current
   DESCRIPTION
      ""
   ::= {pr1645v2PortSwEIfInHwPriorityQueuesH24PerformanceEntry 11}

pr1645v2PortSwEIfInHwPriorityQueuesH24PerformanceSysUpTime OBJECT-TYPE
   SYNTAX      TimeTicks
   MAX-ACCESS  read-only
   STATUS      current
   DESCRIPTION
      "Path: ethernet3.performance.ifInHwPriorityQueues.h24Performance.sysUpTime

       Time in centi-second."
   ::= {pr1645v2PortSwEIfInHwPriorityQueuesH24PerformanceEntry 16777216}

pr1645v2PortSwEIfInHwPriorityQueuesH24PerformanceTotPkts OBJECT-TYPE
   SYNTAX      Counter64
   MAX-ACCESS  read-only
   STATUS      current
   DESCRIPTION
      "Path: ethernet3.performance.ifInHwPriorityQueues.h24Performance.totalPkts

       64 bit unsigned wrappable counter."
   ::= {pr1645v2PortSwEIfInHwPriorityQueuesH24PerformanceEntry 234881024}

pr1645v2PortSwEIfInHwPriorityQueuesH24PerformanceTotOcts OBJECT-TYPE
   SYNTAX      Counter64
   MAX-ACCESS  read-only
   STATUS      current
   DESCRIPTION
      "Path: ethernet3.performance.ifInHwPriorityQueues.h24Performance.totalOctets

       64 bit unsigned wrappable counter."
   ::= {pr1645v2PortSwEIfInHwPriorityQueuesH24PerformanceEntry 251658240}

pr1645v2PortSwEIfInHwPriorityQueuesH24PerformanceBandwidth OBJECT-TYPE
   SYNTAX      Integer32
   MAX-ACCESS  read-only
   STATUS      current
   DESCRIPTION
      "Path: ethernet3.performance.ifInHwPriorityQueues.h24Performance.bandwidth

       unit name = bps
       formula = 8 * ; 8 /"
   ::= {pr1645v2PortSwEIfInHwPriorityQueuesH24PerformanceEntry 268435456}

pr1645v2PortSwEIfInHwPriorityQueuesD7Performance OBJECT-TYPE
   SYNTAX      SEQUENCE OF Pr1645v2PortSwEIfInHwPriorityQueuesD7PerformanceEntry
   MAX-ACCESS  not-accessible
   STATUS      current
   DESCRIPTION
      ""
   ::= {pr1645v2PortSwEIfInHwPriorityQueues 117440512}

pr1645v2PortSwEIfInHwPriorityQueuesD7PerformanceEntry OBJECT-TYPE
   SYNTAX      Pr1645v2PortSwEIfInHwPriorityQueuesD7PerformanceEntry
   MAX-ACCESS  not-accessible
   STATUS      current
   DESCRIPTION
      ""
   INDEX      { pr1645v2PortSwEIfInHwPriorityQueuesTableIx,
                pr1645v2PortSwEIfInHwPriorityQueuesD7PerformanceTableIx }
   ::= {pr1645v2PortSwEIfInHwPriorityQueuesD7Performance 1}

Pr1645v2PortSwEIfInHwPriorityQueuesD7PerformanceEntry ::=
   SEQUENCE
      {
      pr1645v2PortSwEIfInHwPriorityQueuesD7PerformanceTableIx
         TableIndex,
      pr1645v2PortSwEIfInHwPriorityQueuesD7PerformanceSysUpTime
         TimeTicks,
      pr1645v2PortSwEIfInHwPriorityQueuesD7PerformanceTotPkts
         Counter64,
      pr1645v2PortSwEIfInHwPriorityQueuesD7PerformanceTotOcts
         Counter64,
      pr1645v2PortSwEIfInHwPriorityQueuesD7PerformanceBandwidth
         Integer32
      }

pr1645v2PortSwEIfInHwPriorityQueuesD7PerformanceTableIx OBJECT-TYPE
   SYNTAX      TableIndex
   MAX-ACCESS  not-accessible
   STATUS      current
   DESCRIPTION
      ""
   ::= {pr1645v2PortSwEIfInHwPriorityQueuesD7PerformanceEntry 11}

pr1645v2PortSwEIfInHwPriorityQueuesD7PerformanceSysUpTime OBJECT-TYPE
   SYNTAX      TimeTicks
   MAX-ACCESS  read-only
   STATUS      current
   DESCRIPTION
      "Path: ethernet3.performance.ifInHwPriorityQueues.d7Performance.sysUpTime

       Time in centi-second."
   ::= {pr1645v2PortSwEIfInHwPriorityQueuesD7PerformanceEntry 16777216}

pr1645v2PortSwEIfInHwPriorityQueuesD7PerformanceTotPkts OBJECT-TYPE
   SYNTAX      Counter64
   MAX-ACCESS  read-only
   STATUS      current
   DESCRIPTION
      "Path: ethernet3.performance.ifInHwPriorityQueues.d7Performance.totalPkts

       64 bit unsigned wrappable counter."
   ::= {pr1645v2PortSwEIfInHwPriorityQueuesD7PerformanceEntry 234881024}

pr1645v2PortSwEIfInHwPriorityQueuesD7PerformanceTotOcts OBJECT-TYPE
   SYNTAX      Counter64
   MAX-ACCESS  read-only
   STATUS      current
   DESCRIPTION
      "Path: ethernet3.performance.ifInHwPriorityQueues.d7Performance.totalOctets

       64 bit unsigned wrappable counter."
   ::= {pr1645v2PortSwEIfInHwPriorityQueuesD7PerformanceEntry 251658240}

pr1645v2PortSwEIfInHwPriorityQueuesD7PerformanceBandwidth OBJECT-TYPE
   SYNTAX      Integer32
   MAX-ACCESS  read-only
   STATUS      current
   DESCRIPTION
      "Path: ethernet3.performance.ifInHwPriorityQueues.d7Performance.bandwidth

       unit name = bps
       formula = 8 * ; 8 /"
   ::= {pr1645v2PortSwEIfInHwPriorityQueuesD7PerformanceEntry 268435456}


pr1645v2PortSwEMibCntrs OBJECT IDENTIFIER ::= {pr1645v2PortSwE 198}

pr1645v2PortSwEMibCntrsSSCTable OBJECT-TYPE
   SYNTAX      SEQUENCE OF Pr1645v2PortSwEMibCntrsEntry
   MAX-ACCESS  not-accessible
   STATUS      current
   DESCRIPTION
      "Ethernet Switch MIB Counters"
   ::= {pr1645v2PortSwEMibCntrs 1}

pr1645v2PortSwEMibCntrsEntry OBJECT-TYPE
   SYNTAX      Pr1645v2PortSwEMibCntrsEntry
   MAX-ACCESS  not-accessible
   STATUS      current
   DESCRIPTION
      ""
   INDEX      { pr1645v2PortSwEMibCntrsTableIx }
   ::= {pr1645v2PortSwEMibCntrsSSCTable 1}

Pr1645v2PortSwEMibCntrsEntry ::=
   SEQUENCE
      {
      pr1645v2PortSwEMibCntrsTableIx
         TableIndex,
      pr1645v2PortSwEMibCntrsPortName
         INTEGER,
      pr1645v2PortSwEMibCntrsInOctets
         Counter64,
      pr1645v2PortSwEMibCntrsInUcast
         Counter64,
      pr1645v2PortSwEMibCntrsInNUcastPkts
         Counter64,
      pr1645v2PortSwEMibCntrsInDiscards
         Counter64,
      pr1645v2PortSwEMibCntrsInPause
         Counter64,
      pr1645v2PortSwEMibCntrsInErrors
         Counter64,
      pr1645v2PortSwEMibCntrsInBandwidth15sec
         Integer32,
      pr1645v2PortSwEMibCntrsInBandwidth30sec
         Integer32,
      pr1645v2PortSwEMibCntrsInBandwidth1min
         Integer32,
      pr1645v2PortSwEMibCntrsInBandwidth2min
         Integer32,
      pr1645v2PortSwEMibCntrsInBandwidth5min
         Integer32,
      pr1645v2PortSwEMibCntrsOutOctets
         Counter64,
      pr1645v2PortSwEMibCntrsOutUcastPkts
         Counter64,
      pr1645v2PortSwEMibCntrsOutNUcastPkts
         Counter64,
      pr1645v2PortSwEMibCntrsOutDiscards
         Counter64,
      pr1645v2PortSwEMibCntrsOutPause
         Counter64,
      pr1645v2PortSwEMibCntrsOutErrors
         Counter64,
      pr1645v2PortSwEMibCntrsOutBandwidth15sec
         Integer32,
      pr1645v2PortSwEMibCntrsOutBandwidth30sec
         Integer32,
      pr1645v2PortSwEMibCntrsOutBandwidth1min
         Integer32,
      pr1645v2PortSwEMibCntrsOutBandwidth2min
         Integer32,
      pr1645v2PortSwEMibCntrsOutBandwidth5min
         Integer32
      }

pr1645v2PortSwEMibCntrsTableIx OBJECT-TYPE
   SYNTAX      TableIndex
   MAX-ACCESS  not-accessible
   STATUS      current
   DESCRIPTION
      ""
   ::= {pr1645v2PortSwEMibCntrsEntry 11}

pr1645v2PortSwEMibCntrsPortName OBJECT-TYPE
   SYNTAX      INTEGER
               {
               hwPortu1 (1),
               hwPortu2 (2),
               hwPortu3 (3),
               hwPortu4 (4),
               hwPortu5 (5),
               hwPortu6 (6),
               hwPortu7 (7),
               hwPortu8 (8),
               hwPortuLocalPort (255)
               }
   MAX-ACCESS  read-only
   STATUS      current
   DESCRIPTION
      "Path: ethernet3.performance.mibCounters.portName

       Possibilities:
               hwPort_1   (1)
               hwPort_2   (2)
               hwPort_3   (3)
               hwPort_4   (4)
               hwPort_5   (5)
               hwPort_6   (6)
               hwPort_7   (7)
               hwPort_8   (8)
               hwPort_LocalPort   (255)"
   ::= {pr1645v2PortSwEMibCntrsEntry 16777216}

pr1645v2PortSwEMibCntrsInOctets OBJECT-TYPE
   SYNTAX      Counter64
   MAX-ACCESS  read-only
   STATUS      current
   DESCRIPTION
      "Path: ethernet3.performance.mibCounters.ifInOctets

       64 bit unsigned wrappable counter."
   ::= {pr1645v2PortSwEMibCntrsEntry 1828716544}

pr1645v2PortSwEMibCntrsInUcast OBJECT-TYPE
   SYNTAX      Counter64
   MAX-ACCESS  read-only
   STATUS      current
   DESCRIPTION
      "Path: ethernet3.performance.mibCounters.ifInUcastPkts

       64 bit unsigned wrappable counter."
   ::= {pr1645v2PortSwEMibCntrsEntry 1845493760}

pr1645v2PortSwEMibCntrsInNUcastPkts OBJECT-TYPE
   SYNTAX      Counter64
   MAX-ACCESS  read-only
   STATUS      current
   DESCRIPTION
      "Path: ethernet3.performance.mibCounters.ifInNUcastPkts

       64 bit unsigned wrappable counter."
   ::= {pr1645v2PortSwEMibCntrsEntry 1862270976}

pr1645v2PortSwEMibCntrsInDiscards OBJECT-TYPE
   SYNTAX      Counter64
   MAX-ACCESS  read-only
   STATUS      current
   DESCRIPTION
      "Path: ethernet3.performance.mibCounters.ifInDiscards

       64 bit unsigned wrappable counter."
   ::= {pr1645v2PortSwEMibCntrsEntry 1879048192}

pr1645v2PortSwEMibCntrsInPause OBJECT-TYPE
   SYNTAX      Counter64
   MAX-ACCESS  read-only
   STATUS      current
   DESCRIPTION
      "Path: ethernet3.performance.mibCounters.ifInPause

       64 bit unsigned wrappable counter."
   ::= {pr1645v2PortSwEMibCntrsEntry 4194304000}

pr1645v2PortSwEMibCntrsInErrors OBJECT-TYPE
   SYNTAX      Counter64
   MAX-ACCESS  read-only
   STATUS      current
   DESCRIPTION
      "Path: ethernet3.performance.mibCounters.ifInErrors

       64 bit unsigned wrappable counter."
   ::= {pr1645v2PortSwEMibCntrsEntry 1895825408}

pr1645v2PortSwEMibCntrsInBandwidth15sec OBJECT-TYPE
   SYNTAX      Integer32
   MAX-ACCESS  read-only
   STATUS      current
   DESCRIPTION
      "Path: ethernet3.performance.mibCounters.ifInBandwidth.15sec

       unit name = bps
       formula = 8 * ; 8 /"
   ::= {pr1645v2PortSwEMibCntrsEntry 3037003776}

pr1645v2PortSwEMibCntrsInBandwidth30sec OBJECT-TYPE
   SYNTAX      Integer32
   MAX-ACCESS  read-only
   STATUS      current
   DESCRIPTION
      "Path: ethernet3.performance.mibCounters.ifInBandwidth.30sec

       unit name = bps
       formula = 8 * ; 8 /"
   ::= {pr1645v2PortSwEMibCntrsEntry 3037331456}

pr1645v2PortSwEMibCntrsInBandwidth1min OBJECT-TYPE
   SYNTAX      Integer32
   MAX-ACCESS  read-only
   STATUS      current
   DESCRIPTION
      "Path: ethernet3.performance.mibCounters.ifInBandwidth.1min

       unit name = bps
       formula = 8 * ; 8 /"
   ::= {pr1645v2PortSwEMibCntrsEntry 3037986816}

pr1645v2PortSwEMibCntrsInBandwidth2min OBJECT-TYPE
   SYNTAX      Integer32
   MAX-ACCESS  read-only
   STATUS      current
   DESCRIPTION
      "Path: ethernet3.performance.mibCounters.ifInBandwidth.2min

       unit name = bps
       formula = 8 * ; 8 /"
   ::= {pr1645v2PortSwEMibCntrsEntry 3039297536}

pr1645v2PortSwEMibCntrsInBandwidth5min OBJECT-TYPE
   SYNTAX      Integer32
   MAX-ACCESS  read-only
   STATUS      current
   DESCRIPTION
      "Path: ethernet3.performance.mibCounters.ifInBandwidth.5min

       unit name = bps
       formula = 8 * ; 8 /"
   ::= {pr1645v2PortSwEMibCntrsEntry 3043229696}

pr1645v2PortSwEMibCntrsOutOctets OBJECT-TYPE
   SYNTAX      Counter64
   MAX-ACCESS  read-only
   STATUS      current
   DESCRIPTION
      "Path: ethernet3.performance.mibCounters.ifOutOctets

       64 bit unsigned wrappable counter."
   ::= {pr1645v2PortSwEMibCntrsEntry 1929379840}

pr1645v2PortSwEMibCntrsOutUcastPkts OBJECT-TYPE
   SYNTAX      Counter64
   MAX-ACCESS  read-only
   STATUS      current
   DESCRIPTION
      "Path: ethernet3.performance.mibCounters.ifOutUcastPkts

       64 bit unsigned wrappable counter."
   ::= {pr1645v2PortSwEMibCntrsEntry 1946157056}

pr1645v2PortSwEMibCntrsOutNUcastPkts OBJECT-TYPE
   SYNTAX      Counter64
   MAX-ACCESS  read-only
   STATUS      current
   DESCRIPTION
      "Path: ethernet3.performance.mibCounters.ifOutNUcastPkts

       64 bit unsigned wrappable counter."
   ::= {pr1645v2PortSwEMibCntrsEntry 1962934272}

pr1645v2PortSwEMibCntrsOutDiscards OBJECT-TYPE
   SYNTAX      Counter64
   MAX-ACCESS  read-only
   STATUS      current
   DESCRIPTION
      "Path: ethernet3.performance.mibCounters.ifOutDiscards

       64 bit unsigned wrappable counter."
   ::= {pr1645v2PortSwEMibCntrsEntry 1979711488}

pr1645v2PortSwEMibCntrsOutPause OBJECT-TYPE
   SYNTAX      Counter64
   MAX-ACCESS  read-only
   STATUS      current
   DESCRIPTION
      "Path: ethernet3.performance.mibCounters.ifOutPause

       64 bit unsigned wrappable counter."
   ::= {pr1645v2PortSwEMibCntrsEntry 4211081216}

pr1645v2PortSwEMibCntrsOutErrors OBJECT-TYPE
   SYNTAX      Counter64
   MAX-ACCESS  read-only
   STATUS      current
   DESCRIPTION
      "Path: ethernet3.performance.mibCounters.ifOutErrors

       64 bit unsigned wrappable counter."
   ::= {pr1645v2PortSwEMibCntrsEntry 1996488704}

pr1645v2PortSwEMibCntrsOutBandwidth15sec OBJECT-TYPE
   SYNTAX      Integer32
   MAX-ACCESS  read-only
   STATUS      current
   DESCRIPTION
      "Path: ethernet3.performance.mibCounters.ifOutBandwidth.15sec

       unit name = bps
       formula = 8 * ; 8 /"
   ::= {pr1645v2PortSwEMibCntrsEntry 3053780992}

pr1645v2PortSwEMibCntrsOutBandwidth30sec OBJECT-TYPE
   SYNTAX      Integer32
   MAX-ACCESS  read-only
   STATUS      current
   DESCRIPTION
      "Path: ethernet3.performance.mibCounters.ifOutBandwidth.30sec

       unit name = bps
       formula = 8 * ; 8 /"
   ::= {pr1645v2PortSwEMibCntrsEntry 3054108672}

pr1645v2PortSwEMibCntrsOutBandwidth1min OBJECT-TYPE
   SYNTAX      Integer32
   MAX-ACCESS  read-only
   STATUS      current
   DESCRIPTION
      "Path: ethernet3.performance.mibCounters.ifOutBandwidth.1min

       unit name = bps
       formula = 8 * ; 8 /"
   ::= {pr1645v2PortSwEMibCntrsEntry 3054764032}

pr1645v2PortSwEMibCntrsOutBandwidth2min OBJECT-TYPE
   SYNTAX      Integer32
   MAX-ACCESS  read-only
   STATUS      current
   DESCRIPTION
      "Path: ethernet3.performance.mibCounters.ifOutBandwidth.2min

       unit name = bps
       formula = 8 * ; 8 /"
   ::= {pr1645v2PortSwEMibCntrsEntry 3056074752}

pr1645v2PortSwEMibCntrsOutBandwidth5min OBJECT-TYPE
   SYNTAX      Integer32
   MAX-ACCESS  read-only
   STATUS      current
   DESCRIPTION
      "Path: ethernet3.performance.mibCounters.ifOutBandwidth.5min

       unit name = bps
       formula = 8 * ; 8 /"
   ::= {pr1645v2PortSwEMibCntrsEntry 3060006912}

pr1645v2PortSwEMibCntrsH2P OBJECT-TYPE
   SYNTAX      SEQUENCE OF Pr1645v2PortSwEMibCntrsH2PEntry
   MAX-ACCESS  not-accessible
   STATUS      current
   DESCRIPTION
      ""
   ::= {pr1645v2PortSwEMibCntrs 2046820352}

pr1645v2PortSwEMibCntrsH2PEntry OBJECT-TYPE
   SYNTAX      Pr1645v2PortSwEMibCntrsH2PEntry
   MAX-ACCESS  not-accessible
   STATUS      current
   DESCRIPTION
      ""
   INDEX      { pr1645v2PortSwEMibCntrsTableIx,
                pr1645v2PortSwEMibCntrsH2PTableIx }
   ::= {pr1645v2PortSwEMibCntrsH2P 1}

Pr1645v2PortSwEMibCntrsH2PEntry ::=
   SEQUENCE
      {
      pr1645v2PortSwEMibCntrsH2PTableIx
         TableIndex,
      pr1645v2PortSwEMibCntrsH2PSysUpTime
         TimeTicks,
      pr1645v2PortSwEMibCntrsH2PIfUpTime
         TimeTicks,
      pr1645v2PortSwEMibCntrsH2PIfStatChanges
         Counter32,
      pr1645v2PortSwEMibCntrsH2PIfInOctets
         Counter64,
      pr1645v2PortSwEMibCntrsH2PIfInUCPkts
         Counter64,
      pr1645v2PortSwEMibCntrsH2PIfInNUCPkts
         Counter64,
      pr1645v2PortSwEMibCntrsH2PIfInDiscards
         Counter64,
      pr1645v2PortSwEMibCntrsH2PIfInErrors
         Counter64,
      pr1645v2PortSwEMibCntrsH2PIfInBandwidth
         Integer32,
      pr1645v2PortSwEMibCntrsH2PIfOutOctets
         Counter64,
      pr1645v2PortSwEMibCntrsH2PIfOutUCPkts
         Counter64,
      pr1645v2PortSwEMibCntrsH2PIfOutNUCPkts
         Counter64,
      pr1645v2PortSwEMibCntrsH2PIfOutDiscards
         Counter64,
      pr1645v2PortSwEMibCntrsH2PIfOutErrors
         Counter64,
      pr1645v2PortSwEMibCntrsH2PIfOutBandwidth
         Integer32,
      pr1645v2PortSwEMibCntrsH2PIfErrSec
         Counter32
      }

pr1645v2PortSwEMibCntrsH2PTableIx OBJECT-TYPE
   SYNTAX      TableIndex
   MAX-ACCESS  not-accessible
   STATUS      current
   DESCRIPTION
      ""
   ::= {pr1645v2PortSwEMibCntrsH2PEntry 11}

pr1645v2PortSwEMibCntrsH2PSysUpTime OBJECT-TYPE
   SYNTAX      TimeTicks
   MAX-ACCESS  read-only
   STATUS      current
   DESCRIPTION
      "Path: ethernet3.performance.mibCounters.h2Performance.sysUpTime

       Time in centi-second."
   ::= {pr1645v2PortSwEMibCntrsH2PEntry 16777216}

pr1645v2PortSwEMibCntrsH2PIfUpTime OBJECT-TYPE
   SYNTAX      TimeTicks
   MAX-ACCESS  read-only
   STATUS      current
   DESCRIPTION
      "Path: ethernet3.performance.mibCounters.h2Performance.ifUpTime

       Time in centi-second."
   ::= {pr1645v2PortSwEMibCntrsH2PEntry 33554432}

pr1645v2PortSwEMibCntrsH2PIfStatChanges OBJECT-TYPE
   SYNTAX      Counter32
   MAX-ACCESS  read-only
   STATUS      current
   DESCRIPTION
      "Path: ethernet3.performance.mibCounters.h2Performance.ifStatusChanges

       32 bit unsigned wrappable counter."
   ::= {pr1645v2PortSwEMibCntrsH2PEntry 50331648}

pr1645v2PortSwEMibCntrsH2PIfInOctets OBJECT-TYPE
   SYNTAX      Counter64
   MAX-ACCESS  read-only
   STATUS      current
   DESCRIPTION
      "Path: ethernet3.performance.mibCounters.h2Performance.ifInOctets

       64 bit unsigned wrappable counter."
   ::= {pr1645v2PortSwEMibCntrsH2PEntry 67108864}

pr1645v2PortSwEMibCntrsH2PIfInUCPkts OBJECT-TYPE
   SYNTAX      Counter64
   MAX-ACCESS  read-only
   STATUS      current
   DESCRIPTION
      "Path: ethernet3.performance.mibCounters.h2Performance.ifInUcastPkts

       64 bit unsigned wrappable counter."
   ::= {pr1645v2PortSwEMibCntrsH2PEntry 83886080}

pr1645v2PortSwEMibCntrsH2PIfInNUCPkts OBJECT-TYPE
   SYNTAX      Counter64
   MAX-ACCESS  read-only
   STATUS      current
   DESCRIPTION
      "Path: ethernet3.performance.mibCounters.h2Performance.ifInNUcastPkts

       64 bit unsigned wrappable counter."
   ::= {pr1645v2PortSwEMibCntrsH2PEntry 100663296}

pr1645v2PortSwEMibCntrsH2PIfInDiscards OBJECT-TYPE
   SYNTAX      Counter64
   MAX-ACCESS  read-only
   STATUS      current
   DESCRIPTION
      "Path: ethernet3.performance.mibCounters.h2Performance.ifInDiscards

       64 bit unsigned wrappable counter."
   ::= {pr1645v2PortSwEMibCntrsH2PEntry 117440512}

pr1645v2PortSwEMibCntrsH2PIfInErrors OBJECT-TYPE
   SYNTAX      Counter64
   MAX-ACCESS  read-only
   STATUS      current
   DESCRIPTION
      "Path: ethernet3.performance.mibCounters.h2Performance.ifInErrors

       64 bit unsigned wrappable counter."
   ::= {pr1645v2PortSwEMibCntrsH2PEntry 134217728}

pr1645v2PortSwEMibCntrsH2PIfInBandwidth OBJECT-TYPE
   SYNTAX      Integer32
   MAX-ACCESS  read-only
   STATUS      current
   DESCRIPTION
      "Path: ethernet3.performance.mibCounters.h2Performance.ifInBandwidth

       unit name = bps
       formula = 8 * ; 8 /"
   ::= {pr1645v2PortSwEMibCntrsH2PEntry 268435456}

pr1645v2PortSwEMibCntrsH2PIfOutOctets OBJECT-TYPE
   SYNTAX      Counter64
   MAX-ACCESS  read-only
   STATUS      current
   DESCRIPTION
      "Path: ethernet3.performance.mibCounters.h2Performance.ifOutOctets

       64 bit unsigned wrappable counter."
   ::= {pr1645v2PortSwEMibCntrsH2PEntry 167772160}

pr1645v2PortSwEMibCntrsH2PIfOutUCPkts OBJECT-TYPE
   SYNTAX      Counter64
   MAX-ACCESS  read-only
   STATUS      current
   DESCRIPTION
      "Path: ethernet3.performance.mibCounters.h2Performance.ifOutUcastPkts

       64 bit unsigned wrappable counter."
   ::= {pr1645v2PortSwEMibCntrsH2PEntry 184549376}

pr1645v2PortSwEMibCntrsH2PIfOutNUCPkts OBJECT-TYPE
   SYNTAX      Counter64
   MAX-ACCESS  read-only
   STATUS      current
   DESCRIPTION
      "Path: ethernet3.performance.mibCounters.h2Performance.ifOutNUcastPkts

       64 bit unsigned wrappable counter."
   ::= {pr1645v2PortSwEMibCntrsH2PEntry 201326592}

pr1645v2PortSwEMibCntrsH2PIfOutDiscards OBJECT-TYPE
   SYNTAX      Counter64
   MAX-ACCESS  read-only
   STATUS      current
   DESCRIPTION
      "Path: ethernet3.performance.mibCounters.h2Performance.ifOutDiscards

       64 bit unsigned wrappable counter."
   ::= {pr1645v2PortSwEMibCntrsH2PEntry 218103808}

pr1645v2PortSwEMibCntrsH2PIfOutErrors OBJECT-TYPE
   SYNTAX      Counter64
   MAX-ACCESS  read-only
   STATUS      current
   DESCRIPTION
      "Path: ethernet3.performance.mibCounters.h2Performance.ifOutErrors

       64 bit unsigned wrappable counter."
   ::= {pr1645v2PortSwEMibCntrsH2PEntry 234881024}

pr1645v2PortSwEMibCntrsH2PIfOutBandwidth OBJECT-TYPE
   SYNTAX      Integer32
   MAX-ACCESS  read-only
   STATUS      current
   DESCRIPTION
      "Path: ethernet3.performance.mibCounters.h2Performance.ifOutBandwidth

       unit name = bps
       formula = 8 * ; 8 /"
   ::= {pr1645v2PortSwEMibCntrsH2PEntry 285212672}

pr1645v2PortSwEMibCntrsH2PIfErrSec OBJECT-TYPE
   SYNTAX      Counter32
   MAX-ACCESS  read-only
   STATUS      current
   DESCRIPTION
      "Path: ethernet3.performance.mibCounters.h2Performance.ifErrSec

       32 bit unsigned wrappable counter."
   ::= {pr1645v2PortSwEMibCntrsH2PEntry 251658240}

pr1645v2PortSwEMibCntrsH24P OBJECT-TYPE
   SYNTAX      SEQUENCE OF Pr1645v2PortSwEMibCntrsH24PEntry
   MAX-ACCESS  not-accessible
   STATUS      current
   DESCRIPTION
      ""
   ::= {pr1645v2PortSwEMibCntrs 2063597568}

pr1645v2PortSwEMibCntrsH24PEntry OBJECT-TYPE
   SYNTAX      Pr1645v2PortSwEMibCntrsH24PEntry
   MAX-ACCESS  not-accessible
   STATUS      current
   DESCRIPTION
      ""
   INDEX      { pr1645v2PortSwEMibCntrsTableIx,
                pr1645v2PortSwEMibCntrsH24PTableIx }
   ::= {pr1645v2PortSwEMibCntrsH24P 1}

Pr1645v2PortSwEMibCntrsH24PEntry ::=
   SEQUENCE
      {
      pr1645v2PortSwEMibCntrsH24PTableIx
         TableIndex,
      pr1645v2PortSwEMibCntrsH24PSysUpTime
         TimeTicks,
      pr1645v2PortSwEMibCntrsH24PIfUpTime
         TimeTicks,
      pr1645v2PortSwEMibCntrsH24PIfStatChanges
         Counter32,
      pr1645v2PortSwEMibCntrsH24PIfInOctets
         Counter64,
      pr1645v2PortSwEMibCntrsH24PIfInUCPkts
         Counter64,
      pr1645v2PortSwEMibCntrsH24PIfInNUCPkts
         Counter64,
      pr1645v2PortSwEMibCntrsH24PIfInDiscards
         Counter64,
      pr1645v2PortSwEMibCntrsH24PIfInErrors
         Counter64,
      pr1645v2PortSwEMibCntrsH24PIfInBandwidth
         Integer32,
      pr1645v2PortSwEMibCntrsH24PIfOutOctets
         Counter64,
      pr1645v2PortSwEMibCntrsH24PIfOutUCPkts
         Counter64,
      pr1645v2PortSwEMibCntrsH24PIfOutNUCPkts
         Counter64,
      pr1645v2PortSwEMibCntrsH24PIfOutDiscards
         Counter64,
      pr1645v2PortSwEMibCntrsH24PIfOutErrors
         Counter64,
      pr1645v2PortSwEMibCntrsH24PIfOutBandwidth
         Integer32,
      pr1645v2PortSwEMibCntrsH24PIfErrSec
         Counter32
      }

pr1645v2PortSwEMibCntrsH24PTableIx OBJECT-TYPE
   SYNTAX      TableIndex
   MAX-ACCESS  not-accessible
   STATUS      current
   DESCRIPTION
      ""
   ::= {pr1645v2PortSwEMibCntrsH24PEntry 11}

pr1645v2PortSwEMibCntrsH24PSysUpTime OBJECT-TYPE
   SYNTAX      TimeTicks
   MAX-ACCESS  read-only
   STATUS      current
   DESCRIPTION
      "Path: ethernet3.performance.mibCounters.h24Performance.sysUpTime

       Time in centi-second."
   ::= {pr1645v2PortSwEMibCntrsH24PEntry 16777216}

pr1645v2PortSwEMibCntrsH24PIfUpTime OBJECT-TYPE
   SYNTAX      TimeTicks
   MAX-ACCESS  read-only
   STATUS      current
   DESCRIPTION
      "Path: ethernet3.performance.mibCounters.h24Performance.ifUpTime

       Time in centi-second."
   ::= {pr1645v2PortSwEMibCntrsH24PEntry 33554432}

pr1645v2PortSwEMibCntrsH24PIfStatChanges OBJECT-TYPE
   SYNTAX      Counter32
   MAX-ACCESS  read-only
   STATUS      current
   DESCRIPTION
      "Path: ethernet3.performance.mibCounters.h24Performance.ifStatusChanges

       32 bit unsigned wrappable counter."
   ::= {pr1645v2PortSwEMibCntrsH24PEntry 50331648}

pr1645v2PortSwEMibCntrsH24PIfInOctets OBJECT-TYPE
   SYNTAX      Counter64
   MAX-ACCESS  read-only
   STATUS      current
   DESCRIPTION
      "Path: ethernet3.performance.mibCounters.h24Performance.ifInOctets

       64 bit unsigned wrappable counter."
   ::= {pr1645v2PortSwEMibCntrsH24PEntry 67108864}

pr1645v2PortSwEMibCntrsH24PIfInUCPkts OBJECT-TYPE
   SYNTAX      Counter64
   MAX-ACCESS  read-only
   STATUS      current
   DESCRIPTION
      "Path: ethernet3.performance.mibCounters.h24Performance.ifInUcastPkts

       64 bit unsigned wrappable counter."
   ::= {pr1645v2PortSwEMibCntrsH24PEntry 83886080}

pr1645v2PortSwEMibCntrsH24PIfInNUCPkts OBJECT-TYPE
   SYNTAX      Counter64
   MAX-ACCESS  read-only
   STATUS      current
   DESCRIPTION
      "Path: ethernet3.performance.mibCounters.h24Performance.ifInNUcastPkts

       64 bit unsigned wrappable counter."
   ::= {pr1645v2PortSwEMibCntrsH24PEntry 100663296}

pr1645v2PortSwEMibCntrsH24PIfInDiscards OBJECT-TYPE
   SYNTAX      Counter64
   MAX-ACCESS  read-only
   STATUS      current
   DESCRIPTION
      "Path: ethernet3.performance.mibCounters.h24Performance.ifInDiscards

       64 bit unsigned wrappable counter."
   ::= {pr1645v2PortSwEMibCntrsH24PEntry 117440512}

pr1645v2PortSwEMibCntrsH24PIfInErrors OBJECT-TYPE
   SYNTAX      Counter64
   MAX-ACCESS  read-only
   STATUS      current
   DESCRIPTION
      "Path: ethernet3.performance.mibCounters.h24Performance.ifInErrors

       64 bit unsigned wrappable counter."
   ::= {pr1645v2PortSwEMibCntrsH24PEntry 134217728}

pr1645v2PortSwEMibCntrsH24PIfInBandwidth OBJECT-TYPE
   SYNTAX      Integer32
   MAX-ACCESS  read-only
   STATUS      current
   DESCRIPTION
      "Path: ethernet3.performance.mibCounters.h24Performance.ifInBandwidth

       unit name = bps
       formula = 8 * ; 8 /"
   ::= {pr1645v2PortSwEMibCntrsH24PEntry 268435456}

pr1645v2PortSwEMibCntrsH24PIfOutOctets OBJECT-TYPE
   SYNTAX      Counter64
   MAX-ACCESS  read-only
   STATUS      current
   DESCRIPTION
      "Path: ethernet3.performance.mibCounters.h24Performance.ifOutOctets

       64 bit unsigned wrappable counter."
   ::= {pr1645v2PortSwEMibCntrsH24PEntry 167772160}

pr1645v2PortSwEMibCntrsH24PIfOutUCPkts OBJECT-TYPE
   SYNTAX      Counter64
   MAX-ACCESS  read-only
   STATUS      current
   DESCRIPTION
      "Path: ethernet3.performance.mibCounters.h24Performance.ifOutUcastPkts

       64 bit unsigned wrappable counter."
   ::= {pr1645v2PortSwEMibCntrsH24PEntry 184549376}

pr1645v2PortSwEMibCntrsH24PIfOutNUCPkts OBJECT-TYPE
   SYNTAX      Counter64
   MAX-ACCESS  read-only
   STATUS      current
   DESCRIPTION
      "Path: ethernet3.performance.mibCounters.h24Performance.ifOutNUcastPkts

       64 bit unsigned wrappable counter."
   ::= {pr1645v2PortSwEMibCntrsH24PEntry 201326592}

pr1645v2PortSwEMibCntrsH24PIfOutDiscards OBJECT-TYPE
   SYNTAX      Counter64
   MAX-ACCESS  read-only
   STATUS      current
   DESCRIPTION
      "Path: ethernet3.performance.mibCounters.h24Performance.ifOutDiscards

       64 bit unsigned wrappable counter."
   ::= {pr1645v2PortSwEMibCntrsH24PEntry 218103808}

pr1645v2PortSwEMibCntrsH24PIfOutErrors OBJECT-TYPE
   SYNTAX      Counter64
   MAX-ACCESS  read-only
   STATUS      current
   DESCRIPTION
      "Path: ethernet3.performance.mibCounters.h24Performance.ifOutErrors

       64 bit unsigned wrappable counter."
   ::= {pr1645v2PortSwEMibCntrsH24PEntry 234881024}

pr1645v2PortSwEMibCntrsH24PIfOutBandwidth OBJECT-TYPE
   SYNTAX      Integer32
   MAX-ACCESS  read-only
   STATUS      current
   DESCRIPTION
      "Path: ethernet3.performance.mibCounters.h24Performance.ifOutBandwidth

       unit name = bps
       formula = 8 * ; 8 /"
   ::= {pr1645v2PortSwEMibCntrsH24PEntry 285212672}

pr1645v2PortSwEMibCntrsH24PIfErrSec OBJECT-TYPE
   SYNTAX      Counter32
   MAX-ACCESS  read-only
   STATUS      current
   DESCRIPTION
      "Path: ethernet3.performance.mibCounters.h24Performance.ifErrSec

       32 bit unsigned wrappable counter."
   ::= {pr1645v2PortSwEMibCntrsH24PEntry 251658240}

pr1645v2PortSwEMibCntrsD7P OBJECT-TYPE
   SYNTAX      SEQUENCE OF Pr1645v2PortSwEMibCntrsD7PEntry
   MAX-ACCESS  not-accessible
   STATUS      current
   DESCRIPTION
      ""
   ::= {pr1645v2PortSwEMibCntrs 2080374784}

pr1645v2PortSwEMibCntrsD7PEntry OBJECT-TYPE
   SYNTAX      Pr1645v2PortSwEMibCntrsD7PEntry
   MAX-ACCESS  not-accessible
   STATUS      current
   DESCRIPTION
      ""
   INDEX      { pr1645v2PortSwEMibCntrsTableIx,
                pr1645v2PortSwEMibCntrsD7PTableIx }
   ::= {pr1645v2PortSwEMibCntrsD7P 1}

Pr1645v2PortSwEMibCntrsD7PEntry ::=
   SEQUENCE
      {
      pr1645v2PortSwEMibCntrsD7PTableIx
         TableIndex,
      pr1645v2PortSwEMibCntrsD7PSysUpTime
         TimeTicks,
      pr1645v2PortSwEMibCntrsD7PIfUpTime
         TimeTicks,
      pr1645v2PortSwEMibCntrsD7PIfStatChanges
         Counter32,
      pr1645v2PortSwEMibCntrsD7PIfInOctets
         Counter64,
      pr1645v2PortSwEMibCntrsD7PIfInUCPkts
         Counter64,
      pr1645v2PortSwEMibCntrsD7PIfInNUCPkts
         Counter64,
      pr1645v2PortSwEMibCntrsD7PIfInDiscards
         Counter64,
      pr1645v2PortSwEMibCntrsD7PIfInErrors
         Counter64,
      pr1645v2PortSwEMibCntrsD7PIfInBandwidth
         Integer32,
      pr1645v2PortSwEMibCntrsD7PIfOutOctets
         Counter64,
      pr1645v2PortSwEMibCntrsD7PIfOutUCPkts
         Counter64,
      pr1645v2PortSwEMibCntrsD7PIfOutNUCPkts
         Counter64,
      pr1645v2PortSwEMibCntrsD7PIfOutDiscards
         Counter64,
      pr1645v2PortSwEMibCntrsD7PIfOutErrors
         Counter64,
      pr1645v2PortSwEMibCntrsD7PIfOutBandwidth
         Integer32,
      pr1645v2PortSwEMibCntrsD7PIfErrSec
         Counter32
      }

pr1645v2PortSwEMibCntrsD7PTableIx OBJECT-TYPE
   SYNTAX      TableIndex
   MAX-ACCESS  not-accessible
   STATUS      current
   DESCRIPTION
      ""
   ::= {pr1645v2PortSwEMibCntrsD7PEntry 11}

pr1645v2PortSwEMibCntrsD7PSysUpTime OBJECT-TYPE
   SYNTAX      TimeTicks
   MAX-ACCESS  read-only
   STATUS      current
   DESCRIPTION
      "Path: ethernet3.performance.mibCounters.d7Performance.sysUpTime

       Time in centi-second."
   ::= {pr1645v2PortSwEMibCntrsD7PEntry 16777216}

pr1645v2PortSwEMibCntrsD7PIfUpTime OBJECT-TYPE
   SYNTAX      TimeTicks
   MAX-ACCESS  read-only
   STATUS      current
   DESCRIPTION
      "Path: ethernet3.performance.mibCounters.d7Performance.ifUpTime

       Time in centi-second."
   ::= {pr1645v2PortSwEMibCntrsD7PEntry 33554432}

pr1645v2PortSwEMibCntrsD7PIfStatChanges OBJECT-TYPE
   SYNTAX      Counter32
   MAX-ACCESS  read-only
   STATUS      current
   DESCRIPTION
      "Path: ethernet3.performance.mibCounters.d7Performance.ifStatusChanges

       32 bit unsigned wrappable counter."
   ::= {pr1645v2PortSwEMibCntrsD7PEntry 50331648}

pr1645v2PortSwEMibCntrsD7PIfInOctets OBJECT-TYPE
   SYNTAX      Counter64
   MAX-ACCESS  read-only
   STATUS      current
   DESCRIPTION
      "Path: ethernet3.performance.mibCounters.d7Performance.ifInOctets

       64 bit unsigned wrappable counter."
   ::= {pr1645v2PortSwEMibCntrsD7PEntry 67108864}

pr1645v2PortSwEMibCntrsD7PIfInUCPkts OBJECT-TYPE
   SYNTAX      Counter64
   MAX-ACCESS  read-only
   STATUS      current
   DESCRIPTION
      "Path: ethernet3.performance.mibCounters.d7Performance.ifInUcastPkts

       64 bit unsigned wrappable counter."
   ::= {pr1645v2PortSwEMibCntrsD7PEntry 83886080}

pr1645v2PortSwEMibCntrsD7PIfInNUCPkts OBJECT-TYPE
   SYNTAX      Counter64
   MAX-ACCESS  read-only
   STATUS      current
   DESCRIPTION
      "Path: ethernet3.performance.mibCounters.d7Performance.ifInNUcastPkts

       64 bit unsigned wrappable counter."
   ::= {pr1645v2PortSwEMibCntrsD7PEntry 100663296}

pr1645v2PortSwEMibCntrsD7PIfInDiscards OBJECT-TYPE
   SYNTAX      Counter64
   MAX-ACCESS  read-only
   STATUS      current
   DESCRIPTION
      "Path: ethernet3.performance.mibCounters.d7Performance.ifInDiscards

       64 bit unsigned wrappable counter."
   ::= {pr1645v2PortSwEMibCntrsD7PEntry 117440512}

pr1645v2PortSwEMibCntrsD7PIfInErrors OBJECT-TYPE
   SYNTAX      Counter64
   MAX-ACCESS  read-only
   STATUS      current
   DESCRIPTION
      "Path: ethernet3.performance.mibCounters.d7Performance.ifInErrors

       64 bit unsigned wrappable counter."
   ::= {pr1645v2PortSwEMibCntrsD7PEntry 134217728}

pr1645v2PortSwEMibCntrsD7PIfInBandwidth OBJECT-TYPE
   SYNTAX      Integer32
   MAX-ACCESS  read-only
   STATUS      current
   DESCRIPTION
      "Path: ethernet3.performance.mibCounters.d7Performance.ifInBandwidth

       unit name = bps
       formula = 8 * ; 8 /"
   ::= {pr1645v2PortSwEMibCntrsD7PEntry 268435456}

pr1645v2PortSwEMibCntrsD7PIfOutOctets OBJECT-TYPE
   SYNTAX      Counter64
   MAX-ACCESS  read-only
   STATUS      current
   DESCRIPTION
      "Path: ethernet3.performance.mibCounters.d7Performance.ifOutOctets

       64 bit unsigned wrappable counter."
   ::= {pr1645v2PortSwEMibCntrsD7PEntry 167772160}

pr1645v2PortSwEMibCntrsD7PIfOutUCPkts OBJECT-TYPE
   SYNTAX      Counter64
   MAX-ACCESS  read-only
   STATUS      current
   DESCRIPTION
      "Path: ethernet3.performance.mibCounters.d7Performance.ifOutUcastPkts

       64 bit unsigned wrappable counter."
   ::= {pr1645v2PortSwEMibCntrsD7PEntry 184549376}

pr1645v2PortSwEMibCntrsD7PIfOutNUCPkts OBJECT-TYPE
   SYNTAX      Counter64
   MAX-ACCESS  read-only
   STATUS      current
   DESCRIPTION
      "Path: ethernet3.performance.mibCounters.d7Performance.ifOutNUcastPkts

       64 bit unsigned wrappable counter."
   ::= {pr1645v2PortSwEMibCntrsD7PEntry 201326592}

pr1645v2PortSwEMibCntrsD7PIfOutDiscards OBJECT-TYPE
   SYNTAX      Counter64
   MAX-ACCESS  read-only
   STATUS      current
   DESCRIPTION
      "Path: ethernet3.performance.mibCounters.d7Performance.ifOutDiscards

       64 bit unsigned wrappable counter."
   ::= {pr1645v2PortSwEMibCntrsD7PEntry 218103808}

pr1645v2PortSwEMibCntrsD7PIfOutErrors OBJECT-TYPE
   SYNTAX      Counter64
   MAX-ACCESS  read-only
   STATUS      current
   DESCRIPTION
      "Path: ethernet3.performance.mibCounters.d7Performance.ifOutErrors

       64 bit unsigned wrappable counter."
   ::= {pr1645v2PortSwEMibCntrsD7PEntry 234881024}

pr1645v2PortSwEMibCntrsD7PIfOutBandwidth OBJECT-TYPE
   SYNTAX      Integer32
   MAX-ACCESS  read-only
   STATUS      current
   DESCRIPTION
      "Path: ethernet3.performance.mibCounters.d7Performance.ifOutBandwidth

       unit name = bps
       formula = 8 * ; 8 /"
   ::= {pr1645v2PortSwEMibCntrsD7PEntry 285212672}

pr1645v2PortSwEMibCntrsD7PIfErrSec OBJECT-TYPE
   SYNTAX      Counter32
   MAX-ACCESS  read-only
   STATUS      current
   DESCRIPTION
      "Path: ethernet3.performance.mibCounters.d7Performance.ifErrSec

       32 bit unsigned wrappable counter."
   ::= {pr1645v2PortSwEMibCntrsD7PEntry 251658240}



fr1645v2PortSwE OBJECT IDENTIFIER ::= {r1645v2PortSwE 13}


fr1645v2PortSwEAlarm OBJECT IDENTIFIER ::= {fr1645v2PortSwE 207}

fr1645v2PortSwEAlarmSSC OBJECT IDENTIFIER ::= {fr1645v2PortSwEAlarm 1}

fr1645v2PortSwEAlarmEntry OBJECT IDENTIFIER ::= {fr1645v2PortSwEAlarmSSC 1}

fr1645v2PortSwEAlarmDiscriminator OBJECT-TYPE
   SYNTAX      Integer32
   MAX-ACCESS  read-only
   STATUS      current
   DESCRIPTION
      "Path: ethernet3.alarms.alarmInfo.discriminator"
   ::= {fr1645v2PortSwEAlarmEntry 16777216}

fr1645v2PortSwEAlarmCurrent OBJECT-TYPE
   SYNTAX      Integer32
   MAX-ACCESS  read-only
   STATUS      current
   DESCRIPTION
      "Path: ethernet3.alarms.alarmInfo.currentAlarms

       Bit meanings:
               bit 0 = linkDown"
   ::= {fr1645v2PortSwEAlarmEntry 33554432}

fr1645v2PortSwEAlarmPrevious OBJECT-TYPE
   SYNTAX      Integer32
   MAX-ACCESS  read-only
   STATUS      current
   DESCRIPTION
      "Path: ethernet3.alarms.alarmInfo.previousAlarms

       Bit meanings:
               bit 0 = linkDown"
   ::= {fr1645v2PortSwEAlarmEntry 50331648}

fr1645v2PortSwEAlarmMask OBJECT-TYPE
   SYNTAX      Integer32
   MAX-ACCESS  read-only
   STATUS      current
   DESCRIPTION
      "Path: ethernet3.alarms.alarmInfo.alarmMask

       Bit meanings:
               bit 0 = linkDown"
   ::= {fr1645v2PortSwEAlarmEntry 67108864}

fr1645v2PortSwEAlarmLevLinkDown OBJECT-TYPE
   SYNTAX      Integer32
   MAX-ACCESS  read-only
   STATUS      current
   DESCRIPTION
      "Path: ethernet3.alarms.alarmInfo.alarmLevel.linkDown"
   ::= {fr1645v2PortSwEAlarmEntry 83951616}


fr1645v2PortSwEAlarmE2 OBJECT IDENTIFIER ::= {fr1645v2PortSwEAlarm 2}

fr1645v2PortSwEAlarmE2Entry OBJECT IDENTIFIER ::= {fr1645v2PortSwEAlarmE2 1}

fr1645v2PortSwEAlarmE2LinkDown OBJECT IDENTIFIER ::= {fr1645v2PortSwEAlarmE2Entry 10}

fr1645v2PortSwEAlarmE2LinkDownPfx OBJECT IDENTIFIER ::= {fr1645v2PortSwEAlarmE2LinkDown 0}

fr1645v2PortSwEAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'portSwitchExt'
                (root='router1645') has changed from the ON to the OFF state."
   ::= {fr1645v2PortSwEAlarmE2LinkDownPfx 1}

fr1645v2PortSwEAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'portSwitchExt'
                (root='router1645') has changed from the OFF to the ON state."
   ::= {fr1645v2PortSwEAlarmE2LinkDownPfx 2}



ar1645v2PortSwE OBJECT IDENTIFIER ::= {r1645v2PortSwE 16}


ar1645v2PortSwEClearCounters OBJECT-TYPE
   SYNTAX      Integer32
   MAX-ACCESS  read-write
   STATUS      current
   DESCRIPTION
      "Path: ethernet3.actions.clearCounters
       Info: reset counters"
   ::= {ar1645v2PortSwE 263}


ar1645v2PortSwESalAction OBJECT-TYPE
   SYNTAX      Integer32
   MAX-ACCESS  read-write
   STATUS      current
   DESCRIPTION
      "Path: ethernet3.actions.salAction
       Info: action in the debug group"
   ::= {ar1645v2PortSwE 97}


ar1645v2PortSwERegAction OBJECT-TYPE
   SYNTAX      Integer32
   MAX-ACCESS  read-write
   STATUS      current
   DESCRIPTION
      "Path: ethernet3.actions.regAction
       Info: action in the debug group"
   ::= {ar1645v2PortSwE 95}


ar1645v2PortSwEMeasTemp OBJECT-TYPE
   SYNTAX      Integer32
   MAX-ACCESS  read-write
   STATUS      current
   DESCRIPTION
      "Path: ethernet3.actions.measTemp
       Info: action in the debug group"
   ::= {ar1645v2PortSwE 85}


ar1645v2PortSwEClearAction OBJECT-TYPE
   SYNTAX      Integer32
   MAX-ACCESS  read-write
   STATUS      current
   DESCRIPTION
      "Path: ethernet3.actions.clearAction
       Info: action in the debug group"
   ::= {ar1645v2PortSwE 84}


ar1645v2PortSwEClearSwitchCache OBJECT-TYPE
   SYNTAX      Integer32
   MAX-ACCESS  read-write
   STATUS      current
   DESCRIPTION
      "Path: ethernet3.actions.clearSwitchCache
       Info: Clear the dnamic entries in the swith MAC cache"
   ::= {ar1645v2PortSwE 81}


ar1645v2PortSwEEnableRds OBJECT-TYPE
   SYNTAX      Integer32
   MAX-ACCESS  read-write
   STATUS      current
   DESCRIPTION
      "Path: ethernet3.actions.enableRds
       Info: action in the debug group"
   ::= {ar1645v2PortSwE 367}


ar1645v2PortSwEDisableRds OBJECT-TYPE
   SYNTAX      Integer32
   MAX-ACCESS  read-write
   STATUS      current
   DESCRIPTION
      "Path: ethernet3.actions.disableRds
       Info: action in the debug group"
   ::= {ar1645v2PortSwE 366}


ar1645v2PortSwEEnableTds OBJECT-TYPE
   SYNTAX      Integer32
   MAX-ACCESS  read-write
   STATUS      current
   DESCRIPTION
      "Path: ethernet3.actions.enableTds
       Info: action in the debug group"
   ::= {ar1645v2PortSwE 365}


ar1645v2PortSwEDisableTds OBJECT-TYPE
   SYNTAX      Integer32
   MAX-ACCESS  read-write
   STATUS      current
   DESCRIPTION
      "Path: ethernet3.actions.disableTds
       Info: action in the debug group"
   ::= {ar1645v2PortSwE 364}


ar1645v2PortSwEClearTsecStats OBJECT-TYPE
   SYNTAX      Integer32
   MAX-ACCESS  read-write
   STATUS      current
   DESCRIPTION
      "Path: ethernet3.actions.clearTsecStats
       Info: action in the debug group"
   ::= {ar1645v2PortSwE 363}


ar1645v2PortSwEStopTsecStats OBJECT-TYPE
   SYNTAX      Integer32
   MAX-ACCESS  read-write
   STATUS      current
   DESCRIPTION
      "Path: ethernet3.actions.stopTsecStats
       Info: action in the debug group"
   ::= {ar1645v2PortSwE 362}


ar1645v2PortSwEStartTsecStats OBJECT-TYPE
   SYNTAX      Integer32
   MAX-ACCESS  read-write
   STATUS      current
   DESCRIPTION
      "Path: ethernet3.actions.startTsecStats
       Info: action in the debug group"
   ::= {ar1645v2PortSwE 361}


ar1645v2PortSwEClearDebugCounters OBJECT-TYPE
   SYNTAX      Integer32
   MAX-ACCESS  read-write
   STATUS      current
   DESCRIPTION
      "Path: ethernet3.actions.clearDebugCounters
       Info: action in the debug group"
   ::= {ar1645v2PortSwE 76}



END
