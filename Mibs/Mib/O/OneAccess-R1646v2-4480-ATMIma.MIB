OneAccess-R1646v2-4480-ATMIma DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2ATMIma OBJECT IDENTIFIER ::= {r1646Rootv2 4480}

r1646v2ATMImaMOProp OBJECT IDENTIFIER ::= {r1646v2ATMIma 1}

r1646v2ATMImaMOPropEntry OBJECT IDENTIFIER ::= {r1646v2ATMImaMOProp 1}

r1646v2ATMImaMOPropPath OBJECT-TYPE
   SYNTAX      ContainmentPath
   MAX-ACCESS  read-only
   STATUS      current
   DESCRIPTION
      "Textual description of the containment tree from the instance of
       the root object down to the instance of the current object."
   ::= {r1646v2ATMImaMOPropEntry 3}

r1646v2ATMImaMOPropRev OBJECT-TYPE
   SYNTAX      ObjectRevision
   MAX-ACCESS  read-only
   STATUS      current
   DESCRIPTION
      "This value corresponds with the revision of the MANAGED OBJECT."
   ::= {r1646v2ATMImaMOPropEntry 4}



er1646v2ATMIma OBJECT IDENTIFIER ::= {r1646v2ATMIma 11}


er1646v2ATMImaVp OBJECT IDENTIFIER ::= {er1646v2ATMIma 92}

er1646v2ATMImaVpSSCTable OBJECT-TYPE
   SYNTAX      SEQUENCE OF Er1646v2ATMImaVpEntry
   MAX-ACCESS  not-accessible
   STATUS      current
   DESCRIPTION
      ""
   ::= {er1646v2ATMImaVp 1}

er1646v2ATMImaVpEntry OBJECT-TYPE
   SYNTAX      Er1646v2ATMImaVpEntry
   MAX-ACCESS  not-accessible
   STATUS      current
   DESCRIPTION
      ""
   INDEX      { er1646v2ATMImaVpTableIx }
   ::= {er1646v2ATMImaVpSSCTable 1}

Er1646v2ATMImaVpEntry ::=
   SEQUENCE
      {
      er1646v2ATMImaVpActions
         VariableLengthTableActions,
      er1646v2ATMImaVpTableIx
         TableIndex,
      er1646v2ATMImaVpVpi
         Integer32,
      er1646v2ATMImaVpLbOper
         INTEGER,
      er1646v2ATMImaVpLbInterval
         TimeTicks,
      er1646v2ATMImaVpLbFailsPerm
         Integer32,
      er1646v2ATMImaVpLbTar
         INTEGER,
      er1646v2ATMImaVpCcDir
         INTEGER,
      er1646v2ATMImaVpCcTar
         INTEGER,
      er1646v2ATMImaVpCcTxMode
         INTEGER,
      er1646v2ATMImaVpCcTxTxPer
         TimeTicks,
      er1646v2ATMImaVpCcRxRcvTim
         TimeTicks,
      er1646v2ATMImaVpCcActProc
         INTEGER,
      er1646v2ATMImaVpCcActTim
         TimeTicks,
      er1646v2ATMImaVpCcActCnt
         Integer32,
      er1646v2ATMImaVpPmDir
         INTEGER,
      er1646v2ATMImaVpPmTar
         INTEGER,
      er1646v2ATMImaVpPmType
         INTEGER,
      er1646v2ATMImaVpPmPolicy
         INTEGER,
      er1646v2ATMImaVpPmBsizeamb
         INTEGER,
      er1646v2ATMImaVpPmBsizebma
         INTEGER,
      er1646v2ATMImaVpPmActProc
         INTEGER,
      er1646v2ATMImaVpPmActTim
         TimeTicks,
      er1646v2ATMImaVpPmActCnt
         Integer32,
      er1646v2ATMImaVpCpt
         INTEGER
      }

er1646v2ATMImaVpActions OBJECT-TYPE
   SYNTAX      VariableLengthTableActions
   MAX-ACCESS  read-write
   STATUS      current
   DESCRIPTION
      "By way of this field, some manipulations
       on this table may be performed."
   ::= {er1646v2ATMImaVpEntry 2}

er1646v2ATMImaVpTableIx OBJECT-TYPE
   SYNTAX      TableIndex
   MAX-ACCESS  not-accessible
   STATUS      current
   DESCRIPTION
      ""
   ::= {er1646v2ATMImaVpEntry 11}

er1646v2ATMImaVpVpi OBJECT-TYPE
   SYNTAX      Integer32
   MAX-ACCESS  read-write
   STATUS      current
   DESCRIPTION
      "Path: atm.editConf.vp.vpi"
   ::= {er1646v2ATMImaVpEntry 16777216}

er1646v2ATMImaVpLbOper OBJECT-TYPE
   SYNTAX      INTEGER
               {
               disabled (0),
               enabled (1)
               }
   MAX-ACCESS  read-write
   STATUS      current
   DESCRIPTION
      "Path: atm.editConf.vp.oamF4Loopback.operation

       Possibilities:
               disabled   (0)
               enabled   (1)"
   ::= {er1646v2ATMImaVpEntry 33619968}

er1646v2ATMImaVpLbInterval OBJECT-TYPE
   SYNTAX      TimeTicks
   MAX-ACCESS  read-write
   STATUS      current
   DESCRIPTION
      "Path: atm.editConf.vp.oamF4Loopback.interval

       Time in centi-second."
   ::= {er1646v2ATMImaVpEntry 33685504}

er1646v2ATMImaVpLbFailsPerm OBJECT-TYPE
   SYNTAX      Integer32
   MAX-ACCESS  read-write
   STATUS      current
   DESCRIPTION
      "Path: atm.editConf.vp.oamF4Loopback.failsPermitted"
   ::= {er1646v2ATMImaVpEntry 33816576}

er1646v2ATMImaVpLbTar OBJECT-TYPE
   SYNTAX      INTEGER
               {
               endToEnd (0),
               segment (1),
               both (2)
               }
   MAX-ACCESS  read-write
   STATUS      current
   DESCRIPTION
      "Path: atm.editConf.vp.oamF4Loopback.target

       Possibilities:
               endToEnd   (0)
               segment   (1)
               both   (2)"
   ::= {er1646v2ATMImaVpEntry 33882112}

er1646v2ATMImaVpCcDir OBJECT-TYPE
   SYNTAX      INTEGER
               {
               sink (1),
               source (2),
               both (3)
               }
   MAX-ACCESS  read-write
   STATUS      current
   DESCRIPTION
      "Path: atm.editConf.vp.oamF4CC.direction

       Possibilities:
               sink   (1)
               source   (2)
               both   (3)"
   ::= {er1646v2ATMImaVpEntry 50397184}

er1646v2ATMImaVpCcTar OBJECT-TYPE
   SYNTAX      INTEGER
               {
               endToEnd (0),
               segment (1),
               both (2)
               }
   MAX-ACCESS  read-write
   STATUS      current
   DESCRIPTION
      "Path: atm.editConf.vp.oamF4CC.target

       Possibilities:
               endToEnd   (0)
               segment   (1)
               both   (2)"
   ::= {er1646v2ATMImaVpEntry 50462720}

er1646v2ATMImaVpCcTxMode OBJECT-TYPE
   SYNTAX      INTEGER
               {
               continuously (0),
               onIdle (1)
               }
   MAX-ACCESS  read-write
   STATUS      current
   DESCRIPTION
      "Path: atm.editConf.vp.oamF4CC.tx.mode

       Possibilities:
               continuously   (0)
               onIdle   (1)"
   ::= {er1646v2ATMImaVpEntry 50528512}

er1646v2ATMImaVpCcTxTxPer OBJECT-TYPE
   SYNTAX      TimeTicks
   MAX-ACCESS  read-write
   STATUS      current
   DESCRIPTION
      "Path: atm.editConf.vp.oamF4CC.tx.interval

       Time in centi-second."
   ::= {er1646v2ATMImaVpEntry 50528768}

er1646v2ATMImaVpCcRxRcvTim OBJECT-TYPE
   SYNTAX      TimeTicks
   MAX-ACCESS  read-write
   STATUS      current
   DESCRIPTION
      "Path: atm.editConf.vp.oamF4CC.rx.timeOut

       Time in centi-second."
   ::= {er1646v2ATMImaVpEntry 50725120}

er1646v2ATMImaVpCcActProc OBJECT-TYPE
   SYNTAX      INTEGER
               {
               passive (0),
               activated (1),
               deactivated (2),
               initActivation (3)
               }
   MAX-ACCESS  read-write
   STATUS      current
   DESCRIPTION
      "Path: atm.editConf.vp.oamF4CC.actDeact.initProcedure

       Possibilities:
               passive   (0)
               activated   (1)
               deactivated   (2)
               initActivation   (3)"
   ::= {er1646v2ATMImaVpEntry 50594048}

er1646v2ATMImaVpCcActTim OBJECT-TYPE
   SYNTAX      TimeTicks
   MAX-ACCESS  read-write
   STATUS      current
   DESCRIPTION
      "Path: atm.editConf.vp.oamF4CC.actDeact.retryInterval

       Time in centi-second."
   ::= {er1646v2ATMImaVpEntry 50594304}

er1646v2ATMImaVpCcActCnt OBJECT-TYPE
   SYNTAX      Integer32
   MAX-ACCESS  read-write
   STATUS      current
   DESCRIPTION
      "Path: atm.editConf.vp.oamF4CC.actDeact.retryCount"
   ::= {er1646v2ATMImaVpEntry 50594560}

er1646v2ATMImaVpPmDir OBJECT-TYPE
   SYNTAX      INTEGER
               {
               sink (1),
               source (2),
               both (3)
               }
   MAX-ACCESS  read-write
   STATUS      current
   DESCRIPTION
      "Path: atm.editConf.vp.oamF4PM.direction

       Possibilities:
               sink   (1)
               source   (2)
               both   (3)"
   ::= {er1646v2ATMImaVpEntry 67174400}

er1646v2ATMImaVpPmTar OBJECT-TYPE
   SYNTAX      INTEGER
               {
               endToEnd (0),
               segment (1)
               }
   MAX-ACCESS  read-write
   STATUS      current
   DESCRIPTION
      "Path: atm.editConf.vp.oamF4PM.target

       Possibilities:
               endToEnd   (0)
               segment   (1)"
   ::= {er1646v2ATMImaVpEntry 67239936}

er1646v2ATMImaVpPmType OBJECT-TYPE
   SYNTAX      INTEGER
               {
               fpm (0),
               fpmWithBr (1)
               }
   MAX-ACCESS  read-write
   STATUS      current
   DESCRIPTION
      "Path: atm.editConf.vp.oamF4PM.type

       Possibilities:
               fpm   (0)
               fpmWithBr   (1)"
   ::= {er1646v2ATMImaVpEntry 67305472}

er1646v2ATMImaVpPmPolicy OBJECT-TYPE
   SYNTAX      INTEGER
               {
               inband (0),
               outband (1)
               }
   MAX-ACCESS  read-write
   STATUS      current
   DESCRIPTION
      "Path: atm.editConf.vp.oamF4PM.policy

       Possibilities:
               inband   (0)
               outband   (1)"
   ::= {er1646v2ATMImaVpEntry 67371008}

er1646v2ATMImaVpPmBsizeamb OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.vp.oamF4PM.blockSizeAB

       Possibilities:
               128   (0)
               256   (1)
               512   (2)
               1024   (3)
               2048   (4)
               4096   (5)
               8192   (6)
               16384   (7)
               32768   (8)"
   ::= {er1646v2ATMImaVpEntry 67436544}

er1646v2ATMImaVpPmBsizebma OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.vp.oamF4PM.blockSizeBA

       Possibilities:
               128   (0)
               256   (1)
               512   (2)
               1024   (3)
               2048   (4)
               4096   (5)
               8192   (6)
               16384   (7)
               32768   (8)"
   ::= {er1646v2ATMImaVpEntry 67502080}

er1646v2ATMImaVpPmActProc OBJECT-TYPE
   SYNTAX      INTEGER
               {
               passive (0),
               activated (1),
               deactivated (2),
               initActivation (3)
               }
   MAX-ACCESS  read-write
   STATUS      current
   DESCRIPTION
      "Path: atm.editConf.vp.oamF4PM.actDeact.initProcedure

       Possibilities:
               passive   (0)
               activated   (1)
               deactivated   (2)
               initActivation   (3)"
   ::= {er1646v2ATMImaVpEntry 67567872}

er1646v2ATMImaVpPmActTim OBJECT-TYPE
   SYNTAX      TimeTicks
   MAX-ACCESS  read-write
   STATUS      current
   DESCRIPTION
      "Path: atm.editConf.vp.oamF4PM.actDeact.retryInterval

       Time in centi-second."
   ::= {er1646v2ATMImaVpEntry 67568128}

er1646v2ATMImaVpPmActCnt OBJECT-TYPE
   SYNTAX      Integer32
   MAX-ACCESS  read-write
   STATUS      current
   DESCRIPTION
      "Path: atm.editConf.vp.oamF4PM.actDeact.retryCount"
   ::= {er1646v2ATMImaVpEntry 67568384}

er1646v2ATMImaVpCpt OBJECT-TYPE
   SYNTAX      INTEGER
               {
               no (0),
               yes (1)
               }
   MAX-ACCESS  read-write
   STATUS      current
   DESCRIPTION
      "Path: atm.editConf.vp.segmentEndPoint

       Possibilities:
               no   (0)
               yes   (1)"
   ::= {er1646v2ATMImaVpEntry 83886080}


er1646v2ATMImaCfg OBJECT IDENTIFIER ::= {er1646v2ATMIma 1}

er1646v2ATMImaCfgSSCTable OBJECT-TYPE
   SYNTAX      SEQUENCE OF Er1646v2ATMImaCfgEntry
   MAX-ACCESS  not-accessible
   STATUS      current
   DESCRIPTION
      ""
   ::= {er1646v2ATMImaCfg 1}

er1646v2ATMImaCfgEntry OBJECT-TYPE
   SYNTAX      Er1646v2ATMImaCfgEntry
   MAX-ACCESS  not-accessible
   STATUS      current
   DESCRIPTION
      ""
   INDEX      { er1646v2ATMImaCfgTableIx }
   ::= {er1646v2ATMImaCfgSSCTable 1}

Er1646v2ATMImaCfgEntry ::=
   SEQUENCE
      {
      er1646v2ATMImaCfgActions
         VariableLengthTableActions,
      er1646v2ATMImaCfgTableIx
         TableIndex,
      er1646v2ATMImaCfgName
         DisplayString,
      er1646v2ATMImaCfgRemark
         DisplayString,
      er1646v2ATMImaCfgAdminStatus
         INTEGER,
      er1646v2ATMImaCfgMode
         INTEGER,
      er1646v2ATMImaCfgPriorityPolicy
         DisplayString,
      er1646v2ATMImaCfgDelayOptimisation
         INTEGER,
      er1646v2ATMImaCfgIpVrfRouter
         DisplayString,
      er1646v2ATMImaCfgIpAdr
         IpAddress,
      er1646v2ATMImaCfgIpNetm
         IpAddress,
      er1646v2ATMImaCfgIpSNetName
         INTEGER,
      er1646v2ATMImaCfgIpSNetCust
         DisplayString,
      er1646v2ATMImaCfgIpRem
         IpAddress,
      er1646v2ATMImaCfgIpUnnumbered
         DisplayString,
      er1646v2ATMImaCfgIpGwPref
         Integer32,
      er1646v2ATMImaCfgIpRsn
         INTEGER,
      er1646v2ATMImaCfgIpMtu
         Integer32,
      er1646v2ATMImaCfgIpMssAdjust
         INTEGER,
      er1646v2ATMImaCfgIpRipMetric
         Integer32,
      er1646v2ATMImaCfgIpRipMetricOut
         Integer32,
      er1646v2ATMImaCfgIpRipMode
         INTEGER,
      er1646v2ATMImaCfgIpRipTxVer
         INTEGER,
      er1646v2ATMImaCfgIpRipRxVer
         INTEGER,
      er1646v2ATMImaCfgIpRipSplitH
         INTEGER,
      er1646v2ATMImaCfgIpRipAuth
         INTEGER,
      er1646v2ATMImaCfgIpRipFilter
         DisplayString,
      er1646v2ATMImaCfgIpRipFilterIn
         DisplayString,
      er1646v2ATMImaCfgIpRipClearNextHop
         INTEGER,
      er1646v2ATMImaCfgIpAccPol
         DisplayString,
      er1646v2ATMImaCfgIpAB
         DisplayString,
      er1646v2ATMImaCfgIpMA
         INTEGER,
      er1646v2ATMImaCfgIpMF
         Integer32,
      er1646v2ATMImaCfgIpDB
         INTEGER,
      er1646v2ATMImaCfgIpIR
         INTEGER,
      er1646v2ATMImaCfgIpIgmp
         INTEGER,
      er1646v2ATMImaCfgIpNN
         DisplayString,
      er1646v2ATMImaCfgIpPimMode
         INTEGER,
      er1646v2ATMImaCfgIpPimDrPriority
         Counter32,
      er1646v2ATMImaCfgIpPimHelloTime
         TimeTicks,
      er1646v2ATMImaCfgIpPimPropagationDelay
         TimeTicks,
      er1646v2ATMImaCfgIpPimOverrideInterval
         TimeTicks,
      er1646v2ATMImaCfgIpPimBsrBorder
         INTEGER,
      er1646v2ATMImaCfgIpPimTtlThreshold
         Integer32,
      er1646v2ATMImaCfgIpIMNetworkUnreachable
         INTEGER,
      er1646v2ATMImaCfgIpIMHostUnreachable
         INTEGER,
      er1646v2ATMImaCfgIpIMProtocolUnreachable
         INTEGER,
      er1646v2ATMImaCfgIpIMPortUnreachable
         INTEGER,
      er1646v2ATMImaCfgIpIMMtuExceeded
         INTEGER,
      er1646v2ATMImaCfgIpIMAdminProhibited
         INTEGER,
      er1646v2ATMImaCfgIpIMTtlExceeded
         INTEGER,
      er1646v2ATMImaCfgIpIMRedirect
         INTEGER,
      er1646v2ATMImaCfgIpV6VrfRouter
         DisplayString,
      er1646v2ATMImaCfgIpV6AddrAutoConfigNrDupAddrDetects
         Integer32,
      er1646v2ATMImaCfgIpV6AddrAutoConfigAcceptRa
         INTEGER,
      er1646v2ATMImaCfgIpV6AddrAutoConfigAcceptRaRdnss
         INTEGER,
      er1646v2ATMImaCfgIpV6AddrAutoConfigAcceptRaDnssl
         INTEGER,
      er1646v2ATMImaCfgIpV6DefaultRoute
         INTEGER,
      er1646v2ATMImaCfgIpV6RaSend
         INTEGER,
      er1646v2ATMImaCfgIpV6RaMinInterval
         TimeTicks,
      er1646v2ATMImaCfgIpV6RaMaxInterval
         TimeTicks,
      er1646v2ATMImaCfgIpV6RaManagedFlag
         INTEGER,
      er1646v2ATMImaCfgIpV6RaOtherConfFlag
         INTEGER,
      er1646v2ATMImaCfgIpV6RaLinkMtu
         Integer32,
      er1646v2ATMImaCfgIpV6RaReachableTime
         TimeTicks,
      er1646v2ATMImaCfgIpV6RaRetransmitTime
         TimeTicks,
      er1646v2ATMImaCfgIpV6RaHopLimit
         Integer32,
      er1646v2ATMImaCfgIpV6RaDefaultLifeTime
         TimeTicks,
      er1646v2ATMImaCfgIpV6RaDnsOptionsRdnssLifeTime
         TimeTicks,
      er1646v2ATMImaCfgIpV6RaDnsOptionsRdnssImportServers
         INTEGER,
      er1646v2ATMImaCfgIpV6RaDnsOptionsDnsslLifeTime
         TimeTicks,
      er1646v2ATMImaCfgIpV6RaDnsOptionsDnsslImportDomains
         INTEGER,
      er1646v2ATMImaCfgIpV6RsSend
         INTEGER,
      er1646v2ATMImaCfgIpV6RsMaxRandomDelay
         TimeTicks,
      er1646v2ATMImaCfgIpV6RsInterval
         TimeTicks,
      er1646v2ATMImaCfgIpV6RsMaxSolicitations
         Integer32,
      er1646v2ATMImaCfgIpV6TrafficPolicyInbound
         DisplayString,
      er1646v2ATMImaCfgIpV6TrafficPolicyOutbound
         DisplayString,
      er1646v2ATMImaCfgIpV6FirewallZone
         DisplayString,
      er1646v2ATMImaCfgIpV6DhcpClientAddrAC
         INTEGER,
      er1646v2ATMImaCfgIpV6DhcpClientPrDelMode
         INTEGER,
      er1646v2ATMImaCfgIpV6DhcpClientPrDelPool
         DisplayString,
      er1646v2ATMImaCfgIpV6DhcpClientPrDelPdExclOpt
         INTEGER,
      er1646v2ATMImaCfgIpV6DhcpClientDnsServerPref
         Integer32,
      er1646v2ATMImaCfgIpV6DhcpClientRapidCommit
         INTEGER,
      er1646v2ATMImaCfgIpV6DhcpClientTimersSolTimeOut
         TimeTicks,
      er1646v2ATMImaCfgIpV6DhcpClientTimersSolMaxRt
         TimeTicks,
      er1646v2ATMImaCfgIpV6DhcpClientTimersInfoRefresh
         TimeTicks,
      er1646v2ATMImaCfgIpV6DhcpServerMode
         INTEGER,
      er1646v2ATMImaCfgIpV6DhcpServerPreference
         Integer32,
      er1646v2ATMImaCfgIpV6DhcpServerPool
         DisplayString,
      er1646v2ATMImaCfgIpV6DhcpServerRapidCommit
         INTEGER,
      er1646v2ATMImaCfgIpV6DhcpServerTimersInfoRefresh
         TimeTicks,
      er1646v2ATMImaCfgIpV6DhcpRelayMode
         INTEGER,
      er1646v2ATMImaCfgIpV6SendRedirect
         INTEGER,
      er1646v2ATMImaCfgIpV6LinkMtu
         Integer32,
      er1646v2ATMImaCfgIpV6InterfaceId
         OCTET STRING,
      er1646v2ATMImaCfgIpV6MF
         Integer32,
      er1646v2ATMImaCfgIpV6IcmpMessagesNoRoute
         INTEGER,
      er1646v2ATMImaCfgIpV6IcmpMessagesBeyondScope
         INTEGER,
      er1646v2ATMImaCfgIpV6IcmpMessagesAddressUnreachable
         INTEGER,
      er1646v2ATMImaCfgIpV6IcmpMessagesPortUnreachable
         INTEGER,
      er1646v2ATMImaCfgIpV6IcmpMessagesPacketTooBig
         INTEGER,
      er1646v2ATMImaCfgIpV6IcmpMessagesHopLimitExceeded
         INTEGER,
      er1646v2ATMImaCfgIpV6IcmpMessagesFragTimeExceeded
         INTEGER,
      er1646v2ATMImaCfgIpV6IcmpMessagesHeaderFieldErr
         INTEGER,
      er1646v2ATMImaCfgIpV6IcmpMessagesOptionUnrecognized
         INTEGER,
      er1646v2ATMImaCfgIpV6IcmpMessagesRedirect
         INTEGER,
      er1646v2ATMImaCfgBridgingAccList
         DisplayString,
      er1646v2ATMImaCfgBridgingInACL
         DisplayString,
      er1646v2ATMImaCfgBridgingTp
         DisplayString,
      er1646v2ATMImaCfgBridgingBrGrp
         DisplayString,
      er1646v2ATMImaCfgBridgingLimBC
         INTEGER,
      er1646v2ATMImaCfgBridgingPrivateMode
         INTEGER,
      er1646v2ATMImaCfgBridgingLearning
         INTEGER,
      er1646v2ATMImaCfgBridgingMaxCacheSize
         INTEGER,
      er1646v2ATMImaCfgBridgingRelearnDropOnRelearn
         INTEGER,
      er1646v2ATMImaCfgBridgingRelearnShutdownThreshold
         Integer32,
      er1646v2ATMImaCfgBridgingRelearnShutdownTime
         TimeTicks,
      er1646v2ATMImaCfgBridgingRelearnLoopDetection
         INTEGER,
      er1646v2ATMImaCfgBridgingRelearnLoopDetectionInterval
         TimeTicks,
      er1646v2ATMImaCfgBridgingVlanMemberShip
         INTEGER,
      er1646v2ATMImaCfgBridgingVlTUntaggedAction
         INTEGER,
      er1646v2ATMImaCfgBridgingVlTUntaggedTagInfoTpid
         INTEGER,
      er1646v2ATMImaCfgBridgingVlTUntaggedTagInfoVid
         Integer32,
      er1646v2ATMImaCfgBridgingVlTUnknownVlansAction
         INTEGER,
      er1646v2ATMImaCfgBridgingVlTUnknownVlansTagInfoTpid
         INTEGER,
      er1646v2ATMImaCfgBridgingVlTUnknownVlansTagInfoVid
         Integer32,
      er1646v2ATMImaCfgBridgingDot1adType
         INTEGER,
      er1646v2ATMImaCfgBridgingPriority
         Integer32,
      er1646v2ATMImaCfgBridgingPathCost
         Integer32,
      er1646v2ATMImaCfgBridgingInternalPathCost
         Integer32,
      er1646v2ATMImaCfgBridgingTCD
         INTEGER,
      er1646v2ATMImaCfgBridgingRestrictedRole
         INTEGER,
      er1646v2ATMImaCfgBridgingAdminEdge
         INTEGER,
      er1646v2ATMImaCfgBridgingOamMacDeviceMac
         DisplayString,
      er1646v2ATMImaCfgBridgingOamMacUserMac
         OCTET STRING,
      er1646v2ATMImaCfgBridgingOamMacBridgeMac
         DisplayString,
      er1646v2ATMImaCfgBridgingMgmtInline
         INTEGER,
      er1646v2ATMImaCfgBridgingL2ptMode
         INTEGER,
      er1646v2ATMImaCfgBridgingL2ptProtocols
         Integer32,
      er1646v2ATMImaCfgBridgingL2ptDestMac
         OCTET STRING,
      er1646v2ATMImaCfgBridgingL2ptCos
         INTEGER,
      er1646v2ATMImaCfgBridgingL2ptDropThrStp
         INTEGER,
      er1646v2ATMImaCfgBridgingL2ptDropThrLldp
         INTEGER,
      er1646v2ATMImaCfgBridgingL2ptDropThrOam
         INTEGER,
      er1646v2ATMImaCfgBridgingL2ptDropThrCdp
         INTEGER,
      er1646v2ATMImaCfgBridgingL2ptDropThrVtp
         INTEGER,
      er1646v2ATMImaCfgBridgingL2ptDropThrLacp
         INTEGER,
      er1646v2ATMImaCfgBridgingL2ptDropThrEfmOam
         INTEGER,
      er1646v2ATMImaCfgBridgingL2ptDropThrPvst
         INTEGER,
      er1646v2ATMImaCfgBridgingL2ptDropThrMmrp
         INTEGER,
      er1646v2ATMImaCfgBridgingL2ptDropThrMvrp
         INTEGER,
      er1646v2ATMImaCfgBridgingL2ptDropThrGvrp
         INTEGER,
      er1646v2ATMImaCfgBridgingL2ptDropThrGmrp
         INTEGER,
      er1646v2ATMImaCfgBridgingL2ptDropThrDtp
         INTEGER,
      er1646v2ATMImaCfgBridgingL2ptDropThrPagp
         INTEGER,
      er1646v2ATMImaCfgBridgingL2ptDropThrUdld
         INTEGER,
      er1646v2ATMImaCfgVirtEthernetVirtualEthernet
         DisplayString,
      er1646v2ATMImaCfgAtmVpi
         Integer32,
      er1646v2ATMImaCfgAtmVci
         Integer32,
      er1646v2ATMImaCfgAtmHighLayProt
         INTEGER,
      er1646v2ATMImaCfgAtmMultiProt
         INTEGER,
      er1646v2ATMImaCfgAtmServCat
         INTEGER,
      er1646v2ATMImaCfgAtmPeakCellRate
         INTEGER,
      er1646v2ATMImaCfgAtmSustCellRate
         INTEGER,
      er1646v2ATMImaCfgAtmMaxBurstSize
         Integer32,
      er1646v2ATMImaCfgAtmInArpTimeOut
         TimeTicks,
      er1646v2ATMImaCfgAtmF5LbOper
         INTEGER,
      er1646v2ATMImaCfgAtmF5LbInterval
         TimeTicks,
      er1646v2ATMImaCfgAtmF5LbFailsPerm
         Integer32,
      er1646v2ATMImaCfgAtmF5LbTar
         INTEGER,
      er1646v2ATMImaCfgAtmF5ccDir
         INTEGER,
      er1646v2ATMImaCfgAtmF5ccTar
         INTEGER,
      er1646v2ATMImaCfgAtmF5ccTxMode
         INTEGER,
      er1646v2ATMImaCfgAtmF5ccTxTxPer
         TimeTicks,
      er1646v2ATMImaCfgAtmF5ccRxRcvTim
         TimeTicks,
      er1646v2ATMImaCfgAtmF5ccActProc
         INTEGER,
      er1646v2ATMImaCfgAtmF5ccActTim
         TimeTicks,
      er1646v2ATMImaCfgAtmF5ccActCnt
         Integer32,
      er1646v2ATMImaCfgAtmF5pmDir
         INTEGER,
      er1646v2ATMImaCfgAtmF5pmTar
         INTEGER,
      er1646v2ATMImaCfgAtmF5pmType
         INTEGER,
      er1646v2ATMImaCfgAtmF5pmPolicy
         INTEGER,
      er1646v2ATMImaCfgAtmF5pmBsizeamb
         INTEGER,
      er1646v2ATMImaCfgAtmF5pmBsizebma
         INTEGER,
      er1646v2ATMImaCfgAtmF5pmActProc
         INTEGER,
      er1646v2ATMImaCfgAtmF5pmActTim
         TimeTicks,
      er1646v2ATMImaCfgAtmF5pmActCnt
         Integer32,
      er1646v2ATMImaCfgAtmCpt
         INTEGER,
      er1646v2ATMImaCfgPppLnkMOperation
         INTEGER,
      er1646v2ATMImaCfgPppLnkMInterval
         TimeTicks,
      er1646v2ATMImaCfgPppLnkMRepTimeOut
         TimeTicks,
      er1646v2ATMImaCfgPppLnkMFailsPrmt
         Integer32,
      er1646v2ATMImaCfgPppAuthentication
         INTEGER,
      er1646v2ATMImaCfgPppAuthenPeriod
         TimeTicks,
      er1646v2ATMImaCfgPppCompression
         INTEGER,
      er1646v2ATMImaCfgPppSessionName
         DisplayString,
      er1646v2ATMImaCfgPppSessionSecret
         DisplayString,
      er1646v2ATMImaCfgPppEncModeSessionSecret
         INTEGER,
      er1646v2ATMImaCfgPppEncSessionSecret
         DisplayString,
      er1646v2ATMImaCfgPppServiceName
         DisplayString,
      er1646v2ATMImaCfgFrComLmiMode
         INTEGER,
      er1646v2ATMImaCfgFrComLmiType
         INTEGER,
      er1646v2ATMImaCfgFrComLmiPollInt
         TimeTicks,
      er1646v2ATMImaCfgFrComLmiErrThres
         Integer32,
      er1646v2ATMImaCfgFrComLmiMonEvt
         Integer32,
      er1646v2ATMImaCfgFrComLmiExpPollInt
         TimeTicks,
      er1646v2ATMImaCfgFrComLmiFullEnqInt
         Integer32,
      er1646v2ATMImaCfgFrComFragIMode
         INTEGER,
      er1646v2ATMImaCfgFrComMLD
         INTEGER,
      er1646v2ATMImaCfgInbBwCir
         Integer32,
      er1646v2ATMImaCfgInbBwTc
         INTEGER,
      er1646v2ATMImaCfgInbBwCorrType
         INTEGER,
      er1646v2ATMImaCfgInbBwCorrPredefEncapsFrameRelay
         DisplayString,
      er1646v2ATMImaCfgInbBwCorrPredefEncapsPpp
         DisplayString,
      er1646v2ATMImaCfgInbBwCorrPredefEncapsAtmHl
         INTEGER,
      er1646v2ATMImaCfgInbBwCorrPredefEncapsAtmMp
         INTEGER,
      er1646v2ATMImaCfgInbBwCorrPredefEncapsHdlc
         DisplayString,
      er1646v2ATMImaCfgInbBwCorrPredefEncapsEfmFs
         Integer32,
      er1646v2ATMImaCfgInbBwCorrPredefEncapsEfmIb
         Integer32,
      er1646v2ATMImaCfgInbBwCorrPredefMode
         INTEGER,
      er1646v2ATMImaCfgInbBwCorrManualOverhead
         Integer32,
      er1646v2ATMImaCfgInbBwCorrManualFrameData
         Counter32,
      er1646v2ATMImaCfgInbBwCorrManualFrameHeader
         Counter32,
      er1646v2ATMImaCfgInbBwMaxFifoQLen
         Integer32,
      er1646v2ATMImaCfgInbBwPriorityPolicy
         DisplayString
      }

er1646v2ATMImaCfgActions OBJECT-TYPE
   SYNTAX      VariableLengthTableActions
   MAX-ACCESS  read-write
   STATUS      current
   DESCRIPTION
      "By way of this field, some manipulations
       on this table may be performed."
   ::= {er1646v2ATMImaCfgEntry 2}

er1646v2ATMImaCfgTableIx OBJECT-TYPE
   SYNTAX      TableIndex
   MAX-ACCESS  not-accessible
   STATUS      current
   DESCRIPTION
      ""
   ::= {er1646v2ATMImaCfgEntry 11}

er1646v2ATMImaCfgName OBJECT-TYPE
   SYNTAX      DisplayString
   MAX-ACCESS  read-write
   STATUS      current
   DESCRIPTION
      "Path: atm.editConf.pvcTable.name"
   ::= {er1646v2ATMImaCfgEntry 16777216}

er1646v2ATMImaCfgRemark OBJECT-TYPE
   SYNTAX      DisplayString
   MAX-ACCESS  read-write
   STATUS      current
   DESCRIPTION
      "Path: atm.editConf.pvcTable.remark"
   ::= {er1646v2ATMImaCfgEntry 1157627904}

er1646v2ATMImaCfgAdminStatus OBJECT-TYPE
   SYNTAX      INTEGER
               {
               up (1),
               down (2)
               }
   MAX-ACCESS  read-write
   STATUS      current
   DESCRIPTION
      "Path: atm.editConf.pvcTable.adminStatus

       Possibilities:
               up   (1)
               down   (2)"
   ::= {er1646v2ATMImaCfgEntry 33554432}

er1646v2ATMImaCfgMode OBJECT-TYPE
   SYNTAX      INTEGER
               {
               routing (1),
               ipV6 (16),
               ipV6ipV4 (17),
               bridging (2),
               routingAndBridging (3),
               multiLink (8),
               virtEthernet (32),
               iwf (128)
               }
   MAX-ACCESS  read-write
   STATUS      current
   DESCRIPTION
      "Path: atm.editConf.pvcTable.mode

       Possibilities:
               routing   (1)
               ipV6   (16)
               ipV6/ipV4   (17)
               bridging   (2)
               routingAndBridging   (3)
               multiLink   (8)
               virtEthernet   (32)
               iwf   (128)"
   ::= {er1646v2ATMImaCfgEntry 67108864}

er1646v2ATMImaCfgPriorityPolicy OBJECT-TYPE
   SYNTAX      DisplayString
   MAX-ACCESS  read-write
   STATUS      current
   DESCRIPTION
      "Path: atm.editConf.pvcTable.priorityPolicy"
   ::= {er1646v2ATMImaCfgEntry 83886080}

er1646v2ATMImaCfgDelayOptimisation OBJECT-TYPE
   SYNTAX      INTEGER
               {
               disabled (0),
               enabled (1)
               }
   MAX-ACCESS  read-write
   STATUS      current
   DESCRIPTION
      "Path: atm.editConf.pvcTable.delayOptimisation

       Possibilities:
               disabled   (0)
               enabled   (1)"
   ::= {er1646v2ATMImaCfgEntry 553648128}

er1646v2ATMImaCfgIpVrfRouter OBJECT-TYPE
   SYNTAX      DisplayString
   MAX-ACCESS  read-write
   STATUS      current
   DESCRIPTION
      "Path: atm.editConf.pvcTable.ip.vrfRouter"
   ::= {er1646v2ATMImaCfgEntry 53215232}

er1646v2ATMImaCfgIpAdr OBJECT-TYPE
   SYNTAX      IpAddress
   MAX-ACCESS  read-write
   STATUS      current
   DESCRIPTION
      "Path: atm.editConf.pvcTable.ip.address"
   ::= {er1646v2ATMImaCfgEntry 58261504}

er1646v2ATMImaCfgIpNetm OBJECT-TYPE
   SYNTAX      IpAddress
   MAX-ACCESS  read-write
   STATUS      current
   DESCRIPTION
      "Path: atm.editConf.pvcTable.ip.netMask"
   ::= {er1646v2ATMImaCfgEntry 58392576}

er1646v2ATMImaCfgIpSNetName OBJECT-TYPE
   SYNTAX      INTEGER
               {
               slOPTg (0),
               corp (2),
               dmz (3),
               internet (1)
               }
   MAX-ACCESS  read-write
   STATUS      current
   DESCRIPTION
      "Path: atm.editConf.pvcTable.ip.sNet.name

       Possibilities:
               <OPT>   (0)
               corp   (2)
               dmz   (3)
               internet   (1)"
   ::= {er1646v2ATMImaCfgEntry 53674240}

er1646v2ATMImaCfgIpSNetCust OBJECT-TYPE
   SYNTAX      DisplayString
   MAX-ACCESS  read-write
   STATUS      current
   DESCRIPTION
      "Path: atm.editConf.pvcTable.ip.sNet.custom"
   ::= {er1646v2ATMImaCfgEntry 53674496}

er1646v2ATMImaCfgIpRem OBJECT-TYPE
   SYNTAX      IpAddress
   MAX-ACCESS  read-write
   STATUS      current
   DESCRIPTION
      "Path: atm.editConf.pvcTable.ip.remote"
   ::= {er1646v2ATMImaCfgEntry 58458112}

er1646v2ATMImaCfgIpUnnumbered OBJECT-TYPE
   SYNTAX      DisplayString
   MAX-ACCESS  read-write
   STATUS      current
   DESCRIPTION
      "Path: atm.editConf.pvcTable.ip.unnumbered"
   ::= {er1646v2ATMImaCfgEntry 52625408}

er1646v2ATMImaCfgIpGwPref OBJECT-TYPE
   SYNTAX      Integer32
   MAX-ACCESS  read-write
   STATUS      current
   DESCRIPTION
      "Path: atm.editConf.pvcTable.ip.gatewayPreference"
   ::= {er1646v2ATMImaCfgEntry 52690944}

er1646v2ATMImaCfgIpRsn OBJECT-TYPE
   SYNTAX      INTEGER
               {
               disabled (0),
               enabled (1)
               }
   MAX-ACCESS  read-write
   STATUS      current
   DESCRIPTION
      "Path: atm.editConf.pvcTable.ip.requestSubnet

       Possibilities:
               disabled   (0)
               enabled   (1)"
   ::= {er1646v2ATMImaCfgEntry 56688640}

er1646v2ATMImaCfgIpMtu OBJECT-TYPE
   SYNTAX      Integer32
   MAX-ACCESS  read-write
   STATUS      current
   DESCRIPTION
      "Path: atm.editConf.pvcTable.ip.mtu"
   ::= {er1646v2ATMImaCfgEntry 52953088}

er1646v2ATMImaCfgIpMssAdjust OBJECT-TYPE
   SYNTAX      INTEGER
               {
               disabled (0),
               auto (65536)
               }
   MAX-ACCESS  read-write
   STATUS      current
   DESCRIPTION
      "Path: atm.editConf.pvcTable.ip.mssAdjust

       Possibilities:
               disabled   (0)
               auto   (65536)"
   ::= {er1646v2ATMImaCfgEntry 53280768}

er1646v2ATMImaCfgIpRipMetric OBJECT-TYPE
   SYNTAX      Integer32
   MAX-ACCESS  read-write
   STATUS      current
   DESCRIPTION
      "Path: atm.editConf.pvcTable.ip.rip.metric"
   ::= {er1646v2ATMImaCfgEntry 51712768}

er1646v2ATMImaCfgIpRipMetricOut OBJECT-TYPE
   SYNTAX      Integer32
   MAX-ACCESS  read-write
   STATUS      current
   DESCRIPTION
      "Path: atm.editConf.pvcTable.ip.rip.metricOut"
   ::= {er1646v2ATMImaCfgEntry 51713024}

er1646v2ATMImaCfgIpRipMode OBJECT-TYPE
   SYNTAX      INTEGER
               {
               disabled (0),
               passive (1),
               active (2)
               }
   MAX-ACCESS  read-write
   STATUS      current
   DESCRIPTION
      "Path: atm.editConf.pvcTable.ip.rip.mode

       Possibilities:
               disabled   (0)
               passive   (1)
               active   (2)"
   ::= {er1646v2ATMImaCfgEntry 51713280}

er1646v2ATMImaCfgIpRipTxVer OBJECT-TYPE
   SYNTAX      INTEGER
               {
               rip1 (0),
               rip2 (1),
               rip1mcompatible (2)
               }
   MAX-ACCESS  read-write
   STATUS      current
   DESCRIPTION
      "Path: atm.editConf.pvcTable.ip.rip.txVersion

       Possibilities:
               rip1   (0)
               rip2   (1)
               rip1-compatible   (2)"
   ::= {er1646v2ATMImaCfgEntry 51716864}

er1646v2ATMImaCfgIpRipRxVer OBJECT-TYPE
   SYNTAX      INTEGER
               {
               rip1only (0),
               rip2only (1),
               rip12 (2)
               }
   MAX-ACCESS  read-write
   STATUS      current
   DESCRIPTION
      "Path: atm.editConf.pvcTable.ip.rip.rxVersion

       Possibilities:
               rip1only   (0)
               rip2only   (1)
               rip1&2   (2)"
   ::= {er1646v2ATMImaCfgEntry 51717120}

er1646v2ATMImaCfgIpRipSplitH OBJECT-TYPE
   SYNTAX      INTEGER
               {
               disabled (0),
               enabled (1),
               poisonedReverse (2)
               }
   MAX-ACCESS  read-write
   STATUS      current
   DESCRIPTION
      "Path: atm.editConf.pvcTable.ip.rip.splitHorizon

       Possibilities:
               disabled   (0)
               enabled   (1)
               poisonedReverse   (2)"
   ::= {er1646v2ATMImaCfgEntry 51713792}

er1646v2ATMImaCfgIpRipAuth OBJECT-TYPE
   SYNTAX      INTEGER
               {
               disabled (0),
               texts (1),
               md5 (2)
               }
   MAX-ACCESS  read-write
   STATUS      current
   DESCRIPTION
      "Path: atm.editConf.pvcTable.ip.rip.authentication

       Possibilities:
               disabled   (0)
               text    (1)
               md5   (2)"
   ::= {er1646v2ATMImaCfgEntry 51712512}

er1646v2ATMImaCfgIpRipFilter OBJECT-TYPE
   SYNTAX      DisplayString
   MAX-ACCESS  read-write
   STATUS      current
   DESCRIPTION
      "Path: atm.editConf.pvcTable.ip.rip.filter"
   ::= {er1646v2ATMImaCfgEntry 51716096}

er1646v2ATMImaCfgIpRipFilterIn OBJECT-TYPE
   SYNTAX      DisplayString
   MAX-ACCESS  read-write
   STATUS      current
   DESCRIPTION
      "Path: atm.editConf.pvcTable.ip.rip.filterIn"
   ::= {er1646v2ATMImaCfgEntry 51716352}

er1646v2ATMImaCfgIpRipClearNextHop OBJECT-TYPE
   SYNTAX      INTEGER
               {
               disabled (0),
               enabled (1)
               }
   MAX-ACCESS  read-write
   STATUS      current
   DESCRIPTION
      "Path: atm.editConf.pvcTable.ip.rip.clearNextHop

       Possibilities:
               disabled   (0)
               enabled   (1)"
   ::= {er1646v2ATMImaCfgEntry 51708416}

er1646v2ATMImaCfgIpAccPol OBJECT-TYPE
   SYNTAX      DisplayString
   MAX-ACCESS  read-write
   STATUS      current
   DESCRIPTION
      "Path: atm.editConf.pvcTable.ip.accessPolicy"
   ::= {er1646v2ATMImaCfgEntry 53084160}

er1646v2ATMImaCfgIpAB OBJECT-TYPE
   SYNTAX      DisplayString
   MAX-ACCESS  read-write
   STATUS      current
   DESCRIPTION
      "Path: atm.editConf.pvcTable.ip.trafficPolicy"
   ::= {er1646v2ATMImaCfgEntry 51249152}

er1646v2ATMImaCfgIpMA OBJECT-TYPE
   SYNTAX      INTEGER
               {
               disabled (0),
               enabled (1)
               }
   MAX-ACCESS  read-write
   STATUS      current
   DESCRIPTION
      "Path: atm.editConf.pvcTable.ip.mgmtAccess

       Possibilities:
               disabled   (0)
               enabled   (1)"
   ::= {er1646v2ATMImaCfgEntry 51380224}

er1646v2ATMImaCfgIpMF OBJECT-TYPE
   SYNTAX      Integer32
   MAX-ACCESS  read-write
   STATUS      current
   DESCRIPTION
      "Path: atm.editConf.pvcTable.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2ATMImaCfgEntry 51445760}

er1646v2ATMImaCfgIpDB OBJECT-TYPE
   SYNTAX      INTEGER
               {
               disabled (0),
               enabled (1)
               }
   MAX-ACCESS  read-write
   STATUS      current
   DESCRIPTION
      "Path: atm.editConf.pvcTable.ip.directedBroadcasts

       Possibilities:
               disabled   (0)
               enabled   (1)"
   ::= {er1646v2ATMImaCfgEntry 51773440}

er1646v2ATMImaCfgIpIR OBJECT-TYPE
   SYNTAX      INTEGER
               {
               disabled (0),
               enabled (1)
               }
   MAX-ACCESS  read-write
   STATUS      current
   DESCRIPTION
      "Path: atm.editConf.pvcTable.ip.icmpRedirects

       Possibilities:
               disabled   (0)
               enabled   (1)"
   ::= {er1646v2ATMImaCfgEntry 52035584}

er1646v2ATMImaCfgIpIgmp OBJECT-TYPE
   SYNTAX      INTEGER
               {
               disabled (0),
               proxy (1),
               router (2),
               v3Router (5)
               }
   MAX-ACCESS  read-write
   STATUS      current
   DESCRIPTION
      "Path: atm.editConf.pvcTable.ip.igmp

       Possibilities:
               disabled   (0)
               proxy   (1)
               router   (2)
               v3Router   (5)"
   ::= {er1646v2ATMImaCfgEntry 52428800}

er1646v2ATMImaCfgIpNN OBJECT-TYPE
   SYNTAX      DisplayString
   MAX-ACCESS  read-write
   STATUS      current
   DESCRIPTION
      "Path: atm.editConf.pvcTable.ip.nat"
   ::= {er1646v2ATMImaCfgEntry 52101120}

er1646v2ATMImaCfgIpPimMode OBJECT-TYPE
   SYNTAX      INTEGER
               {
               disabled (0),
               sparse (1),
               passive (2)
               }
   MAX-ACCESS  read-write
   STATUS      current
   DESCRIPTION
      "Path: atm.editConf.pvcTable.ip.pim.mode

       Possibilities:
               disabled   (0)
               sparse   (1)
               passive   (2)"
   ::= {er1646v2ATMImaCfgEntry 53346560}

er1646v2ATMImaCfgIpPimDrPriority OBJECT-TYPE
   SYNTAX      Counter32
   MAX-ACCESS  read-write
   STATUS      current
   DESCRIPTION
      "Path: atm.editConf.pvcTable.ip.pim.drPriority

       32 bit unsigned wrappable counter."
   ::= {er1646v2ATMImaCfgEntry 53346816}

er1646v2ATMImaCfgIpPimHelloTime OBJECT-TYPE
   SYNTAX      TimeTicks
   MAX-ACCESS  read-write
   STATUS      current
   DESCRIPTION
      "Path: atm.editConf.pvcTable.ip.pim.helloTime

       Time in centi-second."
   ::= {er1646v2ATMImaCfgEntry 53347072}

er1646v2ATMImaCfgIpPimPropagationDelay OBJECT-TYPE
   SYNTAX      TimeTicks
   MAX-ACCESS  read-write
   STATUS      current
   DESCRIPTION
      "Path: atm.editConf.pvcTable.ip.pim.propagationDelay

       Time in centi-second."
   ::= {er1646v2ATMImaCfgEntry 53347328}

er1646v2ATMImaCfgIpPimOverrideInterval OBJECT-TYPE
   SYNTAX      TimeTicks
   MAX-ACCESS  read-write
   STATUS      current
   DESCRIPTION
      "Path: atm.editConf.pvcTable.ip.pim.overrideInterval

       Time in centi-second."
   ::= {er1646v2ATMImaCfgEntry 53347584}

er1646v2ATMImaCfgIpPimBsrBorder OBJECT-TYPE
   SYNTAX      INTEGER
               {
               disabled (0),
               enabled (1)
               }
   MAX-ACCESS  read-write
   STATUS      current
   DESCRIPTION
      "Path: atm.editConf.pvcTable.ip.pim.bsrBorder

       Possibilities:
               disabled   (0)
               enabled   (1)"
   ::= {er1646v2ATMImaCfgEntry 53347840}

er1646v2ATMImaCfgIpPimTtlThreshold OBJECT-TYPE
   SYNTAX      Integer32
   MAX-ACCESS  read-write
   STATUS      current
   DESCRIPTION
      "Path: atm.editConf.pvcTable.ip.pim.ttlThreshold"
   ::= {er1646v2ATMImaCfgEntry 53348096}

er1646v2ATMImaCfgIpIMNetworkUnreachable OBJECT-TYPE
   SYNTAX      INTEGER
               {
               disabled (0),
               enabled (1)
               }
   MAX-ACCESS  read-write
   STATUS      current
   DESCRIPTION
      "Path: atm.editConf.pvcTable.ip.icmpMessages.networkUnreachable

       Possibilities:
               disabled   (0)
               enabled   (1)"
   ::= {er1646v2ATMImaCfgEntry 53412096}

er1646v2ATMImaCfgIpIMHostUnreachable OBJECT-TYPE
   SYNTAX      INTEGER
               {
               disabled (0),
               enabled (1)
               }
   MAX-ACCESS  read-write
   STATUS      current
   DESCRIPTION
      "Path: atm.editConf.pvcTable.ip.icmpMessages.hostUnreachable

       Possibilities:
               disabled   (0)
               enabled   (1)"
   ::= {er1646v2ATMImaCfgEntry 53412352}

er1646v2ATMImaCfgIpIMProtocolUnreachable OBJECT-TYPE
   SYNTAX      INTEGER
               {
               disabled (0),
               enabled (1)
               }
   MAX-ACCESS  read-write
   STATUS      current
   DESCRIPTION
      "Path: atm.editConf.pvcTable.ip.icmpMessages.protocolUnreachable

       Possibilities:
               disabled   (0)
               enabled   (1)"
   ::= {er1646v2ATMImaCfgEntry 53412608}

er1646v2ATMImaCfgIpIMPortUnreachable OBJECT-TYPE
   SYNTAX      INTEGER
               {
               disabled (0),
               enabled (1)
               }
   MAX-ACCESS  read-write
   STATUS      current
   DESCRIPTION
      "Path: atm.editConf.pvcTable.ip.icmpMessages.portUnreachable

       Possibilities:
               disabled   (0)
               enabled   (1)"
   ::= {er1646v2ATMImaCfgEntry 53412864}

er1646v2ATMImaCfgIpIMMtuExceeded OBJECT-TYPE
   SYNTAX      INTEGER
               {
               disabled (0),
               enabled (1)
               }
   MAX-ACCESS  read-write
   STATUS      current
   DESCRIPTION
      "Path: atm.editConf.pvcTable.ip.icmpMessages.mtuExceeded

       Possibilities:
               disabled   (0)
               enabled   (1)"
   ::= {er1646v2ATMImaCfgEntry 53413120}

er1646v2ATMImaCfgIpIMAdminProhibited OBJECT-TYPE
   SYNTAX      INTEGER
               {
               disabled (0),
               enabled (1)
               }
   MAX-ACCESS  read-write
   STATUS      current
   DESCRIPTION
      "Path: atm.editConf.pvcTable.ip.icmpMessages.adminProhibited

       Possibilities:
               disabled   (0)
               enabled   (1)"
   ::= {er1646v2ATMImaCfgEntry 53413376}

er1646v2ATMImaCfgIpIMTtlExceeded OBJECT-TYPE
   SYNTAX      INTEGER
               {
               disabled (0),
               enabled (1)
               }
   MAX-ACCESS  read-write
   STATUS      current
   DESCRIPTION
      "Path: atm.editConf.pvcTable.ip.icmpMessages.ttlExceeded

       Possibilities:
               disabled   (0)
               enabled   (1)"
   ::= {er1646v2ATMImaCfgEntry 53413632}

er1646v2ATMImaCfgIpIMRedirect OBJECT-TYPE
   SYNTAX      INTEGER
               {
               disabled (0),
               enabled (1)
               }
   MAX-ACCESS  read-write
   STATUS      current
   DESCRIPTION
      "Path: atm.editConf.pvcTable.ip.icmpMessages.redirect

       Possibilities:
               disabled   (0)
               enabled   (1)"
   ::= {er1646v2ATMImaCfgEntry 53413888}

er1646v2ATMImaCfgIpV6VrfRouter OBJECT-TYPE
   SYNTAX      DisplayString
   MAX-ACCESS  read-write
   STATUS      current
   DESCRIPTION
      "Path: atm.editConf.pvcTable.ipV6.vrfRouter"
   ::= {er1646v2ATMImaCfgEntry 704708608}

er1646v2ATMImaCfgIpV6AddrAutoConfigNrDupAddrDetects OBJECT-TYPE
   SYNTAX      Integer32
   MAX-ACCESS  read-write
   STATUS      current
   DESCRIPTION
      "Path: atm.editConf.pvcTable.ipV6.addrAutoConfig.nrDupAddrDetects"
   ::= {er1646v2ATMImaCfgEntry 704905472}

er1646v2ATMImaCfgIpV6AddrAutoConfigAcceptRa OBJECT-TYPE
   SYNTAX      INTEGER
               {
               disabled (0),
               enabled (1)
               }
   MAX-ACCESS  read-write
   STATUS      current
   DESCRIPTION
      "Path: atm.editConf.pvcTable.ipV6.addrAutoConfig.acceptRa

       Possibilities:
               disabled   (0)
               enabled   (1)"
   ::= {er1646v2ATMImaCfgEntry 704905728}

er1646v2ATMImaCfgIpV6AddrAutoConfigAcceptRaRdnss OBJECT-TYPE
   SYNTAX      INTEGER
               {
               disabled (0),
               enabled (1)
               }
   MAX-ACCESS  read-write
   STATUS      current
   DESCRIPTION
      "Path: atm.editConf.pvcTable.ipV6.addrAutoConfig.acceptRaRdnss

       Possibilities:
               disabled   (0)
               enabled   (1)"
   ::= {er1646v2ATMImaCfgEntry 704905984}

er1646v2ATMImaCfgIpV6AddrAutoConfigAcceptRaDnssl OBJECT-TYPE
   SYNTAX      INTEGER
               {
               disabled (0),
               enabled (1)
               }
   MAX-ACCESS  read-write
   STATUS      current
   DESCRIPTION
      "Path: atm.editConf.pvcTable.ipV6.addrAutoConfig.acceptRaDnssl

       Possibilities:
               disabled   (0)
               enabled   (1)"
   ::= {er1646v2ATMImaCfgEntry 704906240}

er1646v2ATMImaCfgIpV6DefaultRoute OBJECT-TYPE
   SYNTAX      INTEGER
               {
               disabled (0),
               enabled (1)
               }
   MAX-ACCESS  read-write
   STATUS      current
   DESCRIPTION
      "Path: atm.editConf.pvcTable.ipV6.defaultRoute

       Possibilities:
               disabled   (0)
               enabled   (1)"
   ::= {er1646v2ATMImaCfgEntry 704970752}

er1646v2ATMImaCfgIpV6RaSend OBJECT-TYPE
   SYNTAX      INTEGER
               {
               disabled (0),
               enabled (1)
               }
   MAX-ACCESS  read-write
   STATUS      current
   DESCRIPTION
      "Path: atm.editConf.pvcTable.ipV6.ra.send

       Possibilities:
               disabled   (0)
               enabled   (1)"
   ::= {er1646v2ATMImaCfgEntry 705036544}

er1646v2ATMImaCfgIpV6RaMinInterval OBJECT-TYPE
   SYNTAX      TimeTicks
   MAX-ACCESS  read-write
   STATUS      current
   DESCRIPTION
      "Path: atm.editConf.pvcTable.ipV6.ra.minInterval

       Time in centi-second."
   ::= {er1646v2ATMImaCfgEntry 705036800}

er1646v2ATMImaCfgIpV6RaMaxInterval OBJECT-TYPE
   SYNTAX      TimeTicks
   MAX-ACCESS  read-write
   STATUS      current
   DESCRIPTION
      "Path: atm.editConf.pvcTable.ipV6.ra.maxInterval

       Time in centi-second."
   ::= {er1646v2ATMImaCfgEntry 705037056}

er1646v2ATMImaCfgIpV6RaManagedFlag OBJECT-TYPE
   SYNTAX      INTEGER
               {
               disabled (0),
               enabled (1)
               }
   MAX-ACCESS  read-write
   STATUS      current
   DESCRIPTION
      "Path: atm.editConf.pvcTable.ipV6.ra.managedFlag

       Possibilities:
               disabled   (0)
               enabled   (1)"
   ::= {er1646v2ATMImaCfgEntry 705037312}

er1646v2ATMImaCfgIpV6RaOtherConfFlag OBJECT-TYPE
   SYNTAX      INTEGER
               {
               disabled (0),
               enabled (1)
               }
   MAX-ACCESS  read-write
   STATUS      current
   DESCRIPTION
      "Path: atm.editConf.pvcTable.ipV6.ra.otherConfFlag

       Possibilities:
               disabled   (0)
               enabled   (1)"
   ::= {er1646v2ATMImaCfgEntry 705037568}

er1646v2ATMImaCfgIpV6RaLinkMtu OBJECT-TYPE
   SYNTAX      Integer32
   MAX-ACCESS  read-write
   STATUS      current
   DESCRIPTION
      "Path: atm.editConf.pvcTable.ipV6.ra.linkMtu"
   ::= {er1646v2ATMImaCfgEntry 705037824}

er1646v2ATMImaCfgIpV6RaReachableTime OBJECT-TYPE
   SYNTAX      TimeTicks
   MAX-ACCESS  read-write
   STATUS      current
   DESCRIPTION
      "Path: atm.editConf.pvcTable.ipV6.ra.reachableTime

       Time in centi-second."
   ::= {er1646v2ATMImaCfgEntry 705038080}

er1646v2ATMImaCfgIpV6RaRetransmitTime OBJECT-TYPE
   SYNTAX      TimeTicks
   MAX-ACCESS  read-write
   STATUS      current
   DESCRIPTION
      "Path: atm.editConf.pvcTable.ipV6.ra.retransmitTime

       Time in centi-second."
   ::= {er1646v2ATMImaCfgEntry 705038336}

er1646v2ATMImaCfgIpV6RaHopLimit OBJECT-TYPE
   SYNTAX      Integer32
   MAX-ACCESS  read-write
   STATUS      current
   DESCRIPTION
      "Path: atm.editConf.pvcTable.ipV6.ra.hopLimit"
   ::= {er1646v2ATMImaCfgEntry 705038592}

er1646v2ATMImaCfgIpV6RaDefaultLifeTime OBJECT-TYPE
   SYNTAX      TimeTicks
   MAX-ACCESS  read-write
   STATUS      current
   DESCRIPTION
      "Path: atm.editConf.pvcTable.ipV6.ra.defaultLifeTime

       Time in centi-second."
   ::= {er1646v2ATMImaCfgEntry 705038848}

er1646v2ATMImaCfgIpV6RaDnsOptionsRdnssLifeTime OBJECT-TYPE
   SYNTAX      TimeTicks
   MAX-ACCESS  read-write
   STATUS      current
   DESCRIPTION
      "Path: atm.editConf.pvcTable.ipV6.ra.dnsOptions.rdnss.lifeTime

       Time in centi-second."
   ::= {er1646v2ATMImaCfgEntry 705039140}

er1646v2ATMImaCfgIpV6RaDnsOptionsRdnssImportServers OBJECT-TYPE
   SYNTAX      INTEGER
               {
               disabled (0),
               enabled (1)
               }
   MAX-ACCESS  read-write
   STATUS      current
   DESCRIPTION
      "Path: atm.editConf.pvcTable.ipV6.ra.dnsOptions.rdnss.importServers

       Possibilities:
               disabled   (0)
               enabled   (1)"
   ::= {er1646v2ATMImaCfgEntry 705039148}

er1646v2ATMImaCfgIpV6RaDnsOptionsDnsslLifeTime OBJECT-TYPE
   SYNTAX      TimeTicks
   MAX-ACCESS  read-write
   STATUS      current
   DESCRIPTION
      "Path: atm.editConf.pvcTable.ipV6.ra.dnsOptions.dnssl.lifeTime

       Time in centi-second."
   ::= {er1646v2ATMImaCfgEntry 705039172}

er1646v2ATMImaCfgIpV6RaDnsOptionsDnsslImportDomains OBJECT-TYPE
   SYNTAX      INTEGER
               {
               disabled (0),
               enabled (1)
               }
   MAX-ACCESS  read-write
   STATUS      current
   DESCRIPTION
      "Path: atm.editConf.pvcTable.ipV6.ra.dnsOptions.dnssl.importDomains

       Possibilities:
               disabled   (0)
               enabled   (1)"
   ::= {er1646v2ATMImaCfgEntry 705039180}

er1646v2ATMImaCfgIpV6RsSend OBJECT-TYPE
   SYNTAX      INTEGER
               {
               disabled (0),
               enabled (1)
               }
   MAX-ACCESS  read-write
   STATUS      current
   DESCRIPTION
      "Path: atm.editConf.pvcTable.ipV6.rs.send

       Possibilities:
               disabled   (0)
               enabled   (1)"
   ::= {er1646v2ATMImaCfgEntry 705954048}

er1646v2ATMImaCfgIpV6RsMaxRandomDelay OBJECT-TYPE
   SYNTAX      TimeTicks
   MAX-ACCESS  read-write
   STATUS      current
   DESCRIPTION
      "Path: atm.editConf.pvcTable.ipV6.rs.maxRandomDelay

       Time in centi-second."
   ::= {er1646v2ATMImaCfgEntry 705954304}

er1646v2ATMImaCfgIpV6RsInterval OBJECT-TYPE
   SYNTAX      TimeTicks
   MAX-ACCESS  read-write
   STATUS      current
   DESCRIPTION
      "Path: atm.editConf.pvcTable.ipV6.rs.interval

       Time in centi-second."
   ::= {er1646v2ATMImaCfgEntry 705954560}

er1646v2ATMImaCfgIpV6RsMaxSolicitations OBJECT-TYPE
   SYNTAX      Integer32
   MAX-ACCESS  read-write
   STATUS      current
   DESCRIPTION
      "Path: atm.editConf.pvcTable.ipV6.rs.maxSolicitations"
   ::= {er1646v2ATMImaCfgEntry 705954816}

er1646v2ATMImaCfgIpV6TrafficPolicyInbound OBJECT-TYPE
   SYNTAX      DisplayString
   MAX-ACCESS  read-write
   STATUS      current
   DESCRIPTION
      "Path: atm.editConf.pvcTable.ipV6.trafficPolicy.inbound"
   ::= {er1646v2ATMImaCfgEntry 705364224}

er1646v2ATMImaCfgIpV6TrafficPolicyOutbound OBJECT-TYPE
   SYNTAX      DisplayString
   MAX-ACCESS  read-write
   STATUS      current
   DESCRIPTION
      "Path: atm.editConf.pvcTable.ipV6.trafficPolicy.outbound"
   ::= {er1646v2ATMImaCfgEntry 705364480}

er1646v2ATMImaCfgIpV6FirewallZone OBJECT-TYPE
   SYNTAX      DisplayString
   MAX-ACCESS  read-write
   STATUS      current
   DESCRIPTION
      "Path: atm.editConf.pvcTable.ipV6.firewall.zone"
   ::= {er1646v2ATMImaCfgEntry 705429760}

er1646v2ATMImaCfgIpV6DhcpClientAddrAC OBJECT-TYPE
   SYNTAX      INTEGER
               {
               disabled (0),
               enabled (1)
               }
   MAX-ACCESS  read-write
   STATUS      current
   DESCRIPTION
      "Path: atm.editConf.pvcTable.ipV6.dhcp.client.addrAutoConfig

       Possibilities:
               disabled   (0)
               enabled   (1)"
   ::= {er1646v2ATMImaCfgEntry 705307648}

er1646v2ATMImaCfgIpV6DhcpClientPrDelMode OBJECT-TYPE
   SYNTAX      INTEGER
               {
               disabled (0),
               enabled (1)
               }
   MAX-ACCESS  read-write
   STATUS      current
   DESCRIPTION
      "Path: atm.editConf.pvcTable.ipV6.dhcp.client.pd.mode

       Possibilities:
               disabled   (0)
               enabled   (1)"
   ::= {er1646v2ATMImaCfgEntry 705308676}

er1646v2ATMImaCfgIpV6DhcpClientPrDelPool OBJECT-TYPE
   SYNTAX      DisplayString
   MAX-ACCESS  read-write
   STATUS      current
   DESCRIPTION
      "Path: atm.editConf.pvcTable.ipV6.dhcp.client.pd.pool"
   ::= {er1646v2ATMImaCfgEntry 705308680}

er1646v2ATMImaCfgIpV6DhcpClientPrDelPdExclOpt OBJECT-TYPE
   SYNTAX      INTEGER
               {
               disabled (0),
               enabled (1)
               }
   MAX-ACCESS  read-write
   STATUS      current
   DESCRIPTION
      "Path: atm.editConf.pvcTable.ipV6.dhcp.client.pd.pdExclOpt

       Possibilities:
               disabled   (0)
               enabled   (1)"
   ::= {er1646v2ATMImaCfgEntry 705308684}

er1646v2ATMImaCfgIpV6DhcpClientDnsServerPref OBJECT-TYPE
   SYNTAX      Integer32
   MAX-ACCESS  read-write
   STATUS      current
   DESCRIPTION
      "Path: atm.editConf.pvcTable.ipV6.dhcp.client.dns.serverPref"
   ::= {er1646v2ATMImaCfgEntry 705310724}

er1646v2ATMImaCfgIpV6DhcpClientRapidCommit OBJECT-TYPE
   SYNTAX      INTEGER
               {
               disabled (0),
               enabled (1)
               }
   MAX-ACCESS  read-write
   STATUS      current
   DESCRIPTION
      "Path: atm.editConf.pvcTable.ipV6.dhcp.client.rapidCommit

       Possibilities:
               disabled   (0)
               enabled   (1)"
   ::= {er1646v2ATMImaCfgEntry 705309696}

er1646v2ATMImaCfgIpV6DhcpClientTimersSolTimeOut OBJECT-TYPE
   SYNTAX      TimeTicks
   MAX-ACCESS  read-write
   STATUS      current
   DESCRIPTION
      "Path: atm.editConf.pvcTable.ipV6.dhcp.client.timers.solTimeOut

       Time in centi-second."
   ::= {er1646v2ATMImaCfgEntry 705311748}

er1646v2ATMImaCfgIpV6DhcpClientTimersSolMaxRt OBJECT-TYPE
   SYNTAX      TimeTicks
   MAX-ACCESS  read-write
   STATUS      current
   DESCRIPTION
      "Path: atm.editConf.pvcTable.ipV6.dhcp.client.timers.solMaxRt

       Time in centi-second."
   ::= {er1646v2ATMImaCfgEntry 705311752}

er1646v2ATMImaCfgIpV6DhcpClientTimersInfoRefresh OBJECT-TYPE
   SYNTAX      TimeTicks
   MAX-ACCESS  read-write
   STATUS      current
   DESCRIPTION
      "Path: atm.editConf.pvcTable.ipV6.dhcp.client.timers.infoRefresh

       Time in centi-second."
   ::= {er1646v2ATMImaCfgEntry 705311756}

er1646v2ATMImaCfgIpV6DhcpServerMode OBJECT-TYPE
   SYNTAX      INTEGER
               {
               disabled (0),
               enabled (1)
               }
   MAX-ACCESS  read-write
   STATUS      current
   DESCRIPTION
      "Path: atm.editConf.pvcTable.ipV6.dhcp.server.mode

       Possibilities:
               disabled   (0)
               enabled   (1)"
   ::= {er1646v2ATMImaCfgEntry 705315840}

er1646v2ATMImaCfgIpV6DhcpServerPreference OBJECT-TYPE
   SYNTAX      Integer32
   MAX-ACCESS  read-write
   STATUS      current
   DESCRIPTION
      "Path: atm.editConf.pvcTable.ipV6.dhcp.server.preference"
   ::= {er1646v2ATMImaCfgEntry 705316864}

er1646v2ATMImaCfgIpV6DhcpServerPool OBJECT-TYPE
   SYNTAX      DisplayString
   MAX-ACCESS  read-write
   STATUS      current
   DESCRIPTION
      "Path: atm.editConf.pvcTable.ipV6.dhcp.server.pool"
   ::= {er1646v2ATMImaCfgEntry 705317888}

er1646v2ATMImaCfgIpV6DhcpServerRapidCommit OBJECT-TYPE
   SYNTAX      INTEGER
               {
               disabled (0),
               enabled (1)
               }
   MAX-ACCESS  read-write
   STATUS      current
   DESCRIPTION
      "Path: atm.editConf.pvcTable.ipV6.dhcp.server.rapidCommit

       Possibilities:
               disabled   (0)
               enabled   (1)"
   ::= {er1646v2ATMImaCfgEntry 705318912}

er1646v2ATMImaCfgIpV6DhcpServerTimersInfoRefresh OBJECT-TYPE
   SYNTAX      TimeTicks
   MAX-ACCESS  read-write
   STATUS      current
   DESCRIPTION
      "Path: atm.editConf.pvcTable.ipV6.dhcp.server.timers.infoRefresh

       Time in centi-second."
   ::= {er1646v2ATMImaCfgEntry 705319940}

er1646v2ATMImaCfgIpV6DhcpRelayMode OBJECT-TYPE
   SYNTAX      INTEGER
               {
               disabled (0),
               enabled (1)
               }
   MAX-ACCESS  read-write
   STATUS      current
   DESCRIPTION
      "Path: atm.editConf.pvcTable.ipV6.dhcp.relay.mode

       Possibilities:
               disabled   (0)
               enabled   (1)"
   ::= {er1646v2ATMImaCfgEntry 705323040}

er1646v2ATMImaCfgIpV6SendRedirect OBJECT-TYPE
   SYNTAX      INTEGER
               {
               disabled (0),
               enabled (1)
               }
   MAX-ACCESS  read-write
   STATUS      current
   DESCRIPTION
      "Path: atm.editConf.pvcTable.ipV6.sendRedirect

       Possibilities:
               disabled   (0)
               enabled   (1)"
   ::= {er1646v2ATMImaCfgEntry 705101824}

er1646v2ATMImaCfgIpV6LinkMtu OBJECT-TYPE
   SYNTAX      Integer32
   MAX-ACCESS  read-write
   STATUS      current
   DESCRIPTION
      "Path: atm.editConf.pvcTable.ipV6.linkMtu"
   ::= {er1646v2ATMImaCfgEntry 705167360}

er1646v2ATMImaCfgIpV6InterfaceId OBJECT-TYPE
   SYNTAX      OCTET STRING
   MAX-ACCESS  read-write
   STATUS      current
   DESCRIPTION
      "Path: atm.editConf.pvcTable.ipV6.interfaceId"
   ::= {er1646v2ATMImaCfgEntry 705232896}

er1646v2ATMImaCfgIpV6MF OBJECT-TYPE
   SYNTAX      Integer32
   MAX-ACCESS  read-write
   STATUS      current
   DESCRIPTION
      "Path: atm.editConf.pvcTable.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2ATMImaCfgEntry 705757184}

er1646v2ATMImaCfgIpV6IcmpMessagesNoRoute OBJECT-TYPE
   SYNTAX      INTEGER
               {
               disabled (0),
               enabled (1)
               }
   MAX-ACCESS  read-write
   STATUS      current
   DESCRIPTION
      "Path: atm.editConf.pvcTable.ipV6.icmpMessages.noRoute

       Possibilities:
               disabled   (0)
               enabled   (1)"
   ::= {er1646v2ATMImaCfgEntry 705822976}

er1646v2ATMImaCfgIpV6IcmpMessagesBeyondScope OBJECT-TYPE
   SYNTAX      INTEGER
               {
               disabled (0),
               enabled (1)
               }
   MAX-ACCESS  read-write
   STATUS      current
   DESCRIPTION
      "Path: atm.editConf.pvcTable.ipV6.icmpMessages.beyondScope

       Possibilities:
               disabled   (0)
               enabled   (1)"
   ::= {er1646v2ATMImaCfgEntry 705823488}

er1646v2ATMImaCfgIpV6IcmpMessagesAddressUnreachable OBJECT-TYPE
   SYNTAX      INTEGER
               {
               disabled (0),
               enabled (1)
               }
   MAX-ACCESS  read-write
   STATUS      current
   DESCRIPTION
      "Path: atm.editConf.pvcTable.ipV6.icmpMessages.addressUnreachable

       Possibilities:
               disabled   (0)
               enabled   (1)"
   ::= {er1646v2ATMImaCfgEntry 705823744}

er1646v2ATMImaCfgIpV6IcmpMessagesPortUnreachable OBJECT-TYPE
   SYNTAX      INTEGER
               {
               disabled (0),
               enabled (1)
               }
   MAX-ACCESS  read-write
   STATUS      current
   DESCRIPTION
      "Path: atm.editConf.pvcTable.ipV6.icmpMessages.portUnreachable

       Possibilities:
               disabled   (0)
               enabled   (1)"
   ::= {er1646v2ATMImaCfgEntry 705824000}

er1646v2ATMImaCfgIpV6IcmpMessagesPacketTooBig OBJECT-TYPE
   SYNTAX      INTEGER
               {
               disabled (0),
               enabled (1)
               }
   MAX-ACCESS  read-write
   STATUS      current
   DESCRIPTION
      "Path: atm.editConf.pvcTable.ipV6.icmpMessages.packetTooBig

       Possibilities:
               disabled   (0)
               enabled   (1)"
   ::= {er1646v2ATMImaCfgEntry 705825280}

er1646v2ATMImaCfgIpV6IcmpMessagesHopLimitExceeded OBJECT-TYPE
   SYNTAX      INTEGER
               {
               disabled (0),
               enabled (1)
               }
   MAX-ACCESS  read-write
   STATUS      current
   DESCRIPTION
      "Path: atm.editConf.pvcTable.ipV6.icmpMessages.hopLimitExceeded

       Possibilities:
               disabled   (0)
               enabled   (1)"
   ::= {er1646v2ATMImaCfgEntry 705827840}

er1646v2ATMImaCfgIpV6IcmpMessagesFragTimeExceeded OBJECT-TYPE
   SYNTAX      INTEGER
               {
               disabled (0),
               enabled (1)
               }
   MAX-ACCESS  read-write
   STATUS      current
   DESCRIPTION
      "Path: atm.editConf.pvcTable.ipV6.icmpMessages.fragTimeExceeded

       Possibilities:
               disabled   (0)
               enabled   (1)"
   ::= {er1646v2ATMImaCfgEntry 705828096}

er1646v2ATMImaCfgIpV6IcmpMessagesHeaderFieldErr OBJECT-TYPE
   SYNTAX      INTEGER
               {
               disabled (0),
               enabled (1)
               }
   MAX-ACCESS  read-write
   STATUS      current
   DESCRIPTION
      "Path: atm.editConf.pvcTable.ipV6.icmpMessages.headerFieldErr

       Possibilities:
               disabled   (0)
               enabled   (1)"
   ::= {er1646v2ATMImaCfgEntry 705830400}

er1646v2ATMImaCfgIpV6IcmpMessagesOptionUnrecognized OBJECT-TYPE
   SYNTAX      INTEGER
               {
               disabled (0),
               enabled (1)
               }
   MAX-ACCESS  read-write
   STATUS      current
   DESCRIPTION
      "Path: atm.editConf.pvcTable.ipV6.icmpMessages.optionUnrecognized

       Possibilities:
               disabled   (0)
               enabled   (1)"
   ::= {er1646v2ATMImaCfgEntry 705830912}

er1646v2ATMImaCfgIpV6IcmpMessagesRedirect OBJECT-TYPE
   SYNTAX      INTEGER
               {
               disabled (0),
               enabled (1)
               }
   MAX-ACCESS  read-write
   STATUS      current
   DESCRIPTION
      "Path: atm.editConf.pvcTable.ipV6.icmpMessages.redirect

       Possibilities:
               disabled   (0)
               enabled   (1)"
   ::= {er1646v2ATMImaCfgEntry 705832960}

er1646v2ATMImaCfgBridgingAccList OBJECT-TYPE
   SYNTAX      DisplayString
   MAX-ACCESS  read-write
   STATUS      current
   DESCRIPTION
      "Path: atm.editConf.pvcTable.bridging.accessList"
   ::= {er1646v2ATMImaCfgEntry 453246976}

er1646v2ATMImaCfgBridgingInACL OBJECT-TYPE
   SYNTAX      DisplayString
   MAX-ACCESS  read-write
   STATUS      current
   DESCRIPTION
      "Path: atm.editConf.pvcTable.bridging.inAccessList"
   ::= {er1646v2ATMImaCfgEntry 456916992}

er1646v2ATMImaCfgBridgingTp OBJECT-TYPE
   SYNTAX      DisplayString
   MAX-ACCESS  read-write
   STATUS      current
   DESCRIPTION
      "Path: atm.editConf.pvcTable.bridging.trafficPolicy"
   ::= {er1646v2ATMImaCfgEntry 454295552}

er1646v2ATMImaCfgBridgingBrGrp OBJECT-TYPE
   SYNTAX      DisplayString
   MAX-ACCESS  read-write
   STATUS      current
   DESCRIPTION
      "Path: atm.editConf.pvcTable.bridging.bridgeGroup"
   ::= {er1646v2ATMImaCfgEntry 454819840}

er1646v2ATMImaCfgBridgingLimBC OBJECT-TYPE
   SYNTAX      INTEGER
               {
               disabled (0),
               enabled (1)
               }
   MAX-ACCESS  read-write
   STATUS      current
   DESCRIPTION
      "Path: atm.editConf.pvcTable.bridging.limitBroadcasts

       Possibilities:
               disabled   (0)
               enabled   (1)"
   ::= {er1646v2ATMImaCfgEntry 455081984}

er1646v2ATMImaCfgBridgingPrivateMode OBJECT-TYPE
   SYNTAX      INTEGER
               {
               disabled (0),
               enabled (1)
               }
   MAX-ACCESS  read-write
   STATUS      current
   DESCRIPTION
      "Path: atm.editConf.pvcTable.bridging.privateMode

       Possibilities:
               disabled   (0)
               enabled   (1)"
   ::= {er1646v2ATMImaCfgEntry 459538432}

er1646v2ATMImaCfgBridgingLearning OBJECT-TYPE
   SYNTAX      INTEGER
               {
               disabled (0),
               enabled (1)
               }
   MAX-ACCESS  read-write
   STATUS      current
   DESCRIPTION
      "Path: atm.editConf.pvcTable.bridging.learning

       Possibilities:
               disabled   (0)
               enabled   (1)"
   ::= {er1646v2ATMImaCfgEntry 456130560}

er1646v2ATMImaCfgBridgingMaxCacheSize OBJECT-TYPE
   SYNTAX      INTEGER
               {
               unlimited (0)
               }
   MAX-ACCESS  read-write
   STATUS      current
   DESCRIPTION
      "Path: atm.editConf.pvcTable.bridging.maxCacheSize

       Possibilities:
               unlimited   (0)"
   ::= {er1646v2ATMImaCfgEntry 456392704}

er1646v2ATMImaCfgBridgingRelearnDropOnRelearn OBJECT-TYPE
   SYNTAX      INTEGER
               {
               disabled (0),
               enabled (1)
               }
   MAX-ACCESS  read-write
   STATUS      current
   DESCRIPTION
      "Path: atm.editConf.pvcTable.bridging.relearn.dropOnRelearn

       Possibilities:
               disabled   (0)
               enabled   (1)"
   ::= {er1646v2ATMImaCfgEntry 456655872}

er1646v2ATMImaCfgBridgingRelearnShutdownThreshold OBJECT-TYPE
   SYNTAX      Integer32
   MAX-ACCESS  read-write
   STATUS      current
   DESCRIPTION
      "Path: atm.editConf.pvcTable.bridging.relearn.shutdownThreshold"
   ::= {er1646v2ATMImaCfgEntry 456656896}

er1646v2ATMImaCfgBridgingRelearnShutdownTime OBJECT-TYPE
   SYNTAX      TimeTicks
   MAX-ACCESS  read-write
   STATUS      current
   DESCRIPTION
      "Path: atm.editConf.pvcTable.bridging.relearn.shutdownTime

       Time in centi-second."
   ::= {er1646v2ATMImaCfgEntry 456657920}

er1646v2ATMImaCfgBridgingRelearnLoopDetection OBJECT-TYPE
   SYNTAX      INTEGER
               {
               disabled (0),
               passive (1),
               active (2)
               }
   MAX-ACCESS  read-write
   STATUS      current
   DESCRIPTION
      "Path: atm.editConf.pvcTable.bridging.relearn.loopDetection

       Possibilities:
               disabled   (0)
               passive   (1)
               active   (2)"
   ::= {er1646v2ATMImaCfgEntry 456658944}

er1646v2ATMImaCfgBridgingRelearnLoopDetectionInterval OBJECT-TYPE
   SYNTAX      TimeTicks
   MAX-ACCESS  read-write
   STATUS      current
   DESCRIPTION
      "Path: atm.editConf.pvcTable.bridging.relearn.loopDetectionInterval

       Time in centi-second."
   ::= {er1646v2ATMImaCfgEntry 456659968}

er1646v2ATMImaCfgBridgingVlanMemberShip OBJECT-TYPE
   SYNTAX      INTEGER
               {
               all (0),
               none (1),
               grouped (2)
               }
   MAX-ACCESS  read-write
   STATUS      current
   DESCRIPTION
      "Path: atm.editConf.pvcTable.bridging.vlanMemberShip

       Possibilities:
               all   (0)
               none   (1)
               grouped   (2)"
   ::= {er1646v2ATMImaCfgEntry 457965568}

er1646v2ATMImaCfgBridgingVlTUntaggedAction OBJECT-TYPE
   SYNTAX      INTEGER
               {
               discard (0),
               accept (1),
               tag (2)
               }
   MAX-ACCESS  read-write
   STATUS      current
   DESCRIPTION
      "Path: atm.editConf.pvcTable.bridging.vlanTagging.untagged.action

       Possibilities:
               discard   (0)
               accept   (1)
               tag   (2)"
   ::= {er1646v2ATMImaCfgEntry 459055104}

er1646v2ATMImaCfgBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.untagged.tagInfo.tpid

       Possibilities:
               dot1Q   (33024)
               dot1ad   (34984)
               0x9100   (37120)
               0x9200   (37376)
               0x9300   (37632)"
   ::= {er1646v2ATMImaCfgEntry 459059712}

er1646v2ATMImaCfgBridgingVlTUntaggedTagInfoVid OBJECT-TYPE
   SYNTAX      Integer32
   MAX-ACCESS  read-write
   STATUS      current
   DESCRIPTION
      "Path: atm.editConf.pvcTable.bridging.vlanTagging.untagged.tagInfo.vid"
   ::= {er1646v2ATMImaCfgEntry 459060224}

er1646v2ATMImaCfgBridgingVlTUnknownVlansAction OBJECT-TYPE
   SYNTAX      INTEGER
               {
               discard (0),
               accept (1),
               tag (2)
               }
   MAX-ACCESS  read-write
   STATUS      current
   DESCRIPTION
      "Path: atm.editConf.pvcTable.bridging.vlanTagging.unknownVlans.action

       Possibilities:
               discard   (0)
               accept   (1)
               tag   (2)"
   ::= {er1646v2ATMImaCfgEntry 459120640}

er1646v2ATMImaCfgBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.unknownVlans.tagInfo.tpid

       Possibilities:
               dot1Q   (33024)
               dot1ad   (34984)
               0x9100   (37120)
               0x9200   (37376)
               0x9300   (37632)"
   ::= {er1646v2ATMImaCfgEntry 459125248}

er1646v2ATMImaCfgBridgingVlTUnknownVlansTagInfoVid OBJECT-TYPE
   SYNTAX      Integer32
   MAX-ACCESS  read-write
   STATUS      current
   DESCRIPTION
      "Path: atm.editConf.pvcTable.bridging.vlanTagging.unknownVlans.tagInfo.vid"
   ::= {er1646v2ATMImaCfgEntry 459125760}

er1646v2ATMImaCfgBridgingDot1adType OBJECT-TYPE
   SYNTAX      INTEGER
               {
               slOPTg (0),
               cPort (4),
               sPort (1),
               nni (2)
               }
   MAX-ACCESS  read-write
   STATUS      current
   DESCRIPTION
      "Path: atm.editConf.pvcTable.bridging.dot1ad.type

       Possibilities:
               <OPT>   (0)
               cPort   (4)
               sPort   (1)
               nni   (2)"
   ::= {er1646v2ATMImaCfgEntry 460850176}

er1646v2ATMImaCfgBridgingPriority OBJECT-TYPE
   SYNTAX      Integer32
   MAX-ACCESS  read-write
   STATUS      current
   DESCRIPTION
      "Path: atm.editConf.pvcTable.bridging.priority"
   ::= {er1646v2ATMImaCfgEntry 453509120}

er1646v2ATMImaCfgBridgingPathCost OBJECT-TYPE
   SYNTAX      Integer32
   MAX-ACCESS  read-write
   STATUS      current
   DESCRIPTION
      "Path: atm.editConf.pvcTable.bridging.pathCost"
   ::= {er1646v2ATMImaCfgEntry 453771264}

er1646v2ATMImaCfgBridgingInternalPathCost OBJECT-TYPE
   SYNTAX      Integer32
   MAX-ACCESS  read-write
   STATUS      current
   DESCRIPTION
      "Path: atm.editConf.pvcTable.bridging.internalPathCost"
   ::= {er1646v2ATMImaCfgEntry 457703424}

er1646v2ATMImaCfgBridgingTCD OBJECT-TYPE
   SYNTAX      INTEGER
               {
               disabled (0),
               enabled (1)
               }
   MAX-ACCESS  read-write
   STATUS      current
   DESCRIPTION
      "Path: atm.editConf.pvcTable.bridging.topologyChangeDetection

       Possibilities:
               disabled   (0)
               enabled   (1)"
   ::= {er1646v2ATMImaCfgEntry 454033408}

er1646v2ATMImaCfgBridgingRestrictedRole OBJECT-TYPE
   SYNTAX      INTEGER
               {
               disabled (0),
               enabled (1)
               }
   MAX-ACCESS  read-write
   STATUS      current
   DESCRIPTION
      "Path: atm.editConf.pvcTable.bridging.restrictedRole

       Possibilities:
               disabled   (0)
               enabled   (1)"
   ::= {er1646v2ATMImaCfgEntry 458227712}

er1646v2ATMImaCfgBridgingAdminEdge OBJECT-TYPE
   SYNTAX      INTEGER
               {
               disabled (0),
               enabled (1)
               }
   MAX-ACCESS  read-write
   STATUS      current
   DESCRIPTION
      "Path: atm.editConf.pvcTable.bridging.adminEdge

       Possibilities:
               disabled   (0)
               enabled   (1)"
   ::= {er1646v2ATMImaCfgEntry 457179136}

er1646v2ATMImaCfgBridgingOamMacDeviceMac OBJECT-TYPE
   SYNTAX      DisplayString
   MAX-ACCESS  read-write
   STATUS      current
   DESCRIPTION
      "Path: atm.editConf.pvcTable.bridging.ethOam.macAddress.deviceMac"
   ::= {er1646v2ATMImaCfgEntry 458506496}

er1646v2ATMImaCfgBridgingOamMacUserMac OBJECT-TYPE
   SYNTAX      OCTET STRING
   MAX-ACCESS  read-write
   STATUS      current
   DESCRIPTION
      "Path: atm.editConf.pvcTable.bridging.ethOam.macAddress.userMac

       MAC address."
   ::= {er1646v2ATMImaCfgEntry 458506368}

er1646v2ATMImaCfgBridgingOamMacBridgeMac OBJECT-TYPE
   SYNTAX      DisplayString
   MAX-ACCESS  read-write
   STATUS      current
   DESCRIPTION
      "Path: atm.editConf.pvcTable.bridging.ethOam.macAddress.bridgeMac"
   ::= {er1646v2ATMImaCfgEntry 458506432}

er1646v2ATMImaCfgBridgingMgmtInline OBJECT-TYPE
   SYNTAX      INTEGER
               {
               disabled (0),
               enabled (1)
               }
   MAX-ACCESS  read-write
   STATUS      current
   DESCRIPTION
      "Path: atm.editConf.pvcTable.bridging.mgmtInline

       Possibilities:
               disabled   (0)
               enabled   (1)"
   ::= {er1646v2ATMImaCfgEntry 458752000}

er1646v2ATMImaCfgBridgingL2ptMode OBJECT-TYPE
   SYNTAX      INTEGER
               {
               disabled (0),
               enabled (1)
               }
   MAX-ACCESS  read-write
   STATUS      current
   DESCRIPTION
      "Path: atm.editConf.pvcTable.bridging.l2ProtTunnel.mode

       Possibilities:
               disabled   (0)
               enabled   (1)"
   ::= {er1646v2ATMImaCfgEntry 459292672}

er1646v2ATMImaCfgBridgingL2ptProtocols OBJECT-TYPE
   SYNTAX      Integer32
   MAX-ACCESS  read-write
   STATUS      current
   DESCRIPTION
      "Path: atm.editConf.pvcTable.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2ATMImaCfgEntry 459309056}

er1646v2ATMImaCfgBridgingL2ptDestMac OBJECT-TYPE
   SYNTAX      OCTET STRING
   MAX-ACCESS  read-write
   STATUS      current
   DESCRIPTION
      "Path: atm.editConf.pvcTable.bridging.l2ProtTunnel.destinationMac

       MAC address."
   ::= {er1646v2ATMImaCfgEntry 459325440}

er1646v2ATMImaCfgBridgingL2ptCos OBJECT-TYPE
   SYNTAX      INTEGER
               {
               unchanged (255)
               }
   MAX-ACCESS  read-write
   STATUS      current
   DESCRIPTION
      "Path: atm.editConf.pvcTable.bridging.l2ProtTunnel.cos

       Possibilities:
               unchanged   (255)"
   ::= {er1646v2ATMImaCfgEntry 459341824}

er1646v2ATMImaCfgBridgingL2ptDropThrStp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.stp

       unit name = packets/sec

       Possibilities:
               unlimited   (0)"
   ::= {er1646v2ATMImaCfgEntry 459358272}

er1646v2ATMImaCfgBridgingL2ptDropThrLldp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.lldp

       unit name = packets/sec

       Possibilities:
               unlimited   (0)"
   ::= {er1646v2ATMImaCfgEntry 459358336}

er1646v2ATMImaCfgBridgingL2ptDropThrOam OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.oam

       unit name = packets/sec

       Possibilities:
               unlimited   (0)"
   ::= {er1646v2ATMImaCfgEntry 459358400}

er1646v2ATMImaCfgBridgingL2ptDropThrCdp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.cdp

       unit name = packets/sec

       Possibilities:
               unlimited   (0)"
   ::= {er1646v2ATMImaCfgEntry 459358464}

er1646v2ATMImaCfgBridgingL2ptDropThrVtp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.vtp

       unit name = packets/sec

       Possibilities:
               unlimited   (0)"
   ::= {er1646v2ATMImaCfgEntry 459358528}

er1646v2ATMImaCfgBridgingL2ptDropThrLacp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.lacp

       unit name = packets/sec

       Possibilities:
               unlimited   (0)"
   ::= {er1646v2ATMImaCfgEntry 459358592}

er1646v2ATMImaCfgBridgingL2ptDropThrEfmOam OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.efmOam

       unit name = packets/sec

       Possibilities:
               unlimited   (0)"
   ::= {er1646v2ATMImaCfgEntry 459358656}

er1646v2ATMImaCfgBridgingL2ptDropThrPvst OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.pvst

       unit name = packets/sec

       Possibilities:
               unlimited   (0)"
   ::= {er1646v2ATMImaCfgEntry 459358720}

er1646v2ATMImaCfgBridgingL2ptDropThrMmrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.mmrp

       unit name = packets/sec

       Possibilities:
               unlimited   (0)"
   ::= {er1646v2ATMImaCfgEntry 459358784}

er1646v2ATMImaCfgBridgingL2ptDropThrMvrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.mvrp

       unit name = packets/sec

       Possibilities:
               unlimited   (0)"
   ::= {er1646v2ATMImaCfgEntry 459358848}

er1646v2ATMImaCfgBridgingL2ptDropThrGvrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.gvrp

       unit name = packets/sec

       Possibilities:
               unlimited   (0)"
   ::= {er1646v2ATMImaCfgEntry 459358912}

er1646v2ATMImaCfgBridgingL2ptDropThrGmrp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.gmrp

       unit name = packets/sec

       Possibilities:
               unlimited   (0)"
   ::= {er1646v2ATMImaCfgEntry 459358976}

er1646v2ATMImaCfgBridgingL2ptDropThrDtp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.dtp

       unit name = packets/sec

       Possibilities:
               unlimited   (0)"
   ::= {er1646v2ATMImaCfgEntry 459359040}

er1646v2ATMImaCfgBridgingL2ptDropThrPagp OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.pagp

       unit name = packets/sec

       Possibilities:
               unlimited   (0)"
   ::= {er1646v2ATMImaCfgEntry 459359104}

er1646v2ATMImaCfgBridgingL2ptDropThrUdld OBJECT-TYPE
   SYNTAX      INTEGER
               {
               unlimited (0)
               }
   UNITS       "packets/sec"
   MAX-ACCESS  read-write
   STATUS      current
   DESCRIPTION
      "Path: atm.editConf.pvcTable.bridging.l2ProtTunnel.dropThresholds.udld

       unit name = packets/sec

       Possibilities:
               unlimited   (0)"
   ::= {er1646v2ATMImaCfgEntry 459359168}

er1646v2ATMImaCfgVirtEthernetVirtualEthernet OBJECT-TYPE
   SYNTAX      DisplayString
   MAX-ACCESS  read-write
   STATUS      current
   DESCRIPTION
      "Path: atm.editConf.pvcTable.virtEthernet.virtualEthernet"
   ::= {er1646v2ATMImaCfgEntry 151060480}

er1646v2ATMImaCfgAtmVpi OBJECT-TYPE
   SYNTAX      Integer32
   MAX-ACCESS  read-write
   STATUS      current
   DESCRIPTION
      "Path: atm.editConf.pvcTable.atm.vpi"
   ::= {er1646v2ATMImaCfgEntry 285278208}

er1646v2ATMImaCfgAtmVci OBJECT-TYPE
   SYNTAX      Integer32
   MAX-ACCESS  read-write
   STATUS      current
   DESCRIPTION
      "Path: atm.editConf.pvcTable.atm.vci"
   ::= {er1646v2ATMImaCfgEntry 285343744}

er1646v2ATMImaCfgAtmHighLayProt OBJECT-TYPE
   SYNTAX      INTEGER
               {
               rfc2684 (7),
               ppp (2),
               pppOverEthernet (11)
               }
   MAX-ACCESS  read-write
   STATUS      current
   DESCRIPTION
      "Path: atm.editConf.pvcTable.atm.higherLayerProtocol

       Possibilities:
               rfc2684   (7)
               ppp   (2)
               pppOverEthernet   (11)"
   ::= {er1646v2ATMImaCfgEntry 285409280}

er1646v2ATMImaCfgAtmMultiProt OBJECT-TYPE
   SYNTAX      INTEGER
               {
               llcEncapsulation (0),
               vcMultiplexing (1)
               }
   MAX-ACCESS  read-write
   STATUS      current
   DESCRIPTION
      "Path: atm.editConf.pvcTable.atm.multiProtocolMech

       Possibilities:
               llcEncapsulation   (0)
               vcMultiplexing   (1)"
   ::= {er1646v2ATMImaCfgEntry 285474816}

er1646v2ATMImaCfgAtmServCat OBJECT-TYPE
   SYNTAX      INTEGER
               {
               cbr (1),
               vbrmrt (2),
               vbrmnrt (3),
               ubr (4)
               }
   MAX-ACCESS  read-write
   STATUS      current
   DESCRIPTION
      "Path: atm.editConf.pvcTable.atm.serviceCategory

       Possibilities:
               cbr   (1)
               vbr-rt   (2)
               vbr-nrt   (3)
               ubr   (4)"
   ::= {er1646v2ATMImaCfgEntry 285999104}

er1646v2ATMImaCfgAtmPeakCellRate OBJECT-TYPE
   SYNTAX      INTEGER
               {
               auto (0)
               }
   UNITS       "bps"
   MAX-ACCESS  read-write
   STATUS      current
   DESCRIPTION
      "Path: atm.editConf.pvcTable.atm.peakCellRate

       unit name = bps

       Possibilities:
               auto   (0)"
   ::= {er1646v2ATMImaCfgEntry 285540352}

er1646v2ATMImaCfgAtmSustCellRate OBJECT-TYPE
   SYNTAX      INTEGER
               {
               auto (0)
               }
   UNITS       "bps"
   MAX-ACCESS  read-write
   STATUS      current
   DESCRIPTION
      "Path: atm.editConf.pvcTable.atm.sustCellRate

       unit name = bps

       Possibilities:
               auto   (0)"
   ::= {er1646v2ATMImaCfgEntry 285868032}

er1646v2ATMImaCfgAtmMaxBurstSize OBJECT-TYPE
   SYNTAX      Integer32
   UNITS       "cellTimes"
   MAX-ACCESS  read-write
   STATUS      current
   DESCRIPTION
      "Path: atm.editConf.pvcTable.atm.maxBurstSize

       unit name = cellTimes"
   ::= {er1646v2ATMImaCfgEntry 285933568}

er1646v2ATMImaCfgAtmInArpTimeOut OBJECT-TYPE
   SYNTAX      TimeTicks
   MAX-ACCESS  read-write
   STATUS      current
   DESCRIPTION
      "Path: atm.editConf.pvcTable.atm.inArpTimeOut

       Time in centi-second."
   ::= {er1646v2ATMImaCfgEntry 285605888}

er1646v2ATMImaCfgAtmF5LbOper OBJECT-TYPE
   SYNTAX      INTEGER
               {
               disabled (0),
               enabled (1)
               }
   MAX-ACCESS  read-write
   STATUS      current
   DESCRIPTION
      "Path: atm.editConf.pvcTable.atm.oamF5Loopback.operation

       Possibilities:
               disabled   (0)
               enabled   (1)"
   ::= {er1646v2ATMImaCfgEntry 285671680}

er1646v2ATMImaCfgAtmF5LbInterval OBJECT-TYPE
   SYNTAX      TimeTicks
   MAX-ACCESS  read-write
   STATUS      current
   DESCRIPTION
      "Path: atm.editConf.pvcTable.atm.oamF5Loopback.interval

       Time in centi-second."
   ::= {er1646v2ATMImaCfgEntry 285671936}

er1646v2ATMImaCfgAtmF5LbFailsPerm OBJECT-TYPE
   SYNTAX      Integer32
   MAX-ACCESS  read-write
   STATUS      current
   DESCRIPTION
      "Path: atm.editConf.pvcTable.atm.oamF5Loopback.failsPermitted"
   ::= {er1646v2ATMImaCfgEntry 285672448}

er1646v2ATMImaCfgAtmF5LbTar OBJECT-TYPE
   SYNTAX      INTEGER
               {
               endToEnd (0),
               segment (1),
               both (2)
               }
   MAX-ACCESS  read-write
   STATUS      current
   DESCRIPTION
      "Path: atm.editConf.pvcTable.atm.oamF5Loopback.target

       Possibilities:
               endToEnd   (0)
               segment   (1)
               both   (2)"
   ::= {er1646v2ATMImaCfgEntry 285672704}

er1646v2ATMImaCfgAtmF5ccDir OBJECT-TYPE
   SYNTAX      INTEGER
               {
               sink (1),
               source (2),
               both (3)
               }
   MAX-ACCESS  read-write
   STATUS      current
   DESCRIPTION
      "Path: atm.editConf.pvcTable.atm.oamF5CC.direction

       Possibilities:
               sink   (1)
               source   (2)
               both   (3)"
   ::= {er1646v2ATMImaCfgEntry 285737216}

er1646v2ATMImaCfgAtmF5ccTar OBJECT-TYPE
   SYNTAX      INTEGER
               {
               endToEnd (0),
               segment (1),
               both (2)
               }
   MAX-ACCESS  read-write
   STATUS      current
   DESCRIPTION
      "Path: atm.editConf.pvcTable.atm.oamF5CC.target

       Possibilities:
               endToEnd   (0)
               segment   (1)
               both   (2)"
   ::= {er1646v2ATMImaCfgEntry 285737472}

er1646v2ATMImaCfgAtmF5ccTxMode OBJECT-TYPE
   SYNTAX      INTEGER
               {
               continuously (0),
               onIdle (1)
               }
   MAX-ACCESS  read-write
   STATUS      current
   DESCRIPTION
      "Path: atm.editConf.pvcTable.atm.oamF5CC.tx.mode

       Possibilities:
               continuously   (0)
               onIdle   (1)"
   ::= {er1646v2ATMImaCfgEntry 285737729}

er1646v2ATMImaCfgAtmF5ccTxTxPer OBJECT-TYPE
   SYNTAX      TimeTicks
   MAX-ACCESS  read-write
   STATUS      current
   DESCRIPTION
      "Path: atm.editConf.pvcTable.atm.oamF5CC.tx.interval

       Time in centi-second."
   ::= {er1646v2ATMImaCfgEntry 285737730}

er1646v2ATMImaCfgAtmF5ccRxRcvTim OBJECT-TYPE
   SYNTAX      TimeTicks
   MAX-ACCESS  read-write
   STATUS      current
   DESCRIPTION
      "Path: atm.editConf.pvcTable.atm.oamF5CC.rx.timeOut

       Time in centi-second."
   ::= {er1646v2ATMImaCfgEntry 285738497}

er1646v2ATMImaCfgAtmF5ccActProc OBJECT-TYPE
   SYNTAX      INTEGER
               {
               passive (0),
               activated (1),
               deactivated (2),
               initActivation (3)
               }
   MAX-ACCESS  read-write
   STATUS      current
   DESCRIPTION
      "Path: atm.editConf.pvcTable.atm.oamF5CC.actDeact.initProcedure

       Possibilities:
               passive   (0)
               activated   (1)
               deactivated   (2)
               initActivation   (3)"
   ::= {er1646v2ATMImaCfgEntry 285737985}

er1646v2ATMImaCfgAtmF5ccActTim OBJECT-TYPE
   SYNTAX      TimeTicks
   MAX-ACCESS  read-write
   STATUS      current
   DESCRIPTION
      "Path: atm.editConf.pvcTable.atm.oamF5CC.actDeact.retryInterval

       Time in centi-second."
   ::= {er1646v2ATMImaCfgEntry 285737986}

er1646v2ATMImaCfgAtmF5ccActCnt OBJECT-TYPE
   SYNTAX      Integer32
   MAX-ACCESS  read-write
   STATUS      current
   DESCRIPTION
      "Path: atm.editConf.pvcTable.atm.oamF5CC.actDeact.retryCount"
   ::= {er1646v2ATMImaCfgEntry 285737987}

er1646v2ATMImaCfgAtmF5pmDir OBJECT-TYPE
   SYNTAX      INTEGER
               {
               sink (1),
               source (2),
               both (3)
               }
   MAX-ACCESS  read-write
   STATUS      current
   DESCRIPTION
      "Path: atm.editConf.pvcTable.atm.oamF5PM.direction

       Possibilities:
               sink   (1)
               source   (2)
               both   (3)"
   ::= {er1646v2ATMImaCfgEntry 285802752}

er1646v2ATMImaCfgAtmF5pmTar OBJECT-TYPE
   SYNTAX      INTEGER
               {
               endToEnd (0),
               segment (1)
               }
   MAX-ACCESS  read-write
   STATUS      current
   DESCRIPTION
      "Path: atm.editConf.pvcTable.atm.oamF5PM.target

       Possibilities:
               endToEnd   (0)
               segment   (1)"
   ::= {er1646v2ATMImaCfgEntry 285803008}

er1646v2ATMImaCfgAtmF5pmType OBJECT-TYPE
   SYNTAX      INTEGER
               {
               fpm (0),
               fpmWithBr (1)
               }
   MAX-ACCESS  read-write
   STATUS      current
   DESCRIPTION
      "Path: atm.editConf.pvcTable.atm.oamF5PM.type

       Possibilities:
               fpm   (0)
               fpmWithBr   (1)"
   ::= {er1646v2ATMImaCfgEntry 285803264}

er1646v2ATMImaCfgAtmF5pmPolicy OBJECT-TYPE
   SYNTAX      INTEGER
               {
               inband (0),
               outband (1)
               }
   MAX-ACCESS  read-write
   STATUS      current
   DESCRIPTION
      "Path: atm.editConf.pvcTable.atm.oamF5PM.policy

       Possibilities:
               inband   (0)
               outband   (1)"
   ::= {er1646v2ATMImaCfgEntry 285803520}

er1646v2ATMImaCfgAtmF5pmBsizeamb OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.pvcTable.atm.oamF5PM.blockSizeAB

       Possibilities:
               128   (0)
               256   (1)
               512   (2)
               1024   (3)
               2048   (4)
               4096   (5)
               8192   (6)
               16384   (7)
               32768   (8)"
   ::= {er1646v2ATMImaCfgEntry 285803776}

er1646v2ATMImaCfgAtmF5pmBsizebma OBJECT-TYPE
   SYNTAX      INTEGER
               {
               s128 (0),
               s256 (1),
               s512 (2),
               s1024 (3),
               s2048 (4),
               s4096 (5),
               s8192 (6),
               s16384 (7),
               s32768 (8)
               }
   MAX-ACCESS  read-write
   STATUS      current
   DESCRIPTION
      "Path: atm.editConf.pvcTable.atm.oamF5PM.blockSizeBA

       Possibilities:
               128   (0)
               256   (1)
               512   (2)
               1024   (3)
               2048   (4)
               4096   (5)
               8192   (6)
               16384   (7)
               32768   (8)"
   ::= {er1646v2ATMImaCfgEntry 285804032}

er1646v2ATMImaCfgAtmF5pmActProc OBJECT-TYPE
   SYNTAX      INTEGER
               {
               passive (0),
               activated (1),
               deactivated (2),
               initActivation (3)
               }
   MAX-ACCESS  read-write
   STATUS      current
   DESCRIPTION
      "Path: atm.editConf.pvcTable.atm.oamF5PM.actDeact.initProcedure

       Possibilities:
               passive   (0)
               activated   (1)
               deactivated   (2)
               initActivation   (3)"
   ::= {er1646v2ATMImaCfgEntry 285804289}

er1646v2ATMImaCfgAtmF5pmActTim OBJECT-TYPE
   SYNTAX      TimeTicks
   MAX-ACCESS  read-write
   STATUS      current
   DESCRIPTION
      "Path: atm.editConf.pvcTable.atm.oamF5PM.actDeact.retryInterval

       Time in centi-second."
   ::= {er1646v2ATMImaCfgEntry 285804290}

er1646v2ATMImaCfgAtmF5pmActCnt OBJECT-TYPE
   SYNTAX      Integer32
   MAX-ACCESS  read-write
   STATUS      current
   DESCRIPTION
      "Path: atm.editConf.pvcTable.atm.oamF5PM.actDeact.retryCount"
   ::= {er1646v2ATMImaCfgEntry 285804291}

er1646v2ATMImaCfgAtmCpt OBJECT-TYPE
   SYNTAX      INTEGER
               {
               no (0),
               yes (1)
               }
   MAX-ACCESS  read-write
   STATUS      current
   DESCRIPTION
      "Path: atm.editConf.pvcTable.atm.segmentEndPoint

       Possibilities:
               no   (0)
               yes   (1)"
   ::= {er1646v2ATMImaCfgEntry 286195712}

er1646v2ATMImaCfgPppLnkMOperation OBJECT-TYPE
   SYNTAX      INTEGER
               {
               disabled (0),
               enabled (1)
               }
   MAX-ACCESS  read-write
   STATUS      current
   DESCRIPTION
      "Path: atm.editConf.pvcTable.ppp.linkMonitoring.operation

       Possibilities:
               disabled   (0)
               enabled   (1)"
   ::= {er1646v2ATMImaCfgEntry 201392384}

er1646v2ATMImaCfgPppLnkMInterval OBJECT-TYPE
   SYNTAX      TimeTicks
   MAX-ACCESS  read-write
   STATUS      current
   DESCRIPTION
      "Path: atm.editConf.pvcTable.ppp.linkMonitoring.interval

       Time in centi-second."
   ::= {er1646v2ATMImaCfgEntry 201392640}

er1646v2ATMImaCfgPppLnkMRepTimeOut OBJECT-TYPE
   SYNTAX      TimeTicks
   MAX-ACCESS  read-write
   STATUS      current
   DESCRIPTION
      "Path: atm.editConf.pvcTable.ppp.linkMonitoring.replyTimeOut

       Time in centi-second."
   ::= {er1646v2ATMImaCfgEntry 201392896}

er1646v2ATMImaCfgPppLnkMFailsPrmt OBJECT-TYPE
   SYNTAX      Integer32
   MAX-ACCESS  read-write
   STATUS      current
   DESCRIPTION
      "Path: atm.editConf.pvcTable.ppp.linkMonitoring.failsPermitted"
   ::= {er1646v2ATMImaCfgEntry 201393152}

er1646v2ATMImaCfgPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: atm.editConf.pvcTable.ppp.authentication

       Possibilities:
               disabled   (0)
               chap   (1)
               pap   (2)
               chapOrPap   (3)
               msChap   (4)
               msChapV2   (5)"
   ::= {er1646v2ATMImaCfgEntry 201457664}

er1646v2ATMImaCfgPppAuthenPeriod OBJECT-TYPE
   SYNTAX      TimeTicks
   MAX-ACCESS  read-write
   STATUS      current
   DESCRIPTION
      "Path: atm.editConf.pvcTable.ppp.authenPeriod

       Time in centi-second."
   ::= {er1646v2ATMImaCfgEntry 201523200}

er1646v2ATMImaCfgPppCompression OBJECT-TYPE
   SYNTAX      INTEGER
               {
               disabled (0),
               predictor1 (1)
               }
   MAX-ACCESS  read-write
   STATUS      current
   DESCRIPTION
      "Path: atm.editConf.pvcTable.ppp.compression

       Possibilities:
               disabled   (0)
               predictor1   (1)"
   ::= {er1646v2ATMImaCfgEntry 201588736}

er1646v2ATMImaCfgPppSessionName OBJECT-TYPE
   SYNTAX      DisplayString
   MAX-ACCESS  read-write
   STATUS      current
   DESCRIPTION
      "Path: atm.editConf.pvcTable.ppp.sessionName"
   ::= {er1646v2ATMImaCfgEntry 201654272}

er1646v2ATMImaCfgPppSessionSecret OBJECT-TYPE
   SYNTAX      DisplayString
   MAX-ACCESS  read-write
   STATUS      current
   DESCRIPTION
      "Path: atm.editConf.pvcTable.ppp.sessionSecret"
   ::= {er1646v2ATMImaCfgEntry 201719808}

er1646v2ATMImaCfgPppEncModeSessionSecret OBJECT-TYPE
   SYNTAX      INTEGER
               {
               none (1),
               encrypt (2),
               encType1 (3),
               invalid (128)
               }
   MAX-ACCESS  read-write
   STATUS      current
   DESCRIPTION
      "Path: atm.editConf.pvcTable.ppp.encModeSessionSecret

       Possibilities:
               none   (1)
               encrypt   (2)
               encType1   (3)
               invalid   (128)"
   ::= {er1646v2ATMImaCfgEntry 201850880}

er1646v2ATMImaCfgPppEncSessionSecret OBJECT-TYPE
   SYNTAX      DisplayString
   MAX-ACCESS  read-write
   STATUS      current
   DESCRIPTION
      "Path: atm.editConf.pvcTable.ppp.encSessionSecret"
   ::= {er1646v2ATMImaCfgEntry 201916416}

er1646v2ATMImaCfgPppServiceName OBJECT-TYPE
   SYNTAX      DisplayString
   MAX-ACCESS  read-write
   STATUS      current
   DESCRIPTION
      "Path: atm.editConf.pvcTable.ppp.serviceName"
   ::= {er1646v2ATMImaCfgEntry 201785344}

er1646v2ATMImaCfgFrComLmiMode OBJECT-TYPE
   SYNTAX      INTEGER
               {
               noLmi (3),
               user (2),
               network (1),
               nni (4),
               auto (0)
               }
   MAX-ACCESS  read-write
   STATUS      current
   DESCRIPTION
      "Path: atm.editConf.pvcTable.frameRelay.common.lmi.mode

       Possibilities:
               noLmi   (3)
               user   (2)
               network   (1)
               nni   (4)
               auto   (0)"
   ::= {er1646v2ATMImaCfgEntry 688918560}

er1646v2ATMImaCfgFrComLmiType OBJECT-TYPE
   SYNTAX      INTEGER
               {
               lmiRev1 (1),
               ansiT1m617md (2),
               q933mAnnexmA (3),
               frf1m2 (4)
               }
   MAX-ACCESS  read-write
   STATUS      current
   DESCRIPTION
      "Path: atm.editConf.pvcTable.frameRelay.common.lmi.type

       Possibilities:
               lmiRev1   (1)
               ansiT1-617-d   (2)
               q933-Annex-A   (3)
               frf1-2   (4)"
   ::= {er1646v2ATMImaCfgEntry 688918544}

er1646v2ATMImaCfgFrComLmiPollInt OBJECT-TYPE
   SYNTAX      TimeTicks
   MAX-ACCESS  read-write
   STATUS      current
   DESCRIPTION
      "Path: atm.editConf.pvcTable.frameRelay.common.lmi.pollingInterval

       Time in centi-second."
   ::= {er1646v2ATMImaCfgEntry 688918576}

er1646v2ATMImaCfgFrComLmiErrThres OBJECT-TYPE
   SYNTAX      Integer32
   MAX-ACCESS  read-write
   STATUS      current
   DESCRIPTION
      "Path: atm.editConf.pvcTable.frameRelay.common.lmi.errorThreshold"
   ::= {er1646v2ATMImaCfgEntry 688918592}

er1646v2ATMImaCfgFrComLmiMonEvt OBJECT-TYPE
   SYNTAX      Integer32
   MAX-ACCESS  read-write
   STATUS      current
   DESCRIPTION
      "Path: atm.editConf.pvcTable.frameRelay.common.lmi.monitoredEvents"
   ::= {er1646v2ATMImaCfgEntry 688918608}

er1646v2ATMImaCfgFrComLmiExpPollInt OBJECT-TYPE
   SYNTAX      TimeTicks
   MAX-ACCESS  read-write
   STATUS      current
   DESCRIPTION
      "Path: atm.editConf.pvcTable.frameRelay.common.lmi.expectedPollInterval

       Time in centi-second."
   ::= {er1646v2ATMImaCfgEntry 688918624}

er1646v2ATMImaCfgFrComLmiFullEnqInt OBJECT-TYPE
   SYNTAX      Integer32
   MAX-ACCESS  read-write
   STATUS      current
   DESCRIPTION
      "Path: atm.editConf.pvcTable.frameRelay.common.lmi.fullEnquiryInterval"
   ::= {er1646v2ATMImaCfgEntry 688918640}

er1646v2ATMImaCfgFrComFragIMode OBJECT-TYPE
   SYNTAX      INTEGER
               {
               disabled (0),
               enabled (1)
               }
   MAX-ACCESS  read-write
   STATUS      current
   DESCRIPTION
      "Path: atm.editConf.pvcTable.frameRelay.common.fragmentation.interfaceFormat

       Possibilities:
               disabled   (0)
               enabled   (1)"
   ::= {er1646v2ATMImaCfgEntry 688922640}

er1646v2ATMImaCfgFrComMLD OBJECT-TYPE
   SYNTAX      INTEGER
               {
               routing (0),
               bridging (1),
               routingAndBridging (2)
               }
   MAX-ACCESS  read-write
   STATUS      current
   DESCRIPTION
      "Path: atm.editConf.pvcTable.frameRelay.common.modeLearnedDlci

       Possibilities:
               routing   (0)
               bridging   (1)
               routingAndBridging   (2)"
   ::= {er1646v2ATMImaCfgEntry 688926720}

er1646v2ATMImaCfgInbBwCir OBJECT-TYPE
   SYNTAX      Integer32
   MAX-ACCESS  read-write
   STATUS      current
   DESCRIPTION
      "Path: atm.editConf.pvcTable.inboundBandwidth.cir"
   ::= {er1646v2ATMImaCfgEntry 117506048}

er1646v2ATMImaCfgInbBwTc OBJECT-TYPE
   SYNTAX      INTEGER
               {
               auto (0)
               }
   MAX-ACCESS  read-write
   STATUS      current
   DESCRIPTION
      "Path: atm.editConf.pvcTable.inboundBandwidth.tc

       Possibilities:
               auto   (0)"
   ::= {er1646v2ATMImaCfgEntry 117833728}

er1646v2ATMImaCfgInbBwCorrType OBJECT-TYPE
   SYNTAX      INTEGER
               {
               noCorrection (0),
               predefined (1),
               manual (2)
               }
   MAX-ACCESS  read-write
   STATUS      current
   DESCRIPTION
      "Path: atm.editConf.pvcTable.inboundBandwidth.correction.type

       Possibilities:
               noCorrection   (0)
               predefined   (1)
               manual   (2)"
   ::= {er1646v2ATMImaCfgEntry 117579776}

er1646v2ATMImaCfgInbBwCorrPredefEncapsFrameRelay OBJECT-TYPE
   SYNTAX      DisplayString
   MAX-ACCESS  read-write
   STATUS      current
   DESCRIPTION
      "Path: atm.editConf.pvcTable.inboundBandwidth.correction.predefined.encapsulation.frameRelay"
   ::= {er1646v2ATMImaCfgEntry 117589056}

er1646v2ATMImaCfgInbBwCorrPredefEncapsPpp OBJECT-TYPE
   SYNTAX      DisplayString
   MAX-ACCESS  read-write
   STATUS      current
   DESCRIPTION
      "Path: atm.editConf.pvcTable.inboundBandwidth.correction.predefined.encapsulation.ppp"
   ::= {er1646v2ATMImaCfgEntry 117589120}

er1646v2ATMImaCfgInbBwCorrPredefEncapsAtmHl OBJECT-TYPE
   SYNTAX      INTEGER
               {
               rfc2684 (0),
               ppp (1),
               pppOverEthernet (2)
               }
   MAX-ACCESS  read-write
   STATUS      current
   DESCRIPTION
      "Path: atm.editConf.pvcTable.inboundBandwidth.correction.predefined.encapsulation.atm.higherLayer

       Possibilities:
               rfc2684   (0)
               ppp   (1)
               pppOverEthernet   (2)"
   ::= {er1646v2ATMImaCfgEntry 117589192}

er1646v2ATMImaCfgInbBwCorrPredefEncapsAtmMp OBJECT-TYPE
   SYNTAX      INTEGER
               {
               llcEncapsulation (0),
               vcMultiplexing (1)
               }
   MAX-ACCESS  read-write
   STATUS      current
   DESCRIPTION
      "Path: atm.editConf.pvcTable.inboundBandwidth.correction.predefined.encapsulation.atm.multiProtocol

       Possibilities:
               llcEncapsulation   (0)
               vcMultiplexing   (1)"
   ::= {er1646v2ATMImaCfgEntry 117589200}

er1646v2ATMImaCfgInbBwCorrPredefEncapsHdlc OBJECT-TYPE
   SYNTAX      DisplayString
   MAX-ACCESS  read-write
   STATUS      current
   DESCRIPTION
      "Path: atm.editConf.pvcTable.inboundBandwidth.correction.predefined.encapsulation.hdlc"
   ::= {er1646v2ATMImaCfgEntry 117589248}

er1646v2ATMImaCfgInbBwCorrPredefEncapsEfmFs OBJECT-TYPE
   SYNTAX      Integer32
   MAX-ACCESS  read-write
   STATUS      current
   DESCRIPTION
      "Path: atm.editConf.pvcTable.inboundBandwidth.correction.predefined.encapsulation.efm.fragmentSize"
   ::= {er1646v2ATMImaCfgEntry 117589320}

er1646v2ATMImaCfgInbBwCorrPredefEncapsEfmIb OBJECT-TYPE
   SYNTAX      Integer32
   MAX-ACCESS  read-write
   STATUS      current
   DESCRIPTION
      "Path: atm.editConf.pvcTable.inboundBandwidth.correction.predefined.encapsulation.efm.idleBytes"
   ::= {er1646v2ATMImaCfgEntry 117589328}

er1646v2ATMImaCfgInbBwCorrPredefMode OBJECT-TYPE
   SYNTAX      INTEGER
               {
               routing (0),
               bridging (1)
               }
   MAX-ACCESS  read-write
   STATUS      current
   DESCRIPTION
      "Path: atm.editConf.pvcTable.inboundBandwidth.correction.predefined.mode

       Possibilities:
               routing   (0)
               bridging   (1)"
   ::= {er1646v2ATMImaCfgEntry 117590016}

er1646v2ATMImaCfgInbBwCorrManualOverhead OBJECT-TYPE
   SYNTAX      Integer32
   MAX-ACCESS  read-write
   STATUS      current
   DESCRIPTION
      "Path: atm.editConf.pvcTable.inboundBandwidth.correction.manual.overhead"
   ::= {er1646v2ATMImaCfgEntry 117596192}

er1646v2ATMImaCfgInbBwCorrManualFrameData OBJECT-TYPE
   SYNTAX      Counter32
   MAX-ACCESS  read-write
   STATUS      current
   DESCRIPTION
      "Path: atm.editConf.pvcTable.inboundBandwidth.correction.manual.frameData

       32 bit unsigned wrappable counter."
   ::= {er1646v2ATMImaCfgEntry 117596224}

er1646v2ATMImaCfgInbBwCorrManualFrameHeader OBJECT-TYPE
   SYNTAX      Counter32
   MAX-ACCESS  read-write
   STATUS      current
   DESCRIPTION
      "Path: atm.editConf.pvcTable.inboundBandwidth.correction.manual.frameHeader

       32 bit unsigned wrappable counter."
   ::= {er1646v2ATMImaCfgEntry 117596256}

er1646v2ATMImaCfgInbBwMaxFifoQLen OBJECT-TYPE
   SYNTAX      Integer32
   MAX-ACCESS  read-write
   STATUS      current
   DESCRIPTION
      "Path: atm.editConf.pvcTable.inboundBandwidth.maxFifoQLen"
   ::= {er1646v2ATMImaCfgEntry 117637120}

er1646v2ATMImaCfgInbBwPriorityPolicy OBJECT-TYPE
   SYNTAX      DisplayString
   MAX-ACCESS  read-write
   STATUS      current
   DESCRIPTION
      "Path: atm.editConf.pvcTable.inboundBandwidth.priorityPolicy"
   ::= {er1646v2ATMImaCfgEntry 117702656}

er1646v2ATMImaCfgIpH OBJECT-TYPE
   SYNTAX      SEQUENCE OF Er1646v2ATMImaCfgIpHEntry
   MAX-ACCESS  not-accessible
   STATUS      current
   DESCRIPTION
      ""
   ::= {er1646v2ATMImaCfg 51314688}

er1646v2ATMImaCfgIpHEntry OBJECT-TYPE
   SYNTAX      Er1646v2ATMImaCfgIpHEntry
   MAX-ACCESS  not-accessible
   STATUS      current
   DESCRIPTION
      ""
   INDEX      { er1646v2ATMImaCfgTableIx,
                er1646v2ATMImaCfgIpHTableIx }
   ::= {er1646v2ATMImaCfgIpH 1}

Er1646v2ATMImaCfgIpHEntry ::=
   SEQUENCE
      {
      er1646v2ATMImaCfgIpHActions
         VariableLengthTableActions,
      er1646v2ATMImaCfgIpHTableIx
         TableIndex,
      er1646v2ATMImaCfgIpHAddress
         IpAddress,
      er1646v2ATMImaCfgIpHDhcpRelayOptionSubscriberId
         DisplayString
      }

er1646v2ATMImaCfgIpHActions OBJECT-TYPE
   SYNTAX      VariableLengthTableActions
   MAX-ACCESS  read-write
   STATUS      current
   DESCRIPTION
      "By way of this field, some manipulations
       on this table may be performed."
   ::= {er1646v2ATMImaCfgIpHEntry 2}

er1646v2ATMImaCfgIpHTableIx OBJECT-TYPE
   SYNTAX      TableIndex
   MAX-ACCESS  not-accessible
   STATUS      current
   DESCRIPTION
      ""
   ::= {er1646v2ATMImaCfgIpHEntry 11}

er1646v2ATMImaCfgIpHAddress OBJECT-TYPE
   SYNTAX      IpAddress
   MAX-ACCESS  read-write
   STATUS      current
   DESCRIPTION
      "Path: atm.editConf.pvcTable.ip.helpers.address"
   ::= {er1646v2ATMImaCfgIpHEntry 16777216}

er1646v2ATMImaCfgIpHDhcpRelayOptionSubscriberId OBJECT-TYPE
   SYNTAX      DisplayString
   MAX-ACCESS  read-write
   STATUS      current
   DESCRIPTION
      "Path: atm.editConf.pvcTable.ip.helpers.dhcpRelayOption.subscriberId"
   ::= {er1646v2ATMImaCfgIpHEntry 33947648}

er1646v2ATMImaCfgIpV6Addresses OBJECT-TYPE
   SYNTAX      SEQUENCE OF Er1646v2ATMImaCfgIpV6AddressesEntry
   MAX-ACCESS  not-accessible
   STATUS      current
   DESCRIPTION
      ""
   ::= {er1646v2ATMImaCfg 704839680}

er1646v2ATMImaCfgIpV6AddressesEntry OBJECT-TYPE
   SYNTAX      Er1646v2ATMImaCfgIpV6AddressesEntry
   MAX-ACCESS  not-accessible
   STATUS      current
   DESCRIPTION
      ""
   INDEX      { er1646v2ATMImaCfgTableIx,
                er1646v2ATMImaCfgIpV6AddressesTableIx }
   ::= {er1646v2ATMImaCfgIpV6Addresses 1}

Er1646v2ATMImaCfgIpV6AddressesEntry ::=
   SEQUENCE
      {
      er1646v2ATMImaCfgIpV6AddressesActions
         VariableLengthTableActions,
      er1646v2ATMImaCfgIpV6AddressesTableIx
         TableIndex,
      er1646v2ATMImaCfgIpV6AddressesType
         INTEGER,
      er1646v2ATMImaCfgIpV6AddressesAddress
         Ipv6Address,
      er1646v2ATMImaCfgIpV6AddressesPrefixLength
         Integer32,
      er1646v2ATMImaCfgIpV6AddressesGeneralPrefix
         DisplayString,
      er1646v2ATMImaCfgIpV6AddressesRaSend
         INTEGER,
      er1646v2ATMImaCfgIpV6AddressesRaOnLinkFlag
         INTEGER,
      er1646v2ATMImaCfgIpV6AddressesRaAutoFlag
         INTEGER,
      er1646v2ATMImaCfgIpV6AddressesRaValidLifeTime
         TimeTicks,
      er1646v2ATMImaCfgIpV6AddressesRaValidLTMode
         INTEGER,
      er1646v2ATMImaCfgIpV6AddressesRaPrefLifeTime
         TimeTicks,
      er1646v2ATMImaCfgIpV6AddressesRaPrefLTMode
         INTEGER
      }

er1646v2ATMImaCfgIpV6AddressesActions OBJECT-TYPE
   SYNTAX      VariableLengthTableActions
   MAX-ACCESS  read-write
   STATUS      current
   DESCRIPTION
      "By way of this field, some manipulations
       on this table may be performed."
   ::= {er1646v2ATMImaCfgIpV6AddressesEntry 2}

er1646v2ATMImaCfgIpV6AddressesTableIx OBJECT-TYPE
   SYNTAX      TableIndex
   MAX-ACCESS  not-accessible
   STATUS      current
   DESCRIPTION
      ""
   ::= {er1646v2ATMImaCfgIpV6AddressesEntry 11}

er1646v2ATMImaCfgIpV6AddressesType OBJECT-TYPE
   SYNTAX      INTEGER
               {
               unicast (0),
               eui64 (1),
               anycast (2),
               linkLocal (3),
               generalPrefix (4)
               }
   MAX-ACCESS  read-write
   STATUS      current
   DESCRIPTION
      "Path: atm.editConf.pvcTable.ipV6.addresses.type

       Possibilities:
               unicast   (0)
               eui64   (1)
               anycast   (2)
               linkLocal   (3)
               generalPrefix   (4)"
   ::= {er1646v2ATMImaCfgIpV6AddressesEntry 50331648}

er1646v2ATMImaCfgIpV6AddressesAddress OBJECT-TYPE
   SYNTAX      Ipv6Address
   MAX-ACCESS  read-write
   STATUS      current
   DESCRIPTION
      "Path: atm.editConf.pvcTable.ipV6.addresses.address

       ipv6 address"
   ::= {er1646v2ATMImaCfgIpV6AddressesEntry 16777216}

er1646v2ATMImaCfgIpV6AddressesPrefixLength OBJECT-TYPE
   SYNTAX      Integer32
   MAX-ACCESS  read-write
   STATUS      current
   DESCRIPTION
      "Path: atm.editConf.pvcTable.ipV6.addresses.prefixLength"
   ::= {er1646v2ATMImaCfgIpV6AddressesEntry 33554432}

er1646v2ATMImaCfgIpV6AddressesGeneralPrefix OBJECT-TYPE
   SYNTAX      DisplayString
   MAX-ACCESS  read-write
   STATUS      current
   DESCRIPTION
      "Path: atm.editConf.pvcTable.ipV6.addresses.generalPrefix"
   ::= {er1646v2ATMImaCfgIpV6AddressesEntry 83886080}

er1646v2ATMImaCfgIpV6AddressesRaSend OBJECT-TYPE
   SYNTAX      INTEGER
               {
               disabled (0),
               enabled (1)
               }
   MAX-ACCESS  read-write
   STATUS      current
   DESCRIPTION
      "Path: atm.editConf.pvcTable.ipV6.addresses.ra.send

       Possibilities:
               disabled   (0)
               enabled   (1)"
   ::= {er1646v2ATMImaCfgIpV6AddressesEntry 67174400}

er1646v2ATMImaCfgIpV6AddressesRaOnLinkFlag OBJECT-TYPE
   SYNTAX      INTEGER
               {
               disabled (0),
               enabled (1)
               }
   MAX-ACCESS  read-write
   STATUS      current
   DESCRIPTION
      "Path: atm.editConf.pvcTable.ipV6.addresses.ra.onLinkFlag

       Possibilities:
               disabled   (0)
               enabled   (1)"
   ::= {er1646v2ATMImaCfgIpV6AddressesEntry 67371008}

er1646v2ATMImaCfgIpV6AddressesRaAutoFlag OBJECT-TYPE
   SYNTAX      INTEGER
               {
               disabled (0),
               enabled (1)
               }
   MAX-ACCESS  read-write
   STATUS      current
   DESCRIPTION
      "Path: atm.editConf.pvcTable.ipV6.addresses.ra.autonomousFlag

       Possibilities:
               disabled   (0)
               enabled   (1)"
   ::= {er1646v2ATMImaCfgIpV6AddressesEntry 67567616}

er1646v2ATMImaCfgIpV6AddressesRaValidLifeTime OBJECT-TYPE
   SYNTAX      TimeTicks
   MAX-ACCESS  read-write
   STATUS      current
   DESCRIPTION
      "Path: atm.editConf.pvcTable.ipV6.addresses.ra.validLifeTime

       Time in centi-second."
   ::= {er1646v2ATMImaCfgIpV6AddressesEntry 67239936}

er1646v2ATMImaCfgIpV6AddressesRaValidLTMode OBJECT-TYPE
   SYNTAX      INTEGER
               {
               fixed (0),
               infinite (2)
               }
   MAX-ACCESS  read-write
   STATUS      current
   DESCRIPTION
      "Path: atm.editConf.pvcTable.ipV6.addresses.ra.validLifeTimeMode

       Possibilities:
               fixed   (0)
               infinite   (2)"
   ::= {er1646v2ATMImaCfgIpV6AddressesEntry 67305472}

er1646v2ATMImaCfgIpV6AddressesRaPrefLifeTime OBJECT-TYPE
   SYNTAX      TimeTicks
   MAX-ACCESS  read-write
   STATUS      current
   DESCRIPTION
      "Path: atm.editConf.pvcTable.ipV6.addresses.ra.prefLifeTime

       Time in centi-second."
   ::= {er1646v2ATMImaCfgIpV6AddressesEntry 67436544}

er1646v2ATMImaCfgIpV6AddressesRaPrefLTMode OBJECT-TYPE
   SYNTAX      INTEGER
               {
               fixed (0),
               infinite (2)
               }
   MAX-ACCESS  read-write
   STATUS      current
   DESCRIPTION
      "Path: atm.editConf.pvcTable.ipV6.addresses.ra.prefLifeTimeMode

       Possibilities:
               fixed   (0)
               infinite   (2)"
   ::= {er1646v2ATMImaCfgIpV6AddressesEntry 67502080}

er1646v2ATMImaCfgIpV6RaDnsOptionsRdnssServers OBJECT-TYPE
   SYNTAX      SEQUENCE OF Er1646v2ATMImaCfgIpV6RaDnsOptionsRdnssServersEntry
   MAX-ACCESS  not-accessible
   STATUS      current
   DESCRIPTION
      ""
   ::= {er1646v2ATMImaCfg 705039144}

er1646v2ATMImaCfgIpV6RaDnsOptionsRdnssServersEntry OBJECT-TYPE
   SYNTAX      Er1646v2ATMImaCfgIpV6RaDnsOptionsRdnssServersEntry
   MAX-ACCESS  not-accessible
   STATUS      current
   DESCRIPTION
      ""
   INDEX      { er1646v2ATMImaCfgTableIx,
                er1646v2ATMImaCfgIpV6RaDnsOptionsRdnssServersTableIx }
   ::= {er1646v2ATMImaCfgIpV6RaDnsOptionsRdnssServers 1}

Er1646v2ATMImaCfgIpV6RaDnsOptionsRdnssServersEntry ::=
   SEQUENCE
      {
      er1646v2ATMImaCfgIpV6RaDnsOptionsRdnssServersActions
         VariableLengthTableActions,
      er1646v2ATMImaCfgIpV6RaDnsOptionsRdnssServersTableIx
         TableIndex,
      er1646v2ATMImaCfgIpV6RaDnsOptionsRdnssServersAddress
         Ipv6Address
      }

er1646v2ATMImaCfgIpV6RaDnsOptionsRdnssServersActions OBJECT-TYPE
   SYNTAX      VariableLengthTableActions
   MAX-ACCESS  read-write
   STATUS      current
   DESCRIPTION
      "By way of this field, some manipulations
       on this table may be performed."
   ::= {er1646v2ATMImaCfgIpV6RaDnsOptionsRdnssServersEntry 2}

er1646v2ATMImaCfgIpV6RaDnsOptionsRdnssServersTableIx OBJECT-TYPE
   SYNTAX      TableIndex
   MAX-ACCESS  not-accessible
   STATUS      current
   DESCRIPTION
      ""
   ::= {er1646v2ATMImaCfgIpV6RaDnsOptionsRdnssServersEntry 11}

er1646v2ATMImaCfgIpV6RaDnsOptionsRdnssServersAddress OBJECT-TYPE
   SYNTAX      Ipv6Address
   MAX-ACCESS  read-write
   STATUS      current
   DESCRIPTION
      "Path: atm.editConf.pvcTable.ipV6.ra.dnsOptions.rdnss.servers.address

       ipv6 address"
   ::= {er1646v2ATMImaCfgIpV6RaDnsOptionsRdnssServersEntry 16777216}

er1646v2ATMImaCfgIpV6RaDnsOptionsDnsslDomains OBJECT-TYPE
   SYNTAX      SEQUENCE OF Er1646v2ATMImaCfgIpV6RaDnsOptionsDnsslDomainsEntry
   MAX-ACCESS  not-accessible
   STATUS      current
   DESCRIPTION
      ""
   ::= {er1646v2ATMImaCfg 705039176}

er1646v2ATMImaCfgIpV6RaDnsOptionsDnsslDomainsEntry OBJECT-TYPE
   SYNTAX      Er1646v2ATMImaCfgIpV6RaDnsOptionsDnsslDomainsEntry
   MAX-ACCESS  not-accessible
   STATUS      current
   DESCRIPTION
      ""
   INDEX      { er1646v2ATMImaCfgTableIx,
                er1646v2ATMImaCfgIpV6RaDnsOptionsDnsslDomainsTableIx }
   ::= {er1646v2ATMImaCfgIpV6RaDnsOptionsDnsslDomains 1}

Er1646v2ATMImaCfgIpV6RaDnsOptionsDnsslDomainsEntry ::=
   SEQUENCE
      {
      er1646v2ATMImaCfgIpV6RaDnsOptionsDnsslDomainsActions
         VariableLengthTableActions,
      er1646v2ATMImaCfgIpV6RaDnsOptionsDnsslDomainsTableIx
         TableIndex,
      er1646v2ATMImaCfgIpV6RaDnsOptionsDnsslDomainsName
         DisplayString
      }

er1646v2ATMImaCfgIpV6RaDnsOptionsDnsslDomainsActions OBJECT-TYPE
   SYNTAX      VariableLengthTableActions
   MAX-ACCESS  read-write
   STATUS      current
   DESCRIPTION
      "By way of this field, some manipulations
       on this table may be performed."
   ::= {er1646v2ATMImaCfgIpV6RaDnsOptionsDnsslDomainsEntry 2}

er1646v2ATMImaCfgIpV6RaDnsOptionsDnsslDomainsTableIx OBJECT-TYPE
   SYNTAX      TableIndex
   MAX-ACCESS  not-accessible
   STATUS      current
   DESCRIPTION
      ""
   ::= {er1646v2ATMImaCfgIpV6RaDnsOptionsDnsslDomainsEntry 11}

er1646v2ATMImaCfgIpV6RaDnsOptionsDnsslDomainsName OBJECT-TYPE
   SYNTAX      DisplayString
   MAX-ACCESS  read-write
   STATUS      current
   DESCRIPTION
      "Path: atm.editConf.pvcTable.ipV6.ra.dnsOptions.dnssl.domains.name"
   ::= {er1646v2ATMImaCfgIpV6RaDnsOptionsDnsslDomainsEntry 16777216}

er1646v2ATMImaCfgIpV6DhcpClientUserClassOpt OBJECT-TYPE
   SYNTAX      SEQUENCE OF Er1646v2ATMImaCfgIpV6DhcpClientUserClassOptEntry
   MAX-ACCESS  not-accessible
   STATUS      current
   DESCRIPTION
      ""
   ::= {er1646v2ATMImaCfg 705312768}

er1646v2ATMImaCfgIpV6DhcpClientUserClassOptEntry OBJECT-TYPE
   SYNTAX      Er1646v2ATMImaCfgIpV6DhcpClientUserClassOptEntry
   MAX-ACCESS  not-accessible
   STATUS      current
   DESCRIPTION
      ""
   INDEX      { er1646v2ATMImaCfgTableIx,
                er1646v2ATMImaCfgIpV6DhcpClientUserClassOptTableIx }
   ::= {er1646v2ATMImaCfgIpV6DhcpClientUserClassOpt 1}

Er1646v2ATMImaCfgIpV6DhcpClientUserClassOptEntry ::=
   SEQUENCE
      {
      er1646v2ATMImaCfgIpV6DhcpClientUserClassOptActions
         VariableLengthTableActions,
      er1646v2ATMImaCfgIpV6DhcpClientUserClassOptTableIx
         TableIndex,
      er1646v2ATMImaCfgIpV6DhcpClientUserClassOptValueAscii
         DisplayString,
      er1646v2ATMImaCfgIpV6DhcpClientUserClassOptValueDecimal
         Integer32,
      er1646v2ATMImaCfgIpV6DhcpClientUserClassOptValueHexData
         OCTET STRING
      }

er1646v2ATMImaCfgIpV6DhcpClientUserClassOptActions OBJECT-TYPE
   SYNTAX      VariableLengthTableActions
   MAX-ACCESS  read-write
   STATUS      current
   DESCRIPTION
      "By way of this field, some manipulations
       on this table may be performed."
   ::= {er1646v2ATMImaCfgIpV6DhcpClientUserClassOptEntry 2}

er1646v2ATMImaCfgIpV6DhcpClientUserClassOptTableIx OBJECT-TYPE
   SYNTAX      TableIndex
   MAX-ACCESS  not-accessible
   STATUS      current
   DESCRIPTION
      ""
   ::= {er1646v2ATMImaCfgIpV6DhcpClientUserClassOptEntry 11}

er1646v2ATMImaCfgIpV6DhcpClientUserClassOptValueAscii OBJECT-TYPE
   SYNTAX      DisplayString
   MAX-ACCESS  read-write
   STATUS      current
   DESCRIPTION
      "Path: atm.editConf.pvcTable.ipV6.dhcp.client.userClassOpt.value.ascii"
   ::= {er1646v2ATMImaCfgIpV6DhcpClientUserClassOptEntry 16842752}

er1646v2ATMImaCfgIpV6DhcpClientUserClassOptValueDecimal OBJECT-TYPE
   SYNTAX      Integer32
   MAX-ACCESS  read-write
   STATUS      current
   DESCRIPTION
      "Path: atm.editConf.pvcTable.ipV6.dhcp.client.userClassOpt.value.decimal"
   ::= {er1646v2ATMImaCfgIpV6DhcpClientUserClassOptEntry 16908288}

er1646v2ATMImaCfgIpV6DhcpClientUserClassOptValueHexData OBJECT-TYPE
   SYNTAX      OCTET STRING
   MAX-ACCESS  read-write
   STATUS      current
   DESCRIPTION
      "Path: atm.editConf.pvcTable.ipV6.dhcp.client.userClassOpt.value.hexData"
   ::= {er1646v2ATMImaCfgIpV6DhcpClientUserClassOptEntry 16973824}

er1646v2ATMImaCfgIpV6DhcpClientVendorCl OBJECT-TYPE
   SYNTAX      SEQUENCE OF Er1646v2ATMImaCfgIpV6DhcpClientVendorClEntry
   MAX-ACCESS  not-accessible
   STATUS      current
   DESCRIPTION
      ""
   ::= {er1646v2ATMImaCfg 705313792}

er1646v2ATMImaCfgIpV6DhcpClientVendorClEntry OBJECT-TYPE
   SYNTAX      Er1646v2ATMImaCfgIpV6DhcpClientVendorClEntry
   MAX-ACCESS  not-accessible
   STATUS      current
   DESCRIPTION
      ""
   INDEX      { er1646v2ATMImaCfgTableIx,
                er1646v2ATMImaCfgIpV6DhcpClientVendorClTableIx }
   ::= {er1646v2ATMImaCfgIpV6DhcpClientVendorCl 1}

Er1646v2ATMImaCfgIpV6DhcpClientVendorClEntry ::=
   SEQUENCE
      {
      er1646v2ATMImaCfgIpV6DhcpClientVendorClActions
         VariableLengthTableActions,
      er1646v2ATMImaCfgIpV6DhcpClientVendorClTableIx
         TableIndex,
      er1646v2ATMImaCfgIpV6DhcpClientVendorClValueAscii
         DisplayString,
      er1646v2ATMImaCfgIpV6DhcpClientVendorClValueDecimal
         Integer32,
      er1646v2ATMImaCfgIpV6DhcpClientVendorClValueHexData
         OCTET STRING
      }

er1646v2ATMImaCfgIpV6DhcpClientVendorClActions OBJECT-TYPE
   SYNTAX      VariableLengthTableActions
   MAX-ACCESS  read-write
   STATUS      current
   DESCRIPTION
      "By way of this field, some manipulations
       on this table may be performed."
   ::= {er1646v2ATMImaCfgIpV6DhcpClientVendorClEntry 2}

er1646v2ATMImaCfgIpV6DhcpClientVendorClTableIx OBJECT-TYPE
   SYNTAX      TableIndex
   MAX-ACCESS  not-accessible
   STATUS      current
   DESCRIPTION
      ""
   ::= {er1646v2ATMImaCfgIpV6DhcpClientVendorClEntry 11}

er1646v2ATMImaCfgIpV6DhcpClientVendorClValueAscii OBJECT-TYPE
   SYNTAX      DisplayString
   MAX-ACCESS  read-write
   STATUS      current
   DESCRIPTION
      "Path: atm.editConf.pvcTable.ipV6.dhcp.client.vendorClassOpt.value.ascii"
   ::= {er1646v2ATMImaCfgIpV6DhcpClientVendorClEntry 16842752}

er1646v2ATMImaCfgIpV6DhcpClientVendorClValueDecimal OBJECT-TYPE
   SYNTAX      Integer32
   MAX-ACCESS  read-write
   STATUS      current
   DESCRIPTION
      "Path: atm.editConf.pvcTable.ipV6.dhcp.client.vendorClassOpt.value.decimal"
   ::= {er1646v2ATMImaCfgIpV6DhcpClientVendorClEntry 16908288}

er1646v2ATMImaCfgIpV6DhcpClientVendorClValueHexData OBJECT-TYPE
   SYNTAX      OCTET STRING
   MAX-ACCESS  read-write
   STATUS      current
   DESCRIPTION
      "Path: atm.editConf.pvcTable.ipV6.dhcp.client.vendorClassOpt.value.hexData"
   ::= {er1646v2ATMImaCfgIpV6DhcpClientVendorClEntry 16973824}

er1646v2ATMImaCfgIpV6DhcpRelayDestinations OBJECT-TYPE
   SYNTAX      SEQUENCE OF Er1646v2ATMImaCfgIpV6DhcpRelayDestinationsEntry
   MAX-ACCESS  not-accessible
   STATUS      current
   DESCRIPTION
      ""
   ::= {er1646v2ATMImaCfg 705323072}

er1646v2ATMImaCfgIpV6DhcpRelayDestinationsEntry OBJECT-TYPE
   SYNTAX      Er1646v2ATMImaCfgIpV6DhcpRelayDestinationsEntry
   MAX-ACCESS  not-accessible
   STATUS      current
   DESCRIPTION
      ""
   INDEX      { er1646v2ATMImaCfgTableIx,
                er1646v2ATMImaCfgIpV6DhcpRelayDestinationsTableIx }
   ::= {er1646v2ATMImaCfgIpV6DhcpRelayDestinations 1}

Er1646v2ATMImaCfgIpV6DhcpRelayDestinationsEntry ::=
   SEQUENCE
      {
      er1646v2ATMImaCfgIpV6DhcpRelayDestinationsActions
         VariableLengthTableActions,
      er1646v2ATMImaCfgIpV6DhcpRelayDestinationsTableIx
         TableIndex,
      er1646v2ATMImaCfgIpV6DhcpRelayDestinationsAddress
         Ipv6Address,
      er1646v2ATMImaCfgIpV6DhcpRelayDestinationsInterface
         DisplayString
      }

er1646v2ATMImaCfgIpV6DhcpRelayDestinationsActions OBJECT-TYPE
   SYNTAX      VariableLengthTableActions
   MAX-ACCESS  read-write
   STATUS      current
   DESCRIPTION
      "By way of this field, some manipulations
       on this table may be performed."
   ::= {er1646v2ATMImaCfgIpV6DhcpRelayDestinationsEntry 2}

er1646v2ATMImaCfgIpV6DhcpRelayDestinationsTableIx OBJECT-TYPE
   SYNTAX      TableIndex
   MAX-ACCESS  not-accessible
   STATUS      current
   DESCRIPTION
      ""
   ::= {er1646v2ATMImaCfgIpV6DhcpRelayDestinationsEntry 11}

er1646v2ATMImaCfgIpV6DhcpRelayDestinationsAddress OBJECT-TYPE
   SYNTAX      Ipv6Address
   MAX-ACCESS  read-write
   STATUS      current
   DESCRIPTION
      "Path: atm.editConf.pvcTable.ipV6.dhcp.relay.destinations.address

       ipv6 address"
   ::= {er1646v2ATMImaCfgIpV6DhcpRelayDestinationsEntry 16777216}

er1646v2ATMImaCfgIpV6DhcpRelayDestinationsInterface OBJECT-TYPE
   SYNTAX      DisplayString
   MAX-ACCESS  read-write
   STATUS      current
   DESCRIPTION
      "Path: atm.editConf.pvcTable.ipV6.dhcp.relay.destinations.interface"
   ::= {er1646v2ATMImaCfgIpV6DhcpRelayDestinationsEntry 33554432}

er1646v2ATMImaCfgBridgingVlTVlans OBJECT-TYPE
   SYNTAX      SEQUENCE OF Er1646v2ATMImaCfgBridgingVlTVlansEntry
   MAX-ACCESS  not-accessible
   STATUS      current
   DESCRIPTION
      ""
   ::= {er1646v2ATMImaCfg 459079680}

er1646v2ATMImaCfgBridgingVlTVlansEntry OBJECT-TYPE
   SYNTAX      Er1646v2ATMImaCfgBridgingVlTVlansEntry
   MAX-ACCESS  not-accessible
   STATUS      current
   DESCRIPTION
      ""
   INDEX      { er1646v2ATMImaCfgTableIx,
                er1646v2ATMImaCfgBridgingVlTVlansTableIx }
   ::= {er1646v2ATMImaCfgBridgingVlTVlans 1}

Er1646v2ATMImaCfgBridgingVlTVlansEntry ::=
   SEQUENCE
      {
      er1646v2ATMImaCfgBridgingVlTVlansActions
         VariableLengthTableActions,
      er1646v2ATMImaCfgBridgingVlTVlansTableIx
         TableIndex,
      er1646v2ATMImaCfgBridgingVlTVlansVid
         Integer32,
      er1646v2ATMImaCfgBridgingVlTVlansEndVid
         Integer32,
      er1646v2ATMImaCfgBridgingVlTVlansAction
         INTEGER,
      er1646v2ATMImaCfgBridgingVlTVlansTagInfoTpid
         INTEGER,
      er1646v2ATMImaCfgBridgingVlTVlansTagInfoVid
         Integer32
      }

er1646v2ATMImaCfgBridgingVlTVlansActions OBJECT-TYPE
   SYNTAX      VariableLengthTableActions
   MAX-ACCESS  read-write
   STATUS      current
   DESCRIPTION
      "By way of this field, some manipulations
       on this table may be performed."
   ::= {er1646v2ATMImaCfgBridgingVlTVlansEntry 2}

er1646v2ATMImaCfgBridgingVlTVlansTableIx OBJECT-TYPE
   SYNTAX      TableIndex
   MAX-ACCESS  not-accessible
   STATUS      current
   DESCRIPTION
      ""
   ::= {er1646v2ATMImaCfgBridgingVlTVlansEntry 11}

er1646v2ATMImaCfgBridgingVlTVlansVid OBJECT-TYPE
   SYNTAX      Integer32
   MAX-ACCESS  read-write
   STATUS      current
   DESCRIPTION
      "Path: atm.editConf.pvcTable.bridging.vlanTagging.vlans.vid"
   ::= {er1646v2ATMImaCfgBridgingVlTVlansEntry 536870912}

er1646v2ATMImaCfgBridgingVlTVlansEndVid OBJECT-TYPE
   SYNTAX      Integer32
   MAX-ACCESS  read-write
   STATUS      current
   DESCRIPTION
      "Path: atm.editConf.pvcTable.bridging.vlanTagging.vlans.endVid"
   ::= {er1646v2ATMImaCfgBridgingVlTVlansEntry 2147483648}

er1646v2ATMImaCfgBridgingVlTVlansAction OBJECT-TYPE
   SYNTAX      INTEGER
               {
               discard (0),
               accept (1),
               tag (2)
               }
   MAX-ACCESS  read-write
   STATUS      current
   DESCRIPTION
      "Path: atm.editConf.pvcTable.bridging.vlanTagging.vlans.action

       Possibilities:
               discard   (0)
               accept   (1)
               tag   (2)"
   ::= {er1646v2ATMImaCfgBridgingVlTVlansEntry 1073741824}

er1646v2ATMImaCfgBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.bridging.vlanTagging.vlans.tagInfo.tpid

       Possibilities:
               dot1Q   (33024)
               dot1ad   (34984)
               0x9100   (37120)
               0x9200   (37376)
               0x9300   (37632)"
   ::= {er1646v2ATMImaCfgBridgingVlTVlansEntry 1677721600}

er1646v2ATMImaCfgBridgingVlTVlansTagInfoVid OBJECT-TYPE
   SYNTAX      Integer32
   MAX-ACCESS  read-write
   STATUS      current
   DESCRIPTION
      "Path: atm.editConf.pvcTable.bridging.vlanTagging.vlans.tagInfo.vid"
   ::= {er1646v2ATMImaCfgBridgingVlTVlansEntry 1744830464}

er1646v2ATMImaCfgFrDlci OBJECT-TYPE
   SYNTAX      SEQUENCE OF Er1646v2ATMImaCfgFrDlciEntry
   MAX-ACCESS  not-accessible
   STATUS      current
   DESCRIPTION
      ""
   ::= {er1646v2ATMImaCfg 689963008}

er1646v2ATMImaCfgFrDlciEntry OBJECT-TYPE
   SYNTAX      Er1646v2ATMImaCfgFrDlciEntry
   MAX-ACCESS  not-accessible
   STATUS      current
   DESCRIPTION
      ""
   INDEX      { er1646v2ATMImaCfgTableIx,
                er1646v2ATMImaCfgFrDlciTableIx }
   ::= {er1646v2ATMImaCfgFrDlci 1}

Er1646v2ATMImaCfgFrDlciEntry ::=
   SEQUENCE
      {
      er1646v2ATMImaCfgFrDlciActions
         VariableLengthTableActions,
      er1646v2ATMImaCfgFrDlciTableIx
         TableIndex,
      er1646v2ATMImaCfgFrDlciName
         DisplayString,
      er1646v2ATMImaCfgFrDlciAdminStatus
         INTEGER,
      er1646v2ATMImaCfgFrDlciMode
         INTEGER,
      er1646v2ATMImaCfgFrDlciIpVrfRouter
         DisplayString,
      er1646v2ATMImaCfgFrDlciIpAdr
         IpAddress,
      er1646v2ATMImaCfgFrDlciIpNetm
         IpAddress,
      er1646v2ATMImaCfgFrDlciIpSNetName
         INTEGER,
      er1646v2ATMImaCfgFrDlciIpSNetCust
         DisplayString,
      er1646v2ATMImaCfgFrDlciIpRem
         IpAddress,
      er1646v2ATMImaCfgFrDlciIpMtu
         Integer32,
      er1646v2ATMImaCfgFrDlciIpMssAdjust
         INTEGER,
      er1646v2ATMImaCfgFrDlciIpRipMetric
         Integer32,
      er1646v2ATMImaCfgFrDlciIpRipMetricOut
         Integer32,
      er1646v2ATMImaCfgFrDlciIpRipMode
         INTEGER,
      er1646v2ATMImaCfgFrDlciIpRipTxVer
         INTEGER,
      er1646v2ATMImaCfgFrDlciIpRipRxVer
         INTEGER,
      er1646v2ATMImaCfgFrDlciIpRipSplitH
         INTEGER,
      er1646v2ATMImaCfgFrDlciIpRipAuth
         INTEGER,
      er1646v2ATMImaCfgFrDlciIpRipFilter
         DisplayString,
      er1646v2ATMImaCfgFrDlciIpRipFilterIn
         DisplayString,
      er1646v2ATMImaCfgFrDlciIpRipClearNextHop
         INTEGER,
      er1646v2ATMImaCfgFrDlciIpAccPol
         DisplayString,
      er1646v2ATMImaCfgFrDlciIpAB
         DisplayString,
      er1646v2ATMImaCfgFrDlciIpMA
         INTEGER,
      er1646v2ATMImaCfgFrDlciIpMF
         Integer32,
      er1646v2ATMImaCfgFrDlciIpDB
         INTEGER,
      er1646v2ATMImaCfgFrDlciIpIR
         INTEGER,
      er1646v2ATMImaCfgFrDlciIpIgmp
         INTEGER,
      er1646v2ATMImaCfgFrDlciIpNN
         DisplayString,
      er1646v2ATMImaCfgFrDlciIpPimMode
         INTEGER,
      er1646v2ATMImaCfgFrDlciIpPimDrPriority
         Counter32,
      er1646v2ATMImaCfgFrDlciIpPimHelloTime
         TimeTicks,
      er1646v2ATMImaCfgFrDlciIpPimPropagationDelay
         TimeTicks,
      er1646v2ATMImaCfgFrDlciIpPimOverrideInterval
         TimeTicks,
      er1646v2ATMImaCfgFrDlciIpPimBsrBorder
         INTEGER,
      er1646v2ATMImaCfgFrDlciIpPimTtlThreshold
         Integer32,
      er1646v2ATMImaCfgFrDlciIpIMNetworkUnreachable
         INTEGER,
      er1646v2ATMImaCfgFrDlciIpIMHostUnreachable
         INTEGER,
      er1646v2ATMImaCfgFrDlciIpIMProtocolUnreachable
         INTEGER,
      er1646v2ATMImaCfgFrDlciIpIMPortUnreachable
         INTEGER,
      er1646v2ATMImaCfgFrDlciIpIMMtuExceeded
         INTEGER,
      er1646v2ATMImaCfgFrDlciIpIMAdminProhibited
         INTEGER,
      er1646v2ATMImaCfgFrDlciIpIMTtlExceeded
         INTEGER,
      er1646v2ATMImaCfgFrDlciIpIMRedirect
         INTEGER,
      er1646v2ATMImaCfgFrDlciBridgingAccList
         DisplayString,
      er1646v2ATMImaCfgFrDlciBridgingInACL
         DisplayString,
      er1646v2ATMImaCfgFrDlciBridgingTp
         DisplayString,
      er1646v2ATMImaCfgFrDlciBridgingBrGrp
         DisplayString,
      er1646v2ATMImaCfgFrDlciBridgingLimBC
         INTEGER,
      er1646v2ATMImaCfgFrDlciBridgingPrivateMode
         INTEGER,
      er1646v2ATMImaCfgFrDlciBridgingLearning
         INTEGER,
      er1646v2ATMImaCfgFrDlciBridgingMaxCacheSize
         INTEGER,
      er1646v2ATMImaCfgFrDlciBridgingRelearnDropOnRelearn
         INTEGER,
      er1646v2ATMImaCfgFrDlciBridgingRelearnShutdownThreshold
         Integer32,
      er1646v2ATMImaCfgFrDlciBridgingRelearnShutdownTime
         TimeTicks,
      er1646v2ATMImaCfgFrDlciBridgingRelearnLoopDetection
         INTEGER,
      er1646v2ATMImaCfgFrDlciBridgingRelearnLoopDetectionInterval
         TimeTicks,
      er1646v2ATMImaCfgFrDlciBridgingVlanMemberShip
         INTEGER,
      er1646v2ATMImaCfgFrDlciBridgingVlTUntaggedAction
         INTEGER,
      er1646v2ATMImaCfgFrDlciBridgingVlTUntaggedTagInfoTpid
         INTEGER,
      er1646v2ATMImaCfgFrDlciBridgingVlTUntaggedTagInfoVid
         Integer32,
      er1646v2ATMImaCfgFrDlciBridgingVlTUnknownVlansAction
         INTEGER,
      er1646v2ATMImaCfgFrDlciBridgingVlTUnknownVlansTagInfoTpid
         INTEGER,
      er1646v2ATMImaCfgFrDlciBridgingVlTUnknownVlansTagInfoVid
         Integer32,
      er1646v2ATMImaCfgFrDlciBridgingDot1adType
         INTEGER,
      er1646v2ATMImaCfgFrDlciBridgingPriority
         Integer32,
      er1646v2ATMImaCfgFrDlciBridgingPathCost
         Integer32,
      er1646v2ATMImaCfgFrDlciBridgingInternalPathCost
         Integer32,
      er1646v2ATMImaCfgFrDlciBridgingTCD
         INTEGER,
      er1646v2ATMImaCfgFrDlciBridgingRestrictedRole
         INTEGER,
      er1646v2ATMImaCfgFrDlciBridgingAdminEdge
         INTEGER,
      er1646v2ATMImaCfgFrDlciBridgingOamMacDeviceMac
         DisplayString,
      er1646v2ATMImaCfgFrDlciBridgingOamMacUserMac
         OCTET STRING,
      er1646v2ATMImaCfgFrDlciBridgingOamMacBridgeMac
         DisplayString,
      er1646v2ATMImaCfgFrDlciBridgingMgmtInline
         INTEGER,
      er1646v2ATMImaCfgFrDlciBridgingL2ptMode
         INTEGER,
      er1646v2ATMImaCfgFrDlciBridgingL2ptProtocols
         Integer32,
      er1646v2ATMImaCfgFrDlciBridgingL2ptDestMac
         OCTET STRING,
      er1646v2ATMImaCfgFrDlciBridgingL2ptCos
         INTEGER,
      er1646v2ATMImaCfgFrDlciBridgingL2ptDropThrStp
         INTEGER,
      er1646v2ATMImaCfgFrDlciBridgingL2ptDropThrLldp
         INTEGER,
      er1646v2ATMImaCfgFrDlciBridgingL2ptDropThrOam
         INTEGER,
      er1646v2ATMImaCfgFrDlciBridgingL2ptDropThrCdp
         INTEGER,
      er1646v2ATMImaCfgFrDlciBridgingL2ptDropThrVtp
         INTEGER,
      er1646v2ATMImaCfgFrDlciBridgingL2ptDropThrLacp
         INTEGER,
      er1646v2ATMImaCfgFrDlciBridgingL2ptDropThrEfmOam
         INTEGER,
      er1646v2ATMImaCfgFrDlciBridgingL2ptDropThrPvst
         INTEGER,
      er1646v2ATMImaCfgFrDlciBridgingL2ptDropThrMmrp
         INTEGER,
      er1646v2ATMImaCfgFrDlciBridgingL2ptDropThrMvrp
         INTEGER,
      er1646v2ATMImaCfgFrDlciBridgingL2ptDropThrGvrp
         INTEGER,
      er1646v2ATMImaCfgFrDlciBridgingL2ptDropThrGmrp
         INTEGER,
      er1646v2ATMImaCfgFrDlciBridgingL2ptDropThrDtp
         INTEGER,
      er1646v2ATMImaCfgFrDlciBridgingL2ptDropThrPagp
         INTEGER,
      er1646v2ATMImaCfgFrDlciBridgingL2ptDropThrUdld
         INTEGER,
      er1646v2ATMImaCfgFrDlciFrDlci
         Integer32,
      er1646v2ATMImaCfgFrDlciFrCir
         Integer32,
      er1646v2ATMImaCfgFrDlciFrOverhead
         Integer32,
      er1646v2ATMImaCfgFrDlciFrTc
         Integer32,
      er1646v2ATMImaCfgFrDlciFrSlidingWindow
         INTEGER,
      er1646v2ATMImaCfgFrDlciFrDeBitSet
         INTEGER,
      er1646v2ATMImaCfgFrDlciFrDefaultQueue
         INTEGER,
      er1646v2ATMImaCfgFrDlciFrRxCir
         Integer32,
      er1646v2ATMImaCfgFrDlciFrRxExcess
         INTEGER,
      er1646v2ATMImaCfgFrDlciFrFragEMode
         INTEGER
      }

er1646v2ATMImaCfgFrDlciActions OBJECT-TYPE
   SYNTAX      VariableLengthTableActions
   MAX-ACCESS  read-write
   STATUS      current
   DESCRIPTION
      "By way of this field, some manipulations
       on this table may be performed."
   ::= {er1646v2ATMImaCfgFrDlciEntry 2}

er1646v2ATMImaCfgFrDlciTableIx OBJECT-TYPE
   SYNTAX      TableIndex
   MAX-ACCESS  not-accessible
   STATUS      current
   DESCRIPTION
      ""
   ::= {er1646v2ATMImaCfgFrDlciEntry 11}

er1646v2ATMImaCfgFrDlciName OBJECT-TYPE
   SYNTAX      DisplayString
   MAX-ACCESS  read-write
   STATUS      current
   DESCRIPTION
      "Path: atm.editConf.pvcTable.frameRelay.dlciTable.name"
   ::= {er1646v2ATMImaCfgFrDlciEntry 16777216}

er1646v2ATMImaCfgFrDlciAdminStatus OBJECT-TYPE
   SYNTAX      INTEGER
               {
               up (1),
               down (2)
               }
   MAX-ACCESS  read-write
   STATUS      current
   DESCRIPTION
      "Path: atm.editConf.pvcTable.frameRelay.dlciTable.adminStatus

       Possibilities:
               up   (1)
               down   (2)"
   ::= {er1646v2ATMImaCfgFrDlciEntry 33554432}

er1646v2ATMImaCfgFrDlciMode OBJECT-TYPE
   SYNTAX      INTEGER
               {
               routing (1),
               bridging (2),
               routingAndBridging (3)
               }
   MAX-ACCESS  read-write
   STATUS      current
   DESCRIPTION
      "Path: atm.editConf.pvcTable.frameRelay.dlciTable.mode

       Possibilities:
               routing   (1)
               bridging   (2)
               routingAndBridging   (3)"
   ::= {er1646v2ATMImaCfgFrDlciEntry 67108864}

er1646v2ATMImaCfgFrDlciIpVrfRouter OBJECT-TYPE
   SYNTAX      DisplayString
   MAX-ACCESS  read-write
   STATUS      current
   DESCRIPTION
      "Path: atm.editConf.pvcTable.frameRelay.dlciTable.ip.vrfRouter"
   ::= {er1646v2ATMImaCfgFrDlciEntry 53215232}

er1646v2ATMImaCfgFrDlciIpAdr OBJECT-TYPE
   SYNTAX      IpAddress
   MAX-ACCESS  read-write
   STATUS      current
   DESCRIPTION
      "Path: atm.editConf.pvcTable.frameRelay.dlciTable.ip.address"
   ::= {er1646v2ATMImaCfgFrDlciEntry 58261504}

er1646v2ATMImaCfgFrDlciIpNetm OBJECT-TYPE
   SYNTAX      IpAddress
   MAX-ACCESS  read-write
   STATUS      current
   DESCRIPTION
      "Path: atm.editConf.pvcTable.frameRelay.dlciTable.ip.netMask"
   ::= {er1646v2ATMImaCfgFrDlciEntry 58392576}

er1646v2ATMImaCfgFrDlciIpSNetName OBJECT-TYPE
   SYNTAX      INTEGER
               {
               slOPTg (0),
               corp (2),
               dmz (3),
               internet (1)
               }
   MAX-ACCESS  read-write
   STATUS      current
   DESCRIPTION
      "Path: atm.editConf.pvcTable.frameRelay.dlciTable.ip.sNet.name

       Possibilities:
               <OPT>   (0)
               corp   (2)
               dmz   (3)
               internet   (1)"
   ::= {er1646v2ATMImaCfgFrDlciEntry 53674240}

er1646v2ATMImaCfgFrDlciIpSNetCust OBJECT-TYPE
   SYNTAX      DisplayString
   MAX-ACCESS  read-write
   STATUS      current
   DESCRIPTION
      "Path: atm.editConf.pvcTable.frameRelay.dlciTable.ip.sNet.custom"
   ::= {er1646v2ATMImaCfgFrDlciEntry 53674496}

er1646v2ATMImaCfgFrDlciIpRem OBJECT-TYPE
   SYNTAX      IpAddress
   MAX-ACCESS  read-write
   STATUS      current
   DESCRIPTION
      "Path: atm.editConf.pvcTable.frameRelay.dlciTable.ip.remote"
   ::= {er1646v2ATMImaCfgFrDlciEntry 58458112}

er1646v2ATMImaCfgFrDlciIpMtu OBJECT-TYPE
   SYNTAX      Integer32
   MAX-ACCESS  read-write
   STATUS      current
   DESCRIPTION
      "Path: atm.editConf.pvcTable.frameRelay.dlciTable.ip.mtu"
   ::= {er1646v2ATMImaCfgFrDlciEntry 52953088}

er1646v2ATMImaCfgFrDlciIpMssAdjust OBJECT-TYPE
   SYNTAX      INTEGER
               {
               disabled (0),
               auto (65536)
               }
   MAX-ACCESS  read-write
   STATUS      current
   DESCRIPTION
      "Path: atm.editConf.pvcTable.frameRelay.dlciTable.ip.mssAdjust

       Possibilities:
               disabled   (0)
               auto   (65536)"
   ::= {er1646v2ATMImaCfgFrDlciEntry 53280768}

er1646v2ATMImaCfgFrDlciIpRipMetric OBJECT-TYPE
   SYNTAX      Integer32
   MAX-ACCESS  read-write
   STATUS      current
   DESCRIPTION
      "Path: atm.editConf.pvcTable.frameRelay.dlciTable.ip.rip.metric"
   ::= {er1646v2ATMImaCfgFrDlciEntry 51712768}

er1646v2ATMImaCfgFrDlciIpRipMetricOut OBJECT-TYPE
   SYNTAX      Integer32
   MAX-ACCESS  read-write
   STATUS      current
   DESCRIPTION
      "Path: atm.editConf.pvcTable.frameRelay.dlciTable.ip.rip.metricOut"
   ::= {er1646v2ATMImaCfgFrDlciEntry 51713024}

er1646v2ATMImaCfgFrDlciIpRipMode OBJECT-TYPE
   SYNTAX      INTEGER
               {
               disabled (0),
               passive (1),
               active (2)
               }
   MAX-ACCESS  read-write
   STATUS      current
   DESCRIPTION
      "Path: atm.editConf.pvcTable.frameRelay.dlciTable.ip.rip.mode

       Possibilities:
               disabled   (0)
               passive   (1)
               active   (2)"
   ::= {er1646v2ATMImaCfgFrDlciEntry 51713280}

er1646v2ATMImaCfgFrDlciIpRipTxVer OBJECT-TYPE
   SYNTAX      INTEGER
               {
               rip1 (0),
               rip2 (1),
               rip1mcompatible (2)
               }
   MAX-ACCESS  read-write
   STATUS      current
   DESCRIPTION
      "Path: atm.editConf.pvcTable.frameRelay.dlciTable.ip.rip.txVersion

       Possibilities:
               rip1   (0)
               rip2   (1)
               rip1-compatible   (2)"
   ::= {er1646v2ATMImaCfgFrDlciEntry 51716864}

er1646v2ATMImaCfgFrDlciIpRipRxVer OBJECT-TYPE
   SYNTAX      INTEGER
               {
               rip1only (0),
               rip2only (1),
               rip12 (2)
               }
   MAX-ACCESS  read-write
   STATUS      current
   DESCRIPTION
      "Path: atm.editConf.pvcTable.frameRelay.dlciTable.ip.rip.rxVersion

       Possibilities:
               rip1only   (0)
               rip2only   (1)
               rip1&2   (2)"
   ::= {er1646v2ATMImaCfgFrDlciEntry 51717120}

er1646v2ATMImaCfgFrDlciIpRipSplitH OBJECT-TYPE
   SYNTAX      INTEGER
               {
               disabled (0),
               enabled (1),
               poisonedReverse (2)
               }
   MAX-ACCESS  read-write
   STATUS      current
   DESCRIPTION
      "Path: atm.editConf.pvcTable.frameRelay.dlciTable.ip.rip.splitHorizon

       Possibilities:
               disabled   (0)
               enabled   (1)
               poisonedReverse   (2)"
   ::= {er1646v2ATMImaCfgFrDlciEntry 51713792}

er1646v2ATMImaCfgFrDlciIpRipAuth OBJECT-TYPE
   SYNTAX      INTEGER
               {
               disabled (0),
               texts (1),
               md5 (2)
               }
   MAX-ACCESS  read-write
   STATUS      current
   DESCRIPTION
      "Path: atm.editConf.pvcTable.frameRelay.dlciTable.ip.rip.authentication

       Possibilities:
               disabled   (0)
               text    (1)
               md5   (2)"
   ::= {er1646v2ATMImaCfgFrDlciEntry 51712512}

er1646v2ATMImaCfgFrDlciIpRipFilter OBJECT-TYPE
   SYNTAX      DisplayString
   MAX-ACCESS  read-write
   STATUS      current
   DESCRIPTION
      "Path: atm.editConf.pvcTable.frameRelay.dlciTable.ip.rip.filter"
   ::= {er1646v2ATMImaCfgFrDlciEntry 51716096}

er1646v2ATMImaCfgFrDlciIpRipFilterIn OBJECT-TYPE
   SYNTAX      DisplayString
   MAX-ACCESS  read-write
   STATUS      current
   DESCRIPTION
      "Path: atm.editConf.pvcTable.frameRelay.dlciTable.ip.rip.filterIn"
   ::= {er1646v2ATMImaCfgFrDlciEntry 51716352}

er1646v2ATMImaCfgFrDlciIpRipClearNextHop OBJECT-TYPE
   SYNTAX      INTEGER
               {
               disabled (0),
               enabled (1)
               }
   MAX-ACCESS  read-write
   STATUS      current
   DESCRIPTION
      "Path: atm.editConf.pvcTable.frameRelay.dlciTable.ip.rip.clearNextHop

       Possibilities:
               disabled   (0)
               enabled   (1)"
   ::= {er1646v2ATMImaCfgFrDlciEntry 51708416}

er1646v2ATMImaCfgFrDlciIpAccPol OBJECT-TYPE
   SYNTAX      DisplayString
   MAX-ACCESS  read-write
   STATUS      current
   DESCRIPTION
      "Path: atm.editConf.pvcTable.frameRelay.dlciTable.ip.accessPolicy"
   ::= {er1646v2ATMImaCfgFrDlciEntry 53084160}

er1646v2ATMImaCfgFrDlciIpAB OBJECT-TYPE
   SYNTAX      DisplayString
   MAX-ACCESS  read-write
   STATUS      current
   DESCRIPTION
      "Path: atm.editConf.pvcTable.frameRelay.dlciTable.ip.trafficPolicy"
   ::= {er1646v2ATMImaCfgFrDlciEntry 51249152}

er1646v2ATMImaCfgFrDlciIpMA OBJECT-TYPE
   SYNTAX      INTEGER
               {
               disabled (0),
               enabled (1)
               }
   MAX-ACCESS  read-write
   STATUS      current
   DESCRIPTION
      "Path: atm.editConf.pvcTable.frameRelay.dlciTable.ip.mgmtAccess

       Possibilities:
               disabled   (0)
               enabled   (1)"
   ::= {er1646v2ATMImaCfgFrDlciEntry 51380224}

er1646v2ATMImaCfgFrDlciIpMF OBJECT-TYPE
   SYNTAX      Integer32
   MAX-ACCESS  read-write
   STATUS      current
   DESCRIPTION
      "Path: atm.editConf.pvcTable.frameRelay.dlciTable.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2ATMImaCfgFrDlciEntry 51445760}

er1646v2ATMImaCfgFrDlciIpDB OBJECT-TYPE
   SYNTAX      INTEGER
               {
               disabled (0),
               enabled (1)
               }
   MAX-ACCESS  read-write
   STATUS      current
   DESCRIPTION
      "Path: atm.editConf.pvcTable.frameRelay.dlciTable.ip.directedBroadcasts

       Possibilities:
               disabled   (0)
               enabled   (1)"
   ::= {er1646v2ATMImaCfgFrDlciEntry 51773440}

er1646v2ATMImaCfgFrDlciIpIR OBJECT-TYPE
   SYNTAX      INTEGER
               {
               disabled (0),
               enabled (1)
               }
   MAX-ACCESS  read-write
   STATUS      current
   DESCRIPTION
      "Path: atm.editConf.pvcTable.frameRelay.dlciTable.ip.icmpRedirects

       Possibilities:
               disabled   (0)
               enabled   (1)"
   ::= {er1646v2ATMImaCfgFrDlciEntry 52035584}

er1646v2ATMImaCfgFrDlciIpIgmp OBJECT-TYPE
   SYNTAX      INTEGER
               {
               disabled (0),
               proxy (1),
               router (2),
               v3Router (5)
               }
   MAX-ACCESS  read-write
   STATUS      current
   DESCRIPTION
      "Path: atm.editConf.pvcTable.frameRelay.dlciTable.ip.igmp

       Possibilities:
               disabled   (0)
               proxy   (1)
               router   (2)
               v3Router   (5)"
   ::= {er1646v2ATMImaCfgFrDlciEntry 52428800}

er1646v2ATMImaCfgFrDlciIpNN OBJECT-TYPE
   SYNTAX      DisplayString
   MAX-ACCESS  read-write
   STATUS      current
   DESCRIPTION
      "Path: atm.editConf.pvcTable.frameRelay.dlciTable.ip.nat"
   ::= {er1646v2ATMImaCfgFrDlciEntry 52101120}

er1646v2ATMImaCfgFrDlciIpPimMode OBJECT-TYPE
   SYNTAX      INTEGER
               {
               disabled (0),
               sparse (1),
               passive (2)
               }
   MAX-ACCESS  read-write
   STATUS      current
   DESCRIPTION
      "Path: atm.editConf.pvcTable.frameRelay.dlciTable.ip.pim.mode

       Possibilities:
               disabled   (0)
               sparse   (1)
               passive   (2)"
   ::= {er1646v2ATMImaCfgFrDlciEntry 53346560}

er1646v2ATMImaCfgFrDlciIpPimDrPriority OBJECT-TYPE
   SYNTAX      Counter32
   MAX-ACCESS  read-write
   STATUS      current
   DESCRIPTION
      "Path: atm.editConf.pvcTable.frameRelay.dlciTable.ip.pim.drPriority

       32 bit unsigned wrappable counter."
   ::= {er1646v2ATMImaCfgFrDlciEntry 53346816}

er1646v2ATMImaCfgFrDlciIpPimHelloTime OBJECT-TYPE
   SYNTAX      TimeTicks
   MAX-ACCESS  read-write
   STATUS      current
   DESCRIPTION
      "Path: atm.editConf.pvcTable.frameRelay.dlciTable.ip.pim.helloTime

       Time in centi-second."
   ::= {er1646v2ATMImaCfgFrDlciEntry 53347072}

er1646v2ATMImaCfgFrDlciIpPimPropagationDelay OBJECT-TYPE
   SYNTAX      TimeTicks
   MAX-ACCESS  read-write
   STATUS      current
   DESCRIPTION
      "Path: atm.editConf.pvcTable.frameRelay.dlciTable.ip.pim.propagationDelay

       Time in centi-second."
   ::= {er1646v2ATMImaCfgFrDlciEntry 53347328}

er1646v2ATMImaCfgFrDlciIpPimOverrideInterval OBJECT-TYPE
   SYNTAX      TimeTicks
   MAX-ACCESS  read-write
   STATUS      current
   DESCRIPTION
      "Path: atm.editConf.pvcTable.frameRelay.dlciTable.ip.pim.overrideInterval

       Time in centi-second."
   ::= {er1646v2ATMImaCfgFrDlciEntry 53347584}

er1646v2ATMImaCfgFrDlciIpPimBsrBorder OBJECT-TYPE
   SYNTAX      INTEGER
               {
               disabled (0),
               enabled (1)
               }
   MAX-ACCESS  read-write
   STATUS      current
   DESCRIPTION
      "Path: atm.editConf.pvcTable.frameRelay.dlciTable.ip.pim.bsrBorder

       Possibilities:
               disabled   (0)
               enabled   (1)"
   ::= {er1646v2ATMImaCfgFrDlciEntry 53347840}

er1646v2ATMImaCfgFrDlciIpPimTtlThreshold OBJECT-TYPE
   SYNTAX      Integer32
   MAX-ACCESS  read-write
   STATUS      current
   DESCRIPTION
      "Path: atm.editConf.pvcTable.frameRelay.dlciTable.ip.pim.ttlThreshold"
   ::= {er1646v2ATMImaCfgFrDlciEntry 53348096}

er1646v2ATMImaCfgFrDlciIpIMNetworkUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.networkUnreachable

       Possibilities:
               disabled   (0)
               enabled   (1)"
   ::= {er1646v2ATMImaCfgFrDlciEntry 53412096}

er1646v2ATMImaCfgFrDlciIpIMHostUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.hostUnreachable

       Possibilities:
               disabled   (0)
               enabled   (1)"
   ::= {er1646v2ATMImaCfgFrDlciEntry 53412352}

er1646v2ATMImaCfgFrDlciIpIMProtocolUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.protocolUnreachable

       Possibilities:
               disabled   (0)
               enabled   (1)"
   ::= {er1646v2ATMImaCfgFrDlciEntry 53412608}

er1646v2ATMImaCfgFrDlciIpIMPortUnreachable OBJECT-TYPE
   SYNTAX      INTEGER
               {
               disabled (0),
               enabled (1)
               }
   MAX-ACCESS  read-write
   STATUS      current
   DESCRIPTION
      "Path: atm.editConf.pvcTable.frameRelay.dlciTable.ip.icmpMessages.portUnreachable

       Possibilities:
               disabled   (0)
               enabled   (1)"
   ::= {er1646v2ATMImaCfgFrDlciEntry 53412864}

er1646v2ATMImaCfgFrDlciIpIMMtuExceeded OBJECT-TYPE
   SYNTAX      INTEGER
               {
               disabled (0),
               enabled (1)
               }
   MAX-ACCESS  read-write
   STATUS      current
   DESCRIPTION
      "Path: atm.editConf.pvcTable.frameRelay.dlciTable.ip.icmpMessages.mtuExceeded

       Possibilities:
               disabled   (0)
               enabled   (1)"
   ::= {er1646v2ATMImaCfgFrDlciEntry 53413120}

er1646v2ATMImaCfgFrDlciIpIMAdminProhibited OBJECT-TYPE
   SYNTAX      INTEGER
               {
               disabled (0),
               enabled (1)
               }
   MAX-ACCESS  read-write
   STATUS      current
   DESCRIPTION
      "Path: atm.editConf.pvcTable.frameRelay.dlciTable.ip.icmpMessages.adminProhibited

       Possibilities:
               disabled   (0)
               enabled   (1)"
   ::= {er1646v2ATMImaCfgFrDlciEntry 53413376}

er1646v2ATMImaCfgFrDlciIpIMTtlExceeded OBJECT-TYPE
   SYNTAX      INTEGER
               {
               disabled (0),
               enabled (1)
               }
   MAX-ACCESS  read-write
   STATUS      current
   DESCRIPTION
      "Path: atm.editConf.pvcTable.frameRelay.dlciTable.ip.icmpMessages.ttlExceeded

       Possibilities:
               disabled   (0)
               enabled   (1)"
   ::= {er1646v2ATMImaCfgFrDlciEntry 53413632}

er1646v2ATMImaCfgFrDlciIpIMRedirect OBJECT-TYPE
   SYNTAX      INTEGER
               {
               disabled (0),
               enabled (1)
               }
   MAX-ACCESS  read-write
   STATUS      current
   DESCRIPTION
      "Path: atm.editConf.pvcTable.frameRelay.dlciTable.ip.icmpMessages.redirect

       Possibilities:
               disabled   (0)
               enabled   (1)"
   ::= {er1646v2ATMImaCfgFrDlciEntry 53413888}

er1646v2ATMImaCfgFrDlciBridgingAccList OBJECT-TYPE
   SYNTAX      DisplayString
   MAX-ACCESS  read-write
   STATUS      current
   DESCRIPTION
      "Path: atm.editConf.pvcTable.frameRelay.dlciTable.bridging.accessList"
   ::= {er1646v2ATMImaCfgFrDlciEntry 453246976}

er1646v2ATMImaCfgFrDlciBridgingInACL OBJECT-TYPE
   SYNTAX      DisplayString
   MAX-ACCESS  read-write
   STATUS      current
   DESCRIPTION
      "Path: atm.editConf.pvcTable.frameRelay.dlciTable.bridging.inAccessList"
   ::= {er1646v2ATMImaCfgFrDlciEntry 456916992}

er1646v2ATMImaCfgFrDlciBridgingTp OBJECT-TYPE
   SYNTAX      DisplayString
   MAX-ACCESS  read-write
   STATUS      current
   DESCRIPTION
      "Path: atm.editConf.pvcTable.frameRelay.dlciTable.bridging.trafficPolicy"
   ::= {er1646v2ATMImaCfgFrDlciEntry 454295552}

er1646v2ATMImaCfgFrDlciBridgingBrGrp OBJECT-TYPE
   SYNTAX      DisplayString
   MAX-ACCESS  read-write
   STATUS      current
   DESCRIPTION
      "Path: atm.editConf.pvcTable.frameRelay.dlciTable.bridging.bridgeGroup"
   ::= {er1646v2ATMImaCfgFrDlciEntry 454819840}

er1646v2ATMImaCfgFrDlciBridgingLimBC OBJECT-TYPE
   SYNTAX      INTEGER
               {
               disabled (0),
               enabled (1)
               }
   MAX-ACCESS  read-write
   STATUS      current
   DESCRIPTION
      "Path: atm.editConf.pvcTable.frameRelay.dlciTable.bridging.limitBroadcasts

       Possibilities:
               disabled   (0)
               enabled   (1)"
   ::= {er1646v2ATMImaCfgFrDlciEntry 455081984}

er1646v2ATMImaCfgFrDlciBridgingPrivateMode OBJECT-TYPE
   SYNTAX      INTEGER
               {
               disabled (0),
               enabled (1)
               }
   MAX-ACCESS  read-write
   STATUS      current
   DESCRIPTION
      "Path: atm.editConf.pvcTable.frameRelay.dlciTable.bridging.privateMode

       Possibilities:
               disabled   (0)
               enabled   (1)"
   ::= {er1646v2ATMImaCfgFrDlciEntry 459538432}

er1646v2ATMImaCfgFrDlciBridgingLearning OBJECT-TYPE
   SYNTAX      INTEGER
               {
               disabled (0),
               enabled (1)
               }
   MAX-ACCESS  read-write
   STATUS      current
   DESCRIPTION
      "Path: atm.editConf.pvcTable.frameRelay.dlciTable.bridging.learning

       Possibilities:
               disabled   (0)
               enabled   (1)"
   ::= {er1646v2ATMImaCfgFrDlciEntry 456130560}

er1646v2ATMImaCfgFrDlciBridgingMaxCacheSize OBJECT-TYPE
   SYNTAX      INTEGER
               {
               unlimited (0)
               }
   MAX-ACCESS  read-write
   STATUS      current
   DESCRIPTION
      "Path: atm.editConf.pvcTable.frameRelay.dlciTable.bridging.maxCacheSize

       Possibilities:
               unlimited   (0)"
   ::= {er1646v2ATMImaCfgFrDlciEntry 456392704}

er1646v2ATMImaCfgFrDlciBridgingRelearnDropOnRelearn OBJECT-TYPE
   SYNTAX      INTEGER
               {
               disabled (0),
               enabled (1)
               }
   MAX-ACCESS  read-write
   STATUS      current
   DESCRIPTION
      "Path: atm.editConf.pvcTable.frameRelay.dlciTable.bridging.relearn.dropOnRelearn

       Possibilities:
               disabled   (0)
               enabled   (1)"
   ::= {er1646v2ATMImaCfgFrDlciEntry 456655872}

er1646v2ATMImaCfgFrDlciBridgingRelearnShutdownThreshold OBJECT-TYPE
   SYNTAX      Integer32
   MAX-ACCESS  read-write
   STATUS      current
   DESCRIPTION
      "Path: atm.editConf.pvcTable.frameRelay.dlciTable.bridging.relearn.shutdownThreshold"
   ::= {er1646v2ATMImaCfgFrDlciEntry 456656896}

er1646v2ATMImaCfgFrDlciBridgingRelearnShutdownTime OBJECT-TYPE
   SYNTAX      TimeTicks
   MAX-ACCESS  read-write
   STATUS      current
   DESCRIPTION
      "Path: atm.editConf.pvcTable.frameRelay.dlciTable.bridging.relearn.shutdownTime

       Time in centi-second."
   ::= {er1646v2ATMImaCfgFrDlciEntry 456657920}

er1646v2ATMImaCfgFrDlciBridgingRelearnLoopDetection OBJECT-TYPE
   SYNTAX      INTEGER
               {
               disabled (0),
               passive (1),
               active (2)
               }
   MAX-ACCESS  read-write
   STATUS      current
   DESCRIPTION
      "Path: atm.editConf.pvcTable.frameRelay.dlciTable.bridging.relearn.loopDetection

       Possibilities:
               disabled   (0)
               passive   (1)
               active   (2)"
   ::= {er1646v2ATMImaCfgFrDlciEntry 456658944}

er1646v2ATMImaCfgFrDlciBridgingRelearnLoopDetectionInterval OBJECT-TYPE
   SYNTAX      TimeTicks
   MAX-ACCESS  read-write
   STATUS      current
   DESCRIPTION
      "Path: atm.editConf.pvcTable.frameRelay.dlciTable.bridging.relearn.loopDetectionInterval

       Time in centi-second."
   ::= {er1646v2ATMImaCfgFrDlciEntry 456659968}

er1646v2ATMImaCfgFrDlciBridgingVlanMemberShip OBJECT-TYPE
   SYNTAX      INTEGER
               {
               all (0),
               none (1),
               grouped (2)
               }
   MAX-ACCESS  read-write
   STATUS      current
   DESCRIPTION
      "Path: atm.editConf.pvcTable.frameRelay.dlciTable.bridging.vlanMemberShip

       Possibilities:
               all   (0)
               none   (1)
               grouped   (2)"
   ::= {er1646v2ATMImaCfgFrDlciEntry 457965568}

er1646v2ATMImaCfgFrDlciBridgingVlTUntaggedAction OBJECT-TYPE
   SYNTAX      INTEGER
               {
               discard (0),
               accept (1),
               tag (2)
               }
   MAX-ACCESS  read-write
   STATUS      current
   DESCRIPTION
      "Path: atm.editConf.pvcTable.frameRelay.dlciTable.bridging.vlanTagging.untagged.action

       Possibilities:
               discard   (0)
               accept   (1)
               tag   (2)"
   ::= {er1646v2ATMImaCfgFrDlciEntry 459055104}

er1646v2ATMImaCfgFrDlciBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.frameRelay.dlciTable.bridging.vlanTagging.untagged.tagInfo.tpid

       Possibilities:
               dot1Q   (33024)
               dot1ad   (34984)
               0x9100   (37120)
               0x9200   (37376)
               0x9300   (37632)"
   ::= {er1646v2ATMImaCfgFrDlciEntry 459059712}

er1646v2ATMImaCfgFrDlciBridgingVlTUntaggedTagInfoVid OBJECT-TYPE
   SYNTAX      Integer32
   MAX-ACCESS  read-write
   STATUS      current
   DESCRIPTION
      "Path: atm.editConf.pvcTable.frameRelay.dlciTable.bridging.vlanTagging.untagged.tagInfo.vid"
   ::= {er1646v2ATMImaCfgFrDlciEntry 459060224}

er1646v2ATMImaCfgFrDlciBridgingVlTUnknownVlansAction OBJECT-TYPE
   SYNTAX      INTEGER
               {
               discard (0),
               accept (1),
               tag (2)
               }
   MAX-ACCESS  read-write
   STATUS      current
   DESCRIPTION
      "Path: atm.editConf.pvcTable.frameRelay.dlciTable.bridging.vlanTagging.unknownVlans.action

       Possibilities:
               discard   (0)
               accept   (1)
               tag   (2)"
   ::= {er1646v2ATMImaCfgFrDlciEntry 459120640}

er1646v2ATMImaCfgFrDlciBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.frameRelay.dlciTable.bridging.vlanTagging.unknownVlans.tagInfo.tpid

       Possibilities:
               dot1Q   (33024)
               dot1ad   (34984)
               0x9100   (37120)
               0x9200   (37376)
               0x9300   (37632)"
   ::= {er1646v2ATMImaCfgFrDlciEntry 459125248}

er1646v2ATMImaCfgFrDlciBridgingVlTUnknownVlansTagInfoVid OBJECT-TYPE
   SYNTAX      Integer32
   MAX-ACCESS  read-write
   STATUS      current
   DESCRIPTION
      "Path: atm.editConf.pvcTable.frameRelay.dlciTable.bridging.vlanTagging.unknownVlans.tagInfo.vid"
   ::= {er1646v2ATMImaCfgFrDlciEntry 459125760}

er1646v2ATMImaCfgFrDlciBridgingDot1adType OBJECT-TYPE
   SYNTAX      INTEGER
               {
               slOPTg (0),
               cPort (4),
               sPort (1),
               nni (2)
               }
   MAX-ACCESS  read-write
   STATUS      current
   DESCRIPTION
      "Path: atm.editConf.pvcTable.frameRelay.dlciTable.bridging.dot1ad.type

       Possibilities:
               <OPT>   (0)
               cPort   (4)
               sPort   (1)
               nni   (2)"
   ::= {er1646v2ATMImaCfgFrDlciEntry 460850176}

er1646v2ATMImaCfgFrDlciBridgingPriority OBJECT-TYPE
   SYNTAX      Integer32
   MAX-ACCESS  read-write
   STATUS      current
   DESCRIPTION
      "Path: atm.editConf.pvcTable.frameRelay.dlciTable.bridging.priority"
   ::= {er1646v2ATMImaCfgFrDlciEntry 453509120}

er1646v2ATMImaCfgFrDlciBridgingPathCost OBJECT-TYPE
   SYNTAX      Integer32
   MAX-ACCESS  read-write
   STATUS      current
   DESCRIPTION
      "Path: atm.editConf.pvcTable.frameRelay.dlciTable.bridging.pathCost"
   ::= {er1646v2ATMImaCfgFrDlciEntry 453771264}

er1646v2ATMImaCfgFrDlciBridgingInternalPathCost OBJECT-TYPE
   SYNTAX      Integer32
   MAX-ACCESS  read-write
   STATUS      current
   DESCRIPTION
      "Path: atm.editConf.pvcTable.frameRelay.dlciTable.bridging.internalPathCost"
   ::= {er1646v2ATMImaCfgFrDlciEntry 457703424}

er1646v2ATMImaCfgFrDlciBridgingTCD OBJECT-TYPE
   SYNTAX      INTEGER
               {
               disabled (0),
               enabled (1)
               }
   MAX-ACCESS  read-write
   STATUS      current
   DESCRIPTION
      "Path: atm.editConf.pvcTable.frameRelay.dlciTable.bridging.topologyChangeDetection

       Possibilities:
               disabled   (0)
               enabled   (1)"
   ::= {er1646v2ATMImaCfgFrDlciEntry 454033408}

er1646v2ATMImaCfgFrDlciBridgingRestrictedRole OBJECT-TYPE
   SYNTAX      INTEGER
               {
               disabled (0),
               enabled (1)
               }
   MAX-ACCESS  read-write
   STATUS      current
   DESCRIPTION
      "Path: atm.editConf.pvcTable.frameRelay.dlciTable.bridging.restrictedRole

       Possibilities:
               disabled   (0)
               enabled   (1)"
   ::= {er1646v2ATMImaCfgFrDlciEntry 458227712}

er1646v2ATMImaCfgFrDlciBridgingAdminEdge OBJECT-TYPE
   SYNTAX      INTEGER
               {
               disabled (0),
               enabled (1)
               }
   MAX-ACCESS  read-write
   STATUS      current
   DESCRIPTION
      "Path: atm.editConf.pvcTable.frameRelay.dlciTable.bridging.adminEdge

       Possibilities:
               disabled   (0)
               enabled   (1)"
   ::= {er1646v2ATMImaCfgFrDlciEntry 457179136}

er1646v2ATMImaCfgFrDlciBridgingOamMacDeviceMac OBJECT-TYPE
   SYNTAX      DisplayString
   MAX-ACCESS  read-write
   STATUS      current
   DESCRIPTION
      "Path: atm.editConf.pvcTable.frameRelay.dlciTable.bridging.ethOam.macAddress.deviceMac"
   ::= {er1646v2ATMImaCfgFrDlciEntry 458506496}

er1646v2ATMImaCfgFrDlciBridgingOamMacUserMac OBJECT-TYPE
   SYNTAX      OCTET STRING
   MAX-ACCESS  read-write
   STATUS      current
   DESCRIPTION
      "Path: atm.editConf.pvcTable.frameRelay.dlciTable.bridging.ethOam.macAddress.userMac

       MAC address."
   ::= {er1646v2ATMImaCfgFrDlciEntry 458506368}

er1646v2ATMImaCfgFrDlciBridgingOamMacBridgeMac OBJECT-TYPE
   SYNTAX      DisplayString
   MAX-ACCESS  read-write
   STATUS      current
   DESCRIPTION
      "Path: atm.editConf.pvcTable.frameRelay.dlciTable.bridging.ethOam.macAddress.bridgeMac"
   ::= {er1646v2ATMImaCfgFrDlciEntry 458506432}

er1646v2ATMImaCfgFrDlciBridgingMgmtInline OBJECT-TYPE
   SYNTAX      INTEGER
               {
               disabled (0),
               enabled (1)
               }
   MAX-ACCESS  read-write
   STATUS      current
   DESCRIPTION
      "Path: atm.editConf.pvcTable.frameRelay.dlciTable.bridging.mgmtInline

       Possibilities:
               disabled   (0)
               enabled   (1)"
   ::= {er1646v2ATMImaCfgFrDlciEntry 458752000}

er1646v2ATMImaCfgFrDlciBridgingL2ptMode OBJECT-TYPE
   SYNTAX      INTEGER
               {
               disabled (0),
               enabled (1)
               }
   MAX-ACCESS  read-write
   STATUS      current
   DESCRIPTION
      "Path: atm.editConf.pvcTable.frameRelay.dlciTable.bridging.l2ProtTunnel.mode

       Possibilities:
               disabled   (0)
               enabled   (1)"
   ::= {er1646v2ATMImaCfgFrDlciEntry 459292672}

er1646v2ATMImaCfgFrDlciBridgingL2ptProtocols OBJECT-TYPE
   SYNTAX      Integer32
   MAX-ACCESS  read-write
   STATUS      current
   DESCRIPTION
      "Path: atm.editConf.pvcTable.frameRelay.dlciTable.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2ATMImaCfgFrDlciEntry 459309056}

er1646v2ATMImaCfgFrDlciBridgingL2ptDestMac OBJECT-TYPE
   SYNTAX      OCTET STRING
   MAX-ACCESS  read-write
   STATUS      current
   DESCRIPTION
      "Path: atm.editConf.pvcTable.frameRelay.dlciTable.bridging.l2ProtTunnel.destinationMac

       MAC address."
   ::= {er1646v2ATMImaCfgFrDlciEntry 459325440}

er1646v2ATMImaCfgFrDlciBridgingL2ptCos OBJECT-TYPE
   SYNTAX      INTEGER
               {
               unchanged (255)
               }
   MAX-ACCESS  read-write
   STATUS      current
   DESCRIPTION
      "Path: atm.editConf.pvcTable.frameRelay.dlciTable.bridging.l2ProtTunnel.cos

       Possibilities:
               unchanged   (255)"
   ::= {er1646v2ATMImaCfgFrDlciEntry 459341824}

er1646v2ATMImaCfgFrDlciBridgingL2ptDropThrStp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.stp

       unit name = packets/sec

       Possibilities:
               unlimited   (0)"
   ::= {er1646v2ATMImaCfgFrDlciEntry 459358272}

er1646v2ATMImaCfgFrDlciBridgingL2ptDropThrLldp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.lldp

       unit name = packets/sec

       Possibilities:
               unlimited   (0)"
   ::= {er1646v2ATMImaCfgFrDlciEntry 459358336}

er1646v2ATMImaCfgFrDlciBridgingL2ptDropThrOam OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.oam

       unit name = packets/sec

       Possibilities:
               unlimited   (0)"
   ::= {er1646v2ATMImaCfgFrDlciEntry 459358400}

er1646v2ATMImaCfgFrDlciBridgingL2ptDropThrCdp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.cdp

       unit name = packets/sec

       Possibilities:
               unlimited   (0)"
   ::= {er1646v2ATMImaCfgFrDlciEntry 459358464}

er1646v2ATMImaCfgFrDlciBridgingL2ptDropThrVtp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.vtp

       unit name = packets/sec

       Possibilities:
               unlimited   (0)"
   ::= {er1646v2ATMImaCfgFrDlciEntry 459358528}

er1646v2ATMImaCfgFrDlciBridgingL2ptDropThrLacp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.lacp

       unit name = packets/sec

       Possibilities:
               unlimited   (0)"
   ::= {er1646v2ATMImaCfgFrDlciEntry 459358592}

er1646v2ATMImaCfgFrDlciBridgingL2ptDropThrEfmOam OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.efmOam

       unit name = packets/sec

       Possibilities:
               unlimited   (0)"
   ::= {er1646v2ATMImaCfgFrDlciEntry 459358656}

er1646v2ATMImaCfgFrDlciBridgingL2ptDropThrPvst OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.pvst

       unit name = packets/sec

       Possibilities:
               unlimited   (0)"
   ::= {er1646v2ATMImaCfgFrDlciEntry 459358720}

er1646v2ATMImaCfgFrDlciBridgingL2ptDropThrMmrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.mmrp

       unit name = packets/sec

       Possibilities:
               unlimited   (0)"
   ::= {er1646v2ATMImaCfgFrDlciEntry 459358784}

er1646v2ATMImaCfgFrDlciBridgingL2ptDropThrMvrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.mvrp

       unit name = packets/sec

       Possibilities:
               unlimited   (0)"
   ::= {er1646v2ATMImaCfgFrDlciEntry 459358848}

er1646v2ATMImaCfgFrDlciBridgingL2ptDropThrGvrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.gvrp

       unit name = packets/sec

       Possibilities:
               unlimited   (0)"
   ::= {er1646v2ATMImaCfgFrDlciEntry 459358912}

er1646v2ATMImaCfgFrDlciBridgingL2ptDropThrGmrp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.gmrp

       unit name = packets/sec

       Possibilities:
               unlimited   (0)"
   ::= {er1646v2ATMImaCfgFrDlciEntry 459358976}

er1646v2ATMImaCfgFrDlciBridgingL2ptDropThrDtp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.dtp

       unit name = packets/sec

       Possibilities:
               unlimited   (0)"
   ::= {er1646v2ATMImaCfgFrDlciEntry 459359040}

er1646v2ATMImaCfgFrDlciBridgingL2ptDropThrPagp OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.pagp

       unit name = packets/sec

       Possibilities:
               unlimited   (0)"
   ::= {er1646v2ATMImaCfgFrDlciEntry 459359104}

er1646v2ATMImaCfgFrDlciBridgingL2ptDropThrUdld OBJECT-TYPE
   SYNTAX      INTEGER
               {
               unlimited (0)
               }
   UNITS       "packets/sec"
   MAX-ACCESS  read-write
   STATUS      current
   DESCRIPTION
      "Path: atm.editConf.pvcTable.frameRelay.dlciTable.bridging.l2ProtTunnel.dropThresholds.udld

       unit name = packets/sec

       Possibilities:
               unlimited   (0)"
   ::= {er1646v2ATMImaCfgFrDlciEntry 459359168}

er1646v2ATMImaCfgFrDlciFrDlci OBJECT-TYPE
   SYNTAX      Integer32
   MAX-ACCESS  read-write
   STATUS      current
   DESCRIPTION
      "Path: atm.editConf.pvcTable.frameRelay.dlciTable.frameRelay.dlci"
   ::= {er1646v2ATMImaCfgFrDlciEntry 218169344}

er1646v2ATMImaCfgFrDlciFrCir OBJECT-TYPE
   SYNTAX      Integer32
   MAX-ACCESS  read-write
   STATUS      current
   DESCRIPTION
      "Path: atm.editConf.pvcTable.frameRelay.dlciTable.frameRelay.cir"
   ::= {er1646v2ATMImaCfgFrDlciEntry 218234880}

er1646v2ATMImaCfgFrDlciFrOverhead OBJECT-TYPE
   SYNTAX      Integer32
   MAX-ACCESS  read-write
   STATUS      current
   DESCRIPTION
      "Path: atm.editConf.pvcTable.frameRelay.dlciTable.frameRelay.overhead"
   ::= {er1646v2ATMImaCfgFrDlciEntry 218890240}

er1646v2ATMImaCfgFrDlciFrTc OBJECT-TYPE
   SYNTAX      Integer32
   MAX-ACCESS  read-write
   STATUS      current
   DESCRIPTION
      "Path: atm.editConf.pvcTable.frameRelay.dlciTable.frameRelay.tc"
   ::= {er1646v2ATMImaCfgFrDlciEntry 218759168}

er1646v2ATMImaCfgFrDlciFrSlidingWindow OBJECT-TYPE
   SYNTAX      INTEGER
               {
               disabled (0),
               enabled (1)
               }
   MAX-ACCESS  read-write
   STATUS      current
   DESCRIPTION
      "Path: atm.editConf.pvcTable.frameRelay.dlciTable.frameRelay.slidingWindow

       Possibilities:
               disabled   (0)
               enabled   (1)"
   ::= {er1646v2ATMImaCfgFrDlciEntry 218824704}

er1646v2ATMImaCfgFrDlciFrDeBitSet OBJECT-TYPE
   SYNTAX      INTEGER
               {
               disabled (0),
               enabled (1)
               }
   MAX-ACCESS  read-write
   STATUS      current
   DESCRIPTION
      "Path: atm.editConf.pvcTable.frameRelay.dlciTable.frameRelay.deBitSet

       Possibilities:
               disabled   (0)
               enabled   (1)"
   ::= {er1646v2ATMImaCfgFrDlciEntry 218431488}

er1646v2ATMImaCfgFrDlciFrDefaultQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: atm.editConf.pvcTable.frameRelay.dlciTable.frameRelay.defaultQueue

       Possibilities:
               queue1   (0)
               queue2   (1)
               queue3   (2)
               queue4   (3)
               queue5   (4)
               lowDelayQueue   (5)
               lowDelay2Queue   (6)
               systemQueue   (7)"
   ::= {er1646v2ATMImaCfgFrDlciEntry 218628096}

er1646v2ATMImaCfgFrDlciFrRxCir OBJECT-TYPE
   SYNTAX      Integer32
   MAX-ACCESS  read-write
   STATUS      current
   DESCRIPTION
      "Path: atm.editConf.pvcTable.frameRelay.dlciTable.frameRelay.rxCir"
   ::= {er1646v2ATMImaCfgFrDlciEntry 218497024}

er1646v2ATMImaCfgFrDlciFrRxExcess OBJECT-TYPE
   SYNTAX      INTEGER
               {
               discard (0),
               setDeBit (1),
               ignore (2)
               }
   MAX-ACCESS  read-write
   STATUS      current
   DESCRIPTION
      "Path: atm.editConf.pvcTable.frameRelay.dlciTable.frameRelay.rxExcess

       Possibilities:
               discard   (0)
               setDeBit   (1)
               ignore   (2)"
   ::= {er1646v2ATMImaCfgFrDlciEntry 218562560}

er1646v2ATMImaCfgFrDlciFrFragEMode OBJECT-TYPE
   SYNTAX      INTEGER
               {
               disabled (0),
               enabled (1)
               }
   MAX-ACCESS  read-write
   STATUS      current
   DESCRIPTION
      "Path: atm.editConf.pvcTable.frameRelay.dlciTable.frameRelay.fragmentation.endToEndFormat

       Possibilities:
               disabled   (0)
               enabled   (1)"
   ::= {er1646v2ATMImaCfgFrDlciEntry 218366208}

er1646v2ATMImaCfgFrDlciIpH OBJECT-TYPE
   SYNTAX      SEQUENCE OF Er1646v2ATMImaCfgFrDlciIpHEntry
   MAX-ACCESS  not-accessible
   STATUS      current
   DESCRIPTION
      ""
   ::= {er1646v2ATMImaCfg 689975536}

er1646v2ATMImaCfgFrDlciIpHEntry OBJECT-TYPE
   SYNTAX      Er1646v2ATMImaCfgFrDlciIpHEntry
   MAX-ACCESS  not-accessible
   STATUS      current
   DESCRIPTION
      ""
   INDEX      { er1646v2ATMImaCfgTableIx,
                er1646v2ATMImaCfgFrDlciTableIx,
                er1646v2ATMImaCfgFrDlciIpHTableIx }
   ::= {er1646v2ATMImaCfgFrDlciIpH 1}

Er1646v2ATMImaCfgFrDlciIpHEntry ::=
   SEQUENCE
      {
      er1646v2ATMImaCfgFrDlciIpHActions
         VariableLengthTableActions,
      er1646v2ATMImaCfgFrDlciIpHTableIx
         TableIndex,
      er1646v2ATMImaCfgFrDlciIpHAddress
         IpAddress,
      er1646v2ATMImaCfgFrDlciIpHDhcpRelayOptionSubscriberId
         DisplayString
      }

er1646v2ATMImaCfgFrDlciIpHActions OBJECT-TYPE
   SYNTAX      VariableLengthTableActions
   MAX-ACCESS  read-write
   STATUS      current
   DESCRIPTION
      "By way of this field, some manipulations
       on this table may be performed."
   ::= {er1646v2ATMImaCfgFrDlciIpHEntry 2}

er1646v2ATMImaCfgFrDlciIpHTableIx OBJECT-TYPE
   SYNTAX      TableIndex
   MAX-ACCESS  not-accessible
   STATUS      current
   DESCRIPTION
      ""
   ::= {er1646v2ATMImaCfgFrDlciIpHEntry 11}

er1646v2ATMImaCfgFrDlciIpHAddress OBJECT-TYPE
   SYNTAX      IpAddress
   MAX-ACCESS  read-write
   STATUS      current
   DESCRIPTION
      "Path: atm.editConf.pvcTable.frameRelay.dlciTable.ip.helpers.address"
   ::= {er1646v2ATMImaCfgFrDlciIpHEntry 16777216}

er1646v2ATMImaCfgFrDlciIpHDhcpRelayOptionSubscriberId OBJECT-TYPE
   SYNTAX      DisplayString
   MAX-ACCESS  read-write
   STATUS      current
   DESCRIPTION
      "Path: atm.editConf.pvcTable.frameRelay.dlciTable.ip.helpers.dhcpRelayOption.subscriberId"
   ::= {er1646v2ATMImaCfgFrDlciIpHEntry 33947648}

er1646v2ATMImaCfgFrDlciBridgingVlTVlans OBJECT-TYPE
   SYNTAX      SEQUENCE OF Er1646v2ATMImaCfgFrDlciBridgingVlTVlansEntry
   MAX-ACCESS  not-accessible
   STATUS      current
   DESCRIPTION
      ""
   ::= {er1646v2ATMImaCfg 690075088}

er1646v2ATMImaCfgFrDlciBridgingVlTVlansEntry OBJECT-TYPE
   SYNTAX      Er1646v2ATMImaCfgFrDlciBridgingVlTVlansEntry
   MAX-ACCESS  not-accessible
   STATUS      current
   DESCRIPTION
      ""
   INDEX      { er1646v2ATMImaCfgTableIx,
                er1646v2ATMImaCfgFrDlciTableIx,
                er1646v2ATMImaCfgFrDlciBridgingVlTVlansTableIx }
   ::= {er1646v2ATMImaCfgFrDlciBridgingVlTVlans 1}

Er1646v2ATMImaCfgFrDlciBridgingVlTVlansEntry ::=
   SEQUENCE
      {
      er1646v2ATMImaCfgFrDlciBridgingVlTVlansActions
         VariableLengthTableActions,
      er1646v2ATMImaCfgFrDlciBridgingVlTVlansTableIx
         TableIndex,
      er1646v2ATMImaCfgFrDlciBridgingVlTVlansVid
         Integer32,
      er1646v2ATMImaCfgFrDlciBridgingVlTVlansEndVid
         Integer32,
      er1646v2ATMImaCfgFrDlciBridgingVlTVlansAction
         INTEGER,
      er1646v2ATMImaCfgFrDlciBridgingVlTVlansTagInfoTpid
         INTEGER,
      er1646v2ATMImaCfgFrDlciBridgingVlTVlansTagInfoVid
         Integer32
      }

er1646v2ATMImaCfgFrDlciBridgingVlTVlansActions OBJECT-TYPE
   SYNTAX      VariableLengthTableActions
   MAX-ACCESS  read-write
   STATUS      current
   DESCRIPTION
      "By way of this field, some manipulations
       on this table may be performed."
   ::= {er1646v2ATMImaCfgFrDlciBridgingVlTVlansEntry 2}

er1646v2ATMImaCfgFrDlciBridgingVlTVlansTableIx OBJECT-TYPE
   SYNTAX      TableIndex
   MAX-ACCESS  not-accessible
   STATUS      current
   DESCRIPTION
      ""
   ::= {er1646v2ATMImaCfgFrDlciBridgingVlTVlansEntry 11}

er1646v2ATMImaCfgFrDlciBridgingVlTVlansVid OBJECT-TYPE
   SYNTAX      Integer32
   MAX-ACCESS  read-write
   STATUS      current
   DESCRIPTION
      "Path: atm.editConf.pvcTable.frameRelay.dlciTable.bridging.vlanTagging.vlans.vid"
   ::= {er1646v2ATMImaCfgFrDlciBridgingVlTVlansEntry 536870912}

er1646v2ATMImaCfgFrDlciBridgingVlTVlansEndVid OBJECT-TYPE
   SYNTAX      Integer32
   MAX-ACCESS  read-write
   STATUS      current
   DESCRIPTION
      "Path: atm.editConf.pvcTable.frameRelay.dlciTable.bridging.vlanTagging.vlans.endVid"
   ::= {er1646v2ATMImaCfgFrDlciBridgingVlTVlansEntry 2147483648}

er1646v2ATMImaCfgFrDlciBridgingVlTVlansAction OBJECT-TYPE
   SYNTAX      INTEGER
               {
               discard (0),
               accept (1),
               tag (2)
               }
   MAX-ACCESS  read-write
   STATUS      current
   DESCRIPTION
      "Path: atm.editConf.pvcTable.frameRelay.dlciTable.bridging.vlanTagging.vlans.action

       Possibilities:
               discard   (0)
               accept   (1)
               tag   (2)"
   ::= {er1646v2ATMImaCfgFrDlciBridgingVlTVlansEntry 1073741824}

er1646v2ATMImaCfgFrDlciBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: atm.editConf.pvcTable.frameRelay.dlciTable.bridging.vlanTagging.vlans.tagInfo.tpid

       Possibilities:
               dot1Q   (33024)
               dot1ad   (34984)
               0x9100   (37120)
               0x9200   (37376)
               0x9300   (37632)"
   ::= {er1646v2ATMImaCfgFrDlciBridgingVlTVlansEntry 1677721600}

er1646v2ATMImaCfgFrDlciBridgingVlTVlansTagInfoVid OBJECT-TYPE
   SYNTAX      Integer32
   MAX-ACCESS  read-write
   STATUS      current
   DESCRIPTION
      "Path: atm.editConf.pvcTable.frameRelay.dlciTable.bridging.vlanTagging.vlans.tagInfo.vid"
   ::= {er1646v2ATMImaCfgFrDlciBridgingVlTVlansEntry 1744830464}


er1646v2ATMImaImaMode OBJECT-TYPE
   SYNTAX      INTEGER
               {
               disabled (0),
               enabled (1),
               auto (2)
               }
   MAX-ACCESS  read-write
   STATUS      current
   DESCRIPTION
      "Path: atm.editConf.imaMode
       Info: IMA enabling

       Possibilities:
               disabled   (0)
               enabled   (1)
               auto   (2)"
   ::= {er1646v2ATMIma 117}



sr1646v2ATMIma OBJECT IDENTIFIER ::= {r1646v2ATMIma 14}


sr1646v2ATMImaAtmSync OBJECT-TYPE
   SYNTAX      INTEGER
               {
               notSynced (0),
               synced (1)
               }
   MAX-ACCESS  read-only
   STATUS      current
   DESCRIPTION
      "Path: atm.status.atmSync

       Possibilities:
               notSynced   (0)
               synced   (1)"
   ::= {sr1646v2ATMIma 91}


sr1646v2ATMImaVp OBJECT IDENTIFIER ::= {sr1646v2ATMIma 93}

sr1646v2ATMImaVpSSCTable OBJECT-TYPE
   SYNTAX      SEQUENCE OF Sr1646v2ATMImaVpEntry
   MAX-ACCESS  not-accessible
   STATUS      current
   DESCRIPTION
      ""
   ::= {sr1646v2ATMImaVp 1}

sr1646v2ATMImaVpEntry OBJECT-TYPE
   SYNTAX      Sr1646v2ATMImaVpEntry
   MAX-ACCESS  not-accessible
   STATUS      current
   DESCRIPTION
      ""
   INDEX      { sr1646v2ATMImaVpTableIx }
   ::= {sr1646v2ATMImaVpSSCTable 1}

Sr1646v2ATMImaVpEntry ::=
   SEQUENCE
      {
      sr1646v2ATMImaVpTableIx
         TableIndex,
      sr1646v2ATMImaVpVpi
         Integer32,
      sr1646v2ATMImaVpIfOperStatus
         INTEGER,
      sr1646v2ATMImaVpOamF4SegOamLB
         INTEGER,
      sr1646v2ATMImaVpOamF4SegOamCC
         INTEGER,
      sr1646v2ATMImaVpOamF4SegOamPMStatus
         INTEGER,
      sr1646v2ATMImaVpOamF4SegOamPMBlockSizeAB
         INTEGER,
      sr1646v2ATMImaVpOamF4SegOamPMBlockSizeBA
         INTEGER,
      sr1646v2ATMImaVpOamF4SegAis
         INTEGER,
      sr1646v2ATMImaVpOamF4SegRdi
         INTEGER,
      sr1646v2ATMImaVpOamF4EteOamLB
         INTEGER,
      sr1646v2ATMImaVpOamF4EteOamCC
         INTEGER,
      sr1646v2ATMImaVpOamF4EteOamPMStatus
         INTEGER,
      sr1646v2ATMImaVpOamF4EteOamPMBlockSizeAB
         INTEGER,
      sr1646v2ATMImaVpOamF4EteOamPMBlockSizeBA
         INTEGER,
      sr1646v2ATMImaVpOamF4EteAis
         INTEGER,
      sr1646v2ATMImaVpOamF4EteRdi
         INTEGER,
      sr1646v2ATMImaVpOamF4SegEP
         INTEGER,
      sr1646v2ATMImaVpOamF4CnxEP
         INTEGER
      }

sr1646v2ATMImaVpTableIx OBJECT-TYPE
   SYNTAX      TableIndex
   MAX-ACCESS  not-accessible
   STATUS      current
   DESCRIPTION
      ""
   ::= {sr1646v2ATMImaVpEntry 11}

sr1646v2ATMImaVpVpi OBJECT-TYPE
   SYNTAX      Integer32
   MAX-ACCESS  read-only
   STATUS      current
   DESCRIPTION
      "Path: atm.status.vp.vpi"
   ::= {sr1646v2ATMImaVpEntry 16777216}

sr1646v2ATMImaVpIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.vp.ifOperStatus

       Possibilities:
               up   (1)
               down   (2)
               testing   (3)
               unknown   (4)
               dormant   (5)
               notPresent   (6)
               lowerLayerDown   (7)"
   ::= {sr1646v2ATMImaVpEntry 1795162112}

sr1646v2ATMImaVpOamF4SegOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamLB

       Possibilities:
               ready   (0)
               waitActRes   (1)
               waitActCon   (2)
               waitDeactCon   (3)
               active   (4)
               deactivated   (5)"
   ::= {sr1646v2ATMImaVpEntry 33628160}

sr1646v2ATMImaVpOamF4SegOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamCC

       Possibilities:
               ready   (0)
               waitActRes   (1)
               waitActCon   (2)
               waitDeactCon   (3)
               active   (4)
               deactivated   (5)"
   ::= {sr1646v2ATMImaVpEntry 33636352}

sr1646v2ATMImaVpOamF4SegOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.segment.oamPM.status

       Possibilities:
               ready   (0)
               waitActRes   (1)
               waitActCon   (2)
               waitDeactCon   (3)
               active   (4)
               deactivated   (5)"
   ::= {sr1646v2ATMImaVpEntry 33645568}

sr1646v2ATMImaVpOamF4SegOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.segment.oamPM.blockSizeAB

       Possibilities:
               128   (0)
               256   (1)
               512   (2)
               1024   (3)
               2048   (4)
               4096   (5)
               8192   (6)
               16384   (7)
               32768   (8)"
   ::= {sr1646v2ATMImaVpEntry 33646592}

sr1646v2ATMImaVpOamF4SegOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.segment.oamPM.blockSizeBA

       Possibilities:
               128   (0)
               256   (1)
               512   (2)
               1024   (3)
               2048   (4)
               4096   (5)
               8192   (6)
               16384   (7)
               32768   (8)"
   ::= {sr1646v2ATMImaVpEntry 33647616}

sr1646v2ATMImaVpOamF4SegAis OBJECT-TYPE
   SYNTAX      INTEGER
               {
               inactive (0),
               active (1)
               }
   MAX-ACCESS  read-only
   STATUS      current
   DESCRIPTION
      "Path: atm.status.vp.oamF4.segment.aisState

       Possibilities:
               inactive   (0)
               active   (1)"
   ::= {sr1646v2ATMImaVpEntry 33652736}

sr1646v2ATMImaVpOamF4SegRdi OBJECT-TYPE
   SYNTAX      INTEGER
               {
               inactive (0),
               active (1)
               }
   MAX-ACCESS  read-only
   STATUS      current
   DESCRIPTION
      "Path: atm.status.vp.oamF4.segment.rdiState

       Possibilities:
               inactive   (0)
               active   (1)"
   ::= {sr1646v2ATMImaVpEntry 33660928}

sr1646v2ATMImaVpOamF4EteOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamLB

       Possibilities:
               ready   (0)
               waitActRes   (1)
               waitActCon   (2)
               waitDeactCon   (3)
               active   (4)
               deactivated   (5)"
   ::= {sr1646v2ATMImaVpEntry 33693696}

sr1646v2ATMImaVpOamF4EteOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamCC

       Possibilities:
               ready   (0)
               waitActRes   (1)
               waitActCon   (2)
               waitDeactCon   (3)
               active   (4)
               deactivated   (5)"
   ::= {sr1646v2ATMImaVpEntry 33701888}

sr1646v2ATMImaVpOamF4EteOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.vp.oamF4.endToEnd.oamPM.status

       Possibilities:
               ready   (0)
               waitActRes   (1)
               waitActCon   (2)
               waitDeactCon   (3)
               active   (4)
               deactivated   (5)"
   ::= {sr1646v2ATMImaVpEntry 33711104}

sr1646v2ATMImaVpOamF4EteOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.endToEnd.oamPM.blockSizeAB

       Possibilities:
               128   (0)
               256   (1)
               512   (2)
               1024   (3)
               2048   (4)
               4096   (5)
               8192   (6)
               16384   (7)
               32768   (8)"
   ::= {sr1646v2ATMImaVpEntry 33712128}

sr1646v2ATMImaVpOamF4EteOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.vp.oamF4.endToEnd.oamPM.blockSizeBA

       Possibilities:
               128   (0)
               256   (1)
               512   (2)
               1024   (3)
               2048   (4)
               4096   (5)
               8192   (6)
               16384   (7)
               32768   (8)"
   ::= {sr1646v2ATMImaVpEntry 33713152}

sr1646v2ATMImaVpOamF4EteAis OBJECT-TYPE
   SYNTAX      INTEGER
               {
               inactive (0),
               active (1)
               }
   MAX-ACCESS  read-only
   STATUS      current
   DESCRIPTION
      "Path: atm.status.vp.oamF4.endToEnd.aisState

       Possibilities:
               inactive   (0)
               active   (1)"
   ::= {sr1646v2ATMImaVpEntry 33718272}

sr1646v2ATMImaVpOamF4EteRdi OBJECT-TYPE
   SYNTAX      INTEGER
               {
               inactive (0),
               active (1)
               }
   MAX-ACCESS  read-only
   STATUS      current
   DESCRIPTION
      "Path: atm.status.vp.oamF4.endToEnd.rdiState

       Possibilities:
               inactive   (0)
               active   (1)"
   ::= {sr1646v2ATMImaVpEntry 33726464}

sr1646v2ATMImaVpOamF4SegEP OBJECT-TYPE
   SYNTAX      INTEGER
               {
               no (0),
               yes (1)
               }
   MAX-ACCESS  read-only
   STATUS      current
   DESCRIPTION
      "Path: atm.status.vp.oamF4.segmentEndPoint

       Possibilities:
               no   (0)
               yes   (1)"
   ::= {sr1646v2ATMImaVpEntry 33751040}

sr1646v2ATMImaVpOamF4CnxEP OBJECT-TYPE
   SYNTAX      INTEGER
               {
               no (0),
               yes (1)
               }
   MAX-ACCESS  read-only
   STATUS      current
   DESCRIPTION
      "Path: atm.status.vp.oamF4.connectionEndPoint

       Possibilities:
               no   (0)
               yes   (1)"
   ::= {sr1646v2ATMImaVpEntry 33816576}


sr1646v2ATMImaStat OBJECT IDENTIFIER ::= {sr1646v2ATMIma 2}

sr1646v2ATMImaStatSSCTable OBJECT-TYPE
   SYNTAX      SEQUENCE OF Sr1646v2ATMImaStatEntry
   MAX-ACCESS  not-accessible
   STATUS      current
   DESCRIPTION
      ""
   ::= {sr1646v2ATMImaStat 1}

sr1646v2ATMImaStatEntry OBJECT-TYPE
   SYNTAX      Sr1646v2ATMImaStatEntry
   MAX-ACCESS  not-accessible
   STATUS      current
   DESCRIPTION
      ""
   INDEX      { sr1646v2ATMImaStatTableIx }
   ::= {sr1646v2ATMImaStatSSCTable 1}

Sr1646v2ATMImaStatEntry ::=
   SEQUENCE
      {
      sr1646v2ATMImaStatTableIx
         TableIndex,
      sr1646v2ATMImaStatName
         DisplayString,
      sr1646v2ATMImaStatMode
         INTEGER,
      sr1646v2ATMImaStatIfOperStatus
         INTEGER,
      sr1646v2ATMImaStatIfLastChange
         TimeTicks,
      sr1646v2ATMImaStatIfLastChangeDate
         DisplayString,
      sr1646v2ATMImaStatIpAddress
         IpAddress,
      sr1646v2ATMImaStatIpNetMask
         IpAddress,
      sr1646v2ATMImaStatIpRemote
         IpAddress,
      sr1646v2ATMImaStatIpV6State
         INTEGER,
      sr1646v2ATMImaStatIpV6InterfaceId
         OCTET STRING,
      sr1646v2ATMImaStatIpV6LinkMtu
         Integer32,
      sr1646v2ATMImaStatIpV6HopLimit
         Integer32,
      sr1646v2ATMImaStatIpV6DhcpIaid
         Counter32,
      sr1646v2ATMImaStatIpV6RaRcvOption
         Integer32,
      sr1646v2ATMImaStatBridgingStatus
         INTEGER,
      sr1646v2ATMImaStatBridgingSpanningTreePortRole
         INTEGER,
      sr1646v2ATMImaStatBridgingSpanningTreePortId
         Integer32,
      sr1646v2ATMImaStatBridgingSpanningTreePpCostExtPathCost
         Integer32,
      sr1646v2ATMImaStatBridgingSpanningTreePpCostIntPathCost
         Integer32,
      sr1646v2ATMImaStatBridgingSpanningTreeExtRpCost
         Integer32,
      sr1646v2ATMImaStatBridgingSpanningTreeIntRpCost
         Integer32,
      sr1646v2ATMImaStatBridgingSpanningTreeDesBrIdPriority
         Integer32,
      sr1646v2ATMImaStatBridgingSpanningTreeDesBrIdMacAddress
         OCTET STRING,
      sr1646v2ATMImaStatBridgingSpanningTreeDesPrtId
         Integer32,
      sr1646v2ATMImaStatBridgingSpanningTreeDesInt
         INTEGER,
      sr1646v2ATMImaStatBridgingSpanningTreeEdgeDetection
         INTEGER,
      sr1646v2ATMImaStatAtmVpi
         Integer32,
      sr1646v2ATMImaStatAtmVci
         Integer32,
      sr1646v2ATMImaStatAtmServCat
         INTEGER,
      sr1646v2ATMImaStatAtmPeakCellRate
         Integer32,
      sr1646v2ATMImaStatAtmSustCellRate
         Integer32,
      sr1646v2ATMImaStatAtmMaxBurstSize
         Integer32,
      sr1646v2ATMImaStatAtmPppOEthDiscState
         INTEGER,
      sr1646v2ATMImaStatAtmPppOEthPeerMac
         OCTET STRING,
      sr1646v2ATMImaStatAtmPppOEthServiceName
         DisplayString,
      sr1646v2ATMImaStatAtmPppLcpState
         INTEGER,
      sr1646v2ATMImaStatAtmPppIpcpState
         INTEGER,
      sr1646v2ATMImaStatAtmPppIp6cpState
         INTEGER,
      sr1646v2ATMImaStatAtmPppBcpState
         INTEGER,
      sr1646v2ATMImaStatAtmPppCcpState
         INTEGER,
      sr1646v2ATMImaStatAtmPppHisCompRat
         Integer32,
      sr1646v2ATMImaStatAtmPppMyCompRat
         Integer32,
      sr1646v2ATMImaStatAtmPppMyAutSt
         INTEGER,
      sr1646v2ATMImaStatAtmPppHisAutSt
         INTEGER,
      sr1646v2ATMImaStatAtmOamF5SegOamLB
         INTEGER,
      sr1646v2ATMImaStatAtmOamF5SegOamCC
         INTEGER,
      sr1646v2ATMImaStatAtmOamF5SegOamPMStatus
         INTEGER,
      sr1646v2ATMImaStatAtmOamF5SegOamPMBlockSizeAB
         INTEGER,
      sr1646v2ATMImaStatAtmOamF5SegOamPMBlockSizeBA
         INTEGER,
      sr1646v2ATMImaStatAtmOamF5SegAis
         INTEGER,
      sr1646v2ATMImaStatAtmOamF5SegRdi
         INTEGER,
      sr1646v2ATMImaStatAtmOamF5EteOamLB
         INTEGER,
      sr1646v2ATMImaStatAtmOamF5EteOamCC
         INTEGER,
      sr1646v2ATMImaStatAtmOamF5EteOamPMStatus
         INTEGER,
      sr1646v2ATMImaStatAtmOamF5EteOamPMBlockSizeAB
         INTEGER,
      sr1646v2ATMImaStatAtmOamF5EteOamPMBlockSizeBA
         INTEGER,
      sr1646v2ATMImaStatAtmOamF5EteAis
         INTEGER,
      sr1646v2ATMImaStatAtmOamF5EteRdi
         INTEGER,
      sr1646v2ATMImaStatAtmOamF5SegEP
         INTEGER,
      sr1646v2ATMImaStatAtmOamF5CnxEP
         INTEGER,
      sr1646v2ATMImaStatFrLmiMode
         INTEGER,
      sr1646v2ATMImaStatFrLmiType
         INTEGER,
      sr1646v2ATMImaStatFrLmiStatus
         INTEGER,
      sr1646v2ATMImaStatFrLmiLastChange
         TimeTicks,
      sr1646v2ATMImaStatFrLmiLastError
         INTEGER,
      sr1646v2ATMImaStatFrLmiNetTxSeqNum
         Integer32,
      sr1646v2ATMImaStatFrLmiNetRxSeqNum
         Integer32,
      sr1646v2ATMImaStatFrLmiNetErrors
         Integer32,
      sr1646v2ATMImaStatFrLmiUserTxSeqNum
         Integer32,
      sr1646v2ATMImaStatFrLmiUserRxSeqNum
         Integer32,
      sr1646v2ATMImaStatFrLmiUserErrors
         Integer32,
      sr1646v2ATMImaStatFrLmiUWaitFullEnq
         Integer32,
      sr1646v2ATMImaStatFrLmiULstRepTypeTx
         INTEGER
      }

sr1646v2ATMImaStatTableIx OBJECT-TYPE
   SYNTAX      TableIndex
   MAX-ACCESS  not-accessible
   STATUS      current
   DESCRIPTION
      ""
   ::= {sr1646v2ATMImaStatEntry 11}

sr1646v2ATMImaStatName OBJECT-TYPE
   SYNTAX      DisplayString
   MAX-ACCESS  read-only
   STATUS      current
   DESCRIPTION
      "Path: atm.status.pvcTable.name"
   ::= {sr1646v2ATMImaStatEntry 16777216}

sr1646v2ATMImaStatMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: atm.status.pvcTable.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2ATMImaStatEntry 335544320}

sr1646v2ATMImaStatIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.pvcTable.ifOperStatus

       Possibilities:
               up   (1)
               down   (2)
               testing   (3)
               unknown   (4)
               dormant   (5)
               notPresent   (6)
               lowerLayerDown   (7)"
   ::= {sr1646v2ATMImaStatEntry 1795162112}

sr1646v2ATMImaStatIfLastChange OBJECT-TYPE
   SYNTAX      TimeTicks
   MAX-ACCESS  read-only
   STATUS      current
   DESCRIPTION
      "Path: atm.status.pvcTable.ifLastChange

       Time in centi-second."
   ::= {sr1646v2ATMImaStatEntry 1811939328}

sr1646v2ATMImaStatIfLastChangeDate OBJECT-TYPE
   SYNTAX      DisplayString
   MAX-ACCESS  read-only
   STATUS      current
   DESCRIPTION
      "Path: atm.status.pvcTable.ifLastChangeDate"
   ::= {sr1646v2ATMImaStatEntry 3070230528}

sr1646v2ATMImaStatIpAddress OBJECT-TYPE
   SYNTAX      IpAddress
   MAX-ACCESS  read-only
   STATUS      current
   DESCRIPTION
      "Path: atm.status.pvcTable.ip.address"
   ::= {sr1646v2ATMImaStatEntry 51380224}

sr1646v2ATMImaStatIpNetMask OBJECT-TYPE
   SYNTAX      IpAddress
   MAX-ACCESS  read-only
   STATUS      current
   DESCRIPTION
      "Path: atm.status.pvcTable.ip.netMask"
   ::= {sr1646v2ATMImaStatEntry 51445760}

sr1646v2ATMImaStatIpRemote OBJECT-TYPE
   SYNTAX      IpAddress
   MAX-ACCESS  read-only
   STATUS      current
   DESCRIPTION
      "Path: atm.status.pvcTable.ip.remote"
   ::= {sr1646v2ATMImaStatEntry 51511296}

sr1646v2ATMImaStatIpV6State OBJECT-TYPE
   SYNTAX      INTEGER
               {
               disabled (0),
               enabled (1)
               }
   MAX-ACCESS  read-only
   STATUS      current
   DESCRIPTION
      "Path: atm.status.pvcTable.ipV6.state

       Possibilities:
               disabled   (0)
               enabled   (1)"
   ::= {sr1646v2ATMImaStatEntry 100728832}

sr1646v2ATMImaStatIpV6InterfaceId OBJECT-TYPE
   SYNTAX      OCTET STRING
   MAX-ACCESS  read-only
   STATUS      current
   DESCRIPTION
      "Path: atm.status.pvcTable.ipV6.interfaceId"
   ::= {sr1646v2ATMImaStatEntry 100794368}

sr1646v2ATMImaStatIpV6LinkMtu OBJECT-TYPE
   SYNTAX      Integer32
   MAX-ACCESS  read-only
   STATUS      current
   DESCRIPTION
      "Path: atm.status.pvcTable.ipV6.linkMtu"
   ::= {sr1646v2ATMImaStatEntry 100925440}

sr1646v2ATMImaStatIpV6HopLimit OBJECT-TYPE
   SYNTAX      Integer32
   MAX-ACCESS  read-only
   STATUS      current
   DESCRIPTION
      "Path: atm.status.pvcTable.ipV6.hopLimit"
   ::= {sr1646v2ATMImaStatEntry 100990976}

sr1646v2ATMImaStatIpV6DhcpIaid OBJECT-TYPE
   SYNTAX      Counter32
   MAX-ACCESS  read-only
   STATUS      current
   DESCRIPTION
      "Path: atm.status.pvcTable.ipV6.dhcp.iaid

       32 bit unsigned wrappable counter."
   ::= {sr1646v2ATMImaStatEntry 101056768}

sr1646v2ATMImaStatIpV6RaRcvOption OBJECT-TYPE
   SYNTAX      Integer32
   MAX-ACCESS  read-only
   STATUS      current
   DESCRIPTION
      "Path: atm.status.pvcTable.ipV6.raRcvOption

       Bit meanings:
               bit 0 = linkMtu,
               bit 1 = srcLinkLayer,
               bit 2 = prefixInfo,
               bit 3 = rdnss,
               bit 4 = dnssl"
   ::= {sr1646v2ATMImaStatEntry 101122048}

sr1646v2ATMImaStatBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: atm.status.pvcTable.bridging.status

       Possibilities:
               disabled   (0)
               discarding   (1)
               learning   (2)
               forwarding   (3)
               backupBlockedIntfDown   (256)
               backupBlockedIntfUp   (259)
               shutdown   (255)"
   ::= {sr1646v2ATMImaStatEntry 453050368}

sr1646v2ATMImaStatBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: atm.status.pvcTable.bridging.spanningTree.portRole

       Possibilities:
               none   (0)
               root   (1)
               designated   (2)
               alternate   (3)
               backup   (4)
               disabled   (5)
               master   (6)"
   ::= {sr1646v2ATMImaStatEntry 453116160}

sr1646v2ATMImaStatBridgingSpanningTreePortId OBJECT-TYPE
   SYNTAX      Integer32
   MAX-ACCESS  read-only
   STATUS      current
   DESCRIPTION
      "Path: atm.status.pvcTable.bridging.spanningTree.portId"
   ::= {sr1646v2ATMImaStatEntry 453116416}

sr1646v2ATMImaStatBridgingSpanningTreePpCostExtPathCost OBJECT-TYPE
   SYNTAX      Integer32
   MAX-ACCESS  read-only
   STATUS      current
   DESCRIPTION
      "Path: atm.status.pvcTable.bridging.spanningTree.portPathCosts.extPathCost"
   ::= {sr1646v2ATMImaStatEntry 453116673}

sr1646v2ATMImaStatBridgingSpanningTreePpCostIntPathCost OBJECT-TYPE
   SYNTAX      Integer32
   MAX-ACCESS  read-only
   STATUS      current
   DESCRIPTION
      "Path: atm.status.pvcTable.bridging.spanningTree.portPathCosts.intPathCost"
   ::= {sr1646v2ATMImaStatEntry 453116674}

sr1646v2ATMImaStatBridgingSpanningTreeExtRpCost OBJECT-TYPE
   SYNTAX      Integer32
   MAX-ACCESS  read-only
   STATUS      current
   DESCRIPTION
      "Path: atm.status.pvcTable.bridging.spanningTree.extRootPathCost"
   ::= {sr1646v2ATMImaStatEntry 453116928}

sr1646v2ATMImaStatBridgingSpanningTreeIntRpCost OBJECT-TYPE
   SYNTAX      Integer32
   MAX-ACCESS  read-only
   STATUS      current
   DESCRIPTION
      "Path: atm.status.pvcTable.bridging.spanningTree.intRootPathCost"
   ::= {sr1646v2ATMImaStatEntry 453117184}

sr1646v2ATMImaStatBridgingSpanningTreeDesBrIdPriority OBJECT-TYPE
   SYNTAX      Integer32
   MAX-ACCESS  read-only
   STATUS      current
   DESCRIPTION
      "Path: atm.status.pvcTable.bridging.spanningTree.designatedBridgeId.priority"
   ::= {sr1646v2ATMImaStatEntry 453117441}

sr1646v2ATMImaStatBridgingSpanningTreeDesBrIdMacAddress OBJECT-TYPE
   SYNTAX      OCTET STRING
   MAX-ACCESS  read-only
   STATUS      current
   DESCRIPTION
      "Path: atm.status.pvcTable.bridging.spanningTree.designatedBridgeId.macAddress

       MAC address."
   ::= {sr1646v2ATMImaStatEntry 453117442}

sr1646v2ATMImaStatBridgingSpanningTreeDesPrtId OBJECT-TYPE
   SYNTAX      Integer32
   MAX-ACCESS  read-only
   STATUS      current
   DESCRIPTION
      "Path: atm.status.pvcTable.bridging.spanningTree.designatedPortId"
   ::= {sr1646v2ATMImaStatEntry 453117696}

sr1646v2ATMImaStatBridgingSpanningTreeDesInt OBJECT-TYPE
   SYNTAX      INTEGER
               {
               no (0),
               yes (1)
               }
   MAX-ACCESS  read-only
   STATUS      current
   DESCRIPTION
      "Path: atm.status.pvcTable.bridging.spanningTree.designatedOrInternal

       Possibilities:
               no   (0)
               yes   (1)"
   ::= {sr1646v2ATMImaStatEntry 453117952}

sr1646v2ATMImaStatBridgingSpanningTreeEdgeDetection OBJECT-TYPE
   SYNTAX      INTEGER
               {
               none (0),
               edge (1),
               notEdge (2)
               }
   MAX-ACCESS  read-only
   STATUS      current
   DESCRIPTION
      "Path: atm.status.pvcTable.bridging.spanningTree.edgeDetection

       Possibilities:
               none   (0)
               edge   (1)
               notEdge   (2)"
   ::= {sr1646v2ATMImaStatEntry 453118208}

sr1646v2ATMImaStatAtmVpi OBJECT-TYPE
   SYNTAX      Integer32
   MAX-ACCESS  read-only
   STATUS      current
   DESCRIPTION
      "Path: atm.status.pvcTable.atm.vpi"
   ::= {sr1646v2ATMImaStatEntry 285278208}

sr1646v2ATMImaStatAtmVci OBJECT-TYPE
   SYNTAX      Integer32
   MAX-ACCESS  read-only
   STATUS      current
   DESCRIPTION
      "Path: atm.status.pvcTable.atm.vci"
   ::= {sr1646v2ATMImaStatEntry 285343744}

sr1646v2ATMImaStatAtmServCat OBJECT-TYPE
   SYNTAX      INTEGER
               {
               notAssigned (0),
               cbr (1),
               vbrmrt (2),
               vbrmnrt (3),
               ubr (4),
               cbrudg (5),
               vbrudgmrt (6),
               vbrudgmnrt (7),
               optional (50)
               }
   MAX-ACCESS  read-only
   STATUS      current
   DESCRIPTION
      "Path: atm.status.pvcTable.atm.serviceCategory

       Possibilities:
               notAssigned   (0)
               cbr   (1)
               vbr-rt   (2)
               vbr-nrt   (3)
               ubr   (4)
               cbr_dg   (5)
               vbr_dg-rt   (6)
               vbr_dg-nrt   (7)
               optional   (50)"
   ::= {sr1646v2ATMImaStatEntry 285736960}

sr1646v2ATMImaStatAtmPeakCellRate OBJECT-TYPE
   SYNTAX      Integer32
   UNITS       "bps"
   MAX-ACCESS  read-only
   STATUS      current
   DESCRIPTION
      "Path: atm.status.pvcTable.atm.peakCellRate

       unit name = bps"
   ::= {sr1646v2ATMImaStatEntry 285605888}

sr1646v2ATMImaStatAtmSustCellRate OBJECT-TYPE
   SYNTAX      Integer32
   UNITS       "bps"
   MAX-ACCESS  read-only
   STATUS      current
   DESCRIPTION
      "Path: atm.status.pvcTable.atm.sustCellRate

       unit name = bps"
   ::= {sr1646v2ATMImaStatEntry 285671424}

sr1646v2ATMImaStatAtmMaxBurstSize OBJECT-TYPE
   SYNTAX      Integer32
   UNITS       "cellTimes"
   MAX-ACCESS  read-only
   STATUS      current
   DESCRIPTION
      "Path: atm.status.pvcTable.atm.maxBurstSize

       unit name = cellTimes"
   ::= {sr1646v2ATMImaStatEntry 285802496}

sr1646v2ATMImaStatAtmPppOEthDiscState OBJECT-TYPE
   SYNTAX      INTEGER
               {
               idle (0),
               waitForPADO (1),
               waitForPADS (2),
               established (3)
               }
   MAX-ACCESS  read-only
   STATUS      current
   DESCRIPTION
      "Path: atm.status.pvcTable.atm.pppOverEth.discState

       Possibilities:
               idle   (0)
               waitForPADO   (1)
               waitForPADS   (2)
               established   (3)"
   ::= {sr1646v2ATMImaStatEntry 285409536}

sr1646v2ATMImaStatAtmPppOEthPeerMac OBJECT-TYPE
   SYNTAX      OCTET STRING
   MAX-ACCESS  read-only
   STATUS      current
   DESCRIPTION
      "Path: atm.status.pvcTable.atm.pppOverEth.remoteMacAddress

       MAC address."
   ::= {sr1646v2ATMImaStatEntry 285409792}

sr1646v2ATMImaStatAtmPppOEthServiceName OBJECT-TYPE
   SYNTAX      DisplayString
   MAX-ACCESS  read-only
   STATUS      current
   DESCRIPTION
      "Path: atm.status.pvcTable.atm.pppOverEth.serviceName"
   ::= {sr1646v2ATMImaStatEntry 285410048}

sr1646v2ATMImaStatAtmPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMImaStatEntry 285475072}

sr1646v2ATMImaStatAtmPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMImaStatEntry 285475328}

sr1646v2ATMImaStatAtmPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMImaStatEntry 285478656}

sr1646v2ATMImaStatAtmPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMImaStatEntry 285475584}

sr1646v2ATMImaStatAtmPppCcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: atm.status.pvcTable.atm.ppp.ccpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2ATMImaStatEntry 285477888}

sr1646v2ATMImaStatAtmPppHisCompRat OBJECT-TYPE
   SYNTAX      Integer32
   UNITS       "%"
   MAX-ACCESS  read-only
   STATUS      current
   DESCRIPTION
      "Path: atm.status.pvcTable.atm.ppp.myCompressionRatio

       unit name = %"
   ::= {sr1646v2ATMImaStatEntry 285478144}

sr1646v2ATMImaStatAtmPppMyCompRat OBJECT-TYPE
   SYNTAX      Integer32
   UNITS       "%"
   MAX-ACCESS  read-only
   STATUS      current
   DESCRIPTION
      "Path: atm.status.pvcTable.atm.ppp.hisCompressionRatio

       unit name = %"
   ::= {sr1646v2ATMImaStatEntry 285478400}

sr1646v2ATMImaStatAtmPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: atm.status.pvcTable.atm.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2ATMImaStatEntry 285477376}

sr1646v2ATMImaStatAtmPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: atm.status.pvcTable.atm.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2ATMImaStatEntry 285477632}

sr1646v2ATMImaStatAtmOamF5SegOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamLB

       Possibilities:
               ready   (0)
               waitActRes   (1)
               waitActCon   (2)
               waitDeactCon   (3)
               active   (4)
               deactivated   (5)"
   ::= {sr1646v2ATMImaStatEntry 285540640}

sr1646v2ATMImaStatAtmOamF5SegOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamCC

       Possibilities:
               ready   (0)
               waitActRes   (1)
               waitActCon   (2)
               waitDeactCon   (3)
               active   (4)
               deactivated   (5)"
   ::= {sr1646v2ATMImaStatEntry 285540672}

sr1646v2ATMImaStatAtmOamF5SegOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.segment.oamPM.status

       Possibilities:
               ready   (0)
               waitActRes   (1)
               waitActCon   (2)
               waitDeactCon   (3)
               active   (4)
               deactivated   (5)"
   ::= {sr1646v2ATMImaStatEntry 285540708}

sr1646v2ATMImaStatAtmOamF5SegOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.segment.oamPM.blockSizeAB

       Possibilities:
               128   (0)
               256   (1)
               512   (2)
               1024   (3)
               2048   (4)
               4096   (5)
               8192   (6)
               16384   (7)
               32768   (8)"
   ::= {sr1646v2ATMImaStatEntry 285540712}

sr1646v2ATMImaStatAtmOamF5SegOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.segment.oamPM.blockSizeBA

       Possibilities:
               128   (0)
               256   (1)
               512   (2)
               1024   (3)
               2048   (4)
               4096   (5)
               8192   (6)
               16384   (7)
               32768   (8)"
   ::= {sr1646v2ATMImaStatEntry 285540716}

sr1646v2ATMImaStatAtmOamF5SegAis OBJECT-TYPE
   SYNTAX      INTEGER
               {
               inactive (0),
               active (1)
               }
   MAX-ACCESS  read-only
   STATUS      current
   DESCRIPTION
      "Path: atm.status.pvcTable.atm.oamF5.segment.aisState

       Possibilities:
               inactive   (0)
               active   (1)"
   ::= {sr1646v2ATMImaStatEntry 285540736}

sr1646v2ATMImaStatAtmOamF5SegRdi OBJECT-TYPE
   SYNTAX      INTEGER
               {
               inactive (0),
               active (1)
               }
   MAX-ACCESS  read-only
   STATUS      current
   DESCRIPTION
      "Path: atm.status.pvcTable.atm.oamF5.segment.rdiState

       Possibilities:
               inactive   (0)
               active   (1)"
   ::= {sr1646v2ATMImaStatEntry 285540768}

sr1646v2ATMImaStatAtmOamF5EteOamLB OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamLB

       Possibilities:
               ready   (0)
               waitActRes   (1)
               waitActCon   (2)
               waitDeactCon   (3)
               active   (4)
               deactivated   (5)"
   ::= {sr1646v2ATMImaStatEntry 285540896}

sr1646v2ATMImaStatAtmOamF5EteOamCC OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamCC

       Possibilities:
               ready   (0)
               waitActRes   (1)
               waitActCon   (2)
               waitDeactCon   (3)
               active   (4)
               deactivated   (5)"
   ::= {sr1646v2ATMImaStatEntry 285540928}

sr1646v2ATMImaStatAtmOamF5EteOamPMStatus OBJECT-TYPE
   SYNTAX      INTEGER
               {
               ready (0),
               waitActRes (1),
               waitActCon (2),
               waitDeactCon (3),
               active (4),
               deactivated (5)
               }
   MAX-ACCESS  read-only
   STATUS      current
   DESCRIPTION
      "Path: atm.status.pvcTable.atm.oamF5.endToEnd.oamPM.status

       Possibilities:
               ready   (0)
               waitActRes   (1)
               waitActCon   (2)
               waitDeactCon   (3)
               active   (4)
               deactivated   (5)"
   ::= {sr1646v2ATMImaStatEntry 285540964}

sr1646v2ATMImaStatAtmOamF5EteOamPMBlockSizeAB OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.endToEnd.oamPM.blockSizeAB

       Possibilities:
               128   (0)
               256   (1)
               512   (2)
               1024   (3)
               2048   (4)
               4096   (5)
               8192   (6)
               16384   (7)
               32768   (8)"
   ::= {sr1646v2ATMImaStatEntry 285540968}

sr1646v2ATMImaStatAtmOamF5EteOamPMBlockSizeBA OBJECT-TYPE
   SYNTAX      INTEGER
               {
               s128 (0),
               s256 (1),
               s512 (2),
               s1024 (3),
               s2048 (4),
               s4096 (5),
               s8192 (6),
               s16384 (7),
               s32768 (8)
               }
   MAX-ACCESS  read-only
   STATUS      current
   DESCRIPTION
      "Path: atm.status.pvcTable.atm.oamF5.endToEnd.oamPM.blockSizeBA

       Possibilities:
               128   (0)
               256   (1)
               512   (2)
               1024   (3)
               2048   (4)
               4096   (5)
               8192   (6)
               16384   (7)
               32768   (8)"
   ::= {sr1646v2ATMImaStatEntry 285540972}

sr1646v2ATMImaStatAtmOamF5EteAis OBJECT-TYPE
   SYNTAX      INTEGER
               {
               inactive (0),
               active (1)
               }
   MAX-ACCESS  read-only
   STATUS      current
   DESCRIPTION
      "Path: atm.status.pvcTable.atm.oamF5.endToEnd.aisState

       Possibilities:
               inactive   (0)
               active   (1)"
   ::= {sr1646v2ATMImaStatEntry 285540992}

sr1646v2ATMImaStatAtmOamF5EteRdi OBJECT-TYPE
   SYNTAX      INTEGER
               {
               inactive (0),
               active (1)
               }
   MAX-ACCESS  read-only
   STATUS      current
   DESCRIPTION
      "Path: atm.status.pvcTable.atm.oamF5.endToEnd.rdiState

       Possibilities:
               inactive   (0)
               active   (1)"
   ::= {sr1646v2ATMImaStatEntry 285541024}

sr1646v2ATMImaStatAtmOamF5SegEP OBJECT-TYPE
   SYNTAX      INTEGER
               {
               no (0),
               yes (1)
               }
   MAX-ACCESS  read-only
   STATUS      current
   DESCRIPTION
      "Path: atm.status.pvcTable.atm.oamF5.segmentEndPoint

       Possibilities:
               no   (0)
               yes   (1)"
   ::= {sr1646v2ATMImaStatEntry 285541120}

sr1646v2ATMImaStatAtmOamF5CnxEP OBJECT-TYPE
   SYNTAX      INTEGER
               {
               no (0),
               yes (1)
               }
   MAX-ACCESS  read-only
   STATUS      current
   DESCRIPTION
      "Path: atm.status.pvcTable.atm.oamF5.connectionEndPoint

       Possibilities:
               no   (0)
               yes   (1)"
   ::= {sr1646v2ATMImaStatEntry 285541376}

sr1646v2ATMImaStatFrLmiMode OBJECT-TYPE
   SYNTAX      INTEGER
               {
               auto (0),
               network (1),
               user (2),
               noLmi (3),
               nni (4)
               }
   MAX-ACCESS  read-only
   STATUS      current
   DESCRIPTION
      "Path: atm.status.pvcTable.frameRelay.lmi.mode

       Possibilities:
               auto   (0)
               network   (1)
               user   (2)
               noLmi   (3)
               nni   (4)"
   ::= {sr1646v2ATMImaStatEntry 503382528}

sr1646v2ATMImaStatFrLmiType OBJECT-TYPE
   SYNTAX      INTEGER
               {
               lmiRev1 (1),
               ansiT1m617md (2),
               q933mAnnexmA (3),
               frf1m2 (4)
               }
   MAX-ACCESS  read-only
   STATUS      current
   DESCRIPTION
      "Path: atm.status.pvcTable.frameRelay.lmi.type

       Possibilities:
               lmiRev1   (1)
               ansiT1-617-d   (2)
               q933-Annex-A   (3)
               frf1-2   (4)"
   ::= {sr1646v2ATMImaStatEntry 503382272}

sr1646v2ATMImaStatFrLmiStatus OBJECT-TYPE
   SYNTAX      INTEGER
               {
               up (1),
               down (0)
               }
   MAX-ACCESS  read-only
   STATUS      current
   DESCRIPTION
      "Path: atm.status.pvcTable.frameRelay.lmi.status

       Possibilities:
               up   (1)
               down   (0)"
   ::= {sr1646v2ATMImaStatEntry 503382784}

sr1646v2ATMImaStatFrLmiLastChange OBJECT-TYPE
   SYNTAX      TimeTicks
   MAX-ACCESS  read-only
   STATUS      current
   DESCRIPTION
      "Path: atm.status.pvcTable.frameRelay.lmi.lastStatusChange

       Time in centi-second."
   ::= {sr1646v2ATMImaStatEntry 503383040}

sr1646v2ATMImaStatFrLmiLastError OBJECT-TYPE
   SYNTAX      INTEGER
               {
               none (10),
               protocolserror (6),
               unknownsinformationselement (7),
               sequenceserror (8),
               unknownsreport (9),
               timersexpired (38),
               invalidsreportstype (39),
               unsolicitedsstatus (54)
               }
   MAX-ACCESS  read-only
   STATUS      current
   DESCRIPTION
      "Path: atm.status.pvcTable.frameRelay.lmi.lastError

       Possibilities:
               none   (10)
               protocol error   (6)
               unknown information element   (7)
               sequence error   (8)
               unknown report   (9)
               timer expired   (38)
               invalid report type   (39)
               unsolicited status   (54)"
   ::= {sr1646v2ATMImaStatEntry 503383296}

sr1646v2ATMImaStatFrLmiNetTxSeqNum OBJECT-TYPE
   SYNTAX      Integer32
   MAX-ACCESS  read-only
   STATUS      current
   DESCRIPTION
      "Path: atm.status.pvcTable.frameRelay.lmi.netTxSeqNum"
   ::= {sr1646v2ATMImaStatEntry 503383552}

sr1646v2ATMImaStatFrLmiNetRxSeqNum OBJECT-TYPE
   SYNTAX      Integer32
   MAX-ACCESS  read-only
   STATUS      current
   DESCRIPTION
      "Path: atm.status.pvcTable.frameRelay.lmi.netRxSeqNum"
   ::= {sr1646v2ATMImaStatEntry 503383808}

sr1646v2ATMImaStatFrLmiNetErrors OBJECT-TYPE
   SYNTAX      Integer32
   MAX-ACCESS  read-only
   STATUS      current
   DESCRIPTION
      "Path: atm.status.pvcTable.frameRelay.lmi.netErrors"
   ::= {sr1646v2ATMImaStatEntry 503384064}

sr1646v2ATMImaStatFrLmiUserTxSeqNum OBJECT-TYPE
   SYNTAX      Integer32
   MAX-ACCESS  read-only
   STATUS      current
   DESCRIPTION
      "Path: atm.status.pvcTable.frameRelay.lmi.userTxSeqNum"
   ::= {sr1646v2ATMImaStatEntry 503387136}

sr1646v2ATMImaStatFrLmiUserRxSeqNum OBJECT-TYPE
   SYNTAX      Integer32
   MAX-ACCESS  read-only
   STATUS      current
   DESCRIPTION
      "Path: atm.status.pvcTable.frameRelay.lmi.userRxSeqNum"
   ::= {sr1646v2ATMImaStatEntry 503387392}

sr1646v2ATMImaStatFrLmiUserErrors OBJECT-TYPE
   SYNTAX      Integer32
   MAX-ACCESS  read-only
   STATUS      current
   DESCRIPTION
      "Path: atm.status.pvcTable.frameRelay.lmi.userErrors"
   ::= {sr1646v2ATMImaStatEntry 503387648}

sr1646v2ATMImaStatFrLmiUWaitFullEnq OBJECT-TYPE
   SYNTAX      Integer32
   MAX-ACCESS  read-only
   STATUS      current
   DESCRIPTION
      "Path: atm.status.pvcTable.frameRelay.lmi.userWaitFullEnquiry"
   ::= {sr1646v2ATMImaStatEntry 503387904}

sr1646v2ATMImaStatFrLmiULstRepTypeTx OBJECT-TYPE
   SYNTAX      INTEGER
               {
               fullsstatus (0),
               linksintegrity (1),
               singlesstatus (2),
               updatedsstatus (3),
               fullsstatusscontd (4),
               smmmmmmmm (170)
               }
   MAX-ACCESS  read-only
   STATUS      current
   DESCRIPTION
      "Path: atm.status.pvcTable.frameRelay.lmi.userLastReportTypeSent

       Possibilities:
               full status   (0)
               link integrity   (1)
               single status   (2)
               updated status   (3)
               full status cont.   (4)
               --------   (170)"
   ::= {sr1646v2ATMImaStatEntry 503388160}

sr1646v2ATMImaStatIpV6Addresses OBJECT-TYPE
   SYNTAX      SEQUENCE OF Sr1646v2ATMImaStatIpV6AddressesEntry
   MAX-ACCESS  not-accessible
   STATUS      current
   DESCRIPTION
      ""
   ::= {sr1646v2ATMImaStat 100859904}

sr1646v2ATMImaStatIpV6AddressesEntry OBJECT-TYPE
   SYNTAX      Sr1646v2ATMImaStatIpV6AddressesEntry
   MAX-ACCESS  not-accessible
   STATUS      current
   DESCRIPTION
      ""
   INDEX      { sr1646v2ATMImaStatTableIx,
                sr1646v2ATMImaStatIpV6AddressesTableIx }
   ::= {sr1646v2ATMImaStatIpV6Addresses 1}

Sr1646v2ATMImaStatIpV6AddressesEntry ::=
   SEQUENCE
      {
      sr1646v2ATMImaStatIpV6AddressesTableIx
         TableIndex,
      sr1646v2ATMImaStatIpV6AddressesAddress
         Ipv6Address,
      sr1646v2ATMImaStatIpV6AddressesPrefixLength
         Integer32,
      sr1646v2ATMImaStatIpV6AddressesStatus
         INTEGER,
      sr1646v2ATMImaStatIpV6AddressesOrigin
         INTEGER,
      sr1646v2ATMImaStatIpV6AddressesFlagsInterfaceId
         INTEGER,
      sr1646v2ATMImaStatIpV6AddressesFlagsAnycast
         INTEGER,
      sr1646v2ATMImaStatIpV6AddressesTimersValidLifeTime
         TimeTicks,
      sr1646v2ATMImaStatIpV6AddressesTimersPrefLifeTime
         TimeTicks
      }

sr1646v2ATMImaStatIpV6AddressesTableIx OBJECT-TYPE
   SYNTAX      TableIndex
   MAX-ACCESS  not-accessible
   STATUS      current
   DESCRIPTION
      ""
   ::= {sr1646v2ATMImaStatIpV6AddressesEntry 11}

sr1646v2ATMImaStatIpV6AddressesAddress OBJECT-TYPE
   SYNTAX      Ipv6Address
   MAX-ACCESS  read-only
   STATUS      current
   DESCRIPTION
      "Path: atm.status.pvcTable.ipV6.addresses.address

       ipv6 address"
   ::= {sr1646v2ATMImaStatIpV6AddressesEntry 16777216}

sr1646v2ATMImaStatIpV6AddressesPrefixLength OBJECT-TYPE
   SYNTAX      Integer32
   MAX-ACCESS  read-only
   STATUS      current
   DESCRIPTION
      "Path: atm.status.pvcTable.ipV6.addresses.prefixLength"
   ::= {sr1646v2ATMImaStatIpV6AddressesEntry 33554432}

sr1646v2ATMImaStatIpV6AddressesStatus OBJECT-TYPE
   SYNTAX      INTEGER
               {
               invalid (0),
               tentative (1),
               deprecated (2),
               preferred (3)
               }
   MAX-ACCESS  read-only
   STATUS      current
   DESCRIPTION
      "Path: atm.status.pvcTable.ipV6.addresses.status

       Possibilities:
               invalid   (0)
               tentative   (1)
               deprecated   (2)
               preferred   (3)"
   ::= {sr1646v2ATMImaStatIpV6AddressesEntry 50331648}

sr1646v2ATMImaStatIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: atm.status.pvcTable.ipV6.addresses.origin

       Possibilities:
               unknown   (0)
               manual   (1)
               generalPrefix   (2)
               statelessAuto   (3)
               statefullAuto   (4)"
   ::= {sr1646v2ATMImaStatIpV6AddressesEntry 67108864}

sr1646v2ATMImaStatIpV6AddressesFlagsInterfaceId OBJECT-TYPE
   SYNTAX      INTEGER
               {
               no (0),
               yes (1)
               }
   MAX-ACCESS  read-only
   STATUS      current
   DESCRIPTION
      "Path: atm.status.pvcTable.ipV6.addresses.flags.interfaceId

       Possibilities:
               no   (0)
               yes   (1)"
   ::= {sr1646v2ATMImaStatIpV6AddressesEntry 83951616}

sr1646v2ATMImaStatIpV6AddressesFlagsAnycast OBJECT-TYPE
   SYNTAX      INTEGER
               {
               no (0),
               yes (1)
               }
   MAX-ACCESS  read-only
   STATUS      current
   DESCRIPTION
      "Path: atm.status.pvcTable.ipV6.addresses.flags.anycast

       Possibilities:
               no   (0)
               yes   (1)"
   ::= {sr1646v2ATMImaStatIpV6AddressesEntry 84017152}

sr1646v2ATMImaStatIpV6AddressesTimersValidLifeTime OBJECT-TYPE
   SYNTAX      TimeTicks
   MAX-ACCESS  read-only
   STATUS      current
   DESCRIPTION
      "Path: atm.status.pvcTable.ipV6.addresses.timers.validLifeTime

       Time in centi-second."
   ::= {sr1646v2ATMImaStatIpV6AddressesEntry 100794368}

sr1646v2ATMImaStatIpV6AddressesTimersPrefLifeTime OBJECT-TYPE
   SYNTAX      TimeTicks
   MAX-ACCESS  read-only
   STATUS      current
   DESCRIPTION
      "Path: atm.status.pvcTable.ipV6.addresses.timers.prefLifeTime

       Time in centi-second."
   ::= {sr1646v2ATMImaStatIpV6AddressesEntry 100728832}

sr1646v2ATMImaStatFrDlci OBJECT-TYPE
   SYNTAX      SEQUENCE OF Sr1646v2ATMImaStatFrDlciEntry
   MAX-ACCESS  not-accessible
   STATUS      current
   DESCRIPTION
      ""
   ::= {sr1646v2ATMImaStat 503447552}

sr1646v2ATMImaStatFrDlciEntry OBJECT-TYPE
   SYNTAX      Sr1646v2ATMImaStatFrDlciEntry
   MAX-ACCESS  not-accessible
   STATUS      current
   DESCRIPTION
      ""
   INDEX      { sr1646v2ATMImaStatTableIx,
                sr1646v2ATMImaStatFrDlciTableIx }
   ::= {sr1646v2ATMImaStatFrDlci 1}

Sr1646v2ATMImaStatFrDlciEntry ::=
   SEQUENCE
      {
      sr1646v2ATMImaStatFrDlciTableIx
         TableIndex,
      sr1646v2ATMImaStatFrDlciName
         DisplayString,
      sr1646v2ATMImaStatFrDlciMode
         INTEGER,
      sr1646v2ATMImaStatFrDlciIfOperStatus
         INTEGER,
      sr1646v2ATMImaStatFrDlciIfLastChange
         TimeTicks,
      sr1646v2ATMImaStatFrDlciIfLastChangeDate
         DisplayString,
      sr1646v2ATMImaStatFrDlciIpAddress
         IpAddress,
      sr1646v2ATMImaStatFrDlciIpNetMask
         IpAddress,
      sr1646v2ATMImaStatFrDlciIpRemote
         IpAddress,
      sr1646v2ATMImaStatFrDlciBridgingStatus
         INTEGER,
      sr1646v2ATMImaStatFrDlciBridgingSpanningTreePortRole
         INTEGER,
      sr1646v2ATMImaStatFrDlciBridgingSpanningTreePortId
         Integer32,
      sr1646v2ATMImaStatFrDlciBridgingSpanningTreePpCostExtPathCost
         Integer32,
      sr1646v2ATMImaStatFrDlciBridgingSpanningTreePpCostIntPathCost
         Integer32,
      sr1646v2ATMImaStatFrDlciBridgingSpanningTreeExtRpCost
         Integer32,
      sr1646v2ATMImaStatFrDlciBridgingSpanningTreeIntRpCost
         Integer32,
      sr1646v2ATMImaStatFrDlciBridgingSpanningTreeDesBrIdPriority
         Integer32,
      sr1646v2ATMImaStatFrDlciBridgingSpanningTreeDesBrIdMacAddress
         OCTET STRING,
      sr1646v2ATMImaStatFrDlciBridgingSpanningTreeDesPrtId
         Integer32,
      sr1646v2ATMImaStatFrDlciBridgingSpanningTreeDesInt
         INTEGER,
      sr1646v2ATMImaStatFrDlciBridgingSpanningTreeEdgeDetection
         INTEGER,
      sr1646v2ATMImaStatFrDlciFrDlci
         Integer32,
      sr1646v2ATMImaStatFrDlciFrActive
         INTEGER,
      sr1646v2ATMImaStatFrDlciFrNew
         INTEGER,
      sr1646v2ATMImaStatFrDlciFrDelete
         INTEGER,
      sr1646v2ATMImaStatFrDlciFrRr
         INTEGER,
      sr1646v2ATMImaStatFrDlciFrBandwidth
         Integer32,
      sr1646v2ATMImaStatFrDlciFrCllmLstCong
         INTEGER
      }

sr1646v2ATMImaStatFrDlciTableIx OBJECT-TYPE
   SYNTAX      TableIndex
   MAX-ACCESS  not-accessible
   STATUS      current
   DESCRIPTION
      ""
   ::= {sr1646v2ATMImaStatFrDlciEntry 11}

sr1646v2ATMImaStatFrDlciName OBJECT-TYPE
   SYNTAX      DisplayString
   MAX-ACCESS  read-only
   STATUS      current
   DESCRIPTION
      "Path: atm.status.pvcTable.frameRelay.dlciTable.name"
   ::= {sr1646v2ATMImaStatFrDlciEntry 16777216}

sr1646v2ATMImaStatFrDlciMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: atm.status.pvcTable.frameRelay.dlciTable.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2ATMImaStatFrDlciEntry 335544320}

sr1646v2ATMImaStatFrDlciIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: atm.status.pvcTable.frameRelay.dlciTable.ifOperStatus

       Possibilities:
               up   (1)
               down   (2)
               testing   (3)
               unknown   (4)
               dormant   (5)
               notPresent   (6)
               lowerLayerDown   (7)"
   ::= {sr1646v2ATMImaStatFrDlciEntry 1795162112}

sr1646v2ATMImaStatFrDlciIfLastChange OBJECT-TYPE
   SYNTAX      TimeTicks
   MAX-ACCESS  read-only
   STATUS      current
   DESCRIPTION
      "Path: atm.status.pvcTable.frameRelay.dlciTable.ifLastChange

       Time in centi-second."
   ::= {sr1646v2ATMImaStatFrDlciEntry 1811939328}

sr1646v2ATMImaStatFrDlciIfLastChangeDate OBJECT-TYPE
   SYNTAX      DisplayString
   MAX-ACCESS  read-only
   STATUS      current
   DESCRIPTION
      "Path: atm.status.pvcTable.frameRelay.dlciTable.ifLastChangeDate"
   ::= {sr1646v2ATMImaStatFrDlciEntry 3070230528}

sr1646v2ATMImaStatFrDlciIpAddress OBJECT-TYPE
   SYNTAX      IpAddress
   MAX-ACCESS  read-only
   STATUS      current
   DESCRIPTION
      "Path: atm.status.pvcTable.frameRelay.dlciTable.ip.address"
   ::= {sr1646v2ATMImaStatFrDlciEntry 51380224}

sr1646v2ATMImaStatFrDlciIpNetMask OBJECT-TYPE
   SYNTAX      IpAddress
   MAX-ACCESS  read-only
   STATUS      current
   DESCRIPTION
      "Path: atm.status.pvcTable.frameRelay.dlciTable.ip.netMask"
   ::= {sr1646v2ATMImaStatFrDlciEntry 51445760}

sr1646v2ATMImaStatFrDlciIpRemote OBJECT-TYPE
   SYNTAX      IpAddress
   MAX-ACCESS  read-only
   STATUS      current
   DESCRIPTION
      "Path: atm.status.pvcTable.frameRelay.dlciTable.ip.remote"
   ::= {sr1646v2ATMImaStatFrDlciEntry 51511296}

sr1646v2ATMImaStatFrDlciBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: atm.status.pvcTable.frameRelay.dlciTable.bridging.status

       Possibilities:
               disabled   (0)
               discarding   (1)
               learning   (2)
               forwarding   (3)
               backupBlockedIntfDown   (256)
               backupBlockedIntfUp   (259)
               shutdown   (255)"
   ::= {sr1646v2ATMImaStatFrDlciEntry 453050368}

sr1646v2ATMImaStatFrDlciBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: atm.status.pvcTable.frameRelay.dlciTable.bridging.spanningTree.portRole

       Possibilities:
               none   (0)
               root   (1)
               designated   (2)
               alternate   (3)
               backup   (4)
               disabled   (5)
               master   (6)"
   ::= {sr1646v2ATMImaStatFrDlciEntry 453116160}

sr1646v2ATMImaStatFrDlciBridgingSpanningTreePortId OBJECT-TYPE
   SYNTAX      Integer32
   MAX-ACCESS  read-only
   STATUS      current
   DESCRIPTION
      "Path: atm.status.pvcTable.frameRelay.dlciTable.bridging.spanningTree.portId"
   ::= {sr1646v2ATMImaStatFrDlciEntry 453116416}

sr1646v2ATMImaStatFrDlciBridgingSpanningTreePpCostExtPathCost OBJECT-TYPE
   SYNTAX      Integer32
   MAX-ACCESS  read-only
   STATUS      current
   DESCRIPTION
      "Path: atm.status.pvcTable.frameRelay.dlciTable.bridging.spanningTree.portPathCosts.extPathCost"
   ::= {sr1646v2ATMImaStatFrDlciEntry 453116673}

sr1646v2ATMImaStatFrDlciBridgingSpanningTreePpCostIntPathCost OBJECT-TYPE
   SYNTAX      Integer32
   MAX-ACCESS  read-only
   STATUS      current
   DESCRIPTION
      "Path: atm.status.pvcTable.frameRelay.dlciTable.bridging.spanningTree.portPathCosts.intPathCost"
   ::= {sr1646v2ATMImaStatFrDlciEntry 453116674}

sr1646v2ATMImaStatFrDlciBridgingSpanningTreeExtRpCost OBJECT-TYPE
   SYNTAX      Integer32
   MAX-ACCESS  read-only
   STATUS      current
   DESCRIPTION
      "Path: atm.status.pvcTable.frameRelay.dlciTable.bridging.spanningTree.extRootPathCost"
   ::= {sr1646v2ATMImaStatFrDlciEntry 453116928}

sr1646v2ATMImaStatFrDlciBridgingSpanningTreeIntRpCost OBJECT-TYPE
   SYNTAX      Integer32
   MAX-ACCESS  read-only
   STATUS      current
   DESCRIPTION
      "Path: atm.status.pvcTable.frameRelay.dlciTable.bridging.spanningTree.intRootPathCost"
   ::= {sr1646v2ATMImaStatFrDlciEntry 453117184}

sr1646v2ATMImaStatFrDlciBridgingSpanningTreeDesBrIdPriority OBJECT-TYPE
   SYNTAX      Integer32
   MAX-ACCESS  read-only
   STATUS      current
   DESCRIPTION
      "Path: atm.status.pvcTable.frameRelay.dlciTable.bridging.spanningTree.designatedBridgeId.priority"
   ::= {sr1646v2ATMImaStatFrDlciEntry 453117441}

sr1646v2ATMImaStatFrDlciBridgingSpanningTreeDesBrIdMacAddress OBJECT-TYPE
   SYNTAX      OCTET STRING
   MAX-ACCESS  read-only
   STATUS      current
   DESCRIPTION
      "Path: atm.status.pvcTable.frameRelay.dlciTable.bridging.spanningTree.designatedBridgeId.macAddress

       MAC address."
   ::= {sr1646v2ATMImaStatFrDlciEntry 453117442}

sr1646v2ATMImaStatFrDlciBridgingSpanningTreeDesPrtId OBJECT-TYPE
   SYNTAX      Integer32
   MAX-ACCESS  read-only
   STATUS      current
   DESCRIPTION
      "Path: atm.status.pvcTable.frameRelay.dlciTable.bridging.spanningTree.designatedPortId"
   ::= {sr1646v2ATMImaStatFrDlciEntry 453117696}

sr1646v2ATMImaStatFrDlciBridgingSpanningTreeDesInt OBJECT-TYPE
   SYNTAX      INTEGER
               {
               no (0),
               yes (1)
               }
   MAX-ACCESS  read-only
   STATUS      current
   DESCRIPTION
      "Path: atm.status.pvcTable.frameRelay.dlciTable.bridging.spanningTree.designatedOrInternal

       Possibilities:
               no   (0)
               yes   (1)"
   ::= {sr1646v2ATMImaStatFrDlciEntry 453117952}

sr1646v2ATMImaStatFrDlciBridgingSpanningTreeEdgeDetection OBJECT-TYPE
   SYNTAX      INTEGER
               {
               none (0),
               edge (1),
               notEdge (2)
               }
   MAX-ACCESS  read-only
   STATUS      current
   DESCRIPTION
      "Path: atm.status.pvcTable.frameRelay.dlciTable.bridging.spanningTree.edgeDetection

       Possibilities:
               none   (0)
               edge   (1)
               notEdge   (2)"
   ::= {sr1646v2ATMImaStatFrDlciEntry 453118208}

sr1646v2ATMImaStatFrDlciFrDlci OBJECT-TYPE
   SYNTAX      Integer32
   MAX-ACCESS  read-only
   STATUS      current
   DESCRIPTION
      "Path: atm.status.pvcTable.frameRelay.dlciTable.frameRelay.dlci"
   ::= {sr1646v2ATMImaStatFrDlciEntry 218169344}

sr1646v2ATMImaStatFrDlciFrActive OBJECT-TYPE
   SYNTAX      INTEGER
               {
               off (0),
               on (1)
               }
   MAX-ACCESS  read-only
   STATUS      current
   DESCRIPTION
      "Path: atm.status.pvcTable.frameRelay.dlciTable.frameRelay.active

       Possibilities:
               off   (0)
               on   (1)"
   ::= {sr1646v2ATMImaStatFrDlciEntry 218234880}

sr1646v2ATMImaStatFrDlciFrNew OBJECT-TYPE
   SYNTAX      INTEGER
               {
               off (0),
               on (1)
               }
   MAX-ACCESS  read-only
   STATUS      current
   DESCRIPTION
      "Path: atm.status.pvcTable.frameRelay.dlciTable.frameRelay.new

       Possibilities:
               off   (0)
               on   (1)"
   ::= {sr1646v2ATMImaStatFrDlciEntry 218300416}

sr1646v2ATMImaStatFrDlciFrDelete OBJECT-TYPE
   SYNTAX      INTEGER
               {
               off (0),
               on (1)
               }
   MAX-ACCESS  read-only
   STATUS      current
   DESCRIPTION
      "Path: atm.status.pvcTable.frameRelay.dlciTable.frameRelay.delete

       Possibilities:
               off   (0)
               on   (1)"
   ::= {sr1646v2ATMImaStatFrDlciEntry 218365952}

sr1646v2ATMImaStatFrDlciFrRr OBJECT-TYPE
   SYNTAX      INTEGER
               {
               off (0),
               on (1)
               }
   MAX-ACCESS  read-only
   STATUS      current
   DESCRIPTION
      "Path: atm.status.pvcTable.frameRelay.dlciTable.frameRelay.rr

       Possibilities:
               off   (0)
               on   (1)"
   ::= {sr1646v2ATMImaStatFrDlciEntry 218431488}

sr1646v2ATMImaStatFrDlciFrBandwidth OBJECT-TYPE
   SYNTAX      Integer32
   MAX-ACCESS  read-only
   STATUS      current
   DESCRIPTION
      "Path: atm.status.pvcTable.frameRelay.dlciTable.frameRelay.bandwidth"
   ::= {sr1646v2ATMImaStatFrDlciEntry 218497024}

sr1646v2ATMImaStatFrDlciFrCllmLstCong OBJECT-TYPE
   SYNTAX      INTEGER
               {
               none (0),
               shortstermsexcessivestraffic (2),
               longstermsexcessivestraffic (3),
               shortstermsequipmentsfailure (6),
               longstermsequipmentsfailure (7),
               shortstermsmaintenancesaction (10),
               longstermsmaintenancesaction (11),
               shortstermsunknownscause (16),
               longstermsunknownscause (17),
               unknownscause (255)
               }
   MAX-ACCESS  read-only
   STATUS      current
   DESCRIPTION
      "Path: atm.status.pvcTable.frameRelay.dlciTable.frameRelay.cllmLastCongestionCause

       Possibilities:
               none   (0)
               short term, excessive traffic   (2)
               long term, excessive traffic   (3)
               short term, equipment failure   (6)
               long term, equipment failure   (7)
               short term, maintenance action   (10)
               long term, maintenance action   (11)
               short term, unknown cause   (16)
               long term, unknown cause   (17)
               unknown cause   (255)"
   ::= {sr1646v2ATMImaStatFrDlciEntry 218562560}



pr1646v2ATMIma OBJECT IDENTIFIER ::= {r1646v2ATMIma 12}


pr1646v2ATMImaUnknownCells OBJECT-TYPE
   SYNTAX      Gauge32
   MAX-ACCESS  read-only
   STATUS      current
   DESCRIPTION
      "Path: atm.performance.unknownCells

       32 bit unsigned gauge value."
   ::= {pr1646v2ATMIma 44}


pr1646v2ATMImaVp OBJECT IDENTIFIER ::= {pr1646v2ATMIma 94}

pr1646v2ATMImaVpSSCTable OBJECT-TYPE
   SYNTAX      SEQUENCE OF Pr1646v2ATMImaVpEntry
   MAX-ACCESS  not-accessible
   STATUS      current
   DESCRIPTION
      ""
   ::= {pr1646v2ATMImaVp 1}

pr1646v2ATMImaVpEntry OBJECT-TYPE
   SYNTAX      Pr1646v2ATMImaVpEntry
   MAX-ACCESS  not-accessible
   STATUS      current
   DESCRIPTION
      ""
   INDEX      { pr1646v2ATMImaVpTableIx }
   ::= {pr1646v2ATMImaVpSSCTable 1}

Pr1646v2ATMImaVpEntry ::=
   SEQUENCE
      {
      pr1646v2ATMImaVpTableIx
         TableIndex,
      pr1646v2ATMImaVpVpi
         Integer32,
      pr1646v2ATMImaVpOamF4SegLbRx
         Gauge32,
      pr1646v2ATMImaVpOamF4SegLbTx
         Gauge32,
      pr1646v2ATMImaVpOamF4SegCcRx
         Gauge32,
      pr1646v2ATMImaVpOamF4SegCcTx
         Gauge32,
      pr1646v2ATMImaVpOamF4SegFpmRx
         Gauge32,
      pr1646v2ATMImaVpOamF4SegFpmTx
         Gauge32,
      pr1646v2ATMImaVpOamF4SegBrRx
         Gauge32,
      pr1646v2ATMImaVpOamF4SegBrTx
         Gauge32,
      pr1646v2ATMImaVpOamF4SegAdRx
         Gauge32,
      pr1646v2ATMImaVpOamF4SegAdTx
         Gauge32,
      pr1646v2ATMImaVpOamF4SegAisRx
         Gauge32,
      pr1646v2ATMImaVpOamF4SegAisTx
         Gauge32,
      pr1646v2ATMImaVpOamF4SegRdiRx
         Gauge32,
      pr1646v2ATMImaVpOamF4SegRdiTx
         Gauge32,
      pr1646v2ATMImaVpOamF4SegRxpmNLOC
         Gauge32,
      pr1646v2ATMImaVpOamF4SegRxpmNLUC
         Gauge32,
      pr1646v2ATMImaVpOamF4SegRxpmNEUC
         Gauge32,
      pr1646v2ATMImaVpOamF4SegRxpmNMUC
         Gauge32,
      pr1646v2ATMImaVpOamF4SegRxpmCer
         Integer32,
      pr1646v2ATMImaVpOamF4SegRxpmClr
         Integer32,
      pr1646v2ATMImaVpOamF4SegRxpmCmr
         Integer32,
      pr1646v2ATMImaVpOamF4SegRxpmSecb
         Integer32,
      pr1646v2ATMImaVpOamF4SegTxpmNLOC
         Gauge32,
      pr1646v2ATMImaVpOamF4SegTxpmNLUC
         Gauge32,
      pr1646v2ATMImaVpOamF4SegTxpmNEUC
         Gauge32,
      pr1646v2ATMImaVpOamF4SegTxpmNMUC
         Gauge32,
      pr1646v2ATMImaVpOamF4SegTxpmCer
         Integer32,
      pr1646v2ATMImaVpOamF4SegTxpmClr
         Integer32,
      pr1646v2ATMImaVpOamF4SegTxpmCmr
         Integer32,
      pr1646v2ATMImaVpOamF4SegTxpmSecb
         Integer32,
      pr1646v2ATMImaVpOamF4EteLbRx
         Gauge32,
      pr1646v2ATMImaVpOamF4EteLbTx
         Gauge32,
      pr1646v2ATMImaVpOamF4EteCcRx
         Gauge32,
      pr1646v2ATMImaVpOamF4EteCcTx
         Gauge32,
      pr1646v2ATMImaVpOamF4EteFpmRx
         Gauge32,
      pr1646v2ATMImaVpOamF4EteFpmTx
         Gauge32,
      pr1646v2ATMImaVpOamF4EteBrRx
         Gauge32,
      pr1646v2ATMImaVpOamF4EteBrTx
         Gauge32,
      pr1646v2ATMImaVpOamF4EteAdRx
         Gauge32,
      pr1646v2ATMImaVpOamF4EteAdTx
         Gauge32,
      pr1646v2ATMImaVpOamF4EteAisRx
         Gauge32,
      pr1646v2ATMImaVpOamF4EteAisTx
         Gauge32,
      pr1646v2ATMImaVpOamF4EteRdiRx
         Gauge32,
      pr1646v2ATMImaVpOamF4EteRdiTx
         Gauge32,
      pr1646v2ATMImaVpOamF4EteRxpmNLOC
         Gauge32,
      pr1646v2ATMImaVpOamF4EteRxpmNLUC
         Gauge32,
      pr1646v2ATMImaVpOamF4EteRxpmNEUC
         Gauge32,
      pr1646v2ATMImaVpOamF4EteRxpmNMUC
         Gauge32,
      pr1646v2ATMImaVpOamF4EteRxpmCer
         Integer32,
      pr1646v2ATMImaVpOamF4EteRxpmClr
         Integer32,
      pr1646v2ATMImaVpOamF4EteRxpmCmr
         Integer32,
      pr1646v2ATMImaVpOamF4EteRxpmSecb
         Integer32,
      pr1646v2ATMImaVpOamF4EteTxpmNLOC
         Gauge32,
      pr1646v2ATMImaVpOamF4EteTxpmNLUC
         Gauge32,
      pr1646v2ATMImaVpOamF4EteTxpmNEUC
         Gauge32,
      pr1646v2ATMImaVpOamF4EteTxpmNMUC
         Gauge32,
      pr1646v2ATMImaVpOamF4EteTxpmCer
         Integer32,
      pr1646v2ATMImaVpOamF4EteTxpmClr
         Integer32,
      pr1646v2ATMImaVpOamF4EteTxpmCmr
         Integer32,
      pr1646v2ATMImaVpOamF4EteTxpmSecb
         Integer32
      }

pr1646v2ATMImaVpTableIx OBJECT-TYPE
   SYNTAX      TableIndex
   MAX-ACCESS  not-accessible
   STATUS      current
   DESCRIPTION
      ""
   ::= {pr1646v2ATMImaVpEntry 11}

pr1646v2ATMImaVpVpi OBJECT-TYPE
   SYNTAX      Integer32
   MAX-ACCESS  read-only
   STATUS      current
   DESCRIPTION
      "Path: atm.performance.vp.vpi"
   ::= {pr1646v2ATMImaVpEntry 268435456}

pr1646v2ATMImaVpOamF4SegLbRx OBJECT-TYPE
   SYNTAX      Gauge32
   MAX-ACCESS  read-only
   STATUS      current
   DESCRIPTION
      "Path: atm.performance.vp.oamF4.segment.lbRx

       32 bit unsigned gauge value."
   ::= {pr1646v2ATMImaVpEntry 571473920}

pr1646v2ATMImaVpOamF4SegLbTx OBJECT-TYPE
   SYNTAX      Gauge32
   MAX-ACCESS  read-only
   STATUS      current
   DESCRIPTION
      "Path: atm.performance.vp.oamF4.segment.lbTx

       32 bit unsigned gauge value."
   ::= {pr1646v2ATMImaVpEntry 572522496}

pr1646v2ATMImaVpOamF4SegCcRx OBJECT-TYPE
   SYNTAX      Gauge32
   MAX-ACCESS  read-only
   STATUS      current
   DESCRIPTION
      "Path: atm.performance.vp.oamF4.segment.ccRx

       32 bit unsigned gauge value."
   ::= {pr1646v2ATMImaVpEntry 573571072}

pr1646v2ATMImaVpOamF4SegCcTx OBJECT-TYPE
   SYNTAX      Gauge32
   MAX-ACCESS  read-only
   STATUS      current
   DESCRIPTION
      "Path: atm.performance.vp.oamF4.segment.ccTx

       32 bit unsigned gauge value."
   ::= {pr1646v2ATMImaVpEntry 574619648}

pr1646v2ATMImaVpOamF4SegFpmRx OBJECT-TYPE
   SYNTAX      Gauge32
   MAX-ACCESS  read-only
   STATUS      current
   DESCRIPTION
      "Path: atm.performance.vp.oamF4.segment.fpmRx

       32 bit unsigned gauge value."
   ::= {pr1646v2ATMImaVpEntry 575668224}

pr1646v2ATMImaVpOamF4SegFpmTx OBJECT-TYPE
   SYNTAX      Gauge32
   MAX-ACCESS  read-only
   STATUS      current
   DESCRIPTION
      "Path: atm.performance.vp.oamF4.segment.fpmTx

       32 bit unsigned gauge value."
   ::= {pr1646v2ATMImaVpEntry 576716800}

pr1646v2ATMImaVpOamF4SegBrRx OBJECT-TYPE
   SYNTAX      Gauge32
   MAX-ACCESS  read-only
   STATUS      current
   DESCRIPTION
      "Path: atm.performance.vp.oamF4.segment.brRx

       32 bit unsigned gauge value."
   ::= {pr1646v2ATMImaVpEntry 577765376}

pr1646v2ATMImaVpOamF4SegBrTx OBJECT-TYPE
   SYNTAX      Gauge32
   MAX-ACCESS  read-only
   STATUS      current
   DESCRIPTION
      "Path: atm.performance.vp.oamF4.segment.brTx

       32 bit unsigned gauge value."
   ::= {pr1646v2ATMImaVpEntry 578813952}

pr1646v2ATMImaVpOamF4SegAdRx OBJECT-TYPE
   SYNTAX      Gauge32
   MAX-ACCESS  read-only
   STATUS      current
   DESCRIPTION
      "Path: atm.performance.vp.oamF4.segment.actDeactRx

       32 bit unsigned gauge value."
   ::= {pr1646v2ATMImaVpEntry 579862528}

pr1646v2ATMImaVpOamF4SegAdTx OBJECT-TYPE
   SYNTAX      Gauge32
   MAX-ACCESS  read-only
   STATUS      current
   DESCRIPTION
      "Path: atm.performance.vp.oamF4.segment.actDeactTx

       32 bit unsigned gauge value."
   ::= {pr1646v2ATMImaVpEntry 580911104}

pr1646v2ATMImaVpOamF4SegAisRx OBJECT-TYPE
   SYNTAX      Gauge32
   MAX-ACCESS  read-only
   STATUS      current
   DESCRIPTION
      "Path: atm.performance.vp.oamF4.segment.aisRx

       32 bit unsigned gauge value."
   ::= {pr1646v2ATMImaVpEntry 581959680}

pr1646v2ATMImaVpOamF4SegAisTx OBJECT-TYPE
   SYNTAX      Gauge32
   MAX-ACCESS  read-only
   STATUS      current
   DESCRIPTION
      "Path: atm.performance.vp.oamF4.segment.aisTx

       32 bit unsigned gauge value."
   ::= {pr1646v2ATMImaVpEntry 583008256}

pr1646v2ATMImaVpOamF4SegRdiRx OBJECT-TYPE
   SYNTAX      Gauge32
   MAX-ACCESS  read-only
   STATUS      current
   DESCRIPTION
      "Path: atm.performance.vp.oamF4.segment.rdiRx

       32 bit unsigned gauge value."
   ::= {pr1646v2ATMImaVpEntry 584056832}

pr1646v2ATMImaVpOamF4SegRdiTx OBJECT-TYPE
   SYNTAX      Gauge32
   MAX-ACCESS  read-only
   STATUS      current
   DESCRIPTION
      "Path: atm.performance.vp.oamF4.segment.rdiTx

       32 bit unsigned gauge value."
   ::= {pr1646v2ATMImaVpEntry 585105408}

pr1646v2ATMImaVpOamF4SegRxpmNLOC OBJECT-TYPE
   SYNTAX      Gauge32
   MAX-ACCESS  read-only
   STATUS      current
   DESCRIPTION
      "Path: atm.performance.vp.oamF4.segment.pmRxStats.lostOamCells

       32 bit unsigned gauge value."
   ::= {pr1646v2ATMImaVpEntry 586158080}

pr1646v2ATMImaVpOamF4SegRxpmNLUC OBJECT-TYPE
   SYNTAX      Gauge32
   MAX-ACCESS  read-only
   STATUS      current
   DESCRIPTION
      "Path: atm.performance.vp.oamF4.segment.pmRxStats.lostUserCells

       32 bit unsigned gauge value."
   ::= {pr1646v2ATMImaVpEntry 586162176}

pr1646v2ATMImaVpOamF4SegRxpmNEUC OBJECT-TYPE
   SYNTAX      Gauge32
   MAX-ACCESS  read-only
   STATUS      current
   DESCRIPTION
      "Path: atm.performance.vp.oamF4.segment.pmRxStats.errUserCells

       32 bit unsigned gauge value."
   ::= {pr1646v2ATMImaVpEntry 586166272}

pr1646v2ATMImaVpOamF4SegRxpmNMUC OBJECT-TYPE
   SYNTAX      Gauge32
   MAX-ACCESS  read-only
   STATUS      current
   DESCRIPTION
      "Path: atm.performance.vp.oamF4.segment.pmRxStats.misInsertUserCells

       32 bit unsigned gauge value."
   ::= {pr1646v2ATMImaVpEntry 586170368}

pr1646v2ATMImaVpOamF4SegRxpmCer OBJECT-TYPE
   SYNTAX      Integer32
   MAX-ACCESS  read-only
   STATUS      current
   DESCRIPTION
      "Path: atm.performance.vp.oamF4.segment.pmRxStats.cellErrRatio

       formula = 1000000000 / ; 1000000000 *"
   ::= {pr1646v2ATMImaVpEntry 586174464}

pr1646v2ATMImaVpOamF4SegRxpmClr OBJECT-TYPE
   SYNTAX      Integer32
   MAX-ACCESS  read-only
   STATUS      current
   DESCRIPTION
      "Path: atm.performance.vp.oamF4.segment.pmRxStats.cellLossRatio

       formula = 1000000000 / ; 1000000000 *"
   ::= {pr1646v2ATMImaVpEntry 586178560}

pr1646v2ATMImaVpOamF4SegRxpmCmr OBJECT-TYPE
   SYNTAX      Integer32
   MAX-ACCESS  read-only
   STATUS      current
   DESCRIPTION
      "Path: atm.performance.vp.oamF4.segment.pmRxStats.cellMisinsertRatio

       unit name = misinserts/sec
       formula = 1000000000 / ; 1000000000 *"
   ::= {pr1646v2ATMImaVpEntry 586182656}

pr1646v2ATMImaVpOamF4SegRxpmSecb OBJECT-TYPE
   SYNTAX      Integer32
   MAX-ACCESS  read-only
   STATUS      current
   DESCRIPTION
      "Path: atm.performance.vp.oamF4.segment.pmRxStats.sevErrCellBlckRatio

       formula = 1000000000 / ; 1000000000 *"
   ::= {pr1646v2ATMImaVpEntry 586186752}

pr1646v2ATMImaVpOamF4SegTxpmNLOC OBJECT-TYPE
   SYNTAX      Gauge32
   MAX-ACCESS  read-only
   STATUS      current
   DESCRIPTION
      "Path: atm.performance.vp.oamF4.segment.pmTxStats.lostOamCells

       32 bit unsigned gauge value."
   ::= {pr1646v2ATMImaVpEntry 587206656}

pr1646v2ATMImaVpOamF4SegTxpmNLUC OBJECT-TYPE
   SYNTAX      Gauge32
   MAX-ACCESS  read-only
   STATUS      current
   DESCRIPTION
      "Path: atm.performance.vp.oamF4.segment.pmTxStats.lostUserCells

       32 bit unsigned gauge value."
   ::= {pr1646v2ATMImaVpEntry 587210752}

pr1646v2ATMImaVpOamF4SegTxpmNEUC OBJECT-TYPE
   SYNTAX      Gauge32
   MAX-ACCESS  read-only
   STATUS      current
   DESCRIPTION
      "Path: atm.performance.vp.oamF4.segment.pmTxStats.errUserCells

       32 bit unsigned gauge value."
   ::= {pr1646v2ATMImaVpEntry 587214848}

pr1646v2ATMImaVpOamF4SegTxpmNMUC OBJECT-TYPE
   SYNTAX      Gauge32
   MAX-ACCESS  read-only
   STATUS      current
   DESCRIPTION
      "Path: atm.performance.vp.oamF4.segment.pmTxStats.misInsertUserCells

       32 bit unsigned gauge value."
   ::= {pr1646v2ATMImaVpEntry 587218944}

pr1646v2ATMImaVpOamF4SegTxpmCer OBJECT-TYPE
   SYNTAX      Integer32
   MAX-ACCESS  read-only
   STATUS      current
   DESCRIPTION
      "Path: atm.performance.vp.oamF4.segment.pmTxStats.cellErrRatio

       formula = 1000000000 / ; 1000000000 *"
   ::= {pr1646v2ATMImaVpEntry 587223040}

pr1646v2ATMImaVpOamF4SegTxpmClr OBJECT-TYPE
   SYNTAX      Integer32
   MAX-ACCESS  read-only
   STATUS      current
   DESCRIPTION
      "Path: atm.performance.vp.oamF4.segment.pmTxStats.cellLossRatio

       formula = 1000000000 / ; 1000000000 *"
   ::= {pr1646v2ATMImaVpEntry 587227136}

pr1646v2ATMImaVpOamF4SegTxpmCmr OBJECT-TYPE
   SYNTAX      Integer32
   MAX-ACCESS  read-only
   STATUS      current
   DESCRIPTION
      "Path: atm.performance.vp.oamF4.segment.pmTxStats.cellMisinsertRatio

       unit name = misinserts/sec
       formula = 1000000000 / ; 1000000000 *"
   ::= {pr1646v2ATMImaVpEntry 587231232}

pr1646v2ATMImaVpOamF4SegTxpmSecb OBJECT-TYPE
   SYNTAX      Integer32
   MAX-ACCESS  read-only
   STATUS      current
   DESCRIPTION
      "Path: atm.performance.vp.oamF4.segment.pmTxStats.sevErrCellBlckRatio

       formula = 1000000000 / ; 1000000000 *"
   ::= {pr1646v2ATMImaVpEntry 587235328}

pr1646v2ATMImaVpOamF4EteLbRx OBJECT-TYPE
   SYNTAX      Gauge32
   MAX-ACCESS  read-only
   STATUS      current
   DESCRIPTION
      "Path: atm.performance.vp.oamF4.endToEnd.lbRx

       32 bit unsigned gauge value."
   ::= {pr1646v2ATMImaVpEntry 605028352}

pr1646v2ATMImaVpOamF4EteLbTx OBJECT-TYPE
   SYNTAX      Gauge32
   MAX-ACCESS  read-only
   STATUS      current
   DESCRIPTION
      "Path: atm.performance.vp.oamF4.endToEnd.lbTx

       32 bit unsigned gauge value."
   ::= {pr1646v2ATMImaVpEntry 606076928}

pr1646v2ATMImaVpOamF4EteCcRx OBJECT-TYPE
   SYNTAX      Gauge32
   MAX-ACCESS  read-only
   STATUS      current
   DESCRIPTION
      "Path: atm.performance.vp.oamF4.endToEnd.ccRx

       32 bit unsigned gauge value."
   ::= {pr1646v2ATMImaVpEntry 607125504}

pr1646v2ATMImaVpOamF4EteCcTx OBJECT-TYPE
   SYNTAX      Gauge32
   MAX-ACCESS  read-only
   STATUS      current
   DESCRIPTION
      "Path: atm.performance.vp.oamF4.endToEnd.ccTx

       32 bit unsigned gauge value."
   ::= {pr1646v2ATMImaVpEntry 608174080}

pr1646v2ATMImaVpOamF4EteFpmRx OBJECT-TYPE
   SYNTAX      Gauge32
   MAX-ACCESS  read-only
   STATUS      current
   DESCRIPTION
      "Path: atm.performance.vp.oamF4.endToEnd.fpmRx

       32 bit unsigned gauge value."
   ::= {pr1646v2ATMImaVpEntry 609222656}

pr1646v2ATMImaVpOamF4EteFpmTx OBJECT-TYPE
   SYNTAX      Gauge32
   MAX-ACCESS  read-only
   STATUS      current
   DESCRIPTION
      "Path: atm.performance.vp.oamF4.endToEnd.fpmTx

       32 bit unsigned gauge value."
   ::= {pr1646v2ATMImaVpEntry 610271232}

pr1646v2ATMImaVpOamF4EteBrRx OBJECT-TYPE
   SYNTAX      Gauge32
   MAX-ACCESS  read-only
   STATUS      current
   DESCRIPTION
      "Path: atm.performance.vp.oamF4.endToEnd.brRx

       32 bit unsigned gauge value."
   ::= {pr1646v2ATMImaVpEntry 611319808}

pr1646v2ATMImaVpOamF4EteBrTx OBJECT-TYPE
   SYNTAX      Gauge32
   MAX-ACCESS  read-only
   STATUS      current
   DESCRIPTION
      "Path: atm.performance.vp.oamF4.endToEnd.brTx

       32 bit unsigned gauge value."
   ::= {pr1646v2ATMImaVpEntry 612368384}

pr1646v2ATMImaVpOamF4EteAdRx OBJECT-TYPE
   SYNTAX      Gauge32
   MAX-ACCESS  read-only
   STATUS      current
   DESCRIPTION
      "Path: atm.performance.vp.oamF4.endToEnd.actDeactRx

       32 bit unsigned gauge value."
   ::= {pr1646v2ATMImaVpEntry 613416960}

pr1646v2ATMImaVpOamF4EteAdTx OBJECT-TYPE
   SYNTAX      Gauge32
   MAX-ACCESS  read-only
   STATUS      current
   DESCRIPTION
      "Path: atm.performance.vp.oamF4.endToEnd.actDeactTx

       32 bit unsigned gauge value."
   ::= {pr1646v2ATMImaVpEntry 614465536}

pr1646v2ATMImaVpOamF4EteAisRx OBJECT-TYPE
   SYNTAX      Gauge32
   MAX-ACCESS  read-only
   STATUS      current
   DESCRIPTION
      "Path: atm.performance.vp.oamF4.endToEnd.aisRx

       32 bit unsigned gauge value."
   ::= {pr1646v2ATMImaVpEntry 615514112}

pr1646v2ATMImaVpOamF4EteAisTx OBJECT-TYPE
   SYNTAX      Gauge32
   MAX-ACCESS  read-only
   STATUS      current
   DESCRIPTION
      "Path: atm.performance.vp.oamF4.endToEnd.aisTx

       32 bit unsigned gauge value."
   ::= {pr1646v2ATMImaVpEntry 616562688}

pr1646v2ATMImaVpOamF4EteRdiRx OBJECT-TYPE
   SYNTAX      Gauge32
   MAX-ACCESS  read-only
   STATUS      current
   DESCRIPTION
      "Path: atm.performance.vp.oamF4.endToEnd.rdiRx

       32 bit unsigned gauge value."
   ::= {pr1646v2ATMImaVpEntry 617611264}

pr1646v2ATMImaVpOamF4EteRdiTx OBJECT-TYPE
   SYNTAX      Gauge32
   MAX-ACCESS  read-only
   STATUS      current
   DESCRIPTION
      "Path: atm.performance.vp.oamF4.endToEnd.rdiTx

       32 bit unsigned gauge value."
   ::= {pr1646v2ATMImaVpEntry 618659840}

pr1646v2ATMImaVpOamF4EteRxpmNLOC OBJECT-TYPE
   SYNTAX      Gauge32
   MAX-ACCESS  read-only
   STATUS      current
   DESCRIPTION
      "Path: atm.performance.vp.oamF4.endToEnd.pmRxStats.lostOamCells

       32 bit unsigned gauge value."
   ::= {pr1646v2ATMImaVpEntry 619712512}

pr1646v2ATMImaVpOamF4EteRxpmNLUC OBJECT-TYPE
   SYNTAX      Gauge32
   MAX-ACCESS  read-only
   STATUS      current
   DESCRIPTION
      "Path: atm.performance.vp.oamF4.endToEnd.pmRxStats.lostUserCells

       32 bit unsigned gauge value."
   ::= {pr1646v2ATMImaVpEntry 619716608}

pr1646v2ATMImaVpOamF4EteRxpmNEUC OBJECT-TYPE
   SYNTAX      Gauge32
   MAX-ACCESS  read-only
   STATUS      current
   DESCRIPTION
      "Path: atm.performance.vp.oamF4.endToEnd.pmRxStats.errUserCells

       32 bit unsigned gauge value."
   ::= {pr1646v2ATMImaVpEntry 619720704}

pr1646v2ATMImaVpOamF4EteRxpmNMUC OBJECT-TYPE
   SYNTAX      Gauge32
   MAX-ACCESS  read-only
   STATUS      current
   DESCRIPTION
      "Path: atm.performance.vp.oamF4.endToEnd.pmRxStats.misInsertUserCells

       32 bit unsigned gauge value."
   ::= {pr1646v2ATMImaVpEntry 619724800}

pr1646v2ATMImaVpOamF4EteRxpmCer OBJECT-TYPE
   SYNTAX      Integer32
   MAX-ACCESS  read-only
   STATUS      current
   DESCRIPTION
      "Path: atm.performance.vp.oamF4.endToEnd.pmRxStats.cellErrRatio

       formula = 1000000000 / ; 1000000000 *"
   ::= {pr1646v2ATMImaVpEntry 619728896}

pr1646v2ATMImaVpOamF4EteRxpmClr OBJECT-TYPE
   SYNTAX      Integer32
   MAX-ACCESS  read-only
   STATUS      current
   DESCRIPTION
      "Path: atm.performance.vp.oamF4.endToEnd.pmRxStats.cellLossRatio

       formula = 1000000000 / ; 1000000000 *"
   ::= {pr1646v2ATMImaVpEntry 619732992}

pr1646v2ATMImaVpOamF4EteRxpmCmr OBJECT-TYPE
   SYNTAX      Integer32
   MAX-ACCESS  read-only
   STATUS      current
   DESCRIPTION
      "Path: atm.performance.vp.oamF4.endToEnd.pmRxStats.cellMisinsertRatio

       unit name = misinserts/sec
       formula = 1000000000 / ; 1000000000 *"
   ::= {pr1646v2ATMImaVpEntry 619737088}

pr1646v2ATMImaVpOamF4EteRxpmSecb OBJECT-TYPE
   SYNTAX      Integer32
   MAX-ACCESS  read-only
   STATUS      current
   DESCRIPTION
      "Path: atm.performance.vp.oamF4.endToEnd.pmRxStats.sevErrCellBlckRatio

       formula = 1000000000 / ; 1000000000 *"
   ::= {pr1646v2ATMImaVpEntry 619741184}

pr1646v2ATMImaVpOamF4EteTxpmNLOC OBJECT-TYPE
   SYNTAX      Gauge32
   MAX-ACCESS  read-only
   STATUS      current
   DESCRIPTION
      "Path: atm.performance.vp.oamF4.endToEnd.pmTxStats.lostOamCells

       32 bit unsigned gauge value."
   ::= {pr1646v2ATMImaVpEntry 620761088}

pr1646v2ATMImaVpOamF4EteTxpmNLUC OBJECT-TYPE
   SYNTAX      Gauge32
   MAX-ACCESS  read-only
   STATUS      current
   DESCRIPTION
      "Path: atm.performance.vp.oamF4.endToEnd.pmTxStats.lostUserCells

       32 bit unsigned gauge value."
   ::= {pr1646v2ATMImaVpEntry 620765184}

pr1646v2ATMImaVpOamF4EteTxpmNEUC OBJECT-TYPE
   SYNTAX      Gauge32
   MAX-ACCESS  read-only
   STATUS      current
   DESCRIPTION
      "Path: atm.performance.vp.oamF4.endToEnd.pmTxStats.errUserCells

       32 bit unsigned gauge value."
   ::= {pr1646v2ATMImaVpEntry 620769280}

pr1646v2ATMImaVpOamF4EteTxpmNMUC OBJECT-TYPE
   SYNTAX      Gauge32
   MAX-ACCESS  read-only
   STATUS      current
   DESCRIPTION
      "Path: atm.performance.vp.oamF4.endToEnd.pmTxStats.misInsertUserCells

       32 bit unsigned gauge value."
   ::= {pr1646v2ATMImaVpEntry 620773376}

pr1646v2ATMImaVpOamF4EteTxpmCer OBJECT-TYPE
   SYNTAX      Integer32
   MAX-ACCESS  read-only
   STATUS      current
   DESCRIPTION
      "Path: atm.performance.vp.oamF4.endToEnd.pmTxStats.cellErrRatio

       formula = 1000000000 / ; 1000000000 *"
   ::= {pr1646v2ATMImaVpEntry 620777472}

pr1646v2ATMImaVpOamF4EteTxpmClr OBJECT-TYPE
   SYNTAX      Integer32
   MAX-ACCESS  read-only
   STATUS      current
   DESCRIPTION
      "Path: atm.performance.vp.oamF4.endToEnd.pmTxStats.cellLossRatio

       formula = 1000000000 / ; 1000000000 *"
   ::= {pr1646v2ATMImaVpEntry 620781568}

pr1646v2ATMImaVpOamF4EteTxpmCmr OBJECT-TYPE
   SYNTAX      Integer32
   MAX-ACCESS  read-only
   STATUS      current
   DESCRIPTION
      "Path: atm.performance.vp.oamF4.endToEnd.pmTxStats.cellMisinsertRatio

       unit name = misinserts/sec
       formula = 1000000000 / ; 1000000000 *"
   ::= {pr1646v2ATMImaVpEntry 620785664}

pr1646v2ATMImaVpOamF4EteTxpmSecb OBJECT-TYPE
   SYNTAX      Integer32
   MAX-ACCESS  read-only
   STATUS      current
   DESCRIPTION
      "Path: atm.performance.vp.oamF4.endToEnd.pmTxStats.sevErrCellBlckRatio

       formula = 1000000000 / ; 1000000000 *"
   ::= {pr1646v2ATMImaVpEntry 620789760}


pr1646v2ATMImaPer OBJECT IDENTIFIER ::= {pr1646v2ATMIma 3}

pr1646v2ATMImaPerSSCTable OBJECT-TYPE
   SYNTAX      SEQUENCE OF Pr1646v2ATMImaPerEntry
   MAX-ACCESS  not-accessible
   STATUS      current
   DESCRIPTION
      ""
   ::= {pr1646v2ATMImaPer 1}

pr1646v2ATMImaPerEntry OBJECT-TYPE
   SYNTAX      Pr1646v2ATMImaPerEntry
   MAX-ACCESS  not-accessible
   STATUS      current
   DESCRIPTION
      ""
   INDEX      { pr1646v2ATMImaPerTableIx }
   ::= {pr1646v2ATMImaPerSSCTable 1}

Pr1646v2ATMImaPerEntry ::=
   SEQUENCE
      {
      pr1646v2ATMImaPerTableIx
         TableIndex,
      pr1646v2ATMImaPerName
         DisplayString,
      pr1646v2ATMImaPerMCInOctets
         Counter64,
      pr1646v2ATMImaPerMCInUcast
         Counter64,
      pr1646v2ATMImaPerMCInNUcastPkts
         Counter64,
      pr1646v2ATMImaPerMCInBcastPkts
         Counter64,
      pr1646v2ATMImaPerMCInMcastPkts
         Counter64,
      pr1646v2ATMImaPerMCInDiscards
         Counter64,
      pr1646v2ATMImaPerMCInErrors
         Counter64,
      pr1646v2ATMImaPerMCInUnknownProtos
         Counter64,
      pr1646v2ATMImaPerMCInDropEx
         Counter64,
      pr1646v2ATMImaPerMCInDropNoMac
         Counter64,
      pr1646v2ATMImaPerMCInDropNUCast
         Counter64,
      pr1646v2ATMImaPerMCInDropFilter
         Counter64,
      pr1646v2ATMImaPerMCInBandwidth15sec
         Integer32,
      pr1646v2ATMImaPerMCInBandwidth30sec
         Integer32,
      pr1646v2ATMImaPerMCInBandwidth1min
         Integer32,
      pr1646v2ATMImaPerMCInBandwidth2min
         Integer32,
      pr1646v2ATMImaPerMCInBandwidth5min
         Integer32,
      pr1646v2ATMImaPerMCOutOctets
         Counter64,
      pr1646v2ATMImaPerMCOutUcastPkts
         Counter64,
      pr1646v2ATMImaPerMCOutNUcastPkts
         Counter64,
      pr1646v2ATMImaPerMCOutBcastPkts
         Counter64,
      pr1646v2ATMImaPerMCOutMcastPkts
         Counter64,
      pr1646v2ATMImaPerMCOutDiscards
         Counter64,
      pr1646v2ATMImaPerMCOutErrors
         Counter64,
      pr1646v2ATMImaPerMCOutQLen
         Counter32,
      pr1646v2ATMImaPerMCOutDropEx
         Counter64,
      pr1646v2ATMImaPerMCOutDropNoArp
         Counter64,
      pr1646v2ATMImaPerMCOutDropFilter
         Counter64,
      pr1646v2ATMImaPerMCOutBandwidth15sec
         Integer32,
      pr1646v2ATMImaPerMCOutBandwidth30sec
         Integer32,
      pr1646v2ATMImaPerMCOutBandwidth1min
         Integer32,
      pr1646v2ATMImaPerMCOutBandwidth2min
         Integer32,
      pr1646v2ATMImaPerMCOutBandwidth5min
         Integer32,
      pr1646v2ATMImaPerAtmVpi
         Integer32,
      pr1646v2ATMImaPerAtmVci
         Integer32,
      pr1646v2ATMImaPerAtmF5SegLbRx
         Gauge32,
      pr1646v2ATMImaPerAtmF5SegLbTx
         Gauge32,
      pr1646v2ATMImaPerAtmF5SegCcRx
         Gauge32,
      pr1646v2ATMImaPerAtmF5SegCcTx
         Gauge32,
      pr1646v2ATMImaPerAtmF5SegFpmRx
         Gauge32,
      pr1646v2ATMImaPerAtmF5SegFpmTx
         Gauge32,
      pr1646v2ATMImaPerAtmF5SegBrRx
         Gauge32,
      pr1646v2ATMImaPerAtmF5SegBrTx
         Gauge32,
      pr1646v2ATMImaPerAtmF5SegAdRx
         Gauge32,
      pr1646v2ATMImaPerAtmF5SegAdTx
         Gauge32,
      pr1646v2ATMImaPerAtmF5SegAisRx
         Gauge32,
      pr1646v2ATMImaPerAtmF5SegAisTx
         Gauge32,
      pr1646v2ATMImaPerAtmF5SegRdiRx
         Gauge32,
      pr1646v2ATMImaPerAtmF5SegRdiTx
         Gauge32,
      pr1646v2ATMImaPerAtmF5SegRxpmNLOC
         Gauge32,
      pr1646v2ATMImaPerAtmF5SegRxpmNLUC
         Gauge32,
      pr1646v2ATMImaPerAtmF5SegRxpmNEUC
         Gauge32,
      pr1646v2ATMImaPerAtmF5SegRxpmNMUC
         Gauge32,
      pr1646v2ATMImaPerAtmF5SegRxpmCer
         Integer32,
      pr1646v2ATMImaPerAtmF5SegRxpmClr
         Integer32,
      pr1646v2ATMImaPerAtmF5SegRxpmCmr
         Integer32,
      pr1646v2ATMImaPerAtmF5SegRxpmSecb
         Integer32,
      pr1646v2ATMImaPerAtmF5SegTxpmNLOC
         Gauge32,
      pr1646v2ATMImaPerAtmF5SegTxpmNLUC
         Gauge32,
      pr1646v2ATMImaPerAtmF5SegTxpmNEUC
         Gauge32,
      pr1646v2ATMImaPerAtmF5SegTxpmNMUC
         Gauge32,
      pr1646v2ATMImaPerAtmF5SegTxpmCer
         Integer32,
      pr1646v2ATMImaPerAtmF5SegTxpmClr
         Integer32,
      pr1646v2ATMImaPerAtmF5SegTxpmCmr
         Integer32,
      pr1646v2ATMImaPerAtmF5SegTxpmSecb
         Integer32,
      pr1646v2ATMImaPerAtmF5EteLbRx
         Gauge32,
      pr1646v2ATMImaPerAtmF5EteLbTx
         Gauge32,
      pr1646v2ATMImaPerAtmF5EteCcRx
         Gauge32,
      pr1646v2ATMImaPerAtmF5EteCcTx
         Gauge32,
      pr1646v2ATMImaPerAtmF5EteFpmRx
         Gauge32,
      pr1646v2ATMImaPerAtmF5EteFpmTx
         Gauge32,
      pr1646v2ATMImaPerAtmF5EteBrRx
         Gauge32,
      pr1646v2ATMImaPerAtmF5EteBrTx
         Gauge32,
      pr1646v2ATMImaPerAtmF5EteAdRx
         Gauge32,
      pr1646v2ATMImaPerAtmF5EteAdTx
         Gauge32,
      pr1646v2ATMImaPerAtmF5EteAisRx
         Gauge32,
      pr1646v2ATMImaPerAtmF5EteAisTx
         Gauge32,
      pr1646v2ATMImaPerAtmF5EteRdiRx
         Gauge32,
      pr1646v2ATMImaPerAtmF5EteRdiTx
         Gauge32,
      pr1646v2ATMImaPerAtmF5EteRxpmNLOC
         Gauge32,
      pr1646v2ATMImaPerAtmF5EteRxpmNLUC
         Gauge32,
      pr1646v2ATMImaPerAtmF5EteRxpmNEUC
         Gauge32,
      pr1646v2ATMImaPerAtmF5EteRxpmNMUC
         Gauge32,
      pr1646v2ATMImaPerAtmF5EteRxpmCer
         Integer32,
      pr1646v2ATMImaPerAtmF5EteRxpmClr
         Integer32,
      pr1646v2ATMImaPerAtmF5EteRxpmCmr
         Integer32,
      pr1646v2ATMImaPerAtmF5EteRxpmSecb
         Integer32,
      pr1646v2ATMImaPerAtmF5EteTxpmNLOC
         Gauge32,
      pr1646v2ATMImaPerAtmF5EteTxpmNLUC
         Gauge32,
      pr1646v2ATMImaPerAtmF5EteTxpmNEUC
         Gauge32,
      pr1646v2ATMImaPerAtmF5EteTxpmNMUC
         Gauge32,
      pr1646v2ATMImaPerAtmF5EteTxpmCer
         Integer32,
      pr1646v2ATMImaPerAtmF5EteTxpmClr
         Integer32,
      pr1646v2ATMImaPerAtmF5EteTxpmCmr
         Integer32,
      pr1646v2ATMImaPerAtmF5EteTxpmSecb
         Integer32,
      pr1646v2ATMImaPerAtmPppLinkMonitoringRequestsSent
         Gauge32,
      pr1646v2ATMImaPerAtmPppLinkMonitoringRepliesRcvd
         Gauge32,
      pr1646v2ATMImaPerAtmPppLinkMonitoringRequestsRcvd
         Gauge32,
      pr1646v2ATMImaPerAtmPppLinkMonitoringRepliesSent
         Gauge32,
      pr1646v2ATMImaPerFrLmiInStatusEnq
         Counter32,
      pr1646v2ATMImaPerFrLmiInStatus
         Counter32,
      pr1646v2ATMImaPerFrLmiInStatUpdate
         Counter32,
      pr1646v2ATMImaPerFrLmiOutStatusEnq
         Counter32,
      pr1646v2ATMImaPerFrLmiOutStatus
         Counter32,
      pr1646v2ATMImaPerFrLmiOutStatUpdate
         Counter32,
      pr1646v2ATMImaPerFrLmiNetPollNotRcvd
         Counter32,
      pr1646v2ATMImaPerFrLmiUsrNoRespRcvd
         Counter32,
      pr1646v2ATMImaPerFrLmiUsrBadRespRcvd
         Counter32
      }

pr1646v2ATMImaPerTableIx OBJECT-TYPE
   SYNTAX      TableIndex
   MAX-ACCESS  not-accessible
   STATUS      current
   DESCRIPTION
      ""
   ::= {pr1646v2ATMImaPerEntry 11}

pr1646v2ATMImaPerName OBJECT-TYPE
   SYNTAX      DisplayString
   MAX-ACCESS  read-only
   STATUS      current
   DESCRIPTION
      "Path: atm.performance.pvcTable.name"
   ::= {pr1646v2ATMImaPerEntry 16777216}

pr1646v2ATMImaPerMCInOctets OBJECT-TYPE
   SYNTAX      Counter64
   MAX-ACCESS  read-only
   STATUS      current
   DESCRIPTION
      "Path: atm.performance.pvcTable.mibCounters.ifInOctets

       64 bit unsigned wrappable counter."
   ::= {pr1646v2ATMImaPerEntry 40697856}

pr1646v2ATMImaPerMCInUcast OBJECT-TYPE
   SYNTAX      Counter64
   MAX-ACCESS  read-only
   STATUS      current
   DESCRIPTION
      "Path: atm.performance.pvcTable.mibCounters.ifInUcastPkts

       64 bit unsigned wrappable counter."
   ::= {pr1646v2ATMImaPerEntry 40763392}

pr1646v2ATMImaPerMCInNUcastPkts OBJECT-TYPE
   SYNTAX      Counter64
   MAX-ACCESS  read-only
   STATUS      current
   DESCRIPTION
      "Path: atm.performance.pvcTable.mibCounters.ifInNUcastPkts

       64 bit unsigned wrappable counter."
   ::= {pr1646v2ATMImaPerEntry 40828928}

pr1646v2ATMImaPerMCInBcastPkts OBJECT-TYPE
   SYNTAX      Counter64
   MAX-ACCESS  read-only
   STATUS      current
   DESCRIPTION
      "Path: atm.performance.pvcTable.mibCounters.ifInBcastPkts

       64 bit unsigned wrappable counter."
   ::= {pr1646v2ATMImaPerEntry 47382528}

pr1646v2ATMImaPerMCInMcastPkts OBJECT-TYPE
   SYNTAX      Counter64
   MAX-ACCESS  read-only
   STATUS      current
   DESCRIPTION
      "Path: atm.performance.pvcTable.mibCounters.ifInMcastPkts

       64 bit unsigned wrappable counter."
   ::= {pr1646v2ATMImaPerEntry 48037888}

pr1646v2ATMImaPerMCInDiscards OBJECT-TYPE
   SYNTAX      Counter64
   MAX-ACCESS  read-only
   STATUS      current
   DESCRIPTION
      "Path: atm.performance.pvcTable.mibCounters.ifInDiscards

       64 bit unsigned wrappable counter."
   ::= {pr1646v2ATMImaPerEntry 40894464}

pr1646v2ATMImaPerMCInErrors OBJECT-TYPE
   SYNTAX      Counter64
   MAX-ACCESS  read-only
   STATUS      current
   DESCRIPTION
      "Path: atm.performance.pvcTable.mibCounters.ifInErrors

       64 bit unsigned wrappable counter."
   ::= {pr1646v2ATMImaPerEntry 40960000}

pr1646v2ATMImaPerMCInUnknownProtos OBJECT-TYPE
   SYNTAX      Counter64
   MAX-ACCESS  read-only
   STATUS      current
   DESCRIPTION
      "Path: atm.performance.pvcTable.mibCounters.ifInUnknownProtos

       64 bit unsigned wrappable counter."
   ::= {pr1646v2ATMImaPerEntry 41025536}

pr1646v2ATMImaPerMCInDropEx OBJECT-TYPE
   SYNTAX      Counter64
   MAX-ACCESS  read-only
   STATUS      current
   DESCRIPTION
      "Path: atm.performance.pvcTable.mibCounters.ifInDropLevelExceeded

       64 bit unsigned wrappable counter."
   ::= {pr1646v2ATMImaPerEntry 42074112}

pr1646v2ATMImaPerMCInDropNoMac OBJECT-TYPE
   SYNTAX      Counter64
   MAX-ACCESS  read-only
   STATUS      current
   DESCRIPTION
      "Path: atm.performance.pvcTable.mibCounters.ifInDiscardsNoMacFit

       64 bit unsigned wrappable counter."
   ::= {pr1646v2ATMImaPerEntry 42270720}

pr1646v2ATMImaPerMCInDropNUCast OBJECT-TYPE
   SYNTAX      Counter64
   MAX-ACCESS  read-only
   STATUS      current
   DESCRIPTION
      "Path: atm.performance.pvcTable.mibCounters.ifInDiscardsNUCast

       64 bit unsigned wrappable counter."
   ::= {pr1646v2ATMImaPerEntry 42467328}

pr1646v2ATMImaPerMCInDropFilter OBJECT-TYPE
   SYNTAX      Counter64
   MAX-ACCESS  read-only
   STATUS      current
   DESCRIPTION
      "Path: atm.performance.pvcTable.mibCounters.ifInDiscardsFilter

       64 bit unsigned wrappable counter."
   ::= {pr1646v2ATMImaPerEntry 42532864}

pr1646v2ATMImaPerMCInBandwidth15sec OBJECT-TYPE
   SYNTAX      Integer32
   MAX-ACCESS  read-only
   STATUS      current
   DESCRIPTION
      "Path: atm.performance.pvcTable.mibCounters.ifInBandwidth.15sec

       unit name = bps
       formula = 8 * ; 8 /"
   ::= {pr1646v2ATMImaPerEntry 45417728}

pr1646v2ATMImaPerMCInBandwidth30sec OBJECT-TYPE
   SYNTAX      Integer32
   MAX-ACCESS  read-only
   STATUS      current
   DESCRIPTION
      "Path: atm.performance.pvcTable.mibCounters.ifInBandwidth.30sec

       unit name = bps
       formula = 8 * ; 8 /"
   ::= {pr1646v2ATMImaPerEntry 45419008}

pr1646v2ATMImaPerMCInBandwidth1min OBJECT-TYPE
   SYNTAX      Integer32
   MAX-ACCESS  read-only
   STATUS      current
   DESCRIPTION
      "Path: atm.performance.pvcTable.mibCounters.ifInBandwidth.1min

       unit name = bps
       formula = 8 * ; 8 /"
   ::= {pr1646v2ATMImaPerEntry 45421568}

pr1646v2ATMImaPerMCInBandwidth2min OBJECT-TYPE
   SYNTAX      Integer32
   MAX-ACCESS  read-only
   STATUS      current
   DESCRIPTION
      "Path: atm.performance.pvcTable.mibCounters.ifInBandwidth.2min

       unit name = bps
       formula = 8 * ; 8 /"
   ::= {pr1646v2ATMImaPerEntry 45426688}

pr1646v2ATMImaPerMCInBandwidth5min OBJECT-TYPE
   SYNTAX      Integer32
   MAX-ACCESS  read-only
   STATUS      current
   DESCRIPTION
      "Path: atm.performance.pvcTable.mibCounters.ifInBandwidth.5min

       unit name = bps
       formula = 8 * ; 8 /"
   ::= {pr1646v2ATMImaPerEntry 45442048}

pr1646v2ATMImaPerMCOutOctets OBJECT-TYPE
   SYNTAX      Counter64
   MAX-ACCESS  read-only
   STATUS      current
   DESCRIPTION
      "Path: atm.performance.pvcTable.mibCounters.ifOutOctets

       64 bit unsigned wrappable counter."
   ::= {pr1646v2ATMImaPerEntry 41091072}

pr1646v2ATMImaPerMCOutUcastPkts OBJECT-TYPE
   SYNTAX      Counter64
   MAX-ACCESS  read-only
   STATUS      current
   DESCRIPTION
      "Path: atm.performance.pvcTable.mibCounters.ifOutUcastPkts

       64 bit unsigned wrappable counter."
   ::= {pr1646v2ATMImaPerEntry 41156608}

pr1646v2ATMImaPerMCOutNUcastPkts OBJECT-TYPE
   SYNTAX      Counter64
   MAX-ACCESS  read-only
   STATUS      current
   DESCRIPTION
      "Path: atm.performance.pvcTable.mibCounters.ifOutNUcastPkts

       64 bit unsigned wrappable counter."
   ::= {pr1646v2ATMImaPerEntry 41222144}

pr1646v2ATMImaPerMCOutBcastPkts OBJECT-TYPE
   SYNTAX      Counter64
   MAX-ACCESS  read-only
   STATUS      current
   DESCRIPTION
      "Path: atm.performance.pvcTable.mibCounters.ifOutBcastPkts

       64 bit unsigned wrappable counter."
   ::= {pr1646v2ATMImaPerEntry 47775744}

pr1646v2ATMImaPerMCOutMcastPkts OBJECT-TYPE
   SYNTAX      Counter64
   MAX-ACCESS  read-only
   STATUS      current
   DESCRIPTION
      "Path: atm.performance.pvcTable.mibCounters.ifOutMcastPkts

       64 bit unsigned wrappable counter."
   ::= {pr1646v2ATMImaPerEntry 48431104}

pr1646v2ATMImaPerMCOutDiscards OBJECT-TYPE
   SYNTAX      Counter64
   MAX-ACCESS  read-only
   STATUS      current
   DESCRIPTION
      "Path: atm.performance.pvcTable.mibCounters.ifOutDiscards

       64 bit unsigned wrappable counter."
   ::= {pr1646v2ATMImaPerEntry 41287680}

pr1646v2ATMImaPerMCOutErrors OBJECT-TYPE
   SYNTAX      Counter64
   MAX-ACCESS  read-only
   STATUS      current
   DESCRIPTION
      "Path: atm.performance.pvcTable.mibCounters.ifOutErrors

       64 bit unsigned wrappable counter."
   ::= {pr1646v2ATMImaPerEntry 41353216}

pr1646v2ATMImaPerMCOutQLen OBJECT-TYPE
   SYNTAX      Counter32
   MAX-ACCESS  read-only
   STATUS      current
   DESCRIPTION
      "Path: atm.performance.pvcTable.mibCounters.ifOutQLen

       32 bit unsigned wrappable counter."
   ::= {pr1646v2ATMImaPerEntry 41418752}

pr1646v2ATMImaPerMCOutDropEx OBJECT-TYPE
   SYNTAX      Counter64
   MAX-ACCESS  read-only
   STATUS      current
   DESCRIPTION
      "Path: atm.performance.pvcTable.mibCounters.ifOutDropLevelExceeded

       64 bit unsigned wrappable counter."
   ::= {pr1646v2ATMImaPerEntry 41484288}

pr1646v2ATMImaPerMCOutDropNoArp OBJECT-TYPE
   SYNTAX      Counter64
   MAX-ACCESS  read-only
   STATUS      current
   DESCRIPTION
      "Path: atm.performance.pvcTable.mibCounters.ifOutDiscardsNoArp

       64 bit unsigned wrappable counter."
   ::= {pr1646v2ATMImaPerEntry 42336256}

pr1646v2ATMImaPerMCOutDropFilter OBJECT-TYPE
   SYNTAX      Counter64
   MAX-ACCESS  read-only
   STATUS      current
   DESCRIPTION
      "Path: atm.performance.pvcTable.mibCounters.ifOutDiscardsFilter

       64 bit unsigned wrappable counter."
   ::= {pr1646v2ATMImaPerEntry 42598400}

pr1646v2ATMImaPerMCOutBandwidth15sec OBJECT-TYPE
   SYNTAX      Integer32
   MAX-ACCESS  read-only
   STATUS      current
   DESCRIPTION
      "Path: atm.performance.pvcTable.mibCounters.ifOutBandwidth.15sec

       unit name = bps
       formula = 8 * ; 8 /"
   ::= {pr1646v2ATMImaPerEntry 45483264}

pr1646v2ATMImaPerMCOutBandwidth30sec OBJECT-TYPE
   SYNTAX      Integer32
   MAX-ACCESS  read-only
   STATUS      current
   DESCRIPTION
      "Path: atm.performance.pvcTable.mibCounters.ifOutBandwidth.30sec

       unit name = bps
       formula = 8 * ; 8 /"
   ::= {pr1646v2ATMImaPerEntry 45484544}

pr1646v2ATMImaPerMCOutBandwidth1min OBJECT-TYPE
   SYNTAX      Integer32
   MAX-ACCESS  read-only
   STATUS      current
   DESCRIPTION
      "Path: atm.performance.pvcTable.mibCounters.ifOutBandwidth.1min

       unit name = bps
       formula = 8 * ; 8 /"
   ::= {pr1646v2ATMImaPerEntry 45487104}

pr1646v2ATMImaPerMCOutBandwidth2min OBJECT-TYPE
   SYNTAX      Integer32
   MAX-ACCESS  read-only
   STATUS      current
   DESCRIPTION
      "Path: atm.performance.pvcTable.mibCounters.ifOutBandwidth.2min

       unit name = bps
       formula = 8 * ; 8 /"
   ::= {pr1646v2ATMImaPerEntry 45492224}

pr1646v2ATMImaPerMCOutBandwidth5min OBJECT-TYPE
   SYNTAX      Integer32
   MAX-ACCESS  read-only
   STATUS      current
   DESCRIPTION
      "Path: atm.performance.pvcTable.mibCounters.ifOutBandwidth.5min

       unit name = bps
       formula = 8 * ; 8 /"
   ::= {pr1646v2ATMImaPerEntry 45507584}

pr1646v2ATMImaPerAtmVpi OBJECT-TYPE
   SYNTAX      Integer32
   MAX-ACCESS  read-only
   STATUS      current
   DESCRIPTION
      "Path: atm.performance.pvcTable.atm.vpi"
   ::= {pr1646v2ATMImaPerEntry 286261248}

pr1646v2ATMImaPerAtmVci OBJECT-TYPE
   SYNTAX      Integer32
   MAX-ACCESS  read-only
   STATUS      current
   DESCRIPTION
      "Path: atm.performance.pvcTable.atm.vci"
   ::= {pr1646v2ATMImaPerEntry 287309824}

pr1646v2ATMImaPerAtmF5SegLbRx OBJECT-TYPE
   SYNTAX      Gauge32
   MAX-ACCESS  read-only
   STATUS      current
   DESCRIPTION
      "Path: atm.performance.pvcTable.atm.oamF5.segment.lbRx

       32 bit unsigned gauge value."
   ::= {pr1646v2ATMImaPerEntry 288493568}

pr1646v2ATMImaPerAtmF5SegLbTx OBJECT-TYPE
   SYNTAX      Gauge32
   MAX-ACCESS  read-only
   STATUS      current
   DESCRIPTION
      "Path: atm.performance.pvcTable.atm.oamF5.segment.lbTx

       32 bit unsigned gauge value."
   ::= {pr1646v2ATMImaPerEntry 288497664}

pr1646v2ATMImaPerAtmF5SegCcRx OBJECT-TYPE
   SYNTAX      Gauge32
   MAX-ACCESS  read-only
   STATUS      current
   DESCRIPTION
      "Path: atm.performance.pvcTable.atm.oamF5.segment.ccRx

       32 bit unsigned gauge value."
   ::= {pr1646v2ATMImaPerEntry 288501760}

pr1646v2ATMImaPerAtmF5SegCcTx OBJECT-TYPE
   SYNTAX      Gauge32
   MAX-ACCESS  read-only
   STATUS      current
   DESCRIPTION
      "Path: atm.performance.pvcTable.atm.oamF5.segment.ccTx

       32 bit unsigned gauge value."
   ::= {pr1646v2ATMImaPerEntry 288505856}

pr1646v2ATMImaPerAtmF5SegFpmRx OBJECT-TYPE
   SYNTAX      Gauge32
   MAX-ACCESS  read-only
   STATUS      current
   DESCRIPTION
      "Path: atm.performance.pvcTable.atm.oamF5.segment.fpmRx

       32 bit unsigned gauge value."
   ::= {pr1646v2ATMImaPerEntry 288509952}

pr1646v2ATMImaPerAtmF5SegFpmTx OBJECT-TYPE
   SYNTAX      Gauge32
   MAX-ACCESS  read-only
   STATUS      current
   DESCRIPTION
      "Path: atm.performance.pvcTable.atm.oamF5.segment.fpmTx

       32 bit unsigned gauge value."
   ::= {pr1646v2ATMImaPerEntry 288514048}

pr1646v2ATMImaPerAtmF5SegBrRx OBJECT-TYPE
   SYNTAX      Gauge32
   MAX-ACCESS  read-only
   STATUS      current
   DESCRIPTION
      "Path: atm.performance.pvcTable.atm.oamF5.segment.brRx

       32 bit unsigned gauge value."
   ::= {pr1646v2ATMImaPerEntry 288518144}

pr1646v2ATMImaPerAtmF5SegBrTx OBJECT-TYPE
   SYNTAX      Gauge32
   MAX-ACCESS  read-only
   STATUS      current
   DESCRIPTION
      "Path: atm.performance.pvcTable.atm.oamF5.segment.brTx

       32 bit unsigned gauge value."
   ::= {pr1646v2ATMImaPerEntry 288522240}

pr1646v2ATMImaPerAtmF5SegAdRx OBJECT-TYPE
   SYNTAX      Gauge32
   MAX-ACCESS  read-only
   STATUS      current
   DESCRIPTION
      "Path: atm.performance.pvcTable.atm.oamF5.segment.actDeactRx

       32 bit unsigned gauge value."
   ::= {pr1646v2ATMImaPerEntry 288526336}

pr1646v2ATMImaPerAtmF5SegAdTx OBJECT-TYPE
   SYNTAX      Gauge32
   MAX-ACCESS  read-only
   STATUS      current
   DESCRIPTION
      "Path: atm.performance.pvcTable.atm.oamF5.segment.actDeactTx

       32 bit unsigned gauge value."
   ::= {pr1646v2ATMImaPerEntry 288530432}

pr1646v2ATMImaPerAtmF5SegAisRx OBJECT-TYPE
   SYNTAX      Gauge32
   MAX-ACCESS  read-only
   STATUS      current
   DESCRIPTION
      "Path: atm.performance.pvcTable.atm.oamF5.segment.aisRx

       32 bit unsigned gauge value."
   ::= {pr1646v2ATMImaPerEntry 288534528}

pr1646v2ATMImaPerAtmF5SegAisTx OBJECT-TYPE
   SYNTAX      Gauge32
   MAX-ACCESS  read-only
   STATUS      current
   DESCRIPTION
      "Path: atm.performance.pvcTable.atm.oamF5.segment.aisTx

       32 bit unsigned gauge value."
   ::= {pr1646v2ATMImaPerEntry 288538624}

pr1646v2ATMImaPerAtmF5SegRdiRx OBJECT-TYPE
   SYNTAX      Gauge32
   MAX-ACCESS  read-only
   STATUS      current
   DESCRIPTION
      "Path: atm.performance.pvcTable.atm.oamF5.segment.rdiRx

       32 bit unsigned gauge value."
   ::= {pr1646v2ATMImaPerEntry 288542720}

pr1646v2ATMImaPerAtmF5SegRdiTx OBJECT-TYPE
   SYNTAX      Gauge32
   MAX-ACCESS  read-only
   STATUS      current
   DESCRIPTION
      "Path: atm.performance.pvcTable.atm.oamF5.segment.rdiTx

       32 bit unsigned gauge value."
   ::= {pr1646v2ATMImaPerEntry 288546816}

pr1646v2ATMImaPerAtmF5SegRxpmNLOC OBJECT-TYPE
   SYNTAX      Gauge32
   MAX-ACCESS  read-only
   STATUS      current
   DESCRIPTION
      "Path: atm.performance.pvcTable.atm.oamF5.segment.pmRxStats.lostOamCells

       32 bit unsigned gauge value."
   ::= {pr1646v2ATMImaPerEntry 288550928}

pr1646v2ATMImaPerAtmF5SegRxpmNLUC OBJECT-TYPE
   SYNTAX      Gauge32
   MAX-ACCESS  read-only
   STATUS      current
   DESCRIPTION
      "Path: atm.performance.pvcTable.atm.oamF5.segment.pmRxStats.lostUserCells

       32 bit unsigned gauge value."
   ::= {pr1646v2ATMImaPerEntry 288550944}

pr1646v2ATMImaPerAtmF5SegRxpmNEUC OBJECT-TYPE
   SYNTAX      Gauge32
   MAX-ACCESS  read-only
   STATUS      current
   DESCRIPTION
      "Path: atm.performance.pvcTable.atm.oamF5.segment.pmRxStats.errUserCells

       32 bit unsigned gauge value."
   ::= {pr1646v2ATMImaPerEntry 288550960}

pr1646v2ATMImaPerAtmF5SegRxpmNMUC OBJECT-TYPE
   SYNTAX      Gauge32
   MAX-ACCESS  read-only
   STATUS      current
   DESCRIPTION
      "Path: atm.performance.pvcTable.atm.oamF5.segment.pmRxStats.misInsertUserCells

       32 bit unsigned gauge value."
   ::= {pr1646v2ATMImaPerEntry 288550976}

pr1646v2ATMImaPerAtmF5SegRxpmCer OBJECT-TYPE
   SYNTAX      Integer32
   MAX-ACCESS  read-only
   STATUS      current
   DESCRIPTION
      "Path: atm.performance.pvcTable.atm.oamF5.segment.pmRxStats.cellErrRatio

       formula = 1000000000 / ; 1000000000 *"
   ::= {pr1646v2ATMImaPerEntry 288550992}

pr1646v2ATMImaPerAtmF5SegRxpmClr OBJECT-TYPE
   SYNTAX      Integer32
   MAX-ACCESS  read-only
   STATUS      current
   DESCRIPTION
      "Path: atm.performance.pvcTable.atm.oamF5.segment.pmRxStats.cellLossRatio

       formula = 1000000000 / ; 1000000000 *"
   ::= {pr1646v2ATMImaPerEntry 288551008}

pr1646v2ATMImaPerAtmF5SegRxpmCmr OBJECT-TYPE
   SYNTAX      Integer32
   MAX-ACCESS  read-only
   STATUS      current
   DESCRIPTION
      "Path: atm.performance.pvcTable.atm.oamF5.segment.pmRxStats.cellMisinsertRatio

       unit name = misinserts/sec
       formula = 1000000000 / ; 1000000000 *"
   ::= {pr1646v2ATMImaPerEntry 288551024}

pr1646v2ATMImaPerAtmF5SegRxpmSecb OBJECT-TYPE
   SYNTAX      Integer32
   MAX-ACCESS  read-only
   STATUS      current
   DESCRIPTION
      "Path: atm.performance.pvcTable.atm.oamF5.segment.pmRxStats.sevErrCellBlckRatio

       formula = 1000000000 / ; 1000000000 *"
   ::= {pr1646v2ATMImaPerEntry 288551040}

pr1646v2ATMImaPerAtmF5SegTxpmNLOC OBJECT-TYPE
   SYNTAX      Gauge32
   MAX-ACCESS  read-only
   STATUS      current
   DESCRIPTION
      "Path: atm.performance.pvcTable.atm.oamF5.segment.pmTxStats.lostOamCells

       32 bit unsigned gauge value."
   ::= {pr1646v2ATMImaPerEntry 288555024}

pr1646v2ATMImaPerAtmF5SegTxpmNLUC OBJECT-TYPE
   SYNTAX      Gauge32
   MAX-ACCESS  read-only
   STATUS      current
   DESCRIPTION
      "Path: atm.performance.pvcTable.atm.oamF5.segment.pmTxStats.lostUserCells

       32 bit unsigned gauge value."
   ::= {pr1646v2ATMImaPerEntry 288555040}

pr1646v2ATMImaPerAtmF5SegTxpmNEUC OBJECT-TYPE
   SYNTAX      Gauge32
   MAX-ACCESS  read-only
   STATUS      current
   DESCRIPTION
      "Path: atm.performance.pvcTable.atm.oamF5.segment.pmTxStats.errUserCells

       32 bit unsigned gauge value."
   ::= {pr1646v2ATMImaPerEntry 288555056}

pr1646v2ATMImaPerAtmF5SegTxpmNMUC OBJECT-TYPE
   SYNTAX      Gauge32
   MAX-ACCESS  read-only
   STATUS      current
   DESCRIPTION
      "Path: atm.performance.pvcTable.atm.oamF5.segment.pmTxStats.misInsertUserCells

       32 bit unsigned gauge value."
   ::= {pr1646v2ATMImaPerEntry 288555072}

pr1646v2ATMImaPerAtmF5SegTxpmCer OBJECT-TYPE
   SYNTAX      Integer32
   MAX-ACCESS  read-only
   STATUS      current
   DESCRIPTION
      "Path: atm.performance.pvcTable.atm.oamF5.segment.pmTxStats.cellErrRatio

       formula = 1000000000 / ; 1000000000 *"
   ::= {pr1646v2ATMImaPerEntry 288555088}

pr1646v2ATMImaPerAtmF5SegTxpmClr OBJECT-TYPE
   SYNTAX      Integer32
   MAX-ACCESS  read-only
   STATUS      current
   DESCRIPTION
      "Path: atm.performance.pvcTable.atm.oamF5.segment.pmTxStats.cellLossRatio

       formula = 1000000000 / ; 1000000000 *"
   ::= {pr1646v2ATMImaPerEntry 288555104}

pr1646v2ATMImaPerAtmF5SegTxpmCmr OBJECT-TYPE
   SYNTAX      Integer32
   MAX-ACCESS  read-only
   STATUS      current
   DESCRIPTION
      "Path: atm.performance.pvcTable.atm.oamF5.segment.pmTxStats.cellMisinsertRatio

       unit name = misinserts/sec
       formula = 1000000000 / ; 1000000000 *"
   ::= {pr1646v2ATMImaPerEntry 288555120}

pr1646v2ATMImaPerAtmF5SegTxpmSecb OBJECT-TYPE
   SYNTAX      Integer32
   MAX-ACCESS  read-only
   STATUS      current
   DESCRIPTION
      "Path: atm.performance.pvcTable.atm.oamF5.segment.pmTxStats.sevErrCellBlckRatio

       formula = 1000000000 / ; 1000000000 *"
   ::= {pr1646v2ATMImaPerEntry 288555136}

pr1646v2ATMImaPerAtmF5EteLbRx OBJECT-TYPE
   SYNTAX      Gauge32
   MAX-ACCESS  read-only
   STATUS      current
   DESCRIPTION
      "Path: atm.performance.pvcTable.atm.oamF5.endToEnd.lbRx

       32 bit unsigned gauge value."
   ::= {pr1646v2ATMImaPerEntry 288624640}

pr1646v2ATMImaPerAtmF5EteLbTx OBJECT-TYPE
   SYNTAX      Gauge32
   MAX-ACCESS  read-only
   STATUS      current
   DESCRIPTION
      "Path: atm.performance.pvcTable.atm.oamF5.endToEnd.lbTx

       32 bit unsigned gauge value."
   ::= {pr1646v2ATMImaPerEntry 288628736}

pr1646v2ATMImaPerAtmF5EteCcRx OBJECT-TYPE
   SYNTAX      Gauge32
   MAX-ACCESS  read-only
   STATUS      current
   DESCRIPTION
      "Path: atm.performance.pvcTable.atm.oamF5.endToEnd.ccRx

       32 bit unsigned gauge value."
   ::= {pr1646v2ATMImaPerEntry 288632832}

pr1646v2ATMImaPerAtmF5EteCcTx OBJECT-TYPE
   SYNTAX      Gauge32
   MAX-ACCESS  read-only
   STATUS      current
   DESCRIPTION
      "Path: atm.performance.pvcTable.atm.oamF5.endToEnd.ccTx

       32 bit unsigned gauge value."
   ::= {pr1646v2ATMImaPerEntry 288636928}

pr1646v2ATMImaPerAtmF5EteFpmRx OBJECT-TYPE
   SYNTAX      Gauge32
   MAX-ACCESS  read-only
   STATUS      current
   DESCRIPTION
      "Path: atm.performance.pvcTable.atm.oamF5.endToEnd.fpmRx

       32 bit unsigned gauge value."
   ::= {pr1646v2ATMImaPerEntry 288641024}

pr1646v2ATMImaPerAtmF5EteFpmTx OBJECT-TYPE
   SYNTAX      Gauge32
   MAX-ACCESS  read-only
   STATUS      current
   DESCRIPTION
      "Path: atm.performance.pvcTable.atm.oamF5.endToEnd.fpmTx

       32 bit unsigned gauge value."
   ::= {pr1646v2ATMImaPerEntry 288645120}

pr1646v2ATMImaPerAtmF5EteBrRx OBJECT-TYPE
   SYNTAX      Gauge32
   MAX-ACCESS  read-only
   STATUS      current
   DESCRIPTION
      "Path: atm.performance.pvcTable.atm.oamF5.endToEnd.brRx

       32 bit unsigned gauge value."
   ::= {pr1646v2ATMImaPerEntry 288649216}

pr1646v2ATMImaPerAtmF5EteBrTx OBJECT-TYPE
   SYNTAX      Gauge32
   MAX-ACCESS  read-only
   STATUS      current
   DESCRIPTION
      "Path: atm.performance.pvcTable.atm.oamF5.endToEnd.brTx

       32 bit unsigned gauge value."
   ::= {pr1646v2ATMImaPerEntry 288653312}

pr1646v2ATMImaPerAtmF5EteAdRx OBJECT-TYPE
   SYNTAX      Gauge32
   MAX-ACCESS  read-only
   STATUS      current
   DESCRIPTION
      "Path: atm.performance.pvcTable.atm.oamF5.endToEnd.actDeactRx

       32 bit unsigned gauge value."
   ::= {pr1646v2ATMImaPerEntry 288657408}

pr1646v2ATMImaPerAtmF5EteAdTx OBJECT-TYPE
   SYNTAX      Gauge32
   MAX-ACCESS  read-only
   STATUS      current
   DESCRIPTION
      "Path: atm.performance.pvcTable.atm.oamF5.endToEnd.actDeactTx

       32 bit unsigned gauge value."
   ::= {pr1646v2ATMImaPerEntry 288661504}

pr1646v2ATMImaPerAtmF5EteAisRx OBJECT-TYPE
   SYNTAX      Gauge32
   MAX-ACCESS  read-only
   STATUS      current
   DESCRIPTION
      "Path: atm.performance.pvcTable.atm.oamF5.endToEnd.aisRx

       32 bit unsigned gauge value."
   ::= {pr1646v2ATMImaPerEntry 288665600}

pr1646v2ATMImaPerAtmF5EteAisTx OBJECT-TYPE
   SYNTAX      Gauge32
   MAX-ACCESS  read-only
   STATUS      current
   DESCRIPTION
      "Path: atm.performance.pvcTable.atm.oamF5.endToEnd.aisTx

       32 bit unsigned gauge value."
   ::= {pr1646v2ATMImaPerEntry 288669696}

pr1646v2ATMImaPerAtmF5EteRdiRx OBJECT-TYPE
   SYNTAX      Gauge32
   MAX-ACCESS  read-only
   STATUS      current
   DESCRIPTION
      "Path: atm.performance.pvcTable.atm.oamF5.endToEnd.rdiRx

       32 bit unsigned gauge value."
   ::= {pr1646v2ATMImaPerEntry 288673792}

pr1646v2ATMImaPerAtmF5EteRdiTx OBJECT-TYPE
   SYNTAX      Gauge32
   MAX-ACCESS  read-only
   STATUS      current
   DESCRIPTION
      "Path: atm.performance.pvcTable.atm.oamF5.endToEnd.rdiTx

       32 bit unsigned gauge value."
   ::= {pr1646v2ATMImaPerEntry 288677888}

pr1646v2ATMImaPerAtmF5EteRxpmNLOC OBJECT-TYPE
   SYNTAX      Gauge32
   MAX-ACCESS  read-only
   STATUS      current
   DESCRIPTION
      "Path: atm.performance.pvcTable.atm.oamF5.endToEnd.pmRxStats.lostOamCells

       32 bit unsigned gauge value."
   ::= {pr1646v2ATMImaPerEntry 288682000}

pr1646v2ATMImaPerAtmF5EteRxpmNLUC OBJECT-TYPE
   SYNTAX      Gauge32
   MAX-ACCESS  read-only
   STATUS      current
   DESCRIPTION
      "Path: atm.performance.pvcTable.atm.oamF5.endToEnd.pmRxStats.lostUserCells

       32 bit unsigned gauge value."
   ::= {pr1646v2ATMImaPerEntry 288682016}

pr1646v2ATMImaPerAtmF5EteRxpmNEUC OBJECT-TYPE
   SYNTAX      Gauge32
   MAX-ACCESS  read-only
   STATUS      current
   DESCRIPTION
      "Path: atm.performance.pvcTable.atm.oamF5.endToEnd.pmRxStats.errUserCells

       32 bit unsigned gauge value."
   ::= {pr1646v2ATMImaPerEntry 288682032}

pr1646v2ATMImaPerAtmF5EteRxpmNMUC OBJECT-TYPE
   SYNTAX      Gauge32
   MAX-ACCESS  read-only
   STATUS      current
   DESCRIPTION
      "Path: atm.performance.pvcTable.atm.oamF5.endToEnd.pmRxStats.misInsertUserCells

       32 bit unsigned gauge value."
   ::= {pr1646v2ATMImaPerEntry 288682048}

pr1646v2ATMImaPerAtmF5EteRxpmCer OBJECT-TYPE
   SYNTAX      Integer32
   MAX-ACCESS  read-only
   STATUS      current
   DESCRIPTION
      "Path: atm.performance.pvcTable.atm.oamF5.endToEnd.pmRxStats.cellErrRatio

       formula = 1000000000 / ; 1000000000 *"
   ::= {pr1646v2ATMImaPerEntry 288682064}

pr1646v2ATMImaPerAtmF5EteRxpmClr OBJECT-TYPE
   SYNTAX      Integer32
   MAX-ACCESS  read-only
   STATUS      current
   DESCRIPTION
      "Path: atm.performance.pvcTable.atm.oamF5.endToEnd.pmRxStats.cellLossRatio

       formula = 1000000000 / ; 1000000000 *"
   ::= {pr1646v2ATMImaPerEntry 288682080}

pr1646v2ATMImaPerAtmF5EteRxpmCmr OBJECT-TYPE
   SYNTAX      Integer32
   MAX-ACCESS  read-only
   STATUS      current
   DESCRIPTION
      "Path: atm.performance.pvcTable.atm.oamF5.endToEnd.pmRxStats.cellMisinsertRatio

       unit name = misinserts/sec
       formula = 1000000000 / ; 1000000000 *"
   ::= {pr1646v2ATMImaPerEntry 288682096}

pr1646v2ATMImaPerAtmF5EteRxpmSecb OBJECT-TYPE
   SYNTAX      Integer32
   MAX-ACCESS  read-only
   STATUS      current
   DESCRIPTION
      "Path: atm.performance.pvcTable.atm.oamF5.endToEnd.pmRxStats.sevErrCellBlckRatio

       formula = 1000000000 / ; 1000000000 *"
   ::= {pr1646v2ATMImaPerEntry 288682112}

pr1646v2ATMImaPerAtmF5EteTxpmNLOC OBJECT-TYPE
   SYNTAX      Gauge32
   MAX-ACCESS  read-only
   STATUS      current
   DESCRIPTION
      "Path: atm.performance.pvcTable.atm.oamF5.endToEnd.pmTxStats.lostOamCells

       32 bit unsigned gauge value."
   ::= {pr1646v2ATMImaPerEntry 288686096}

pr1646v2ATMImaPerAtmF5EteTxpmNLUC OBJECT-TYPE
   SYNTAX      Gauge32
   MAX-ACCESS  read-only
   STATUS      current
   DESCRIPTION
      "Path: atm.performance.pvcTable.atm.oamF5.endToEnd.pmTxStats.lostUserCells

       32 bit unsigned gauge value."
   ::= {pr1646v2ATMImaPerEntry 288686112}

pr1646v2ATMImaPerAtmF5EteTxpmNEUC OBJECT-TYPE
   SYNTAX      Gauge32
   MAX-ACCESS  read-only
   STATUS      current
   DESCRIPTION
      "Path: atm.performance.pvcTable.atm.oamF5.endToEnd.pmTxStats.errUserCells

       32 bit unsigned gauge value."
   ::= {pr1646v2ATMImaPerEntry 288686128}

pr1646v2ATMImaPerAtmF5EteTxpmNMUC OBJECT-TYPE
   SYNTAX      Gauge32
   MAX-ACCESS  read-only
   STATUS      current
   DESCRIPTION
      "Path: atm.performance.pvcTable.atm.oamF5.endToEnd.pmTxStats.misInsertUserCells

       32 bit unsigned gauge value."
   ::= {pr1646v2ATMImaPerEntry 288686144}

pr1646v2ATMImaPerAtmF5EteTxpmCer OBJECT-TYPE
   SYNTAX      Integer32
   MAX-ACCESS  read-only
   STATUS      current
   DESCRIPTION
      "Path: atm.performance.pvcTable.atm.oamF5.endToEnd.pmTxStats.cellErrRatio

       formula = 1000000000 / ; 1000000000 *"
   ::= {pr1646v2ATMImaPerEntry 288686160}

pr1646v2ATMImaPerAtmF5EteTxpmClr OBJECT-TYPE
   SYNTAX      Integer32
   MAX-ACCESS  read-only
   STATUS      current
   DESCRIPTION
      "Path: atm.performance.pvcTable.atm.oamF5.endToEnd.pmTxStats.cellLossRatio

       formula = 1000000000 / ; 1000000000 *"
   ::= {pr1646v2ATMImaPerEntry 288686176}

pr1646v2ATMImaPerAtmF5EteTxpmCmr OBJECT-TYPE
   SYNTAX      Integer32
   MAX-ACCESS  read-only
   STATUS      current
   DESCRIPTION
      "Path: atm.performance.pvcTable.atm.oamF5.endToEnd.pmTxStats.cellMisinsertRatio

       unit name = misinserts/sec
       formula = 1000000000 / ; 1000000000 *"
   ::= {pr1646v2ATMImaPerEntry 288686192}

pr1646v2ATMImaPerAtmF5EteTxpmSecb OBJECT-TYPE
   SYNTAX      Integer32
   MAX-ACCESS  read-only
   STATUS      current
   DESCRIPTION
      "Path: atm.performance.pvcTable.atm.oamF5.endToEnd.pmTxStats.sevErrCellBlckRatio

       formula = 1000000000 / ; 1000000000 *"
   ::= {pr1646v2ATMImaPerEntry 288686208}

pr1646v2ATMImaPerAtmPppLinkMonitoringRequestsSent OBJECT-TYPE
   SYNTAX      Gauge32
   MAX-ACCESS  read-only
   STATUS      current
   DESCRIPTION
      "Path: atm.performance.pvcTable.atm.ppp.linkMonitoring.requestsSent

       32 bit unsigned gauge value."
   ::= {pr1646v2ATMImaPerEntry 289411088}

pr1646v2ATMImaPerAtmPppLinkMonitoringRepliesRcvd OBJECT-TYPE
   SYNTAX      Gauge32
   MAX-ACCESS  read-only
   STATUS      current
   DESCRIPTION
      "Path: atm.performance.pvcTable.atm.ppp.linkMonitoring.repliesRcvd

       32 bit unsigned gauge value."
   ::= {pr1646v2ATMImaPerEntry 289411104}

pr1646v2ATMImaPerAtmPppLinkMonitoringRequestsRcvd OBJECT-TYPE
   SYNTAX      Gauge32
   MAX-ACCESS  read-only
   STATUS      current
   DESCRIPTION
      "Path: atm.performance.pvcTable.atm.ppp.linkMonitoring.requestsRcvd

       32 bit unsigned gauge value."
   ::= {pr1646v2ATMImaPerEntry 289411120}

pr1646v2ATMImaPerAtmPppLinkMonitoringRepliesSent OBJECT-TYPE
   SYNTAX      Gauge32
   MAX-ACCESS  read-only
   STATUS      current
   DESCRIPTION
      "Path: atm.performance.pvcTable.atm.ppp.linkMonitoring.repliesSent

       32 bit unsigned gauge value."
   ::= {pr1646v2ATMImaPerEntry 289411136}

pr1646v2ATMImaPerFrLmiInStatusEnq OBJECT-TYPE
   SYNTAX      Counter32
   MAX-ACCESS  read-only
   STATUS      current
   DESCRIPTION
      "Path: atm.performance.pvcTable.frameRelay.lmi.inStatusEnquiry

       32 bit unsigned wrappable counter."
   ::= {pr1646v2ATMImaPerEntry 503382272}

pr1646v2ATMImaPerFrLmiInStatus OBJECT-TYPE
   SYNTAX      Counter32
   MAX-ACCESS  read-only
   STATUS      current
   DESCRIPTION
      "Path: atm.performance.pvcTable.frameRelay.lmi.inStatus

       32 bit unsigned wrappable counter."
   ::= {pr1646v2ATMImaPerEntry 503382528}

pr1646v2ATMImaPerFrLmiInStatUpdate OBJECT-TYPE
   SYNTAX      Counter32
   MAX-ACCESS  read-only
   STATUS      current
   DESCRIPTION
      "Path: atm.performance.pvcTable.frameRelay.lmi.inStatusUpdate

       32 bit unsigned wrappable counter."
   ::= {pr1646v2ATMImaPerEntry 503382784}

pr1646v2ATMImaPerFrLmiOutStatusEnq OBJECT-TYPE
   SYNTAX      Counter32
   MAX-ACCESS  read-only
   STATUS      current
   DESCRIPTION
      "Path: atm.performance.pvcTable.frameRelay.lmi.outStatusEnquiry

       32 bit unsigned wrappable counter."
   ::= {pr1646v2ATMImaPerEntry 503383040}

pr1646v2ATMImaPerFrLmiOutStatus OBJECT-TYPE
   SYNTAX      Counter32
   MAX-ACCESS  read-only
   STATUS      current
   DESCRIPTION
      "Path: atm.performance.pvcTable.frameRelay.lmi.outStatus

       32 bit unsigned wrappable counter."
   ::= {pr1646v2ATMImaPerEntry 503383296}

pr1646v2ATMImaPerFrLmiOutStatUpdate OBJECT-TYPE
   SYNTAX      Counter32
   MAX-ACCESS  read-only
   STATUS      current
   DESCRIPTION
      "Path: atm.performance.pvcTable.frameRelay.lmi.outStatusUpdate

       32 bit unsigned wrappable counter."
   ::= {pr1646v2ATMImaPerEntry 503383552}

pr1646v2ATMImaPerFrLmiNetPollNotRcvd OBJECT-TYPE
   SYNTAX      Counter32
   MAX-ACCESS  read-only
   STATUS      current
   DESCRIPTION
      "Path: atm.performance.pvcTable.frameRelay.lmi.netPollNotRcvd

       32 bit unsigned wrappable counter."
   ::= {pr1646v2ATMImaPerEntry 503383808}

pr1646v2ATMImaPerFrLmiUsrNoRespRcvd OBJECT-TYPE
   SYNTAX      Counter32
   MAX-ACCESS  read-only
   STATUS      current
   DESCRIPTION
      "Path: atm.performance.pvcTable.frameRelay.lmi.userNoResponseRcvd

       32 bit unsigned wrappable counter."
   ::= {pr1646v2ATMImaPerEntry 503387136}

pr1646v2ATMImaPerFrLmiUsrBadRespRcvd OBJECT-TYPE
   SYNTAX      Counter32
   MAX-ACCESS  read-only
   STATUS      current
   DESCRIPTION
      "Path: atm.performance.pvcTable.frameRelay.lmi.userBadResponsesRcvd

       32 bit unsigned wrappable counter."
   ::= {pr1646v2ATMImaPerEntry 503387392}

pr1646v2ATMImaPerMCH2P OBJECT-TYPE
   SYNTAX      SEQUENCE OF Pr1646v2ATMImaPerMCH2PEntry
   MAX-ACCESS  not-accessible
   STATUS      current
   DESCRIPTION
      ""
   ::= {pr1646v2ATMImaPer 41549824}

pr1646v2ATMImaPerMCH2PEntry OBJECT-TYPE
   SYNTAX      Pr1646v2ATMImaPerMCH2PEntry
   MAX-ACCESS  not-accessible
   STATUS      current
   DESCRIPTION
      ""
   INDEX      { pr1646v2ATMImaPerTableIx,
                pr1646v2ATMImaPerMCH2PTableIx }
   ::= {pr1646v2ATMImaPerMCH2P 1}

Pr1646v2ATMImaPerMCH2PEntry ::=
   SEQUENCE
      {
      pr1646v2ATMImaPerMCH2PTableIx
         TableIndex,
      pr1646v2ATMImaPerMCH2PSysUpTime
         TimeTicks,
      pr1646v2ATMImaPerMCH2PIfUpTime
         TimeTicks,
      pr1646v2ATMImaPerMCH2PIfStatChanges
         Counter32,
      pr1646v2ATMImaPerMCH2PIfInOctets
         Counter64,
      pr1646v2ATMImaPerMCH2PIfInUCPkts
         Counter64,
      pr1646v2ATMImaPerMCH2PIfInNUCPkts
         Counter64,
      pr1646v2ATMImaPerMCH2PIfInBCPkts
         Counter64,
      pr1646v2ATMImaPerMCH2PIfInMCPkts
         Counter64,
      pr1646v2ATMImaPerMCH2PIfInDiscards
         Counter64,
      pr1646v2ATMImaPerMCH2PIfInErrors
         Counter64,
      pr1646v2ATMImaPerMCH2PIfInUnkwn
         Counter64,
      pr1646v2ATMImaPerMCH2PInDropEx
         Counter64,
      pr1646v2ATMImaPerMCH2PInDropNoMac
         Counter64,
      pr1646v2ATMImaPerMCH2PInDropNUCast
         Counter64,
      pr1646v2ATMImaPerMCH2PInDropFilter
         Counter64,
      pr1646v2ATMImaPerMCH2PIfInBandwidth
         Integer32,
      pr1646v2ATMImaPerMCH2PIfOutOctets
         Counter64,
      pr1646v2ATMImaPerMCH2PIfOutUCPkts
         Counter64,
      pr1646v2ATMImaPerMCH2PIfOutNUCPkts
         Counter64,
      pr1646v2ATMImaPerMCH2PIfOutBCPkts
         Counter64,
      pr1646v2ATMImaPerMCH2PIfOutMCPkts
         Counter64,
      pr1646v2ATMImaPerMCH2PIfOutDiscards
         Counter64,
      pr1646v2ATMImaPerMCH2PIfOutErrors
         Counter64,
      pr1646v2ATMImaPerMCH2POutDropEx
         Counter64,
      pr1646v2ATMImaPerMCH2POutDropNoArp
         Counter64,
      pr1646v2ATMImaPerMCH2POutDropFilter
         Counter64,
      pr1646v2ATMImaPerMCH2PIfOutBandwidth
         Integer32,
      pr1646v2ATMImaPerMCH2PIfErrSec
         Counter32
      }

pr1646v2ATMImaPerMCH2PTableIx OBJECT-TYPE
   SYNTAX      TableIndex
   MAX-ACCESS  not-accessible
   STATUS      current
   DESCRIPTION
      ""
   ::= {pr1646v2ATMImaPerMCH2PEntry 11}

pr1646v2ATMImaPerMCH2PSysUpTime OBJECT-TYPE
   SYNTAX      TimeTicks
   MAX-ACCESS  read-only
   STATUS      current
   DESCRIPTION
      "Path: atm.performance.pvcTable.mibCounters.h2Performance.sysUpTime

       Time in centi-second."
   ::= {pr1646v2ATMImaPerMCH2PEntry 16777216}

pr1646v2ATMImaPerMCH2PIfUpTime OBJECT-TYPE
   SYNTAX      TimeTicks
   MAX-ACCESS  read-only
   STATUS      current
   DESCRIPTION
      "Path: atm.performance.pvcTable.mibCounters.h2Performance.ifUpTime

       Time in centi-second."
   ::= {pr1646v2ATMImaPerMCH2PEntry 33554432}

pr1646v2ATMImaPerMCH2PIfStatChanges OBJECT-TYPE
   SYNTAX      Counter32
   MAX-ACCESS  read-only
   STATUS      current
   DESCRIPTION
      "Path: atm.performance.pvcTable.mibCounters.h2Performance.ifStatusChanges

       32 bit unsigned wrappable counter."
   ::= {pr1646v2ATMImaPerMCH2PEntry 50331648}

pr1646v2ATMImaPerMCH2PIfInOctets OBJECT-TYPE
   SYNTAX      Counter64
   MAX-ACCESS  read-only
   STATUS      current
   DESCRIPTION
      "Path: atm.performance.pvcTable.mibCounters.h2Performance.ifInOctets

       64 bit unsigned wrappable counter."
   ::= {pr1646v2ATMImaPerMCH2PEntry 67108864}

pr1646v2ATMImaPerMCH2PIfInUCPkts OBJECT-TYPE
   SYNTAX      Counter64
   MAX-ACCESS  read-only
   STATUS      current
   DESCRIPTION
      "Path: atm.performance.pvcTable.mibCounters.h2Performance.ifInUcastPkts

       64 bit unsigned wrappable counter."
   ::= {pr1646v2ATMImaPerMCH2PEntry 83886080}

pr1646v2ATMImaPerMCH2PIfInNUCPkts OBJECT-TYPE
   SYNTAX      Counter64
   MAX-ACCESS  read-only
   STATUS      current
   DESCRIPTION
      "Path: atm.performance.pvcTable.mibCounters.h2Performance.ifInNUcastPkts

       64 bit unsigned wrappable counter."
   ::= {pr1646v2ATMImaPerMCH2PEntry 100663296}

pr1646v2ATMImaPerMCH2PIfInBCPkts OBJECT-TYPE
   SYNTAX      Counter64
   MAX-ACCESS  read-only
   STATUS      current
   DESCRIPTION
      "Path: atm.performance.pvcTable.mibCounters.h2Performance.ifInBcastPkts

       64 bit unsigned wrappable counter."
   ::= {pr1646v2ATMImaPerMCH2PEntry 419430400}

pr1646v2ATMImaPerMCH2PIfInMCPkts OBJECT-TYPE
   SYNTAX      Counter64
   MAX-ACCESS  read-only
   STATUS      current
   DESCRIPTION
      "Path: atm.performance.pvcTable.mibCounters.h2Performance.ifInMcastPkts

       64 bit unsigned wrappable counter."
   ::= {pr1646v2ATMImaPerMCH2PEntry 436207616}

pr1646v2ATMImaPerMCH2PIfInDiscards OBJECT-TYPE
   SYNTAX      Counter64
   MAX-ACCESS  read-only
   STATUS      current
   DESCRIPTION
      "Path: atm.performance.pvcTable.mibCounters.h2Performance.ifInDiscards

       64 bit unsigned wrappable counter."
   ::= {pr1646v2ATMImaPerMCH2PEntry 117440512}

pr1646v2ATMImaPerMCH2PIfInErrors OBJECT-TYPE
   SYNTAX      Counter64
   MAX-ACCESS  read-only
   STATUS      current
   DESCRIPTION
      "Path: atm.performance.pvcTable.mibCounters.h2Performance.ifInErrors

       64 bit unsigned wrappable counter."
   ::= {pr1646v2ATMImaPerMCH2PEntry 134217728}

pr1646v2ATMImaPerMCH2PIfInUnkwn OBJECT-TYPE
   SYNTAX      Counter64
   MAX-ACCESS  read-only
   STATUS      current
   DESCRIPTION
      "Path: atm.performance.pvcTable.mibCounters.h2Performance.ifInUnknownProtos

       64 bit unsigned wrappable counter."
   ::= {pr1646v2ATMImaPerMCH2PEntry 150994944}

pr1646v2ATMImaPerMCH2PInDropEx OBJECT-TYPE
   SYNTAX      Counter64
   MAX-ACCESS  read-only
   STATUS      current
   DESCRIPTION
      "Path: atm.performance.pvcTable.mibCounters.h2Performance.ifInDropLevelExceeded

       64 bit unsigned wrappable counter."
   ::= {pr1646v2ATMImaPerMCH2PEntry 335544320}

pr1646v2ATMImaPerMCH2PInDropNoMac OBJECT-TYPE
   SYNTAX      Counter64
   MAX-ACCESS  read-only
   STATUS      current
   DESCRIPTION
      "Path: atm.performance.pvcTable.mibCounters.h2Performance.fInDiscardsNoMacFit

       64 bit unsigned wrappable counter."
   ::= {pr1646v2ATMImaPerMCH2PEntry 301989888}

pr1646v2ATMImaPerMCH2PInDropNUCast OBJECT-TYPE
   SYNTAX      Counter64
   MAX-ACCESS  read-only
   STATUS      current
   DESCRIPTION
      "Path: atm.performance.pvcTable.mibCounters.h2Performance.fInDiscardsNUCast

       64 bit unsigned wrappable counter."
   ::= {pr1646v2ATMImaPerMCH2PEntry 318767104}

pr1646v2ATMImaPerMCH2PInDropFilter OBJECT-TYPE
   SYNTAX      Counter64
   MAX-ACCESS  read-only
   STATUS      current
   DESCRIPTION
      "Path: atm.performance.pvcTable.mibCounters.h2Performance.fInDiscardsFilter

       64 bit unsigned wrappable counter."
   ::= {pr1646v2ATMImaPerMCH2PEntry 385875968}

pr1646v2ATMImaPerMCH2PIfInBandwidth OBJECT-TYPE
   SYNTAX      Integer32
   MAX-ACCESS  read-only
   STATUS      current
   DESCRIPTION
      "Path: atm.performance.pvcTable.mibCounters.h2Performance.ifInBandwidth

       unit name = bps
       formula = 8 * ; 8 /"
   ::= {pr1646v2ATMImaPerMCH2PEntry 268435456}

pr1646v2ATMImaPerMCH2PIfOutOctets OBJECT-TYPE
   SYNTAX      Counter64
   MAX-ACCESS  read-only
   STATUS      current
   DESCRIPTION
      "Path: atm.performance.pvcTable.mibCounters.h2Performance.ifOutOctets

       64 bit unsigned wrappable counter."
   ::= {pr1646v2ATMImaPerMCH2PEntry 167772160}

pr1646v2ATMImaPerMCH2PIfOutUCPkts OBJECT-TYPE
   SYNTAX      Counter64
   MAX-ACCESS  read-only
   STATUS      current
   DESCRIPTION
      "Path: atm.performance.pvcTable.mibCounters.h2Performance.ifOutUcastPkts

       64 bit unsigned wrappable counter."
   ::= {pr1646v2ATMImaPerMCH2PEntry 184549376}

pr1646v2ATMImaPerMCH2PIfOutNUCPkts OBJECT-TYPE
   SYNTAX      Counter64
   MAX-ACCESS  read-only
   STATUS      current
   DESCRIPTION
      "Path: atm.performance.pvcTable.mibCounters.h2Performance.ifOutNUcastPkts

       64 bit unsigned wrappable counter."
   ::= {pr1646v2ATMImaPerMCH2PEntry 201326592}

pr1646v2ATMImaPerMCH2PIfOutBCPkts OBJECT-TYPE
   SYNTAX      Counter64
   MAX-ACCESS  read-only
   STATUS      current
   DESCRIPTION
      "Path: atm.performance.pvcTable.mibCounters.h2Performance.ifOutBcastPkts

       64 bit unsigned wrappable counter."
   ::= {pr1646v2ATMImaPerMCH2PEntry 452984832}

pr1646v2ATMImaPerMCH2PIfOutMCPkts OBJECT-TYPE
   SYNTAX      Counter64
   MAX-ACCESS  read-only
   STATUS      current
   DESCRIPTION
      "Path: atm.performance.pvcTable.mibCounters.h2Performance.ifOutMcastPkts

       64 bit unsigned wrappable counter."
   ::= {pr1646v2ATMImaPerMCH2PEntry 469762048}

pr1646v2ATMImaPerMCH2PIfOutDiscards OBJECT-TYPE
   SYNTAX      Counter64
   MAX-ACCESS  read-only
   STATUS      current
   DESCRIPTION
      "Path: atm.performance.pvcTable.mibCounters.h2Performance.ifOutDiscards

       64 bit unsigned wrappable counter."
   ::= {pr1646v2ATMImaPerMCH2PEntry 218103808}

pr1646v2ATMImaPerMCH2PIfOutErrors OBJECT-TYPE
   SYNTAX      Counter64
   MAX-ACCESS  read-only
   STATUS      current
   DESCRIPTION
      "Path: atm.performance.pvcTable.mibCounters.h2Performance.ifOutErrors

       64 bit unsigned wrappable counter."
   ::= {pr1646v2ATMImaPerMCH2PEntry 234881024}

pr1646v2ATMImaPerMCH2POutDropEx OBJECT-TYPE
   SYNTAX      Counter64
   MAX-ACCESS  read-only
   STATUS      current
   DESCRIPTION
      "Path: atm.performance.pvcTable.mibCounters.h2Performance.ifOutDropLevelExceeded

       64 bit unsigned wrappable counter."
   ::= {pr1646v2ATMImaPerMCH2PEntry 352321536}

pr1646v2ATMImaPerMCH2POutDropNoArp OBJECT-TYPE
   SYNTAX      Counter64
   MAX-ACCESS  read-only
   STATUS      current
   DESCRIPTION
      "Path: atm.performance.pvcTable.mibCounters.h2Performance.ifOutDiscardsNoArp

       64 bit unsigned wrappable counter."
   ::= {pr1646v2ATMImaPerMCH2PEntry 369098752}

pr1646v2ATMImaPerMCH2POutDropFilter OBJECT-TYPE
   SYNTAX      Counter64
   MAX-ACCESS  read-only
   STATUS      current
   DESCRIPTION
      "Path: atm.performance.pvcTable.mibCounters.h2Performance.ifOutDiscardsFilter

       64 bit unsigned wrappable counter."
   ::= {pr1646v2ATMImaPerMCH2PEntry 402653184}

pr1646v2ATMImaPerMCH2PIfOutBandwidth OBJECT-TYPE
   SYNTAX      Integer32
   MAX-ACCESS  read-only
   STATUS      current
   DESCRIPTION
      "Path: atm.performance.pvcTable.mibCounters.h2Performance.ifOutBandwidth

       unit name = bps
       formula = 8 * ; 8 /"
   ::= {pr1646v2ATMImaPerMCH2PEntry 285212672}

pr1646v2ATMImaPerMCH2PIfErrSec OBJECT-TYPE
   SYNTAX      Counter32
   MAX-ACCESS  read-only
   STATUS      current
   DESCRIPTION
      "Path: atm.performance.pvcTable.mibCounters.h2Performance.ifErrSec

       32 bit unsigned wrappable counter."
   ::= {pr1646v2ATMImaPerMCH2PEntry 251658240}

pr1646v2ATMImaPerMCH24P OBJECT-TYPE
   SYNTAX      SEQUENCE OF Pr1646v2ATMImaPerMCH24PEntry
   MAX-ACCESS  not-accessible
   STATUS      current
   DESCRIPTION
      ""
   ::= {pr1646v2ATMImaPer 41615360}

pr1646v2ATMImaPerMCH24PEntry OBJECT-TYPE
   SYNTAX      Pr1646v2ATMImaPerMCH24PEntry
   MAX-ACCESS  not-accessible
   STATUS      current
   DESCRIPTION
      ""
   INDEX      { pr1646v2ATMImaPerTableIx,
                pr1646v2ATMImaPerMCH24PTableIx }
   ::= {pr1646v2ATMImaPerMCH24P 1}

Pr1646v2ATMImaPerMCH24PEntry ::=
   SEQUENCE
      {
      pr1646v2ATMImaPerMCH24PTableIx
         TableIndex,
      pr1646v2ATMImaPerMCH24PSysUpTime
         TimeTicks,
      pr1646v2ATMImaPerMCH24PIfUpTime
         TimeTicks,
      pr1646v2ATMImaPerMCH24PIfStatChanges
         Counter32,
      pr1646v2ATMImaPerMCH24PIfInOctets
         Counter64,
      pr1646v2ATMImaPerMCH24PIfInUCPkts
         Counter64,
      pr1646v2ATMImaPerMCH24PIfInNUCPkts
         Counter64,
      pr1646v2ATMImaPerMCH24PIfInBCPkts
         Counter64,
      pr1646v2ATMImaPerMCH24PIfInMCPkts
         Counter64,
      pr1646v2ATMImaPerMCH24PIfInDiscards
         Counter64,
      pr1646v2ATMImaPerMCH24PIfInErrors
         Counter64,
      pr1646v2ATMImaPerMCH24PIfInUnkwn
         Counter64,
      pr1646v2ATMImaPerMCH24PInDropEx
         Counter64,
      pr1646v2ATMImaPerMCH24PInDropNoMac
         Counter64,
      pr1646v2ATMImaPerMCH24PInDropNUCast
         Counter64,
      pr1646v2ATMImaPerMCH24PInDropFilter
         Counter64,
      pr1646v2ATMImaPerMCH24PIfInBandwidth
         Integer32,
      pr1646v2ATMImaPerMCH24PIfOutOctets
         Counter64,
      pr1646v2ATMImaPerMCH24PIfOutUCPkts
         Counter64,
      pr1646v2ATMImaPerMCH24PIfOutNUCPkts
         Counter64,
      pr1646v2ATMImaPerMCH24PIfOutBCPkts
         Counter64,
      pr1646v2ATMImaPerMCH24PIfOutMCPkts
         Counter64,
      pr1646v2ATMImaPerMCH24PIfOutDiscards
         Counter64,
      pr1646v2ATMImaPerMCH24PIfOutErrors
         Counter64,
      pr1646v2ATMImaPerMCH24POutDropEx
         Counter64,
      pr1646v2ATMImaPerMCH24POutDropNoArp
         Counter64,
      pr1646v2ATMImaPerMCH24POutDropFilter
         Counter64,
      pr1646v2ATMImaPerMCH24PIfOutBandwidth
         Integer32,
      pr1646v2ATMImaPerMCH24PIfErrSec
         Counter32
      }

pr1646v2ATMImaPerMCH24PTableIx OBJECT-TYPE
   SYNTAX      TableIndex
   MAX-ACCESS  not-accessible
   STATUS      current
   DESCRIPTION
      ""
   ::= {pr1646v2ATMImaPerMCH24PEntry 11}

pr1646v2ATMImaPerMCH24PSysUpTime OBJECT-TYPE
   SYNTAX      TimeTicks
   MAX-ACCESS  read-only
   STATUS      current
   DESCRIPTION
      "Path: atm.performance.pvcTable.mibCounters.h24Performance.sysUpTime

       Time in centi-second."
   ::= {pr1646v2ATMImaPerMCH24PEntry 16777216}

pr1646v2ATMImaPerMCH24PIfUpTime OBJECT-TYPE
   SYNTAX      TimeTicks
   MAX-ACCESS  read-only
   STATUS      current
   DESCRIPTION
      "Path: atm.performance.pvcTable.mibCounters.h24Performance.ifUpTime

       Time in centi-second."
   ::= {pr1646v2ATMImaPerMCH24PEntry 33554432}

pr1646v2ATMImaPerMCH24PIfStatChanges OBJECT-TYPE
   SYNTAX      Counter32
   MAX-ACCESS  read-only
   STATUS      current
   DESCRIPTION
      "Path: atm.performance.pvcTable.mibCounters.h24Performance.ifStatusChanges

       32 bit unsigned wrappable counter."
   ::= {pr1646v2ATMImaPerMCH24PEntry 50331648}

pr1646v2ATMImaPerMCH24PIfInOctets OBJECT-TYPE
   SYNTAX      Counter64
   MAX-ACCESS  read-only
   STATUS      current
   DESCRIPTION
      "Path: atm.performance.pvcTable.mibCounters.h24Performance.ifInOctets

       64 bit unsigned wrappable counter."
   ::= {pr1646v2ATMImaPerMCH24PEntry 67108864}

pr1646v2ATMImaPerMCH24PIfInUCPkts OBJECT-TYPE
   SYNTAX      Counter64
   MAX-ACCESS  read-only
   STATUS      current
   DESCRIPTION
      "Path: atm.performance.pvcTable.mibCounters.h24Performance.ifInUcastPkts

       64 bit unsigned wrappable counter."
   ::= {pr1646v2ATMImaPerMCH24PEntry 83886080}

pr1646v2ATMImaPerMCH24PIfInNUCPkts OBJECT-TYPE
   SYNTAX      Counter64
   MAX-ACCESS  read-only
   STATUS      current
   DESCRIPTION
      "Path: atm.performance.pvcTable.mibCounters.h24Performance.ifInNUcastPkts

       64 bit unsigned wrappable counter."
   ::= {pr1646v2ATMImaPerMCH24PEntry 100663296}

pr1646v2ATMImaPerMCH24PIfInBCPkts OBJECT-TYPE
   SYNTAX      Counter64
   MAX-ACCESS  read-only
   STATUS      current
   DESCRIPTION
      "Path: atm.performance.pvcTable.mibCounters.h24Performance.ifInBcastPkts

       64 bit unsigned wrappable counter."
   ::= {pr1646v2ATMImaPerMCH24PEntry 419430400}

pr1646v2ATMImaPerMCH24PIfInMCPkts OBJECT-TYPE
   SYNTAX      Counter64
   MAX-ACCESS  read-only
   STATUS      current
   DESCRIPTION
      "Path: atm.performance.pvcTable.mibCounters.h24Performance.ifInMcastPkts

       64 bit unsigned wrappable counter."
   ::= {pr1646v2ATMImaPerMCH24PEntry 436207616}

pr1646v2ATMImaPerMCH24PIfInDiscards OBJECT-TYPE
   SYNTAX      Counter64
   MAX-ACCESS  read-only
   STATUS      current
   DESCRIPTION
      "Path: atm.performance.pvcTable.mibCounters.h24Performance.ifInDiscards

       64 bit unsigned wrappable counter."
   ::= {pr1646v2ATMImaPerMCH24PEntry 117440512}

pr1646v2ATMImaPerMCH24PIfInErrors OBJECT-TYPE
   SYNTAX      Counter64
   MAX-ACCESS  read-only
   STATUS      current
   DESCRIPTION
      "Path: atm.performance.pvcTable.mibCounters.h24Performance.ifInErrors

       64 bit unsigned wrappable counter."
   ::= {pr1646v2ATMImaPerMCH24PEntry 134217728}

pr1646v2ATMImaPerMCH24PIfInUnkwn OBJECT-TYPE
   SYNTAX      Counter64
   MAX-ACCESS  read-only
   STATUS      current
   DESCRIPTION
      "Path: atm.performance.pvcTable.mibCounters.h24Performance.ifInUnknownProtos

       64 bit unsigned wrappable counter."
   ::= {pr1646v2ATMImaPerMCH24PEntry 150994944}

pr1646v2ATMImaPerMCH24PInDropEx OBJECT-TYPE
   SYNTAX      Counter64
   MAX-ACCESS  read-only
   STATUS      current
   DESCRIPTION
      "Path: atm.performance.pvcTable.mibCounters.h24Performance.ifInDropLevelExceeded

       64 bit unsigned wrappable counter."
   ::= {pr1646v2ATMImaPerMCH24PEntry 335544320}

pr1646v2ATMImaPerMCH24PInDropNoMac OBJECT-TYPE
   SYNTAX      Counter64
   MAX-ACCESS  read-only
   STATUS      current
   DESCRIPTION
      "Path: atm.performance.pvcTable.mibCounters.h24Performance.fInDiscardsNoMacFit

       64 bit unsigned wrappable counter."
   ::= {pr1646v2ATMImaPerMCH24PEntry 301989888}

pr1646v2ATMImaPerMCH24PInDropNUCast OBJECT-TYPE
   SYNTAX      Counter64
   MAX-ACCESS  read-only
   STATUS      current
   DESCRIPTION
      "Path: atm.performance.pvcTable.mibCounters.h24Performance.fInDiscardsNUCast

       64 bit unsigned wrappable counter."
   ::= {pr1646v2ATMImaPerMCH24PEntry 318767104}

pr1646v2ATMImaPerMCH24PInDropFilter OBJECT-TYPE
   SYNTAX      Counter64
   MAX-ACCESS  read-only
   STATUS      current
   DESCRIPTION
      "Path: atm.performance.pvcTable.mibCounters.h24Performance.fInDiscardsFilter

       64 bit unsigned wrappable counter."
   ::= {pr1646v2ATMImaPerMCH24PEntry 385875968}

pr1646v2ATMImaPerMCH24PIfInBandwidth OBJECT-TYPE
   SYNTAX      Integer32
   MAX-ACCESS  read-only
   STATUS      current
   DESCRIPTION
      "Path: atm.performance.pvcTable.mibCounters.h24Performance.ifInBandwidth

       unit name = bps
       formula = 8 * ; 8 /"
   ::= {pr1646v2ATMImaPerMCH24PEntry 268435456}

pr1646v2ATMImaPerMCH24PIfOutOctets OBJECT-TYPE
   SYNTAX      Counter64
   MAX-ACCESS  read-only
   STATUS      current
   DESCRIPTION
      "Path: atm.performance.pvcTable.mibCounters.h24Performance.ifOutOctets

       64 bit unsigned wrappable counter."
   ::= {pr1646v2ATMImaPerMCH24PEntry 167772160}

pr1646v2ATMImaPerMCH24PIfOutUCPkts OBJECT-TYPE
   SYNTAX      Counter64
   MAX-ACCESS  read-only
   STATUS      current
   DESCRIPTION
      "Path: atm.performance.pvcTable.mibCounters.h24Performance.ifOutUcastPkts

       64 bit unsigned wrappable counter."
   ::= {pr1646v2ATMImaPerMCH24PEntry 184549376}

pr1646v2ATMImaPerMCH24PIfOutNUCPkts OBJECT-TYPE
   SYNTAX      Counter64
   MAX-ACCESS  read-only
   STATUS      current
   DESCRIPTION
      "Path: atm.performance.pvcTable.mibCounters.h24Performance.ifOutNUcastPkts

       64 bit unsigned wrappable counter."
   ::= {pr1646v2ATMImaPerMCH24PEntry 201326592}

pr1646v2ATMImaPerMCH24PIfOutBCPkts OBJECT-TYPE
   SYNTAX      Counter64
   MAX-ACCESS  read-only
   STATUS      current
   DESCRIPTION
      "Path: atm.performance.pvcTable.mibCounters.h24Performance.ifOutBcastPkts

       64 bit unsigned wrappable counter."
   ::= {pr1646v2ATMImaPerMCH24PEntry 452984832}

pr1646v2ATMImaPerMCH24PIfOutMCPkts OBJECT-TYPE
   SYNTAX      Counter64
   MAX-ACCESS  read-only
   STATUS      current
   DESCRIPTION
      "Path: atm.performance.pvcTable.mibCounters.h24Performance.ifOutMcastPkts

       64 bit unsigned wrappable counter."
   ::= {pr1646v2ATMImaPerMCH24PEntry 469762048}

pr1646v2ATMImaPerMCH24PIfOutDiscards OBJECT-TYPE
   SYNTAX      Counter64
   MAX-ACCESS  read-only
   STATUS      current
   DESCRIPTION
      "Path: atm.performance.pvcTable.mibCounters.h24Performance.ifOutDiscards

       64 bit unsigned wrappable counter."
   ::= {pr1646v2ATMImaPerMCH24PEntry 218103808}

pr1646v2ATMImaPerMCH24PIfOutErrors OBJECT-TYPE
   SYNTAX      Counter64
   MAX-ACCESS  read-only
   STATUS      current
   DESCRIPTION
      "Path: atm.performance.pvcTable.mibCounters.h24Performance.ifOutErrors

       64 bit unsigned wrappable counter."
   ::= {pr1646v2ATMImaPerMCH24PEntry 234881024}

pr1646v2ATMImaPerMCH24POutDropEx OBJECT-TYPE
   SYNTAX      Counter64
   MAX-ACCESS  read-only
   STATUS      current
   DESCRIPTION
      "Path: atm.performance.pvcTable.mibCounters.h24Performance.ifOutDropLevelExceeded

       64 bit unsigned wrappable counter."
   ::= {pr1646v2ATMImaPerMCH24PEntry 352321536}

pr1646v2ATMImaPerMCH24POutDropNoArp OBJECT-TYPE
   SYNTAX      Counter64
   MAX-ACCESS  read-only
   STATUS      current
   DESCRIPTION
      "Path: atm.performance.pvcTable.mibCounters.h24Performance.ifOutDiscardsNoArp

       64 bit unsigned wrappable counter."
   ::= {pr1646v2ATMImaPerMCH24PEntry 369098752}

pr1646v2ATMImaPerMCH24POutDropFilter OBJECT-TYPE
   SYNTAX      Counter64
   MAX-ACCESS  read-only
   STATUS      current
   DESCRIPTION
      "Path: atm.performance.pvcTable.mibCounters.h24Performance.ifOutDiscardsFilter

       64 bit unsigned wrappable counter."
   ::= {pr1646v2ATMImaPerMCH24PEntry 402653184}

pr1646v2ATMImaPerMCH24PIfOutBandwidth OBJECT-TYPE
   SYNTAX      Integer32
   MAX-ACCESS  read-only
   STATUS      current
   DESCRIPTION
      "Path: atm.performance.pvcTable.mibCounters.h24Performance.ifOutBandwidth

       unit name = bps
       formula = 8 * ; 8 /"
   ::= {pr1646v2ATMImaPerMCH24PEntry 285212672}

pr1646v2ATMImaPerMCH24PIfErrSec OBJECT-TYPE
   SYNTAX      Counter32
   MAX-ACCESS  read-only
   STATUS      current
   DESCRIPTION
      "Path: atm.performance.pvcTable.mibCounters.h24Performance.ifErrSec

       32 bit unsigned wrappable counter."
   ::= {pr1646v2ATMImaPerMCH24PEntry 251658240}

pr1646v2ATMImaPerMCD7P OBJECT-TYPE
   SYNTAX      SEQUENCE OF Pr1646v2ATMImaPerMCD7PEntry
   MAX-ACCESS  not-accessible
   STATUS      current
   DESCRIPTION
      ""
   ::= {pr1646v2ATMImaPer 41680896}

pr1646v2ATMImaPerMCD7PEntry OBJECT-TYPE
   SYNTAX      Pr1646v2ATMImaPerMCD7PEntry
   MAX-ACCESS  not-accessible
   STATUS      current
   DESCRIPTION
      ""
   INDEX      { pr1646v2ATMImaPerTableIx,
                pr1646v2ATMImaPerMCD7PTableIx }
   ::= {pr1646v2ATMImaPerMCD7P 1}

Pr1646v2ATMImaPerMCD7PEntry ::=
   SEQUENCE
      {
      pr1646v2ATMImaPerMCD7PTableIx
         TableIndex,
      pr1646v2ATMImaPerMCD7PSysUpTime
         TimeTicks,
      pr1646v2ATMImaPerMCD7PIfUpTime
         TimeTicks,
      pr1646v2ATMImaPerMCD7PIfStatChanges
         Counter32,
      pr1646v2ATMImaPerMCD7PIfInOctets
         Counter64,
      pr1646v2ATMImaPerMCD7PIfInUCPkts
         Counter64,
      pr1646v2ATMImaPerMCD7PIfInNUCPkts
         Counter64,
      pr1646v2ATMImaPerMCD7PIfInBCPkts
         Counter64,
      pr1646v2ATMImaPerMCD7PIfInMCPkts
         Counter64,
      pr1646v2ATMImaPerMCD7PIfInDiscards
         Counter64,
      pr1646v2ATMImaPerMCD7PIfInErrors
         Counter64,
      pr1646v2ATMImaPerMCD7PIfInUnkwn
         Counter64,
      pr1646v2ATMImaPerMCD7PInDropEx
         Counter64,
      pr1646v2ATMImaPerMCD7PInDropNoMac
         Counter64,
      pr1646v2ATMImaPerMCD7PInDropNUCast
         Counter64,
      pr1646v2ATMImaPerMCD7PInDropFilter
         Counter64,
      pr1646v2ATMImaPerMCD7PIfInBandwidth
         Integer32,
      pr1646v2ATMImaPerMCD7PIfOutOctets
         Counter64,
      pr1646v2ATMImaPerMCD7PIfOutUCPkts
         Counter64,
      pr1646v2ATMImaPerMCD7PIfOutNUCPkts
         Counter64,
      pr1646v2ATMImaPerMCD7PIfOutBCPkts
         Counter64,
      pr1646v2ATMImaPerMCD7PIfOutMCPkts
         Counter64,
      pr1646v2ATMImaPerMCD7PIfOutDiscards
         Counter64,
      pr1646v2ATMImaPerMCD7PIfOutErrors
         Counter64,
      pr1646v2ATMImaPerMCD7POutDropEx
         Counter64,
      pr1646v2ATMImaPerMCD7POutDropNoArp
         Counter64,
      pr1646v2ATMImaPerMCD7POutDropFilter
         Counter64,
      pr1646v2ATMImaPerMCD7PIfOutBandwidth
         Integer32,
      pr1646v2ATMImaPerMCD7PIfErrSec
         Counter32
      }

pr1646v2ATMImaPerMCD7PTableIx OBJECT-TYPE
   SYNTAX      TableIndex
   MAX-ACCESS  not-accessible
   STATUS      current
   DESCRIPTION
      ""
   ::= {pr1646v2ATMImaPerMCD7PEntry 11}

pr1646v2ATMImaPerMCD7PSysUpTime OBJECT-TYPE
   SYNTAX      TimeTicks
   MAX-ACCESS  read-only
   STATUS      current
   DESCRIPTION
      "Path: atm.performance.pvcTable.mibCounters.d7Performance.sysUpTime

       Time in centi-second."
   ::= {pr1646v2ATMImaPerMCD7PEntry 16777216}

pr1646v2ATMImaPerMCD7PIfUpTime OBJECT-TYPE
   SYNTAX      TimeTicks
   MAX-ACCESS  read-only
   STATUS      current
   DESCRIPTION
      "Path: atm.performance.pvcTable.mibCounters.d7Performance.ifUpTime

       Time in centi-second."
   ::= {pr1646v2ATMImaPerMCD7PEntry 33554432}

pr1646v2ATMImaPerMCD7PIfStatChanges OBJECT-TYPE
   SYNTAX      Counter32
   MAX-ACCESS  read-only
   STATUS      current
   DESCRIPTION
      "Path: atm.performance.pvcTable.mibCounters.d7Performance.ifStatusChanges

       32 bit unsigned wrappable counter."
   ::= {pr1646v2ATMImaPerMCD7PEntry 50331648}

pr1646v2ATMImaPerMCD7PIfInOctets OBJECT-TYPE
   SYNTAX      Counter64
   MAX-ACCESS  read-only
   STATUS      current
   DESCRIPTION
      "Path: atm.performance.pvcTable.mibCounters.d7Performance.ifInOctets

       64 bit unsigned wrappable counter."
   ::= {pr1646v2ATMImaPerMCD7PEntry 67108864}

pr1646v2ATMImaPerMCD7PIfInUCPkts OBJECT-TYPE
   SYNTAX      Counter64
   MAX-ACCESS  read-only
   STATUS      current
   DESCRIPTION
      "Path: atm.performance.pvcTable.mibCounters.d7Performance.ifInUcastPkts

       64 bit unsigned wrappable counter."
   ::= {pr1646v2ATMImaPerMCD7PEntry 83886080}

pr1646v2ATMImaPerMCD7PIfInNUCPkts OBJECT-TYPE
   SYNTAX      Counter64
   MAX-ACCESS  read-only
   STATUS      current
   DESCRIPTION
      "Path: atm.performance.pvcTable.mibCounters.d7Performance.ifInNUcastPkts

       64 bit unsigned wrappable counter."
   ::= {pr1646v2ATMImaPerMCD7PEntry 100663296}

pr1646v2ATMImaPerMCD7PIfInBCPkts OBJECT-TYPE
   SYNTAX      Counter64
   MAX-ACCESS  read-only
   STATUS      current
   DESCRIPTION
      "Path: atm.performance.pvcTable.mibCounters.d7Performance.ifInBcastPkts

       64 bit unsigned wrappable counter."
   ::= {pr1646v2ATMImaPerMCD7PEntry 419430400}

pr1646v2ATMImaPerMCD7PIfInMCPkts OBJECT-TYPE
   SYNTAX      Counter64
   MAX-ACCESS  read-only
   STATUS      current
   DESCRIPTION
      "Path: atm.performance.pvcTable.mibCounters.d7Performance.ifInMcastPkts

       64 bit unsigned wrappable counter."
   ::= {pr1646v2ATMImaPerMCD7PEntry 436207616}

pr1646v2ATMImaPerMCD7PIfInDiscards OBJECT-TYPE
   SYNTAX      Counter64
   MAX-ACCESS  read-only
   STATUS      current
   DESCRIPTION
      "Path: atm.performance.pvcTable.mibCounters.d7Performance.ifInDiscards

       64 bit unsigned wrappable counter."
   ::= {pr1646v2ATMImaPerMCD7PEntry 117440512}

pr1646v2ATMImaPerMCD7PIfInErrors OBJECT-TYPE
   SYNTAX      Counter64
   MAX-ACCESS  read-only
   STATUS      current
   DESCRIPTION
      "Path: atm.performance.pvcTable.mibCounters.d7Performance.ifInErrors

       64 bit unsigned wrappable counter."
   ::= {pr1646v2ATMImaPerMCD7PEntry 134217728}

pr1646v2ATMImaPerMCD7PIfInUnkwn OBJECT-TYPE
   SYNTAX      Counter64
   MAX-ACCESS  read-only
   STATUS      current
   DESCRIPTION
      "Path: atm.performance.pvcTable.mibCounters.d7Performance.ifInUnknownProtos

       64 bit unsigned wrappable counter."
   ::= {pr1646v2ATMImaPerMCD7PEntry 150994944}

pr1646v2ATMImaPerMCD7PInDropEx OBJECT-TYPE
   SYNTAX      Counter64
   MAX-ACCESS  read-only
   STATUS      current
   DESCRIPTION
      "Path: atm.performance.pvcTable.mibCounters.d7Performance.ifInDropLevelExceeded

       64 bit unsigned wrappable counter."
   ::= {pr1646v2ATMImaPerMCD7PEntry 335544320}

pr1646v2ATMImaPerMCD7PInDropNoMac OBJECT-TYPE
   SYNTAX      Counter64
   MAX-ACCESS  read-only
   STATUS      current
   DESCRIPTION
      "Path: atm.performance.pvcTable.mibCounters.d7Performance.fInDiscardsNoMacFit

       64 bit unsigned wrappable counter."
   ::= {pr1646v2ATMImaPerMCD7PEntry 301989888}

pr1646v2ATMImaPerMCD7PInDropNUCast OBJECT-TYPE
   SYNTAX      Counter64
   MAX-ACCESS  read-only
   STATUS      current
   DESCRIPTION
      "Path: atm.performance.pvcTable.mibCounters.d7Performance.fInDiscardsNUCast

       64 bit unsigned wrappable counter."
   ::= {pr1646v2ATMImaPerMCD7PEntry 318767104}

pr1646v2ATMImaPerMCD7PInDropFilter OBJECT-TYPE
   SYNTAX      Counter64
   MAX-ACCESS  read-only
   STATUS      current
   DESCRIPTION
      "Path: atm.performance.pvcTable.mibCounters.d7Performance.fInDiscardsFilter

       64 bit unsigned wrappable counter."
   ::= {pr1646v2ATMImaPerMCD7PEntry 385875968}

pr1646v2ATMImaPerMCD7PIfInBandwidth OBJECT-TYPE
   SYNTAX      Integer32
   MAX-ACCESS  read-only
   STATUS      current
   DESCRIPTION
      "Path: atm.performance.pvcTable.mibCounters.d7Performance.ifInBandwidth

       unit name = bps
       formula = 8 * ; 8 /"
   ::= {pr1646v2ATMImaPerMCD7PEntry 268435456}

pr1646v2ATMImaPerMCD7PIfOutOctets OBJECT-TYPE
   SYNTAX      Counter64
   MAX-ACCESS  read-only
   STATUS      current
   DESCRIPTION
      "Path: atm.performance.pvcTable.mibCounters.d7Performance.ifOutOctets

       64 bit unsigned wrappable counter."
   ::= {pr1646v2ATMImaPerMCD7PEntry 167772160}

pr1646v2ATMImaPerMCD7PIfOutUCPkts OBJECT-TYPE
   SYNTAX      Counter64
   MAX-ACCESS  read-only
   STATUS      current
   DESCRIPTION
      "Path: atm.performance.pvcTable.mibCounters.d7Performance.ifOutUcastPkts

       64 bit unsigned wrappable counter."
   ::= {pr1646v2ATMImaPerMCD7PEntry 184549376}

pr1646v2ATMImaPerMCD7PIfOutNUCPkts OBJECT-TYPE
   SYNTAX      Counter64
   MAX-ACCESS  read-only
   STATUS      current
   DESCRIPTION
      "Path: atm.performance.pvcTable.mibCounters.d7Performance.ifOutNUcastPkts

       64 bit unsigned wrappable counter."
   ::= {pr1646v2ATMImaPerMCD7PEntry 201326592}

pr1646v2ATMImaPerMCD7PIfOutBCPkts OBJECT-TYPE
   SYNTAX      Counter64
   MAX-ACCESS  read-only
   STATUS      current
   DESCRIPTION
      "Path: atm.performance.pvcTable.mibCounters.d7Performance.ifOutBcastPkts

       64 bit unsigned wrappable counter."
   ::= {pr1646v2ATMImaPerMCD7PEntry 452984832}

pr1646v2ATMImaPerMCD7PIfOutMCPkts OBJECT-TYPE
   SYNTAX      Counter64
   MAX-ACCESS  read-only
   STATUS      current
   DESCRIPTION
      "Path: atm.performance.pvcTable.mibCounters.d7Performance.ifOutMcastPkts

       64 bit unsigned wrappable counter."
   ::= {pr1646v2ATMImaPerMCD7PEntry 469762048}

pr1646v2ATMImaPerMCD7PIfOutDiscards OBJECT-TYPE
   SYNTAX      Counter64
   MAX-ACCESS  read-only
   STATUS      current
   DESCRIPTION
      "Path: atm.performance.pvcTable.mibCounters.d7Performance.ifOutDiscards

       64 bit unsigned wrappable counter."
   ::= {pr1646v2ATMImaPerMCD7PEntry 218103808}

pr1646v2ATMImaPerMCD7PIfOutErrors OBJECT-TYPE
   SYNTAX      Counter64
   MAX-ACCESS  read-only
   STATUS      current
   DESCRIPTION
      "Path: atm.performance.pvcTable.mibCounters.d7Performance.ifOutErrors

       64 bit unsigned wrappable counter."
   ::= {pr1646v2ATMImaPerMCD7PEntry 234881024}

pr1646v2ATMImaPerMCD7POutDropEx OBJECT-TYPE
   SYNTAX      Counter64
   MAX-ACCESS  read-only
   STATUS      current
   DESCRIPTION
      "Path: atm.performance.pvcTable.mibCounters.d7Performance.ifOutDropLevelExceeded

       64 bit unsigned wrappable counter."
   ::= {pr1646v2ATMImaPerMCD7PEntry 352321536}

pr1646v2ATMImaPerMCD7POutDropNoArp OBJECT-TYPE
   SYNTAX      Counter64
   MAX-ACCESS  read-only
   STATUS      current
   DESCRIPTION
      "Path: atm.performance.pvcTable.mibCounters.d7Performance.ifOutDiscardsNoArp

       64 bit unsigned wrappable counter."
   ::= {pr1646v2ATMImaPerMCD7PEntry 369098752}

pr1646v2ATMImaPerMCD7POutDropFilter OBJECT-TYPE
   SYNTAX      Counter64
   MAX-ACCESS  read-only
   STATUS      current
   DESCRIPTION
      "Path: atm.performance.pvcTable.mibCounters.d7Performance.ifOutDiscardsFilter

       64 bit unsigned wrappable counter."
   ::= {pr1646v2ATMImaPerMCD7PEntry 402653184}

pr1646v2ATMImaPerMCD7PIfOutBandwidth OBJECT-TYPE
   SYNTAX      Integer32
   MAX-ACCESS  read-only
   STATUS      current
   DESCRIPTION
      "Path: atm.performance.pvcTable.mibCounters.d7Performance.ifOutBandwidth

       unit name = bps
       formula = 8 * ; 8 /"
   ::= {pr1646v2ATMImaPerMCD7PEntry 285212672}

pr1646v2ATMImaPerMCD7PIfErrSec OBJECT-TYPE
   SYNTAX      Counter32
   MAX-ACCESS  read-only
   STATUS      current
   DESCRIPTION
      "Path: atm.performance.pvcTable.mibCounters.d7Performance.ifErrSec

       32 bit unsigned wrappable counter."
   ::= {pr1646v2ATMImaPerMCD7PEntry 251658240}

pr1646v2ATMImaPerInPQs OBJECT-TYPE
   SYNTAX      SEQUENCE OF Pr1646v2ATMImaPerInPQsEntry
   MAX-ACCESS  not-accessible
   STATUS      current
   DESCRIPTION
      ""
   ::= {pr1646v2ATMImaPer 100663296}

pr1646v2ATMImaPerInPQsEntry OBJECT-TYPE
   SYNTAX      Pr1646v2ATMImaPerInPQsEntry
   MAX-ACCESS  not-accessible
   STATUS      current
   DESCRIPTION
      ""
   INDEX      { pr1646v2ATMImaPerTableIx,
                pr1646v2ATMImaPerInPQsTableIx }
   ::= {pr1646v2ATMImaPerInPQs 1}

Pr1646v2ATMImaPerInPQsEntry ::=
   SEQUENCE
      {
      pr1646v2ATMImaPerInPQsTableIx
         TableIndex,
      pr1646v2ATMImaPerInPQsName
         INTEGER,
      pr1646v2ATMImaPerInPQsLength
         Integer32,
      pr1646v2ATMImaPerInPQsOctetLength
         Integer32,
      pr1646v2ATMImaPerInPQsRedLength
         Integer32,
      pr1646v2ATMImaPerInPQsPacketsTotal
         Counter64,
      pr1646v2ATMImaPerInPQsPacketsDirectTx
         Counter64,
      pr1646v2ATMImaPerInPQsPacketsQueued
         Counter64,
      pr1646v2ATMImaPerInPQsPacketsDropped
         Counter64,
      pr1646v2ATMImaPerInPQsPacketsRedDropped
         Counter64,
      pr1646v2ATMImaPerInPQsPacketsCirTx
         Counter64,
      pr1646v2ATMImaPerInPQsPacketsEirTx
         Counter64,
      pr1646v2ATMImaPerInPQsPacketsViolateTx
         Counter64,
      pr1646v2ATMImaPerInPQsOctetsTotal
         Counter64,
      pr1646v2ATMImaPerInPQsOctetsDirectTx
         Counter64,
      pr1646v2ATMImaPerInPQsOctetsQueued
         Counter64,
      pr1646v2ATMImaPerInPQsOctetsDropped
         Counter64,
      pr1646v2ATMImaPerInPQsOctetsRedDropped
         Counter64,
      pr1646v2ATMImaPerInPQsOctetsCirTx
         Counter64,
      pr1646v2ATMImaPerInPQsOctetsEirTx
         Counter64,
      pr1646v2ATMImaPerInPQsOctetsViolateTx
         Counter64,
      pr1646v2ATMImaPerInPQsOctetsBandwidth15sec
         Integer32,
      pr1646v2ATMImaPerInPQsOctetsBandwidth30sec
         Integer32,
      pr1646v2ATMImaPerInPQsOctetsBandwidth1min
         Integer32,
      pr1646v2ATMImaPerInPQsOctetsBandwidth2min
         Integer32,
      pr1646v2ATMImaPerInPQsOctetsBandwidth5min
         Integer32
      }

pr1646v2ATMImaPerInPQsTableIx OBJECT-TYPE
   SYNTAX      TableIndex
   MAX-ACCESS  not-accessible
   STATUS      current
   DESCRIPTION
      ""
   ::= {pr1646v2ATMImaPerInPQsEntry 11}

pr1646v2ATMImaPerInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMImaPerInPQsEntry 16777216}

pr1646v2ATMImaPerInPQsLength OBJECT-TYPE
   SYNTAX      Integer32
   MAX-ACCESS  read-only
   STATUS      current
   DESCRIPTION
      "Path: atm.performance.pvcTable.inPriorityQueues.length"
   ::= {pr1646v2ATMImaPerInPQsEntry 33554432}

pr1646v2ATMImaPerInPQsOctetLength OBJECT-TYPE
   SYNTAX      Integer32
   MAX-ACCESS  read-only
   STATUS      current
   DESCRIPTION
      "Path: atm.performance.pvcTable.inPriorityQueues.octetLength"
   ::= {pr1646v2ATMImaPerInPQsEntry 150994944}

pr1646v2ATMImaPerInPQsRedLength OBJECT-TYPE
   SYNTAX      Integer32
   MAX-ACCESS  read-only
   STATUS      current
   DESCRIPTION
      "Path: atm.performance.pvcTable.inPriorityQueues.redLength"
   ::= {pr1646v2ATMImaPerInPQsEntry 134217728}

pr1646v2ATMImaPerInPQsPacketsTotal OBJECT-TYPE
   SYNTAX      Counter64
   MAX-ACCESS  read-only
   STATUS      current
   DESCRIPTION
      "Path: atm.performance.pvcTable.inPriorityQueues.packets.total

       64 bit unsigned wrappable counter."
   ::= {pr1646v2ATMImaPerInPQsEntry 50790400}

pr1646v2ATMImaPerInPQsPacketsDirectTx OBJECT-TYPE
   SYNTAX      Counter64
   MAX-ACCESS  read-only
   STATUS      current
   DESCRIPTION
      "Path: atm.performance.pvcTable.inPriorityQueues.packets.directTx

       64 bit unsigned wrappable counter."
   ::= {pr1646v2ATMImaPerInPQsEntry 50397184}

pr1646v2ATMImaPerInPQsPacketsQueued OBJECT-TYPE
   SYNTAX      Counter64
   MAX-ACCESS  read-only
   STATUS      current
   DESCRIPTION
      "Path: atm.performance.pvcTable.inPriorityQueues.packets.queued

       64 bit unsigned wrappable counter."
   ::= {pr1646v2ATMImaPerInPQsEntry 50462720}

pr1646v2ATMImaPerInPQsPacketsDropped OBJECT-TYPE
   SYNTAX      Counter64
   MAX-ACCESS  read-only
   STATUS      current
   DESCRIPTION
      "Path: atm.performance.pvcTable.inPriorityQueues.packets.dropped

       64 bit unsigned wrappable counter."
   ::= {pr1646v2ATMImaPerInPQsEntry 50528256}

pr1646v2ATMImaPerInPQsPacketsRedDropped OBJECT-TYPE
   SYNTAX      Counter64
   MAX-ACCESS  read-only
   STATUS      current
   DESCRIPTION
      "Path: atm.performance.pvcTable.inPriorityQueues.packets.redDropped

       64 bit unsigned wrappable counter."
   ::= {pr1646v2ATMImaPerInPQsEntry 50724864}

pr1646v2ATMImaPerInPQsPacketsCirTx OBJECT-TYPE
   SYNTAX      Counter64
   MAX-ACCESS  read-only
   STATUS      current
   DESCRIPTION
      "Path: atm.performance.pvcTable.inPriorityQueues.packets.cirTx

       64 bit unsigned wrappable counter."
   ::= {pr1646v2ATMImaPerInPQsEntry 50593792}

pr1646v2ATMImaPerInPQsPacketsEirTx OBJECT-TYPE
   SYNTAX      Counter64
   MAX-ACCESS  read-only
   STATUS      current
   DESCRIPTION
      "Path: atm.performance.pvcTable.inPriorityQueues.packets.eirTx

       64 bit unsigned wrappable counter."
   ::= {pr1646v2ATMImaPerInPQsEntry 50659328}

pr1646v2ATMImaPerInPQsPacketsViolateTx OBJECT-TYPE
   SYNTAX      Counter64
   MAX-ACCESS  read-only
   STATUS      current
   DESCRIPTION
      "Path: atm.performance.pvcTable.inPriorityQueues.packets.violateTx

       64 bit unsigned wrappable counter."
   ::= {pr1646v2ATMImaPerInPQsEntry 50855936}

pr1646v2ATMImaPerInPQsOctetsTotal OBJECT-TYPE
   SYNTAX      Counter64
   MAX-ACCESS  read-only
   STATUS      current
   DESCRIPTION
      "Path: atm.performance.pvcTable.inPriorityQueues.octets.total

       64 bit unsigned wrappable counter."
   ::= {pr1646v2ATMImaPerInPQsEntry 67567616}

pr1646v2ATMImaPerInPQsOctetsDirectTx OBJECT-TYPE
   SYNTAX      Counter64
   MAX-ACCESS  read-only
   STATUS      current
   DESCRIPTION
      "Path: atm.performance.pvcTable.inPriorityQueues.octets.directTx

       64 bit unsigned wrappable counter."
   ::= {pr1646v2ATMImaPerInPQsEntry 67174400}

pr1646v2ATMImaPerInPQsOctetsQueued OBJECT-TYPE
   SYNTAX      Counter64
   MAX-ACCESS  read-only
   STATUS      current
   DESCRIPTION
      "Path: atm.performance.pvcTable.inPriorityQueues.octets.queued

       64 bit unsigned wrappable counter."
   ::= {pr1646v2ATMImaPerInPQsEntry 67239936}

pr1646v2ATMImaPerInPQsOctetsDropped OBJECT-TYPE
   SYNTAX      Counter64
   MAX-ACCESS  read-only
   STATUS      current
   DESCRIPTION
      "Path: atm.performance.pvcTable.inPriorityQueues.octets.dropped

       64 bit unsigned wrappable counter."
   ::= {pr1646v2ATMImaPerInPQsEntry 67305472}

pr1646v2ATMImaPerInPQsOctetsRedDropped OBJECT-TYPE
   SYNTAX      Counter64
   MAX-ACCESS  read-only
   STATUS      current
   DESCRIPTION
      "Path: atm.performance.pvcTable.inPriorityQueues.octets.redDropped

       64 bit unsigned wrappable counter."
   ::= {pr1646v2ATMImaPerInPQsEntry 67502080}

pr1646v2ATMImaPerInPQsOctetsCirTx OBJECT-TYPE
   SYNTAX      Counter64
   MAX-ACCESS  read-only
   STATUS      current
   DESCRIPTION
      "Path: atm.performance.pvcTable.inPriorityQueues.octets.cirTx

       64 bit unsigned wrappable counter."
   ::= {pr1646v2ATMImaPerInPQsEntry 67371008}

pr1646v2ATMImaPerInPQsOctetsEirTx OBJECT-TYPE
   SYNTAX      Counter64
   MAX-ACCESS  read-only
   STATUS      current
   DESCRIPTION
      "Path: atm.performance.pvcTable.inPriorityQueues.octets.eirTx

       64 bit unsigned wrappable counter."
   ::= {pr1646v2ATMImaPerInPQsEntry 67436544}

pr1646v2ATMImaPerInPQsOctetsViolateTx OBJECT-TYPE
   SYNTAX      Counter64
   MAX-ACCESS  read-only
   STATUS      current
   DESCRIPTION
      "Path: atm.performance.pvcTable.inPriorityQueues.octets.violateTx

       64 bit unsigned wrappable counter."
   ::= {pr1646v2ATMImaPerInPQsEntry 67633152}

pr1646v2ATMImaPerInPQsOctetsBandwidth15sec OBJECT-TYPE
   SYNTAX      Integer32
   MAX-ACCESS  read-only
   STATUS      current
   DESCRIPTION
      "Path: atm.performance.pvcTable.inPriorityQueues.octets.bandwidth.15sec

       unit name = bps
       formula = 8 * ; 8 /"
   ::= {pr1646v2ATMImaPerInPQsEntry 70386944}

pr1646v2ATMImaPerInPQsOctetsBandwidth30sec OBJECT-TYPE
   SYNTAX      Integer32
   MAX-ACCESS  read-only
   STATUS      current
   DESCRIPTION
      "Path: atm.performance.pvcTable.inPriorityQueues.octets.bandwidth.30sec

       unit name = bps
       formula = 8 * ; 8 /"
   ::= {pr1646v2ATMImaPerInPQsEntry 70388224}

pr1646v2ATMImaPerInPQsOctetsBandwidth1min OBJECT-TYPE
   SYNTAX      Integer32
   MAX-ACCESS  read-only
   STATUS      current
   DESCRIPTION
      "Path: atm.performance.pvcTable.inPriorityQueues.octets.bandwidth.1min

       unit name = bps
       formula = 8 * ; 8 /"
   ::= {pr1646v2ATMImaPerInPQsEntry 70390784}

pr1646v2ATMImaPerInPQsOctetsBandwidth2min OBJECT-TYPE
   SYNTAX      Integer32
   MAX-ACCESS  read-only
   STATUS      current
   DESCRIPTION
      "Path: atm.performance.pvcTable.inPriorityQueues.octets.bandwidth.2min

       unit name = bps
       formula = 8 * ; 8 /"
   ::= {pr1646v2ATMImaPerInPQsEntry 70395904}

pr1646v2ATMImaPerInPQsOctetsBandwidth5min OBJECT-TYPE
   SYNTAX      Integer32
   MAX-ACCESS  read-only
   STATUS      current
   DESCRIPTION
      "Path: atm.performance.pvcTable.inPriorityQueues.octets.bandwidth.5min

       unit name = bps
       formula = 8 * ; 8 /"
   ::= {pr1646v2ATMImaPerInPQsEntry 70411264}

pr1646v2ATMImaPerInPQsH2Performance OBJECT-TYPE
   SYNTAX      SEQUENCE OF Pr1646v2ATMImaPerInPQsH2PerformanceEntry
   MAX-ACCESS  not-accessible
   STATUS      current
   DESCRIPTION
      ""
   ::= {pr1646v2ATMImaPer 100990976}

pr1646v2ATMImaPerInPQsH2PerformanceEntry OBJECT-TYPE
   SYNTAX      Pr1646v2ATMImaPerInPQsH2PerformanceEntry
   MAX-ACCESS  not-accessible
   STATUS      current
   DESCRIPTION
      ""
   INDEX      { pr1646v2ATMImaPerTableIx,
                pr1646v2ATMImaPerInPQsTableIx,
                pr1646v2ATMImaPerInPQsH2PerformanceTableIx }
   ::= {pr1646v2ATMImaPerInPQsH2Performance 1}

Pr1646v2ATMImaPerInPQsH2PerformanceEntry ::=
   SEQUENCE
      {
      pr1646v2ATMImaPerInPQsH2PerformanceTableIx
         TableIndex,
      pr1646v2ATMImaPerInPQsH2PerformanceSysUpTime
         TimeTicks,
      pr1646v2ATMImaPerInPQsH2PerformanceTotPkts
         Counter64,
      pr1646v2ATMImaPerInPQsH2PerformanceDirTxPkts
         Counter64,
      pr1646v2ATMImaPerInPQsH2PerformanceQdPkts
         Counter64,
      pr1646v2ATMImaPerInPQsH2PerformanceDropPkts
         Counter64,
      pr1646v2ATMImaPerInPQsH2PerformanceRDropPkts
         Counter64,
      pr1646v2ATMImaPerInPQsH2PerformanceCirTxPkts
         Counter64,
      pr1646v2ATMImaPerInPQsH2PerformanceEirTxPkts
         Counter64,
      pr1646v2ATMImaPerInPQsH2PerformanceViolTxPkts
         Counter64,
      pr1646v2ATMImaPerInPQsH2PerformanceTotOcts
         Counter64,
      pr1646v2ATMImaPerInPQsH2PerformanceDirTxOcts
         Counter64,
      pr1646v2ATMImaPerInPQsH2PerformanceQdOcts
         Counter64,
      pr1646v2ATMImaPerInPQsH2PerformanceDropOcts
         Counter64,
      pr1646v2ATMImaPerInPQsH2PerformanceRDropOcts
         Counter64,
      pr1646v2ATMImaPerInPQsH2PerformanceCirTxOcts
         Counter64,
      pr1646v2ATMImaPerInPQsH2PerformanceEirTxOcts
         Counter64,
      pr1646v2ATMImaPerInPQsH2PerformanceViolTxOcts
         Counter64,
      pr1646v2ATMImaPerInPQsH2PerformanceBandwidth
         Integer32
      }

pr1646v2ATMImaPerInPQsH2PerformanceTableIx OBJECT-TYPE
   SYNTAX      TableIndex
   MAX-ACCESS  not-accessible
   STATUS      current
   DESCRIPTION
      ""
   ::= {pr1646v2ATMImaPerInPQsH2PerformanceEntry 11}

pr1646v2ATMImaPerInPQsH2PerformanceSysUpTime OBJECT-TYPE
   SYNTAX      TimeTicks
   MAX-ACCESS  read-only
   STATUS      current
   DESCRIPTION
      "Path: atm.performance.pvcTable.inPriorityQueues.h2Performance.sysUpTime

       Time in centi-second."
   ::= {pr1646v2ATMImaPerInPQsH2PerformanceEntry 16777216}

pr1646v2ATMImaPerInPQsH2PerformanceTotPkts OBJECT-TYPE
   SYNTAX      Counter64
   MAX-ACCESS  read-only
   STATUS      current
   DESCRIPTION
      "Path: atm.performance.pvcTable.inPriorityQueues.h2Performance.totalPkts

       64 bit unsigned wrappable counter."
   ::= {pr1646v2ATMImaPerInPQsH2PerformanceEntry 234881024}

pr1646v2ATMImaPerInPQsH2PerformanceDirTxPkts OBJECT-TYPE
   SYNTAX      Counter64
   MAX-ACCESS  read-only
   STATUS      current
   DESCRIPTION
      "Path: atm.performance.pvcTable.inPriorityQueues.h2Performance.directTxPkts

       64 bit unsigned wrappable counter."
   ::= {pr1646v2ATMImaPerInPQsH2PerformanceEntry 33554432}

pr1646v2ATMImaPerInPQsH2PerformanceQdPkts OBJECT-TYPE
   SYNTAX      Counter64
   MAX-ACCESS  read-only
   STATUS      current
   DESCRIPTION
      "Path: atm.performance.pvcTable.inPriorityQueues.h2Performance.queuedPkts

       64 bit unsigned wrappable counter."
   ::= {pr1646v2ATMImaPerInPQsH2PerformanceEntry 50331648}

pr1646v2ATMImaPerInPQsH2PerformanceDropPkts OBJECT-TYPE
   SYNTAX      Counter64
   MAX-ACCESS  read-only
   STATUS      current
   DESCRIPTION
      "Path: atm.performance.pvcTable.inPriorityQueues.h2Performance.droppedPkts

       64 bit unsigned wrappable counter."
   ::= {pr1646v2ATMImaPerInPQsH2PerformanceEntry 67108864}

pr1646v2ATMImaPerInPQsH2PerformanceRDropPkts OBJECT-TYPE
   SYNTAX      Counter64
   MAX-ACCESS  read-only
   STATUS      current
   DESCRIPTION
      "Path: atm.performance.pvcTable.inPriorityQueues.h2Performance.redDroppedPkts

       64 bit unsigned wrappable counter."
   ::= {pr1646v2ATMImaPerInPQsH2PerformanceEntry 201326592}

pr1646v2ATMImaPerInPQsH2PerformanceCirTxPkts OBJECT-TYPE
   SYNTAX      Counter64
   MAX-ACCESS  read-only
   STATUS      current
   DESCRIPTION
      "Path: atm.performance.pvcTable.inPriorityQueues.h2Performance.cirTxPkts

       64 bit unsigned wrappable counter."
   ::= {pr1646v2ATMImaPerInPQsH2PerformanceEntry 83886080}

pr1646v2ATMImaPerInPQsH2PerformanceEirTxPkts OBJECT-TYPE
   SYNTAX      Counter64
   MAX-ACCESS  read-only
   STATUS      current
   DESCRIPTION
      "Path: atm.performance.pvcTable.inPriorityQueues.h2Performance.eirTxPkts

       64 bit unsigned wrappable counter."
   ::= {pr1646v2ATMImaPerInPQsH2PerformanceEntry 100663296}

pr1646v2ATMImaPerInPQsH2PerformanceViolTxPkts OBJECT-TYPE
   SYNTAX      Counter64
   MAX-ACCESS  read-only
   STATUS      current
   DESCRIPTION
      "Path: atm.performance.pvcTable.inPriorityQueues.h2Performance.violateTxPkts

       64 bit unsigned wrappable counter."
   ::= {pr1646v2ATMImaPerInPQsH2PerformanceEntry 301989888}

pr1646v2ATMImaPerInPQsH2PerformanceTotOcts OBJECT-TYPE
   SYNTAX      Counter64
   MAX-ACCESS  read-only
   STATUS      current
   DESCRIPTION
      "Path: atm.performance.pvcTable.inPriorityQueues.h2Performance.totalOctets

       64 bit unsigned wrappable counter."
   ::= {pr1646v2ATMImaPerInPQsH2PerformanceEntry 251658240}

pr1646v2ATMImaPerInPQsH2PerformanceDirTxOcts OBJECT-TYPE
   SYNTAX      Counter64
   MAX-ACCESS  read-only
   STATUS      current
   DESCRIPTION
      "Path: atm.performance.pvcTable.inPriorityQueues.h2Performance.directTxOctets

       64 bit unsigned wrappable counter."
   ::= {pr1646v2ATMImaPerInPQsH2PerformanceEntry 117440512}

pr1646v2ATMImaPerInPQsH2PerformanceQdOcts OBJECT-TYPE
   SYNTAX      Counter64
   MAX-ACCESS  read-only
   STATUS      current
   DESCRIPTION
      "Path: atm.performance.pvcTable.inPriorityQueues.h2Performance.queuedOctets

       64 bit unsigned wrappable counter."
   ::= {pr1646v2ATMImaPerInPQsH2PerformanceEntry 134217728}

pr1646v2ATMImaPerInPQsH2PerformanceDropOcts OBJECT-TYPE
   SYNTAX      Counter64
   MAX-ACCESS  read-only
   STATUS      current
   DESCRIPTION
      "Path: atm.performance.pvcTable.inPriorityQueues.h2Performance.droppedOctets

       64 bit unsigned wrappable counter."
   ::= {pr1646v2ATMImaPerInPQsH2PerformanceEntry 150994944}

pr1646v2ATMImaPerInPQsH2PerformanceRDropOcts OBJECT-TYPE
   SYNTAX      Counter64
   MAX-ACCESS  read-only
   STATUS      current
   DESCRIPTION
      "Path: atm.performance.pvcTable.inPriorityQueues.h2Performance.redDroppedOctets

       64 bit unsigned wrappable counter."
   ::= {pr1646v2ATMImaPerInPQsH2PerformanceEntry 218103808}

pr1646v2ATMImaPerInPQsH2PerformanceCirTxOcts OBJECT-TYPE
   SYNTAX      Counter64
   MAX-ACCESS  read-only
   STATUS      current
   DESCRIPTION
      "Path: atm.performance.pvcTable.inPriorityQueues.h2Performance.cirTxOctets

       64 bit unsigned wrappable counter."
   ::= {pr1646v2ATMImaPerInPQsH2PerformanceEntry 167772160}

pr1646v2ATMImaPerInPQsH2PerformanceEirTxOcts OBJECT-TYPE
   SYNTAX      Counter64
   MAX-ACCESS  read-only
   STATUS      current
   DESCRIPTION
      "Path: atm.performance.pvcTable.inPriorityQueues.h2Performance.eirTxOctets

       64 bit unsigned wrappable counter."
   ::= {pr1646v2ATMImaPerInPQsH2PerformanceEntry 184549376}

pr1646v2ATMImaPerInPQsH2PerformanceViolTxOcts OBJECT-TYPE
   SYNTAX      Counter64
   MAX-ACCESS  read-only
   STATUS      current
   DESCRIPTION
      "Path: atm.performance.pvcTable.inPriorityQueues.h2Performance.violateTxOctets

       64 bit unsigned wrappable counter."
   ::= {pr1646v2ATMImaPerInPQsH2PerformanceEntry 318767104}

pr1646v2ATMImaPerInPQsH2PerformanceBandwidth OBJECT-TYPE
   SYNTAX      Integer32
   MAX-ACCESS  read-only
   STATUS      current
   DESCRIPTION
      "Path: atm.performance.pvcTable.inPriorityQueues.h2Performance.bandwidth

       unit name = bps
       formula = 8 * ; 8 /"
   ::= {pr1646v2ATMImaPerInPQsH2PerformanceEntry 268435456}

pr1646v2ATMImaPerInPQsH24Performance OBJECT-TYPE
   SYNTAX      SEQUENCE OF Pr1646v2ATMImaPerInPQsH24PerformanceEntry
   MAX-ACCESS  not-accessible
   STATUS      current
   DESCRIPTION
      ""
   ::= {pr1646v2ATMImaPer 101056512}

pr1646v2ATMImaPerInPQsH24PerformanceEntry OBJECT-TYPE
   SYNTAX      Pr1646v2ATMImaPerInPQsH24PerformanceEntry
   MAX-ACCESS  not-accessible
   STATUS      current
   DESCRIPTION
      ""
   INDEX      { pr1646v2ATMImaPerTableIx,
                pr1646v2ATMImaPerInPQsTableIx,
                pr1646v2ATMImaPerInPQsH24PerformanceTableIx }
   ::= {pr1646v2ATMImaPerInPQsH24Performance 1}

Pr1646v2ATMImaPerInPQsH24PerformanceEntry ::=
   SEQUENCE
      {
      pr1646v2ATMImaPerInPQsH24PerformanceTableIx
         TableIndex,
      pr1646v2ATMImaPerInPQsH24PerformanceSysUpTime
         TimeTicks,
      pr1646v2ATMImaPerInPQsH24PerformanceTotPkts
         Counter64,
      pr1646v2ATMImaPerInPQsH24PerformanceDirTxPkts
         Counter64,
      pr1646v2ATMImaPerInPQsH24PerformanceQdPkts
         Counter64,
      pr1646v2ATMImaPerInPQsH24PerformanceDropPkts
         Counter64,
      pr1646v2ATMImaPerInPQsH24PerformanceRDropPkts
         Counter64,
      pr1646v2ATMImaPerInPQsH24PerformanceCirTxPkts
         Counter64,
      pr1646v2ATMImaPerInPQsH24PerformanceEirTxPkts
         Counter64,
      pr1646v2ATMImaPerInPQsH24PerformanceViolTxPkts
         Counter64,
      pr1646v2ATMImaPerInPQsH24PerformanceTotOcts
         Counter64,
      pr1646v2ATMImaPerInPQsH24PerformanceDirTxOcts
         Counter64,
      pr1646v2ATMImaPerInPQsH24PerformanceQdOcts
         Counter64,
      pr1646v2ATMImaPerInPQsH24PerformanceDropOcts
         Counter64,
      pr1646v2ATMImaPerInPQsH24PerformanceRDropOcts
         Counter64,
      pr1646v2ATMImaPerInPQsH24PerformanceCirTxOcts
         Counter64,
      pr1646v2ATMImaPerInPQsH24PerformanceEirTxOcts
         Counter64,
      pr1646v2ATMImaPerInPQsH24PerformanceViolTxOcts
         Counter64,
      pr1646v2ATMImaPerInPQsH24PerformanceBandwidth
         Integer32
      }

pr1646v2ATMImaPerInPQsH24PerformanceTableIx OBJECT-TYPE
   SYNTAX      TableIndex
   MAX-ACCESS  not-accessible
   STATUS      current
   DESCRIPTION
      ""
   ::= {pr1646v2ATMImaPerInPQsH24PerformanceEntry 11}

pr1646v2ATMImaPerInPQsH24PerformanceSysUpTime OBJECT-TYPE
   SYNTAX      TimeTicks
   MAX-ACCESS  read-only
   STATUS      current
   DESCRIPTION
      "Path: atm.performance.pvcTable.inPriorityQueues.h24Performance.sysUpTime

       Time in centi-second."
   ::= {pr1646v2ATMImaPerInPQsH24PerformanceEntry 16777216}

pr1646v2ATMImaPerInPQsH24PerformanceTotPkts OBJECT-TYPE
   SYNTAX      Counter64
   MAX-ACCESS  read-only
   STATUS      current
   DESCRIPTION
      "Path: atm.performance.pvcTable.inPriorityQueues.h24Performance.totalPkts

       64 bit unsigned wrappable counter."
   ::= {pr1646v2ATMImaPerInPQsH24PerformanceEntry 234881024}

pr1646v2ATMImaPerInPQsH24PerformanceDirTxPkts OBJECT-TYPE
   SYNTAX      Counter64
   MAX-ACCESS  read-only
   STATUS      current
   DESCRIPTION
      "Path: atm.performance.pvcTable.inPriorityQueues.h24Performance.directTxPkts

       64 bit unsigned wrappable counter."
   ::= {pr1646v2ATMImaPerInPQsH24PerformanceEntry 33554432}

pr1646v2ATMImaPerInPQsH24PerformanceQdPkts OBJECT-TYPE
   SYNTAX      Counter64
   MAX-ACCESS  read-only
   STATUS      current
   DESCRIPTION
      "Path: atm.performance.pvcTable.inPriorityQueues.h24Performance.queuedPkts

       64 bit unsigned wrappable counter."
   ::= {pr1646v2ATMImaPerInPQsH24PerformanceEntry 50331648}

pr1646v2ATMImaPerInPQsH24PerformanceDropPkts OBJECT-TYPE
   SYNTAX      Counter64
   MAX-ACCESS  read-only
   STATUS      current
   DESCRIPTION
      "Path: atm.performance.pvcTable.inPriorityQueues.h24Performance.droppedPkts

       64 bit unsigned wrappable counter."
   ::= {pr1646v2ATMImaPerInPQsH24PerformanceEntry 67108864}

pr1646v2ATMImaPerInPQsH24PerformanceRDropPkts OBJECT-TYPE
   SYNTAX      Counter64
   MAX-ACCESS  read-only
   STATUS      current
   DESCRIPTION
      "Path: atm.performance.pvcTable.inPriorityQueues.h24Performance.redDroppedPkts

       64 bit unsigned wrappable counter."
   ::= {pr1646v2ATMImaPerInPQsH24PerformanceEntry 201326592}

pr1646v2ATMImaPerInPQsH24PerformanceCirTxPkts OBJECT-TYPE
   SYNTAX      Counter64
   MAX-ACCESS  read-only
   STATUS      current
   DESCRIPTION
      "Path: atm.performance.pvcTable.inPriorityQueues.h24Performance.cirTxPkts

       64 bit unsigned wrappable counter."
   ::= {pr1646v2ATMImaPerInPQsH24PerformanceEntry 83886080}

pr1646v2ATMImaPerInPQsH24PerformanceEirTxPkts OBJECT-TYPE
   SYNTAX      Counter64
   MAX-ACCESS  read-only
   STATUS      current
   DESCRIPTION
      "Path: atm.performance.pvcTable.inPriorityQueues.h24Performance.eirTxPkts

       64 bit unsigned wrappable counter."
   ::= {pr1646v2ATMImaPerInPQsH24PerformanceEntry 100663296}

pr1646v2ATMImaPerInPQsH24PerformanceViolTxPkts OBJECT-TYPE
   SYNTAX      Counter64
   MAX-ACCESS  read-only
   STATUS      current
   DESCRIPTION
      "Path: atm.performance.pvcTable.inPriorityQueues.h24Performance.violateTxPkts

       64 bit unsigned wrappable counter."
   ::= {pr1646v2ATMImaPerInPQsH24PerformanceEntry 301989888}

pr1646v2ATMImaPerInPQsH24PerformanceTotOcts OBJECT-TYPE
   SYNTAX      Counter64
   MAX-ACCESS  read-only
   STATUS      current
   DESCRIPTION
      "Path: atm.performance.pvcTable.inPriorityQueues.h24Performance.totalOctets

       64 bit unsigned wrappable counter."
   ::= {pr1646v2ATMImaPerInPQsH24PerformanceEntry 251658240}

pr1646v2ATMImaPerInPQsH24PerformanceDirTxOcts OBJECT-TYPE
   SYNTAX      Counter64
   MAX-ACCESS  read-only
   STATUS      current
   DESCRIPTION
      "Path: atm.performance.pvcTable.inPriorityQueues.h24Performance.directTxOctets

       64 bit unsigned wrappable counter."
   ::= {pr1646v2ATMImaPerInPQsH24PerformanceEntry 117440512}

pr1646v2ATMImaPerInPQsH24PerformanceQdOcts OBJECT-TYPE
   SYNTAX      Counter64
   MAX-ACCESS  read-only
   STATUS      current
   DESCRIPTION
      "Path: atm.performance.pvcTable.inPriorityQueues.h24Performance.queuedOctets

       64 bit unsigned wrappable counter."
   ::= {pr1646v2ATMImaPerInPQsH24PerformanceEntry 134217728}

pr1646v2ATMImaPerInPQsH24PerformanceDropOcts OBJECT-TYPE
   SYNTAX      Counter64
   MAX-ACCESS  read-only
   STATUS      current
   DESCRIPTION
      "Path: atm.performance.pvcTable.inPriorityQueues.h24Performance.droppedOctets

       64 bit unsigned wrappable counter."
   ::= {pr1646v2ATMImaPerInPQsH24PerformanceEntry 150994944}

pr1646v2ATMImaPerInPQsH24PerformanceRDropOcts OBJECT-TYPE
   SYNTAX      Counter64
   MAX-ACCESS  read-only
   STATUS      current
   DESCRIPTION
      "Path: atm.performance.pvcTable.inPriorityQueues.h24Performance.redDroppedOctets

       64 bit unsigned wrappable counter."
   ::= {pr1646v2ATMImaPerInPQsH24PerformanceEntry 218103808}

pr1646v2ATMImaPerInPQsH24PerformanceCirTxOcts OBJECT-TYPE
   SYNTAX      Counter64
   MAX-ACCESS  read-only
   STATUS      current
   DESCRIPTION
      "Path: atm.performance.pvcTable.inPriorityQueues.h24Performance.cirTxOctets

       64 bit unsigned wrappable counter."
   ::= {pr1646v2ATMImaPerInPQsH24PerformanceEntry 167772160}

pr1646v2ATMImaPerInPQsH24PerformanceEirTxOcts OBJECT-TYPE
   SYNTAX      Counter64
   MAX-ACCESS  read-only
   STATUS      current
   DESCRIPTION
      "Path: atm.performance.pvcTable.inPriorityQueues.h24Performance.eirTxOctets

       64 bit unsigned wrappable counter."
   ::= {pr1646v2ATMImaPerInPQsH24PerformanceEntry 184549376}

pr1646v2ATMImaPerInPQsH24PerformanceViolTxOcts OBJECT-TYPE
   SYNTAX      Counter64
   MAX-ACCESS  read-only
   STATUS      current
   DESCRIPTION
      "Path: atm.performance.pvcTable.inPriorityQueues.h24Performance.violateTxOctets

       64 bit unsigned wrappable counter."
   ::= {pr1646v2ATMImaPerInPQsH24PerformanceEntry 318767104}

pr1646v2ATMImaPerInPQsH24PerformanceBandwidth OBJECT-TYPE
   SYNTAX      Integer32
   MAX-ACCESS  read-only
   STATUS      current
   DESCRIPTION
      "Path: atm.performance.pvcTable.inPriorityQueues.h24Performance.bandwidth

       unit name = bps
       formula = 8 * ; 8 /"
   ::= {pr1646v2ATMImaPerInPQsH24PerformanceEntry 268435456}

pr1646v2ATMImaPerInPQsD7Performance OBJECT-TYPE
   SYNTAX      SEQUENCE OF Pr1646v2ATMImaPerInPQsD7PerformanceEntry
   MAX-ACCESS  not-accessible
   STATUS      current
   DESCRIPTION
      ""
   ::= {pr1646v2ATMImaPer 101122048}

pr1646v2ATMImaPerInPQsD7PerformanceEntry OBJECT-TYPE
   SYNTAX      Pr1646v2ATMImaPerInPQsD7PerformanceEntry
   MAX-ACCESS  not-accessible
   STATUS      current
   DESCRIPTION
      ""
   INDEX      { pr1646v2ATMImaPerTableIx,
                pr1646v2ATMImaPerInPQsTableIx,
                pr1646v2ATMImaPerInPQsD7PerformanceTableIx }
   ::= {pr1646v2ATMImaPerInPQsD7Performance 1}

Pr1646v2ATMImaPerInPQsD7PerformanceEntry ::=
   SEQUENCE
      {
      pr1646v2ATMImaPerInPQsD7PerformanceTableIx
         TableIndex,
      pr1646v2ATMImaPerInPQsD7PerformanceSysUpTime
         TimeTicks,
      pr1646v2ATMImaPerInPQsD7PerformanceTotPkts
         Counter64,
      pr1646v2ATMImaPerInPQsD7PerformanceDirTxPkts
         Counter64,
      pr1646v2ATMImaPerInPQsD7PerformanceQdPkts
         Counter64,
      pr1646v2ATMImaPerInPQsD7PerformanceDropPkts
         Counter64,
      pr1646v2ATMImaPerInPQsD7PerformanceRDropPkts
         Counter64,
      pr1646v2ATMImaPerInPQsD7PerformanceCirTxPkts
         Counter64,
      pr1646v2ATMImaPerInPQsD7PerformanceEirTxPkts
         Counter64,
      pr1646v2ATMImaPerInPQsD7PerformanceViolTxPkts
         Counter64,
      pr1646v2ATMImaPerInPQsD7PerformanceTotOcts
         Counter64,
      pr1646v2ATMImaPerInPQsD7PerformanceDirTxOcts
         Counter64,
      pr1646v2ATMImaPerInPQsD7PerformanceQdOcts
         Counter64,
      pr1646v2ATMImaPerInPQsD7PerformanceDropOcts
         Counter64,
      pr1646v2ATMImaPerInPQsD7PerformanceRDropOcts
         Counter64,
      pr1646v2ATMImaPerInPQsD7PerformanceCirTxOcts
         Counter64,
      pr1646v2ATMImaPerInPQsD7PerformanceEirTxOcts
         Counter64,
      pr1646v2ATMImaPerInPQsD7PerformanceViolTxOcts
         Counter64,
      pr1646v2ATMImaPerInPQsD7PerformanceBandwidth
         Integer32
      }

pr1646v2ATMImaPerInPQsD7PerformanceTableIx OBJECT-TYPE
   SYNTAX      TableIndex
   MAX-ACCESS  not-accessible
   STATUS      current
   DESCRIPTION
      ""
   ::= {pr1646v2ATMImaPerInPQsD7PerformanceEntry 11}

pr1646v2ATMImaPerInPQsD7PerformanceSysUpTime OBJECT-TYPE
   SYNTAX      TimeTicks
   MAX-ACCESS  read-only
   STATUS      current
   DESCRIPTION
      "Path: atm.performance.pvcTable.inPriorityQueues.d7Performance.sysUpTime

       Time in centi-second."
   ::= {pr1646v2ATMImaPerInPQsD7PerformanceEntry 16777216}

pr1646v2ATMImaPerInPQsD7PerformanceTotPkts OBJECT-TYPE
   SYNTAX      Counter64
   MAX-ACCESS  read-only
   STATUS      current
   DESCRIPTION
      "Path: atm.performance.pvcTable.inPriorityQueues.d7Performance.totalPkts

       64 bit unsigned wrappable counter."
   ::= {pr1646v2ATMImaPerInPQsD7PerformanceEntry 234881024}

pr1646v2ATMImaPerInPQsD7PerformanceDirTxPkts OBJECT-TYPE
   SYNTAX      Counter64
   MAX-ACCESS  read-only
   STATUS      current
   DESCRIPTION
      "Path: atm.performance.pvcTable.inPriorityQueues.d7Performance.directTxPkts

       64 bit unsigned wrappable counter."
   ::= {pr1646v2ATMImaPerInPQsD7PerformanceEntry 33554432}

pr1646v2ATMImaPerInPQsD7PerformanceQdPkts OBJECT-TYPE
   SYNTAX      Counter64
   MAX-ACCESS  read-only
   STATUS      current
   DESCRIPTION
      "Path: atm.performance.pvcTable.inPriorityQueues.d7Performance.queuedPkts

       64 bit unsigned wrappable counter."
   ::= {pr1646v2ATMImaPerInPQsD7PerformanceEntry 50331648}

pr1646v2ATMImaPerInPQsD7PerformanceDropPkts OBJECT-TYPE
   SYNTAX      Counter64
   MAX-ACCESS  read-only
   STATUS      current
   DESCRIPTION
      "Path: atm.performance.pvcTable.inPriorityQueues.d7Performance.droppedPkts

       64 bit unsigned wrappable counter."
   ::= {pr1646v2ATMImaPerInPQsD7PerformanceEntry 67108864}

pr1646v2ATMImaPerInPQsD7PerformanceRDropPkts OBJECT-TYPE
   SYNTAX      Counter64
   MAX-ACCESS  read-only
   STATUS      current
   DESCRIPTION
      "Path: atm.performance.pvcTable.inPriorityQueues.d7Performance.redDroppedPkts

       64 bit unsigned wrappable counter."
   ::= {pr1646v2ATMImaPerInPQsD7PerformanceEntry 201326592}

pr1646v2ATMImaPerInPQsD7PerformanceCirTxPkts OBJECT-TYPE
   SYNTAX      Counter64
   MAX-ACCESS  read-only
   STATUS      current
   DESCRIPTION
      "Path: atm.performance.pvcTable.inPriorityQueues.d7Performance.cirTxPkts

       64 bit unsigned wrappable counter."
   ::= {pr1646v2ATMImaPerInPQsD7PerformanceEntry 83886080}

pr1646v2ATMImaPerInPQsD7PerformanceEirTxPkts OBJECT-TYPE
   SYNTAX      Counter64
   MAX-ACCESS  read-only
   STATUS      current
   DESCRIPTION
      "Path: atm.performance.pvcTable.inPriorityQueues.d7Performance.eirTxPkts

       64 bit unsigned wrappable counter."
   ::= {pr1646v2ATMImaPerInPQsD7PerformanceEntry 100663296}

pr1646v2ATMImaPerInPQsD7PerformanceViolTxPkts OBJECT-TYPE
   SYNTAX      Counter64
   MAX-ACCESS  read-only
   STATUS      current
   DESCRIPTION
      "Path: atm.performance.pvcTable.inPriorityQueues.d7Performance.violateTxPkts

       64 bit unsigned wrappable counter."
   ::= {pr1646v2ATMImaPerInPQsD7PerformanceEntry 301989888}

pr1646v2ATMImaPerInPQsD7PerformanceTotOcts OBJECT-TYPE
   SYNTAX      Counter64
   MAX-ACCESS  read-only
   STATUS      current
   DESCRIPTION
      "Path: atm.performance.pvcTable.inPriorityQueues.d7Performance.totalOctets

       64 bit unsigned wrappable counter."
   ::= {pr1646v2ATMImaPerInPQsD7PerformanceEntry 251658240}

pr1646v2ATMImaPerInPQsD7PerformanceDirTxOcts OBJECT-TYPE
   SYNTAX      Counter64
   MAX-ACCESS  read-only
   STATUS      current
   DESCRIPTION
      "Path: atm.performance.pvcTable.inPriorityQueues.d7Performance.directTxOctets

       64 bit unsigned wrappable counter."
   ::= {pr1646v2ATMImaPerInPQsD7PerformanceEntry 117440512}

pr1646v2ATMImaPerInPQsD7PerformanceQdOcts OBJECT-TYPE
   SYNTAX      Counter64
   MAX-ACCESS  read-only
   STATUS      current
   DESCRIPTION
      "Path: atm.performance.pvcTable.inPriorityQueues.d7Performance.queuedOctets

       64 bit unsigned wrappable counter."
   ::= {pr1646v2ATMImaPerInPQsD7PerformanceEntry 134217728}

pr1646v2ATMImaPerInPQsD7PerformanceDropOcts OBJECT-TYPE
   SYNTAX      Counter64
   MAX-ACCESS  read-only
   STATUS      current
   DESCRIPTION
      "Path: atm.performance.pvcTable.inPriorityQueues.d7Performance.droppedOctets

       64 bit unsigned wrappable counter."
   ::= {pr1646v2ATMImaPerInPQsD7PerformanceEntry 150994944}

pr1646v2ATMImaPerInPQsD7PerformanceRDropOcts OBJECT-TYPE
   SYNTAX      Counter64
   MAX-ACCESS  read-only
   STATUS      current
   DESCRIPTION
      "Path: atm.performance.pvcTable.inPriorityQueues.d7Performance.redDroppedOctets

       64 bit unsigned wrappable counter."
   ::= {pr1646v2ATMImaPerInPQsD7PerformanceEntry 218103808}

pr1646v2ATMImaPerInPQsD7PerformanceCirTxOcts OBJECT-TYPE
   SYNTAX      Counter64
   MAX-ACCESS  read-only
   STATUS      current
   DESCRIPTION
      "Path: atm.performance.pvcTable.inPriorityQueues.d7Performance.cirTxOctets

       64 bit unsigned wrappable counter."
   ::= {pr1646v2ATMImaPerInPQsD7PerformanceEntry 167772160}

pr1646v2ATMImaPerInPQsD7PerformanceEirTxOcts OBJECT-TYPE
   SYNTAX      Counter64
   MAX-ACCESS  read-only
   STATUS      current
   DESCRIPTION
      "Path: atm.performance.pvcTable.inPriorityQueues.d7Performance.eirTxOctets

       64 bit unsigned wrappable counter."
   ::= {pr1646v2ATMImaPerInPQsD7PerformanceEntry 184549376}

pr1646v2ATMImaPerInPQsD7PerformanceViolTxOcts OBJECT-TYPE
   SYNTAX      Counter64
   MAX-ACCESS  read-only
   STATUS      current
   DESCRIPTION
      "Path: atm.performance.pvcTable.inPriorityQueues.d7Performance.violateTxOctets

       64 bit unsigned wrappable counter."
   ::= {pr1646v2ATMImaPerInPQsD7PerformanceEntry 318767104}

pr1646v2ATMImaPerInPQsD7PerformanceBandwidth OBJECT-TYPE
   SYNTAX      Integer32
   MAX-ACCESS  read-only
   STATUS      current
   DESCRIPTION
      "Path: atm.performance.pvcTable.inPriorityQueues.d7Performance.bandwidth

       unit name = bps
       formula = 8 * ; 8 /"
   ::= {pr1646v2ATMImaPerInPQsD7PerformanceEntry 268435456}

pr1646v2ATMImaPerOutPQs OBJECT-TYPE
   SYNTAX      SEQUENCE OF Pr1646v2ATMImaPerOutPQsEntry
   MAX-ACCESS  not-accessible
   STATUS      current
   DESCRIPTION
      ""
   ::= {pr1646v2ATMImaPer 83886080}

pr1646v2ATMImaPerOutPQsEntry OBJECT-TYPE
   SYNTAX      Pr1646v2ATMImaPerOutPQsEntry
   MAX-ACCESS  not-accessible
   STATUS      current
   DESCRIPTION
      ""
   INDEX      { pr1646v2ATMImaPerTableIx,
                pr1646v2ATMImaPerOutPQsTableIx }
   ::= {pr1646v2ATMImaPerOutPQs 1}

Pr1646v2ATMImaPerOutPQsEntry ::=
   SEQUENCE
      {
      pr1646v2ATMImaPerOutPQsTableIx
         TableIndex,
      pr1646v2ATMImaPerOutPQsName
         INTEGER,
      pr1646v2ATMImaPerOutPQsLength
         Integer32,
      pr1646v2ATMImaPerOutPQsOctetLength
         Integer32,
      pr1646v2ATMImaPerOutPQsRedLength
         Integer32,
      pr1646v2ATMImaPerOutPQsPacketsTotal
         Counter64,
      pr1646v2ATMImaPerOutPQsPacketsDirectTx
         Counter64,
      pr1646v2ATMImaPerOutPQsPacketsQueued
         Counter64,
      pr1646v2ATMImaPerOutPQsPacketsDropped
         Counter64,
      pr1646v2ATMImaPerOutPQsPacketsRedDropped
         Counter64,
      pr1646v2ATMImaPerOutPQsPacketsCirTx
         Counter64,
      pr1646v2ATMImaPerOutPQsPacketsEirTx
         Counter64,
      pr1646v2ATMImaPerOutPQsPacketsViolateTx
         Counter64,
      pr1646v2ATMImaPerOutPQsOctetsTotal
         Counter64,
      pr1646v2ATMImaPerOutPQsOctetsDirectTx
         Counter64,
      pr1646v2ATMImaPerOutPQsOctetsQueued
         Counter64,
      pr1646v2ATMImaPerOutPQsOctetsDropped
         Counter64,
      pr1646v2ATMImaPerOutPQsOctetsRedDropped
         Counter64,
      pr1646v2ATMImaPerOutPQsOctetsCirTx
         Counter64,
      pr1646v2ATMImaPerOutPQsOctetsEirTx
         Counter64,
      pr1646v2ATMImaPerOutPQsOctetsViolateTx
         Counter64,
      pr1646v2ATMImaPerOutPQsOctetsBandwidth15sec
         Integer32,
      pr1646v2ATMImaPerOutPQsOctetsBandwidth30sec
         Integer32,
      pr1646v2ATMImaPerOutPQsOctetsBandwidth1min
         Integer32,
      pr1646v2ATMImaPerOutPQsOctetsBandwidth2min
         Integer32,
      pr1646v2ATMImaPerOutPQsOctetsBandwidth5min
         Integer32
      }

pr1646v2ATMImaPerOutPQsTableIx OBJECT-TYPE
   SYNTAX      TableIndex
   MAX-ACCESS  not-accessible
   STATUS      current
   DESCRIPTION
      ""
   ::= {pr1646v2ATMImaPerOutPQsEntry 11}

pr1646v2ATMImaPerOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMImaPerOutPQsEntry 16777216}

pr1646v2ATMImaPerOutPQsLength OBJECT-TYPE
   SYNTAX      Integer32
   MAX-ACCESS  read-only
   STATUS      current
   DESCRIPTION
      "Path: atm.performance.pvcTable.outPriorityQueues.length"
   ::= {pr1646v2ATMImaPerOutPQsEntry 33554432}

pr1646v2ATMImaPerOutPQsOctetLength OBJECT-TYPE
   SYNTAX      Integer32
   MAX-ACCESS  read-only
   STATUS      current
   DESCRIPTION
      "Path: atm.performance.pvcTable.outPriorityQueues.octetLength"
   ::= {pr1646v2ATMImaPerOutPQsEntry 150994944}

pr1646v2ATMImaPerOutPQsRedLength OBJECT-TYPE
   SYNTAX      Integer32
   MAX-ACCESS  read-only
   STATUS      current
   DESCRIPTION
      "Path: atm.performance.pvcTable.outPriorityQueues.redLength"
   ::= {pr1646v2ATMImaPerOutPQsEntry 134217728}

pr1646v2ATMImaPerOutPQsPacketsTotal OBJECT-TYPE
   SYNTAX      Counter64
   MAX-ACCESS  read-only
   STATUS      current
   DESCRIPTION
      "Path: atm.performance.pvcTable.outPriorityQueues.packets.total

       64 bit unsigned wrappable counter."
   ::= {pr1646v2ATMImaPerOutPQsEntry 50790400}

pr1646v2ATMImaPerOutPQsPacketsDirectTx OBJECT-TYPE
   SYNTAX      Counter64
   MAX-ACCESS  read-only
   STATUS      current
   DESCRIPTION
      "Path: atm.performance.pvcTable.outPriorityQueues.packets.directTx

       64 bit unsigned wrappable counter."
   ::= {pr1646v2ATMImaPerOutPQsEntry 50397184}

pr1646v2ATMImaPerOutPQsPacketsQueued OBJECT-TYPE
   SYNTAX      Counter64
   MAX-ACCESS  read-only
   STATUS      current
   DESCRIPTION
      "Path: atm.performance.pvcTable.outPriorityQueues.packets.queued

       64 bit unsigned wrappable counter."
   ::= {pr1646v2ATMImaPerOutPQsEntry 50462720}

pr1646v2ATMImaPerOutPQsPacketsDropped OBJECT-TYPE
   SYNTAX      Counter64
   MAX-ACCESS  read-only
   STATUS      current
   DESCRIPTION
      "Path: atm.performance.pvcTable.outPriorityQueues.packets.dropped

       64 bit unsigned wrappable counter."
   ::= {pr1646v2ATMImaPerOutPQsEntry 50528256}

pr1646v2ATMImaPerOutPQsPacketsRedDropped OBJECT-TYPE
   SYNTAX      Counter64
   MAX-ACCESS  read-only
   STATUS      current
   DESCRIPTION
      "Path: atm.performance.pvcTable.outPriorityQueues.packets.redDropped

       64 bit unsigned wrappable counter."
   ::= {pr1646v2ATMImaPerOutPQsEntry 50724864}

pr1646v2ATMImaPerOutPQsPacketsCirTx OBJECT-TYPE
   SYNTAX      Counter64
   MAX-ACCESS  read-only
   STATUS      current
   DESCRIPTION
      "Path: atm.performance.pvcTable.outPriorityQueues.packets.cirTx

       64 bit unsigned wrappable counter."
   ::= {pr1646v2ATMImaPerOutPQsEntry 50593792}

pr1646v2ATMImaPerOutPQsPacketsEirTx OBJECT-TYPE
   SYNTAX      Counter64
   MAX-ACCESS  read-only
   STATUS      current
   DESCRIPTION
      "Path: atm.performance.pvcTable.outPriorityQueues.packets.eirTx

       64 bit unsigned wrappable counter."
   ::= {pr1646v2ATMImaPerOutPQsEntry 50659328}

pr1646v2ATMImaPerOutPQsPacketsViolateTx OBJECT-TYPE
   SYNTAX      Counter64
   MAX-ACCESS  read-only
   STATUS      current
   DESCRIPTION
      "Path: atm.performance.pvcTable.outPriorityQueues.packets.violateTx

       64 bit unsigned wrappable counter."
   ::= {pr1646v2ATMImaPerOutPQsEntry 50855936}

pr1646v2ATMImaPerOutPQsOctetsTotal OBJECT-TYPE
   SYNTAX      Counter64
   MAX-ACCESS  read-only
   STATUS      current
   DESCRIPTION
      "Path: atm.performance.pvcTable.outPriorityQueues.octets.total

       64 bit unsigned wrappable counter."
   ::= {pr1646v2ATMImaPerOutPQsEntry 67567616}

pr1646v2ATMImaPerOutPQsOctetsDirectTx OBJECT-TYPE
   SYNTAX      Counter64
   MAX-ACCESS  read-only
   STATUS      current
   DESCRIPTION
      "Path: atm.performance.pvcTable.outPriorityQueues.octets.directTx

       64 bit unsigned wrappable counter."
   ::= {pr1646v2ATMImaPerOutPQsEntry 67174400}

pr1646v2ATMImaPerOutPQsOctetsQueued OBJECT-TYPE
   SYNTAX      Counter64
   MAX-ACCESS  read-only
   STATUS      current
   DESCRIPTION
      "Path: atm.performance.pvcTable.outPriorityQueues.octets.queued

       64 bit unsigned wrappable counter."
   ::= {pr1646v2ATMImaPerOutPQsEntry 67239936}

pr1646v2ATMImaPerOutPQsOctetsDropped OBJECT-TYPE
   SYNTAX      Counter64
   MAX-ACCESS  read-only
   STATUS      current
   DESCRIPTION
      "Path: atm.performance.pvcTable.outPriorityQueues.octets.dropped

       64 bit unsigned wrappable counter."
   ::= {pr1646v2ATMImaPerOutPQsEntry 67305472}

pr1646v2ATMImaPerOutPQsOctetsRedDropped OBJECT-TYPE
   SYNTAX      Counter64
   MAX-ACCESS  read-only
   STATUS      current
   DESCRIPTION
      "Path: atm.performance.pvcTable.outPriorityQueues.octets.redDropped

       64 bit unsigned wrappable counter."
   ::= {pr1646v2ATMImaPerOutPQsEntry 67502080}

pr1646v2ATMImaPerOutPQsOctetsCirTx OBJECT-TYPE
   SYNTAX      Counter64
   MAX-ACCESS  read-only
   STATUS      current
   DESCRIPTION
      "Path: atm.performance.pvcTable.outPriorityQueues.octets.cirTx

       64 bit unsigned wrappable counter."
   ::= {pr1646v2ATMImaPerOutPQsEntry 67371008}

pr1646v2ATMImaPerOutPQsOctetsEirTx OBJECT-TYPE
   SYNTAX      Counter64
   MAX-ACCESS  read-only
   STATUS      current
   DESCRIPTION
      "Path: atm.performance.pvcTable.outPriorityQueues.octets.eirTx

       64 bit unsigned wrappable counter."
   ::= {pr1646v2ATMImaPerOutPQsEntry 67436544}

pr1646v2ATMImaPerOutPQsOctetsViolateTx OBJECT-TYPE
   SYNTAX      Counter64
   MAX-ACCESS  read-only
   STATUS      current
   DESCRIPTION
      "Path: atm.performance.pvcTable.outPriorityQueues.octets.violateTx

       64 bit unsigned wrappable counter."
   ::= {pr1646v2ATMImaPerOutPQsEntry 67633152}

pr1646v2ATMImaPerOutPQsOctetsBandwidth15sec OBJECT-TYPE
   SYNTAX      Integer32
   MAX-ACCESS  read-only
   STATUS      current
   DESCRIPTION
      "Path: atm.performance.pvcTable.outPriorityQueues.octets.bandwidth.15sec

       unit name = bps
       formula = 8 * ; 8 /"
   ::= {pr1646v2ATMImaPerOutPQsEntry 70386944}

pr1646v2ATMImaPerOutPQsOctetsBandwidth30sec OBJECT-TYPE
   SYNTAX      Integer32
   MAX-ACCESS  read-only
   STATUS      current
   DESCRIPTION
      "Path: atm.performance.pvcTable.outPriorityQueues.octets.bandwidth.30sec

       unit name = bps
       formula = 8 * ; 8 /"
   ::= {pr1646v2ATMImaPerOutPQsEntry 70388224}

pr1646v2ATMImaPerOutPQsOctetsBandwidth1min OBJECT-TYPE
   SYNTAX      Integer32
   MAX-ACCESS  read-only
   STATUS      current
   DESCRIPTION
      "Path: atm.performance.pvcTable.outPriorityQueues.octets.bandwidth.1min

       unit name = bps
       formula = 8 * ; 8 /"
   ::= {pr1646v2ATMImaPerOutPQsEntry 70390784}

pr1646v2ATMImaPerOutPQsOctetsBandwidth2min OBJECT-TYPE
   SYNTAX      Integer32
   MAX-ACCESS  read-only
   STATUS      current
   DESCRIPTION
      "Path: atm.performance.pvcTable.outPriorityQueues.octets.bandwidth.2min

       unit name = bps
       formula = 8 * ; 8 /"
   ::= {pr1646v2ATMImaPerOutPQsEntry 70395904}

pr1646v2ATMImaPerOutPQsOctetsBandwidth5min OBJECT-TYPE
   SYNTAX      Integer32
   MAX-ACCESS  read-only
   STATUS      current
   DESCRIPTION
      "Path: atm.performance.pvcTable.outPriorityQueues.octets.bandwidth.5min

       unit name = bps
       formula = 8 * ; 8 /"
   ::= {pr1646v2ATMImaPerOutPQsEntry 70411264}

pr1646v2ATMImaPerOutPQsH2Performance OBJECT-TYPE
   SYNTAX      SEQUENCE OF Pr1646v2ATMImaPerOutPQsH2PerformanceEntry
   MAX-ACCESS  not-accessible
   STATUS      current
   DESCRIPTION
      ""
   ::= {pr1646v2ATMImaPer 84213760}

pr1646v2ATMImaPerOutPQsH2PerformanceEntry OBJECT-TYPE
   SYNTAX      Pr1646v2ATMImaPerOutPQsH2PerformanceEntry
   MAX-ACCESS  not-accessible
   STATUS      current
   DESCRIPTION
      ""
   INDEX      { pr1646v2ATMImaPerTableIx,
                pr1646v2ATMImaPerOutPQsTableIx,
                pr1646v2ATMImaPerOutPQsH2PerformanceTableIx }
   ::= {pr1646v2ATMImaPerOutPQsH2Performance 1}

Pr1646v2ATMImaPerOutPQsH2PerformanceEntry ::=
   SEQUENCE
      {
      pr1646v2ATMImaPerOutPQsH2PerformanceTableIx
         TableIndex,
      pr1646v2ATMImaPerOutPQsH2PerformanceSysUpTime
         TimeTicks,
      pr1646v2ATMImaPerOutPQsH2PerformanceTotPkts
         Counter64,
      pr1646v2ATMImaPerOutPQsH2PerformanceDirTxPkts
         Counter64,
      pr1646v2ATMImaPerOutPQsH2PerformanceQdPkts
         Counter64,
      pr1646v2ATMImaPerOutPQsH2PerformanceDropPkts
         Counter64,
      pr1646v2ATMImaPerOutPQsH2PerformanceRDropPkts
         Counter64,
      pr1646v2ATMImaPerOutPQsH2PerformanceCirTxPkts
         Counter64,
      pr1646v2ATMImaPerOutPQsH2PerformanceEirTxPkts
         Counter64,
      pr1646v2ATMImaPerOutPQsH2PerformanceViolTxPkts
         Counter64,
      pr1646v2ATMImaPerOutPQsH2PerformanceTotOcts
         Counter64,
      pr1646v2ATMImaPerOutPQsH2PerformanceDirTxOcts
         Counter64,
      pr1646v2ATMImaPerOutPQsH2PerformanceQdOcts
         Counter64,
      pr1646v2ATMImaPerOutPQsH2PerformanceDropOcts
         Counter64,
      pr1646v2ATMImaPerOutPQsH2PerformanceRDropOcts
         Counter64,
      pr1646v2ATMImaPerOutPQsH2PerformanceCirTxOcts
         Counter64,
      pr1646v2ATMImaPerOutPQsH2PerformanceEirTxOcts
         Counter64,
      pr1646v2ATMImaPerOutPQsH2PerformanceViolTxOcts
         Counter64,
      pr1646v2ATMImaPerOutPQsH2PerformanceBandwidth
         Integer32
      }

pr1646v2ATMImaPerOutPQsH2PerformanceTableIx OBJECT-TYPE
   SYNTAX      TableIndex
   MAX-ACCESS  not-accessible
   STATUS      current
   DESCRIPTION
      ""
   ::= {pr1646v2ATMImaPerOutPQsH2PerformanceEntry 11}

pr1646v2ATMImaPerOutPQsH2PerformanceSysUpTime OBJECT-TYPE
   SYNTAX      TimeTicks
   MAX-ACCESS  read-only
   STATUS      current
   DESCRIPTION
      "Path: atm.performance.pvcTable.outPriorityQueues.h2Performance.sysUpTime

       Time in centi-second."
   ::= {pr1646v2ATMImaPerOutPQsH2PerformanceEntry 16777216}

pr1646v2ATMImaPerOutPQsH2PerformanceTotPkts OBJECT-TYPE
   SYNTAX      Counter64
   MAX-ACCESS  read-only
   STATUS      current
   DESCRIPTION
      "Path: atm.performance.pvcTable.outPriorityQueues.h2Performance.totalPkts

       64 bit unsigned wrappable counter."
   ::= {pr1646v2ATMImaPerOutPQsH2PerformanceEntry 234881024}

pr1646v2ATMImaPerOutPQsH2PerformanceDirTxPkts OBJECT-TYPE
   SYNTAX      Counter64
   MAX-ACCESS  read-only
   STATUS      current
   DESCRIPTION
      "Path: atm.performance.pvcTable.outPriorityQueues.h2Performance.directTxPkts

       64 bit unsigned wrappable counter."
   ::= {pr1646v2ATMImaPerOutPQsH2PerformanceEntry 33554432}

pr1646v2ATMImaPerOutPQsH2PerformanceQdPkts OBJECT-TYPE
   SYNTAX      Counter64
   MAX-ACCESS  read-only
   STATUS      current
   DESCRIPTION
      "Path: atm.performance.pvcTable.outPriorityQueues.h2Performance.queuedPkts

       64 bit unsigned wrappable counter."
   ::= {pr1646v2ATMImaPerOutPQsH2PerformanceEntry 50331648}

pr1646v2ATMImaPerOutPQsH2PerformanceDropPkts OBJECT-TYPE
   SYNTAX      Counter64
   MAX-ACCESS  read-only
   STATUS      current
   DESCRIPTION
      "Path: atm.performance.pvcTable.outPriorityQueues.h2Performance.droppedPkts

       64 bit unsigned wrappable counter."
   ::= {pr1646v2ATMImaPerOutPQsH2PerformanceEntry 67108864}

pr1646v2ATMImaPerOutPQsH2PerformanceRDropPkts OBJECT-TYPE
   SYNTAX      Counter64
   MAX-ACCESS  read-only
   STATUS      current
   DESCRIPTION
      "Path: atm.performance.pvcTable.outPriorityQueues.h2Performance.redDroppedPkts

       64 bit unsigned wrappable counter."
   ::= {pr1646v2ATMImaPerOutPQsH2PerformanceEntry 201326592}

pr1646v2ATMImaPerOutPQsH2PerformanceCirTxPkts OBJECT-TYPE
   SYNTAX      Counter64
   MAX-ACCESS  read-only
   STATUS      current
   DESCRIPTION
      "Path: atm.performance.pvcTable.outPriorityQueues.h2Performance.cirTxPkts

       64 bit unsigned wrappable counter."
   ::= {pr1646v2ATMImaPerOutPQsH2PerformanceEntry 83886080}

pr1646v2ATMImaPerOutPQsH2PerformanceEirTxPkts OBJECT-TYPE
   SYNTAX      Counter64
   MAX-ACCESS  read-only
   STATUS      current
   DESCRIPTION
      "Path: atm.performance.pvcTable.outPriorityQueues.h2Performance.eirTxPkts

       64 bit unsigned wrappable counter."
   ::= {pr1646v2ATMImaPerOutPQsH2PerformanceEntry 100663296}

pr1646v2ATMImaPerOutPQsH2PerformanceViolTxPkts OBJECT-TYPE
   SYNTAX      Counter64
   MAX-ACCESS  read-only
   STATUS      current
   DESCRIPTION
      "Path: atm.performance.pvcTable.outPriorityQueues.h2Performance.violateTxPkts

       64 bit unsigned wrappable counter."
   ::= {pr1646v2ATMImaPerOutPQsH2PerformanceEntry 301989888}

pr1646v2ATMImaPerOutPQsH2PerformanceTotOcts OBJECT-TYPE
   SYNTAX      Counter64
   MAX-ACCESS  read-only
   STATUS      current
   DESCRIPTION
      "Path: atm.performance.pvcTable.outPriorityQueues.h2Performance.totalOctets

       64 bit unsigned wrappable counter."
   ::= {pr1646v2ATMImaPerOutPQsH2PerformanceEntry 251658240}

pr1646v2ATMImaPerOutPQsH2PerformanceDirTxOcts OBJECT-TYPE
   SYNTAX      Counter64
   MAX-ACCESS  read-only
   STATUS      current
   DESCRIPTION
      "Path: atm.performance.pvcTable.outPriorityQueues.h2Performance.directTxOctets

       64 bit unsigned wrappable counter."
   ::= {pr1646v2ATMImaPerOutPQsH2PerformanceEntry 117440512}

pr1646v2ATMImaPerOutPQsH2PerformanceQdOcts OBJECT-TYPE
   SYNTAX      Counter64
   MAX-ACCESS  read-only
   STATUS      current
   DESCRIPTION
      "Path: atm.performance.pvcTable.outPriorityQueues.h2Performance.queuedOctets

       64 bit unsigned wrappable counter."
   ::= {pr1646v2ATMImaPerOutPQsH2PerformanceEntry 134217728}

pr1646v2ATMImaPerOutPQsH2PerformanceDropOcts OBJECT-TYPE
   SYNTAX      Counter64
   MAX-ACCESS  read-only
   STATUS      current
   DESCRIPTION
      "Path: atm.performance.pvcTable.outPriorityQueues.h2Performance.droppedOctets

       64 bit unsigned wrappable counter."
   ::= {pr1646v2ATMImaPerOutPQsH2PerformanceEntry 150994944}

pr1646v2ATMImaPerOutPQsH2PerformanceRDropOcts OBJECT-TYPE
   SYNTAX      Counter64
   MAX-ACCESS  read-only
   STATUS      current
   DESCRIPTION
      "Path: atm.performance.pvcTable.outPriorityQueues.h2Performance.redDroppedOctets

       64 bit unsigned wrappable counter."
   ::= {pr1646v2ATMImaPerOutPQsH2PerformanceEntry 218103808}

pr1646v2ATMImaPerOutPQsH2PerformanceCirTxOcts OBJECT-TYPE
   SYNTAX      Counter64
   MAX-ACCESS  read-only
   STATUS      current
   DESCRIPTION
      "Path: atm.performance.pvcTable.outPriorityQueues.h2Performance.cirTxOctets

       64 bit unsigned wrappable counter."
   ::= {pr1646v2ATMImaPerOutPQsH2PerformanceEntry 167772160}

pr1646v2ATMImaPerOutPQsH2PerformanceEirTxOcts OBJECT-TYPE
   SYNTAX      Counter64
   MAX-ACCESS  read-only
   STATUS      current
   DESCRIPTION
      "Path: atm.performance.pvcTable.outPriorityQueues.h2Performance.eirTxOctets

       64 bit unsigned wrappable counter."
   ::= {pr1646v2ATMImaPerOutPQsH2PerformanceEntry 184549376}

pr1646v2ATMImaPerOutPQsH2PerformanceViolTxOcts OBJECT-TYPE
   SYNTAX      Counter64
   MAX-ACCESS  read-only
   STATUS      current
   DESCRIPTION
      "Path: atm.performance.pvcTable.outPriorityQueues.h2Performance.violateTxOctets

       64 bit unsigned wrappable counter."
   ::= {pr1646v2ATMImaPerOutPQsH2PerformanceEntry 318767104}

pr1646v2ATMImaPerOutPQsH2PerformanceBandwidth OBJECT-TYPE
   SYNTAX      Integer32
   MAX-ACCESS  read-only
   STATUS      current
   DESCRIPTION
      "Path: atm.performance.pvcTable.outPriorityQueues.h2Performance.bandwidth

       unit name = bps
       formula = 8 * ; 8 /"
   ::= {pr1646v2ATMImaPerOutPQsH2PerformanceEntry 268435456}

pr1646v2ATMImaPerOutPQsH24Performance OBJECT-TYPE
   SYNTAX      SEQUENCE OF Pr1646v2ATMImaPerOutPQsH24PerformanceEntry
   MAX-ACCESS  not-accessible
   STATUS      current
   DESCRIPTION
      ""
   ::= {pr1646v2ATMImaPer 84279296}

pr1646v2ATMImaPerOutPQsH24PerformanceEntry OBJECT-TYPE
   SYNTAX      Pr1646v2ATMImaPerOutPQsH24PerformanceEntry
   MAX-ACCESS  not-accessible
   STATUS      current
   DESCRIPTION
      ""
   INDEX      { pr1646v2ATMImaPerTableIx,
                pr1646v2ATMImaPerOutPQsTableIx,
                pr1646v2ATMImaPerOutPQsH24PerformanceTableIx }
   ::= {pr1646v2ATMImaPerOutPQsH24Performance 1}

Pr1646v2ATMImaPerOutPQsH24PerformanceEntry ::=
   SEQUENCE
      {
      pr1646v2ATMImaPerOutPQsH24PerformanceTableIx
         TableIndex,
      pr1646v2ATMImaPerOutPQsH24PerformanceSysUpTime
         TimeTicks,
      pr1646v2ATMImaPerOutPQsH24PerformanceTotPkts
         Counter64,
      pr1646v2ATMImaPerOutPQsH24PerformanceDirTxPkts
         Counter64,
      pr1646v2ATMImaPerOutPQsH24PerformanceQdPkts
         Counter64,
      pr1646v2ATMImaPerOutPQsH24PerformanceDropPkts
         Counter64,
      pr1646v2ATMImaPerOutPQsH24PerformanceRDropPkts
         Counter64,
      pr1646v2ATMImaPerOutPQsH24PerformanceCirTxPkts
         Counter64,
      pr1646v2ATMImaPerOutPQsH24PerformanceEirTxPkts
         Counter64,
      pr1646v2ATMImaPerOutPQsH24PerformanceViolTxPkts
         Counter64,
      pr1646v2ATMImaPerOutPQsH24PerformanceTotOcts
         Counter64,
      pr1646v2ATMImaPerOutPQsH24PerformanceDirTxOcts
         Counter64,
      pr1646v2ATMImaPerOutPQsH24PerformanceQdOcts
         Counter64,
      pr1646v2ATMImaPerOutPQsH24PerformanceDropOcts
         Counter64,
      pr1646v2ATMImaPerOutPQsH24PerformanceRDropOcts
         Counter64,
      pr1646v2ATMImaPerOutPQsH24PerformanceCirTxOcts
         Counter64,
      pr1646v2ATMImaPerOutPQsH24PerformanceEirTxOcts
         Counter64,
      pr1646v2ATMImaPerOutPQsH24PerformanceViolTxOcts
         Counter64,
      pr1646v2ATMImaPerOutPQsH24PerformanceBandwidth
         Integer32
      }

pr1646v2ATMImaPerOutPQsH24PerformanceTableIx OBJECT-TYPE
   SYNTAX      TableIndex
   MAX-ACCESS  not-accessible
   STATUS      current
   DESCRIPTION
      ""
   ::= {pr1646v2ATMImaPerOutPQsH24PerformanceEntry 11}

pr1646v2ATMImaPerOutPQsH24PerformanceSysUpTime OBJECT-TYPE
   SYNTAX      TimeTicks
   MAX-ACCESS  read-only
   STATUS      current
   DESCRIPTION
      "Path: atm.performance.pvcTable.outPriorityQueues.h24Performance.sysUpTime

       Time in centi-second."
   ::= {pr1646v2ATMImaPerOutPQsH24PerformanceEntry 16777216}

pr1646v2ATMImaPerOutPQsH24PerformanceTotPkts OBJECT-TYPE
   SYNTAX      Counter64
   MAX-ACCESS  read-only
   STATUS      current
   DESCRIPTION
      "Path: atm.performance.pvcTable.outPriorityQueues.h24Performance.totalPkts

       64 bit unsigned wrappable counter."
   ::= {pr1646v2ATMImaPerOutPQsH24PerformanceEntry 234881024}

pr1646v2ATMImaPerOutPQsH24PerformanceDirTxPkts OBJECT-TYPE
   SYNTAX      Counter64
   MAX-ACCESS  read-only
   STATUS      current
   DESCRIPTION
      "Path: atm.performance.pvcTable.outPriorityQueues.h24Performance.directTxPkts

       64 bit unsigned wrappable counter."
   ::= {pr1646v2ATMImaPerOutPQsH24PerformanceEntry 33554432}

pr1646v2ATMImaPerOutPQsH24PerformanceQdPkts OBJECT-TYPE
   SYNTAX      Counter64
   MAX-ACCESS  read-only
   STATUS      current
   DESCRIPTION
      "Path: atm.performance.pvcTable.outPriorityQueues.h24Performance.queuedPkts

       64 bit unsigned wrappable counter."
   ::= {pr1646v2ATMImaPerOutPQsH24PerformanceEntry 50331648}

pr1646v2ATMImaPerOutPQsH24PerformanceDropPkts OBJECT-TYPE
   SYNTAX      Counter64
   MAX-ACCESS  read-only
   STATUS      current
   DESCRIPTION
      "Path: atm.performance.pvcTable.outPriorityQueues.h24Performance.droppedPkts

       64 bit unsigned wrappable counter."
   ::= {pr1646v2ATMImaPerOutPQsH24PerformanceEntry 67108864}

pr1646v2ATMImaPerOutPQsH24PerformanceRDropPkts OBJECT-TYPE
   SYNTAX      Counter64
   MAX-ACCESS  read-only
   STATUS      current
   DESCRIPTION
      "Path: atm.performance.pvcTable.outPriorityQueues.h24Performance.redDroppedPkts

       64 bit unsigned wrappable counter."
   ::= {pr1646v2ATMImaPerOutPQsH24PerformanceEntry 201326592}

pr1646v2ATMImaPerOutPQsH24PerformanceCirTxPkts OBJECT-TYPE
   SYNTAX      Counter64
   MAX-ACCESS  read-only
   STATUS      current
   DESCRIPTION
      "Path: atm.performance.pvcTable.outPriorityQueues.h24Performance.cirTxPkts

       64 bit unsigned wrappable counter."
   ::= {pr1646v2ATMImaPerOutPQsH24PerformanceEntry 83886080}

pr1646v2ATMImaPerOutPQsH24PerformanceEirTxPkts OBJECT-TYPE
   SYNTAX      Counter64
   MAX-ACCESS  read-only
   STATUS      current
   DESCRIPTION
      "Path: atm.performance.pvcTable.outPriorityQueues.h24Performance.eirTxPkts

       64 bit unsigned wrappable counter."
   ::= {pr1646v2ATMImaPerOutPQsH24PerformanceEntry 100663296}

pr1646v2ATMImaPerOutPQsH24PerformanceViolTxPkts OBJECT-TYPE
   SYNTAX      Counter64
   MAX-ACCESS  read-only
   STATUS      current
   DESCRIPTION
      "Path: atm.performance.pvcTable.outPriorityQueues.h24Performance.violateTxPkts

       64 bit unsigned wrappable counter."
   ::= {pr1646v2ATMImaPerOutPQsH24PerformanceEntry 301989888}

pr1646v2ATMImaPerOutPQsH24PerformanceTotOcts OBJECT-TYPE
   SYNTAX      Counter64
   MAX-ACCESS  read-only
   STATUS      current
   DESCRIPTION
      "Path: atm.performance.pvcTable.outPriorityQueues.h24Performance.totalOctets

       64 bit unsigned wrappable counter."
   ::= {pr1646v2ATMImaPerOutPQsH24PerformanceEntry 251658240}

pr1646v2ATMImaPerOutPQsH24PerformanceDirTxOcts OBJECT-TYPE
   SYNTAX      Counter64
   MAX-ACCESS  read-only
   STATUS      current
   DESCRIPTION
      "Path: atm.performance.pvcTable.outPriorityQueues.h24Performance.directTxOctets

       64 bit unsigned wrappable counter."
   ::= {pr1646v2ATMImaPerOutPQsH24PerformanceEntry 117440512}

pr1646v2ATMImaPerOutPQsH24PerformanceQdOcts OBJECT-TYPE
   SYNTAX      Counter64
   MAX-ACCESS  read-only
   STATUS      current
   DESCRIPTION
      "Path: atm.performance.pvcTable.outPriorityQueues.h24Performance.queuedOctets

       64 bit unsigned wrappable counter."
   ::= {pr1646v2ATMImaPerOutPQsH24PerformanceEntry 134217728}

pr1646v2ATMImaPerOutPQsH24PerformanceDropOcts OBJECT-TYPE
   SYNTAX      Counter64
   MAX-ACCESS  read-only
   STATUS      current
   DESCRIPTION
      "Path: atm.performance.pvcTable.outPriorityQueues.h24Performance.droppedOctets

       64 bit unsigned wrappable counter."
   ::= {pr1646v2ATMImaPerOutPQsH24PerformanceEntry 150994944}

pr1646v2ATMImaPerOutPQsH24PerformanceRDropOcts OBJECT-TYPE
   SYNTAX      Counter64
   MAX-ACCESS  read-only
   STATUS      current
   DESCRIPTION
      "Path: atm.performance.pvcTable.outPriorityQueues.h24Performance.redDroppedOctets

       64 bit unsigned wrappable counter."
   ::= {pr1646v2ATMImaPerOutPQsH24PerformanceEntry 218103808}

pr1646v2ATMImaPerOutPQsH24PerformanceCirTxOcts OBJECT-TYPE
   SYNTAX      Counter64
   MAX-ACCESS  read-only
   STATUS      current
   DESCRIPTION
      "Path: atm.performance.pvcTable.outPriorityQueues.h24Performance.cirTxOctets

       64 bit unsigned wrappable counter."
   ::= {pr1646v2ATMImaPerOutPQsH24PerformanceEntry 167772160}

pr1646v2ATMImaPerOutPQsH24PerformanceEirTxOcts OBJECT-TYPE
   SYNTAX      Counter64
   MAX-ACCESS  read-only
   STATUS      current
   DESCRIPTION
      "Path: atm.performance.pvcTable.outPriorityQueues.h24Performance.eirTxOctets

       64 bit unsigned wrappable counter."
   ::= {pr1646v2ATMImaPerOutPQsH24PerformanceEntry 184549376}

pr1646v2ATMImaPerOutPQsH24PerformanceViolTxOcts OBJECT-TYPE
   SYNTAX      Counter64
   MAX-ACCESS  read-only
   STATUS      current
   DESCRIPTION
      "Path: atm.performance.pvcTable.outPriorityQueues.h24Performance.violateTxOctets

       64 bit unsigned wrappable counter."
   ::= {pr1646v2ATMImaPerOutPQsH24PerformanceEntry 318767104}

pr1646v2ATMImaPerOutPQsH24PerformanceBandwidth OBJECT-TYPE
   SYNTAX      Integer32
   MAX-ACCESS  read-only
   STATUS      current
   DESCRIPTION
      "Path: atm.performance.pvcTable.outPriorityQueues.h24Performance.bandwidth

       unit name = bps
       formula = 8 * ; 8 /"
   ::= {pr1646v2ATMImaPerOutPQsH24PerformanceEntry 268435456}

pr1646v2ATMImaPerOutPQsD7Performance OBJECT-TYPE
   SYNTAX      SEQUENCE OF Pr1646v2ATMImaPerOutPQsD7PerformanceEntry
   MAX-ACCESS  not-accessible
   STATUS      current
   DESCRIPTION
      ""
   ::= {pr1646v2ATMImaPer 84344832}

pr1646v2ATMImaPerOutPQsD7PerformanceEntry OBJECT-TYPE
   SYNTAX      Pr1646v2ATMImaPerOutPQsD7PerformanceEntry
   MAX-ACCESS  not-accessible
   STATUS      current
   DESCRIPTION
      ""
   INDEX      { pr1646v2ATMImaPerTableIx,
                pr1646v2ATMImaPerOutPQsTableIx,
                pr1646v2ATMImaPerOutPQsD7PerformanceTableIx }
   ::= {pr1646v2ATMImaPerOutPQsD7Performance 1}

Pr1646v2ATMImaPerOutPQsD7PerformanceEntry ::=
   SEQUENCE
      {
      pr1646v2ATMImaPerOutPQsD7PerformanceTableIx
         TableIndex,
      pr1646v2ATMImaPerOutPQsD7PerformanceSysUpTime
         TimeTicks,
      pr1646v2ATMImaPerOutPQsD7PerformanceTotPkts
         Counter64,
      pr1646v2ATMImaPerOutPQsD7PerformanceDirTxPkts
         Counter64,
      pr1646v2ATMImaPerOutPQsD7PerformanceQdPkts
         Counter64,
      pr1646v2ATMImaPerOutPQsD7PerformanceDropPkts
         Counter64,
      pr1646v2ATMImaPerOutPQsD7PerformanceRDropPkts
         Counter64,
      pr1646v2ATMImaPerOutPQsD7PerformanceCirTxPkts
         Counter64,
      pr1646v2ATMImaPerOutPQsD7PerformanceEirTxPkts
         Counter64,
      pr1646v2ATMImaPerOutPQsD7PerformanceViolTxPkts
         Counter64,
      pr1646v2ATMImaPerOutPQsD7PerformanceTotOcts
         Counter64,
      pr1646v2ATMImaPerOutPQsD7PerformanceDirTxOcts
         Counter64,
      pr1646v2ATMImaPerOutPQsD7PerformanceQdOcts
         Counter64,
      pr1646v2ATMImaPerOutPQsD7PerformanceDropOcts
         Counter64,
      pr1646v2ATMImaPerOutPQsD7PerformanceRDropOcts
         Counter64,
      pr1646v2ATMImaPerOutPQsD7PerformanceCirTxOcts
         Counter64,
      pr1646v2ATMImaPerOutPQsD7PerformanceEirTxOcts
         Counter64,
      pr1646v2ATMImaPerOutPQsD7PerformanceViolTxOcts
         Counter64,
      pr1646v2ATMImaPerOutPQsD7PerformanceBandwidth
         Integer32
      }

pr1646v2ATMImaPerOutPQsD7PerformanceTableIx OBJECT-TYPE
   SYNTAX      TableIndex
   MAX-ACCESS  not-accessible
   STATUS      current
   DESCRIPTION
      ""
   ::= {pr1646v2ATMImaPerOutPQsD7PerformanceEntry 11}

pr1646v2ATMImaPerOutPQsD7PerformanceSysUpTime OBJECT-TYPE
   SYNTAX      TimeTicks
   MAX-ACCESS  read-only
   STATUS      current
   DESCRIPTION
      "Path: atm.performance.pvcTable.outPriorityQueues.d7Performance.sysUpTime

       Time in centi-second."
   ::= {pr1646v2ATMImaPerOutPQsD7PerformanceEntry 16777216}

pr1646v2ATMImaPerOutPQsD7PerformanceTotPkts OBJECT-TYPE
   SYNTAX      Counter64
   MAX-ACCESS  read-only
   STATUS      current
   DESCRIPTION
      "Path: atm.performance.pvcTable.outPriorityQueues.d7Performance.totalPkts

       64 bit unsigned wrappable counter."
   ::= {pr1646v2ATMImaPerOutPQsD7PerformanceEntry 234881024}

pr1646v2ATMImaPerOutPQsD7PerformanceDirTxPkts OBJECT-TYPE
   SYNTAX      Counter64
   MAX-ACCESS  read-only
   STATUS      current
   DESCRIPTION
      "Path: atm.performance.pvcTable.outPriorityQueues.d7Performance.directTxPkts

       64 bit unsigned wrappable counter."
   ::= {pr1646v2ATMImaPerOutPQsD7PerformanceEntry 33554432}

pr1646v2ATMImaPerOutPQsD7PerformanceQdPkts OBJECT-TYPE
   SYNTAX      Counter64
   MAX-ACCESS  read-only
   STATUS      current
   DESCRIPTION
      "Path: atm.performance.pvcTable.outPriorityQueues.d7Performance.queuedPkts

       64 bit unsigned wrappable counter."
   ::= {pr1646v2ATMImaPerOutPQsD7PerformanceEntry 50331648}

pr1646v2ATMImaPerOutPQsD7PerformanceDropPkts OBJECT-TYPE
   SYNTAX      Counter64
   MAX-ACCESS  read-only
   STATUS      current
   DESCRIPTION
      "Path: atm.performance.pvcTable.outPriorityQueues.d7Performance.droppedPkts

       64 bit unsigned wrappable counter."
   ::= {pr1646v2ATMImaPerOutPQsD7PerformanceEntry 67108864}

pr1646v2ATMImaPerOutPQsD7PerformanceRDropPkts OBJECT-TYPE
   SYNTAX      Counter64
   MAX-ACCESS  read-only
   STATUS      current
   DESCRIPTION
      "Path: atm.performance.pvcTable.outPriorityQueues.d7Performance.redDroppedPkts

       64 bit unsigned wrappable counter."
   ::= {pr1646v2ATMImaPerOutPQsD7PerformanceEntry 201326592}

pr1646v2ATMImaPerOutPQsD7PerformanceCirTxPkts OBJECT-TYPE
   SYNTAX      Counter64
   MAX-ACCESS  read-only
   STATUS      current
   DESCRIPTION
      "Path: atm.performance.pvcTable.outPriorityQueues.d7Performance.cirTxPkts

       64 bit unsigned wrappable counter."
   ::= {pr1646v2ATMImaPerOutPQsD7PerformanceEntry 83886080}

pr1646v2ATMImaPerOutPQsD7PerformanceEirTxPkts OBJECT-TYPE
   SYNTAX      Counter64
   MAX-ACCESS  read-only
   STATUS      current
   DESCRIPTION
      "Path: atm.performance.pvcTable.outPriorityQueues.d7Performance.eirTxPkts

       64 bit unsigned wrappable counter."
   ::= {pr1646v2ATMImaPerOutPQsD7PerformanceEntry 100663296}

pr1646v2ATMImaPerOutPQsD7PerformanceViolTxPkts OBJECT-TYPE
   SYNTAX      Counter64
   MAX-ACCESS  read-only
   STATUS      current
   DESCRIPTION
      "Path: atm.performance.pvcTable.outPriorityQueues.d7Performance.violateTxPkts

       64 bit unsigned wrappable counter."
   ::= {pr1646v2ATMImaPerOutPQsD7PerformanceEntry 301989888}

pr1646v2ATMImaPerOutPQsD7PerformanceTotOcts OBJECT-TYPE
   SYNTAX      Counter64
   MAX-ACCESS  read-only
   STATUS      current
   DESCRIPTION
      "Path: atm.performance.pvcTable.outPriorityQueues.d7Performance.totalOctets

       64 bit unsigned wrappable counter."
   ::= {pr1646v2ATMImaPerOutPQsD7PerformanceEntry 251658240}

pr1646v2ATMImaPerOutPQsD7PerformanceDirTxOcts OBJECT-TYPE
   SYNTAX      Counter64
   MAX-ACCESS  read-only
   STATUS      current
   DESCRIPTION
      "Path: atm.performance.pvcTable.outPriorityQueues.d7Performance.directTxOctets

       64 bit unsigned wrappable counter."
   ::= {pr1646v2ATMImaPerOutPQsD7PerformanceEntry 117440512}

pr1646v2ATMImaPerOutPQsD7PerformanceQdOcts OBJECT-TYPE
   SYNTAX      Counter64
   MAX-ACCESS  read-only
   STATUS      current
   DESCRIPTION
      "Path: atm.performance.pvcTable.outPriorityQueues.d7Performance.queuedOctets

       64 bit unsigned wrappable counter."
   ::= {pr1646v2ATMImaPerOutPQsD7PerformanceEntry 134217728}

pr1646v2ATMImaPerOutPQsD7PerformanceDropOcts OBJECT-TYPE
   SYNTAX      Counter64
   MAX-ACCESS  read-only
   STATUS      current
   DESCRIPTION
      "Path: atm.performance.pvcTable.outPriorityQueues.d7Performance.droppedOctets

       64 bit unsigned wrappable counter."
   ::= {pr1646v2ATMImaPerOutPQsD7PerformanceEntry 150994944}

pr1646v2ATMImaPerOutPQsD7PerformanceRDropOcts OBJECT-TYPE
   SYNTAX      Counter64
   MAX-ACCESS  read-only
   STATUS      current
   DESCRIPTION
      "Path: atm.performance.pvcTable.outPriorityQueues.d7Performance.redDroppedOctets

       64 bit unsigned wrappable counter."
   ::= {pr1646v2ATMImaPerOutPQsD7PerformanceEntry 218103808}

pr1646v2ATMImaPerOutPQsD7PerformanceCirTxOcts OBJECT-TYPE
   SYNTAX      Counter64
   MAX-ACCESS  read-only
   STATUS      current
   DESCRIPTION
      "Path: atm.performance.pvcTable.outPriorityQueues.d7Performance.cirTxOctets

       64 bit unsigned wrappable counter."
   ::= {pr1646v2ATMImaPerOutPQsD7PerformanceEntry 167772160}

pr1646v2ATMImaPerOutPQsD7PerformanceEirTxOcts OBJECT-TYPE
   SYNTAX      Counter64
   MAX-ACCESS  read-only
   STATUS      current
   DESCRIPTION
      "Path: atm.performance.pvcTable.outPriorityQueues.d7Performance.eirTxOctets

       64 bit unsigned wrappable counter."
   ::= {pr1646v2ATMImaPerOutPQsD7PerformanceEntry 184549376}

pr1646v2ATMImaPerOutPQsD7PerformanceViolTxOcts OBJECT-TYPE
   SYNTAX      Counter64
   MAX-ACCESS  read-only
   STATUS      current
   DESCRIPTION
      "Path: atm.performance.pvcTable.outPriorityQueues.d7Performance.violateTxOctets

       64 bit unsigned wrappable counter."
   ::= {pr1646v2ATMImaPerOutPQsD7PerformanceEntry 318767104}

pr1646v2ATMImaPerOutPQsD7PerformanceBandwidth OBJECT-TYPE
   SYNTAX      Integer32
   MAX-ACCESS  read-only
   STATUS      current
   DESCRIPTION
      "Path: atm.performance.pvcTable.outPriorityQueues.d7Performance.bandwidth

       unit name = bps
       formula = 8 * ; 8 /"
   ::= {pr1646v2ATMImaPerOutPQsD7PerformanceEntry 268435456}

pr1646v2ATMImaPerFrDlci OBJECT-TYPE
   SYNTAX      SEQUENCE OF Pr1646v2ATMImaPerFrDlciEntry
   MAX-ACCESS  not-accessible
   STATUS      current
   DESCRIPTION
      ""
   ::= {pr1646v2ATMImaPer 503447552}

pr1646v2ATMImaPerFrDlciEntry OBJECT-TYPE
   SYNTAX      Pr1646v2ATMImaPerFrDlciEntry
   MAX-ACCESS  not-accessible
   STATUS      current
   DESCRIPTION
      ""
   INDEX      { pr1646v2ATMImaPerTableIx,
                pr1646v2ATMImaPerFrDlciTableIx }
   ::= {pr1646v2ATMImaPerFrDlci 1}

Pr1646v2ATMImaPerFrDlciEntry ::=
   SEQUENCE
      {
      pr1646v2ATMImaPerFrDlciTableIx
         TableIndex,
      pr1646v2ATMImaPerFrDlciName
         DisplayString,
      pr1646v2ATMImaPerFrDlciMCInOctets
         Counter64,
      pr1646v2ATMImaPerFrDlciMCInUcast
         Counter64,
      pr1646v2ATMImaPerFrDlciMCInNUcastPkts
         Counter64,
      pr1646v2ATMImaPerFrDlciMCInBcastPkts
         Counter64,
      pr1646v2ATMImaPerFrDlciMCInMcastPkts
         Counter64,
      pr1646v2ATMImaPerFrDlciMCInDiscards
         Counter64,
      pr1646v2ATMImaPerFrDlciMCInErrors
         Counter64,
      pr1646v2ATMImaPerFrDlciMCInUnknownProtos
         Counter64,
      pr1646v2ATMImaPerFrDlciMCInDropEx
         Counter64,
      pr1646v2ATMImaPerFrDlciMCInDropNoMac
         Counter64,
      pr1646v2ATMImaPerFrDlciMCInDropNUCast
         Counter64,
      pr1646v2ATMImaPerFrDlciMCInDropFilter
         Counter64,
      pr1646v2ATMImaPerFrDlciMCInBandwidth15sec
         Integer32,
      pr1646v2ATMImaPerFrDlciMCInBandwidth30sec
         Integer32,
      pr1646v2ATMImaPerFrDlciMCInBandwidth1min
         Integer32,
      pr1646v2ATMImaPerFrDlciMCInBandwidth2min
         Integer32,
      pr1646v2ATMImaPerFrDlciMCInBandwidth5min
         Integer32,
      pr1646v2ATMImaPerFrDlciMCOutOctets
         Counter64,
      pr1646v2ATMImaPerFrDlciMCOutUcastPkts
         Counter64,
      pr1646v2ATMImaPerFrDlciMCOutNUcastPkts
         Counter64,
      pr1646v2ATMImaPerFrDlciMCOutBcastPkts
         Counter64,
      pr1646v2ATMImaPerFrDlciMCOutMcastPkts
         Counter64,
      pr1646v2ATMImaPerFrDlciMCOutDiscards
         Counter64,
      pr1646v2ATMImaPerFrDlciMCOutErrors
         Counter64,
      pr1646v2ATMImaPerFrDlciMCOutQLen
         Counter32,
      pr1646v2ATMImaPerFrDlciMCOutDropEx
         Counter64,
      pr1646v2ATMImaPerFrDlciMCOutDropNoArp
         Counter64,
      pr1646v2ATMImaPerFrDlciMCOutDropFilter
         Counter64,
      pr1646v2ATMImaPerFrDlciMCOutBandwidth15sec
         Integer32,
      pr1646v2ATMImaPerFrDlciMCOutBandwidth30sec
         Integer32,
      pr1646v2ATMImaPerFrDlciMCOutBandwidth1min
         Integer32,
      pr1646v2ATMImaPerFrDlciMCOutBandwidth2min
         Integer32,
      pr1646v2ATMImaPerFrDlciMCOutBandwidth5min
         Integer32,
      pr1646v2ATMImaPerFrDlciFrDlci
         Integer32,
      pr1646v2ATMImaPerFrDlciFrInFecn
         Counter32,
      pr1646v2ATMImaPerFrDlciFrInBecn
         Counter32,
      pr1646v2ATMImaPerFrDlciFrInDe
         Counter32,
      pr1646v2ATMImaPerFrDlciFrInOctets
         Counter32,
      pr1646v2ATMImaPerFrDlciFrInFrames
         Counter32,
      pr1646v2ATMImaPerFrDlciFrOutFecn
         Counter32,
      pr1646v2ATMImaPerFrDlciFrOutBecn
         Counter32,
      pr1646v2ATMImaPerFrDlciFrOutDe
         Counter32,
      pr1646v2ATMImaPerFrDlciFrOutOctets
         Counter32,
      pr1646v2ATMImaPerFrDlciFrOutFrames
         Counter32
      }

pr1646v2ATMImaPerFrDlciTableIx OBJECT-TYPE
   SYNTAX      TableIndex
   MAX-ACCESS  not-accessible
   STATUS      current
   DESCRIPTION
      ""
   ::= {pr1646v2ATMImaPerFrDlciEntry 11}

pr1646v2ATMImaPerFrDlciName OBJECT-TYPE
   SYNTAX      DisplayString
   MAX-ACCESS  read-only
   STATUS      current
   DESCRIPTION
      "Path: atm.performance.pvcTable.frameRelay.dlciTable.name"
   ::= {pr1646v2ATMImaPerFrDlciEntry 16777216}

pr1646v2ATMImaPerFrDlciMCInOctets OBJECT-TYPE
   SYNTAX      Counter64
   MAX-ACCESS  read-only
   STATUS      current
   DESCRIPTION
      "Path: atm.performance.pvcTable.frameRelay.dlciTable.mibCounters.ifInOctets

       64 bit unsigned wrappable counter."
   ::= {pr1646v2ATMImaPerFrDlciEntry 40697856}

pr1646v2ATMImaPerFrDlciMCInUcast OBJECT-TYPE
   SYNTAX      Counter64
   MAX-ACCESS  read-only
   STATUS      current
   DESCRIPTION
      "Path: atm.performance.pvcTable.frameRelay.dlciTable.mibCounters.ifInUcastPkts

       64 bit unsigned wrappable counter."
   ::= {pr1646v2ATMImaPerFrDlciEntry 40763392}

pr1646v2ATMImaPerFrDlciMCInNUcastPkts OBJECT-TYPE
   SYNTAX      Counter64
   MAX-ACCESS  read-only
   STATUS      current
   DESCRIPTION
      "Path: atm.performance.pvcTable.frameRelay.dlciTable.mibCounters.ifInNUcastPkts

       64 bit unsigned wrappable counter."
   ::= {pr1646v2ATMImaPerFrDlciEntry 40828928}

pr1646v2ATMImaPerFrDlciMCInBcastPkts OBJECT-TYPE
   SYNTAX      Counter64
   MAX-ACCESS  read-only
   STATUS      current
   DESCRIPTION
      "Path: atm.performance.pvcTable.frameRelay.dlciTable.mibCounters.ifInBcastPkts

       64 bit unsigned wrappable counter."
   ::= {pr1646v2ATMImaPerFrDlciEntry 47382528}

pr1646v2ATMImaPerFrDlciMCInMcastPkts OBJECT-TYPE
   SYNTAX      Counter64
   MAX-ACCESS  read-only
   STATUS      current
   DESCRIPTION
      "Path: atm.performance.pvcTable.frameRelay.dlciTable.mibCounters.ifInMcastPkts

       64 bit unsigned wrappable counter."
   ::= {pr1646v2ATMImaPerFrDlciEntry 48037888}

pr1646v2ATMImaPerFrDlciMCInDiscards OBJECT-TYPE
   SYNTAX      Counter64
   MAX-ACCESS  read-only
   STATUS      current
   DESCRIPTION
      "Path: atm.performance.pvcTable.frameRelay.dlciTable.mibCounters.ifInDiscards

       64 bit unsigned wrappable counter."
   ::= {pr1646v2ATMImaPerFrDlciEntry 40894464}

pr1646v2ATMImaPerFrDlciMCInErrors OBJECT-TYPE
   SYNTAX      Counter64
   MAX-ACCESS  read-only
   STATUS      current
   DESCRIPTION
      "Path: atm.performance.pvcTable.frameRelay.dlciTable.mibCounters.ifInErrors

       64 bit unsigned wrappable counter."
   ::= {pr1646v2ATMImaPerFrDlciEntry 40960000}

pr1646v2ATMImaPerFrDlciMCInUnknownProtos OBJECT-TYPE
   SYNTAX      Counter64
   MAX-ACCESS  read-only
   STATUS      current
   DESCRIPTION
      "Path: atm.performance.pvcTable.frameRelay.dlciTable.mibCounters.ifInUnknownProtos

       64 bit unsigned wrappable counter."
   ::= {pr1646v2ATMImaPerFrDlciEntry 41025536}

pr1646v2ATMImaPerFrDlciMCInDropEx OBJECT-TYPE
   SYNTAX      Counter64
   MAX-ACCESS  read-only
   STATUS      current
   DESCRIPTION
      "Path: atm.performance.pvcTable.frameRelay.dlciTable.mibCounters.ifInDropLevelExceeded

       64 bit unsigned wrappable counter."
   ::= {pr1646v2ATMImaPerFrDlciEntry 42074112}

pr1646v2ATMImaPerFrDlciMCInDropNoMac OBJECT-TYPE
   SYNTAX      Counter64
   MAX-ACCESS  read-only
   STATUS      current
   DESCRIPTION
      "Path: atm.performance.pvcTable.frameRelay.dlciTable.mibCounters.ifInDiscardsNoMacFit

       64 bit unsigned wrappable counter."
   ::= {pr1646v2ATMImaPerFrDlciEntry 42270720}

pr1646v2ATMImaPerFrDlciMCInDropNUCast OBJECT-TYPE
   SYNTAX      Counter64
   MAX-ACCESS  read-only
   STATUS      current
   DESCRIPTION
      "Path: atm.performance.pvcTable.frameRelay.dlciTable.mibCounters.ifInDiscardsNUCast

       64 bit unsigned wrappable counter."
   ::= {pr1646v2ATMImaPerFrDlciEntry 42467328}

pr1646v2ATMImaPerFrDlciMCInDropFilter OBJECT-TYPE
   SYNTAX      Counter64
   MAX-ACCESS  read-only
   STATUS      current
   DESCRIPTION
      "Path: atm.performance.pvcTable.frameRelay.dlciTable.mibCounters.ifInDiscardsFilter

       64 bit unsigned wrappable counter."
   ::= {pr1646v2ATMImaPerFrDlciEntry 42532864}

pr1646v2ATMImaPerFrDlciMCInBandwidth15sec OBJECT-TYPE
   SYNTAX      Integer32
   MAX-ACCESS  read-only
   STATUS      current
   DESCRIPTION
      "Path: atm.performance.pvcTable.frameRelay.dlciTable.mibCounters.ifInBandwidth.15sec

       unit name = bps
       formula = 8 * ; 8 /"
   ::= {pr1646v2ATMImaPerFrDlciEntry 45417728}

pr1646v2ATMImaPerFrDlciMCInBandwidth30sec OBJECT-TYPE
   SYNTAX      Integer32
   MAX-ACCESS  read-only
   STATUS      current
   DESCRIPTION
      "Path: atm.performance.pvcTable.frameRelay.dlciTable.mibCounters.ifInBandwidth.30sec

       unit name = bps
       formula = 8 * ; 8 /"
   ::= {pr1646v2ATMImaPerFrDlciEntry 45419008}

pr1646v2ATMImaPerFrDlciMCInBandwidth1min OBJECT-TYPE
   SYNTAX      Integer32
   MAX-ACCESS  read-only
   STATUS      current
   DESCRIPTION
      "Path: atm.performance.pvcTable.frameRelay.dlciTable.mibCounters.ifInBandwidth.1min

       unit name = bps
       formula = 8 * ; 8 /"
   ::= {pr1646v2ATMImaPerFrDlciEntry 45421568}

pr1646v2ATMImaPerFrDlciMCInBandwidth2min OBJECT-TYPE
   SYNTAX      Integer32
   MAX-ACCESS  read-only
   STATUS      current
   DESCRIPTION
      "Path: atm.performance.pvcTable.frameRelay.dlciTable.mibCounters.ifInBandwidth.2min

       unit name = bps
       formula = 8 * ; 8 /"
   ::= {pr1646v2ATMImaPerFrDlciEntry 45426688}

pr1646v2ATMImaPerFrDlciMCInBandwidth5min OBJECT-TYPE
   SYNTAX      Integer32
   MAX-ACCESS  read-only
   STATUS      current
   DESCRIPTION
      "Path: atm.performance.pvcTable.frameRelay.dlciTable.mibCounters.ifInBandwidth.5min

       unit name = bps
       formula = 8 * ; 8 /"
   ::= {pr1646v2ATMImaPerFrDlciEntry 45442048}

pr1646v2ATMImaPerFrDlciMCOutOctets OBJECT-TYPE
   SYNTAX      Counter64
   MAX-ACCESS  read-only
   STATUS      current
   DESCRIPTION
      "Path: atm.performance.pvcTable.frameRelay.dlciTable.mibCounters.ifOutOctets

       64 bit unsigned wrappable counter."
   ::= {pr1646v2ATMImaPerFrDlciEntry 41091072}

pr1646v2ATMImaPerFrDlciMCOutUcastPkts OBJECT-TYPE
   SYNTAX      Counter64
   MAX-ACCESS  read-only
   STATUS      current
   DESCRIPTION
      "Path: atm.performance.pvcTable.frameRelay.dlciTable.mibCounters.ifOutUcastPkts

       64 bit unsigned wrappable counter."
   ::= {pr1646v2ATMImaPerFrDlciEntry 41156608}

pr1646v2ATMImaPerFrDlciMCOutNUcastPkts OBJECT-TYPE
   SYNTAX      Counter64
   MAX-ACCESS  read-only
   STATUS      current
   DESCRIPTION
      "Path: atm.performance.pvcTable.frameRelay.dlciTable.mibCounters.ifOutNUcastPkts

       64 bit unsigned wrappable counter."
   ::= {pr1646v2ATMImaPerFrDlciEntry 41222144}

pr1646v2ATMImaPerFrDlciMCOutBcastPkts OBJECT-TYPE
   SYNTAX      Counter64
   MAX-ACCESS  read-only
   STATUS      current
   DESCRIPTION
      "Path: atm.performance.pvcTable.frameRelay.dlciTable.mibCounters.ifOutBcastPkts

       64 bit unsigned wrappable counter."
   ::= {pr1646v2ATMImaPerFrDlciEntry 47775744}

pr1646v2ATMImaPerFrDlciMCOutMcastPkts OBJECT-TYPE
   SYNTAX      Counter64
   MAX-ACCESS  read-only
   STATUS      current
   DESCRIPTION
      "Path: atm.performance.pvcTable.frameRelay.dlciTable.mibCounters.ifOutMcastPkts

       64 bit unsigned wrappable counter."
   ::= {pr1646v2ATMImaPerFrDlciEntry 48431104}

pr1646v2ATMImaPerFrDlciMCOutDiscards OBJECT-TYPE
   SYNTAX      Counter64
   MAX-ACCESS  read-only
   STATUS      current
   DESCRIPTION
      "Path: atm.performance.pvcTable.frameRelay.dlciTable.mibCounters.ifOutDiscards

       64 bit unsigned wrappable counter."
   ::= {pr1646v2ATMImaPerFrDlciEntry 41287680}

pr1646v2ATMImaPerFrDlciMCOutErrors OBJECT-TYPE
   SYNTAX      Counter64
   MAX-ACCESS  read-only
   STATUS      current
   DESCRIPTION
      "Path: atm.performance.pvcTable.frameRelay.dlciTable.mibCounters.ifOutErrors

       64 bit unsigned wrappable counter."
   ::= {pr1646v2ATMImaPerFrDlciEntry 41353216}

pr1646v2ATMImaPerFrDlciMCOutQLen OBJECT-TYPE
   SYNTAX      Counter32
   MAX-ACCESS  read-only
   STATUS      current
   DESCRIPTION
      "Path: atm.performance.pvcTable.frameRelay.dlciTable.mibCounters.ifOutQLen

       32 bit unsigned wrappable counter."
   ::= {pr1646v2ATMImaPerFrDlciEntry 41418752}

pr1646v2ATMImaPerFrDlciMCOutDropEx OBJECT-TYPE
   SYNTAX      Counter64
   MAX-ACCESS  read-only
   STATUS      current
   DESCRIPTION
      "Path: atm.performance.pvcTable.frameRelay.dlciTable.mibCounters.ifOutDropLevelExceeded

       64 bit unsigned wrappable counter."
   ::= {pr1646v2ATMImaPerFrDlciEntry 41484288}

pr1646v2ATMImaPerFrDlciMCOutDropNoArp OBJECT-TYPE
   SYNTAX      Counter64
   MAX-ACCESS  read-only
   STATUS      current
   DESCRIPTION
      "Path: atm.performance.pvcTable.frameRelay.dlciTable.mibCounters.ifOutDiscardsNoArp

       64 bit unsigned wrappable counter."
   ::= {pr1646v2ATMImaPerFrDlciEntry 42336256}

pr1646v2ATMImaPerFrDlciMCOutDropFilter OBJECT-TYPE
   SYNTAX      Counter64
   MAX-ACCESS  read-only
   STATUS      current
   DESCRIPTION
      "Path: atm.performance.pvcTable.frameRelay.dlciTable.mibCounters.ifOutDiscardsFilter

       64 bit unsigned wrappable counter."
   ::= {pr1646v2ATMImaPerFrDlciEntry 42598400}

pr1646v2ATMImaPerFrDlciMCOutBandwidth15sec OBJECT-TYPE
   SYNTAX      Integer32
   MAX-ACCESS  read-only
   STATUS      current
   DESCRIPTION
      "Path: atm.performance.pvcTable.frameRelay.dlciTable.mibCounters.ifOutBandwidth.15sec

       unit name = bps
       formula = 8 * ; 8 /"
   ::= {pr1646v2ATMImaPerFrDlciEntry 45483264}

pr1646v2ATMImaPerFrDlciMCOutBandwidth30sec OBJECT-TYPE
   SYNTAX      Integer32
   MAX-ACCESS  read-only
   STATUS      current
   DESCRIPTION
      "Path: atm.performance.pvcTable.frameRelay.dlciTable.mibCounters.ifOutBandwidth.30sec

       unit name = bps
       formula = 8 * ; 8 /"
   ::= {pr1646v2ATMImaPerFrDlciEntry 45484544}

pr1646v2ATMImaPerFrDlciMCOutBandwidth1min OBJECT-TYPE
   SYNTAX      Integer32
   MAX-ACCESS  read-only
   STATUS      current
   DESCRIPTION
      "Path: atm.performance.pvcTable.frameRelay.dlciTable.mibCounters.ifOutBandwidth.1min

       unit name = bps
       formula = 8 * ; 8 /"
   ::= {pr1646v2ATMImaPerFrDlciEntry 45487104}

pr1646v2ATMImaPerFrDlciMCOutBandwidth2min OBJECT-TYPE
   SYNTAX      Integer32
   MAX-ACCESS  read-only
   STATUS      current
   DESCRIPTION
      "Path: atm.performance.pvcTable.frameRelay.dlciTable.mibCounters.ifOutBandwidth.2min

       unit name = bps
       formula = 8 * ; 8 /"
   ::= {pr1646v2ATMImaPerFrDlciEntry 45492224}

pr1646v2ATMImaPerFrDlciMCOutBandwidth5min OBJECT-TYPE
   SYNTAX      Integer32
   MAX-ACCESS  read-only
   STATUS      current
   DESCRIPTION
      "Path: atm.performance.pvcTable.frameRelay.dlciTable.mibCounters.ifOutBandwidth.5min

       unit name = bps
       formula = 8 * ; 8 /"
   ::= {pr1646v2ATMImaPerFrDlciEntry 45507584}

pr1646v2ATMImaPerFrDlciFrDlci OBJECT-TYPE
   SYNTAX      Integer32
   MAX-ACCESS  read-only
   STATUS      current
   DESCRIPTION
      "Path: atm.performance.pvcTable.frameRelay.dlciTable.frameRelay.dlci"
   ::= {pr1646v2ATMImaPerFrDlciEntry 224657408}

pr1646v2ATMImaPerFrDlciFrInFecn OBJECT-TYPE
   SYNTAX      Counter32
   MAX-ACCESS  read-only
   STATUS      current
   DESCRIPTION
      "Path: atm.performance.pvcTable.frameRelay.dlciTable.frameRelay.inFecn

       32 bit unsigned wrappable counter."
   ::= {pr1646v2ATMImaPerFrDlciEntry 218169344}

pr1646v2ATMImaPerFrDlciFrInBecn OBJECT-TYPE
   SYNTAX      Counter32
   MAX-ACCESS  read-only
   STATUS      current
   DESCRIPTION
      "Path: atm.performance.pvcTable.frameRelay.dlciTable.frameRelay.inBecn

       32 bit unsigned wrappable counter."
   ::= {pr1646v2ATMImaPerFrDlciEntry 218234880}

pr1646v2ATMImaPerFrDlciFrInDe OBJECT-TYPE
   SYNTAX      Counter32
   MAX-ACCESS  read-only
   STATUS      current
   DESCRIPTION
      "Path: atm.performance.pvcTable.frameRelay.dlciTable.frameRelay.inDe

       32 bit unsigned wrappable counter."
   ::= {pr1646v2ATMImaPerFrDlciEntry 218300416}

pr1646v2ATMImaPerFrDlciFrInOctets OBJECT-TYPE
   SYNTAX      Counter32
   MAX-ACCESS  read-only
   STATUS      current
   DESCRIPTION
      "Path: atm.performance.pvcTable.frameRelay.dlciTable.frameRelay.inOctets

       32 bit unsigned wrappable counter."
   ::= {pr1646v2ATMImaPerFrDlciEntry 218365952}

pr1646v2ATMImaPerFrDlciFrInFrames OBJECT-TYPE
   SYNTAX      Counter32
   MAX-ACCESS  read-only
   STATUS      current
   DESCRIPTION
      "Path: atm.performance.pvcTable.frameRelay.dlciTable.frameRelay.inFrames

       32 bit unsigned wrappable counter."
   ::= {pr1646v2ATMImaPerFrDlciEntry 218431488}

pr1646v2ATMImaPerFrDlciFrOutFecn OBJECT-TYPE
   SYNTAX      Counter32
   MAX-ACCESS  read-only
   STATUS      current
   DESCRIPTION
      "Path: atm.performance.pvcTable.frameRelay.dlciTable.frameRelay.outFecn

       32 bit unsigned wrappable counter."
   ::= {pr1646v2ATMImaPerFrDlciEntry 226492416}

pr1646v2ATMImaPerFrDlciFrOutBecn OBJECT-TYPE
   SYNTAX      Counter32
   MAX-ACCESS  read-only
   STATUS      current
   DESCRIPTION
      "Path: atm.performance.pvcTable.frameRelay.dlciTable.frameRelay.outBecn

       32 bit unsigned wrappable counter."
   ::= {pr1646v2ATMImaPerFrDlciEntry 226557952}

pr1646v2ATMImaPerFrDlciFrOutDe OBJECT-TYPE
   SYNTAX      Counter32
   MAX-ACCESS  read-only
   STATUS      current
   DESCRIPTION
      "Path: atm.performance.pvcTable.frameRelay.dlciTable.frameRelay.outDe

       32 bit unsigned wrappable counter."
   ::= {pr1646v2ATMImaPerFrDlciEntry 226623488}

pr1646v2ATMImaPerFrDlciFrOutOctets OBJECT-TYPE
   SYNTAX      Counter32
   MAX-ACCESS  read-only
   STATUS      current
   DESCRIPTION
      "Path: atm.performance.pvcTable.frameRelay.dlciTable.frameRelay.outOctets

       32 bit unsigned wrappable counter."
   ::= {pr1646v2ATMImaPerFrDlciEntry 226689024}

pr1646v2ATMImaPerFrDlciFrOutFrames OBJECT-TYPE
   SYNTAX      Counter32
   MAX-ACCESS  read-only
   STATUS      current
   DESCRIPTION
      "Path: atm.performance.pvcTable.frameRelay.dlciTable.frameRelay.outFrames

       32 bit unsigned wrappable counter."
   ::= {pr1646v2ATMImaPerFrDlciEntry 226754560}

pr1646v2ATMImaPerFrDlciMCH2P OBJECT-TYPE
   SYNTAX      SEQUENCE OF Pr1646v2ATMImaPerFrDlciMCH2PEntry
   MAX-ACCESS  not-accessible
   STATUS      current
   DESCRIPTION
      ""
   ::= {pr1646v2ATMImaPer 503448186}

pr1646v2ATMImaPerFrDlciMCH2PEntry OBJECT-TYPE
   SYNTAX      Pr1646v2ATMImaPerFrDlciMCH2PEntry
   MAX-ACCESS  not-accessible
   STATUS      current
   DESCRIPTION
      ""
   INDEX      { pr1646v2ATMImaPerTableIx,
                pr1646v2ATMImaPerFrDlciTableIx,
                pr1646v2ATMImaPerFrDlciMCH2PTableIx }
   ::= {pr1646v2ATMImaPerFrDlciMCH2P 1}

Pr1646v2ATMImaPerFrDlciMCH2PEntry ::=
   SEQUENCE
      {
      pr1646v2ATMImaPerFrDlciMCH2PTableIx
         TableIndex,
      pr1646v2ATMImaPerFrDlciMCH2PSysUpTime
         TimeTicks,
      pr1646v2ATMImaPerFrDlciMCH2PIfUpTime
         TimeTicks,
      pr1646v2ATMImaPerFrDlciMCH2PIfStatChanges
         Counter32,
      pr1646v2ATMImaPerFrDlciMCH2PIfInOctets
         Counter64,
      pr1646v2ATMImaPerFrDlciMCH2PIfInUCPkts
         Counter64,
      pr1646v2ATMImaPerFrDlciMCH2PIfInNUCPkts
         Counter64,
      pr1646v2ATMImaPerFrDlciMCH2PIfInBCPkts
         Counter64,
      pr1646v2ATMImaPerFrDlciMCH2PIfInMCPkts
         Counter64,
      pr1646v2ATMImaPerFrDlciMCH2PIfInDiscards
         Counter64,
      pr1646v2ATMImaPerFrDlciMCH2PIfInErrors
         Counter64,
      pr1646v2ATMImaPerFrDlciMCH2PIfInUnkwn
         Counter64,
      pr1646v2ATMImaPerFrDlciMCH2PInDropEx
         Counter64,
      pr1646v2ATMImaPerFrDlciMCH2PInDropNoMac
         Counter64,
      pr1646v2ATMImaPerFrDlciMCH2PInDropNUCast
         Counter64,
      pr1646v2ATMImaPerFrDlciMCH2PInDropFilter
         Counter64,
      pr1646v2ATMImaPerFrDlciMCH2PIfInBandwidth
         Integer32,
      pr1646v2ATMImaPerFrDlciMCH2PIfOutOctets
         Counter64,
      pr1646v2ATMImaPerFrDlciMCH2PIfOutUCPkts
         Counter64,
      pr1646v2ATMImaPerFrDlciMCH2PIfOutNUCPkts
         Counter64,
      pr1646v2ATMImaPerFrDlciMCH2PIfOutBCPkts
         Counter64,
      pr1646v2ATMImaPerFrDlciMCH2PIfOutMCPkts
         Counter64,
      pr1646v2ATMImaPerFrDlciMCH2PIfOutDiscards
         Counter64,
      pr1646v2ATMImaPerFrDlciMCH2PIfOutErrors
         Counter64,
      pr1646v2ATMImaPerFrDlciMCH2POutDropEx
         Counter64,
      pr1646v2ATMImaPerFrDlciMCH2POutDropNoArp
         Counter64,
      pr1646v2ATMImaPerFrDlciMCH2POutDropFilter
         Counter64,
      pr1646v2ATMImaPerFrDlciMCH2PIfOutBandwidth
         Integer32,
      pr1646v2ATMImaPerFrDlciMCH2PIfErrSec
         Counter32
      }

pr1646v2ATMImaPerFrDlciMCH2PTableIx OBJECT-TYPE
   SYNTAX      TableIndex
   MAX-ACCESS  not-accessible
   STATUS      current
   DESCRIPTION
      ""
   ::= {pr1646v2ATMImaPerFrDlciMCH2PEntry 11}

pr1646v2ATMImaPerFrDlciMCH2PSysUpTime OBJECT-TYPE
   SYNTAX      TimeTicks
   MAX-ACCESS  read-only
   STATUS      current
   DESCRIPTION
      "Path: atm.performance.pvcTable.frameRelay.dlciTable.mibCounters.h2Performance.sysUpTime

       Time in centi-second."
   ::= {pr1646v2ATMImaPerFrDlciMCH2PEntry 16777216}

pr1646v2ATMImaPerFrDlciMCH2PIfUpTime OBJECT-TYPE
   SYNTAX      TimeTicks
   MAX-ACCESS  read-only
   STATUS      current
   DESCRIPTION
      "Path: atm.performance.pvcTable.frameRelay.dlciTable.mibCounters.h2Performance.ifUpTime

       Time in centi-second."
   ::= {pr1646v2ATMImaPerFrDlciMCH2PEntry 33554432}

pr1646v2ATMImaPerFrDlciMCH2PIfStatChanges OBJECT-TYPE
   SYNTAX      Counter32
   MAX-ACCESS  read-only
   STATUS      current
   DESCRIPTION
      "Path: atm.performance.pvcTable.frameRelay.dlciTable.mibCounters.h2Performance.ifStatusChanges

       32 bit unsigned wrappable counter."
   ::= {pr1646v2ATMImaPerFrDlciMCH2PEntry 50331648}

pr1646v2ATMImaPerFrDlciMCH2PIfInOctets OBJECT-TYPE
   SYNTAX      Counter64
   MAX-ACCESS  read-only
   STATUS      current
   DESCRIPTION
      "Path: atm.performance.pvcTable.frameRelay.dlciTable.mibCounters.h2Performance.ifInOctets

       64 bit unsigned wrappable counter."
   ::= {pr1646v2ATMImaPerFrDlciMCH2PEntry 67108864}

pr1646v2ATMImaPerFrDlciMCH2PIfInUCPkts OBJECT-TYPE
   SYNTAX      Counter64
   MAX-ACCESS  read-only
   STATUS      current
   DESCRIPTION
      "Path: atm.performance.pvcTable.frameRelay.dlciTable.mibCounters.h2Performance.ifInUcastPkts

       64 bit unsigned wrappable counter."
   ::= {pr1646v2ATMImaPerFrDlciMCH2PEntry 83886080}

pr1646v2ATMImaPerFrDlciMCH2PIfInNUCPkts OBJECT-TYPE
   SYNTAX      Counter64
   MAX-ACCESS  read-only
   STATUS      current
   DESCRIPTION
      "Path: atm.performance.pvcTable.frameRelay.dlciTable.mibCounters.h2Performance.ifInNUcastPkts

       64 bit unsigned wrappable counter."
   ::= {pr1646v2ATMImaPerFrDlciMCH2PEntry 100663296}

pr1646v2ATMImaPerFrDlciMCH2PIfInBCPkts OBJECT-TYPE
   SYNTAX      Counter64
   MAX-ACCESS  read-only
   STATUS      current
   DESCRIPTION
      "Path: atm.performance.pvcTable.frameRelay.dlciTable.mibCounters.h2Performance.ifInBcastPkts

       64 bit unsigned wrappable counter."
   ::= {pr1646v2ATMImaPerFrDlciMCH2PEntry 419430400}

pr1646v2ATMImaPerFrDlciMCH2PIfInMCPkts OBJECT-TYPE
   SYNTAX      Counter64
   MAX-ACCESS  read-only
   STATUS      current
   DESCRIPTION
      "Path: atm.performance.pvcTable.frameRelay.dlciTable.mibCounters.h2Performance.ifInMcastPkts

       64 bit unsigned wrappable counter."
   ::= {pr1646v2ATMImaPerFrDlciMCH2PEntry 436207616}

pr1646v2ATMImaPerFrDlciMCH2PIfInDiscards OBJECT-TYPE
   SYNTAX      Counter64
   MAX-ACCESS  read-only
   STATUS      current
   DESCRIPTION
      "Path: atm.performance.pvcTable.frameRelay.dlciTable.mibCounters.h2Performance.ifInDiscards

       64 bit unsigned wrappable counter."
   ::= {pr1646v2ATMImaPerFrDlciMCH2PEntry 117440512}

pr1646v2ATMImaPerFrDlciMCH2PIfInErrors OBJECT-TYPE
   SYNTAX      Counter64
   MAX-ACCESS  read-only
   STATUS      current
   DESCRIPTION
      "Path: atm.performance.pvcTable.frameRelay.dlciTable.mibCounters.h2Performance.ifInErrors

       64 bit unsigned wrappable counter."
   ::= {pr1646v2ATMImaPerFrDlciMCH2PEntry 134217728}

pr1646v2ATMImaPerFrDlciMCH2PIfInUnkwn OBJECT-TYPE
   SYNTAX      Counter64
   MAX-ACCESS  read-only
   STATUS      current
   DESCRIPTION
      "Path: atm.performance.pvcTable.frameRelay.dlciTable.mibCounters.h2Performance.ifInUnknownProtos

       64 bit unsigned wrappable counter."
   ::= {pr1646v2ATMImaPerFrDlciMCH2PEntry 150994944}

pr1646v2ATMImaPerFrDlciMCH2PInDropEx OBJECT-TYPE
   SYNTAX      Counter64
   MAX-ACCESS  read-only
   STATUS      current
   DESCRIPTION
      "Path: atm.performance.pvcTable.frameRelay.dlciTable.mibCounters.h2Performance.ifInDropLevelExceeded

       64 bit unsigned wrappable counter."
   ::= {pr1646v2ATMImaPerFrDlciMCH2PEntry 335544320}

pr1646v2ATMImaPerFrDlciMCH2PInDropNoMac OBJECT-TYPE
   SYNTAX      Counter64
   MAX-ACCESS  read-only
   STATUS      current
   DESCRIPTION
      "Path: atm.performance.pvcTable.frameRelay.dlciTable.mibCounters.h2Performance.fInDiscardsNoMacFit

       64 bit unsigned wrappable counter."
   ::= {pr1646v2ATMImaPerFrDlciMCH2PEntry 301989888}

pr1646v2ATMImaPerFrDlciMCH2PInDropNUCast OBJECT-TYPE
   SYNTAX      Counter64
   MAX-ACCESS  read-only
   STATUS      current
   DESCRIPTION
      "Path: atm.performance.pvcTable.frameRelay.dlciTable.mibCounters.h2Performance.fInDiscardsNUCast

       64 bit unsigned wrappable counter."
   ::= {pr1646v2ATMImaPerFrDlciMCH2PEntry 318767104}

pr1646v2ATMImaPerFrDlciMCH2PInDropFilter OBJECT-TYPE
   SYNTAX      Counter64
   MAX-ACCESS  read-only
   STATUS      current
   DESCRIPTION
      "Path: atm.performance.pvcTable.frameRelay.dlciTable.mibCounters.h2Performance.fInDiscardsFilter

       64 bit unsigned wrappable counter."
   ::= {pr1646v2ATMImaPerFrDlciMCH2PEntry 385875968}

pr1646v2ATMImaPerFrDlciMCH2PIfInBandwidth OBJECT-TYPE
   SYNTAX      Integer32
   MAX-ACCESS  read-only
   STATUS      current
   DESCRIPTION
      "Path: atm.performance.pvcTable.frameRelay.dlciTable.mibCounters.h2Performance.ifInBandwidth

       unit name = bps
       formula = 8 * ; 8 /"
   ::= {pr1646v2ATMImaPerFrDlciMCH2PEntry 268435456}

pr1646v2ATMImaPerFrDlciMCH2PIfOutOctets OBJECT-TYPE
   SYNTAX      Counter64
   MAX-ACCESS  read-only
   STATUS      current
   DESCRIPTION
      "Path: atm.performance.pvcTable.frameRelay.dlciTable.mibCounters.h2Performance.ifOutOctets

       64 bit unsigned wrappable counter."
   ::= {pr1646v2ATMImaPerFrDlciMCH2PEntry 167772160}

pr1646v2ATMImaPerFrDlciMCH2PIfOutUCPkts OBJECT-TYPE
   SYNTAX      Counter64
   MAX-ACCESS  read-only
   STATUS      current
   DESCRIPTION
      "Path: atm.performance.pvcTable.frameRelay.dlciTable.mibCounters.h2Performance.ifOutUcastPkts

       64 bit unsigned wrappable counter."
   ::= {pr1646v2ATMImaPerFrDlciMCH2PEntry 184549376}

pr1646v2ATMImaPerFrDlciMCH2PIfOutNUCPkts OBJECT-TYPE
   SYNTAX      Counter64
   MAX-ACCESS  read-only
   STATUS      current
   DESCRIPTION
      "Path: atm.performance.pvcTable.frameRelay.dlciTable.mibCounters.h2Performance.ifOutNUcastPkts

       64 bit unsigned wrappable counter."
   ::= {pr1646v2ATMImaPerFrDlciMCH2PEntry 201326592}

pr1646v2ATMImaPerFrDlciMCH2PIfOutBCPkts OBJECT-TYPE
   SYNTAX      Counter64
   MAX-ACCESS  read-only
   STATUS      current
   DESCRIPTION
      "Path: atm.performance.pvcTable.frameRelay.dlciTable.mibCounters.h2Performance.ifOutBcastPkts

       64 bit unsigned wrappable counter."
   ::= {pr1646v2ATMImaPerFrDlciMCH2PEntry 452984832}

pr1646v2ATMImaPerFrDlciMCH2PIfOutMCPkts OBJECT-TYPE
   SYNTAX      Counter64
   MAX-ACCESS  read-only
   STATUS      current
   DESCRIPTION
      "Path: atm.performance.pvcTable.frameRelay.dlciTable.mibCounters.h2Performance.ifOutMcastPkts

       64 bit unsigned wrappable counter."
   ::= {pr1646v2ATMImaPerFrDlciMCH2PEntry 469762048}

pr1646v2ATMImaPerFrDlciMCH2PIfOutDiscards OBJECT-TYPE
   SYNTAX      Counter64
   MAX-ACCESS  read-only
   STATUS      current
   DESCRIPTION
      "Path: atm.performance.pvcTable.frameRelay.dlciTable.mibCounters.h2Performance.ifOutDiscards

       64 bit unsigned wrappable counter."
   ::= {pr1646v2ATMImaPerFrDlciMCH2PEntry 218103808}

pr1646v2ATMImaPerFrDlciMCH2PIfOutErrors OBJECT-TYPE
   SYNTAX      Counter64
   MAX-ACCESS  read-only
   STATUS      current
   DESCRIPTION
      "Path: atm.performance.pvcTable.frameRelay.dlciTable.mibCounters.h2Performance.ifOutErrors

       64 bit unsigned wrappable counter."
   ::= {pr1646v2ATMImaPerFrDlciMCH2PEntry 234881024}

pr1646v2ATMImaPerFrDlciMCH2POutDropEx OBJECT-TYPE
   SYNTAX      Counter64
   MAX-ACCESS  read-only
   STATUS      current
   DESCRIPTION
      "Path: atm.performance.pvcTable.frameRelay.dlciTable.mibCounters.h2Performance.ifOutDropLevelExceeded

       64 bit unsigned wrappable counter."
   ::= {pr1646v2ATMImaPerFrDlciMCH2PEntry 352321536}

pr1646v2ATMImaPerFrDlciMCH2POutDropNoArp OBJECT-TYPE
   SYNTAX      Counter64
   MAX-ACCESS  read-only
   STATUS      current
   DESCRIPTION
      "Path: atm.performance.pvcTable.frameRelay.dlciTable.mibCounters.h2Performance.ifOutDiscardsNoArp

       64 bit unsigned wrappable counter."
   ::= {pr1646v2ATMImaPerFrDlciMCH2PEntry 369098752}

pr1646v2ATMImaPerFrDlciMCH2POutDropFilter OBJECT-TYPE
   SYNTAX      Counter64
   MAX-ACCESS  read-only
   STATUS      current
   DESCRIPTION
      "Path: atm.performance.pvcTable.frameRelay.dlciTable.mibCounters.h2Performance.ifOutDiscardsFilter

       64 bit unsigned wrappable counter."
   ::= {pr1646v2ATMImaPerFrDlciMCH2PEntry 402653184}

pr1646v2ATMImaPerFrDlciMCH2PIfOutBandwidth OBJECT-TYPE
   SYNTAX      Integer32
   MAX-ACCESS  read-only
   STATUS      current
   DESCRIPTION
      "Path: atm.performance.pvcTable.frameRelay.dlciTable.mibCounters.h2Performance.ifOutBandwidth

       unit name = bps
       formula = 8 * ; 8 /"
   ::= {pr1646v2ATMImaPerFrDlciMCH2PEntry 285212672}

pr1646v2ATMImaPerFrDlciMCH2PIfErrSec OBJECT-TYPE
   SYNTAX      Counter32
   MAX-ACCESS  read-only
   STATUS      current
   DESCRIPTION
      "Path: atm.performance.pvcTable.frameRelay.dlciTable.mibCounters.h2Performance.ifErrSec

       32 bit unsigned wrappable counter."
   ::= {pr1646v2ATMImaPerFrDlciMCH2PEntry 251658240}

pr1646v2ATMImaPerFrDlciMCH24P OBJECT-TYPE
   SYNTAX      SEQUENCE OF Pr1646v2ATMImaPerFrDlciMCH24PEntry
   MAX-ACCESS  not-accessible
   STATUS      current
   DESCRIPTION
      ""
   ::= {pr1646v2ATMImaPer 503448187}

pr1646v2ATMImaPerFrDlciMCH24PEntry OBJECT-TYPE
   SYNTAX      Pr1646v2ATMImaPerFrDlciMCH24PEntry
   MAX-ACCESS  not-accessible
   STATUS      current
   DESCRIPTION
      ""
   INDEX      { pr1646v2ATMImaPerTableIx,
                pr1646v2ATMImaPerFrDlciTableIx,
                pr1646v2ATMImaPerFrDlciMCH24PTableIx }
   ::= {pr1646v2ATMImaPerFrDlciMCH24P 1}

Pr1646v2ATMImaPerFrDlciMCH24PEntry ::=
   SEQUENCE
      {
      pr1646v2ATMImaPerFrDlciMCH24PTableIx
         TableIndex,
      pr1646v2ATMImaPerFrDlciMCH24PSysUpTime
         TimeTicks,
      pr1646v2ATMImaPerFrDlciMCH24PIfUpTime
         TimeTicks,
      pr1646v2ATMImaPerFrDlciMCH24PIfStatChanges
         Counter32,
      pr1646v2ATMImaPerFrDlciMCH24PIfInOctets
         Counter64,
      pr1646v2ATMImaPerFrDlciMCH24PIfInUCPkts
         Counter64,
      pr1646v2ATMImaPerFrDlciMCH24PIfInNUCPkts
         Counter64,
      pr1646v2ATMImaPerFrDlciMCH24PIfInBCPkts
         Counter64,
      pr1646v2ATMImaPerFrDlciMCH24PIfInMCPkts
         Counter64,
      pr1646v2ATMImaPerFrDlciMCH24PIfInDiscards
         Counter64,
      pr1646v2ATMImaPerFrDlciMCH24PIfInErrors
         Counter64,
      pr1646v2ATMImaPerFrDlciMCH24PIfInUnkwn
         Counter64,
      pr1646v2ATMImaPerFrDlciMCH24PInDropEx
         Counter64,
      pr1646v2ATMImaPerFrDlciMCH24PInDropNoMac
         Counter64,
      pr1646v2ATMImaPerFrDlciMCH24PInDropNUCast
         Counter64,
      pr1646v2ATMImaPerFrDlciMCH24PInDropFilter
         Counter64,
      pr1646v2ATMImaPerFrDlciMCH24PIfInBandwidth
         Integer32,
      pr1646v2ATMImaPerFrDlciMCH24PIfOutOctets
         Counter64,
      pr1646v2ATMImaPerFrDlciMCH24PIfOutUCPkts
         Counter64,
      pr1646v2ATMImaPerFrDlciMCH24PIfOutNUCPkts
         Counter64,
      pr1646v2ATMImaPerFrDlciMCH24PIfOutBCPkts
         Counter64,
      pr1646v2ATMImaPerFrDlciMCH24PIfOutMCPkts
         Counter64,
      pr1646v2ATMImaPerFrDlciMCH24PIfOutDiscards
         Counter64,
      pr1646v2ATMImaPerFrDlciMCH24PIfOutErrors
         Counter64,
      pr1646v2ATMImaPerFrDlciMCH24POutDropEx
         Counter64,
      pr1646v2ATMImaPerFrDlciMCH24POutDropNoArp
         Counter64,
      pr1646v2ATMImaPerFrDlciMCH24POutDropFilter
         Counter64,
      pr1646v2ATMImaPerFrDlciMCH24PIfOutBandwidth
         Integer32,
      pr1646v2ATMImaPerFrDlciMCH24PIfErrSec
         Counter32
      }

pr1646v2ATMImaPerFrDlciMCH24PTableIx OBJECT-TYPE
   SYNTAX      TableIndex
   MAX-ACCESS  not-accessible
   STATUS      current
   DESCRIPTION
      ""
   ::= {pr1646v2ATMImaPerFrDlciMCH24PEntry 11}

pr1646v2ATMImaPerFrDlciMCH24PSysUpTime OBJECT-TYPE
   SYNTAX      TimeTicks
   MAX-ACCESS  read-only
   STATUS      current
   DESCRIPTION
      "Path: atm.performance.pvcTable.frameRelay.dlciTable.mibCounters.h24Performance.sysUpTime

       Time in centi-second."
   ::= {pr1646v2ATMImaPerFrDlciMCH24PEntry 16777216}

pr1646v2ATMImaPerFrDlciMCH24PIfUpTime OBJECT-TYPE
   SYNTAX      TimeTicks
   MAX-ACCESS  read-only
   STATUS      current
   DESCRIPTION
      "Path: atm.performance.pvcTable.frameRelay.dlciTable.mibCounters.h24Performance.ifUpTime

       Time in centi-second."
   ::= {pr1646v2ATMImaPerFrDlciMCH24PEntry 33554432}

pr1646v2ATMImaPerFrDlciMCH24PIfStatChanges OBJECT-TYPE
   SYNTAX      Counter32
   MAX-ACCESS  read-only
   STATUS      current
   DESCRIPTION
      "Path: atm.performance.pvcTable.frameRelay.dlciTable.mibCounters.h24Performance.ifStatusChanges

       32 bit unsigned wrappable counter."
   ::= {pr1646v2ATMImaPerFrDlciMCH24PEntry 50331648}

pr1646v2ATMImaPerFrDlciMCH24PIfInOctets OBJECT-TYPE
   SYNTAX      Counter64
   MAX-ACCESS  read-only
   STATUS      current
   DESCRIPTION
      "Path: atm.performance.pvcTable.frameRelay.dlciTable.mibCounters.h24Performance.ifInOctets

       64 bit unsigned wrappable counter."
   ::= {pr1646v2ATMImaPerFrDlciMCH24PEntry 67108864}

pr1646v2ATMImaPerFrDlciMCH24PIfInUCPkts OBJECT-TYPE
   SYNTAX      Counter64
   MAX-ACCESS  read-only
   STATUS      current
   DESCRIPTION
      "Path: atm.performance.pvcTable.frameRelay.dlciTable.mibCounters.h24Performance.ifInUcastPkts

       64 bit unsigned wrappable counter."
   ::= {pr1646v2ATMImaPerFrDlciMCH24PEntry 83886080}

pr1646v2ATMImaPerFrDlciMCH24PIfInNUCPkts OBJECT-TYPE
   SYNTAX      Counter64
   MAX-ACCESS  read-only
   STATUS      current
   DESCRIPTION
      "Path: atm.performance.pvcTable.frameRelay.dlciTable.mibCounters.h24Performance.ifInNUcastPkts

       64 bit unsigned wrappable counter."
   ::= {pr1646v2ATMImaPerFrDlciMCH24PEntry 100663296}

pr1646v2ATMImaPerFrDlciMCH24PIfInBCPkts OBJECT-TYPE
   SYNTAX      Counter64
   MAX-ACCESS  read-only
   STATUS      current
   DESCRIPTION
      "Path: atm.performance.pvcTable.frameRelay.dlciTable.mibCounters.h24Performance.ifInBcastPkts

       64 bit unsigned wrappable counter."
   ::= {pr1646v2ATMImaPerFrDlciMCH24PEntry 419430400}

pr1646v2ATMImaPerFrDlciMCH24PIfInMCPkts OBJECT-TYPE
   SYNTAX      Counter64
   MAX-ACCESS  read-only
   STATUS      current
   DESCRIPTION
      "Path: atm.performance.pvcTable.frameRelay.dlciTable.mibCounters.h24Performance.ifInMcastPkts

       64 bit unsigned wrappable counter."
   ::= {pr1646v2ATMImaPerFrDlciMCH24PEntry 436207616}

pr1646v2ATMImaPerFrDlciMCH24PIfInDiscards OBJECT-TYPE
   SYNTAX      Counter64
   MAX-ACCESS  read-only
   STATUS      current
   DESCRIPTION
      "Path: atm.performance.pvcTable.frameRelay.dlciTable.mibCounters.h24Performance.ifInDiscards

       64 bit unsigned wrappable counter."
   ::= {pr1646v2ATMImaPerFrDlciMCH24PEntry 117440512}

pr1646v2ATMImaPerFrDlciMCH24PIfInErrors OBJECT-TYPE
   SYNTAX      Counter64
   MAX-ACCESS  read-only
   STATUS      current
   DESCRIPTION
      "Path: atm.performance.pvcTable.frameRelay.dlciTable.mibCounters.h24Performance.ifInErrors

       64 bit unsigned wrappable counter."
   ::= {pr1646v2ATMImaPerFrDlciMCH24PEntry 134217728}

pr1646v2ATMImaPerFrDlciMCH24PIfInUnkwn OBJECT-TYPE
   SYNTAX      Counter64
   MAX-ACCESS  read-only
   STATUS      current
   DESCRIPTION
      "Path: atm.performance.pvcTable.frameRelay.dlciTable.mibCounters.h24Performance.ifInUnknownProtos

       64 bit unsigned wrappable counter."
   ::= {pr1646v2ATMImaPerFrDlciMCH24PEntry 150994944}

pr1646v2ATMImaPerFrDlciMCH24PInDropEx OBJECT-TYPE
   SYNTAX      Counter64
   MAX-ACCESS  read-only
   STATUS      current
   DESCRIPTION
      "Path: atm.performance.pvcTable.frameRelay.dlciTable.mibCounters.h24Performance.ifInDropLevelExceeded

       64 bit unsigned wrappable counter."
   ::= {pr1646v2ATMImaPerFrDlciMCH24PEntry 335544320}

pr1646v2ATMImaPerFrDlciMCH24PInDropNoMac OBJECT-TYPE
   SYNTAX      Counter64
   MAX-ACCESS  read-only
   STATUS      current
   DESCRIPTION
      "Path: atm.performance.pvcTable.frameRelay.dlciTable.mibCounters.h24Performance.fInDiscardsNoMacFit

       64 bit unsigned wrappable counter."
   ::= {pr1646v2ATMImaPerFrDlciMCH24PEntry 301989888}

pr1646v2ATMImaPerFrDlciMCH24PInDropNUCast OBJECT-TYPE
   SYNTAX      Counter64
   MAX-ACCESS  read-only
   STATUS      current
   DESCRIPTION
      "Path: atm.performance.pvcTable.frameRelay.dlciTable.mibCounters.h24Performance.fInDiscardsNUCast

       64 bit unsigned wrappable counter."
   ::= {pr1646v2ATMImaPerFrDlciMCH24PEntry 318767104}

pr1646v2ATMImaPerFrDlciMCH24PInDropFilter OBJECT-TYPE
   SYNTAX      Counter64
   MAX-ACCESS  read-only
   STATUS      current
   DESCRIPTION
      "Path: atm.performance.pvcTable.frameRelay.dlciTable.mibCounters.h24Performance.fInDiscardsFilter

       64 bit unsigned wrappable counter."
   ::= {pr1646v2ATMImaPerFrDlciMCH24PEntry 385875968}

pr1646v2ATMImaPerFrDlciMCH24PIfInBandwidth OBJECT-TYPE
   SYNTAX      Integer32
   MAX-ACCESS  read-only
   STATUS      current
   DESCRIPTION
      "Path: atm.performance.pvcTable.frameRelay.dlciTable.mibCounters.h24Performance.ifInBandwidth

       unit name = bps
       formula = 8 * ; 8 /"
   ::= {pr1646v2ATMImaPerFrDlciMCH24PEntry 268435456}

pr1646v2ATMImaPerFrDlciMCH24PIfOutOctets OBJECT-TYPE
   SYNTAX      Counter64
   MAX-ACCESS  read-only
   STATUS      current
   DESCRIPTION
      "Path: atm.performance.pvcTable.frameRelay.dlciTable.mibCounters.h24Performance.ifOutOctets

       64 bit unsigned wrappable counter."
   ::= {pr1646v2ATMImaPerFrDlciMCH24PEntry 167772160}

pr1646v2ATMImaPerFrDlciMCH24PIfOutUCPkts OBJECT-TYPE
   SYNTAX      Counter64
   MAX-ACCESS  read-only
   STATUS      current
   DESCRIPTION
      "Path: atm.performance.pvcTable.frameRelay.dlciTable.mibCounters.h24Performance.ifOutUcastPkts

       64 bit unsigned wrappable counter."
   ::= {pr1646v2ATMImaPerFrDlciMCH24PEntry 184549376}

pr1646v2ATMImaPerFrDlciMCH24PIfOutNUCPkts OBJECT-TYPE
   SYNTAX      Counter64
   MAX-ACCESS  read-only
   STATUS      current
   DESCRIPTION
      "Path: atm.performance.pvcTable.frameRelay.dlciTable.mibCounters.h24Performance.ifOutNUcastPkts

       64 bit unsigned wrappable counter."
   ::= {pr1646v2ATMImaPerFrDlciMCH24PEntry 201326592}

pr1646v2ATMImaPerFrDlciMCH24PIfOutBCPkts OBJECT-TYPE
   SYNTAX      Counter64
   MAX-ACCESS  read-only
   STATUS      current
   DESCRIPTION
      "Path: atm.performance.pvcTable.frameRelay.dlciTable.mibCounters.h24Performance.ifOutBcastPkts

       64 bit unsigned wrappable counter."
   ::= {pr1646v2ATMImaPerFrDlciMCH24PEntry 452984832}

pr1646v2ATMImaPerFrDlciMCH24PIfOutMCPkts OBJECT-TYPE
   SYNTAX      Counter64
   MAX-ACCESS  read-only
   STATUS      current
   DESCRIPTION
      "Path: atm.performance.pvcTable.frameRelay.dlciTable.mibCounters.h24Performance.ifOutMcastPkts

       64 bit unsigned wrappable counter."
   ::= {pr1646v2ATMImaPerFrDlciMCH24PEntry 469762048}

pr1646v2ATMImaPerFrDlciMCH24PIfOutDiscards OBJECT-TYPE
   SYNTAX      Counter64
   MAX-ACCESS  read-only
   STATUS      current
   DESCRIPTION
      "Path: atm.performance.pvcTable.frameRelay.dlciTable.mibCounters.h24Performance.ifOutDiscards

       64 bit unsigned wrappable counter."
   ::= {pr1646v2ATMImaPerFrDlciMCH24PEntry 218103808}

pr1646v2ATMImaPerFrDlciMCH24PIfOutErrors OBJECT-TYPE
   SYNTAX      Counter64
   MAX-ACCESS  read-only
   STATUS      current
   DESCRIPTION
      "Path: atm.performance.pvcTable.frameRelay.dlciTable.mibCounters.h24Performance.ifOutErrors

       64 bit unsigned wrappable counter."
   ::= {pr1646v2ATMImaPerFrDlciMCH24PEntry 234881024}

pr1646v2ATMImaPerFrDlciMCH24POutDropEx OBJECT-TYPE
   SYNTAX      Counter64
   MAX-ACCESS  read-only
   STATUS      current
   DESCRIPTION
      "Path: atm.performance.pvcTable.frameRelay.dlciTable.mibCounters.h24Performance.ifOutDropLevelExceeded

       64 bit unsigned wrappable counter."
   ::= {pr1646v2ATMImaPerFrDlciMCH24PEntry 352321536}

pr1646v2ATMImaPerFrDlciMCH24POutDropNoArp OBJECT-TYPE
   SYNTAX      Counter64
   MAX-ACCESS  read-only
   STATUS      current
   DESCRIPTION
      "Path: atm.performance.pvcTable.frameRelay.dlciTable.mibCounters.h24Performance.ifOutDiscardsNoArp

       64 bit unsigned wrappable counter."
   ::= {pr1646v2ATMImaPerFrDlciMCH24PEntry 369098752}

pr1646v2ATMImaPerFrDlciMCH24POutDropFilter OBJECT-TYPE
   SYNTAX      Counter64
   MAX-ACCESS  read-only
   STATUS      current
   DESCRIPTION
      "Path: atm.performance.pvcTable.frameRelay.dlciTable.mibCounters.h24Performance.ifOutDiscardsFilter

       64 bit unsigned wrappable counter."
   ::= {pr1646v2ATMImaPerFrDlciMCH24PEntry 402653184}

pr1646v2ATMImaPerFrDlciMCH24PIfOutBandwidth OBJECT-TYPE
   SYNTAX      Integer32
   MAX-ACCESS  read-only
   STATUS      current
   DESCRIPTION
      "Path: atm.performance.pvcTable.frameRelay.dlciTable.mibCounters.h24Performance.ifOutBandwidth

       unit name = bps
       formula = 8 * ; 8 /"
   ::= {pr1646v2ATMImaPerFrDlciMCH24PEntry 285212672}

pr1646v2ATMImaPerFrDlciMCH24PIfErrSec OBJECT-TYPE
   SYNTAX      Counter32
   MAX-ACCESS  read-only
   STATUS      current
   DESCRIPTION
      "Path: atm.performance.pvcTable.frameRelay.dlciTable.mibCounters.h24Performance.ifErrSec

       32 bit unsigned wrappable counter."
   ::= {pr1646v2ATMImaPerFrDlciMCH24PEntry 251658240}

pr1646v2ATMImaPerFrDlciMCD7P OBJECT-TYPE
   SYNTAX      SEQUENCE OF Pr1646v2ATMImaPerFrDlciMCD7PEntry
   MAX-ACCESS  not-accessible
   STATUS      current
   DESCRIPTION
      ""
   ::= {pr1646v2ATMImaPer 503448188}

pr1646v2ATMImaPerFrDlciMCD7PEntry OBJECT-TYPE
   SYNTAX      Pr1646v2ATMImaPerFrDlciMCD7PEntry
   MAX-ACCESS  not-accessible
   STATUS      current
   DESCRIPTION
      ""
   INDEX      { pr1646v2ATMImaPerTableIx,
                pr1646v2ATMImaPerFrDlciTableIx,
                pr1646v2ATMImaPerFrDlciMCD7PTableIx }
   ::= {pr1646v2ATMImaPerFrDlciMCD7P 1}

Pr1646v2ATMImaPerFrDlciMCD7PEntry ::=
   SEQUENCE
      {
      pr1646v2ATMImaPerFrDlciMCD7PTableIx
         TableIndex,
      pr1646v2ATMImaPerFrDlciMCD7PSysUpTime
         TimeTicks,
      pr1646v2ATMImaPerFrDlciMCD7PIfUpTime
         TimeTicks,
      pr1646v2ATMImaPerFrDlciMCD7PIfStatChanges
         Counter32,
      pr1646v2ATMImaPerFrDlciMCD7PIfInOctets
         Counter64,
      pr1646v2ATMImaPerFrDlciMCD7PIfInUCPkts
         Counter64,
      pr1646v2ATMImaPerFrDlciMCD7PIfInNUCPkts
         Counter64,
      pr1646v2ATMImaPerFrDlciMCD7PIfInBCPkts
         Counter64,
      pr1646v2ATMImaPerFrDlciMCD7PIfInMCPkts
         Counter64,
      pr1646v2ATMImaPerFrDlciMCD7PIfInDiscards
         Counter64,
      pr1646v2ATMImaPerFrDlciMCD7PIfInErrors
         Counter64,
      pr1646v2ATMImaPerFrDlciMCD7PIfInUnkwn
         Counter64,
      pr1646v2ATMImaPerFrDlciMCD7PInDropEx
         Counter64,
      pr1646v2ATMImaPerFrDlciMCD7PInDropNoMac
         Counter64,
      pr1646v2ATMImaPerFrDlciMCD7PInDropNUCast
         Counter64,
      pr1646v2ATMImaPerFrDlciMCD7PInDropFilter
         Counter64,
      pr1646v2ATMImaPerFrDlciMCD7PIfInBandwidth
         Integer32,
      pr1646v2ATMImaPerFrDlciMCD7PIfOutOctets
         Counter64,
      pr1646v2ATMImaPerFrDlciMCD7PIfOutUCPkts
         Counter64,
      pr1646v2ATMImaPerFrDlciMCD7PIfOutNUCPkts
         Counter64,
      pr1646v2ATMImaPerFrDlciMCD7PIfOutBCPkts
         Counter64,
      pr1646v2ATMImaPerFrDlciMCD7PIfOutMCPkts
         Counter64,
      pr1646v2ATMImaPerFrDlciMCD7PIfOutDiscards
         Counter64,
      pr1646v2ATMImaPerFrDlciMCD7PIfOutErrors
         Counter64,
      pr1646v2ATMImaPerFrDlciMCD7POutDropEx
         Counter64,
      pr1646v2ATMImaPerFrDlciMCD7POutDropNoArp
         Counter64,
      pr1646v2ATMImaPerFrDlciMCD7POutDropFilter
         Counter64,
      pr1646v2ATMImaPerFrDlciMCD7PIfOutBandwidth
         Integer32,
      pr1646v2ATMImaPerFrDlciMCD7PIfErrSec
         Counter32
      }

pr1646v2ATMImaPerFrDlciMCD7PTableIx OBJECT-TYPE
   SYNTAX      TableIndex
   MAX-ACCESS  not-accessible
   STATUS      current
   DESCRIPTION
      ""
   ::= {pr1646v2ATMImaPerFrDlciMCD7PEntry 11}

pr1646v2ATMImaPerFrDlciMCD7PSysUpTime OBJECT-TYPE
   SYNTAX      TimeTicks
   MAX-ACCESS  read-only
   STATUS      current
   DESCRIPTION
      "Path: atm.performance.pvcTable.frameRelay.dlciTable.mibCounters.d7Performance.sysUpTime

       Time in centi-second."
   ::= {pr1646v2ATMImaPerFrDlciMCD7PEntry 16777216}

pr1646v2ATMImaPerFrDlciMCD7PIfUpTime OBJECT-TYPE
   SYNTAX      TimeTicks
   MAX-ACCESS  read-only
   STATUS      current
   DESCRIPTION
      "Path: atm.performance.pvcTable.frameRelay.dlciTable.mibCounters.d7Performance.ifUpTime

       Time in centi-second."
   ::= {pr1646v2ATMImaPerFrDlciMCD7PEntry 33554432}

pr1646v2ATMImaPerFrDlciMCD7PIfStatChanges OBJECT-TYPE
   SYNTAX      Counter32
   MAX-ACCESS  read-only
   STATUS      current
   DESCRIPTION
      "Path: atm.performance.pvcTable.frameRelay.dlciTable.mibCounters.d7Performance.ifStatusChanges

       32 bit unsigned wrappable counter."
   ::= {pr1646v2ATMImaPerFrDlciMCD7PEntry 50331648}

pr1646v2ATMImaPerFrDlciMCD7PIfInOctets OBJECT-TYPE
   SYNTAX      Counter64
   MAX-ACCESS  read-only
   STATUS      current
   DESCRIPTION
      "Path: atm.performance.pvcTable.frameRelay.dlciTable.mibCounters.d7Performance.ifInOctets

       64 bit unsigned wrappable counter."
   ::= {pr1646v2ATMImaPerFrDlciMCD7PEntry 67108864}

pr1646v2ATMImaPerFrDlciMCD7PIfInUCPkts OBJECT-TYPE
   SYNTAX      Counter64
   MAX-ACCESS  read-only
   STATUS      current
   DESCRIPTION
      "Path: atm.performance.pvcTable.frameRelay.dlciTable.mibCounters.d7Performance.ifInUcastPkts

       64 bit unsigned wrappable counter."
   ::= {pr1646v2ATMImaPerFrDlciMCD7PEntry 83886080}

pr1646v2ATMImaPerFrDlciMCD7PIfInNUCPkts OBJECT-TYPE
   SYNTAX      Counter64
   MAX-ACCESS  read-only
   STATUS      current
   DESCRIPTION
      "Path: atm.performance.pvcTable.frameRelay.dlciTable.mibCounters.d7Performance.ifInNUcastPkts

       64 bit unsigned wrappable counter."
   ::= {pr1646v2ATMImaPerFrDlciMCD7PEntry 100663296}

pr1646v2ATMImaPerFrDlciMCD7PIfInBCPkts OBJECT-TYPE
   SYNTAX      Counter64
   MAX-ACCESS  read-only
   STATUS      current
   DESCRIPTION
      "Path: atm.performance.pvcTable.frameRelay.dlciTable.mibCounters.d7Performance.ifInBcastPkts

       64 bit unsigned wrappable counter."
   ::= {pr1646v2ATMImaPerFrDlciMCD7PEntry 419430400}

pr1646v2ATMImaPerFrDlciMCD7PIfInMCPkts OBJECT-TYPE
   SYNTAX      Counter64
   MAX-ACCESS  read-only
   STATUS      current
   DESCRIPTION
      "Path: atm.performance.pvcTable.frameRelay.dlciTable.mibCounters.d7Performance.ifInMcastPkts

       64 bit unsigned wrappable counter."
   ::= {pr1646v2ATMImaPerFrDlciMCD7PEntry 436207616}

pr1646v2ATMImaPerFrDlciMCD7PIfInDiscards OBJECT-TYPE
   SYNTAX      Counter64
   MAX-ACCESS  read-only
   STATUS      current
   DESCRIPTION
      "Path: atm.performance.pvcTable.frameRelay.dlciTable.mibCounters.d7Performance.ifInDiscards

       64 bit unsigned wrappable counter."
   ::= {pr1646v2ATMImaPerFrDlciMCD7PEntry 117440512}

pr1646v2ATMImaPerFrDlciMCD7PIfInErrors OBJECT-TYPE
   SYNTAX      Counter64
   MAX-ACCESS  read-only
   STATUS      current
   DESCRIPTION
      "Path: atm.performance.pvcTable.frameRelay.dlciTable.mibCounters.d7Performance.ifInErrors

       64 bit unsigned wrappable counter."
   ::= {pr1646v2ATMImaPerFrDlciMCD7PEntry 134217728}

pr1646v2ATMImaPerFrDlciMCD7PIfInUnkwn OBJECT-TYPE
   SYNTAX      Counter64
   MAX-ACCESS  read-only
   STATUS      current
   DESCRIPTION
      "Path: atm.performance.pvcTable.frameRelay.dlciTable.mibCounters.d7Performance.ifInUnknownProtos

       64 bit unsigned wrappable counter."
   ::= {pr1646v2ATMImaPerFrDlciMCD7PEntry 150994944}

pr1646v2ATMImaPerFrDlciMCD7PInDropEx OBJECT-TYPE
   SYNTAX      Counter64
   MAX-ACCESS  read-only
   STATUS      current
   DESCRIPTION
      "Path: atm.performance.pvcTable.frameRelay.dlciTable.mibCounters.d7Performance.ifInDropLevelExceeded

       64 bit unsigned wrappable counter."
   ::= {pr1646v2ATMImaPerFrDlciMCD7PEntry 335544320}

pr1646v2ATMImaPerFrDlciMCD7PInDropNoMac OBJECT-TYPE
   SYNTAX      Counter64
   MAX-ACCESS  read-only
   STATUS      current
   DESCRIPTION
      "Path: atm.performance.pvcTable.frameRelay.dlciTable.mibCounters.d7Performance.fInDiscardsNoMacFit

       64 bit unsigned wrappable counter."
   ::= {pr1646v2ATMImaPerFrDlciMCD7PEntry 301989888}

pr1646v2ATMImaPerFrDlciMCD7PInDropNUCast OBJECT-TYPE
   SYNTAX      Counter64
   MAX-ACCESS  read-only
   STATUS      current
   DESCRIPTION
      "Path: atm.performance.pvcTable.frameRelay.dlciTable.mibCounters.d7Performance.fInDiscardsNUCast

       64 bit unsigned wrappable counter."
   ::= {pr1646v2ATMImaPerFrDlciMCD7PEntry 318767104}

pr1646v2ATMImaPerFrDlciMCD7PInDropFilter OBJECT-TYPE
   SYNTAX      Counter64
   MAX-ACCESS  read-only
   STATUS      current
   DESCRIPTION
      "Path: atm.performance.pvcTable.frameRelay.dlciTable.mibCounters.d7Performance.fInDiscardsFilter

       64 bit unsigned wrappable counter."
   ::= {pr1646v2ATMImaPerFrDlciMCD7PEntry 385875968}

pr1646v2ATMImaPerFrDlciMCD7PIfInBandwidth OBJECT-TYPE
   SYNTAX      Integer32
   MAX-ACCESS  read-only
   STATUS      current
   DESCRIPTION
      "Path: atm.performance.pvcTable.frameRelay.dlciTable.mibCounters.d7Performance.ifInBandwidth

       unit name = bps
       formula = 8 * ; 8 /"
   ::= {pr1646v2ATMImaPerFrDlciMCD7PEntry 268435456}

pr1646v2ATMImaPerFrDlciMCD7PIfOutOctets OBJECT-TYPE
   SYNTAX      Counter64
   MAX-ACCESS  read-only
   STATUS      current
   DESCRIPTION
      "Path: atm.performance.pvcTable.frameRelay.dlciTable.mibCounters.d7Performance.ifOutOctets

       64 bit unsigned wrappable counter."
   ::= {pr1646v2ATMImaPerFrDlciMCD7PEntry 167772160}

pr1646v2ATMImaPerFrDlciMCD7PIfOutUCPkts OBJECT-TYPE
   SYNTAX      Counter64
   MAX-ACCESS  read-only
   STATUS      current
   DESCRIPTION
      "Path: atm.performance.pvcTable.frameRelay.dlciTable.mibCounters.d7Performance.ifOutUcastPkts

       64 bit unsigned wrappable counter."
   ::= {pr1646v2ATMImaPerFrDlciMCD7PEntry 184549376}

pr1646v2ATMImaPerFrDlciMCD7PIfOutNUCPkts OBJECT-TYPE
   SYNTAX      Counter64
   MAX-ACCESS  read-only
   STATUS      current
   DESCRIPTION
      "Path: atm.performance.pvcTable.frameRelay.dlciTable.mibCounters.d7Performance.ifOutNUcastPkts

       64 bit unsigned wrappable counter."
   ::= {pr1646v2ATMImaPerFrDlciMCD7PEntry 201326592}

pr1646v2ATMImaPerFrDlciMCD7PIfOutBCPkts OBJECT-TYPE
   SYNTAX      Counter64
   MAX-ACCESS  read-only
   STATUS      current
   DESCRIPTION
      "Path: atm.performance.pvcTable.frameRelay.dlciTable.mibCounters.d7Performance.ifOutBcastPkts

       64 bit unsigned wrappable counter."
   ::= {pr1646v2ATMImaPerFrDlciMCD7PEntry 452984832}

pr1646v2ATMImaPerFrDlciMCD7PIfOutMCPkts OBJECT-TYPE
   SYNTAX      Counter64
   MAX-ACCESS  read-only
   STATUS      current
   DESCRIPTION
      "Path: atm.performance.pvcTable.frameRelay.dlciTable.mibCounters.d7Performance.ifOutMcastPkts

       64 bit unsigned wrappable counter."
   ::= {pr1646v2ATMImaPerFrDlciMCD7PEntry 469762048}

pr1646v2ATMImaPerFrDlciMCD7PIfOutDiscards OBJECT-TYPE
   SYNTAX      Counter64
   MAX-ACCESS  read-only
   STATUS      current
   DESCRIPTION
      "Path: atm.performance.pvcTable.frameRelay.dlciTable.mibCounters.d7Performance.ifOutDiscards

       64 bit unsigned wrappable counter."
   ::= {pr1646v2ATMImaPerFrDlciMCD7PEntry 218103808}

pr1646v2ATMImaPerFrDlciMCD7PIfOutErrors OBJECT-TYPE
   SYNTAX      Counter64
   MAX-ACCESS  read-only
   STATUS      current
   DESCRIPTION
      "Path: atm.performance.pvcTable.frameRelay.dlciTable.mibCounters.d7Performance.ifOutErrors

       64 bit unsigned wrappable counter."
   ::= {pr1646v2ATMImaPerFrDlciMCD7PEntry 234881024}

pr1646v2ATMImaPerFrDlciMCD7POutDropEx OBJECT-TYPE
   SYNTAX      Counter64
   MAX-ACCESS  read-only
   STATUS      current
   DESCRIPTION
      "Path: atm.performance.pvcTable.frameRelay.dlciTable.mibCounters.d7Performance.ifOutDropLevelExceeded

       64 bit unsigned wrappable counter."
   ::= {pr1646v2ATMImaPerFrDlciMCD7PEntry 352321536}

pr1646v2ATMImaPerFrDlciMCD7POutDropNoArp OBJECT-TYPE
   SYNTAX      Counter64
   MAX-ACCESS  read-only
   STATUS      current
   DESCRIPTION
      "Path: atm.performance.pvcTable.frameRelay.dlciTable.mibCounters.d7Performance.ifOutDiscardsNoArp

       64 bit unsigned wrappable counter."
   ::= {pr1646v2ATMImaPerFrDlciMCD7PEntry 369098752}

pr1646v2ATMImaPerFrDlciMCD7POutDropFilter OBJECT-TYPE
   SYNTAX      Counter64
   MAX-ACCESS  read-only
   STATUS      current
   DESCRIPTION
      "Path: atm.performance.pvcTable.frameRelay.dlciTable.mibCounters.d7Performance.ifOutDiscardsFilter

       64 bit unsigned wrappable counter."
   ::= {pr1646v2ATMImaPerFrDlciMCD7PEntry 402653184}

pr1646v2ATMImaPerFrDlciMCD7PIfOutBandwidth OBJECT-TYPE
   SYNTAX      Integer32
   MAX-ACCESS  read-only
   STATUS      current
   DESCRIPTION
      "Path: atm.performance.pvcTable.frameRelay.dlciTable.mibCounters.d7Performance.ifOutBandwidth

       unit name = bps
       formula = 8 * ; 8 /"
   ::= {pr1646v2ATMImaPerFrDlciMCD7PEntry 285212672}

pr1646v2ATMImaPerFrDlciMCD7PIfErrSec OBJECT-TYPE
   SYNTAX      Counter32
   MAX-ACCESS  read-only
   STATUS      current
   DESCRIPTION
      "Path: atm.performance.pvcTable.frameRelay.dlciTable.mibCounters.d7Performance.ifErrSec

       32 bit unsigned wrappable counter."
   ::= {pr1646v2ATMImaPerFrDlciMCD7PEntry 251658240}

pr1646v2ATMImaPerFrDlciInPQs OBJECT-TYPE
   SYNTAX      SEQUENCE OF Pr1646v2ATMImaPerFrDlciInPQsEntry
   MAX-ACCESS  not-accessible
   STATUS      current
   DESCRIPTION
      ""
   ::= {pr1646v2ATMImaPer 503449088}

pr1646v2ATMImaPerFrDlciInPQsEntry OBJECT-TYPE
   SYNTAX      Pr1646v2ATMImaPerFrDlciInPQsEntry
   MAX-ACCESS  not-accessible
   STATUS      current
   DESCRIPTION
      ""
   INDEX      { pr1646v2ATMImaPerTableIx,
                pr1646v2ATMImaPerFrDlciTableIx,
                pr1646v2ATMImaPerFrDlciInPQsTableIx }
   ::= {pr1646v2ATMImaPerFrDlciInPQs 1}

Pr1646v2ATMImaPerFrDlciInPQsEntry ::=
   SEQUENCE
      {
      pr1646v2ATMImaPerFrDlciInPQsTableIx
         TableIndex,
      pr1646v2ATMImaPerFrDlciInPQsName
         INTEGER,
      pr1646v2ATMImaPerFrDlciInPQsLength
         Integer32,
      pr1646v2ATMImaPerFrDlciInPQsOctetLength
         Integer32,
      pr1646v2ATMImaPerFrDlciInPQsRedLength
         Integer32,
      pr1646v2ATMImaPerFrDlciInPQsPacketsTotal
         Counter64,
      pr1646v2ATMImaPerFrDlciInPQsPacketsDirectTx
         Counter64,
      pr1646v2ATMImaPerFrDlciInPQsPacketsQueued
         Counter64,
      pr1646v2ATMImaPerFrDlciInPQsPacketsDropped
         Counter64,
      pr1646v2ATMImaPerFrDlciInPQsPacketsRedDropped
         Counter64,
      pr1646v2ATMImaPerFrDlciInPQsPacketsCirTx
         Counter64,
      pr1646v2ATMImaPerFrDlciInPQsPacketsEirTx
         Counter64,
      pr1646v2ATMImaPerFrDlciInPQsPacketsViolateTx
         Counter64,
      pr1646v2ATMImaPerFrDlciInPQsOctetsTotal
         Counter64,
      pr1646v2ATMImaPerFrDlciInPQsOctetsDirectTx
         Counter64,
      pr1646v2ATMImaPerFrDlciInPQsOctetsQueued
         Counter64,
      pr1646v2ATMImaPerFrDlciInPQsOctetsDropped
         Counter64,
      pr1646v2ATMImaPerFrDlciInPQsOctetsRedDropped
         Counter64,
      pr1646v2ATMImaPerFrDlciInPQsOctetsCirTx
         Counter64,
      pr1646v2ATMImaPerFrDlciInPQsOctetsEirTx
         Counter64,
      pr1646v2ATMImaPerFrDlciInPQsOctetsViolateTx
         Counter64,
      pr1646v2ATMImaPerFrDlciInPQsOctetsBandwidth15sec
         Integer32,
      pr1646v2ATMImaPerFrDlciInPQsOctetsBandwidth30sec
         Integer32,
      pr1646v2ATMImaPerFrDlciInPQsOctetsBandwidth1min
         Integer32,
      pr1646v2ATMImaPerFrDlciInPQsOctetsBandwidth2min
         Integer32,
      pr1646v2ATMImaPerFrDlciInPQsOctetsBandwidth5min
         Integer32
      }

pr1646v2ATMImaPerFrDlciInPQsTableIx OBJECT-TYPE
   SYNTAX      TableIndex
   MAX-ACCESS  not-accessible
   STATUS      current
   DESCRIPTION
      ""
   ::= {pr1646v2ATMImaPerFrDlciInPQsEntry 11}

pr1646v2ATMImaPerFrDlciInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.frameRelay.dlciTable.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMImaPerFrDlciInPQsEntry 16777216}

pr1646v2ATMImaPerFrDlciInPQsLength OBJECT-TYPE
   SYNTAX      Integer32
   MAX-ACCESS  read-only
   STATUS      current
   DESCRIPTION
      "Path: atm.performance.pvcTable.frameRelay.dlciTable.inPriorityQueues.length"
   ::= {pr1646v2ATMImaPerFrDlciInPQsEntry 33554432}

pr1646v2ATMImaPerFrDlciInPQsOctetLength OBJECT-TYPE
   SYNTAX      Integer32
   MAX-ACCESS  read-only
   STATUS      current
   DESCRIPTION
      "Path: atm.performance.pvcTable.frameRelay.dlciTable.inPriorityQueues.octetLength"
   ::= {pr1646v2ATMImaPerFrDlciInPQsEntry 150994944}

pr1646v2ATMImaPerFrDlciInPQsRedLength OBJECT-TYPE
   SYNTAX      Integer32
   MAX-ACCESS  read-only
   STATUS      current
   DESCRIPTION
      "Path: atm.performance.pvcTable.frameRelay.dlciTable.inPriorityQueues.redLength"
   ::= {pr1646v2ATMImaPerFrDlciInPQsEntry 134217728}

pr1646v2ATMImaPerFrDlciInPQsPacketsTotal OBJECT-TYPE
   SYNTAX      Counter64
   MAX-ACCESS  read-only
   STATUS      current
   DESCRIPTION
      "Path: atm.performance.pvcTable.frameRelay.dlciTable.inPriorityQueues.packets.total

       64 bit unsigned wrappable counter."
   ::= {pr1646v2ATMImaPerFrDlciInPQsEntry 50790400}

pr1646v2ATMImaPerFrDlciInPQsPacketsDirectTx OBJECT-TYPE
   SYNTAX      Counter64
   MAX-ACCESS  read-only
   STATUS      current
   DESCRIPTION
      "Path: atm.performance.pvcTable.frameRelay.dlciTable.inPriorityQueues.packets.directTx

       64 bit unsigned wrappable counter."
   ::= {pr1646v2ATMImaPerFrDlciInPQsEntry 50397184}

pr1646v2ATMImaPerFrDlciInPQsPacketsQueued OBJECT-TYPE
   SYNTAX      Counter64
   MAX-ACCESS  read-only
   STATUS      current
   DESCRIPTION
      "Path: atm.performance.pvcTable.frameRelay.dlciTable.inPriorityQueues.packets.queued

       64 bit unsigned wrappable counter."
   ::= {pr1646v2ATMImaPerFrDlciInPQsEntry 50462720}

pr1646v2ATMImaPerFrDlciInPQsPacketsDropped OBJECT-TYPE
   SYNTAX      Counter64
   MAX-ACCESS  read-only
   STATUS      current
   DESCRIPTION
      "Path: atm.performance.pvcTable.frameRelay.dlciTable.inPriorityQueues.packets.dropped

       64 bit unsigned wrappable counter."
   ::= {pr1646v2ATMImaPerFrDlciInPQsEntry 50528256}

pr1646v2ATMImaPerFrDlciInPQsPacketsRedDropped OBJECT-TYPE
   SYNTAX      Counter64
   MAX-ACCESS  read-only
   STATUS      current
   DESCRIPTION
      "Path: atm.performance.pvcTable.frameRelay.dlciTable.inPriorityQueues.packets.redDropped

       64 bit unsigned wrappable counter."
   ::= {pr1646v2ATMImaPerFrDlciInPQsEntry 50724864}

pr1646v2ATMImaPerFrDlciInPQsPacketsCirTx OBJECT-TYPE
   SYNTAX      Counter64
   MAX-ACCESS  read-only
   STATUS      current
   DESCRIPTION
      "Path: atm.performance.pvcTable.frameRelay.dlciTable.inPriorityQueues.packets.cirTx

       64 bit unsigned wrappable counter."
   ::= {pr1646v2ATMImaPerFrDlciInPQsEntry 50593792}

pr1646v2ATMImaPerFrDlciInPQsPacketsEirTx OBJECT-TYPE
   SYNTAX      Counter64
   MAX-ACCESS  read-only
   STATUS      current
   DESCRIPTION
      "Path: atm.performance.pvcTable.frameRelay.dlciTable.inPriorityQueues.packets.eirTx

       64 bit unsigned wrappable counter."
   ::= {pr1646v2ATMImaPerFrDlciInPQsEntry 50659328}

pr1646v2ATMImaPerFrDlciInPQsPacketsViolateTx OBJECT-TYPE
   SYNTAX      Counter64
   MAX-ACCESS  read-only
   STATUS      current
   DESCRIPTION
      "Path: atm.performance.pvcTable.frameRelay.dlciTable.inPriorityQueues.packets.violateTx

       64 bit unsigned wrappable counter."
   ::= {pr1646v2ATMImaPerFrDlciInPQsEntry 50855936}

pr1646v2ATMImaPerFrDlciInPQsOctetsTotal OBJECT-TYPE
   SYNTAX      Counter64
   MAX-ACCESS  read-only
   STATUS      current
   DESCRIPTION
      "Path: atm.performance.pvcTable.frameRelay.dlciTable.inPriorityQueues.octets.total

       64 bit unsigned wrappable counter."
   ::= {pr1646v2ATMImaPerFrDlciInPQsEntry 67567616}

pr1646v2ATMImaPerFrDlciInPQsOctetsDirectTx OBJECT-TYPE
   SYNTAX      Counter64
   MAX-ACCESS  read-only
   STATUS      current
   DESCRIPTION
      "Path: atm.performance.pvcTable.frameRelay.dlciTable.inPriorityQueues.octets.directTx

       64 bit unsigned wrappable counter."
   ::= {pr1646v2ATMImaPerFrDlciInPQsEntry 67174400}

pr1646v2ATMImaPerFrDlciInPQsOctetsQueued OBJECT-TYPE
   SYNTAX      Counter64
   MAX-ACCESS  read-only
   STATUS      current
   DESCRIPTION
      "Path: atm.performance.pvcTable.frameRelay.dlciTable.inPriorityQueues.octets.queued

       64 bit unsigned wrappable counter."
   ::= {pr1646v2ATMImaPerFrDlciInPQsEntry 67239936}

pr1646v2ATMImaPerFrDlciInPQsOctetsDropped OBJECT-TYPE
   SYNTAX      Counter64
   MAX-ACCESS  read-only
   STATUS      current
   DESCRIPTION
      "Path: atm.performance.pvcTable.frameRelay.dlciTable.inPriorityQueues.octets.dropped

       64 bit unsigned wrappable counter."
   ::= {pr1646v2ATMImaPerFrDlciInPQsEntry 67305472}

pr1646v2ATMImaPerFrDlciInPQsOctetsRedDropped OBJECT-TYPE
   SYNTAX      Counter64
   MAX-ACCESS  read-only
   STATUS      current
   DESCRIPTION
      "Path: atm.performance.pvcTable.frameRelay.dlciTable.inPriorityQueues.octets.redDropped

       64 bit unsigned wrappable counter."
   ::= {pr1646v2ATMImaPerFrDlciInPQsEntry 67502080}

pr1646v2ATMImaPerFrDlciInPQsOctetsCirTx OBJECT-TYPE
   SYNTAX      Counter64
   MAX-ACCESS  read-only
   STATUS      current
   DESCRIPTION
      "Path: atm.performance.pvcTable.frameRelay.dlciTable.inPriorityQueues.octets.cirTx

       64 bit unsigned wrappable counter."
   ::= {pr1646v2ATMImaPerFrDlciInPQsEntry 67371008}

pr1646v2ATMImaPerFrDlciInPQsOctetsEirTx OBJECT-TYPE
   SYNTAX      Counter64
   MAX-ACCESS  read-only
   STATUS      current
   DESCRIPTION
      "Path: atm.performance.pvcTable.frameRelay.dlciTable.inPriorityQueues.octets.eirTx

       64 bit unsigned wrappable counter."
   ::= {pr1646v2ATMImaPerFrDlciInPQsEntry 67436544}

pr1646v2ATMImaPerFrDlciInPQsOctetsViolateTx OBJECT-TYPE
   SYNTAX      Counter64
   MAX-ACCESS  read-only
   STATUS      current
   DESCRIPTION
      "Path: atm.performance.pvcTable.frameRelay.dlciTable.inPriorityQueues.octets.violateTx

       64 bit unsigned wrappable counter."
   ::= {pr1646v2ATMImaPerFrDlciInPQsEntry 67633152}

pr1646v2ATMImaPerFrDlciInPQsOctetsBandwidth15sec OBJECT-TYPE
   SYNTAX      Integer32
   MAX-ACCESS  read-only
   STATUS      current
   DESCRIPTION
      "Path: atm.performance.pvcTable.frameRelay.dlciTable.inPriorityQueues.octets.bandwidth.15sec

       unit name = bps
       formula = 8 * ; 8 /"
   ::= {pr1646v2ATMImaPerFrDlciInPQsEntry 70386944}

pr1646v2ATMImaPerFrDlciInPQsOctetsBandwidth30sec OBJECT-TYPE
   SYNTAX      Integer32
   MAX-ACCESS  read-only
   STATUS      current
   DESCRIPTION
      "Path: atm.performance.pvcTable.frameRelay.dlciTable.inPriorityQueues.octets.bandwidth.30sec

       unit name = bps
       formula = 8 * ; 8 /"
   ::= {pr1646v2ATMImaPerFrDlciInPQsEntry 70388224}

pr1646v2ATMImaPerFrDlciInPQsOctetsBandwidth1min OBJECT-TYPE
   SYNTAX      Integer32
   MAX-ACCESS  read-only
   STATUS      current
   DESCRIPTION
      "Path: atm.performance.pvcTable.frameRelay.dlciTable.inPriorityQueues.octets.bandwidth.1min

       unit name = bps
       formula = 8 * ; 8 /"
   ::= {pr1646v2ATMImaPerFrDlciInPQsEntry 70390784}

pr1646v2ATMImaPerFrDlciInPQsOctetsBandwidth2min OBJECT-TYPE
   SYNTAX      Integer32
   MAX-ACCESS  read-only
   STATUS      current
   DESCRIPTION
      "Path: atm.performance.pvcTable.frameRelay.dlciTable.inPriorityQueues.octets.bandwidth.2min

       unit name = bps
       formula = 8 * ; 8 /"
   ::= {pr1646v2ATMImaPerFrDlciInPQsEntry 70395904}

pr1646v2ATMImaPerFrDlciInPQsOctetsBandwidth5min OBJECT-TYPE
   SYNTAX      Integer32
   MAX-ACCESS  read-only
   STATUS      current
   DESCRIPTION
      "Path: atm.performance.pvcTable.frameRelay.dlciTable.inPriorityQueues.octets.bandwidth.5min

       unit name = bps
       formula = 8 * ; 8 /"
   ::= {pr1646v2ATMImaPerFrDlciInPQsEntry 70411264}

pr1646v2ATMImaPerFrDlciInPQsH2Performance OBJECT-TYPE
   SYNTAX      SEQUENCE OF Pr1646v2ATMImaPerFrDlciInPQsH2PerformanceEntry
   MAX-ACCESS  not-accessible
   STATUS      current
   DESCRIPTION
      ""
   ::= {pr1646v2ATMImaPer 503449093}

pr1646v2ATMImaPerFrDlciInPQsH2PerformanceEntry OBJECT-TYPE
   SYNTAX      Pr1646v2ATMImaPerFrDlciInPQsH2PerformanceEntry
   MAX-ACCESS  not-accessible
   STATUS      current
   DESCRIPTION
      ""
   INDEX      { pr1646v2ATMImaPerTableIx,
                pr1646v2ATMImaPerFrDlciTableIx,
                pr1646v2ATMImaPerFrDlciInPQsTableIx,
                pr1646v2ATMImaPerFrDlciInPQsH2PerformanceTableIx }
   ::= {pr1646v2ATMImaPerFrDlciInPQsH2Performance 1}

Pr1646v2ATMImaPerFrDlciInPQsH2PerformanceEntry ::=
   SEQUENCE
      {
      pr1646v2ATMImaPerFrDlciInPQsH2PerformanceTableIx
         TableIndex,
      pr1646v2ATMImaPerFrDlciInPQsH2PerformanceSysUpTime
         TimeTicks,
      pr1646v2ATMImaPerFrDlciInPQsH2PerformanceTotPkts
         Counter64,
      pr1646v2ATMImaPerFrDlciInPQsH2PerformanceDirTxPkts
         Counter64,
      pr1646v2ATMImaPerFrDlciInPQsH2PerformanceQdPkts
         Counter64,
      pr1646v2ATMImaPerFrDlciInPQsH2PerformanceDropPkts
         Counter64,
      pr1646v2ATMImaPerFrDlciInPQsH2PerformanceRDropPkts
         Counter64,
      pr1646v2ATMImaPerFrDlciInPQsH2PerformanceCirTxPkts
         Counter64,
      pr1646v2ATMImaPerFrDlciInPQsH2PerformanceEirTxPkts
         Counter64,
      pr1646v2ATMImaPerFrDlciInPQsH2PerformanceViolTxPkts
         Counter64,
      pr1646v2ATMImaPerFrDlciInPQsH2PerformanceTotOcts
         Counter64,
      pr1646v2ATMImaPerFrDlciInPQsH2PerformanceDirTxOcts
         Counter64,
      pr1646v2ATMImaPerFrDlciInPQsH2PerformanceQdOcts
         Counter64,
      pr1646v2ATMImaPerFrDlciInPQsH2PerformanceDropOcts
         Counter64,
      pr1646v2ATMImaPerFrDlciInPQsH2PerformanceRDropOcts
         Counter64,
      pr1646v2ATMImaPerFrDlciInPQsH2PerformanceCirTxOcts
         Counter64,
      pr1646v2ATMImaPerFrDlciInPQsH2PerformanceEirTxOcts
         Counter64,
      pr1646v2ATMImaPerFrDlciInPQsH2PerformanceViolTxOcts
         Counter64,
      pr1646v2ATMImaPerFrDlciInPQsH2PerformanceBandwidth
         Integer32
      }

pr1646v2ATMImaPerFrDlciInPQsH2PerformanceTableIx OBJECT-TYPE
   SYNTAX      TableIndex
   MAX-ACCESS  not-accessible
   STATUS      current
   DESCRIPTION
      ""
   ::= {pr1646v2ATMImaPerFrDlciInPQsH2PerformanceEntry 11}

pr1646v2ATMImaPerFrDlciInPQsH2PerformanceSysUpTime OBJECT-TYPE
   SYNTAX      TimeTicks
   MAX-ACCESS  read-only
   STATUS      current
   DESCRIPTION
      "Path: atm.performance.pvcTable.frameRelay.dlciTable.inPriorityQueues.h2Performance.sysUpTime

       Time in centi-second."
   ::= {pr1646v2ATMImaPerFrDlciInPQsH2PerformanceEntry 16777216}

pr1646v2ATMImaPerFrDlciInPQsH2PerformanceTotPkts OBJECT-TYPE
   SYNTAX      Counter64
   MAX-ACCESS  read-only
   STATUS      current
   DESCRIPTION
      "Path: atm.performance.pvcTable.frameRelay.dlciTable.inPriorityQueues.h2Performance.totalPkts

       64 bit unsigned wrappable counter."
   ::= {pr1646v2ATMImaPerFrDlciInPQsH2PerformanceEntry 234881024}

pr1646v2ATMImaPerFrDlciInPQsH2PerformanceDirTxPkts OBJECT-TYPE
   SYNTAX      Counter64
   MAX-ACCESS  read-only
   STATUS      current
   DESCRIPTION
      "Path: atm.performance.pvcTable.frameRelay.dlciTable.inPriorityQueues.h2Performance.directTxPkts

       64 bit unsigned wrappable counter."
   ::= {pr1646v2ATMImaPerFrDlciInPQsH2PerformanceEntry 33554432}

pr1646v2ATMImaPerFrDlciInPQsH2PerformanceQdPkts OBJECT-TYPE
   SYNTAX      Counter64
   MAX-ACCESS  read-only
   STATUS      current
   DESCRIPTION
      "Path: atm.performance.pvcTable.frameRelay.dlciTable.inPriorityQueues.h2Performance.queuedPkts

       64 bit unsigned wrappable counter."
   ::= {pr1646v2ATMImaPerFrDlciInPQsH2PerformanceEntry 50331648}

pr1646v2ATMImaPerFrDlciInPQsH2PerformanceDropPkts OBJECT-TYPE
   SYNTAX      Counter64
   MAX-ACCESS  read-only
   STATUS      current
   DESCRIPTION
      "Path: atm.performance.pvcTable.frameRelay.dlciTable.inPriorityQueues.h2Performance.droppedPkts

       64 bit unsigned wrappable counter."
   ::= {pr1646v2ATMImaPerFrDlciInPQsH2PerformanceEntry 67108864}

pr1646v2ATMImaPerFrDlciInPQsH2PerformanceRDropPkts OBJECT-TYPE
   SYNTAX      Counter64
   MAX-ACCESS  read-only
   STATUS      current
   DESCRIPTION
      "Path: atm.performance.pvcTable.frameRelay.dlciTable.inPriorityQueues.h2Performance.redDroppedPkts

       64 bit unsigned wrappable counter."
   ::= {pr1646v2ATMImaPerFrDlciInPQsH2PerformanceEntry 201326592}

pr1646v2ATMImaPerFrDlciInPQsH2PerformanceCirTxPkts OBJECT-TYPE
   SYNTAX      Counter64
   MAX-ACCESS  read-only
   STATUS      current
   DESCRIPTION
      "Path: atm.performance.pvcTable.frameRelay.dlciTable.inPriorityQueues.h2Performance.cirTxPkts

       64 bit unsigned wrappable counter."
   ::= {pr1646v2ATMImaPerFrDlciInPQsH2PerformanceEntry 83886080}

pr1646v2ATMImaPerFrDlciInPQsH2PerformanceEirTxPkts OBJECT-TYPE
   SYNTAX      Counter64
   MAX-ACCESS  read-only
   STATUS      current
   DESCRIPTION
      "Path: atm.performance.pvcTable.frameRelay.dlciTable.inPriorityQueues.h2Performance.eirTxPkts

       64 bit unsigned wrappable counter."
   ::= {pr1646v2ATMImaPerFrDlciInPQsH2PerformanceEntry 100663296}

pr1646v2ATMImaPerFrDlciInPQsH2PerformanceViolTxPkts OBJECT-TYPE
   SYNTAX      Counter64
   MAX-ACCESS  read-only
   STATUS      current
   DESCRIPTION
      "Path: atm.performance.pvcTable.frameRelay.dlciTable.inPriorityQueues.h2Performance.violateTxPkts

       64 bit unsigned wrappable counter."
   ::= {pr1646v2ATMImaPerFrDlciInPQsH2PerformanceEntry 301989888}

pr1646v2ATMImaPerFrDlciInPQsH2PerformanceTotOcts OBJECT-TYPE
   SYNTAX      Counter64
   MAX-ACCESS  read-only
   STATUS      current
   DESCRIPTION
      "Path: atm.performance.pvcTable.frameRelay.dlciTable.inPriorityQueues.h2Performance.totalOctets

       64 bit unsigned wrappable counter."
   ::= {pr1646v2ATMImaPerFrDlciInPQsH2PerformanceEntry 251658240}

pr1646v2ATMImaPerFrDlciInPQsH2PerformanceDirTxOcts OBJECT-TYPE
   SYNTAX      Counter64
   MAX-ACCESS  read-only
   STATUS      current
   DESCRIPTION
      "Path: atm.performance.pvcTable.frameRelay.dlciTable.inPriorityQueues.h2Performance.directTxOctets

       64 bit unsigned wrappable counter."
   ::= {pr1646v2ATMImaPerFrDlciInPQsH2PerformanceEntry 117440512}

pr1646v2ATMImaPerFrDlciInPQsH2PerformanceQdOcts OBJECT-TYPE
   SYNTAX      Counter64
   MAX-ACCESS  read-only
   STATUS      current
   DESCRIPTION
      "Path: atm.performance.pvcTable.frameRelay.dlciTable.inPriorityQueues.h2Performance.queuedOctets

       64 bit unsigned wrappable counter."
   ::= {pr1646v2ATMImaPerFrDlciInPQsH2PerformanceEntry 134217728}

pr1646v2ATMImaPerFrDlciInPQsH2PerformanceDropOcts OBJECT-TYPE
   SYNTAX      Counter64
   MAX-ACCESS  read-only
   STATUS      current
   DESCRIPTION
      "Path: atm.performance.pvcTable.frameRelay.dlciTable.inPriorityQueues.h2Performance.droppedOctets

       64 bit unsigned wrappable counter."
   ::= {pr1646v2ATMImaPerFrDlciInPQsH2PerformanceEntry 150994944}

pr1646v2ATMImaPerFrDlciInPQsH2PerformanceRDropOcts OBJECT-TYPE
   SYNTAX      Counter64
   MAX-ACCESS  read-only
   STATUS      current
   DESCRIPTION
      "Path: atm.performance.pvcTable.frameRelay.dlciTable.inPriorityQueues.h2Performance.redDroppedOctets

       64 bit unsigned wrappable counter."
   ::= {pr1646v2ATMImaPerFrDlciInPQsH2PerformanceEntry 218103808}

pr1646v2ATMImaPerFrDlciInPQsH2PerformanceCirTxOcts OBJECT-TYPE
   SYNTAX      Counter64
   MAX-ACCESS  read-only
   STATUS      current
   DESCRIPTION
      "Path: atm.performance.pvcTable.frameRelay.dlciTable.inPriorityQueues.h2Performance.cirTxOctets

       64 bit unsigned wrappable counter."
   ::= {pr1646v2ATMImaPerFrDlciInPQsH2PerformanceEntry 167772160}

pr1646v2ATMImaPerFrDlciInPQsH2PerformanceEirTxOcts OBJECT-TYPE
   SYNTAX      Counter64
   MAX-ACCESS  read-only
   STATUS      current
   DESCRIPTION
      "Path: atm.performance.pvcTable.frameRelay.dlciTable.inPriorityQueues.h2Performance.eirTxOctets

       64 bit unsigned wrappable counter."
   ::= {pr1646v2ATMImaPerFrDlciInPQsH2PerformanceEntry 184549376}

pr1646v2ATMImaPerFrDlciInPQsH2PerformanceViolTxOcts OBJECT-TYPE
   SYNTAX      Counter64
   MAX-ACCESS  read-only
   STATUS      current
   DESCRIPTION
      "Path: atm.performance.pvcTable.frameRelay.dlciTable.inPriorityQueues.h2Performance.violateTxOctets

       64 bit unsigned wrappable counter."
   ::= {pr1646v2ATMImaPerFrDlciInPQsH2PerformanceEntry 318767104}

pr1646v2ATMImaPerFrDlciInPQsH2PerformanceBandwidth OBJECT-TYPE
   SYNTAX      Integer32
   MAX-ACCESS  read-only
   STATUS      current
   DESCRIPTION
      "Path: atm.performance.pvcTable.frameRelay.dlciTable.inPriorityQueues.h2Performance.bandwidth

       unit name = bps
       formula = 8 * ; 8 /"
   ::= {pr1646v2ATMImaPerFrDlciInPQsH2PerformanceEntry 268435456}

pr1646v2ATMImaPerFrDlciInPQsH24Performance OBJECT-TYPE
   SYNTAX      SEQUENCE OF Pr1646v2ATMImaPerFrDlciInPQsH24PerformanceEntry
   MAX-ACCESS  not-accessible
   STATUS      current
   DESCRIPTION
      ""
   ::= {pr1646v2ATMImaPer 503449094}

pr1646v2ATMImaPerFrDlciInPQsH24PerformanceEntry OBJECT-TYPE
   SYNTAX      Pr1646v2ATMImaPerFrDlciInPQsH24PerformanceEntry
   MAX-ACCESS  not-accessible
   STATUS      current
   DESCRIPTION
      ""
   INDEX      { pr1646v2ATMImaPerTableIx,
                pr1646v2ATMImaPerFrDlciTableIx,
                pr1646v2ATMImaPerFrDlciInPQsTableIx,
                pr1646v2ATMImaPerFrDlciInPQsH24PerformanceTableIx }
   ::= {pr1646v2ATMImaPerFrDlciInPQsH24Performance 1}

Pr1646v2ATMImaPerFrDlciInPQsH24PerformanceEntry ::=
   SEQUENCE
      {
      pr1646v2ATMImaPerFrDlciInPQsH24PerformanceTableIx
         TableIndex,
      pr1646v2ATMImaPerFrDlciInPQsH24PerformanceSysUpTime
         TimeTicks,
      pr1646v2ATMImaPerFrDlciInPQsH24PerformanceTotPkts
         Counter64,
      pr1646v2ATMImaPerFrDlciInPQsH24PerformanceDirTxPkts
         Counter64,
      pr1646v2ATMImaPerFrDlciInPQsH24PerformanceQdPkts
         Counter64,
      pr1646v2ATMImaPerFrDlciInPQsH24PerformanceDropPkts
         Counter64,
      pr1646v2ATMImaPerFrDlciInPQsH24PerformanceRDropPkts
         Counter64,
      pr1646v2ATMImaPerFrDlciInPQsH24PerformanceCirTxPkts
         Counter64,
      pr1646v2ATMImaPerFrDlciInPQsH24PerformanceEirTxPkts
         Counter64,
      pr1646v2ATMImaPerFrDlciInPQsH24PerformanceViolTxPkts
         Counter64,
      pr1646v2ATMImaPerFrDlciInPQsH24PerformanceTotOcts
         Counter64,
      pr1646v2ATMImaPerFrDlciInPQsH24PerformanceDirTxOcts
         Counter64,
      pr1646v2ATMImaPerFrDlciInPQsH24PerformanceQdOcts
         Counter64,
      pr1646v2ATMImaPerFrDlciInPQsH24PerformanceDropOcts
         Counter64,
      pr1646v2ATMImaPerFrDlciInPQsH24PerformanceRDropOcts
         Counter64,
      pr1646v2ATMImaPerFrDlciInPQsH24PerformanceCirTxOcts
         Counter64,
      pr1646v2ATMImaPerFrDlciInPQsH24PerformanceEirTxOcts
         Counter64,
      pr1646v2ATMImaPerFrDlciInPQsH24PerformanceViolTxOcts
         Counter64,
      pr1646v2ATMImaPerFrDlciInPQsH24PerformanceBandwidth
         Integer32
      }

pr1646v2ATMImaPerFrDlciInPQsH24PerformanceTableIx OBJECT-TYPE
   SYNTAX      TableIndex
   MAX-ACCESS  not-accessible
   STATUS      current
   DESCRIPTION
      ""
   ::= {pr1646v2ATMImaPerFrDlciInPQsH24PerformanceEntry 11}

pr1646v2ATMImaPerFrDlciInPQsH24PerformanceSysUpTime OBJECT-TYPE
   SYNTAX      TimeTicks
   MAX-ACCESS  read-only
   STATUS      current
   DESCRIPTION
      "Path: atm.performance.pvcTable.frameRelay.dlciTable.inPriorityQueues.h24Performance.sysUpTime

       Time in centi-second."
   ::= {pr1646v2ATMImaPerFrDlciInPQsH24PerformanceEntry 16777216}

pr1646v2ATMImaPerFrDlciInPQsH24PerformanceTotPkts OBJECT-TYPE
   SYNTAX      Counter64
   MAX-ACCESS  read-only
   STATUS      current
   DESCRIPTION
      "Path: atm.performance.pvcTable.frameRelay.dlciTable.inPriorityQueues.h24Performance.totalPkts

       64 bit unsigned wrappable counter."
   ::= {pr1646v2ATMImaPerFrDlciInPQsH24PerformanceEntry 234881024}

pr1646v2ATMImaPerFrDlciInPQsH24PerformanceDirTxPkts OBJECT-TYPE
   SYNTAX      Counter64
   MAX-ACCESS  read-only
   STATUS      current
   DESCRIPTION
      "Path: atm.performance.pvcTable.frameRelay.dlciTable.inPriorityQueues.h24Performance.directTxPkts

       64 bit unsigned wrappable counter."
   ::= {pr1646v2ATMImaPerFrDlciInPQsH24PerformanceEntry 33554432}

pr1646v2ATMImaPerFrDlciInPQsH24PerformanceQdPkts OBJECT-TYPE
   SYNTAX      Counter64
   MAX-ACCESS  read-only
   STATUS      current
   DESCRIPTION
      "Path: atm.performance.pvcTable.frameRelay.dlciTable.inPriorityQueues.h24Performance.queuedPkts

       64 bit unsigned wrappable counter."
   ::= {pr1646v2ATMImaPerFrDlciInPQsH24PerformanceEntry 50331648}

pr1646v2ATMImaPerFrDlciInPQsH24PerformanceDropPkts OBJECT-TYPE
   SYNTAX      Counter64
   MAX-ACCESS  read-only
   STATUS      current
   DESCRIPTION
      "Path: atm.performance.pvcTable.frameRelay.dlciTable.inPriorityQueues.h24Performance.droppedPkts

       64 bit unsigned wrappable counter."
   ::= {pr1646v2ATMImaPerFrDlciInPQsH24PerformanceEntry 67108864}

pr1646v2ATMImaPerFrDlciInPQsH24PerformanceRDropPkts OBJECT-TYPE
   SYNTAX      Counter64
   MAX-ACCESS  read-only
   STATUS      current
   DESCRIPTION
      "Path: atm.performance.pvcTable.frameRelay.dlciTable.inPriorityQueues.h24Performance.redDroppedPkts

       64 bit unsigned wrappable counter."
   ::= {pr1646v2ATMImaPerFrDlciInPQsH24PerformanceEntry 201326592}

pr1646v2ATMImaPerFrDlciInPQsH24PerformanceCirTxPkts OBJECT-TYPE
   SYNTAX      Counter64
   MAX-ACCESS  read-only
   STATUS      current
   DESCRIPTION
      "Path: atm.performance.pvcTable.frameRelay.dlciTable.inPriorityQueues.h24Performance.cirTxPkts

       64 bit unsigned wrappable counter."
   ::= {pr1646v2ATMImaPerFrDlciInPQsH24PerformanceEntry 83886080}

pr1646v2ATMImaPerFrDlciInPQsH24PerformanceEirTxPkts OBJECT-TYPE
   SYNTAX      Counter64
   MAX-ACCESS  read-only
   STATUS      current
   DESCRIPTION
      "Path: atm.performance.pvcTable.frameRelay.dlciTable.inPriorityQueues.h24Performance.eirTxPkts

       64 bit unsigned wrappable counter."
   ::= {pr1646v2ATMImaPerFrDlciInPQsH24PerformanceEntry 100663296}

pr1646v2ATMImaPerFrDlciInPQsH24PerformanceViolTxPkts OBJECT-TYPE
   SYNTAX      Counter64
   MAX-ACCESS  read-only
   STATUS      current
   DESCRIPTION
      "Path: atm.performance.pvcTable.frameRelay.dlciTable.inPriorityQueues.h24Performance.violateTxPkts

       64 bit unsigned wrappable counter."
   ::= {pr1646v2ATMImaPerFrDlciInPQsH24PerformanceEntry 301989888}

pr1646v2ATMImaPerFrDlciInPQsH24PerformanceTotOcts OBJECT-TYPE
   SYNTAX      Counter64
   MAX-ACCESS  read-only
   STATUS      current
   DESCRIPTION
      "Path: atm.performance.pvcTable.frameRelay.dlciTable.inPriorityQueues.h24Performance.totalOctets

       64 bit unsigned wrappable counter."
   ::= {pr1646v2ATMImaPerFrDlciInPQsH24PerformanceEntry 251658240}

pr1646v2ATMImaPerFrDlciInPQsH24PerformanceDirTxOcts OBJECT-TYPE
   SYNTAX      Counter64
   MAX-ACCESS  read-only
   STATUS      current
   DESCRIPTION
      "Path: atm.performance.pvcTable.frameRelay.dlciTable.inPriorityQueues.h24Performance.directTxOctets

       64 bit unsigned wrappable counter."
   ::= {pr1646v2ATMImaPerFrDlciInPQsH24PerformanceEntry 117440512}

pr1646v2ATMImaPerFrDlciInPQsH24PerformanceQdOcts OBJECT-TYPE
   SYNTAX      Counter64
   MAX-ACCESS  read-only
   STATUS      current
   DESCRIPTION
      "Path: atm.performance.pvcTable.frameRelay.dlciTable.inPriorityQueues.h24Performance.queuedOctets

       64 bit unsigned wrappable counter."
   ::= {pr1646v2ATMImaPerFrDlciInPQsH24PerformanceEntry 134217728}

pr1646v2ATMImaPerFrDlciInPQsH24PerformanceDropOcts OBJECT-TYPE
   SYNTAX      Counter64
   MAX-ACCESS  read-only
   STATUS      current
   DESCRIPTION
      "Path: atm.performance.pvcTable.frameRelay.dlciTable.inPriorityQueues.h24Performance.droppedOctets

       64 bit unsigned wrappable counter."
   ::= {pr1646v2ATMImaPerFrDlciInPQsH24PerformanceEntry 150994944}

pr1646v2ATMImaPerFrDlciInPQsH24PerformanceRDropOcts OBJECT-TYPE
   SYNTAX      Counter64
   MAX-ACCESS  read-only
   STATUS      current
   DESCRIPTION
      "Path: atm.performance.pvcTable.frameRelay.dlciTable.inPriorityQueues.h24Performance.redDroppedOctets

       64 bit unsigned wrappable counter."
   ::= {pr1646v2ATMImaPerFrDlciInPQsH24PerformanceEntry 218103808}

pr1646v2ATMImaPerFrDlciInPQsH24PerformanceCirTxOcts OBJECT-TYPE
   SYNTAX      Counter64
   MAX-ACCESS  read-only
   STATUS      current
   DESCRIPTION
      "Path: atm.performance.pvcTable.frameRelay.dlciTable.inPriorityQueues.h24Performance.cirTxOctets

       64 bit unsigned wrappable counter."
   ::= {pr1646v2ATMImaPerFrDlciInPQsH24PerformanceEntry 167772160}

pr1646v2ATMImaPerFrDlciInPQsH24PerformanceEirTxOcts OBJECT-TYPE
   SYNTAX      Counter64
   MAX-ACCESS  read-only
   STATUS      current
   DESCRIPTION
      "Path: atm.performance.pvcTable.frameRelay.dlciTable.inPriorityQueues.h24Performance.eirTxOctets

       64 bit unsigned wrappable counter."
   ::= {pr1646v2ATMImaPerFrDlciInPQsH24PerformanceEntry 184549376}

pr1646v2ATMImaPerFrDlciInPQsH24PerformanceViolTxOcts OBJECT-TYPE
   SYNTAX      Counter64
   MAX-ACCESS  read-only
   STATUS      current
   DESCRIPTION
      "Path: atm.performance.pvcTable.frameRelay.dlciTable.inPriorityQueues.h24Performance.violateTxOctets

       64 bit unsigned wrappable counter."
   ::= {pr1646v2ATMImaPerFrDlciInPQsH24PerformanceEntry 318767104}

pr1646v2ATMImaPerFrDlciInPQsH24PerformanceBandwidth OBJECT-TYPE
   SYNTAX      Integer32
   MAX-ACCESS  read-only
   STATUS      current
   DESCRIPTION
      "Path: atm.performance.pvcTable.frameRelay.dlciTable.inPriorityQueues.h24Performance.bandwidth

       unit name = bps
       formula = 8 * ; 8 /"
   ::= {pr1646v2ATMImaPerFrDlciInPQsH24PerformanceEntry 268435456}

pr1646v2ATMImaPerFrDlciInPQsD7Performance OBJECT-TYPE
   SYNTAX      SEQUENCE OF Pr1646v2ATMImaPerFrDlciInPQsD7PerformanceEntry
   MAX-ACCESS  not-accessible
   STATUS      current
   DESCRIPTION
      ""
   ::= {pr1646v2ATMImaPer 503449095}

pr1646v2ATMImaPerFrDlciInPQsD7PerformanceEntry OBJECT-TYPE
   SYNTAX      Pr1646v2ATMImaPerFrDlciInPQsD7PerformanceEntry
   MAX-ACCESS  not-accessible
   STATUS      current
   DESCRIPTION
      ""
   INDEX      { pr1646v2ATMImaPerTableIx,
                pr1646v2ATMImaPerFrDlciTableIx,
                pr1646v2ATMImaPerFrDlciInPQsTableIx,
                pr1646v2ATMImaPerFrDlciInPQsD7PerformanceTableIx }
   ::= {pr1646v2ATMImaPerFrDlciInPQsD7Performance 1}

Pr1646v2ATMImaPerFrDlciInPQsD7PerformanceEntry ::=
   SEQUENCE
      {
      pr1646v2ATMImaPerFrDlciInPQsD7PerformanceTableIx
         TableIndex,
      pr1646v2ATMImaPerFrDlciInPQsD7PerformanceSysUpTime
         TimeTicks,
      pr1646v2ATMImaPerFrDlciInPQsD7PerformanceTotPkts
         Counter64,
      pr1646v2ATMImaPerFrDlciInPQsD7PerformanceDirTxPkts
         Counter64,
      pr1646v2ATMImaPerFrDlciInPQsD7PerformanceQdPkts
         Counter64,
      pr1646v2ATMImaPerFrDlciInPQsD7PerformanceDropPkts
         Counter64,
      pr1646v2ATMImaPerFrDlciInPQsD7PerformanceRDropPkts
         Counter64,
      pr1646v2ATMImaPerFrDlciInPQsD7PerformanceCirTxPkts
         Counter64,
      pr1646v2ATMImaPerFrDlciInPQsD7PerformanceEirTxPkts
         Counter64,
      pr1646v2ATMImaPerFrDlciInPQsD7PerformanceViolTxPkts
         Counter64,
      pr1646v2ATMImaPerFrDlciInPQsD7PerformanceTotOcts
         Counter64,
      pr1646v2ATMImaPerFrDlciInPQsD7PerformanceDirTxOcts
         Counter64,
      pr1646v2ATMImaPerFrDlciInPQsD7PerformanceQdOcts
         Counter64,
      pr1646v2ATMImaPerFrDlciInPQsD7PerformanceDropOcts
         Counter64,
      pr1646v2ATMImaPerFrDlciInPQsD7PerformanceRDropOcts
         Counter64,
      pr1646v2ATMImaPerFrDlciInPQsD7PerformanceCirTxOcts
         Counter64,
      pr1646v2ATMImaPerFrDlciInPQsD7PerformanceEirTxOcts
         Counter64,
      pr1646v2ATMImaPerFrDlciInPQsD7PerformanceViolTxOcts
         Counter64,
      pr1646v2ATMImaPerFrDlciInPQsD7PerformanceBandwidth
         Integer32
      }

pr1646v2ATMImaPerFrDlciInPQsD7PerformanceTableIx OBJECT-TYPE
   SYNTAX      TableIndex
   MAX-ACCESS  not-accessible
   STATUS      current
   DESCRIPTION
      ""
   ::= {pr1646v2ATMImaPerFrDlciInPQsD7PerformanceEntry 11}

pr1646v2ATMImaPerFrDlciInPQsD7PerformanceSysUpTime OBJECT-TYPE
   SYNTAX      TimeTicks
   MAX-ACCESS  read-only
   STATUS      current
   DESCRIPTION
      "Path: atm.performance.pvcTable.frameRelay.dlciTable.inPriorityQueues.d7Performance.sysUpTime

       Time in centi-second."
   ::= {pr1646v2ATMImaPerFrDlciInPQsD7PerformanceEntry 16777216}

pr1646v2ATMImaPerFrDlciInPQsD7PerformanceTotPkts OBJECT-TYPE
   SYNTAX      Counter64
   MAX-ACCESS  read-only
   STATUS      current
   DESCRIPTION
      "Path: atm.performance.pvcTable.frameRelay.dlciTable.inPriorityQueues.d7Performance.totalPkts

       64 bit unsigned wrappable counter."
   ::= {pr1646v2ATMImaPerFrDlciInPQsD7PerformanceEntry 234881024}

pr1646v2ATMImaPerFrDlciInPQsD7PerformanceDirTxPkts OBJECT-TYPE
   SYNTAX      Counter64
   MAX-ACCESS  read-only
   STATUS      current
   DESCRIPTION
      "Path: atm.performance.pvcTable.frameRelay.dlciTable.inPriorityQueues.d7Performance.directTxPkts

       64 bit unsigned wrappable counter."
   ::= {pr1646v2ATMImaPerFrDlciInPQsD7PerformanceEntry 33554432}

pr1646v2ATMImaPerFrDlciInPQsD7PerformanceQdPkts OBJECT-TYPE
   SYNTAX      Counter64
   MAX-ACCESS  read-only
   STATUS      current
   DESCRIPTION
      "Path: atm.performance.pvcTable.frameRelay.dlciTable.inPriorityQueues.d7Performance.queuedPkts

       64 bit unsigned wrappable counter."
   ::= {pr1646v2ATMImaPerFrDlciInPQsD7PerformanceEntry 50331648}

pr1646v2ATMImaPerFrDlciInPQsD7PerformanceDropPkts OBJECT-TYPE
   SYNTAX      Counter64
   MAX-ACCESS  read-only
   STATUS      current
   DESCRIPTION
      "Path: atm.performance.pvcTable.frameRelay.dlciTable.inPriorityQueues.d7Performance.droppedPkts

       64 bit unsigned wrappable counter."
   ::= {pr1646v2ATMImaPerFrDlciInPQsD7PerformanceEntry 67108864}

pr1646v2ATMImaPerFrDlciInPQsD7PerformanceRDropPkts OBJECT-TYPE
   SYNTAX      Counter64
   MAX-ACCESS  read-only
   STATUS      current
   DESCRIPTION
      "Path: atm.performance.pvcTable.frameRelay.dlciTable.inPriorityQueues.d7Performance.redDroppedPkts

       64 bit unsigned wrappable counter."
   ::= {pr1646v2ATMImaPerFrDlciInPQsD7PerformanceEntry 201326592}

pr1646v2ATMImaPerFrDlciInPQsD7PerformanceCirTxPkts OBJECT-TYPE
   SYNTAX      Counter64
   MAX-ACCESS  read-only
   STATUS      current
   DESCRIPTION
      "Path: atm.performance.pvcTable.frameRelay.dlciTable.inPriorityQueues.d7Performance.cirTxPkts

       64 bit unsigned wrappable counter."
   ::= {pr1646v2ATMImaPerFrDlciInPQsD7PerformanceEntry 83886080}

pr1646v2ATMImaPerFrDlciInPQsD7PerformanceEirTxPkts OBJECT-TYPE
   SYNTAX      Counter64
   MAX-ACCESS  read-only
   STATUS      current
   DESCRIPTION
      "Path: atm.performance.pvcTable.frameRelay.dlciTable.inPriorityQueues.d7Performance.eirTxPkts

       64 bit unsigned wrappable counter."
   ::= {pr1646v2ATMImaPerFrDlciInPQsD7PerformanceEntry 100663296}

pr1646v2ATMImaPerFrDlciInPQsD7PerformanceViolTxPkts OBJECT-TYPE
   SYNTAX      Counter64
   MAX-ACCESS  read-only
   STATUS      current
   DESCRIPTION
      "Path: atm.performance.pvcTable.frameRelay.dlciTable.inPriorityQueues.d7Performance.violateTxPkts

       64 bit unsigned wrappable counter."
   ::= {pr1646v2ATMImaPerFrDlciInPQsD7PerformanceEntry 301989888}

pr1646v2ATMImaPerFrDlciInPQsD7PerformanceTotOcts OBJECT-TYPE
   SYNTAX      Counter64
   MAX-ACCESS  read-only
   STATUS      current
   DESCRIPTION
      "Path: atm.performance.pvcTable.frameRelay.dlciTable.inPriorityQueues.d7Performance.totalOctets

       64 bit unsigned wrappable counter."
   ::= {pr1646v2ATMImaPerFrDlciInPQsD7PerformanceEntry 251658240}

pr1646v2ATMImaPerFrDlciInPQsD7PerformanceDirTxOcts OBJECT-TYPE
   SYNTAX      Counter64
   MAX-ACCESS  read-only
   STATUS      current
   DESCRIPTION
      "Path: atm.performance.pvcTable.frameRelay.dlciTable.inPriorityQueues.d7Performance.directTxOctets

       64 bit unsigned wrappable counter."
   ::= {pr1646v2ATMImaPerFrDlciInPQsD7PerformanceEntry 117440512}

pr1646v2ATMImaPerFrDlciInPQsD7PerformanceQdOcts OBJECT-TYPE
   SYNTAX      Counter64
   MAX-ACCESS  read-only
   STATUS      current
   DESCRIPTION
      "Path: atm.performance.pvcTable.frameRelay.dlciTable.inPriorityQueues.d7Performance.queuedOctets

       64 bit unsigned wrappable counter."
   ::= {pr1646v2ATMImaPerFrDlciInPQsD7PerformanceEntry 134217728}

pr1646v2ATMImaPerFrDlciInPQsD7PerformanceDropOcts OBJECT-TYPE
   SYNTAX      Counter64
   MAX-ACCESS  read-only
   STATUS      current
   DESCRIPTION
      "Path: atm.performance.pvcTable.frameRelay.dlciTable.inPriorityQueues.d7Performance.droppedOctets

       64 bit unsigned wrappable counter."
   ::= {pr1646v2ATMImaPerFrDlciInPQsD7PerformanceEntry 150994944}

pr1646v2ATMImaPerFrDlciInPQsD7PerformanceRDropOcts OBJECT-TYPE
   SYNTAX      Counter64
   MAX-ACCESS  read-only
   STATUS      current
   DESCRIPTION
      "Path: atm.performance.pvcTable.frameRelay.dlciTable.inPriorityQueues.d7Performance.redDroppedOctets

       64 bit unsigned wrappable counter."
   ::= {pr1646v2ATMImaPerFrDlciInPQsD7PerformanceEntry 218103808}

pr1646v2ATMImaPerFrDlciInPQsD7PerformanceCirTxOcts OBJECT-TYPE
   SYNTAX      Counter64
   MAX-ACCESS  read-only
   STATUS      current
   DESCRIPTION
      "Path: atm.performance.pvcTable.frameRelay.dlciTable.inPriorityQueues.d7Performance.cirTxOctets

       64 bit unsigned wrappable counter."
   ::= {pr1646v2ATMImaPerFrDlciInPQsD7PerformanceEntry 167772160}

pr1646v2ATMImaPerFrDlciInPQsD7PerformanceEirTxOcts OBJECT-TYPE
   SYNTAX      Counter64
   MAX-ACCESS  read-only
   STATUS      current
   DESCRIPTION
      "Path: atm.performance.pvcTable.frameRelay.dlciTable.inPriorityQueues.d7Performance.eirTxOctets

       64 bit unsigned wrappable counter."
   ::= {pr1646v2ATMImaPerFrDlciInPQsD7PerformanceEntry 184549376}

pr1646v2ATMImaPerFrDlciInPQsD7PerformanceViolTxOcts OBJECT-TYPE
   SYNTAX      Counter64
   MAX-ACCESS  read-only
   STATUS      current
   DESCRIPTION
      "Path: atm.performance.pvcTable.frameRelay.dlciTable.inPriorityQueues.d7Performance.violateTxOctets

       64 bit unsigned wrappable counter."
   ::= {pr1646v2ATMImaPerFrDlciInPQsD7PerformanceEntry 318767104}

pr1646v2ATMImaPerFrDlciInPQsD7PerformanceBandwidth OBJECT-TYPE
   SYNTAX      Integer32
   MAX-ACCESS  read-only
   STATUS      current
   DESCRIPTION
      "Path: atm.performance.pvcTable.frameRelay.dlciTable.inPriorityQueues.d7Performance.bandwidth

       unit name = bps
       formula = 8 * ; 8 /"
   ::= {pr1646v2ATMImaPerFrDlciInPQsD7PerformanceEntry 268435456}

pr1646v2ATMImaPerFrDlciOutPQs OBJECT-TYPE
   SYNTAX      SEQUENCE OF Pr1646v2ATMImaPerFrDlciOutPQsEntry
   MAX-ACCESS  not-accessible
   STATUS      current
   DESCRIPTION
      ""
   ::= {pr1646v2ATMImaPer 503448832}

pr1646v2ATMImaPerFrDlciOutPQsEntry OBJECT-TYPE
   SYNTAX      Pr1646v2ATMImaPerFrDlciOutPQsEntry
   MAX-ACCESS  not-accessible
   STATUS      current
   DESCRIPTION
      ""
   INDEX      { pr1646v2ATMImaPerTableIx,
                pr1646v2ATMImaPerFrDlciTableIx,
                pr1646v2ATMImaPerFrDlciOutPQsTableIx }
   ::= {pr1646v2ATMImaPerFrDlciOutPQs 1}

Pr1646v2ATMImaPerFrDlciOutPQsEntry ::=
   SEQUENCE
      {
      pr1646v2ATMImaPerFrDlciOutPQsTableIx
         TableIndex,
      pr1646v2ATMImaPerFrDlciOutPQsName
         INTEGER,
      pr1646v2ATMImaPerFrDlciOutPQsLength
         Integer32,
      pr1646v2ATMImaPerFrDlciOutPQsOctetLength
         Integer32,
      pr1646v2ATMImaPerFrDlciOutPQsRedLength
         Integer32,
      pr1646v2ATMImaPerFrDlciOutPQsPacketsTotal
         Counter64,
      pr1646v2ATMImaPerFrDlciOutPQsPacketsDirectTx
         Counter64,
      pr1646v2ATMImaPerFrDlciOutPQsPacketsQueued
         Counter64,
      pr1646v2ATMImaPerFrDlciOutPQsPacketsDropped
         Counter64,
      pr1646v2ATMImaPerFrDlciOutPQsPacketsRedDropped
         Counter64,
      pr1646v2ATMImaPerFrDlciOutPQsPacketsCirTx
         Counter64,
      pr1646v2ATMImaPerFrDlciOutPQsPacketsEirTx
         Counter64,
      pr1646v2ATMImaPerFrDlciOutPQsPacketsViolateTx
         Counter64,
      pr1646v2ATMImaPerFrDlciOutPQsOctetsTotal
         Counter64,
      pr1646v2ATMImaPerFrDlciOutPQsOctetsDirectTx
         Counter64,
      pr1646v2ATMImaPerFrDlciOutPQsOctetsQueued
         Counter64,
      pr1646v2ATMImaPerFrDlciOutPQsOctetsDropped
         Counter64,
      pr1646v2ATMImaPerFrDlciOutPQsOctetsRedDropped
         Counter64,
      pr1646v2ATMImaPerFrDlciOutPQsOctetsCirTx
         Counter64,
      pr1646v2ATMImaPerFrDlciOutPQsOctetsEirTx
         Counter64,
      pr1646v2ATMImaPerFrDlciOutPQsOctetsViolateTx
         Counter64,
      pr1646v2ATMImaPerFrDlciOutPQsOctetsBandwidth15sec
         Integer32,
      pr1646v2ATMImaPerFrDlciOutPQsOctetsBandwidth30sec
         Integer32,
      pr1646v2ATMImaPerFrDlciOutPQsOctetsBandwidth1min
         Integer32,
      pr1646v2ATMImaPerFrDlciOutPQsOctetsBandwidth2min
         Integer32,
      pr1646v2ATMImaPerFrDlciOutPQsOctetsBandwidth5min
         Integer32
      }

pr1646v2ATMImaPerFrDlciOutPQsTableIx OBJECT-TYPE
   SYNTAX      TableIndex
   MAX-ACCESS  not-accessible
   STATUS      current
   DESCRIPTION
      ""
   ::= {pr1646v2ATMImaPerFrDlciOutPQsEntry 11}

pr1646v2ATMImaPerFrDlciOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: atm.performance.pvcTable.frameRelay.dlciTable.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2ATMImaPerFrDlciOutPQsEntry 16777216}

pr1646v2ATMImaPerFrDlciOutPQsLength OBJECT-TYPE
   SYNTAX      Integer32
   MAX-ACCESS  read-only
   STATUS      current
   DESCRIPTION
      "Path: atm.performance.pvcTable.frameRelay.dlciTable.outPriorityQueues.length"
   ::= {pr1646v2ATMImaPerFrDlciOutPQsEntry 33554432}

pr1646v2ATMImaPerFrDlciOutPQsOctetLength OBJECT-TYPE
   SYNTAX      Integer32
   MAX-ACCESS  read-only
   STATUS      current
   DESCRIPTION
      "Path: atm.performance.pvcTable.frameRelay.dlciTable.outPriorityQueues.octetLength"
   ::= {pr1646v2ATMImaPerFrDlciOutPQsEntry 150994944}

pr1646v2ATMImaPerFrDlciOutPQsRedLength OBJECT-TYPE
   SYNTAX      Integer32
   MAX-ACCESS  read-only
   STATUS      current
   DESCRIPTION
      "Path: atm.performance.pvcTable.frameRelay.dlciTable.outPriorityQueues.redLength"
   ::= {pr1646v2ATMImaPerFrDlciOutPQsEntry 134217728}

pr1646v2ATMImaPerFrDlciOutPQsPacketsTotal OBJECT-TYPE
   SYNTAX      Counter64
   MAX-ACCESS  read-only
   STATUS      current
   DESCRIPTION
      "Path: atm.performance.pvcTable.frameRelay.dlciTable.outPriorityQueues.packets.total

       64 bit unsigned wrappable counter."
   ::= {pr1646v2ATMImaPerFrDlciOutPQsEntry 50790400}

pr1646v2ATMImaPerFrDlciOutPQsPacketsDirectTx OBJECT-TYPE
   SYNTAX      Counter64
   MAX-ACCESS  read-only
   STATUS      current
   DESCRIPTION
      "Path: atm.performance.pvcTable.frameRelay.dlciTable.outPriorityQueues.packets.directTx

       64 bit unsigned wrappable counter."
   ::= {pr1646v2ATMImaPerFrDlciOutPQsEntry 50397184}

pr1646v2ATMImaPerFrDlciOutPQsPacketsQueued OBJECT-TYPE
   SYNTAX      Counter64
   MAX-ACCESS  read-only
   STATUS      current
   DESCRIPTION
      "Path: atm.performance.pvcTable.frameRelay.dlciTable.outPriorityQueues.packets.queued

       64 bit unsigned wrappable counter."
   ::= {pr1646v2ATMImaPerFrDlciOutPQsEntry 50462720}

pr1646v2ATMImaPerFrDlciOutPQsPacketsDropped OBJECT-TYPE
   SYNTAX      Counter64
   MAX-ACCESS  read-only
   STATUS      current
   DESCRIPTION
      "Path: atm.performance.pvcTable.frameRelay.dlciTable.outPriorityQueues.packets.dropped

       64 bit unsigned wrappable counter."
   ::= {pr1646v2ATMImaPerFrDlciOutPQsEntry 50528256}

pr1646v2ATMImaPerFrDlciOutPQsPacketsRedDropped OBJECT-TYPE
   SYNTAX      Counter64
   MAX-ACCESS  read-only
   STATUS      current
   DESCRIPTION
      "Path: atm.performance.pvcTable.frameRelay.dlciTable.outPriorityQueues.packets.redDropped

       64 bit unsigned wrappable counter."
   ::= {pr1646v2ATMImaPerFrDlciOutPQsEntry 50724864}

pr1646v2ATMImaPerFrDlciOutPQsPacketsCirTx OBJECT-TYPE
   SYNTAX      Counter64
   MAX-ACCESS  read-only
   STATUS      current
   DESCRIPTION
      "Path: atm.performance.pvcTable.frameRelay.dlciTable.outPriorityQueues.packets.cirTx

       64 bit unsigned wrappable counter."
   ::= {pr1646v2ATMImaPerFrDlciOutPQsEntry 50593792}

pr1646v2ATMImaPerFrDlciOutPQsPacketsEirTx OBJECT-TYPE
   SYNTAX      Counter64
   MAX-ACCESS  read-only
   STATUS      current
   DESCRIPTION
      "Path: atm.performance.pvcTable.frameRelay.dlciTable.outPriorityQueues.packets.eirTx

       64 bit unsigned wrappable counter."
   ::= {pr1646v2ATMImaPerFrDlciOutPQsEntry 50659328}

pr1646v2ATMImaPerFrDlciOutPQsPacketsViolateTx OBJECT-TYPE
   SYNTAX      Counter64
   MAX-ACCESS  read-only
   STATUS      current
   DESCRIPTION
      "Path: atm.performance.pvcTable.frameRelay.dlciTable.outPriorityQueues.packets.violateTx

       64 bit unsigned wrappable counter."
   ::= {pr1646v2ATMImaPerFrDlciOutPQsEntry 50855936}

pr1646v2ATMImaPerFrDlciOutPQsOctetsTotal OBJECT-TYPE
   SYNTAX      Counter64
   MAX-ACCESS  read-only
   STATUS      current
   DESCRIPTION
      "Path: atm.performance.pvcTable.frameRelay.dlciTable.outPriorityQueues.octets.total

       64 bit unsigned wrappable counter."
   ::= {pr1646v2ATMImaPerFrDlciOutPQsEntry 67567616}

pr1646v2ATMImaPerFrDlciOutPQsOctetsDirectTx OBJECT-TYPE
   SYNTAX      Counter64
   MAX-ACCESS  read-only
   STATUS      current
   DESCRIPTION
      "Path: atm.performance.pvcTable.frameRelay.dlciTable.outPriorityQueues.octets.directTx

       64 bit unsigned wrappable counter."
   ::= {pr1646v2ATMImaPerFrDlciOutPQsEntry 67174400}

pr1646v2ATMImaPerFrDlciOutPQsOctetsQueued OBJECT-TYPE
   SYNTAX      Counter64
   MAX-ACCESS  read-only
   STATUS      current
   DESCRIPTION
      "Path: atm.performance.pvcTable.frameRelay.dlciTable.outPriorityQueues.octets.queued

       64 bit unsigned wrappable counter."
   ::= {pr1646v2ATMImaPerFrDlciOutPQsEntry 67239936}

pr1646v2ATMImaPerFrDlciOutPQsOctetsDropped OBJECT-TYPE
   SYNTAX      Counter64
   MAX-ACCESS  read-only
   STATUS      current
   DESCRIPTION
      "Path: atm.performance.pvcTable.frameRelay.dlciTable.outPriorityQueues.octets.dropped

       64 bit unsigned wrappable counter."
   ::= {pr1646v2ATMImaPerFrDlciOutPQsEntry 67305472}

pr1646v2ATMImaPerFrDlciOutPQsOctetsRedDropped OBJECT-TYPE
   SYNTAX      Counter64
   MAX-ACCESS  read-only
   STATUS      current
   DESCRIPTION
      "Path: atm.performance.pvcTable.frameRelay.dlciTable.outPriorityQueues.octets.redDropped

       64 bit unsigned wrappable counter."
   ::= {pr1646v2ATMImaPerFrDlciOutPQsEntry 67502080}

pr1646v2ATMImaPerFrDlciOutPQsOctetsCirTx OBJECT-TYPE
   SYNTAX      Counter64
   MAX-ACCESS  read-only
   STATUS      current
   DESCRIPTION
      "Path: atm.performance.pvcTable.frameRelay.dlciTable.outPriorityQueues.octets.cirTx

       64 bit unsigned wrappable counter."
   ::= {pr1646v2ATMImaPerFrDlciOutPQsEntry 67371008}

pr1646v2ATMImaPerFrDlciOutPQsOctetsEirTx OBJECT-TYPE
   SYNTAX      Counter64
   MAX-ACCESS  read-only
   STATUS      current
   DESCRIPTION
      "Path: atm.performance.pvcTable.frameRelay.dlciTable.outPriorityQueues.octets.eirTx

       64 bit unsigned wrappable counter."
   ::= {pr1646v2ATMImaPerFrDlciOutPQsEntry 67436544}

pr1646v2ATMImaPerFrDlciOutPQsOctetsViolateTx OBJECT-TYPE
   SYNTAX      Counter64
   MAX-ACCESS  read-only
   STATUS      current
   DESCRIPTION
      "Path: atm.performance.pvcTable.frameRelay.dlciTable.outPriorityQueues.octets.violateTx

       64 bit unsigned wrappable counter."
   ::= {pr1646v2ATMImaPerFrDlciOutPQsEntry 67633152}

pr1646v2ATMImaPerFrDlciOutPQsOctetsBandwidth15sec OBJECT-TYPE
   SYNTAX      Integer32
   MAX-ACCESS  read-only
   STATUS      current
   DESCRIPTION
      "Path: atm.performance.pvcTable.frameRelay.dlciTable.outPriorityQueues.octets.bandwidth.15sec

       unit name = bps
       formula = 8 * ; 8 /"
   ::= {pr1646v2ATMImaPerFrDlciOutPQsEntry 70386944}

pr1646v2ATMImaPerFrDlciOutPQsOctetsBandwidth30sec OBJECT-TYPE
   SYNTAX      Integer32
   MAX-ACCESS  read-only
   STATUS      current
   DESCRIPTION
      "Path: atm.performance.pvcTable.frameRelay.dlciTable.outPriorityQueues.octets.bandwidth.30sec

       unit name = bps
       formula = 8 * ; 8 /"
   ::= {pr1646v2ATMImaPerFrDlciOutPQsEntry 70388224}

pr1646v2ATMImaPerFrDlciOutPQsOctetsBandwidth1min OBJECT-TYPE
   SYNTAX      Integer32
   MAX-ACCESS  read-only
   STATUS      current
   DESCRIPTION
      "Path: atm.performance.pvcTable.frameRelay.dlciTable.outPriorityQueues.octets.bandwidth.1min

       unit name = bps
       formula = 8 * ; 8 /"
   ::= {pr1646v2ATMImaPerFrDlciOutPQsEntry 70390784}

pr1646v2ATMImaPerFrDlciOutPQsOctetsBandwidth2min OBJECT-TYPE
   SYNTAX      Integer32
   MAX-ACCESS  read-only
   STATUS      current
   DESCRIPTION
      "Path: atm.performance.pvcTable.frameRelay.dlciTable.outPriorityQueues.octets.bandwidth.2min

       unit name = bps
       formula = 8 * ; 8 /"
   ::= {pr1646v2ATMImaPerFrDlciOutPQsEntry 70395904}

pr1646v2ATMImaPerFrDlciOutPQsOctetsBandwidth5min OBJECT-TYPE
   SYNTAX      Integer32
   MAX-ACCESS  read-only
   STATUS      current
   DESCRIPTION
      "Path: atm.performance.pvcTable.frameRelay.dlciTable.outPriorityQueues.octets.bandwidth.5min

       unit name = bps
       formula = 8 * ; 8 /"
   ::= {pr1646v2ATMImaPerFrDlciOutPQsEntry 70411264}

pr1646v2ATMImaPerFrDlciOutPQsH2Performance OBJECT-TYPE
   SYNTAX      SEQUENCE OF Pr1646v2ATMImaPerFrDlciOutPQsH2PerformanceEntry
   MAX-ACCESS  not-accessible
   STATUS      current
   DESCRIPTION
      ""
   ::= {pr1646v2ATMImaPer 503448837}

pr1646v2ATMImaPerFrDlciOutPQsH2PerformanceEntry OBJECT-TYPE
   SYNTAX      Pr1646v2ATMImaPerFrDlciOutPQsH2PerformanceEntry
   MAX-ACCESS  not-accessible
   STATUS      current
   DESCRIPTION
      ""
   INDEX      { pr1646v2ATMImaPerTableIx,
                pr1646v2ATMImaPerFrDlciTableIx,
                pr1646v2ATMImaPerFrDlciOutPQsTableIx,
                pr1646v2ATMImaPerFrDlciOutPQsH2PerformanceTableIx }
   ::= {pr1646v2ATMImaPerFrDlciOutPQsH2Performance 1}

Pr1646v2ATMImaPerFrDlciOutPQsH2PerformanceEntry ::=
   SEQUENCE
      {
      pr1646v2ATMImaPerFrDlciOutPQsH2PerformanceTableIx
         TableIndex,
      pr1646v2ATMImaPerFrDlciOutPQsH2PerformanceSysUpTime
         TimeTicks,
      pr1646v2ATMImaPerFrDlciOutPQsH2PerformanceTotPkts
         Counter64,
      pr1646v2ATMImaPerFrDlciOutPQsH2PerformanceDirTxPkts
         Counter64,
      pr1646v2ATMImaPerFrDlciOutPQsH2PerformanceQdPkts
         Counter64,
      pr1646v2ATMImaPerFrDlciOutPQsH2PerformanceDropPkts
         Counter64,
      pr1646v2ATMImaPerFrDlciOutPQsH2PerformanceRDropPkts
         Counter64,
      pr1646v2ATMImaPerFrDlciOutPQsH2PerformanceCirTxPkts
         Counter64,
      pr1646v2ATMImaPerFrDlciOutPQsH2PerformanceEirTxPkts
         Counter64,
      pr1646v2ATMImaPerFrDlciOutPQsH2PerformanceViolTxPkts
         Counter64,
      pr1646v2ATMImaPerFrDlciOutPQsH2PerformanceTotOcts
         Counter64,
      pr1646v2ATMImaPerFrDlciOutPQsH2PerformanceDirTxOcts
         Counter64,
      pr1646v2ATMImaPerFrDlciOutPQsH2PerformanceQdOcts
         Counter64,
      pr1646v2ATMImaPerFrDlciOutPQsH2PerformanceDropOcts
         Counter64,
      pr1646v2ATMImaPerFrDlciOutPQsH2PerformanceRDropOcts
         Counter64,
      pr1646v2ATMImaPerFrDlciOutPQsH2PerformanceCirTxOcts
         Counter64,
      pr1646v2ATMImaPerFrDlciOutPQsH2PerformanceEirTxOcts
         Counter64,
      pr1646v2ATMImaPerFrDlciOutPQsH2PerformanceViolTxOcts
         Counter64,
      pr1646v2ATMImaPerFrDlciOutPQsH2PerformanceBandwidth
         Integer32
      }

pr1646v2ATMImaPerFrDlciOutPQsH2PerformanceTableIx OBJECT-TYPE
   SYNTAX      TableIndex
   MAX-ACCESS  not-accessible
   STATUS      current
   DESCRIPTION
      ""
   ::= {pr1646v2ATMImaPerFrDlciOutPQsH2PerformanceEntry 11}

pr1646v2ATMImaPerFrDlciOutPQsH2PerformanceSysUpTime OBJECT-TYPE
   SYNTAX      TimeTicks
   MAX-ACCESS  read-only
   STATUS      current
   DESCRIPTION
      "Path: atm.performance.pvcTable.frameRelay.dlciTable.outPriorityQueues.h2Performance.sysUpTime

       Time in centi-second."
   ::= {pr1646v2ATMImaPerFrDlciOutPQsH2PerformanceEntry 16777216}

pr1646v2ATMImaPerFrDlciOutPQsH2PerformanceTotPkts OBJECT-TYPE
   SYNTAX      Counter64
   MAX-ACCESS  read-only
   STATUS      current
   DESCRIPTION
      "Path: atm.performance.pvcTable.frameRelay.dlciTable.outPriorityQueues.h2Performance.totalPkts

       64 bit unsigned wrappable counter."
   ::= {pr1646v2ATMImaPerFrDlciOutPQsH2PerformanceEntry 234881024}

pr1646v2ATMImaPerFrDlciOutPQsH2PerformanceDirTxPkts OBJECT-TYPE
   SYNTAX      Counter64
   MAX-ACCESS  read-only
   STATUS      current
   DESCRIPTION
      "Path: atm.performance.pvcTable.frameRelay.dlciTable.outPriorityQueues.h2Performance.directTxPkts

       64 bit unsigned wrappable counter."
   ::= {pr1646v2ATMImaPerFrDlciOutPQsH2PerformanceEntry 33554432}

pr1646v2ATMImaPerFrDlciOutPQsH2PerformanceQdPkts OBJECT-TYPE
   SYNTAX      Counter64
   MAX-ACCESS  read-only
   STATUS      current
   DESCRIPTION
      "Path: atm.performance.pvcTable.frameRelay.dlciTable.outPriorityQueues.h2Performance.queuedPkts

       64 bit unsigned wrappable counter."
   ::= {pr1646v2ATMImaPerFrDlciOutPQsH2PerformanceEntry 50331648}

pr1646v2ATMImaPerFrDlciOutPQsH2PerformanceDropPkts OBJECT-TYPE
   SYNTAX      Counter64
   MAX-ACCESS  read-only
   STATUS      current
   DESCRIPTION
      "Path: atm.performance.pvcTable.frameRelay.dlciTable.outPriorityQueues.h2Performance.droppedPkts

       64 bit unsigned wrappable counter."
   ::= {pr1646v2ATMImaPerFrDlciOutPQsH2PerformanceEntry 67108864}

pr1646v2ATMImaPerFrDlciOutPQsH2PerformanceRDropPkts OBJECT-TYPE
   SYNTAX      Counter64
   MAX-ACCESS  read-only
   STATUS      current
   DESCRIPTION
      "Path: atm.performance.pvcTable.frameRelay.dlciTable.outPriorityQueues.h2Performance.redDroppedPkts

       64 bit unsigned wrappable counter."
   ::= {pr1646v2ATMImaPerFrDlciOutPQsH2PerformanceEntry 201326592}

pr1646v2ATMImaPerFrDlciOutPQsH2PerformanceCirTxPkts OBJECT-TYPE
   SYNTAX      Counter64
   MAX-ACCESS  read-only
   STATUS      current
   DESCRIPTION
      "Path: atm.performance.pvcTable.frameRelay.dlciTable.outPriorityQueues.h2Performance.cirTxPkts

       64 bit unsigned wrappable counter."
   ::= {pr1646v2ATMImaPerFrDlciOutPQsH2PerformanceEntry 83886080}

pr1646v2ATMImaPerFrDlciOutPQsH2PerformanceEirTxPkts OBJECT-TYPE
   SYNTAX      Counter64
   MAX-ACCESS  read-only
   STATUS      current
   DESCRIPTION
      "Path: atm.performance.pvcTable.frameRelay.dlciTable.outPriorityQueues.h2Performance.eirTxPkts

       64 bit unsigned wrappable counter."
   ::= {pr1646v2ATMImaPerFrDlciOutPQsH2PerformanceEntry 100663296}

pr1646v2ATMImaPerFrDlciOutPQsH2PerformanceViolTxPkts OBJECT-TYPE
   SYNTAX      Counter64
   MAX-ACCESS  read-only
   STATUS      current
   DESCRIPTION
      "Path: atm.performance.pvcTable.frameRelay.dlciTable.outPriorityQueues.h2Performance.violateTxPkts

       64 bit unsigned wrappable counter."
   ::= {pr1646v2ATMImaPerFrDlciOutPQsH2PerformanceEntry 301989888}

pr1646v2ATMImaPerFrDlciOutPQsH2PerformanceTotOcts OBJECT-TYPE
   SYNTAX      Counter64
   MAX-ACCESS  read-only
   STATUS      current
   DESCRIPTION
      "Path: atm.performance.pvcTable.frameRelay.dlciTable.outPriorityQueues.h2Performance.totalOctets

       64 bit unsigned wrappable counter."
   ::= {pr1646v2ATMImaPerFrDlciOutPQsH2PerformanceEntry 251658240}

pr1646v2ATMImaPerFrDlciOutPQsH2PerformanceDirTxOcts OBJECT-TYPE
   SYNTAX      Counter64
   MAX-ACCESS  read-only
   STATUS      current
   DESCRIPTION
      "Path: atm.performance.pvcTable.frameRelay.dlciTable.outPriorityQueues.h2Performance.directTxOctets

       64 bit unsigned wrappable counter."
   ::= {pr1646v2ATMImaPerFrDlciOutPQsH2PerformanceEntry 117440512}

pr1646v2ATMImaPerFrDlciOutPQsH2PerformanceQdOcts OBJECT-TYPE
   SYNTAX      Counter64
   MAX-ACCESS  read-only
   STATUS      current
   DESCRIPTION
      "Path: atm.performance.pvcTable.frameRelay.dlciTable.outPriorityQueues.h2Performance.queuedOctets

       64 bit unsigned wrappable counter."
   ::= {pr1646v2ATMImaPerFrDlciOutPQsH2PerformanceEntry 134217728}

pr1646v2ATMImaPerFrDlciOutPQsH2PerformanceDropOcts OBJECT-TYPE
   SYNTAX      Counter64
   MAX-ACCESS  read-only
   STATUS      current
   DESCRIPTION
      "Path: atm.performance.pvcTable.frameRelay.dlciTable.outPriorityQueues.h2Performance.droppedOctets

       64 bit unsigned wrappable counter."
   ::= {pr1646v2ATMImaPerFrDlciOutPQsH2PerformanceEntry 150994944}

pr1646v2ATMImaPerFrDlciOutPQsH2PerformanceRDropOcts OBJECT-TYPE
   SYNTAX      Counter64
   MAX-ACCESS  read-only
   STATUS      current
   DESCRIPTION
      "Path: atm.performance.pvcTable.frameRelay.dlciTable.outPriorityQueues.h2Performance.redDroppedOctets

       64 bit unsigned wrappable counter."
   ::= {pr1646v2ATMImaPerFrDlciOutPQsH2PerformanceEntry 218103808}

pr1646v2ATMImaPerFrDlciOutPQsH2PerformanceCirTxOcts OBJECT-TYPE
   SYNTAX      Counter64
   MAX-ACCESS  read-only
   STATUS      current
   DESCRIPTION
      "Path: atm.performance.pvcTable.frameRelay.dlciTable.outPriorityQueues.h2Performance.cirTxOctets

       64 bit unsigned wrappable counter."
   ::= {pr1646v2ATMImaPerFrDlciOutPQsH2PerformanceEntry 167772160}

pr1646v2ATMImaPerFrDlciOutPQsH2PerformanceEirTxOcts OBJECT-TYPE
   SYNTAX      Counter64
   MAX-ACCESS  read-only
   STATUS      current
   DESCRIPTION
      "Path: atm.performance.pvcTable.frameRelay.dlciTable.outPriorityQueues.h2Performance.eirTxOctets

       64 bit unsigned wrappable counter."
   ::= {pr1646v2ATMImaPerFrDlciOutPQsH2PerformanceEntry 184549376}

pr1646v2ATMImaPerFrDlciOutPQsH2PerformanceViolTxOcts OBJECT-TYPE
   SYNTAX      Counter64
   MAX-ACCESS  read-only
   STATUS      current
   DESCRIPTION
      "Path: atm.performance.pvcTable.frameRelay.dlciTable.outPriorityQueues.h2Performance.violateTxOctets

       64 bit unsigned wrappable counter."
   ::= {pr1646v2ATMImaPerFrDlciOutPQsH2PerformanceEntry 318767104}

pr1646v2ATMImaPerFrDlciOutPQsH2PerformanceBandwidth OBJECT-TYPE
   SYNTAX      Integer32
   MAX-ACCESS  read-only
   STATUS      current
   DESCRIPTION
      "Path: atm.performance.pvcTable.frameRelay.dlciTable.outPriorityQueues.h2Performance.bandwidth

       unit name = bps
       formula = 8 * ; 8 /"
   ::= {pr1646v2ATMImaPerFrDlciOutPQsH2PerformanceEntry 268435456}

pr1646v2ATMImaPerFrDlciOutPQsH24Performance OBJECT-TYPE
   SYNTAX      SEQUENCE OF Pr1646v2ATMImaPerFrDlciOutPQsH24PerformanceEntry
   MAX-ACCESS  not-accessible
   STATUS      current
   DESCRIPTION
      ""
   ::= {pr1646v2ATMImaPer 503448838}

pr1646v2ATMImaPerFrDlciOutPQsH24PerformanceEntry OBJECT-TYPE
   SYNTAX      Pr1646v2ATMImaPerFrDlciOutPQsH24PerformanceEntry
   MAX-ACCESS  not-accessible
   STATUS      current
   DESCRIPTION
      ""
   INDEX      { pr1646v2ATMImaPerTableIx,
                pr1646v2ATMImaPerFrDlciTableIx,
                pr1646v2ATMImaPerFrDlciOutPQsTableIx,
                pr1646v2ATMImaPerFrDlciOutPQsH24PerformanceTableIx }
   ::= {pr1646v2ATMImaPerFrDlciOutPQsH24Performance 1}

Pr1646v2ATMImaPerFrDlciOutPQsH24PerformanceEntry ::=
   SEQUENCE
      {
      pr1646v2ATMImaPerFrDlciOutPQsH24PerformanceTableIx
         TableIndex,
      pr1646v2ATMImaPerFrDlciOutPQsH24PerformanceSysUpTime
         TimeTicks,
      pr1646v2ATMImaPerFrDlciOutPQsH24PerformanceTotPkts
         Counter64,
      pr1646v2ATMImaPerFrDlciOutPQsH24PerformanceDirTxPkts
         Counter64,
      pr1646v2ATMImaPerFrDlciOutPQsH24PerformanceQdPkts
         Counter64,
      pr1646v2ATMImaPerFrDlciOutPQsH24PerformanceDropPkts
         Counter64,
      pr1646v2ATMImaPerFrDlciOutPQsH24PerformanceRDropPkts
         Counter64,
      pr1646v2ATMImaPerFrDlciOutPQsH24PerformanceCirTxPkts
         Counter64,
      pr1646v2ATMImaPerFrDlciOutPQsH24PerformanceEirTxPkts
         Counter64,
      pr1646v2ATMImaPerFrDlciOutPQsH24PerformanceViolTxPkts
         Counter64,
      pr1646v2ATMImaPerFrDlciOutPQsH24PerformanceTotOcts
         Counter64,
      pr1646v2ATMImaPerFrDlciOutPQsH24PerformanceDirTxOcts
         Counter64,
      pr1646v2ATMImaPerFrDlciOutPQsH24PerformanceQdOcts
         Counter64,
      pr1646v2ATMImaPerFrDlciOutPQsH24PerformanceDropOcts
         Counter64,
      pr1646v2ATMImaPerFrDlciOutPQsH24PerformanceRDropOcts
         Counter64,
      pr1646v2ATMImaPerFrDlciOutPQsH24PerformanceCirTxOcts
         Counter64,
      pr1646v2ATMImaPerFrDlciOutPQsH24PerformanceEirTxOcts
         Counter64,
      pr1646v2ATMImaPerFrDlciOutPQsH24PerformanceViolTxOcts
         Counter64,
      pr1646v2ATMImaPerFrDlciOutPQsH24PerformanceBandwidth
         Integer32
      }

pr1646v2ATMImaPerFrDlciOutPQsH24PerformanceTableIx OBJECT-TYPE
   SYNTAX      TableIndex
   MAX-ACCESS  not-accessible
   STATUS      current
   DESCRIPTION
      ""
   ::= {pr1646v2ATMImaPerFrDlciOutPQsH24PerformanceEntry 11}

pr1646v2ATMImaPerFrDlciOutPQsH24PerformanceSysUpTime OBJECT-TYPE
   SYNTAX      TimeTicks
   MAX-ACCESS  read-only
   STATUS      current
   DESCRIPTION
      "Path: atm.performance.pvcTable.frameRelay.dlciTable.outPriorityQueues.h24Performance.sysUpTime

       Time in centi-second."
   ::= {pr1646v2ATMImaPerFrDlciOutPQsH24PerformanceEntry 16777216}

pr1646v2ATMImaPerFrDlciOutPQsH24PerformanceTotPkts OBJECT-TYPE
   SYNTAX      Counter64
   MAX-ACCESS  read-only
   STATUS      current
   DESCRIPTION
      "Path: atm.performance.pvcTable.frameRelay.dlciTable.outPriorityQueues.h24Performance.totalPkts

       64 bit unsigned wrappable counter."
   ::= {pr1646v2ATMImaPerFrDlciOutPQsH24PerformanceEntry 234881024}

pr1646v2ATMImaPerFrDlciOutPQsH24PerformanceDirTxPkts OBJECT-TYPE
   SYNTAX      Counter64
   MAX-ACCESS  read-only
   STATUS      current
   DESCRIPTION
      "Path: atm.performance.pvcTable.frameRelay.dlciTable.outPriorityQueues.h24Performance.directTxPkts

       64 bit unsigned wrappable counter."
   ::= {pr1646v2ATMImaPerFrDlciOutPQsH24PerformanceEntry 33554432}

pr1646v2ATMImaPerFrDlciOutPQsH24PerformanceQdPkts OBJECT-TYPE
   SYNTAX      Counter64
   MAX-ACCESS  read-only
   STATUS      current
   DESCRIPTION
      "Path: atm.performance.pvcTable.frameRelay.dlciTable.outPriorityQueues.h24Performance.queuedPkts

       64 bit unsigned wrappable counter."
   ::= {pr1646v2ATMImaPerFrDlciOutPQsH24PerformanceEntry 50331648}

pr1646v2ATMImaPerFrDlciOutPQsH24PerformanceDropPkts OBJECT-TYPE
   SYNTAX      Counter64
   MAX-ACCESS  read-only
   STATUS      current
   DESCRIPTION
      "Path: atm.performance.pvcTable.frameRelay.dlciTable.outPriorityQueues.h24Performance.droppedPkts

       64 bit unsigned wrappable counter."
   ::= {pr1646v2ATMImaPerFrDlciOutPQsH24PerformanceEntry 67108864}

pr1646v2ATMImaPerFrDlciOutPQsH24PerformanceRDropPkts OBJECT-TYPE
   SYNTAX      Counter64
   MAX-ACCESS  read-only
   STATUS      current
   DESCRIPTION
      "Path: atm.performance.pvcTable.frameRelay.dlciTable.outPriorityQueues.h24Performance.redDroppedPkts

       64 bit unsigned wrappable counter."
   ::= {pr1646v2ATMImaPerFrDlciOutPQsH24PerformanceEntry 201326592}

pr1646v2ATMImaPerFrDlciOutPQsH24PerformanceCirTxPkts OBJECT-TYPE
   SYNTAX      Counter64
   MAX-ACCESS  read-only
   STATUS      current
   DESCRIPTION
      "Path: atm.performance.pvcTable.frameRelay.dlciTable.outPriorityQueues.h24Performance.cirTxPkts

       64 bit unsigned wrappable counter."
   ::= {pr1646v2ATMImaPerFrDlciOutPQsH24PerformanceEntry 83886080}

pr1646v2ATMImaPerFrDlciOutPQsH24PerformanceEirTxPkts OBJECT-TYPE
   SYNTAX      Counter64
   MAX-ACCESS  read-only
   STATUS      current
   DESCRIPTION
      "Path: atm.performance.pvcTable.frameRelay.dlciTable.outPriorityQueues.h24Performance.eirTxPkts

       64 bit unsigned wrappable counter."
   ::= {pr1646v2ATMImaPerFrDlciOutPQsH24PerformanceEntry 100663296}

pr1646v2ATMImaPerFrDlciOutPQsH24PerformanceViolTxPkts OBJECT-TYPE
   SYNTAX      Counter64
   MAX-ACCESS  read-only
   STATUS      current
   DESCRIPTION
      "Path: atm.performance.pvcTable.frameRelay.dlciTable.outPriorityQueues.h24Performance.violateTxPkts

       64 bit unsigned wrappable counter."
   ::= {pr1646v2ATMImaPerFrDlciOutPQsH24PerformanceEntry 301989888}

pr1646v2ATMImaPerFrDlciOutPQsH24PerformanceTotOcts OBJECT-TYPE
   SYNTAX      Counter64
   MAX-ACCESS  read-only
   STATUS      current
   DESCRIPTION
      "Path: atm.performance.pvcTable.frameRelay.dlciTable.outPriorityQueues.h24Performance.totalOctets

       64 bit unsigned wrappable counter."
   ::= {pr1646v2ATMImaPerFrDlciOutPQsH24PerformanceEntry 251658240}

pr1646v2ATMImaPerFrDlciOutPQsH24PerformanceDirTxOcts OBJECT-TYPE
   SYNTAX      Counter64
   MAX-ACCESS  read-only
   STATUS      current
   DESCRIPTION
      "Path: atm.performance.pvcTable.frameRelay.dlciTable.outPriorityQueues.h24Performance.directTxOctets

       64 bit unsigned wrappable counter."
   ::= {pr1646v2ATMImaPerFrDlciOutPQsH24PerformanceEntry 117440512}

pr1646v2ATMImaPerFrDlciOutPQsH24PerformanceQdOcts OBJECT-TYPE
   SYNTAX      Counter64
   MAX-ACCESS  read-only
   STATUS      current
   DESCRIPTION
      "Path: atm.performance.pvcTable.frameRelay.dlciTable.outPriorityQueues.h24Performance.queuedOctets

       64 bit unsigned wrappable counter."
   ::= {pr1646v2ATMImaPerFrDlciOutPQsH24PerformanceEntry 134217728}

pr1646v2ATMImaPerFrDlciOutPQsH24PerformanceDropOcts OBJECT-TYPE
   SYNTAX      Counter64
   MAX-ACCESS  read-only
   STATUS      current
   DESCRIPTION
      "Path: atm.performance.pvcTable.frameRelay.dlciTable.outPriorityQueues.h24Performance.droppedOctets

       64 bit unsigned wrappable counter."
   ::= {pr1646v2ATMImaPerFrDlciOutPQsH24PerformanceEntry 150994944}

pr1646v2ATMImaPerFrDlciOutPQsH24PerformanceRDropOcts OBJECT-TYPE
   SYNTAX      Counter64
   MAX-ACCESS  read-only
   STATUS      current
   DESCRIPTION
      "Path: atm.performance.pvcTable.frameRelay.dlciTable.outPriorityQueues.h24Performance.redDroppedOctets

       64 bit unsigned wrappable counter."
   ::= {pr1646v2ATMImaPerFrDlciOutPQsH24PerformanceEntry 218103808}

pr1646v2ATMImaPerFrDlciOutPQsH24PerformanceCirTxOcts OBJECT-TYPE
   SYNTAX      Counter64
   MAX-ACCESS  read-only
   STATUS      current
   DESCRIPTION
      "Path: atm.performance.pvcTable.frameRelay.dlciTable.outPriorityQueues.h24Performance.cirTxOctets

       64 bit unsigned wrappable counter."
   ::= {pr1646v2ATMImaPerFrDlciOutPQsH24PerformanceEntry 167772160}

pr1646v2ATMImaPerFrDlciOutPQsH24PerformanceEirTxOcts OBJECT-TYPE
   SYNTAX      Counter64
   MAX-ACCESS  read-only
   STATUS      current
   DESCRIPTION
      "Path: atm.performance.pvcTable.frameRelay.dlciTable.outPriorityQueues.h24Performance.eirTxOctets

       64 bit unsigned wrappable counter."
   ::= {pr1646v2ATMImaPerFrDlciOutPQsH24PerformanceEntry 184549376}

pr1646v2ATMImaPerFrDlciOutPQsH24PerformanceViolTxOcts OBJECT-TYPE
   SYNTAX      Counter64
   MAX-ACCESS  read-only
   STATUS      current
   DESCRIPTION
      "Path: atm.performance.pvcTable.frameRelay.dlciTable.outPriorityQueues.h24Performance.violateTxOctets

       64 bit unsigned wrappable counter."
   ::= {pr1646v2ATMImaPerFrDlciOutPQsH24PerformanceEntry 318767104}

pr1646v2ATMImaPerFrDlciOutPQsH24PerformanceBandwidth OBJECT-TYPE
   SYNTAX      Integer32
   MAX-ACCESS  read-only
   STATUS      current
   DESCRIPTION
      "Path: atm.performance.pvcTable.frameRelay.dlciTable.outPriorityQueues.h24Performance.bandwidth

       unit name = bps
       formula = 8 * ; 8 /"
   ::= {pr1646v2ATMImaPerFrDlciOutPQsH24PerformanceEntry 268435456}

pr1646v2ATMImaPerFrDlciOutPQsD7Performance OBJECT-TYPE
   SYNTAX      SEQUENCE OF Pr1646v2ATMImaPerFrDlciOutPQsD7PerformanceEntry
   MAX-ACCESS  not-accessible
   STATUS      current
   DESCRIPTION
      ""
   ::= {pr1646v2ATMImaPer 503448839}

pr1646v2ATMImaPerFrDlciOutPQsD7PerformanceEntry OBJECT-TYPE
   SYNTAX      Pr1646v2ATMImaPerFrDlciOutPQsD7PerformanceEntry
   MAX-ACCESS  not-accessible
   STATUS      current
   DESCRIPTION
      ""
   INDEX      { pr1646v2ATMImaPerTableIx,
                pr1646v2ATMImaPerFrDlciTableIx,
                pr1646v2ATMImaPerFrDlciOutPQsTableIx,
                pr1646v2ATMImaPerFrDlciOutPQsD7PerformanceTableIx }
   ::= {pr1646v2ATMImaPerFrDlciOutPQsD7Performance 1}

Pr1646v2ATMImaPerFrDlciOutPQsD7PerformanceEntry ::=
   SEQUENCE
      {
      pr1646v2ATMImaPerFrDlciOutPQsD7PerformanceTableIx
         TableIndex,
      pr1646v2ATMImaPerFrDlciOutPQsD7PerformanceSysUpTime
         TimeTicks,
      pr1646v2ATMImaPerFrDlciOutPQsD7PerformanceTotPkts
         Counter64,
      pr1646v2ATMImaPerFrDlciOutPQsD7PerformanceDirTxPkts
         Counter64,
      pr1646v2ATMImaPerFrDlciOutPQsD7PerformanceQdPkts
         Counter64,
      pr1646v2ATMImaPerFrDlciOutPQsD7PerformanceDropPkts
         Counter64,
      pr1646v2ATMImaPerFrDlciOutPQsD7PerformanceRDropPkts
         Counter64,
      pr1646v2ATMImaPerFrDlciOutPQsD7PerformanceCirTxPkts
         Counter64,
      pr1646v2ATMImaPerFrDlciOutPQsD7PerformanceEirTxPkts
         Counter64,
      pr1646v2ATMImaPerFrDlciOutPQsD7PerformanceViolTxPkts
         Counter64,
      pr1646v2ATMImaPerFrDlciOutPQsD7PerformanceTotOcts
         Counter64,
      pr1646v2ATMImaPerFrDlciOutPQsD7PerformanceDirTxOcts
         Counter64,
      pr1646v2ATMImaPerFrDlciOutPQsD7PerformanceQdOcts
         Counter64,
      pr1646v2ATMImaPerFrDlciOutPQsD7PerformanceDropOcts
         Counter64,
      pr1646v2ATMImaPerFrDlciOutPQsD7PerformanceRDropOcts
         Counter64,
      pr1646v2ATMImaPerFrDlciOutPQsD7PerformanceCirTxOcts
         Counter64,
      pr1646v2ATMImaPerFrDlciOutPQsD7PerformanceEirTxOcts
         Counter64,
      pr1646v2ATMImaPerFrDlciOutPQsD7PerformanceViolTxOcts
         Counter64,
      pr1646v2ATMImaPerFrDlciOutPQsD7PerformanceBandwidth
         Integer32
      }

pr1646v2ATMImaPerFrDlciOutPQsD7PerformanceTableIx OBJECT-TYPE
   SYNTAX      TableIndex
   MAX-ACCESS  not-accessible
   STATUS      current
   DESCRIPTION
      ""
   ::= {pr1646v2ATMImaPerFrDlciOutPQsD7PerformanceEntry 11}

pr1646v2ATMImaPerFrDlciOutPQsD7PerformanceSysUpTime OBJECT-TYPE
   SYNTAX      TimeTicks
   MAX-ACCESS  read-only
   STATUS      current
   DESCRIPTION
      "Path: atm.performance.pvcTable.frameRelay.dlciTable.outPriorityQueues.d7Performance.sysUpTime

       Time in centi-second."
   ::= {pr1646v2ATMImaPerFrDlciOutPQsD7PerformanceEntry 16777216}

pr1646v2ATMImaPerFrDlciOutPQsD7PerformanceTotPkts OBJECT-TYPE
   SYNTAX      Counter64
   MAX-ACCESS  read-only
   STATUS      current
   DESCRIPTION
      "Path: atm.performance.pvcTable.frameRelay.dlciTable.outPriorityQueues.d7Performance.totalPkts

       64 bit unsigned wrappable counter."
   ::= {pr1646v2ATMImaPerFrDlciOutPQsD7PerformanceEntry 234881024}

pr1646v2ATMImaPerFrDlciOutPQsD7PerformanceDirTxPkts OBJECT-TYPE
   SYNTAX      Counter64
   MAX-ACCESS  read-only
   STATUS      current
   DESCRIPTION
      "Path: atm.performance.pvcTable.frameRelay.dlciTable.outPriorityQueues.d7Performance.directTxPkts

       64 bit unsigned wrappable counter."
   ::= {pr1646v2ATMImaPerFrDlciOutPQsD7PerformanceEntry 33554432}

pr1646v2ATMImaPerFrDlciOutPQsD7PerformanceQdPkts OBJECT-TYPE
   SYNTAX      Counter64
   MAX-ACCESS  read-only
   STATUS      current
   DESCRIPTION
      "Path: atm.performance.pvcTable.frameRelay.dlciTable.outPriorityQueues.d7Performance.queuedPkts

       64 bit unsigned wrappable counter."
   ::= {pr1646v2ATMImaPerFrDlciOutPQsD7PerformanceEntry 50331648}

pr1646v2ATMImaPerFrDlciOutPQsD7PerformanceDropPkts OBJECT-TYPE
   SYNTAX      Counter64
   MAX-ACCESS  read-only
   STATUS      current
   DESCRIPTION
      "Path: atm.performance.pvcTable.frameRelay.dlciTable.outPriorityQueues.d7Performance.droppedPkts

       64 bit unsigned wrappable counter."
   ::= {pr1646v2ATMImaPerFrDlciOutPQsD7PerformanceEntry 67108864}

pr1646v2ATMImaPerFrDlciOutPQsD7PerformanceRDropPkts OBJECT-TYPE
   SYNTAX      Counter64
   MAX-ACCESS  read-only
   STATUS      current
   DESCRIPTION
      "Path: atm.performance.pvcTable.frameRelay.dlciTable.outPriorityQueues.d7Performance.redDroppedPkts

       64 bit unsigned wrappable counter."
   ::= {pr1646v2ATMImaPerFrDlciOutPQsD7PerformanceEntry 201326592}

pr1646v2ATMImaPerFrDlciOutPQsD7PerformanceCirTxPkts OBJECT-TYPE
   SYNTAX      Counter64
   MAX-ACCESS  read-only
   STATUS      current
   DESCRIPTION
      "Path: atm.performance.pvcTable.frameRelay.dlciTable.outPriorityQueues.d7Performance.cirTxPkts

       64 bit unsigned wrappable counter."
   ::= {pr1646v2ATMImaPerFrDlciOutPQsD7PerformanceEntry 83886080}

pr1646v2ATMImaPerFrDlciOutPQsD7PerformanceEirTxPkts OBJECT-TYPE
   SYNTAX      Counter64
   MAX-ACCESS  read-only
   STATUS      current
   DESCRIPTION
      "Path: atm.performance.pvcTable.frameRelay.dlciTable.outPriorityQueues.d7Performance.eirTxPkts

       64 bit unsigned wrappable counter."
   ::= {pr1646v2ATMImaPerFrDlciOutPQsD7PerformanceEntry 100663296}

pr1646v2ATMImaPerFrDlciOutPQsD7PerformanceViolTxPkts OBJECT-TYPE
   SYNTAX      Counter64
   MAX-ACCESS  read-only
   STATUS      current
   DESCRIPTION
      "Path: atm.performance.pvcTable.frameRelay.dlciTable.outPriorityQueues.d7Performance.violateTxPkts

       64 bit unsigned wrappable counter."
   ::= {pr1646v2ATMImaPerFrDlciOutPQsD7PerformanceEntry 301989888}

pr1646v2ATMImaPerFrDlciOutPQsD7PerformanceTotOcts OBJECT-TYPE
   SYNTAX      Counter64
   MAX-ACCESS  read-only
   STATUS      current
   DESCRIPTION
      "Path: atm.performance.pvcTable.frameRelay.dlciTable.outPriorityQueues.d7Performance.totalOctets

       64 bit unsigned wrappable counter."
   ::= {pr1646v2ATMImaPerFrDlciOutPQsD7PerformanceEntry 251658240}

pr1646v2ATMImaPerFrDlciOutPQsD7PerformanceDirTxOcts OBJECT-TYPE
   SYNTAX      Counter64
   MAX-ACCESS  read-only
   STATUS      current
   DESCRIPTION
      "Path: atm.performance.pvcTable.frameRelay.dlciTable.outPriorityQueues.d7Performance.directTxOctets

       64 bit unsigned wrappable counter."
   ::= {pr1646v2ATMImaPerFrDlciOutPQsD7PerformanceEntry 117440512}

pr1646v2ATMImaPerFrDlciOutPQsD7PerformanceQdOcts OBJECT-TYPE
   SYNTAX      Counter64
   MAX-ACCESS  read-only
   STATUS      current
   DESCRIPTION
      "Path: atm.performance.pvcTable.frameRelay.dlciTable.outPriorityQueues.d7Performance.queuedOctets

       64 bit unsigned wrappable counter."
   ::= {pr1646v2ATMImaPerFrDlciOutPQsD7PerformanceEntry 134217728}

pr1646v2ATMImaPerFrDlciOutPQsD7PerformanceDropOcts OBJECT-TYPE
   SYNTAX      Counter64
   MAX-ACCESS  read-only
   STATUS      current
   DESCRIPTION
      "Path: atm.performance.pvcTable.frameRelay.dlciTable.outPriorityQueues.d7Performance.droppedOctets

       64 bit unsigned wrappable counter."
   ::= {pr1646v2ATMImaPerFrDlciOutPQsD7PerformanceEntry 150994944}

pr1646v2ATMImaPerFrDlciOutPQsD7PerformanceRDropOcts OBJECT-TYPE
   SYNTAX      Counter64
   MAX-ACCESS  read-only
   STATUS      current
   DESCRIPTION
      "Path: atm.performance.pvcTable.frameRelay.dlciTable.outPriorityQueues.d7Performance.redDroppedOctets

       64 bit unsigned wrappable counter."
   ::= {pr1646v2ATMImaPerFrDlciOutPQsD7PerformanceEntry 218103808}

pr1646v2ATMImaPerFrDlciOutPQsD7PerformanceCirTxOcts OBJECT-TYPE
   SYNTAX      Counter64
   MAX-ACCESS  read-only
   STATUS      current
   DESCRIPTION
      "Path: atm.performance.pvcTable.frameRelay.dlciTable.outPriorityQueues.d7Performance.cirTxOctets

       64 bit unsigned wrappable counter."
   ::= {pr1646v2ATMImaPerFrDlciOutPQsD7PerformanceEntry 167772160}

pr1646v2ATMImaPerFrDlciOutPQsD7PerformanceEirTxOcts OBJECT-TYPE
   SYNTAX      Counter64
   MAX-ACCESS  read-only
   STATUS      current
   DESCRIPTION
      "Path: atm.performance.pvcTable.frameRelay.dlciTable.outPriorityQueues.d7Performance.eirTxOctets

       64 bit unsigned wrappable counter."
   ::= {pr1646v2ATMImaPerFrDlciOutPQsD7PerformanceEntry 184549376}

pr1646v2ATMImaPerFrDlciOutPQsD7PerformanceViolTxOcts OBJECT-TYPE
   SYNTAX      Counter64
   MAX-ACCESS  read-only
   STATUS      current
   DESCRIPTION
      "Path: atm.performance.pvcTable.frameRelay.dlciTable.outPriorityQueues.d7Performance.violateTxOctets

       64 bit unsigned wrappable counter."
   ::= {pr1646v2ATMImaPerFrDlciOutPQsD7PerformanceEntry 318767104}

pr1646v2ATMImaPerFrDlciOutPQsD7PerformanceBandwidth OBJECT-TYPE
   SYNTAX      Integer32
   MAX-ACCESS  read-only
   STATUS      current
   DESCRIPTION
      "Path: atm.performance.pvcTable.frameRelay.dlciTable.outPriorityQueues.d7Performance.bandwidth

       unit name = bps
       formula = 8 * ; 8 /"
   ::= {pr1646v2ATMImaPerFrDlciOutPQsD7PerformanceEntry 268435456}



ar1646v2ATMIma OBJECT IDENTIFIER ::= {r1646v2ATMIma 16}


ar1646v2ATMImaClearCounters OBJECT-TYPE
   SYNTAX      Integer32
   MAX-ACCESS  read-write
   STATUS      current
   DESCRIPTION
      "Path: atm.actions.clearCounters
       Info: reset counters"
   ::= {ar1646v2ATMIma 263}



END
