OneAccess-R1645v2-4491 DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2 OBJECT IDENTIFIER ::= {r1645Rootv2 4491}

r1645v2MOProp OBJECT IDENTIFIER ::= {r1645v2 1}

r1645v2MOPropEntry OBJECT IDENTIFIER ::= {r1645v2MOProp 1}

r1645v2MOPropPath OBJECT-TYPE
   SYNTAX      ContainmentPath
   MAX-ACCESS  read-only
   STATUS      current
   DESCRIPTION
      "Textual description of the containment tree from the instance of
       the root object down to the instance of the current object."
   ::= {r1645v2MOPropEntry 3}

r1645v2MOPropRev OBJECT-TYPE
   SYNTAX      ObjectRevision
   MAX-ACCESS  read-only
   STATUS      current
   DESCRIPTION
      "This value corresponds with the revision of the MANAGED OBJECT."
   ::= {r1645v2MOPropEntry 4}



er1645v2 OBJECT IDENTIFIER ::= {r1645v2 11}


er1645v2SysName OBJECT-TYPE
   SYNTAX      DisplayString
   MAX-ACCESS  read-write
   STATUS      current
   DESCRIPTION
      "Path: router1645.editConf.sysName
       Info: sysName"
   ::= {er1645v2 1}


er1645v2SysContact OBJECT-TYPE
   SYNTAX      DisplayString
   MAX-ACCESS  read-write
   STATUS      current
   DESCRIPTION
      "Path: router1645.editConf.sysContact
       Info: sysContact"
   ::= {er1645v2 2}


er1645v2SysLocation OBJECT-TYPE
   SYNTAX      DisplayString
   MAX-ACCESS  read-write
   STATUS      current
   DESCRIPTION
      "Path: router1645.editConf.sysLocation
       Info: sysLocation"
   ::= {er1645v2 3}


er1645v2BootFromFlash OBJECT-TYPE
   SYNTAX      INTEGER
               {
               flash1 (1),
               flash2 (2),
               auto (3),
               lastLoaded (4)
               }
   MAX-ACCESS  read-write
   STATUS      current
   DESCRIPTION
      "Path: router1645.editConf.bootFromFlash
       Info: bootFromFlash

       Possibilities:
               flash1   (1)
               flash2   (2)
               auto   (3)
               lastLoaded   (4)"
   ::= {er1645v2 226}


er1645v2Tracing OBJECT IDENTIFIER ::= {er1645v2 700}

er1645v2TracingModules OBJECT-TYPE
   SYNTAX      SEQUENCE OF Er1645v2TracingModulesEntry
   MAX-ACCESS  not-accessible
   STATUS      current
   DESCRIPTION
      ""
   ::= {er1645v2Tracing 16777216}

er1645v2TracingModulesEntry OBJECT-TYPE
   SYNTAX      Er1645v2TracingModulesEntry
   MAX-ACCESS  not-accessible
   STATUS      current
   DESCRIPTION
      ""
   INDEX      { er1645v2TracingModulesTableIx }
   ::= {er1645v2TracingModules 1}

Er1645v2TracingModulesEntry ::=
   SEQUENCE
      {
      er1645v2TracingModulesActions
         VariableLengthTableActions,
      er1645v2TracingModulesTableIx
         TableIndex,
      er1645v2TracingModulesLevelsNone
         DisplayString,
      er1645v2TracingModulesLevelsAaa
         Integer32,
      er1645v2TracingModulesLevelsAtm
         Integer32,
      er1645v2TracingModulesLevelsAuthd
         Integer32,
      er1645v2TracingModulesLevelsAutoDiscovery
         Integer32,
      er1645v2TracingModulesLevelsBgp
         Integer32,
      er1645v2TracingModulesLevelsCellular
         Integer32,
      er1645v2TracingModulesLevelsCert
         Integer32,
      er1645v2TracingModulesLevelsCli
         Integer32,
      er1645v2TracingModulesLevelsCms2Application
         Integer32,
      er1645v2TracingModulesLevelsCwmp
         Integer32,
      er1645v2TracingModulesLevelsDhcpSrv
         Integer32,
      er1645v2TracingModulesLevelsDnsd
         Integer32,
      er1645v2TracingModulesLevelsDnsUpdateClient
         Integer32,
      er1645v2TracingModulesLevelsDot1x
         Integer32,
      er1645v2TracingModulesLevelsEfmOam
         Integer32,
      er1645v2TracingModulesLevelsEthSwitch
         Integer32,
      er1645v2TracingModulesLevelsE2e
         Integer32,
      er1645v2TracingModulesLevelsFileSystem
         Integer32,
      er1645v2TracingModulesLevelsFrameRelay
         Integer32,
      er1645v2TracingModulesLevelsGre
         Integer32,
      er1645v2TracingModulesLevelsHardware
         Integer32,
      er1645v2TracingModulesLevelsHwMan
         Integer32,
      er1645v2TracingModulesLevelsIfMan
         Integer32,
      er1645v2TracingModulesLevelsIgmp
         Integer32,
      er1645v2TracingModulesLevelsIke
         Integer32,
      er1645v2TracingModulesLevelsIma
         Integer32,
      er1645v2TracingModulesLevelsIpsec
         Integer32,
      er1645v2TracingModulesLevelsIpV6
         Integer32,
      er1645v2TracingModulesLevelsIsdn
         Integer32,
      er1645v2TracingModulesLevelsLanAutoDetection
         Integer32,
      er1645v2TracingModulesLevelsL2tp
         Integer32,
      er1645v2TracingModulesLevelsModemDsp
         Integer32,
      er1645v2TracingModulesLevelsNtp
         Integer32,
      er1645v2TracingModulesLevelsOrchid
         Integer32,
      er1645v2TracingModulesLevelsOspf
         Integer32,
      er1645v2TracingModulesLevelsO10Node
         Integer32,
      er1645v2TracingModulesLevelsPerformance
         Integer32,
      er1645v2TracingModulesLevelsPim
         Integer32,
      er1645v2TracingModulesLevelsPpp
         Integer32,
      er1645v2TracingModulesLevelsProtocolStack
         Integer32,
      er1645v2TracingModulesLevelsPstn
         Integer32,
      er1645v2TracingModulesLevelsRemPow
         Integer32,
      er1645v2TracingModulesLevelsSdfe4
         Integer32,
      er1645v2TracingModulesLevelsSocket
         Integer32,
      er1645v2TracingModulesLevelsTcp
         Integer32,
      er1645v2TracingModulesLevelsTelnet
         Integer32,
      er1645v2TracingModulesLevelsTracert
         Integer32,
      er1645v2TracingModulesLevelsWww
         Integer32,
      er1645v2TracingModulesDestination
         Integer32
      }

er1645v2TracingModulesActions OBJECT-TYPE
   SYNTAX      VariableLengthTableActions
   MAX-ACCESS  read-write
   STATUS      current
   DESCRIPTION
      "By way of this field, some manipulations
       on this table may be performed."
   ::= {er1645v2TracingModulesEntry 2}

er1645v2TracingModulesTableIx OBJECT-TYPE
   SYNTAX      TableIndex
   MAX-ACCESS  not-accessible
   STATUS      current
   DESCRIPTION
      ""
   ::= {er1645v2TracingModulesEntry 11}

er1645v2TracingModulesLevelsNone OBJECT-TYPE
   SYNTAX      DisplayString
   MAX-ACCESS  read-write
   STATUS      current
   DESCRIPTION
      "Path: router1645.editConf.tracing.modules.levels.none"
   ::= {er1645v2TracingModulesEntry 26607616}

er1645v2TracingModulesLevelsAaa OBJECT-TYPE
   SYNTAX      Integer32
   MAX-ACCESS  read-write
   STATUS      current
   DESCRIPTION
      "Path: router1645.editConf.tracing.modules.levels.aaa

       Bit meanings:
               bit 0 = tacacsEvents,
               bit 1 = tacacsErrors,
               bit 2 = tacacsPkts"
   ::= {er1645v2TracingModulesEntry 19267584}

er1645v2TracingModulesLevelsAtm OBJECT-TYPE
   SYNTAX      Integer32
   MAX-ACCESS  read-write
   STATUS      current
   DESCRIPTION
      "Path: router1645.editConf.tracing.modules.levels.atm

       Bit meanings:
               bit 0 = error,
               bit 1 = warning,
               bit 2 = info,
               bit 3 = data,
               bit 4 = debug,
               bit 5 = event,
               bit 6 = log"
   ::= {er1645v2TracingModulesEntry 17039360}

er1645v2TracingModulesLevelsAuthd OBJECT-TYPE
   SYNTAX      Integer32
   MAX-ACCESS  read-write
   STATUS      current
   DESCRIPTION
      "Path: router1645.editConf.tracing.modules.levels.authd

       Bit meanings:
               bit 0 = error,
               bit 1 = warning,
               bit 2 = info,
               bit 3 = data,
               bit 4 = debug,
               bit 5 = event,
               bit 6 = log"
   ::= {er1645v2TracingModulesEntry 17367040}

er1645v2TracingModulesLevelsAutoDiscovery OBJECT-TYPE
   SYNTAX      Integer32
   MAX-ACCESS  read-write
   STATUS      current
   DESCRIPTION
      "Path: router1645.editConf.tracing.modules.levels.autoDiscovery

       Bit meanings:
               bit 0 = error,
               bit 1 = warning,
               bit 2 = info,
               bit 3 = data,
               bit 4 = debug"
   ::= {er1645v2TracingModulesEntry 18153472}

er1645v2TracingModulesLevelsBgp OBJECT-TYPE
   SYNTAX      Integer32
   MAX-ACCESS  read-write
   STATUS      current
   DESCRIPTION
      "Path: router1645.editConf.tracing.modules.levels.bgp

       Bit meanings:
               bit 0 = fsm,
               bit 1 = notification,
               bit 2 = packet,
               bit 3 = error"
   ::= {er1645v2TracingModulesEntry 18612224}

er1645v2TracingModulesLevelsCellular OBJECT-TYPE
   SYNTAX      Integer32
   MAX-ACCESS  read-write
   STATUS      current
   DESCRIPTION
      "Path: router1645.editConf.tracing.modules.levels.cellular

       Bit meanings:
               bit 0 = controller,
               bit 1 = dataIn,
               bit 2 = dataOut,
               bit 3 = dialer,
               bit 4 = monitor,
               bit 5 = at,
               bit 6 = qmi"
   ::= {er1645v2TracingModulesEntry 19922944}

er1645v2TracingModulesLevelsCert OBJECT-TYPE
   SYNTAX      Integer32
   MAX-ACCESS  read-write
   STATUS      current
   DESCRIPTION
      "Path: router1645.editConf.tracing.modules.levels.cert

       Bit meanings:
               bit 0 = error,
               bit 1 = warning,
               bit 2 = info,
               bit 3 = data,
               bit 4 = debug,
               bit 5 = event,
               bit 6 = log"
   ::= {er1645v2TracingModulesEntry 17301504}

er1645v2TracingModulesLevelsCli OBJECT-TYPE
   SYNTAX      Integer32
   MAX-ACCESS  read-write
   STATUS      current
   DESCRIPTION
      "Path: router1645.editConf.tracing.modules.levels.cli

       Bit meanings:
               bit 0 = error,
               bit 1 = warning,
               bit 2 = info,
               bit 3 = data,
               bit 4 = debug,
               bit 5 = event,
               bit 6 = log"
   ::= {er1645v2TracingModulesEntry 19202048}

er1645v2TracingModulesLevelsCms2Application OBJECT-TYPE
   SYNTAX      Integer32
   MAX-ACCESS  read-write
   STATUS      current
   DESCRIPTION
      "Path: router1645.editConf.tracing.modules.levels.cms2Application

       Bit meanings:
               bit 0 = cms2Error,
               bit 1 = cms2Warning,
               bit 2 = cms2Info,
               bit 3 = cms2Data,
               bit 4 = cms2Debug,
               bit 5 = dbaseError,
               bit 6 = dbaseWarning,
               bit 7 = dbaseInfo,
               bit 8 = dbaseData,
               bit 9 = dbaseDebug,
               bit 10 = cacheInfo,
               bit 11 = cacheDebug"
   ::= {er1645v2TracingModulesEntry 16908288}

er1645v2TracingModulesLevelsCwmp OBJECT-TYPE
   SYNTAX      Integer32
   MAX-ACCESS  read-write
   STATUS      current
   DESCRIPTION
      "Path: router1645.editConf.tracing.modules.levels.cwmp

       Bit meanings:
               bit 0 = error,
               bit 1 = warning,
               bit 2 = info,
               bit 3 = data,
               bit 4 = debug,
               bit 5 = event,
               bit 6 = log"
   ::= {er1645v2TracingModulesEntry 19726336}

er1645v2TracingModulesLevelsDhcpSrv OBJECT-TYPE
   SYNTAX      Integer32
   MAX-ACCESS  read-write
   STATUS      current
   DESCRIPTION
      "Path: router1645.editConf.tracing.modules.levels.dhcpSrv

       Bit meanings:
               bit 0 = error,
               bit 1 = warning,
               bit 2 = info,
               bit 3 = data,
               bit 4 = debug,
               bit 5 = event,
               bit 6 = log"
   ::= {er1645v2TracingModulesEntry 18219008}

er1645v2TracingModulesLevelsDnsd OBJECT-TYPE
   SYNTAX      Integer32
   MAX-ACCESS  read-write
   STATUS      current
   DESCRIPTION
      "Path: router1645.editConf.tracing.modules.levels.dnsd

       Bit meanings:
               bit 0 = error,
               bit 1 = warning,
               bit 2 = info,
               bit 3 = data,
               bit 4 = debug,
               bit 5 = event,
               bit 6 = log"
   ::= {er1645v2TracingModulesEntry 17432576}

er1645v2TracingModulesLevelsDnsUpdateClient OBJECT-TYPE
   SYNTAX      Integer32
   MAX-ACCESS  read-write
   STATUS      current
   DESCRIPTION
      "Path: router1645.editConf.tracing.modules.levels.dnsUpdateClient

       Bit meanings:
               bit 0 = error,
               bit 1 = warning,
               bit 2 = info,
               bit 3 = data,
               bit 4 = debug,
               bit 5 = event,
               bit 6 = log"
   ::= {er1645v2TracingModulesEntry 18677760}

er1645v2TracingModulesLevelsDot1x OBJECT-TYPE
   SYNTAX      Integer32
   MAX-ACCESS  read-write
   STATUS      current
   DESCRIPTION
      "Path: router1645.editConf.tracing.modules.levels.dot1x

       Bit meanings:
               bit 0 = failure,
               bit 1 = success,
               bit 2 = error,
               bit 3 = event"
   ::= {er1645v2TracingModulesEntry 19791872}

er1645v2TracingModulesLevelsEfmOam OBJECT-TYPE
   SYNTAX      Integer32
   MAX-ACCESS  read-write
   STATUS      current
   DESCRIPTION
      "Path: router1645.editConf.tracing.modules.levels.efmOam

       Bit meanings:
               bit 0 = discards,
               bit 1 = violations,
               bit 2 = loopback,
               bit 3 = flags,
               bit 4 = info,
               bit 5 = timer,
               bit 6 = txDump,
               bit 7 = rxInfoReq,
               bit 8 = rxEvNot,
               bit 9 = rxVarReq,
               bit 10 = rxVarResp,
               bit 11 = rxLpbkCtrl,
               bit 12 = rxOrgSpec"
   ::= {er1645v2TracingModulesEntry 18939904}

er1645v2TracingModulesLevelsEthSwitch OBJECT-TYPE
   SYNTAX      Integer32
   MAX-ACCESS  read-write
   STATUS      current
   DESCRIPTION
      "Path: router1645.editConf.tracing.modules.levels.ethSwitch

       Bit meanings:
               bit 0 = stateMachine,
               bit 1 = access,
               bit 2 = link,
               bit 3 = debug,
               bit 4 = error"
   ::= {er1645v2TracingModulesEntry 19988480}

er1645v2TracingModulesLevelsE2e OBJECT-TYPE
   SYNTAX      Integer32
   MAX-ACCESS  read-write
   STATUS      current
   DESCRIPTION
      "Path: router1645.editConf.tracing.modules.levels.e2e

       Bit meanings:
               bit 0 = error,
               bit 1 = warning,
               bit 2 = info,
               bit 3 = data,
               bit 4 = debug"
   ::= {er1645v2TracingModulesEntry 17629184}

er1645v2TracingModulesLevelsFileSystem OBJECT-TYPE
   SYNTAX      Integer32
   MAX-ACCESS  read-write
   STATUS      current
   DESCRIPTION
      "Path: router1645.editConf.tracing.modules.levels.fileSystem

       Bit meanings:
               bit 0 = error,
               bit 1 = warning,
               bit 2 = info,
               bit 3 = data,
               bit 4 = debug"
   ::= {er1645v2TracingModulesEntry 18087936}

er1645v2TracingModulesLevelsFrameRelay OBJECT-TYPE
   SYNTAX      Integer32
   MAX-ACCESS  read-write
   STATUS      current
   DESCRIPTION
      "Path: router1645.editConf.tracing.modules.levels.frameRelay

       Bit meanings:
               bit 0 = error,
               bit 1 = warning,
               bit 2 = info,
               bit 3 = data,
               bit 4 = debug,
               bit 5 = event,
               bit 6 = log"
   ::= {er1645v2TracingModulesEntry 17825792}

er1645v2TracingModulesLevelsGre OBJECT-TYPE
   SYNTAX      Integer32
   MAX-ACCESS  read-write
   STATUS      current
   DESCRIPTION
      "Path: router1645.editConf.tracing.modules.levels.gre

       Bit meanings:
               bit 0 = error,
               bit 1 = warning,
               bit 2 = info,
               bit 3 = data,
               bit 4 = debug,
               bit 5 = event,
               bit 6 = log"
   ::= {er1645v2TracingModulesEntry 17956864}

er1645v2TracingModulesLevelsHardware OBJECT-TYPE
   SYNTAX      Integer32
   MAX-ACCESS  read-write
   STATUS      current
   DESCRIPTION
      "Path: router1645.editConf.tracing.modules.levels.hardware

       Bit meanings:
               bit 0 = flexError,
               bit 1 = flexWarning,
               bit 2 = flexInfo,
               bit 3 = flexData,
               bit 4 = flexDebug,
               bit 5 = liuError,
               bit 6 = liuWarning,
               bit 7 = liuInfo,
               bit 8 = liuData,
               bit 9 = liuDebug"
   ::= {er1645v2TracingModulesEntry 18808832}

er1645v2TracingModulesLevelsHwMan OBJECT-TYPE
   SYNTAX      Integer32
   MAX-ACCESS  read-write
   STATUS      current
   DESCRIPTION
      "Path: router1645.editConf.tracing.modules.levels.hwMan

       Bit meanings:
               bit 0 = error,
               bit 1 = warning,
               bit 2 = info,
               bit 3 = data,
               bit 4 = debug,
               bit 5 = event,
               bit 6 = log"
   ::= {er1645v2TracingModulesEntry 17694720}

er1645v2TracingModulesLevelsIfMan OBJECT-TYPE
   SYNTAX      Integer32
   MAX-ACCESS  read-write
   STATUS      current
   DESCRIPTION
      "Path: router1645.editConf.tracing.modules.levels.ifMan

       Bit meanings:
               bit 0 = error,
               bit 1 = warning,
               bit 2 = info,
               bit 3 = data,
               bit 4 = debug,
               bit 5 = event,
               bit 6 = log"
   ::= {er1645v2TracingModulesEntry 17760256}

er1645v2TracingModulesLevelsIgmp OBJECT-TYPE
   SYNTAX      Integer32
   MAX-ACCESS  read-write
   STATUS      current
   DESCRIPTION
      "Path: router1645.editConf.tracing.modules.levels.igmp

       Bit meanings:
               bit 0 = error,
               bit 1 = warning,
               bit 2 = info,
               bit 3 = data,
               bit 4 = debug,
               bit 5 = event,
               bit 6 = log"
   ::= {er1645v2TracingModulesEntry 17891328}

er1645v2TracingModulesLevelsIke OBJECT-TYPE
   SYNTAX      Integer32
   MAX-ACCESS  read-write
   STATUS      current
   DESCRIPTION
      "Path: router1645.editConf.tracing.modules.levels.ike

       Bit meanings:
               bit 0 = error,
               bit 1 = warning,
               bit 2 = info,
               bit 3 = data,
               bit 4 = debug,
               bit 5 = event,
               bit 6 = log"
   ::= {er1645v2TracingModulesEntry 17170432}

er1645v2TracingModulesLevelsIma OBJECT-TYPE
   SYNTAX      Integer32
   MAX-ACCESS  read-write
   STATUS      current
   DESCRIPTION
      "Path: router1645.editConf.tracing.modules.levels.ima

       Bit meanings:
               bit 0 = error,
               bit 1 = icp,
               bit 2 = linkEvents,
               bit 3 = linkState,
               bit 4 = groupEvents,
               bit 5 = groupState,
               bit 6 = debug"
   ::= {er1645v2TracingModulesEntry 19005440}

er1645v2TracingModulesLevelsIpsec OBJECT-TYPE
   SYNTAX      Integer32
   MAX-ACCESS  read-write
   STATUS      current
   DESCRIPTION
      "Path: router1645.editConf.tracing.modules.levels.ipsec

       Bit meanings:
               bit 0 = error,
               bit 1 = warning,
               bit 2 = info,
               bit 3 = data,
               bit 4 = debug,
               bit 5 = event,
               bit 6 = log"
   ::= {er1645v2TracingModulesEntry 17235968}

er1645v2TracingModulesLevelsIpV6 OBJECT-TYPE
   SYNTAX      Integer32
   MAX-ACCESS  read-write
   STATUS      current
   DESCRIPTION
      "Path: router1645.editConf.tracing.modules.levels.ipV6

       Bit meanings:
               bit 0 = address,
               bit 1 = icmp,
               bit 2 = dhcp,
               bit 3 = packetIn,
               bit 4 = packetOut,
               bit 5 = debug"
   ::= {er1645v2TracingModulesEntry 19857408}

er1645v2TracingModulesLevelsIsdn OBJECT-TYPE
   SYNTAX      Integer32
   MAX-ACCESS  read-write
   STATUS      current
   DESCRIPTION
      "Path: router1645.editConf.tracing.modules.levels.isdn

       Bit meanings:
               bit 0 = error,
               bit 1 = warning,
               bit 2 = info,
               bit 3 = data,
               bit 4 = debug,
               bit 5 = event,
               bit 7 = physical,
               bit 8 = q921,
               bit 9 = q931,
               bit 10 = bap"
   ::= {er1645v2TracingModulesEntry 18022400}

er1645v2TracingModulesLevelsLanAutoDetection OBJECT-TYPE
   SYNTAX      Integer32
   MAX-ACCESS  read-write
   STATUS      current
   DESCRIPTION
      "Path: router1645.editConf.tracing.modules.levels.lanAutoDetection

       Bit meanings:
               bit 0 = error,
               bit 1 = warning,
               bit 2 = info,
               bit 3 = data,
               bit 4 = debug,
               bit 5 = event,
               bit 6 = log"
   ::= {er1645v2TracingModulesEntry 17563648}

er1645v2TracingModulesLevelsL2tp OBJECT-TYPE
   SYNTAX      Integer32
   MAX-ACCESS  read-write
   STATUS      current
   DESCRIPTION
      "Path: router1645.editConf.tracing.modules.levels.l2tp

       Bit meanings:
               bit 0 = error,
               bit 1 = warning,
               bit 2 = info,
               bit 3 = data,
               bit 4 = debug,
               bit 5 = event,
               bit 6 = log"
   ::= {er1645v2TracingModulesEntry 18546688}

er1645v2TracingModulesLevelsModemDsp OBJECT-TYPE
   SYNTAX      Integer32
   MAX-ACCESS  read-write
   STATUS      current
   DESCRIPTION
      "Path: router1645.editConf.tracing.modules.levels.modemDsp

       Bit meanings:
               bit 0 = eocError,
               bit 1 = eocInfo,
               bit 2 = eocDataType,
               bit 3 = eocDataBytes,
               bit 4 = eocDebug,
               bit 5 = dspError,
               bit 6 = dspInfo,
               bit 7 = dspDebug"
   ::= {er1645v2TracingModulesEntry 16973824}

er1645v2TracingModulesLevelsNtp OBJECT-TYPE
   SYNTAX      Integer32
   MAX-ACCESS  read-write
   STATUS      current
   DESCRIPTION
      "Path: router1645.editConf.tracing.modules.levels.ntp

       Bit meanings:
               bit 0 = error,
               bit 1 = warning,
               bit 2 = info,
               bit 3 = data,
               bit 4 = debug"
   ::= {er1645v2TracingModulesEntry 19464192}

er1645v2TracingModulesLevelsOrchid OBJECT-TYPE
   SYNTAX      Integer32
   MAX-ACCESS  read-write
   STATUS      current
   DESCRIPTION
      "Path: router1645.editConf.tracing.modules.levels.orchid

       Bit meanings:
               bit 0 = o10Error,
               bit 1 = o10Warning,
               bit 2 = o10Info,
               bit 3 = o10Data,
               bit 4 = o10Debug,
               bit 5 = modelError,
               bit 6 = modelWarning,
               bit 7 = modelInfo,
               bit 8 = modelData,
               bit 9 = modelDebug"
   ::= {er1645v2TracingModulesEntry 18743296}

er1645v2TracingModulesLevelsOspf OBJECT-TYPE
   SYNTAX      Integer32
   MAX-ACCESS  read-write
   STATUS      current
   DESCRIPTION
      "Path: router1645.editConf.tracing.modules.levels.ospf

       Bit meanings:
               bit 0 = adjacency,
               bit 1 = packet,
               bit 2 = event,
               bit 3 = route"
   ::= {er1645v2TracingModulesEntry 17498112}

er1645v2TracingModulesLevelsO10Node OBJECT-TYPE
   SYNTAX      Integer32
   MAX-ACCESS  read-write
   STATUS      current
   DESCRIPTION
      "Path: router1645.editConf.tracing.modules.levels.o10Node

       Bit meanings:
               bit 0 = error,
               bit 1 = events,
               bit 2 = o10FrameType,
               bit 3 = cms2FrameType,
               bit 4 = o10FrameData,
               bit 5 = cms2FrameData,
               bit 6 = driver,
               bit 7 = debug"
   ::= {er1645v2TracingModulesEntry 16842752}

er1645v2TracingModulesLevelsPerformance OBJECT-TYPE
   SYNTAX      Integer32
   MAX-ACCESS  read-write
   STATUS      current
   DESCRIPTION
      "Path: router1645.editConf.tracing.modules.levels.performance

       Bit meanings:
               bit 0 = error,
               bit 1 = warning,
               bit 2 = info,
               bit 3 = data,
               bit 4 = debug"
   ::= {er1645v2TracingModulesEntry 18284544}

er1645v2TracingModulesLevelsPim OBJECT-TYPE
   SYNTAX      Integer32
   MAX-ACCESS  read-write
   STATUS      current
   DESCRIPTION
      "Path: router1645.editConf.tracing.modules.levels.pim

       Bit meanings:
               bit 0 = error,
               bit 1 = warning,
               bit 2 = info,
               bit 3 = data,
               bit 4 = debug,
               bit 5 = event,
               bit 6 = log"
   ::= {er1645v2TracingModulesEntry 20054016}

er1645v2TracingModulesLevelsPpp OBJECT-TYPE
   SYNTAX      Integer32
   MAX-ACCESS  read-write
   STATUS      current
   DESCRIPTION
      "Path: router1645.editConf.tracing.modules.levels.ppp

       Bit meanings:
               bit 0 = error,
               bit 1 = warning,
               bit 2 = info,
               bit 3 = data,
               bit 4 = debug,
               bit 5 = event,
               bit 6 = log,
               bit 7 = pppoe"
   ::= {er1645v2TracingModulesEntry 17104896}

er1645v2TracingModulesLevelsProtocolStack OBJECT-TYPE
   SYNTAX      Integer32
   MAX-ACCESS  read-write
   STATUS      current
   DESCRIPTION
      "Path: router1645.editConf.tracing.modules.levels.protocolStack

       Bit meanings:
               bit 0 = error,
               bit 1 = warning,
               bit 2 = info,
               bit 3 = data,
               bit 4 = debug,
               bit 5 = event,
               bit 6 = log"
   ::= {er1645v2TracingModulesEntry 19529728}

er1645v2TracingModulesLevelsPstn OBJECT-TYPE
   SYNTAX      Integer32
   MAX-ACCESS  read-write
   STATUS      current
   DESCRIPTION
      "Path: router1645.editConf.tracing.modules.levels.pstn

       Bit meanings:
               bit 0 = error,
               bit 1 = warning,
               bit 2 = info,
               bit 3 = data,
               bit 4 = debug,
               bit 5 = event,
               bit 6 = log"
   ::= {er1645v2TracingModulesEntry 18350080}

er1645v2TracingModulesLevelsRemPow OBJECT-TYPE
   SYNTAX      Integer32
   MAX-ACCESS  read-write
   STATUS      current
   DESCRIPTION
      "Path: router1645.editConf.tracing.modules.levels.remPow

       Bit meanings:
               bit 0 = error,
               bit 1 = warning,
               bit 2 = info,
               bit 3 = data,
               bit 4 = debug"
   ::= {er1645v2TracingModulesEntry 18874368}

er1645v2TracingModulesLevelsSdfe4 OBJECT-TYPE
   SYNTAX      Integer32
   MAX-ACCESS  read-write
   STATUS      current
   DESCRIPTION
      "Path: router1645.editConf.tracing.modules.levels.sdfe4

       Bit meanings:
               bit 0 = error,
               bit 1 = warning,
               bit 2 = info,
               bit 3 = data,
               bit 4 = debug,
               bit 5 = event,
               bit 6 = log"
   ::= {er1645v2TracingModulesEntry 18481152}

er1645v2TracingModulesLevelsSocket OBJECT-TYPE
   SYNTAX      Integer32
   MAX-ACCESS  read-write
   STATUS      current
   DESCRIPTION
      "Path: router1645.editConf.tracing.modules.levels.socket

       Bit meanings:
               bit 0 = error,
               bit 1 = warning,
               bit 2 = info,
               bit 3 = data,
               bit 4 = debug,
               bit 5 = event,
               bit 6 = log"
   ::= {er1645v2TracingModulesEntry 19660800}

er1645v2TracingModulesLevelsTcp OBJECT-TYPE
   SYNTAX      Integer32
   MAX-ACCESS  read-write
   STATUS      current
   DESCRIPTION
      "Path: router1645.editConf.tracing.modules.levels.tcp

       Bit meanings:
               bit 0 = error,
               bit 1 = warning,
               bit 2 = info,
               bit 3 = data,
               bit 4 = debug,
               bit 5 = event,
               bit 6 = log"
   ::= {er1645v2TracingModulesEntry 19595264}

er1645v2TracingModulesLevelsTelnet OBJECT-TYPE
   SYNTAX      Integer32
   MAX-ACCESS  read-write
   STATUS      current
   DESCRIPTION
      "Path: router1645.editConf.tracing.modules.levels.telnet

       Bit meanings:
               bit 0 = error,
               bit 1 = warning,
               bit 2 = info,
               bit 3 = data,
               bit 4 = debug,
               bit 5 = event,
               bit 6 = log"
   ::= {er1645v2TracingModulesEntry 19136512}

er1645v2TracingModulesLevelsTracert OBJECT-TYPE
   SYNTAX      Integer32
   MAX-ACCESS  read-write
   STATUS      current
   DESCRIPTION
      "Path: router1645.editConf.tracing.modules.levels.tracert

       Bit meanings:
               bit 0 = error,
               bit 1 = warning,
               bit 2 = info,
               bit 3 = data,
               bit 4 = debug,
               bit 5 = event,
               bit 6 = log"
   ::= {er1645v2TracingModulesEntry 18415616}

er1645v2TracingModulesLevelsWww OBJECT-TYPE
   SYNTAX      Integer32
   MAX-ACCESS  read-write
   STATUS      current
   DESCRIPTION
      "Path: router1645.editConf.tracing.modules.levels.www

       Bit meanings:
               bit 0 = error,
               bit 1 = warning,
               bit 2 = info,
               bit 3 = data,
               bit 4 = debug,
               bit 5 = event,
               bit 6 = log"
   ::= {er1645v2TracingModulesEntry 19070976}

er1645v2TracingModulesDestination OBJECT-TYPE
   SYNTAX      Integer32
   MAX-ACCESS  read-write
   STATUS      current
   DESCRIPTION
      "Path: router1645.editConf.tracing.modules.destination

       Bit meanings:
               bit 0 = syslog,
               bit 1 = console,
               bit 2 = table,
               bit 4 = telnet,
               bit 5 = file"
   ::= {er1645v2TracingModulesEntry 33554432}


er1645v2Security OBJECT IDENTIFIER ::= {er1645v2 220}

er1645v2SecuritySSCTable OBJECT-TYPE
   SYNTAX      SEQUENCE OF Er1645v2SecurityEntry
   MAX-ACCESS  not-accessible
   STATUS      current
   DESCRIPTION
      "security"
   ::= {er1645v2Security 1}

er1645v2SecurityEntry OBJECT-TYPE
   SYNTAX      Er1645v2SecurityEntry
   MAX-ACCESS  not-accessible
   STATUS      current
   DESCRIPTION
      ""
   INDEX      { er1645v2SecurityTableIx }
   ::= {er1645v2SecuritySSCTable 1}

Er1645v2SecurityEntry ::=
   SEQUENCE
      {
      er1645v2SecurityActions
         VariableLengthTableActions,
      er1645v2SecurityTableIx
         TableIndex,
      er1645v2SecurityRemark
         DisplayString,
      er1645v2SecurityType
         INTEGER,
      er1645v2SecurityPassword
         DisplayString,
      er1645v2SecurityEncModePassw
         INTEGER,
      er1645v2SecurityEncPassword
         DisplayString,
      er1645v2SecurityGroup
         DisplayString,
      er1645v2SecurityPrivLevel
         Integer32,
      er1645v2SecurityAccessRights
         Integer32,
      er1645v2SecurityApplicationsAll
         DisplayString,
      er1645v2SecurityApplicationsAllow
         Integer32,
      er1645v2SecurityApplicationsDeny
         Integer32,
      er1645v2SecuritySnmpv3AuthProtocol
         INTEGER,
      er1645v2SecuritySnmpv3AuthPassword
         DisplayString,
      er1645v2SecuritySnmpv3EncModeAuthPassw
         INTEGER,
      er1645v2SecuritySnmpv3EncAuthPassword
         DisplayString,
      er1645v2SecuritySnmpv3PrivProtocol
         INTEGER,
      er1645v2SecuritySnmpv3PrivPassword
         DisplayString,
      er1645v2SecuritySnmpv3EncModePrivPassw
         INTEGER,
      er1645v2SecuritySnmpv3EncPrivPassword
         DisplayString
      }

er1645v2SecurityActions OBJECT-TYPE
   SYNTAX      VariableLengthTableActions
   MAX-ACCESS  read-write
   STATUS      current
   DESCRIPTION
      "By way of this field, some manipulations
       on this table may be performed."
   ::= {er1645v2SecurityEntry 2}

er1645v2SecurityTableIx OBJECT-TYPE
   SYNTAX      TableIndex
   MAX-ACCESS  not-accessible
   STATUS      current
   DESCRIPTION
      ""
   ::= {er1645v2SecurityEntry 11}

er1645v2SecurityRemark OBJECT-TYPE
   SYNTAX      DisplayString
   MAX-ACCESS  read-write
   STATUS      current
   DESCRIPTION
      "Path: router1645.editConf.security.remark"
   ::= {er1645v2SecurityEntry 67108864}

er1645v2SecurityType OBJECT-TYPE
   SYNTAX      INTEGER
               {
               password (0),
               privLevel (1)
               }
   MAX-ACCESS  read-write
   STATUS      current
   DESCRIPTION
      "Path: router1645.editConf.security.type

       Possibilities:
               password   (0)
               privLevel   (1)"
   ::= {er1645v2SecurityEntry 117440512}

er1645v2SecurityPassword OBJECT-TYPE
   SYNTAX      DisplayString
   MAX-ACCESS  read-write
   STATUS      current
   DESCRIPTION
      "Path: router1645.editConf.security.password"
   ::= {er1645v2SecurityEntry 16777216}

er1645v2SecurityEncModePassw OBJECT-TYPE
   SYNTAX      INTEGER
               {
               none (1),
               encrypt (2),
               encType1 (3),
               invalid (128)
               }
   MAX-ACCESS  read-write
   STATUS      current
   DESCRIPTION
      "Path: router1645.editConf.security.encModePassw

       Possibilities:
               none   (1)
               encrypt   (2)
               encType1   (3)
               invalid   (128)"
   ::= {er1645v2SecurityEntry 100663296}

er1645v2SecurityEncPassword OBJECT-TYPE
   SYNTAX      DisplayString
   MAX-ACCESS  read-write
   STATUS      current
   DESCRIPTION
      "Path: router1645.editConf.security.encPassword"
   ::= {er1645v2SecurityEntry 83886080}

er1645v2SecurityGroup OBJECT-TYPE
   SYNTAX      DisplayString
   MAX-ACCESS  read-write
   STATUS      current
   DESCRIPTION
      "Path: router1645.editConf.security.group"
   ::= {er1645v2SecurityEntry 167772160}

er1645v2SecurityPrivLevel OBJECT-TYPE
   SYNTAX      Integer32
   MAX-ACCESS  read-write
   STATUS      current
   DESCRIPTION
      "Path: router1645.editConf.security.privLevel"
   ::= {er1645v2SecurityEntry 134217728}

er1645v2SecurityAccessRights OBJECT-TYPE
   SYNTAX      Integer32
   MAX-ACCESS  read-write
   STATUS      current
   DESCRIPTION
      "Path: router1645.editConf.security.accessRights

       Bit meanings:
               bit 0 = readAccess,
               bit 1 = writeAccess,
               bit 2 = securityAccess,
               bit 4 = fileSystemAccess,
               bit 5 = testAccess"
   ::= {er1645v2SecurityEntry 33554432}

er1645v2SecurityApplicationsAll OBJECT-TYPE
   SYNTAX      DisplayString
   MAX-ACCESS  read-write
   STATUS      current
   DESCRIPTION
      "Path: router1645.editConf.security.applications.all"
   ::= {er1645v2SecurityEntry 151060480}

er1645v2SecurityApplicationsAllow OBJECT-TYPE
   SYNTAX      Integer32
   MAX-ACCESS  read-write
   STATUS      current
   DESCRIPTION
      "Path: router1645.editConf.security.applications.allow

       Bit meanings:
               bit 0 = cms2,
               bit 2 = console-cli,
               bit 3 = console-cms2,
               bit 4 = snmp,
               bit 5 = tftp,
               bit 6 = ftp,
               bit 7 = telnet,
               bit 8 = ssh,
               bit 9 = snmpv3,
               bit 12 = http-classic,
               bit 13 = http-tma,
               bit 14 = http-easyConfig,
               bit 20 = https-classic,
               bit 21 = https-tma,
               bit 22 = https-easyConfig"
   ::= {er1645v2SecurityEntry 151126016}

er1645v2SecurityApplicationsDeny OBJECT-TYPE
   SYNTAX      Integer32
   MAX-ACCESS  read-write
   STATUS      current
   DESCRIPTION
      "Path: router1645.editConf.security.applications.deny

       Bit meanings:
               bit 0 = cms2,
               bit 2 = console-cli,
               bit 3 = console-cms2,
               bit 4 = snmp,
               bit 5 = tftp,
               bit 6 = ftp,
               bit 7 = telnet,
               bit 8 = ssh,
               bit 9 = snmpv3,
               bit 12 = http-classic,
               bit 13 = http-tma,
               bit 14 = http-easyConfig,
               bit 20 = https-classic,
               bit 21 = https-tma,
               bit 22 = https-easyConfig"
   ::= {er1645v2SecurityEntry 151191552}

er1645v2SecuritySnmpv3AuthProtocol OBJECT-TYPE
   SYNTAX      INTEGER
               {
               none (0),
               hmacmmd5 (1),
               hmacusham1 (2)
               }
   MAX-ACCESS  read-write
   STATUS      current
   DESCRIPTION
      "Path: router1645.editConf.security.snmpv3.authProtocol

       Possibilities:
               none   (0)
               hmac-md5   (1)
               hmac_sha-1   (2)"
   ::= {er1645v2SecurityEntry 50397184}

er1645v2SecuritySnmpv3AuthPassword OBJECT-TYPE
   SYNTAX      DisplayString
   MAX-ACCESS  read-write
   STATUS      current
   DESCRIPTION
      "Path: router1645.editConf.security.snmpv3.authPassword"
   ::= {er1645v2SecurityEntry 50462720}

er1645v2SecuritySnmpv3EncModeAuthPassw OBJECT-TYPE
   SYNTAX      INTEGER
               {
               none (1),
               encrypt (2),
               encType1 (3),
               invalid (128)
               }
   MAX-ACCESS  read-write
   STATUS      current
   DESCRIPTION
      "Path: router1645.editConf.security.snmpv3.encModeAuthPassw

       Possibilities:
               none   (1)
               encrypt   (2)
               encType1   (3)
               invalid   (128)"
   ::= {er1645v2SecurityEntry 50659328}

er1645v2SecuritySnmpv3EncAuthPassword OBJECT-TYPE
   SYNTAX      DisplayString
   MAX-ACCESS  read-write
   STATUS      current
   DESCRIPTION
      "Path: router1645.editConf.security.snmpv3.encAuthPassword"
   ::= {er1645v2SecurityEntry 50790400}

er1645v2SecuritySnmpv3PrivProtocol OBJECT-TYPE
   SYNTAX      INTEGER
               {
               none (0),
               des (1),
               aes128 (2)
               }
   MAX-ACCESS  read-write
   STATUS      current
   DESCRIPTION
      "Path: router1645.editConf.security.snmpv3.privProtocol

       Possibilities:
               none   (0)
               des   (1)
               aes128   (2)"
   ::= {er1645v2SecurityEntry 50528256}

er1645v2SecuritySnmpv3PrivPassword OBJECT-TYPE
   SYNTAX      DisplayString
   MAX-ACCESS  read-write
   STATUS      current
   DESCRIPTION
      "Path: router1645.editConf.security.snmpv3.privPassword"
   ::= {er1645v2SecurityEntry 50593792}

er1645v2SecuritySnmpv3EncModePrivPassw OBJECT-TYPE
   SYNTAX      INTEGER
               {
               none (1),
               encrypt (2),
               encType1 (3),
               invalid (128)
               }
   MAX-ACCESS  read-write
   STATUS      current
   DESCRIPTION
      "Path: router1645.editConf.security.snmpv3.encModePrivPassw

       Possibilities:
               none   (1)
               encrypt   (2)
               encType1   (3)
               invalid   (128)"
   ::= {er1645v2SecurityEntry 50724864}

er1645v2SecuritySnmpv3EncPrivPassword OBJECT-TYPE
   SYNTAX      DisplayString
   MAX-ACCESS  read-write
   STATUS      current
   DESCRIPTION
      "Path: router1645.editConf.security.snmpv3.encPrivPassword"
   ::= {er1645v2SecurityEntry 50855936}

er1645v2SecuritySnmpAccessFilter OBJECT-TYPE
   SYNTAX      SEQUENCE OF Er1645v2SecuritySnmpAccessFilterEntry
   MAX-ACCESS  not-accessible
   STATUS      current
   DESCRIPTION
      ""
   ::= {er1645v2Security 855638016}

er1645v2SecuritySnmpAccessFilterEntry OBJECT-TYPE
   SYNTAX      Er1645v2SecuritySnmpAccessFilterEntry
   MAX-ACCESS  not-accessible
   STATUS      current
   DESCRIPTION
      ""
   INDEX      { er1645v2SecurityTableIx,
                er1645v2SecuritySnmpAccessFilterTableIx }
   ::= {er1645v2SecuritySnmpAccessFilter 1}

Er1645v2SecuritySnmpAccessFilterEntry ::=
   SEQUENCE
      {
      er1645v2SecuritySnmpAccessFilterActions
         VariableLengthTableActions,
      er1645v2SecuritySnmpAccessFilterTableIx
         TableIndex,
      er1645v2SecuritySnmpAccessFilterRemark
         DisplayString,
      er1645v2SecuritySnmpAccessFilterFilter
         DisplayString
      }

er1645v2SecuritySnmpAccessFilterActions OBJECT-TYPE
   SYNTAX      VariableLengthTableActions
   MAX-ACCESS  read-write
   STATUS      current
   DESCRIPTION
      "By way of this field, some manipulations
       on this table may be performed."
   ::= {er1645v2SecuritySnmpAccessFilterEntry 2}

er1645v2SecuritySnmpAccessFilterTableIx OBJECT-TYPE
   SYNTAX      TableIndex
   MAX-ACCESS  not-accessible
   STATUS      current
   DESCRIPTION
      ""
   ::= {er1645v2SecuritySnmpAccessFilterEntry 11}

er1645v2SecuritySnmpAccessFilterRemark OBJECT-TYPE
   SYNTAX      DisplayString
   MAX-ACCESS  read-write
   STATUS      current
   DESCRIPTION
      "Path: router1645.editConf.security.snmpAccessFilter.remark"
   ::= {er1645v2SecuritySnmpAccessFilterEntry 251658240}

er1645v2SecuritySnmpAccessFilterFilter OBJECT-TYPE
   SYNTAX      DisplayString
   MAX-ACCESS  read-write
   STATUS      current
   DESCRIPTION
      "Path: router1645.editConf.security.snmpAccessFilter.filter"
   ::= {er1645v2SecuritySnmpAccessFilterEntry 16777216}

er1645v2SecurityAclLin OBJECT-TYPE
   SYNTAX      SEQUENCE OF Er1645v2SecurityAclLinEntry
   MAX-ACCESS  not-accessible
   STATUS      current
   DESCRIPTION
      ""
   ::= {er1645v2Security 838860800}

er1645v2SecurityAclLinEntry OBJECT-TYPE
   SYNTAX      Er1645v2SecurityAclLinEntry
   MAX-ACCESS  not-accessible
   STATUS      current
   DESCRIPTION
      ""
   INDEX      { er1645v2SecurityTableIx,
                er1645v2SecurityAclLinTableIx }
   ::= {er1645v2SecurityAclLin 1}

Er1645v2SecurityAclLinEntry ::=
   SEQUENCE
      {
      er1645v2SecurityAclLinActions
         VariableLengthTableActions,
      er1645v2SecurityAclLinTableIx
         TableIndex,
      er1645v2SecurityAclLinRemark
         DisplayString,
      er1645v2SecurityAclLinSrcIpStart
         IpAddress,
      er1645v2SecurityAclLinSrcIpEnd
         IpAddress,
      er1645v2SecurityAclLinSrcIpV6Start
         Ipv6Address,
      er1645v2SecurityAclLinSrcIpV6End
         Ipv6Address,
      er1645v2SecurityAclLinVrfRouter
         DisplayString,
      er1645v2SecurityAclLinApplicationsAll
         DisplayString,
      er1645v2SecurityAclLinApplicationsAllow
         Integer32,
      er1645v2SecurityAclLinApplicationsDeny
         Integer32
      }

er1645v2SecurityAclLinActions OBJECT-TYPE
   SYNTAX      VariableLengthTableActions
   MAX-ACCESS  read-write
   STATUS      current
   DESCRIPTION
      "By way of this field, some manipulations
       on this table may be performed."
   ::= {er1645v2SecurityAclLinEntry 2}

er1645v2SecurityAclLinTableIx OBJECT-TYPE
   SYNTAX      TableIndex
   MAX-ACCESS  not-accessible
   STATUS      current
   DESCRIPTION
      ""
   ::= {er1645v2SecurityAclLinEntry 11}

er1645v2SecurityAclLinRemark OBJECT-TYPE
   SYNTAX      DisplayString
   MAX-ACCESS  read-write
   STATUS      current
   DESCRIPTION
      "Path: router1645.editConf.security.accessList.remark"
   ::= {er1645v2SecurityAclLinEntry 251658240}

er1645v2SecurityAclLinSrcIpStart OBJECT-TYPE
   SYNTAX      IpAddress
   MAX-ACCESS  read-write
   STATUS      current
   DESCRIPTION
      "Path: router1645.editConf.security.accessList.sourceIpStartAddress"
   ::= {er1645v2SecurityAclLinEntry 16777216}

er1645v2SecurityAclLinSrcIpEnd OBJECT-TYPE
   SYNTAX      IpAddress
   MAX-ACCESS  read-write
   STATUS      current
   DESCRIPTION
      "Path: router1645.editConf.security.accessList.sourceIpEndAddress"
   ::= {er1645v2SecurityAclLinEntry 33554432}

er1645v2SecurityAclLinSrcIpV6Start OBJECT-TYPE
   SYNTAX      Ipv6Address
   MAX-ACCESS  read-write
   STATUS      current
   DESCRIPTION
      "Path: router1645.editConf.security.accessList.sourceIpV6StartAddress

       ipv6 address"
   ::= {er1645v2SecurityAclLinEntry 50331648}

er1645v2SecurityAclLinSrcIpV6End OBJECT-TYPE
   SYNTAX      Ipv6Address
   MAX-ACCESS  read-write
   STATUS      current
   DESCRIPTION
      "Path: router1645.editConf.security.accessList.sourceIpV6EndAddress

       ipv6 address"
   ::= {er1645v2SecurityAclLinEntry 67108864}

er1645v2SecurityAclLinVrfRouter OBJECT-TYPE
   SYNTAX      DisplayString
   MAX-ACCESS  read-write
   STATUS      current
   DESCRIPTION
      "Path: router1645.editConf.security.accessList.vrfRouter"
   ::= {er1645v2SecurityAclLinEntry 117440512}

er1645v2SecurityAclLinApplicationsAll OBJECT-TYPE
   SYNTAX      DisplayString
   MAX-ACCESS  read-write
   STATUS      current
   DESCRIPTION
      "Path: router1645.editConf.security.accessList.applications.all"
   ::= {er1645v2SecurityAclLinEntry 100728832}

er1645v2SecurityAclLinApplicationsAllow OBJECT-TYPE
   SYNTAX      Integer32
   MAX-ACCESS  read-write
   STATUS      current
   DESCRIPTION
      "Path: router1645.editConf.security.accessList.applications.allow

       Bit meanings:
               bit 0 = cms2,
               bit 2 = console-cli,
               bit 3 = console-cms2,
               bit 4 = snmp,
               bit 5 = tftp,
               bit 6 = ftp,
               bit 7 = telnet,
               bit 8 = ssh,
               bit 9 = snmpv3,
               bit 12 = http-classic,
               bit 13 = http-tma,
               bit 14 = http-easyConfig,
               bit 20 = https-classic,
               bit 21 = https-tma,
               bit 22 = https-easyConfig"
   ::= {er1645v2SecurityAclLinEntry 100794368}

er1645v2SecurityAclLinApplicationsDeny OBJECT-TYPE
   SYNTAX      Integer32
   MAX-ACCESS  read-write
   STATUS      current
   DESCRIPTION
      "Path: router1645.editConf.security.accessList.applications.deny

       Bit meanings:
               bit 0 = cms2,
               bit 2 = console-cli,
               bit 3 = console-cms2,
               bit 4 = snmp,
               bit 5 = tftp,
               bit 6 = ftp,
               bit 7 = telnet,
               bit 8 = ssh,
               bit 9 = snmpv3,
               bit 12 = http-classic,
               bit 13 = http-tma,
               bit 14 = http-easyConfig,
               bit 20 = https-classic,
               bit 21 = https-tma,
               bit 22 = https-easyConfig"
   ::= {er1645v2SecurityAclLinEntry 100859904}


er1645v2AlarmMask OBJECT-TYPE
   SYNTAX      Integer32
   MAX-ACCESS  read-write
   STATUS      current
   DESCRIPTION
      "Path: router1645.editConf.alarmMask
       Info: sysAlarmMask

       Bit meanings:
               bit 0 = notResponding,
               bit 1 = alarmSyncLoss,
               bit 2 = configChanged,
               bit 3 = access,
               bit 4 = powerSupplyFail,
               bit 5 = powerSupplyProblem,
               bit 8 = unknownState,
               bit 9 = coldBoot,
               bit 10 = warmBoot,
               bit 12 = codeFallback,
               bit 13 = configFallback,
               bit 14 = codeConsistencyFail,
               bit 15 = configConsistencyFail"
   ::= {er1645v2 170}


er1645v2AlarmLev OBJECT IDENTIFIER ::= {er1645v2 169}

er1645v2AlarmLevSSC OBJECT IDENTIFIER ::= {er1645v2AlarmLev 1}

er1645v2AlarmLevEntry OBJECT IDENTIFIER ::= {er1645v2AlarmLevSSC 1}

er1645v2AlarmLevNotResponding OBJECT-TYPE
   SYNTAX      Integer32
   MAX-ACCESS  read-write
   STATUS      current
   DESCRIPTION
      "Path: router1645.editConf.alarmLevel.notResponding"
   ::= {er1645v2AlarmLevEntry 16777216}

er1645v2AlarmLevSyncLoss OBJECT-TYPE
   SYNTAX      Integer32
   MAX-ACCESS  read-write
   STATUS      current
   DESCRIPTION
      "Path: router1645.editConf.alarmLevel.alarmSyncLoss"
   ::= {er1645v2AlarmLevEntry 33554432}

er1645v2AlarmLevConfigChanged OBJECT-TYPE
   SYNTAX      Integer32
   MAX-ACCESS  read-write
   STATUS      current
   DESCRIPTION
      "Path: router1645.editConf.alarmLevel.configChanged"
   ::= {er1645v2AlarmLevEntry 50331648}

er1645v2AlarmLevAccess OBJECT-TYPE
   SYNTAX      Integer32
   MAX-ACCESS  read-write
   STATUS      current
   DESCRIPTION
      "Path: router1645.editConf.alarmLevel.access"
   ::= {er1645v2AlarmLevEntry 67108864}

er1645v2AlarmLevPowerSupplyFail OBJECT-TYPE
   SYNTAX      Integer32
   MAX-ACCESS  read-write
   STATUS      current
   DESCRIPTION
      "Path: router1645.editConf.alarmLevel.powerSupplyFail"
   ::= {er1645v2AlarmLevEntry 83886080}

er1645v2AlarmLevPowerSupplyProblem OBJECT-TYPE
   SYNTAX      Integer32
   MAX-ACCESS  read-write
   STATUS      current
   DESCRIPTION
      "Path: router1645.editConf.alarmLevel.powerSupplyProblem"
   ::= {er1645v2AlarmLevEntry 100663296}

er1645v2AlarmLevUnknownState OBJECT-TYPE
   SYNTAX      Integer32
   MAX-ACCESS  read-write
   STATUS      current
   DESCRIPTION
      "Path: router1645.editConf.alarmLevel.unknownState"
   ::= {er1645v2AlarmLevEntry 150994944}

er1645v2AlarmLevColdBoot OBJECT-TYPE
   SYNTAX      Integer32
   MAX-ACCESS  read-write
   STATUS      current
   DESCRIPTION
      "Path: router1645.editConf.alarmLevel.coldBoot"
   ::= {er1645v2AlarmLevEntry 167772160}

er1645v2AlarmLevWarmBoot OBJECT-TYPE
   SYNTAX      Integer32
   MAX-ACCESS  read-write
   STATUS      current
   DESCRIPTION
      "Path: router1645.editConf.alarmLevel.warmBoot"
   ::= {er1645v2AlarmLevEntry 184549376}

er1645v2AlarmLevCodeFallback OBJECT-TYPE
   SYNTAX      Integer32
   MAX-ACCESS  read-write
   STATUS      current
   DESCRIPTION
      "Path: router1645.editConf.alarmLevel.codeFallback"
   ::= {er1645v2AlarmLevEntry 218103808}

er1645v2AlarmLevConfigFallback OBJECT-TYPE
   SYNTAX      Integer32
   MAX-ACCESS  read-write
   STATUS      current
   DESCRIPTION
      "Path: router1645.editConf.alarmLevel.configFallback"
   ::= {er1645v2AlarmLevEntry 234881024}

er1645v2AlarmLevCdeConsFl OBJECT-TYPE
   SYNTAX      Integer32
   MAX-ACCESS  read-write
   STATUS      current
   DESCRIPTION
      "Path: router1645.editConf.alarmLevel.codeConsistencyFail"
   ::= {er1645v2AlarmLevEntry 251658240}

er1645v2AlarmLevCnfConsFl OBJECT-TYPE
   SYNTAX      Integer32
   MAX-ACCESS  read-write
   STATUS      current
   DESCRIPTION
      "Path: router1645.editConf.alarmLevel.configConsistencyFail"
   ::= {er1645v2AlarmLevEntry 268435456}



sr1645v2 OBJECT IDENTIFIER ::= {r1645v2 14}


sr1645v2SysDescr OBJECT-TYPE
   SYNTAX      DisplayString
   MAX-ACCESS  read-only
   STATUS      current
   DESCRIPTION
      "Path: router1645.status.sysDescr
       Info: sysDescr"
   ::= {sr1645v2 4}


sr1645v2SysObjectID OBJECT-TYPE
   SYNTAX      DisplayString
   MAX-ACCESS  read-only
   STATUS      current
   DESCRIPTION
      "Path: router1645.status.sysObjectID
       Info: sysObjectID"
   ::= {sr1645v2 5}


sr1645v2SysUpTime OBJECT-TYPE
   SYNTAX      TimeTicks
   MAX-ACCESS  read-only
   STATUS      current
   DESCRIPTION
      "Path: router1645.status.sysUpTime
       Info: sysUpTime

       Time in centi-second."
   ::= {sr1645v2 6}


sr1645v2SysServices OBJECT-TYPE
   SYNTAX      Integer32
   MAX-ACCESS  read-only
   STATUS      current
   DESCRIPTION
      "Path: router1645.status.sysServices
       Info: sysServices"
   ::= {sr1645v2 7}


sr1645v2Flash1Version OBJECT-TYPE
   SYNTAX      DisplayString
   MAX-ACCESS  read-only
   STATUS      current
   DESCRIPTION
      "Path: router1645.status.flash1Version
       Info: flash1Version"
   ::= {sr1645v2 234}


sr1645v2Flash2Version OBJECT-TYPE
   SYNTAX      DisplayString
   MAX-ACCESS  read-only
   STATUS      current
   DESCRIPTION
      "Path: router1645.status.flash2Version
       Info: flash2Version"
   ::= {sr1645v2 235}


sr1645v2ActiveFlash OBJECT-TYPE
   SYNTAX      INTEGER
               {
               flash1 (1),
               flash2 (2),
               verifyFlash1 (6),
               verifyFlash2 (7),
               restoredFlash1 (17),
               restoredFlash2 (18)
               }
   MAX-ACCESS  read-only
   STATUS      current
   DESCRIPTION
      "Path: router1645.status.activeFlash
       Info: activeFlash

       Possibilities:
               flash1   (1)
               flash2   (2)
               verifyFlash1   (6)
               verifyFlash2   (7)
               restoredFlash1   (17)
               restoredFlash2   (18)"
   ::= {sr1645v2 236}


sr1645v2NextActiveFlash OBJECT-TYPE
   SYNTAX      INTEGER
               {
               flash1 (1),
               flash2 (2),
               verifyFlash1 (6),
               verifyFlash2 (7),
               restoredFlash1 (17),
               restoredFlash2 (18)
               }
   MAX-ACCESS  read-only
   STATUS      current
   DESCRIPTION
      "Path: router1645.status.nextActiveFlash
       Info: activeFlash

       Possibilities:
               flash1   (1)
               flash2   (2)
               verifyFlash1   (6)
               verifyFlash2   (7)
               restoredFlash1   (17)
               restoredFlash2   (18)"
   ::= {sr1645v2 216}


sr1645v2BootVersion OBJECT-TYPE
   SYNTAX      DisplayString
   MAX-ACCESS  read-only
   STATUS      current
   DESCRIPTION
      "Path: router1645.status.bootVersion
       Info: bootVersion"
   ::= {sr1645v2 237}


sr1645v2FlashVersions OBJECT-TYPE
   SYNTAX      Integer32
   MAX-ACCESS  read-only
   STATUS      current
   DESCRIPTION
      "Path: router1645.status.flashVersions
       Info: Number of versions of applicationcode that can be stored"
   ::= {sr1645v2 215}


sr1645v2Messages OBJECT IDENTIFIER ::= {sr1645v2 254}

sr1645v2MessagesSSCTable OBJECT-TYPE
   SYNTAX      SEQUENCE OF Sr1645v2MessagesEntry
   MAX-ACCESS  not-accessible
   STATUS      current
   DESCRIPTION
      "log or tracing messages"
   ::= {sr1645v2Messages 1}

sr1645v2MessagesEntry OBJECT-TYPE
   SYNTAX      Sr1645v2MessagesEntry
   MAX-ACCESS  not-accessible
   STATUS      current
   DESCRIPTION
      ""
   INDEX      { sr1645v2MessagesTableIx }
   ::= {sr1645v2MessagesSSCTable 1}

Sr1645v2MessagesEntry ::=
   SEQUENCE
      {
      sr1645v2MessagesTableIx
         TableIndex,
      sr1645v2MessagesMessage
         DisplayString
      }

sr1645v2MessagesTableIx OBJECT-TYPE
   SYNTAX      TableIndex
   MAX-ACCESS  not-accessible
   STATUS      current
   DESCRIPTION
      ""
   ::= {sr1645v2MessagesEntry 11}

sr1645v2MessagesMessage OBJECT-TYPE
   SYNTAX      DisplayString
   MAX-ACCESS  read-only
   STATUS      current
   DESCRIPTION
      "Path: router1645.status.messages.message"
   ::= {sr1645v2MessagesEntry 16777216}


sr1645v2TraceMessages OBJECT IDENTIFIER ::= {sr1645v2 271}

sr1645v2TraceMessagesSSCTable OBJECT-TYPE
   SYNTAX      SEQUENCE OF Sr1645v2TraceMessagesEntry
   MAX-ACCESS  not-accessible
   STATUS      current
   DESCRIPTION
      "log or tracing messages"
   ::= {sr1645v2TraceMessages 1}

sr1645v2TraceMessagesEntry OBJECT-TYPE
   SYNTAX      Sr1645v2TraceMessagesEntry
   MAX-ACCESS  not-accessible
   STATUS      current
   DESCRIPTION
      ""
   INDEX      { sr1645v2TraceMessagesTableIx }
   ::= {sr1645v2TraceMessagesSSCTable 1}

Sr1645v2TraceMessagesEntry ::=
   SEQUENCE
      {
      sr1645v2TraceMessagesTableIx
         TableIndex,
      sr1645v2TraceMessagesMessage
         DisplayString
      }

sr1645v2TraceMessagesTableIx OBJECT-TYPE
   SYNTAX      TableIndex
   MAX-ACCESS  not-accessible
   STATUS      current
   DESCRIPTION
      ""
   ::= {sr1645v2TraceMessagesEntry 11}

sr1645v2TraceMessagesMessage OBJECT-TYPE
   SYNTAX      DisplayString
   MAX-ACCESS  read-only
   STATUS      current
   DESCRIPTION
      "Path: router1645.status.traceMessages.message"
   ::= {sr1645v2TraceMessagesEntry 16777216}


sr1645v2TraceInfo OBJECT IDENTIFIER ::= {sr1645v2 282}

sr1645v2TraceInfoSSC OBJECT IDENTIFIER ::= {sr1645v2TraceInfo 1}

sr1645v2TraceInfoEntry OBJECT IDENTIFIER ::= {sr1645v2TraceInfoSSC 1}

sr1645v2TraceInfoCnt OBJECT-TYPE
   SYNTAX      Counter32
   MAX-ACCESS  read-only
   STATUS      current
   DESCRIPTION
      "Path: router1645.status.traceInfo.cnt

       32 bit unsigned wrappable counter."
   ::= {sr1645v2TraceInfoEntry 16777216}

sr1645v2TraceInfoFileName OBJECT-TYPE
   SYNTAX      DisplayString
   MAX-ACCESS  read-only
   STATUS      current
   DESCRIPTION
      "Path: router1645.status.traceInfo.fileName"
   ::= {sr1645v2TraceInfoEntry 33554432}

sr1645v2TraceInfoFileSize OBJECT-TYPE
   SYNTAX      Gauge32
   MAX-ACCESS  read-only
   STATUS      current
   DESCRIPTION
      "Path: router1645.status.traceInfo.fileSize

       32 bit unsigned gauge value."
   ::= {sr1645v2TraceInfoEntry 50331648}


sr1645v2DeviceId OBJECT-TYPE
   SYNTAX      DisplayString
   MAX-ACCESS  read-only
   STATUS      current
   DESCRIPTION
      "Path: router1645.status.deviceId
       Info: This string uniquely identifies the device."
   ::= {sr1645v2 248}


sr1645v2TdreVersion OBJECT-TYPE
   SYNTAX      DisplayString
   MAX-ACCESS  read-only
   STATUS      current
   DESCRIPTION
      "Path: router1645.status.tdreVersion
       Info: tdreVersion"
   ::= {sr1645v2 265}


sr1645v2Date OBJECT-TYPE
   SYNTAX      DisplayString
   MAX-ACCESS  read-only
   STATUS      current
   DESCRIPTION
      "Path: router1645.status.date
       Info: current date"
   ::= {sr1645v2 15}


sr1645v2Time OBJECT-TYPE
   SYNTAX      DisplayString
   MAX-ACCESS  read-only
   STATUS      current
   DESCRIPTION
      "Path: router1645.status.time
       Info: current time"
   ::= {sr1645v2 16}


sr1645v2Day OBJECT-TYPE
   SYNTAX      INTEGER
               {
               sunday (1),
               monday (2),
               tuesday (3),
               wednesday (4),
               thursday (5),
               friday (6),
               saturday (7)
               }
   MAX-ACCESS  read-only
   STATUS      current
   DESCRIPTION
      "Path: router1645.status.day
       Info: day of week

       Possibilities:
               sunday   (1)
               monday   (2)
               tuesday   (3)
               wednesday   (4)
               thursday   (5)
               friday   (6)
               saturday   (7)"
   ::= {sr1645v2 14}


sr1645v2ScheduleReboot OBJECT IDENTIFIER ::= {sr1645v2 162}

sr1645v2ScheduleRebootSSC OBJECT IDENTIFIER ::= {sr1645v2ScheduleReboot 1}

sr1645v2ScheduleRebootEntry OBJECT IDENTIFIER ::= {sr1645v2ScheduleRebootSSC 1}

sr1645v2ScheduleRebootState OBJECT-TYPE
   SYNTAX      INTEGER
               {
               notRunning (1),
               cancelled (2),
               waitForTimer (3),
               waitForTime (4),
               waitForDateAndTime (5),
               loadingConfig (11),
               waitForStartTesting (12),
               testing (13),
               waitEndStabilityTest (14),
               failedLossThreshold (101),
               failedDelayThreshold (102)
               }
   MAX-ACCESS  read-only
   STATUS      current
   DESCRIPTION
      "Path: router1645.status.scheduleReboot.state

       Possibilities:
               notRunning   (1)
               cancelled   (2)
               waitForTimer   (3)
               waitForTime   (4)
               waitForDateAndTime   (5)
               loadingConfig   (11)
               waitForStartTesting   (12)
               testing   (13)
               waitEndStabilityTest   (14)
               failedLossThreshold   (101)
               failedDelayThreshold   (102)"
   ::= {sr1645v2ScheduleRebootEntry 16777216}

sr1645v2ScheduleRebootTimeUntilReboot OBJECT-TYPE
   SYNTAX      TimeTicks
   MAX-ACCESS  read-only
   STATUS      current
   DESCRIPTION
      "Path: router1645.status.scheduleReboot.timeUntilReboot

       Time in centi-second."
   ::= {sr1645v2ScheduleRebootEntry 33554432}

sr1645v2ScheduleRebootRebootDateTimeYear OBJECT-TYPE
   SYNTAX      Integer32
   MAX-ACCESS  read-only
   STATUS      current
   DESCRIPTION
      "Path: router1645.status.scheduleReboot.rebootDateTime.year"
   ::= {sr1645v2ScheduleRebootEntry 83951616}

sr1645v2ScheduleRebootRebootDateTimeMonth OBJECT-TYPE
   SYNTAX      Integer32
   MAX-ACCESS  read-only
   STATUS      current
   DESCRIPTION
      "Path: router1645.status.scheduleReboot.rebootDateTime.month"
   ::= {sr1645v2ScheduleRebootEntry 84017152}

sr1645v2ScheduleRebootRebootDateTimeDay OBJECT-TYPE
   SYNTAX      Integer32
   MAX-ACCESS  read-only
   STATUS      current
   DESCRIPTION
      "Path: router1645.status.scheduleReboot.rebootDateTime.day"
   ::= {sr1645v2ScheduleRebootEntry 84082688}

sr1645v2ScheduleRebootRebootDateTimeHour OBJECT-TYPE
   SYNTAX      Integer32
   MAX-ACCESS  read-only
   STATUS      current
   DESCRIPTION
      "Path: router1645.status.scheduleReboot.rebootDateTime.hour"
   ::= {sr1645v2ScheduleRebootEntry 84148224}

sr1645v2ScheduleRebootRebootDateTimeMinute OBJECT-TYPE
   SYNTAX      Integer32
   MAX-ACCESS  read-only
   STATUS      current
   DESCRIPTION
      "Path: router1645.status.scheduleReboot.rebootDateTime.minute"
   ::= {sr1645v2ScheduleRebootEntry 84213760}


sr1645v2ScheduleLoad OBJECT IDENTIFIER ::= {sr1645v2 281}

sr1645v2ScheduleLoadSSC OBJECT IDENTIFIER ::= {sr1645v2ScheduleLoad 1}

sr1645v2ScheduleLoadEntry OBJECT IDENTIFIER ::= {sr1645v2ScheduleLoadSSC 1}

sr1645v2ScheduleLoadState OBJECT-TYPE
   SYNTAX      INTEGER
               {
               notRunning (1),
               cancelled (2),
               waitForTimer (3),
               waitForTime (4),
               waitForDateAndTime (5),
               loadingConfig (11),
               waitForStartTesting (12),
               testing (13),
               waitEndStabilityTest (14),
               failedLossThreshold (101),
               failedDelayThreshold (102)
               }
   MAX-ACCESS  read-only
   STATUS      current
   DESCRIPTION
      "Path: router1645.status.scheduleLoad.state

       Possibilities:
               notRunning   (1)
               cancelled   (2)
               waitForTimer   (3)
               waitForTime   (4)
               waitForDateAndTime   (5)
               loadingConfig   (11)
               waitForStartTesting   (12)
               testing   (13)
               waitEndStabilityTest   (14)
               failedLossThreshold   (101)
               failedDelayThreshold   (102)"
   ::= {sr1645v2ScheduleLoadEntry 16777216}

sr1645v2ScheduleLoadTimeUntilNextAction OBJECT-TYPE
   SYNTAX      TimeTicks
   MAX-ACCESS  read-only
   STATUS      current
   DESCRIPTION
      "Path: router1645.status.scheduleLoad.timeUntilNextAction

       Time in centi-second."
   ::= {sr1645v2ScheduleLoadEntry 33554432}

sr1645v2ScheduleLoadActionDateTimeYear OBJECT-TYPE
   SYNTAX      Integer32
   MAX-ACCESS  read-only
   STATUS      current
   DESCRIPTION
      "Path: router1645.status.scheduleLoad.actionDateTime.year"
   ::= {sr1645v2ScheduleLoadEntry 83951616}

sr1645v2ScheduleLoadActionDateTimeMonth OBJECT-TYPE
   SYNTAX      Integer32
   MAX-ACCESS  read-only
   STATUS      current
   DESCRIPTION
      "Path: router1645.status.scheduleLoad.actionDateTime.month"
   ::= {sr1645v2ScheduleLoadEntry 84017152}

sr1645v2ScheduleLoadActionDateTimeDay OBJECT-TYPE
   SYNTAX      Integer32
   MAX-ACCESS  read-only
   STATUS      current
   DESCRIPTION
      "Path: router1645.status.scheduleLoad.actionDateTime.day"
   ::= {sr1645v2ScheduleLoadEntry 84082688}

sr1645v2ScheduleLoadActionDateTimeHour OBJECT-TYPE
   SYNTAX      Integer32
   MAX-ACCESS  read-only
   STATUS      current
   DESCRIPTION
      "Path: router1645.status.scheduleLoad.actionDateTime.hour"
   ::= {sr1645v2ScheduleLoadEntry 84148224}

sr1645v2ScheduleLoadActionDateTimeMinute OBJECT-TYPE
   SYNTAX      Integer32
   MAX-ACCESS  read-only
   STATUS      current
   DESCRIPTION
      "Path: router1645.status.scheduleLoad.actionDateTime.minute"
   ::= {sr1645v2ScheduleLoadEntry 84213760}

sr1645v2ScheduleLoadConfigFile OBJECT-TYPE
   SYNTAX      DisplayString
   MAX-ACCESS  read-only
   STATUS      current
   DESCRIPTION
      "Path: router1645.status.scheduleLoad.configFile"
   ::= {sr1645v2ScheduleLoadEntry 117440512}

sr1645v2ScheduleLoadIcmpTestResultNbrOfTxPackets OBJECT-TYPE
   SYNTAX      Integer32
   MAX-ACCESS  read-only
   STATUS      current
   DESCRIPTION
      "Path: router1645.status.scheduleLoad.icmpTestResult.nbrOfTxPackets"
   ::= {sr1645v2ScheduleLoadEntry 100859904}

sr1645v2ScheduleLoadIcmpTestResultLoss OBJECT-TYPE
   SYNTAX      Integer32
   UNITS       "%"
   MAX-ACCESS  read-only
   STATUS      current
   DESCRIPTION
      "Path: router1645.status.scheduleLoad.icmpTestResult.loss

       unit name = %"
   ::= {sr1645v2ScheduleLoadEntry 100728832}

sr1645v2ScheduleLoadIcmpTestResultDelay OBJECT-TYPE
   SYNTAX      Integer32
   UNITS       "msec"
   MAX-ACCESS  read-only
   STATUS      current
   DESCRIPTION
      "Path: router1645.status.scheduleLoad.icmpTestResult.delay

       unit name = msec"
   ::= {sr1645v2ScheduleLoadEntry 100794368}


sr1645v2LoaderVersion OBJECT-TYPE
   SYNTAX      DisplayString
   MAX-ACCESS  read-only
   STATUS      current
   DESCRIPTION
      "Path: router1645.status.loaderVersion
       Info: loaderVersion"
   ::= {sr1645v2 218}


sr1645v2Dsp1Version OBJECT-TYPE
   SYNTAX      DisplayString
   MAX-ACCESS  read-only
   STATUS      current
   DESCRIPTION
      "Path: router1645.status.dsp1Version
       Info: dspVersion"
   ::= {sr1645v2 238}


sr1645v2ConfigurationSaving OBJECT-TYPE
   SYNTAX      INTEGER
               {
               done (0),
               waitTimeOut (1),
               waitUserAck (2),
               ackedWaitTimeOut (3),
               restoredPrevious (10)
               }
   MAX-ACCESS  read-only
   STATUS      current
   DESCRIPTION
      "Path: router1645.status.configurationSaving
       Info: indicates whether the configuration is being saved or not.

       Possibilities:
               done   (0)
               waitTimeOut   (1)
               waitUserAck   (2)
               ackedWaitTimeOut   (3)
               restoredPrevious   (10)"
   ::= {sr1645v2 256}


sr1645v2SystemHwInfo OBJECT IDENTIFIER ::= {sr1645v2 20}

sr1645v2SystemHwInfoSSC OBJECT IDENTIFIER ::= {sr1645v2SystemHwInfo 1}

sr1645v2SystemHwInfoEntry OBJECT IDENTIFIER ::= {sr1645v2SystemHwInfoSSC 1}

sr1645v2SystemHwInfoBusFreq OBJECT-TYPE
   SYNTAX      Gauge32
   MAX-ACCESS  read-only
   STATUS      current
   DESCRIPTION
      "Path: router1645.status.systemHwInfo.busFreq

       32 bit unsigned gauge value."
   ::= {sr1645v2SystemHwInfoEntry 16777216}

sr1645v2SystemHwInfoCpuFreq OBJECT-TYPE
   SYNTAX      Gauge32
   MAX-ACCESS  read-only
   STATUS      current
   DESCRIPTION
      "Path: router1645.status.systemHwInfo.cpuFreq

       32 bit unsigned gauge value."
   ::= {sr1645v2SystemHwInfoEntry 33554432}

sr1645v2SystemHwInfoCeFreq OBJECT-TYPE
   SYNTAX      Gauge32
   MAX-ACCESS  read-only
   STATUS      current
   DESCRIPTION
      "Path: router1645.status.systemHwInfo.ceFreq

       32 bit unsigned gauge value."
   ::= {sr1645v2SystemHwInfoEntry 117440512}

sr1645v2SystemHwInfoPcbRev OBJECT-TYPE
   SYNTAX      INTEGER
               {
               s0d0 (0),
               s0d1 (1),
               s0d2 (2),
               s0d3 (3),
               s0d4 (4),
               s0d5 (5),
               s0d6 (6),
               sl0d2 (102),
               sl0d3 (103),
               sl0d4 (104),
               sl0d5 (105),
               sl0d6 (106),
               sl0d7 (107),
               unknown (255)
               }
   MAX-ACCESS  read-only
   STATUS      current
   DESCRIPTION
      "Path: router1645.status.systemHwInfo.pcbRev

       Possibilities:
               0.0   (0)
               0.1   (1)
               0.2   (2)
               0.3   (3)
               0.4   (4)
               0.5   (5)
               0.6   (6)
               <0.2   (102)
               <0.3   (103)
               <0.4   (104)
               <0.5   (105)
               <0.6   (106)
               <0.7   (107)
               unknown   (255)"
   ::= {sr1645v2SystemHwInfoEntry 50331648}

sr1645v2SystemHwInfoMemSize OBJECT-TYPE
   SYNTAX      Gauge32
   MAX-ACCESS  read-only
   STATUS      current
   DESCRIPTION
      "Path: router1645.status.systemHwInfo.memSize

       32 bit unsigned gauge value."
   ::= {sr1645v2SystemHwInfoEntry 67108864}

sr1645v2SystemHwInfoCpuFamily OBJECT-TYPE
   SYNTAX      INTEGER
               {
               mpc860 (0),
               mpc862 (1),
               mpc866 (2),
               mpc885 (3),
               mpc8260 (20),
               mpc8280 (21),
               mpc8272 (22),
               mpc8360 (40),
               e300c1 (50),
               e300c2 (51),
               e300c3 (52),
               p1020 (60),
               p1011 (61),
               p1021 (62),
               p1012 (63),
               p2020 (64),
               p2010 (65),
               unknown (255)
               }
   MAX-ACCESS  read-only
   STATUS      current
   DESCRIPTION
      "Path: router1645.status.systemHwInfo.cpuFamily

       Possibilities:
               mpc860   (0)
               mpc862   (1)
               mpc866   (2)
               mpc885   (3)
               mpc8260   (20)
               mpc8280   (21)
               mpc8272   (22)
               mpc8360   (40)
               e300c1   (50)
               e300c2   (51)
               e300c3   (52)
               p1020   (60)
               p1011   (61)
               p1021   (62)
               p1012   (63)
               p2020   (64)
               p2010   (65)
               unknown   (255)"
   ::= {sr1645v2SystemHwInfoEntry 83886080}

sr1645v2SystemHwInfoCpuRev OBJECT-TYPE
   SYNTAX      INTEGER
               {
               s0d0 (0),
               s0d1 (1),
               s0d2 (2),
               s0d3 (3),
               s0d4 (4),
               s0d5 (5),
               s0d6 (6),
               ad0 (10),
               ad1 (11),
               ad2 (12),
               ad3 (13),
               ad4 (14),
               bd0 (20),
               bd1 (21),
               bd2 (22),
               bd3 (23),
               bd4 (24),
               cd0 (30),
               cd1 (31),
               cd2 (32),
               cd3 (33),
               cd4 (34),
               dd0 (40),
               dd1 (41),
               dd2 (42),
               dd3 (43),
               dd4 (44),
               s1d0 (50),
               s1d1 (51),
               s1d2 (52),
               s1d3 (53),
               s1d4 (54),
               s2d0 (60),
               s2d1 (61),
               s2d2 (62),
               s2d3 (63),
               s2d4 (64),
               s3d0 (70),
               s3d1 (71),
               s3d2 (72),
               s3d3 (73),
               s3d4 (74),
               s4d0 (80),
               s4d1 (81),
               s4d2 (82),
               s4d3 (83),
               s4d4 (84),
               unknown (255)
               }
   MAX-ACCESS  read-only
   STATUS      current
   DESCRIPTION
      "Path: router1645.status.systemHwInfo.cpuRev

       Possibilities:
               0.0   (0)
               0.1   (1)
               0.2   (2)
               0.3   (3)
               0.4   (4)
               0.5   (5)
               0.6   (6)
               A.0   (10)
               A.1   (11)
               A.2   (12)
               A.3   (13)
               A.4   (14)
               B.0   (20)
               B.1   (21)
               B.2   (22)
               B.3   (23)
               B.4   (24)
               C.0   (30)
               C.1   (31)
               C.2   (32)
               C.3   (33)
               C.4   (34)
               D.0   (40)
               D.1   (41)
               D.2   (42)
               D.3   (43)
               D.4   (44)
               1.0   (50)
               1.1   (51)
               1.2   (52)
               1.3   (53)
               1.4   (54)
               2.0   (60)
               2.1   (61)
               2.2   (62)
               2.3   (63)
               2.4   (64)
               3.0   (70)
               3.1   (71)
               3.2   (72)
               3.3   (73)
               3.4   (74)
               4.0   (80)
               4.1   (81)
               4.2   (82)
               4.3   (83)
               4.4   (84)
               unknown   (255)"
   ::= {sr1645v2SystemHwInfoEntry 100663296}

sr1645v2SystemHwInfoPsuPsu1Status OBJECT-TYPE
   SYNTAX      INTEGER
               {
               unplugged (0),
               plugged (1),
               notAvailable (255)
               }
   MAX-ACCESS  read-only
   STATUS      current
   DESCRIPTION
      "Path: router1645.status.systemHwInfo.psu.psu1Status

       Possibilities:
               unplugged   (0)
               plugged   (1)
               notAvailable   (255)"
   ::= {sr1645v2SystemHwInfoEntry 134283264}

sr1645v2SystemHwInfoPsuPsu1Power OBJECT-TYPE
   SYNTAX      INTEGER
               {
               off (0),
               on (1),
               notAvailable (255)
               }
   MAX-ACCESS  read-only
   STATUS      current
   DESCRIPTION
      "Path: router1645.status.systemHwInfo.psu.psu1Power

       Possibilities:
               off   (0)
               on   (1)
               notAvailable   (255)"
   ::= {sr1645v2SystemHwInfoEntry 134348800}

sr1645v2SystemHwInfoPsuPsu2Status OBJECT-TYPE
   SYNTAX      INTEGER
               {
               unplugged (0),
               plugged (1),
               notAvailable (255)
               }
   MAX-ACCESS  read-only
   STATUS      current
   DESCRIPTION
      "Path: router1645.status.systemHwInfo.psu.psu2Status

       Possibilities:
               unplugged   (0)
               plugged   (1)
               notAvailable   (255)"
   ::= {sr1645v2SystemHwInfoEntry 134414336}

sr1645v2SystemHwInfoPsuPsu2Power OBJECT-TYPE
   SYNTAX      INTEGER
               {
               off (0),
               on (1),
               notAvailable (255)
               }
   MAX-ACCESS  read-only
   STATUS      current
   DESCRIPTION
      "Path: router1645.status.systemHwInfo.psu.psu2Power

       Possibilities:
               off   (0)
               on   (1)
               notAvailable   (255)"
   ::= {sr1645v2SystemHwInfoEntry 134479872}



fr1645v2 OBJECT IDENTIFIER ::= {r1645v2 13}


fr1645v2TotalAlarmLevel OBJECT-TYPE
   SYNTAX      Integer32
   MAX-ACCESS  read-only
   STATUS      current
   DESCRIPTION
      "Path: router1645.alarms.totalAlarmLevel
       Info: The total alarm level of the product."
   ::= {fr1645v2 213}


fr1645v2Alarm OBJECT IDENTIFIER ::= {fr1645v2 201}

fr1645v2AlarmSSC OBJECT IDENTIFIER ::= {fr1645v2Alarm 1}

fr1645v2AlarmEntry OBJECT IDENTIFIER ::= {fr1645v2AlarmSSC 1}

fr1645v2AlarmDiscriminator OBJECT-TYPE
   SYNTAX      Integer32
   MAX-ACCESS  read-only
   STATUS      current
   DESCRIPTION
      "Path: router1645.alarms.alarmInfo.discriminator"
   ::= {fr1645v2AlarmEntry 16777216}

fr1645v2AlarmCurrent OBJECT-TYPE
   SYNTAX      Integer32
   MAX-ACCESS  read-only
   STATUS      current
   DESCRIPTION
      "Path: router1645.alarms.alarmInfo.currentAlarms

       Bit meanings:
               bit 0 = notResponding,
               bit 1 = alarmSyncLoss,
               bit 2 = configChanged,
               bit 3 = access,
               bit 4 = powerSupplyFail,
               bit 5 = powerSupplyProblem,
               bit 8 = unknownState,
               bit 9 = coldBoot,
               bit 10 = warmBoot,
               bit 12 = codeFallback,
               bit 13 = configFallback,
               bit 14 = codeConsistencyFail,
               bit 15 = configConsistencyFail"
   ::= {fr1645v2AlarmEntry 33554432}

fr1645v2AlarmPrevious OBJECT-TYPE
   SYNTAX      Integer32
   MAX-ACCESS  read-only
   STATUS      current
   DESCRIPTION
      "Path: router1645.alarms.alarmInfo.previousAlarms

       Bit meanings:
               bit 0 = notResponding,
               bit 1 = alarmSyncLoss,
               bit 2 = configChanged,
               bit 3 = access,
               bit 4 = powerSupplyFail,
               bit 5 = powerSupplyProblem,
               bit 8 = unknownState,
               bit 9 = coldBoot,
               bit 10 = warmBoot,
               bit 12 = codeFallback,
               bit 13 = configFallback,
               bit 14 = codeConsistencyFail,
               bit 15 = configConsistencyFail"
   ::= {fr1645v2AlarmEntry 50331648}

fr1645v2AlarmMask OBJECT-TYPE
   SYNTAX      Integer32
   MAX-ACCESS  read-only
   STATUS      current
   DESCRIPTION
      "Path: router1645.alarms.alarmInfo.alarmMask

       Bit meanings:
               bit 0 = notResponding,
               bit 1 = alarmSyncLoss,
               bit 2 = configChanged,
               bit 3 = access,
               bit 4 = powerSupplyFail,
               bit 5 = powerSupplyProblem,
               bit 8 = unknownState,
               bit 9 = coldBoot,
               bit 10 = warmBoot,
               bit 12 = codeFallback,
               bit 13 = configFallback,
               bit 14 = codeConsistencyFail,
               bit 15 = configConsistencyFail"
   ::= {fr1645v2AlarmEntry 67108864}

fr1645v2AlarmLevNotResponding OBJECT-TYPE
   SYNTAX      Integer32
   MAX-ACCESS  read-only
   STATUS      current
   DESCRIPTION
      "Path: router1645.alarms.alarmInfo.alarmLevel.notResponding"
   ::= {fr1645v2AlarmEntry 83951616}

fr1645v2AlarmLevSyncLoss OBJECT-TYPE
   SYNTAX      Integer32
   MAX-ACCESS  read-only
   STATUS      current
   DESCRIPTION
      "Path: router1645.alarms.alarmInfo.alarmLevel.alarmSyncLoss"
   ::= {fr1645v2AlarmEntry 84017152}

fr1645v2AlarmLevConfigChanged OBJECT-TYPE
   SYNTAX      Integer32
   MAX-ACCESS  read-only
   STATUS      current
   DESCRIPTION
      "Path: router1645.alarms.alarmInfo.alarmLevel.configChanged"
   ::= {fr1645v2AlarmEntry 84082688}

fr1645v2AlarmLevAccess OBJECT-TYPE
   SYNTAX      Integer32
   MAX-ACCESS  read-only
   STATUS      current
   DESCRIPTION
      "Path: router1645.alarms.alarmInfo.alarmLevel.access"
   ::= {fr1645v2AlarmEntry 84148224}

fr1645v2AlarmLevPowerSupplyFail OBJECT-TYPE
   SYNTAX      Integer32
   MAX-ACCESS  read-only
   STATUS      current
   DESCRIPTION
      "Path: router1645.alarms.alarmInfo.alarmLevel.powerSupplyFail"
   ::= {fr1645v2AlarmEntry 84213760}

fr1645v2AlarmLevPowerSupplyProblem OBJECT-TYPE
   SYNTAX      Integer32
   MAX-ACCESS  read-only
   STATUS      current
   DESCRIPTION
      "Path: router1645.alarms.alarmInfo.alarmLevel.powerSupplyProblem"
   ::= {fr1645v2AlarmEntry 84279296}

fr1645v2AlarmLevUnknownState OBJECT-TYPE
   SYNTAX      Integer32
   MAX-ACCESS  read-only
   STATUS      current
   DESCRIPTION
      "Path: router1645.alarms.alarmInfo.alarmLevel.unknownState"
   ::= {fr1645v2AlarmEntry 84475904}

fr1645v2AlarmLevColdBoot OBJECT-TYPE
   SYNTAX      Integer32
   MAX-ACCESS  read-only
   STATUS      current
   DESCRIPTION
      "Path: router1645.alarms.alarmInfo.alarmLevel.coldBoot"
   ::= {fr1645v2AlarmEntry 84541440}

fr1645v2AlarmLevWarmBoot OBJECT-TYPE
   SYNTAX      Integer32
   MAX-ACCESS  read-only
   STATUS      current
   DESCRIPTION
      "Path: router1645.alarms.alarmInfo.alarmLevel.warmBoot"
   ::= {fr1645v2AlarmEntry 84606976}

fr1645v2AlarmLevCodeFallback OBJECT-TYPE
   SYNTAX      Integer32
   MAX-ACCESS  read-only
   STATUS      current
   DESCRIPTION
      "Path: router1645.alarms.alarmInfo.alarmLevel.codeFallback"
   ::= {fr1645v2AlarmEntry 84738048}

fr1645v2AlarmLevConfigFallback OBJECT-TYPE
   SYNTAX      Integer32
   MAX-ACCESS  read-only
   STATUS      current
   DESCRIPTION
      "Path: router1645.alarms.alarmInfo.alarmLevel.configFallback"
   ::= {fr1645v2AlarmEntry 84803584}

fr1645v2AlarmLevCdeConsFl OBJECT-TYPE
   SYNTAX      Integer32
   MAX-ACCESS  read-only
   STATUS      current
   DESCRIPTION
      "Path: router1645.alarms.alarmInfo.alarmLevel.codeConsistencyFail"
   ::= {fr1645v2AlarmEntry 84869120}

fr1645v2AlarmLevCnfConsFl OBJECT-TYPE
   SYNTAX      Integer32
   MAX-ACCESS  read-only
   STATUS      current
   DESCRIPTION
      "Path: router1645.alarms.alarmInfo.alarmLevel.configConsistencyFail"
   ::= {fr1645v2AlarmEntry 84934656}


fr1645v2AlarmE2 OBJECT IDENTIFIER ::= {fr1645v2Alarm 2}

fr1645v2AlarmE2Entry OBJECT IDENTIFIER ::= {fr1645v2AlarmE2 1}

fr1645v2AlarmE2NotResponding OBJECT IDENTIFIER ::= {fr1645v2AlarmE2Entry 10}

fr1645v2AlarmE2NotRespondingPfx OBJECT IDENTIFIER ::= {fr1645v2AlarmE2NotResponding 0}

fr1645v2AlarmE2NotRespondingOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'notResponding'
                representing an alarm condition in the alarm word
                of attribute 'alarmInfo' of managed object 'router1645'
                (root='router1645') has changed from the ON to the OFF state."
   ::= {fr1645v2AlarmE2NotRespondingPfx 1}

fr1645v2AlarmE2NotRespondingOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'notResponding'
                representing an alarm condition in the alarm word
                of attribute 'alarmInfo' of managed object 'router1645'
                (root='router1645') has changed from the OFF to the ON state."
   ::= {fr1645v2AlarmE2NotRespondingPfx 2}

fr1645v2AlarmE2SyncLoss OBJECT IDENTIFIER ::= {fr1645v2AlarmE2Entry 11}

fr1645v2AlarmE2SyncLossPfx OBJECT IDENTIFIER ::= {fr1645v2AlarmE2SyncLoss 0}

fr1645v2AlarmE2SyncLossOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'alarmSyncLoss'
                representing an alarm condition in the alarm word
                of attribute 'alarmInfo' of managed object 'router1645'
                (root='router1645') has changed from the ON to the OFF state."
   ::= {fr1645v2AlarmE2SyncLossPfx 1}

fr1645v2AlarmE2SyncLossOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'alarmSyncLoss'
                representing an alarm condition in the alarm word
                of attribute 'alarmInfo' of managed object 'router1645'
                (root='router1645') has changed from the OFF to the ON state."
   ::= {fr1645v2AlarmE2SyncLossPfx 2}

fr1645v2AlarmE2ConfigChanged OBJECT IDENTIFIER ::= {fr1645v2AlarmE2Entry 12}

fr1645v2AlarmE2ConfigChangedPfx OBJECT IDENTIFIER ::= {fr1645v2AlarmE2ConfigChanged 0}

fr1645v2AlarmE2ConfigChangedOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'configChanged'
                representing an alarm condition in the alarm word
                of attribute 'alarmInfo' of managed object 'router1645'
                (root='router1645') has changed from the ON to the OFF state."
   ::= {fr1645v2AlarmE2ConfigChangedPfx 1}

fr1645v2AlarmE2ConfigChangedOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'configChanged'
                representing an alarm condition in the alarm word
                of attribute 'alarmInfo' of managed object 'router1645'
                (root='router1645') has changed from the OFF to the ON state."
   ::= {fr1645v2AlarmE2ConfigChangedPfx 2}

fr1645v2AlarmE2Access OBJECT IDENTIFIER ::= {fr1645v2AlarmE2Entry 13}

fr1645v2AlarmE2AccessPfx OBJECT IDENTIFIER ::= {fr1645v2AlarmE2Access 0}

fr1645v2AlarmE2AccessOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'access'
                representing an alarm condition in the alarm word
                of attribute 'alarmInfo' of managed object 'router1645'
                (root='router1645') has changed from the ON to the OFF state."
   ::= {fr1645v2AlarmE2AccessPfx 1}

fr1645v2AlarmE2AccessOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'access'
                representing an alarm condition in the alarm word
                of attribute 'alarmInfo' of managed object 'router1645'
                (root='router1645') has changed from the OFF to the ON state."
   ::= {fr1645v2AlarmE2AccessPfx 2}

fr1645v2AlarmE2PowerSupplyFail OBJECT IDENTIFIER ::= {fr1645v2AlarmE2Entry 14}

fr1645v2AlarmE2PowerSupplyFailPfx OBJECT IDENTIFIER ::= {fr1645v2AlarmE2PowerSupplyFail 0}

fr1645v2AlarmE2PowerSupplyFailOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'powerSupplyFail'
                representing an alarm condition in the alarm word
                of attribute 'alarmInfo' of managed object 'router1645'
                (root='router1645') has changed from the ON to the OFF state."
   ::= {fr1645v2AlarmE2PowerSupplyFailPfx 1}

fr1645v2AlarmE2PowerSupplyFailOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'powerSupplyFail'
                representing an alarm condition in the alarm word
                of attribute 'alarmInfo' of managed object 'router1645'
                (root='router1645') has changed from the OFF to the ON state."
   ::= {fr1645v2AlarmE2PowerSupplyFailPfx 2}

fr1645v2AlarmE2PowerSupplyProblem OBJECT IDENTIFIER ::= {fr1645v2AlarmE2Entry 15}

fr1645v2AlarmE2PowerSupplyProblemPfx OBJECT IDENTIFIER ::= {fr1645v2AlarmE2PowerSupplyProblem 0}

fr1645v2AlarmE2PowerSupplyProblemOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'powerSupplyProblem'
                representing an alarm condition in the alarm word
                of attribute 'alarmInfo' of managed object 'router1645'
                (root='router1645') has changed from the ON to the OFF state."
   ::= {fr1645v2AlarmE2PowerSupplyProblemPfx 1}

fr1645v2AlarmE2PowerSupplyProblemOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'powerSupplyProblem'
                representing an alarm condition in the alarm word
                of attribute 'alarmInfo' of managed object 'router1645'
                (root='router1645') has changed from the OFF to the ON state."
   ::= {fr1645v2AlarmE2PowerSupplyProblemPfx 2}

fr1645v2AlarmE2UnknownState OBJECT IDENTIFIER ::= {fr1645v2AlarmE2Entry 18}

fr1645v2AlarmE2UnknownStatePfx OBJECT IDENTIFIER ::= {fr1645v2AlarmE2UnknownState 0}

fr1645v2AlarmE2UnknownStateOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unknownState'
                representing an alarm condition in the alarm word
                of attribute 'alarmInfo' of managed object 'router1645'
                (root='router1645') has changed from the ON to the OFF state."
   ::= {fr1645v2AlarmE2UnknownStatePfx 1}

fr1645v2AlarmE2UnknownStateOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'unknownState'
                representing an alarm condition in the alarm word
                of attribute 'alarmInfo' of managed object 'router1645'
                (root='router1645') has changed from the OFF to the ON state."
   ::= {fr1645v2AlarmE2UnknownStatePfx 2}

fr1645v2AlarmE2ColdBoot OBJECT IDENTIFIER ::= {fr1645v2AlarmE2Entry 19}

fr1645v2AlarmE2ColdBootPfx OBJECT IDENTIFIER ::= {fr1645v2AlarmE2ColdBoot 0}

fr1645v2AlarmE2ColdBootOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'coldBoot'
                representing an alarm condition in the alarm word
                of attribute 'alarmInfo' of managed object 'router1645'
                (root='router1645') has changed from the ON to the OFF state."
   ::= {fr1645v2AlarmE2ColdBootPfx 1}

fr1645v2AlarmE2ColdBootOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'coldBoot'
                representing an alarm condition in the alarm word
                of attribute 'alarmInfo' of managed object 'router1645'
                (root='router1645') has changed from the OFF to the ON state."
   ::= {fr1645v2AlarmE2ColdBootPfx 2}

fr1645v2AlarmE2WarmBoot OBJECT IDENTIFIER ::= {fr1645v2AlarmE2Entry 20}

fr1645v2AlarmE2WarmBootPfx OBJECT IDENTIFIER ::= {fr1645v2AlarmE2WarmBoot 0}

fr1645v2AlarmE2WarmBootOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'warmBoot'
                representing an alarm condition in the alarm word
                of attribute 'alarmInfo' of managed object 'router1645'
                (root='router1645') has changed from the ON to the OFF state."
   ::= {fr1645v2AlarmE2WarmBootPfx 1}

fr1645v2AlarmE2WarmBootOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'warmBoot'
                representing an alarm condition in the alarm word
                of attribute 'alarmInfo' of managed object 'router1645'
                (root='router1645') has changed from the OFF to the ON state."
   ::= {fr1645v2AlarmE2WarmBootPfx 2}

fr1645v2AlarmE2CodeFallback OBJECT IDENTIFIER ::= {fr1645v2AlarmE2Entry 22}

fr1645v2AlarmE2CodeFallbackPfx OBJECT IDENTIFIER ::= {fr1645v2AlarmE2CodeFallback 0}

fr1645v2AlarmE2CodeFallbackOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'codeFallback'
                representing an alarm condition in the alarm word
                of attribute 'alarmInfo' of managed object 'router1645'
                (root='router1645') has changed from the ON to the OFF state."
   ::= {fr1645v2AlarmE2CodeFallbackPfx 1}

fr1645v2AlarmE2CodeFallbackOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'codeFallback'
                representing an alarm condition in the alarm word
                of attribute 'alarmInfo' of managed object 'router1645'
                (root='router1645') has changed from the OFF to the ON state."
   ::= {fr1645v2AlarmE2CodeFallbackPfx 2}

fr1645v2AlarmE2ConfigFallback OBJECT IDENTIFIER ::= {fr1645v2AlarmE2Entry 23}

fr1645v2AlarmE2ConfigFallbackPfx OBJECT IDENTIFIER ::= {fr1645v2AlarmE2ConfigFallback 0}

fr1645v2AlarmE2ConfigFallbackOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'configFallback'
                representing an alarm condition in the alarm word
                of attribute 'alarmInfo' of managed object 'router1645'
                (root='router1645') has changed from the ON to the OFF state."
   ::= {fr1645v2AlarmE2ConfigFallbackPfx 1}

fr1645v2AlarmE2ConfigFallbackOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'configFallback'
                representing an alarm condition in the alarm word
                of attribute 'alarmInfo' of managed object 'router1645'
                (root='router1645') has changed from the OFF to the ON state."
   ::= {fr1645v2AlarmE2ConfigFallbackPfx 2}

fr1645v2AlarmE2CdeConsFl OBJECT IDENTIFIER ::= {fr1645v2AlarmE2Entry 24}

fr1645v2AlarmE2CdeConsFlPfx OBJECT IDENTIFIER ::= {fr1645v2AlarmE2CdeConsFl 0}

fr1645v2AlarmE2CdeConsFlOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'codeConsistencyFail'
                representing an alarm condition in the alarm word
                of attribute 'alarmInfo' of managed object 'router1645'
                (root='router1645') has changed from the ON to the OFF state."
   ::= {fr1645v2AlarmE2CdeConsFlPfx 1}

fr1645v2AlarmE2CdeConsFlOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'codeConsistencyFail'
                representing an alarm condition in the alarm word
                of attribute 'alarmInfo' of managed object 'router1645'
                (root='router1645') has changed from the OFF to the ON state."
   ::= {fr1645v2AlarmE2CdeConsFlPfx 2}

fr1645v2AlarmE2CnfConsFl OBJECT IDENTIFIER ::= {fr1645v2AlarmE2Entry 25}

fr1645v2AlarmE2CnfConsFlPfx OBJECT IDENTIFIER ::= {fr1645v2AlarmE2CnfConsFl 0}

fr1645v2AlarmE2CnfConsFlOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'configConsistencyFail'
                representing an alarm condition in the alarm word
                of attribute 'alarmInfo' of managed object 'router1645'
                (root='router1645') has changed from the ON to the OFF state."
   ::= {fr1645v2AlarmE2CnfConsFlPfx 1}

fr1645v2AlarmE2CnfConsFlOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'configConsistencyFail'
                representing an alarm condition in the alarm word
                of attribute 'alarmInfo' of managed object 'router1645'
                (root='router1645') has changed from the OFF to the ON state."
   ::= {fr1645v2AlarmE2CnfConsFlPfx 2}



ar1645v2 OBJECT IDENTIFIER ::= {r1645v2 16}


ar1645v2LoadConfigFile OBJECT-TYPE
   SYNTAX      Integer32
   MAX-ACCESS  read-write
   STATUS      current
   DESCRIPTION
      "Path: router1645.actions.loadConfigFile
       Info: loadSavedConf"
   ::= {ar1645v2 276}


ar1645v2File OBJECT-TYPE
   SYNTAX      DisplayString
   MAX-ACCESS  read-write
   STATUS      current
   DESCRIPTION
      "Path: router1645.actions.file
       Info: filename"
   ::= {ar1645v2 277}


ar1645v2ClearAllCounters OBJECT-TYPE
   SYNTAX      Integer32
   MAX-ACCESS  read-write
   STATUS      current
   DESCRIPTION
      "Path: router1645.actions.clearAllCounters
       Info: reset counters"
   ::= {ar1645v2 266}


ar1645v2SaveEditDbase OBJECT-TYPE
   SYNTAX      Integer32
   MAX-ACCESS  read-write
   STATUS      current
   DESCRIPTION
      "Path: router1645.actions.saveEditDbase
       Info: saveEditDbase"
   ::= {ar1645v2 158}


ar1645v2ClearDbase OBJECT-TYPE
   SYNTAX      Integer32
   MAX-ACCESS  read-write
   STATUS      current
   DESCRIPTION
      "Path: router1645.actions.clearDbase
       Info: clearDbase"
   ::= {ar1645v2 157}


ar1645v2ColdBoot OBJECT-TYPE
   SYNTAX      Integer32
   MAX-ACCESS  read-write
   STATUS      current
   DESCRIPTION
      "Path: router1645.actions.coldBoot
       Info: coldBoot"
   ::= {ar1645v2 153}


ar1645v2LoadDefConfig OBJECT-TYPE
   SYNTAX      Integer32
   MAX-ACCESS  read-write
   STATUS      current
   DESCRIPTION
      "Path: router1645.actions.loadDefConfig
       Info: loadDefConf"
   ::= {ar1645v2 152}


ar1645v2LoadSavedConfig OBJECT-TYPE
   SYNTAX      Integer32
   MAX-ACCESS  read-write
   STATUS      current
   DESCRIPTION
      "Path: router1645.actions.loadSavedConfig
       Info: loadSavedConf"
   ::= {ar1645v2 151}


ar1645v2Config OBJECT-TYPE
   SYNTAX      INTEGER
               {
               current (0),
               previous (1)
               }
   MAX-ACCESS  read-write
   STATUS      current
   DESCRIPTION
      "Path: router1645.actions.config
       Info: data for load saved config

       Possibilities:
               current   (0)
               previous   (1)"
   ::= {ar1645v2 275}


ar1645v2AcceptConfiguration OBJECT-TYPE
   SYNTAX      Integer32
   MAX-ACCESS  read-write
   STATUS      current
   DESCRIPTION
      "Path: router1645.actions.acceptConfiguration
       Info: Action Accept Configuration"
   ::= {ar1645v2 274}


ar1645v2ActivateConfig OBJECT-TYPE
   SYNTAX      Integer32
   MAX-ACCESS  read-write
   STATUS      current
   DESCRIPTION
      "Path: router1645.actions.activateConfig
       Info: activateConf"
   ::= {ar1645v2 150}


ar1645v2SaveType OBJECT IDENTIFIER ::= {ar1645v2 273}

ar1645v2SaveTypeSSC OBJECT IDENTIFIER ::= {ar1645v2SaveType 1}

ar1645v2SaveTypeEntry OBJECT IDENTIFIER ::= {ar1645v2SaveTypeSSC 1}

ar1645v2SaveTypeNormal OBJECT-TYPE
   SYNTAX      OCTET STRING
   MAX-ACCESS  read-write
   STATUS      current
   DESCRIPTION
      "Path: router1645.actions.saveType.normal"
   ::= {ar1645v2SaveTypeEntry 16777216}

ar1645v2SaveTypeImmediate OBJECT-TYPE
   SYNTAX      OCTET STRING
   MAX-ACCESS  read-write
   STATUS      current
   DESCRIPTION
      "Path: router1645.actions.saveType.immediate"
   ::= {ar1645v2SaveTypeEntry 50331648}

ar1645v2SaveTypeWaitUserAck OBJECT-TYPE
   SYNTAX      TimeTicks
   MAX-ACCESS  read-write
   STATUS      current
   DESCRIPTION
      "Path: router1645.actions.saveType.waitUserAck

       Time in centi-second."
   ::= {ar1645v2SaveTypeEntry 33554432}


ar1645v2EraseDebugTable OBJECT-TYPE
   SYNTAX      Integer32
   MAX-ACCESS  read-write
   STATUS      current
   DESCRIPTION
      "Path: router1645.actions.eraseDebugTable
       Info: action in the debug group"
   ::= {ar1645v2 620}


ar1645v2DebugMaskAction OBJECT-TYPE
   SYNTAX      Integer32
   MAX-ACCESS  read-write
   STATUS      current
   DESCRIPTION
      "Path: router1645.actions.debugMaskAction
       Info: action in the debug group"
   ::= {ar1645v2 616}


ar1645v2DebugMaskValue OBJECT-TYPE
   SYNTAX      Integer32
   MAX-ACCESS  read-write
   STATUS      current
   DESCRIPTION
      "Path: router1645.actions.debugMaskValue

       Bit meanings:
               bit 0 = modelUpload,
               bit 1 = alarmSynchronisation,
               bit 2 = o10,
               bit 3 = inventory,
               bit 4 = alarmGeneration,
               bit 5 = autoDiscovery,
               bit 6 = ip,
               bit 7 = ima,
               bit 8 = modemDsp"
   ::= {ar1645v2 617}


ar1645v2CloseSessions OBJECT-TYPE
   SYNTAX      Integer32
   MAX-ACCESS  read-write
   STATUS      current
   DESCRIPTION
      "Path: router1645.actions.closeSessions
       Info: action in the debug group"
   ::= {ar1645v2 614}


ar1645v2CloseTraceLogFile OBJECT-TYPE
   SYNTAX      Integer32
   MAX-ACCESS  read-write
   STATUS      current
   DESCRIPTION
      "Path: router1645.actions.closeTraceLogFile
       Info: close the trace log file"
   ::= {ar1645v2 283}


ar1645v2ClearTraceMessages OBJECT-TYPE
   SYNTAX      Integer32
   MAX-ACCESS  read-write
   STATUS      current
   DESCRIPTION
      "Path: router1645.actions.clearTraceMessages
       Info: clear trace message table"
   ::= {ar1645v2 272}


ar1645v2CancelLoadConfig OBJECT-TYPE
   SYNTAX      Integer32
   MAX-ACCESS  read-write
   STATUS      current
   DESCRIPTION
      "Path: router1645.actions.cancelLoadConfig
       Info: cancel of a running scheduled load config action"
   ::= {ar1645v2 280}


ar1645v2ScheduleLoad OBJECT-TYPE
   SYNTAX      Integer32
   MAX-ACCESS  read-write
   STATUS      current
   DESCRIPTION
      "Path: router1645.actions.scheduleLoad
       Info: start scheduled load of new configuration"
   ::= {ar1645v2 278}


ar1645v2Load OBJECT IDENTIFIER ::= {ar1645v2 279}

ar1645v2LoadSSC OBJECT IDENTIFIER ::= {ar1645v2Load 1}

ar1645v2LoadEntry OBJECT IDENTIFIER ::= {ar1645v2LoadSSC 1}

ar1645v2LoadTimeTimeOut OBJECT-TYPE
   SYNTAX      TimeTicks
   MAX-ACCESS  read-write
   STATUS      current
   DESCRIPTION
      "Path: router1645.actions.load.time.timeOut

       Time in centi-second."
   ::= {ar1645v2LoadEntry 16842752}

ar1645v2LoadTimeTimeHour OBJECT-TYPE
   SYNTAX      Integer32
   MAX-ACCESS  read-write
   STATUS      current
   DESCRIPTION
      "Path: router1645.actions.load.time.time.hour"
   ::= {ar1645v2LoadEntry 16909312}

ar1645v2LoadTimeTimeMinute OBJECT-TYPE
   SYNTAX      Integer32
   MAX-ACCESS  read-write
   STATUS      current
   DESCRIPTION
      "Path: router1645.actions.load.time.time.minute"
   ::= {ar1645v2LoadEntry 16909568}

ar1645v2LoadTimeDateTimeYear OBJECT-TYPE
   SYNTAX      Integer32
   MAX-ACCESS  read-write
   STATUS      current
   DESCRIPTION
      "Path: router1645.actions.load.time.dateTime.year"
   ::= {ar1645v2LoadEntry 16974080}

ar1645v2LoadTimeDateTimeMonth OBJECT-TYPE
   SYNTAX      Integer32
   MAX-ACCESS  read-write
   STATUS      current
   DESCRIPTION
      "Path: router1645.actions.load.time.dateTime.month"
   ::= {ar1645v2LoadEntry 16974336}

ar1645v2LoadTimeDateTimeDay OBJECT-TYPE
   SYNTAX      Integer32
   MAX-ACCESS  read-write
   STATUS      current
   DESCRIPTION
      "Path: router1645.actions.load.time.dateTime.day"
   ::= {ar1645v2LoadEntry 16974592}

ar1645v2LoadTimeDateTimeHour OBJECT-TYPE
   SYNTAX      Integer32
   MAX-ACCESS  read-write
   STATUS      current
   DESCRIPTION
      "Path: router1645.actions.load.time.dateTime.hour"
   ::= {ar1645v2LoadEntry 16974848}

ar1645v2LoadTimeDateTimeMinute OBJECT-TYPE
   SYNTAX      Integer32
   MAX-ACCESS  read-write
   STATUS      current
   DESCRIPTION
      "Path: router1645.actions.load.time.dateTime.minute"
   ::= {ar1645v2LoadEntry 16975104}

ar1645v2LoadFile OBJECT-TYPE
   SYNTAX      DisplayString
   MAX-ACCESS  read-write
   STATUS      current
   DESCRIPTION
      "Path: router1645.actions.load.file"
   ::= {ar1645v2LoadEntry 33554432}

ar1645v2LoadPreColdBoot OBJECT-TYPE
   SYNTAX      INTEGER
               {
               no (1),
               yes (2)
               }
   MAX-ACCESS  read-write
   STATUS      current
   DESCRIPTION
      "Path: router1645.actions.load.preColdBoot

       Possibilities:
               no   (1)
               yes   (2)"
   ::= {ar1645v2LoadEntry 50331648}

ar1645v2LoadPostColdBoot OBJECT-TYPE
   SYNTAX      INTEGER
               {
               no (1),
               yes (2)
               }
   MAX-ACCESS  read-write
   STATUS      current
   DESCRIPTION
      "Path: router1645.actions.load.postColdBoot

       Possibilities:
               no   (1)
               yes   (2)"
   ::= {ar1645v2LoadEntry 67108864}

ar1645v2LoadStabilityTime OBJECT-TYPE
   SYNTAX      TimeTicks
   MAX-ACCESS  read-write
   STATUS      current
   DESCRIPTION
      "Path: router1645.actions.load.stabilityTime

       Time in centi-second."
   ::= {ar1645v2LoadEntry 117440512}

ar1645v2LoadTimeBeforeTest OBJECT-TYPE
   SYNTAX      TimeTicks
   MAX-ACCESS  read-write
   STATUS      current
   DESCRIPTION
      "Path: router1645.actions.load.timeBeforeTest

       Time in centi-second."
   ::= {ar1645v2LoadEntry 100663296}

ar1645v2LoadIcmpTestDestination OBJECT-TYPE
   SYNTAX      DisplayString
   MAX-ACCESS  read-write
   STATUS      current
   DESCRIPTION
      "Path: router1645.actions.load.icmpTest.destination"
   ::= {ar1645v2LoadEntry 83951616}

ar1645v2LoadIcmpTestDuration OBJECT-TYPE
   SYNTAX      TimeTicks
   MAX-ACCESS  read-write
   STATUS      current
   DESCRIPTION
      "Path: router1645.actions.load.icmpTest.duration

       Time in centi-second."
   ::= {ar1645v2LoadEntry 84017152}

ar1645v2LoadIcmpTestInterval OBJECT-TYPE
   SYNTAX      Integer32
   MAX-ACCESS  read-write
   STATUS      current
   DESCRIPTION
      "Path: router1645.actions.load.icmpTest.interval

       unit name = sec
       formula = 10 / ; 10 *"
   ::= {ar1645v2LoadEntry 84213760}

ar1645v2LoadIcmpTestTimeOut OBJECT-TYPE
   SYNTAX      Integer32
   UNITS       "sec"
   MAX-ACCESS  read-write
   STATUS      current
   DESCRIPTION
      "Path: router1645.actions.load.icmpTest.timeOut

       unit name = sec"
   ::= {ar1645v2LoadEntry 84082688}

ar1645v2LoadIcmpTestLossThreshold OBJECT-TYPE
   SYNTAX      Integer32
   UNITS       "%"
   MAX-ACCESS  read-write
   STATUS      current
   DESCRIPTION
      "Path: router1645.actions.load.icmpTest.lossThreshold

       unit name = %"
   ::= {ar1645v2LoadEntry 84148224}

ar1645v2LoadIcmpTestDelayThreshold OBJECT-TYPE
   SYNTAX      Integer32
   UNITS       "msec"
   MAX-ACCESS  read-write
   STATUS      current
   DESCRIPTION
      "Path: router1645.actions.load.icmpTest.delayThreshold

       unit name = msec"
   ::= {ar1645v2LoadEntry 84279296}


ar1645v2ToggleFlash OBJECT-TYPE
   SYNTAX      Integer32
   MAX-ACCESS  read-write
   STATUS      current
   DESCRIPTION
      "Path: router1645.actions.toggleFlash
       Info: cancel of a running scheduled reboot action"
   ::= {ar1645v2 166}


ar1645v2CancelReboot OBJECT-TYPE
   SYNTAX      Integer32
   MAX-ACCESS  read-write
   STATUS      current
   DESCRIPTION
      "Path: router1645.actions.cancelReboot
       Info: cancel of a running scheduled reboot action"
   ::= {ar1645v2 165}


ar1645v2ScheduleReboot OBJECT-TYPE
   SYNTAX      Integer32
   MAX-ACCESS  read-write
   STATUS      current
   DESCRIPTION
      "Path: router1645.actions.scheduleReboot
       Info: start scheduled reboot"
   ::= {ar1645v2 163}


ar1645v2TimeToReboot OBJECT IDENTIFIER ::= {ar1645v2 164}

ar1645v2TimeToRebootSSC OBJECT IDENTIFIER ::= {ar1645v2TimeToReboot 1}

ar1645v2TimeToRebootEntry OBJECT IDENTIFIER ::= {ar1645v2TimeToRebootSSC 1}

ar1645v2TimeToRebootTimeOut OBJECT-TYPE
   SYNTAX      TimeTicks
   MAX-ACCESS  read-write
   STATUS      current
   DESCRIPTION
      "Path: router1645.actions.timeToReboot.timeOut

       Time in centi-second."
   ::= {ar1645v2TimeToRebootEntry 16777216}

ar1645v2TimeToRebootTimeHour OBJECT-TYPE
   SYNTAX      Integer32
   MAX-ACCESS  read-write
   STATUS      current
   DESCRIPTION
      "Path: router1645.actions.timeToReboot.time.hour"
   ::= {ar1645v2TimeToRebootEntry 33816576}

ar1645v2TimeToRebootTimeMinute OBJECT-TYPE
   SYNTAX      Integer32
   MAX-ACCESS  read-write
   STATUS      current
   DESCRIPTION
      "Path: router1645.actions.timeToReboot.time.minute"
   ::= {ar1645v2TimeToRebootEntry 33882112}

ar1645v2TimeToRebootDateTimeYear OBJECT-TYPE
   SYNTAX      Integer32
   MAX-ACCESS  read-write
   STATUS      current
   DESCRIPTION
      "Path: router1645.actions.timeToReboot.dateTime.year"
   ::= {ar1645v2TimeToRebootEntry 50397184}

ar1645v2TimeToRebootDateTimeMonth OBJECT-TYPE
   SYNTAX      Integer32
   MAX-ACCESS  read-write
   STATUS      current
   DESCRIPTION
      "Path: router1645.actions.timeToReboot.dateTime.month"
   ::= {ar1645v2TimeToRebootEntry 50462720}

ar1645v2TimeToRebootDateTimeDay OBJECT-TYPE
   SYNTAX      Integer32
   MAX-ACCESS  read-write
   STATUS      current
   DESCRIPTION
      "Path: router1645.actions.timeToReboot.dateTime.day"
   ::= {ar1645v2TimeToRebootEntry 50528256}

ar1645v2TimeToRebootDateTimeHour OBJECT-TYPE
   SYNTAX      Integer32
   MAX-ACCESS  read-write
   STATUS      current
   DESCRIPTION
      "Path: router1645.actions.timeToReboot.dateTime.hour"
   ::= {ar1645v2TimeToRebootEntry 50593792}

ar1645v2TimeToRebootDateTimeMinute OBJECT-TYPE
   SYNTAX      Integer32
   MAX-ACCESS  read-write
   STATUS      current
   DESCRIPTION
      "Path: router1645.actions.timeToReboot.dateTime.minute"
   ::= {ar1645v2TimeToRebootEntry 50659328}


ar1645v2SetTime OBJECT-TYPE
   SYNTAX      Integer32
   MAX-ACCESS  read-write
   STATUS      current
   DESCRIPTION
      "Path: router1645.actions.setTime
       Info: set time"
   ::= {ar1645v2 52}


ar1645v2Time OBJECT-TYPE
   SYNTAX      DisplayString
   MAX-ACCESS  read-write
   STATUS      current
   DESCRIPTION
      "Path: router1645.actions.time
       Info: time"
   ::= {ar1645v2 53}


ar1645v2SetDate OBJECT-TYPE
   SYNTAX      Integer32
   MAX-ACCESS  read-write
   STATUS      current
   DESCRIPTION
      "Path: router1645.actions.setDate
       Info: set date"
   ::= {ar1645v2 50}


ar1645v2Date OBJECT-TYPE
   SYNTAX      DisplayString
   MAX-ACCESS  read-write
   STATUS      current
   DESCRIPTION
      "Path: router1645.actions.date
       Info: date"
   ::= {ar1645v2 51}


ar1645v2LoadPreconf OBJECT-TYPE
   SYNTAX      Integer32
   MAX-ACCESS  read-write
   STATUS      current
   DESCRIPTION
      "Path: router1645.actions.loadPreconf
       Info: loadPreconf"
   ::= {ar1645v2 159}


ar1645v2HwaAction4 OBJECT-TYPE
   SYNTAX      Integer32
   MAX-ACCESS  read-write
   STATUS      current
   DESCRIPTION
      "Path: router1645.actions.hwaAction4
       Info: action in the debug group"
   ::= {ar1645v2 660}


ar1645v2HwaAction3 OBJECT-TYPE
   SYNTAX      Integer32
   MAX-ACCESS  read-write
   STATUS      current
   DESCRIPTION
      "Path: router1645.actions.hwaAction3
       Info: action in the debug group"
   ::= {ar1645v2 657}


ar1645v2HwaAction2 OBJECT-TYPE
   SYNTAX      Integer32
   MAX-ACCESS  read-write
   STATUS      current
   DESCRIPTION
      "Path: router1645.actions.hwaAction2
       Info: action in the debug group"
   ::= {ar1645v2 652}


ar1645v2HwaAction OBJECT-TYPE
   SYNTAX      Integer32
   MAX-ACCESS  read-write
   STATUS      current
   DESCRIPTION
      "Path: router1645.actions.hwaAction
       Info: action in the debug group"
   ::= {ar1645v2 651}



pr1645v2 OBJECT IDENTIFIER ::= {r1645v2 12}


pr1645v2Interfaces OBJECT IDENTIFIER ::= {pr1645v2 284}

pr1645v2InterfacesSSCTable OBJECT-TYPE
   SYNTAX      SEQUENCE OF Pr1645v2InterfacesEntry
   MAX-ACCESS  not-accessible
   STATUS      current
   DESCRIPTION
      "list of all interface manager interfaces"
   ::= {pr1645v2Interfaces 1}

pr1645v2InterfacesEntry OBJECT-TYPE
   SYNTAX      Pr1645v2InterfacesEntry
   MAX-ACCESS  not-accessible
   STATUS      current
   DESCRIPTION
      ""
   INDEX      { pr1645v2InterfacesTableIx }
   ::= {pr1645v2InterfacesSSCTable 1}

Pr1645v2InterfacesEntry ::=
   SEQUENCE
      {
      pr1645v2InterfacesTableIx
         TableIndex,
      pr1645v2InterfacesIfDescr
         DisplayString,
      pr1645v2InterfacesRemark
         DisplayString,
      pr1645v2InterfacesPath
         DisplayString,
      pr1645v2InterfacesParentIfDescr
         DisplayString,
      pr1645v2InterfacesEncapsulation
         INTEGER,
      pr1645v2InterfacesIfType
         INTEGER,
      pr1645v2InterfacesMode
         INTEGER,
      pr1645v2InterfacesIfAdminStatus
         INTEGER,
      pr1645v2InterfacesIfOperStatus
         INTEGER,
      pr1645v2InterfacesIfLastChange
         TimeTicks,
      pr1645v2InterfacesIfLastChangeDate
         DisplayString,
      pr1645v2InterfacesIfSpeed
         Gauge32,
      pr1645v2InterfacesIfIndex
         Integer32,
      pr1645v2InterfacesRowNumber
         Integer32,
      pr1645v2InterfacesMacAddress
         OCTET STRING,
      pr1645v2InterfacesIpVrfRouter
         DisplayString,
      pr1645v2InterfacesIpAddress
         IpAddress,
      pr1645v2InterfacesIpNetMask
         IpAddress,
      pr1645v2InterfacesMibCountersInOctets
         Counter64,
      pr1645v2InterfacesMibCountersInUcast
         Counter64,
      pr1645v2InterfacesMibCountersInNUcastPkts
         Counter64,
      pr1645v2InterfacesMibCountersInBcastPkts
         Counter64,
      pr1645v2InterfacesMibCountersInMcastPkts
         Counter64,
      pr1645v2InterfacesMibCountersInDiscards
         Counter64,
      pr1645v2InterfacesMibCountersInErrors
         Counter64,
      pr1645v2InterfacesMibCountersInUnknownProtos
         Counter64,
      pr1645v2InterfacesMibCountersInDropEx
         Counter64,
      pr1645v2InterfacesMibCountersInDropNoMac
         Counter64,
      pr1645v2InterfacesMibCountersInDropNUCast
         Counter64,
      pr1645v2InterfacesMibCountersInDropFilter
         Counter64,
      pr1645v2InterfacesMibCountersInBandwidth15sec
         Integer32,
      pr1645v2InterfacesMibCountersInBandwidth30sec
         Integer32,
      pr1645v2InterfacesMibCountersInBandwidth1min
         Integer32,
      pr1645v2InterfacesMibCountersInBandwidth2min
         Integer32,
      pr1645v2InterfacesMibCountersInBandwidth5min
         Integer32,
      pr1645v2InterfacesMibCountersOutOctets
         Counter64,
      pr1645v2InterfacesMibCountersOutUcastPkts
         Counter64,
      pr1645v2InterfacesMibCountersOutNUcastPkts
         Counter64,
      pr1645v2InterfacesMibCountersOutBcastPkts
         Counter64,
      pr1645v2InterfacesMibCountersOutMcastPkts
         Counter64,
      pr1645v2InterfacesMibCountersOutDiscards
         Counter64,
      pr1645v2InterfacesMibCountersOutErrors
         Counter64,
      pr1645v2InterfacesMibCountersOutQLen
         Counter32,
      pr1645v2InterfacesMibCountersOutDropEx
         Counter64,
      pr1645v2InterfacesMibCountersOutDropNoArp
         Counter64,
      pr1645v2InterfacesMibCountersOutDropFilter
         Counter64,
      pr1645v2InterfacesMibCountersOutBandwidth15sec
         Integer32,
      pr1645v2InterfacesMibCountersOutBandwidth30sec
         Integer32,
      pr1645v2InterfacesMibCountersOutBandwidth1min
         Integer32,
      pr1645v2InterfacesMibCountersOutBandwidth2min
         Integer32,
      pr1645v2InterfacesMibCountersOutBandwidth5min
         Integer32
      }

pr1645v2InterfacesTableIx OBJECT-TYPE
   SYNTAX      TableIndex
   MAX-ACCESS  not-accessible
   STATUS      current
   DESCRIPTION
      ""
   ::= {pr1645v2InterfacesEntry 11}

pr1645v2InterfacesIfDescr OBJECT-TYPE
   SYNTAX      DisplayString
   MAX-ACCESS  read-only
   STATUS      current
   DESCRIPTION
      "Path: router1645.performance.interfaces.ifDescr"
   ::= {pr1645v2InterfacesEntry 1694498816}

pr1645v2InterfacesRemark OBJECT-TYPE
   SYNTAX      DisplayString
   MAX-ACCESS  read-only
   STATUS      current
   DESCRIPTION
      "Path: router1645.performance.interfaces.remark"
   ::= {pr1645v2InterfacesEntry 167772160}

pr1645v2InterfacesPath OBJECT-TYPE
   SYNTAX      DisplayString
   MAX-ACCESS  read-only
   STATUS      current
   DESCRIPTION
      "Path: router1645.performance.interfaces.path"
   ::= {pr1645v2InterfacesEntry 83886080}

pr1645v2InterfacesParentIfDescr OBJECT-TYPE
   SYNTAX      DisplayString
   MAX-ACCESS  read-only
   STATUS      current
   DESCRIPTION
      "Path: router1645.performance.interfaces.parentIfDescr"
   ::= {pr1645v2InterfacesEntry 117440512}

pr1645v2InterfacesEncapsulation OBJECT-TYPE
   SYNTAX      INTEGER
               {
               none (0),
               ethernet (1),
               ethernetuvlan (2),
               pppuoverueth (3),
               ppp (4),
               framerelay (5),
               framerelayudlci (6),
               atm (7),
               atmuvci (8),
               hdlc (9),
               x25 (10),
               tunneluparent (11),
               dummyutunnel (12),
               l2tputunnel (13),
               bridgeugateway (14),
               loopback (15),
               multilink (16),
               multilinkuppp (17),
               mlufrf15 (18),
               mlufrf16 (19),
               mlufrf16udlci (20),
               g703uparent (21),
               pppuatmuvci (22),
               pppuethuatmuvci (23),
               isdn (24),
               ces (25),
               ima (26),
               imauvci (27),
               pppuimauvci (28),
               pppuethuimauvci (29),
               default (30),
               smppp (31),
               et (32),
               pppoeuinstance (33),
               bridgeuvlan (34),
               ethernetuvlan0 (35),
               tdmuparent (36),
               trafgen (37),
               greutunneludummy (38),
               greuipsecutunneludummy (39),
               greutunnel (40),
               atmuoam (41),
               ethernetuport (42),
               ctr (43),
               s6to4tunnels (44),
               ethernetubundle (45),
               pppudialmap (46),
               ethernetuvlanupppoe (47),
               qmiudialmap (48),
               usb (49),
               vxlan (50),
               vxlanudummy (51)
               }
   MAX-ACCESS  read-only
   STATUS      current
   DESCRIPTION
      "Path: router1645.performance.interfaces.encapsulation

       Possibilities:
               none   (0)
               ethernet   (1)
               ethernet_vlan   (2)
               ppp_over_eth   (3)
               ppp   (4)
               framerelay   (5)
               framerelay_dlci   (6)
               atm   (7)
               atm_vci   (8)
               hdlc   (9)
               x25   (10)
               tunnel_parent   (11)
               dummy_tunnel   (12)
               l2tp_tunnel   (13)
               bridge_gateway   (14)
               loopback   (15)
               multilink   (16)
               multilink_ppp   (17)
               ml_frf15   (18)
               ml_frf16   (19)
               ml_frf16_dlci   (20)
               g703_parent   (21)
               ppp_atm_vci   (22)
               ppp_eth_atm_vci   (23)
               isdn   (24)
               ces   (25)
               ima   (26)
               ima_vci   (27)
               ppp_ima_vci   (28)
               ppp_eth_ima_vci   (29)
               default   (30)
               smppp   (31)
               et   (32)
               pppoe_instance   (33)
               bridge_vlan   (34)
               ethernet_vlan0   (35)
               tdm_parent   (36)
               trafgen   (37)
               gre_tunnel_dummy   (38)
               gre_ipsec_tunnel_dummy   (39)
               gre_tunnel   (40)
               atm_oam   (41)
               ethernet_port   (42)
               ctr   (43)
               6to4tunnels   (44)
               ethernet_bundle   (45)
               ppp_dialmap   (46)
               ethernet_vlan_pppoe   (47)
               qmi_dialmap   (48)
               usb   (49)
               vxlan   (50)
               vxlan_dummy   (51)"
   ::= {pr1645v2InterfacesEntry 67108864}

pr1645v2InterfacesIfType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: router1645.performance.interfaces.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {pr1645v2InterfacesEntry 1711276032}

pr1645v2InterfacesMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: router1645.performance.interfaces.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {pr1645v2InterfacesEntry 335544320}

pr1645v2InterfacesIfAdminStatus OBJECT-TYPE
   SYNTAX      INTEGER
               {
               up (1),
               down (2),
               testing (3)
               }
   MAX-ACCESS  read-only
   STATUS      current
   DESCRIPTION
      "Path: router1645.performance.interfaces.ifAdminStatus

       Possibilities:
               up   (1)
               down   (2)
               testing   (3)"
   ::= {pr1645v2InterfacesEntry 1778384896}

pr1645v2InterfacesIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: router1645.performance.interfaces.ifOperStatus

       Possibilities:
               up   (1)
               down   (2)
               testing   (3)
               unknown   (4)
               dormant   (5)
               notPresent   (6)
               lowerLayerDown   (7)"
   ::= {pr1645v2InterfacesEntry 1795162112}

pr1645v2InterfacesIfLastChange OBJECT-TYPE
   SYNTAX      TimeTicks
   MAX-ACCESS  read-only
   STATUS      current
   DESCRIPTION
      "Path: router1645.performance.interfaces.ifLastChange

       Time in centi-second."
   ::= {pr1645v2InterfacesEntry 1811939328}

pr1645v2InterfacesIfLastChangeDate OBJECT-TYPE
   SYNTAX      DisplayString
   MAX-ACCESS  read-only
   STATUS      current
   DESCRIPTION
      "Path: router1645.performance.interfaces.ifLastChangeDate"
   ::= {pr1645v2InterfacesEntry 3070230528}

pr1645v2InterfacesIfSpeed OBJECT-TYPE
   SYNTAX      Gauge32
   MAX-ACCESS  read-only
   STATUS      current
   DESCRIPTION
      "Path: router1645.performance.interfaces.ifSpeed

       32 bit unsigned gauge value."
   ::= {pr1645v2InterfacesEntry 1744830464}

pr1645v2InterfacesIfIndex OBJECT-TYPE
   SYNTAX      Integer32
   MAX-ACCESS  read-only
   STATUS      current
   DESCRIPTION
      "Path: router1645.performance.interfaces.ifIndex"
   ::= {pr1645v2InterfacesEntry 1677721600}

pr1645v2InterfacesRowNumber OBJECT-TYPE
   SYNTAX      Integer32
   MAX-ACCESS  read-only
   STATUS      current
   DESCRIPTION
      "Path: router1645.performance.interfaces.rowNumber"
   ::= {pr1645v2InterfacesEntry 1660944384}

pr1645v2InterfacesMacAddress OBJECT-TYPE
   SYNTAX      OCTET STRING
   MAX-ACCESS  read-only
   STATUS      current
   DESCRIPTION
      "Path: router1645.performance.interfaces.macAddress

       MAC address."
   ::= {pr1645v2InterfacesEntry 1761607680}

pr1645v2InterfacesIpVrfRouter OBJECT-TYPE
   SYNTAX      DisplayString
   MAX-ACCESS  read-only
   STATUS      current
   DESCRIPTION
      "Path: router1645.performance.interfaces.ip.vrfRouter"
   ::= {pr1645v2InterfacesEntry 53215232}

pr1645v2InterfacesIpAddress OBJECT-TYPE
   SYNTAX      IpAddress
   MAX-ACCESS  read-only
   STATUS      current
   DESCRIPTION
      "Path: router1645.performance.interfaces.ip.address"
   ::= {pr1645v2InterfacesEntry 58261504}

pr1645v2InterfacesIpNetMask OBJECT-TYPE
   SYNTAX      IpAddress
   MAX-ACCESS  read-only
   STATUS      current
   DESCRIPTION
      "Path: router1645.performance.interfaces.ip.netMask"
   ::= {pr1645v2InterfacesEntry 58392576}

pr1645v2InterfacesMibCountersInOctets OBJECT-TYPE
   SYNTAX      Counter64
   MAX-ACCESS  read-only
   STATUS      current
   DESCRIPTION
      "Path: router1645.performance.interfaces.mibCounters.ifInOctets

       64 bit unsigned wrappable counter."
   ::= {pr1645v2InterfacesEntry 40697856}

pr1645v2InterfacesMibCountersInUcast OBJECT-TYPE
   SYNTAX      Counter64
   MAX-ACCESS  read-only
   STATUS      current
   DESCRIPTION
      "Path: router1645.performance.interfaces.mibCounters.ifInUcastPkts

       64 bit unsigned wrappable counter."
   ::= {pr1645v2InterfacesEntry 40763392}

pr1645v2InterfacesMibCountersInNUcastPkts OBJECT-TYPE
   SYNTAX      Counter64
   MAX-ACCESS  read-only
   STATUS      current
   DESCRIPTION
      "Path: router1645.performance.interfaces.mibCounters.ifInNUcastPkts

       64 bit unsigned wrappable counter."
   ::= {pr1645v2InterfacesEntry 40828928}

pr1645v2InterfacesMibCountersInBcastPkts OBJECT-TYPE
   SYNTAX      Counter64
   MAX-ACCESS  read-only
   STATUS      current
   DESCRIPTION
      "Path: router1645.performance.interfaces.mibCounters.ifInBcastPkts

       64 bit unsigned wrappable counter."
   ::= {pr1645v2InterfacesEntry 47382528}

pr1645v2InterfacesMibCountersInMcastPkts OBJECT-TYPE
   SYNTAX      Counter64
   MAX-ACCESS  read-only
   STATUS      current
   DESCRIPTION
      "Path: router1645.performance.interfaces.mibCounters.ifInMcastPkts

       64 bit unsigned wrappable counter."
   ::= {pr1645v2InterfacesEntry 48037888}

pr1645v2InterfacesMibCountersInDiscards OBJECT-TYPE
   SYNTAX      Counter64
   MAX-ACCESS  read-only
   STATUS      current
   DESCRIPTION
      "Path: router1645.performance.interfaces.mibCounters.ifInDiscards

       64 bit unsigned wrappable counter."
   ::= {pr1645v2InterfacesEntry 40894464}

pr1645v2InterfacesMibCountersInErrors OBJECT-TYPE
   SYNTAX      Counter64
   MAX-ACCESS  read-only
   STATUS      current
   DESCRIPTION
      "Path: router1645.performance.interfaces.mibCounters.ifInErrors

       64 bit unsigned wrappable counter."
   ::= {pr1645v2InterfacesEntry 40960000}

pr1645v2InterfacesMibCountersInUnknownProtos OBJECT-TYPE
   SYNTAX      Counter64
   MAX-ACCESS  read-only
   STATUS      current
   DESCRIPTION
      "Path: router1645.performance.interfaces.mibCounters.ifInUnknownProtos

       64 bit unsigned wrappable counter."
   ::= {pr1645v2InterfacesEntry 41025536}

pr1645v2InterfacesMibCountersInDropEx OBJECT-TYPE
   SYNTAX      Counter64
   MAX-ACCESS  read-only
   STATUS      current
   DESCRIPTION
      "Path: router1645.performance.interfaces.mibCounters.ifInDropLevelExceeded

       64 bit unsigned wrappable counter."
   ::= {pr1645v2InterfacesEntry 42074112}

pr1645v2InterfacesMibCountersInDropNoMac OBJECT-TYPE
   SYNTAX      Counter64
   MAX-ACCESS  read-only
   STATUS      current
   DESCRIPTION
      "Path: router1645.performance.interfaces.mibCounters.ifInDiscardsNoMacFit

       64 bit unsigned wrappable counter."
   ::= {pr1645v2InterfacesEntry 42270720}

pr1645v2InterfacesMibCountersInDropNUCast OBJECT-TYPE
   SYNTAX      Counter64
   MAX-ACCESS  read-only
   STATUS      current
   DESCRIPTION
      "Path: router1645.performance.interfaces.mibCounters.ifInDiscardsNUCast

       64 bit unsigned wrappable counter."
   ::= {pr1645v2InterfacesEntry 42467328}

pr1645v2InterfacesMibCountersInDropFilter OBJECT-TYPE
   SYNTAX      Counter64
   MAX-ACCESS  read-only
   STATUS      current
   DESCRIPTION
      "Path: router1645.performance.interfaces.mibCounters.ifInDiscardsFilter

       64 bit unsigned wrappable counter."
   ::= {pr1645v2InterfacesEntry 42532864}

pr1645v2InterfacesMibCountersInBandwidth15sec OBJECT-TYPE
   SYNTAX      Integer32
   MAX-ACCESS  read-only
   STATUS      current
   DESCRIPTION
      "Path: router1645.performance.interfaces.mibCounters.ifInBandwidth.15sec

       unit name = bps
       formula = 8 * ; 8 /"
   ::= {pr1645v2InterfacesEntry 45417728}

pr1645v2InterfacesMibCountersInBandwidth30sec OBJECT-TYPE
   SYNTAX      Integer32
   MAX-ACCESS  read-only
   STATUS      current
   DESCRIPTION
      "Path: router1645.performance.interfaces.mibCounters.ifInBandwidth.30sec

       unit name = bps
       formula = 8 * ; 8 /"
   ::= {pr1645v2InterfacesEntry 45419008}

pr1645v2InterfacesMibCountersInBandwidth1min OBJECT-TYPE
   SYNTAX      Integer32
   MAX-ACCESS  read-only
   STATUS      current
   DESCRIPTION
      "Path: router1645.performance.interfaces.mibCounters.ifInBandwidth.1min

       unit name = bps
       formula = 8 * ; 8 /"
   ::= {pr1645v2InterfacesEntry 45421568}

pr1645v2InterfacesMibCountersInBandwidth2min OBJECT-TYPE
   SYNTAX      Integer32
   MAX-ACCESS  read-only
   STATUS      current
   DESCRIPTION
      "Path: router1645.performance.interfaces.mibCounters.ifInBandwidth.2min

       unit name = bps
       formula = 8 * ; 8 /"
   ::= {pr1645v2InterfacesEntry 45426688}

pr1645v2InterfacesMibCountersInBandwidth5min OBJECT-TYPE
   SYNTAX      Integer32
   MAX-ACCESS  read-only
   STATUS      current
   DESCRIPTION
      "Path: router1645.performance.interfaces.mibCounters.ifInBandwidth.5min

       unit name = bps
       formula = 8 * ; 8 /"
   ::= {pr1645v2InterfacesEntry 45442048}

pr1645v2InterfacesMibCountersOutOctets OBJECT-TYPE
   SYNTAX      Counter64
   MAX-ACCESS  read-only
   STATUS      current
   DESCRIPTION
      "Path: router1645.performance.interfaces.mibCounters.ifOutOctets

       64 bit unsigned wrappable counter."
   ::= {pr1645v2InterfacesEntry 41091072}

pr1645v2InterfacesMibCountersOutUcastPkts OBJECT-TYPE
   SYNTAX      Counter64
   MAX-ACCESS  read-only
   STATUS      current
   DESCRIPTION
      "Path: router1645.performance.interfaces.mibCounters.ifOutUcastPkts

       64 bit unsigned wrappable counter."
   ::= {pr1645v2InterfacesEntry 41156608}

pr1645v2InterfacesMibCountersOutNUcastPkts OBJECT-TYPE
   SYNTAX      Counter64
   MAX-ACCESS  read-only
   STATUS      current
   DESCRIPTION
      "Path: router1645.performance.interfaces.mibCounters.ifOutNUcastPkts

       64 bit unsigned wrappable counter."
   ::= {pr1645v2InterfacesEntry 41222144}

pr1645v2InterfacesMibCountersOutBcastPkts OBJECT-TYPE
   SYNTAX      Counter64
   MAX-ACCESS  read-only
   STATUS      current
   DESCRIPTION
      "Path: router1645.performance.interfaces.mibCounters.ifOutBcastPkts

       64 bit unsigned wrappable counter."
   ::= {pr1645v2InterfacesEntry 47775744}

pr1645v2InterfacesMibCountersOutMcastPkts OBJECT-TYPE
   SYNTAX      Counter64
   MAX-ACCESS  read-only
   STATUS      current
   DESCRIPTION
      "Path: router1645.performance.interfaces.mibCounters.ifOutMcastPkts

       64 bit unsigned wrappable counter."
   ::= {pr1645v2InterfacesEntry 48431104}

pr1645v2InterfacesMibCountersOutDiscards OBJECT-TYPE
   SYNTAX      Counter64
   MAX-ACCESS  read-only
   STATUS      current
   DESCRIPTION
      "Path: router1645.performance.interfaces.mibCounters.ifOutDiscards

       64 bit unsigned wrappable counter."
   ::= {pr1645v2InterfacesEntry 41287680}

pr1645v2InterfacesMibCountersOutErrors OBJECT-TYPE
   SYNTAX      Counter64
   MAX-ACCESS  read-only
   STATUS      current
   DESCRIPTION
      "Path: router1645.performance.interfaces.mibCounters.ifOutErrors

       64 bit unsigned wrappable counter."
   ::= {pr1645v2InterfacesEntry 41353216}

pr1645v2InterfacesMibCountersOutQLen OBJECT-TYPE
   SYNTAX      Counter32
   MAX-ACCESS  read-only
   STATUS      current
   DESCRIPTION
      "Path: router1645.performance.interfaces.mibCounters.ifOutQLen

       32 bit unsigned wrappable counter."
   ::= {pr1645v2InterfacesEntry 41418752}

pr1645v2InterfacesMibCountersOutDropEx OBJECT-TYPE
   SYNTAX      Counter64
   MAX-ACCESS  read-only
   STATUS      current
   DESCRIPTION
      "Path: router1645.performance.interfaces.mibCounters.ifOutDropLevelExceeded

       64 bit unsigned wrappable counter."
   ::= {pr1645v2InterfacesEntry 41484288}

pr1645v2InterfacesMibCountersOutDropNoArp OBJECT-TYPE
   SYNTAX      Counter64
   MAX-ACCESS  read-only
   STATUS      current
   DESCRIPTION
      "Path: router1645.performance.interfaces.mibCounters.ifOutDiscardsNoArp

       64 bit unsigned wrappable counter."
   ::= {pr1645v2InterfacesEntry 42336256}

pr1645v2InterfacesMibCountersOutDropFilter OBJECT-TYPE
   SYNTAX      Counter64
   MAX-ACCESS  read-only
   STATUS      current
   DESCRIPTION
      "Path: router1645.performance.interfaces.mibCounters.ifOutDiscardsFilter

       64 bit unsigned wrappable counter."
   ::= {pr1645v2InterfacesEntry 42598400}

pr1645v2InterfacesMibCountersOutBandwidth15sec OBJECT-TYPE
   SYNTAX      Integer32
   MAX-ACCESS  read-only
   STATUS      current
   DESCRIPTION
      "Path: router1645.performance.interfaces.mibCounters.ifOutBandwidth.15sec

       unit name = bps
       formula = 8 * ; 8 /"
   ::= {pr1645v2InterfacesEntry 45483264}

pr1645v2InterfacesMibCountersOutBandwidth30sec OBJECT-TYPE
   SYNTAX      Integer32
   MAX-ACCESS  read-only
   STATUS      current
   DESCRIPTION
      "Path: router1645.performance.interfaces.mibCounters.ifOutBandwidth.30sec

       unit name = bps
       formula = 8 * ; 8 /"
   ::= {pr1645v2InterfacesEntry 45484544}

pr1645v2InterfacesMibCountersOutBandwidth1min OBJECT-TYPE
   SYNTAX      Integer32
   MAX-ACCESS  read-only
   STATUS      current
   DESCRIPTION
      "Path: router1645.performance.interfaces.mibCounters.ifOutBandwidth.1min

       unit name = bps
       formula = 8 * ; 8 /"
   ::= {pr1645v2InterfacesEntry 45487104}

pr1645v2InterfacesMibCountersOutBandwidth2min OBJECT-TYPE
   SYNTAX      Integer32
   MAX-ACCESS  read-only
   STATUS      current
   DESCRIPTION
      "Path: router1645.performance.interfaces.mibCounters.ifOutBandwidth.2min

       unit name = bps
       formula = 8 * ; 8 /"
   ::= {pr1645v2InterfacesEntry 45492224}

pr1645v2InterfacesMibCountersOutBandwidth5min OBJECT-TYPE
   SYNTAX      Integer32
   MAX-ACCESS  read-only
   STATUS      current
   DESCRIPTION
      "Path: router1645.performance.interfaces.mibCounters.ifOutBandwidth.5min

       unit name = bps
       formula = 8 * ; 8 /"
   ::= {pr1645v2InterfacesEntry 45507584}

pr1645v2InterfacesIpSecondaryIp OBJECT-TYPE
   SYNTAX      SEQUENCE OF Pr1645v2InterfacesIpSecondaryIpEntry
   MAX-ACCESS  not-accessible
   STATUS      current
   DESCRIPTION
      ""
   ::= {pr1645v2Interfaces 51838976}

pr1645v2InterfacesIpSecondaryIpEntry OBJECT-TYPE
   SYNTAX      Pr1645v2InterfacesIpSecondaryIpEntry
   MAX-ACCESS  not-accessible
   STATUS      current
   DESCRIPTION
      ""
   INDEX      { pr1645v2InterfacesTableIx,
                pr1645v2InterfacesIpSecondaryIpTableIx }
   ::= {pr1645v2InterfacesIpSecondaryIp 1}

Pr1645v2InterfacesIpSecondaryIpEntry ::=
   SEQUENCE
      {
      pr1645v2InterfacesIpSecondaryIpTableIx
         TableIndex,
      pr1645v2InterfacesIpSecondaryIpAddress
         IpAddress,
      pr1645v2InterfacesIpSecondaryIpNetMask
         IpAddress
      }

pr1645v2InterfacesIpSecondaryIpTableIx OBJECT-TYPE
   SYNTAX      TableIndex
   MAX-ACCESS  not-accessible
   STATUS      current
   DESCRIPTION
      ""
   ::= {pr1645v2InterfacesIpSecondaryIpEntry 11}

pr1645v2InterfacesIpSecondaryIpAddress OBJECT-TYPE
   SYNTAX      IpAddress
   MAX-ACCESS  read-only
   STATUS      current
   DESCRIPTION
      "Path: router1645.performance.interfaces.ip.secondaryIp.address"
   ::= {pr1645v2InterfacesIpSecondaryIpEntry 2030043136}

pr1645v2InterfacesIpSecondaryIpNetMask OBJECT-TYPE
   SYNTAX      IpAddress
   MAX-ACCESS  read-only
   STATUS      current
   DESCRIPTION
      "Path: router1645.performance.interfaces.ip.secondaryIp.netMask"
   ::= {pr1645v2InterfacesIpSecondaryIpEntry 2063597568}

pr1645v2InterfacesMibCountersH2P OBJECT-TYPE
   SYNTAX      SEQUENCE OF Pr1645v2InterfacesMibCountersH2PEntry
   MAX-ACCESS  not-accessible
   STATUS      current
   DESCRIPTION
      ""
   ::= {pr1645v2Interfaces 41549824}

pr1645v2InterfacesMibCountersH2PEntry OBJECT-TYPE
   SYNTAX      Pr1645v2InterfacesMibCountersH2PEntry
   MAX-ACCESS  not-accessible
   STATUS      current
   DESCRIPTION
      ""
   INDEX      { pr1645v2InterfacesTableIx,
                pr1645v2InterfacesMibCountersH2PTableIx }
   ::= {pr1645v2InterfacesMibCountersH2P 1}

Pr1645v2InterfacesMibCountersH2PEntry ::=
   SEQUENCE
      {
      pr1645v2InterfacesMibCountersH2PTableIx
         TableIndex,
      pr1645v2InterfacesMibCountersH2PSysUpTime
         TimeTicks,
      pr1645v2InterfacesMibCountersH2PIfUpTime
         TimeTicks,
      pr1645v2InterfacesMibCountersH2PIfStatChanges
         Counter32,
      pr1645v2InterfacesMibCountersH2PIfInOctets
         Counter64,
      pr1645v2InterfacesMibCountersH2PIfInUCPkts
         Counter64,
      pr1645v2InterfacesMibCountersH2PIfInNUCPkts
         Counter64,
      pr1645v2InterfacesMibCountersH2PIfInBCPkts
         Counter64,
      pr1645v2InterfacesMibCountersH2PIfInMCPkts
         Counter64,
      pr1645v2InterfacesMibCountersH2PIfInDiscards
         Counter64,
      pr1645v2InterfacesMibCountersH2PIfInErrors
         Counter64,
      pr1645v2InterfacesMibCountersH2PIfInUnkwn
         Counter64,
      pr1645v2InterfacesMibCountersH2PInDropEx
         Counter64,
      pr1645v2InterfacesMibCountersH2PInDropNoMac
         Counter64,
      pr1645v2InterfacesMibCountersH2PInDropNUCast
         Counter64,
      pr1645v2InterfacesMibCountersH2PInDropFilter
         Counter64,
      pr1645v2InterfacesMibCountersH2PIfInBandwidth
         Integer32,
      pr1645v2InterfacesMibCountersH2PIfOutOctets
         Counter64,
      pr1645v2InterfacesMibCountersH2PIfOutUCPkts
         Counter64,
      pr1645v2InterfacesMibCountersH2PIfOutNUCPkts
         Counter64,
      pr1645v2InterfacesMibCountersH2PIfOutBCPkts
         Counter64,
      pr1645v2InterfacesMibCountersH2PIfOutMCPkts
         Counter64,
      pr1645v2InterfacesMibCountersH2PIfOutDiscards
         Counter64,
      pr1645v2InterfacesMibCountersH2PIfOutErrors
         Counter64,
      pr1645v2InterfacesMibCountersH2POutDropEx
         Counter64,
      pr1645v2InterfacesMibCountersH2POutDropNoArp
         Counter64,
      pr1645v2InterfacesMibCountersH2POutDropFilter
         Counter64,
      pr1645v2InterfacesMibCountersH2PIfOutBandwidth
         Integer32,
      pr1645v2InterfacesMibCountersH2PIfErrSec
         Counter32
      }

pr1645v2InterfacesMibCountersH2PTableIx OBJECT-TYPE
   SYNTAX      TableIndex
   MAX-ACCESS  not-accessible
   STATUS      current
   DESCRIPTION
      ""
   ::= {pr1645v2InterfacesMibCountersH2PEntry 11}

pr1645v2InterfacesMibCountersH2PSysUpTime OBJECT-TYPE
   SYNTAX      TimeTicks
   MAX-ACCESS  read-only
   STATUS      current
   DESCRIPTION
      "Path: router1645.performance.interfaces.mibCounters.h2Performance.sysUpTime

       Time in centi-second."
   ::= {pr1645v2InterfacesMibCountersH2PEntry 16777216}

pr1645v2InterfacesMibCountersH2PIfUpTime OBJECT-TYPE
   SYNTAX      TimeTicks
   MAX-ACCESS  read-only
   STATUS      current
   DESCRIPTION
      "Path: router1645.performance.interfaces.mibCounters.h2Performance.ifUpTime

       Time in centi-second."
   ::= {pr1645v2InterfacesMibCountersH2PEntry 33554432}

pr1645v2InterfacesMibCountersH2PIfStatChanges OBJECT-TYPE
   SYNTAX      Counter32
   MAX-ACCESS  read-only
   STATUS      current
   DESCRIPTION
      "Path: router1645.performance.interfaces.mibCounters.h2Performance.ifStatusChanges

       32 bit unsigned wrappable counter."
   ::= {pr1645v2InterfacesMibCountersH2PEntry 50331648}

pr1645v2InterfacesMibCountersH2PIfInOctets OBJECT-TYPE
   SYNTAX      Counter64
   MAX-ACCESS  read-only
   STATUS      current
   DESCRIPTION
      "Path: router1645.performance.interfaces.mibCounters.h2Performance.ifInOctets

       64 bit unsigned wrappable counter."
   ::= {pr1645v2InterfacesMibCountersH2PEntry 67108864}

pr1645v2InterfacesMibCountersH2PIfInUCPkts OBJECT-TYPE
   SYNTAX      Counter64
   MAX-ACCESS  read-only
   STATUS      current
   DESCRIPTION
      "Path: router1645.performance.interfaces.mibCounters.h2Performance.ifInUcastPkts

       64 bit unsigned wrappable counter."
   ::= {pr1645v2InterfacesMibCountersH2PEntry 83886080}

pr1645v2InterfacesMibCountersH2PIfInNUCPkts OBJECT-TYPE
   SYNTAX      Counter64
   MAX-ACCESS  read-only
   STATUS      current
   DESCRIPTION
      "Path: router1645.performance.interfaces.mibCounters.h2Performance.ifInNUcastPkts

       64 bit unsigned wrappable counter."
   ::= {pr1645v2InterfacesMibCountersH2PEntry 100663296}

pr1645v2InterfacesMibCountersH2PIfInBCPkts OBJECT-TYPE
   SYNTAX      Counter64
   MAX-ACCESS  read-only
   STATUS      current
   DESCRIPTION
      "Path: router1645.performance.interfaces.mibCounters.h2Performance.ifInBcastPkts

       64 bit unsigned wrappable counter."
   ::= {pr1645v2InterfacesMibCountersH2PEntry 419430400}

pr1645v2InterfacesMibCountersH2PIfInMCPkts OBJECT-TYPE
   SYNTAX      Counter64
   MAX-ACCESS  read-only
   STATUS      current
   DESCRIPTION
      "Path: router1645.performance.interfaces.mibCounters.h2Performance.ifInMcastPkts

       64 bit unsigned wrappable counter."
   ::= {pr1645v2InterfacesMibCountersH2PEntry 436207616}

pr1645v2InterfacesMibCountersH2PIfInDiscards OBJECT-TYPE
   SYNTAX      Counter64
   MAX-ACCESS  read-only
   STATUS      current
   DESCRIPTION
      "Path: router1645.performance.interfaces.mibCounters.h2Performance.ifInDiscards

       64 bit unsigned wrappable counter."
   ::= {pr1645v2InterfacesMibCountersH2PEntry 117440512}

pr1645v2InterfacesMibCountersH2PIfInErrors OBJECT-TYPE
   SYNTAX      Counter64
   MAX-ACCESS  read-only
   STATUS      current
   DESCRIPTION
      "Path: router1645.performance.interfaces.mibCounters.h2Performance.ifInErrors

       64 bit unsigned wrappable counter."
   ::= {pr1645v2InterfacesMibCountersH2PEntry 134217728}

pr1645v2InterfacesMibCountersH2PIfInUnkwn OBJECT-TYPE
   SYNTAX      Counter64
   MAX-ACCESS  read-only
   STATUS      current
   DESCRIPTION
      "Path: router1645.performance.interfaces.mibCounters.h2Performance.ifInUnknownProtos

       64 bit unsigned wrappable counter."
   ::= {pr1645v2InterfacesMibCountersH2PEntry 150994944}

pr1645v2InterfacesMibCountersH2PInDropEx OBJECT-TYPE
   SYNTAX      Counter64
   MAX-ACCESS  read-only
   STATUS      current
   DESCRIPTION
      "Path: router1645.performance.interfaces.mibCounters.h2Performance.ifInDropLevelExceeded

       64 bit unsigned wrappable counter."
   ::= {pr1645v2InterfacesMibCountersH2PEntry 335544320}

pr1645v2InterfacesMibCountersH2PInDropNoMac OBJECT-TYPE
   SYNTAX      Counter64
   MAX-ACCESS  read-only
   STATUS      current
   DESCRIPTION
      "Path: router1645.performance.interfaces.mibCounters.h2Performance.fInDiscardsNoMacFit

       64 bit unsigned wrappable counter."
   ::= {pr1645v2InterfacesMibCountersH2PEntry 301989888}

pr1645v2InterfacesMibCountersH2PInDropNUCast OBJECT-TYPE
   SYNTAX      Counter64
   MAX-ACCESS  read-only
   STATUS      current
   DESCRIPTION
      "Path: router1645.performance.interfaces.mibCounters.h2Performance.fInDiscardsNUCast

       64 bit unsigned wrappable counter."
   ::= {pr1645v2InterfacesMibCountersH2PEntry 318767104}

pr1645v2InterfacesMibCountersH2PInDropFilter OBJECT-TYPE
   SYNTAX      Counter64
   MAX-ACCESS  read-only
   STATUS      current
   DESCRIPTION
      "Path: router1645.performance.interfaces.mibCounters.h2Performance.fInDiscardsFilter

       64 bit unsigned wrappable counter."
   ::= {pr1645v2InterfacesMibCountersH2PEntry 385875968}

pr1645v2InterfacesMibCountersH2PIfInBandwidth OBJECT-TYPE
   SYNTAX      Integer32
   MAX-ACCESS  read-only
   STATUS      current
   DESCRIPTION
      "Path: router1645.performance.interfaces.mibCounters.h2Performance.ifInBandwidth

       unit name = bps
       formula = 8 * ; 8 /"
   ::= {pr1645v2InterfacesMibCountersH2PEntry 268435456}

pr1645v2InterfacesMibCountersH2PIfOutOctets OBJECT-TYPE
   SYNTAX      Counter64
   MAX-ACCESS  read-only
   STATUS      current
   DESCRIPTION
      "Path: router1645.performance.interfaces.mibCounters.h2Performance.ifOutOctets

       64 bit unsigned wrappable counter."
   ::= {pr1645v2InterfacesMibCountersH2PEntry 167772160}

pr1645v2InterfacesMibCountersH2PIfOutUCPkts OBJECT-TYPE
   SYNTAX      Counter64
   MAX-ACCESS  read-only
   STATUS      current
   DESCRIPTION
      "Path: router1645.performance.interfaces.mibCounters.h2Performance.ifOutUcastPkts

       64 bit unsigned wrappable counter."
   ::= {pr1645v2InterfacesMibCountersH2PEntry 184549376}

pr1645v2InterfacesMibCountersH2PIfOutNUCPkts OBJECT-TYPE
   SYNTAX      Counter64
   MAX-ACCESS  read-only
   STATUS      current
   DESCRIPTION
      "Path: router1645.performance.interfaces.mibCounters.h2Performance.ifOutNUcastPkts

       64 bit unsigned wrappable counter."
   ::= {pr1645v2InterfacesMibCountersH2PEntry 201326592}

pr1645v2InterfacesMibCountersH2PIfOutBCPkts OBJECT-TYPE
   SYNTAX      Counter64
   MAX-ACCESS  read-only
   STATUS      current
   DESCRIPTION
      "Path: router1645.performance.interfaces.mibCounters.h2Performance.ifOutBcastPkts

       64 bit unsigned wrappable counter."
   ::= {pr1645v2InterfacesMibCountersH2PEntry 452984832}

pr1645v2InterfacesMibCountersH2PIfOutMCPkts OBJECT-TYPE
   SYNTAX      Counter64
   MAX-ACCESS  read-only
   STATUS      current
   DESCRIPTION
      "Path: router1645.performance.interfaces.mibCounters.h2Performance.ifOutMcastPkts

       64 bit unsigned wrappable counter."
   ::= {pr1645v2InterfacesMibCountersH2PEntry 469762048}

pr1645v2InterfacesMibCountersH2PIfOutDiscards OBJECT-TYPE
   SYNTAX      Counter64
   MAX-ACCESS  read-only
   STATUS      current
   DESCRIPTION
      "Path: router1645.performance.interfaces.mibCounters.h2Performance.ifOutDiscards

       64 bit unsigned wrappable counter."
   ::= {pr1645v2InterfacesMibCountersH2PEntry 218103808}

pr1645v2InterfacesMibCountersH2PIfOutErrors OBJECT-TYPE
   SYNTAX      Counter64
   MAX-ACCESS  read-only
   STATUS      current
   DESCRIPTION
      "Path: router1645.performance.interfaces.mibCounters.h2Performance.ifOutErrors

       64 bit unsigned wrappable counter."
   ::= {pr1645v2InterfacesMibCountersH2PEntry 234881024}

pr1645v2InterfacesMibCountersH2POutDropEx OBJECT-TYPE
   SYNTAX      Counter64
   MAX-ACCESS  read-only
   STATUS      current
   DESCRIPTION
      "Path: router1645.performance.interfaces.mibCounters.h2Performance.ifOutDropLevelExceeded

       64 bit unsigned wrappable counter."
   ::= {pr1645v2InterfacesMibCountersH2PEntry 352321536}

pr1645v2InterfacesMibCountersH2POutDropNoArp OBJECT-TYPE
   SYNTAX      Counter64
   MAX-ACCESS  read-only
   STATUS      current
   DESCRIPTION
      "Path: router1645.performance.interfaces.mibCounters.h2Performance.ifOutDiscardsNoArp

       64 bit unsigned wrappable counter."
   ::= {pr1645v2InterfacesMibCountersH2PEntry 369098752}

pr1645v2InterfacesMibCountersH2POutDropFilter OBJECT-TYPE
   SYNTAX      Counter64
   MAX-ACCESS  read-only
   STATUS      current
   DESCRIPTION
      "Path: router1645.performance.interfaces.mibCounters.h2Performance.ifOutDiscardsFilter

       64 bit unsigned wrappable counter."
   ::= {pr1645v2InterfacesMibCountersH2PEntry 402653184}

pr1645v2InterfacesMibCountersH2PIfOutBandwidth OBJECT-TYPE
   SYNTAX      Integer32
   MAX-ACCESS  read-only
   STATUS      current
   DESCRIPTION
      "Path: router1645.performance.interfaces.mibCounters.h2Performance.ifOutBandwidth

       unit name = bps
       formula = 8 * ; 8 /"
   ::= {pr1645v2InterfacesMibCountersH2PEntry 285212672}

pr1645v2InterfacesMibCountersH2PIfErrSec OBJECT-TYPE
   SYNTAX      Counter32
   MAX-ACCESS  read-only
   STATUS      current
   DESCRIPTION
      "Path: router1645.performance.interfaces.mibCounters.h2Performance.ifErrSec

       32 bit unsigned wrappable counter."
   ::= {pr1645v2InterfacesMibCountersH2PEntry 251658240}

pr1645v2InterfacesMibCountersH24P OBJECT-TYPE
   SYNTAX      SEQUENCE OF Pr1645v2InterfacesMibCountersH24PEntry
   MAX-ACCESS  not-accessible
   STATUS      current
   DESCRIPTION
      ""
   ::= {pr1645v2Interfaces 41615360}

pr1645v2InterfacesMibCountersH24PEntry OBJECT-TYPE
   SYNTAX      Pr1645v2InterfacesMibCountersH24PEntry
   MAX-ACCESS  not-accessible
   STATUS      current
   DESCRIPTION
      ""
   INDEX      { pr1645v2InterfacesTableIx,
                pr1645v2InterfacesMibCountersH24PTableIx }
   ::= {pr1645v2InterfacesMibCountersH24P 1}

Pr1645v2InterfacesMibCountersH24PEntry ::=
   SEQUENCE
      {
      pr1645v2InterfacesMibCountersH24PTableIx
         TableIndex,
      pr1645v2InterfacesMibCountersH24PSysUpTime
         TimeTicks,
      pr1645v2InterfacesMibCountersH24PIfUpTime
         TimeTicks,
      pr1645v2InterfacesMibCountersH24PIfStatChanges
         Counter32,
      pr1645v2InterfacesMibCountersH24PIfInOctets
         Counter64,
      pr1645v2InterfacesMibCountersH24PIfInUCPkts
         Counter64,
      pr1645v2InterfacesMibCountersH24PIfInNUCPkts
         Counter64,
      pr1645v2InterfacesMibCountersH24PIfInBCPkts
         Counter64,
      pr1645v2InterfacesMibCountersH24PIfInMCPkts
         Counter64,
      pr1645v2InterfacesMibCountersH24PIfInDiscards
         Counter64,
      pr1645v2InterfacesMibCountersH24PIfInErrors
         Counter64,
      pr1645v2InterfacesMibCountersH24PIfInUnkwn
         Counter64,
      pr1645v2InterfacesMibCountersH24PInDropEx
         Counter64,
      pr1645v2InterfacesMibCountersH24PInDropNoMac
         Counter64,
      pr1645v2InterfacesMibCountersH24PInDropNUCast
         Counter64,
      pr1645v2InterfacesMibCountersH24PInDropFilter
         Counter64,
      pr1645v2InterfacesMibCountersH24PIfInBandwidth
         Integer32,
      pr1645v2InterfacesMibCountersH24PIfOutOctets
         Counter64,
      pr1645v2InterfacesMibCountersH24PIfOutUCPkts
         Counter64,
      pr1645v2InterfacesMibCountersH24PIfOutNUCPkts
         Counter64,
      pr1645v2InterfacesMibCountersH24PIfOutBCPkts
         Counter64,
      pr1645v2InterfacesMibCountersH24PIfOutMCPkts
         Counter64,
      pr1645v2InterfacesMibCountersH24PIfOutDiscards
         Counter64,
      pr1645v2InterfacesMibCountersH24PIfOutErrors
         Counter64,
      pr1645v2InterfacesMibCountersH24POutDropEx
         Counter64,
      pr1645v2InterfacesMibCountersH24POutDropNoArp
         Counter64,
      pr1645v2InterfacesMibCountersH24POutDropFilter
         Counter64,
      pr1645v2InterfacesMibCountersH24PIfOutBandwidth
         Integer32,
      pr1645v2InterfacesMibCountersH24PIfErrSec
         Counter32
      }

pr1645v2InterfacesMibCountersH24PTableIx OBJECT-TYPE
   SYNTAX      TableIndex
   MAX-ACCESS  not-accessible
   STATUS      current
   DESCRIPTION
      ""
   ::= {pr1645v2InterfacesMibCountersH24PEntry 11}

pr1645v2InterfacesMibCountersH24PSysUpTime OBJECT-TYPE
   SYNTAX      TimeTicks
   MAX-ACCESS  read-only
   STATUS      current
   DESCRIPTION
      "Path: router1645.performance.interfaces.mibCounters.h24Performance.sysUpTime

       Time in centi-second."
   ::= {pr1645v2InterfacesMibCountersH24PEntry 16777216}

pr1645v2InterfacesMibCountersH24PIfUpTime OBJECT-TYPE
   SYNTAX      TimeTicks
   MAX-ACCESS  read-only
   STATUS      current
   DESCRIPTION
      "Path: router1645.performance.interfaces.mibCounters.h24Performance.ifUpTime

       Time in centi-second."
   ::= {pr1645v2InterfacesMibCountersH24PEntry 33554432}

pr1645v2InterfacesMibCountersH24PIfStatChanges OBJECT-TYPE
   SYNTAX      Counter32
   MAX-ACCESS  read-only
   STATUS      current
   DESCRIPTION
      "Path: router1645.performance.interfaces.mibCounters.h24Performance.ifStatusChanges

       32 bit unsigned wrappable counter."
   ::= {pr1645v2InterfacesMibCountersH24PEntry 50331648}

pr1645v2InterfacesMibCountersH24PIfInOctets OBJECT-TYPE
   SYNTAX      Counter64
   MAX-ACCESS  read-only
   STATUS      current
   DESCRIPTION
      "Path: router1645.performance.interfaces.mibCounters.h24Performance.ifInOctets

       64 bit unsigned wrappable counter."
   ::= {pr1645v2InterfacesMibCountersH24PEntry 67108864}

pr1645v2InterfacesMibCountersH24PIfInUCPkts OBJECT-TYPE
   SYNTAX      Counter64
   MAX-ACCESS  read-only
   STATUS      current
   DESCRIPTION
      "Path: router1645.performance.interfaces.mibCounters.h24Performance.ifInUcastPkts

       64 bit unsigned wrappable counter."
   ::= {pr1645v2InterfacesMibCountersH24PEntry 83886080}

pr1645v2InterfacesMibCountersH24PIfInNUCPkts OBJECT-TYPE
   SYNTAX      Counter64
   MAX-ACCESS  read-only
   STATUS      current
   DESCRIPTION
      "Path: router1645.performance.interfaces.mibCounters.h24Performance.ifInNUcastPkts

       64 bit unsigned wrappable counter."
   ::= {pr1645v2InterfacesMibCountersH24PEntry 100663296}

pr1645v2InterfacesMibCountersH24PIfInBCPkts OBJECT-TYPE
   SYNTAX      Counter64
   MAX-ACCESS  read-only
   STATUS      current
   DESCRIPTION
      "Path: router1645.performance.interfaces.mibCounters.h24Performance.ifInBcastPkts

       64 bit unsigned wrappable counter."
   ::= {pr1645v2InterfacesMibCountersH24PEntry 419430400}

pr1645v2InterfacesMibCountersH24PIfInMCPkts OBJECT-TYPE
   SYNTAX      Counter64
   MAX-ACCESS  read-only
   STATUS      current
   DESCRIPTION
      "Path: router1645.performance.interfaces.mibCounters.h24Performance.ifInMcastPkts

       64 bit unsigned wrappable counter."
   ::= {pr1645v2InterfacesMibCountersH24PEntry 436207616}

pr1645v2InterfacesMibCountersH24PIfInDiscards OBJECT-TYPE
   SYNTAX      Counter64
   MAX-ACCESS  read-only
   STATUS      current
   DESCRIPTION
      "Path: router1645.performance.interfaces.mibCounters.h24Performance.ifInDiscards

       64 bit unsigned wrappable counter."
   ::= {pr1645v2InterfacesMibCountersH24PEntry 117440512}

pr1645v2InterfacesMibCountersH24PIfInErrors OBJECT-TYPE
   SYNTAX      Counter64
   MAX-ACCESS  read-only
   STATUS      current
   DESCRIPTION
      "Path: router1645.performance.interfaces.mibCounters.h24Performance.ifInErrors

       64 bit unsigned wrappable counter."
   ::= {pr1645v2InterfacesMibCountersH24PEntry 134217728}

pr1645v2InterfacesMibCountersH24PIfInUnkwn OBJECT-TYPE
   SYNTAX      Counter64
   MAX-ACCESS  read-only
   STATUS      current
   DESCRIPTION
      "Path: router1645.performance.interfaces.mibCounters.h24Performance.ifInUnknownProtos

       64 bit unsigned wrappable counter."
   ::= {pr1645v2InterfacesMibCountersH24PEntry 150994944}

pr1645v2InterfacesMibCountersH24PInDropEx OBJECT-TYPE
   SYNTAX      Counter64
   MAX-ACCESS  read-only
   STATUS      current
   DESCRIPTION
      "Path: router1645.performance.interfaces.mibCounters.h24Performance.ifInDropLevelExceeded

       64 bit unsigned wrappable counter."
   ::= {pr1645v2InterfacesMibCountersH24PEntry 335544320}

pr1645v2InterfacesMibCountersH24PInDropNoMac OBJECT-TYPE
   SYNTAX      Counter64
   MAX-ACCESS  read-only
   STATUS      current
   DESCRIPTION
      "Path: router1645.performance.interfaces.mibCounters.h24Performance.fInDiscardsNoMacFit

       64 bit unsigned wrappable counter."
   ::= {pr1645v2InterfacesMibCountersH24PEntry 301989888}

pr1645v2InterfacesMibCountersH24PInDropNUCast OBJECT-TYPE
   SYNTAX      Counter64
   MAX-ACCESS  read-only
   STATUS      current
   DESCRIPTION
      "Path: router1645.performance.interfaces.mibCounters.h24Performance.fInDiscardsNUCast

       64 bit unsigned wrappable counter."
   ::= {pr1645v2InterfacesMibCountersH24PEntry 318767104}

pr1645v2InterfacesMibCountersH24PInDropFilter OBJECT-TYPE
   SYNTAX      Counter64
   MAX-ACCESS  read-only
   STATUS      current
   DESCRIPTION
      "Path: router1645.performance.interfaces.mibCounters.h24Performance.fInDiscardsFilter

       64 bit unsigned wrappable counter."
   ::= {pr1645v2InterfacesMibCountersH24PEntry 385875968}

pr1645v2InterfacesMibCountersH24PIfInBandwidth OBJECT-TYPE
   SYNTAX      Integer32
   MAX-ACCESS  read-only
   STATUS      current
   DESCRIPTION
      "Path: router1645.performance.interfaces.mibCounters.h24Performance.ifInBandwidth

       unit name = bps
       formula = 8 * ; 8 /"
   ::= {pr1645v2InterfacesMibCountersH24PEntry 268435456}

pr1645v2InterfacesMibCountersH24PIfOutOctets OBJECT-TYPE
   SYNTAX      Counter64
   MAX-ACCESS  read-only
   STATUS      current
   DESCRIPTION
      "Path: router1645.performance.interfaces.mibCounters.h24Performance.ifOutOctets

       64 bit unsigned wrappable counter."
   ::= {pr1645v2InterfacesMibCountersH24PEntry 167772160}

pr1645v2InterfacesMibCountersH24PIfOutUCPkts OBJECT-TYPE
   SYNTAX      Counter64
   MAX-ACCESS  read-only
   STATUS      current
   DESCRIPTION
      "Path: router1645.performance.interfaces.mibCounters.h24Performance.ifOutUcastPkts

       64 bit unsigned wrappable counter."
   ::= {pr1645v2InterfacesMibCountersH24PEntry 184549376}

pr1645v2InterfacesMibCountersH24PIfOutNUCPkts OBJECT-TYPE
   SYNTAX      Counter64
   MAX-ACCESS  read-only
   STATUS      current
   DESCRIPTION
      "Path: router1645.performance.interfaces.mibCounters.h24Performance.ifOutNUcastPkts

       64 bit unsigned wrappable counter."
   ::= {pr1645v2InterfacesMibCountersH24PEntry 201326592}

pr1645v2InterfacesMibCountersH24PIfOutBCPkts OBJECT-TYPE
   SYNTAX      Counter64
   MAX-ACCESS  read-only
   STATUS      current
   DESCRIPTION
      "Path: router1645.performance.interfaces.mibCounters.h24Performance.ifOutBcastPkts

       64 bit unsigned wrappable counter."
   ::= {pr1645v2InterfacesMibCountersH24PEntry 452984832}

pr1645v2InterfacesMibCountersH24PIfOutMCPkts OBJECT-TYPE
   SYNTAX      Counter64
   MAX-ACCESS  read-only
   STATUS      current
   DESCRIPTION
      "Path: router1645.performance.interfaces.mibCounters.h24Performance.ifOutMcastPkts

       64 bit unsigned wrappable counter."
   ::= {pr1645v2InterfacesMibCountersH24PEntry 469762048}

pr1645v2InterfacesMibCountersH24PIfOutDiscards OBJECT-TYPE
   SYNTAX      Counter64
   MAX-ACCESS  read-only
   STATUS      current
   DESCRIPTION
      "Path: router1645.performance.interfaces.mibCounters.h24Performance.ifOutDiscards

       64 bit unsigned wrappable counter."
   ::= {pr1645v2InterfacesMibCountersH24PEntry 218103808}

pr1645v2InterfacesMibCountersH24PIfOutErrors OBJECT-TYPE
   SYNTAX      Counter64
   MAX-ACCESS  read-only
   STATUS      current
   DESCRIPTION
      "Path: router1645.performance.interfaces.mibCounters.h24Performance.ifOutErrors

       64 bit unsigned wrappable counter."
   ::= {pr1645v2InterfacesMibCountersH24PEntry 234881024}

pr1645v2InterfacesMibCountersH24POutDropEx OBJECT-TYPE
   SYNTAX      Counter64
   MAX-ACCESS  read-only
   STATUS      current
   DESCRIPTION
      "Path: router1645.performance.interfaces.mibCounters.h24Performance.ifOutDropLevelExceeded

       64 bit unsigned wrappable counter."
   ::= {pr1645v2InterfacesMibCountersH24PEntry 352321536}

pr1645v2InterfacesMibCountersH24POutDropNoArp OBJECT-TYPE
   SYNTAX      Counter64
   MAX-ACCESS  read-only
   STATUS      current
   DESCRIPTION
      "Path: router1645.performance.interfaces.mibCounters.h24Performance.ifOutDiscardsNoArp

       64 bit unsigned wrappable counter."
   ::= {pr1645v2InterfacesMibCountersH24PEntry 369098752}

pr1645v2InterfacesMibCountersH24POutDropFilter OBJECT-TYPE
   SYNTAX      Counter64
   MAX-ACCESS  read-only
   STATUS      current
   DESCRIPTION
      "Path: router1645.performance.interfaces.mibCounters.h24Performance.ifOutDiscardsFilter

       64 bit unsigned wrappable counter."
   ::= {pr1645v2InterfacesMibCountersH24PEntry 402653184}

pr1645v2InterfacesMibCountersH24PIfOutBandwidth OBJECT-TYPE
   SYNTAX      Integer32
   MAX-ACCESS  read-only
   STATUS      current
   DESCRIPTION
      "Path: router1645.performance.interfaces.mibCounters.h24Performance.ifOutBandwidth

       unit name = bps
       formula = 8 * ; 8 /"
   ::= {pr1645v2InterfacesMibCountersH24PEntry 285212672}

pr1645v2InterfacesMibCountersH24PIfErrSec OBJECT-TYPE
   SYNTAX      Counter32
   MAX-ACCESS  read-only
   STATUS      current
   DESCRIPTION
      "Path: router1645.performance.interfaces.mibCounters.h24Performance.ifErrSec

       32 bit unsigned wrappable counter."
   ::= {pr1645v2InterfacesMibCountersH24PEntry 251658240}

pr1645v2InterfacesMibCountersD7P OBJECT-TYPE
   SYNTAX      SEQUENCE OF Pr1645v2InterfacesMibCountersD7PEntry
   MAX-ACCESS  not-accessible
   STATUS      current
   DESCRIPTION
      ""
   ::= {pr1645v2Interfaces 41680896}

pr1645v2InterfacesMibCountersD7PEntry OBJECT-TYPE
   SYNTAX      Pr1645v2InterfacesMibCountersD7PEntry
   MAX-ACCESS  not-accessible
   STATUS      current
   DESCRIPTION
      ""
   INDEX      { pr1645v2InterfacesTableIx,
                pr1645v2InterfacesMibCountersD7PTableIx }
   ::= {pr1645v2InterfacesMibCountersD7P 1}

Pr1645v2InterfacesMibCountersD7PEntry ::=
   SEQUENCE
      {
      pr1645v2InterfacesMibCountersD7PTableIx
         TableIndex,
      pr1645v2InterfacesMibCountersD7PSysUpTime
         TimeTicks,
      pr1645v2InterfacesMibCountersD7PIfUpTime
         TimeTicks,
      pr1645v2InterfacesMibCountersD7PIfStatChanges
         Counter32,
      pr1645v2InterfacesMibCountersD7PIfInOctets
         Counter64,
      pr1645v2InterfacesMibCountersD7PIfInUCPkts
         Counter64,
      pr1645v2InterfacesMibCountersD7PIfInNUCPkts
         Counter64,
      pr1645v2InterfacesMibCountersD7PIfInBCPkts
         Counter64,
      pr1645v2InterfacesMibCountersD7PIfInMCPkts
         Counter64,
      pr1645v2InterfacesMibCountersD7PIfInDiscards
         Counter64,
      pr1645v2InterfacesMibCountersD7PIfInErrors
         Counter64,
      pr1645v2InterfacesMibCountersD7PIfInUnkwn
         Counter64,
      pr1645v2InterfacesMibCountersD7PInDropEx
         Counter64,
      pr1645v2InterfacesMibCountersD7PInDropNoMac
         Counter64,
      pr1645v2InterfacesMibCountersD7PInDropNUCast
         Counter64,
      pr1645v2InterfacesMibCountersD7PInDropFilter
         Counter64,
      pr1645v2InterfacesMibCountersD7PIfInBandwidth
         Integer32,
      pr1645v2InterfacesMibCountersD7PIfOutOctets
         Counter64,
      pr1645v2InterfacesMibCountersD7PIfOutUCPkts
         Counter64,
      pr1645v2InterfacesMibCountersD7PIfOutNUCPkts
         Counter64,
      pr1645v2InterfacesMibCountersD7PIfOutBCPkts
         Counter64,
      pr1645v2InterfacesMibCountersD7PIfOutMCPkts
         Counter64,
      pr1645v2InterfacesMibCountersD7PIfOutDiscards
         Counter64,
      pr1645v2InterfacesMibCountersD7PIfOutErrors
         Counter64,
      pr1645v2InterfacesMibCountersD7POutDropEx
         Counter64,
      pr1645v2InterfacesMibCountersD7POutDropNoArp
         Counter64,
      pr1645v2InterfacesMibCountersD7POutDropFilter
         Counter64,
      pr1645v2InterfacesMibCountersD7PIfOutBandwidth
         Integer32,
      pr1645v2InterfacesMibCountersD7PIfErrSec
         Counter32
      }

pr1645v2InterfacesMibCountersD7PTableIx OBJECT-TYPE
   SYNTAX      TableIndex
   MAX-ACCESS  not-accessible
   STATUS      current
   DESCRIPTION
      ""
   ::= {pr1645v2InterfacesMibCountersD7PEntry 11}

pr1645v2InterfacesMibCountersD7PSysUpTime OBJECT-TYPE
   SYNTAX      TimeTicks
   MAX-ACCESS  read-only
   STATUS      current
   DESCRIPTION
      "Path: router1645.performance.interfaces.mibCounters.d7Performance.sysUpTime

       Time in centi-second."
   ::= {pr1645v2InterfacesMibCountersD7PEntry 16777216}

pr1645v2InterfacesMibCountersD7PIfUpTime OBJECT-TYPE
   SYNTAX      TimeTicks
   MAX-ACCESS  read-only
   STATUS      current
   DESCRIPTION
      "Path: router1645.performance.interfaces.mibCounters.d7Performance.ifUpTime

       Time in centi-second."
   ::= {pr1645v2InterfacesMibCountersD7PEntry 33554432}

pr1645v2InterfacesMibCountersD7PIfStatChanges OBJECT-TYPE
   SYNTAX      Counter32
   MAX-ACCESS  read-only
   STATUS      current
   DESCRIPTION
      "Path: router1645.performance.interfaces.mibCounters.d7Performance.ifStatusChanges

       32 bit unsigned wrappable counter."
   ::= {pr1645v2InterfacesMibCountersD7PEntry 50331648}

pr1645v2InterfacesMibCountersD7PIfInOctets OBJECT-TYPE
   SYNTAX      Counter64
   MAX-ACCESS  read-only
   STATUS      current
   DESCRIPTION
      "Path: router1645.performance.interfaces.mibCounters.d7Performance.ifInOctets

       64 bit unsigned wrappable counter."
   ::= {pr1645v2InterfacesMibCountersD7PEntry 67108864}

pr1645v2InterfacesMibCountersD7PIfInUCPkts OBJECT-TYPE
   SYNTAX      Counter64
   MAX-ACCESS  read-only
   STATUS      current
   DESCRIPTION
      "Path: router1645.performance.interfaces.mibCounters.d7Performance.ifInUcastPkts

       64 bit unsigned wrappable counter."
   ::= {pr1645v2InterfacesMibCountersD7PEntry 83886080}

pr1645v2InterfacesMibCountersD7PIfInNUCPkts OBJECT-TYPE
   SYNTAX      Counter64
   MAX-ACCESS  read-only
   STATUS      current
   DESCRIPTION
      "Path: router1645.performance.interfaces.mibCounters.d7Performance.ifInNUcastPkts

       64 bit unsigned wrappable counter."
   ::= {pr1645v2InterfacesMibCountersD7PEntry 100663296}

pr1645v2InterfacesMibCountersD7PIfInBCPkts OBJECT-TYPE
   SYNTAX      Counter64
   MAX-ACCESS  read-only
   STATUS      current
   DESCRIPTION
      "Path: router1645.performance.interfaces.mibCounters.d7Performance.ifInBcastPkts

       64 bit unsigned wrappable counter."
   ::= {pr1645v2InterfacesMibCountersD7PEntry 419430400}

pr1645v2InterfacesMibCountersD7PIfInMCPkts OBJECT-TYPE
   SYNTAX      Counter64
   MAX-ACCESS  read-only
   STATUS      current
   DESCRIPTION
      "Path: router1645.performance.interfaces.mibCounters.d7Performance.ifInMcastPkts

       64 bit unsigned wrappable counter."
   ::= {pr1645v2InterfacesMibCountersD7PEntry 436207616}

pr1645v2InterfacesMibCountersD7PIfInDiscards OBJECT-TYPE
   SYNTAX      Counter64
   MAX-ACCESS  read-only
   STATUS      current
   DESCRIPTION
      "Path: router1645.performance.interfaces.mibCounters.d7Performance.ifInDiscards

       64 bit unsigned wrappable counter."
   ::= {pr1645v2InterfacesMibCountersD7PEntry 117440512}

pr1645v2InterfacesMibCountersD7PIfInErrors OBJECT-TYPE
   SYNTAX      Counter64
   MAX-ACCESS  read-only
   STATUS      current
   DESCRIPTION
      "Path: router1645.performance.interfaces.mibCounters.d7Performance.ifInErrors

       64 bit unsigned wrappable counter."
   ::= {pr1645v2InterfacesMibCountersD7PEntry 134217728}

pr1645v2InterfacesMibCountersD7PIfInUnkwn OBJECT-TYPE
   SYNTAX      Counter64
   MAX-ACCESS  read-only
   STATUS      current
   DESCRIPTION
      "Path: router1645.performance.interfaces.mibCounters.d7Performance.ifInUnknownProtos

       64 bit unsigned wrappable counter."
   ::= {pr1645v2InterfacesMibCountersD7PEntry 150994944}

pr1645v2InterfacesMibCountersD7PInDropEx OBJECT-TYPE
   SYNTAX      Counter64
   MAX-ACCESS  read-only
   STATUS      current
   DESCRIPTION
      "Path: router1645.performance.interfaces.mibCounters.d7Performance.ifInDropLevelExceeded

       64 bit unsigned wrappable counter."
   ::= {pr1645v2InterfacesMibCountersD7PEntry 335544320}

pr1645v2InterfacesMibCountersD7PInDropNoMac OBJECT-TYPE
   SYNTAX      Counter64
   MAX-ACCESS  read-only
   STATUS      current
   DESCRIPTION
      "Path: router1645.performance.interfaces.mibCounters.d7Performance.fInDiscardsNoMacFit

       64 bit unsigned wrappable counter."
   ::= {pr1645v2InterfacesMibCountersD7PEntry 301989888}

pr1645v2InterfacesMibCountersD7PInDropNUCast OBJECT-TYPE
   SYNTAX      Counter64
   MAX-ACCESS  read-only
   STATUS      current
   DESCRIPTION
      "Path: router1645.performance.interfaces.mibCounters.d7Performance.fInDiscardsNUCast

       64 bit unsigned wrappable counter."
   ::= {pr1645v2InterfacesMibCountersD7PEntry 318767104}

pr1645v2InterfacesMibCountersD7PInDropFilter OBJECT-TYPE
   SYNTAX      Counter64
   MAX-ACCESS  read-only
   STATUS      current
   DESCRIPTION
      "Path: router1645.performance.interfaces.mibCounters.d7Performance.fInDiscardsFilter

       64 bit unsigned wrappable counter."
   ::= {pr1645v2InterfacesMibCountersD7PEntry 385875968}

pr1645v2InterfacesMibCountersD7PIfInBandwidth OBJECT-TYPE
   SYNTAX      Integer32
   MAX-ACCESS  read-only
   STATUS      current
   DESCRIPTION
      "Path: router1645.performance.interfaces.mibCounters.d7Performance.ifInBandwidth

       unit name = bps
       formula = 8 * ; 8 /"
   ::= {pr1645v2InterfacesMibCountersD7PEntry 268435456}

pr1645v2InterfacesMibCountersD7PIfOutOctets OBJECT-TYPE
   SYNTAX      Counter64
   MAX-ACCESS  read-only
   STATUS      current
   DESCRIPTION
      "Path: router1645.performance.interfaces.mibCounters.d7Performance.ifOutOctets

       64 bit unsigned wrappable counter."
   ::= {pr1645v2InterfacesMibCountersD7PEntry 167772160}

pr1645v2InterfacesMibCountersD7PIfOutUCPkts OBJECT-TYPE
   SYNTAX      Counter64
   MAX-ACCESS  read-only
   STATUS      current
   DESCRIPTION
      "Path: router1645.performance.interfaces.mibCounters.d7Performance.ifOutUcastPkts

       64 bit unsigned wrappable counter."
   ::= {pr1645v2InterfacesMibCountersD7PEntry 184549376}

pr1645v2InterfacesMibCountersD7PIfOutNUCPkts OBJECT-TYPE
   SYNTAX      Counter64
   MAX-ACCESS  read-only
   STATUS      current
   DESCRIPTION
      "Path: router1645.performance.interfaces.mibCounters.d7Performance.ifOutNUcastPkts

       64 bit unsigned wrappable counter."
   ::= {pr1645v2InterfacesMibCountersD7PEntry 201326592}

pr1645v2InterfacesMibCountersD7PIfOutBCPkts OBJECT-TYPE
   SYNTAX      Counter64
   MAX-ACCESS  read-only
   STATUS      current
   DESCRIPTION
      "Path: router1645.performance.interfaces.mibCounters.d7Performance.ifOutBcastPkts

       64 bit unsigned wrappable counter."
   ::= {pr1645v2InterfacesMibCountersD7PEntry 452984832}

pr1645v2InterfacesMibCountersD7PIfOutMCPkts OBJECT-TYPE
   SYNTAX      Counter64
   MAX-ACCESS  read-only
   STATUS      current
   DESCRIPTION
      "Path: router1645.performance.interfaces.mibCounters.d7Performance.ifOutMcastPkts

       64 bit unsigned wrappable counter."
   ::= {pr1645v2InterfacesMibCountersD7PEntry 469762048}

pr1645v2InterfacesMibCountersD7PIfOutDiscards OBJECT-TYPE
   SYNTAX      Counter64
   MAX-ACCESS  read-only
   STATUS      current
   DESCRIPTION
      "Path: router1645.performance.interfaces.mibCounters.d7Performance.ifOutDiscards

       64 bit unsigned wrappable counter."
   ::= {pr1645v2InterfacesMibCountersD7PEntry 218103808}

pr1645v2InterfacesMibCountersD7PIfOutErrors OBJECT-TYPE
   SYNTAX      Counter64
   MAX-ACCESS  read-only
   STATUS      current
   DESCRIPTION
      "Path: router1645.performance.interfaces.mibCounters.d7Performance.ifOutErrors

       64 bit unsigned wrappable counter."
   ::= {pr1645v2InterfacesMibCountersD7PEntry 234881024}

pr1645v2InterfacesMibCountersD7POutDropEx OBJECT-TYPE
   SYNTAX      Counter64
   MAX-ACCESS  read-only
   STATUS      current
   DESCRIPTION
      "Path: router1645.performance.interfaces.mibCounters.d7Performance.ifOutDropLevelExceeded

       64 bit unsigned wrappable counter."
   ::= {pr1645v2InterfacesMibCountersD7PEntry 352321536}

pr1645v2InterfacesMibCountersD7POutDropNoArp OBJECT-TYPE
   SYNTAX      Counter64
   MAX-ACCESS  read-only
   STATUS      current
   DESCRIPTION
      "Path: router1645.performance.interfaces.mibCounters.d7Performance.ifOutDiscardsNoArp

       64 bit unsigned wrappable counter."
   ::= {pr1645v2InterfacesMibCountersD7PEntry 369098752}

pr1645v2InterfacesMibCountersD7POutDropFilter OBJECT-TYPE
   SYNTAX      Counter64
   MAX-ACCESS  read-only
   STATUS      current
   DESCRIPTION
      "Path: router1645.performance.interfaces.mibCounters.d7Performance.ifOutDiscardsFilter

       64 bit unsigned wrappable counter."
   ::= {pr1645v2InterfacesMibCountersD7PEntry 402653184}

pr1645v2InterfacesMibCountersD7PIfOutBandwidth OBJECT-TYPE
   SYNTAX      Integer32
   MAX-ACCESS  read-only
   STATUS      current
   DESCRIPTION
      "Path: router1645.performance.interfaces.mibCounters.d7Performance.ifOutBandwidth

       unit name = bps
       formula = 8 * ; 8 /"
   ::= {pr1645v2InterfacesMibCountersD7PEntry 285212672}

pr1645v2InterfacesMibCountersD7PIfErrSec OBJECT-TYPE
   SYNTAX      Counter32
   MAX-ACCESS  read-only
   STATUS      current
   DESCRIPTION
      "Path: router1645.performance.interfaces.mibCounters.d7Performance.ifErrSec

       32 bit unsigned wrappable counter."
   ::= {pr1645v2InterfacesMibCountersD7PEntry 251658240}

pr1645v2InterfacesIfInPriorityQueues OBJECT-TYPE
   SYNTAX      SEQUENCE OF Pr1645v2InterfacesIfInPriorityQueuesEntry
   MAX-ACCESS  not-accessible
   STATUS      current
   DESCRIPTION
      ""
   ::= {pr1645v2Interfaces 2197815296}

pr1645v2InterfacesIfInPriorityQueuesEntry OBJECT-TYPE
   SYNTAX      Pr1645v2InterfacesIfInPriorityQueuesEntry
   MAX-ACCESS  not-accessible
   STATUS      current
   DESCRIPTION
      ""
   INDEX      { pr1645v2InterfacesTableIx,
                pr1645v2InterfacesIfInPriorityQueuesTableIx }
   ::= {pr1645v2InterfacesIfInPriorityQueues 1}

Pr1645v2InterfacesIfInPriorityQueuesEntry ::=
   SEQUENCE
      {
      pr1645v2InterfacesIfInPriorityQueuesTableIx
         TableIndex,
      pr1645v2InterfacesIfInPriorityQueuesName
         INTEGER,
      pr1645v2InterfacesIfInPriorityQueuesLength
         Integer32,
      pr1645v2InterfacesIfInPriorityQueuesOctetLength
         Integer32,
      pr1645v2InterfacesIfInPriorityQueuesRedLength
         Integer32,
      pr1645v2InterfacesIfInPriorityQueuesPacketsTotal
         Counter64,
      pr1645v2InterfacesIfInPriorityQueuesPacketsDirectTx
         Counter64,
      pr1645v2InterfacesIfInPriorityQueuesPacketsQueued
         Counter64,
      pr1645v2InterfacesIfInPriorityQueuesPacketsDropped
         Counter64,
      pr1645v2InterfacesIfInPriorityQueuesPacketsRedDropped
         Counter64,
      pr1645v2InterfacesIfInPriorityQueuesPacketsCirTx
         Counter64,
      pr1645v2InterfacesIfInPriorityQueuesPacketsEirTx
         Counter64,
      pr1645v2InterfacesIfInPriorityQueuesPacketsViolateTx
         Counter64,
      pr1645v2InterfacesIfInPriorityQueuesOctetsTotal
         Counter64,
      pr1645v2InterfacesIfInPriorityQueuesOctetsDirectTx
         Counter64,
      pr1645v2InterfacesIfInPriorityQueuesOctetsQueued
         Counter64,
      pr1645v2InterfacesIfInPriorityQueuesOctetsDropped
         Counter64,
      pr1645v2InterfacesIfInPriorityQueuesOctetsRedDropped
         Counter64,
      pr1645v2InterfacesIfInPriorityQueuesOctetsCirTx
         Counter64,
      pr1645v2InterfacesIfInPriorityQueuesOctetsEirTx
         Counter64,
      pr1645v2InterfacesIfInPriorityQueuesOctetsViolateTx
         Counter64,
      pr1645v2InterfacesIfInPriorityQueuesOctetsBandwidth15sec
         Integer32,
      pr1645v2InterfacesIfInPriorityQueuesOctetsBandwidth30sec
         Integer32,
      pr1645v2InterfacesIfInPriorityQueuesOctetsBandwidth1min
         Integer32,
      pr1645v2InterfacesIfInPriorityQueuesOctetsBandwidth2min
         Integer32,
      pr1645v2InterfacesIfInPriorityQueuesOctetsBandwidth5min
         Integer32
      }

pr1645v2InterfacesIfInPriorityQueuesTableIx OBJECT-TYPE
   SYNTAX      TableIndex
   MAX-ACCESS  not-accessible
   STATUS      current
   DESCRIPTION
      ""
   ::= {pr1645v2InterfacesIfInPriorityQueuesEntry 11}

pr1645v2InterfacesIfInPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: router1645.performance.interfaces.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2InterfacesIfInPriorityQueuesEntry 16777216}

pr1645v2InterfacesIfInPriorityQueuesLength OBJECT-TYPE
   SYNTAX      Integer32
   MAX-ACCESS  read-only
   STATUS      current
   DESCRIPTION
      "Path: router1645.performance.interfaces.ifInPriorityQueues.length"
   ::= {pr1645v2InterfacesIfInPriorityQueuesEntry 33554432}

pr1645v2InterfacesIfInPriorityQueuesOctetLength OBJECT-TYPE
   SYNTAX      Integer32
   MAX-ACCESS  read-only
   STATUS      current
   DESCRIPTION
      "Path: router1645.performance.interfaces.ifInPriorityQueues.octetLength"
   ::= {pr1645v2InterfacesIfInPriorityQueuesEntry 150994944}

pr1645v2InterfacesIfInPriorityQueuesRedLength OBJECT-TYPE
   SYNTAX      Integer32
   MAX-ACCESS  read-only
   STATUS      current
   DESCRIPTION
      "Path: router1645.performance.interfaces.ifInPriorityQueues.redLength"
   ::= {pr1645v2InterfacesIfInPriorityQueuesEntry 134217728}

pr1645v2InterfacesIfInPriorityQueuesPacketsTotal OBJECT-TYPE
   SYNTAX      Counter64
   MAX-ACCESS  read-only
   STATUS      current
   DESCRIPTION
      "Path: router1645.performance.interfaces.ifInPriorityQueues.packets.total

       64 bit unsigned wrappable counter."
   ::= {pr1645v2InterfacesIfInPriorityQueuesEntry 50790400}

pr1645v2InterfacesIfInPriorityQueuesPacketsDirectTx OBJECT-TYPE
   SYNTAX      Counter64
   MAX-ACCESS  read-only
   STATUS      current
   DESCRIPTION
      "Path: router1645.performance.interfaces.ifInPriorityQueues.packets.directTx

       64 bit unsigned wrappable counter."
   ::= {pr1645v2InterfacesIfInPriorityQueuesEntry 50397184}

pr1645v2InterfacesIfInPriorityQueuesPacketsQueued OBJECT-TYPE
   SYNTAX      Counter64
   MAX-ACCESS  read-only
   STATUS      current
   DESCRIPTION
      "Path: router1645.performance.interfaces.ifInPriorityQueues.packets.queued

       64 bit unsigned wrappable counter."
   ::= {pr1645v2InterfacesIfInPriorityQueuesEntry 50462720}

pr1645v2InterfacesIfInPriorityQueuesPacketsDropped OBJECT-TYPE
   SYNTAX      Counter64
   MAX-ACCESS  read-only
   STATUS      current
   DESCRIPTION
      "Path: router1645.performance.interfaces.ifInPriorityQueues.packets.dropped

       64 bit unsigned wrappable counter."
   ::= {pr1645v2InterfacesIfInPriorityQueuesEntry 50528256}

pr1645v2InterfacesIfInPriorityQueuesPacketsRedDropped OBJECT-TYPE
   SYNTAX      Counter64
   MAX-ACCESS  read-only
   STATUS      current
   DESCRIPTION
      "Path: router1645.performance.interfaces.ifInPriorityQueues.packets.redDropped

       64 bit unsigned wrappable counter."
   ::= {pr1645v2InterfacesIfInPriorityQueuesEntry 50724864}

pr1645v2InterfacesIfInPriorityQueuesPacketsCirTx OBJECT-TYPE
   SYNTAX      Counter64
   MAX-ACCESS  read-only
   STATUS      current
   DESCRIPTION
      "Path: router1645.performance.interfaces.ifInPriorityQueues.packets.cirTx

       64 bit unsigned wrappable counter."
   ::= {pr1645v2InterfacesIfInPriorityQueuesEntry 50593792}

pr1645v2InterfacesIfInPriorityQueuesPacketsEirTx OBJECT-TYPE
   SYNTAX      Counter64
   MAX-ACCESS  read-only
   STATUS      current
   DESCRIPTION
      "Path: router1645.performance.interfaces.ifInPriorityQueues.packets.eirTx

       64 bit unsigned wrappable counter."
   ::= {pr1645v2InterfacesIfInPriorityQueuesEntry 50659328}

pr1645v2InterfacesIfInPriorityQueuesPacketsViolateTx OBJECT-TYPE
   SYNTAX      Counter64
   MAX-ACCESS  read-only
   STATUS      current
   DESCRIPTION
      "Path: router1645.performance.interfaces.ifInPriorityQueues.packets.violateTx

       64 bit unsigned wrappable counter."
   ::= {pr1645v2InterfacesIfInPriorityQueuesEntry 50855936}

pr1645v2InterfacesIfInPriorityQueuesOctetsTotal OBJECT-TYPE
   SYNTAX      Counter64
   MAX-ACCESS  read-only
   STATUS      current
   DESCRIPTION
      "Path: router1645.performance.interfaces.ifInPriorityQueues.octets.total

       64 bit unsigned wrappable counter."
   ::= {pr1645v2InterfacesIfInPriorityQueuesEntry 67567616}

pr1645v2InterfacesIfInPriorityQueuesOctetsDirectTx OBJECT-TYPE
   SYNTAX      Counter64
   MAX-ACCESS  read-only
   STATUS      current
   DESCRIPTION
      "Path: router1645.performance.interfaces.ifInPriorityQueues.octets.directTx

       64 bit unsigned wrappable counter."
   ::= {pr1645v2InterfacesIfInPriorityQueuesEntry 67174400}

pr1645v2InterfacesIfInPriorityQueuesOctetsQueued OBJECT-TYPE
   SYNTAX      Counter64
   MAX-ACCESS  read-only
   STATUS      current
   DESCRIPTION
      "Path: router1645.performance.interfaces.ifInPriorityQueues.octets.queued

       64 bit unsigned wrappable counter."
   ::= {pr1645v2InterfacesIfInPriorityQueuesEntry 67239936}

pr1645v2InterfacesIfInPriorityQueuesOctetsDropped OBJECT-TYPE
   SYNTAX      Counter64
   MAX-ACCESS  read-only
   STATUS      current
   DESCRIPTION
      "Path: router1645.performance.interfaces.ifInPriorityQueues.octets.dropped

       64 bit unsigned wrappable counter."
   ::= {pr1645v2InterfacesIfInPriorityQueuesEntry 67305472}

pr1645v2InterfacesIfInPriorityQueuesOctetsRedDropped OBJECT-TYPE
   SYNTAX      Counter64
   MAX-ACCESS  read-only
   STATUS      current
   DESCRIPTION
      "Path: router1645.performance.interfaces.ifInPriorityQueues.octets.redDropped

       64 bit unsigned wrappable counter."
   ::= {pr1645v2InterfacesIfInPriorityQueuesEntry 67502080}

pr1645v2InterfacesIfInPriorityQueuesOctetsCirTx OBJECT-TYPE
   SYNTAX      Counter64
   MAX-ACCESS  read-only
   STATUS      current
   DESCRIPTION
      "Path: router1645.performance.interfaces.ifInPriorityQueues.octets.cirTx

       64 bit unsigned wrappable counter."
   ::= {pr1645v2InterfacesIfInPriorityQueuesEntry 67371008}

pr1645v2InterfacesIfInPriorityQueuesOctetsEirTx OBJECT-TYPE
   SYNTAX      Counter64
   MAX-ACCESS  read-only
   STATUS      current
   DESCRIPTION
      "Path: router1645.performance.interfaces.ifInPriorityQueues.octets.eirTx

       64 bit unsigned wrappable counter."
   ::= {pr1645v2InterfacesIfInPriorityQueuesEntry 67436544}

pr1645v2InterfacesIfInPriorityQueuesOctetsViolateTx OBJECT-TYPE
   SYNTAX      Counter64
   MAX-ACCESS  read-only
   STATUS      current
   DESCRIPTION
      "Path: router1645.performance.interfaces.ifInPriorityQueues.octets.violateTx

       64 bit unsigned wrappable counter."
   ::= {pr1645v2InterfacesIfInPriorityQueuesEntry 67633152}

pr1645v2InterfacesIfInPriorityQueuesOctetsBandwidth15sec OBJECT-TYPE
   SYNTAX      Integer32
   MAX-ACCESS  read-only
   STATUS      current
   DESCRIPTION
      "Path: router1645.performance.interfaces.ifInPriorityQueues.octets.bandwidth.15sec

       unit name = bps
       formula = 8 * ; 8 /"
   ::= {pr1645v2InterfacesIfInPriorityQueuesEntry 70386944}

pr1645v2InterfacesIfInPriorityQueuesOctetsBandwidth30sec OBJECT-TYPE
   SYNTAX      Integer32
   MAX-ACCESS  read-only
   STATUS      current
   DESCRIPTION
      "Path: router1645.performance.interfaces.ifInPriorityQueues.octets.bandwidth.30sec

       unit name = bps
       formula = 8 * ; 8 /"
   ::= {pr1645v2InterfacesIfInPriorityQueuesEntry 70388224}

pr1645v2InterfacesIfInPriorityQueuesOctetsBandwidth1min OBJECT-TYPE
   SYNTAX      Integer32
   MAX-ACCESS  read-only
   STATUS      current
   DESCRIPTION
      "Path: router1645.performance.interfaces.ifInPriorityQueues.octets.bandwidth.1min

       unit name = bps
       formula = 8 * ; 8 /"
   ::= {pr1645v2InterfacesIfInPriorityQueuesEntry 70390784}

pr1645v2InterfacesIfInPriorityQueuesOctetsBandwidth2min OBJECT-TYPE
   SYNTAX      Integer32
   MAX-ACCESS  read-only
   STATUS      current
   DESCRIPTION
      "Path: router1645.performance.interfaces.ifInPriorityQueues.octets.bandwidth.2min

       unit name = bps
       formula = 8 * ; 8 /"
   ::= {pr1645v2InterfacesIfInPriorityQueuesEntry 70395904}

pr1645v2InterfacesIfInPriorityQueuesOctetsBandwidth5min OBJECT-TYPE
   SYNTAX      Integer32
   MAX-ACCESS  read-only
   STATUS      current
   DESCRIPTION
      "Path: router1645.performance.interfaces.ifInPriorityQueues.octets.bandwidth.5min

       unit name = bps
       formula = 8 * ; 8 /"
   ::= {pr1645v2InterfacesIfInPriorityQueuesEntry 70411264}

pr1645v2InterfacesIfInPriorityQueuesH2Performance OBJECT-TYPE
   SYNTAX      SEQUENCE OF Pr1645v2InterfacesIfInPriorityQueuesH2PerformanceEntry
   MAX-ACCESS  not-accessible
   STATUS      current
   DESCRIPTION
      ""
   ::= {pr1645v2Interfaces 2198142976}

pr1645v2InterfacesIfInPriorityQueuesH2PerformanceEntry OBJECT-TYPE
   SYNTAX      Pr1645v2InterfacesIfInPriorityQueuesH2PerformanceEntry
   MAX-ACCESS  not-accessible
   STATUS      current
   DESCRIPTION
      ""
   INDEX      { pr1645v2InterfacesTableIx,
                pr1645v2InterfacesIfInPriorityQueuesTableIx,
                pr1645v2InterfacesIfInPriorityQueuesH2PerformanceTableIx }
   ::= {pr1645v2InterfacesIfInPriorityQueuesH2Performance 1}

Pr1645v2InterfacesIfInPriorityQueuesH2PerformanceEntry ::=
   SEQUENCE
      {
      pr1645v2InterfacesIfInPriorityQueuesH2PerformanceTableIx
         TableIndex,
      pr1645v2InterfacesIfInPriorityQueuesH2PerformanceSysUpTime
         TimeTicks,
      pr1645v2InterfacesIfInPriorityQueuesH2PerformanceTotPkts
         Counter64,
      pr1645v2InterfacesIfInPriorityQueuesH2PerformanceDirTxPkts
         Counter64,
      pr1645v2InterfacesIfInPriorityQueuesH2PerformanceQdPkts
         Counter64,
      pr1645v2InterfacesIfInPriorityQueuesH2PerformanceDropPkts
         Counter64,
      pr1645v2InterfacesIfInPriorityQueuesH2PerformanceRDropPkts
         Counter64,
      pr1645v2InterfacesIfInPriorityQueuesH2PerformanceCirTxPkts
         Counter64,
      pr1645v2InterfacesIfInPriorityQueuesH2PerformanceEirTxPkts
         Counter64,
      pr1645v2InterfacesIfInPriorityQueuesH2PerformanceViolTxPkts
         Counter64,
      pr1645v2InterfacesIfInPriorityQueuesH2PerformanceTotOcts
         Counter64,
      pr1645v2InterfacesIfInPriorityQueuesH2PerformanceDirTxOcts
         Counter64,
      pr1645v2InterfacesIfInPriorityQueuesH2PerformanceQdOcts
         Counter64,
      pr1645v2InterfacesIfInPriorityQueuesH2PerformanceDropOcts
         Counter64,
      pr1645v2InterfacesIfInPriorityQueuesH2PerformanceRDropOcts
         Counter64,
      pr1645v2InterfacesIfInPriorityQueuesH2PerformanceCirTxOcts
         Counter64,
      pr1645v2InterfacesIfInPriorityQueuesH2PerformanceEirTxOcts
         Counter64,
      pr1645v2InterfacesIfInPriorityQueuesH2PerformanceViolTxOcts
         Counter64,
      pr1645v2InterfacesIfInPriorityQueuesH2PerformanceBandwidth
         Integer32
      }

pr1645v2InterfacesIfInPriorityQueuesH2PerformanceTableIx OBJECT-TYPE
   SYNTAX      TableIndex
   MAX-ACCESS  not-accessible
   STATUS      current
   DESCRIPTION
      ""
   ::= {pr1645v2InterfacesIfInPriorityQueuesH2PerformanceEntry 11}

pr1645v2InterfacesIfInPriorityQueuesH2PerformanceSysUpTime OBJECT-TYPE
   SYNTAX      TimeTicks
   MAX-ACCESS  read-only
   STATUS      current
   DESCRIPTION
      "Path: router1645.performance.interfaces.ifInPriorityQueues.h2Performance.sysUpTime

       Time in centi-second."
   ::= {pr1645v2InterfacesIfInPriorityQueuesH2PerformanceEntry 16777216}

pr1645v2InterfacesIfInPriorityQueuesH2PerformanceTotPkts OBJECT-TYPE
   SYNTAX      Counter64
   MAX-ACCESS  read-only
   STATUS      current
   DESCRIPTION
      "Path: router1645.performance.interfaces.ifInPriorityQueues.h2Performance.totalPkts

       64 bit unsigned wrappable counter."
   ::= {pr1645v2InterfacesIfInPriorityQueuesH2PerformanceEntry 234881024}

pr1645v2InterfacesIfInPriorityQueuesH2PerformanceDirTxPkts OBJECT-TYPE
   SYNTAX      Counter64
   MAX-ACCESS  read-only
   STATUS      current
   DESCRIPTION
      "Path: router1645.performance.interfaces.ifInPriorityQueues.h2Performance.directTxPkts

       64 bit unsigned wrappable counter."
   ::= {pr1645v2InterfacesIfInPriorityQueuesH2PerformanceEntry 33554432}

pr1645v2InterfacesIfInPriorityQueuesH2PerformanceQdPkts OBJECT-TYPE
   SYNTAX      Counter64
   MAX-ACCESS  read-only
   STATUS      current
   DESCRIPTION
      "Path: router1645.performance.interfaces.ifInPriorityQueues.h2Performance.queuedPkts

       64 bit unsigned wrappable counter."
   ::= {pr1645v2InterfacesIfInPriorityQueuesH2PerformanceEntry 50331648}

pr1645v2InterfacesIfInPriorityQueuesH2PerformanceDropPkts OBJECT-TYPE
   SYNTAX      Counter64
   MAX-ACCESS  read-only
   STATUS      current
   DESCRIPTION
      "Path: router1645.performance.interfaces.ifInPriorityQueues.h2Performance.droppedPkts

       64 bit unsigned wrappable counter."
   ::= {pr1645v2InterfacesIfInPriorityQueuesH2PerformanceEntry 67108864}

pr1645v2InterfacesIfInPriorityQueuesH2PerformanceRDropPkts OBJECT-TYPE
   SYNTAX      Counter64
   MAX-ACCESS  read-only
   STATUS      current
   DESCRIPTION
      "Path: router1645.performance.interfaces.ifInPriorityQueues.h2Performance.redDroppedPkts

       64 bit unsigned wrappable counter."
   ::= {pr1645v2InterfacesIfInPriorityQueuesH2PerformanceEntry 201326592}

pr1645v2InterfacesIfInPriorityQueuesH2PerformanceCirTxPkts OBJECT-TYPE
   SYNTAX      Counter64
   MAX-ACCESS  read-only
   STATUS      current
   DESCRIPTION
      "Path: router1645.performance.interfaces.ifInPriorityQueues.h2Performance.cirTxPkts

       64 bit unsigned wrappable counter."
   ::= {pr1645v2InterfacesIfInPriorityQueuesH2PerformanceEntry 83886080}

pr1645v2InterfacesIfInPriorityQueuesH2PerformanceEirTxPkts OBJECT-TYPE
   SYNTAX      Counter64
   MAX-ACCESS  read-only
   STATUS      current
   DESCRIPTION
      "Path: router1645.performance.interfaces.ifInPriorityQueues.h2Performance.eirTxPkts

       64 bit unsigned wrappable counter."
   ::= {pr1645v2InterfacesIfInPriorityQueuesH2PerformanceEntry 100663296}

pr1645v2InterfacesIfInPriorityQueuesH2PerformanceViolTxPkts OBJECT-TYPE
   SYNTAX      Counter64
   MAX-ACCESS  read-only
   STATUS      current
   DESCRIPTION
      "Path: router1645.performance.interfaces.ifInPriorityQueues.h2Performance.violateTxPkts

       64 bit unsigned wrappable counter."
   ::= {pr1645v2InterfacesIfInPriorityQueuesH2PerformanceEntry 301989888}

pr1645v2InterfacesIfInPriorityQueuesH2PerformanceTotOcts OBJECT-TYPE
   SYNTAX      Counter64
   MAX-ACCESS  read-only
   STATUS      current
   DESCRIPTION
      "Path: router1645.performance.interfaces.ifInPriorityQueues.h2Performance.totalOctets

       64 bit unsigned wrappable counter."
   ::= {pr1645v2InterfacesIfInPriorityQueuesH2PerformanceEntry 251658240}

pr1645v2InterfacesIfInPriorityQueuesH2PerformanceDirTxOcts OBJECT-TYPE
   SYNTAX      Counter64
   MAX-ACCESS  read-only
   STATUS      current
   DESCRIPTION
      "Path: router1645.performance.interfaces.ifInPriorityQueues.h2Performance.directTxOctets

       64 bit unsigned wrappable counter."
   ::= {pr1645v2InterfacesIfInPriorityQueuesH2PerformanceEntry 117440512}

pr1645v2InterfacesIfInPriorityQueuesH2PerformanceQdOcts OBJECT-TYPE
   SYNTAX      Counter64
   MAX-ACCESS  read-only
   STATUS      current
   DESCRIPTION
      "Path: router1645.performance.interfaces.ifInPriorityQueues.h2Performance.queuedOctets

       64 bit unsigned wrappable counter."
   ::= {pr1645v2InterfacesIfInPriorityQueuesH2PerformanceEntry 134217728}

pr1645v2InterfacesIfInPriorityQueuesH2PerformanceDropOcts OBJECT-TYPE
   SYNTAX      Counter64
   MAX-ACCESS  read-only
   STATUS      current
   DESCRIPTION
      "Path: router1645.performance.interfaces.ifInPriorityQueues.h2Performance.droppedOctets

       64 bit unsigned wrappable counter."
   ::= {pr1645v2InterfacesIfInPriorityQueuesH2PerformanceEntry 150994944}

pr1645v2InterfacesIfInPriorityQueuesH2PerformanceRDropOcts OBJECT-TYPE
   SYNTAX      Counter64
   MAX-ACCESS  read-only
   STATUS      current
   DESCRIPTION
      "Path: router1645.performance.interfaces.ifInPriorityQueues.h2Performance.redDroppedOctets

       64 bit unsigned wrappable counter."
   ::= {pr1645v2InterfacesIfInPriorityQueuesH2PerformanceEntry 218103808}

pr1645v2InterfacesIfInPriorityQueuesH2PerformanceCirTxOcts OBJECT-TYPE
   SYNTAX      Counter64
   MAX-ACCESS  read-only
   STATUS      current
   DESCRIPTION
      "Path: router1645.performance.interfaces.ifInPriorityQueues.h2Performance.cirTxOctets

       64 bit unsigned wrappable counter."
   ::= {pr1645v2InterfacesIfInPriorityQueuesH2PerformanceEntry 167772160}

pr1645v2InterfacesIfInPriorityQueuesH2PerformanceEirTxOcts OBJECT-TYPE
   SYNTAX      Counter64
   MAX-ACCESS  read-only
   STATUS      current
   DESCRIPTION
      "Path: router1645.performance.interfaces.ifInPriorityQueues.h2Performance.eirTxOctets

       64 bit unsigned wrappable counter."
   ::= {pr1645v2InterfacesIfInPriorityQueuesH2PerformanceEntry 184549376}

pr1645v2InterfacesIfInPriorityQueuesH2PerformanceViolTxOcts OBJECT-TYPE
   SYNTAX      Counter64
   MAX-ACCESS  read-only
   STATUS      current
   DESCRIPTION
      "Path: router1645.performance.interfaces.ifInPriorityQueues.h2Performance.violateTxOctets

       64 bit unsigned wrappable counter."
   ::= {pr1645v2InterfacesIfInPriorityQueuesH2PerformanceEntry 318767104}

pr1645v2InterfacesIfInPriorityQueuesH2PerformanceBandwidth OBJECT-TYPE
   SYNTAX      Integer32
   MAX-ACCESS  read-only
   STATUS      current
   DESCRIPTION
      "Path: router1645.performance.interfaces.ifInPriorityQueues.h2Performance.bandwidth

       unit name = bps
       formula = 8 * ; 8 /"
   ::= {pr1645v2InterfacesIfInPriorityQueuesH2PerformanceEntry 268435456}

pr1645v2InterfacesIfInPriorityQueuesH24Performance OBJECT-TYPE
   SYNTAX      SEQUENCE OF Pr1645v2InterfacesIfInPriorityQueuesH24PerformanceEntry
   MAX-ACCESS  not-accessible
   STATUS      current
   DESCRIPTION
      ""
   ::= {pr1645v2Interfaces 2198208512}

pr1645v2InterfacesIfInPriorityQueuesH24PerformanceEntry OBJECT-TYPE
   SYNTAX      Pr1645v2InterfacesIfInPriorityQueuesH24PerformanceEntry
   MAX-ACCESS  not-accessible
   STATUS      current
   DESCRIPTION
      ""
   INDEX      { pr1645v2InterfacesTableIx,
                pr1645v2InterfacesIfInPriorityQueuesTableIx,
                pr1645v2InterfacesIfInPriorityQueuesH24PerformanceTableIx }
   ::= {pr1645v2InterfacesIfInPriorityQueuesH24Performance 1}

Pr1645v2InterfacesIfInPriorityQueuesH24PerformanceEntry ::=
   SEQUENCE
      {
      pr1645v2InterfacesIfInPriorityQueuesH24PerformanceTableIx
         TableIndex,
      pr1645v2InterfacesIfInPriorityQueuesH24PerformanceSysUpTime
         TimeTicks,
      pr1645v2InterfacesIfInPriorityQueuesH24PerformanceTotPkts
         Counter64,
      pr1645v2InterfacesIfInPriorityQueuesH24PerformanceDirTxPkts
         Counter64,
      pr1645v2InterfacesIfInPriorityQueuesH24PerformanceQdPkts
         Counter64,
      pr1645v2InterfacesIfInPriorityQueuesH24PerformanceDropPkts
         Counter64,
      pr1645v2InterfacesIfInPriorityQueuesH24PerformanceRDropPkts
         Counter64,
      pr1645v2InterfacesIfInPriorityQueuesH24PerformanceCirTxPkts
         Counter64,
      pr1645v2InterfacesIfInPriorityQueuesH24PerformanceEirTxPkts
         Counter64,
      pr1645v2InterfacesIfInPriorityQueuesH24PerformanceViolTxPkts
         Counter64,
      pr1645v2InterfacesIfInPriorityQueuesH24PerformanceTotOcts
         Counter64,
      pr1645v2InterfacesIfInPriorityQueuesH24PerformanceDirTxOcts
         Counter64,
      pr1645v2InterfacesIfInPriorityQueuesH24PerformanceQdOcts
         Counter64,
      pr1645v2InterfacesIfInPriorityQueuesH24PerformanceDropOcts
         Counter64,
      pr1645v2InterfacesIfInPriorityQueuesH24PerformanceRDropOcts
         Counter64,
      pr1645v2InterfacesIfInPriorityQueuesH24PerformanceCirTxOcts
         Counter64,
      pr1645v2InterfacesIfInPriorityQueuesH24PerformanceEirTxOcts
         Counter64,
      pr1645v2InterfacesIfInPriorityQueuesH24PerformanceViolTxOcts
         Counter64,
      pr1645v2InterfacesIfInPriorityQueuesH24PerformanceBandwidth
         Integer32
      }

pr1645v2InterfacesIfInPriorityQueuesH24PerformanceTableIx OBJECT-TYPE
   SYNTAX      TableIndex
   MAX-ACCESS  not-accessible
   STATUS      current
   DESCRIPTION
      ""
   ::= {pr1645v2InterfacesIfInPriorityQueuesH24PerformanceEntry 11}

pr1645v2InterfacesIfInPriorityQueuesH24PerformanceSysUpTime OBJECT-TYPE
   SYNTAX      TimeTicks
   MAX-ACCESS  read-only
   STATUS      current
   DESCRIPTION
      "Path: router1645.performance.interfaces.ifInPriorityQueues.h24Performance.sysUpTime

       Time in centi-second."
   ::= {pr1645v2InterfacesIfInPriorityQueuesH24PerformanceEntry 16777216}

pr1645v2InterfacesIfInPriorityQueuesH24PerformanceTotPkts OBJECT-TYPE
   SYNTAX      Counter64
   MAX-ACCESS  read-only
   STATUS      current
   DESCRIPTION
      "Path: router1645.performance.interfaces.ifInPriorityQueues.h24Performance.totalPkts

       64 bit unsigned wrappable counter."
   ::= {pr1645v2InterfacesIfInPriorityQueuesH24PerformanceEntry 234881024}

pr1645v2InterfacesIfInPriorityQueuesH24PerformanceDirTxPkts OBJECT-TYPE
   SYNTAX      Counter64
   MAX-ACCESS  read-only
   STATUS      current
   DESCRIPTION
      "Path: router1645.performance.interfaces.ifInPriorityQueues.h24Performance.directTxPkts

       64 bit unsigned wrappable counter."
   ::= {pr1645v2InterfacesIfInPriorityQueuesH24PerformanceEntry 33554432}

pr1645v2InterfacesIfInPriorityQueuesH24PerformanceQdPkts OBJECT-TYPE
   SYNTAX      Counter64
   MAX-ACCESS  read-only
   STATUS      current
   DESCRIPTION
      "Path: router1645.performance.interfaces.ifInPriorityQueues.h24Performance.queuedPkts

       64 bit unsigned wrappable counter."
   ::= {pr1645v2InterfacesIfInPriorityQueuesH24PerformanceEntry 50331648}

pr1645v2InterfacesIfInPriorityQueuesH24PerformanceDropPkts OBJECT-TYPE
   SYNTAX      Counter64
   MAX-ACCESS  read-only
   STATUS      current
   DESCRIPTION
      "Path: router1645.performance.interfaces.ifInPriorityQueues.h24Performance.droppedPkts

       64 bit unsigned wrappable counter."
   ::= {pr1645v2InterfacesIfInPriorityQueuesH24PerformanceEntry 67108864}

pr1645v2InterfacesIfInPriorityQueuesH24PerformanceRDropPkts OBJECT-TYPE
   SYNTAX      Counter64
   MAX-ACCESS  read-only
   STATUS      current
   DESCRIPTION
      "Path: router1645.performance.interfaces.ifInPriorityQueues.h24Performance.redDroppedPkts

       64 bit unsigned wrappable counter."
   ::= {pr1645v2InterfacesIfInPriorityQueuesH24PerformanceEntry 201326592}

pr1645v2InterfacesIfInPriorityQueuesH24PerformanceCirTxPkts OBJECT-TYPE
   SYNTAX      Counter64
   MAX-ACCESS  read-only
   STATUS      current
   DESCRIPTION
      "Path: router1645.performance.interfaces.ifInPriorityQueues.h24Performance.cirTxPkts

       64 bit unsigned wrappable counter."
   ::= {pr1645v2InterfacesIfInPriorityQueuesH24PerformanceEntry 83886080}

pr1645v2InterfacesIfInPriorityQueuesH24PerformanceEirTxPkts OBJECT-TYPE
   SYNTAX      Counter64
   MAX-ACCESS  read-only
   STATUS      current
   DESCRIPTION
      "Path: router1645.performance.interfaces.ifInPriorityQueues.h24Performance.eirTxPkts

       64 bit unsigned wrappable counter."
   ::= {pr1645v2InterfacesIfInPriorityQueuesH24PerformanceEntry 100663296}

pr1645v2InterfacesIfInPriorityQueuesH24PerformanceViolTxPkts OBJECT-TYPE
   SYNTAX      Counter64
   MAX-ACCESS  read-only
   STATUS      current
   DESCRIPTION
      "Path: router1645.performance.interfaces.ifInPriorityQueues.h24Performance.violateTxPkts

       64 bit unsigned wrappable counter."
   ::= {pr1645v2InterfacesIfInPriorityQueuesH24PerformanceEntry 301989888}

pr1645v2InterfacesIfInPriorityQueuesH24PerformanceTotOcts OBJECT-TYPE
   SYNTAX      Counter64
   MAX-ACCESS  read-only
   STATUS      current
   DESCRIPTION
      "Path: router1645.performance.interfaces.ifInPriorityQueues.h24Performance.totalOctets

       64 bit unsigned wrappable counter."
   ::= {pr1645v2InterfacesIfInPriorityQueuesH24PerformanceEntry 251658240}

pr1645v2InterfacesIfInPriorityQueuesH24PerformanceDirTxOcts OBJECT-TYPE
   SYNTAX      Counter64
   MAX-ACCESS  read-only
   STATUS      current
   DESCRIPTION
      "Path: router1645.performance.interfaces.ifInPriorityQueues.h24Performance.directTxOctets

       64 bit unsigned wrappable counter."
   ::= {pr1645v2InterfacesIfInPriorityQueuesH24PerformanceEntry 117440512}

pr1645v2InterfacesIfInPriorityQueuesH24PerformanceQdOcts OBJECT-TYPE
   SYNTAX      Counter64
   MAX-ACCESS  read-only
   STATUS      current
   DESCRIPTION
      "Path: router1645.performance.interfaces.ifInPriorityQueues.h24Performance.queuedOctets

       64 bit unsigned wrappable counter."
   ::= {pr1645v2InterfacesIfInPriorityQueuesH24PerformanceEntry 134217728}

pr1645v2InterfacesIfInPriorityQueuesH24PerformanceDropOcts OBJECT-TYPE
   SYNTAX      Counter64
   MAX-ACCESS  read-only
   STATUS      current
   DESCRIPTION
      "Path: router1645.performance.interfaces.ifInPriorityQueues.h24Performance.droppedOctets

       64 bit unsigned wrappable counter."
   ::= {pr1645v2InterfacesIfInPriorityQueuesH24PerformanceEntry 150994944}

pr1645v2InterfacesIfInPriorityQueuesH24PerformanceRDropOcts OBJECT-TYPE
   SYNTAX      Counter64
   MAX-ACCESS  read-only
   STATUS      current
   DESCRIPTION
      "Path: router1645.performance.interfaces.ifInPriorityQueues.h24Performance.redDroppedOctets

       64 bit unsigned wrappable counter."
   ::= {pr1645v2InterfacesIfInPriorityQueuesH24PerformanceEntry 218103808}

pr1645v2InterfacesIfInPriorityQueuesH24PerformanceCirTxOcts OBJECT-TYPE
   SYNTAX      Counter64
   MAX-ACCESS  read-only
   STATUS      current
   DESCRIPTION
      "Path: router1645.performance.interfaces.ifInPriorityQueues.h24Performance.cirTxOctets

       64 bit unsigned wrappable counter."
   ::= {pr1645v2InterfacesIfInPriorityQueuesH24PerformanceEntry 167772160}

pr1645v2InterfacesIfInPriorityQueuesH24PerformanceEirTxOcts OBJECT-TYPE
   SYNTAX      Counter64
   MAX-ACCESS  read-only
   STATUS      current
   DESCRIPTION
      "Path: router1645.performance.interfaces.ifInPriorityQueues.h24Performance.eirTxOctets

       64 bit unsigned wrappable counter."
   ::= {pr1645v2InterfacesIfInPriorityQueuesH24PerformanceEntry 184549376}

pr1645v2InterfacesIfInPriorityQueuesH24PerformanceViolTxOcts OBJECT-TYPE
   SYNTAX      Counter64
   MAX-ACCESS  read-only
   STATUS      current
   DESCRIPTION
      "Path: router1645.performance.interfaces.ifInPriorityQueues.h24Performance.violateTxOctets

       64 bit unsigned wrappable counter."
   ::= {pr1645v2InterfacesIfInPriorityQueuesH24PerformanceEntry 318767104}

pr1645v2InterfacesIfInPriorityQueuesH24PerformanceBandwidth OBJECT-TYPE
   SYNTAX      Integer32
   MAX-ACCESS  read-only
   STATUS      current
   DESCRIPTION
      "Path: router1645.performance.interfaces.ifInPriorityQueues.h24Performance.bandwidth

       unit name = bps
       formula = 8 * ; 8 /"
   ::= {pr1645v2InterfacesIfInPriorityQueuesH24PerformanceEntry 268435456}

pr1645v2InterfacesIfInPriorityQueuesD7Performance OBJECT-TYPE
   SYNTAX      SEQUENCE OF Pr1645v2InterfacesIfInPriorityQueuesD7PerformanceEntry
   MAX-ACCESS  not-accessible
   STATUS      current
   DESCRIPTION
      ""
   ::= {pr1645v2Interfaces 2198274048}

pr1645v2InterfacesIfInPriorityQueuesD7PerformanceEntry OBJECT-TYPE
   SYNTAX      Pr1645v2InterfacesIfInPriorityQueuesD7PerformanceEntry
   MAX-ACCESS  not-accessible
   STATUS      current
   DESCRIPTION
      ""
   INDEX      { pr1645v2InterfacesTableIx,
                pr1645v2InterfacesIfInPriorityQueuesTableIx,
                pr1645v2InterfacesIfInPriorityQueuesD7PerformanceTableIx }
   ::= {pr1645v2InterfacesIfInPriorityQueuesD7Performance 1}

Pr1645v2InterfacesIfInPriorityQueuesD7PerformanceEntry ::=
   SEQUENCE
      {
      pr1645v2InterfacesIfInPriorityQueuesD7PerformanceTableIx
         TableIndex,
      pr1645v2InterfacesIfInPriorityQueuesD7PerformanceSysUpTime
         TimeTicks,
      pr1645v2InterfacesIfInPriorityQueuesD7PerformanceTotPkts
         Counter64,
      pr1645v2InterfacesIfInPriorityQueuesD7PerformanceDirTxPkts
         Counter64,
      pr1645v2InterfacesIfInPriorityQueuesD7PerformanceQdPkts
         Counter64,
      pr1645v2InterfacesIfInPriorityQueuesD7PerformanceDropPkts
         Counter64,
      pr1645v2InterfacesIfInPriorityQueuesD7PerformanceRDropPkts
         Counter64,
      pr1645v2InterfacesIfInPriorityQueuesD7PerformanceCirTxPkts
         Counter64,
      pr1645v2InterfacesIfInPriorityQueuesD7PerformanceEirTxPkts
         Counter64,
      pr1645v2InterfacesIfInPriorityQueuesD7PerformanceViolTxPkts
         Counter64,
      pr1645v2InterfacesIfInPriorityQueuesD7PerformanceTotOcts
         Counter64,
      pr1645v2InterfacesIfInPriorityQueuesD7PerformanceDirTxOcts
         Counter64,
      pr1645v2InterfacesIfInPriorityQueuesD7PerformanceQdOcts
         Counter64,
      pr1645v2InterfacesIfInPriorityQueuesD7PerformanceDropOcts
         Counter64,
      pr1645v2InterfacesIfInPriorityQueuesD7PerformanceRDropOcts
         Counter64,
      pr1645v2InterfacesIfInPriorityQueuesD7PerformanceCirTxOcts
         Counter64,
      pr1645v2InterfacesIfInPriorityQueuesD7PerformanceEirTxOcts
         Counter64,
      pr1645v2InterfacesIfInPriorityQueuesD7PerformanceViolTxOcts
         Counter64,
      pr1645v2InterfacesIfInPriorityQueuesD7PerformanceBandwidth
         Integer32
      }

pr1645v2InterfacesIfInPriorityQueuesD7PerformanceTableIx OBJECT-TYPE
   SYNTAX      TableIndex
   MAX-ACCESS  not-accessible
   STATUS      current
   DESCRIPTION
      ""
   ::= {pr1645v2InterfacesIfInPriorityQueuesD7PerformanceEntry 11}

pr1645v2InterfacesIfInPriorityQueuesD7PerformanceSysUpTime OBJECT-TYPE
   SYNTAX      TimeTicks
   MAX-ACCESS  read-only
   STATUS      current
   DESCRIPTION
      "Path: router1645.performance.interfaces.ifInPriorityQueues.d7Performance.sysUpTime

       Time in centi-second."
   ::= {pr1645v2InterfacesIfInPriorityQueuesD7PerformanceEntry 16777216}

pr1645v2InterfacesIfInPriorityQueuesD7PerformanceTotPkts OBJECT-TYPE
   SYNTAX      Counter64
   MAX-ACCESS  read-only
   STATUS      current
   DESCRIPTION
      "Path: router1645.performance.interfaces.ifInPriorityQueues.d7Performance.totalPkts

       64 bit unsigned wrappable counter."
   ::= {pr1645v2InterfacesIfInPriorityQueuesD7PerformanceEntry 234881024}

pr1645v2InterfacesIfInPriorityQueuesD7PerformanceDirTxPkts OBJECT-TYPE
   SYNTAX      Counter64
   MAX-ACCESS  read-only
   STATUS      current
   DESCRIPTION
      "Path: router1645.performance.interfaces.ifInPriorityQueues.d7Performance.directTxPkts

       64 bit unsigned wrappable counter."
   ::= {pr1645v2InterfacesIfInPriorityQueuesD7PerformanceEntry 33554432}

pr1645v2InterfacesIfInPriorityQueuesD7PerformanceQdPkts OBJECT-TYPE
   SYNTAX      Counter64
   MAX-ACCESS  read-only
   STATUS      current
   DESCRIPTION
      "Path: router1645.performance.interfaces.ifInPriorityQueues.d7Performance.queuedPkts

       64 bit unsigned wrappable counter."
   ::= {pr1645v2InterfacesIfInPriorityQueuesD7PerformanceEntry 50331648}

pr1645v2InterfacesIfInPriorityQueuesD7PerformanceDropPkts OBJECT-TYPE
   SYNTAX      Counter64
   MAX-ACCESS  read-only
   STATUS      current
   DESCRIPTION
      "Path: router1645.performance.interfaces.ifInPriorityQueues.d7Performance.droppedPkts

       64 bit unsigned wrappable counter."
   ::= {pr1645v2InterfacesIfInPriorityQueuesD7PerformanceEntry 67108864}

pr1645v2InterfacesIfInPriorityQueuesD7PerformanceRDropPkts OBJECT-TYPE
   SYNTAX      Counter64
   MAX-ACCESS  read-only
   STATUS      current
   DESCRIPTION
      "Path: router1645.performance.interfaces.ifInPriorityQueues.d7Performance.redDroppedPkts

       64 bit unsigned wrappable counter."
   ::= {pr1645v2InterfacesIfInPriorityQueuesD7PerformanceEntry 201326592}

pr1645v2InterfacesIfInPriorityQueuesD7PerformanceCirTxPkts OBJECT-TYPE
   SYNTAX      Counter64
   MAX-ACCESS  read-only
   STATUS      current
   DESCRIPTION
      "Path: router1645.performance.interfaces.ifInPriorityQueues.d7Performance.cirTxPkts

       64 bit unsigned wrappable counter."
   ::= {pr1645v2InterfacesIfInPriorityQueuesD7PerformanceEntry 83886080}

pr1645v2InterfacesIfInPriorityQueuesD7PerformanceEirTxPkts OBJECT-TYPE
   SYNTAX      Counter64
   MAX-ACCESS  read-only
   STATUS      current
   DESCRIPTION
      "Path: router1645.performance.interfaces.ifInPriorityQueues.d7Performance.eirTxPkts

       64 bit unsigned wrappable counter."
   ::= {pr1645v2InterfacesIfInPriorityQueuesD7PerformanceEntry 100663296}

pr1645v2InterfacesIfInPriorityQueuesD7PerformanceViolTxPkts OBJECT-TYPE
   SYNTAX      Counter64
   MAX-ACCESS  read-only
   STATUS      current
   DESCRIPTION
      "Path: router1645.performance.interfaces.ifInPriorityQueues.d7Performance.violateTxPkts

       64 bit unsigned wrappable counter."
   ::= {pr1645v2InterfacesIfInPriorityQueuesD7PerformanceEntry 301989888}

pr1645v2InterfacesIfInPriorityQueuesD7PerformanceTotOcts OBJECT-TYPE
   SYNTAX      Counter64
   MAX-ACCESS  read-only
   STATUS      current
   DESCRIPTION
      "Path: router1645.performance.interfaces.ifInPriorityQueues.d7Performance.totalOctets

       64 bit unsigned wrappable counter."
   ::= {pr1645v2InterfacesIfInPriorityQueuesD7PerformanceEntry 251658240}

pr1645v2InterfacesIfInPriorityQueuesD7PerformanceDirTxOcts OBJECT-TYPE
   SYNTAX      Counter64
   MAX-ACCESS  read-only
   STATUS      current
   DESCRIPTION
      "Path: router1645.performance.interfaces.ifInPriorityQueues.d7Performance.directTxOctets

       64 bit unsigned wrappable counter."
   ::= {pr1645v2InterfacesIfInPriorityQueuesD7PerformanceEntry 117440512}

pr1645v2InterfacesIfInPriorityQueuesD7PerformanceQdOcts OBJECT-TYPE
   SYNTAX      Counter64
   MAX-ACCESS  read-only
   STATUS      current
   DESCRIPTION
      "Path: router1645.performance.interfaces.ifInPriorityQueues.d7Performance.queuedOctets

       64 bit unsigned wrappable counter."
   ::= {pr1645v2InterfacesIfInPriorityQueuesD7PerformanceEntry 134217728}

pr1645v2InterfacesIfInPriorityQueuesD7PerformanceDropOcts OBJECT-TYPE
   SYNTAX      Counter64
   MAX-ACCESS  read-only
   STATUS      current
   DESCRIPTION
      "Path: router1645.performance.interfaces.ifInPriorityQueues.d7Performance.droppedOctets

       64 bit unsigned wrappable counter."
   ::= {pr1645v2InterfacesIfInPriorityQueuesD7PerformanceEntry 150994944}

pr1645v2InterfacesIfInPriorityQueuesD7PerformanceRDropOcts OBJECT-TYPE
   SYNTAX      Counter64
   MAX-ACCESS  read-only
   STATUS      current
   DESCRIPTION
      "Path: router1645.performance.interfaces.ifInPriorityQueues.d7Performance.redDroppedOctets

       64 bit unsigned wrappable counter."
   ::= {pr1645v2InterfacesIfInPriorityQueuesD7PerformanceEntry 218103808}

pr1645v2InterfacesIfInPriorityQueuesD7PerformanceCirTxOcts OBJECT-TYPE
   SYNTAX      Counter64
   MAX-ACCESS  read-only
   STATUS      current
   DESCRIPTION
      "Path: router1645.performance.interfaces.ifInPriorityQueues.d7Performance.cirTxOctets

       64 bit unsigned wrappable counter."
   ::= {pr1645v2InterfacesIfInPriorityQueuesD7PerformanceEntry 167772160}

pr1645v2InterfacesIfInPriorityQueuesD7PerformanceEirTxOcts OBJECT-TYPE
   SYNTAX      Counter64
   MAX-ACCESS  read-only
   STATUS      current
   DESCRIPTION
      "Path: router1645.performance.interfaces.ifInPriorityQueues.d7Performance.eirTxOctets

       64 bit unsigned wrappable counter."
   ::= {pr1645v2InterfacesIfInPriorityQueuesD7PerformanceEntry 184549376}

pr1645v2InterfacesIfInPriorityQueuesD7PerformanceViolTxOcts OBJECT-TYPE
   SYNTAX      Counter64
   MAX-ACCESS  read-only
   STATUS      current
   DESCRIPTION
      "Path: router1645.performance.interfaces.ifInPriorityQueues.d7Performance.violateTxOctets

       64 bit unsigned wrappable counter."
   ::= {pr1645v2InterfacesIfInPriorityQueuesD7PerformanceEntry 318767104}

pr1645v2InterfacesIfInPriorityQueuesD7PerformanceBandwidth OBJECT-TYPE
   SYNTAX      Integer32
   MAX-ACCESS  read-only
   STATUS      current
   DESCRIPTION
      "Path: router1645.performance.interfaces.ifInPriorityQueues.d7Performance.bandwidth

       unit name = bps
       formula = 8 * ; 8 /"
   ::= {pr1645v2InterfacesIfInPriorityQueuesD7PerformanceEntry 268435456}

pr1645v2InterfacesIfOutPriorityQueues OBJECT-TYPE
   SYNTAX      SEQUENCE OF Pr1645v2InterfacesIfOutPriorityQueuesEntry
   MAX-ACCESS  not-accessible
   STATUS      current
   DESCRIPTION
      ""
   ::= {pr1645v2Interfaces 2214592512}

pr1645v2InterfacesIfOutPriorityQueuesEntry OBJECT-TYPE
   SYNTAX      Pr1645v2InterfacesIfOutPriorityQueuesEntry
   MAX-ACCESS  not-accessible
   STATUS      current
   DESCRIPTION
      ""
   INDEX      { pr1645v2InterfacesTableIx,
                pr1645v2InterfacesIfOutPriorityQueuesTableIx }
   ::= {pr1645v2InterfacesIfOutPriorityQueues 1}

Pr1645v2InterfacesIfOutPriorityQueuesEntry ::=
   SEQUENCE
      {
      pr1645v2InterfacesIfOutPriorityQueuesTableIx
         TableIndex,
      pr1645v2InterfacesIfOutPriorityQueuesName
         INTEGER,
      pr1645v2InterfacesIfOutPriorityQueuesLength
         Integer32,
      pr1645v2InterfacesIfOutPriorityQueuesOctetLength
         Integer32,
      pr1645v2InterfacesIfOutPriorityQueuesRedLength
         Integer32,
      pr1645v2InterfacesIfOutPriorityQueuesPacketsTotal
         Counter64,
      pr1645v2InterfacesIfOutPriorityQueuesPacketsDirectTx
         Counter64,
      pr1645v2InterfacesIfOutPriorityQueuesPacketsQueued
         Counter64,
      pr1645v2InterfacesIfOutPriorityQueuesPacketsDropped
         Counter64,
      pr1645v2InterfacesIfOutPriorityQueuesPacketsRedDropped
         Counter64,
      pr1645v2InterfacesIfOutPriorityQueuesPacketsCirTx
         Counter64,
      pr1645v2InterfacesIfOutPriorityQueuesPacketsEirTx
         Counter64,
      pr1645v2InterfacesIfOutPriorityQueuesPacketsViolateTx
         Counter64,
      pr1645v2InterfacesIfOutPriorityQueuesOctetsTotal
         Counter64,
      pr1645v2InterfacesIfOutPriorityQueuesOctetsDirectTx
         Counter64,
      pr1645v2InterfacesIfOutPriorityQueuesOctetsQueued
         Counter64,
      pr1645v2InterfacesIfOutPriorityQueuesOctetsDropped
         Counter64,
      pr1645v2InterfacesIfOutPriorityQueuesOctetsRedDropped
         Counter64,
      pr1645v2InterfacesIfOutPriorityQueuesOctetsCirTx
         Counter64,
      pr1645v2InterfacesIfOutPriorityQueuesOctetsEirTx
         Counter64,
      pr1645v2InterfacesIfOutPriorityQueuesOctetsViolateTx
         Counter64,
      pr1645v2InterfacesIfOutPriorityQueuesOctetsBandwidth15sec
         Integer32,
      pr1645v2InterfacesIfOutPriorityQueuesOctetsBandwidth30sec
         Integer32,
      pr1645v2InterfacesIfOutPriorityQueuesOctetsBandwidth1min
         Integer32,
      pr1645v2InterfacesIfOutPriorityQueuesOctetsBandwidth2min
         Integer32,
      pr1645v2InterfacesIfOutPriorityQueuesOctetsBandwidth5min
         Integer32
      }

pr1645v2InterfacesIfOutPriorityQueuesTableIx OBJECT-TYPE
   SYNTAX      TableIndex
   MAX-ACCESS  not-accessible
   STATUS      current
   DESCRIPTION
      ""
   ::= {pr1645v2InterfacesIfOutPriorityQueuesEntry 11}

pr1645v2InterfacesIfOutPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: router1645.performance.interfaces.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2InterfacesIfOutPriorityQueuesEntry 16777216}

pr1645v2InterfacesIfOutPriorityQueuesLength OBJECT-TYPE
   SYNTAX      Integer32
   MAX-ACCESS  read-only
   STATUS      current
   DESCRIPTION
      "Path: router1645.performance.interfaces.ifOutPriorityQueues.length"
   ::= {pr1645v2InterfacesIfOutPriorityQueuesEntry 33554432}

pr1645v2InterfacesIfOutPriorityQueuesOctetLength OBJECT-TYPE
   SYNTAX      Integer32
   MAX-ACCESS  read-only
   STATUS      current
   DESCRIPTION
      "Path: router1645.performance.interfaces.ifOutPriorityQueues.octetLength"
   ::= {pr1645v2InterfacesIfOutPriorityQueuesEntry 150994944}

pr1645v2InterfacesIfOutPriorityQueuesRedLength OBJECT-TYPE
   SYNTAX      Integer32
   MAX-ACCESS  read-only
   STATUS      current
   DESCRIPTION
      "Path: router1645.performance.interfaces.ifOutPriorityQueues.redLength"
   ::= {pr1645v2InterfacesIfOutPriorityQueuesEntry 134217728}

pr1645v2InterfacesIfOutPriorityQueuesPacketsTotal OBJECT-TYPE
   SYNTAX      Counter64
   MAX-ACCESS  read-only
   STATUS      current
   DESCRIPTION
      "Path: router1645.performance.interfaces.ifOutPriorityQueues.packets.total

       64 bit unsigned wrappable counter."
   ::= {pr1645v2InterfacesIfOutPriorityQueuesEntry 50790400}

pr1645v2InterfacesIfOutPriorityQueuesPacketsDirectTx OBJECT-TYPE
   SYNTAX      Counter64
   MAX-ACCESS  read-only
   STATUS      current
   DESCRIPTION
      "Path: router1645.performance.interfaces.ifOutPriorityQueues.packets.directTx

       64 bit unsigned wrappable counter."
   ::= {pr1645v2InterfacesIfOutPriorityQueuesEntry 50397184}

pr1645v2InterfacesIfOutPriorityQueuesPacketsQueued OBJECT-TYPE
   SYNTAX      Counter64
   MAX-ACCESS  read-only
   STATUS      current
   DESCRIPTION
      "Path: router1645.performance.interfaces.ifOutPriorityQueues.packets.queued

       64 bit unsigned wrappable counter."
   ::= {pr1645v2InterfacesIfOutPriorityQueuesEntry 50462720}

pr1645v2InterfacesIfOutPriorityQueuesPacketsDropped OBJECT-TYPE
   SYNTAX      Counter64
   MAX-ACCESS  read-only
   STATUS      current
   DESCRIPTION
      "Path: router1645.performance.interfaces.ifOutPriorityQueues.packets.dropped

       64 bit unsigned wrappable counter."
   ::= {pr1645v2InterfacesIfOutPriorityQueuesEntry 50528256}

pr1645v2InterfacesIfOutPriorityQueuesPacketsRedDropped OBJECT-TYPE
   SYNTAX      Counter64
   MAX-ACCESS  read-only
   STATUS      current
   DESCRIPTION
      "Path: router1645.performance.interfaces.ifOutPriorityQueues.packets.redDropped

       64 bit unsigned wrappable counter."
   ::= {pr1645v2InterfacesIfOutPriorityQueuesEntry 50724864}

pr1645v2InterfacesIfOutPriorityQueuesPacketsCirTx OBJECT-TYPE
   SYNTAX      Counter64
   MAX-ACCESS  read-only
   STATUS      current
   DESCRIPTION
      "Path: router1645.performance.interfaces.ifOutPriorityQueues.packets.cirTx

       64 bit unsigned wrappable counter."
   ::= {pr1645v2InterfacesIfOutPriorityQueuesEntry 50593792}

pr1645v2InterfacesIfOutPriorityQueuesPacketsEirTx OBJECT-TYPE
   SYNTAX      Counter64
   MAX-ACCESS  read-only
   STATUS      current
   DESCRIPTION
      "Path: router1645.performance.interfaces.ifOutPriorityQueues.packets.eirTx

       64 bit unsigned wrappable counter."
   ::= {pr1645v2InterfacesIfOutPriorityQueuesEntry 50659328}

pr1645v2InterfacesIfOutPriorityQueuesPacketsViolateTx OBJECT-TYPE
   SYNTAX      Counter64
   MAX-ACCESS  read-only
   STATUS      current
   DESCRIPTION
      "Path: router1645.performance.interfaces.ifOutPriorityQueues.packets.violateTx

       64 bit unsigned wrappable counter."
   ::= {pr1645v2InterfacesIfOutPriorityQueuesEntry 50855936}

pr1645v2InterfacesIfOutPriorityQueuesOctetsTotal OBJECT-TYPE
   SYNTAX      Counter64
   MAX-ACCESS  read-only
   STATUS      current
   DESCRIPTION
      "Path: router1645.performance.interfaces.ifOutPriorityQueues.octets.total

       64 bit unsigned wrappable counter."
   ::= {pr1645v2InterfacesIfOutPriorityQueuesEntry 67567616}

pr1645v2InterfacesIfOutPriorityQueuesOctetsDirectTx OBJECT-TYPE
   SYNTAX      Counter64
   MAX-ACCESS  read-only
   STATUS      current
   DESCRIPTION
      "Path: router1645.performance.interfaces.ifOutPriorityQueues.octets.directTx

       64 bit unsigned wrappable counter."
   ::= {pr1645v2InterfacesIfOutPriorityQueuesEntry 67174400}

pr1645v2InterfacesIfOutPriorityQueuesOctetsQueued OBJECT-TYPE
   SYNTAX      Counter64
   MAX-ACCESS  read-only
   STATUS      current
   DESCRIPTION
      "Path: router1645.performance.interfaces.ifOutPriorityQueues.octets.queued

       64 bit unsigned wrappable counter."
   ::= {pr1645v2InterfacesIfOutPriorityQueuesEntry 67239936}

pr1645v2InterfacesIfOutPriorityQueuesOctetsDropped OBJECT-TYPE
   SYNTAX      Counter64
   MAX-ACCESS  read-only
   STATUS      current
   DESCRIPTION
      "Path: router1645.performance.interfaces.ifOutPriorityQueues.octets.dropped

       64 bit unsigned wrappable counter."
   ::= {pr1645v2InterfacesIfOutPriorityQueuesEntry 67305472}

pr1645v2InterfacesIfOutPriorityQueuesOctetsRedDropped OBJECT-TYPE
   SYNTAX      Counter64
   MAX-ACCESS  read-only
   STATUS      current
   DESCRIPTION
      "Path: router1645.performance.interfaces.ifOutPriorityQueues.octets.redDropped

       64 bit unsigned wrappable counter."
   ::= {pr1645v2InterfacesIfOutPriorityQueuesEntry 67502080}

pr1645v2InterfacesIfOutPriorityQueuesOctetsCirTx OBJECT-TYPE
   SYNTAX      Counter64
   MAX-ACCESS  read-only
   STATUS      current
   DESCRIPTION
      "Path: router1645.performance.interfaces.ifOutPriorityQueues.octets.cirTx

       64 bit unsigned wrappable counter."
   ::= {pr1645v2InterfacesIfOutPriorityQueuesEntry 67371008}

pr1645v2InterfacesIfOutPriorityQueuesOctetsEirTx OBJECT-TYPE
   SYNTAX      Counter64
   MAX-ACCESS  read-only
   STATUS      current
   DESCRIPTION
      "Path: router1645.performance.interfaces.ifOutPriorityQueues.octets.eirTx

       64 bit unsigned wrappable counter."
   ::= {pr1645v2InterfacesIfOutPriorityQueuesEntry 67436544}

pr1645v2InterfacesIfOutPriorityQueuesOctetsViolateTx OBJECT-TYPE
   SYNTAX      Counter64
   MAX-ACCESS  read-only
   STATUS      current
   DESCRIPTION
      "Path: router1645.performance.interfaces.ifOutPriorityQueues.octets.violateTx

       64 bit unsigned wrappable counter."
   ::= {pr1645v2InterfacesIfOutPriorityQueuesEntry 67633152}

pr1645v2InterfacesIfOutPriorityQueuesOctetsBandwidth15sec OBJECT-TYPE
   SYNTAX      Integer32
   MAX-ACCESS  read-only
   STATUS      current
   DESCRIPTION
      "Path: router1645.performance.interfaces.ifOutPriorityQueues.octets.bandwidth.15sec

       unit name = bps
       formula = 8 * ; 8 /"
   ::= {pr1645v2InterfacesIfOutPriorityQueuesEntry 70386944}

pr1645v2InterfacesIfOutPriorityQueuesOctetsBandwidth30sec OBJECT-TYPE
   SYNTAX      Integer32
   MAX-ACCESS  read-only
   STATUS      current
   DESCRIPTION
      "Path: router1645.performance.interfaces.ifOutPriorityQueues.octets.bandwidth.30sec

       unit name = bps
       formula = 8 * ; 8 /"
   ::= {pr1645v2InterfacesIfOutPriorityQueuesEntry 70388224}

pr1645v2InterfacesIfOutPriorityQueuesOctetsBandwidth1min OBJECT-TYPE
   SYNTAX      Integer32
   MAX-ACCESS  read-only
   STATUS      current
   DESCRIPTION
      "Path: router1645.performance.interfaces.ifOutPriorityQueues.octets.bandwidth.1min

       unit name = bps
       formula = 8 * ; 8 /"
   ::= {pr1645v2InterfacesIfOutPriorityQueuesEntry 70390784}

pr1645v2InterfacesIfOutPriorityQueuesOctetsBandwidth2min OBJECT-TYPE
   SYNTAX      Integer32
   MAX-ACCESS  read-only
   STATUS      current
   DESCRIPTION
      "Path: router1645.performance.interfaces.ifOutPriorityQueues.octets.bandwidth.2min

       unit name = bps
       formula = 8 * ; 8 /"
   ::= {pr1645v2InterfacesIfOutPriorityQueuesEntry 70395904}

pr1645v2InterfacesIfOutPriorityQueuesOctetsBandwidth5min OBJECT-TYPE
   SYNTAX      Integer32
   MAX-ACCESS  read-only
   STATUS      current
   DESCRIPTION
      "Path: router1645.performance.interfaces.ifOutPriorityQueues.octets.bandwidth.5min

       unit name = bps
       formula = 8 * ; 8 /"
   ::= {pr1645v2InterfacesIfOutPriorityQueuesEntry 70411264}

pr1645v2InterfacesIfOutPriorityQueuesH2Performance OBJECT-TYPE
   SYNTAX      SEQUENCE OF Pr1645v2InterfacesIfOutPriorityQueuesH2PerformanceEntry
   MAX-ACCESS  not-accessible
   STATUS      current
   DESCRIPTION
      ""
   ::= {pr1645v2Interfaces 2214920192}

pr1645v2InterfacesIfOutPriorityQueuesH2PerformanceEntry OBJECT-TYPE
   SYNTAX      Pr1645v2InterfacesIfOutPriorityQueuesH2PerformanceEntry
   MAX-ACCESS  not-accessible
   STATUS      current
   DESCRIPTION
      ""
   INDEX      { pr1645v2InterfacesTableIx,
                pr1645v2InterfacesIfOutPriorityQueuesTableIx,
                pr1645v2InterfacesIfOutPriorityQueuesH2PerformanceTableIx }
   ::= {pr1645v2InterfacesIfOutPriorityQueuesH2Performance 1}

Pr1645v2InterfacesIfOutPriorityQueuesH2PerformanceEntry ::=
   SEQUENCE
      {
      pr1645v2InterfacesIfOutPriorityQueuesH2PerformanceTableIx
         TableIndex,
      pr1645v2InterfacesIfOutPriorityQueuesH2PerformanceSysUpTime
         TimeTicks,
      pr1645v2InterfacesIfOutPriorityQueuesH2PerformanceTotPkts
         Counter64,
      pr1645v2InterfacesIfOutPriorityQueuesH2PerformanceDirTxPkts
         Counter64,
      pr1645v2InterfacesIfOutPriorityQueuesH2PerformanceQdPkts
         Counter64,
      pr1645v2InterfacesIfOutPriorityQueuesH2PerformanceDropPkts
         Counter64,
      pr1645v2InterfacesIfOutPriorityQueuesH2PerformanceRDropPkts
         Counter64,
      pr1645v2InterfacesIfOutPriorityQueuesH2PerformanceCirTxPkts
         Counter64,
      pr1645v2InterfacesIfOutPriorityQueuesH2PerformanceEirTxPkts
         Counter64,
      pr1645v2InterfacesIfOutPriorityQueuesH2PerformanceViolTxPkts
         Counter64,
      pr1645v2InterfacesIfOutPriorityQueuesH2PerformanceTotOcts
         Counter64,
      pr1645v2InterfacesIfOutPriorityQueuesH2PerformanceDirTxOcts
         Counter64,
      pr1645v2InterfacesIfOutPriorityQueuesH2PerformanceQdOcts
         Counter64,
      pr1645v2InterfacesIfOutPriorityQueuesH2PerformanceDropOcts
         Counter64,
      pr1645v2InterfacesIfOutPriorityQueuesH2PerformanceRDropOcts
         Counter64,
      pr1645v2InterfacesIfOutPriorityQueuesH2PerformanceCirTxOcts
         Counter64,
      pr1645v2InterfacesIfOutPriorityQueuesH2PerformanceEirTxOcts
         Counter64,
      pr1645v2InterfacesIfOutPriorityQueuesH2PerformanceViolTxOcts
         Counter64,
      pr1645v2InterfacesIfOutPriorityQueuesH2PerformanceBandwidth
         Integer32
      }

pr1645v2InterfacesIfOutPriorityQueuesH2PerformanceTableIx OBJECT-TYPE
   SYNTAX      TableIndex
   MAX-ACCESS  not-accessible
   STATUS      current
   DESCRIPTION
      ""
   ::= {pr1645v2InterfacesIfOutPriorityQueuesH2PerformanceEntry 11}

pr1645v2InterfacesIfOutPriorityQueuesH2PerformanceSysUpTime OBJECT-TYPE
   SYNTAX      TimeTicks
   MAX-ACCESS  read-only
   STATUS      current
   DESCRIPTION
      "Path: router1645.performance.interfaces.ifOutPriorityQueues.h2Performance.sysUpTime

       Time in centi-second."
   ::= {pr1645v2InterfacesIfOutPriorityQueuesH2PerformanceEntry 16777216}

pr1645v2InterfacesIfOutPriorityQueuesH2PerformanceTotPkts OBJECT-TYPE
   SYNTAX      Counter64
   MAX-ACCESS  read-only
   STATUS      current
   DESCRIPTION
      "Path: router1645.performance.interfaces.ifOutPriorityQueues.h2Performance.totalPkts

       64 bit unsigned wrappable counter."
   ::= {pr1645v2InterfacesIfOutPriorityQueuesH2PerformanceEntry 234881024}

pr1645v2InterfacesIfOutPriorityQueuesH2PerformanceDirTxPkts OBJECT-TYPE
   SYNTAX      Counter64
   MAX-ACCESS  read-only
   STATUS      current
   DESCRIPTION
      "Path: router1645.performance.interfaces.ifOutPriorityQueues.h2Performance.directTxPkts

       64 bit unsigned wrappable counter."
   ::= {pr1645v2InterfacesIfOutPriorityQueuesH2PerformanceEntry 33554432}

pr1645v2InterfacesIfOutPriorityQueuesH2PerformanceQdPkts OBJECT-TYPE
   SYNTAX      Counter64
   MAX-ACCESS  read-only
   STATUS      current
   DESCRIPTION
      "Path: router1645.performance.interfaces.ifOutPriorityQueues.h2Performance.queuedPkts

       64 bit unsigned wrappable counter."
   ::= {pr1645v2InterfacesIfOutPriorityQueuesH2PerformanceEntry 50331648}

pr1645v2InterfacesIfOutPriorityQueuesH2PerformanceDropPkts OBJECT-TYPE
   SYNTAX      Counter64
   MAX-ACCESS  read-only
   STATUS      current
   DESCRIPTION
      "Path: router1645.performance.interfaces.ifOutPriorityQueues.h2Performance.droppedPkts

       64 bit unsigned wrappable counter."
   ::= {pr1645v2InterfacesIfOutPriorityQueuesH2PerformanceEntry 67108864}

pr1645v2InterfacesIfOutPriorityQueuesH2PerformanceRDropPkts OBJECT-TYPE
   SYNTAX      Counter64
   MAX-ACCESS  read-only
   STATUS      current
   DESCRIPTION
      "Path: router1645.performance.interfaces.ifOutPriorityQueues.h2Performance.redDroppedPkts

       64 bit unsigned wrappable counter."
   ::= {pr1645v2InterfacesIfOutPriorityQueuesH2PerformanceEntry 201326592}

pr1645v2InterfacesIfOutPriorityQueuesH2PerformanceCirTxPkts OBJECT-TYPE
   SYNTAX      Counter64
   MAX-ACCESS  read-only
   STATUS      current
   DESCRIPTION
      "Path: router1645.performance.interfaces.ifOutPriorityQueues.h2Performance.cirTxPkts

       64 bit unsigned wrappable counter."
   ::= {pr1645v2InterfacesIfOutPriorityQueuesH2PerformanceEntry 83886080}

pr1645v2InterfacesIfOutPriorityQueuesH2PerformanceEirTxPkts OBJECT-TYPE
   SYNTAX      Counter64
   MAX-ACCESS  read-only
   STATUS      current
   DESCRIPTION
      "Path: router1645.performance.interfaces.ifOutPriorityQueues.h2Performance.eirTxPkts

       64 bit unsigned wrappable counter."
   ::= {pr1645v2InterfacesIfOutPriorityQueuesH2PerformanceEntry 100663296}

pr1645v2InterfacesIfOutPriorityQueuesH2PerformanceViolTxPkts OBJECT-TYPE
   SYNTAX      Counter64
   MAX-ACCESS  read-only
   STATUS      current
   DESCRIPTION
      "Path: router1645.performance.interfaces.ifOutPriorityQueues.h2Performance.violateTxPkts

       64 bit unsigned wrappable counter."
   ::= {pr1645v2InterfacesIfOutPriorityQueuesH2PerformanceEntry 301989888}

pr1645v2InterfacesIfOutPriorityQueuesH2PerformanceTotOcts OBJECT-TYPE
   SYNTAX      Counter64
   MAX-ACCESS  read-only
   STATUS      current
   DESCRIPTION
      "Path: router1645.performance.interfaces.ifOutPriorityQueues.h2Performance.totalOctets

       64 bit unsigned wrappable counter."
   ::= {pr1645v2InterfacesIfOutPriorityQueuesH2PerformanceEntry 251658240}

pr1645v2InterfacesIfOutPriorityQueuesH2PerformanceDirTxOcts OBJECT-TYPE
   SYNTAX      Counter64
   MAX-ACCESS  read-only
   STATUS      current
   DESCRIPTION
      "Path: router1645.performance.interfaces.ifOutPriorityQueues.h2Performance.directTxOctets

       64 bit unsigned wrappable counter."
   ::= {pr1645v2InterfacesIfOutPriorityQueuesH2PerformanceEntry 117440512}

pr1645v2InterfacesIfOutPriorityQueuesH2PerformanceQdOcts OBJECT-TYPE
   SYNTAX      Counter64
   MAX-ACCESS  read-only
   STATUS      current
   DESCRIPTION
      "Path: router1645.performance.interfaces.ifOutPriorityQueues.h2Performance.queuedOctets

       64 bit unsigned wrappable counter."
   ::= {pr1645v2InterfacesIfOutPriorityQueuesH2PerformanceEntry 134217728}

pr1645v2InterfacesIfOutPriorityQueuesH2PerformanceDropOcts OBJECT-TYPE
   SYNTAX      Counter64
   MAX-ACCESS  read-only
   STATUS      current
   DESCRIPTION
      "Path: router1645.performance.interfaces.ifOutPriorityQueues.h2Performance.droppedOctets

       64 bit unsigned wrappable counter."
   ::= {pr1645v2InterfacesIfOutPriorityQueuesH2PerformanceEntry 150994944}

pr1645v2InterfacesIfOutPriorityQueuesH2PerformanceRDropOcts OBJECT-TYPE
   SYNTAX      Counter64
   MAX-ACCESS  read-only
   STATUS      current
   DESCRIPTION
      "Path: router1645.performance.interfaces.ifOutPriorityQueues.h2Performance.redDroppedOctets

       64 bit unsigned wrappable counter."
   ::= {pr1645v2InterfacesIfOutPriorityQueuesH2PerformanceEntry 218103808}

pr1645v2InterfacesIfOutPriorityQueuesH2PerformanceCirTxOcts OBJECT-TYPE
   SYNTAX      Counter64
   MAX-ACCESS  read-only
   STATUS      current
   DESCRIPTION
      "Path: router1645.performance.interfaces.ifOutPriorityQueues.h2Performance.cirTxOctets

       64 bit unsigned wrappable counter."
   ::= {pr1645v2InterfacesIfOutPriorityQueuesH2PerformanceEntry 167772160}

pr1645v2InterfacesIfOutPriorityQueuesH2PerformanceEirTxOcts OBJECT-TYPE
   SYNTAX      Counter64
   MAX-ACCESS  read-only
   STATUS      current
   DESCRIPTION
      "Path: router1645.performance.interfaces.ifOutPriorityQueues.h2Performance.eirTxOctets

       64 bit unsigned wrappable counter."
   ::= {pr1645v2InterfacesIfOutPriorityQueuesH2PerformanceEntry 184549376}

pr1645v2InterfacesIfOutPriorityQueuesH2PerformanceViolTxOcts OBJECT-TYPE
   SYNTAX      Counter64
   MAX-ACCESS  read-only
   STATUS      current
   DESCRIPTION
      "Path: router1645.performance.interfaces.ifOutPriorityQueues.h2Performance.violateTxOctets

       64 bit unsigned wrappable counter."
   ::= {pr1645v2InterfacesIfOutPriorityQueuesH2PerformanceEntry 318767104}

pr1645v2InterfacesIfOutPriorityQueuesH2PerformanceBandwidth OBJECT-TYPE
   SYNTAX      Integer32
   MAX-ACCESS  read-only
   STATUS      current
   DESCRIPTION
      "Path: router1645.performance.interfaces.ifOutPriorityQueues.h2Performance.bandwidth

       unit name = bps
       formula = 8 * ; 8 /"
   ::= {pr1645v2InterfacesIfOutPriorityQueuesH2PerformanceEntry 268435456}

pr1645v2InterfacesIfOutPriorityQueuesH24Performance OBJECT-TYPE
   SYNTAX      SEQUENCE OF Pr1645v2InterfacesIfOutPriorityQueuesH24PerformanceEntry
   MAX-ACCESS  not-accessible
   STATUS      current
   DESCRIPTION
      ""
   ::= {pr1645v2Interfaces 2214985728}

pr1645v2InterfacesIfOutPriorityQueuesH24PerformanceEntry OBJECT-TYPE
   SYNTAX      Pr1645v2InterfacesIfOutPriorityQueuesH24PerformanceEntry
   MAX-ACCESS  not-accessible
   STATUS      current
   DESCRIPTION
      ""
   INDEX      { pr1645v2InterfacesTableIx,
                pr1645v2InterfacesIfOutPriorityQueuesTableIx,
                pr1645v2InterfacesIfOutPriorityQueuesH24PerformanceTableIx }
   ::= {pr1645v2InterfacesIfOutPriorityQueuesH24Performance 1}

Pr1645v2InterfacesIfOutPriorityQueuesH24PerformanceEntry ::=
   SEQUENCE
      {
      pr1645v2InterfacesIfOutPriorityQueuesH24PerformanceTableIx
         TableIndex,
      pr1645v2InterfacesIfOutPriorityQueuesH24PerformanceSysUpTime
         TimeTicks,
      pr1645v2InterfacesIfOutPriorityQueuesH24PerformanceTotPkts
         Counter64,
      pr1645v2InterfacesIfOutPriorityQueuesH24PerformanceDirTxPkts
         Counter64,
      pr1645v2InterfacesIfOutPriorityQueuesH24PerformanceQdPkts
         Counter64,
      pr1645v2InterfacesIfOutPriorityQueuesH24PerformanceDropPkts
         Counter64,
      pr1645v2InterfacesIfOutPriorityQueuesH24PerformanceRDropPkts
         Counter64,
      pr1645v2InterfacesIfOutPriorityQueuesH24PerformanceCirTxPkts
         Counter64,
      pr1645v2InterfacesIfOutPriorityQueuesH24PerformanceEirTxPkts
         Counter64,
      pr1645v2InterfacesIfOutPriorityQueuesH24PerformanceViolTxPkts
         Counter64,
      pr1645v2InterfacesIfOutPriorityQueuesH24PerformanceTotOcts
         Counter64,
      pr1645v2InterfacesIfOutPriorityQueuesH24PerformanceDirTxOcts
         Counter64,
      pr1645v2InterfacesIfOutPriorityQueuesH24PerformanceQdOcts
         Counter64,
      pr1645v2InterfacesIfOutPriorityQueuesH24PerformanceDropOcts
         Counter64,
      pr1645v2InterfacesIfOutPriorityQueuesH24PerformanceRDropOcts
         Counter64,
      pr1645v2InterfacesIfOutPriorityQueuesH24PerformanceCirTxOcts
         Counter64,
      pr1645v2InterfacesIfOutPriorityQueuesH24PerformanceEirTxOcts
         Counter64,
      pr1645v2InterfacesIfOutPriorityQueuesH24PerformanceViolTxOcts
         Counter64,
      pr1645v2InterfacesIfOutPriorityQueuesH24PerformanceBandwidth
         Integer32
      }

pr1645v2InterfacesIfOutPriorityQueuesH24PerformanceTableIx OBJECT-TYPE
   SYNTAX      TableIndex
   MAX-ACCESS  not-accessible
   STATUS      current
   DESCRIPTION
      ""
   ::= {pr1645v2InterfacesIfOutPriorityQueuesH24PerformanceEntry 11}

pr1645v2InterfacesIfOutPriorityQueuesH24PerformanceSysUpTime OBJECT-TYPE
   SYNTAX      TimeTicks
   MAX-ACCESS  read-only
   STATUS      current
   DESCRIPTION
      "Path: router1645.performance.interfaces.ifOutPriorityQueues.h24Performance.sysUpTime

       Time in centi-second."
   ::= {pr1645v2InterfacesIfOutPriorityQueuesH24PerformanceEntry 16777216}

pr1645v2InterfacesIfOutPriorityQueuesH24PerformanceTotPkts OBJECT-TYPE
   SYNTAX      Counter64
   MAX-ACCESS  read-only
   STATUS      current
   DESCRIPTION
      "Path: router1645.performance.interfaces.ifOutPriorityQueues.h24Performance.totalPkts

       64 bit unsigned wrappable counter."
   ::= {pr1645v2InterfacesIfOutPriorityQueuesH24PerformanceEntry 234881024}

pr1645v2InterfacesIfOutPriorityQueuesH24PerformanceDirTxPkts OBJECT-TYPE
   SYNTAX      Counter64
   MAX-ACCESS  read-only
   STATUS      current
   DESCRIPTION
      "Path: router1645.performance.interfaces.ifOutPriorityQueues.h24Performance.directTxPkts

       64 bit unsigned wrappable counter."
   ::= {pr1645v2InterfacesIfOutPriorityQueuesH24PerformanceEntry 33554432}

pr1645v2InterfacesIfOutPriorityQueuesH24PerformanceQdPkts OBJECT-TYPE
   SYNTAX      Counter64
   MAX-ACCESS  read-only
   STATUS      current
   DESCRIPTION
      "Path: router1645.performance.interfaces.ifOutPriorityQueues.h24Performance.queuedPkts

       64 bit unsigned wrappable counter."
   ::= {pr1645v2InterfacesIfOutPriorityQueuesH24PerformanceEntry 50331648}

pr1645v2InterfacesIfOutPriorityQueuesH24PerformanceDropPkts OBJECT-TYPE
   SYNTAX      Counter64
   MAX-ACCESS  read-only
   STATUS      current
   DESCRIPTION
      "Path: router1645.performance.interfaces.ifOutPriorityQueues.h24Performance.droppedPkts

       64 bit unsigned wrappable counter."
   ::= {pr1645v2InterfacesIfOutPriorityQueuesH24PerformanceEntry 67108864}

pr1645v2InterfacesIfOutPriorityQueuesH24PerformanceRDropPkts OBJECT-TYPE
   SYNTAX      Counter64
   MAX-ACCESS  read-only
   STATUS      current
   DESCRIPTION
      "Path: router1645.performance.interfaces.ifOutPriorityQueues.h24Performance.redDroppedPkts

       64 bit unsigned wrappable counter."
   ::= {pr1645v2InterfacesIfOutPriorityQueuesH24PerformanceEntry 201326592}

pr1645v2InterfacesIfOutPriorityQueuesH24PerformanceCirTxPkts OBJECT-TYPE
   SYNTAX      Counter64
   MAX-ACCESS  read-only
   STATUS      current
   DESCRIPTION
      "Path: router1645.performance.interfaces.ifOutPriorityQueues.h24Performance.cirTxPkts

       64 bit unsigned wrappable counter."
   ::= {pr1645v2InterfacesIfOutPriorityQueuesH24PerformanceEntry 83886080}

pr1645v2InterfacesIfOutPriorityQueuesH24PerformanceEirTxPkts OBJECT-TYPE
   SYNTAX      Counter64
   MAX-ACCESS  read-only
   STATUS      current
   DESCRIPTION
      "Path: router1645.performance.interfaces.ifOutPriorityQueues.h24Performance.eirTxPkts

       64 bit unsigned wrappable counter."
   ::= {pr1645v2InterfacesIfOutPriorityQueuesH24PerformanceEntry 100663296}

pr1645v2InterfacesIfOutPriorityQueuesH24PerformanceViolTxPkts OBJECT-TYPE
   SYNTAX      Counter64
   MAX-ACCESS  read-only
   STATUS      current
   DESCRIPTION
      "Path: router1645.performance.interfaces.ifOutPriorityQueues.h24Performance.violateTxPkts

       64 bit unsigned wrappable counter."
   ::= {pr1645v2InterfacesIfOutPriorityQueuesH24PerformanceEntry 301989888}

pr1645v2InterfacesIfOutPriorityQueuesH24PerformanceTotOcts OBJECT-TYPE
   SYNTAX      Counter64
   MAX-ACCESS  read-only
   STATUS      current
   DESCRIPTION
      "Path: router1645.performance.interfaces.ifOutPriorityQueues.h24Performance.totalOctets

       64 bit unsigned wrappable counter."
   ::= {pr1645v2InterfacesIfOutPriorityQueuesH24PerformanceEntry 251658240}

pr1645v2InterfacesIfOutPriorityQueuesH24PerformanceDirTxOcts OBJECT-TYPE
   SYNTAX      Counter64
   MAX-ACCESS  read-only
   STATUS      current
   DESCRIPTION
      "Path: router1645.performance.interfaces.ifOutPriorityQueues.h24Performance.directTxOctets

       64 bit unsigned wrappable counter."
   ::= {pr1645v2InterfacesIfOutPriorityQueuesH24PerformanceEntry 117440512}

pr1645v2InterfacesIfOutPriorityQueuesH24PerformanceQdOcts OBJECT-TYPE
   SYNTAX      Counter64
   MAX-ACCESS  read-only
   STATUS      current
   DESCRIPTION
      "Path: router1645.performance.interfaces.ifOutPriorityQueues.h24Performance.queuedOctets

       64 bit unsigned wrappable counter."
   ::= {pr1645v2InterfacesIfOutPriorityQueuesH24PerformanceEntry 134217728}

pr1645v2InterfacesIfOutPriorityQueuesH24PerformanceDropOcts OBJECT-TYPE
   SYNTAX      Counter64
   MAX-ACCESS  read-only
   STATUS      current
   DESCRIPTION
      "Path: router1645.performance.interfaces.ifOutPriorityQueues.h24Performance.droppedOctets

       64 bit unsigned wrappable counter."
   ::= {pr1645v2InterfacesIfOutPriorityQueuesH24PerformanceEntry 150994944}

pr1645v2InterfacesIfOutPriorityQueuesH24PerformanceRDropOcts OBJECT-TYPE
   SYNTAX      Counter64
   MAX-ACCESS  read-only
   STATUS      current
   DESCRIPTION
      "Path: router1645.performance.interfaces.ifOutPriorityQueues.h24Performance.redDroppedOctets

       64 bit unsigned wrappable counter."
   ::= {pr1645v2InterfacesIfOutPriorityQueuesH24PerformanceEntry 218103808}

pr1645v2InterfacesIfOutPriorityQueuesH24PerformanceCirTxOcts OBJECT-TYPE
   SYNTAX      Counter64
   MAX-ACCESS  read-only
   STATUS      current
   DESCRIPTION
      "Path: router1645.performance.interfaces.ifOutPriorityQueues.h24Performance.cirTxOctets

       64 bit unsigned wrappable counter."
   ::= {pr1645v2InterfacesIfOutPriorityQueuesH24PerformanceEntry 167772160}

pr1645v2InterfacesIfOutPriorityQueuesH24PerformanceEirTxOcts OBJECT-TYPE
   SYNTAX      Counter64
   MAX-ACCESS  read-only
   STATUS      current
   DESCRIPTION
      "Path: router1645.performance.interfaces.ifOutPriorityQueues.h24Performance.eirTxOctets

       64 bit unsigned wrappable counter."
   ::= {pr1645v2InterfacesIfOutPriorityQueuesH24PerformanceEntry 184549376}

pr1645v2InterfacesIfOutPriorityQueuesH24PerformanceViolTxOcts OBJECT-TYPE
   SYNTAX      Counter64
   MAX-ACCESS  read-only
   STATUS      current
   DESCRIPTION
      "Path: router1645.performance.interfaces.ifOutPriorityQueues.h24Performance.violateTxOctets

       64 bit unsigned wrappable counter."
   ::= {pr1645v2InterfacesIfOutPriorityQueuesH24PerformanceEntry 318767104}

pr1645v2InterfacesIfOutPriorityQueuesH24PerformanceBandwidth OBJECT-TYPE
   SYNTAX      Integer32
   MAX-ACCESS  read-only
   STATUS      current
   DESCRIPTION
      "Path: router1645.performance.interfaces.ifOutPriorityQueues.h24Performance.bandwidth

       unit name = bps
       formula = 8 * ; 8 /"
   ::= {pr1645v2InterfacesIfOutPriorityQueuesH24PerformanceEntry 268435456}

pr1645v2InterfacesIfOutPriorityQueuesD7Performance OBJECT-TYPE
   SYNTAX      SEQUENCE OF Pr1645v2InterfacesIfOutPriorityQueuesD7PerformanceEntry
   MAX-ACCESS  not-accessible
   STATUS      current
   DESCRIPTION
      ""
   ::= {pr1645v2Interfaces 2215051264}

pr1645v2InterfacesIfOutPriorityQueuesD7PerformanceEntry OBJECT-TYPE
   SYNTAX      Pr1645v2InterfacesIfOutPriorityQueuesD7PerformanceEntry
   MAX-ACCESS  not-accessible
   STATUS      current
   DESCRIPTION
      ""
   INDEX      { pr1645v2InterfacesTableIx,
                pr1645v2InterfacesIfOutPriorityQueuesTableIx,
                pr1645v2InterfacesIfOutPriorityQueuesD7PerformanceTableIx }
   ::= {pr1645v2InterfacesIfOutPriorityQueuesD7Performance 1}

Pr1645v2InterfacesIfOutPriorityQueuesD7PerformanceEntry ::=
   SEQUENCE
      {
      pr1645v2InterfacesIfOutPriorityQueuesD7PerformanceTableIx
         TableIndex,
      pr1645v2InterfacesIfOutPriorityQueuesD7PerformanceSysUpTime
         TimeTicks,
      pr1645v2InterfacesIfOutPriorityQueuesD7PerformanceTotPkts
         Counter64,
      pr1645v2InterfacesIfOutPriorityQueuesD7PerformanceDirTxPkts
         Counter64,
      pr1645v2InterfacesIfOutPriorityQueuesD7PerformanceQdPkts
         Counter64,
      pr1645v2InterfacesIfOutPriorityQueuesD7PerformanceDropPkts
         Counter64,
      pr1645v2InterfacesIfOutPriorityQueuesD7PerformanceRDropPkts
         Counter64,
      pr1645v2InterfacesIfOutPriorityQueuesD7PerformanceCirTxPkts
         Counter64,
      pr1645v2InterfacesIfOutPriorityQueuesD7PerformanceEirTxPkts
         Counter64,
      pr1645v2InterfacesIfOutPriorityQueuesD7PerformanceViolTxPkts
         Counter64,
      pr1645v2InterfacesIfOutPriorityQueuesD7PerformanceTotOcts
         Counter64,
      pr1645v2InterfacesIfOutPriorityQueuesD7PerformanceDirTxOcts
         Counter64,
      pr1645v2InterfacesIfOutPriorityQueuesD7PerformanceQdOcts
         Counter64,
      pr1645v2InterfacesIfOutPriorityQueuesD7PerformanceDropOcts
         Counter64,
      pr1645v2InterfacesIfOutPriorityQueuesD7PerformanceRDropOcts
         Counter64,
      pr1645v2InterfacesIfOutPriorityQueuesD7PerformanceCirTxOcts
         Counter64,
      pr1645v2InterfacesIfOutPriorityQueuesD7PerformanceEirTxOcts
         Counter64,
      pr1645v2InterfacesIfOutPriorityQueuesD7PerformanceViolTxOcts
         Counter64,
      pr1645v2InterfacesIfOutPriorityQueuesD7PerformanceBandwidth
         Integer32
      }

pr1645v2InterfacesIfOutPriorityQueuesD7PerformanceTableIx OBJECT-TYPE
   SYNTAX      TableIndex
   MAX-ACCESS  not-accessible
   STATUS      current
   DESCRIPTION
      ""
   ::= {pr1645v2InterfacesIfOutPriorityQueuesD7PerformanceEntry 11}

pr1645v2InterfacesIfOutPriorityQueuesD7PerformanceSysUpTime OBJECT-TYPE
   SYNTAX      TimeTicks
   MAX-ACCESS  read-only
   STATUS      current
   DESCRIPTION
      "Path: router1645.performance.interfaces.ifOutPriorityQueues.d7Performance.sysUpTime

       Time in centi-second."
   ::= {pr1645v2InterfacesIfOutPriorityQueuesD7PerformanceEntry 16777216}

pr1645v2InterfacesIfOutPriorityQueuesD7PerformanceTotPkts OBJECT-TYPE
   SYNTAX      Counter64
   MAX-ACCESS  read-only
   STATUS      current
   DESCRIPTION
      "Path: router1645.performance.interfaces.ifOutPriorityQueues.d7Performance.totalPkts

       64 bit unsigned wrappable counter."
   ::= {pr1645v2InterfacesIfOutPriorityQueuesD7PerformanceEntry 234881024}

pr1645v2InterfacesIfOutPriorityQueuesD7PerformanceDirTxPkts OBJECT-TYPE
   SYNTAX      Counter64
   MAX-ACCESS  read-only
   STATUS      current
   DESCRIPTION
      "Path: router1645.performance.interfaces.ifOutPriorityQueues.d7Performance.directTxPkts

       64 bit unsigned wrappable counter."
   ::= {pr1645v2InterfacesIfOutPriorityQueuesD7PerformanceEntry 33554432}

pr1645v2InterfacesIfOutPriorityQueuesD7PerformanceQdPkts OBJECT-TYPE
   SYNTAX      Counter64
   MAX-ACCESS  read-only
   STATUS      current
   DESCRIPTION
      "Path: router1645.performance.interfaces.ifOutPriorityQueues.d7Performance.queuedPkts

       64 bit unsigned wrappable counter."
   ::= {pr1645v2InterfacesIfOutPriorityQueuesD7PerformanceEntry 50331648}

pr1645v2InterfacesIfOutPriorityQueuesD7PerformanceDropPkts OBJECT-TYPE
   SYNTAX      Counter64
   MAX-ACCESS  read-only
   STATUS      current
   DESCRIPTION
      "Path: router1645.performance.interfaces.ifOutPriorityQueues.d7Performance.droppedPkts

       64 bit unsigned wrappable counter."
   ::= {pr1645v2InterfacesIfOutPriorityQueuesD7PerformanceEntry 67108864}

pr1645v2InterfacesIfOutPriorityQueuesD7PerformanceRDropPkts OBJECT-TYPE
   SYNTAX      Counter64
   MAX-ACCESS  read-only
   STATUS      current
   DESCRIPTION
      "Path: router1645.performance.interfaces.ifOutPriorityQueues.d7Performance.redDroppedPkts

       64 bit unsigned wrappable counter."
   ::= {pr1645v2InterfacesIfOutPriorityQueuesD7PerformanceEntry 201326592}

pr1645v2InterfacesIfOutPriorityQueuesD7PerformanceCirTxPkts OBJECT-TYPE
   SYNTAX      Counter64
   MAX-ACCESS  read-only
   STATUS      current
   DESCRIPTION
      "Path: router1645.performance.interfaces.ifOutPriorityQueues.d7Performance.cirTxPkts

       64 bit unsigned wrappable counter."
   ::= {pr1645v2InterfacesIfOutPriorityQueuesD7PerformanceEntry 83886080}

pr1645v2InterfacesIfOutPriorityQueuesD7PerformanceEirTxPkts OBJECT-TYPE
   SYNTAX      Counter64
   MAX-ACCESS  read-only
   STATUS      current
   DESCRIPTION
      "Path: router1645.performance.interfaces.ifOutPriorityQueues.d7Performance.eirTxPkts

       64 bit unsigned wrappable counter."
   ::= {pr1645v2InterfacesIfOutPriorityQueuesD7PerformanceEntry 100663296}

pr1645v2InterfacesIfOutPriorityQueuesD7PerformanceViolTxPkts OBJECT-TYPE
   SYNTAX      Counter64
   MAX-ACCESS  read-only
   STATUS      current
   DESCRIPTION
      "Path: router1645.performance.interfaces.ifOutPriorityQueues.d7Performance.violateTxPkts

       64 bit unsigned wrappable counter."
   ::= {pr1645v2InterfacesIfOutPriorityQueuesD7PerformanceEntry 301989888}

pr1645v2InterfacesIfOutPriorityQueuesD7PerformanceTotOcts OBJECT-TYPE
   SYNTAX      Counter64
   MAX-ACCESS  read-only
   STATUS      current
   DESCRIPTION
      "Path: router1645.performance.interfaces.ifOutPriorityQueues.d7Performance.totalOctets

       64 bit unsigned wrappable counter."
   ::= {pr1645v2InterfacesIfOutPriorityQueuesD7PerformanceEntry 251658240}

pr1645v2InterfacesIfOutPriorityQueuesD7PerformanceDirTxOcts OBJECT-TYPE
   SYNTAX      Counter64
   MAX-ACCESS  read-only
   STATUS      current
   DESCRIPTION
      "Path: router1645.performance.interfaces.ifOutPriorityQueues.d7Performance.directTxOctets

       64 bit unsigned wrappable counter."
   ::= {pr1645v2InterfacesIfOutPriorityQueuesD7PerformanceEntry 117440512}

pr1645v2InterfacesIfOutPriorityQueuesD7PerformanceQdOcts OBJECT-TYPE
   SYNTAX      Counter64
   MAX-ACCESS  read-only
   STATUS      current
   DESCRIPTION
      "Path: router1645.performance.interfaces.ifOutPriorityQueues.d7Performance.queuedOctets

       64 bit unsigned wrappable counter."
   ::= {pr1645v2InterfacesIfOutPriorityQueuesD7PerformanceEntry 134217728}

pr1645v2InterfacesIfOutPriorityQueuesD7PerformanceDropOcts OBJECT-TYPE
   SYNTAX      Counter64
   MAX-ACCESS  read-only
   STATUS      current
   DESCRIPTION
      "Path: router1645.performance.interfaces.ifOutPriorityQueues.d7Performance.droppedOctets

       64 bit unsigned wrappable counter."
   ::= {pr1645v2InterfacesIfOutPriorityQueuesD7PerformanceEntry 150994944}

pr1645v2InterfacesIfOutPriorityQueuesD7PerformanceRDropOcts OBJECT-TYPE
   SYNTAX      Counter64
   MAX-ACCESS  read-only
   STATUS      current
   DESCRIPTION
      "Path: router1645.performance.interfaces.ifOutPriorityQueues.d7Performance.redDroppedOctets

       64 bit unsigned wrappable counter."
   ::= {pr1645v2InterfacesIfOutPriorityQueuesD7PerformanceEntry 218103808}

pr1645v2InterfacesIfOutPriorityQueuesD7PerformanceCirTxOcts OBJECT-TYPE
   SYNTAX      Counter64
   MAX-ACCESS  read-only
   STATUS      current
   DESCRIPTION
      "Path: router1645.performance.interfaces.ifOutPriorityQueues.d7Performance.cirTxOctets

       64 bit unsigned wrappable counter."
   ::= {pr1645v2InterfacesIfOutPriorityQueuesD7PerformanceEntry 167772160}

pr1645v2InterfacesIfOutPriorityQueuesD7PerformanceEirTxOcts OBJECT-TYPE
   SYNTAX      Counter64
   MAX-ACCESS  read-only
   STATUS      current
   DESCRIPTION
      "Path: router1645.performance.interfaces.ifOutPriorityQueues.d7Performance.eirTxOctets

       64 bit unsigned wrappable counter."
   ::= {pr1645v2InterfacesIfOutPriorityQueuesD7PerformanceEntry 184549376}

pr1645v2InterfacesIfOutPriorityQueuesD7PerformanceViolTxOcts OBJECT-TYPE
   SYNTAX      Counter64
   MAX-ACCESS  read-only
   STATUS      current
   DESCRIPTION
      "Path: router1645.performance.interfaces.ifOutPriorityQueues.d7Performance.violateTxOctets

       64 bit unsigned wrappable counter."
   ::= {pr1645v2InterfacesIfOutPriorityQueuesD7PerformanceEntry 318767104}

pr1645v2InterfacesIfOutPriorityQueuesD7PerformanceBandwidth OBJECT-TYPE
   SYNTAX      Integer32
   MAX-ACCESS  read-only
   STATUS      current
   DESCRIPTION
      "Path: router1645.performance.interfaces.ifOutPriorityQueues.d7Performance.bandwidth

       unit name = bps
       formula = 8 * ; 8 /"
   ::= {pr1645v2InterfacesIfOutPriorityQueuesD7PerformanceEntry 268435456}



END
