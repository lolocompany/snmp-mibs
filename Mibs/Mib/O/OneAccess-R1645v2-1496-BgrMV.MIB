OneAccess-R1645v2-1496-BgrMV DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2BgrMV OBJECT IDENTIFIER ::= {r1645Rootv2 1496}

r1645v2BgrMVMOProp OBJECT IDENTIFIER ::= {r1645v2BgrMV 1}

r1645v2BgrMVMOPropEntry OBJECT IDENTIFIER ::= {r1645v2BgrMVMOProp 1}

r1645v2BgrMVMOPropPath OBJECT-TYPE
   SYNTAX      ContainmentPath
   MAX-ACCESS  read-only
   STATUS      current
   DESCRIPTION
      "Textual description of the containment tree from the instance of
       the root object down to the instance of the current object."
   ::= {r1645v2BgrMVMOPropEntry 3}

r1645v2BgrMVMOPropRev OBJECT-TYPE
   SYNTAX      ObjectRevision
   MAX-ACCESS  read-only
   STATUS      current
   DESCRIPTION
      "This value corresponds with the revision of the MANAGED OBJECT."
   ::= {r1645v2BgrMVMOPropEntry 4}



er1645v2BgrMV OBJECT IDENTIFIER ::= {r1645v2BgrMV 11}


er1645v2BgrMVBridgeCache OBJECT-TYPE
   SYNTAX      INTEGER
               {
               disabled (0),
               learning (1),
               switching (2)
               }
   MAX-ACCESS  read-write
   STATUS      current
   DESCRIPTION
      "Path: bridgeGroup.editConf.bridgeCache
       Info: used for bridgeCache

       Possibilities:
               disabled   (0)
               learning   (1)
               switching   (2)"
   ::= {er1645v2BgrMV 10}


er1645v2BgrMVMaxCacheSize OBJECT-TYPE
   SYNTAX      INTEGER
               {
               unlimited (0)
               }
   MAX-ACCESS  read-write
   STATUS      current
   DESCRIPTION
      "Path: bridgeGroup.editConf.maxCacheSize
       Info: used for size of bridgeCache

       Possibilities:
               unlimited   (0)"
   ::= {er1645v2BgrMV 38}


er1645v2BgrMVStaticBridgeCache OBJECT IDENTIFIER ::= {er1645v2BgrMV 36}

er1645v2BgrMVStaticBridgeCacheSSCTable OBJECT-TYPE
   SYNTAX      SEQUENCE OF Er1645v2BgrMVStaticBridgeCacheEntry
   MAX-ACCESS  not-accessible
   STATUS      current
   DESCRIPTION
      "bridge cache"
   ::= {er1645v2BgrMVStaticBridgeCache 1}

er1645v2BgrMVStaticBridgeCacheEntry OBJECT-TYPE
   SYNTAX      Er1645v2BgrMVStaticBridgeCacheEntry
   MAX-ACCESS  not-accessible
   STATUS      current
   DESCRIPTION
      ""
   INDEX      { er1645v2BgrMVStaticBridgeCacheTableIx }
   ::= {er1645v2BgrMVStaticBridgeCacheSSCTable 1}

Er1645v2BgrMVStaticBridgeCacheEntry ::=
   SEQUENCE
      {
      er1645v2BgrMVStaticBridgeCacheActions
         VariableLengthTableActions,
      er1645v2BgrMVStaticBridgeCacheTableIx
         TableIndex,
      er1645v2BgrMVStaticBridgeCacheIf
         DisplayString,
      er1645v2BgrMVStaticBridgeCacheMacAddress
         OCTET STRING,
      er1645v2BgrMVStaticBridgeCacheVlanId
         Integer32
      }

er1645v2BgrMVStaticBridgeCacheActions OBJECT-TYPE
   SYNTAX      VariableLengthTableActions
   MAX-ACCESS  read-write
   STATUS      current
   DESCRIPTION
      "By way of this field, some manipulations
       on this table may be performed."
   ::= {er1645v2BgrMVStaticBridgeCacheEntry 2}

er1645v2BgrMVStaticBridgeCacheTableIx OBJECT-TYPE
   SYNTAX      TableIndex
   MAX-ACCESS  not-accessible
   STATUS      current
   DESCRIPTION
      ""
   ::= {er1645v2BgrMVStaticBridgeCacheEntry 11}

er1645v2BgrMVStaticBridgeCacheIf OBJECT-TYPE
   SYNTAX      DisplayString
   MAX-ACCESS  read-write
   STATUS      current
   DESCRIPTION
      "Path: bridgeGroup.editConf.staticBridgeCache.interface"
   ::= {er1645v2BgrMVStaticBridgeCacheEntry 16777216}

er1645v2BgrMVStaticBridgeCacheMacAddress OBJECT-TYPE
   SYNTAX      OCTET STRING
   MAX-ACCESS  read-write
   STATUS      current
   DESCRIPTION
      "Path: bridgeGroup.editConf.staticBridgeCache.macAddress

       MAC address."
   ::= {er1645v2BgrMVStaticBridgeCacheEntry 33554432}

er1645v2BgrMVStaticBridgeCacheVlanId OBJECT-TYPE
   SYNTAX      Integer32
   MAX-ACCESS  read-write
   STATUS      current
   DESCRIPTION
      "Path: bridgeGroup.editConf.staticBridgeCache.vlanId"
   ::= {er1645v2BgrMVStaticBridgeCacheEntry 50331648}


er1645v2BgrMVForwardMulticast OBJECT-TYPE
   SYNTAX      INTEGER
               {
               noSpanningTree (0),
               all (1),
               noLinkConstrainedProtos (2),
               dot1ad (3)
               }
   MAX-ACCESS  read-write
   STATUS      current
   DESCRIPTION
      "Path: bridgeGroup.editConf.forwardMulticast
       Info: used for size of bridgeCache

       Possibilities:
               noSpanningTree   (0)
               all   (1)
               noLinkConstrainedProtos   (2)
               dot1ad   (3)"
   ::= {er1645v2BgrMV 35}


er1645v2BgrMVVlanLearningMode OBJECT-TYPE
   SYNTAX      INTEGER
               {
               shared (0),
               independent (1),
               grouped (2)
               }
   MAX-ACCESS  read-write
   STATUS      current
   DESCRIPTION
      "Path: bridgeGroup.editConf.vlanLearningMode

       Possibilities:
               shared   (0)
               independent   (1)
               grouped   (2)"
   ::= {er1645v2BgrMV 17}


er1645v2BgrMVVlanSwitching OBJECT IDENTIFIER ::= {er1645v2BgrMV 15}

er1645v2BgrMVVlanSwitchingSSCTable OBJECT-TYPE
   SYNTAX      SEQUENCE OF Er1645v2BgrMVVlanSwitchingEntry
   MAX-ACCESS  not-accessible
   STATUS      current
   DESCRIPTION
      "used for bridgeCache"
   ::= {er1645v2BgrMVVlanSwitching 1}

er1645v2BgrMVVlanSwitchingEntry OBJECT-TYPE
   SYNTAX      Er1645v2BgrMVVlanSwitchingEntry
   MAX-ACCESS  not-accessible
   STATUS      current
   DESCRIPTION
      ""
   INDEX      { er1645v2BgrMVVlanSwitchingTableIx }
   ::= {er1645v2BgrMVVlanSwitchingSSCTable 1}

Er1645v2BgrMVVlanSwitchingEntry ::=
   SEQUENCE
      {
      er1645v2BgrMVVlanSwitchingActions
         VariableLengthTableActions,
      er1645v2BgrMVVlanSwitchingTableIx
         TableIndex,
      er1645v2BgrMVVlanSwitchingSi
         DisplayString,
      er1645v2BgrMVVlanSwitchingSv
         INTEGER,
      er1645v2BgrMVVlanSwitchingSp
         INTEGER,
      er1645v2BgrMVVlanSwitchingSmP0
         Integer32,
      er1645v2BgrMVVlanSwitchingSmP1
         Integer32,
      er1645v2BgrMVVlanSwitchingSmP2
         Integer32,
      er1645v2BgrMVVlanSwitchingSmP3
         Integer32,
      er1645v2BgrMVVlanSwitchingSmP4
         Integer32,
      er1645v2BgrMVVlanSwitchingSmP5
         Integer32,
      er1645v2BgrMVVlanSwitchingSmP6
         Integer32,
      er1645v2BgrMVVlanSwitchingSmP7
         Integer32,
      er1645v2BgrMVVlanSwitchingDi
         DisplayString,
      er1645v2BgrMVVlanSwitchingDv
         INTEGER,
      er1645v2BgrMVVlanSwitchingDp
         INTEGER,
      er1645v2BgrMVVlanSwitchingDmP0
         Integer32,
      er1645v2BgrMVVlanSwitchingDmP1
         Integer32,
      er1645v2BgrMVVlanSwitchingDmP2
         Integer32,
      er1645v2BgrMVVlanSwitchingDmP3
         Integer32,
      er1645v2BgrMVVlanSwitchingDmP4
         Integer32,
      er1645v2BgrMVVlanSwitchingDmP5
         Integer32,
      er1645v2BgrMVVlanSwitchingDmP6
         Integer32,
      er1645v2BgrMVVlanSwitchingDmP7
         Integer32,
      er1645v2BgrMVVlanSwitchingTunnel
         INTEGER,
      er1645v2BgrMVVlanSwitchingBidir
         INTEGER
      }

er1645v2BgrMVVlanSwitchingActions OBJECT-TYPE
   SYNTAX      VariableLengthTableActions
   MAX-ACCESS  read-write
   STATUS      current
   DESCRIPTION
      "By way of this field, some manipulations
       on this table may be performed."
   ::= {er1645v2BgrMVVlanSwitchingEntry 2}

er1645v2BgrMVVlanSwitchingTableIx OBJECT-TYPE
   SYNTAX      TableIndex
   MAX-ACCESS  not-accessible
   STATUS      current
   DESCRIPTION
      ""
   ::= {er1645v2BgrMVVlanSwitchingEntry 11}

er1645v2BgrMVVlanSwitchingSi OBJECT-TYPE
   SYNTAX      DisplayString
   MAX-ACCESS  read-write
   STATUS      current
   DESCRIPTION
      "Path: bridgeGroup.editConf.vlanSwitching.sourceIntf"
   ::= {er1645v2BgrMVVlanSwitchingEntry 16777216}

er1645v2BgrMVVlanSwitchingSv OBJECT-TYPE
   SYNTAX      INTEGER
               {
               any (-1)
               }
   MAX-ACCESS  read-write
   STATUS      current
   DESCRIPTION
      "Path: bridgeGroup.editConf.vlanSwitching.sourceVlan

       Possibilities:
               any   (-1)"
   ::= {er1645v2BgrMVVlanSwitchingEntry 33554432}

er1645v2BgrMVVlanSwitchingSp OBJECT-TYPE
   SYNTAX      INTEGER
               {
               any (-1)
               }
   MAX-ACCESS  read-write
   STATUS      current
   DESCRIPTION
      "Path: bridgeGroup.editConf.vlanSwitching.sourcePFilter

       Possibilities:
               any   (-1)"
   ::= {er1645v2BgrMVVlanSwitchingEntry 134217728}

er1645v2BgrMVVlanSwitchingSmP0 OBJECT-TYPE
   SYNTAX      Integer32
   MAX-ACCESS  read-write
   STATUS      current
   DESCRIPTION
      "Path: bridgeGroup.editConf.vlanSwitching.sourcePMap.p0"
   ::= {er1645v2BgrMVVlanSwitchingEntry 50397184}

er1645v2BgrMVVlanSwitchingSmP1 OBJECT-TYPE
   SYNTAX      Integer32
   MAX-ACCESS  read-write
   STATUS      current
   DESCRIPTION
      "Path: bridgeGroup.editConf.vlanSwitching.sourcePMap.p1"
   ::= {er1645v2BgrMVVlanSwitchingEntry 50462720}

er1645v2BgrMVVlanSwitchingSmP2 OBJECT-TYPE
   SYNTAX      Integer32
   MAX-ACCESS  read-write
   STATUS      current
   DESCRIPTION
      "Path: bridgeGroup.editConf.vlanSwitching.sourcePMap.p2"
   ::= {er1645v2BgrMVVlanSwitchingEntry 50528256}

er1645v2BgrMVVlanSwitchingSmP3 OBJECT-TYPE
   SYNTAX      Integer32
   MAX-ACCESS  read-write
   STATUS      current
   DESCRIPTION
      "Path: bridgeGroup.editConf.vlanSwitching.sourcePMap.p3"
   ::= {er1645v2BgrMVVlanSwitchingEntry 50593792}

er1645v2BgrMVVlanSwitchingSmP4 OBJECT-TYPE
   SYNTAX      Integer32
   MAX-ACCESS  read-write
   STATUS      current
   DESCRIPTION
      "Path: bridgeGroup.editConf.vlanSwitching.sourcePMap.p4"
   ::= {er1645v2BgrMVVlanSwitchingEntry 50659328}

er1645v2BgrMVVlanSwitchingSmP5 OBJECT-TYPE
   SYNTAX      Integer32
   MAX-ACCESS  read-write
   STATUS      current
   DESCRIPTION
      "Path: bridgeGroup.editConf.vlanSwitching.sourcePMap.p5"
   ::= {er1645v2BgrMVVlanSwitchingEntry 50724864}

er1645v2BgrMVVlanSwitchingSmP6 OBJECT-TYPE
   SYNTAX      Integer32
   MAX-ACCESS  read-write
   STATUS      current
   DESCRIPTION
      "Path: bridgeGroup.editConf.vlanSwitching.sourcePMap.p6"
   ::= {er1645v2BgrMVVlanSwitchingEntry 50790400}

er1645v2BgrMVVlanSwitchingSmP7 OBJECT-TYPE
   SYNTAX      Integer32
   MAX-ACCESS  read-write
   STATUS      current
   DESCRIPTION
      "Path: bridgeGroup.editConf.vlanSwitching.sourcePMap.p7"
   ::= {er1645v2BgrMVVlanSwitchingEntry 50855936}

er1645v2BgrMVVlanSwitchingDi OBJECT-TYPE
   SYNTAX      DisplayString
   MAX-ACCESS  read-write
   STATUS      current
   DESCRIPTION
      "Path: bridgeGroup.editConf.vlanSwitching.destinationIntf"
   ::= {er1645v2BgrMVVlanSwitchingEntry 67108864}

er1645v2BgrMVVlanSwitchingDv OBJECT-TYPE
   SYNTAX      INTEGER
               {
               unchanged (-1)
               }
   MAX-ACCESS  read-write
   STATUS      current
   DESCRIPTION
      "Path: bridgeGroup.editConf.vlanSwitching.destinationVlan

       Possibilities:
               unchanged   (-1)"
   ::= {er1645v2BgrMVVlanSwitchingEntry 83886080}

er1645v2BgrMVVlanSwitchingDp OBJECT-TYPE
   SYNTAX      INTEGER
               {
               any (-1)
               }
   MAX-ACCESS  read-write
   STATUS      current
   DESCRIPTION
      "Path: bridgeGroup.editConf.vlanSwitching.destinationPFilter

       Possibilities:
               any   (-1)"
   ::= {er1645v2BgrMVVlanSwitchingEntry 167772160}

er1645v2BgrMVVlanSwitchingDmP0 OBJECT-TYPE
   SYNTAX      Integer32
   MAX-ACCESS  read-write
   STATUS      current
   DESCRIPTION
      "Path: bridgeGroup.editConf.vlanSwitching.destinationPMap.p0"
   ::= {er1645v2BgrMVVlanSwitchingEntry 100728832}

er1645v2BgrMVVlanSwitchingDmP1 OBJECT-TYPE
   SYNTAX      Integer32
   MAX-ACCESS  read-write
   STATUS      current
   DESCRIPTION
      "Path: bridgeGroup.editConf.vlanSwitching.destinationPMap.p1"
   ::= {er1645v2BgrMVVlanSwitchingEntry 100794368}

er1645v2BgrMVVlanSwitchingDmP2 OBJECT-TYPE
   SYNTAX      Integer32
   MAX-ACCESS  read-write
   STATUS      current
   DESCRIPTION
      "Path: bridgeGroup.editConf.vlanSwitching.destinationPMap.p2"
   ::= {er1645v2BgrMVVlanSwitchingEntry 100859904}

er1645v2BgrMVVlanSwitchingDmP3 OBJECT-TYPE
   SYNTAX      Integer32
   MAX-ACCESS  read-write
   STATUS      current
   DESCRIPTION
      "Path: bridgeGroup.editConf.vlanSwitching.destinationPMap.p3"
   ::= {er1645v2BgrMVVlanSwitchingEntry 100925440}

er1645v2BgrMVVlanSwitchingDmP4 OBJECT-TYPE
   SYNTAX      Integer32
   MAX-ACCESS  read-write
   STATUS      current
   DESCRIPTION
      "Path: bridgeGroup.editConf.vlanSwitching.destinationPMap.p4"
   ::= {er1645v2BgrMVVlanSwitchingEntry 100990976}

er1645v2BgrMVVlanSwitchingDmP5 OBJECT-TYPE
   SYNTAX      Integer32
   MAX-ACCESS  read-write
   STATUS      current
   DESCRIPTION
      "Path: bridgeGroup.editConf.vlanSwitching.destinationPMap.p5"
   ::= {er1645v2BgrMVVlanSwitchingEntry 101056512}

er1645v2BgrMVVlanSwitchingDmP6 OBJECT-TYPE
   SYNTAX      Integer32
   MAX-ACCESS  read-write
   STATUS      current
   DESCRIPTION
      "Path: bridgeGroup.editConf.vlanSwitching.destinationPMap.p6"
   ::= {er1645v2BgrMVVlanSwitchingEntry 101122048}

er1645v2BgrMVVlanSwitchingDmP7 OBJECT-TYPE
   SYNTAX      Integer32
   MAX-ACCESS  read-write
   STATUS      current
   DESCRIPTION
      "Path: bridgeGroup.editConf.vlanSwitching.destinationPMap.p7"
   ::= {er1645v2BgrMVVlanSwitchingEntry 101187584}

er1645v2BgrMVVlanSwitchingTunnel OBJECT-TYPE
   SYNTAX      INTEGER
               {
               disabled (0),
               enabled (1),
               sVlan (3)
               }
   MAX-ACCESS  read-write
   STATUS      current
   DESCRIPTION
      "Path: bridgeGroup.editConf.vlanSwitching.tunnel

       Possibilities:
               disabled   (0)
               enabled   (1)
               sVlan   (3)"
   ::= {er1645v2BgrMVVlanSwitchingEntry 117440512}

er1645v2BgrMVVlanSwitchingBidir OBJECT-TYPE
   SYNTAX      INTEGER
               {
               no (0),
               yes (1)
               }
   MAX-ACCESS  read-write
   STATUS      current
   DESCRIPTION
      "Path: bridgeGroup.editConf.vlanSwitching.bidirectional

       Possibilities:
               no   (0)
               yes   (1)"
   ::= {er1645v2BgrMVVlanSwitchingEntry 150994944}


er1645v2BgrMVPktCounters OBJECT-TYPE
   SYNTAX      INTEGER
               {
               disabled (1),
               enabled (2)
               }
   MAX-ACCESS  read-write
   STATUS      current
   DESCRIPTION
      "Path: bridgeGroup.editConf.pktCounters

       Possibilities:
               disabled   (1)
               enabled   (2)"
   ::= {er1645v2BgrMV 31}


er1645v2BgrMVBackup OBJECT IDENTIFIER ::= {er1645v2BgrMV 32}

er1645v2BgrMVBackupSSC OBJECT IDENTIFIER ::= {er1645v2BgrMVBackup 1}

er1645v2BgrMVBackupEntry OBJECT IDENTIFIER ::= {er1645v2BgrMVBackupSSC 1}

er1645v2BgrMVBackupDisabled OBJECT-TYPE
   SYNTAX      OCTET STRING
   MAX-ACCESS  read-write
   STATUS      current
   DESCRIPTION
      "Path: bridgeGroup.editConf.backup.disabled"
   ::= {er1645v2BgrMVBackupEntry 16777216}

er1645v2BgrMVBackupSimpleInterface1 OBJECT-TYPE
   SYNTAX      DisplayString
   MAX-ACCESS  read-write
   STATUS      current
   DESCRIPTION
      "Path: bridgeGroup.editConf.backup.simple.interface1"
   ::= {er1645v2BgrMVBackupEntry 33619968}

er1645v2BgrMVBackupSimpleInterface1MepName OBJECT-TYPE
   SYNTAX      DisplayString
   MAX-ACCESS  read-write
   STATUS      current
   DESCRIPTION
      "Path: bridgeGroup.editConf.backup.simple.interface1MepName"
   ::= {er1645v2BgrMVBackupEntry 33947648}

er1645v2BgrMVBackupSimpleInterface2 OBJECT-TYPE
   SYNTAX      DisplayString
   MAX-ACCESS  read-write
   STATUS      current
   DESCRIPTION
      "Path: bridgeGroup.editConf.backup.simple.interface2"
   ::= {er1645v2BgrMVBackupEntry 33685504}

er1645v2BgrMVBackupSimpleInterface2MepName OBJECT-TYPE
   SYNTAX      DisplayString
   MAX-ACCESS  read-write
   STATUS      current
   DESCRIPTION
      "Path: bridgeGroup.editConf.backup.simple.interface2MepName"
   ::= {er1645v2BgrMVBackupEntry 34013184}

er1645v2BgrMVBackupSimpleBackup OBJECT-TYPE
   SYNTAX      DisplayString
   MAX-ACCESS  read-write
   STATUS      current
   DESCRIPTION
      "Path: bridgeGroup.editConf.backup.simple.backup"
   ::= {er1645v2BgrMVBackupEntry 33751040}

er1645v2BgrMVBackupSimpleBackupMepName OBJECT-TYPE
   SYNTAX      DisplayString
   MAX-ACCESS  read-write
   STATUS      current
   DESCRIPTION
      "Path: bridgeGroup.editConf.backup.simple.backupMepName"
   ::= {er1645v2BgrMVBackupEntry 33816576}

er1645v2BgrMVBackupSimpleType OBJECT-TYPE
   SYNTAX      INTEGER
               {
               master (1),
               slave (2)
               }
   MAX-ACCESS  read-write
   STATUS      current
   DESCRIPTION
      "Path: bridgeGroup.editConf.backup.simple.type

       Possibilities:
               master   (1)
               slave   (2)"
   ::= {er1645v2BgrMVBackupEntry 33882112}

er1645v2BgrMVBackupSimpleCacheDistribution OBJECT-TYPE
   SYNTAX      SEQUENCE OF Er1645v2BgrMVBackupSimpleCacheDistributionEntry
   MAX-ACCESS  not-accessible
   STATUS      current
   DESCRIPTION
      ""
   ::= {er1645v2BgrMVBackup 34078720}

er1645v2BgrMVBackupSimpleCacheDistributionEntry OBJECT-TYPE
   SYNTAX      Er1645v2BgrMVBackupSimpleCacheDistributionEntry
   MAX-ACCESS  not-accessible
   STATUS      current
   DESCRIPTION
      ""
   INDEX      { er1645v2BgrMVBackupSimpleCacheDistributionTableIx }
   ::= {er1645v2BgrMVBackupSimpleCacheDistribution 1}

Er1645v2BgrMVBackupSimpleCacheDistributionEntry ::=
   SEQUENCE
      {
      er1645v2BgrMVBackupSimpleCacheDistributionActions
         VariableLengthTableActions,
      er1645v2BgrMVBackupSimpleCacheDistributionTableIx
         TableIndex,
      er1645v2BgrMVBackupSimpleCacheDistributionDestinationMac
         OCTET STRING,
      er1645v2BgrMVBackupSimpleCacheDistributionType
         INTEGER
      }

er1645v2BgrMVBackupSimpleCacheDistributionActions OBJECT-TYPE
   SYNTAX      VariableLengthTableActions
   MAX-ACCESS  read-write
   STATUS      current
   DESCRIPTION
      "By way of this field, some manipulations
       on this table may be performed."
   ::= {er1645v2BgrMVBackupSimpleCacheDistributionEntry 2}

er1645v2BgrMVBackupSimpleCacheDistributionTableIx OBJECT-TYPE
   SYNTAX      TableIndex
   MAX-ACCESS  not-accessible
   STATUS      current
   DESCRIPTION
      ""
   ::= {er1645v2BgrMVBackupSimpleCacheDistributionEntry 11}

er1645v2BgrMVBackupSimpleCacheDistributionDestinationMac OBJECT-TYPE
   SYNTAX      OCTET STRING
   MAX-ACCESS  read-write
   STATUS      current
   DESCRIPTION
      "Path: bridgeGroup.editConf.backup.simple.cacheDistribution.destinationMac

       MAC address."
   ::= {er1645v2BgrMVBackupSimpleCacheDistributionEntry 16777216}

er1645v2BgrMVBackupSimpleCacheDistributionType OBJECT-TYPE
   SYNTAX      INTEGER
               {
               arp (2054)
               }
   MAX-ACCESS  read-write
   STATUS      current
   DESCRIPTION
      "Path: bridgeGroup.editConf.backup.simple.cacheDistribution.type

       Possibilities:
               arp   (2054)"
   ::= {er1645v2BgrMVBackupSimpleCacheDistributionEntry 33554432}


er1645v2BgrMVAlarmMask OBJECT-TYPE
   SYNTAX      Integer32
   MAX-ACCESS  read-write
   STATUS      current
   DESCRIPTION
      "Path: bridgeGroup.editConf.alarmMask
       Info: bridge group alarmMask

       Bit meanings:
               bit 0 = linkDown,
               bit 1 = linkShutdown"
   ::= {er1645v2BgrMV 50}


er1645v2BgrMVAlarmLev OBJECT IDENTIFIER ::= {er1645v2BgrMV 51}

er1645v2BgrMVAlarmLevSSC OBJECT IDENTIFIER ::= {er1645v2BgrMVAlarmLev 1}

er1645v2BgrMVAlarmLevEntry OBJECT IDENTIFIER ::= {er1645v2BgrMVAlarmLevSSC 1}

er1645v2BgrMVAlarmLevLinkDown OBJECT-TYPE
   SYNTAX      Integer32
   MAX-ACCESS  read-write
   STATUS      current
   DESCRIPTION
      "Path: bridgeGroup.editConf.alarmLevel.linkDown"
   ::= {er1645v2BgrMVAlarmLevEntry 16777216}

er1645v2BgrMVAlarmLevLinkShutdown OBJECT-TYPE
   SYNTAX      Integer32
   MAX-ACCESS  read-write
   STATUS      current
   DESCRIPTION
      "Path: bridgeGroup.editConf.alarmLevel.linkShutdown"
   ::= {er1645v2BgrMVAlarmLevEntry 33554432}


er1645v2BgrMVBridgeTimeOut OBJECT-TYPE
   SYNTAX      TimeTicks
   MAX-ACCESS  read-write
   STATUS      current
   DESCRIPTION
      "Path: bridgeGroup.editConf.bridgeTimeOut
       Info: timeout of bridge cache entries

       Time in centi-second."
   ::= {er1645v2BgrMV 21}


er1645v2BgrMVName OBJECT-TYPE
   SYNTAX      DisplayString
   MAX-ACCESS  read-write
   STATUS      current
   DESCRIPTION
      "Path: bridgeGroup.editConf.name
       Info: config interface name"
   ::= {er1645v2BgrMV 2}


er1645v2BgrMVRemark OBJECT-TYPE
   SYNTAX      DisplayString
   MAX-ACCESS  read-write
   STATUS      current
   DESCRIPTION
      "Path: bridgeGroup.editConf.remark
       Info: intfRemark"
   ::= {er1645v2BgrMV 321}


er1645v2BgrMVMode OBJECT-TYPE
   SYNTAX      INTEGER
               {
               routing (1),
               ipV6 (3),
               ipV6ipV4 (4),
               disabled (100)
               }
   MAX-ACCESS  read-write
   STATUS      current
   DESCRIPTION
      "Path: bridgeGroup.editConf.mode
       Info: routing and/or ipV6 selection

       Possibilities:
               routing   (1)
               ipV6   (3)
               ipV6/ipV4   (4)
               disabled   (100)"
   ::= {er1645v2BgrMV 4}


er1645v2BgrMVIpV6 OBJECT IDENTIFIER ::= {er1645v2BgrMV 16}

er1645v2BgrMVIpV6SSC OBJECT IDENTIFIER ::= {er1645v2BgrMVIpV6 1}

er1645v2BgrMVIpV6Entry OBJECT IDENTIFIER ::= {er1645v2BgrMVIpV6SSC 1}

er1645v2BgrMVIpV6VrfRouter OBJECT-TYPE
   SYNTAX      DisplayString
   MAX-ACCESS  read-write
   STATUS      current
   DESCRIPTION
      "Path: bridgeGroup.editConf.ipV6.vrfRouter"
   ::= {er1645v2BgrMVIpV6Entry 16777216}

er1645v2BgrMVIpV6AddrAutoConfigNrDupAddrDetects OBJECT-TYPE
   SYNTAX      Integer32
   MAX-ACCESS  read-write
   STATUS      current
   DESCRIPTION
      "Path: bridgeGroup.editConf.ipV6.addrAutoConfig.nrDupAddrDetects"
   ::= {er1645v2BgrMVIpV6Entry 67174400}

er1645v2BgrMVIpV6AddrAutoConfigAcceptRa OBJECT-TYPE
   SYNTAX      INTEGER
               {
               disabled (0),
               enabled (1)
               }
   MAX-ACCESS  read-write
   STATUS      current
   DESCRIPTION
      "Path: bridgeGroup.editConf.ipV6.addrAutoConfig.acceptRa

       Possibilities:
               disabled   (0)
               enabled   (1)"
   ::= {er1645v2BgrMVIpV6Entry 67239936}

er1645v2BgrMVIpV6AddrAutoConfigAcceptRaRdnss OBJECT-TYPE
   SYNTAX      INTEGER
               {
               disabled (0),
               enabled (1)
               }
   MAX-ACCESS  read-write
   STATUS      current
   DESCRIPTION
      "Path: bridgeGroup.editConf.ipV6.addrAutoConfig.acceptRaRdnss

       Possibilities:
               disabled   (0)
               enabled   (1)"
   ::= {er1645v2BgrMVIpV6Entry 67305472}

er1645v2BgrMVIpV6AddrAutoConfigAcceptRaDnssl OBJECT-TYPE
   SYNTAX      INTEGER
               {
               disabled (0),
               enabled (1)
               }
   MAX-ACCESS  read-write
   STATUS      current
   DESCRIPTION
      "Path: bridgeGroup.editConf.ipV6.addrAutoConfig.acceptRaDnssl

       Possibilities:
               disabled   (0)
               enabled   (1)"
   ::= {er1645v2BgrMVIpV6Entry 67371008}

er1645v2BgrMVIpV6DefaultRoute OBJECT-TYPE
   SYNTAX      INTEGER
               {
               disabled (0),
               enabled (1)
               }
   MAX-ACCESS  read-write
   STATUS      current
   DESCRIPTION
      "Path: bridgeGroup.editConf.ipV6.defaultRoute

       Possibilities:
               disabled   (0)
               enabled   (1)"
   ::= {er1645v2BgrMVIpV6Entry 83886080}

er1645v2BgrMVIpV6RaSend OBJECT-TYPE
   SYNTAX      INTEGER
               {
               disabled (0),
               enabled (1)
               }
   MAX-ACCESS  read-write
   STATUS      current
   DESCRIPTION
      "Path: bridgeGroup.editConf.ipV6.ra.send

       Possibilities:
               disabled   (0)
               enabled   (1)"
   ::= {er1645v2BgrMVIpV6Entry 100728832}

er1645v2BgrMVIpV6RaMinInterval OBJECT-TYPE
   SYNTAX      TimeTicks
   MAX-ACCESS  read-write
   STATUS      current
   DESCRIPTION
      "Path: bridgeGroup.editConf.ipV6.ra.minInterval

       Time in centi-second."
   ::= {er1645v2BgrMVIpV6Entry 100794368}

er1645v2BgrMVIpV6RaMaxInterval OBJECT-TYPE
   SYNTAX      TimeTicks
   MAX-ACCESS  read-write
   STATUS      current
   DESCRIPTION
      "Path: bridgeGroup.editConf.ipV6.ra.maxInterval

       Time in centi-second."
   ::= {er1645v2BgrMVIpV6Entry 100859904}

er1645v2BgrMVIpV6RaManagedFlag OBJECT-TYPE
   SYNTAX      INTEGER
               {
               disabled (0),
               enabled (1)
               }
   MAX-ACCESS  read-write
   STATUS      current
   DESCRIPTION
      "Path: bridgeGroup.editConf.ipV6.ra.managedFlag

       Possibilities:
               disabled   (0)
               enabled   (1)"
   ::= {er1645v2BgrMVIpV6Entry 100925440}

er1645v2BgrMVIpV6RaOtherConfFlag OBJECT-TYPE
   SYNTAX      INTEGER
               {
               disabled (0),
               enabled (1)
               }
   MAX-ACCESS  read-write
   STATUS      current
   DESCRIPTION
      "Path: bridgeGroup.editConf.ipV6.ra.otherConfFlag

       Possibilities:
               disabled   (0)
               enabled   (1)"
   ::= {er1645v2BgrMVIpV6Entry 100990976}

er1645v2BgrMVIpV6RaLinkMtu OBJECT-TYPE
   SYNTAX      Integer32
   MAX-ACCESS  read-write
   STATUS      current
   DESCRIPTION
      "Path: bridgeGroup.editConf.ipV6.ra.linkMtu"
   ::= {er1645v2BgrMVIpV6Entry 101056512}

er1645v2BgrMVIpV6RaReachableTime OBJECT-TYPE
   SYNTAX      TimeTicks
   MAX-ACCESS  read-write
   STATUS      current
   DESCRIPTION
      "Path: bridgeGroup.editConf.ipV6.ra.reachableTime

       Time in centi-second."
   ::= {er1645v2BgrMVIpV6Entry 101122048}

er1645v2BgrMVIpV6RaRetransmitTime OBJECT-TYPE
   SYNTAX      TimeTicks
   MAX-ACCESS  read-write
   STATUS      current
   DESCRIPTION
      "Path: bridgeGroup.editConf.ipV6.ra.retransmitTime

       Time in centi-second."
   ::= {er1645v2BgrMVIpV6Entry 101187584}

er1645v2BgrMVIpV6RaHopLimit OBJECT-TYPE
   SYNTAX      Integer32
   MAX-ACCESS  read-write
   STATUS      current
   DESCRIPTION
      "Path: bridgeGroup.editConf.ipV6.ra.hopLimit"
   ::= {er1645v2BgrMVIpV6Entry 101253120}

er1645v2BgrMVIpV6RaDefaultLifeTime OBJECT-TYPE
   SYNTAX      TimeTicks
   MAX-ACCESS  read-write
   STATUS      current
   DESCRIPTION
      "Path: bridgeGroup.editConf.ipV6.ra.defaultLifeTime

       Time in centi-second."
   ::= {er1645v2BgrMVIpV6Entry 101318656}

er1645v2BgrMVIpV6RaDnsOptionsRdnssLifeTime OBJECT-TYPE
   SYNTAX      TimeTicks
   MAX-ACCESS  read-write
   STATUS      current
   DESCRIPTION
      "Path: bridgeGroup.editConf.ipV6.ra.dnsOptions.rdnss.lifeTime

       Time in centi-second."
   ::= {er1645v2BgrMVIpV6Entry 101393408}

er1645v2BgrMVIpV6RaDnsOptionsRdnssImportServers OBJECT-TYPE
   SYNTAX      INTEGER
               {
               disabled (0),
               enabled (1)
               }
   MAX-ACCESS  read-write
   STATUS      current
   DESCRIPTION
      "Path: bridgeGroup.editConf.ipV6.ra.dnsOptions.rdnss.importServers

       Possibilities:
               disabled   (0)
               enabled   (1)"
   ::= {er1645v2BgrMVIpV6Entry 101395456}

er1645v2BgrMVIpV6RaDnsOptionsDnsslLifeTime OBJECT-TYPE
   SYNTAX      TimeTicks
   MAX-ACCESS  read-write
   STATUS      current
   DESCRIPTION
      "Path: bridgeGroup.editConf.ipV6.ra.dnsOptions.dnssl.lifeTime

       Time in centi-second."
   ::= {er1645v2BgrMVIpV6Entry 101401600}

er1645v2BgrMVIpV6RaDnsOptionsDnsslImportDomains OBJECT-TYPE
   SYNTAX      INTEGER
               {
               disabled (0),
               enabled (1)
               }
   MAX-ACCESS  read-write
   STATUS      current
   DESCRIPTION
      "Path: bridgeGroup.editConf.ipV6.ra.dnsOptions.dnssl.importDomains

       Possibilities:
               disabled   (0)
               enabled   (1)"
   ::= {er1645v2BgrMVIpV6Entry 101403648}

er1645v2BgrMVIpV6RsSend OBJECT-TYPE
   SYNTAX      INTEGER
               {
               disabled (0),
               enabled (1)
               }
   MAX-ACCESS  read-write
   STATUS      current
   DESCRIPTION
      "Path: bridgeGroup.editConf.ipV6.rs.send

       Possibilities:
               disabled   (0)
               enabled   (1)"
   ::= {er1645v2BgrMVIpV6Entry 335609856}

er1645v2BgrMVIpV6RsMaxRandomDelay OBJECT-TYPE
   SYNTAX      TimeTicks
   MAX-ACCESS  read-write
   STATUS      current
   DESCRIPTION
      "Path: bridgeGroup.editConf.ipV6.rs.maxRandomDelay

       Time in centi-second."
   ::= {er1645v2BgrMVIpV6Entry 335675392}

er1645v2BgrMVIpV6RsInterval OBJECT-TYPE
   SYNTAX      TimeTicks
   MAX-ACCESS  read-write
   STATUS      current
   DESCRIPTION
      "Path: bridgeGroup.editConf.ipV6.rs.interval

       Time in centi-second."
   ::= {er1645v2BgrMVIpV6Entry 335740928}

er1645v2BgrMVIpV6RsMaxSolicitations OBJECT-TYPE
   SYNTAX      Integer32
   MAX-ACCESS  read-write
   STATUS      current
   DESCRIPTION
      "Path: bridgeGroup.editConf.ipV6.rs.maxSolicitations"
   ::= {er1645v2BgrMVIpV6Entry 335806464}

er1645v2BgrMVIpV6TrafficPolicyInbound OBJECT-TYPE
   SYNTAX      DisplayString
   MAX-ACCESS  read-write
   STATUS      current
   DESCRIPTION
      "Path: bridgeGroup.editConf.ipV6.trafficPolicy.inbound"
   ::= {er1645v2BgrMVIpV6Entry 184614912}

er1645v2BgrMVIpV6TrafficPolicyOutbound OBJECT-TYPE
   SYNTAX      DisplayString
   MAX-ACCESS  read-write
   STATUS      current
   DESCRIPTION
      "Path: bridgeGroup.editConf.ipV6.trafficPolicy.outbound"
   ::= {er1645v2BgrMVIpV6Entry 184680448}

er1645v2BgrMVIpV6FirewallZone OBJECT-TYPE
   SYNTAX      DisplayString
   MAX-ACCESS  read-write
   STATUS      current
   DESCRIPTION
      "Path: bridgeGroup.editConf.ipV6.firewall.zone"
   ::= {er1645v2BgrMVIpV6Entry 201392128}

er1645v2BgrMVIpV6DhcpClientAddrAC OBJECT-TYPE
   SYNTAX      INTEGER
               {
               disabled (0),
               enabled (1)
               }
   MAX-ACCESS  read-write
   STATUS      current
   DESCRIPTION
      "Path: bridgeGroup.editConf.ipV6.dhcp.client.addrAutoConfig

       Possibilities:
               disabled   (0)
               enabled   (1)"
   ::= {er1645v2BgrMVIpV6Entry 170131456}

er1645v2BgrMVIpV6DhcpClientPrDelMode OBJECT-TYPE
   SYNTAX      INTEGER
               {
               disabled (0),
               enabled (1)
               }
   MAX-ACCESS  read-write
   STATUS      current
   DESCRIPTION
      "Path: bridgeGroup.editConf.ipV6.dhcp.client.pd.mode

       Possibilities:
               disabled   (0)
               enabled   (1)"
   ::= {er1645v2BgrMVIpV6Entry 170394624}

er1645v2BgrMVIpV6DhcpClientPrDelPool OBJECT-TYPE
   SYNTAX      DisplayString
   MAX-ACCESS  read-write
   STATUS      current
   DESCRIPTION
      "Path: bridgeGroup.editConf.ipV6.dhcp.client.pd.pool"
   ::= {er1645v2BgrMVIpV6Entry 170395648}

er1645v2BgrMVIpV6DhcpClientPrDelPdExclOpt OBJECT-TYPE
   SYNTAX      INTEGER
               {
               disabled (0),
               enabled (1)
               }
   MAX-ACCESS  read-write
   STATUS      current
   DESCRIPTION
      "Path: bridgeGroup.editConf.ipV6.dhcp.client.pd.pdExclOpt

       Possibilities:
               disabled   (0)
               enabled   (1)"
   ::= {er1645v2BgrMVIpV6Entry 170396672}

er1645v2BgrMVIpV6DhcpClientDnsServerPref OBJECT-TYPE
   SYNTAX      Integer32
   MAX-ACCESS  read-write
   STATUS      current
   DESCRIPTION
      "Path: bridgeGroup.editConf.ipV6.dhcp.client.dns.serverPref"
   ::= {er1645v2BgrMVIpV6Entry 170918912}

er1645v2BgrMVIpV6DhcpClientRapidCommit OBJECT-TYPE
   SYNTAX      INTEGER
               {
               disabled (0),
               enabled (1)
               }
   MAX-ACCESS  read-write
   STATUS      current
   DESCRIPTION
      "Path: bridgeGroup.editConf.ipV6.dhcp.client.rapidCommit

       Possibilities:
               disabled   (0)
               enabled   (1)"
   ::= {er1645v2BgrMVIpV6Entry 170655744}

er1645v2BgrMVIpV6DhcpClientTimersSolTimeOut OBJECT-TYPE
   SYNTAX      TimeTicks
   MAX-ACCESS  read-write
   STATUS      current
   DESCRIPTION
      "Path: bridgeGroup.editConf.ipV6.dhcp.client.timers.solTimeOut

       Time in centi-second."
   ::= {er1645v2BgrMVIpV6Entry 171181056}

er1645v2BgrMVIpV6DhcpClientTimersSolMaxRt OBJECT-TYPE
   SYNTAX      TimeTicks
   MAX-ACCESS  read-write
   STATUS      current
   DESCRIPTION
      "Path: bridgeGroup.editConf.ipV6.dhcp.client.timers.solMaxRt

       Time in centi-second."
   ::= {er1645v2BgrMVIpV6Entry 171182080}

er1645v2BgrMVIpV6DhcpClientTimersInfoRefresh OBJECT-TYPE
   SYNTAX      TimeTicks
   MAX-ACCESS  read-write
   STATUS      current
   DESCRIPTION
      "Path: bridgeGroup.editConf.ipV6.dhcp.client.timers.infoRefresh

       Time in centi-second."
   ::= {er1645v2BgrMVIpV6Entry 171183104}

er1645v2BgrMVIpV6DhcpServerMode OBJECT-TYPE
   SYNTAX      INTEGER
               {
               disabled (0),
               enabled (1)
               }
   MAX-ACCESS  read-write
   STATUS      current
   DESCRIPTION
      "Path: bridgeGroup.editConf.ipV6.dhcp.server.mode

       Possibilities:
               disabled   (0)
               enabled   (1)"
   ::= {er1645v2BgrMVIpV6Entry 172228608}

er1645v2BgrMVIpV6DhcpServerPreference OBJECT-TYPE
   SYNTAX      Integer32
   MAX-ACCESS  read-write
   STATUS      current
   DESCRIPTION
      "Path: bridgeGroup.editConf.ipV6.dhcp.server.preference"
   ::= {er1645v2BgrMVIpV6Entry 172490752}

er1645v2BgrMVIpV6DhcpServerPool OBJECT-TYPE
   SYNTAX      DisplayString
   MAX-ACCESS  read-write
   STATUS      current
   DESCRIPTION
      "Path: bridgeGroup.editConf.ipV6.dhcp.server.pool"
   ::= {er1645v2BgrMVIpV6Entry 172752896}

er1645v2BgrMVIpV6DhcpServerRapidCommit OBJECT-TYPE
   SYNTAX      INTEGER
               {
               disabled (0),
               enabled (1)
               }
   MAX-ACCESS  read-write
   STATUS      current
   DESCRIPTION
      "Path: bridgeGroup.editConf.ipV6.dhcp.server.rapidCommit

       Possibilities:
               disabled   (0)
               enabled   (1)"
   ::= {er1645v2BgrMVIpV6Entry 173015040}

er1645v2BgrMVIpV6DhcpServerTimersInfoRefresh OBJECT-TYPE
   SYNTAX      TimeTicks
   MAX-ACCESS  read-write
   STATUS      current
   DESCRIPTION
      "Path: bridgeGroup.editConf.ipV6.dhcp.server.timers.infoRefresh

       Time in centi-second."
   ::= {er1645v2BgrMVIpV6Entry 173278208}

er1645v2BgrMVIpV6DhcpRelayMode OBJECT-TYPE
   SYNTAX      INTEGER
               {
               disabled (0),
               enabled (1)
               }
   MAX-ACCESS  read-write
   STATUS      current
   DESCRIPTION
      "Path: bridgeGroup.editConf.ipV6.dhcp.relay.mode

       Possibilities:
               disabled   (0)
               enabled   (1)"
   ::= {er1645v2BgrMVIpV6Entry 174071808}

er1645v2BgrMVIpV6SendRedirect OBJECT-TYPE
   SYNTAX      INTEGER
               {
               disabled (0),
               enabled (1)
               }
   MAX-ACCESS  read-write
   STATUS      current
   DESCRIPTION
      "Path: bridgeGroup.editConf.ipV6.sendRedirect

       Possibilities:
               disabled   (0)
               enabled   (1)"
   ::= {er1645v2BgrMVIpV6Entry 117440512}

er1645v2BgrMVIpV6LinkMtu OBJECT-TYPE
   SYNTAX      Integer32
   MAX-ACCESS  read-write
   STATUS      current
   DESCRIPTION
      "Path: bridgeGroup.editConf.ipV6.linkMtu"
   ::= {er1645v2BgrMVIpV6Entry 134217728}

er1645v2BgrMVIpV6InterfaceId OBJECT-TYPE
   SYNTAX      OCTET STRING
   MAX-ACCESS  read-write
   STATUS      current
   DESCRIPTION
      "Path: bridgeGroup.editConf.ipV6.interfaceId"
   ::= {er1645v2BgrMVIpV6Entry 150994944}

er1645v2BgrMVIpV6MF OBJECT-TYPE
   SYNTAX      Integer32
   MAX-ACCESS  read-write
   STATUS      current
   DESCRIPTION
      "Path: bridgeGroup.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2BgrMVIpV6Entry 285212672}

er1645v2BgrMVIpV6IcmpMessagesNoRoute OBJECT-TYPE
   SYNTAX      INTEGER
               {
               disabled (0),
               enabled (1)
               }
   MAX-ACCESS  read-write
   STATUS      current
   DESCRIPTION
      "Path: bridgeGroup.editConf.ipV6.icmpMessages.noRoute

       Possibilities:
               disabled   (0)
               enabled   (1)"
   ::= {er1645v2BgrMVIpV6Entry 302055424}

er1645v2BgrMVIpV6IcmpMessagesBeyondScope OBJECT-TYPE
   SYNTAX      INTEGER
               {
               disabled (0),
               enabled (1)
               }
   MAX-ACCESS  read-write
   STATUS      current
   DESCRIPTION
      "Path: bridgeGroup.editConf.ipV6.icmpMessages.beyondScope

       Possibilities:
               disabled   (0)
               enabled   (1)"
   ::= {er1645v2BgrMVIpV6Entry 302186496}

er1645v2BgrMVIpV6IcmpMessagesAddressUnreachable OBJECT-TYPE
   SYNTAX      INTEGER
               {
               disabled (0),
               enabled (1)
               }
   MAX-ACCESS  read-write
   STATUS      current
   DESCRIPTION
      "Path: bridgeGroup.editConf.ipV6.icmpMessages.addressUnreachable

       Possibilities:
               disabled   (0)
               enabled   (1)"
   ::= {er1645v2BgrMVIpV6Entry 302252032}

er1645v2BgrMVIpV6IcmpMessagesPortUnreachable OBJECT-TYPE
   SYNTAX      INTEGER
               {
               disabled (0),
               enabled (1)
               }
   MAX-ACCESS  read-write
   STATUS      current
   DESCRIPTION
      "Path: bridgeGroup.editConf.ipV6.icmpMessages.portUnreachable

       Possibilities:
               disabled   (0)
               enabled   (1)"
   ::= {er1645v2BgrMVIpV6Entry 302317568}

er1645v2BgrMVIpV6IcmpMessagesPacketTooBig OBJECT-TYPE
   SYNTAX      INTEGER
               {
               disabled (0),
               enabled (1)
               }
   MAX-ACCESS  read-write
   STATUS      current
   DESCRIPTION
      "Path: bridgeGroup.editConf.ipV6.icmpMessages.packetTooBig

       Possibilities:
               disabled   (0)
               enabled   (1)"
   ::= {er1645v2BgrMVIpV6Entry 302645248}

er1645v2BgrMVIpV6IcmpMessagesHopLimitExceeded OBJECT-TYPE
   SYNTAX      INTEGER
               {
               disabled (0),
               enabled (1)
               }
   MAX-ACCESS  read-write
   STATUS      current
   DESCRIPTION
      "Path: bridgeGroup.editConf.ipV6.icmpMessages.hopLimitExceeded

       Possibilities:
               disabled   (0)
               enabled   (1)"
   ::= {er1645v2BgrMVIpV6Entry 303300608}

er1645v2BgrMVIpV6IcmpMessagesFragTimeExceeded OBJECT-TYPE
   SYNTAX      INTEGER
               {
               disabled (0),
               enabled (1)
               }
   MAX-ACCESS  read-write
   STATUS      current
   DESCRIPTION
      "Path: bridgeGroup.editConf.ipV6.icmpMessages.fragTimeExceeded

       Possibilities:
               disabled   (0)
               enabled   (1)"
   ::= {er1645v2BgrMVIpV6Entry 303366144}

er1645v2BgrMVIpV6IcmpMessagesHeaderFieldErr OBJECT-TYPE
   SYNTAX      INTEGER
               {
               disabled (0),
               enabled (1)
               }
   MAX-ACCESS  read-write
   STATUS      current
   DESCRIPTION
      "Path: bridgeGroup.editConf.ipV6.icmpMessages.headerFieldErr

       Possibilities:
               disabled   (0)
               enabled   (1)"
   ::= {er1645v2BgrMVIpV6Entry 303955968}

er1645v2BgrMVIpV6IcmpMessagesOptionUnrecognized OBJECT-TYPE
   SYNTAX      INTEGER
               {
               disabled (0),
               enabled (1)
               }
   MAX-ACCESS  read-write
   STATUS      current
   DESCRIPTION
      "Path: bridgeGroup.editConf.ipV6.icmpMessages.optionUnrecognized

       Possibilities:
               disabled   (0)
               enabled   (1)"
   ::= {er1645v2BgrMVIpV6Entry 304087040}

er1645v2BgrMVIpV6IcmpMessagesRedirect OBJECT-TYPE
   SYNTAX      INTEGER
               {
               disabled (0),
               enabled (1)
               }
   MAX-ACCESS  read-write
   STATUS      current
   DESCRIPTION
      "Path: bridgeGroup.editConf.ipV6.icmpMessages.redirect

       Possibilities:
               disabled   (0)
               enabled   (1)"
   ::= {er1645v2BgrMVIpV6Entry 304611328}

er1645v2BgrMVIpV6Addresses OBJECT-TYPE
   SYNTAX      SEQUENCE OF Er1645v2BgrMVIpV6AddressesEntry
   MAX-ACCESS  not-accessible
   STATUS      current
   DESCRIPTION
      ""
   ::= {er1645v2BgrMVIpV6 50331648}

er1645v2BgrMVIpV6AddressesEntry OBJECT-TYPE
   SYNTAX      Er1645v2BgrMVIpV6AddressesEntry
   MAX-ACCESS  not-accessible
   STATUS      current
   DESCRIPTION
      ""
   INDEX      { er1645v2BgrMVIpV6AddressesTableIx }
   ::= {er1645v2BgrMVIpV6Addresses 1}

Er1645v2BgrMVIpV6AddressesEntry ::=
   SEQUENCE
      {
      er1645v2BgrMVIpV6AddressesActions
         VariableLengthTableActions,
      er1645v2BgrMVIpV6AddressesTableIx
         TableIndex,
      er1645v2BgrMVIpV6AddressesType
         INTEGER,
      er1645v2BgrMVIpV6AddressesAddress
         Ipv6Address,
      er1645v2BgrMVIpV6AddressesPrefixLength
         Integer32,
      er1645v2BgrMVIpV6AddressesGeneralPrefix
         DisplayString,
      er1645v2BgrMVIpV6AddressesRaSend
         INTEGER,
      er1645v2BgrMVIpV6AddressesRaOnLinkFlag
         INTEGER,
      er1645v2BgrMVIpV6AddressesRaAutoFlag
         INTEGER,
      er1645v2BgrMVIpV6AddressesRaValidLifeTime
         TimeTicks,
      er1645v2BgrMVIpV6AddressesRaValidLTMode
         INTEGER,
      er1645v2BgrMVIpV6AddressesRaPrefLifeTime
         TimeTicks,
      er1645v2BgrMVIpV6AddressesRaPrefLTMode
         INTEGER
      }

er1645v2BgrMVIpV6AddressesActions OBJECT-TYPE
   SYNTAX      VariableLengthTableActions
   MAX-ACCESS  read-write
   STATUS      current
   DESCRIPTION
      "By way of this field, some manipulations
       on this table may be performed."
   ::= {er1645v2BgrMVIpV6AddressesEntry 2}

er1645v2BgrMVIpV6AddressesTableIx OBJECT-TYPE
   SYNTAX      TableIndex
   MAX-ACCESS  not-accessible
   STATUS      current
   DESCRIPTION
      ""
   ::= {er1645v2BgrMVIpV6AddressesEntry 11}

er1645v2BgrMVIpV6AddressesType OBJECT-TYPE
   SYNTAX      INTEGER
               {
               unicast (0),
               eui64 (1),
               anycast (2),
               linkLocal (3),
               generalPrefix (4)
               }
   MAX-ACCESS  read-write
   STATUS      current
   DESCRIPTION
      "Path: bridgeGroup.editConf.ipV6.addresses.type

       Possibilities:
               unicast   (0)
               eui64   (1)
               anycast   (2)
               linkLocal   (3)
               generalPrefix   (4)"
   ::= {er1645v2BgrMVIpV6AddressesEntry 50331648}

er1645v2BgrMVIpV6AddressesAddress OBJECT-TYPE
   SYNTAX      Ipv6Address
   MAX-ACCESS  read-write
   STATUS      current
   DESCRIPTION
      "Path: bridgeGroup.editConf.ipV6.addresses.address

       ipv6 address"
   ::= {er1645v2BgrMVIpV6AddressesEntry 16777216}

er1645v2BgrMVIpV6AddressesPrefixLength OBJECT-TYPE
   SYNTAX      Integer32
   MAX-ACCESS  read-write
   STATUS      current
   DESCRIPTION
      "Path: bridgeGroup.editConf.ipV6.addresses.prefixLength"
   ::= {er1645v2BgrMVIpV6AddressesEntry 33554432}

er1645v2BgrMVIpV6AddressesGeneralPrefix OBJECT-TYPE
   SYNTAX      DisplayString
   MAX-ACCESS  read-write
   STATUS      current
   DESCRIPTION
      "Path: bridgeGroup.editConf.ipV6.addresses.generalPrefix"
   ::= {er1645v2BgrMVIpV6AddressesEntry 83886080}

er1645v2BgrMVIpV6AddressesRaSend OBJECT-TYPE
   SYNTAX      INTEGER
               {
               disabled (0),
               enabled (1)
               }
   MAX-ACCESS  read-write
   STATUS      current
   DESCRIPTION
      "Path: bridgeGroup.editConf.ipV6.addresses.ra.send

       Possibilities:
               disabled   (0)
               enabled   (1)"
   ::= {er1645v2BgrMVIpV6AddressesEntry 67174400}

er1645v2BgrMVIpV6AddressesRaOnLinkFlag OBJECT-TYPE
   SYNTAX      INTEGER
               {
               disabled (0),
               enabled (1)
               }
   MAX-ACCESS  read-write
   STATUS      current
   DESCRIPTION
      "Path: bridgeGroup.editConf.ipV6.addresses.ra.onLinkFlag

       Possibilities:
               disabled   (0)
               enabled   (1)"
   ::= {er1645v2BgrMVIpV6AddressesEntry 67371008}

er1645v2BgrMVIpV6AddressesRaAutoFlag OBJECT-TYPE
   SYNTAX      INTEGER
               {
               disabled (0),
               enabled (1)
               }
   MAX-ACCESS  read-write
   STATUS      current
   DESCRIPTION
      "Path: bridgeGroup.editConf.ipV6.addresses.ra.autonomousFlag

       Possibilities:
               disabled   (0)
               enabled   (1)"
   ::= {er1645v2BgrMVIpV6AddressesEntry 67567616}

er1645v2BgrMVIpV6AddressesRaValidLifeTime OBJECT-TYPE
   SYNTAX      TimeTicks
   MAX-ACCESS  read-write
   STATUS      current
   DESCRIPTION
      "Path: bridgeGroup.editConf.ipV6.addresses.ra.validLifeTime

       Time in centi-second."
   ::= {er1645v2BgrMVIpV6AddressesEntry 67239936}

er1645v2BgrMVIpV6AddressesRaValidLTMode OBJECT-TYPE
   SYNTAX      INTEGER
               {
               fixed (0),
               infinite (2)
               }
   MAX-ACCESS  read-write
   STATUS      current
   DESCRIPTION
      "Path: bridgeGroup.editConf.ipV6.addresses.ra.validLifeTimeMode

       Possibilities:
               fixed   (0)
               infinite   (2)"
   ::= {er1645v2BgrMVIpV6AddressesEntry 67305472}

er1645v2BgrMVIpV6AddressesRaPrefLifeTime OBJECT-TYPE
   SYNTAX      TimeTicks
   MAX-ACCESS  read-write
   STATUS      current
   DESCRIPTION
      "Path: bridgeGroup.editConf.ipV6.addresses.ra.prefLifeTime

       Time in centi-second."
   ::= {er1645v2BgrMVIpV6AddressesEntry 67436544}

er1645v2BgrMVIpV6AddressesRaPrefLTMode OBJECT-TYPE
   SYNTAX      INTEGER
               {
               fixed (0),
               infinite (2)
               }
   MAX-ACCESS  read-write
   STATUS      current
   DESCRIPTION
      "Path: bridgeGroup.editConf.ipV6.addresses.ra.prefLifeTimeMode

       Possibilities:
               fixed   (0)
               infinite   (2)"
   ::= {er1645v2BgrMVIpV6AddressesEntry 67502080}

er1645v2BgrMVIpV6RaDnsOptionsRdnssServers OBJECT-TYPE
   SYNTAX      SEQUENCE OF Er1645v2BgrMVIpV6RaDnsOptionsRdnssServersEntry
   MAX-ACCESS  not-accessible
   STATUS      current
   DESCRIPTION
      ""
   ::= {er1645v2BgrMVIpV6 101394432}

er1645v2BgrMVIpV6RaDnsOptionsRdnssServersEntry OBJECT-TYPE
   SYNTAX      Er1645v2BgrMVIpV6RaDnsOptionsRdnssServersEntry
   MAX-ACCESS  not-accessible
   STATUS      current
   DESCRIPTION
      ""
   INDEX      { er1645v2BgrMVIpV6RaDnsOptionsRdnssServersTableIx }
   ::= {er1645v2BgrMVIpV6RaDnsOptionsRdnssServers 1}

Er1645v2BgrMVIpV6RaDnsOptionsRdnssServersEntry ::=
   SEQUENCE
      {
      er1645v2BgrMVIpV6RaDnsOptionsRdnssServersActions
         VariableLengthTableActions,
      er1645v2BgrMVIpV6RaDnsOptionsRdnssServersTableIx
         TableIndex,
      er1645v2BgrMVIpV6RaDnsOptionsRdnssServersAddress
         Ipv6Address
      }

er1645v2BgrMVIpV6RaDnsOptionsRdnssServersActions OBJECT-TYPE
   SYNTAX      VariableLengthTableActions
   MAX-ACCESS  read-write
   STATUS      current
   DESCRIPTION
      "By way of this field, some manipulations
       on this table may be performed."
   ::= {er1645v2BgrMVIpV6RaDnsOptionsRdnssServersEntry 2}

er1645v2BgrMVIpV6RaDnsOptionsRdnssServersTableIx OBJECT-TYPE
   SYNTAX      TableIndex
   MAX-ACCESS  not-accessible
   STATUS      current
   DESCRIPTION
      ""
   ::= {er1645v2BgrMVIpV6RaDnsOptionsRdnssServersEntry 11}

er1645v2BgrMVIpV6RaDnsOptionsRdnssServersAddress OBJECT-TYPE
   SYNTAX      Ipv6Address
   MAX-ACCESS  read-write
   STATUS      current
   DESCRIPTION
      "Path: bridgeGroup.editConf.ipV6.ra.dnsOptions.rdnss.servers.address

       ipv6 address"
   ::= {er1645v2BgrMVIpV6RaDnsOptionsRdnssServersEntry 16777216}

er1645v2BgrMVIpV6RaDnsOptionsDnsslDomains OBJECT-TYPE
   SYNTAX      SEQUENCE OF Er1645v2BgrMVIpV6RaDnsOptionsDnsslDomainsEntry
   MAX-ACCESS  not-accessible
   STATUS      current
   DESCRIPTION
      ""
   ::= {er1645v2BgrMVIpV6 101402624}

er1645v2BgrMVIpV6RaDnsOptionsDnsslDomainsEntry OBJECT-TYPE
   SYNTAX      Er1645v2BgrMVIpV6RaDnsOptionsDnsslDomainsEntry
   MAX-ACCESS  not-accessible
   STATUS      current
   DESCRIPTION
      ""
   INDEX      { er1645v2BgrMVIpV6RaDnsOptionsDnsslDomainsTableIx }
   ::= {er1645v2BgrMVIpV6RaDnsOptionsDnsslDomains 1}

Er1645v2BgrMVIpV6RaDnsOptionsDnsslDomainsEntry ::=
   SEQUENCE
      {
      er1645v2BgrMVIpV6RaDnsOptionsDnsslDomainsActions
         VariableLengthTableActions,
      er1645v2BgrMVIpV6RaDnsOptionsDnsslDomainsTableIx
         TableIndex,
      er1645v2BgrMVIpV6RaDnsOptionsDnsslDomainsName
         DisplayString
      }

er1645v2BgrMVIpV6RaDnsOptionsDnsslDomainsActions OBJECT-TYPE
   SYNTAX      VariableLengthTableActions
   MAX-ACCESS  read-write
   STATUS      current
   DESCRIPTION
      "By way of this field, some manipulations
       on this table may be performed."
   ::= {er1645v2BgrMVIpV6RaDnsOptionsDnsslDomainsEntry 2}

er1645v2BgrMVIpV6RaDnsOptionsDnsslDomainsTableIx OBJECT-TYPE
   SYNTAX      TableIndex
   MAX-ACCESS  not-accessible
   STATUS      current
   DESCRIPTION
      ""
   ::= {er1645v2BgrMVIpV6RaDnsOptionsDnsslDomainsEntry 11}

er1645v2BgrMVIpV6RaDnsOptionsDnsslDomainsName OBJECT-TYPE
   SYNTAX      DisplayString
   MAX-ACCESS  read-write
   STATUS      current
   DESCRIPTION
      "Path: bridgeGroup.editConf.ipV6.ra.dnsOptions.dnssl.domains.name"
   ::= {er1645v2BgrMVIpV6RaDnsOptionsDnsslDomainsEntry 16777216}

er1645v2BgrMVIpV6DhcpClientUserClassOpt OBJECT-TYPE
   SYNTAX      SEQUENCE OF Er1645v2BgrMVIpV6DhcpClientUserClassOptEntry
   MAX-ACCESS  not-accessible
   STATUS      current
   DESCRIPTION
      ""
   ::= {er1645v2BgrMVIpV6 171442176}

er1645v2BgrMVIpV6DhcpClientUserClassOptEntry OBJECT-TYPE
   SYNTAX      Er1645v2BgrMVIpV6DhcpClientUserClassOptEntry
   MAX-ACCESS  not-accessible
   STATUS      current
   DESCRIPTION
      ""
   INDEX      { er1645v2BgrMVIpV6DhcpClientUserClassOptTableIx }
   ::= {er1645v2BgrMVIpV6DhcpClientUserClassOpt 1}

Er1645v2BgrMVIpV6DhcpClientUserClassOptEntry ::=
   SEQUENCE
      {
      er1645v2BgrMVIpV6DhcpClientUserClassOptActions
         VariableLengthTableActions,
      er1645v2BgrMVIpV6DhcpClientUserClassOptTableIx
         TableIndex,
      er1645v2BgrMVIpV6DhcpClientUserClassOptValueAscii
         DisplayString,
      er1645v2BgrMVIpV6DhcpClientUserClassOptValueDecimal
         Integer32,
      er1645v2BgrMVIpV6DhcpClientUserClassOptValueHexData
         OCTET STRING
      }

er1645v2BgrMVIpV6DhcpClientUserClassOptActions OBJECT-TYPE
   SYNTAX      VariableLengthTableActions
   MAX-ACCESS  read-write
   STATUS      current
   DESCRIPTION
      "By way of this field, some manipulations
       on this table may be performed."
   ::= {er1645v2BgrMVIpV6DhcpClientUserClassOptEntry 2}

er1645v2BgrMVIpV6DhcpClientUserClassOptTableIx OBJECT-TYPE
   SYNTAX      TableIndex
   MAX-ACCESS  not-accessible
   STATUS      current
   DESCRIPTION
      ""
   ::= {er1645v2BgrMVIpV6DhcpClientUserClassOptEntry 11}

er1645v2BgrMVIpV6DhcpClientUserClassOptValueAscii OBJECT-TYPE
   SYNTAX      DisplayString
   MAX-ACCESS  read-write
   STATUS      current
   DESCRIPTION
      "Path: bridgeGroup.editConf.ipV6.dhcp.client.userClassOpt.value.ascii"
   ::= {er1645v2BgrMVIpV6DhcpClientUserClassOptEntry 16842752}

er1645v2BgrMVIpV6DhcpClientUserClassOptValueDecimal OBJECT-TYPE
   SYNTAX      Integer32
   MAX-ACCESS  read-write
   STATUS      current
   DESCRIPTION
      "Path: bridgeGroup.editConf.ipV6.dhcp.client.userClassOpt.value.decimal"
   ::= {er1645v2BgrMVIpV6DhcpClientUserClassOptEntry 16908288}

er1645v2BgrMVIpV6DhcpClientUserClassOptValueHexData OBJECT-TYPE
   SYNTAX      OCTET STRING
   MAX-ACCESS  read-write
   STATUS      current
   DESCRIPTION
      "Path: bridgeGroup.editConf.ipV6.dhcp.client.userClassOpt.value.hexData"
   ::= {er1645v2BgrMVIpV6DhcpClientUserClassOptEntry 16973824}

er1645v2BgrMVIpV6DhcpClientVendorCl OBJECT-TYPE
   SYNTAX      SEQUENCE OF Er1645v2BgrMVIpV6DhcpClientVendorClEntry
   MAX-ACCESS  not-accessible
   STATUS      current
   DESCRIPTION
      ""
   ::= {er1645v2BgrMVIpV6 171704320}

er1645v2BgrMVIpV6DhcpClientVendorClEntry OBJECT-TYPE
   SYNTAX      Er1645v2BgrMVIpV6DhcpClientVendorClEntry
   MAX-ACCESS  not-accessible
   STATUS      current
   DESCRIPTION
      ""
   INDEX      { er1645v2BgrMVIpV6DhcpClientVendorClTableIx }
   ::= {er1645v2BgrMVIpV6DhcpClientVendorCl 1}

Er1645v2BgrMVIpV6DhcpClientVendorClEntry ::=
   SEQUENCE
      {
      er1645v2BgrMVIpV6DhcpClientVendorClActions
         VariableLengthTableActions,
      er1645v2BgrMVIpV6DhcpClientVendorClTableIx
         TableIndex,
      er1645v2BgrMVIpV6DhcpClientVendorClValueAscii
         DisplayString,
      er1645v2BgrMVIpV6DhcpClientVendorClValueDecimal
         Integer32,
      er1645v2BgrMVIpV6DhcpClientVendorClValueHexData
         OCTET STRING
      }

er1645v2BgrMVIpV6DhcpClientVendorClActions OBJECT-TYPE
   SYNTAX      VariableLengthTableActions
   MAX-ACCESS  read-write
   STATUS      current
   DESCRIPTION
      "By way of this field, some manipulations
       on this table may be performed."
   ::= {er1645v2BgrMVIpV6DhcpClientVendorClEntry 2}

er1645v2BgrMVIpV6DhcpClientVendorClTableIx OBJECT-TYPE
   SYNTAX      TableIndex
   MAX-ACCESS  not-accessible
   STATUS      current
   DESCRIPTION
      ""
   ::= {er1645v2BgrMVIpV6DhcpClientVendorClEntry 11}

er1645v2BgrMVIpV6DhcpClientVendorClValueAscii OBJECT-TYPE
   SYNTAX      DisplayString
   MAX-ACCESS  read-write
   STATUS      current
   DESCRIPTION
      "Path: bridgeGroup.editConf.ipV6.dhcp.client.vendorClassOpt.value.ascii"
   ::= {er1645v2BgrMVIpV6DhcpClientVendorClEntry 16842752}

er1645v2BgrMVIpV6DhcpClientVendorClValueDecimal OBJECT-TYPE
   SYNTAX      Integer32
   MAX-ACCESS  read-write
   STATUS      current
   DESCRIPTION
      "Path: bridgeGroup.editConf.ipV6.dhcp.client.vendorClassOpt.value.decimal"
   ::= {er1645v2BgrMVIpV6DhcpClientVendorClEntry 16908288}

er1645v2BgrMVIpV6DhcpClientVendorClValueHexData OBJECT-TYPE
   SYNTAX      OCTET STRING
   MAX-ACCESS  read-write
   STATUS      current
   DESCRIPTION
      "Path: bridgeGroup.editConf.ipV6.dhcp.client.vendorClassOpt.value.hexData"
   ::= {er1645v2BgrMVIpV6DhcpClientVendorClEntry 16973824}

er1645v2BgrMVIpV6DhcpRelayDestinations OBJECT-TYPE
   SYNTAX      SEQUENCE OF Er1645v2BgrMVIpV6DhcpRelayDestinationsEntry
   MAX-ACCESS  not-accessible
   STATUS      current
   DESCRIPTION
      ""
   ::= {er1645v2BgrMVIpV6 174080000}

er1645v2BgrMVIpV6DhcpRelayDestinationsEntry OBJECT-TYPE
   SYNTAX      Er1645v2BgrMVIpV6DhcpRelayDestinationsEntry
   MAX-ACCESS  not-accessible
   STATUS      current
   DESCRIPTION
      ""
   INDEX      { er1645v2BgrMVIpV6DhcpRelayDestinationsTableIx }
   ::= {er1645v2BgrMVIpV6DhcpRelayDestinations 1}

Er1645v2BgrMVIpV6DhcpRelayDestinationsEntry ::=
   SEQUENCE
      {
      er1645v2BgrMVIpV6DhcpRelayDestinationsActions
         VariableLengthTableActions,
      er1645v2BgrMVIpV6DhcpRelayDestinationsTableIx
         TableIndex,
      er1645v2BgrMVIpV6DhcpRelayDestinationsAddress
         Ipv6Address,
      er1645v2BgrMVIpV6DhcpRelayDestinationsInterface
         DisplayString
      }

er1645v2BgrMVIpV6DhcpRelayDestinationsActions OBJECT-TYPE
   SYNTAX      VariableLengthTableActions
   MAX-ACCESS  read-write
   STATUS      current
   DESCRIPTION
      "By way of this field, some manipulations
       on this table may be performed."
   ::= {er1645v2BgrMVIpV6DhcpRelayDestinationsEntry 2}

er1645v2BgrMVIpV6DhcpRelayDestinationsTableIx OBJECT-TYPE
   SYNTAX      TableIndex
   MAX-ACCESS  not-accessible
   STATUS      current
   DESCRIPTION
      ""
   ::= {er1645v2BgrMVIpV6DhcpRelayDestinationsEntry 11}

er1645v2BgrMVIpV6DhcpRelayDestinationsAddress OBJECT-TYPE
   SYNTAX      Ipv6Address
   MAX-ACCESS  read-write
   STATUS      current
   DESCRIPTION
      "Path: bridgeGroup.editConf.ipV6.dhcp.relay.destinations.address

       ipv6 address"
   ::= {er1645v2BgrMVIpV6DhcpRelayDestinationsEntry 16777216}

er1645v2BgrMVIpV6DhcpRelayDestinationsInterface OBJECT-TYPE
   SYNTAX      DisplayString
   MAX-ACCESS  read-write
   STATUS      current
   DESCRIPTION
      "Path: bridgeGroup.editConf.ipV6.dhcp.relay.destinations.interface"
   ::= {er1645v2BgrMVIpV6DhcpRelayDestinationsEntry 33554432}


er1645v2BgrMVArp OBJECT IDENTIFIER ::= {er1645v2BgrMV 19}

er1645v2BgrMVArpSSC OBJECT IDENTIFIER ::= {er1645v2BgrMVArp 1}

er1645v2BgrMVArpEntry OBJECT IDENTIFIER ::= {er1645v2BgrMVArpSSC 1}

er1645v2BgrMVArpTimeOut OBJECT-TYPE
   SYNTAX      TimeTicks
   MAX-ACCESS  read-write
   STATUS      current
   DESCRIPTION
      "Path: bridgeGroup.editConf.arp.timeOut

       Time in centi-second."
   ::= {er1645v2BgrMVArpEntry 201326592}

er1645v2BgrMVArpProxyArp OBJECT-TYPE
   SYNTAX      INTEGER
               {
               disabled (0),
               enabled (1)
               }
   MAX-ACCESS  read-write
   STATUS      current
   DESCRIPTION
      "Path: bridgeGroup.editConf.arp.proxyArp

       Possibilities:
               disabled   (0)
               enabled   (1)"
   ::= {er1645v2BgrMVArpEntry 838860800}

er1645v2BgrMVArpStaticArp OBJECT-TYPE
   SYNTAX      SEQUENCE OF Er1645v2BgrMVArpStaticArpEntry
   MAX-ACCESS  not-accessible
   STATUS      current
   DESCRIPTION
      ""
   ::= {er1645v2BgrMVArp 50331648}

er1645v2BgrMVArpStaticArpEntry OBJECT-TYPE
   SYNTAX      Er1645v2BgrMVArpStaticArpEntry
   MAX-ACCESS  not-accessible
   STATUS      current
   DESCRIPTION
      ""
   INDEX      { er1645v2BgrMVArpStaticArpTableIx }
   ::= {er1645v2BgrMVArpStaticArp 1}

Er1645v2BgrMVArpStaticArpEntry ::=
   SEQUENCE
      {
      er1645v2BgrMVArpStaticArpActions
         VariableLengthTableActions,
      er1645v2BgrMVArpStaticArpTableIx
         TableIndex,
      er1645v2BgrMVArpStaticArpMacAddress
         OCTET STRING,
      er1645v2BgrMVArpStaticArpIpAddress
         IpAddress
      }

er1645v2BgrMVArpStaticArpActions OBJECT-TYPE
   SYNTAX      VariableLengthTableActions
   MAX-ACCESS  read-write
   STATUS      current
   DESCRIPTION
      "By way of this field, some manipulations
       on this table may be performed."
   ::= {er1645v2BgrMVArpStaticArpEntry 2}

er1645v2BgrMVArpStaticArpTableIx OBJECT-TYPE
   SYNTAX      TableIndex
   MAX-ACCESS  not-accessible
   STATUS      current
   DESCRIPTION
      ""
   ::= {er1645v2BgrMVArpStaticArpEntry 11}

er1645v2BgrMVArpStaticArpMacAddress OBJECT-TYPE
   SYNTAX      OCTET STRING
   MAX-ACCESS  read-write
   STATUS      current
   DESCRIPTION
      "Path: bridgeGroup.editConf.arp.staticArp.macAddress

       MAC address."
   ::= {er1645v2BgrMVArpStaticArpEntry 16777216}

er1645v2BgrMVArpStaticArpIpAddress OBJECT-TYPE
   SYNTAX      IpAddress
   MAX-ACCESS  read-write
   STATUS      current
   DESCRIPTION
      "Path: bridgeGroup.editConf.arp.staticArp.ipAddress"
   ::= {er1645v2BgrMVArpStaticArpEntry 33554432}


er1645v2BgrMVSpanningTree OBJECT IDENTIFIER ::= {er1645v2BgrMV 5}

er1645v2BgrMVSpanningTreeSSC OBJECT IDENTIFIER ::= {er1645v2BgrMVSpanningTree 1}

er1645v2BgrMVSpanningTreeEntry OBJECT IDENTIFIER ::= {er1645v2BgrMVSpanningTreeSSC 1}

er1645v2BgrMVSpanningTreeSpTProt OBJECT-TYPE
   SYNTAX      INTEGER
               {
               none (0),
               p802d1DsmsSTPsCompatibility (2),
               p802d1D (1),
               p802d1Q (3)
               }
   MAX-ACCESS  read-write
   STATUS      current
   DESCRIPTION
      "Path: bridgeGroup.editConf.spanningTree.protocol

       Possibilities:
               none   (0)
               p802.1D - STP Compatibility   (2)
               p802.1D   (1)
               p802.1Q   (3)"
   ::= {er1645v2BgrMVSpanningTreeEntry 16777216}

er1645v2BgrMVSpanningTreeBrPrio OBJECT-TYPE
   SYNTAX      Integer32
   MAX-ACCESS  read-write
   STATUS      current
   DESCRIPTION
      "Path: bridgeGroup.editConf.spanningTree.bridgePriority"
   ::= {er1645v2BgrMVSpanningTreeEntry 33554432}

er1645v2BgrMVSpanningTreeBrMAge OBJECT-TYPE
   SYNTAX      TimeTicks
   MAX-ACCESS  read-write
   STATUS      current
   DESCRIPTION
      "Path: bridgeGroup.editConf.spanningTree.bridgeMaxAge

       Time in centi-second."
   ::= {er1645v2BgrMVSpanningTreeEntry 50331648}

er1645v2BgrMVSpanningTreeBrHTim OBJECT-TYPE
   SYNTAX      TimeTicks
   MAX-ACCESS  read-write
   STATUS      current
   DESCRIPTION
      "Path: bridgeGroup.editConf.spanningTree.bridgeHelloTime

       Time in centi-second."
   ::= {er1645v2BgrMVSpanningTreeEntry 67108864}

er1645v2BgrMVSpanningTreeBrFDel OBJECT-TYPE
   SYNTAX      TimeTicks
   MAX-ACCESS  read-write
   STATUS      current
   DESCRIPTION
      "Path: bridgeGroup.editConf.spanningTree.bridgeForwardDelay

       Time in centi-second."
   ::= {er1645v2BgrMVSpanningTreeEntry 83886080}

er1645v2BgrMVSpanningTreeTxHoldCnt OBJECT-TYPE
   SYNTAX      Integer32
   MAX-ACCESS  read-write
   STATUS      current
   DESCRIPTION
      "Path: bridgeGroup.editConf.spanningTree.transmitHoldCount"
   ::= {er1645v2BgrMVSpanningTreeEntry 100663296}

er1645v2BgrMVSpanningTreeMstConfigIdName OBJECT-TYPE
   SYNTAX      DisplayString
   MAX-ACCESS  read-write
   STATUS      current
   DESCRIPTION
      "Path: bridgeGroup.editConf.spanningTree.mstConfigId.name"
   ::= {er1645v2BgrMVSpanningTreeEntry 117506048}

er1645v2BgrMVSpanningTreeMstConfigIdRevisionLevel OBJECT-TYPE
   SYNTAX      Integer32
   MAX-ACCESS  read-write
   STATUS      current
   DESCRIPTION
      "Path: bridgeGroup.editConf.spanningTree.mstConfigId.revisionLevel"
   ::= {er1645v2BgrMVSpanningTreeEntry 117571584}

er1645v2BgrMVSpanningTreeMaxHops OBJECT-TYPE
   SYNTAX      Integer32
   MAX-ACCESS  read-write
   STATUS      current
   DESCRIPTION
      "Path: bridgeGroup.editConf.spanningTree.maxHops"
   ::= {er1645v2BgrMVSpanningTreeEntry 134217728}


er1645v2BgrMVLocalAccess OBJECT-TYPE
   SYNTAX      INTEGER
               {
               permitted (0),
               restricted (1)
               }
   MAX-ACCESS  read-write
   STATUS      current
   DESCRIPTION
      "Path: bridgeGroup.editConf.localAccess
       Info: restricts access to protocolstack via bridgegroup

       Possibilities:
               permitted   (0)
               restricted   (1)"
   ::= {er1645v2BgrMV 28}


er1645v2BgrMVAccessControl OBJECT IDENTIFIER ::= {er1645v2BgrMV 29}

er1645v2BgrMVAccessControlSSC OBJECT IDENTIFIER ::= {er1645v2BgrMVAccessControl 1}

er1645v2BgrMVAccessControlEntry OBJECT IDENTIFIER ::= {er1645v2BgrMVAccessControlSSC 1}

er1645v2BgrMVAccessControlInAccessList OBJECT-TYPE
   SYNTAX      DisplayString
   MAX-ACCESS  read-write
   STATUS      current
   DESCRIPTION
      "Path: bridgeGroup.editConf.accessControl.inAccessList"
   ::= {er1645v2BgrMVAccessControlEntry 83886080}

er1645v2BgrMVAccessControlLimBC OBJECT-TYPE
   SYNTAX      INTEGER
               {
               disabled (0),
               enabled (1)
               }
   MAX-ACCESS  read-write
   STATUS      current
   DESCRIPTION
      "Path: bridgeGroup.editConf.accessControl.limitBroadcasts

       Possibilities:
               disabled   (0)
               enabled   (1)"
   ::= {er1645v2BgrMVAccessControlEntry 134217728}


er1645v2BgrMVIp OBJECT IDENTIFIER ::= {er1645v2BgrMV 18}

er1645v2BgrMVIpSSC OBJECT IDENTIFIER ::= {er1645v2BgrMVIp 1}

er1645v2BgrMVIpEntry OBJECT IDENTIFIER ::= {er1645v2BgrMVIpSSC 1}

er1645v2BgrMVIpVrfRouter OBJECT-TYPE
   SYNTAX      DisplayString
   MAX-ACCESS  read-write
   STATUS      current
   DESCRIPTION
      "Path: bridgeGroup.editConf.ip.vrfRouter"
   ::= {er1645v2BgrMVIpEntry 738197504}

er1645v2BgrMVIpAdr OBJECT-TYPE
   SYNTAX      IpAddress
   MAX-ACCESS  read-write
   STATUS      current
   DESCRIPTION
      "Path: bridgeGroup.editConf.ip.address"
   ::= {er1645v2BgrMVIpEntry 2030043136}

er1645v2BgrMVIpNetm OBJECT-TYPE
   SYNTAX      IpAddress
   MAX-ACCESS  read-write
   STATUS      current
   DESCRIPTION
      "Path: bridgeGroup.editConf.ip.netMask"
   ::= {er1645v2BgrMVIpEntry 2063597568}

er1645v2BgrMVIpSNetName OBJECT-TYPE
   SYNTAX      INTEGER
               {
               slOPTg (0),
               corp (2),
               dmz (3),
               internet (1)
               }
   MAX-ACCESS  read-write
   STATUS      current
   DESCRIPTION
      "Path: bridgeGroup.editConf.ip.sNet.name

       Possibilities:
               <OPT>   (0)
               corp   (2)
               dmz   (3)
               internet   (1)"
   ::= {er1645v2BgrMVIpEntry 855703552}

er1645v2BgrMVIpSNetCust OBJECT-TYPE
   SYNTAX      DisplayString
   MAX-ACCESS  read-write
   STATUS      current
   DESCRIPTION
      "Path: bridgeGroup.editConf.ip.sNet.custom"
   ::= {er1645v2BgrMVIpEntry 855769088}

er1645v2BgrMVIpDhcpC OBJECT-TYPE
   SYNTAX      INTEGER
               {
               disabled (0),
               enabled (1)
               }
   MAX-ACCESS  read-write
   STATUS      current
   DESCRIPTION
      "Path: bridgeGroup.editConf.ip.dhcpClient

       Possibilities:
               disabled   (0)
               enabled   (1)"
   ::= {er1645v2BgrMVIpEntry 838860800}

er1645v2BgrMVIpDhcpGatewayPreference OBJECT-TYPE
   SYNTAX      Integer32
   MAX-ACCESS  read-write
   STATUS      current
   DESCRIPTION
      "Path: bridgeGroup.editConf.ip.dhcp.gatewayPreference"
   ::= {er1645v2BgrMVIpEntry 872480768}

er1645v2BgrMVIpDhcpRoutePreference OBJECT-TYPE
   SYNTAX      Integer32
   MAX-ACCESS  read-write
   STATUS      current
   DESCRIPTION
      "Path: bridgeGroup.editConf.ip.dhcp.routePreference"
   ::= {er1645v2BgrMVIpEntry 872546304}

er1645v2BgrMVIpDhcpDnsPreference OBJECT-TYPE
   SYNTAX      Integer32
   MAX-ACCESS  read-write
   STATUS      current
   DESCRIPTION
      "Path: bridgeGroup.editConf.ip.dhcp.dnsPreference"
   ::= {er1645v2BgrMVIpEntry 872611840}

er1645v2BgrMVIpMtu OBJECT-TYPE
   SYNTAX      Integer32
   MAX-ACCESS  read-write
   STATUS      current
   DESCRIPTION
      "Path: bridgeGroup.editConf.ip.mtu"
   ::= {er1645v2BgrMVIpEntry 671088640}

er1645v2BgrMVIpMssAdjust OBJECT-TYPE
   SYNTAX      INTEGER
               {
               disabled (0),
               auto (65536)
               }
   MAX-ACCESS  read-write
   STATUS      current
   DESCRIPTION
      "Path: bridgeGroup.editConf.ip.mssAdjust

       Possibilities:
               disabled   (0)
               auto   (65536)"
   ::= {er1645v2BgrMVIpEntry 754974720}

er1645v2BgrMVIpRipMetric OBJECT-TYPE
   SYNTAX      Integer32
   MAX-ACCESS  read-write
   STATUS      current
   DESCRIPTION
      "Path: bridgeGroup.editConf.ip.rip.metric"
   ::= {er1645v2BgrMVIpEntry 353566720}

er1645v2BgrMVIpRipMetricOut OBJECT-TYPE
   SYNTAX      Integer32
   MAX-ACCESS  read-write
   STATUS      current
   DESCRIPTION
      "Path: bridgeGroup.editConf.ip.rip.metricOut"
   ::= {er1645v2BgrMVIpEntry 353632256}

er1645v2BgrMVIpRipMode OBJECT-TYPE
   SYNTAX      INTEGER
               {
               disabled (0),
               passive (1),
               active (2)
               }
   MAX-ACCESS  read-write
   STATUS      current
   DESCRIPTION
      "Path: bridgeGroup.editConf.ip.rip.mode

       Possibilities:
               disabled   (0)
               passive   (1)
               active   (2)"
   ::= {er1645v2BgrMVIpEntry 353697792}

er1645v2BgrMVIpRipTxVer OBJECT-TYPE
   SYNTAX      INTEGER
               {
               rip1 (0),
               rip2 (1),
               rip1mcompatible (2)
               }
   MAX-ACCESS  read-write
   STATUS      current
   DESCRIPTION
      "Path: bridgeGroup.editConf.ip.rip.txVersion

       Possibilities:
               rip1   (0)
               rip2   (1)
               rip1-compatible   (2)"
   ::= {er1645v2BgrMVIpEntry 354615296}

er1645v2BgrMVIpRipRxVer OBJECT-TYPE
   SYNTAX      INTEGER
               {
               rip1only (0),
               rip2only (1),
               rip12 (2)
               }
   MAX-ACCESS  read-write
   STATUS      current
   DESCRIPTION
      "Path: bridgeGroup.editConf.ip.rip.rxVersion

       Possibilities:
               rip1only   (0)
               rip2only   (1)
               rip1&2   (2)"
   ::= {er1645v2BgrMVIpEntry 354680832}

er1645v2BgrMVIpRipSplitH OBJECT-TYPE
   SYNTAX      INTEGER
               {
               disabled (0),
               enabled (1),
               poisonedReverse (2)
               }
   MAX-ACCESS  read-write
   STATUS      current
   DESCRIPTION
      "Path: bridgeGroup.editConf.ip.rip.splitHorizon

       Possibilities:
               disabled   (0)
               enabled   (1)
               poisonedReverse   (2)"
   ::= {er1645v2BgrMVIpEntry 353828864}

er1645v2BgrMVIpRipAuth OBJECT-TYPE
   SYNTAX      INTEGER
               {
               disabled (0),
               texts (1),
               md5 (2)
               }
   MAX-ACCESS  read-write
   STATUS      current
   DESCRIPTION
      "Path: bridgeGroup.editConf.ip.rip.authentication

       Possibilities:
               disabled   (0)
               text    (1)
               md5   (2)"
   ::= {er1645v2BgrMVIpEntry 353501184}

er1645v2BgrMVIpRipFilter OBJECT-TYPE
   SYNTAX      DisplayString
   MAX-ACCESS  read-write
   STATUS      current
   DESCRIPTION
      "Path: bridgeGroup.editConf.ip.rip.filter"
   ::= {er1645v2BgrMVIpEntry 354418688}

er1645v2BgrMVIpRipFilterIn OBJECT-TYPE
   SYNTAX      DisplayString
   MAX-ACCESS  read-write
   STATUS      current
   DESCRIPTION
      "Path: bridgeGroup.editConf.ip.rip.filterIn"
   ::= {er1645v2BgrMVIpEntry 354484224}

er1645v2BgrMVIpRipClearNextHop OBJECT-TYPE
   SYNTAX      INTEGER
               {
               disabled (0),
               enabled (1)
               }
   MAX-ACCESS  read-write
   STATUS      current
   DESCRIPTION
      "Path: bridgeGroup.editConf.ip.rip.clearNextHop

       Possibilities:
               disabled   (0)
               enabled   (1)"
   ::= {er1645v2BgrMVIpEntry 352452608}

er1645v2BgrMVIpAccPol OBJECT-TYPE
   SYNTAX      DisplayString
   MAX-ACCESS  read-write
   STATUS      current
   DESCRIPTION
      "Path: bridgeGroup.editConf.ip.accessPolicy"
   ::= {er1645v2BgrMVIpEntry 704643072}

er1645v2BgrMVIpAB OBJECT-TYPE
   SYNTAX      DisplayString
   MAX-ACCESS  read-write
   STATUS      current
   DESCRIPTION
      "Path: bridgeGroup.editConf.ip.trafficPolicy"
   ::= {er1645v2BgrMVIpEntry 234881024}

er1645v2BgrMVIpMA OBJECT-TYPE
   SYNTAX      INTEGER
               {
               disabled (0),
               enabled (1)
               }
   MAX-ACCESS  read-write
   STATUS      current
   DESCRIPTION
      "Path: bridgeGroup.editConf.ip.mgmtAccess

       Possibilities:
               disabled   (0)
               enabled   (1)"
   ::= {er1645v2BgrMVIpEntry 268435456}

er1645v2BgrMVIpMF OBJECT-TYPE
   SYNTAX      Integer32
   MAX-ACCESS  read-write
   STATUS      current
   DESCRIPTION
      "Path: bridgeGroup.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2BgrMVIpEntry 285212672}

er1645v2BgrMVIpDB OBJECT-TYPE
   SYNTAX      INTEGER
               {
               disabled (0),
               enabled (1)
               }
   MAX-ACCESS  read-write
   STATUS      current
   DESCRIPTION
      "Path: bridgeGroup.editConf.ip.directedBroadcasts

       Possibilities:
               disabled   (0)
               enabled   (1)"
   ::= {er1645v2BgrMVIpEntry 369098752}

er1645v2BgrMVIpIR OBJECT-TYPE
   SYNTAX      INTEGER
               {
               disabled (0),
               enabled (1)
               }
   MAX-ACCESS  read-write
   STATUS      current
   DESCRIPTION
      "Path: bridgeGroup.editConf.ip.icmpRedirects

       Possibilities:
               disabled   (0)
               enabled   (1)"
   ::= {er1645v2BgrMVIpEntry 436207616}

er1645v2BgrMVIpIgmp OBJECT-TYPE
   SYNTAX      INTEGER
               {
               disabled (0),
               proxy (1),
               router (2),
               v3Router (5)
               }
   MAX-ACCESS  read-write
   STATUS      current
   DESCRIPTION
      "Path: bridgeGroup.editConf.ip.igmp

       Possibilities:
               disabled   (0)
               proxy   (1)
               router   (2)
               v3Router   (5)"
   ::= {er1645v2BgrMVIpEntry 536870912}

er1645v2BgrMVIpNN OBJECT-TYPE
   SYNTAX      DisplayString
   MAX-ACCESS  read-write
   STATUS      current
   DESCRIPTION
      "Path: bridgeGroup.editConf.ip.nat"
   ::= {er1645v2BgrMVIpEntry 452984832}

er1645v2BgrMVIpVrrp OBJECT-TYPE
   SYNTAX      INTEGER
               {
               disabled (0),
               enabled (1)
               }
   MAX-ACCESS  read-write
   STATUS      current
   DESCRIPTION
      "Path: bridgeGroup.editConf.ip.vrrp

       Possibilities:
               disabled   (0)
               enabled   (1)"
   ::= {er1645v2BgrMVIpEntry 721420288}

er1645v2BgrMVIpPimMode OBJECT-TYPE
   SYNTAX      INTEGER
               {
               disabled (0),
               sparse (1),
               passive (2)
               }
   MAX-ACCESS  read-write
   STATUS      current
   DESCRIPTION
      "Path: bridgeGroup.editConf.ip.pim.mode

       Possibilities:
               disabled   (0)
               sparse   (1)
               passive   (2)"
   ::= {er1645v2BgrMVIpEntry 771817472}

er1645v2BgrMVIpPimDrPriority OBJECT-TYPE
   SYNTAX      Counter32
   MAX-ACCESS  read-write
   STATUS      current
   DESCRIPTION
      "Path: bridgeGroup.editConf.ip.pim.drPriority

       32 bit unsigned wrappable counter."
   ::= {er1645v2BgrMVIpEntry 771883008}

er1645v2BgrMVIpPimHelloTime OBJECT-TYPE
   SYNTAX      TimeTicks
   MAX-ACCESS  read-write
   STATUS      current
   DESCRIPTION
      "Path: bridgeGroup.editConf.ip.pim.helloTime

       Time in centi-second."
   ::= {er1645v2BgrMVIpEntry 771948544}

er1645v2BgrMVIpPimPropagationDelay OBJECT-TYPE
   SYNTAX      TimeTicks
   MAX-ACCESS  read-write
   STATUS      current
   DESCRIPTION
      "Path: bridgeGroup.editConf.ip.pim.propagationDelay

       Time in centi-second."
   ::= {er1645v2BgrMVIpEntry 772014080}

er1645v2BgrMVIpPimOverrideInterval OBJECT-TYPE
   SYNTAX      TimeTicks
   MAX-ACCESS  read-write
   STATUS      current
   DESCRIPTION
      "Path: bridgeGroup.editConf.ip.pim.overrideInterval

       Time in centi-second."
   ::= {er1645v2BgrMVIpEntry 772079616}

er1645v2BgrMVIpPimBsrBorder OBJECT-TYPE
   SYNTAX      INTEGER
               {
               disabled (0),
               enabled (1)
               }
   MAX-ACCESS  read-write
   STATUS      current
   DESCRIPTION
      "Path: bridgeGroup.editConf.ip.pim.bsrBorder

       Possibilities:
               disabled   (0)
               enabled   (1)"
   ::= {er1645v2BgrMVIpEntry 772145152}

er1645v2BgrMVIpPimTtlThreshold OBJECT-TYPE
   SYNTAX      Integer32
   MAX-ACCESS  read-write
   STATUS      current
   DESCRIPTION
      "Path: bridgeGroup.editConf.ip.pim.ttlThreshold"
   ::= {er1645v2BgrMVIpEntry 772210688}

er1645v2BgrMVIpIMNetworkUnreachable OBJECT-TYPE
   SYNTAX      INTEGER
               {
               disabled (0),
               enabled (1)
               }
   MAX-ACCESS  read-write
   STATUS      current
   DESCRIPTION
      "Path: bridgeGroup.editConf.ip.icmpMessages.networkUnreachable

       Possibilities:
               disabled   (0)
               enabled   (1)"
   ::= {er1645v2BgrMVIpEntry 788594688}

er1645v2BgrMVIpIMHostUnreachable OBJECT-TYPE
   SYNTAX      INTEGER
               {
               disabled (0),
               enabled (1)
               }
   MAX-ACCESS  read-write
   STATUS      current
   DESCRIPTION
      "Path: bridgeGroup.editConf.ip.icmpMessages.hostUnreachable

       Possibilities:
               disabled   (0)
               enabled   (1)"
   ::= {er1645v2BgrMVIpEntry 788660224}

er1645v2BgrMVIpIMProtocolUnreachable OBJECT-TYPE
   SYNTAX      INTEGER
               {
               disabled (0),
               enabled (1)
               }
   MAX-ACCESS  read-write
   STATUS      current
   DESCRIPTION
      "Path: bridgeGroup.editConf.ip.icmpMessages.protocolUnreachable

       Possibilities:
               disabled   (0)
               enabled   (1)"
   ::= {er1645v2BgrMVIpEntry 788725760}

er1645v2BgrMVIpIMPortUnreachable OBJECT-TYPE
   SYNTAX      INTEGER
               {
               disabled (0),
               enabled (1)
               }
   MAX-ACCESS  read-write
   STATUS      current
   DESCRIPTION
      "Path: bridgeGroup.editConf.ip.icmpMessages.portUnreachable

       Possibilities:
               disabled   (0)
               enabled   (1)"
   ::= {er1645v2BgrMVIpEntry 788791296}

er1645v2BgrMVIpIMMtuExceeded OBJECT-TYPE
   SYNTAX      INTEGER
               {
               disabled (0),
               enabled (1)
               }
   MAX-ACCESS  read-write
   STATUS      current
   DESCRIPTION
      "Path: bridgeGroup.editConf.ip.icmpMessages.mtuExceeded

       Possibilities:
               disabled   (0)
               enabled   (1)"
   ::= {er1645v2BgrMVIpEntry 788856832}

er1645v2BgrMVIpIMAdminProhibited OBJECT-TYPE
   SYNTAX      INTEGER
               {
               disabled (0),
               enabled (1)
               }
   MAX-ACCESS  read-write
   STATUS      current
   DESCRIPTION
      "Path: bridgeGroup.editConf.ip.icmpMessages.adminProhibited

       Possibilities:
               disabled   (0)
               enabled   (1)"
   ::= {er1645v2BgrMVIpEntry 788922368}

er1645v2BgrMVIpIMTtlExceeded OBJECT-TYPE
   SYNTAX      INTEGER
               {
               disabled (0),
               enabled (1)
               }
   MAX-ACCESS  read-write
   STATUS      current
   DESCRIPTION
      "Path: bridgeGroup.editConf.ip.icmpMessages.ttlExceeded

       Possibilities:
               disabled   (0)
               enabled   (1)"
   ::= {er1645v2BgrMVIpEntry 788987904}

er1645v2BgrMVIpIMRedirect OBJECT-TYPE
   SYNTAX      INTEGER
               {
               disabled (0),
               enabled (1)
               }
   MAX-ACCESS  read-write
   STATUS      current
   DESCRIPTION
      "Path: bridgeGroup.editConf.ip.icmpMessages.redirect

       Possibilities:
               disabled   (0)
               enabled   (1)"
   ::= {er1645v2BgrMVIpEntry 789053440}

er1645v2BgrMVIpSaddr OBJECT-TYPE
   SYNTAX      SEQUENCE OF Er1645v2BgrMVIpSaddrEntry
   MAX-ACCESS  not-accessible
   STATUS      current
   DESCRIPTION
      ""
   ::= {er1645v2BgrMVIp 385875968}

er1645v2BgrMVIpSaddrEntry OBJECT-TYPE
   SYNTAX      Er1645v2BgrMVIpSaddrEntry
   MAX-ACCESS  not-accessible
   STATUS      current
   DESCRIPTION
      ""
   INDEX      { er1645v2BgrMVIpSaddrTableIx }
   ::= {er1645v2BgrMVIpSaddr 1}

Er1645v2BgrMVIpSaddrEntry ::=
   SEQUENCE
      {
      er1645v2BgrMVIpSaddrActions
         VariableLengthTableActions,
      er1645v2BgrMVIpSaddrTableIx
         TableIndex,
      er1645v2BgrMVIpSaddrAddress
         IpAddress,
      er1645v2BgrMVIpSaddrNetMask
         IpAddress
      }

er1645v2BgrMVIpSaddrActions OBJECT-TYPE
   SYNTAX      VariableLengthTableActions
   MAX-ACCESS  read-write
   STATUS      current
   DESCRIPTION
      "By way of this field, some manipulations
       on this table may be performed."
   ::= {er1645v2BgrMVIpSaddrEntry 2}

er1645v2BgrMVIpSaddrTableIx OBJECT-TYPE
   SYNTAX      TableIndex
   MAX-ACCESS  not-accessible
   STATUS      current
   DESCRIPTION
      ""
   ::= {er1645v2BgrMVIpSaddrEntry 11}

er1645v2BgrMVIpSaddrAddress OBJECT-TYPE
   SYNTAX      IpAddress
   MAX-ACCESS  read-write
   STATUS      current
   DESCRIPTION
      "Path: bridgeGroup.editConf.ip.secondaryIp.address"
   ::= {er1645v2BgrMVIpSaddrEntry 2030043136}

er1645v2BgrMVIpSaddrNetMask OBJECT-TYPE
   SYNTAX      IpAddress
   MAX-ACCESS  read-write
   STATUS      current
   DESCRIPTION
      "Path: bridgeGroup.editConf.ip.secondaryIp.netMask"
   ::= {er1645v2BgrMVIpSaddrEntry 2063597568}

er1645v2BgrMVIpH OBJECT-TYPE
   SYNTAX      SEQUENCE OF Er1645v2BgrMVIpHEntry
   MAX-ACCESS  not-accessible
   STATUS      current
   DESCRIPTION
      ""
   ::= {er1645v2BgrMVIp 251658240}

er1645v2BgrMVIpHEntry OBJECT-TYPE
   SYNTAX      Er1645v2BgrMVIpHEntry
   MAX-ACCESS  not-accessible
   STATUS      current
   DESCRIPTION
      ""
   INDEX      { er1645v2BgrMVIpHTableIx }
   ::= {er1645v2BgrMVIpH 1}

Er1645v2BgrMVIpHEntry ::=
   SEQUENCE
      {
      er1645v2BgrMVIpHActions
         VariableLengthTableActions,
      er1645v2BgrMVIpHTableIx
         TableIndex,
      er1645v2BgrMVIpHAddress
         IpAddress,
      er1645v2BgrMVIpHDhcpRelayOptionSubscriberId
         DisplayString
      }

er1645v2BgrMVIpHActions OBJECT-TYPE
   SYNTAX      VariableLengthTableActions
   MAX-ACCESS  read-write
   STATUS      current
   DESCRIPTION
      "By way of this field, some manipulations
       on this table may be performed."
   ::= {er1645v2BgrMVIpHEntry 2}

er1645v2BgrMVIpHTableIx OBJECT-TYPE
   SYNTAX      TableIndex
   MAX-ACCESS  not-accessible
   STATUS      current
   DESCRIPTION
      ""
   ::= {er1645v2BgrMVIpHEntry 11}

er1645v2BgrMVIpHAddress OBJECT-TYPE
   SYNTAX      IpAddress
   MAX-ACCESS  read-write
   STATUS      current
   DESCRIPTION
      "Path: bridgeGroup.editConf.ip.helpers.address"
   ::= {er1645v2BgrMVIpHEntry 16777216}

er1645v2BgrMVIpHDhcpRelayOptionSubscriberId OBJECT-TYPE
   SYNTAX      DisplayString
   MAX-ACCESS  read-write
   STATUS      current
   DESCRIPTION
      "Path: bridgeGroup.editConf.ip.helpers.dhcpRelayOption.subscriberId"
   ::= {er1645v2BgrMVIpHEntry 33947648}


er1645v2BgrMVVlan OBJECT IDENTIFIER ::= {er1645v2BgrMV 33}

er1645v2BgrMVVlanSSCTable OBJECT-TYPE
   SYNTAX      SEQUENCE OF Er1645v2BgrMVVlanEntry
   MAX-ACCESS  not-accessible
   STATUS      current
   DESCRIPTION
      ""
   ::= {er1645v2BgrMVVlan 1}

er1645v2BgrMVVlanEntry OBJECT-TYPE
   SYNTAX      Er1645v2BgrMVVlanEntry
   MAX-ACCESS  not-accessible
   STATUS      current
   DESCRIPTION
      ""
   INDEX      { er1645v2BgrMVVlanTableIx }
   ::= {er1645v2BgrMVVlanSSCTable 1}

Er1645v2BgrMVVlanEntry ::=
   SEQUENCE
      {
      er1645v2BgrMVVlanActions
         VariableLengthTableActions,
      er1645v2BgrMVVlanTableIx
         TableIndex,
      er1645v2BgrMVVlanName
         DisplayString,
      er1645v2BgrMVVlanRemark
         DisplayString,
      er1645v2BgrMVVlanAdminStatus
         INTEGER,
      er1645v2BgrMVVlanMode
         INTEGER,
      er1645v2BgrMVVlanIpVrfRouter
         DisplayString,
      er1645v2BgrMVVlanIpAdr
         IpAddress,
      er1645v2BgrMVVlanIpNetm
         IpAddress,
      er1645v2BgrMVVlanIpSNetName
         INTEGER,
      er1645v2BgrMVVlanIpSNetCust
         DisplayString,
      er1645v2BgrMVVlanIpDhcpC
         INTEGER,
      er1645v2BgrMVVlanIpDhcpGatewayPreference
         Integer32,
      er1645v2BgrMVVlanIpDhcpRoutePreference
         Integer32,
      er1645v2BgrMVVlanIpDhcpDnsPreference
         Integer32,
      er1645v2BgrMVVlanIpMtu
         Integer32,
      er1645v2BgrMVVlanIpMssAdjust
         INTEGER,
      er1645v2BgrMVVlanIpRipMetric
         Integer32,
      er1645v2BgrMVVlanIpRipMetricOut
         Integer32,
      er1645v2BgrMVVlanIpRipMode
         INTEGER,
      er1645v2BgrMVVlanIpRipTxVer
         INTEGER,
      er1645v2BgrMVVlanIpRipRxVer
         INTEGER,
      er1645v2BgrMVVlanIpRipSplitH
         INTEGER,
      er1645v2BgrMVVlanIpRipAuth
         INTEGER,
      er1645v2BgrMVVlanIpRipFilter
         DisplayString,
      er1645v2BgrMVVlanIpRipFilterIn
         DisplayString,
      er1645v2BgrMVVlanIpRipClearNextHop
         INTEGER,
      er1645v2BgrMVVlanIpAccPol
         DisplayString,
      er1645v2BgrMVVlanIpAB
         DisplayString,
      er1645v2BgrMVVlanIpMA
         INTEGER,
      er1645v2BgrMVVlanIpMF
         Integer32,
      er1645v2BgrMVVlanIpDB
         INTEGER,
      er1645v2BgrMVVlanIpIR
         INTEGER,
      er1645v2BgrMVVlanIpIgmp
         INTEGER,
      er1645v2BgrMVVlanIpNN
         DisplayString,
      er1645v2BgrMVVlanIpVrrp
         INTEGER,
      er1645v2BgrMVVlanIpPimMode
         INTEGER,
      er1645v2BgrMVVlanIpPimDrPriority
         Counter32,
      er1645v2BgrMVVlanIpPimHelloTime
         TimeTicks,
      er1645v2BgrMVVlanIpPimPropagationDelay
         TimeTicks,
      er1645v2BgrMVVlanIpPimOverrideInterval
         TimeTicks,
      er1645v2BgrMVVlanIpPimBsrBorder
         INTEGER,
      er1645v2BgrMVVlanIpPimTtlThreshold
         Integer32,
      er1645v2BgrMVVlanIpIMNetworkUnreachable
         INTEGER,
      er1645v2BgrMVVlanIpIMHostUnreachable
         INTEGER,
      er1645v2BgrMVVlanIpIMProtocolUnreachable
         INTEGER,
      er1645v2BgrMVVlanIpIMPortUnreachable
         INTEGER,
      er1645v2BgrMVVlanIpIMMtuExceeded
         INTEGER,
      er1645v2BgrMVVlanIpIMAdminProhibited
         INTEGER,
      er1645v2BgrMVVlanIpIMTtlExceeded
         INTEGER,
      er1645v2BgrMVVlanIpIMRedirect
         INTEGER,
      er1645v2BgrMVVlanIpV6VrfRouter
         DisplayString,
      er1645v2BgrMVVlanIpV6AddrAutoConfigNrDupAddrDetects
         Integer32,
      er1645v2BgrMVVlanIpV6AddrAutoConfigAcceptRa
         INTEGER,
      er1645v2BgrMVVlanIpV6AddrAutoConfigAcceptRaRdnss
         INTEGER,
      er1645v2BgrMVVlanIpV6AddrAutoConfigAcceptRaDnssl
         INTEGER,
      er1645v2BgrMVVlanIpV6DefaultRoute
         INTEGER,
      er1645v2BgrMVVlanIpV6RaSend
         INTEGER,
      er1645v2BgrMVVlanIpV6RaMinInterval
         TimeTicks,
      er1645v2BgrMVVlanIpV6RaMaxInterval
         TimeTicks,
      er1645v2BgrMVVlanIpV6RaManagedFlag
         INTEGER,
      er1645v2BgrMVVlanIpV6RaOtherConfFlag
         INTEGER,
      er1645v2BgrMVVlanIpV6RaLinkMtu
         Integer32,
      er1645v2BgrMVVlanIpV6RaReachableTime
         TimeTicks,
      er1645v2BgrMVVlanIpV6RaRetransmitTime
         TimeTicks,
      er1645v2BgrMVVlanIpV6RaHopLimit
         Integer32,
      er1645v2BgrMVVlanIpV6RaDefaultLifeTime
         TimeTicks,
      er1645v2BgrMVVlanIpV6RaDnsOptionsRdnssLifeTime
         TimeTicks,
      er1645v2BgrMVVlanIpV6RaDnsOptionsRdnssImportServers
         INTEGER,
      er1645v2BgrMVVlanIpV6RaDnsOptionsDnsslLifeTime
         TimeTicks,
      er1645v2BgrMVVlanIpV6RaDnsOptionsDnsslImportDomains
         INTEGER,
      er1645v2BgrMVVlanIpV6RsSend
         INTEGER,
      er1645v2BgrMVVlanIpV6RsMaxRandomDelay
         TimeTicks,
      er1645v2BgrMVVlanIpV6RsInterval
         TimeTicks,
      er1645v2BgrMVVlanIpV6RsMaxSolicitations
         Integer32,
      er1645v2BgrMVVlanIpV6TrafficPolicyInbound
         DisplayString,
      er1645v2BgrMVVlanIpV6TrafficPolicyOutbound
         DisplayString,
      er1645v2BgrMVVlanIpV6FirewallZone
         DisplayString,
      er1645v2BgrMVVlanIpV6DhcpClientAddrAC
         INTEGER,
      er1645v2BgrMVVlanIpV6DhcpClientPrDelMode
         INTEGER,
      er1645v2BgrMVVlanIpV6DhcpClientPrDelPool
         DisplayString,
      er1645v2BgrMVVlanIpV6DhcpClientPrDelPdExclOpt
         INTEGER,
      er1645v2BgrMVVlanIpV6DhcpClientDnsServerPref
         Integer32,
      er1645v2BgrMVVlanIpV6DhcpClientRapidCommit
         INTEGER,
      er1645v2BgrMVVlanIpV6DhcpClientTimersSolTimeOut
         TimeTicks,
      er1645v2BgrMVVlanIpV6DhcpClientTimersSolMaxRt
         TimeTicks,
      er1645v2BgrMVVlanIpV6DhcpClientTimersInfoRefresh
         TimeTicks,
      er1645v2BgrMVVlanIpV6DhcpServerMode
         INTEGER,
      er1645v2BgrMVVlanIpV6DhcpServerPreference
         Integer32,
      er1645v2BgrMVVlanIpV6DhcpServerPool
         DisplayString,
      er1645v2BgrMVVlanIpV6DhcpServerRapidCommit
         INTEGER,
      er1645v2BgrMVVlanIpV6DhcpServerTimersInfoRefresh
         TimeTicks,
      er1645v2BgrMVVlanIpV6DhcpRelayMode
         INTEGER,
      er1645v2BgrMVVlanIpV6SendRedirect
         INTEGER,
      er1645v2BgrMVVlanIpV6LinkMtu
         Integer32,
      er1645v2BgrMVVlanIpV6InterfaceId
         OCTET STRING,
      er1645v2BgrMVVlanIpV6MF
         Integer32,
      er1645v2BgrMVVlanIpV6IcmpMessagesNoRoute
         INTEGER,
      er1645v2BgrMVVlanIpV6IcmpMessagesBeyondScope
         INTEGER,
      er1645v2BgrMVVlanIpV6IcmpMessagesAddressUnreachable
         INTEGER,
      er1645v2BgrMVVlanIpV6IcmpMessagesPortUnreachable
         INTEGER,
      er1645v2BgrMVVlanIpV6IcmpMessagesPacketTooBig
         INTEGER,
      er1645v2BgrMVVlanIpV6IcmpMessagesHopLimitExceeded
         INTEGER,
      er1645v2BgrMVVlanIpV6IcmpMessagesFragTimeExceeded
         INTEGER,
      er1645v2BgrMVVlanIpV6IcmpMessagesHeaderFieldErr
         INTEGER,
      er1645v2BgrMVVlanIpV6IcmpMessagesOptionUnrecognized
         INTEGER,
      er1645v2BgrMVVlanIpV6IcmpMessagesRedirect
         INTEGER,
      er1645v2BgrMVVlanVlanVid
         INTEGER,
      er1645v2BgrMVVlanVlanTpid
         INTEGER,
      er1645v2BgrMVVlanVlanTxCos
         INTEGER,
      er1645v2BgrMVVlanVlanChTos
         INTEGER,
      er1645v2BgrMVVlanVlanCTMapP0
         INTEGER,
      er1645v2BgrMVVlanVlanCTMapP1
         INTEGER,
      er1645v2BgrMVVlanVlanCTMapP2
         INTEGER,
      er1645v2BgrMVVlanVlanCTMapP3
         INTEGER,
      er1645v2BgrMVVlanVlanCTMapP4
         INTEGER,
      er1645v2BgrMVVlanVlanCTMapP5
         INTEGER,
      er1645v2BgrMVVlanVlanCTMapP6
         INTEGER,
      er1645v2BgrMVVlanVlanCTMapP7
         INTEGER,
      er1645v2BgrMVVlanVlanQCMapQueue1
         Integer32,
      er1645v2BgrMVVlanVlanQCMapQueue2
         Integer32,
      er1645v2BgrMVVlanVlanQCMapQueue3
         Integer32,
      er1645v2BgrMVVlanVlanQCMapQueue4
         Integer32,
      er1645v2BgrMVVlanVlanQCMapQueue5
         Integer32,
      er1645v2BgrMVVlanVlanQCMapLowDelayQueue
         Integer32,
      er1645v2BgrMVVlanVlanQCMapLowDelay2Queue
         Integer32,
      er1645v2BgrMVVlanVlanQCMapSystemQueue
         Integer32,
      er1645v2BgrMVVlanVlanArpTimeOut
         TimeTicks,
      er1645v2BgrMVVlanVlanArpProxyArp
         INTEGER
      }

er1645v2BgrMVVlanActions OBJECT-TYPE
   SYNTAX      VariableLengthTableActions
   MAX-ACCESS  read-write
   STATUS      current
   DESCRIPTION
      "By way of this field, some manipulations
       on this table may be performed."
   ::= {er1645v2BgrMVVlanEntry 2}

er1645v2BgrMVVlanTableIx OBJECT-TYPE
   SYNTAX      TableIndex
   MAX-ACCESS  not-accessible
   STATUS      current
   DESCRIPTION
      ""
   ::= {er1645v2BgrMVVlanEntry 11}

er1645v2BgrMVVlanName OBJECT-TYPE
   SYNTAX      DisplayString
   MAX-ACCESS  read-write
   STATUS      current
   DESCRIPTION
      "Path: bridgeGroup.editConf.vlan.name"
   ::= {er1645v2BgrMVVlanEntry 16777216}

er1645v2BgrMVVlanRemark OBJECT-TYPE
   SYNTAX      DisplayString
   MAX-ACCESS  read-write
   STATUS      current
   DESCRIPTION
      "Path: bridgeGroup.editConf.vlan.remark"
   ::= {er1645v2BgrMVVlanEntry 1157627904}

er1645v2BgrMVVlanAdminStatus OBJECT-TYPE
   SYNTAX      INTEGER
               {
               up (1),
               down (2)
               }
   MAX-ACCESS  read-write
   STATUS      current
   DESCRIPTION
      "Path: bridgeGroup.editConf.vlan.adminStatus

       Possibilities:
               up   (1)
               down   (2)"
   ::= {er1645v2BgrMVVlanEntry 33554432}

er1645v2BgrMVVlanMode OBJECT-TYPE
   SYNTAX      INTEGER
               {
               routing (1),
               ipV6 (16),
               ipV6ipV4 (17)
               }
   MAX-ACCESS  read-write
   STATUS      current
   DESCRIPTION
      "Path: bridgeGroup.editConf.vlan.mode

       Possibilities:
               routing   (1)
               ipV6   (16)
               ipV6/ipV4   (17)"
   ::= {er1645v2BgrMVVlanEntry 67108864}

er1645v2BgrMVVlanIpVrfRouter OBJECT-TYPE
   SYNTAX      DisplayString
   MAX-ACCESS  read-write
   STATUS      current
   DESCRIPTION
      "Path: bridgeGroup.editConf.vlan.ip.vrfRouter"
   ::= {er1645v2BgrMVVlanEntry 53215232}

er1645v2BgrMVVlanIpAdr OBJECT-TYPE
   SYNTAX      IpAddress
   MAX-ACCESS  read-write
   STATUS      current
   DESCRIPTION
      "Path: bridgeGroup.editConf.vlan.ip.address"
   ::= {er1645v2BgrMVVlanEntry 58261504}

er1645v2BgrMVVlanIpNetm OBJECT-TYPE
   SYNTAX      IpAddress
   MAX-ACCESS  read-write
   STATUS      current
   DESCRIPTION
      "Path: bridgeGroup.editConf.vlan.ip.netMask"
   ::= {er1645v2BgrMVVlanEntry 58392576}

er1645v2BgrMVVlanIpSNetName OBJECT-TYPE
   SYNTAX      INTEGER
               {
               slOPTg (0),
               corp (2),
               dmz (3),
               internet (1)
               }
   MAX-ACCESS  read-write
   STATUS      current
   DESCRIPTION
      "Path: bridgeGroup.editConf.vlan.ip.sNet.name

       Possibilities:
               <OPT>   (0)
               corp   (2)
               dmz   (3)
               internet   (1)"
   ::= {er1645v2BgrMVVlanEntry 53674240}

er1645v2BgrMVVlanIpSNetCust OBJECT-TYPE
   SYNTAX      DisplayString
   MAX-ACCESS  read-write
   STATUS      current
   DESCRIPTION
      "Path: bridgeGroup.editConf.vlan.ip.sNet.custom"
   ::= {er1645v2BgrMVVlanEntry 53674496}

er1645v2BgrMVVlanIpDhcpC OBJECT-TYPE
   SYNTAX      INTEGER
               {
               disabled (0),
               enabled (1)
               }
   MAX-ACCESS  read-write
   STATUS      current
   DESCRIPTION
      "Path: bridgeGroup.editConf.vlan.ip.dhcpClient

       Possibilities:
               disabled   (0)
               enabled   (1)"
   ::= {er1645v2BgrMVVlanEntry 53608448}

er1645v2BgrMVVlanIpDhcpGatewayPreference OBJECT-TYPE
   SYNTAX      Integer32
   MAX-ACCESS  read-write
   STATUS      current
   DESCRIPTION
      "Path: bridgeGroup.editConf.vlan.ip.dhcp.gatewayPreference"
   ::= {er1645v2BgrMVVlanEntry 53739776}

er1645v2BgrMVVlanIpDhcpRoutePreference OBJECT-TYPE
   SYNTAX      Integer32
   MAX-ACCESS  read-write
   STATUS      current
   DESCRIPTION
      "Path: bridgeGroup.editConf.vlan.ip.dhcp.routePreference"
   ::= {er1645v2BgrMVVlanEntry 53740032}

er1645v2BgrMVVlanIpDhcpDnsPreference OBJECT-TYPE
   SYNTAX      Integer32
   MAX-ACCESS  read-write
   STATUS      current
   DESCRIPTION
      "Path: bridgeGroup.editConf.vlan.ip.dhcp.dnsPreference"
   ::= {er1645v2BgrMVVlanEntry 53740288}

er1645v2BgrMVVlanIpMtu OBJECT-TYPE
   SYNTAX      Integer32
   MAX-ACCESS  read-write
   STATUS      current
   DESCRIPTION
      "Path: bridgeGroup.editConf.vlan.ip.mtu"
   ::= {er1645v2BgrMVVlanEntry 52953088}

er1645v2BgrMVVlanIpMssAdjust OBJECT-TYPE
   SYNTAX      INTEGER
               {
               disabled (0),
               auto (65536)
               }
   MAX-ACCESS  read-write
   STATUS      current
   DESCRIPTION
      "Path: bridgeGroup.editConf.vlan.ip.mssAdjust

       Possibilities:
               disabled   (0)
               auto   (65536)"
   ::= {er1645v2BgrMVVlanEntry 53280768}

er1645v2BgrMVVlanIpRipMetric OBJECT-TYPE
   SYNTAX      Integer32
   MAX-ACCESS  read-write
   STATUS      current
   DESCRIPTION
      "Path: bridgeGroup.editConf.vlan.ip.rip.metric"
   ::= {er1645v2BgrMVVlanEntry 51712768}

er1645v2BgrMVVlanIpRipMetricOut OBJECT-TYPE
   SYNTAX      Integer32
   MAX-ACCESS  read-write
   STATUS      current
   DESCRIPTION
      "Path: bridgeGroup.editConf.vlan.ip.rip.metricOut"
   ::= {er1645v2BgrMVVlanEntry 51713024}

er1645v2BgrMVVlanIpRipMode OBJECT-TYPE
   SYNTAX      INTEGER
               {
               disabled (0),
               passive (1),
               active (2)
               }
   MAX-ACCESS  read-write
   STATUS      current
   DESCRIPTION
      "Path: bridgeGroup.editConf.vlan.ip.rip.mode

       Possibilities:
               disabled   (0)
               passive   (1)
               active   (2)"
   ::= {er1645v2BgrMVVlanEntry 51713280}

er1645v2BgrMVVlanIpRipTxVer OBJECT-TYPE
   SYNTAX      INTEGER
               {
               rip1 (0),
               rip2 (1),
               rip1mcompatible (2)
               }
   MAX-ACCESS  read-write
   STATUS      current
   DESCRIPTION
      "Path: bridgeGroup.editConf.vlan.ip.rip.txVersion

       Possibilities:
               rip1   (0)
               rip2   (1)
               rip1-compatible   (2)"
   ::= {er1645v2BgrMVVlanEntry 51716864}

er1645v2BgrMVVlanIpRipRxVer OBJECT-TYPE
   SYNTAX      INTEGER
               {
               rip1only (0),
               rip2only (1),
               rip12 (2)
               }
   MAX-ACCESS  read-write
   STATUS      current
   DESCRIPTION
      "Path: bridgeGroup.editConf.vlan.ip.rip.rxVersion

       Possibilities:
               rip1only   (0)
               rip2only   (1)
               rip1&2   (2)"
   ::= {er1645v2BgrMVVlanEntry 51717120}

er1645v2BgrMVVlanIpRipSplitH OBJECT-TYPE
   SYNTAX      INTEGER
               {
               disabled (0),
               enabled (1),
               poisonedReverse (2)
               }
   MAX-ACCESS  read-write
   STATUS      current
   DESCRIPTION
      "Path: bridgeGroup.editConf.vlan.ip.rip.splitHorizon

       Possibilities:
               disabled   (0)
               enabled   (1)
               poisonedReverse   (2)"
   ::= {er1645v2BgrMVVlanEntry 51713792}

er1645v2BgrMVVlanIpRipAuth OBJECT-TYPE
   SYNTAX      INTEGER
               {
               disabled (0),
               texts (1),
               md5 (2)
               }
   MAX-ACCESS  read-write
   STATUS      current
   DESCRIPTION
      "Path: bridgeGroup.editConf.vlan.ip.rip.authentication

       Possibilities:
               disabled   (0)
               text    (1)
               md5   (2)"
   ::= {er1645v2BgrMVVlanEntry 51712512}

er1645v2BgrMVVlanIpRipFilter OBJECT-TYPE
   SYNTAX      DisplayString
   MAX-ACCESS  read-write
   STATUS      current
   DESCRIPTION
      "Path: bridgeGroup.editConf.vlan.ip.rip.filter"
   ::= {er1645v2BgrMVVlanEntry 51716096}

er1645v2BgrMVVlanIpRipFilterIn OBJECT-TYPE
   SYNTAX      DisplayString
   MAX-ACCESS  read-write
   STATUS      current
   DESCRIPTION
      "Path: bridgeGroup.editConf.vlan.ip.rip.filterIn"
   ::= {er1645v2BgrMVVlanEntry 51716352}

er1645v2BgrMVVlanIpRipClearNextHop OBJECT-TYPE
   SYNTAX      INTEGER
               {
               disabled (0),
               enabled (1)
               }
   MAX-ACCESS  read-write
   STATUS      current
   DESCRIPTION
      "Path: bridgeGroup.editConf.vlan.ip.rip.clearNextHop

       Possibilities:
               disabled   (0)
               enabled   (1)"
   ::= {er1645v2BgrMVVlanEntry 51708416}

er1645v2BgrMVVlanIpAccPol OBJECT-TYPE
   SYNTAX      DisplayString
   MAX-ACCESS  read-write
   STATUS      current
   DESCRIPTION
      "Path: bridgeGroup.editConf.vlan.ip.accessPolicy"
   ::= {er1645v2BgrMVVlanEntry 53084160}

er1645v2BgrMVVlanIpAB OBJECT-TYPE
   SYNTAX      DisplayString
   MAX-ACCESS  read-write
   STATUS      current
   DESCRIPTION
      "Path: bridgeGroup.editConf.vlan.ip.trafficPolicy"
   ::= {er1645v2BgrMVVlanEntry 51249152}

er1645v2BgrMVVlanIpMA OBJECT-TYPE
   SYNTAX      INTEGER
               {
               disabled (0),
               enabled (1)
               }
   MAX-ACCESS  read-write
   STATUS      current
   DESCRIPTION
      "Path: bridgeGroup.editConf.vlan.ip.mgmtAccess

       Possibilities:
               disabled   (0)
               enabled   (1)"
   ::= {er1645v2BgrMVVlanEntry 51380224}

er1645v2BgrMVVlanIpMF OBJECT-TYPE
   SYNTAX      Integer32
   MAX-ACCESS  read-write
   STATUS      current
   DESCRIPTION
      "Path: bridgeGroup.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2BgrMVVlanEntry 51445760}

er1645v2BgrMVVlanIpDB OBJECT-TYPE
   SYNTAX      INTEGER
               {
               disabled (0),
               enabled (1)
               }
   MAX-ACCESS  read-write
   STATUS      current
   DESCRIPTION
      "Path: bridgeGroup.editConf.vlan.ip.directedBroadcasts

       Possibilities:
               disabled   (0)
               enabled   (1)"
   ::= {er1645v2BgrMVVlanEntry 51773440}

er1645v2BgrMVVlanIpIR OBJECT-TYPE
   SYNTAX      INTEGER
               {
               disabled (0),
               enabled (1)
               }
   MAX-ACCESS  read-write
   STATUS      current
   DESCRIPTION
      "Path: bridgeGroup.editConf.vlan.ip.icmpRedirects

       Possibilities:
               disabled   (0)
               enabled   (1)"
   ::= {er1645v2BgrMVVlanEntry 52035584}

er1645v2BgrMVVlanIpIgmp OBJECT-TYPE
   SYNTAX      INTEGER
               {
               disabled (0),
               proxy (1),
               router (2),
               v3Router (5)
               }
   MAX-ACCESS  read-write
   STATUS      current
   DESCRIPTION
      "Path: bridgeGroup.editConf.vlan.ip.igmp

       Possibilities:
               disabled   (0)
               proxy   (1)
               router   (2)
               v3Router   (5)"
   ::= {er1645v2BgrMVVlanEntry 52428800}

er1645v2BgrMVVlanIpNN OBJECT-TYPE
   SYNTAX      DisplayString
   MAX-ACCESS  read-write
   STATUS      current
   DESCRIPTION
      "Path: bridgeGroup.editConf.vlan.ip.nat"
   ::= {er1645v2BgrMVVlanEntry 52101120}

er1645v2BgrMVVlanIpVrrp OBJECT-TYPE
   SYNTAX      INTEGER
               {
               disabled (0),
               enabled (1)
               }
   MAX-ACCESS  read-write
   STATUS      current
   DESCRIPTION
      "Path: bridgeGroup.editConf.vlan.ip.vrrp

       Possibilities:
               disabled   (0)
               enabled   (1)"
   ::= {er1645v2BgrMVVlanEntry 53149696}

er1645v2BgrMVVlanIpPimMode OBJECT-TYPE
   SYNTAX      INTEGER
               {
               disabled (0),
               sparse (1),
               passive (2)
               }
   MAX-ACCESS  read-write
   STATUS      current
   DESCRIPTION
      "Path: bridgeGroup.editConf.vlan.ip.pim.mode

       Possibilities:
               disabled   (0)
               sparse   (1)
               passive   (2)"
   ::= {er1645v2BgrMVVlanEntry 53346560}

er1645v2BgrMVVlanIpPimDrPriority OBJECT-TYPE
   SYNTAX      Counter32
   MAX-ACCESS  read-write
   STATUS      current
   DESCRIPTION
      "Path: bridgeGroup.editConf.vlan.ip.pim.drPriority

       32 bit unsigned wrappable counter."
   ::= {er1645v2BgrMVVlanEntry 53346816}

er1645v2BgrMVVlanIpPimHelloTime OBJECT-TYPE
   SYNTAX      TimeTicks
   MAX-ACCESS  read-write
   STATUS      current
   DESCRIPTION
      "Path: bridgeGroup.editConf.vlan.ip.pim.helloTime

       Time in centi-second."
   ::= {er1645v2BgrMVVlanEntry 53347072}

er1645v2BgrMVVlanIpPimPropagationDelay OBJECT-TYPE
   SYNTAX      TimeTicks
   MAX-ACCESS  read-write
   STATUS      current
   DESCRIPTION
      "Path: bridgeGroup.editConf.vlan.ip.pim.propagationDelay

       Time in centi-second."
   ::= {er1645v2BgrMVVlanEntry 53347328}

er1645v2BgrMVVlanIpPimOverrideInterval OBJECT-TYPE
   SYNTAX      TimeTicks
   MAX-ACCESS  read-write
   STATUS      current
   DESCRIPTION
      "Path: bridgeGroup.editConf.vlan.ip.pim.overrideInterval

       Time in centi-second."
   ::= {er1645v2BgrMVVlanEntry 53347584}

er1645v2BgrMVVlanIpPimBsrBorder OBJECT-TYPE
   SYNTAX      INTEGER
               {
               disabled (0),
               enabled (1)
               }
   MAX-ACCESS  read-write
   STATUS      current
   DESCRIPTION
      "Path: bridgeGroup.editConf.vlan.ip.pim.bsrBorder

       Possibilities:
               disabled   (0)
               enabled   (1)"
   ::= {er1645v2BgrMVVlanEntry 53347840}

er1645v2BgrMVVlanIpPimTtlThreshold OBJECT-TYPE
   SYNTAX      Integer32
   MAX-ACCESS  read-write
   STATUS      current
   DESCRIPTION
      "Path: bridgeGroup.editConf.vlan.ip.pim.ttlThreshold"
   ::= {er1645v2BgrMVVlanEntry 53348096}

er1645v2BgrMVVlanIpIMNetworkUnreachable OBJECT-TYPE
   SYNTAX      INTEGER
               {
               disabled (0),
               enabled (1)
               }
   MAX-ACCESS  read-write
   STATUS      current
   DESCRIPTION
      "Path: bridgeGroup.editConf.vlan.ip.icmpMessages.networkUnreachable

       Possibilities:
               disabled   (0)
               enabled   (1)"
   ::= {er1645v2BgrMVVlanEntry 53412096}

er1645v2BgrMVVlanIpIMHostUnreachable OBJECT-TYPE
   SYNTAX      INTEGER
               {
               disabled (0),
               enabled (1)
               }
   MAX-ACCESS  read-write
   STATUS      current
   DESCRIPTION
      "Path: bridgeGroup.editConf.vlan.ip.icmpMessages.hostUnreachable

       Possibilities:
               disabled   (0)
               enabled   (1)"
   ::= {er1645v2BgrMVVlanEntry 53412352}

er1645v2BgrMVVlanIpIMProtocolUnreachable OBJECT-TYPE
   SYNTAX      INTEGER
               {
               disabled (0),
               enabled (1)
               }
   MAX-ACCESS  read-write
   STATUS      current
   DESCRIPTION
      "Path: bridgeGroup.editConf.vlan.ip.icmpMessages.protocolUnreachable

       Possibilities:
               disabled   (0)
               enabled   (1)"
   ::= {er1645v2BgrMVVlanEntry 53412608}

er1645v2BgrMVVlanIpIMPortUnreachable OBJECT-TYPE
   SYNTAX      INTEGER
               {
               disabled (0),
               enabled (1)
               }
   MAX-ACCESS  read-write
   STATUS      current
   DESCRIPTION
      "Path: bridgeGroup.editConf.vlan.ip.icmpMessages.portUnreachable

       Possibilities:
               disabled   (0)
               enabled   (1)"
   ::= {er1645v2BgrMVVlanEntry 53412864}

er1645v2BgrMVVlanIpIMMtuExceeded OBJECT-TYPE
   SYNTAX      INTEGER
               {
               disabled (0),
               enabled (1)
               }
   MAX-ACCESS  read-write
   STATUS      current
   DESCRIPTION
      "Path: bridgeGroup.editConf.vlan.ip.icmpMessages.mtuExceeded

       Possibilities:
               disabled   (0)
               enabled   (1)"
   ::= {er1645v2BgrMVVlanEntry 53413120}

er1645v2BgrMVVlanIpIMAdminProhibited OBJECT-TYPE
   SYNTAX      INTEGER
               {
               disabled (0),
               enabled (1)
               }
   MAX-ACCESS  read-write
   STATUS      current
   DESCRIPTION
      "Path: bridgeGroup.editConf.vlan.ip.icmpMessages.adminProhibited

       Possibilities:
               disabled   (0)
               enabled   (1)"
   ::= {er1645v2BgrMVVlanEntry 53413376}

er1645v2BgrMVVlanIpIMTtlExceeded OBJECT-TYPE
   SYNTAX      INTEGER
               {
               disabled (0),
               enabled (1)
               }
   MAX-ACCESS  read-write
   STATUS      current
   DESCRIPTION
      "Path: bridgeGroup.editConf.vlan.ip.icmpMessages.ttlExceeded

       Possibilities:
               disabled   (0)
               enabled   (1)"
   ::= {er1645v2BgrMVVlanEntry 53413632}

er1645v2BgrMVVlanIpIMRedirect OBJECT-TYPE
   SYNTAX      INTEGER
               {
               disabled (0),
               enabled (1)
               }
   MAX-ACCESS  read-write
   STATUS      current
   DESCRIPTION
      "Path: bridgeGroup.editConf.vlan.ip.icmpMessages.redirect

       Possibilities:
               disabled   (0)
               enabled   (1)"
   ::= {er1645v2BgrMVVlanEntry 53413888}

er1645v2BgrMVVlanIpV6VrfRouter OBJECT-TYPE
   SYNTAX      DisplayString
   MAX-ACCESS  read-write
   STATUS      current
   DESCRIPTION
      "Path: bridgeGroup.editConf.vlan.ipV6.vrfRouter"
   ::= {er1645v2BgrMVVlanEntry 704708608}

er1645v2BgrMVVlanIpV6AddrAutoConfigNrDupAddrDetects OBJECT-TYPE
   SYNTAX      Integer32
   MAX-ACCESS  read-write
   STATUS      current
   DESCRIPTION
      "Path: bridgeGroup.editConf.vlan.ipV6.addrAutoConfig.nrDupAddrDetects"
   ::= {er1645v2BgrMVVlanEntry 704905472}

er1645v2BgrMVVlanIpV6AddrAutoConfigAcceptRa OBJECT-TYPE
   SYNTAX      INTEGER
               {
               disabled (0),
               enabled (1)
               }
   MAX-ACCESS  read-write
   STATUS      current
   DESCRIPTION
      "Path: bridgeGroup.editConf.vlan.ipV6.addrAutoConfig.acceptRa

       Possibilities:
               disabled   (0)
               enabled   (1)"
   ::= {er1645v2BgrMVVlanEntry 704905728}

er1645v2BgrMVVlanIpV6AddrAutoConfigAcceptRaRdnss OBJECT-TYPE
   SYNTAX      INTEGER
               {
               disabled (0),
               enabled (1)
               }
   MAX-ACCESS  read-write
   STATUS      current
   DESCRIPTION
      "Path: bridgeGroup.editConf.vlan.ipV6.addrAutoConfig.acceptRaRdnss

       Possibilities:
               disabled   (0)
               enabled   (1)"
   ::= {er1645v2BgrMVVlanEntry 704905984}

er1645v2BgrMVVlanIpV6AddrAutoConfigAcceptRaDnssl OBJECT-TYPE
   SYNTAX      INTEGER
               {
               disabled (0),
               enabled (1)
               }
   MAX-ACCESS  read-write
   STATUS      current
   DESCRIPTION
      "Path: bridgeGroup.editConf.vlan.ipV6.addrAutoConfig.acceptRaDnssl

       Possibilities:
               disabled   (0)
               enabled   (1)"
   ::= {er1645v2BgrMVVlanEntry 704906240}

er1645v2BgrMVVlanIpV6DefaultRoute OBJECT-TYPE
   SYNTAX      INTEGER
               {
               disabled (0),
               enabled (1)
               }
   MAX-ACCESS  read-write
   STATUS      current
   DESCRIPTION
      "Path: bridgeGroup.editConf.vlan.ipV6.defaultRoute

       Possibilities:
               disabled   (0)
               enabled   (1)"
   ::= {er1645v2BgrMVVlanEntry 704970752}

er1645v2BgrMVVlanIpV6RaSend OBJECT-TYPE
   SYNTAX      INTEGER
               {
               disabled (0),
               enabled (1)
               }
   MAX-ACCESS  read-write
   STATUS      current
   DESCRIPTION
      "Path: bridgeGroup.editConf.vlan.ipV6.ra.send

       Possibilities:
               disabled   (0)
               enabled   (1)"
   ::= {er1645v2BgrMVVlanEntry 705036544}

er1645v2BgrMVVlanIpV6RaMinInterval OBJECT-TYPE
   SYNTAX      TimeTicks
   MAX-ACCESS  read-write
   STATUS      current
   DESCRIPTION
      "Path: bridgeGroup.editConf.vlan.ipV6.ra.minInterval

       Time in centi-second."
   ::= {er1645v2BgrMVVlanEntry 705036800}

er1645v2BgrMVVlanIpV6RaMaxInterval OBJECT-TYPE
   SYNTAX      TimeTicks
   MAX-ACCESS  read-write
   STATUS      current
   DESCRIPTION
      "Path: bridgeGroup.editConf.vlan.ipV6.ra.maxInterval

       Time in centi-second."
   ::= {er1645v2BgrMVVlanEntry 705037056}

er1645v2BgrMVVlanIpV6RaManagedFlag OBJECT-TYPE
   SYNTAX      INTEGER
               {
               disabled (0),
               enabled (1)
               }
   MAX-ACCESS  read-write
   STATUS      current
   DESCRIPTION
      "Path: bridgeGroup.editConf.vlan.ipV6.ra.managedFlag

       Possibilities:
               disabled   (0)
               enabled   (1)"
   ::= {er1645v2BgrMVVlanEntry 705037312}

er1645v2BgrMVVlanIpV6RaOtherConfFlag OBJECT-TYPE
   SYNTAX      INTEGER
               {
               disabled (0),
               enabled (1)
               }
   MAX-ACCESS  read-write
   STATUS      current
   DESCRIPTION
      "Path: bridgeGroup.editConf.vlan.ipV6.ra.otherConfFlag

       Possibilities:
               disabled   (0)
               enabled   (1)"
   ::= {er1645v2BgrMVVlanEntry 705037568}

er1645v2BgrMVVlanIpV6RaLinkMtu OBJECT-TYPE
   SYNTAX      Integer32
   MAX-ACCESS  read-write
   STATUS      current
   DESCRIPTION
      "Path: bridgeGroup.editConf.vlan.ipV6.ra.linkMtu"
   ::= {er1645v2BgrMVVlanEntry 705037824}

er1645v2BgrMVVlanIpV6RaReachableTime OBJECT-TYPE
   SYNTAX      TimeTicks
   MAX-ACCESS  read-write
   STATUS      current
   DESCRIPTION
      "Path: bridgeGroup.editConf.vlan.ipV6.ra.reachableTime

       Time in centi-second."
   ::= {er1645v2BgrMVVlanEntry 705038080}

er1645v2BgrMVVlanIpV6RaRetransmitTime OBJECT-TYPE
   SYNTAX      TimeTicks
   MAX-ACCESS  read-write
   STATUS      current
   DESCRIPTION
      "Path: bridgeGroup.editConf.vlan.ipV6.ra.retransmitTime

       Time in centi-second."
   ::= {er1645v2BgrMVVlanEntry 705038336}

er1645v2BgrMVVlanIpV6RaHopLimit OBJECT-TYPE
   SYNTAX      Integer32
   MAX-ACCESS  read-write
   STATUS      current
   DESCRIPTION
      "Path: bridgeGroup.editConf.vlan.ipV6.ra.hopLimit"
   ::= {er1645v2BgrMVVlanEntry 705038592}

er1645v2BgrMVVlanIpV6RaDefaultLifeTime OBJECT-TYPE
   SYNTAX      TimeTicks
   MAX-ACCESS  read-write
   STATUS      current
   DESCRIPTION
      "Path: bridgeGroup.editConf.vlan.ipV6.ra.defaultLifeTime

       Time in centi-second."
   ::= {er1645v2BgrMVVlanEntry 705038848}

er1645v2BgrMVVlanIpV6RaDnsOptionsRdnssLifeTime OBJECT-TYPE
   SYNTAX      TimeTicks
   MAX-ACCESS  read-write
   STATUS      current
   DESCRIPTION
      "Path: bridgeGroup.editConf.vlan.ipV6.ra.dnsOptions.rdnss.lifeTime

       Time in centi-second."
   ::= {er1645v2BgrMVVlanEntry 705039140}

er1645v2BgrMVVlanIpV6RaDnsOptionsRdnssImportServers OBJECT-TYPE
   SYNTAX      INTEGER
               {
               disabled (0),
               enabled (1)
               }
   MAX-ACCESS  read-write
   STATUS      current
   DESCRIPTION
      "Path: bridgeGroup.editConf.vlan.ipV6.ra.dnsOptions.rdnss.importServers

       Possibilities:
               disabled   (0)
               enabled   (1)"
   ::= {er1645v2BgrMVVlanEntry 705039148}

er1645v2BgrMVVlanIpV6RaDnsOptionsDnsslLifeTime OBJECT-TYPE
   SYNTAX      TimeTicks
   MAX-ACCESS  read-write
   STATUS      current
   DESCRIPTION
      "Path: bridgeGroup.editConf.vlan.ipV6.ra.dnsOptions.dnssl.lifeTime

       Time in centi-second."
   ::= {er1645v2BgrMVVlanEntry 705039172}

er1645v2BgrMVVlanIpV6RaDnsOptionsDnsslImportDomains OBJECT-TYPE
   SYNTAX      INTEGER
               {
               disabled (0),
               enabled (1)
               }
   MAX-ACCESS  read-write
   STATUS      current
   DESCRIPTION
      "Path: bridgeGroup.editConf.vlan.ipV6.ra.dnsOptions.dnssl.importDomains

       Possibilities:
               disabled   (0)
               enabled   (1)"
   ::= {er1645v2BgrMVVlanEntry 705039180}

er1645v2BgrMVVlanIpV6RsSend OBJECT-TYPE
   SYNTAX      INTEGER
               {
               disabled (0),
               enabled (1)
               }
   MAX-ACCESS  read-write
   STATUS      current
   DESCRIPTION
      "Path: bridgeGroup.editConf.vlan.ipV6.rs.send

       Possibilities:
               disabled   (0)
               enabled   (1)"
   ::= {er1645v2BgrMVVlanEntry 705954048}

er1645v2BgrMVVlanIpV6RsMaxRandomDelay OBJECT-TYPE
   SYNTAX      TimeTicks
   MAX-ACCESS  read-write
   STATUS      current
   DESCRIPTION
      "Path: bridgeGroup.editConf.vlan.ipV6.rs.maxRandomDelay

       Time in centi-second."
   ::= {er1645v2BgrMVVlanEntry 705954304}

er1645v2BgrMVVlanIpV6RsInterval OBJECT-TYPE
   SYNTAX      TimeTicks
   MAX-ACCESS  read-write
   STATUS      current
   DESCRIPTION
      "Path: bridgeGroup.editConf.vlan.ipV6.rs.interval

       Time in centi-second."
   ::= {er1645v2BgrMVVlanEntry 705954560}

er1645v2BgrMVVlanIpV6RsMaxSolicitations OBJECT-TYPE
   SYNTAX      Integer32
   MAX-ACCESS  read-write
   STATUS      current
   DESCRIPTION
      "Path: bridgeGroup.editConf.vlan.ipV6.rs.maxSolicitations"
   ::= {er1645v2BgrMVVlanEntry 705954816}

er1645v2BgrMVVlanIpV6TrafficPolicyInbound OBJECT-TYPE
   SYNTAX      DisplayString
   MAX-ACCESS  read-write
   STATUS      current
   DESCRIPTION
      "Path: bridgeGroup.editConf.vlan.ipV6.trafficPolicy.inbound"
   ::= {er1645v2BgrMVVlanEntry 705364224}

er1645v2BgrMVVlanIpV6TrafficPolicyOutbound OBJECT-TYPE
   SYNTAX      DisplayString
   MAX-ACCESS  read-write
   STATUS      current
   DESCRIPTION
      "Path: bridgeGroup.editConf.vlan.ipV6.trafficPolicy.outbound"
   ::= {er1645v2BgrMVVlanEntry 705364480}

er1645v2BgrMVVlanIpV6FirewallZone OBJECT-TYPE
   SYNTAX      DisplayString
   MAX-ACCESS  read-write
   STATUS      current
   DESCRIPTION
      "Path: bridgeGroup.editConf.vlan.ipV6.firewall.zone"
   ::= {er1645v2BgrMVVlanEntry 705429760}

er1645v2BgrMVVlanIpV6DhcpClientAddrAC OBJECT-TYPE
   SYNTAX      INTEGER
               {
               disabled (0),
               enabled (1)
               }
   MAX-ACCESS  read-write
   STATUS      current
   DESCRIPTION
      "Path: bridgeGroup.editConf.vlan.ipV6.dhcp.client.addrAutoConfig

       Possibilities:
               disabled   (0)
               enabled   (1)"
   ::= {er1645v2BgrMVVlanEntry 705307648}

er1645v2BgrMVVlanIpV6DhcpClientPrDelMode OBJECT-TYPE
   SYNTAX      INTEGER
               {
               disabled (0),
               enabled (1)
               }
   MAX-ACCESS  read-write
   STATUS      current
   DESCRIPTION
      "Path: bridgeGroup.editConf.vlan.ipV6.dhcp.client.pd.mode

       Possibilities:
               disabled   (0)
               enabled   (1)"
   ::= {er1645v2BgrMVVlanEntry 705308676}

er1645v2BgrMVVlanIpV6DhcpClientPrDelPool OBJECT-TYPE
   SYNTAX      DisplayString
   MAX-ACCESS  read-write
   STATUS      current
   DESCRIPTION
      "Path: bridgeGroup.editConf.vlan.ipV6.dhcp.client.pd.pool"
   ::= {er1645v2BgrMVVlanEntry 705308680}

er1645v2BgrMVVlanIpV6DhcpClientPrDelPdExclOpt OBJECT-TYPE
   SYNTAX      INTEGER
               {
               disabled (0),
               enabled (1)
               }
   MAX-ACCESS  read-write
   STATUS      current
   DESCRIPTION
      "Path: bridgeGroup.editConf.vlan.ipV6.dhcp.client.pd.pdExclOpt

       Possibilities:
               disabled   (0)
               enabled   (1)"
   ::= {er1645v2BgrMVVlanEntry 705308684}

er1645v2BgrMVVlanIpV6DhcpClientDnsServerPref OBJECT-TYPE
   SYNTAX      Integer32
   MAX-ACCESS  read-write
   STATUS      current
   DESCRIPTION
      "Path: bridgeGroup.editConf.vlan.ipV6.dhcp.client.dns.serverPref"
   ::= {er1645v2BgrMVVlanEntry 705310724}

er1645v2BgrMVVlanIpV6DhcpClientRapidCommit OBJECT-TYPE
   SYNTAX      INTEGER
               {
               disabled (0),
               enabled (1)
               }
   MAX-ACCESS  read-write
   STATUS      current
   DESCRIPTION
      "Path: bridgeGroup.editConf.vlan.ipV6.dhcp.client.rapidCommit

       Possibilities:
               disabled   (0)
               enabled   (1)"
   ::= {er1645v2BgrMVVlanEntry 705309696}

er1645v2BgrMVVlanIpV6DhcpClientTimersSolTimeOut OBJECT-TYPE
   SYNTAX      TimeTicks
   MAX-ACCESS  read-write
   STATUS      current
   DESCRIPTION
      "Path: bridgeGroup.editConf.vlan.ipV6.dhcp.client.timers.solTimeOut

       Time in centi-second."
   ::= {er1645v2BgrMVVlanEntry 705311748}

er1645v2BgrMVVlanIpV6DhcpClientTimersSolMaxRt OBJECT-TYPE
   SYNTAX      TimeTicks
   MAX-ACCESS  read-write
   STATUS      current
   DESCRIPTION
      "Path: bridgeGroup.editConf.vlan.ipV6.dhcp.client.timers.solMaxRt

       Time in centi-second."
   ::= {er1645v2BgrMVVlanEntry 705311752}

er1645v2BgrMVVlanIpV6DhcpClientTimersInfoRefresh OBJECT-TYPE
   SYNTAX      TimeTicks
   MAX-ACCESS  read-write
   STATUS      current
   DESCRIPTION
      "Path: bridgeGroup.editConf.vlan.ipV6.dhcp.client.timers.infoRefresh

       Time in centi-second."
   ::= {er1645v2BgrMVVlanEntry 705311756}

er1645v2BgrMVVlanIpV6DhcpServerMode OBJECT-TYPE
   SYNTAX      INTEGER
               {
               disabled (0),
               enabled (1)
               }
   MAX-ACCESS  read-write
   STATUS      current
   DESCRIPTION
      "Path: bridgeGroup.editConf.vlan.ipV6.dhcp.server.mode

       Possibilities:
               disabled   (0)
               enabled   (1)"
   ::= {er1645v2BgrMVVlanEntry 705315840}

er1645v2BgrMVVlanIpV6DhcpServerPreference OBJECT-TYPE
   SYNTAX      Integer32
   MAX-ACCESS  read-write
   STATUS      current
   DESCRIPTION
      "Path: bridgeGroup.editConf.vlan.ipV6.dhcp.server.preference"
   ::= {er1645v2BgrMVVlanEntry 705316864}

er1645v2BgrMVVlanIpV6DhcpServerPool OBJECT-TYPE
   SYNTAX      DisplayString
   MAX-ACCESS  read-write
   STATUS      current
   DESCRIPTION
      "Path: bridgeGroup.editConf.vlan.ipV6.dhcp.server.pool"
   ::= {er1645v2BgrMVVlanEntry 705317888}

er1645v2BgrMVVlanIpV6DhcpServerRapidCommit OBJECT-TYPE
   SYNTAX      INTEGER
               {
               disabled (0),
               enabled (1)
               }
   MAX-ACCESS  read-write
   STATUS      current
   DESCRIPTION
      "Path: bridgeGroup.editConf.vlan.ipV6.dhcp.server.rapidCommit

       Possibilities:
               disabled   (0)
               enabled   (1)"
   ::= {er1645v2BgrMVVlanEntry 705318912}

er1645v2BgrMVVlanIpV6DhcpServerTimersInfoRefresh OBJECT-TYPE
   SYNTAX      TimeTicks
   MAX-ACCESS  read-write
   STATUS      current
   DESCRIPTION
      "Path: bridgeGroup.editConf.vlan.ipV6.dhcp.server.timers.infoRefresh

       Time in centi-second."
   ::= {er1645v2BgrMVVlanEntry 705319940}

er1645v2BgrMVVlanIpV6DhcpRelayMode OBJECT-TYPE
   SYNTAX      INTEGER
               {
               disabled (0),
               enabled (1)
               }
   MAX-ACCESS  read-write
   STATUS      current
   DESCRIPTION
      "Path: bridgeGroup.editConf.vlan.ipV6.dhcp.relay.mode

       Possibilities:
               disabled   (0)
               enabled   (1)"
   ::= {er1645v2BgrMVVlanEntry 705323040}

er1645v2BgrMVVlanIpV6SendRedirect OBJECT-TYPE
   SYNTAX      INTEGER
               {
               disabled (0),
               enabled (1)
               }
   MAX-ACCESS  read-write
   STATUS      current
   DESCRIPTION
      "Path: bridgeGroup.editConf.vlan.ipV6.sendRedirect

       Possibilities:
               disabled   (0)
               enabled   (1)"
   ::= {er1645v2BgrMVVlanEntry 705101824}

er1645v2BgrMVVlanIpV6LinkMtu OBJECT-TYPE
   SYNTAX      Integer32
   MAX-ACCESS  read-write
   STATUS      current
   DESCRIPTION
      "Path: bridgeGroup.editConf.vlan.ipV6.linkMtu"
   ::= {er1645v2BgrMVVlanEntry 705167360}

er1645v2BgrMVVlanIpV6InterfaceId OBJECT-TYPE
   SYNTAX      OCTET STRING
   MAX-ACCESS  read-write
   STATUS      current
   DESCRIPTION
      "Path: bridgeGroup.editConf.vlan.ipV6.interfaceId"
   ::= {er1645v2BgrMVVlanEntry 705232896}

er1645v2BgrMVVlanIpV6MF OBJECT-TYPE
   SYNTAX      Integer32
   MAX-ACCESS  read-write
   STATUS      current
   DESCRIPTION
      "Path: bridgeGroup.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2BgrMVVlanEntry 705757184}

er1645v2BgrMVVlanIpV6IcmpMessagesNoRoute OBJECT-TYPE
   SYNTAX      INTEGER
               {
               disabled (0),
               enabled (1)
               }
   MAX-ACCESS  read-write
   STATUS      current
   DESCRIPTION
      "Path: bridgeGroup.editConf.vlan.ipV6.icmpMessages.noRoute

       Possibilities:
               disabled   (0)
               enabled   (1)"
   ::= {er1645v2BgrMVVlanEntry 705822976}

er1645v2BgrMVVlanIpV6IcmpMessagesBeyondScope OBJECT-TYPE
   SYNTAX      INTEGER
               {
               disabled (0),
               enabled (1)
               }
   MAX-ACCESS  read-write
   STATUS      current
   DESCRIPTION
      "Path: bridgeGroup.editConf.vlan.ipV6.icmpMessages.beyondScope

       Possibilities:
               disabled   (0)
               enabled   (1)"
   ::= {er1645v2BgrMVVlanEntry 705823488}

er1645v2BgrMVVlanIpV6IcmpMessagesAddressUnreachable OBJECT-TYPE
   SYNTAX      INTEGER
               {
               disabled (0),
               enabled (1)
               }
   MAX-ACCESS  read-write
   STATUS      current
   DESCRIPTION
      "Path: bridgeGroup.editConf.vlan.ipV6.icmpMessages.addressUnreachable

       Possibilities:
               disabled   (0)
               enabled   (1)"
   ::= {er1645v2BgrMVVlanEntry 705823744}

er1645v2BgrMVVlanIpV6IcmpMessagesPortUnreachable OBJECT-TYPE
   SYNTAX      INTEGER
               {
               disabled (0),
               enabled (1)
               }
   MAX-ACCESS  read-write
   STATUS      current
   DESCRIPTION
      "Path: bridgeGroup.editConf.vlan.ipV6.icmpMessages.portUnreachable

       Possibilities:
               disabled   (0)
               enabled   (1)"
   ::= {er1645v2BgrMVVlanEntry 705824000}

er1645v2BgrMVVlanIpV6IcmpMessagesPacketTooBig OBJECT-TYPE
   SYNTAX      INTEGER
               {
               disabled (0),
               enabled (1)
               }
   MAX-ACCESS  read-write
   STATUS      current
   DESCRIPTION
      "Path: bridgeGroup.editConf.vlan.ipV6.icmpMessages.packetTooBig

       Possibilities:
               disabled   (0)
               enabled   (1)"
   ::= {er1645v2BgrMVVlanEntry 705825280}

er1645v2BgrMVVlanIpV6IcmpMessagesHopLimitExceeded OBJECT-TYPE
   SYNTAX      INTEGER
               {
               disabled (0),
               enabled (1)
               }
   MAX-ACCESS  read-write
   STATUS      current
   DESCRIPTION
      "Path: bridgeGroup.editConf.vlan.ipV6.icmpMessages.hopLimitExceeded

       Possibilities:
               disabled   (0)
               enabled   (1)"
   ::= {er1645v2BgrMVVlanEntry 705827840}

er1645v2BgrMVVlanIpV6IcmpMessagesFragTimeExceeded OBJECT-TYPE
   SYNTAX      INTEGER
               {
               disabled (0),
               enabled (1)
               }
   MAX-ACCESS  read-write
   STATUS      current
   DESCRIPTION
      "Path: bridgeGroup.editConf.vlan.ipV6.icmpMessages.fragTimeExceeded

       Possibilities:
               disabled   (0)
               enabled   (1)"
   ::= {er1645v2BgrMVVlanEntry 705828096}

er1645v2BgrMVVlanIpV6IcmpMessagesHeaderFieldErr OBJECT-TYPE
   SYNTAX      INTEGER
               {
               disabled (0),
               enabled (1)
               }
   MAX-ACCESS  read-write
   STATUS      current
   DESCRIPTION
      "Path: bridgeGroup.editConf.vlan.ipV6.icmpMessages.headerFieldErr

       Possibilities:
               disabled   (0)
               enabled   (1)"
   ::= {er1645v2BgrMVVlanEntry 705830400}

er1645v2BgrMVVlanIpV6IcmpMessagesOptionUnrecognized OBJECT-TYPE
   SYNTAX      INTEGER
               {
               disabled (0),
               enabled (1)
               }
   MAX-ACCESS  read-write
   STATUS      current
   DESCRIPTION
      "Path: bridgeGroup.editConf.vlan.ipV6.icmpMessages.optionUnrecognized

       Possibilities:
               disabled   (0)
               enabled   (1)"
   ::= {er1645v2BgrMVVlanEntry 705830912}

er1645v2BgrMVVlanIpV6IcmpMessagesRedirect OBJECT-TYPE
   SYNTAX      INTEGER
               {
               disabled (0),
               enabled (1)
               }
   MAX-ACCESS  read-write
   STATUS      current
   DESCRIPTION
      "Path: bridgeGroup.editConf.vlan.ipV6.icmpMessages.redirect

       Possibilities:
               disabled   (0)
               enabled   (1)"
   ::= {er1645v2BgrMVVlanEntry 705832960}

er1645v2BgrMVVlanVlanVid OBJECT-TYPE
   SYNTAX      INTEGER
               {
               prioTagged (4096)
               }
   MAX-ACCESS  read-write
   STATUS      current
   DESCRIPTION
      "Path: bridgeGroup.editConf.vlan.vlan.vid

       Possibilities:
               prioTagged   (4096)"
   ::= {er1645v2BgrMVVlanEntry 234946560}

er1645v2BgrMVVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: bridgeGroup.editConf.vlan.vlan.tpid

       Possibilities:
               dot1Q   (33024)
               dot1ad   (34984)
               0x9100   (37120)
               0x9200   (37376)
               0x9300   (37632)"
   ::= {er1645v2BgrMVVlanEntry 241238016}

er1645v2BgrMVVlanVlanTxCos OBJECT-TYPE
   SYNTAX      INTEGER
               {
               tosCosMap (8),
               queueCosMap (16)
               }
   MAX-ACCESS  read-write
   STATUS      current
   DESCRIPTION
      "Path: bridgeGroup.editConf.vlan.vlan.txCos

       Possibilities:
               tosCosMap   (8)
               queueCosMap   (16)"
   ::= {er1645v2BgrMVVlanEntry 235077632}

er1645v2BgrMVVlanVlanChTos OBJECT-TYPE
   SYNTAX      INTEGER
               {
               disabled (0),
               enabled (1)
               }
   MAX-ACCESS  read-write
   STATUS      current
   DESCRIPTION
      "Path: bridgeGroup.editConf.vlan.vlan.changeTos

       Possibilities:
               disabled   (0)
               enabled   (1)"
   ::= {er1645v2BgrMVVlanEntry 235208704}

er1645v2BgrMVVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235143424}

er1645v2BgrMVVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235143680}

er1645v2BgrMVVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235143936}

er1645v2BgrMVVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235144192}

er1645v2BgrMVVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235144448}

er1645v2BgrMVVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235144704}

er1645v2BgrMVVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235144960}

er1645v2BgrMVVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: bridgeGroup.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2BgrMVVlanEntry 235145216}

er1645v2BgrMVVlanVlanQCMapQueue1 OBJECT-TYPE
   SYNTAX      Integer32
   MAX-ACCESS  read-write
   STATUS      current
   DESCRIPTION
      "Path: bridgeGroup.editConf.vlan.vlan.queueCosMap.queue1"
   ::= {er1645v2BgrMVVlanEntry 241434880}

er1645v2BgrMVVlanVlanQCMapQueue2 OBJECT-TYPE
   SYNTAX      Integer32
   MAX-ACCESS  read-write
   STATUS      current
   DESCRIPTION
      "Path: bridgeGroup.editConf.vlan.vlan.queueCosMap.queue2"
   ::= {er1645v2BgrMVVlanEntry 241435136}

er1645v2BgrMVVlanVlanQCMapQueue3 OBJECT-TYPE
   SYNTAX      Integer32
   MAX-ACCESS  read-write
   STATUS      current
   DESCRIPTION
      "Path: bridgeGroup.editConf.vlan.vlan.queueCosMap.queue3"
   ::= {er1645v2BgrMVVlanEntry 241435392}

er1645v2BgrMVVlanVlanQCMapQueue4 OBJECT-TYPE
   SYNTAX      Integer32
   MAX-ACCESS  read-write
   STATUS      current
   DESCRIPTION
      "Path: bridgeGroup.editConf.vlan.vlan.queueCosMap.queue4"
   ::= {er1645v2BgrMVVlanEntry 241435648}

er1645v2BgrMVVlanVlanQCMapQueue5 OBJECT-TYPE
   SYNTAX      Integer32
   MAX-ACCESS  read-write
   STATUS      current
   DESCRIPTION
      "Path: bridgeGroup.editConf.vlan.vlan.queueCosMap.queue5"
   ::= {er1645v2BgrMVVlanEntry 241435904}

er1645v2BgrMVVlanVlanQCMapLowDelayQueue OBJECT-TYPE
   SYNTAX      Integer32
   MAX-ACCESS  read-write
   STATUS      current
   DESCRIPTION
      "Path: bridgeGroup.editConf.vlan.vlan.queueCosMap.lowDelayQueue"
   ::= {er1645v2BgrMVVlanEntry 241436160}

er1645v2BgrMVVlanVlanQCMapLowDelay2Queue OBJECT-TYPE
   SYNTAX      Integer32
   MAX-ACCESS  read-write
   STATUS      current
   DESCRIPTION
      "Path: bridgeGroup.editConf.vlan.vlan.queueCosMap.lowDelay2Queue"
   ::= {er1645v2BgrMVVlanEntry 241436416}

er1645v2BgrMVVlanVlanQCMapSystemQueue OBJECT-TYPE
   SYNTAX      Integer32
   MAX-ACCESS  read-write
   STATUS      current
   DESCRIPTION
      "Path: bridgeGroup.editConf.vlan.vlan.queueCosMap.systemQueue"
   ::= {er1645v2BgrMVVlanEntry 241436672}

er1645v2BgrMVVlanVlanArpTimeOut OBJECT-TYPE
   SYNTAX      TimeTicks
   MAX-ACCESS  read-write
   STATUS      current
   DESCRIPTION
      "Path: bridgeGroup.editConf.vlan.vlan.arp.timeOut

       Time in centi-second."
   ::= {er1645v2BgrMVVlanEntry 235277312}

er1645v2BgrMVVlanVlanArpProxyArp OBJECT-TYPE
   SYNTAX      INTEGER
               {
               disabled (0),
               enabled (1)
               }
   MAX-ACCESS  read-write
   STATUS      current
   DESCRIPTION
      "Path: bridgeGroup.editConf.vlan.vlan.arp.proxyArp

       Possibilities:
               disabled   (0)
               enabled   (1)"
   ::= {er1645v2BgrMVVlanEntry 235287040}

er1645v2BgrMVVlanIpSaddr OBJECT-TYPE
   SYNTAX      SEQUENCE OF Er1645v2BgrMVVlanIpSaddrEntry
   MAX-ACCESS  not-accessible
   STATUS      current
   DESCRIPTION
      ""
   ::= {er1645v2BgrMVVlan 51838976}

er1645v2BgrMVVlanIpSaddrEntry OBJECT-TYPE
   SYNTAX      Er1645v2BgrMVVlanIpSaddrEntry
   MAX-ACCESS  not-accessible
   STATUS      current
   DESCRIPTION
      ""
   INDEX      { er1645v2BgrMVVlanTableIx,
                er1645v2BgrMVVlanIpSaddrTableIx }
   ::= {er1645v2BgrMVVlanIpSaddr 1}

Er1645v2BgrMVVlanIpSaddrEntry ::=
   SEQUENCE
      {
      er1645v2BgrMVVlanIpSaddrActions
         VariableLengthTableActions,
      er1645v2BgrMVVlanIpSaddrTableIx
         TableIndex,
      er1645v2BgrMVVlanIpSaddrAddress
         IpAddress,
      er1645v2BgrMVVlanIpSaddrNetMask
         IpAddress
      }

er1645v2BgrMVVlanIpSaddrActions OBJECT-TYPE
   SYNTAX      VariableLengthTableActions
   MAX-ACCESS  read-write
   STATUS      current
   DESCRIPTION
      "By way of this field, some manipulations
       on this table may be performed."
   ::= {er1645v2BgrMVVlanIpSaddrEntry 2}

er1645v2BgrMVVlanIpSaddrTableIx OBJECT-TYPE
   SYNTAX      TableIndex
   MAX-ACCESS  not-accessible
   STATUS      current
   DESCRIPTION
      ""
   ::= {er1645v2BgrMVVlanIpSaddrEntry 11}

er1645v2BgrMVVlanIpSaddrAddress OBJECT-TYPE
   SYNTAX      IpAddress
   MAX-ACCESS  read-write
   STATUS      current
   DESCRIPTION
      "Path: bridgeGroup.editConf.vlan.ip.secondaryIp.address"
   ::= {er1645v2BgrMVVlanIpSaddrEntry 2030043136}

er1645v2BgrMVVlanIpSaddrNetMask OBJECT-TYPE
   SYNTAX      IpAddress
   MAX-ACCESS  read-write
   STATUS      current
   DESCRIPTION
      "Path: bridgeGroup.editConf.vlan.ip.secondaryIp.netMask"
   ::= {er1645v2BgrMVVlanIpSaddrEntry 2063597568}

er1645v2BgrMVVlanIpH OBJECT-TYPE
   SYNTAX      SEQUENCE OF Er1645v2BgrMVVlanIpHEntry
   MAX-ACCESS  not-accessible
   STATUS      current
   DESCRIPTION
      ""
   ::= {er1645v2BgrMVVlan 51314688}

er1645v2BgrMVVlanIpHEntry OBJECT-TYPE
   SYNTAX      Er1645v2BgrMVVlanIpHEntry
   MAX-ACCESS  not-accessible
   STATUS      current
   DESCRIPTION
      ""
   INDEX      { er1645v2BgrMVVlanTableIx,
                er1645v2BgrMVVlanIpHTableIx }
   ::= {er1645v2BgrMVVlanIpH 1}

Er1645v2BgrMVVlanIpHEntry ::=
   SEQUENCE
      {
      er1645v2BgrMVVlanIpHActions
         VariableLengthTableActions,
      er1645v2BgrMVVlanIpHTableIx
         TableIndex,
      er1645v2BgrMVVlanIpHAddress
         IpAddress,
      er1645v2BgrMVVlanIpHDhcpRelayOptionSubscriberId
         DisplayString
      }

er1645v2BgrMVVlanIpHActions OBJECT-TYPE
   SYNTAX      VariableLengthTableActions
   MAX-ACCESS  read-write
   STATUS      current
   DESCRIPTION
      "By way of this field, some manipulations
       on this table may be performed."
   ::= {er1645v2BgrMVVlanIpHEntry 2}

er1645v2BgrMVVlanIpHTableIx OBJECT-TYPE
   SYNTAX      TableIndex
   MAX-ACCESS  not-accessible
   STATUS      current
   DESCRIPTION
      ""
   ::= {er1645v2BgrMVVlanIpHEntry 11}

er1645v2BgrMVVlanIpHAddress OBJECT-TYPE
   SYNTAX      IpAddress
   MAX-ACCESS  read-write
   STATUS      current
   DESCRIPTION
      "Path: bridgeGroup.editConf.vlan.ip.helpers.address"
   ::= {er1645v2BgrMVVlanIpHEntry 16777216}

er1645v2BgrMVVlanIpHDhcpRelayOptionSubscriberId OBJECT-TYPE
   SYNTAX      DisplayString
   MAX-ACCESS  read-write
   STATUS      current
   DESCRIPTION
      "Path: bridgeGroup.editConf.vlan.ip.helpers.dhcpRelayOption.subscriberId"
   ::= {er1645v2BgrMVVlanIpHEntry 33947648}

er1645v2BgrMVVlanIpV6Addresses OBJECT-TYPE
   SYNTAX      SEQUENCE OF Er1645v2BgrMVVlanIpV6AddressesEntry
   MAX-ACCESS  not-accessible
   STATUS      current
   DESCRIPTION
      ""
   ::= {er1645v2BgrMVVlan 704839680}

er1645v2BgrMVVlanIpV6AddressesEntry OBJECT-TYPE
   SYNTAX      Er1645v2BgrMVVlanIpV6AddressesEntry
   MAX-ACCESS  not-accessible
   STATUS      current
   DESCRIPTION
      ""
   INDEX      { er1645v2BgrMVVlanTableIx,
                er1645v2BgrMVVlanIpV6AddressesTableIx }
   ::= {er1645v2BgrMVVlanIpV6Addresses 1}

Er1645v2BgrMVVlanIpV6AddressesEntry ::=
   SEQUENCE
      {
      er1645v2BgrMVVlanIpV6AddressesActions
         VariableLengthTableActions,
      er1645v2BgrMVVlanIpV6AddressesTableIx
         TableIndex,
      er1645v2BgrMVVlanIpV6AddressesType
         INTEGER,
      er1645v2BgrMVVlanIpV6AddressesAddress
         Ipv6Address,
      er1645v2BgrMVVlanIpV6AddressesPrefixLength
         Integer32,
      er1645v2BgrMVVlanIpV6AddressesGeneralPrefix
         DisplayString,
      er1645v2BgrMVVlanIpV6AddressesRaSend
         INTEGER,
      er1645v2BgrMVVlanIpV6AddressesRaOnLinkFlag
         INTEGER,
      er1645v2BgrMVVlanIpV6AddressesRaAutoFlag
         INTEGER,
      er1645v2BgrMVVlanIpV6AddressesRaValidLifeTime
         TimeTicks,
      er1645v2BgrMVVlanIpV6AddressesRaValidLTMode
         INTEGER,
      er1645v2BgrMVVlanIpV6AddressesRaPrefLifeTime
         TimeTicks,
      er1645v2BgrMVVlanIpV6AddressesRaPrefLTMode
         INTEGER
      }

er1645v2BgrMVVlanIpV6AddressesActions OBJECT-TYPE
   SYNTAX      VariableLengthTableActions
   MAX-ACCESS  read-write
   STATUS      current
   DESCRIPTION
      "By way of this field, some manipulations
       on this table may be performed."
   ::= {er1645v2BgrMVVlanIpV6AddressesEntry 2}

er1645v2BgrMVVlanIpV6AddressesTableIx OBJECT-TYPE
   SYNTAX      TableIndex
   MAX-ACCESS  not-accessible
   STATUS      current
   DESCRIPTION
      ""
   ::= {er1645v2BgrMVVlanIpV6AddressesEntry 11}

er1645v2BgrMVVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: bridgeGroup.editConf.vlan.ipV6.addresses.type

       Possibilities:
               unicast   (0)
               eui64   (1)
               anycast   (2)
               linkLocal   (3)
               generalPrefix   (4)"
   ::= {er1645v2BgrMVVlanIpV6AddressesEntry 50331648}

er1645v2BgrMVVlanIpV6AddressesAddress OBJECT-TYPE
   SYNTAX      Ipv6Address
   MAX-ACCESS  read-write
   STATUS      current
   DESCRIPTION
      "Path: bridgeGroup.editConf.vlan.ipV6.addresses.address

       ipv6 address"
   ::= {er1645v2BgrMVVlanIpV6AddressesEntry 16777216}

er1645v2BgrMVVlanIpV6AddressesPrefixLength OBJECT-TYPE
   SYNTAX      Integer32
   MAX-ACCESS  read-write
   STATUS      current
   DESCRIPTION
      "Path: bridgeGroup.editConf.vlan.ipV6.addresses.prefixLength"
   ::= {er1645v2BgrMVVlanIpV6AddressesEntry 33554432}

er1645v2BgrMVVlanIpV6AddressesGeneralPrefix OBJECT-TYPE
   SYNTAX      DisplayString
   MAX-ACCESS  read-write
   STATUS      current
   DESCRIPTION
      "Path: bridgeGroup.editConf.vlan.ipV6.addresses.generalPrefix"
   ::= {er1645v2BgrMVVlanIpV6AddressesEntry 83886080}

er1645v2BgrMVVlanIpV6AddressesRaSend OBJECT-TYPE
   SYNTAX      INTEGER
               {
               disabled (0),
               enabled (1)
               }
   MAX-ACCESS  read-write
   STATUS      current
   DESCRIPTION
      "Path: bridgeGroup.editConf.vlan.ipV6.addresses.ra.send

       Possibilities:
               disabled   (0)
               enabled   (1)"
   ::= {er1645v2BgrMVVlanIpV6AddressesEntry 67174400}

er1645v2BgrMVVlanIpV6AddressesRaOnLinkFlag OBJECT-TYPE
   SYNTAX      INTEGER
               {
               disabled (0),
               enabled (1)
               }
   MAX-ACCESS  read-write
   STATUS      current
   DESCRIPTION
      "Path: bridgeGroup.editConf.vlan.ipV6.addresses.ra.onLinkFlag

       Possibilities:
               disabled   (0)
               enabled   (1)"
   ::= {er1645v2BgrMVVlanIpV6AddressesEntry 67371008}

er1645v2BgrMVVlanIpV6AddressesRaAutoFlag OBJECT-TYPE
   SYNTAX      INTEGER
               {
               disabled (0),
               enabled (1)
               }
   MAX-ACCESS  read-write
   STATUS      current
   DESCRIPTION
      "Path: bridgeGroup.editConf.vlan.ipV6.addresses.ra.autonomousFlag

       Possibilities:
               disabled   (0)
               enabled   (1)"
   ::= {er1645v2BgrMVVlanIpV6AddressesEntry 67567616}

er1645v2BgrMVVlanIpV6AddressesRaValidLifeTime OBJECT-TYPE
   SYNTAX      TimeTicks
   MAX-ACCESS  read-write
   STATUS      current
   DESCRIPTION
      "Path: bridgeGroup.editConf.vlan.ipV6.addresses.ra.validLifeTime

       Time in centi-second."
   ::= {er1645v2BgrMVVlanIpV6AddressesEntry 67239936}

er1645v2BgrMVVlanIpV6AddressesRaValidLTMode OBJECT-TYPE
   SYNTAX      INTEGER
               {
               fixed (0),
               infinite (2)
               }
   MAX-ACCESS  read-write
   STATUS      current
   DESCRIPTION
      "Path: bridgeGroup.editConf.vlan.ipV6.addresses.ra.validLifeTimeMode

       Possibilities:
               fixed   (0)
               infinite   (2)"
   ::= {er1645v2BgrMVVlanIpV6AddressesEntry 67305472}

er1645v2BgrMVVlanIpV6AddressesRaPrefLifeTime OBJECT-TYPE
   SYNTAX      TimeTicks
   MAX-ACCESS  read-write
   STATUS      current
   DESCRIPTION
      "Path: bridgeGroup.editConf.vlan.ipV6.addresses.ra.prefLifeTime

       Time in centi-second."
   ::= {er1645v2BgrMVVlanIpV6AddressesEntry 67436544}

er1645v2BgrMVVlanIpV6AddressesRaPrefLTMode OBJECT-TYPE
   SYNTAX      INTEGER
               {
               fixed (0),
               infinite (2)
               }
   MAX-ACCESS  read-write
   STATUS      current
   DESCRIPTION
      "Path: bridgeGroup.editConf.vlan.ipV6.addresses.ra.prefLifeTimeMode

       Possibilities:
               fixed   (0)
               infinite   (2)"
   ::= {er1645v2BgrMVVlanIpV6AddressesEntry 67502080}

er1645v2BgrMVVlanIpV6RaDnsOptionsRdnssServers OBJECT-TYPE
   SYNTAX      SEQUENCE OF Er1645v2BgrMVVlanIpV6RaDnsOptionsRdnssServersEntry
   MAX-ACCESS  not-accessible
   STATUS      current
   DESCRIPTION
      ""
   ::= {er1645v2BgrMVVlan 705039144}

er1645v2BgrMVVlanIpV6RaDnsOptionsRdnssServersEntry OBJECT-TYPE
   SYNTAX      Er1645v2BgrMVVlanIpV6RaDnsOptionsRdnssServersEntry
   MAX-ACCESS  not-accessible
   STATUS      current
   DESCRIPTION
      ""
   INDEX      { er1645v2BgrMVVlanTableIx,
                er1645v2BgrMVVlanIpV6RaDnsOptionsRdnssServersTableIx }
   ::= {er1645v2BgrMVVlanIpV6RaDnsOptionsRdnssServers 1}

Er1645v2BgrMVVlanIpV6RaDnsOptionsRdnssServersEntry ::=
   SEQUENCE
      {
      er1645v2BgrMVVlanIpV6RaDnsOptionsRdnssServersActions
         VariableLengthTableActions,
      er1645v2BgrMVVlanIpV6RaDnsOptionsRdnssServersTableIx
         TableIndex,
      er1645v2BgrMVVlanIpV6RaDnsOptionsRdnssServersAddress
         Ipv6Address
      }

er1645v2BgrMVVlanIpV6RaDnsOptionsRdnssServersActions OBJECT-TYPE
   SYNTAX      VariableLengthTableActions
   MAX-ACCESS  read-write
   STATUS      current
   DESCRIPTION
      "By way of this field, some manipulations
       on this table may be performed."
   ::= {er1645v2BgrMVVlanIpV6RaDnsOptionsRdnssServersEntry 2}

er1645v2BgrMVVlanIpV6RaDnsOptionsRdnssServersTableIx OBJECT-TYPE
   SYNTAX      TableIndex
   MAX-ACCESS  not-accessible
   STATUS      current
   DESCRIPTION
      ""
   ::= {er1645v2BgrMVVlanIpV6RaDnsOptionsRdnssServersEntry 11}

er1645v2BgrMVVlanIpV6RaDnsOptionsRdnssServersAddress OBJECT-TYPE
   SYNTAX      Ipv6Address
   MAX-ACCESS  read-write
   STATUS      current
   DESCRIPTION
      "Path: bridgeGroup.editConf.vlan.ipV6.ra.dnsOptions.rdnss.servers.address

       ipv6 address"
   ::= {er1645v2BgrMVVlanIpV6RaDnsOptionsRdnssServersEntry 16777216}

er1645v2BgrMVVlanIpV6RaDnsOptionsDnsslDomains OBJECT-TYPE
   SYNTAX      SEQUENCE OF Er1645v2BgrMVVlanIpV6RaDnsOptionsDnsslDomainsEntry
   MAX-ACCESS  not-accessible
   STATUS      current
   DESCRIPTION
      ""
   ::= {er1645v2BgrMVVlan 705039176}

er1645v2BgrMVVlanIpV6RaDnsOptionsDnsslDomainsEntry OBJECT-TYPE
   SYNTAX      Er1645v2BgrMVVlanIpV6RaDnsOptionsDnsslDomainsEntry
   MAX-ACCESS  not-accessible
   STATUS      current
   DESCRIPTION
      ""
   INDEX      { er1645v2BgrMVVlanTableIx,
                er1645v2BgrMVVlanIpV6RaDnsOptionsDnsslDomainsTableIx }
   ::= {er1645v2BgrMVVlanIpV6RaDnsOptionsDnsslDomains 1}

Er1645v2BgrMVVlanIpV6RaDnsOptionsDnsslDomainsEntry ::=
   SEQUENCE
      {
      er1645v2BgrMVVlanIpV6RaDnsOptionsDnsslDomainsActions
         VariableLengthTableActions,
      er1645v2BgrMVVlanIpV6RaDnsOptionsDnsslDomainsTableIx
         TableIndex,
      er1645v2BgrMVVlanIpV6RaDnsOptionsDnsslDomainsName
         DisplayString
      }

er1645v2BgrMVVlanIpV6RaDnsOptionsDnsslDomainsActions OBJECT-TYPE
   SYNTAX      VariableLengthTableActions
   MAX-ACCESS  read-write
   STATUS      current
   DESCRIPTION
      "By way of this field, some manipulations
       on this table may be performed."
   ::= {er1645v2BgrMVVlanIpV6RaDnsOptionsDnsslDomainsEntry 2}

er1645v2BgrMVVlanIpV6RaDnsOptionsDnsslDomainsTableIx OBJECT-TYPE
   SYNTAX      TableIndex
   MAX-ACCESS  not-accessible
   STATUS      current
   DESCRIPTION
      ""
   ::= {er1645v2BgrMVVlanIpV6RaDnsOptionsDnsslDomainsEntry 11}

er1645v2BgrMVVlanIpV6RaDnsOptionsDnsslDomainsName OBJECT-TYPE
   SYNTAX      DisplayString
   MAX-ACCESS  read-write
   STATUS      current
   DESCRIPTION
      "Path: bridgeGroup.editConf.vlan.ipV6.ra.dnsOptions.dnssl.domains.name"
   ::= {er1645v2BgrMVVlanIpV6RaDnsOptionsDnsslDomainsEntry 16777216}

er1645v2BgrMVVlanIpV6DhcpClientUserClassOpt OBJECT-TYPE
   SYNTAX      SEQUENCE OF Er1645v2BgrMVVlanIpV6DhcpClientUserClassOptEntry
   MAX-ACCESS  not-accessible
   STATUS      current
   DESCRIPTION
      ""
   ::= {er1645v2BgrMVVlan 705312768}

er1645v2BgrMVVlanIpV6DhcpClientUserClassOptEntry OBJECT-TYPE
   SYNTAX      Er1645v2BgrMVVlanIpV6DhcpClientUserClassOptEntry
   MAX-ACCESS  not-accessible
   STATUS      current
   DESCRIPTION
      ""
   INDEX      { er1645v2BgrMVVlanTableIx,
                er1645v2BgrMVVlanIpV6DhcpClientUserClassOptTableIx }
   ::= {er1645v2BgrMVVlanIpV6DhcpClientUserClassOpt 1}

Er1645v2BgrMVVlanIpV6DhcpClientUserClassOptEntry ::=
   SEQUENCE
      {
      er1645v2BgrMVVlanIpV6DhcpClientUserClassOptActions
         VariableLengthTableActions,
      er1645v2BgrMVVlanIpV6DhcpClientUserClassOptTableIx
         TableIndex,
      er1645v2BgrMVVlanIpV6DhcpClientUserClassOptValueAscii
         DisplayString,
      er1645v2BgrMVVlanIpV6DhcpClientUserClassOptValueDecimal
         Integer32,
      er1645v2BgrMVVlanIpV6DhcpClientUserClassOptValueHexData
         OCTET STRING
      }

er1645v2BgrMVVlanIpV6DhcpClientUserClassOptActions OBJECT-TYPE
   SYNTAX      VariableLengthTableActions
   MAX-ACCESS  read-write
   STATUS      current
   DESCRIPTION
      "By way of this field, some manipulations
       on this table may be performed."
   ::= {er1645v2BgrMVVlanIpV6DhcpClientUserClassOptEntry 2}

er1645v2BgrMVVlanIpV6DhcpClientUserClassOptTableIx OBJECT-TYPE
   SYNTAX      TableIndex
   MAX-ACCESS  not-accessible
   STATUS      current
   DESCRIPTION
      ""
   ::= {er1645v2BgrMVVlanIpV6DhcpClientUserClassOptEntry 11}

er1645v2BgrMVVlanIpV6DhcpClientUserClassOptValueAscii OBJECT-TYPE
   SYNTAX      DisplayString
   MAX-ACCESS  read-write
   STATUS      current
   DESCRIPTION
      "Path: bridgeGroup.editConf.vlan.ipV6.dhcp.client.userClassOpt.value.ascii"
   ::= {er1645v2BgrMVVlanIpV6DhcpClientUserClassOptEntry 16842752}

er1645v2BgrMVVlanIpV6DhcpClientUserClassOptValueDecimal OBJECT-TYPE
   SYNTAX      Integer32
   MAX-ACCESS  read-write
   STATUS      current
   DESCRIPTION
      "Path: bridgeGroup.editConf.vlan.ipV6.dhcp.client.userClassOpt.value.decimal"
   ::= {er1645v2BgrMVVlanIpV6DhcpClientUserClassOptEntry 16908288}

er1645v2BgrMVVlanIpV6DhcpClientUserClassOptValueHexData OBJECT-TYPE
   SYNTAX      OCTET STRING
   MAX-ACCESS  read-write
   STATUS      current
   DESCRIPTION
      "Path: bridgeGroup.editConf.vlan.ipV6.dhcp.client.userClassOpt.value.hexData"
   ::= {er1645v2BgrMVVlanIpV6DhcpClientUserClassOptEntry 16973824}

er1645v2BgrMVVlanIpV6DhcpClientVendorCl OBJECT-TYPE
   SYNTAX      SEQUENCE OF Er1645v2BgrMVVlanIpV6DhcpClientVendorClEntry
   MAX-ACCESS  not-accessible
   STATUS      current
   DESCRIPTION
      ""
   ::= {er1645v2BgrMVVlan 705313792}

er1645v2BgrMVVlanIpV6DhcpClientVendorClEntry OBJECT-TYPE
   SYNTAX      Er1645v2BgrMVVlanIpV6DhcpClientVendorClEntry
   MAX-ACCESS  not-accessible
   STATUS      current
   DESCRIPTION
      ""
   INDEX      { er1645v2BgrMVVlanTableIx,
                er1645v2BgrMVVlanIpV6DhcpClientVendorClTableIx }
   ::= {er1645v2BgrMVVlanIpV6DhcpClientVendorCl 1}

Er1645v2BgrMVVlanIpV6DhcpClientVendorClEntry ::=
   SEQUENCE
      {
      er1645v2BgrMVVlanIpV6DhcpClientVendorClActions
         VariableLengthTableActions,
      er1645v2BgrMVVlanIpV6DhcpClientVendorClTableIx
         TableIndex,
      er1645v2BgrMVVlanIpV6DhcpClientVendorClValueAscii
         DisplayString,
      er1645v2BgrMVVlanIpV6DhcpClientVendorClValueDecimal
         Integer32,
      er1645v2BgrMVVlanIpV6DhcpClientVendorClValueHexData
         OCTET STRING
      }

er1645v2BgrMVVlanIpV6DhcpClientVendorClActions OBJECT-TYPE
   SYNTAX      VariableLengthTableActions
   MAX-ACCESS  read-write
   STATUS      current
   DESCRIPTION
      "By way of this field, some manipulations
       on this table may be performed."
   ::= {er1645v2BgrMVVlanIpV6DhcpClientVendorClEntry 2}

er1645v2BgrMVVlanIpV6DhcpClientVendorClTableIx OBJECT-TYPE
   SYNTAX      TableIndex
   MAX-ACCESS  not-accessible
   STATUS      current
   DESCRIPTION
      ""
   ::= {er1645v2BgrMVVlanIpV6DhcpClientVendorClEntry 11}

er1645v2BgrMVVlanIpV6DhcpClientVendorClValueAscii OBJECT-TYPE
   SYNTAX      DisplayString
   MAX-ACCESS  read-write
   STATUS      current
   DESCRIPTION
      "Path: bridgeGroup.editConf.vlan.ipV6.dhcp.client.vendorClassOpt.value.ascii"
   ::= {er1645v2BgrMVVlanIpV6DhcpClientVendorClEntry 16842752}

er1645v2BgrMVVlanIpV6DhcpClientVendorClValueDecimal OBJECT-TYPE
   SYNTAX      Integer32
   MAX-ACCESS  read-write
   STATUS      current
   DESCRIPTION
      "Path: bridgeGroup.editConf.vlan.ipV6.dhcp.client.vendorClassOpt.value.decimal"
   ::= {er1645v2BgrMVVlanIpV6DhcpClientVendorClEntry 16908288}

er1645v2BgrMVVlanIpV6DhcpClientVendorClValueHexData OBJECT-TYPE
   SYNTAX      OCTET STRING
   MAX-ACCESS  read-write
   STATUS      current
   DESCRIPTION
      "Path: bridgeGroup.editConf.vlan.ipV6.dhcp.client.vendorClassOpt.value.hexData"
   ::= {er1645v2BgrMVVlanIpV6DhcpClientVendorClEntry 16973824}

er1645v2BgrMVVlanIpV6DhcpRelayDestinations OBJECT-TYPE
   SYNTAX      SEQUENCE OF Er1645v2BgrMVVlanIpV6DhcpRelayDestinationsEntry
   MAX-ACCESS  not-accessible
   STATUS      current
   DESCRIPTION
      ""
   ::= {er1645v2BgrMVVlan 705323072}

er1645v2BgrMVVlanIpV6DhcpRelayDestinationsEntry OBJECT-TYPE
   SYNTAX      Er1645v2BgrMVVlanIpV6DhcpRelayDestinationsEntry
   MAX-ACCESS  not-accessible
   STATUS      current
   DESCRIPTION
      ""
   INDEX      { er1645v2BgrMVVlanTableIx,
                er1645v2BgrMVVlanIpV6DhcpRelayDestinationsTableIx }
   ::= {er1645v2BgrMVVlanIpV6DhcpRelayDestinations 1}

Er1645v2BgrMVVlanIpV6DhcpRelayDestinationsEntry ::=
   SEQUENCE
      {
      er1645v2BgrMVVlanIpV6DhcpRelayDestinationsActions
         VariableLengthTableActions,
      er1645v2BgrMVVlanIpV6DhcpRelayDestinationsTableIx
         TableIndex,
      er1645v2BgrMVVlanIpV6DhcpRelayDestinationsAddress
         Ipv6Address,
      er1645v2BgrMVVlanIpV6DhcpRelayDestinationsInterface
         DisplayString
      }

er1645v2BgrMVVlanIpV6DhcpRelayDestinationsActions OBJECT-TYPE
   SYNTAX      VariableLengthTableActions
   MAX-ACCESS  read-write
   STATUS      current
   DESCRIPTION
      "By way of this field, some manipulations
       on this table may be performed."
   ::= {er1645v2BgrMVVlanIpV6DhcpRelayDestinationsEntry 2}

er1645v2BgrMVVlanIpV6DhcpRelayDestinationsTableIx OBJECT-TYPE
   SYNTAX      TableIndex
   MAX-ACCESS  not-accessible
   STATUS      current
   DESCRIPTION
      ""
   ::= {er1645v2BgrMVVlanIpV6DhcpRelayDestinationsEntry 11}

er1645v2BgrMVVlanIpV6DhcpRelayDestinationsAddress OBJECT-TYPE
   SYNTAX      Ipv6Address
   MAX-ACCESS  read-write
   STATUS      current
   DESCRIPTION
      "Path: bridgeGroup.editConf.vlan.ipV6.dhcp.relay.destinations.address

       ipv6 address"
   ::= {er1645v2BgrMVVlanIpV6DhcpRelayDestinationsEntry 16777216}

er1645v2BgrMVVlanIpV6DhcpRelayDestinationsInterface OBJECT-TYPE
   SYNTAX      DisplayString
   MAX-ACCESS  read-write
   STATUS      current
   DESCRIPTION
      "Path: bridgeGroup.editConf.vlan.ipV6.dhcp.relay.destinations.interface"
   ::= {er1645v2BgrMVVlanIpV6DhcpRelayDestinationsEntry 33554432}

er1645v2BgrMVVlanVlanTCMap OBJECT-TYPE
   SYNTAX      SEQUENCE OF Er1645v2BgrMVVlanVlanTCMapEntry
   MAX-ACCESS  not-accessible
   STATUS      current
   DESCRIPTION
      ""
   ::= {er1645v2BgrMVVlan 241369088}

er1645v2BgrMVVlanVlanTCMapEntry OBJECT-TYPE
   SYNTAX      Er1645v2BgrMVVlanVlanTCMapEntry
   MAX-ACCESS  not-accessible
   STATUS      current
   DESCRIPTION
      ""
   INDEX      { er1645v2BgrMVVlanTableIx,
                er1645v2BgrMVVlanVlanTCMapTableIx }
   ::= {er1645v2BgrMVVlanVlanTCMap 1}

Er1645v2BgrMVVlanVlanTCMapEntry ::=
   SEQUENCE
      {
      er1645v2BgrMVVlanVlanTCMapActions
         VariableLengthTableActions,
      er1645v2BgrMVVlanVlanTCMapTableIx
         TableIndex,
      er1645v2BgrMVVlanVlanTCMapStartTos
         INTEGER,
      er1645v2BgrMVVlanVlanTCMapEndTos
         INTEGER,
      er1645v2BgrMVVlanVlanTCMapCos
         INTEGER
      }

er1645v2BgrMVVlanVlanTCMapActions OBJECT-TYPE
   SYNTAX      VariableLengthTableActions
   MAX-ACCESS  read-write
   STATUS      current
   DESCRIPTION
      "By way of this field, some manipulations
       on this table may be performed."
   ::= {er1645v2BgrMVVlanVlanTCMapEntry 2}

er1645v2BgrMVVlanVlanTCMapTableIx OBJECT-TYPE
   SYNTAX      TableIndex
   MAX-ACCESS  not-accessible
   STATUS      current
   DESCRIPTION
      ""
   ::= {er1645v2BgrMVVlanVlanTCMapEntry 11}

er1645v2BgrMVVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: bridgeGroup.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BgrMVVlanVlanTCMapEntry 16777216}

er1645v2BgrMVVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: bridgeGroup.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2BgrMVVlanVlanTCMapEntry 33554432}

er1645v2BgrMVVlanVlanTCMapCos OBJECT-TYPE
   SYNTAX      INTEGER
               {
               queueCosMap (8)
               }
   MAX-ACCESS  read-write
   STATUS      current
   DESCRIPTION
      "Path: bridgeGroup.editConf.vlan.vlan.tosCosMap.cos

       Possibilities:
               queueCosMap   (8)"
   ::= {er1645v2BgrMVVlanVlanTCMapEntry 50331648}

er1645v2BgrMVVlanVlanArpStaticArp OBJECT-TYPE
   SYNTAX      SEQUENCE OF Er1645v2BgrMVVlanVlanArpStaticArpEntry
   MAX-ACCESS  not-accessible
   STATUS      current
   DESCRIPTION
      ""
   ::= {er1645v2BgrMVVlan 235275008}

er1645v2BgrMVVlanVlanArpStaticArpEntry OBJECT-TYPE
   SYNTAX      Er1645v2BgrMVVlanVlanArpStaticArpEntry
   MAX-ACCESS  not-accessible
   STATUS      current
   DESCRIPTION
      ""
   INDEX      { er1645v2BgrMVVlanTableIx,
                er1645v2BgrMVVlanVlanArpStaticArpTableIx }
   ::= {er1645v2BgrMVVlanVlanArpStaticArp 1}

Er1645v2BgrMVVlanVlanArpStaticArpEntry ::=
   SEQUENCE
      {
      er1645v2BgrMVVlanVlanArpStaticArpActions
         VariableLengthTableActions,
      er1645v2BgrMVVlanVlanArpStaticArpTableIx
         TableIndex,
      er1645v2BgrMVVlanVlanArpStaticArpMacAddress
         OCTET STRING,
      er1645v2BgrMVVlanVlanArpStaticArpIpAddress
         IpAddress
      }

er1645v2BgrMVVlanVlanArpStaticArpActions OBJECT-TYPE
   SYNTAX      VariableLengthTableActions
   MAX-ACCESS  read-write
   STATUS      current
   DESCRIPTION
      "By way of this field, some manipulations
       on this table may be performed."
   ::= {er1645v2BgrMVVlanVlanArpStaticArpEntry 2}

er1645v2BgrMVVlanVlanArpStaticArpTableIx OBJECT-TYPE
   SYNTAX      TableIndex
   MAX-ACCESS  not-accessible
   STATUS      current
   DESCRIPTION
      ""
   ::= {er1645v2BgrMVVlanVlanArpStaticArpEntry 11}

er1645v2BgrMVVlanVlanArpStaticArpMacAddress OBJECT-TYPE
   SYNTAX      OCTET STRING
   MAX-ACCESS  read-write
   STATUS      current
   DESCRIPTION
      "Path: bridgeGroup.editConf.vlan.vlan.arp.staticArp.macAddress

       MAC address."
   ::= {er1645v2BgrMVVlanVlanArpStaticArpEntry 16777216}

er1645v2BgrMVVlanVlanArpStaticArpIpAddress OBJECT-TYPE
   SYNTAX      IpAddress
   MAX-ACCESS  read-write
   STATUS      current
   DESCRIPTION
      "Path: bridgeGroup.editConf.vlan.vlan.arp.staticArp.ipAddress"
   ::= {er1645v2BgrMVVlanVlanArpStaticArpEntry 33554432}


er1645v2BgrMVPppOE OBJECT IDENTIFIER ::= {er1645v2BgrMV 80}

er1645v2BgrMVPppOESSCTable OBJECT-TYPE
   SYNTAX      SEQUENCE OF Er1645v2BgrMVPppOEEntry
   MAX-ACCESS  not-accessible
   STATUS      current
   DESCRIPTION
      ""
   ::= {er1645v2BgrMVPppOE 1}

er1645v2BgrMVPppOEEntry OBJECT-TYPE
   SYNTAX      Er1645v2BgrMVPppOEEntry
   MAX-ACCESS  not-accessible
   STATUS      current
   DESCRIPTION
      ""
   INDEX      { er1645v2BgrMVPppOETableIx }
   ::= {er1645v2BgrMVPppOESSCTable 1}

Er1645v2BgrMVPppOEEntry ::=
   SEQUENCE
      {
      er1645v2BgrMVPppOEActions
         VariableLengthTableActions,
      er1645v2BgrMVPppOETableIx
         TableIndex,
      er1645v2BgrMVPppOEName
         DisplayString,
      er1645v2BgrMVPppOERemark
         DisplayString,
      er1645v2BgrMVPppOEAdminStatus
         INTEGER,
      er1645v2BgrMVPppOEMode
         INTEGER,
      er1645v2BgrMVPppOEIpVrfRouter
         DisplayString,
      er1645v2BgrMVPppOEIpAdr
         IpAddress,
      er1645v2BgrMVPppOEIpNetm
         IpAddress,
      er1645v2BgrMVPppOEIpSNetName
         INTEGER,
      er1645v2BgrMVPppOEIpSNetCust
         DisplayString,
      er1645v2BgrMVPppOEIpRem
         IpAddress,
      er1645v2BgrMVPppOEIpUnnumbered
         DisplayString,
      er1645v2BgrMVPppOEIpGwPref
         Integer32,
      er1645v2BgrMVPppOEIpRsn
         INTEGER,
      er1645v2BgrMVPppOEIpMtu
         Integer32,
      er1645v2BgrMVPppOEIpMssAdjust
         INTEGER,
      er1645v2BgrMVPppOEIpRipMetric
         Integer32,
      er1645v2BgrMVPppOEIpRipMetricOut
         Integer32,
      er1645v2BgrMVPppOEIpRipMode
         INTEGER,
      er1645v2BgrMVPppOEIpRipTxVer
         INTEGER,
      er1645v2BgrMVPppOEIpRipRxVer
         INTEGER,
      er1645v2BgrMVPppOEIpRipSplitH
         INTEGER,
      er1645v2BgrMVPppOEIpRipAuth
         INTEGER,
      er1645v2BgrMVPppOEIpRipFilter
         DisplayString,
      er1645v2BgrMVPppOEIpRipFilterIn
         DisplayString,
      er1645v2BgrMVPppOEIpRipClearNextHop
         INTEGER,
      er1645v2BgrMVPppOEIpAccPol
         DisplayString,
      er1645v2BgrMVPppOEIpAB
         DisplayString,
      er1645v2BgrMVPppOEIpMA
         INTEGER,
      er1645v2BgrMVPppOEIpMF
         Integer32,
      er1645v2BgrMVPppOEIpDB
         INTEGER,
      er1645v2BgrMVPppOEIpIR
         INTEGER,
      er1645v2BgrMVPppOEIpIgmp
         INTEGER,
      er1645v2BgrMVPppOEIpNN
         DisplayString,
      er1645v2BgrMVPppOEIpPimMode
         INTEGER,
      er1645v2BgrMVPppOEIpPimDrPriority
         Counter32,
      er1645v2BgrMVPppOEIpPimHelloTime
         TimeTicks,
      er1645v2BgrMVPppOEIpPimPropagationDelay
         TimeTicks,
      er1645v2BgrMVPppOEIpPimOverrideInterval
         TimeTicks,
      er1645v2BgrMVPppOEIpPimBsrBorder
         INTEGER,
      er1645v2BgrMVPppOEIpPimTtlThreshold
         Integer32,
      er1645v2BgrMVPppOEIpIMNetworkUnreachable
         INTEGER,
      er1645v2BgrMVPppOEIpIMHostUnreachable
         INTEGER,
      er1645v2BgrMVPppOEIpIMProtocolUnreachable
         INTEGER,
      er1645v2BgrMVPppOEIpIMPortUnreachable
         INTEGER,
      er1645v2BgrMVPppOEIpIMMtuExceeded
         INTEGER,
      er1645v2BgrMVPppOEIpIMAdminProhibited
         INTEGER,
      er1645v2BgrMVPppOEIpIMTtlExceeded
         INTEGER,
      er1645v2BgrMVPppOEIpIMRedirect
         INTEGER,
      er1645v2BgrMVPppOEIpV6VrfRouter
         DisplayString,
      er1645v2BgrMVPppOEIpV6AddrAutoConfigNrDupAddrDetects
         Integer32,
      er1645v2BgrMVPppOEIpV6AddrAutoConfigAcceptRa
         INTEGER,
      er1645v2BgrMVPppOEIpV6AddrAutoConfigAcceptRaRdnss
         INTEGER,
      er1645v2BgrMVPppOEIpV6AddrAutoConfigAcceptRaDnssl
         INTEGER,
      er1645v2BgrMVPppOEIpV6DefaultRoute
         INTEGER,
      er1645v2BgrMVPppOEIpV6RaSend
         INTEGER,
      er1645v2BgrMVPppOEIpV6RaMinInterval
         TimeTicks,
      er1645v2BgrMVPppOEIpV6RaMaxInterval
         TimeTicks,
      er1645v2BgrMVPppOEIpV6RaManagedFlag
         INTEGER,
      er1645v2BgrMVPppOEIpV6RaOtherConfFlag
         INTEGER,
      er1645v2BgrMVPppOEIpV6RaLinkMtu
         Integer32,
      er1645v2BgrMVPppOEIpV6RaReachableTime
         TimeTicks,
      er1645v2BgrMVPppOEIpV6RaRetransmitTime
         TimeTicks,
      er1645v2BgrMVPppOEIpV6RaHopLimit
         Integer32,
      er1645v2BgrMVPppOEIpV6RaDefaultLifeTime
         TimeTicks,
      er1645v2BgrMVPppOEIpV6RaDnsOptionsRdnssLifeTime
         TimeTicks,
      er1645v2BgrMVPppOEIpV6RaDnsOptionsRdnssImportServers
         INTEGER,
      er1645v2BgrMVPppOEIpV6RaDnsOptionsDnsslLifeTime
         TimeTicks,
      er1645v2BgrMVPppOEIpV6RaDnsOptionsDnsslImportDomains
         INTEGER,
      er1645v2BgrMVPppOEIpV6RsSend
         INTEGER,
      er1645v2BgrMVPppOEIpV6RsMaxRandomDelay
         TimeTicks,
      er1645v2BgrMVPppOEIpV6RsInterval
         TimeTicks,
      er1645v2BgrMVPppOEIpV6RsMaxSolicitations
         Integer32,
      er1645v2BgrMVPppOEIpV6TrafficPolicyInbound
         DisplayString,
      er1645v2BgrMVPppOEIpV6TrafficPolicyOutbound
         DisplayString,
      er1645v2BgrMVPppOEIpV6FirewallZone
         DisplayString,
      er1645v2BgrMVPppOEIpV6DhcpClientAddrAC
         INTEGER,
      er1645v2BgrMVPppOEIpV6DhcpClientPrDelMode
         INTEGER,
      er1645v2BgrMVPppOEIpV6DhcpClientPrDelPool
         DisplayString,
      er1645v2BgrMVPppOEIpV6DhcpClientPrDelPdExclOpt
         INTEGER,
      er1645v2BgrMVPppOEIpV6DhcpClientDnsServerPref
         Integer32,
      er1645v2BgrMVPppOEIpV6DhcpClientRapidCommit
         INTEGER,
      er1645v2BgrMVPppOEIpV6DhcpClientTimersSolTimeOut
         TimeTicks,
      er1645v2BgrMVPppOEIpV6DhcpClientTimersSolMaxRt
         TimeTicks,
      er1645v2BgrMVPppOEIpV6DhcpClientTimersInfoRefresh
         TimeTicks,
      er1645v2BgrMVPppOEIpV6DhcpServerMode
         INTEGER,
      er1645v2BgrMVPppOEIpV6DhcpServerPreference
         Integer32,
      er1645v2BgrMVPppOEIpV6DhcpServerPool
         DisplayString,
      er1645v2BgrMVPppOEIpV6DhcpServerRapidCommit
         INTEGER,
      er1645v2BgrMVPppOEIpV6DhcpServerTimersInfoRefresh
         TimeTicks,
      er1645v2BgrMVPppOEIpV6DhcpRelayMode
         INTEGER,
      er1645v2BgrMVPppOEIpV6SendRedirect
         INTEGER,
      er1645v2BgrMVPppOEIpV6LinkMtu
         Integer32,
      er1645v2BgrMVPppOEIpV6InterfaceId
         OCTET STRING,
      er1645v2BgrMVPppOEIpV6MF
         Integer32,
      er1645v2BgrMVPppOEIpV6IcmpMessagesNoRoute
         INTEGER,
      er1645v2BgrMVPppOEIpV6IcmpMessagesBeyondScope
         INTEGER,
      er1645v2BgrMVPppOEIpV6IcmpMessagesAddressUnreachable
         INTEGER,
      er1645v2BgrMVPppOEIpV6IcmpMessagesPortUnreachable
         INTEGER,
      er1645v2BgrMVPppOEIpV6IcmpMessagesPacketTooBig
         INTEGER,
      er1645v2BgrMVPppOEIpV6IcmpMessagesHopLimitExceeded
         INTEGER,
      er1645v2BgrMVPppOEIpV6IcmpMessagesFragTimeExceeded
         INTEGER,
      er1645v2BgrMVPppOEIpV6IcmpMessagesHeaderFieldErr
         INTEGER,
      er1645v2BgrMVPppOEIpV6IcmpMessagesOptionUnrecognized
         INTEGER,
      er1645v2BgrMVPppOEIpV6IcmpMessagesRedirect
         INTEGER,
      er1645v2BgrMVPppOEPppLnkMOperation
         INTEGER,
      er1645v2BgrMVPppOEPppLnkMInterval
         TimeTicks,
      er1645v2BgrMVPppOEPppLnkMRepTimeOut
         TimeTicks,
      er1645v2BgrMVPppOEPppLnkMFailsPrmt
         Integer32,
      er1645v2BgrMVPppOEPppAuthentication
         INTEGER,
      er1645v2BgrMVPppOEPppAuthenPeriod
         TimeTicks,
      er1645v2BgrMVPppOEPppSessionName
         DisplayString,
      er1645v2BgrMVPppOEPppSessionSecret
         DisplayString,
      er1645v2BgrMVPppOEPppEncModeSessionSecret
         INTEGER,
      er1645v2BgrMVPppOEPppEncSessionSecret
         DisplayString,
      er1645v2BgrMVPppOEPppServiceName
         DisplayString
      }

er1645v2BgrMVPppOEActions OBJECT-TYPE
   SYNTAX      VariableLengthTableActions
   MAX-ACCESS  read-write
   STATUS      current
   DESCRIPTION
      "By way of this field, some manipulations
       on this table may be performed."
   ::= {er1645v2BgrMVPppOEEntry 2}

er1645v2BgrMVPppOETableIx OBJECT-TYPE
   SYNTAX      TableIndex
   MAX-ACCESS  not-accessible
   STATUS      current
   DESCRIPTION
      ""
   ::= {er1645v2BgrMVPppOEEntry 11}

er1645v2BgrMVPppOEName OBJECT-TYPE
   SYNTAX      DisplayString
   MAX-ACCESS  read-write
   STATUS      current
   DESCRIPTION
      "Path: bridgeGroup.editConf.pppoEClient.name"
   ::= {er1645v2BgrMVPppOEEntry 16777216}

er1645v2BgrMVPppOERemark OBJECT-TYPE
   SYNTAX      DisplayString
   MAX-ACCESS  read-write
   STATUS      current
   DESCRIPTION
      "Path: bridgeGroup.editConf.pppoEClient.remark"
   ::= {er1645v2BgrMVPppOEEntry 1157627904}

er1645v2BgrMVPppOEAdminStatus OBJECT-TYPE
   SYNTAX      INTEGER
               {
               up (1),
               down (2)
               }
   MAX-ACCESS  read-write
   STATUS      current
   DESCRIPTION
      "Path: bridgeGroup.editConf.pppoEClient.adminStatus

       Possibilities:
               up   (1)
               down   (2)"
   ::= {er1645v2BgrMVPppOEEntry 33554432}

er1645v2BgrMVPppOEMode OBJECT-TYPE
   SYNTAX      INTEGER
               {
               routing (1),
               multilink (8),
               ipV6 (16),
               ipV6ipV4 (17)
               }
   MAX-ACCESS  read-write
   STATUS      current
   DESCRIPTION
      "Path: bridgeGroup.editConf.pppoEClient.mode

       Possibilities:
               routing   (1)
               multilink   (8)
               ipV6   (16)
               ipV6/ipV4   (17)"
   ::= {er1645v2BgrMVPppOEEntry 67108864}

er1645v2BgrMVPppOEIpVrfRouter OBJECT-TYPE
   SYNTAX      DisplayString
   MAX-ACCESS  read-write
   STATUS      current
   DESCRIPTION
      "Path: bridgeGroup.editConf.pppoEClient.ip.vrfRouter"
   ::= {er1645v2BgrMVPppOEEntry 53215232}

er1645v2BgrMVPppOEIpAdr OBJECT-TYPE
   SYNTAX      IpAddress
   MAX-ACCESS  read-write
   STATUS      current
   DESCRIPTION
      "Path: bridgeGroup.editConf.pppoEClient.ip.address"
   ::= {er1645v2BgrMVPppOEEntry 58261504}

er1645v2BgrMVPppOEIpNetm OBJECT-TYPE
   SYNTAX      IpAddress
   MAX-ACCESS  read-write
   STATUS      current
   DESCRIPTION
      "Path: bridgeGroup.editConf.pppoEClient.ip.netMask"
   ::= {er1645v2BgrMVPppOEEntry 58392576}

er1645v2BgrMVPppOEIpSNetName OBJECT-TYPE
   SYNTAX      INTEGER
               {
               slOPTg (0),
               corp (2),
               dmz (3),
               internet (1)
               }
   MAX-ACCESS  read-write
   STATUS      current
   DESCRIPTION
      "Path: bridgeGroup.editConf.pppoEClient.ip.sNet.name

       Possibilities:
               <OPT>   (0)
               corp   (2)
               dmz   (3)
               internet   (1)"
   ::= {er1645v2BgrMVPppOEEntry 53674240}

er1645v2BgrMVPppOEIpSNetCust OBJECT-TYPE
   SYNTAX      DisplayString
   MAX-ACCESS  read-write
   STATUS      current
   DESCRIPTION
      "Path: bridgeGroup.editConf.pppoEClient.ip.sNet.custom"
   ::= {er1645v2BgrMVPppOEEntry 53674496}

er1645v2BgrMVPppOEIpRem OBJECT-TYPE
   SYNTAX      IpAddress
   MAX-ACCESS  read-write
   STATUS      current
   DESCRIPTION
      "Path: bridgeGroup.editConf.pppoEClient.ip.remote"
   ::= {er1645v2BgrMVPppOEEntry 58458112}

er1645v2BgrMVPppOEIpUnnumbered OBJECT-TYPE
   SYNTAX      DisplayString
   MAX-ACCESS  read-write
   STATUS      current
   DESCRIPTION
      "Path: bridgeGroup.editConf.pppoEClient.ip.unnumbered"
   ::= {er1645v2BgrMVPppOEEntry 52625408}

er1645v2BgrMVPppOEIpGwPref OBJECT-TYPE
   SYNTAX      Integer32
   MAX-ACCESS  read-write
   STATUS      current
   DESCRIPTION
      "Path: bridgeGroup.editConf.pppoEClient.ip.gatewayPreference"
   ::= {er1645v2BgrMVPppOEEntry 52690944}

er1645v2BgrMVPppOEIpRsn OBJECT-TYPE
   SYNTAX      INTEGER
               {
               disabled (0),
               enabled (1)
               }
   MAX-ACCESS  read-write
   STATUS      current
   DESCRIPTION
      "Path: bridgeGroup.editConf.pppoEClient.ip.requestSubnet

       Possibilities:
               disabled   (0)
               enabled   (1)"
   ::= {er1645v2BgrMVPppOEEntry 56688640}

er1645v2BgrMVPppOEIpMtu OBJECT-TYPE
   SYNTAX      Integer32
   MAX-ACCESS  read-write
   STATUS      current
   DESCRIPTION
      "Path: bridgeGroup.editConf.pppoEClient.ip.mtu"
   ::= {er1645v2BgrMVPppOEEntry 52953088}

er1645v2BgrMVPppOEIpMssAdjust OBJECT-TYPE
   SYNTAX      INTEGER
               {
               disabled (0),
               auto (65536)
               }
   MAX-ACCESS  read-write
   STATUS      current
   DESCRIPTION
      "Path: bridgeGroup.editConf.pppoEClient.ip.mssAdjust

       Possibilities:
               disabled   (0)
               auto   (65536)"
   ::= {er1645v2BgrMVPppOEEntry 53280768}

er1645v2BgrMVPppOEIpRipMetric OBJECT-TYPE
   SYNTAX      Integer32
   MAX-ACCESS  read-write
   STATUS      current
   DESCRIPTION
      "Path: bridgeGroup.editConf.pppoEClient.ip.rip.metric"
   ::= {er1645v2BgrMVPppOEEntry 51712768}

er1645v2BgrMVPppOEIpRipMetricOut OBJECT-TYPE
   SYNTAX      Integer32
   MAX-ACCESS  read-write
   STATUS      current
   DESCRIPTION
      "Path: bridgeGroup.editConf.pppoEClient.ip.rip.metricOut"
   ::= {er1645v2BgrMVPppOEEntry 51713024}

er1645v2BgrMVPppOEIpRipMode OBJECT-TYPE
   SYNTAX      INTEGER
               {
               disabled (0),
               passive (1),
               active (2)
               }
   MAX-ACCESS  read-write
   STATUS      current
   DESCRIPTION
      "Path: bridgeGroup.editConf.pppoEClient.ip.rip.mode

       Possibilities:
               disabled   (0)
               passive   (1)
               active   (2)"
   ::= {er1645v2BgrMVPppOEEntry 51713280}

er1645v2BgrMVPppOEIpRipTxVer OBJECT-TYPE
   SYNTAX      INTEGER
               {
               rip1 (0),
               rip2 (1),
               rip1mcompatible (2)
               }
   MAX-ACCESS  read-write
   STATUS      current
   DESCRIPTION
      "Path: bridgeGroup.editConf.pppoEClient.ip.rip.txVersion

       Possibilities:
               rip1   (0)
               rip2   (1)
               rip1-compatible   (2)"
   ::= {er1645v2BgrMVPppOEEntry 51716864}

er1645v2BgrMVPppOEIpRipRxVer OBJECT-TYPE
   SYNTAX      INTEGER
               {
               rip1only (0),
               rip2only (1),
               rip12 (2)
               }
   MAX-ACCESS  read-write
   STATUS      current
   DESCRIPTION
      "Path: bridgeGroup.editConf.pppoEClient.ip.rip.rxVersion

       Possibilities:
               rip1only   (0)
               rip2only   (1)
               rip1&2   (2)"
   ::= {er1645v2BgrMVPppOEEntry 51717120}

er1645v2BgrMVPppOEIpRipSplitH OBJECT-TYPE
   SYNTAX      INTEGER
               {
               disabled (0),
               enabled (1),
               poisonedReverse (2)
               }
   MAX-ACCESS  read-write
   STATUS      current
   DESCRIPTION
      "Path: bridgeGroup.editConf.pppoEClient.ip.rip.splitHorizon

       Possibilities:
               disabled   (0)
               enabled   (1)
               poisonedReverse   (2)"
   ::= {er1645v2BgrMVPppOEEntry 51713792}

er1645v2BgrMVPppOEIpRipAuth OBJECT-TYPE
   SYNTAX      INTEGER
               {
               disabled (0),
               texts (1),
               md5 (2)
               }
   MAX-ACCESS  read-write
   STATUS      current
   DESCRIPTION
      "Path: bridgeGroup.editConf.pppoEClient.ip.rip.authentication

       Possibilities:
               disabled   (0)
               text    (1)
               md5   (2)"
   ::= {er1645v2BgrMVPppOEEntry 51712512}

er1645v2BgrMVPppOEIpRipFilter OBJECT-TYPE
   SYNTAX      DisplayString
   MAX-ACCESS  read-write
   STATUS      current
   DESCRIPTION
      "Path: bridgeGroup.editConf.pppoEClient.ip.rip.filter"
   ::= {er1645v2BgrMVPppOEEntry 51716096}

er1645v2BgrMVPppOEIpRipFilterIn OBJECT-TYPE
   SYNTAX      DisplayString
   MAX-ACCESS  read-write
   STATUS      current
   DESCRIPTION
      "Path: bridgeGroup.editConf.pppoEClient.ip.rip.filterIn"
   ::= {er1645v2BgrMVPppOEEntry 51716352}

er1645v2BgrMVPppOEIpRipClearNextHop OBJECT-TYPE
   SYNTAX      INTEGER
               {
               disabled (0),
               enabled (1)
               }
   MAX-ACCESS  read-write
   STATUS      current
   DESCRIPTION
      "Path: bridgeGroup.editConf.pppoEClient.ip.rip.clearNextHop

       Possibilities:
               disabled   (0)
               enabled   (1)"
   ::= {er1645v2BgrMVPppOEEntry 51708416}

er1645v2BgrMVPppOEIpAccPol OBJECT-TYPE
   SYNTAX      DisplayString
   MAX-ACCESS  read-write
   STATUS      current
   DESCRIPTION
      "Path: bridgeGroup.editConf.pppoEClient.ip.accessPolicy"
   ::= {er1645v2BgrMVPppOEEntry 53084160}

er1645v2BgrMVPppOEIpAB OBJECT-TYPE
   SYNTAX      DisplayString
   MAX-ACCESS  read-write
   STATUS      current
   DESCRIPTION
      "Path: bridgeGroup.editConf.pppoEClient.ip.trafficPolicy"
   ::= {er1645v2BgrMVPppOEEntry 51249152}

er1645v2BgrMVPppOEIpMA OBJECT-TYPE
   SYNTAX      INTEGER
               {
               disabled (0),
               enabled (1)
               }
   MAX-ACCESS  read-write
   STATUS      current
   DESCRIPTION
      "Path: bridgeGroup.editConf.pppoEClient.ip.mgmtAccess

       Possibilities:
               disabled   (0)
               enabled   (1)"
   ::= {er1645v2BgrMVPppOEEntry 51380224}

er1645v2BgrMVPppOEIpMF OBJECT-TYPE
   SYNTAX      Integer32
   MAX-ACCESS  read-write
   STATUS      current
   DESCRIPTION
      "Path: bridgeGroup.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2BgrMVPppOEEntry 51445760}

er1645v2BgrMVPppOEIpDB OBJECT-TYPE
   SYNTAX      INTEGER
               {
               disabled (0),
               enabled (1)
               }
   MAX-ACCESS  read-write
   STATUS      current
   DESCRIPTION
      "Path: bridgeGroup.editConf.pppoEClient.ip.directedBroadcasts

       Possibilities:
               disabled   (0)
               enabled   (1)"
   ::= {er1645v2BgrMVPppOEEntry 51773440}

er1645v2BgrMVPppOEIpIR OBJECT-TYPE
   SYNTAX      INTEGER
               {
               disabled (0),
               enabled (1)
               }
   MAX-ACCESS  read-write
   STATUS      current
   DESCRIPTION
      "Path: bridgeGroup.editConf.pppoEClient.ip.icmpRedirects

       Possibilities:
               disabled   (0)
               enabled   (1)"
   ::= {er1645v2BgrMVPppOEEntry 52035584}

er1645v2BgrMVPppOEIpIgmp OBJECT-TYPE
   SYNTAX      INTEGER
               {
               disabled (0),
               proxy (1),
               router (2),
               v3Router (5)
               }
   MAX-ACCESS  read-write
   STATUS      current
   DESCRIPTION
      "Path: bridgeGroup.editConf.pppoEClient.ip.igmp

       Possibilities:
               disabled   (0)
               proxy   (1)
               router   (2)
               v3Router   (5)"
   ::= {er1645v2BgrMVPppOEEntry 52428800}

er1645v2BgrMVPppOEIpNN OBJECT-TYPE
   SYNTAX      DisplayString
   MAX-ACCESS  read-write
   STATUS      current
   DESCRIPTION
      "Path: bridgeGroup.editConf.pppoEClient.ip.nat"
   ::= {er1645v2BgrMVPppOEEntry 52101120}

er1645v2BgrMVPppOEIpPimMode OBJECT-TYPE
   SYNTAX      INTEGER
               {
               disabled (0),
               sparse (1),
               passive (2)
               }
   MAX-ACCESS  read-write
   STATUS      current
   DESCRIPTION
      "Path: bridgeGroup.editConf.pppoEClient.ip.pim.mode

       Possibilities:
               disabled   (0)
               sparse   (1)
               passive   (2)"
   ::= {er1645v2BgrMVPppOEEntry 53346560}

er1645v2BgrMVPppOEIpPimDrPriority OBJECT-TYPE
   SYNTAX      Counter32
   MAX-ACCESS  read-write
   STATUS      current
   DESCRIPTION
      "Path: bridgeGroup.editConf.pppoEClient.ip.pim.drPriority

       32 bit unsigned wrappable counter."
   ::= {er1645v2BgrMVPppOEEntry 53346816}

er1645v2BgrMVPppOEIpPimHelloTime OBJECT-TYPE
   SYNTAX      TimeTicks
   MAX-ACCESS  read-write
   STATUS      current
   DESCRIPTION
      "Path: bridgeGroup.editConf.pppoEClient.ip.pim.helloTime

       Time in centi-second."
   ::= {er1645v2BgrMVPppOEEntry 53347072}

er1645v2BgrMVPppOEIpPimPropagationDelay OBJECT-TYPE
   SYNTAX      TimeTicks
   MAX-ACCESS  read-write
   STATUS      current
   DESCRIPTION
      "Path: bridgeGroup.editConf.pppoEClient.ip.pim.propagationDelay

       Time in centi-second."
   ::= {er1645v2BgrMVPppOEEntry 53347328}

er1645v2BgrMVPppOEIpPimOverrideInterval OBJECT-TYPE
   SYNTAX      TimeTicks
   MAX-ACCESS  read-write
   STATUS      current
   DESCRIPTION
      "Path: bridgeGroup.editConf.pppoEClient.ip.pim.overrideInterval

       Time in centi-second."
   ::= {er1645v2BgrMVPppOEEntry 53347584}

er1645v2BgrMVPppOEIpPimBsrBorder OBJECT-TYPE
   SYNTAX      INTEGER
               {
               disabled (0),
               enabled (1)
               }
   MAX-ACCESS  read-write
   STATUS      current
   DESCRIPTION
      "Path: bridgeGroup.editConf.pppoEClient.ip.pim.bsrBorder

       Possibilities:
               disabled   (0)
               enabled   (1)"
   ::= {er1645v2BgrMVPppOEEntry 53347840}

er1645v2BgrMVPppOEIpPimTtlThreshold OBJECT-TYPE
   SYNTAX      Integer32
   MAX-ACCESS  read-write
   STATUS      current
   DESCRIPTION
      "Path: bridgeGroup.editConf.pppoEClient.ip.pim.ttlThreshold"
   ::= {er1645v2BgrMVPppOEEntry 53348096}

er1645v2BgrMVPppOEIpIMNetworkUnreachable OBJECT-TYPE
   SYNTAX      INTEGER
               {
               disabled (0),
               enabled (1)
               }
   MAX-ACCESS  read-write
   STATUS      current
   DESCRIPTION
      "Path: bridgeGroup.editConf.pppoEClient.ip.icmpMessages.networkUnreachable

       Possibilities:
               disabled   (0)
               enabled   (1)"
   ::= {er1645v2BgrMVPppOEEntry 53412096}

er1645v2BgrMVPppOEIpIMHostUnreachable OBJECT-TYPE
   SYNTAX      INTEGER
               {
               disabled (0),
               enabled (1)
               }
   MAX-ACCESS  read-write
   STATUS      current
   DESCRIPTION
      "Path: bridgeGroup.editConf.pppoEClient.ip.icmpMessages.hostUnreachable

       Possibilities:
               disabled   (0)
               enabled   (1)"
   ::= {er1645v2BgrMVPppOEEntry 53412352}

er1645v2BgrMVPppOEIpIMProtocolUnreachable OBJECT-TYPE
   SYNTAX      INTEGER
               {
               disabled (0),
               enabled (1)
               }
   MAX-ACCESS  read-write
   STATUS      current
   DESCRIPTION
      "Path: bridgeGroup.editConf.pppoEClient.ip.icmpMessages.protocolUnreachable

       Possibilities:
               disabled   (0)
               enabled   (1)"
   ::= {er1645v2BgrMVPppOEEntry 53412608}

er1645v2BgrMVPppOEIpIMPortUnreachable OBJECT-TYPE
   SYNTAX      INTEGER
               {
               disabled (0),
               enabled (1)
               }
   MAX-ACCESS  read-write
   STATUS      current
   DESCRIPTION
      "Path: bridgeGroup.editConf.pppoEClient.ip.icmpMessages.portUnreachable

       Possibilities:
               disabled   (0)
               enabled   (1)"
   ::= {er1645v2BgrMVPppOEEntry 53412864}

er1645v2BgrMVPppOEIpIMMtuExceeded OBJECT-TYPE
   SYNTAX      INTEGER
               {
               disabled (0),
               enabled (1)
               }
   MAX-ACCESS  read-write
   STATUS      current
   DESCRIPTION
      "Path: bridgeGroup.editConf.pppoEClient.ip.icmpMessages.mtuExceeded

       Possibilities:
               disabled   (0)
               enabled   (1)"
   ::= {er1645v2BgrMVPppOEEntry 53413120}

er1645v2BgrMVPppOEIpIMAdminProhibited OBJECT-TYPE
   SYNTAX      INTEGER
               {
               disabled (0),
               enabled (1)
               }
   MAX-ACCESS  read-write
   STATUS      current
   DESCRIPTION
      "Path: bridgeGroup.editConf.pppoEClient.ip.icmpMessages.adminProhibited

       Possibilities:
               disabled   (0)
               enabled   (1)"
   ::= {er1645v2BgrMVPppOEEntry 53413376}

er1645v2BgrMVPppOEIpIMTtlExceeded OBJECT-TYPE
   SYNTAX      INTEGER
               {
               disabled (0),
               enabled (1)
               }
   MAX-ACCESS  read-write
   STATUS      current
   DESCRIPTION
      "Path: bridgeGroup.editConf.pppoEClient.ip.icmpMessages.ttlExceeded

       Possibilities:
               disabled   (0)
               enabled   (1)"
   ::= {er1645v2BgrMVPppOEEntry 53413632}

er1645v2BgrMVPppOEIpIMRedirect OBJECT-TYPE
   SYNTAX      INTEGER
               {
               disabled (0),
               enabled (1)
               }
   MAX-ACCESS  read-write
   STATUS      current
   DESCRIPTION
      "Path: bridgeGroup.editConf.pppoEClient.ip.icmpMessages.redirect

       Possibilities:
               disabled   (0)
               enabled   (1)"
   ::= {er1645v2BgrMVPppOEEntry 53413888}

er1645v2BgrMVPppOEIpV6VrfRouter OBJECT-TYPE
   SYNTAX      DisplayString
   MAX-ACCESS  read-write
   STATUS      current
   DESCRIPTION
      "Path: bridgeGroup.editConf.pppoEClient.ipV6.vrfRouter"
   ::= {er1645v2BgrMVPppOEEntry 704708608}

er1645v2BgrMVPppOEIpV6AddrAutoConfigNrDupAddrDetects OBJECT-TYPE
   SYNTAX      Integer32
   MAX-ACCESS  read-write
   STATUS      current
   DESCRIPTION
      "Path: bridgeGroup.editConf.pppoEClient.ipV6.addrAutoConfig.nrDupAddrDetects"
   ::= {er1645v2BgrMVPppOEEntry 704905472}

er1645v2BgrMVPppOEIpV6AddrAutoConfigAcceptRa OBJECT-TYPE
   SYNTAX      INTEGER
               {
               disabled (0),
               enabled (1)
               }
   MAX-ACCESS  read-write
   STATUS      current
   DESCRIPTION
      "Path: bridgeGroup.editConf.pppoEClient.ipV6.addrAutoConfig.acceptRa

       Possibilities:
               disabled   (0)
               enabled   (1)"
   ::= {er1645v2BgrMVPppOEEntry 704905728}

er1645v2BgrMVPppOEIpV6AddrAutoConfigAcceptRaRdnss OBJECT-TYPE
   SYNTAX      INTEGER
               {
               disabled (0),
               enabled (1)
               }
   MAX-ACCESS  read-write
   STATUS      current
   DESCRIPTION
      "Path: bridgeGroup.editConf.pppoEClient.ipV6.addrAutoConfig.acceptRaRdnss

       Possibilities:
               disabled   (0)
               enabled   (1)"
   ::= {er1645v2BgrMVPppOEEntry 704905984}

er1645v2BgrMVPppOEIpV6AddrAutoConfigAcceptRaDnssl OBJECT-TYPE
   SYNTAX      INTEGER
               {
               disabled (0),
               enabled (1)
               }
   MAX-ACCESS  read-write
   STATUS      current
   DESCRIPTION
      "Path: bridgeGroup.editConf.pppoEClient.ipV6.addrAutoConfig.acceptRaDnssl

       Possibilities:
               disabled   (0)
               enabled   (1)"
   ::= {er1645v2BgrMVPppOEEntry 704906240}

er1645v2BgrMVPppOEIpV6DefaultRoute OBJECT-TYPE
   SYNTAX      INTEGER
               {
               disabled (0),
               enabled (1)
               }
   MAX-ACCESS  read-write
   STATUS      current
   DESCRIPTION
      "Path: bridgeGroup.editConf.pppoEClient.ipV6.defaultRoute

       Possibilities:
               disabled   (0)
               enabled   (1)"
   ::= {er1645v2BgrMVPppOEEntry 704970752}

er1645v2BgrMVPppOEIpV6RaSend OBJECT-TYPE
   SYNTAX      INTEGER
               {
               disabled (0),
               enabled (1)
               }
   MAX-ACCESS  read-write
   STATUS      current
   DESCRIPTION
      "Path: bridgeGroup.editConf.pppoEClient.ipV6.ra.send

       Possibilities:
               disabled   (0)
               enabled   (1)"
   ::= {er1645v2BgrMVPppOEEntry 705036544}

er1645v2BgrMVPppOEIpV6RaMinInterval OBJECT-TYPE
   SYNTAX      TimeTicks
   MAX-ACCESS  read-write
   STATUS      current
   DESCRIPTION
      "Path: bridgeGroup.editConf.pppoEClient.ipV6.ra.minInterval

       Time in centi-second."
   ::= {er1645v2BgrMVPppOEEntry 705036800}

er1645v2BgrMVPppOEIpV6RaMaxInterval OBJECT-TYPE
   SYNTAX      TimeTicks
   MAX-ACCESS  read-write
   STATUS      current
   DESCRIPTION
      "Path: bridgeGroup.editConf.pppoEClient.ipV6.ra.maxInterval

       Time in centi-second."
   ::= {er1645v2BgrMVPppOEEntry 705037056}

er1645v2BgrMVPppOEIpV6RaManagedFlag OBJECT-TYPE
   SYNTAX      INTEGER
               {
               disabled (0),
               enabled (1)
               }
   MAX-ACCESS  read-write
   STATUS      current
   DESCRIPTION
      "Path: bridgeGroup.editConf.pppoEClient.ipV6.ra.managedFlag

       Possibilities:
               disabled   (0)
               enabled   (1)"
   ::= {er1645v2BgrMVPppOEEntry 705037312}

er1645v2BgrMVPppOEIpV6RaOtherConfFlag OBJECT-TYPE
   SYNTAX      INTEGER
               {
               disabled (0),
               enabled (1)
               }
   MAX-ACCESS  read-write
   STATUS      current
   DESCRIPTION
      "Path: bridgeGroup.editConf.pppoEClient.ipV6.ra.otherConfFlag

       Possibilities:
               disabled   (0)
               enabled   (1)"
   ::= {er1645v2BgrMVPppOEEntry 705037568}

er1645v2BgrMVPppOEIpV6RaLinkMtu OBJECT-TYPE
   SYNTAX      Integer32
   MAX-ACCESS  read-write
   STATUS      current
   DESCRIPTION
      "Path: bridgeGroup.editConf.pppoEClient.ipV6.ra.linkMtu"
   ::= {er1645v2BgrMVPppOEEntry 705037824}

er1645v2BgrMVPppOEIpV6RaReachableTime OBJECT-TYPE
   SYNTAX      TimeTicks
   MAX-ACCESS  read-write
   STATUS      current
   DESCRIPTION
      "Path: bridgeGroup.editConf.pppoEClient.ipV6.ra.reachableTime

       Time in centi-second."
   ::= {er1645v2BgrMVPppOEEntry 705038080}

er1645v2BgrMVPppOEIpV6RaRetransmitTime OBJECT-TYPE
   SYNTAX      TimeTicks
   MAX-ACCESS  read-write
   STATUS      current
   DESCRIPTION
      "Path: bridgeGroup.editConf.pppoEClient.ipV6.ra.retransmitTime

       Time in centi-second."
   ::= {er1645v2BgrMVPppOEEntry 705038336}

er1645v2BgrMVPppOEIpV6RaHopLimit OBJECT-TYPE
   SYNTAX      Integer32
   MAX-ACCESS  read-write
   STATUS      current
   DESCRIPTION
      "Path: bridgeGroup.editConf.pppoEClient.ipV6.ra.hopLimit"
   ::= {er1645v2BgrMVPppOEEntry 705038592}

er1645v2BgrMVPppOEIpV6RaDefaultLifeTime OBJECT-TYPE
   SYNTAX      TimeTicks
   MAX-ACCESS  read-write
   STATUS      current
   DESCRIPTION
      "Path: bridgeGroup.editConf.pppoEClient.ipV6.ra.defaultLifeTime

       Time in centi-second."
   ::= {er1645v2BgrMVPppOEEntry 705038848}

er1645v2BgrMVPppOEIpV6RaDnsOptionsRdnssLifeTime OBJECT-TYPE
   SYNTAX      TimeTicks
   MAX-ACCESS  read-write
   STATUS      current
   DESCRIPTION
      "Path: bridgeGroup.editConf.pppoEClient.ipV6.ra.dnsOptions.rdnss.lifeTime

       Time in centi-second."
   ::= {er1645v2BgrMVPppOEEntry 705039140}

er1645v2BgrMVPppOEIpV6RaDnsOptionsRdnssImportServers OBJECT-TYPE
   SYNTAX      INTEGER
               {
               disabled (0),
               enabled (1)
               }
   MAX-ACCESS  read-write
   STATUS      current
   DESCRIPTION
      "Path: bridgeGroup.editConf.pppoEClient.ipV6.ra.dnsOptions.rdnss.importServers

       Possibilities:
               disabled   (0)
               enabled   (1)"
   ::= {er1645v2BgrMVPppOEEntry 705039148}

er1645v2BgrMVPppOEIpV6RaDnsOptionsDnsslLifeTime OBJECT-TYPE
   SYNTAX      TimeTicks
   MAX-ACCESS  read-write
   STATUS      current
   DESCRIPTION
      "Path: bridgeGroup.editConf.pppoEClient.ipV6.ra.dnsOptions.dnssl.lifeTime

       Time in centi-second."
   ::= {er1645v2BgrMVPppOEEntry 705039172}

er1645v2BgrMVPppOEIpV6RaDnsOptionsDnsslImportDomains OBJECT-TYPE
   SYNTAX      INTEGER
               {
               disabled (0),
               enabled (1)
               }
   MAX-ACCESS  read-write
   STATUS      current
   DESCRIPTION
      "Path: bridgeGroup.editConf.pppoEClient.ipV6.ra.dnsOptions.dnssl.importDomains

       Possibilities:
               disabled   (0)
               enabled   (1)"
   ::= {er1645v2BgrMVPppOEEntry 705039180}

er1645v2BgrMVPppOEIpV6RsSend OBJECT-TYPE
   SYNTAX      INTEGER
               {
               disabled (0),
               enabled (1)
               }
   MAX-ACCESS  read-write
   STATUS      current
   DESCRIPTION
      "Path: bridgeGroup.editConf.pppoEClient.ipV6.rs.send

       Possibilities:
               disabled   (0)
               enabled   (1)"
   ::= {er1645v2BgrMVPppOEEntry 705954048}

er1645v2BgrMVPppOEIpV6RsMaxRandomDelay OBJECT-TYPE
   SYNTAX      TimeTicks
   MAX-ACCESS  read-write
   STATUS      current
   DESCRIPTION
      "Path: bridgeGroup.editConf.pppoEClient.ipV6.rs.maxRandomDelay

       Time in centi-second."
   ::= {er1645v2BgrMVPppOEEntry 705954304}

er1645v2BgrMVPppOEIpV6RsInterval OBJECT-TYPE
   SYNTAX      TimeTicks
   MAX-ACCESS  read-write
   STATUS      current
   DESCRIPTION
      "Path: bridgeGroup.editConf.pppoEClient.ipV6.rs.interval

       Time in centi-second."
   ::= {er1645v2BgrMVPppOEEntry 705954560}

er1645v2BgrMVPppOEIpV6RsMaxSolicitations OBJECT-TYPE
   SYNTAX      Integer32
   MAX-ACCESS  read-write
   STATUS      current
   DESCRIPTION
      "Path: bridgeGroup.editConf.pppoEClient.ipV6.rs.maxSolicitations"
   ::= {er1645v2BgrMVPppOEEntry 705954816}

er1645v2BgrMVPppOEIpV6TrafficPolicyInbound OBJECT-TYPE
   SYNTAX      DisplayString
   MAX-ACCESS  read-write
   STATUS      current
   DESCRIPTION
      "Path: bridgeGroup.editConf.pppoEClient.ipV6.trafficPolicy.inbound"
   ::= {er1645v2BgrMVPppOEEntry 705364224}

er1645v2BgrMVPppOEIpV6TrafficPolicyOutbound OBJECT-TYPE
   SYNTAX      DisplayString
   MAX-ACCESS  read-write
   STATUS      current
   DESCRIPTION
      "Path: bridgeGroup.editConf.pppoEClient.ipV6.trafficPolicy.outbound"
   ::= {er1645v2BgrMVPppOEEntry 705364480}

er1645v2BgrMVPppOEIpV6FirewallZone OBJECT-TYPE
   SYNTAX      DisplayString
   MAX-ACCESS  read-write
   STATUS      current
   DESCRIPTION
      "Path: bridgeGroup.editConf.pppoEClient.ipV6.firewall.zone"
   ::= {er1645v2BgrMVPppOEEntry 705429760}

er1645v2BgrMVPppOEIpV6DhcpClientAddrAC OBJECT-TYPE
   SYNTAX      INTEGER
               {
               disabled (0),
               enabled (1)
               }
   MAX-ACCESS  read-write
   STATUS      current
   DESCRIPTION
      "Path: bridgeGroup.editConf.pppoEClient.ipV6.dhcp.client.addrAutoConfig

       Possibilities:
               disabled   (0)
               enabled   (1)"
   ::= {er1645v2BgrMVPppOEEntry 705307648}

er1645v2BgrMVPppOEIpV6DhcpClientPrDelMode OBJECT-TYPE
   SYNTAX      INTEGER
               {
               disabled (0),
               enabled (1)
               }
   MAX-ACCESS  read-write
   STATUS      current
   DESCRIPTION
      "Path: bridgeGroup.editConf.pppoEClient.ipV6.dhcp.client.pd.mode

       Possibilities:
               disabled   (0)
               enabled   (1)"
   ::= {er1645v2BgrMVPppOEEntry 705308676}

er1645v2BgrMVPppOEIpV6DhcpClientPrDelPool OBJECT-TYPE
   SYNTAX      DisplayString
   MAX-ACCESS  read-write
   STATUS      current
   DESCRIPTION
      "Path: bridgeGroup.editConf.pppoEClient.ipV6.dhcp.client.pd.pool"
   ::= {er1645v2BgrMVPppOEEntry 705308680}

er1645v2BgrMVPppOEIpV6DhcpClientPrDelPdExclOpt OBJECT-TYPE
   SYNTAX      INTEGER
               {
               disabled (0),
               enabled (1)
               }
   MAX-ACCESS  read-write
   STATUS      current
   DESCRIPTION
      "Path: bridgeGroup.editConf.pppoEClient.ipV6.dhcp.client.pd.pdExclOpt

       Possibilities:
               disabled   (0)
               enabled   (1)"
   ::= {er1645v2BgrMVPppOEEntry 705308684}

er1645v2BgrMVPppOEIpV6DhcpClientDnsServerPref OBJECT-TYPE
   SYNTAX      Integer32
   MAX-ACCESS  read-write
   STATUS      current
   DESCRIPTION
      "Path: bridgeGroup.editConf.pppoEClient.ipV6.dhcp.client.dns.serverPref"
   ::= {er1645v2BgrMVPppOEEntry 705310724}

er1645v2BgrMVPppOEIpV6DhcpClientRapidCommit OBJECT-TYPE
   SYNTAX      INTEGER
               {
               disabled (0),
               enabled (1)
               }
   MAX-ACCESS  read-write
   STATUS      current
   DESCRIPTION
      "Path: bridgeGroup.editConf.pppoEClient.ipV6.dhcp.client.rapidCommit

       Possibilities:
               disabled   (0)
               enabled   (1)"
   ::= {er1645v2BgrMVPppOEEntry 705309696}

er1645v2BgrMVPppOEIpV6DhcpClientTimersSolTimeOut OBJECT-TYPE
   SYNTAX      TimeTicks
   MAX-ACCESS  read-write
   STATUS      current
   DESCRIPTION
      "Path: bridgeGroup.editConf.pppoEClient.ipV6.dhcp.client.timers.solTimeOut

       Time in centi-second."
   ::= {er1645v2BgrMVPppOEEntry 705311748}

er1645v2BgrMVPppOEIpV6DhcpClientTimersSolMaxRt OBJECT-TYPE
   SYNTAX      TimeTicks
   MAX-ACCESS  read-write
   STATUS      current
   DESCRIPTION
      "Path: bridgeGroup.editConf.pppoEClient.ipV6.dhcp.client.timers.solMaxRt

       Time in centi-second."
   ::= {er1645v2BgrMVPppOEEntry 705311752}

er1645v2BgrMVPppOEIpV6DhcpClientTimersInfoRefresh OBJECT-TYPE
   SYNTAX      TimeTicks
   MAX-ACCESS  read-write
   STATUS      current
   DESCRIPTION
      "Path: bridgeGroup.editConf.pppoEClient.ipV6.dhcp.client.timers.infoRefresh

       Time in centi-second."
   ::= {er1645v2BgrMVPppOEEntry 705311756}

er1645v2BgrMVPppOEIpV6DhcpServerMode OBJECT-TYPE
   SYNTAX      INTEGER
               {
               disabled (0),
               enabled (1)
               }
   MAX-ACCESS  read-write
   STATUS      current
   DESCRIPTION
      "Path: bridgeGroup.editConf.pppoEClient.ipV6.dhcp.server.mode

       Possibilities:
               disabled   (0)
               enabled   (1)"
   ::= {er1645v2BgrMVPppOEEntry 705315840}

er1645v2BgrMVPppOEIpV6DhcpServerPreference OBJECT-TYPE
   SYNTAX      Integer32
   MAX-ACCESS  read-write
   STATUS      current
   DESCRIPTION
      "Path: bridgeGroup.editConf.pppoEClient.ipV6.dhcp.server.preference"
   ::= {er1645v2BgrMVPppOEEntry 705316864}

er1645v2BgrMVPppOEIpV6DhcpServerPool OBJECT-TYPE
   SYNTAX      DisplayString
   MAX-ACCESS  read-write
   STATUS      current
   DESCRIPTION
      "Path: bridgeGroup.editConf.pppoEClient.ipV6.dhcp.server.pool"
   ::= {er1645v2BgrMVPppOEEntry 705317888}

er1645v2BgrMVPppOEIpV6DhcpServerRapidCommit OBJECT-TYPE
   SYNTAX      INTEGER
               {
               disabled (0),
               enabled (1)
               }
   MAX-ACCESS  read-write
   STATUS      current
   DESCRIPTION
      "Path: bridgeGroup.editConf.pppoEClient.ipV6.dhcp.server.rapidCommit

       Possibilities:
               disabled   (0)
               enabled   (1)"
   ::= {er1645v2BgrMVPppOEEntry 705318912}

er1645v2BgrMVPppOEIpV6DhcpServerTimersInfoRefresh OBJECT-TYPE
   SYNTAX      TimeTicks
   MAX-ACCESS  read-write
   STATUS      current
   DESCRIPTION
      "Path: bridgeGroup.editConf.pppoEClient.ipV6.dhcp.server.timers.infoRefresh

       Time in centi-second."
   ::= {er1645v2BgrMVPppOEEntry 705319940}

er1645v2BgrMVPppOEIpV6DhcpRelayMode OBJECT-TYPE
   SYNTAX      INTEGER
               {
               disabled (0),
               enabled (1)
               }
   MAX-ACCESS  read-write
   STATUS      current
   DESCRIPTION
      "Path: bridgeGroup.editConf.pppoEClient.ipV6.dhcp.relay.mode

       Possibilities:
               disabled   (0)
               enabled   (1)"
   ::= {er1645v2BgrMVPppOEEntry 705323040}

er1645v2BgrMVPppOEIpV6SendRedirect OBJECT-TYPE
   SYNTAX      INTEGER
               {
               disabled (0),
               enabled (1)
               }
   MAX-ACCESS  read-write
   STATUS      current
   DESCRIPTION
      "Path: bridgeGroup.editConf.pppoEClient.ipV6.sendRedirect

       Possibilities:
               disabled   (0)
               enabled   (1)"
   ::= {er1645v2BgrMVPppOEEntry 705101824}

er1645v2BgrMVPppOEIpV6LinkMtu OBJECT-TYPE
   SYNTAX      Integer32
   MAX-ACCESS  read-write
   STATUS      current
   DESCRIPTION
      "Path: bridgeGroup.editConf.pppoEClient.ipV6.linkMtu"
   ::= {er1645v2BgrMVPppOEEntry 705167360}

er1645v2BgrMVPppOEIpV6InterfaceId OBJECT-TYPE
   SYNTAX      OCTET STRING
   MAX-ACCESS  read-write
   STATUS      current
   DESCRIPTION
      "Path: bridgeGroup.editConf.pppoEClient.ipV6.interfaceId"
   ::= {er1645v2BgrMVPppOEEntry 705232896}

er1645v2BgrMVPppOEIpV6MF OBJECT-TYPE
   SYNTAX      Integer32
   MAX-ACCESS  read-write
   STATUS      current
   DESCRIPTION
      "Path: bridgeGroup.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2BgrMVPppOEEntry 705757184}

er1645v2BgrMVPppOEIpV6IcmpMessagesNoRoute OBJECT-TYPE
   SYNTAX      INTEGER
               {
               disabled (0),
               enabled (1)
               }
   MAX-ACCESS  read-write
   STATUS      current
   DESCRIPTION
      "Path: bridgeGroup.editConf.pppoEClient.ipV6.icmpMessages.noRoute

       Possibilities:
               disabled   (0)
               enabled   (1)"
   ::= {er1645v2BgrMVPppOEEntry 705822976}

er1645v2BgrMVPppOEIpV6IcmpMessagesBeyondScope OBJECT-TYPE
   SYNTAX      INTEGER
               {
               disabled (0),
               enabled (1)
               }
   MAX-ACCESS  read-write
   STATUS      current
   DESCRIPTION
      "Path: bridgeGroup.editConf.pppoEClient.ipV6.icmpMessages.beyondScope

       Possibilities:
               disabled   (0)
               enabled   (1)"
   ::= {er1645v2BgrMVPppOEEntry 705823488}

er1645v2BgrMVPppOEIpV6IcmpMessagesAddressUnreachable OBJECT-TYPE
   SYNTAX      INTEGER
               {
               disabled (0),
               enabled (1)
               }
   MAX-ACCESS  read-write
   STATUS      current
   DESCRIPTION
      "Path: bridgeGroup.editConf.pppoEClient.ipV6.icmpMessages.addressUnreachable

       Possibilities:
               disabled   (0)
               enabled   (1)"
   ::= {er1645v2BgrMVPppOEEntry 705823744}

er1645v2BgrMVPppOEIpV6IcmpMessagesPortUnreachable OBJECT-TYPE
   SYNTAX      INTEGER
               {
               disabled (0),
               enabled (1)
               }
   MAX-ACCESS  read-write
   STATUS      current
   DESCRIPTION
      "Path: bridgeGroup.editConf.pppoEClient.ipV6.icmpMessages.portUnreachable

       Possibilities:
               disabled   (0)
               enabled   (1)"
   ::= {er1645v2BgrMVPppOEEntry 705824000}

er1645v2BgrMVPppOEIpV6IcmpMessagesPacketTooBig OBJECT-TYPE
   SYNTAX      INTEGER
               {
               disabled (0),
               enabled (1)
               }
   MAX-ACCESS  read-write
   STATUS      current
   DESCRIPTION
      "Path: bridgeGroup.editConf.pppoEClient.ipV6.icmpMessages.packetTooBig

       Possibilities:
               disabled   (0)
               enabled   (1)"
   ::= {er1645v2BgrMVPppOEEntry 705825280}

er1645v2BgrMVPppOEIpV6IcmpMessagesHopLimitExceeded OBJECT-TYPE
   SYNTAX      INTEGER
               {
               disabled (0),
               enabled (1)
               }
   MAX-ACCESS  read-write
   STATUS      current
   DESCRIPTION
      "Path: bridgeGroup.editConf.pppoEClient.ipV6.icmpMessages.hopLimitExceeded

       Possibilities:
               disabled   (0)
               enabled   (1)"
   ::= {er1645v2BgrMVPppOEEntry 705827840}

er1645v2BgrMVPppOEIpV6IcmpMessagesFragTimeExceeded OBJECT-TYPE
   SYNTAX      INTEGER
               {
               disabled (0),
               enabled (1)
               }
   MAX-ACCESS  read-write
   STATUS      current
   DESCRIPTION
      "Path: bridgeGroup.editConf.pppoEClient.ipV6.icmpMessages.fragTimeExceeded

       Possibilities:
               disabled   (0)
               enabled   (1)"
   ::= {er1645v2BgrMVPppOEEntry 705828096}

er1645v2BgrMVPppOEIpV6IcmpMessagesHeaderFieldErr OBJECT-TYPE
   SYNTAX      INTEGER
               {
               disabled (0),
               enabled (1)
               }
   MAX-ACCESS  read-write
   STATUS      current
   DESCRIPTION
      "Path: bridgeGroup.editConf.pppoEClient.ipV6.icmpMessages.headerFieldErr

       Possibilities:
               disabled   (0)
               enabled   (1)"
   ::= {er1645v2BgrMVPppOEEntry 705830400}

er1645v2BgrMVPppOEIpV6IcmpMessagesOptionUnrecognized OBJECT-TYPE
   SYNTAX      INTEGER
               {
               disabled (0),
               enabled (1)
               }
   MAX-ACCESS  read-write
   STATUS      current
   DESCRIPTION
      "Path: bridgeGroup.editConf.pppoEClient.ipV6.icmpMessages.optionUnrecognized

       Possibilities:
               disabled   (0)
               enabled   (1)"
   ::= {er1645v2BgrMVPppOEEntry 705830912}

er1645v2BgrMVPppOEIpV6IcmpMessagesRedirect OBJECT-TYPE
   SYNTAX      INTEGER
               {
               disabled (0),
               enabled (1)
               }
   MAX-ACCESS  read-write
   STATUS      current
   DESCRIPTION
      "Path: bridgeGroup.editConf.pppoEClient.ipV6.icmpMessages.redirect

       Possibilities:
               disabled   (0)
               enabled   (1)"
   ::= {er1645v2BgrMVPppOEEntry 705832960}

er1645v2BgrMVPppOEPppLnkMOperation OBJECT-TYPE
   SYNTAX      INTEGER
               {
               disabled (0),
               enabled (1)
               }
   MAX-ACCESS  read-write
   STATUS      current
   DESCRIPTION
      "Path: bridgeGroup.editConf.pppoEClient.ppp.linkMonitoring.operation

       Possibilities:
               disabled   (0)
               enabled   (1)"
   ::= {er1645v2BgrMVPppOEEntry 251724032}

er1645v2BgrMVPppOEPppLnkMInterval OBJECT-TYPE
   SYNTAX      TimeTicks
   MAX-ACCESS  read-write
   STATUS      current
   DESCRIPTION
      "Path: bridgeGroup.editConf.pppoEClient.ppp.linkMonitoring.interval

       Time in centi-second."
   ::= {er1645v2BgrMVPppOEEntry 251724288}

er1645v2BgrMVPppOEPppLnkMRepTimeOut OBJECT-TYPE
   SYNTAX      TimeTicks
   MAX-ACCESS  read-write
   STATUS      current
   DESCRIPTION
      "Path: bridgeGroup.editConf.pppoEClient.ppp.linkMonitoring.replyTimeOut

       Time in centi-second."
   ::= {er1645v2BgrMVPppOEEntry 251724544}

er1645v2BgrMVPppOEPppLnkMFailsPrmt OBJECT-TYPE
   SYNTAX      Integer32
   MAX-ACCESS  read-write
   STATUS      current
   DESCRIPTION
      "Path: bridgeGroup.editConf.pppoEClient.ppp.linkMonitoring.failsPermitted"
   ::= {er1645v2BgrMVPppOEEntry 251724800}

er1645v2BgrMVPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: bridgeGroup.editConf.pppoEClient.ppp.authentication

       Possibilities:
               disabled   (0)
               chap   (1)
               pap   (2)
               chapOrPap   (3)
               msChap   (4)
               msChapV2   (5)"
   ::= {er1645v2BgrMVPppOEEntry 251789312}

er1645v2BgrMVPppOEPppAuthenPeriod OBJECT-TYPE
   SYNTAX      TimeTicks
   MAX-ACCESS  read-write
   STATUS      current
   DESCRIPTION
      "Path: bridgeGroup.editConf.pppoEClient.ppp.authenPeriod

       Time in centi-second."
   ::= {er1645v2BgrMVPppOEEntry 251854848}

er1645v2BgrMVPppOEPppSessionName OBJECT-TYPE
   SYNTAX      DisplayString
   MAX-ACCESS  read-write
   STATUS      current
   DESCRIPTION
      "Path: bridgeGroup.editConf.pppoEClient.ppp.sessionName"
   ::= {er1645v2BgrMVPppOEEntry 251985920}

er1645v2BgrMVPppOEPppSessionSecret OBJECT-TYPE
   SYNTAX      DisplayString
   MAX-ACCESS  read-write
   STATUS      current
   DESCRIPTION
      "Path: bridgeGroup.editConf.pppoEClient.ppp.sessionSecret"
   ::= {er1645v2BgrMVPppOEEntry 252051456}

er1645v2BgrMVPppOEPppEncModeSessionSecret OBJECT-TYPE
   SYNTAX      INTEGER
               {
               none (1),
               encrypt (2),
               encType1 (3),
               invalid (128)
               }
   MAX-ACCESS  read-write
   STATUS      current
   DESCRIPTION
      "Path: bridgeGroup.editConf.pppoEClient.ppp.encModeSessionSecret

       Possibilities:
               none   (1)
               encrypt   (2)
               encType1   (3)
               invalid   (128)"
   ::= {er1645v2BgrMVPppOEEntry 252182528}

er1645v2BgrMVPppOEPppEncSessionSecret OBJECT-TYPE
   SYNTAX      DisplayString
   MAX-ACCESS  read-write
   STATUS      current
   DESCRIPTION
      "Path: bridgeGroup.editConf.pppoEClient.ppp.encSessionSecret"
   ::= {er1645v2BgrMVPppOEEntry 252248064}

er1645v2BgrMVPppOEPppServiceName OBJECT-TYPE
   SYNTAX      DisplayString
   MAX-ACCESS  read-write
   STATUS      current
   DESCRIPTION
      "Path: bridgeGroup.editConf.pppoEClient.ppp.serviceName"
   ::= {er1645v2BgrMVPppOEEntry 252116992}

er1645v2BgrMVPppOEIpH OBJECT-TYPE
   SYNTAX      SEQUENCE OF Er1645v2BgrMVPppOEIpHEntry
   MAX-ACCESS  not-accessible
   STATUS      current
   DESCRIPTION
      ""
   ::= {er1645v2BgrMVPppOE 51314688}

er1645v2BgrMVPppOEIpHEntry OBJECT-TYPE
   SYNTAX      Er1645v2BgrMVPppOEIpHEntry
   MAX-ACCESS  not-accessible
   STATUS      current
   DESCRIPTION
      ""
   INDEX      { er1645v2BgrMVPppOETableIx,
                er1645v2BgrMVPppOEIpHTableIx }
   ::= {er1645v2BgrMVPppOEIpH 1}

Er1645v2BgrMVPppOEIpHEntry ::=
   SEQUENCE
      {
      er1645v2BgrMVPppOEIpHActions
         VariableLengthTableActions,
      er1645v2BgrMVPppOEIpHTableIx
         TableIndex,
      er1645v2BgrMVPppOEIpHAddress
         IpAddress,
      er1645v2BgrMVPppOEIpHDhcpRelayOptionSubscriberId
         DisplayString
      }

er1645v2BgrMVPppOEIpHActions OBJECT-TYPE
   SYNTAX      VariableLengthTableActions
   MAX-ACCESS  read-write
   STATUS      current
   DESCRIPTION
      "By way of this field, some manipulations
       on this table may be performed."
   ::= {er1645v2BgrMVPppOEIpHEntry 2}

er1645v2BgrMVPppOEIpHTableIx OBJECT-TYPE
   SYNTAX      TableIndex
   MAX-ACCESS  not-accessible
   STATUS      current
   DESCRIPTION
      ""
   ::= {er1645v2BgrMVPppOEIpHEntry 11}

er1645v2BgrMVPppOEIpHAddress OBJECT-TYPE
   SYNTAX      IpAddress
   MAX-ACCESS  read-write
   STATUS      current
   DESCRIPTION
      "Path: bridgeGroup.editConf.pppoEClient.ip.helpers.address"
   ::= {er1645v2BgrMVPppOEIpHEntry 16777216}

er1645v2BgrMVPppOEIpHDhcpRelayOptionSubscriberId OBJECT-TYPE
   SYNTAX      DisplayString
   MAX-ACCESS  read-write
   STATUS      current
   DESCRIPTION
      "Path: bridgeGroup.editConf.pppoEClient.ip.helpers.dhcpRelayOption.subscriberId"
   ::= {er1645v2BgrMVPppOEIpHEntry 33947648}

er1645v2BgrMVPppOEIpV6Addresses OBJECT-TYPE
   SYNTAX      SEQUENCE OF Er1645v2BgrMVPppOEIpV6AddressesEntry
   MAX-ACCESS  not-accessible
   STATUS      current
   DESCRIPTION
      ""
   ::= {er1645v2BgrMVPppOE 704839680}

er1645v2BgrMVPppOEIpV6AddressesEntry OBJECT-TYPE
   SYNTAX      Er1645v2BgrMVPppOEIpV6AddressesEntry
   MAX-ACCESS  not-accessible
   STATUS      current
   DESCRIPTION
      ""
   INDEX      { er1645v2BgrMVPppOETableIx,
                er1645v2BgrMVPppOEIpV6AddressesTableIx }
   ::= {er1645v2BgrMVPppOEIpV6Addresses 1}

Er1645v2BgrMVPppOEIpV6AddressesEntry ::=
   SEQUENCE
      {
      er1645v2BgrMVPppOEIpV6AddressesActions
         VariableLengthTableActions,
      er1645v2BgrMVPppOEIpV6AddressesTableIx
         TableIndex,
      er1645v2BgrMVPppOEIpV6AddressesType
         INTEGER,
      er1645v2BgrMVPppOEIpV6AddressesAddress
         Ipv6Address,
      er1645v2BgrMVPppOEIpV6AddressesPrefixLength
         Integer32,
      er1645v2BgrMVPppOEIpV6AddressesGeneralPrefix
         DisplayString,
      er1645v2BgrMVPppOEIpV6AddressesRaSend
         INTEGER,
      er1645v2BgrMVPppOEIpV6AddressesRaOnLinkFlag
         INTEGER,
      er1645v2BgrMVPppOEIpV6AddressesRaAutoFlag
         INTEGER,
      er1645v2BgrMVPppOEIpV6AddressesRaValidLifeTime
         TimeTicks,
      er1645v2BgrMVPppOEIpV6AddressesRaValidLTMode
         INTEGER,
      er1645v2BgrMVPppOEIpV6AddressesRaPrefLifeTime
         TimeTicks,
      er1645v2BgrMVPppOEIpV6AddressesRaPrefLTMode
         INTEGER
      }

er1645v2BgrMVPppOEIpV6AddressesActions OBJECT-TYPE
   SYNTAX      VariableLengthTableActions
   MAX-ACCESS  read-write
   STATUS      current
   DESCRIPTION
      "By way of this field, some manipulations
       on this table may be performed."
   ::= {er1645v2BgrMVPppOEIpV6AddressesEntry 2}

er1645v2BgrMVPppOEIpV6AddressesTableIx OBJECT-TYPE
   SYNTAX      TableIndex
   MAX-ACCESS  not-accessible
   STATUS      current
   DESCRIPTION
      ""
   ::= {er1645v2BgrMVPppOEIpV6AddressesEntry 11}

er1645v2BgrMVPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: bridgeGroup.editConf.pppoEClient.ipV6.addresses.type

       Possibilities:
               unicast   (0)
               eui64   (1)
               anycast   (2)
               linkLocal   (3)
               generalPrefix   (4)"
   ::= {er1645v2BgrMVPppOEIpV6AddressesEntry 50331648}

er1645v2BgrMVPppOEIpV6AddressesAddress OBJECT-TYPE
   SYNTAX      Ipv6Address
   MAX-ACCESS  read-write
   STATUS      current
   DESCRIPTION
      "Path: bridgeGroup.editConf.pppoEClient.ipV6.addresses.address

       ipv6 address"
   ::= {er1645v2BgrMVPppOEIpV6AddressesEntry 16777216}

er1645v2BgrMVPppOEIpV6AddressesPrefixLength OBJECT-TYPE
   SYNTAX      Integer32
   MAX-ACCESS  read-write
   STATUS      current
   DESCRIPTION
      "Path: bridgeGroup.editConf.pppoEClient.ipV6.addresses.prefixLength"
   ::= {er1645v2BgrMVPppOEIpV6AddressesEntry 33554432}

er1645v2BgrMVPppOEIpV6AddressesGeneralPrefix OBJECT-TYPE
   SYNTAX      DisplayString
   MAX-ACCESS  read-write
   STATUS      current
   DESCRIPTION
      "Path: bridgeGroup.editConf.pppoEClient.ipV6.addresses.generalPrefix"
   ::= {er1645v2BgrMVPppOEIpV6AddressesEntry 83886080}

er1645v2BgrMVPppOEIpV6AddressesRaSend OBJECT-TYPE
   SYNTAX      INTEGER
               {
               disabled (0),
               enabled (1)
               }
   MAX-ACCESS  read-write
   STATUS      current
   DESCRIPTION
      "Path: bridgeGroup.editConf.pppoEClient.ipV6.addresses.ra.send

       Possibilities:
               disabled   (0)
               enabled   (1)"
   ::= {er1645v2BgrMVPppOEIpV6AddressesEntry 67174400}

er1645v2BgrMVPppOEIpV6AddressesRaOnLinkFlag OBJECT-TYPE
   SYNTAX      INTEGER
               {
               disabled (0),
               enabled (1)
               }
   MAX-ACCESS  read-write
   STATUS      current
   DESCRIPTION
      "Path: bridgeGroup.editConf.pppoEClient.ipV6.addresses.ra.onLinkFlag

       Possibilities:
               disabled   (0)
               enabled   (1)"
   ::= {er1645v2BgrMVPppOEIpV6AddressesEntry 67371008}

er1645v2BgrMVPppOEIpV6AddressesRaAutoFlag OBJECT-TYPE
   SYNTAX      INTEGER
               {
               disabled (0),
               enabled (1)
               }
   MAX-ACCESS  read-write
   STATUS      current
   DESCRIPTION
      "Path: bridgeGroup.editConf.pppoEClient.ipV6.addresses.ra.autonomousFlag

       Possibilities:
               disabled   (0)
               enabled   (1)"
   ::= {er1645v2BgrMVPppOEIpV6AddressesEntry 67567616}

er1645v2BgrMVPppOEIpV6AddressesRaValidLifeTime OBJECT-TYPE
   SYNTAX      TimeTicks
   MAX-ACCESS  read-write
   STATUS      current
   DESCRIPTION
      "Path: bridgeGroup.editConf.pppoEClient.ipV6.addresses.ra.validLifeTime

       Time in centi-second."
   ::= {er1645v2BgrMVPppOEIpV6AddressesEntry 67239936}

er1645v2BgrMVPppOEIpV6AddressesRaValidLTMode OBJECT-TYPE
   SYNTAX      INTEGER
               {
               fixed (0),
               infinite (2)
               }
   MAX-ACCESS  read-write
   STATUS      current
   DESCRIPTION
      "Path: bridgeGroup.editConf.pppoEClient.ipV6.addresses.ra.validLifeTimeMode

       Possibilities:
               fixed   (0)
               infinite   (2)"
   ::= {er1645v2BgrMVPppOEIpV6AddressesEntry 67305472}

er1645v2BgrMVPppOEIpV6AddressesRaPrefLifeTime OBJECT-TYPE
   SYNTAX      TimeTicks
   MAX-ACCESS  read-write
   STATUS      current
   DESCRIPTION
      "Path: bridgeGroup.editConf.pppoEClient.ipV6.addresses.ra.prefLifeTime

       Time in centi-second."
   ::= {er1645v2BgrMVPppOEIpV6AddressesEntry 67436544}

er1645v2BgrMVPppOEIpV6AddressesRaPrefLTMode OBJECT-TYPE
   SYNTAX      INTEGER
               {
               fixed (0),
               infinite (2)
               }
   MAX-ACCESS  read-write
   STATUS      current
   DESCRIPTION
      "Path: bridgeGroup.editConf.pppoEClient.ipV6.addresses.ra.prefLifeTimeMode

       Possibilities:
               fixed   (0)
               infinite   (2)"
   ::= {er1645v2BgrMVPppOEIpV6AddressesEntry 67502080}

er1645v2BgrMVPppOEIpV6RaDnsOptionsRdnssServers OBJECT-TYPE
   SYNTAX      SEQUENCE OF Er1645v2BgrMVPppOEIpV6RaDnsOptionsRdnssServersEntry
   MAX-ACCESS  not-accessible
   STATUS      current
   DESCRIPTION
      ""
   ::= {er1645v2BgrMVPppOE 705039144}

er1645v2BgrMVPppOEIpV6RaDnsOptionsRdnssServersEntry OBJECT-TYPE
   SYNTAX      Er1645v2BgrMVPppOEIpV6RaDnsOptionsRdnssServersEntry
   MAX-ACCESS  not-accessible
   STATUS      current
   DESCRIPTION
      ""
   INDEX      { er1645v2BgrMVPppOETableIx,
                er1645v2BgrMVPppOEIpV6RaDnsOptionsRdnssServersTableIx }
   ::= {er1645v2BgrMVPppOEIpV6RaDnsOptionsRdnssServers 1}

Er1645v2BgrMVPppOEIpV6RaDnsOptionsRdnssServersEntry ::=
   SEQUENCE
      {
      er1645v2BgrMVPppOEIpV6RaDnsOptionsRdnssServersActions
         VariableLengthTableActions,
      er1645v2BgrMVPppOEIpV6RaDnsOptionsRdnssServersTableIx
         TableIndex,
      er1645v2BgrMVPppOEIpV6RaDnsOptionsRdnssServersAddress
         Ipv6Address
      }

er1645v2BgrMVPppOEIpV6RaDnsOptionsRdnssServersActions OBJECT-TYPE
   SYNTAX      VariableLengthTableActions
   MAX-ACCESS  read-write
   STATUS      current
   DESCRIPTION
      "By way of this field, some manipulations
       on this table may be performed."
   ::= {er1645v2BgrMVPppOEIpV6RaDnsOptionsRdnssServersEntry 2}

er1645v2BgrMVPppOEIpV6RaDnsOptionsRdnssServersTableIx OBJECT-TYPE
   SYNTAX      TableIndex
   MAX-ACCESS  not-accessible
   STATUS      current
   DESCRIPTION
      ""
   ::= {er1645v2BgrMVPppOEIpV6RaDnsOptionsRdnssServersEntry 11}

er1645v2BgrMVPppOEIpV6RaDnsOptionsRdnssServersAddress OBJECT-TYPE
   SYNTAX      Ipv6Address
   MAX-ACCESS  read-write
   STATUS      current
   DESCRIPTION
      "Path: bridgeGroup.editConf.pppoEClient.ipV6.ra.dnsOptions.rdnss.servers.address

       ipv6 address"
   ::= {er1645v2BgrMVPppOEIpV6RaDnsOptionsRdnssServersEntry 16777216}

er1645v2BgrMVPppOEIpV6RaDnsOptionsDnsslDomains OBJECT-TYPE
   SYNTAX      SEQUENCE OF Er1645v2BgrMVPppOEIpV6RaDnsOptionsDnsslDomainsEntry
   MAX-ACCESS  not-accessible
   STATUS      current
   DESCRIPTION
      ""
   ::= {er1645v2BgrMVPppOE 705039176}

er1645v2BgrMVPppOEIpV6RaDnsOptionsDnsslDomainsEntry OBJECT-TYPE
   SYNTAX      Er1645v2BgrMVPppOEIpV6RaDnsOptionsDnsslDomainsEntry
   MAX-ACCESS  not-accessible
   STATUS      current
   DESCRIPTION
      ""
   INDEX      { er1645v2BgrMVPppOETableIx,
                er1645v2BgrMVPppOEIpV6RaDnsOptionsDnsslDomainsTableIx }
   ::= {er1645v2BgrMVPppOEIpV6RaDnsOptionsDnsslDomains 1}

Er1645v2BgrMVPppOEIpV6RaDnsOptionsDnsslDomainsEntry ::=
   SEQUENCE
      {
      er1645v2BgrMVPppOEIpV6RaDnsOptionsDnsslDomainsActions
         VariableLengthTableActions,
      er1645v2BgrMVPppOEIpV6RaDnsOptionsDnsslDomainsTableIx
         TableIndex,
      er1645v2BgrMVPppOEIpV6RaDnsOptionsDnsslDomainsName
         DisplayString
      }

er1645v2BgrMVPppOEIpV6RaDnsOptionsDnsslDomainsActions OBJECT-TYPE
   SYNTAX      VariableLengthTableActions
   MAX-ACCESS  read-write
   STATUS      current
   DESCRIPTION
      "By way of this field, some manipulations
       on this table may be performed."
   ::= {er1645v2BgrMVPppOEIpV6RaDnsOptionsDnsslDomainsEntry 2}

er1645v2BgrMVPppOEIpV6RaDnsOptionsDnsslDomainsTableIx OBJECT-TYPE
   SYNTAX      TableIndex
   MAX-ACCESS  not-accessible
   STATUS      current
   DESCRIPTION
      ""
   ::= {er1645v2BgrMVPppOEIpV6RaDnsOptionsDnsslDomainsEntry 11}

er1645v2BgrMVPppOEIpV6RaDnsOptionsDnsslDomainsName OBJECT-TYPE
   SYNTAX      DisplayString
   MAX-ACCESS  read-write
   STATUS      current
   DESCRIPTION
      "Path: bridgeGroup.editConf.pppoEClient.ipV6.ra.dnsOptions.dnssl.domains.name"
   ::= {er1645v2BgrMVPppOEIpV6RaDnsOptionsDnsslDomainsEntry 16777216}

er1645v2BgrMVPppOEIpV6DhcpClientUserClassOpt OBJECT-TYPE
   SYNTAX      SEQUENCE OF Er1645v2BgrMVPppOEIpV6DhcpClientUserClassOptEntry
   MAX-ACCESS  not-accessible
   STATUS      current
   DESCRIPTION
      ""
   ::= {er1645v2BgrMVPppOE 705312768}

er1645v2BgrMVPppOEIpV6DhcpClientUserClassOptEntry OBJECT-TYPE
   SYNTAX      Er1645v2BgrMVPppOEIpV6DhcpClientUserClassOptEntry
   MAX-ACCESS  not-accessible
   STATUS      current
   DESCRIPTION
      ""
   INDEX      { er1645v2BgrMVPppOETableIx,
                er1645v2BgrMVPppOEIpV6DhcpClientUserClassOptTableIx }
   ::= {er1645v2BgrMVPppOEIpV6DhcpClientUserClassOpt 1}

Er1645v2BgrMVPppOEIpV6DhcpClientUserClassOptEntry ::=
   SEQUENCE
      {
      er1645v2BgrMVPppOEIpV6DhcpClientUserClassOptActions
         VariableLengthTableActions,
      er1645v2BgrMVPppOEIpV6DhcpClientUserClassOptTableIx
         TableIndex,
      er1645v2BgrMVPppOEIpV6DhcpClientUserClassOptValueAscii
         DisplayString,
      er1645v2BgrMVPppOEIpV6DhcpClientUserClassOptValueDecimal
         Integer32,
      er1645v2BgrMVPppOEIpV6DhcpClientUserClassOptValueHexData
         OCTET STRING
      }

er1645v2BgrMVPppOEIpV6DhcpClientUserClassOptActions OBJECT-TYPE
   SYNTAX      VariableLengthTableActions
   MAX-ACCESS  read-write
   STATUS      current
   DESCRIPTION
      "By way of this field, some manipulations
       on this table may be performed."
   ::= {er1645v2BgrMVPppOEIpV6DhcpClientUserClassOptEntry 2}

er1645v2BgrMVPppOEIpV6DhcpClientUserClassOptTableIx OBJECT-TYPE
   SYNTAX      TableIndex
   MAX-ACCESS  not-accessible
   STATUS      current
   DESCRIPTION
      ""
   ::= {er1645v2BgrMVPppOEIpV6DhcpClientUserClassOptEntry 11}

er1645v2BgrMVPppOEIpV6DhcpClientUserClassOptValueAscii OBJECT-TYPE
   SYNTAX      DisplayString
   MAX-ACCESS  read-write
   STATUS      current
   DESCRIPTION
      "Path: bridgeGroup.editConf.pppoEClient.ipV6.dhcp.client.userClassOpt.value.ascii"
   ::= {er1645v2BgrMVPppOEIpV6DhcpClientUserClassOptEntry 16842752}

er1645v2BgrMVPppOEIpV6DhcpClientUserClassOptValueDecimal OBJECT-TYPE
   SYNTAX      Integer32
   MAX-ACCESS  read-write
   STATUS      current
   DESCRIPTION
      "Path: bridgeGroup.editConf.pppoEClient.ipV6.dhcp.client.userClassOpt.value.decimal"
   ::= {er1645v2BgrMVPppOEIpV6DhcpClientUserClassOptEntry 16908288}

er1645v2BgrMVPppOEIpV6DhcpClientUserClassOptValueHexData OBJECT-TYPE
   SYNTAX      OCTET STRING
   MAX-ACCESS  read-write
   STATUS      current
   DESCRIPTION
      "Path: bridgeGroup.editConf.pppoEClient.ipV6.dhcp.client.userClassOpt.value.hexData"
   ::= {er1645v2BgrMVPppOEIpV6DhcpClientUserClassOptEntry 16973824}

er1645v2BgrMVPppOEIpV6DhcpClientVendorCl OBJECT-TYPE
   SYNTAX      SEQUENCE OF Er1645v2BgrMVPppOEIpV6DhcpClientVendorClEntry
   MAX-ACCESS  not-accessible
   STATUS      current
   DESCRIPTION
      ""
   ::= {er1645v2BgrMVPppOE 705313792}

er1645v2BgrMVPppOEIpV6DhcpClientVendorClEntry OBJECT-TYPE
   SYNTAX      Er1645v2BgrMVPppOEIpV6DhcpClientVendorClEntry
   MAX-ACCESS  not-accessible
   STATUS      current
   DESCRIPTION
      ""
   INDEX      { er1645v2BgrMVPppOETableIx,
                er1645v2BgrMVPppOEIpV6DhcpClientVendorClTableIx }
   ::= {er1645v2BgrMVPppOEIpV6DhcpClientVendorCl 1}

Er1645v2BgrMVPppOEIpV6DhcpClientVendorClEntry ::=
   SEQUENCE
      {
      er1645v2BgrMVPppOEIpV6DhcpClientVendorClActions
         VariableLengthTableActions,
      er1645v2BgrMVPppOEIpV6DhcpClientVendorClTableIx
         TableIndex,
      er1645v2BgrMVPppOEIpV6DhcpClientVendorClValueAscii
         DisplayString,
      er1645v2BgrMVPppOEIpV6DhcpClientVendorClValueDecimal
         Integer32,
      er1645v2BgrMVPppOEIpV6DhcpClientVendorClValueHexData
         OCTET STRING
      }

er1645v2BgrMVPppOEIpV6DhcpClientVendorClActions OBJECT-TYPE
   SYNTAX      VariableLengthTableActions
   MAX-ACCESS  read-write
   STATUS      current
   DESCRIPTION
      "By way of this field, some manipulations
       on this table may be performed."
   ::= {er1645v2BgrMVPppOEIpV6DhcpClientVendorClEntry 2}

er1645v2BgrMVPppOEIpV6DhcpClientVendorClTableIx OBJECT-TYPE
   SYNTAX      TableIndex
   MAX-ACCESS  not-accessible
   STATUS      current
   DESCRIPTION
      ""
   ::= {er1645v2BgrMVPppOEIpV6DhcpClientVendorClEntry 11}

er1645v2BgrMVPppOEIpV6DhcpClientVendorClValueAscii OBJECT-TYPE
   SYNTAX      DisplayString
   MAX-ACCESS  read-write
   STATUS      current
   DESCRIPTION
      "Path: bridgeGroup.editConf.pppoEClient.ipV6.dhcp.client.vendorClassOpt.value.ascii"
   ::= {er1645v2BgrMVPppOEIpV6DhcpClientVendorClEntry 16842752}

er1645v2BgrMVPppOEIpV6DhcpClientVendorClValueDecimal OBJECT-TYPE
   SYNTAX      Integer32
   MAX-ACCESS  read-write
   STATUS      current
   DESCRIPTION
      "Path: bridgeGroup.editConf.pppoEClient.ipV6.dhcp.client.vendorClassOpt.value.decimal"
   ::= {er1645v2BgrMVPppOEIpV6DhcpClientVendorClEntry 16908288}

er1645v2BgrMVPppOEIpV6DhcpClientVendorClValueHexData OBJECT-TYPE
   SYNTAX      OCTET STRING
   MAX-ACCESS  read-write
   STATUS      current
   DESCRIPTION
      "Path: bridgeGroup.editConf.pppoEClient.ipV6.dhcp.client.vendorClassOpt.value.hexData"
   ::= {er1645v2BgrMVPppOEIpV6DhcpClientVendorClEntry 16973824}

er1645v2BgrMVPppOEIpV6DhcpRelayDestinations OBJECT-TYPE
   SYNTAX      SEQUENCE OF Er1645v2BgrMVPppOEIpV6DhcpRelayDestinationsEntry
   MAX-ACCESS  not-accessible
   STATUS      current
   DESCRIPTION
      ""
   ::= {er1645v2BgrMVPppOE 705323072}

er1645v2BgrMVPppOEIpV6DhcpRelayDestinationsEntry OBJECT-TYPE
   SYNTAX      Er1645v2BgrMVPppOEIpV6DhcpRelayDestinationsEntry
   MAX-ACCESS  not-accessible
   STATUS      current
   DESCRIPTION
      ""
   INDEX      { er1645v2BgrMVPppOETableIx,
                er1645v2BgrMVPppOEIpV6DhcpRelayDestinationsTableIx }
   ::= {er1645v2BgrMVPppOEIpV6DhcpRelayDestinations 1}

Er1645v2BgrMVPppOEIpV6DhcpRelayDestinationsEntry ::=
   SEQUENCE
      {
      er1645v2BgrMVPppOEIpV6DhcpRelayDestinationsActions
         VariableLengthTableActions,
      er1645v2BgrMVPppOEIpV6DhcpRelayDestinationsTableIx
         TableIndex,
      er1645v2BgrMVPppOEIpV6DhcpRelayDestinationsAddress
         Ipv6Address,
      er1645v2BgrMVPppOEIpV6DhcpRelayDestinationsInterface
         DisplayString
      }

er1645v2BgrMVPppOEIpV6DhcpRelayDestinationsActions OBJECT-TYPE
   SYNTAX      VariableLengthTableActions
   MAX-ACCESS  read-write
   STATUS      current
   DESCRIPTION
      "By way of this field, some manipulations
       on this table may be performed."
   ::= {er1645v2BgrMVPppOEIpV6DhcpRelayDestinationsEntry 2}

er1645v2BgrMVPppOEIpV6DhcpRelayDestinationsTableIx OBJECT-TYPE
   SYNTAX      TableIndex
   MAX-ACCESS  not-accessible
   STATUS      current
   DESCRIPTION
      ""
   ::= {er1645v2BgrMVPppOEIpV6DhcpRelayDestinationsEntry 11}

er1645v2BgrMVPppOEIpV6DhcpRelayDestinationsAddress OBJECT-TYPE
   SYNTAX      Ipv6Address
   MAX-ACCESS  read-write
   STATUS      current
   DESCRIPTION
      "Path: bridgeGroup.editConf.pppoEClient.ipV6.dhcp.relay.destinations.address

       ipv6 address"
   ::= {er1645v2BgrMVPppOEIpV6DhcpRelayDestinationsEntry 16777216}

er1645v2BgrMVPppOEIpV6DhcpRelayDestinationsInterface OBJECT-TYPE
   SYNTAX      DisplayString
   MAX-ACCESS  read-write
   STATUS      current
   DESCRIPTION
      "Path: bridgeGroup.editConf.pppoEClient.ipV6.dhcp.relay.destinations.interface"
   ::= {er1645v2BgrMVPppOEIpV6DhcpRelayDestinationsEntry 33554432}


er1645v2BgrMVMacAddress OBJECT IDENTIFIER ::= {er1645v2BgrMV 27}

er1645v2BgrMVMacAddressSSC OBJECT IDENTIFIER ::= {er1645v2BgrMVMacAddress 1}

er1645v2BgrMVMacAddressEntry OBJECT IDENTIFIER ::= {er1645v2BgrMVMacAddressSSC 1}

er1645v2BgrMVMacAddressDeviceMac OBJECT-TYPE
   SYNTAX      DisplayString
   MAX-ACCESS  read-write
   STATUS      current
   DESCRIPTION
      "Path: bridgeGroup.editConf.macAddress.deviceMac"
   ::= {er1645v2BgrMVMacAddressEntry 50331648}

er1645v2BgrMVMacAddressUserMac OBJECT-TYPE
   SYNTAX      OCTET STRING
   MAX-ACCESS  read-write
   STATUS      current
   DESCRIPTION
      "Path: bridgeGroup.editConf.macAddress.userMac

       MAC address."
   ::= {er1645v2BgrMVMacAddressEntry 33554432}

er1645v2BgrMVMacAddressRandomMac OBJECT-TYPE
   SYNTAX      Integer32
   MAX-ACCESS  read-write
   STATUS      current
   DESCRIPTION
      "Path: bridgeGroup.editConf.macAddress.randomMac"
   ::= {er1645v2BgrMVMacAddressEntry 67108864}


er1645v2BgrMVPppoEServer OBJECT-TYPE
   SYNTAX      DisplayString
   MAX-ACCESS  read-write
   STATUS      current
   DESCRIPTION
      "Path: bridgeGroup.editConf.pppoEServer
       Info: ppp server name on interface"
   ::= {er1645v2BgrMV 37}



sr1645v2BgrMV OBJECT IDENTIFIER ::= {r1645v2BgrMV 14}


sr1645v2BgrMVBdgCache OBJECT IDENTIFIER ::= {sr1645v2BgrMV 3}

sr1645v2BgrMVBdgCacheSSCTable OBJECT-TYPE
   SYNTAX      SEQUENCE OF Sr1645v2BgrMVBdgCacheEntry
   MAX-ACCESS  not-accessible
   STATUS      current
   DESCRIPTION
      "bridge cache"
   ::= {sr1645v2BgrMVBdgCache 1}

sr1645v2BgrMVBdgCacheEntry OBJECT-TYPE
   SYNTAX      Sr1645v2BgrMVBdgCacheEntry
   MAX-ACCESS  not-accessible
   STATUS      current
   DESCRIPTION
      ""
   INDEX      { sr1645v2BgrMVBdgCacheTableIx }
   ::= {sr1645v2BgrMVBdgCacheSSCTable 1}

Sr1645v2BgrMVBdgCacheEntry ::=
   SEQUENCE
      {
      sr1645v2BgrMVBdgCacheTableIx
         TableIndex,
      sr1645v2BgrMVBdgCacheIf
         DisplayString,
      sr1645v2BgrMVBdgCacheMacAddress
         OCTET STRING,
      sr1645v2BgrMVBdgCacheTpid
         INTEGER,
      sr1645v2BgrMVBdgCacheVlanId
         INTEGER,
      sr1645v2BgrMVBdgCacheTpid2
         INTEGER,
      sr1645v2BgrMVBdgCacheVlanId2
         INTEGER,
      sr1645v2BgrMVBdgCacheType
         INTEGER,
      sr1645v2BgrMVBdgCacheAge
         TimeTicks
      }

sr1645v2BgrMVBdgCacheTableIx OBJECT-TYPE
   SYNTAX      TableIndex
   MAX-ACCESS  not-accessible
   STATUS      current
   DESCRIPTION
      ""
   ::= {sr1645v2BgrMVBdgCacheEntry 11}

sr1645v2BgrMVBdgCacheIf OBJECT-TYPE
   SYNTAX      DisplayString
   MAX-ACCESS  read-only
   STATUS      current
   DESCRIPTION
      "Path: bridgeGroup.status.bridgeCache.interface"
   ::= {sr1645v2BgrMVBdgCacheEntry 16777216}

sr1645v2BgrMVBdgCacheMacAddress OBJECT-TYPE
   SYNTAX      OCTET STRING
   MAX-ACCESS  read-only
   STATUS      current
   DESCRIPTION
      "Path: bridgeGroup.status.bridgeCache.macAddress

       MAC address."
   ::= {sr1645v2BgrMVBdgCacheEntry 33554432}

sr1645v2BgrMVBdgCacheTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: bridgeGroup.status.bridgeCache.tpid

       Possibilities:
               untagged   (0)
               dot1q   (33024)
               dot1ad   (34984)
               group   (65534)
               notUsed   (65535)
               dot1qOrDot1ad   (65536)"
   ::= {sr1645v2BgrMVBdgCacheEntry 150994944}

sr1645v2BgrMVBdgCacheVlanId OBJECT-TYPE
   SYNTAX      INTEGER
               {
               undefined (-1)
               }
   MAX-ACCESS  read-only
   STATUS      current
   DESCRIPTION
      "Path: bridgeGroup.status.bridgeCache.vlanId

       Possibilities:
               undefined   (-1)"
   ::= {sr1645v2BgrMVBdgCacheEntry 83886080}

sr1645v2BgrMVBdgCacheTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: bridgeGroup.status.bridgeCache.tpid2

       Possibilities:
               untagged   (0)
               dot1q   (33024)
               dot1ad   (34984)
               group   (65534)
               notUsed   (65535)
               dot1qOrDot1ad   (65536)"
   ::= {sr1645v2BgrMVBdgCacheEntry 369098752}

sr1645v2BgrMVBdgCacheVlanId2 OBJECT-TYPE
   SYNTAX      INTEGER
               {
               undefined (-1)
               }
   MAX-ACCESS  read-only
   STATUS      current
   DESCRIPTION
      "Path: bridgeGroup.status.bridgeCache.vlanId2

       Possibilities:
               undefined   (-1)"
   ::= {sr1645v2BgrMVBdgCacheEntry 385875968}

sr1645v2BgrMVBdgCacheType OBJECT-TYPE
   SYNTAX      INTEGER
               {
               static (0),
               dynamic (1),
               tester (2),
               fastFlood (3)
               }
   MAX-ACCESS  read-only
   STATUS      current
   DESCRIPTION
      "Path: bridgeGroup.status.bridgeCache.type

       Possibilities:
               static   (0)
               dynamic   (1)
               tester   (2)
               fastFlood   (3)"
   ::= {sr1645v2BgrMVBdgCacheEntry 50331648}

sr1645v2BgrMVBdgCacheAge OBJECT-TYPE
   SYNTAX      TimeTicks
   MAX-ACCESS  read-only
   STATUS      current
   DESCRIPTION
      "Path: bridgeGroup.status.bridgeCache.age

       Time in centi-second."
   ::= {sr1645v2BgrMVBdgCacheEntry 67108864}


sr1645v2BgrMVBridgeCacheSize OBJECT IDENTIFIER ::= {sr1645v2BgrMV 39}

sr1645v2BgrMVBridgeCacheSizeSSC OBJECT IDENTIFIER ::= {sr1645v2BgrMVBridgeCacheSize 1}

sr1645v2BgrMVBridgeCacheSizeEntry OBJECT IDENTIFIER ::= {sr1645v2BgrMVBridgeCacheSizeSSC 1}

sr1645v2BgrMVBridgeCacheSizeSize OBJECT-TYPE
   SYNTAX      Counter32
   MAX-ACCESS  read-only
   STATUS      current
   DESCRIPTION
      "Path: bridgeGroup.status.bridgeCacheSize.size

       32 bit unsigned wrappable counter."
   ::= {sr1645v2BgrMVBridgeCacheSizeEntry 16777216}

sr1645v2BgrMVBridgeCacheSizeMaxSize OBJECT-TYPE
   SYNTAX      INTEGER
               {
               unlimited (0)
               }
   MAX-ACCESS  read-only
   STATUS      current
   DESCRIPTION
      "Path: bridgeGroup.status.bridgeCacheSize.maxSize

       Possibilities:
               unlimited   (0)"
   ::= {sr1645v2BgrMVBridgeCacheSizeEntry 33554432}


sr1645v2BgrMVMacAddress OBJECT-TYPE
   SYNTAX      OCTET STRING
   MAX-ACCESS  read-only
   STATUS      current
   DESCRIPTION
      "Path: bridgeGroup.status.macAddress
       Info: ifPhysAddress

       MAC address."
   ::= {sr1645v2BgrMV 105}


sr1645v2BgrMVDescr OBJECT-TYPE
   SYNTAX      DisplayString
   MAX-ACCESS  read-only
   STATUS      current
   DESCRIPTION
      "Path: bridgeGroup.status.ifDescr
       Info: ifDescr"
   ::= {sr1645v2BgrMV 101}


sr1645v2BgrMVType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: bridgeGroup.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2BgrMV 102}


sr1645v2BgrMVMtu OBJECT-TYPE
   SYNTAX      Integer32
   MAX-ACCESS  read-only
   STATUS      current
   DESCRIPTION
      "Path: bridgeGroup.status.ifMtu
       Info: ifMtu"
   ::= {sr1645v2BgrMV 103}


sr1645v2BgrMVOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: bridgeGroup.status.ifOperStatus
       Info: ifOperStatus

       Possibilities:
               up   (1)
               down   (2)
               testing   (3)
               unknown   (4)
               dormant   (5)
               notPresent   (6)
               lowerLayerDown   (7)"
   ::= {sr1645v2BgrMV 107}


sr1645v2BgrMVIp OBJECT IDENTIFIER ::= {sr1645v2BgrMV 11}

sr1645v2BgrMVIpSSC OBJECT IDENTIFIER ::= {sr1645v2BgrMVIp 1}

sr1645v2BgrMVIpEntry OBJECT IDENTIFIER ::= {sr1645v2BgrMVIpSSC 1}

sr1645v2BgrMVIpAddress OBJECT-TYPE
   SYNTAX      IpAddress
   MAX-ACCESS  read-only
   STATUS      current
   DESCRIPTION
      "Path: bridgeGroup.status.ip.address"
   ::= {sr1645v2BgrMVIpEntry 268435456}

sr1645v2BgrMVIpNetMask OBJECT-TYPE
   SYNTAX      IpAddress
   MAX-ACCESS  read-only
   STATUS      current
   DESCRIPTION
      "Path: bridgeGroup.status.ip.netMask"
   ::= {sr1645v2BgrMVIpEntry 285212672}

sr1645v2BgrMVIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: bridgeGroup.status.ip.dhcp.status

       Possibilities:
               none   (0)
               selecting   (1)
               requesting   (2)
               rebinding   (3)
               bound   (4)
               renewing   (5)
               rebooting   (6)
               initreboot   (7)"
   ::= {sr1645v2BgrMVIpEntry 402718720}

sr1645v2BgrMVIpDhcpLeaseTime OBJECT-TYPE
   SYNTAX      TimeTicks
   MAX-ACCESS  read-only
   STATUS      current
   DESCRIPTION
      "Path: bridgeGroup.status.ip.dhcp.leaseTime

       Time in centi-second."
   ::= {sr1645v2BgrMVIpEntry 402784256}

sr1645v2BgrMVIpSecondaryIp OBJECT-TYPE
   SYNTAX      SEQUENCE OF Sr1645v2BgrMVIpSecondaryIpEntry
   MAX-ACCESS  not-accessible
   STATUS      current
   DESCRIPTION
      ""
   ::= {sr1645v2BgrMVIp 385875968}

sr1645v2BgrMVIpSecondaryIpEntry OBJECT-TYPE
   SYNTAX      Sr1645v2BgrMVIpSecondaryIpEntry
   MAX-ACCESS  not-accessible
   STATUS      current
   DESCRIPTION
      ""
   INDEX      { sr1645v2BgrMVIpSecondaryIpTableIx }
   ::= {sr1645v2BgrMVIpSecondaryIp 1}

Sr1645v2BgrMVIpSecondaryIpEntry ::=
   SEQUENCE
      {
      sr1645v2BgrMVIpSecondaryIpTableIx
         TableIndex,
      sr1645v2BgrMVIpSecondaryIpAddress
         IpAddress,
      sr1645v2BgrMVIpSecondaryIpNetMask
         IpAddress
      }

sr1645v2BgrMVIpSecondaryIpTableIx OBJECT-TYPE
   SYNTAX      TableIndex
   MAX-ACCESS  not-accessible
   STATUS      current
   DESCRIPTION
      ""
   ::= {sr1645v2BgrMVIpSecondaryIpEntry 11}

sr1645v2BgrMVIpSecondaryIpAddress OBJECT-TYPE
   SYNTAX      IpAddress
   MAX-ACCESS  read-only
   STATUS      current
   DESCRIPTION
      "Path: bridgeGroup.status.ip.secondaryIp.address"
   ::= {sr1645v2BgrMVIpSecondaryIpEntry 2030043136}

sr1645v2BgrMVIpSecondaryIpNetMask OBJECT-TYPE
   SYNTAX      IpAddress
   MAX-ACCESS  read-only
   STATUS      current
   DESCRIPTION
      "Path: bridgeGroup.status.ip.secondaryIp.netMask"
   ::= {sr1645v2BgrMVIpSecondaryIpEntry 2063597568}


sr1645v2BgrMVIpV6 OBJECT IDENTIFIER ::= {sr1645v2BgrMV 22}

sr1645v2BgrMVIpV6SSC OBJECT IDENTIFIER ::= {sr1645v2BgrMVIpV6 1}

sr1645v2BgrMVIpV6Entry OBJECT IDENTIFIER ::= {sr1645v2BgrMVIpV6SSC 1}

sr1645v2BgrMVIpV6State OBJECT-TYPE
   SYNTAX      INTEGER
               {
               disabled (0),
               enabled (1)
               }
   MAX-ACCESS  read-only
   STATUS      current
   DESCRIPTION
      "Path: bridgeGroup.status.ipV6.state

       Possibilities:
               disabled   (0)
               enabled   (1)"
   ::= {sr1645v2BgrMVIpV6Entry 16777216}

sr1645v2BgrMVIpV6InterfaceId OBJECT-TYPE
   SYNTAX      OCTET STRING
   MAX-ACCESS  read-only
   STATUS      current
   DESCRIPTION
      "Path: bridgeGroup.status.ipV6.interfaceId"
   ::= {sr1645v2BgrMVIpV6Entry 33554432}

sr1645v2BgrMVIpV6LinkMtu OBJECT-TYPE
   SYNTAX      Integer32
   MAX-ACCESS  read-only
   STATUS      current
   DESCRIPTION
      "Path: bridgeGroup.status.ipV6.linkMtu"
   ::= {sr1645v2BgrMVIpV6Entry 67108864}

sr1645v2BgrMVIpV6HopLimit OBJECT-TYPE
   SYNTAX      Integer32
   MAX-ACCESS  read-only
   STATUS      current
   DESCRIPTION
      "Path: bridgeGroup.status.ipV6.hopLimit"
   ::= {sr1645v2BgrMVIpV6Entry 83886080}

sr1645v2BgrMVIpV6DhcpIaid OBJECT-TYPE
   SYNTAX      Counter32
   MAX-ACCESS  read-only
   STATUS      current
   DESCRIPTION
      "Path: bridgeGroup.status.ipV6.dhcp.iaid

       32 bit unsigned wrappable counter."
   ::= {sr1645v2BgrMVIpV6Entry 100728832}

sr1645v2BgrMVIpV6RaRcvOption OBJECT-TYPE
   SYNTAX      Integer32
   MAX-ACCESS  read-only
   STATUS      current
   DESCRIPTION
      "Path: bridgeGroup.status.ipV6.raRcvOption

       Bit meanings:
               bit 0 = linkMtu,
               bit 1 = srcLinkLayer,
               bit 2 = prefixInfo,
               bit 3 = rdnss,
               bit 4 = dnssl"
   ::= {sr1645v2BgrMVIpV6Entry 117440512}

sr1645v2BgrMVIpV6Addresses OBJECT-TYPE
   SYNTAX      SEQUENCE OF Sr1645v2BgrMVIpV6AddressesEntry
   MAX-ACCESS  not-accessible
   STATUS      current
   DESCRIPTION
      ""
   ::= {sr1645v2BgrMVIpV6 50331648}

sr1645v2BgrMVIpV6AddressesEntry OBJECT-TYPE
   SYNTAX      Sr1645v2BgrMVIpV6AddressesEntry
   MAX-ACCESS  not-accessible
   STATUS      current
   DESCRIPTION
      ""
   INDEX      { sr1645v2BgrMVIpV6AddressesTableIx }
   ::= {sr1645v2BgrMVIpV6Addresses 1}

Sr1645v2BgrMVIpV6AddressesEntry ::=
   SEQUENCE
      {
      sr1645v2BgrMVIpV6AddressesTableIx
         TableIndex,
      sr1645v2BgrMVIpV6AddressesAddress
         Ipv6Address,
      sr1645v2BgrMVIpV6AddressesPrefixLength
         Integer32,
      sr1645v2BgrMVIpV6AddressesStatus
         INTEGER,
      sr1645v2BgrMVIpV6AddressesOrigin
         INTEGER,
      sr1645v2BgrMVIpV6AddressesFlagsInterfaceId
         INTEGER,
      sr1645v2BgrMVIpV6AddressesFlagsAnycast
         INTEGER,
      sr1645v2BgrMVIpV6AddressesTimersValidLifeTime
         TimeTicks,
      sr1645v2BgrMVIpV6AddressesTimersPrefLifeTime
         TimeTicks
      }

sr1645v2BgrMVIpV6AddressesTableIx OBJECT-TYPE
   SYNTAX      TableIndex
   MAX-ACCESS  not-accessible
   STATUS      current
   DESCRIPTION
      ""
   ::= {sr1645v2BgrMVIpV6AddressesEntry 11}

sr1645v2BgrMVIpV6AddressesAddress OBJECT-TYPE
   SYNTAX      Ipv6Address
   MAX-ACCESS  read-only
   STATUS      current
   DESCRIPTION
      "Path: bridgeGroup.status.ipV6.addresses.address

       ipv6 address"
   ::= {sr1645v2BgrMVIpV6AddressesEntry 16777216}

sr1645v2BgrMVIpV6AddressesPrefixLength OBJECT-TYPE
   SYNTAX      Integer32
   MAX-ACCESS  read-only
   STATUS      current
   DESCRIPTION
      "Path: bridgeGroup.status.ipV6.addresses.prefixLength"
   ::= {sr1645v2BgrMVIpV6AddressesEntry 33554432}

sr1645v2BgrMVIpV6AddressesStatus OBJECT-TYPE
   SYNTAX      INTEGER
               {
               invalid (0),
               tentative (1),
               deprecated (2),
               preferred (3)
               }
   MAX-ACCESS  read-only
   STATUS      current
   DESCRIPTION
      "Path: bridgeGroup.status.ipV6.addresses.status

       Possibilities:
               invalid   (0)
               tentative   (1)
               deprecated   (2)
               preferred   (3)"
   ::= {sr1645v2BgrMVIpV6AddressesEntry 50331648}

sr1645v2BgrMVIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: bridgeGroup.status.ipV6.addresses.origin

       Possibilities:
               unknown   (0)
               manual   (1)
               generalPrefix   (2)
               statelessAuto   (3)
               statefullAuto   (4)"
   ::= {sr1645v2BgrMVIpV6AddressesEntry 67108864}

sr1645v2BgrMVIpV6AddressesFlagsInterfaceId OBJECT-TYPE
   SYNTAX      INTEGER
               {
               no (0),
               yes (1)
               }
   MAX-ACCESS  read-only
   STATUS      current
   DESCRIPTION
      "Path: bridgeGroup.status.ipV6.addresses.flags.interfaceId

       Possibilities:
               no   (0)
               yes   (1)"
   ::= {sr1645v2BgrMVIpV6AddressesEntry 83951616}

sr1645v2BgrMVIpV6AddressesFlagsAnycast OBJECT-TYPE
   SYNTAX      INTEGER
               {
               no (0),
               yes (1)
               }
   MAX-ACCESS  read-only
   STATUS      current
   DESCRIPTION
      "Path: bridgeGroup.status.ipV6.addresses.flags.anycast

       Possibilities:
               no   (0)
               yes   (1)"
   ::= {sr1645v2BgrMVIpV6AddressesEntry 84017152}

sr1645v2BgrMVIpV6AddressesTimersValidLifeTime OBJECT-TYPE
   SYNTAX      TimeTicks
   MAX-ACCESS  read-only
   STATUS      current
   DESCRIPTION
      "Path: bridgeGroup.status.ipV6.addresses.timers.validLifeTime

       Time in centi-second."
   ::= {sr1645v2BgrMVIpV6AddressesEntry 100794368}

sr1645v2BgrMVIpV6AddressesTimersPrefLifeTime OBJECT-TYPE
   SYNTAX      TimeTicks
   MAX-ACCESS  read-only
   STATUS      current
   DESCRIPTION
      "Path: bridgeGroup.status.ipV6.addresses.timers.prefLifeTime

       Time in centi-second."
   ::= {sr1645v2BgrMVIpV6AddressesEntry 100728832}


sr1645v2BgrMVStp OBJECT IDENTIFIER ::= {sr1645v2BgrMV 9}

sr1645v2BgrMVStpSSC OBJECT IDENTIFIER ::= {sr1645v2BgrMVStp 1}

sr1645v2BgrMVStpEntry OBJECT IDENTIFIER ::= {sr1645v2BgrMVStpSSC 1}

sr1645v2BgrMVStpBridgePriority OBJECT-TYPE
   SYNTAX      Integer32
   MAX-ACCESS  read-only
   STATUS      current
   DESCRIPTION
      "Path: bridgeGroup.status.spanningTree.bridgePriority"
   ::= {sr1645v2BgrMVStpEntry 16777216}

sr1645v2BgrMVStpBridgeMacAddress OBJECT-TYPE
   SYNTAX      OCTET STRING
   MAX-ACCESS  read-only
   STATUS      current
   DESCRIPTION
      "Path: bridgeGroup.status.spanningTree.bridgeMacAddress

       MAC address."
   ::= {sr1645v2BgrMVStpEntry 33554432}

sr1645v2BgrMVStpBridgeTimesMessageAge OBJECT-TYPE
   SYNTAX      TimeTicks
   MAX-ACCESS  read-only
   STATUS      current
   DESCRIPTION
      "Path: bridgeGroup.status.spanningTree.bridgeTimes.messageAge

       Time in centi-second."
   ::= {sr1645v2BgrMVStpEntry 50397184}

sr1645v2BgrMVStpBridgeTimesMaxAge OBJECT-TYPE
   SYNTAX      TimeTicks
   MAX-ACCESS  read-only
   STATUS      current
   DESCRIPTION
      "Path: bridgeGroup.status.spanningTree.bridgeTimes.maxAge

       Time in centi-second."
   ::= {sr1645v2BgrMVStpEntry 50462720}

sr1645v2BgrMVStpBridgeTimesForwardDelay OBJECT-TYPE
   SYNTAX      TimeTicks
   MAX-ACCESS  read-only
   STATUS      current
   DESCRIPTION
      "Path: bridgeGroup.status.spanningTree.bridgeTimes.forwardDelay

       Time in centi-second."
   ::= {sr1645v2BgrMVStpEntry 50528256}

sr1645v2BgrMVStpBridgeTimesNrHops OBJECT-TYPE
   SYNTAX      Integer32
   MAX-ACCESS  read-only
   STATUS      current
   DESCRIPTION
      "Path: bridgeGroup.status.spanningTree.bridgeTimes.nrHops"
   ::= {sr1645v2BgrMVStpEntry 50593792}

sr1645v2BgrMVStpRootBridgeIdPriority OBJECT-TYPE
   SYNTAX      Integer32
   MAX-ACCESS  read-only
   STATUS      current
   DESCRIPTION
      "Path: bridgeGroup.status.spanningTree.rootBridgeId.priority"
   ::= {sr1645v2BgrMVStpEntry 67174400}

sr1645v2BgrMVStpRootBridgeIdMacAddress OBJECT-TYPE
   SYNTAX      OCTET STRING
   MAX-ACCESS  read-only
   STATUS      current
   DESCRIPTION
      "Path: bridgeGroup.status.spanningTree.rootBridgeId.macAddress

       MAC address."
   ::= {sr1645v2BgrMVStpEntry 67239936}

sr1645v2BgrMVStpRootPortId OBJECT-TYPE
   SYNTAX      Integer32
   MAX-ACCESS  read-only
   STATUS      current
   DESCRIPTION
      "Path: bridgeGroup.status.spanningTree.rootPortId"
   ::= {sr1645v2BgrMVStpEntry 83886080}

sr1645v2BgrMVStpExtRootPathCost OBJECT-TYPE
   SYNTAX      Integer32
   MAX-ACCESS  read-only
   STATUS      current
   DESCRIPTION
      "Path: bridgeGroup.status.spanningTree.extRootPathCost"
   ::= {sr1645v2BgrMVStpEntry 100663296}

sr1645v2BgrMVStpIntRootPathCost OBJECT-TYPE
   SYNTAX      Integer32
   MAX-ACCESS  read-only
   STATUS      current
   DESCRIPTION
      "Path: bridgeGroup.status.spanningTree.intRootPathCost"
   ::= {sr1645v2BgrMVStpEntry 117440512}

sr1645v2BgrMVStpMstConfigIdFormatSelector OBJECT-TYPE
   SYNTAX      Integer32
   MAX-ACCESS  read-only
   STATUS      current
   DESCRIPTION
      "Path: bridgeGroup.status.spanningTree.mstConfigId.formatSelector"
   ::= {sr1645v2BgrMVStpEntry 134283264}

sr1645v2BgrMVStpMstConfigIdName OBJECT-TYPE
   SYNTAX      DisplayString
   MAX-ACCESS  read-only
   STATUS      current
   DESCRIPTION
      "Path: bridgeGroup.status.spanningTree.mstConfigId.name"
   ::= {sr1645v2BgrMVStpEntry 134348800}

sr1645v2BgrMVStpMstConfigIdRevisionLevel OBJECT-TYPE
   SYNTAX      Integer32
   MAX-ACCESS  read-only
   STATUS      current
   DESCRIPTION
      "Path: bridgeGroup.status.spanningTree.mstConfigId.revisionLevel"
   ::= {sr1645v2BgrMVStpEntry 134414336}

sr1645v2BgrMVStpMstConfigIdDigest OBJECT-TYPE
   SYNTAX      OCTET STRING
   MAX-ACCESS  read-only
   STATUS      current
   DESCRIPTION
      "Path: bridgeGroup.status.spanningTree.mstConfigId.digest"
   ::= {sr1645v2BgrMVStpEntry 134479872}


sr1645v2BgrMVBridging OBJECT IDENTIFIER ::= {sr1645v2BgrMV 12}

sr1645v2BgrMVBridgingSSCTable OBJECT-TYPE
   SYNTAX      SEQUENCE OF Sr1645v2BgrMVBridgingEntry
   MAX-ACCESS  not-accessible
   STATUS      current
   DESCRIPTION
      " bridge-port status"
   ::= {sr1645v2BgrMVBridging 1}

sr1645v2BgrMVBridgingEntry OBJECT-TYPE
   SYNTAX      Sr1645v2BgrMVBridgingEntry
   MAX-ACCESS  not-accessible
   STATUS      current
   DESCRIPTION
      ""
   INDEX      { sr1645v2BgrMVBridgingTableIx }
   ::= {sr1645v2BgrMVBridgingSSCTable 1}

Sr1645v2BgrMVBridgingEntry ::=
   SEQUENCE
      {
      sr1645v2BgrMVBridgingTableIx
         TableIndex,
      sr1645v2BgrMVBridgingName
         DisplayString,
      sr1645v2BgrMVBridgingState
         INTEGER,
      sr1645v2BgrMVBridgingCacheSize
         Counter32,
      sr1645v2BgrMVBridgingMaxCacheSize
         INTEGER,
      sr1645v2BgrMVBridgingVlMmbAll
         DisplayString,
      sr1645v2BgrMVBridgingVlMmbNone
         DisplayString,
      sr1645v2BgrMVBridgingStPortRole
         INTEGER,
      sr1645v2BgrMVBridgingStPortId
         Integer32,
      sr1645v2BgrMVBridgingStPpCostExtPathCost
         Integer32,
      sr1645v2BgrMVBridgingStPpCostIntPathCost
         Integer32,
      sr1645v2BgrMVBridgingStExtRpCost
         Integer32,
      sr1645v2BgrMVBridgingStIntRpCost
         Integer32,
      sr1645v2BgrMVBridgingStDesBrIdPriority
         Integer32,
      sr1645v2BgrMVBridgingStDesBrIdMacAddress
         OCTET STRING,
      sr1645v2BgrMVBridgingStDesPrtId
         Integer32,
      sr1645v2BgrMVBridgingStDesInt
         INTEGER,
      sr1645v2BgrMVBridgingStEdgeDetection
         INTEGER
      }

sr1645v2BgrMVBridgingTableIx OBJECT-TYPE
   SYNTAX      TableIndex
   MAX-ACCESS  not-accessible
   STATUS      current
   DESCRIPTION
      ""
   ::= {sr1645v2BgrMVBridgingEntry 11}

sr1645v2BgrMVBridgingName OBJECT-TYPE
   SYNTAX      DisplayString
   MAX-ACCESS  read-only
   STATUS      current
   DESCRIPTION
      "Path: bridgeGroup.status.bridging.name"
   ::= {sr1645v2BgrMVBridgingEntry 16777216}

sr1645v2BgrMVBridgingState OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: bridgeGroup.status.bridging.state

       Possibilities:
               disabled   (0)
               discarding   (1)
               learning   (2)
               forwarding   (3)
               backupBlockedIntfDown   (256)
               backupBlockedIntfUp   (259)
               shutdown   (255)"
   ::= {sr1645v2BgrMVBridgingEntry 33554432}

sr1645v2BgrMVBridgingCacheSize OBJECT-TYPE
   SYNTAX      Counter32
   MAX-ACCESS  read-only
   STATUS      current
   DESCRIPTION
      "Path: bridgeGroup.status.bridging.cacheSize

       32 bit unsigned wrappable counter."
   ::= {sr1645v2BgrMVBridgingEntry 50331648}

sr1645v2BgrMVBridgingMaxCacheSize OBJECT-TYPE
   SYNTAX      INTEGER
               {
               unlimited (0)
               }
   MAX-ACCESS  read-only
   STATUS      current
   DESCRIPTION
      "Path: bridgeGroup.status.bridging.maxCacheSize

       Possibilities:
               unlimited   (0)"
   ::= {sr1645v2BgrMVBridgingEntry 67108864}

sr1645v2BgrMVBridgingVlMmbAll OBJECT-TYPE
   SYNTAX      DisplayString
   MAX-ACCESS  read-only
   STATUS      current
   DESCRIPTION
      "Path: bridgeGroup.status.bridging.vlanMemberShip.all"
   ::= {sr1645v2BgrMVBridgingEntry 100728832}

sr1645v2BgrMVBridgingVlMmbNone OBJECT-TYPE
   SYNTAX      DisplayString
   MAX-ACCESS  read-only
   STATUS      current
   DESCRIPTION
      "Path: bridgeGroup.status.bridging.vlanMemberShip.none"
   ::= {sr1645v2BgrMVBridgingEntry 100794368}

sr1645v2BgrMVBridgingStPortRole OBJECT-TYPE
   SYNTAX      INTEGER
               {
               none (0),
               root (1),
               designated (2),
               alternate (3),
               backup (4),
               disabled (5),
               master (6)
               }
   MAX-ACCESS  read-only
   STATUS      current
   DESCRIPTION
      "Path: bridgeGroup.status.bridging.spanningTree.portRole

       Possibilities:
               none   (0)
               root   (1)
               designated   (2)
               alternate   (3)
               backup   (4)
               disabled   (5)
               master   (6)"
   ::= {sr1645v2BgrMVBridgingEntry 83951616}

sr1645v2BgrMVBridgingStPortId OBJECT-TYPE
   SYNTAX      Integer32
   MAX-ACCESS  read-only
   STATUS      current
   DESCRIPTION
      "Path: bridgeGroup.status.bridging.spanningTree.portId"
   ::= {sr1645v2BgrMVBridgingEntry 84017152}

sr1645v2BgrMVBridgingStPpCostExtPathCost OBJECT-TYPE
   SYNTAX      Integer32
   MAX-ACCESS  read-only
   STATUS      current
   DESCRIPTION
      "Path: bridgeGroup.status.bridging.spanningTree.portPathCosts.extPathCost"
   ::= {sr1645v2BgrMVBridgingEntry 84082944}

sr1645v2BgrMVBridgingStPpCostIntPathCost OBJECT-TYPE
   SYNTAX      Integer32
   MAX-ACCESS  read-only
   STATUS      current
   DESCRIPTION
      "Path: bridgeGroup.status.bridging.spanningTree.portPathCosts.intPathCost"
   ::= {sr1645v2BgrMVBridgingEntry 84083200}

sr1645v2BgrMVBridgingStExtRpCost OBJECT-TYPE
   SYNTAX      Integer32
   MAX-ACCESS  read-only
   STATUS      current
   DESCRIPTION
      "Path: bridgeGroup.status.bridging.spanningTree.extRootPathCost"
   ::= {sr1645v2BgrMVBridgingEntry 84148224}

sr1645v2BgrMVBridgingStIntRpCost OBJECT-TYPE
   SYNTAX      Integer32
   MAX-ACCESS  read-only
   STATUS      current
   DESCRIPTION
      "Path: bridgeGroup.status.bridging.spanningTree.intRootPathCost"
   ::= {sr1645v2BgrMVBridgingEntry 84213760}

sr1645v2BgrMVBridgingStDesBrIdPriority OBJECT-TYPE
   SYNTAX      Integer32
   MAX-ACCESS  read-only
   STATUS      current
   DESCRIPTION
      "Path: bridgeGroup.status.bridging.spanningTree.designatedBridgeId.priority"
   ::= {sr1645v2BgrMVBridgingEntry 84279552}

sr1645v2BgrMVBridgingStDesBrIdMacAddress OBJECT-TYPE
   SYNTAX      OCTET STRING
   MAX-ACCESS  read-only
   STATUS      current
   DESCRIPTION
      "Path: bridgeGroup.status.bridging.spanningTree.designatedBridgeId.macAddress

       MAC address."
   ::= {sr1645v2BgrMVBridgingEntry 84279808}

sr1645v2BgrMVBridgingStDesPrtId OBJECT-TYPE
   SYNTAX      Integer32
   MAX-ACCESS  read-only
   STATUS      current
   DESCRIPTION
      "Path: bridgeGroup.status.bridging.spanningTree.designatedPortId"
   ::= {sr1645v2BgrMVBridgingEntry 84344832}

sr1645v2BgrMVBridgingStDesInt OBJECT-TYPE
   SYNTAX      INTEGER
               {
               no (0),
               yes (1)
               }
   MAX-ACCESS  read-only
   STATUS      current
   DESCRIPTION
      "Path: bridgeGroup.status.bridging.spanningTree.designatedOrInternal

       Possibilities:
               no   (0)
               yes   (1)"
   ::= {sr1645v2BgrMVBridgingEntry 84410368}

sr1645v2BgrMVBridgingStEdgeDetection OBJECT-TYPE
   SYNTAX      INTEGER
               {
               none (0),
               edge (1),
               notEdge (2)
               }
   MAX-ACCESS  read-only
   STATUS      current
   DESCRIPTION
      "Path: bridgeGroup.status.bridging.spanningTree.edgeDetection

       Possibilities:
               none   (0)
               edge   (1)
               notEdge   (2)"
   ::= {sr1645v2BgrMVBridgingEntry 84475904}

sr1645v2BgrMVBridgingVlMmbGrouped OBJECT-TYPE
   SYNTAX      SEQUENCE OF Sr1645v2BgrMVBridgingVlMmbGroupedEntry
   MAX-ACCESS  not-accessible
   STATUS      current
   DESCRIPTION
      ""
   ::= {sr1645v2BgrMVBridging 100859904}

sr1645v2BgrMVBridgingVlMmbGroupedEntry OBJECT-TYPE
   SYNTAX      Sr1645v2BgrMVBridgingVlMmbGroupedEntry
   MAX-ACCESS  not-accessible
   STATUS      current
   DESCRIPTION
      ""
   INDEX      { sr1645v2BgrMVBridgingTableIx,
                sr1645v2BgrMVBridgingVlMmbGroupedTableIx }
   ::= {sr1645v2BgrMVBridgingVlMmbGrouped 1}

Sr1645v2BgrMVBridgingVlMmbGroupedEntry ::=
   SEQUENCE
      {
      sr1645v2BgrMVBridgingVlMmbGroupedTableIx
         TableIndex,
      sr1645v2BgrMVBridgingVlMmbGroupedVlanId
         Integer32
      }

sr1645v2BgrMVBridgingVlMmbGroupedTableIx OBJECT-TYPE
   SYNTAX      TableIndex
   MAX-ACCESS  not-accessible
   STATUS      current
   DESCRIPTION
      ""
   ::= {sr1645v2BgrMVBridgingVlMmbGroupedEntry 11}

sr1645v2BgrMVBridgingVlMmbGroupedVlanId OBJECT-TYPE
   SYNTAX      Integer32
   MAX-ACCESS  read-only
   STATUS      current
   DESCRIPTION
      "Path: bridgeGroup.status.bridging.vlanMemberShip.grouped.vlanId"
   ::= {sr1645v2BgrMVBridgingVlMmbGroupedEntry 16777216}


sr1645v2BgrMVArpCache OBJECT IDENTIFIER ::= {sr1645v2BgrMV 13}

sr1645v2BgrMVArpCacheSSCTable OBJECT-TYPE
   SYNTAX      SEQUENCE OF Sr1645v2BgrMVArpCacheEntry
   MAX-ACCESS  not-accessible
   STATUS      current
   DESCRIPTION
      "arp cache of ethernet interface"
   ::= {sr1645v2BgrMVArpCache 1}

sr1645v2BgrMVArpCacheEntry OBJECT-TYPE
   SYNTAX      Sr1645v2BgrMVArpCacheEntry
   MAX-ACCESS  not-accessible
   STATUS      current
   DESCRIPTION
      ""
   INDEX      { sr1645v2BgrMVArpCacheTableIx }
   ::= {sr1645v2BgrMVArpCacheSSCTable 1}

Sr1645v2BgrMVArpCacheEntry ::=
   SEQUENCE
      {
      sr1645v2BgrMVArpCacheTableIx
         TableIndex,
      sr1645v2BgrMVArpCacheMacAddress
         OCTET STRING,
      sr1645v2BgrMVArpCacheIpAddress
         IpAddress,
      sr1645v2BgrMVArpCacheType
         INTEGER,
      sr1645v2BgrMVArpCacheTimeOut
         TimeTicks
      }

sr1645v2BgrMVArpCacheTableIx OBJECT-TYPE
   SYNTAX      TableIndex
   MAX-ACCESS  not-accessible
   STATUS      current
   DESCRIPTION
      ""
   ::= {sr1645v2BgrMVArpCacheEntry 11}

sr1645v2BgrMVArpCacheMacAddress OBJECT-TYPE
   SYNTAX      OCTET STRING
   MAX-ACCESS  read-only
   STATUS      current
   DESCRIPTION
      "Path: bridgeGroup.status.arpCache.macAddress

       MAC address."
   ::= {sr1645v2BgrMVArpCacheEntry 16777216}

sr1645v2BgrMVArpCacheIpAddress OBJECT-TYPE
   SYNTAX      IpAddress
   MAX-ACCESS  read-only
   STATUS      current
   DESCRIPTION
      "Path: bridgeGroup.status.arpCache.ipAddress"
   ::= {sr1645v2BgrMVArpCacheEntry 33554432}

sr1645v2BgrMVArpCacheType OBJECT-TYPE
   SYNTAX      INTEGER
               {
               static (0),
               dynamic (1)
               }
   MAX-ACCESS  read-only
   STATUS      current
   DESCRIPTION
      "Path: bridgeGroup.status.arpCache.type

       Possibilities:
               static   (0)
               dynamic   (1)"
   ::= {sr1645v2BgrMVArpCacheEntry 50331648}

sr1645v2BgrMVArpCacheTimeOut OBJECT-TYPE
   SYNTAX      TimeTicks
   MAX-ACCESS  read-only
   STATUS      current
   DESCRIPTION
      "Path: bridgeGroup.status.arpCache.timeOut

       Time in centi-second."
   ::= {sr1645v2BgrMVArpCacheEntry 67108864}


sr1645v2BgrMVSnmpIndex OBJECT-TYPE
   SYNTAX      Integer32
   MAX-ACCESS  read-only
   STATUS      current
   DESCRIPTION
      "Path: bridgeGroup.status.snmpIndex
       Info: SNMP index assigned to this object"
   ::= {sr1645v2BgrMV 269}


sr1645v2BgrMVVlan OBJECT IDENTIFIER ::= {sr1645v2BgrMV 34}

sr1645v2BgrMVVlanSSCTable OBJECT-TYPE
   SYNTAX      SEQUENCE OF Sr1645v2BgrMVVlanEntry
   MAX-ACCESS  not-accessible
   STATUS      current
   DESCRIPTION
      ""
   ::= {sr1645v2BgrMVVlan 1}

sr1645v2BgrMVVlanEntry OBJECT-TYPE
   SYNTAX      Sr1645v2BgrMVVlanEntry
   MAX-ACCESS  not-accessible
   STATUS      current
   DESCRIPTION
      ""
   INDEX      { sr1645v2BgrMVVlanTableIx }
   ::= {sr1645v2BgrMVVlanSSCTable 1}

Sr1645v2BgrMVVlanEntry ::=
   SEQUENCE
      {
      sr1645v2BgrMVVlanTableIx
         TableIndex,
      sr1645v2BgrMVVlanName
         DisplayString,
      sr1645v2BgrMVVlanMode
         INTEGER,
      sr1645v2BgrMVVlanIfOperStatus
         INTEGER,
      sr1645v2BgrMVVlanIfLastChange
         TimeTicks,
      sr1645v2BgrMVVlanIfLastChangeDate
         DisplayString,
      sr1645v2BgrMVVlanIpAddress
         IpAddress,
      sr1645v2BgrMVVlanIpNetMask
         IpAddress,
      sr1645v2BgrMVVlanIpDhcpStatus
         INTEGER,
      sr1645v2BgrMVVlanIpDhcpLeaseTime
         TimeTicks,
      sr1645v2BgrMVVlanIpV6State
         INTEGER,
      sr1645v2BgrMVVlanIpV6InterfaceId
         OCTET STRING,
      sr1645v2BgrMVVlanIpV6LinkMtu
         Integer32,
      sr1645v2BgrMVVlanIpV6HopLimit
         Integer32,
      sr1645v2BgrMVVlanIpV6DhcpIaid
         Counter32,
      sr1645v2BgrMVVlanIpV6RaRcvOption
         Integer32,
      sr1645v2BgrMVVlanVlanVid
         Integer32
      }

sr1645v2BgrMVVlanTableIx OBJECT-TYPE
   SYNTAX      TableIndex
   MAX-ACCESS  not-accessible
   STATUS      current
   DESCRIPTION
      ""
   ::= {sr1645v2BgrMVVlanEntry 11}

sr1645v2BgrMVVlanName OBJECT-TYPE
   SYNTAX      DisplayString
   MAX-ACCESS  read-only
   STATUS      current
   DESCRIPTION
      "Path: bridgeGroup.status.vlan.name"
   ::= {sr1645v2BgrMVVlanEntry 16777216}

sr1645v2BgrMVVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: bridgeGroup.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2BgrMVVlanEntry 335544320}

sr1645v2BgrMVVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: bridgeGroup.status.vlan.ifOperStatus

       Possibilities:
               up   (1)
               down   (2)
               testing   (3)
               unknown   (4)
               dormant   (5)
               notPresent   (6)
               lowerLayerDown   (7)"
   ::= {sr1645v2BgrMVVlanEntry 1795162112}

sr1645v2BgrMVVlanIfLastChange OBJECT-TYPE
   SYNTAX      TimeTicks
   MAX-ACCESS  read-only
   STATUS      current
   DESCRIPTION
      "Path: bridgeGroup.status.vlan.ifLastChange

       Time in centi-second."
   ::= {sr1645v2BgrMVVlanEntry 1811939328}

sr1645v2BgrMVVlanIfLastChangeDate OBJECT-TYPE
   SYNTAX      DisplayString
   MAX-ACCESS  read-only
   STATUS      current
   DESCRIPTION
      "Path: bridgeGroup.status.vlan.ifLastChangeDate"
   ::= {sr1645v2BgrMVVlanEntry 3070230528}

sr1645v2BgrMVVlanIpAddress OBJECT-TYPE
   SYNTAX      IpAddress
   MAX-ACCESS  read-only
   STATUS      current
   DESCRIPTION
      "Path: bridgeGroup.status.vlan.ip.address"
   ::= {sr1645v2BgrMVVlanEntry 51380224}

sr1645v2BgrMVVlanIpNetMask OBJECT-TYPE
   SYNTAX      IpAddress
   MAX-ACCESS  read-only
   STATUS      current
   DESCRIPTION
      "Path: bridgeGroup.status.vlan.ip.netMask"
   ::= {sr1645v2BgrMVVlanEntry 51445760}

sr1645v2BgrMVVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: bridgeGroup.status.vlan.ip.dhcp.status

       Possibilities:
               none   (0)
               selecting   (1)
               requesting   (2)
               rebinding   (3)
               bound   (4)
               renewing   (5)
               rebooting   (6)
               initreboot   (7)"
   ::= {sr1645v2BgrMVVlanEntry 51904768}

sr1645v2BgrMVVlanIpDhcpLeaseTime OBJECT-TYPE
   SYNTAX      TimeTicks
   MAX-ACCESS  read-only
   STATUS      current
   DESCRIPTION
      "Path: bridgeGroup.status.vlan.ip.dhcp.leaseTime

       Time in centi-second."
   ::= {sr1645v2BgrMVVlanEntry 51905024}

sr1645v2BgrMVVlanIpV6State OBJECT-TYPE
   SYNTAX      INTEGER
               {
               disabled (0),
               enabled (1)
               }
   MAX-ACCESS  read-only
   STATUS      current
   DESCRIPTION
      "Path: bridgeGroup.status.vlan.ipV6.state

       Possibilities:
               disabled   (0)
               enabled   (1)"
   ::= {sr1645v2BgrMVVlanEntry 100728832}

sr1645v2BgrMVVlanIpV6InterfaceId OBJECT-TYPE
   SYNTAX      OCTET STRING
   MAX-ACCESS  read-only
   STATUS      current
   DESCRIPTION
      "Path: bridgeGroup.status.vlan.ipV6.interfaceId"
   ::= {sr1645v2BgrMVVlanEntry 100794368}

sr1645v2BgrMVVlanIpV6LinkMtu OBJECT-TYPE
   SYNTAX      Integer32
   MAX-ACCESS  read-only
   STATUS      current
   DESCRIPTION
      "Path: bridgeGroup.status.vlan.ipV6.linkMtu"
   ::= {sr1645v2BgrMVVlanEntry 100925440}

sr1645v2BgrMVVlanIpV6HopLimit OBJECT-TYPE
   SYNTAX      Integer32
   MAX-ACCESS  read-only
   STATUS      current
   DESCRIPTION
      "Path: bridgeGroup.status.vlan.ipV6.hopLimit"
   ::= {sr1645v2BgrMVVlanEntry 100990976}

sr1645v2BgrMVVlanIpV6DhcpIaid OBJECT-TYPE
   SYNTAX      Counter32
   MAX-ACCESS  read-only
   STATUS      current
   DESCRIPTION
      "Path: bridgeGroup.status.vlan.ipV6.dhcp.iaid

       32 bit unsigned wrappable counter."
   ::= {sr1645v2BgrMVVlanEntry 101056768}

sr1645v2BgrMVVlanIpV6RaRcvOption OBJECT-TYPE
   SYNTAX      Integer32
   MAX-ACCESS  read-only
   STATUS      current
   DESCRIPTION
      "Path: bridgeGroup.status.vlan.ipV6.raRcvOption

       Bit meanings:
               bit 0 = linkMtu,
               bit 1 = srcLinkLayer,
               bit 2 = prefixInfo,
               bit 3 = rdnss,
               bit 4 = dnssl"
   ::= {sr1645v2BgrMVVlanEntry 101122048}

sr1645v2BgrMVVlanVlanVid OBJECT-TYPE
   SYNTAX      Integer32
   MAX-ACCESS  read-only
   STATUS      current
   DESCRIPTION
      "Path: bridgeGroup.status.vlan.vlan.vid"
   ::= {sr1645v2BgrMVVlanEntry 234946560}

sr1645v2BgrMVVlanIpSecondaryIp OBJECT-TYPE
   SYNTAX      SEQUENCE OF Sr1645v2BgrMVVlanIpSecondaryIpEntry
   MAX-ACCESS  not-accessible
   STATUS      current
   DESCRIPTION
      ""
   ::= {sr1645v2BgrMVVlan 51838976}

sr1645v2BgrMVVlanIpSecondaryIpEntry OBJECT-TYPE
   SYNTAX      Sr1645v2BgrMVVlanIpSecondaryIpEntry
   MAX-ACCESS  not-accessible
   STATUS      current
   DESCRIPTION
      ""
   INDEX      { sr1645v2BgrMVVlanTableIx,
                sr1645v2BgrMVVlanIpSecondaryIpTableIx }
   ::= {sr1645v2BgrMVVlanIpSecondaryIp 1}

Sr1645v2BgrMVVlanIpSecondaryIpEntry ::=
   SEQUENCE
      {
      sr1645v2BgrMVVlanIpSecondaryIpTableIx
         TableIndex,
      sr1645v2BgrMVVlanIpSecondaryIpAddress
         IpAddress,
      sr1645v2BgrMVVlanIpSecondaryIpNetMask
         IpAddress
      }

sr1645v2BgrMVVlanIpSecondaryIpTableIx OBJECT-TYPE
   SYNTAX      TableIndex
   MAX-ACCESS  not-accessible
   STATUS      current
   DESCRIPTION
      ""
   ::= {sr1645v2BgrMVVlanIpSecondaryIpEntry 11}

sr1645v2BgrMVVlanIpSecondaryIpAddress OBJECT-TYPE
   SYNTAX      IpAddress
   MAX-ACCESS  read-only
   STATUS      current
   DESCRIPTION
      "Path: bridgeGroup.status.vlan.ip.secondaryIp.address"
   ::= {sr1645v2BgrMVVlanIpSecondaryIpEntry 2030043136}

sr1645v2BgrMVVlanIpSecondaryIpNetMask OBJECT-TYPE
   SYNTAX      IpAddress
   MAX-ACCESS  read-only
   STATUS      current
   DESCRIPTION
      "Path: bridgeGroup.status.vlan.ip.secondaryIp.netMask"
   ::= {sr1645v2BgrMVVlanIpSecondaryIpEntry 2063597568}

sr1645v2BgrMVVlanIpV6Addresses OBJECT-TYPE
   SYNTAX      SEQUENCE OF Sr1645v2BgrMVVlanIpV6AddressesEntry
   MAX-ACCESS  not-accessible
   STATUS      current
   DESCRIPTION
      ""
   ::= {sr1645v2BgrMVVlan 100859904}

sr1645v2BgrMVVlanIpV6AddressesEntry OBJECT-TYPE
   SYNTAX      Sr1645v2BgrMVVlanIpV6AddressesEntry
   MAX-ACCESS  not-accessible
   STATUS      current
   DESCRIPTION
      ""
   INDEX      { sr1645v2BgrMVVlanTableIx,
                sr1645v2BgrMVVlanIpV6AddressesTableIx }
   ::= {sr1645v2BgrMVVlanIpV6Addresses 1}

Sr1645v2BgrMVVlanIpV6AddressesEntry ::=
   SEQUENCE
      {
      sr1645v2BgrMVVlanIpV6AddressesTableIx
         TableIndex,
      sr1645v2BgrMVVlanIpV6AddressesAddress
         Ipv6Address,
      sr1645v2BgrMVVlanIpV6AddressesPrefixLength
         Integer32,
      sr1645v2BgrMVVlanIpV6AddressesStatus
         INTEGER,
      sr1645v2BgrMVVlanIpV6AddressesOrigin
         INTEGER,
      sr1645v2BgrMVVlanIpV6AddressesFlagsInterfaceId
         INTEGER,
      sr1645v2BgrMVVlanIpV6AddressesFlagsAnycast
         INTEGER,
      sr1645v2BgrMVVlanIpV6AddressesTimersValidLifeTime
         TimeTicks,
      sr1645v2BgrMVVlanIpV6AddressesTimersPrefLifeTime
         TimeTicks
      }

sr1645v2BgrMVVlanIpV6AddressesTableIx OBJECT-TYPE
   SYNTAX      TableIndex
   MAX-ACCESS  not-accessible
   STATUS      current
   DESCRIPTION
      ""
   ::= {sr1645v2BgrMVVlanIpV6AddressesEntry 11}

sr1645v2BgrMVVlanIpV6AddressesAddress OBJECT-TYPE
   SYNTAX      Ipv6Address
   MAX-ACCESS  read-only
   STATUS      current
   DESCRIPTION
      "Path: bridgeGroup.status.vlan.ipV6.addresses.address

       ipv6 address"
   ::= {sr1645v2BgrMVVlanIpV6AddressesEntry 16777216}

sr1645v2BgrMVVlanIpV6AddressesPrefixLength OBJECT-TYPE
   SYNTAX      Integer32
   MAX-ACCESS  read-only
   STATUS      current
   DESCRIPTION
      "Path: bridgeGroup.status.vlan.ipV6.addresses.prefixLength"
   ::= {sr1645v2BgrMVVlanIpV6AddressesEntry 33554432}

sr1645v2BgrMVVlanIpV6AddressesStatus OBJECT-TYPE
   SYNTAX      INTEGER
               {
               invalid (0),
               tentative (1),
               deprecated (2),
               preferred (3)
               }
   MAX-ACCESS  read-only
   STATUS      current
   DESCRIPTION
      "Path: bridgeGroup.status.vlan.ipV6.addresses.status

       Possibilities:
               invalid   (0)
               tentative   (1)
               deprecated   (2)
               preferred   (3)"
   ::= {sr1645v2BgrMVVlanIpV6AddressesEntry 50331648}

sr1645v2BgrMVVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: bridgeGroup.status.vlan.ipV6.addresses.origin

       Possibilities:
               unknown   (0)
               manual   (1)
               generalPrefix   (2)
               statelessAuto   (3)
               statefullAuto   (4)"
   ::= {sr1645v2BgrMVVlanIpV6AddressesEntry 67108864}

sr1645v2BgrMVVlanIpV6AddressesFlagsInterfaceId OBJECT-TYPE
   SYNTAX      INTEGER
               {
               no (0),
               yes (1)
               }
   MAX-ACCESS  read-only
   STATUS      current
   DESCRIPTION
      "Path: bridgeGroup.status.vlan.ipV6.addresses.flags.interfaceId

       Possibilities:
               no   (0)
               yes   (1)"
   ::= {sr1645v2BgrMVVlanIpV6AddressesEntry 83951616}

sr1645v2BgrMVVlanIpV6AddressesFlagsAnycast OBJECT-TYPE
   SYNTAX      INTEGER
               {
               no (0),
               yes (1)
               }
   MAX-ACCESS  read-only
   STATUS      current
   DESCRIPTION
      "Path: bridgeGroup.status.vlan.ipV6.addresses.flags.anycast

       Possibilities:
               no   (0)
               yes   (1)"
   ::= {sr1645v2BgrMVVlanIpV6AddressesEntry 84017152}

sr1645v2BgrMVVlanIpV6AddressesTimersValidLifeTime OBJECT-TYPE
   SYNTAX      TimeTicks
   MAX-ACCESS  read-only
   STATUS      current
   DESCRIPTION
      "Path: bridgeGroup.status.vlan.ipV6.addresses.timers.validLifeTime

       Time in centi-second."
   ::= {sr1645v2BgrMVVlanIpV6AddressesEntry 100794368}

sr1645v2BgrMVVlanIpV6AddressesTimersPrefLifeTime OBJECT-TYPE
   SYNTAX      TimeTicks
   MAX-ACCESS  read-only
   STATUS      current
   DESCRIPTION
      "Path: bridgeGroup.status.vlan.ipV6.addresses.timers.prefLifeTime

       Time in centi-second."
   ::= {sr1645v2BgrMVVlanIpV6AddressesEntry 100728832}

sr1645v2BgrMVVlanVlanArpCache OBJECT-TYPE
   SYNTAX      SEQUENCE OF Sr1645v2BgrMVVlanVlanArpCacheEntry
   MAX-ACCESS  not-accessible
   STATUS      current
   DESCRIPTION
      ""
   ::= {sr1645v2BgrMVVlan 235601920}

sr1645v2BgrMVVlanVlanArpCacheEntry OBJECT-TYPE
   SYNTAX      Sr1645v2BgrMVVlanVlanArpCacheEntry
   MAX-ACCESS  not-accessible
   STATUS      current
   DESCRIPTION
      ""
   INDEX      { sr1645v2BgrMVVlanTableIx,
                sr1645v2BgrMVVlanVlanArpCacheTableIx }
   ::= {sr1645v2BgrMVVlanVlanArpCache 1}

Sr1645v2BgrMVVlanVlanArpCacheEntry ::=
   SEQUENCE
      {
      sr1645v2BgrMVVlanVlanArpCacheTableIx
         TableIndex,
      sr1645v2BgrMVVlanVlanArpCacheMacAddress
         OCTET STRING,
      sr1645v2BgrMVVlanVlanArpCacheIpAddress
         IpAddress,
      sr1645v2BgrMVVlanVlanArpCacheType
         INTEGER,
      sr1645v2BgrMVVlanVlanArpCacheTimeOut
         TimeTicks
      }

sr1645v2BgrMVVlanVlanArpCacheTableIx OBJECT-TYPE
   SYNTAX      TableIndex
   MAX-ACCESS  not-accessible
   STATUS      current
   DESCRIPTION
      ""
   ::= {sr1645v2BgrMVVlanVlanArpCacheEntry 11}

sr1645v2BgrMVVlanVlanArpCacheMacAddress OBJECT-TYPE
   SYNTAX      OCTET STRING
   MAX-ACCESS  read-only
   STATUS      current
   DESCRIPTION
      "Path: bridgeGroup.status.vlan.vlan.arpCache.macAddress

       MAC address."
   ::= {sr1645v2BgrMVVlanVlanArpCacheEntry 16777216}

sr1645v2BgrMVVlanVlanArpCacheIpAddress OBJECT-TYPE
   SYNTAX      IpAddress
   MAX-ACCESS  read-only
   STATUS      current
   DESCRIPTION
      "Path: bridgeGroup.status.vlan.vlan.arpCache.ipAddress"
   ::= {sr1645v2BgrMVVlanVlanArpCacheEntry 33554432}

sr1645v2BgrMVVlanVlanArpCacheType OBJECT-TYPE
   SYNTAX      INTEGER
               {
               static (0),
               dynamic (1)
               }
   MAX-ACCESS  read-only
   STATUS      current
   DESCRIPTION
      "Path: bridgeGroup.status.vlan.vlan.arpCache.type

       Possibilities:
               static   (0)
               dynamic   (1)"
   ::= {sr1645v2BgrMVVlanVlanArpCacheEntry 50331648}

sr1645v2BgrMVVlanVlanArpCacheTimeOut OBJECT-TYPE
   SYNTAX      TimeTicks
   MAX-ACCESS  read-only
   STATUS      current
   DESCRIPTION
      "Path: bridgeGroup.status.vlan.vlan.arpCache.timeOut

       Time in centi-second."
   ::= {sr1645v2BgrMVVlanVlanArpCacheEntry 67108864}


sr1645v2BgrMVPppOE OBJECT IDENTIFIER ::= {sr1645v2BgrMV 81}

sr1645v2BgrMVPppOESSCTable OBJECT-TYPE
   SYNTAX      SEQUENCE OF Sr1645v2BgrMVPppOEEntry
   MAX-ACCESS  not-accessible
   STATUS      current
   DESCRIPTION
      ""
   ::= {sr1645v2BgrMVPppOE 1}

sr1645v2BgrMVPppOEEntry OBJECT-TYPE
   SYNTAX      Sr1645v2BgrMVPppOEEntry
   MAX-ACCESS  not-accessible
   STATUS      current
   DESCRIPTION
      ""
   INDEX      { sr1645v2BgrMVPppOETableIx }
   ::= {sr1645v2BgrMVPppOESSCTable 1}

Sr1645v2BgrMVPppOEEntry ::=
   SEQUENCE
      {
      sr1645v2BgrMVPppOETableIx
         TableIndex,
      sr1645v2BgrMVPppOEName
         DisplayString,
      sr1645v2BgrMVPppOEMode
         INTEGER,
      sr1645v2BgrMVPppOEIfOperStatus
         INTEGER,
      sr1645v2BgrMVPppOEIfLastChange
         TimeTicks,
      sr1645v2BgrMVPppOEIfLastChangeDate
         DisplayString,
      sr1645v2BgrMVPppOEIpAddress
         IpAddress,
      sr1645v2BgrMVPppOEIpNetMask
         IpAddress,
      sr1645v2BgrMVPppOEIpRemote
         IpAddress,
      sr1645v2BgrMVPppOEPppOEthDiscState
         INTEGER,
      sr1645v2BgrMVPppOEPppOEthPeerMac
         OCTET STRING,
      sr1645v2BgrMVPppOEPppOEthServiceName
         DisplayString,
      sr1645v2BgrMVPppOEPppLcpState
         INTEGER,
      sr1645v2BgrMVPppOEPppIpcpState
         INTEGER,
      sr1645v2BgrMVPppOEPppIp6cpState
         INTEGER,
      sr1645v2BgrMVPppOEPppMyAutSt
         INTEGER,
      sr1645v2BgrMVPppOEPppHisAutSt
         INTEGER,
      sr1645v2BgrMVPppOEPppMru
         Integer32,
      sr1645v2BgrMVPppOEIpV6State
         INTEGER,
      sr1645v2BgrMVPppOEIpV6InterfaceId
         OCTET STRING,
      sr1645v2BgrMVPppOEIpV6LinkMtu
         Integer32,
      sr1645v2BgrMVPppOEIpV6HopLimit
         Integer32,
      sr1645v2BgrMVPppOEIpV6DhcpIaid
         Counter32,
      sr1645v2BgrMVPppOEIpV6RaRcvOption
         Integer32
      }

sr1645v2BgrMVPppOETableIx OBJECT-TYPE
   SYNTAX      TableIndex
   MAX-ACCESS  not-accessible
   STATUS      current
   DESCRIPTION
      ""
   ::= {sr1645v2BgrMVPppOEEntry 11}

sr1645v2BgrMVPppOEName OBJECT-TYPE
   SYNTAX      DisplayString
   MAX-ACCESS  read-only
   STATUS      current
   DESCRIPTION
      "Path: bridgeGroup.status.pppoEClient.name"
   ::= {sr1645v2BgrMVPppOEEntry 16777216}

sr1645v2BgrMVPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: bridgeGroup.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2BgrMVPppOEEntry 335544320}

sr1645v2BgrMVPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: bridgeGroup.status.pppoEClient.ifOperStatus

       Possibilities:
               up   (1)
               down   (2)
               testing   (3)
               unknown   (4)
               dormant   (5)
               notPresent   (6)
               lowerLayerDown   (7)"
   ::= {sr1645v2BgrMVPppOEEntry 1795162112}

sr1645v2BgrMVPppOEIfLastChange OBJECT-TYPE
   SYNTAX      TimeTicks
   MAX-ACCESS  read-only
   STATUS      current
   DESCRIPTION
      "Path: bridgeGroup.status.pppoEClient.ifLastChange

       Time in centi-second."
   ::= {sr1645v2BgrMVPppOEEntry 1811939328}

sr1645v2BgrMVPppOEIfLastChangeDate OBJECT-TYPE
   SYNTAX      DisplayString
   MAX-ACCESS  read-only
   STATUS      current
   DESCRIPTION
      "Path: bridgeGroup.status.pppoEClient.ifLastChangeDate"
   ::= {sr1645v2BgrMVPppOEEntry 3070230528}

sr1645v2BgrMVPppOEIpAddress OBJECT-TYPE
   SYNTAX      IpAddress
   MAX-ACCESS  read-only
   STATUS      current
   DESCRIPTION
      "Path: bridgeGroup.status.pppoEClient.ip.address"
   ::= {sr1645v2BgrMVPppOEEntry 51380224}

sr1645v2BgrMVPppOEIpNetMask OBJECT-TYPE
   SYNTAX      IpAddress
   MAX-ACCESS  read-only
   STATUS      current
   DESCRIPTION
      "Path: bridgeGroup.status.pppoEClient.ip.netMask"
   ::= {sr1645v2BgrMVPppOEEntry 51445760}

sr1645v2BgrMVPppOEIpRemote OBJECT-TYPE
   SYNTAX      IpAddress
   MAX-ACCESS  read-only
   STATUS      current
   DESCRIPTION
      "Path: bridgeGroup.status.pppoEClient.ip.remote"
   ::= {sr1645v2BgrMVPppOEEntry 51511296}

sr1645v2BgrMVPppOEPppOEthDiscState OBJECT-TYPE
   SYNTAX      INTEGER
               {
               idle (0),
               waitForPADO (1),
               waitForPADS (2),
               established (3)
               }
   MAX-ACCESS  read-only
   STATUS      current
   DESCRIPTION
      "Path: bridgeGroup.status.pppoEClient.pppOverEth.discState

       Possibilities:
               idle   (0)
               waitForPADO   (1)
               waitForPADS   (2)
               established   (3)"
   ::= {sr1645v2BgrMVPppOEEntry 67174400}

sr1645v2BgrMVPppOEPppOEthPeerMac OBJECT-TYPE
   SYNTAX      OCTET STRING
   MAX-ACCESS  read-only
   STATUS      current
   DESCRIPTION
      "Path: bridgeGroup.status.pppoEClient.pppOverEth.remoteMacAddress

       MAC address."
   ::= {sr1645v2BgrMVPppOEEntry 67239936}

sr1645v2BgrMVPppOEPppOEthServiceName OBJECT-TYPE
   SYNTAX      DisplayString
   MAX-ACCESS  read-only
   STATUS      current
   DESCRIPTION
      "Path: bridgeGroup.status.pppoEClient.pppOverEth.serviceName"
   ::= {sr1645v2BgrMVPppOEEntry 67305472}

sr1645v2BgrMVPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: bridgeGroup.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2BgrMVPppOEEntry 83951616}

sr1645v2BgrMVPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: bridgeGroup.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2BgrMVPppOEEntry 84017152}

sr1645v2BgrMVPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: bridgeGroup.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2BgrMVPppOEEntry 84869120}

sr1645v2BgrMVPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: bridgeGroup.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2BgrMVPppOEEntry 84541440}

sr1645v2BgrMVPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: bridgeGroup.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2BgrMVPppOEEntry 84606976}

sr1645v2BgrMVPppOEPppMru OBJECT-TYPE
   SYNTAX      Integer32
   MAX-ACCESS  read-only
   STATUS      current
   DESCRIPTION
      "Path: bridgeGroup.status.pppoEClient.ppp.mru"
   ::= {sr1645v2BgrMVPppOEEntry 84934656}

sr1645v2BgrMVPppOEIpV6State OBJECT-TYPE
   SYNTAX      INTEGER
               {
               disabled (0),
               enabled (1)
               }
   MAX-ACCESS  read-only
   STATUS      current
   DESCRIPTION
      "Path: bridgeGroup.status.pppoEClient.ipV6.state

       Possibilities:
               disabled   (0)
               enabled   (1)"
   ::= {sr1645v2BgrMVPppOEEntry 100728832}

sr1645v2BgrMVPppOEIpV6InterfaceId OBJECT-TYPE
   SYNTAX      OCTET STRING
   MAX-ACCESS  read-only
   STATUS      current
   DESCRIPTION
      "Path: bridgeGroup.status.pppoEClient.ipV6.interfaceId"
   ::= {sr1645v2BgrMVPppOEEntry 100794368}

sr1645v2BgrMVPppOEIpV6LinkMtu OBJECT-TYPE
   SYNTAX      Integer32
   MAX-ACCESS  read-only
   STATUS      current
   DESCRIPTION
      "Path: bridgeGroup.status.pppoEClient.ipV6.linkMtu"
   ::= {sr1645v2BgrMVPppOEEntry 100925440}

sr1645v2BgrMVPppOEIpV6HopLimit OBJECT-TYPE
   SYNTAX      Integer32
   MAX-ACCESS  read-only
   STATUS      current
   DESCRIPTION
      "Path: bridgeGroup.status.pppoEClient.ipV6.hopLimit"
   ::= {sr1645v2BgrMVPppOEEntry 100990976}

sr1645v2BgrMVPppOEIpV6DhcpIaid OBJECT-TYPE
   SYNTAX      Counter32
   MAX-ACCESS  read-only
   STATUS      current
   DESCRIPTION
      "Path: bridgeGroup.status.pppoEClient.ipV6.dhcp.iaid

       32 bit unsigned wrappable counter."
   ::= {sr1645v2BgrMVPppOEEntry 101056768}

sr1645v2BgrMVPppOEIpV6RaRcvOption OBJECT-TYPE
   SYNTAX      Integer32
   MAX-ACCESS  read-only
   STATUS      current
   DESCRIPTION
      "Path: bridgeGroup.status.pppoEClient.ipV6.raRcvOption

       Bit meanings:
               bit 0 = linkMtu,
               bit 1 = srcLinkLayer,
               bit 2 = prefixInfo,
               bit 3 = rdnss,
               bit 4 = dnssl"
   ::= {sr1645v2BgrMVPppOEEntry 101122048}

sr1645v2BgrMVPppOEIpV6Addresses OBJECT-TYPE
   SYNTAX      SEQUENCE OF Sr1645v2BgrMVPppOEIpV6AddressesEntry
   MAX-ACCESS  not-accessible
   STATUS      current
   DESCRIPTION
      ""
   ::= {sr1645v2BgrMVPppOE 100859904}

sr1645v2BgrMVPppOEIpV6AddressesEntry OBJECT-TYPE
   SYNTAX      Sr1645v2BgrMVPppOEIpV6AddressesEntry
   MAX-ACCESS  not-accessible
   STATUS      current
   DESCRIPTION
      ""
   INDEX      { sr1645v2BgrMVPppOETableIx,
                sr1645v2BgrMVPppOEIpV6AddressesTableIx }
   ::= {sr1645v2BgrMVPppOEIpV6Addresses 1}

Sr1645v2BgrMVPppOEIpV6AddressesEntry ::=
   SEQUENCE
      {
      sr1645v2BgrMVPppOEIpV6AddressesTableIx
         TableIndex,
      sr1645v2BgrMVPppOEIpV6AddressesAddress
         Ipv6Address,
      sr1645v2BgrMVPppOEIpV6AddressesPrefixLength
         Integer32,
      sr1645v2BgrMVPppOEIpV6AddressesStatus
         INTEGER,
      sr1645v2BgrMVPppOEIpV6AddressesOrigin
         INTEGER,
      sr1645v2BgrMVPppOEIpV6AddressesFlagsInterfaceId
         INTEGER,
      sr1645v2BgrMVPppOEIpV6AddressesFlagsAnycast
         INTEGER,
      sr1645v2BgrMVPppOEIpV6AddressesTimersValidLifeTime
         TimeTicks,
      sr1645v2BgrMVPppOEIpV6AddressesTimersPrefLifeTime
         TimeTicks
      }

sr1645v2BgrMVPppOEIpV6AddressesTableIx OBJECT-TYPE
   SYNTAX      TableIndex
   MAX-ACCESS  not-accessible
   STATUS      current
   DESCRIPTION
      ""
   ::= {sr1645v2BgrMVPppOEIpV6AddressesEntry 11}

sr1645v2BgrMVPppOEIpV6AddressesAddress OBJECT-TYPE
   SYNTAX      Ipv6Address
   MAX-ACCESS  read-only
   STATUS      current
   DESCRIPTION
      "Path: bridgeGroup.status.pppoEClient.ipV6.addresses.address

       ipv6 address"
   ::= {sr1645v2BgrMVPppOEIpV6AddressesEntry 16777216}

sr1645v2BgrMVPppOEIpV6AddressesPrefixLength OBJECT-TYPE
   SYNTAX      Integer32
   MAX-ACCESS  read-only
   STATUS      current
   DESCRIPTION
      "Path: bridgeGroup.status.pppoEClient.ipV6.addresses.prefixLength"
   ::= {sr1645v2BgrMVPppOEIpV6AddressesEntry 33554432}

sr1645v2BgrMVPppOEIpV6AddressesStatus OBJECT-TYPE
   SYNTAX      INTEGER
               {
               invalid (0),
               tentative (1),
               deprecated (2),
               preferred (3)
               }
   MAX-ACCESS  read-only
   STATUS      current
   DESCRIPTION
      "Path: bridgeGroup.status.pppoEClient.ipV6.addresses.status

       Possibilities:
               invalid   (0)
               tentative   (1)
               deprecated   (2)
               preferred   (3)"
   ::= {sr1645v2BgrMVPppOEIpV6AddressesEntry 50331648}

sr1645v2BgrMVPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: bridgeGroup.status.pppoEClient.ipV6.addresses.origin

       Possibilities:
               unknown   (0)
               manual   (1)
               generalPrefix   (2)
               statelessAuto   (3)
               statefullAuto   (4)"
   ::= {sr1645v2BgrMVPppOEIpV6AddressesEntry 67108864}

sr1645v2BgrMVPppOEIpV6AddressesFlagsInterfaceId OBJECT-TYPE
   SYNTAX      INTEGER
               {
               no (0),
               yes (1)
               }
   MAX-ACCESS  read-only
   STATUS      current
   DESCRIPTION
      "Path: bridgeGroup.status.pppoEClient.ipV6.addresses.flags.interfaceId

       Possibilities:
               no   (0)
               yes   (1)"
   ::= {sr1645v2BgrMVPppOEIpV6AddressesEntry 83951616}

sr1645v2BgrMVPppOEIpV6AddressesFlagsAnycast OBJECT-TYPE
   SYNTAX      INTEGER
               {
               no (0),
               yes (1)
               }
   MAX-ACCESS  read-only
   STATUS      current
   DESCRIPTION
      "Path: bridgeGroup.status.pppoEClient.ipV6.addresses.flags.anycast

       Possibilities:
               no   (0)
               yes   (1)"
   ::= {sr1645v2BgrMVPppOEIpV6AddressesEntry 84017152}

sr1645v2BgrMVPppOEIpV6AddressesTimersValidLifeTime OBJECT-TYPE
   SYNTAX      TimeTicks
   MAX-ACCESS  read-only
   STATUS      current
   DESCRIPTION
      "Path: bridgeGroup.status.pppoEClient.ipV6.addresses.timers.validLifeTime

       Time in centi-second."
   ::= {sr1645v2BgrMVPppOEIpV6AddressesEntry 100794368}

sr1645v2BgrMVPppOEIpV6AddressesTimersPrefLifeTime OBJECT-TYPE
   SYNTAX      TimeTicks
   MAX-ACCESS  read-only
   STATUS      current
   DESCRIPTION
      "Path: bridgeGroup.status.pppoEClient.ipV6.addresses.timers.prefLifeTime

       Time in centi-second."
   ::= {sr1645v2BgrMVPppOEIpV6AddressesEntry 100728832}



pr1645v2BgrMV OBJECT IDENTIFIER ::= {r1645v2BgrMV 12}


pr1645v2BgrMVCachePerf OBJECT IDENTIFIER ::= {pr1645v2BgrMV 6}

pr1645v2BgrMVCachePerfSSCTable OBJECT-TYPE
   SYNTAX      SEQUENCE OF Pr1645v2BgrMVCachePerfEntry
   MAX-ACCESS  not-accessible
   STATUS      current
   DESCRIPTION
      "cache entry performance"
   ::= {pr1645v2BgrMVCachePerf 1}

pr1645v2BgrMVCachePerfEntry OBJECT-TYPE
   SYNTAX      Pr1645v2BgrMVCachePerfEntry
   MAX-ACCESS  not-accessible
   STATUS      current
   DESCRIPTION
      ""
   INDEX      { pr1645v2BgrMVCachePerfTableIx }
   ::= {pr1645v2BgrMVCachePerfSSCTable 1}

Pr1645v2BgrMVCachePerfEntry ::=
   SEQUENCE
      {
      pr1645v2BgrMVCachePerfTableIx
         TableIndex,
      pr1645v2BgrMVCachePerfIf
         DisplayString,
      pr1645v2BgrMVCachePerfMacAddress
         OCTET STRING,
      pr1645v2BgrMVCachePerfTpid
         INTEGER,
      pr1645v2BgrMVCachePerfVlanId
         INTEGER,
      pr1645v2BgrMVCachePerfTpid2
         INTEGER,
      pr1645v2BgrMVCachePerfVlanId2
         INTEGER,
      pr1645v2BgrMVCachePerfType
         INTEGER,
      pr1645v2BgrMVCachePerfRxPkts
         Counter32,
      pr1645v2BgrMVCachePerfTxPkts
         Counter32,
      pr1645v2BgrMVCachePerfStatViols
         Counter32,
      pr1645v2BgrMVCachePerfRelearns
         Counter32,
      pr1645v2BgrMVCachePerfRelearnDrops
         Counter32
      }

pr1645v2BgrMVCachePerfTableIx OBJECT-TYPE
   SYNTAX      TableIndex
   MAX-ACCESS  not-accessible
   STATUS      current
   DESCRIPTION
      ""
   ::= {pr1645v2BgrMVCachePerfEntry 11}

pr1645v2BgrMVCachePerfIf OBJECT-TYPE
   SYNTAX      DisplayString
   MAX-ACCESS  read-only
   STATUS      current
   DESCRIPTION
      "Path: bridgeGroup.performance.bridgeCache.interface"
   ::= {pr1645v2BgrMVCachePerfEntry 16777216}

pr1645v2BgrMVCachePerfMacAddress OBJECT-TYPE
   SYNTAX      OCTET STRING
   MAX-ACCESS  read-only
   STATUS      current
   DESCRIPTION
      "Path: bridgeGroup.performance.bridgeCache.macAddress

       MAC address."
   ::= {pr1645v2BgrMVCachePerfEntry 33554432}

pr1645v2BgrMVCachePerfTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: bridgeGroup.performance.bridgeCache.tpid

       Possibilities:
               untagged   (0)
               dot1q   (33024)
               dot1ad   (34984)
               group   (65534)
               notUsed   (65535)
               dot1qOrDot1ad   (65536)"
   ::= {pr1645v2BgrMVCachePerfEntry 335544320}

pr1645v2BgrMVCachePerfVlanId OBJECT-TYPE
   SYNTAX      INTEGER
               {
               undefined (-1)
               }
   MAX-ACCESS  read-only
   STATUS      current
   DESCRIPTION
      "Path: bridgeGroup.performance.bridgeCache.vlanId

       Possibilities:
               undefined   (-1)"
   ::= {pr1645v2BgrMVCachePerfEntry 50331648}

pr1645v2BgrMVCachePerfTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: bridgeGroup.performance.bridgeCache.tpid2

       Possibilities:
               untagged   (0)
               dot1q   (33024)
               dot1ad   (34984)
               group   (65534)
               notUsed   (65535)
               dot1qOrDot1ad   (65536)"
   ::= {pr1645v2BgrMVCachePerfEntry 369098752}

pr1645v2BgrMVCachePerfVlanId2 OBJECT-TYPE
   SYNTAX      INTEGER
               {
               undefined (-1)
               }
   MAX-ACCESS  read-only
   STATUS      current
   DESCRIPTION
      "Path: bridgeGroup.performance.bridgeCache.vlanId2

       Possibilities:
               undefined   (-1)"
   ::= {pr1645v2BgrMVCachePerfEntry 385875968}

pr1645v2BgrMVCachePerfType OBJECT-TYPE
   SYNTAX      INTEGER
               {
               static (0),
               dynamic (1),
               tester (2),
               fastFlood (3)
               }
   MAX-ACCESS  read-only
   STATUS      current
   DESCRIPTION
      "Path: bridgeGroup.performance.bridgeCache.type

       Possibilities:
               static   (0)
               dynamic   (1)
               tester   (2)
               fastFlood   (3)"
   ::= {pr1645v2BgrMVCachePerfEntry 352321536}

pr1645v2BgrMVCachePerfRxPkts OBJECT-TYPE
   SYNTAX      Counter32
   MAX-ACCESS  read-only
   STATUS      current
   DESCRIPTION
      "Path: bridgeGroup.performance.bridgeCache.rxPkts

       32 bit unsigned wrappable counter."
   ::= {pr1645v2BgrMVCachePerfEntry 83886080}

pr1645v2BgrMVCachePerfTxPkts OBJECT-TYPE
   SYNTAX      Counter32
   MAX-ACCESS  read-only
   STATUS      current
   DESCRIPTION
      "Path: bridgeGroup.performance.bridgeCache.txPkts

       32 bit unsigned wrappable counter."
   ::= {pr1645v2BgrMVCachePerfEntry 100663296}

pr1645v2BgrMVCachePerfStatViols OBJECT-TYPE
   SYNTAX      Counter32
   MAX-ACCESS  read-only
   STATUS      current
   DESCRIPTION
      "Path: bridgeGroup.performance.bridgeCache.staticViolations

       32 bit unsigned wrappable counter."
   ::= {pr1645v2BgrMVCachePerfEntry 117440512}

pr1645v2BgrMVCachePerfRelearns OBJECT-TYPE
   SYNTAX      Counter32
   MAX-ACCESS  read-only
   STATUS      current
   DESCRIPTION
      "Path: bridgeGroup.performance.bridgeCache.relearns

       32 bit unsigned wrappable counter."
   ::= {pr1645v2BgrMVCachePerfEntry 134217728}

pr1645v2BgrMVCachePerfRelearnDrops OBJECT-TYPE
   SYNTAX      Counter32
   MAX-ACCESS  read-only
   STATUS      current
   DESCRIPTION
      "Path: bridgeGroup.performance.bridgeCache.relearnDrops

       32 bit unsigned wrappable counter."
   ::= {pr1645v2BgrMVCachePerfEntry 150994944}


pr1645v2BgrMVResCachePerf OBJECT IDENTIFIER ::= {pr1645v2BgrMV 45}

pr1645v2BgrMVResCachePerfSSCTable OBJECT-TYPE
   SYNTAX      SEQUENCE OF Pr1645v2BgrMVResCachePerfEntry
   MAX-ACCESS  not-accessible
   STATUS      current
   DESCRIPTION
      "cache of reserved Ethernet addresses"
   ::= {pr1645v2BgrMVResCachePerf 1}

pr1645v2BgrMVResCachePerfEntry OBJECT-TYPE
   SYNTAX      Pr1645v2BgrMVResCachePerfEntry
   MAX-ACCESS  not-accessible
   STATUS      current
   DESCRIPTION
      ""
   INDEX      { pr1645v2BgrMVResCachePerfTableIx }
   ::= {pr1645v2BgrMVResCachePerfSSCTable 1}

Pr1645v2BgrMVResCachePerfEntry ::=
   SEQUENCE
      {
      pr1645v2BgrMVResCachePerfTableIx
         TableIndex,
      pr1645v2BgrMVResCachePerfMacAddress
         OCTET STRING,
      pr1645v2BgrMVResCachePerfRxPkts
         Counter32
      }

pr1645v2BgrMVResCachePerfTableIx OBJECT-TYPE
   SYNTAX      TableIndex
   MAX-ACCESS  not-accessible
   STATUS      current
   DESCRIPTION
      ""
   ::= {pr1645v2BgrMVResCachePerfEntry 11}

pr1645v2BgrMVResCachePerfMacAddress OBJECT-TYPE
   SYNTAX      OCTET STRING
   MAX-ACCESS  read-only
   STATUS      current
   DESCRIPTION
      "Path: bridgeGroup.performance.reservedAddressCache.macAddress

       MAC address."
   ::= {pr1645v2BgrMVResCachePerfEntry 16777216}

pr1645v2BgrMVResCachePerfRxPkts OBJECT-TYPE
   SYNTAX      Counter32
   MAX-ACCESS  read-only
   STATUS      current
   DESCRIPTION
      "Path: bridgeGroup.performance.reservedAddressCache.rxPkts

       32 bit unsigned wrappable counter."
   ::= {pr1645v2BgrMVResCachePerfEntry 33554432}


pr1645v2BgrMVCacheEvents OBJECT IDENTIFIER ::= {pr1645v2BgrMV 44}

pr1645v2BgrMVCacheEventsSSC OBJECT IDENTIFIER ::= {pr1645v2BgrMVCacheEvents 1}

pr1645v2BgrMVCacheEventsEntry OBJECT IDENTIFIER ::= {pr1645v2BgrMVCacheEventsSSC 1}

pr1645v2BgrMVCacheEventsSizeOverflows OBJECT-TYPE
   SYNTAX      Counter32
   MAX-ACCESS  read-only
   STATUS      current
   DESCRIPTION
      "Path: bridgeGroup.performance.cacheEvents.sizeOverflows

       32 bit unsigned wrappable counter."
   ::= {pr1645v2BgrMVCacheEventsEntry 16777216}

pr1645v2BgrMVCacheEventsStaticViolations OBJECT-TYPE
   SYNTAX      Counter32
   MAX-ACCESS  read-only
   STATUS      current
   DESCRIPTION
      "Path: bridgeGroup.performance.cacheEvents.staticViolations

       32 bit unsigned wrappable counter."
   ::= {pr1645v2BgrMVCacheEventsEntry 33554432}

pr1645v2BgrMVCacheEventsRelearns OBJECT-TYPE
   SYNTAX      Counter32
   MAX-ACCESS  read-only
   STATUS      current
   DESCRIPTION
      "Path: bridgeGroup.performance.cacheEvents.relearns

       32 bit unsigned wrappable counter."
   ::= {pr1645v2BgrMVCacheEventsEntry 50331648}

pr1645v2BgrMVCacheEventsRelearnDrops OBJECT-TYPE
   SYNTAX      Counter32
   MAX-ACCESS  read-only
   STATUS      current
   DESCRIPTION
      "Path: bridgeGroup.performance.cacheEvents.relearnDrops

       32 bit unsigned wrappable counter."
   ::= {pr1645v2BgrMVCacheEventsEntry 67108864}

pr1645v2BgrMVCacheEventsLoopsDetected OBJECT-TYPE
   SYNTAX      Counter32
   MAX-ACCESS  read-only
   STATUS      current
   DESCRIPTION
      "Path: bridgeGroup.performance.cacheEvents.loopsDetected

       32 bit unsigned wrappable counter."
   ::= {pr1645v2BgrMVCacheEventsEntry 117440512}


pr1645v2BgrMVBridgeRxPkts OBJECT-TYPE
   SYNTAX      Counter32
   MAX-ACCESS  read-only
   STATUS      current
   DESCRIPTION
      "Path: bridgeGroup.performance.bridgeRxPkts
       Info: counter (floods or discards) of bridge

       32 bit unsigned wrappable counter."
   ::= {pr1645v2BgrMV 42}


pr1645v2BgrMVBridgeTxPkts OBJECT-TYPE
   SYNTAX      Counter32
   MAX-ACCESS  read-only
   STATUS      current
   DESCRIPTION
      "Path: bridgeGroup.performance.bridgeTxPkts
       Info: counter (floods or discards) of bridge

       32 bit unsigned wrappable counter."
   ::= {pr1645v2BgrMV 43}


pr1645v2BgrMVBridgeDiscards OBJECT-TYPE
   SYNTAX      Counter32
   MAX-ACCESS  read-only
   STATUS      current
   DESCRIPTION
      "Path: bridgeGroup.performance.bridgeDiscards
       Info: counter (floods or discards) of bridge

       32 bit unsigned wrappable counter."
   ::= {pr1645v2BgrMV 7}


pr1645v2BgrMVBridgeFloods OBJECT-TYPE
   SYNTAX      Counter32
   MAX-ACCESS  read-only
   STATUS      current
   DESCRIPTION
      "Path: bridgeGroup.performance.bridgeFloods
       Info: counter (floods or discards) of bridge

       32 bit unsigned wrappable counter."
   ::= {pr1645v2BgrMV 8}


pr1645v2BgrMVBridgeBroadcasts OBJECT-TYPE
   SYNTAX      Counter32
   MAX-ACCESS  read-only
   STATUS      current
   DESCRIPTION
      "Path: bridgeGroup.performance.bridgeBroadcasts
       Info: counter (floods or discards) of bridge

       32 bit unsigned wrappable counter."
   ::= {pr1645v2BgrMV 40}


pr1645v2BgrMVBridgeMulticasts OBJECT-TYPE
   SYNTAX      Counter32
   MAX-ACCESS  read-only
   STATUS      current
   DESCRIPTION
      "Path: bridgeGroup.performance.bridgeMulticasts
       Info: counter (floods or discards) of bridge

       32 bit unsigned wrappable counter."
   ::= {pr1645v2BgrMV 41}


pr1645v2BgrMVVlanSwitching OBJECT IDENTIFIER ::= {pr1645v2BgrMV 30}

pr1645v2BgrMVVlanSwitchingSSCTable OBJECT-TYPE
   SYNTAX      SEQUENCE OF Pr1645v2BgrMVVlanSwitchingEntry
   MAX-ACCESS  not-accessible
   STATUS      current
   DESCRIPTION
      "ospf area summary lsa overview"
   ::= {pr1645v2BgrMVVlanSwitching 1}

pr1645v2BgrMVVlanSwitchingEntry OBJECT-TYPE
   SYNTAX      Pr1645v2BgrMVVlanSwitchingEntry
   MAX-ACCESS  not-accessible
   STATUS      current
   DESCRIPTION
      ""
   INDEX      { pr1645v2BgrMVVlanSwitchingTableIx }
   ::= {pr1645v2BgrMVVlanSwitchingSSCTable 1}

Pr1645v2BgrMVVlanSwitchingEntry ::=
   SEQUENCE
      {
      pr1645v2BgrMVVlanSwitchingTableIx
         TableIndex,
      pr1645v2BgrMVVlanSwitchingSrcIntf
         DisplayString,
      pr1645v2BgrMVVlanSwitchingSrcVlan
         INTEGER,
      pr1645v2BgrMVVlanSwitchingSrcPFlt
         INTEGER,
      pr1645v2BgrMVVlanSwitchingDestIntf
         DisplayString,
      pr1645v2BgrMVVlanSwitchingDestVlan
         INTEGER,
      pr1645v2BgrMVVlanSwitchingTunnelMode
         INTEGER,
      pr1645v2BgrMVVlanSwitchingUses
         Counter32
      }

pr1645v2BgrMVVlanSwitchingTableIx OBJECT-TYPE
   SYNTAX      TableIndex
   MAX-ACCESS  not-accessible
   STATUS      current
   DESCRIPTION
      ""
   ::= {pr1645v2BgrMVVlanSwitchingEntry 11}

pr1645v2BgrMVVlanSwitchingSrcIntf OBJECT-TYPE
   SYNTAX      DisplayString
   MAX-ACCESS  read-only
   STATUS      current
   DESCRIPTION
      "Path: bridgeGroup.performance.vlanSwitching.sourceIntf"
   ::= {pr1645v2BgrMVVlanSwitchingEntry 16777216}

pr1645v2BgrMVVlanSwitchingSrcVlan OBJECT-TYPE
   SYNTAX      INTEGER
               {
               any (-1)
               }
   MAX-ACCESS  read-only
   STATUS      current
   DESCRIPTION
      "Path: bridgeGroup.performance.vlanSwitching.sourceVlan

       Possibilities:
               any   (-1)"
   ::= {pr1645v2BgrMVVlanSwitchingEntry 33554432}

pr1645v2BgrMVVlanSwitchingSrcPFlt OBJECT-TYPE
   SYNTAX      INTEGER
               {
               any (-1)
               }
   MAX-ACCESS  read-only
   STATUS      current
   DESCRIPTION
      "Path: bridgeGroup.performance.vlanSwitching.sourcePFilter

       Possibilities:
               any   (-1)"
   ::= {pr1645v2BgrMVVlanSwitchingEntry 100663296}

pr1645v2BgrMVVlanSwitchingDestIntf OBJECT-TYPE
   SYNTAX      DisplayString
   MAX-ACCESS  read-only
   STATUS      current
   DESCRIPTION
      "Path: bridgeGroup.performance.vlanSwitching.destinationIntf"
   ::= {pr1645v2BgrMVVlanSwitchingEntry 50331648}

pr1645v2BgrMVVlanSwitchingDestVlan OBJECT-TYPE
   SYNTAX      INTEGER
               {
               unchanged (-1)
               }
   MAX-ACCESS  read-only
   STATUS      current
   DESCRIPTION
      "Path: bridgeGroup.performance.vlanSwitching.destinationVlan

       Possibilities:
               unchanged   (-1)"
   ::= {pr1645v2BgrMVVlanSwitchingEntry 67108864}

pr1645v2BgrMVVlanSwitchingTunnelMode OBJECT-TYPE
   SYNTAX      INTEGER
               {
               none (0),
               toTunnel (1),
               fromTunnel (2),
               toSVlanTunnel (3),
               fromSVlanTunnel (4)
               }
   MAX-ACCESS  read-only
   STATUS      current
   DESCRIPTION
      "Path: bridgeGroup.performance.vlanSwitching.tunnelMode

       Possibilities:
               none   (0)
               toTunnel   (1)
               fromTunnel   (2)
               toSVlanTunnel   (3)
               fromSVlanTunnel   (4)"
   ::= {pr1645v2BgrMVVlanSwitchingEntry 117440512}

pr1645v2BgrMVVlanSwitchingUses OBJECT-TYPE
   SYNTAX      Counter32
   MAX-ACCESS  read-only
   STATUS      current
   DESCRIPTION
      "Path: bridgeGroup.performance.vlanSwitching.uses

       32 bit unsigned wrappable counter."
   ::= {pr1645v2BgrMVVlanSwitchingEntry 83886080}


pr1645v2BgrMVMibCounters OBJECT IDENTIFIER ::= {pr1645v2BgrMV 100}

pr1645v2BgrMVMibCountersSSC OBJECT IDENTIFIER ::= {pr1645v2BgrMVMibCounters 1}

pr1645v2BgrMVMibCountersEntry OBJECT IDENTIFIER ::= {pr1645v2BgrMVMibCountersSSC 1}

pr1645v2BgrMVMibCountersInOctets OBJECT-TYPE
   SYNTAX      Counter64
   MAX-ACCESS  read-only
   STATUS      current
   DESCRIPTION
      "Path: bridgeGroup.performance.mibCounters.ifInOctets

       64 bit unsigned wrappable counter."
   ::= {pr1645v2BgrMVMibCountersEntry 1828716544}

pr1645v2BgrMVMibCountersInUcast OBJECT-TYPE
   SYNTAX      Counter64
   MAX-ACCESS  read-only
   STATUS      current
   DESCRIPTION
      "Path: bridgeGroup.performance.mibCounters.ifInUcastPkts

       64 bit unsigned wrappable counter."
   ::= {pr1645v2BgrMVMibCountersEntry 1845493760}

pr1645v2BgrMVMibCountersInNUcastPkts OBJECT-TYPE
   SYNTAX      Counter64
   MAX-ACCESS  read-only
   STATUS      current
   DESCRIPTION
      "Path: bridgeGroup.performance.mibCounters.ifInNUcastPkts

       64 bit unsigned wrappable counter."
   ::= {pr1645v2BgrMVMibCountersEntry 1862270976}

pr1645v2BgrMVMibCountersInBcastPkts OBJECT-TYPE
   SYNTAX      Counter64
   MAX-ACCESS  read-only
   STATUS      current
   DESCRIPTION
      "Path: bridgeGroup.performance.mibCounters.ifInBcastPkts

       64 bit unsigned wrappable counter."
   ::= {pr1645v2BgrMVMibCountersEntry 3539992576}

pr1645v2BgrMVMibCountersInMcastPkts OBJECT-TYPE
   SYNTAX      Counter64
   MAX-ACCESS  read-only
   STATUS      current
   DESCRIPTION
      "Path: bridgeGroup.performance.mibCounters.ifInMcastPkts

       64 bit unsigned wrappable counter."
   ::= {pr1645v2BgrMVMibCountersEntry 3707764736}

pr1645v2BgrMVMibCountersInDiscards OBJECT-TYPE
   SYNTAX      Counter64
   MAX-ACCESS  read-only
   STATUS      current
   DESCRIPTION
      "Path: bridgeGroup.performance.mibCounters.ifInDiscards

       64 bit unsigned wrappable counter."
   ::= {pr1645v2BgrMVMibCountersEntry 1879048192}

pr1645v2BgrMVMibCountersInErrors OBJECT-TYPE
   SYNTAX      Counter64
   MAX-ACCESS  read-only
   STATUS      current
   DESCRIPTION
      "Path: bridgeGroup.performance.mibCounters.ifInErrors

       64 bit unsigned wrappable counter."
   ::= {pr1645v2BgrMVMibCountersEntry 1895825408}

pr1645v2BgrMVMibCountersInUnknownProtos OBJECT-TYPE
   SYNTAX      Counter64
   MAX-ACCESS  read-only
   STATUS      current
   DESCRIPTION
      "Path: bridgeGroup.performance.mibCounters.ifInUnknownProtos

       64 bit unsigned wrappable counter."
   ::= {pr1645v2BgrMVMibCountersEntry 1912602624}

pr1645v2BgrMVMibCountersInDropEx OBJECT-TYPE
   SYNTAX      Counter64
   MAX-ACCESS  read-only
   STATUS      current
   DESCRIPTION
      "Path: bridgeGroup.performance.mibCounters.ifInDropLevelExceeded

       64 bit unsigned wrappable counter."
   ::= {pr1645v2BgrMVMibCountersEntry 2181038080}

pr1645v2BgrMVMibCountersInDropNoMac OBJECT-TYPE
   SYNTAX      Counter64
   MAX-ACCESS  read-only
   STATUS      current
   DESCRIPTION
      "Path: bridgeGroup.performance.mibCounters.ifInDiscardsNoMacFit

       64 bit unsigned wrappable counter."
   ::= {pr1645v2BgrMVMibCountersEntry 2231369728}

pr1645v2BgrMVMibCountersInDropNUCast OBJECT-TYPE
   SYNTAX      Counter64
   MAX-ACCESS  read-only
   STATUS      current
   DESCRIPTION
      "Path: bridgeGroup.performance.mibCounters.ifInDiscardsNUCast

       64 bit unsigned wrappable counter."
   ::= {pr1645v2BgrMVMibCountersEntry 2281701376}

pr1645v2BgrMVMibCountersInDropFilter OBJECT-TYPE
   SYNTAX      Counter64
   MAX-ACCESS  read-only
   STATUS      current
   DESCRIPTION
      "Path: bridgeGroup.performance.mibCounters.ifInDiscardsFilter

       64 bit unsigned wrappable counter."
   ::= {pr1645v2BgrMVMibCountersEntry 2298478592}

pr1645v2BgrMVMibCountersInBandwidth15sec OBJECT-TYPE
   SYNTAX      Integer32
   MAX-ACCESS  read-only
   STATUS      current
   DESCRIPTION
      "Path: bridgeGroup.performance.mibCounters.ifInBandwidth.15sec

       unit name = bps
       formula = 8 * ; 8 /"
   ::= {pr1645v2BgrMVMibCountersEntry 3037003776}

pr1645v2BgrMVMibCountersInBandwidth30sec OBJECT-TYPE
   SYNTAX      Integer32
   MAX-ACCESS  read-only
   STATUS      current
   DESCRIPTION
      "Path: bridgeGroup.performance.mibCounters.ifInBandwidth.30sec

       unit name = bps
       formula = 8 * ; 8 /"
   ::= {pr1645v2BgrMVMibCountersEntry 3037331456}

pr1645v2BgrMVMibCountersInBandwidth1min OBJECT-TYPE
   SYNTAX      Integer32
   MAX-ACCESS  read-only
   STATUS      current
   DESCRIPTION
      "Path: bridgeGroup.performance.mibCounters.ifInBandwidth.1min

       unit name = bps
       formula = 8 * ; 8 /"
   ::= {pr1645v2BgrMVMibCountersEntry 3037986816}

pr1645v2BgrMVMibCountersInBandwidth2min OBJECT-TYPE
   SYNTAX      Integer32
   MAX-ACCESS  read-only
   STATUS      current
   DESCRIPTION
      "Path: bridgeGroup.performance.mibCounters.ifInBandwidth.2min

       unit name = bps
       formula = 8 * ; 8 /"
   ::= {pr1645v2BgrMVMibCountersEntry 3039297536}

pr1645v2BgrMVMibCountersInBandwidth5min OBJECT-TYPE
   SYNTAX      Integer32
   MAX-ACCESS  read-only
   STATUS      current
   DESCRIPTION
      "Path: bridgeGroup.performance.mibCounters.ifInBandwidth.5min

       unit name = bps
       formula = 8 * ; 8 /"
   ::= {pr1645v2BgrMVMibCountersEntry 3043229696}

pr1645v2BgrMVMibCountersOutOctets OBJECT-TYPE
   SYNTAX      Counter64
   MAX-ACCESS  read-only
   STATUS      current
   DESCRIPTION
      "Path: bridgeGroup.performance.mibCounters.ifOutOctets

       64 bit unsigned wrappable counter."
   ::= {pr1645v2BgrMVMibCountersEntry 1929379840}

pr1645v2BgrMVMibCountersOutUcastPkts OBJECT-TYPE
   SYNTAX      Counter64
   MAX-ACCESS  read-only
   STATUS      current
   DESCRIPTION
      "Path: bridgeGroup.performance.mibCounters.ifOutUcastPkts

       64 bit unsigned wrappable counter."
   ::= {pr1645v2BgrMVMibCountersEntry 1946157056}

pr1645v2BgrMVMibCountersOutNUcastPkts OBJECT-TYPE
   SYNTAX      Counter64
   MAX-ACCESS  read-only
   STATUS      current
   DESCRIPTION
      "Path: bridgeGroup.performance.mibCounters.ifOutNUcastPkts

       64 bit unsigned wrappable counter."
   ::= {pr1645v2BgrMVMibCountersEntry 1962934272}

pr1645v2BgrMVMibCountersOutBcastPkts OBJECT-TYPE
   SYNTAX      Counter64
   MAX-ACCESS  read-only
   STATUS      current
   DESCRIPTION
      "Path: bridgeGroup.performance.mibCounters.ifOutBcastPkts

       64 bit unsigned wrappable counter."
   ::= {pr1645v2BgrMVMibCountersEntry 3640655872}

pr1645v2BgrMVMibCountersOutMcastPkts OBJECT-TYPE
   SYNTAX      Counter64
   MAX-ACCESS  read-only
   STATUS      current
   DESCRIPTION
      "Path: bridgeGroup.performance.mibCounters.ifOutMcastPkts

       64 bit unsigned wrappable counter."
   ::= {pr1645v2BgrMVMibCountersEntry 3808428032}

pr1645v2BgrMVMibCountersOutDiscards OBJECT-TYPE
   SYNTAX      Counter64
   MAX-ACCESS  read-only
   STATUS      current
   DESCRIPTION
      "Path: bridgeGroup.performance.mibCounters.ifOutDiscards

       64 bit unsigned wrappable counter."
   ::= {pr1645v2BgrMVMibCountersEntry 1979711488}

pr1645v2BgrMVMibCountersOutErrors OBJECT-TYPE
   SYNTAX      Counter64
   MAX-ACCESS  read-only
   STATUS      current
   DESCRIPTION
      "Path: bridgeGroup.performance.mibCounters.ifOutErrors

       64 bit unsigned wrappable counter."
   ::= {pr1645v2BgrMVMibCountersEntry 1996488704}

pr1645v2BgrMVMibCountersOutQLen OBJECT-TYPE
   SYNTAX      Counter32
   MAX-ACCESS  read-only
   STATUS      current
   DESCRIPTION
      "Path: bridgeGroup.performance.mibCounters.ifOutQLen

       32 bit unsigned wrappable counter."
   ::= {pr1645v2BgrMVMibCountersEntry 2013265920}

pr1645v2BgrMVMibCountersOutDropEx OBJECT-TYPE
   SYNTAX      Counter64
   MAX-ACCESS  read-only
   STATUS      current
   DESCRIPTION
      "Path: bridgeGroup.performance.mibCounters.ifOutDropLevelExceeded

       64 bit unsigned wrappable counter."
   ::= {pr1645v2BgrMVMibCountersEntry 2030043136}

pr1645v2BgrMVMibCountersOutDropNoArp OBJECT-TYPE
   SYNTAX      Counter64
   MAX-ACCESS  read-only
   STATUS      current
   DESCRIPTION
      "Path: bridgeGroup.performance.mibCounters.ifOutDiscardsNoArp

       64 bit unsigned wrappable counter."
   ::= {pr1645v2BgrMVMibCountersEntry 2248146944}

pr1645v2BgrMVMibCountersOutDropFilter OBJECT-TYPE
   SYNTAX      Counter64
   MAX-ACCESS  read-only
   STATUS      current
   DESCRIPTION
      "Path: bridgeGroup.performance.mibCounters.ifOutDiscardsFilter

       64 bit unsigned wrappable counter."
   ::= {pr1645v2BgrMVMibCountersEntry 2315255808}

pr1645v2BgrMVMibCountersOutBandwidth15sec OBJECT-TYPE
   SYNTAX      Integer32
   MAX-ACCESS  read-only
   STATUS      current
   DESCRIPTION
      "Path: bridgeGroup.performance.mibCounters.ifOutBandwidth.15sec

       unit name = bps
       formula = 8 * ; 8 /"
   ::= {pr1645v2BgrMVMibCountersEntry 3053780992}

pr1645v2BgrMVMibCountersOutBandwidth30sec OBJECT-TYPE
   SYNTAX      Integer32
   MAX-ACCESS  read-only
   STATUS      current
   DESCRIPTION
      "Path: bridgeGroup.performance.mibCounters.ifOutBandwidth.30sec

       unit name = bps
       formula = 8 * ; 8 /"
   ::= {pr1645v2BgrMVMibCountersEntry 3054108672}

pr1645v2BgrMVMibCountersOutBandwidth1min OBJECT-TYPE
   SYNTAX      Integer32
   MAX-ACCESS  read-only
   STATUS      current
   DESCRIPTION
      "Path: bridgeGroup.performance.mibCounters.ifOutBandwidth.1min

       unit name = bps
       formula = 8 * ; 8 /"
   ::= {pr1645v2BgrMVMibCountersEntry 3054764032}

pr1645v2BgrMVMibCountersOutBandwidth2min OBJECT-TYPE
   SYNTAX      Integer32
   MAX-ACCESS  read-only
   STATUS      current
   DESCRIPTION
      "Path: bridgeGroup.performance.mibCounters.ifOutBandwidth.2min

       unit name = bps
       formula = 8 * ; 8 /"
   ::= {pr1645v2BgrMVMibCountersEntry 3056074752}

pr1645v2BgrMVMibCountersOutBandwidth5min OBJECT-TYPE
   SYNTAX      Integer32
   MAX-ACCESS  read-only
   STATUS      current
   DESCRIPTION
      "Path: bridgeGroup.performance.mibCounters.ifOutBandwidth.5min

       unit name = bps
       formula = 8 * ; 8 /"
   ::= {pr1645v2BgrMVMibCountersEntry 3060006912}

pr1645v2BgrMVMibCountersH2P OBJECT-TYPE
   SYNTAX      SEQUENCE OF Pr1645v2BgrMVMibCountersH2PEntry
   MAX-ACCESS  not-accessible
   STATUS      current
   DESCRIPTION
      ""
   ::= {pr1645v2BgrMVMibCounters 2046820352}

pr1645v2BgrMVMibCountersH2PEntry OBJECT-TYPE
   SYNTAX      Pr1645v2BgrMVMibCountersH2PEntry
   MAX-ACCESS  not-accessible
   STATUS      current
   DESCRIPTION
      ""
   INDEX      { pr1645v2BgrMVMibCountersH2PTableIx }
   ::= {pr1645v2BgrMVMibCountersH2P 1}

Pr1645v2BgrMVMibCountersH2PEntry ::=
   SEQUENCE
      {
      pr1645v2BgrMVMibCountersH2PTableIx
         TableIndex,
      pr1645v2BgrMVMibCountersH2PSysUpTime
         TimeTicks,
      pr1645v2BgrMVMibCountersH2PIfUpTime
         TimeTicks,
      pr1645v2BgrMVMibCountersH2PIfStatChanges
         Counter32,
      pr1645v2BgrMVMibCountersH2PIfInOctets
         Counter64,
      pr1645v2BgrMVMibCountersH2PIfInUCPkts
         Counter64,
      pr1645v2BgrMVMibCountersH2PIfInNUCPkts
         Counter64,
      pr1645v2BgrMVMibCountersH2PIfInBCPkts
         Counter64,
      pr1645v2BgrMVMibCountersH2PIfInMCPkts
         Counter64,
      pr1645v2BgrMVMibCountersH2PIfInDiscards
         Counter64,
      pr1645v2BgrMVMibCountersH2PIfInErrors
         Counter64,
      pr1645v2BgrMVMibCountersH2PIfInUnkwn
         Counter64,
      pr1645v2BgrMVMibCountersH2PInDropEx
         Counter64,
      pr1645v2BgrMVMibCountersH2PInDropNoMac
         Counter64,
      pr1645v2BgrMVMibCountersH2PInDropNUCast
         Counter64,
      pr1645v2BgrMVMibCountersH2PInDropFilter
         Counter64,
      pr1645v2BgrMVMibCountersH2PIfInBandwidth
         Integer32,
      pr1645v2BgrMVMibCountersH2PIfOutOctets
         Counter64,
      pr1645v2BgrMVMibCountersH2PIfOutUCPkts
         Counter64,
      pr1645v2BgrMVMibCountersH2PIfOutNUCPkts
         Counter64,
      pr1645v2BgrMVMibCountersH2PIfOutBCPkts
         Counter64,
      pr1645v2BgrMVMibCountersH2PIfOutMCPkts
         Counter64,
      pr1645v2BgrMVMibCountersH2PIfOutDiscards
         Counter64,
      pr1645v2BgrMVMibCountersH2PIfOutErrors
         Counter64,
      pr1645v2BgrMVMibCountersH2POutDropEx
         Counter64,
      pr1645v2BgrMVMibCountersH2POutDropNoArp
         Counter64,
      pr1645v2BgrMVMibCountersH2POutDropFilter
         Counter64,
      pr1645v2BgrMVMibCountersH2PIfOutBandwidth
         Integer32,
      pr1645v2BgrMVMibCountersH2PIfErrSec
         Counter32
      }

pr1645v2BgrMVMibCountersH2PTableIx OBJECT-TYPE
   SYNTAX      TableIndex
   MAX-ACCESS  not-accessible
   STATUS      current
   DESCRIPTION
      ""
   ::= {pr1645v2BgrMVMibCountersH2PEntry 11}

pr1645v2BgrMVMibCountersH2PSysUpTime OBJECT-TYPE
   SYNTAX      TimeTicks
   MAX-ACCESS  read-only
   STATUS      current
   DESCRIPTION
      "Path: bridgeGroup.performance.mibCounters.h2Performance.sysUpTime

       Time in centi-second."
   ::= {pr1645v2BgrMVMibCountersH2PEntry 16777216}

pr1645v2BgrMVMibCountersH2PIfUpTime OBJECT-TYPE
   SYNTAX      TimeTicks
   MAX-ACCESS  read-only
   STATUS      current
   DESCRIPTION
      "Path: bridgeGroup.performance.mibCounters.h2Performance.ifUpTime

       Time in centi-second."
   ::= {pr1645v2BgrMVMibCountersH2PEntry 33554432}

pr1645v2BgrMVMibCountersH2PIfStatChanges OBJECT-TYPE
   SYNTAX      Counter32
   MAX-ACCESS  read-only
   STATUS      current
   DESCRIPTION
      "Path: bridgeGroup.performance.mibCounters.h2Performance.ifStatusChanges

       32 bit unsigned wrappable counter."
   ::= {pr1645v2BgrMVMibCountersH2PEntry 50331648}

pr1645v2BgrMVMibCountersH2PIfInOctets OBJECT-TYPE
   SYNTAX      Counter64
   MAX-ACCESS  read-only
   STATUS      current
   DESCRIPTION
      "Path: bridgeGroup.performance.mibCounters.h2Performance.ifInOctets

       64 bit unsigned wrappable counter."
   ::= {pr1645v2BgrMVMibCountersH2PEntry 67108864}

pr1645v2BgrMVMibCountersH2PIfInUCPkts OBJECT-TYPE
   SYNTAX      Counter64
   MAX-ACCESS  read-only
   STATUS      current
   DESCRIPTION
      "Path: bridgeGroup.performance.mibCounters.h2Performance.ifInUcastPkts

       64 bit unsigned wrappable counter."
   ::= {pr1645v2BgrMVMibCountersH2PEntry 83886080}

pr1645v2BgrMVMibCountersH2PIfInNUCPkts OBJECT-TYPE
   SYNTAX      Counter64
   MAX-ACCESS  read-only
   STATUS      current
   DESCRIPTION
      "Path: bridgeGroup.performance.mibCounters.h2Performance.ifInNUcastPkts

       64 bit unsigned wrappable counter."
   ::= {pr1645v2BgrMVMibCountersH2PEntry 100663296}

pr1645v2BgrMVMibCountersH2PIfInBCPkts OBJECT-TYPE
   SYNTAX      Counter64
   MAX-ACCESS  read-only
   STATUS      current
   DESCRIPTION
      "Path: bridgeGroup.performance.mibCounters.h2Performance.ifInBcastPkts

       64 bit unsigned wrappable counter."
   ::= {pr1645v2BgrMVMibCountersH2PEntry 419430400}

pr1645v2BgrMVMibCountersH2PIfInMCPkts OBJECT-TYPE
   SYNTAX      Counter64
   MAX-ACCESS  read-only
   STATUS      current
   DESCRIPTION
      "Path: bridgeGroup.performance.mibCounters.h2Performance.ifInMcastPkts

       64 bit unsigned wrappable counter."
   ::= {pr1645v2BgrMVMibCountersH2PEntry 436207616}

pr1645v2BgrMVMibCountersH2PIfInDiscards OBJECT-TYPE
   SYNTAX      Counter64
   MAX-ACCESS  read-only
   STATUS      current
   DESCRIPTION
      "Path: bridgeGroup.performance.mibCounters.h2Performance.ifInDiscards

       64 bit unsigned wrappable counter."
   ::= {pr1645v2BgrMVMibCountersH2PEntry 117440512}

pr1645v2BgrMVMibCountersH2PIfInErrors OBJECT-TYPE
   SYNTAX      Counter64
   MAX-ACCESS  read-only
   STATUS      current
   DESCRIPTION
      "Path: bridgeGroup.performance.mibCounters.h2Performance.ifInErrors

       64 bit unsigned wrappable counter."
   ::= {pr1645v2BgrMVMibCountersH2PEntry 134217728}

pr1645v2BgrMVMibCountersH2PIfInUnkwn OBJECT-TYPE
   SYNTAX      Counter64
   MAX-ACCESS  read-only
   STATUS      current
   DESCRIPTION
      "Path: bridgeGroup.performance.mibCounters.h2Performance.ifInUnknownProtos

       64 bit unsigned wrappable counter."
   ::= {pr1645v2BgrMVMibCountersH2PEntry 150994944}

pr1645v2BgrMVMibCountersH2PInDropEx OBJECT-TYPE
   SYNTAX      Counter64
   MAX-ACCESS  read-only
   STATUS      current
   DESCRIPTION
      "Path: bridgeGroup.performance.mibCounters.h2Performance.ifInDropLevelExceeded

       64 bit unsigned wrappable counter."
   ::= {pr1645v2BgrMVMibCountersH2PEntry 335544320}

pr1645v2BgrMVMibCountersH2PInDropNoMac OBJECT-TYPE
   SYNTAX      Counter64
   MAX-ACCESS  read-only
   STATUS      current
   DESCRIPTION
      "Path: bridgeGroup.performance.mibCounters.h2Performance.fInDiscardsNoMacFit

       64 bit unsigned wrappable counter."
   ::= {pr1645v2BgrMVMibCountersH2PEntry 301989888}

pr1645v2BgrMVMibCountersH2PInDropNUCast OBJECT-TYPE
   SYNTAX      Counter64
   MAX-ACCESS  read-only
   STATUS      current
   DESCRIPTION
      "Path: bridgeGroup.performance.mibCounters.h2Performance.fInDiscardsNUCast

       64 bit unsigned wrappable counter."
   ::= {pr1645v2BgrMVMibCountersH2PEntry 318767104}

pr1645v2BgrMVMibCountersH2PInDropFilter OBJECT-TYPE
   SYNTAX      Counter64
   MAX-ACCESS  read-only
   STATUS      current
   DESCRIPTION
      "Path: bridgeGroup.performance.mibCounters.h2Performance.fInDiscardsFilter

       64 bit unsigned wrappable counter."
   ::= {pr1645v2BgrMVMibCountersH2PEntry 385875968}

pr1645v2BgrMVMibCountersH2PIfInBandwidth OBJECT-TYPE
   SYNTAX      Integer32
   MAX-ACCESS  read-only
   STATUS      current
   DESCRIPTION
      "Path: bridgeGroup.performance.mibCounters.h2Performance.ifInBandwidth

       unit name = bps
       formula = 8 * ; 8 /"
   ::= {pr1645v2BgrMVMibCountersH2PEntry 268435456}

pr1645v2BgrMVMibCountersH2PIfOutOctets OBJECT-TYPE
   SYNTAX      Counter64
   MAX-ACCESS  read-only
   STATUS      current
   DESCRIPTION
      "Path: bridgeGroup.performance.mibCounters.h2Performance.ifOutOctets

       64 bit unsigned wrappable counter."
   ::= {pr1645v2BgrMVMibCountersH2PEntry 167772160}

pr1645v2BgrMVMibCountersH2PIfOutUCPkts OBJECT-TYPE
   SYNTAX      Counter64
   MAX-ACCESS  read-only
   STATUS      current
   DESCRIPTION
      "Path: bridgeGroup.performance.mibCounters.h2Performance.ifOutUcastPkts

       64 bit unsigned wrappable counter."
   ::= {pr1645v2BgrMVMibCountersH2PEntry 184549376}

pr1645v2BgrMVMibCountersH2PIfOutNUCPkts OBJECT-TYPE
   SYNTAX      Counter64
   MAX-ACCESS  read-only
   STATUS      current
   DESCRIPTION
      "Path: bridgeGroup.performance.mibCounters.h2Performance.ifOutNUcastPkts

       64 bit unsigned wrappable counter."
   ::= {pr1645v2BgrMVMibCountersH2PEntry 201326592}

pr1645v2BgrMVMibCountersH2PIfOutBCPkts OBJECT-TYPE
   SYNTAX      Counter64
   MAX-ACCESS  read-only
   STATUS      current
   DESCRIPTION
      "Path: bridgeGroup.performance.mibCounters.h2Performance.ifOutBcastPkts

       64 bit unsigned wrappable counter."
   ::= {pr1645v2BgrMVMibCountersH2PEntry 452984832}

pr1645v2BgrMVMibCountersH2PIfOutMCPkts OBJECT-TYPE
   SYNTAX      Counter64
   MAX-ACCESS  read-only
   STATUS      current
   DESCRIPTION
      "Path: bridgeGroup.performance.mibCounters.h2Performance.ifOutMcastPkts

       64 bit unsigned wrappable counter."
   ::= {pr1645v2BgrMVMibCountersH2PEntry 469762048}

pr1645v2BgrMVMibCountersH2PIfOutDiscards OBJECT-TYPE
   SYNTAX      Counter64
   MAX-ACCESS  read-only
   STATUS      current
   DESCRIPTION
      "Path: bridgeGroup.performance.mibCounters.h2Performance.ifOutDiscards

       64 bit unsigned wrappable counter."
   ::= {pr1645v2BgrMVMibCountersH2PEntry 218103808}

pr1645v2BgrMVMibCountersH2PIfOutErrors OBJECT-TYPE
   SYNTAX      Counter64
   MAX-ACCESS  read-only
   STATUS      current
   DESCRIPTION
      "Path: bridgeGroup.performance.mibCounters.h2Performance.ifOutErrors

       64 bit unsigned wrappable counter."
   ::= {pr1645v2BgrMVMibCountersH2PEntry 234881024}

pr1645v2BgrMVMibCountersH2POutDropEx OBJECT-TYPE
   SYNTAX      Counter64
   MAX-ACCESS  read-only
   STATUS      current
   DESCRIPTION
      "Path: bridgeGroup.performance.mibCounters.h2Performance.ifOutDropLevelExceeded

       64 bit unsigned wrappable counter."
   ::= {pr1645v2BgrMVMibCountersH2PEntry 352321536}

pr1645v2BgrMVMibCountersH2POutDropNoArp OBJECT-TYPE
   SYNTAX      Counter64
   MAX-ACCESS  read-only
   STATUS      current
   DESCRIPTION
      "Path: bridgeGroup.performance.mibCounters.h2Performance.ifOutDiscardsNoArp

       64 bit unsigned wrappable counter."
   ::= {pr1645v2BgrMVMibCountersH2PEntry 369098752}

pr1645v2BgrMVMibCountersH2POutDropFilter OBJECT-TYPE
   SYNTAX      Counter64
   MAX-ACCESS  read-only
   STATUS      current
   DESCRIPTION
      "Path: bridgeGroup.performance.mibCounters.h2Performance.ifOutDiscardsFilter

       64 bit unsigned wrappable counter."
   ::= {pr1645v2BgrMVMibCountersH2PEntry 402653184}

pr1645v2BgrMVMibCountersH2PIfOutBandwidth OBJECT-TYPE
   SYNTAX      Integer32
   MAX-ACCESS  read-only
   STATUS      current
   DESCRIPTION
      "Path: bridgeGroup.performance.mibCounters.h2Performance.ifOutBandwidth

       unit name = bps
       formula = 8 * ; 8 /"
   ::= {pr1645v2BgrMVMibCountersH2PEntry 285212672}

pr1645v2BgrMVMibCountersH2PIfErrSec OBJECT-TYPE
   SYNTAX      Counter32
   MAX-ACCESS  read-only
   STATUS      current
   DESCRIPTION
      "Path: bridgeGroup.performance.mibCounters.h2Performance.ifErrSec

       32 bit unsigned wrappable counter."
   ::= {pr1645v2BgrMVMibCountersH2PEntry 251658240}

pr1645v2BgrMVMibCountersH24P OBJECT-TYPE
   SYNTAX      SEQUENCE OF Pr1645v2BgrMVMibCountersH24PEntry
   MAX-ACCESS  not-accessible
   STATUS      current
   DESCRIPTION
      ""
   ::= {pr1645v2BgrMVMibCounters 2063597568}

pr1645v2BgrMVMibCountersH24PEntry OBJECT-TYPE
   SYNTAX      Pr1645v2BgrMVMibCountersH24PEntry
   MAX-ACCESS  not-accessible
   STATUS      current
   DESCRIPTION
      ""
   INDEX      { pr1645v2BgrMVMibCountersH24PTableIx }
   ::= {pr1645v2BgrMVMibCountersH24P 1}

Pr1645v2BgrMVMibCountersH24PEntry ::=
   SEQUENCE
      {
      pr1645v2BgrMVMibCountersH24PTableIx
         TableIndex,
      pr1645v2BgrMVMibCountersH24PSysUpTime
         TimeTicks,
      pr1645v2BgrMVMibCountersH24PIfUpTime
         TimeTicks,
      pr1645v2BgrMVMibCountersH24PIfStatChanges
         Counter32,
      pr1645v2BgrMVMibCountersH24PIfInOctets
         Counter64,
      pr1645v2BgrMVMibCountersH24PIfInUCPkts
         Counter64,
      pr1645v2BgrMVMibCountersH24PIfInNUCPkts
         Counter64,
      pr1645v2BgrMVMibCountersH24PIfInBCPkts
         Counter64,
      pr1645v2BgrMVMibCountersH24PIfInMCPkts
         Counter64,
      pr1645v2BgrMVMibCountersH24PIfInDiscards
         Counter64,
      pr1645v2BgrMVMibCountersH24PIfInErrors
         Counter64,
      pr1645v2BgrMVMibCountersH24PIfInUnkwn
         Counter64,
      pr1645v2BgrMVMibCountersH24PInDropEx
         Counter64,
      pr1645v2BgrMVMibCountersH24PInDropNoMac
         Counter64,
      pr1645v2BgrMVMibCountersH24PInDropNUCast
         Counter64,
      pr1645v2BgrMVMibCountersH24PInDropFilter
         Counter64,
      pr1645v2BgrMVMibCountersH24PIfInBandwidth
         Integer32,
      pr1645v2BgrMVMibCountersH24PIfOutOctets
         Counter64,
      pr1645v2BgrMVMibCountersH24PIfOutUCPkts
         Counter64,
      pr1645v2BgrMVMibCountersH24PIfOutNUCPkts
         Counter64,
      pr1645v2BgrMVMibCountersH24PIfOutBCPkts
         Counter64,
      pr1645v2BgrMVMibCountersH24PIfOutMCPkts
         Counter64,
      pr1645v2BgrMVMibCountersH24PIfOutDiscards
         Counter64,
      pr1645v2BgrMVMibCountersH24PIfOutErrors
         Counter64,
      pr1645v2BgrMVMibCountersH24POutDropEx
         Counter64,
      pr1645v2BgrMVMibCountersH24POutDropNoArp
         Counter64,
      pr1645v2BgrMVMibCountersH24POutDropFilter
         Counter64,
      pr1645v2BgrMVMibCountersH24PIfOutBandwidth
         Integer32,
      pr1645v2BgrMVMibCountersH24PIfErrSec
         Counter32
      }

pr1645v2BgrMVMibCountersH24PTableIx OBJECT-TYPE
   SYNTAX      TableIndex
   MAX-ACCESS  not-accessible
   STATUS      current
   DESCRIPTION
      ""
   ::= {pr1645v2BgrMVMibCountersH24PEntry 11}

pr1645v2BgrMVMibCountersH24PSysUpTime OBJECT-TYPE
   SYNTAX      TimeTicks
   MAX-ACCESS  read-only
   STATUS      current
   DESCRIPTION
      "Path: bridgeGroup.performance.mibCounters.h24Performance.sysUpTime

       Time in centi-second."
   ::= {pr1645v2BgrMVMibCountersH24PEntry 16777216}

pr1645v2BgrMVMibCountersH24PIfUpTime OBJECT-TYPE
   SYNTAX      TimeTicks
   MAX-ACCESS  read-only
   STATUS      current
   DESCRIPTION
      "Path: bridgeGroup.performance.mibCounters.h24Performance.ifUpTime

       Time in centi-second."
   ::= {pr1645v2BgrMVMibCountersH24PEntry 33554432}

pr1645v2BgrMVMibCountersH24PIfStatChanges OBJECT-TYPE
   SYNTAX      Counter32
   MAX-ACCESS  read-only
   STATUS      current
   DESCRIPTION
      "Path: bridgeGroup.performance.mibCounters.h24Performance.ifStatusChanges

       32 bit unsigned wrappable counter."
   ::= {pr1645v2BgrMVMibCountersH24PEntry 50331648}

pr1645v2BgrMVMibCountersH24PIfInOctets OBJECT-TYPE
   SYNTAX      Counter64
   MAX-ACCESS  read-only
   STATUS      current
   DESCRIPTION
      "Path: bridgeGroup.performance.mibCounters.h24Performance.ifInOctets

       64 bit unsigned wrappable counter."
   ::= {pr1645v2BgrMVMibCountersH24PEntry 67108864}

pr1645v2BgrMVMibCountersH24PIfInUCPkts OBJECT-TYPE
   SYNTAX      Counter64
   MAX-ACCESS  read-only
   STATUS      current
   DESCRIPTION
      "Path: bridgeGroup.performance.mibCounters.h24Performance.ifInUcastPkts

       64 bit unsigned wrappable counter."
   ::= {pr1645v2BgrMVMibCountersH24PEntry 83886080}

pr1645v2BgrMVMibCountersH24PIfInNUCPkts OBJECT-TYPE
   SYNTAX      Counter64
   MAX-ACCESS  read-only
   STATUS      current
   DESCRIPTION
      "Path: bridgeGroup.performance.mibCounters.h24Performance.ifInNUcastPkts

       64 bit unsigned wrappable counter."
   ::= {pr1645v2BgrMVMibCountersH24PEntry 100663296}

pr1645v2BgrMVMibCountersH24PIfInBCPkts OBJECT-TYPE
   SYNTAX      Counter64
   MAX-ACCESS  read-only
   STATUS      current
   DESCRIPTION
      "Path: bridgeGroup.performance.mibCounters.h24Performance.ifInBcastPkts

       64 bit unsigned wrappable counter."
   ::= {pr1645v2BgrMVMibCountersH24PEntry 419430400}

pr1645v2BgrMVMibCountersH24PIfInMCPkts OBJECT-TYPE
   SYNTAX      Counter64
   MAX-ACCESS  read-only
   STATUS      current
   DESCRIPTION
      "Path: bridgeGroup.performance.mibCounters.h24Performance.ifInMcastPkts

       64 bit unsigned wrappable counter."
   ::= {pr1645v2BgrMVMibCountersH24PEntry 436207616}

pr1645v2BgrMVMibCountersH24PIfInDiscards OBJECT-TYPE
   SYNTAX      Counter64
   MAX-ACCESS  read-only
   STATUS      current
   DESCRIPTION
      "Path: bridgeGroup.performance.mibCounters.h24Performance.ifInDiscards

       64 bit unsigned wrappable counter."
   ::= {pr1645v2BgrMVMibCountersH24PEntry 117440512}

pr1645v2BgrMVMibCountersH24PIfInErrors OBJECT-TYPE
   SYNTAX      Counter64
   MAX-ACCESS  read-only
   STATUS      current
   DESCRIPTION
      "Path: bridgeGroup.performance.mibCounters.h24Performance.ifInErrors

       64 bit unsigned wrappable counter."
   ::= {pr1645v2BgrMVMibCountersH24PEntry 134217728}

pr1645v2BgrMVMibCountersH24PIfInUnkwn OBJECT-TYPE
   SYNTAX      Counter64
   MAX-ACCESS  read-only
   STATUS      current
   DESCRIPTION
      "Path: bridgeGroup.performance.mibCounters.h24Performance.ifInUnknownProtos

       64 bit unsigned wrappable counter."
   ::= {pr1645v2BgrMVMibCountersH24PEntry 150994944}

pr1645v2BgrMVMibCountersH24PInDropEx OBJECT-TYPE
   SYNTAX      Counter64
   MAX-ACCESS  read-only
   STATUS      current
   DESCRIPTION
      "Path: bridgeGroup.performance.mibCounters.h24Performance.ifInDropLevelExceeded

       64 bit unsigned wrappable counter."
   ::= {pr1645v2BgrMVMibCountersH24PEntry 335544320}

pr1645v2BgrMVMibCountersH24PInDropNoMac OBJECT-TYPE
   SYNTAX      Counter64
   MAX-ACCESS  read-only
   STATUS      current
   DESCRIPTION
      "Path: bridgeGroup.performance.mibCounters.h24Performance.fInDiscardsNoMacFit

       64 bit unsigned wrappable counter."
   ::= {pr1645v2BgrMVMibCountersH24PEntry 301989888}

pr1645v2BgrMVMibCountersH24PInDropNUCast OBJECT-TYPE
   SYNTAX      Counter64
   MAX-ACCESS  read-only
   STATUS      current
   DESCRIPTION
      "Path: bridgeGroup.performance.mibCounters.h24Performance.fInDiscardsNUCast

       64 bit unsigned wrappable counter."
   ::= {pr1645v2BgrMVMibCountersH24PEntry 318767104}

pr1645v2BgrMVMibCountersH24PInDropFilter OBJECT-TYPE
   SYNTAX      Counter64
   MAX-ACCESS  read-only
   STATUS      current
   DESCRIPTION
      "Path: bridgeGroup.performance.mibCounters.h24Performance.fInDiscardsFilter

       64 bit unsigned wrappable counter."
   ::= {pr1645v2BgrMVMibCountersH24PEntry 385875968}

pr1645v2BgrMVMibCountersH24PIfInBandwidth OBJECT-TYPE
   SYNTAX      Integer32
   MAX-ACCESS  read-only
   STATUS      current
   DESCRIPTION
      "Path: bridgeGroup.performance.mibCounters.h24Performance.ifInBandwidth

       unit name = bps
       formula = 8 * ; 8 /"
   ::= {pr1645v2BgrMVMibCountersH24PEntry 268435456}

pr1645v2BgrMVMibCountersH24PIfOutOctets OBJECT-TYPE
   SYNTAX      Counter64
   MAX-ACCESS  read-only
   STATUS      current
   DESCRIPTION
      "Path: bridgeGroup.performance.mibCounters.h24Performance.ifOutOctets

       64 bit unsigned wrappable counter."
   ::= {pr1645v2BgrMVMibCountersH24PEntry 167772160}

pr1645v2BgrMVMibCountersH24PIfOutUCPkts OBJECT-TYPE
   SYNTAX      Counter64
   MAX-ACCESS  read-only
   STATUS      current
   DESCRIPTION
      "Path: bridgeGroup.performance.mibCounters.h24Performance.ifOutUcastPkts

       64 bit unsigned wrappable counter."
   ::= {pr1645v2BgrMVMibCountersH24PEntry 184549376}

pr1645v2BgrMVMibCountersH24PIfOutNUCPkts OBJECT-TYPE
   SYNTAX      Counter64
   MAX-ACCESS  read-only
   STATUS      current
   DESCRIPTION
      "Path: bridgeGroup.performance.mibCounters.h24Performance.ifOutNUcastPkts

       64 bit unsigned wrappable counter."
   ::= {pr1645v2BgrMVMibCountersH24PEntry 201326592}

pr1645v2BgrMVMibCountersH24PIfOutBCPkts OBJECT-TYPE
   SYNTAX      Counter64
   MAX-ACCESS  read-only
   STATUS      current
   DESCRIPTION
      "Path: bridgeGroup.performance.mibCounters.h24Performance.ifOutBcastPkts

       64 bit unsigned wrappable counter."
   ::= {pr1645v2BgrMVMibCountersH24PEntry 452984832}

pr1645v2BgrMVMibCountersH24PIfOutMCPkts OBJECT-TYPE
   SYNTAX      Counter64
   MAX-ACCESS  read-only
   STATUS      current
   DESCRIPTION
      "Path: bridgeGroup.performance.mibCounters.h24Performance.ifOutMcastPkts

       64 bit unsigned wrappable counter."
   ::= {pr1645v2BgrMVMibCountersH24PEntry 469762048}

pr1645v2BgrMVMibCountersH24PIfOutDiscards OBJECT-TYPE
   SYNTAX      Counter64
   MAX-ACCESS  read-only
   STATUS      current
   DESCRIPTION
      "Path: bridgeGroup.performance.mibCounters.h24Performance.ifOutDiscards

       64 bit unsigned wrappable counter."
   ::= {pr1645v2BgrMVMibCountersH24PEntry 218103808}

pr1645v2BgrMVMibCountersH24PIfOutErrors OBJECT-TYPE
   SYNTAX      Counter64
   MAX-ACCESS  read-only
   STATUS      current
   DESCRIPTION
      "Path: bridgeGroup.performance.mibCounters.h24Performance.ifOutErrors

       64 bit unsigned wrappable counter."
   ::= {pr1645v2BgrMVMibCountersH24PEntry 234881024}

pr1645v2BgrMVMibCountersH24POutDropEx OBJECT-TYPE
   SYNTAX      Counter64
   MAX-ACCESS  read-only
   STATUS      current
   DESCRIPTION
      "Path: bridgeGroup.performance.mibCounters.h24Performance.ifOutDropLevelExceeded

       64 bit unsigned wrappable counter."
   ::= {pr1645v2BgrMVMibCountersH24PEntry 352321536}

pr1645v2BgrMVMibCountersH24POutDropNoArp OBJECT-TYPE
   SYNTAX      Counter64
   MAX-ACCESS  read-only
   STATUS      current
   DESCRIPTION
      "Path: bridgeGroup.performance.mibCounters.h24Performance.ifOutDiscardsNoArp

       64 bit unsigned wrappable counter."
   ::= {pr1645v2BgrMVMibCountersH24PEntry 369098752}

pr1645v2BgrMVMibCountersH24POutDropFilter OBJECT-TYPE
   SYNTAX      Counter64
   MAX-ACCESS  read-only
   STATUS      current
   DESCRIPTION
      "Path: bridgeGroup.performance.mibCounters.h24Performance.ifOutDiscardsFilter

       64 bit unsigned wrappable counter."
   ::= {pr1645v2BgrMVMibCountersH24PEntry 402653184}

pr1645v2BgrMVMibCountersH24PIfOutBandwidth OBJECT-TYPE
   SYNTAX      Integer32
   MAX-ACCESS  read-only
   STATUS      current
   DESCRIPTION
      "Path: bridgeGroup.performance.mibCounters.h24Performance.ifOutBandwidth

       unit name = bps
       formula = 8 * ; 8 /"
   ::= {pr1645v2BgrMVMibCountersH24PEntry 285212672}

pr1645v2BgrMVMibCountersH24PIfErrSec OBJECT-TYPE
   SYNTAX      Counter32
   MAX-ACCESS  read-only
   STATUS      current
   DESCRIPTION
      "Path: bridgeGroup.performance.mibCounters.h24Performance.ifErrSec

       32 bit unsigned wrappable counter."
   ::= {pr1645v2BgrMVMibCountersH24PEntry 251658240}

pr1645v2BgrMVMibCountersD7P OBJECT-TYPE
   SYNTAX      SEQUENCE OF Pr1645v2BgrMVMibCountersD7PEntry
   MAX-ACCESS  not-accessible
   STATUS      current
   DESCRIPTION
      ""
   ::= {pr1645v2BgrMVMibCounters 2080374784}

pr1645v2BgrMVMibCountersD7PEntry OBJECT-TYPE
   SYNTAX      Pr1645v2BgrMVMibCountersD7PEntry
   MAX-ACCESS  not-accessible
   STATUS      current
   DESCRIPTION
      ""
   INDEX      { pr1645v2BgrMVMibCountersD7PTableIx }
   ::= {pr1645v2BgrMVMibCountersD7P 1}

Pr1645v2BgrMVMibCountersD7PEntry ::=
   SEQUENCE
      {
      pr1645v2BgrMVMibCountersD7PTableIx
         TableIndex,
      pr1645v2BgrMVMibCountersD7PSysUpTime
         TimeTicks,
      pr1645v2BgrMVMibCountersD7PIfUpTime
         TimeTicks,
      pr1645v2BgrMVMibCountersD7PIfStatChanges
         Counter32,
      pr1645v2BgrMVMibCountersD7PIfInOctets
         Counter64,
      pr1645v2BgrMVMibCountersD7PIfInUCPkts
         Counter64,
      pr1645v2BgrMVMibCountersD7PIfInNUCPkts
         Counter64,
      pr1645v2BgrMVMibCountersD7PIfInBCPkts
         Counter64,
      pr1645v2BgrMVMibCountersD7PIfInMCPkts
         Counter64,
      pr1645v2BgrMVMibCountersD7PIfInDiscards
         Counter64,
      pr1645v2BgrMVMibCountersD7PIfInErrors
         Counter64,
      pr1645v2BgrMVMibCountersD7PIfInUnkwn
         Counter64,
      pr1645v2BgrMVMibCountersD7PInDropEx
         Counter64,
      pr1645v2BgrMVMibCountersD7PInDropNoMac
         Counter64,
      pr1645v2BgrMVMibCountersD7PInDropNUCast
         Counter64,
      pr1645v2BgrMVMibCountersD7PInDropFilter
         Counter64,
      pr1645v2BgrMVMibCountersD7PIfInBandwidth
         Integer32,
      pr1645v2BgrMVMibCountersD7PIfOutOctets
         Counter64,
      pr1645v2BgrMVMibCountersD7PIfOutUCPkts
         Counter64,
      pr1645v2BgrMVMibCountersD7PIfOutNUCPkts
         Counter64,
      pr1645v2BgrMVMibCountersD7PIfOutBCPkts
         Counter64,
      pr1645v2BgrMVMibCountersD7PIfOutMCPkts
         Counter64,
      pr1645v2BgrMVMibCountersD7PIfOutDiscards
         Counter64,
      pr1645v2BgrMVMibCountersD7PIfOutErrors
         Counter64,
      pr1645v2BgrMVMibCountersD7POutDropEx
         Counter64,
      pr1645v2BgrMVMibCountersD7POutDropNoArp
         Counter64,
      pr1645v2BgrMVMibCountersD7POutDropFilter
         Counter64,
      pr1645v2BgrMVMibCountersD7PIfOutBandwidth
         Integer32,
      pr1645v2BgrMVMibCountersD7PIfErrSec
         Counter32
      }

pr1645v2BgrMVMibCountersD7PTableIx OBJECT-TYPE
   SYNTAX      TableIndex
   MAX-ACCESS  not-accessible
   STATUS      current
   DESCRIPTION
      ""
   ::= {pr1645v2BgrMVMibCountersD7PEntry 11}

pr1645v2BgrMVMibCountersD7PSysUpTime OBJECT-TYPE
   SYNTAX      TimeTicks
   MAX-ACCESS  read-only
   STATUS      current
   DESCRIPTION
      "Path: bridgeGroup.performance.mibCounters.d7Performance.sysUpTime

       Time in centi-second."
   ::= {pr1645v2BgrMVMibCountersD7PEntry 16777216}

pr1645v2BgrMVMibCountersD7PIfUpTime OBJECT-TYPE
   SYNTAX      TimeTicks
   MAX-ACCESS  read-only
   STATUS      current
   DESCRIPTION
      "Path: bridgeGroup.performance.mibCounters.d7Performance.ifUpTime

       Time in centi-second."
   ::= {pr1645v2BgrMVMibCountersD7PEntry 33554432}

pr1645v2BgrMVMibCountersD7PIfStatChanges OBJECT-TYPE
   SYNTAX      Counter32
   MAX-ACCESS  read-only
   STATUS      current
   DESCRIPTION
      "Path: bridgeGroup.performance.mibCounters.d7Performance.ifStatusChanges

       32 bit unsigned wrappable counter."
   ::= {pr1645v2BgrMVMibCountersD7PEntry 50331648}

pr1645v2BgrMVMibCountersD7PIfInOctets OBJECT-TYPE
   SYNTAX      Counter64
   MAX-ACCESS  read-only
   STATUS      current
   DESCRIPTION
      "Path: bridgeGroup.performance.mibCounters.d7Performance.ifInOctets

       64 bit unsigned wrappable counter."
   ::= {pr1645v2BgrMVMibCountersD7PEntry 67108864}

pr1645v2BgrMVMibCountersD7PIfInUCPkts OBJECT-TYPE
   SYNTAX      Counter64
   MAX-ACCESS  read-only
   STATUS      current
   DESCRIPTION
      "Path: bridgeGroup.performance.mibCounters.d7Performance.ifInUcastPkts

       64 bit unsigned wrappable counter."
   ::= {pr1645v2BgrMVMibCountersD7PEntry 83886080}

pr1645v2BgrMVMibCountersD7PIfInNUCPkts OBJECT-TYPE
   SYNTAX      Counter64
   MAX-ACCESS  read-only
   STATUS      current
   DESCRIPTION
      "Path: bridgeGroup.performance.mibCounters.d7Performance.ifInNUcastPkts

       64 bit unsigned wrappable counter."
   ::= {pr1645v2BgrMVMibCountersD7PEntry 100663296}

pr1645v2BgrMVMibCountersD7PIfInBCPkts OBJECT-TYPE
   SYNTAX      Counter64
   MAX-ACCESS  read-only
   STATUS      current
   DESCRIPTION
      "Path: bridgeGroup.performance.mibCounters.d7Performance.ifInBcastPkts

       64 bit unsigned wrappable counter."
   ::= {pr1645v2BgrMVMibCountersD7PEntry 419430400}

pr1645v2BgrMVMibCountersD7PIfInMCPkts OBJECT-TYPE
   SYNTAX      Counter64
   MAX-ACCESS  read-only
   STATUS      current
   DESCRIPTION
      "Path: bridgeGroup.performance.mibCounters.d7Performance.ifInMcastPkts

       64 bit unsigned wrappable counter."
   ::= {pr1645v2BgrMVMibCountersD7PEntry 436207616}

pr1645v2BgrMVMibCountersD7PIfInDiscards OBJECT-TYPE
   SYNTAX      Counter64
   MAX-ACCESS  read-only
   STATUS      current
   DESCRIPTION
      "Path: bridgeGroup.performance.mibCounters.d7Performance.ifInDiscards

       64 bit unsigned wrappable counter."
   ::= {pr1645v2BgrMVMibCountersD7PEntry 117440512}

pr1645v2BgrMVMibCountersD7PIfInErrors OBJECT-TYPE
   SYNTAX      Counter64
   MAX-ACCESS  read-only
   STATUS      current
   DESCRIPTION
      "Path: bridgeGroup.performance.mibCounters.d7Performance.ifInErrors

       64 bit unsigned wrappable counter."
   ::= {pr1645v2BgrMVMibCountersD7PEntry 134217728}

pr1645v2BgrMVMibCountersD7PIfInUnkwn OBJECT-TYPE
   SYNTAX      Counter64
   MAX-ACCESS  read-only
   STATUS      current
   DESCRIPTION
      "Path: bridgeGroup.performance.mibCounters.d7Performance.ifInUnknownProtos

       64 bit unsigned wrappable counter."
   ::= {pr1645v2BgrMVMibCountersD7PEntry 150994944}

pr1645v2BgrMVMibCountersD7PInDropEx OBJECT-TYPE
   SYNTAX      Counter64
   MAX-ACCESS  read-only
   STATUS      current
   DESCRIPTION
      "Path: bridgeGroup.performance.mibCounters.d7Performance.ifInDropLevelExceeded

       64 bit unsigned wrappable counter."
   ::= {pr1645v2BgrMVMibCountersD7PEntry 335544320}

pr1645v2BgrMVMibCountersD7PInDropNoMac OBJECT-TYPE
   SYNTAX      Counter64
   MAX-ACCESS  read-only
   STATUS      current
   DESCRIPTION
      "Path: bridgeGroup.performance.mibCounters.d7Performance.fInDiscardsNoMacFit

       64 bit unsigned wrappable counter."
   ::= {pr1645v2BgrMVMibCountersD7PEntry 301989888}

pr1645v2BgrMVMibCountersD7PInDropNUCast OBJECT-TYPE
   SYNTAX      Counter64
   MAX-ACCESS  read-only
   STATUS      current
   DESCRIPTION
      "Path: bridgeGroup.performance.mibCounters.d7Performance.fInDiscardsNUCast

       64 bit unsigned wrappable counter."
   ::= {pr1645v2BgrMVMibCountersD7PEntry 318767104}

pr1645v2BgrMVMibCountersD7PInDropFilter OBJECT-TYPE
   SYNTAX      Counter64
   MAX-ACCESS  read-only
   STATUS      current
   DESCRIPTION
      "Path: bridgeGroup.performance.mibCounters.d7Performance.fInDiscardsFilter

       64 bit unsigned wrappable counter."
   ::= {pr1645v2BgrMVMibCountersD7PEntry 385875968}

pr1645v2BgrMVMibCountersD7PIfInBandwidth OBJECT-TYPE
   SYNTAX      Integer32
   MAX-ACCESS  read-only
   STATUS      current
   DESCRIPTION
      "Path: bridgeGroup.performance.mibCounters.d7Performance.ifInBandwidth

       unit name = bps
       formula = 8 * ; 8 /"
   ::= {pr1645v2BgrMVMibCountersD7PEntry 268435456}

pr1645v2BgrMVMibCountersD7PIfOutOctets OBJECT-TYPE
   SYNTAX      Counter64
   MAX-ACCESS  read-only
   STATUS      current
   DESCRIPTION
      "Path: bridgeGroup.performance.mibCounters.d7Performance.ifOutOctets

       64 bit unsigned wrappable counter."
   ::= {pr1645v2BgrMVMibCountersD7PEntry 167772160}

pr1645v2BgrMVMibCountersD7PIfOutUCPkts OBJECT-TYPE
   SYNTAX      Counter64
   MAX-ACCESS  read-only
   STATUS      current
   DESCRIPTION
      "Path: bridgeGroup.performance.mibCounters.d7Performance.ifOutUcastPkts

       64 bit unsigned wrappable counter."
   ::= {pr1645v2BgrMVMibCountersD7PEntry 184549376}

pr1645v2BgrMVMibCountersD7PIfOutNUCPkts OBJECT-TYPE
   SYNTAX      Counter64
   MAX-ACCESS  read-only
   STATUS      current
   DESCRIPTION
      "Path: bridgeGroup.performance.mibCounters.d7Performance.ifOutNUcastPkts

       64 bit unsigned wrappable counter."
   ::= {pr1645v2BgrMVMibCountersD7PEntry 201326592}

pr1645v2BgrMVMibCountersD7PIfOutBCPkts OBJECT-TYPE
   SYNTAX      Counter64
   MAX-ACCESS  read-only
   STATUS      current
   DESCRIPTION
      "Path: bridgeGroup.performance.mibCounters.d7Performance.ifOutBcastPkts

       64 bit unsigned wrappable counter."
   ::= {pr1645v2BgrMVMibCountersD7PEntry 452984832}

pr1645v2BgrMVMibCountersD7PIfOutMCPkts OBJECT-TYPE
   SYNTAX      Counter64
   MAX-ACCESS  read-only
   STATUS      current
   DESCRIPTION
      "Path: bridgeGroup.performance.mibCounters.d7Performance.ifOutMcastPkts

       64 bit unsigned wrappable counter."
   ::= {pr1645v2BgrMVMibCountersD7PEntry 469762048}

pr1645v2BgrMVMibCountersD7PIfOutDiscards OBJECT-TYPE
   SYNTAX      Counter64
   MAX-ACCESS  read-only
   STATUS      current
   DESCRIPTION
      "Path: bridgeGroup.performance.mibCounters.d7Performance.ifOutDiscards

       64 bit unsigned wrappable counter."
   ::= {pr1645v2BgrMVMibCountersD7PEntry 218103808}

pr1645v2BgrMVMibCountersD7PIfOutErrors OBJECT-TYPE
   SYNTAX      Counter64
   MAX-ACCESS  read-only
   STATUS      current
   DESCRIPTION
      "Path: bridgeGroup.performance.mibCounters.d7Performance.ifOutErrors

       64 bit unsigned wrappable counter."
   ::= {pr1645v2BgrMVMibCountersD7PEntry 234881024}

pr1645v2BgrMVMibCountersD7POutDropEx OBJECT-TYPE
   SYNTAX      Counter64
   MAX-ACCESS  read-only
   STATUS      current
   DESCRIPTION
      "Path: bridgeGroup.performance.mibCounters.d7Performance.ifOutDropLevelExceeded

       64 bit unsigned wrappable counter."
   ::= {pr1645v2BgrMVMibCountersD7PEntry 352321536}

pr1645v2BgrMVMibCountersD7POutDropNoArp OBJECT-TYPE
   SYNTAX      Counter64
   MAX-ACCESS  read-only
   STATUS      current
   DESCRIPTION
      "Path: bridgeGroup.performance.mibCounters.d7Performance.ifOutDiscardsNoArp

       64 bit unsigned wrappable counter."
   ::= {pr1645v2BgrMVMibCountersD7PEntry 369098752}

pr1645v2BgrMVMibCountersD7POutDropFilter OBJECT-TYPE
   SYNTAX      Counter64
   MAX-ACCESS  read-only
   STATUS      current
   DESCRIPTION
      "Path: bridgeGroup.performance.mibCounters.d7Performance.ifOutDiscardsFilter

       64 bit unsigned wrappable counter."
   ::= {pr1645v2BgrMVMibCountersD7PEntry 402653184}

pr1645v2BgrMVMibCountersD7PIfOutBandwidth OBJECT-TYPE
   SYNTAX      Integer32
   MAX-ACCESS  read-only
   STATUS      current
   DESCRIPTION
      "Path: bridgeGroup.performance.mibCounters.d7Performance.ifOutBandwidth

       unit name = bps
       formula = 8 * ; 8 /"
   ::= {pr1645v2BgrMVMibCountersD7PEntry 285212672}

pr1645v2BgrMVMibCountersD7PIfErrSec OBJECT-TYPE
   SYNTAX      Counter32
   MAX-ACCESS  read-only
   STATUS      current
   DESCRIPTION
      "Path: bridgeGroup.performance.mibCounters.d7Performance.ifErrSec

       32 bit unsigned wrappable counter."
   ::= {pr1645v2BgrMVMibCountersD7PEntry 251658240}


pr1645v2BgrMVBridging OBJECT IDENTIFIER ::= {pr1645v2BgrMV 90}

pr1645v2BgrMVBridgingSSCTable OBJECT-TYPE
   SYNTAX      SEQUENCE OF Pr1645v2BgrMVBridgingEntry
   MAX-ACCESS  not-accessible
   STATUS      current
   DESCRIPTION
      " bridge-port performance"
   ::= {pr1645v2BgrMVBridging 1}

pr1645v2BgrMVBridgingEntry OBJECT-TYPE
   SYNTAX      Pr1645v2BgrMVBridgingEntry
   MAX-ACCESS  not-accessible
   STATUS      current
   DESCRIPTION
      ""
   INDEX      { pr1645v2BgrMVBridgingTableIx }
   ::= {pr1645v2BgrMVBridgingSSCTable 1}

Pr1645v2BgrMVBridgingEntry ::=
   SEQUENCE
      {
      pr1645v2BgrMVBridgingTableIx
         TableIndex,
      pr1645v2BgrMVBridgingName
         DisplayString,
      pr1645v2BgrMVBridgingRxPkts
         Counter32,
      pr1645v2BgrMVBridgingTxPkts
         Counter32,
      pr1645v2BgrMVBridgingRxDiscards
         Counter32,
      pr1645v2BgrMVBridgingRxFloods
         Counter32,
      pr1645v2BgrMVBridgingRxBroadcasts
         Counter32,
      pr1645v2BgrMVBridgingRxMulticasts
         Counter32,
      pr1645v2BgrMVBridgingCacheSizeOverflows
         Counter32,
      pr1645v2BgrMVBridgingCacheStaticViolations
         Counter32,
      pr1645v2BgrMVBridgingCacheRelearns
         Counter32,
      pr1645v2BgrMVBridgingCacheRelearnDrops
         Counter32,
      pr1645v2BgrMVBridgingCacheLoopsDetected
         Counter32,
      pr1645v2BgrMVBridgingVlanMemberShipRxDiscards
         Counter32,
      pr1645v2BgrMVBridgingVlanMemberShipTxDiscards
         Counter32,
      pr1645v2BgrMVBridgingSpanningTreeRxMstp
         Integer32,
      pr1645v2BgrMVBridgingSpanningTreeRxRstp
         Integer32,
      pr1645v2BgrMVBridgingSpanningTreeRxConfig
         Integer32,
      pr1645v2BgrMVBridgingSpanningTreeRxTcn
         Integer32,
      pr1645v2BgrMVBridgingSpanningTreeRxDiscards
         Integer32,
      pr1645v2BgrMVBridgingSpanningTreeTxMstp
         Integer32,
      pr1645v2BgrMVBridgingSpanningTreeTxRstp
         Integer32,
      pr1645v2BgrMVBridgingSpanningTreeTxConfig
         Integer32,
      pr1645v2BgrMVBridgingSpanningTreeTxTcn
         Integer32
      }

pr1645v2BgrMVBridgingTableIx OBJECT-TYPE
   SYNTAX      TableIndex
   MAX-ACCESS  not-accessible
   STATUS      current
   DESCRIPTION
      ""
   ::= {pr1645v2BgrMVBridgingEntry 11}

pr1645v2BgrMVBridgingName OBJECT-TYPE
   SYNTAX      DisplayString
   MAX-ACCESS  read-only
   STATUS      current
   DESCRIPTION
      "Path: bridgeGroup.performance.bridging.name"
   ::= {pr1645v2BgrMVBridgingEntry 16777216}

pr1645v2BgrMVBridgingRxPkts OBJECT-TYPE
   SYNTAX      Counter32
   MAX-ACCESS  read-only
   STATUS      current
   DESCRIPTION
      "Path: bridgeGroup.performance.bridging.rxPkts

       32 bit unsigned wrappable counter."
   ::= {pr1645v2BgrMVBridgingEntry 33554432}

pr1645v2BgrMVBridgingTxPkts OBJECT-TYPE
   SYNTAX      Counter32
   MAX-ACCESS  read-only
   STATUS      current
   DESCRIPTION
      "Path: bridgeGroup.performance.bridging.txPkts

       32 bit unsigned wrappable counter."
   ::= {pr1645v2BgrMVBridgingEntry 50331648}

pr1645v2BgrMVBridgingRxDiscards OBJECT-TYPE
   SYNTAX      Counter32
   MAX-ACCESS  read-only
   STATUS      current
   DESCRIPTION
      "Path: bridgeGroup.performance.bridging.rxDiscards

       32 bit unsigned wrappable counter."
   ::= {pr1645v2BgrMVBridgingEntry 67108864}

pr1645v2BgrMVBridgingRxFloods OBJECT-TYPE
   SYNTAX      Counter32
   MAX-ACCESS  read-only
   STATUS      current
   DESCRIPTION
      "Path: bridgeGroup.performance.bridging.rxFloods

       32 bit unsigned wrappable counter."
   ::= {pr1645v2BgrMVBridgingEntry 83886080}

pr1645v2BgrMVBridgingRxBroadcasts OBJECT-TYPE
   SYNTAX      Counter32
   MAX-ACCESS  read-only
   STATUS      current
   DESCRIPTION
      "Path: bridgeGroup.performance.bridging.rxBroadcasts

       32 bit unsigned wrappable counter."
   ::= {pr1645v2BgrMVBridgingEntry 100663296}

pr1645v2BgrMVBridgingRxMulticasts OBJECT-TYPE
   SYNTAX      Counter32
   MAX-ACCESS  read-only
   STATUS      current
   DESCRIPTION
      "Path: bridgeGroup.performance.bridging.rxMulticasts

       32 bit unsigned wrappable counter."
   ::= {pr1645v2BgrMVBridgingEntry 117440512}

pr1645v2BgrMVBridgingCacheSizeOverflows OBJECT-TYPE
   SYNTAX      Counter32
   MAX-ACCESS  read-only
   STATUS      current
   DESCRIPTION
      "Path: bridgeGroup.performance.bridging.cache.sizeOverflows

       32 bit unsigned wrappable counter."
   ::= {pr1645v2BgrMVBridgingEntry 134283264}

pr1645v2BgrMVBridgingCacheStaticViolations OBJECT-TYPE
   SYNTAX      Counter32
   MAX-ACCESS  read-only
   STATUS      current
   DESCRIPTION
      "Path: bridgeGroup.performance.bridging.cache.staticViolations

       32 bit unsigned wrappable counter."
   ::= {pr1645v2BgrMVBridgingEntry 134348800}

pr1645v2BgrMVBridgingCacheRelearns OBJECT-TYPE
   SYNTAX      Counter32
   MAX-ACCESS  read-only
   STATUS      current
   DESCRIPTION
      "Path: bridgeGroup.performance.bridging.cache.relearns

       32 bit unsigned wrappable counter."
   ::= {pr1645v2BgrMVBridgingEntry 134414336}

pr1645v2BgrMVBridgingCacheRelearnDrops OBJECT-TYPE
   SYNTAX      Counter32
   MAX-ACCESS  read-only
   STATUS      current
   DESCRIPTION
      "Path: bridgeGroup.performance.bridging.cache.relearnDrops

       32 bit unsigned wrappable counter."
   ::= {pr1645v2BgrMVBridgingEntry 134479872}

pr1645v2BgrMVBridgingCacheLoopsDetected OBJECT-TYPE
   SYNTAX      Counter32
   MAX-ACCESS  read-only
   STATUS      current
   DESCRIPTION
      "Path: bridgeGroup.performance.bridging.cache.loopsDetected

       32 bit unsigned wrappable counter."
   ::= {pr1645v2BgrMVBridgingEntry 134676480}

pr1645v2BgrMVBridgingVlanMemberShipRxDiscards OBJECT-TYPE
   SYNTAX      Counter32
   MAX-ACCESS  read-only
   STATUS      current
   DESCRIPTION
      "Path: bridgeGroup.performance.bridging.vlanMemberShip.rxDiscards

       32 bit unsigned wrappable counter."
   ::= {pr1645v2BgrMVBridgingEntry 218169344}

pr1645v2BgrMVBridgingVlanMemberShipTxDiscards OBJECT-TYPE
   SYNTAX      Counter32
   MAX-ACCESS  read-only
   STATUS      current
   DESCRIPTION
      "Path: bridgeGroup.performance.bridging.vlanMemberShip.txDiscards

       32 bit unsigned wrappable counter."
   ::= {pr1645v2BgrMVBridgingEntry 218234880}

pr1645v2BgrMVBridgingSpanningTreeRxMstp OBJECT-TYPE
   SYNTAX      Integer32
   MAX-ACCESS  read-only
   STATUS      current
   DESCRIPTION
      "Path: bridgeGroup.performance.bridging.spanningTree.rxMstp"
   ::= {pr1645v2BgrMVBridgingEntry 201392128}

pr1645v2BgrMVBridgingSpanningTreeRxRstp OBJECT-TYPE
   SYNTAX      Integer32
   MAX-ACCESS  read-only
   STATUS      current
   DESCRIPTION
      "Path: bridgeGroup.performance.bridging.spanningTree.rxRstp"
   ::= {pr1645v2BgrMVBridgingEntry 201457664}

pr1645v2BgrMVBridgingSpanningTreeRxConfig OBJECT-TYPE
   SYNTAX      Integer32
   MAX-ACCESS  read-only
   STATUS      current
   DESCRIPTION
      "Path: bridgeGroup.performance.bridging.spanningTree.rxConfig"
   ::= {pr1645v2BgrMVBridgingEntry 201523200}

pr1645v2BgrMVBridgingSpanningTreeRxTcn OBJECT-TYPE
   SYNTAX      Integer32
   MAX-ACCESS  read-only
   STATUS      current
   DESCRIPTION
      "Path: bridgeGroup.performance.bridging.spanningTree.rxTcn"
   ::= {pr1645v2BgrMVBridgingEntry 201588736}

pr1645v2BgrMVBridgingSpanningTreeRxDiscards OBJECT-TYPE
   SYNTAX      Integer32
   MAX-ACCESS  read-only
   STATUS      current
   DESCRIPTION
      "Path: bridgeGroup.performance.bridging.spanningTree.rxDiscards"
   ::= {pr1645v2BgrMVBridgingEntry 201654272}

pr1645v2BgrMVBridgingSpanningTreeTxMstp OBJECT-TYPE
   SYNTAX      Integer32
   MAX-ACCESS  read-only
   STATUS      current
   DESCRIPTION
      "Path: bridgeGroup.performance.bridging.spanningTree.txMstp"
   ::= {pr1645v2BgrMVBridgingEntry 201719808}

pr1645v2BgrMVBridgingSpanningTreeTxRstp OBJECT-TYPE
   SYNTAX      Integer32
   MAX-ACCESS  read-only
   STATUS      current
   DESCRIPTION
      "Path: bridgeGroup.performance.bridging.spanningTree.txRstp"
   ::= {pr1645v2BgrMVBridgingEntry 201785344}

pr1645v2BgrMVBridgingSpanningTreeTxConfig OBJECT-TYPE
   SYNTAX      Integer32
   MAX-ACCESS  read-only
   STATUS      current
   DESCRIPTION
      "Path: bridgeGroup.performance.bridging.spanningTree.txConfig"
   ::= {pr1645v2BgrMVBridgingEntry 201850880}

pr1645v2BgrMVBridgingSpanningTreeTxTcn OBJECT-TYPE
   SYNTAX      Integer32
   MAX-ACCESS  read-only
   STATUS      current
   DESCRIPTION
      "Path: bridgeGroup.performance.bridging.spanningTree.txTcn"
   ::= {pr1645v2BgrMVBridgingEntry 201916416}

pr1645v2BgrMVBridgingH2Performance OBJECT-TYPE
   SYNTAX      SEQUENCE OF Pr1645v2BgrMVBridgingH2PerformanceEntry
   MAX-ACCESS  not-accessible
   STATUS      current
   DESCRIPTION
      ""
   ::= {pr1645v2BgrMVBridging 150994944}

pr1645v2BgrMVBridgingH2PerformanceEntry OBJECT-TYPE
   SYNTAX      Pr1645v2BgrMVBridgingH2PerformanceEntry
   MAX-ACCESS  not-accessible
   STATUS      current
   DESCRIPTION
      ""
   INDEX      { pr1645v2BgrMVBridgingTableIx,
                pr1645v2BgrMVBridgingH2PerformanceTableIx }
   ::= {pr1645v2BgrMVBridgingH2Performance 1}

Pr1645v2BgrMVBridgingH2PerformanceEntry ::=
   SEQUENCE
      {
      pr1645v2BgrMVBridgingH2PerformanceTableIx
         TableIndex,
      pr1645v2BgrMVBridgingH2PerformanceSysUpTime
         TimeTicks,
      pr1645v2BgrMVBridgingH2PerformanceRxPkts
         Counter32,
      pr1645v2BgrMVBridgingH2PerformanceTxPkts
         Counter32,
      pr1645v2BgrMVBridgingH2PerformanceRxDiscards
         Counter32,
      pr1645v2BgrMVBridgingH2PerformanceRxFloods
         Counter32,
      pr1645v2BgrMVBridgingH2PerformanceRxBroadcasts
         Counter32,
      pr1645v2BgrMVBridgingH2PerformanceRxMulticasts
         Counter32,
      pr1645v2BgrMVBridgingH2PerformanceCacheSizeOverflows
         Counter32,
      pr1645v2BgrMVBridgingH2PerformanceStaticCacheViolations
         Counter32,
      pr1645v2BgrMVBridgingH2PerformanceCacheRelearns
         Counter32,
      pr1645v2BgrMVBridgingH2PerformanceCacheRelearnDrops
         Counter32,
      pr1645v2BgrMVBridgingH2PerformanceLoopsDetected
         Counter32
      }

pr1645v2BgrMVBridgingH2PerformanceTableIx OBJECT-TYPE
   SYNTAX      TableIndex
   MAX-ACCESS  not-accessible
   STATUS      current
   DESCRIPTION
      ""
   ::= {pr1645v2BgrMVBridgingH2PerformanceEntry 11}

pr1645v2BgrMVBridgingH2PerformanceSysUpTime OBJECT-TYPE
   SYNTAX      TimeTicks
   MAX-ACCESS  read-only
   STATUS      current
   DESCRIPTION
      "Path: bridgeGroup.performance.bridging.h2Performance.sysUpTime

       Time in centi-second."
   ::= {pr1645v2BgrMVBridgingH2PerformanceEntry 16777216}

pr1645v2BgrMVBridgingH2PerformanceRxPkts OBJECT-TYPE
   SYNTAX      Counter32
   MAX-ACCESS  read-only
   STATUS      current
   DESCRIPTION
      "Path: bridgeGroup.performance.bridging.h2Performance.rxPkts

       32 bit unsigned wrappable counter."
   ::= {pr1645v2BgrMVBridgingH2PerformanceEntry 33554432}

pr1645v2BgrMVBridgingH2PerformanceTxPkts OBJECT-TYPE
   SYNTAX      Counter32
   MAX-ACCESS  read-only
   STATUS      current
   DESCRIPTION
      "Path: bridgeGroup.performance.bridging.h2Performance.txPkts

       32 bit unsigned wrappable counter."
   ::= {pr1645v2BgrMVBridgingH2PerformanceEntry 50331648}

pr1645v2BgrMVBridgingH2PerformanceRxDiscards OBJECT-TYPE
   SYNTAX      Counter32
   MAX-ACCESS  read-only
   STATUS      current
   DESCRIPTION
      "Path: bridgeGroup.performance.bridging.h2Performance.rxDiscards

       32 bit unsigned wrappable counter."
   ::= {pr1645v2BgrMVBridgingH2PerformanceEntry 67108864}

pr1645v2BgrMVBridgingH2PerformanceRxFloods OBJECT-TYPE
   SYNTAX      Counter32
   MAX-ACCESS  read-only
   STATUS      current
   DESCRIPTION
      "Path: bridgeGroup.performance.bridging.h2Performance.rxFloods

       32 bit unsigned wrappable counter."
   ::= {pr1645v2BgrMVBridgingH2PerformanceEntry 83886080}

pr1645v2BgrMVBridgingH2PerformanceRxBroadcasts OBJECT-TYPE
   SYNTAX      Counter32
   MAX-ACCESS  read-only
   STATUS      current
   DESCRIPTION
      "Path: bridgeGroup.performance.bridging.h2Performance.rxBroadcasts

       32 bit unsigned wrappable counter."
   ::= {pr1645v2BgrMVBridgingH2PerformanceEntry 100663296}

pr1645v2BgrMVBridgingH2PerformanceRxMulticasts OBJECT-TYPE
   SYNTAX      Counter32
   MAX-ACCESS  read-only
   STATUS      current
   DESCRIPTION
      "Path: bridgeGroup.performance.bridging.h2Performance.rxMulticasts

       32 bit unsigned wrappable counter."
   ::= {pr1645v2BgrMVBridgingH2PerformanceEntry 117440512}

pr1645v2BgrMVBridgingH2PerformanceCacheSizeOverflows OBJECT-TYPE
   SYNTAX      Counter32
   MAX-ACCESS  read-only
   STATUS      current
   DESCRIPTION
      "Path: bridgeGroup.performance.bridging.h2Performance.cacheSizeOverflows

       32 bit unsigned wrappable counter."
   ::= {pr1645v2BgrMVBridgingH2PerformanceEntry 134217728}

pr1645v2BgrMVBridgingH2PerformanceStaticCacheViolations OBJECT-TYPE
   SYNTAX      Counter32
   MAX-ACCESS  read-only
   STATUS      current
   DESCRIPTION
      "Path: bridgeGroup.performance.bridging.h2Performance.staticCacheViolations

       32 bit unsigned wrappable counter."
   ::= {pr1645v2BgrMVBridgingH2PerformanceEntry 150994944}

pr1645v2BgrMVBridgingH2PerformanceCacheRelearns OBJECT-TYPE
   SYNTAX      Counter32
   MAX-ACCESS  read-only
   STATUS      current
   DESCRIPTION
      "Path: bridgeGroup.performance.bridging.h2Performance.cacheRelearns

       32 bit unsigned wrappable counter."
   ::= {pr1645v2BgrMVBridgingH2PerformanceEntry 167772160}

pr1645v2BgrMVBridgingH2PerformanceCacheRelearnDrops OBJECT-TYPE
   SYNTAX      Counter32
   MAX-ACCESS  read-only
   STATUS      current
   DESCRIPTION
      "Path: bridgeGroup.performance.bridging.h2Performance.cacheRelearnDrops

       32 bit unsigned wrappable counter."
   ::= {pr1645v2BgrMVBridgingH2PerformanceEntry 184549376}

pr1645v2BgrMVBridgingH2PerformanceLoopsDetected OBJECT-TYPE
   SYNTAX      Counter32
   MAX-ACCESS  read-only
   STATUS      current
   DESCRIPTION
      "Path: bridgeGroup.performance.bridging.h2Performance.loopsDetected

       32 bit unsigned wrappable counter."
   ::= {pr1645v2BgrMVBridgingH2PerformanceEntry 234881024}

pr1645v2BgrMVBridgingH24Performance OBJECT-TYPE
   SYNTAX      SEQUENCE OF Pr1645v2BgrMVBridgingH24PerformanceEntry
   MAX-ACCESS  not-accessible
   STATUS      current
   DESCRIPTION
      ""
   ::= {pr1645v2BgrMVBridging 167772160}

pr1645v2BgrMVBridgingH24PerformanceEntry OBJECT-TYPE
   SYNTAX      Pr1645v2BgrMVBridgingH24PerformanceEntry
   MAX-ACCESS  not-accessible
   STATUS      current
   DESCRIPTION
      ""
   INDEX      { pr1645v2BgrMVBridgingTableIx,
                pr1645v2BgrMVBridgingH24PerformanceTableIx }
   ::= {pr1645v2BgrMVBridgingH24Performance 1}

Pr1645v2BgrMVBridgingH24PerformanceEntry ::=
   SEQUENCE
      {
      pr1645v2BgrMVBridgingH24PerformanceTableIx
         TableIndex,
      pr1645v2BgrMVBridgingH24PerformanceSysUpTime
         TimeTicks,
      pr1645v2BgrMVBridgingH24PerformanceRxPkts
         Counter32,
      pr1645v2BgrMVBridgingH24PerformanceTxPkts
         Counter32,
      pr1645v2BgrMVBridgingH24PerformanceRxDiscards
         Counter32,
      pr1645v2BgrMVBridgingH24PerformanceRxFloods
         Counter32,
      pr1645v2BgrMVBridgingH24PerformanceRxBroadcasts
         Counter32,
      pr1645v2BgrMVBridgingH24PerformanceRxMulticasts
         Counter32,
      pr1645v2BgrMVBridgingH24PerformanceCacheSizeOverflows
         Counter32,
      pr1645v2BgrMVBridgingH24PerformanceStaticCacheViolations
         Counter32,
      pr1645v2BgrMVBridgingH24PerformanceCacheRelearns
         Counter32,
      pr1645v2BgrMVBridgingH24PerformanceCacheRelearnDrops
         Counter32,
      pr1645v2BgrMVBridgingH24PerformanceLoopsDetected
         Counter32
      }

pr1645v2BgrMVBridgingH24PerformanceTableIx OBJECT-TYPE
   SYNTAX      TableIndex
   MAX-ACCESS  not-accessible
   STATUS      current
   DESCRIPTION
      ""
   ::= {pr1645v2BgrMVBridgingH24PerformanceEntry 11}

pr1645v2BgrMVBridgingH24PerformanceSysUpTime OBJECT-TYPE
   SYNTAX      TimeTicks
   MAX-ACCESS  read-only
   STATUS      current
   DESCRIPTION
      "Path: bridgeGroup.performance.bridging.h24Performance.sysUpTime

       Time in centi-second."
   ::= {pr1645v2BgrMVBridgingH24PerformanceEntry 16777216}

pr1645v2BgrMVBridgingH24PerformanceRxPkts OBJECT-TYPE
   SYNTAX      Counter32
   MAX-ACCESS  read-only
   STATUS      current
   DESCRIPTION
      "Path: bridgeGroup.performance.bridging.h24Performance.rxPkts

       32 bit unsigned wrappable counter."
   ::= {pr1645v2BgrMVBridgingH24PerformanceEntry 33554432}

pr1645v2BgrMVBridgingH24PerformanceTxPkts OBJECT-TYPE
   SYNTAX      Counter32
   MAX-ACCESS  read-only
   STATUS      current
   DESCRIPTION
      "Path: bridgeGroup.performance.bridging.h24Performance.txPkts

       32 bit unsigned wrappable counter."
   ::= {pr1645v2BgrMVBridgingH24PerformanceEntry 50331648}

pr1645v2BgrMVBridgingH24PerformanceRxDiscards OBJECT-TYPE
   SYNTAX      Counter32
   MAX-ACCESS  read-only
   STATUS      current
   DESCRIPTION
      "Path: bridgeGroup.performance.bridging.h24Performance.rxDiscards

       32 bit unsigned wrappable counter."
   ::= {pr1645v2BgrMVBridgingH24PerformanceEntry 67108864}

pr1645v2BgrMVBridgingH24PerformanceRxFloods OBJECT-TYPE
   SYNTAX      Counter32
   MAX-ACCESS  read-only
   STATUS      current
   DESCRIPTION
      "Path: bridgeGroup.performance.bridging.h24Performance.rxFloods

       32 bit unsigned wrappable counter."
   ::= {pr1645v2BgrMVBridgingH24PerformanceEntry 83886080}

pr1645v2BgrMVBridgingH24PerformanceRxBroadcasts OBJECT-TYPE
   SYNTAX      Counter32
   MAX-ACCESS  read-only
   STATUS      current
   DESCRIPTION
      "Path: bridgeGroup.performance.bridging.h24Performance.rxBroadcasts

       32 bit unsigned wrappable counter."
   ::= {pr1645v2BgrMVBridgingH24PerformanceEntry 100663296}

pr1645v2BgrMVBridgingH24PerformanceRxMulticasts OBJECT-TYPE
   SYNTAX      Counter32
   MAX-ACCESS  read-only
   STATUS      current
   DESCRIPTION
      "Path: bridgeGroup.performance.bridging.h24Performance.rxMulticasts

       32 bit unsigned wrappable counter."
   ::= {pr1645v2BgrMVBridgingH24PerformanceEntry 117440512}

pr1645v2BgrMVBridgingH24PerformanceCacheSizeOverflows OBJECT-TYPE
   SYNTAX      Counter32
   MAX-ACCESS  read-only
   STATUS      current
   DESCRIPTION
      "Path: bridgeGroup.performance.bridging.h24Performance.cacheSizeOverflows

       32 bit unsigned wrappable counter."
   ::= {pr1645v2BgrMVBridgingH24PerformanceEntry 134217728}

pr1645v2BgrMVBridgingH24PerformanceStaticCacheViolations OBJECT-TYPE
   SYNTAX      Counter32
   MAX-ACCESS  read-only
   STATUS      current
   DESCRIPTION
      "Path: bridgeGroup.performance.bridging.h24Performance.staticCacheViolations

       32 bit unsigned wrappable counter."
   ::= {pr1645v2BgrMVBridgingH24PerformanceEntry 150994944}

pr1645v2BgrMVBridgingH24PerformanceCacheRelearns OBJECT-TYPE
   SYNTAX      Counter32
   MAX-ACCESS  read-only
   STATUS      current
   DESCRIPTION
      "Path: bridgeGroup.performance.bridging.h24Performance.cacheRelearns

       32 bit unsigned wrappable counter."
   ::= {pr1645v2BgrMVBridgingH24PerformanceEntry 167772160}

pr1645v2BgrMVBridgingH24PerformanceCacheRelearnDrops OBJECT-TYPE
   SYNTAX      Counter32
   MAX-ACCESS  read-only
   STATUS      current
   DESCRIPTION
      "Path: bridgeGroup.performance.bridging.h24Performance.cacheRelearnDrops

       32 bit unsigned wrappable counter."
   ::= {pr1645v2BgrMVBridgingH24PerformanceEntry 184549376}

pr1645v2BgrMVBridgingH24PerformanceLoopsDetected OBJECT-TYPE
   SYNTAX      Counter32
   MAX-ACCESS  read-only
   STATUS      current
   DESCRIPTION
      "Path: bridgeGroup.performance.bridging.h24Performance.loopsDetected

       32 bit unsigned wrappable counter."
   ::= {pr1645v2BgrMVBridgingH24PerformanceEntry 234881024}

pr1645v2BgrMVBridgingD7Performance OBJECT-TYPE
   SYNTAX      SEQUENCE OF Pr1645v2BgrMVBridgingD7PerformanceEntry
   MAX-ACCESS  not-accessible
   STATUS      current
   DESCRIPTION
      ""
   ::= {pr1645v2BgrMVBridging 184549376}

pr1645v2BgrMVBridgingD7PerformanceEntry OBJECT-TYPE
   SYNTAX      Pr1645v2BgrMVBridgingD7PerformanceEntry
   MAX-ACCESS  not-accessible
   STATUS      current
   DESCRIPTION
      ""
   INDEX      { pr1645v2BgrMVBridgingTableIx,
                pr1645v2BgrMVBridgingD7PerformanceTableIx }
   ::= {pr1645v2BgrMVBridgingD7Performance 1}

Pr1645v2BgrMVBridgingD7PerformanceEntry ::=
   SEQUENCE
      {
      pr1645v2BgrMVBridgingD7PerformanceTableIx
         TableIndex,
      pr1645v2BgrMVBridgingD7PerformanceSysUpTime
         TimeTicks,
      pr1645v2BgrMVBridgingD7PerformanceRxPkts
         Counter32,
      pr1645v2BgrMVBridgingD7PerformanceTxPkts
         Counter32,
      pr1645v2BgrMVBridgingD7PerformanceRxDiscards
         Counter32,
      pr1645v2BgrMVBridgingD7PerformanceRxFloods
         Counter32,
      pr1645v2BgrMVBridgingD7PerformanceRxBroadcasts
         Counter32,
      pr1645v2BgrMVBridgingD7PerformanceRxMulticasts
         Counter32,
      pr1645v2BgrMVBridgingD7PerformanceCacheSizeOverflows
         Counter32,
      pr1645v2BgrMVBridgingD7PerformanceStaticCacheViolations
         Counter32,
      pr1645v2BgrMVBridgingD7PerformanceCacheRelearns
         Counter32,
      pr1645v2BgrMVBridgingD7PerformanceCacheRelearnDrops
         Counter32,
      pr1645v2BgrMVBridgingD7PerformanceLoopsDetected
         Counter32
      }

pr1645v2BgrMVBridgingD7PerformanceTableIx OBJECT-TYPE
   SYNTAX      TableIndex
   MAX-ACCESS  not-accessible
   STATUS      current
   DESCRIPTION
      ""
   ::= {pr1645v2BgrMVBridgingD7PerformanceEntry 11}

pr1645v2BgrMVBridgingD7PerformanceSysUpTime OBJECT-TYPE
   SYNTAX      TimeTicks
   MAX-ACCESS  read-only
   STATUS      current
   DESCRIPTION
      "Path: bridgeGroup.performance.bridging.d7Performance.sysUpTime

       Time in centi-second."
   ::= {pr1645v2BgrMVBridgingD7PerformanceEntry 16777216}

pr1645v2BgrMVBridgingD7PerformanceRxPkts OBJECT-TYPE
   SYNTAX      Counter32
   MAX-ACCESS  read-only
   STATUS      current
   DESCRIPTION
      "Path: bridgeGroup.performance.bridging.d7Performance.rxPkts

       32 bit unsigned wrappable counter."
   ::= {pr1645v2BgrMVBridgingD7PerformanceEntry 33554432}

pr1645v2BgrMVBridgingD7PerformanceTxPkts OBJECT-TYPE
   SYNTAX      Counter32
   MAX-ACCESS  read-only
   STATUS      current
   DESCRIPTION
      "Path: bridgeGroup.performance.bridging.d7Performance.txPkts

       32 bit unsigned wrappable counter."
   ::= {pr1645v2BgrMVBridgingD7PerformanceEntry 50331648}

pr1645v2BgrMVBridgingD7PerformanceRxDiscards OBJECT-TYPE
   SYNTAX      Counter32
   MAX-ACCESS  read-only
   STATUS      current
   DESCRIPTION
      "Path: bridgeGroup.performance.bridging.d7Performance.rxDiscards

       32 bit unsigned wrappable counter."
   ::= {pr1645v2BgrMVBridgingD7PerformanceEntry 67108864}

pr1645v2BgrMVBridgingD7PerformanceRxFloods OBJECT-TYPE
   SYNTAX      Counter32
   MAX-ACCESS  read-only
   STATUS      current
   DESCRIPTION
      "Path: bridgeGroup.performance.bridging.d7Performance.rxFloods

       32 bit unsigned wrappable counter."
   ::= {pr1645v2BgrMVBridgingD7PerformanceEntry 83886080}

pr1645v2BgrMVBridgingD7PerformanceRxBroadcasts OBJECT-TYPE
   SYNTAX      Counter32
   MAX-ACCESS  read-only
   STATUS      current
   DESCRIPTION
      "Path: bridgeGroup.performance.bridging.d7Performance.rxBroadcasts

       32 bit unsigned wrappable counter."
   ::= {pr1645v2BgrMVBridgingD7PerformanceEntry 100663296}

pr1645v2BgrMVBridgingD7PerformanceRxMulticasts OBJECT-TYPE
   SYNTAX      Counter32
   MAX-ACCESS  read-only
   STATUS      current
   DESCRIPTION
      "Path: bridgeGroup.performance.bridging.d7Performance.rxMulticasts

       32 bit unsigned wrappable counter."
   ::= {pr1645v2BgrMVBridgingD7PerformanceEntry 117440512}

pr1645v2BgrMVBridgingD7PerformanceCacheSizeOverflows OBJECT-TYPE
   SYNTAX      Counter32
   MAX-ACCESS  read-only
   STATUS      current
   DESCRIPTION
      "Path: bridgeGroup.performance.bridging.d7Performance.cacheSizeOverflows

       32 bit unsigned wrappable counter."
   ::= {pr1645v2BgrMVBridgingD7PerformanceEntry 134217728}

pr1645v2BgrMVBridgingD7PerformanceStaticCacheViolations OBJECT-TYPE
   SYNTAX      Counter32
   MAX-ACCESS  read-only
   STATUS      current
   DESCRIPTION
      "Path: bridgeGroup.performance.bridging.d7Performance.staticCacheViolations

       32 bit unsigned wrappable counter."
   ::= {pr1645v2BgrMVBridgingD7PerformanceEntry 150994944}

pr1645v2BgrMVBridgingD7PerformanceCacheRelearns OBJECT-TYPE
   SYNTAX      Counter32
   MAX-ACCESS  read-only
   STATUS      current
   DESCRIPTION
      "Path: bridgeGroup.performance.bridging.d7Performance.cacheRelearns

       32 bit unsigned wrappable counter."
   ::= {pr1645v2BgrMVBridgingD7PerformanceEntry 167772160}

pr1645v2BgrMVBridgingD7PerformanceCacheRelearnDrops OBJECT-TYPE
   SYNTAX      Counter32
   MAX-ACCESS  read-only
   STATUS      current
   DESCRIPTION
      "Path: bridgeGroup.performance.bridging.d7Performance.cacheRelearnDrops

       32 bit unsigned wrappable counter."
   ::= {pr1645v2BgrMVBridgingD7PerformanceEntry 184549376}

pr1645v2BgrMVBridgingD7PerformanceLoopsDetected OBJECT-TYPE
   SYNTAX      Counter32
   MAX-ACCESS  read-only
   STATUS      current
   DESCRIPTION
      "Path: bridgeGroup.performance.bridging.d7Performance.loopsDetected

       32 bit unsigned wrappable counter."
   ::= {pr1645v2BgrMVBridgingD7PerformanceEntry 234881024}


pr1645v2BgrMVL2ProtTunnel OBJECT IDENTIFIER ::= {pr1645v2BgrMV 46}

pr1645v2BgrMVL2ProtTunnelSSCTable OBJECT-TYPE
   SYNTAX      SEQUENCE OF Pr1645v2BgrMVL2ProtTunnelEntry
   MAX-ACCESS  not-accessible
   STATUS      current
   DESCRIPTION
      "l2 protocol tunnel performance"
   ::= {pr1645v2BgrMVL2ProtTunnel 1}

pr1645v2BgrMVL2ProtTunnelEntry OBJECT-TYPE
   SYNTAX      Pr1645v2BgrMVL2ProtTunnelEntry
   MAX-ACCESS  not-accessible
   STATUS      current
   DESCRIPTION
      ""
   INDEX      { pr1645v2BgrMVL2ProtTunnelTableIx }
   ::= {pr1645v2BgrMVL2ProtTunnelSSCTable 1}

Pr1645v2BgrMVL2ProtTunnelEntry ::=
   SEQUENCE
      {
      pr1645v2BgrMVL2ProtTunnelTableIx
         TableIndex,
      pr1645v2BgrMVL2ProtTunnelName
         DisplayString,
      pr1645v2BgrMVL2ProtTunnelEncapsPktsStp
         Counter32,
      pr1645v2BgrMVL2ProtTunnelEncapsPktsLldp
         Counter32,
      pr1645v2BgrMVL2ProtTunnelEncapsPktsOam
         Counter32,
      pr1645v2BgrMVL2ProtTunnelEncapsPktsCdp
         Counter32,
      pr1645v2BgrMVL2ProtTunnelEncapsPktsVtp
         Counter32,
      pr1645v2BgrMVL2ProtTunnelEncapsPktsLacp
         Counter32,
      pr1645v2BgrMVL2ProtTunnelEncapsPktsEfmOam
         Counter32,
      pr1645v2BgrMVL2ProtTunnelEncapsPktsPvst
         Counter32,
      pr1645v2BgrMVL2ProtTunnelEncapsPktsMmrp
         Counter32,
      pr1645v2BgrMVL2ProtTunnelEncapsPktsMvrp
         Counter32,
      pr1645v2BgrMVL2ProtTunnelEncapsPktsGvrp
         Counter32,
      pr1645v2BgrMVL2ProtTunnelEncapsPktsGmrp
         Counter32,
      pr1645v2BgrMVL2ProtTunnelEncapsPktsDtp
         Counter32,
      pr1645v2BgrMVL2ProtTunnelEncapsPktsPagp
         Counter32,
      pr1645v2BgrMVL2ProtTunnelEncapsPktsUdld
         Counter32,
      pr1645v2BgrMVL2ProtTunnelDecapsPktsStp
         Counter32,
      pr1645v2BgrMVL2ProtTunnelDecapsPktsLldp
         Counter32,
      pr1645v2BgrMVL2ProtTunnelDecapsPktsOam
         Counter32,
      pr1645v2BgrMVL2ProtTunnelDecapsPktsCdp
         Counter32,
      pr1645v2BgrMVL2ProtTunnelDecapsPktsVtp
         Counter32,
      pr1645v2BgrMVL2ProtTunnelDecapsPktsLacp
         Counter32,
      pr1645v2BgrMVL2ProtTunnelDecapsPktsEfmOam
         Counter32,
      pr1645v2BgrMVL2ProtTunnelDecapsPktsPvst
         Counter32,
      pr1645v2BgrMVL2ProtTunnelDecapsPktsMmrp
         Counter32,
      pr1645v2BgrMVL2ProtTunnelDecapsPktsMvrp
         Counter32,
      pr1645v2BgrMVL2ProtTunnelDecapsPktsGvrp
         Counter32,
      pr1645v2BgrMVL2ProtTunnelDecapsPktsGmrp
         Counter32,
      pr1645v2BgrMVL2ProtTunnelDecapsPktsDtp
         Counter32,
      pr1645v2BgrMVL2ProtTunnelDecapsPktsPagp
         Counter32,
      pr1645v2BgrMVL2ProtTunnelDecapsPktsUdld
         Counter32,
      pr1645v2BgrMVL2ProtTunnelDroppedStp
         Counter32,
      pr1645v2BgrMVL2ProtTunnelDroppedLldp
         Counter32,
      pr1645v2BgrMVL2ProtTunnelDroppedOam
         Counter32,
      pr1645v2BgrMVL2ProtTunnelDroppedCdp
         Counter32,
      pr1645v2BgrMVL2ProtTunnelDroppedVtp
         Counter32,
      pr1645v2BgrMVL2ProtTunnelDroppedLacp
         Counter32,
      pr1645v2BgrMVL2ProtTunnelDroppedEfmOam
         Counter32,
      pr1645v2BgrMVL2ProtTunnelDroppedPvst
         Counter32,
      pr1645v2BgrMVL2ProtTunnelDroppedMmrp
         Counter32,
      pr1645v2BgrMVL2ProtTunnelDroppedMvrp
         Counter32,
      pr1645v2BgrMVL2ProtTunnelDroppedGvrp
         Counter32,
      pr1645v2BgrMVL2ProtTunnelDroppedGmrp
         Counter32,
      pr1645v2BgrMVL2ProtTunnelDroppedDtp
         Counter32,
      pr1645v2BgrMVL2ProtTunnelDroppedPagp
         Counter32,
      pr1645v2BgrMVL2ProtTunnelDroppedUdld
         Counter32
      }

pr1645v2BgrMVL2ProtTunnelTableIx OBJECT-TYPE
   SYNTAX      TableIndex
   MAX-ACCESS  not-accessible
   STATUS      current
   DESCRIPTION
      ""
   ::= {pr1645v2BgrMVL2ProtTunnelEntry 11}

pr1645v2BgrMVL2ProtTunnelName OBJECT-TYPE
   SYNTAX      DisplayString
   MAX-ACCESS  read-only
   STATUS      current
   DESCRIPTION
      "Path: bridgeGroup.performance.l2ProtTunnel.name"
   ::= {pr1645v2BgrMVL2ProtTunnelEntry 16777216}

pr1645v2BgrMVL2ProtTunnelEncapsPktsStp OBJECT-TYPE
   SYNTAX      Counter32
   MAX-ACCESS  read-only
   STATUS      current
   DESCRIPTION
      "Path: bridgeGroup.performance.l2ProtTunnel.encapsPkts.stp

       32 bit unsigned wrappable counter."
   ::= {pr1645v2BgrMVL2ProtTunnelEntry 33619968}

pr1645v2BgrMVL2ProtTunnelEncapsPktsLldp OBJECT-TYPE
   SYNTAX      Counter32
   MAX-ACCESS  read-only
   STATUS      current
   DESCRIPTION
      "Path: bridgeGroup.performance.l2ProtTunnel.encapsPkts.lldp

       32 bit unsigned wrappable counter."
   ::= {pr1645v2BgrMVL2ProtTunnelEntry 33685504}

pr1645v2BgrMVL2ProtTunnelEncapsPktsOam OBJECT-TYPE
   SYNTAX      Counter32
   MAX-ACCESS  read-only
   STATUS      current
   DESCRIPTION
      "Path: bridgeGroup.performance.l2ProtTunnel.encapsPkts.oam

       32 bit unsigned wrappable counter."
   ::= {pr1645v2BgrMVL2ProtTunnelEntry 33751040}

pr1645v2BgrMVL2ProtTunnelEncapsPktsCdp OBJECT-TYPE
   SYNTAX      Counter32
   MAX-ACCESS  read-only
   STATUS      current
   DESCRIPTION
      "Path: bridgeGroup.performance.l2ProtTunnel.encapsPkts.cdp

       32 bit unsigned wrappable counter."
   ::= {pr1645v2BgrMVL2ProtTunnelEntry 33816576}

pr1645v2BgrMVL2ProtTunnelEncapsPktsVtp OBJECT-TYPE
   SYNTAX      Counter32
   MAX-ACCESS  read-only
   STATUS      current
   DESCRIPTION
      "Path: bridgeGroup.performance.l2ProtTunnel.encapsPkts.vtp

       32 bit unsigned wrappable counter."
   ::= {pr1645v2BgrMVL2ProtTunnelEntry 33882112}

pr1645v2BgrMVL2ProtTunnelEncapsPktsLacp OBJECT-TYPE
   SYNTAX      Counter32
   MAX-ACCESS  read-only
   STATUS      current
   DESCRIPTION
      "Path: bridgeGroup.performance.l2ProtTunnel.encapsPkts.lacp

       32 bit unsigned wrappable counter."
   ::= {pr1645v2BgrMVL2ProtTunnelEntry 33947648}

pr1645v2BgrMVL2ProtTunnelEncapsPktsEfmOam OBJECT-TYPE
   SYNTAX      Counter32
   MAX-ACCESS  read-only
   STATUS      current
   DESCRIPTION
      "Path: bridgeGroup.performance.l2ProtTunnel.encapsPkts.efmOam

       32 bit unsigned wrappable counter."
   ::= {pr1645v2BgrMVL2ProtTunnelEntry 34013184}

pr1645v2BgrMVL2ProtTunnelEncapsPktsPvst OBJECT-TYPE
   SYNTAX      Counter32
   MAX-ACCESS  read-only
   STATUS      current
   DESCRIPTION
      "Path: bridgeGroup.performance.l2ProtTunnel.encapsPkts.pvst

       32 bit unsigned wrappable counter."
   ::= {pr1645v2BgrMVL2ProtTunnelEntry 34078720}

pr1645v2BgrMVL2ProtTunnelEncapsPktsMmrp OBJECT-TYPE
   SYNTAX      Counter32
   MAX-ACCESS  read-only
   STATUS      current
   DESCRIPTION
      "Path: bridgeGroup.performance.l2ProtTunnel.encapsPkts.mmrp

       32 bit unsigned wrappable counter."
   ::= {pr1645v2BgrMVL2ProtTunnelEntry 34144256}

pr1645v2BgrMVL2ProtTunnelEncapsPktsMvrp OBJECT-TYPE
   SYNTAX      Counter32
   MAX-ACCESS  read-only
   STATUS      current
   DESCRIPTION
      "Path: bridgeGroup.performance.l2ProtTunnel.encapsPkts.mvrp

       32 bit unsigned wrappable counter."
   ::= {pr1645v2BgrMVL2ProtTunnelEntry 34209792}

pr1645v2BgrMVL2ProtTunnelEncapsPktsGvrp OBJECT-TYPE
   SYNTAX      Counter32
   MAX-ACCESS  read-only
   STATUS      current
   DESCRIPTION
      "Path: bridgeGroup.performance.l2ProtTunnel.encapsPkts.gvrp

       32 bit unsigned wrappable counter."
   ::= {pr1645v2BgrMVL2ProtTunnelEntry 34275328}

pr1645v2BgrMVL2ProtTunnelEncapsPktsGmrp OBJECT-TYPE
   SYNTAX      Counter32
   MAX-ACCESS  read-only
   STATUS      current
   DESCRIPTION
      "Path: bridgeGroup.performance.l2ProtTunnel.encapsPkts.gmrp

       32 bit unsigned wrappable counter."
   ::= {pr1645v2BgrMVL2ProtTunnelEntry 34340864}

pr1645v2BgrMVL2ProtTunnelEncapsPktsDtp OBJECT-TYPE
   SYNTAX      Counter32
   MAX-ACCESS  read-only
   STATUS      current
   DESCRIPTION
      "Path: bridgeGroup.performance.l2ProtTunnel.encapsPkts.dtp

       32 bit unsigned wrappable counter."
   ::= {pr1645v2BgrMVL2ProtTunnelEntry 34406400}

pr1645v2BgrMVL2ProtTunnelEncapsPktsPagp OBJECT-TYPE
   SYNTAX      Counter32
   MAX-ACCESS  read-only
   STATUS      current
   DESCRIPTION
      "Path: bridgeGroup.performance.l2ProtTunnel.encapsPkts.pagp

       32 bit unsigned wrappable counter."
   ::= {pr1645v2BgrMVL2ProtTunnelEntry 34471936}

pr1645v2BgrMVL2ProtTunnelEncapsPktsUdld OBJECT-TYPE
   SYNTAX      Counter32
   MAX-ACCESS  read-only
   STATUS      current
   DESCRIPTION
      "Path: bridgeGroup.performance.l2ProtTunnel.encapsPkts.udld

       32 bit unsigned wrappable counter."
   ::= {pr1645v2BgrMVL2ProtTunnelEntry 34537472}

pr1645v2BgrMVL2ProtTunnelDecapsPktsStp OBJECT-TYPE
   SYNTAX      Counter32
   MAX-ACCESS  read-only
   STATUS      current
   DESCRIPTION
      "Path: bridgeGroup.performance.l2ProtTunnel.decapsPkts.stp

       32 bit unsigned wrappable counter."
   ::= {pr1645v2BgrMVL2ProtTunnelEntry 50397184}

pr1645v2BgrMVL2ProtTunnelDecapsPktsLldp OBJECT-TYPE
   SYNTAX      Counter32
   MAX-ACCESS  read-only
   STATUS      current
   DESCRIPTION
      "Path: bridgeGroup.performance.l2ProtTunnel.decapsPkts.lldp

       32 bit unsigned wrappable counter."
   ::= {pr1645v2BgrMVL2ProtTunnelEntry 50462720}

pr1645v2BgrMVL2ProtTunnelDecapsPktsOam OBJECT-TYPE
   SYNTAX      Counter32
   MAX-ACCESS  read-only
   STATUS      current
   DESCRIPTION
      "Path: bridgeGroup.performance.l2ProtTunnel.decapsPkts.oam

       32 bit unsigned wrappable counter."
   ::= {pr1645v2BgrMVL2ProtTunnelEntry 50528256}

pr1645v2BgrMVL2ProtTunnelDecapsPktsCdp OBJECT-TYPE
   SYNTAX      Counter32
   MAX-ACCESS  read-only
   STATUS      current
   DESCRIPTION
      "Path: bridgeGroup.performance.l2ProtTunnel.decapsPkts.cdp

       32 bit unsigned wrappable counter."
   ::= {pr1645v2BgrMVL2ProtTunnelEntry 50593792}

pr1645v2BgrMVL2ProtTunnelDecapsPktsVtp OBJECT-TYPE
   SYNTAX      Counter32
   MAX-ACCESS  read-only
   STATUS      current
   DESCRIPTION
      "Path: bridgeGroup.performance.l2ProtTunnel.decapsPkts.vtp

       32 bit unsigned wrappable counter."
   ::= {pr1645v2BgrMVL2ProtTunnelEntry 50659328}

pr1645v2BgrMVL2ProtTunnelDecapsPktsLacp OBJECT-TYPE
   SYNTAX      Counter32
   MAX-ACCESS  read-only
   STATUS      current
   DESCRIPTION
      "Path: bridgeGroup.performance.l2ProtTunnel.decapsPkts.lacp

       32 bit unsigned wrappable counter."
   ::= {pr1645v2BgrMVL2ProtTunnelEntry 50724864}

pr1645v2BgrMVL2ProtTunnelDecapsPktsEfmOam OBJECT-TYPE
   SYNTAX      Counter32
   MAX-ACCESS  read-only
   STATUS      current
   DESCRIPTION
      "Path: bridgeGroup.performance.l2ProtTunnel.decapsPkts.efmOam

       32 bit unsigned wrappable counter."
   ::= {pr1645v2BgrMVL2ProtTunnelEntry 50790400}

pr1645v2BgrMVL2ProtTunnelDecapsPktsPvst OBJECT-TYPE
   SYNTAX      Counter32
   MAX-ACCESS  read-only
   STATUS      current
   DESCRIPTION
      "Path: bridgeGroup.performance.l2ProtTunnel.decapsPkts.pvst

       32 bit unsigned wrappable counter."
   ::= {pr1645v2BgrMVL2ProtTunnelEntry 50855936}

pr1645v2BgrMVL2ProtTunnelDecapsPktsMmrp OBJECT-TYPE
   SYNTAX      Counter32
   MAX-ACCESS  read-only
   STATUS      current
   DESCRIPTION
      "Path: bridgeGroup.performance.l2ProtTunnel.decapsPkts.mmrp

       32 bit unsigned wrappable counter."
   ::= {pr1645v2BgrMVL2ProtTunnelEntry 50921472}

pr1645v2BgrMVL2ProtTunnelDecapsPktsMvrp OBJECT-TYPE
   SYNTAX      Counter32
   MAX-ACCESS  read-only
   STATUS      current
   DESCRIPTION
      "Path: bridgeGroup.performance.l2ProtTunnel.decapsPkts.mvrp

       32 bit unsigned wrappable counter."
   ::= {pr1645v2BgrMVL2ProtTunnelEntry 50987008}

pr1645v2BgrMVL2ProtTunnelDecapsPktsGvrp OBJECT-TYPE
   SYNTAX      Counter32
   MAX-ACCESS  read-only
   STATUS      current
   DESCRIPTION
      "Path: bridgeGroup.performance.l2ProtTunnel.decapsPkts.gvrp

       32 bit unsigned wrappable counter."
   ::= {pr1645v2BgrMVL2ProtTunnelEntry 51052544}

pr1645v2BgrMVL2ProtTunnelDecapsPktsGmrp OBJECT-TYPE
   SYNTAX      Counter32
   MAX-ACCESS  read-only
   STATUS      current
   DESCRIPTION
      "Path: bridgeGroup.performance.l2ProtTunnel.decapsPkts.gmrp

       32 bit unsigned wrappable counter."
   ::= {pr1645v2BgrMVL2ProtTunnelEntry 51118080}

pr1645v2BgrMVL2ProtTunnelDecapsPktsDtp OBJECT-TYPE
   SYNTAX      Counter32
   MAX-ACCESS  read-only
   STATUS      current
   DESCRIPTION
      "Path: bridgeGroup.performance.l2ProtTunnel.decapsPkts.dtp

       32 bit unsigned wrappable counter."
   ::= {pr1645v2BgrMVL2ProtTunnelEntry 51183616}

pr1645v2BgrMVL2ProtTunnelDecapsPktsPagp OBJECT-TYPE
   SYNTAX      Counter32
   MAX-ACCESS  read-only
   STATUS      current
   DESCRIPTION
      "Path: bridgeGroup.performance.l2ProtTunnel.decapsPkts.pagp

       32 bit unsigned wrappable counter."
   ::= {pr1645v2BgrMVL2ProtTunnelEntry 51249152}

pr1645v2BgrMVL2ProtTunnelDecapsPktsUdld OBJECT-TYPE
   SYNTAX      Counter32
   MAX-ACCESS  read-only
   STATUS      current
   DESCRIPTION
      "Path: bridgeGroup.performance.l2ProtTunnel.decapsPkts.udld

       32 bit unsigned wrappable counter."
   ::= {pr1645v2BgrMVL2ProtTunnelEntry 51314688}

pr1645v2BgrMVL2ProtTunnelDroppedStp OBJECT-TYPE
   SYNTAX      Counter32
   MAX-ACCESS  read-only
   STATUS      current
   DESCRIPTION
      "Path: bridgeGroup.performance.l2ProtTunnel.dropped.stp

       32 bit unsigned wrappable counter."
   ::= {pr1645v2BgrMVL2ProtTunnelEntry 67174400}

pr1645v2BgrMVL2ProtTunnelDroppedLldp OBJECT-TYPE
   SYNTAX      Counter32
   MAX-ACCESS  read-only
   STATUS      current
   DESCRIPTION
      "Path: bridgeGroup.performance.l2ProtTunnel.dropped.lldp

       32 bit unsigned wrappable counter."
   ::= {pr1645v2BgrMVL2ProtTunnelEntry 67239936}

pr1645v2BgrMVL2ProtTunnelDroppedOam OBJECT-TYPE
   SYNTAX      Counter32
   MAX-ACCESS  read-only
   STATUS      current
   DESCRIPTION
      "Path: bridgeGroup.performance.l2ProtTunnel.dropped.oam

       32 bit unsigned wrappable counter."
   ::= {pr1645v2BgrMVL2ProtTunnelEntry 67305472}

pr1645v2BgrMVL2ProtTunnelDroppedCdp OBJECT-TYPE
   SYNTAX      Counter32
   MAX-ACCESS  read-only
   STATUS      current
   DESCRIPTION
      "Path: bridgeGroup.performance.l2ProtTunnel.dropped.cdp

       32 bit unsigned wrappable counter."
   ::= {pr1645v2BgrMVL2ProtTunnelEntry 67371008}

pr1645v2BgrMVL2ProtTunnelDroppedVtp OBJECT-TYPE
   SYNTAX      Counter32
   MAX-ACCESS  read-only
   STATUS      current
   DESCRIPTION
      "Path: bridgeGroup.performance.l2ProtTunnel.dropped.vtp

       32 bit unsigned wrappable counter."
   ::= {pr1645v2BgrMVL2ProtTunnelEntry 67436544}

pr1645v2BgrMVL2ProtTunnelDroppedLacp OBJECT-TYPE
   SYNTAX      Counter32
   MAX-ACCESS  read-only
   STATUS      current
   DESCRIPTION
      "Path: bridgeGroup.performance.l2ProtTunnel.dropped.lacp

       32 bit unsigned wrappable counter."
   ::= {pr1645v2BgrMVL2ProtTunnelEntry 67502080}

pr1645v2BgrMVL2ProtTunnelDroppedEfmOam OBJECT-TYPE
   SYNTAX      Counter32
   MAX-ACCESS  read-only
   STATUS      current
   DESCRIPTION
      "Path: bridgeGroup.performance.l2ProtTunnel.dropped.efmOam

       32 bit unsigned wrappable counter."
   ::= {pr1645v2BgrMVL2ProtTunnelEntry 67567616}

pr1645v2BgrMVL2ProtTunnelDroppedPvst OBJECT-TYPE
   SYNTAX      Counter32
   MAX-ACCESS  read-only
   STATUS      current
   DESCRIPTION
      "Path: bridgeGroup.performance.l2ProtTunnel.dropped.pvst

       32 bit unsigned wrappable counter."
   ::= {pr1645v2BgrMVL2ProtTunnelEntry 67633152}

pr1645v2BgrMVL2ProtTunnelDroppedMmrp OBJECT-TYPE
   SYNTAX      Counter32
   MAX-ACCESS  read-only
   STATUS      current
   DESCRIPTION
      "Path: bridgeGroup.performance.l2ProtTunnel.dropped.mmrp

       32 bit unsigned wrappable counter."
   ::= {pr1645v2BgrMVL2ProtTunnelEntry 67698688}

pr1645v2BgrMVL2ProtTunnelDroppedMvrp OBJECT-TYPE
   SYNTAX      Counter32
   MAX-ACCESS  read-only
   STATUS      current
   DESCRIPTION
      "Path: bridgeGroup.performance.l2ProtTunnel.dropped.mvrp

       32 bit unsigned wrappable counter."
   ::= {pr1645v2BgrMVL2ProtTunnelEntry 67764224}

pr1645v2BgrMVL2ProtTunnelDroppedGvrp OBJECT-TYPE
   SYNTAX      Counter32
   MAX-ACCESS  read-only
   STATUS      current
   DESCRIPTION
      "Path: bridgeGroup.performance.l2ProtTunnel.dropped.gvrp

       32 bit unsigned wrappable counter."
   ::= {pr1645v2BgrMVL2ProtTunnelEntry 67829760}

pr1645v2BgrMVL2ProtTunnelDroppedGmrp OBJECT-TYPE
   SYNTAX      Counter32
   MAX-ACCESS  read-only
   STATUS      current
   DESCRIPTION
      "Path: bridgeGroup.performance.l2ProtTunnel.dropped.gmrp

       32 bit unsigned wrappable counter."
   ::= {pr1645v2BgrMVL2ProtTunnelEntry 67895296}

pr1645v2BgrMVL2ProtTunnelDroppedDtp OBJECT-TYPE
   SYNTAX      Counter32
   MAX-ACCESS  read-only
   STATUS      current
   DESCRIPTION
      "Path: bridgeGroup.performance.l2ProtTunnel.dropped.dtp

       32 bit unsigned wrappable counter."
   ::= {pr1645v2BgrMVL2ProtTunnelEntry 67960832}

pr1645v2BgrMVL2ProtTunnelDroppedPagp OBJECT-TYPE
   SYNTAX      Counter32
   MAX-ACCESS  read-only
   STATUS      current
   DESCRIPTION
      "Path: bridgeGroup.performance.l2ProtTunnel.dropped.pagp

       32 bit unsigned wrappable counter."
   ::= {pr1645v2BgrMVL2ProtTunnelEntry 68026368}

pr1645v2BgrMVL2ProtTunnelDroppedUdld OBJECT-TYPE
   SYNTAX      Counter32
   MAX-ACCESS  read-only
   STATUS      current
   DESCRIPTION
      "Path: bridgeGroup.performance.l2ProtTunnel.dropped.udld

       32 bit unsigned wrappable counter."
   ::= {pr1645v2BgrMVL2ProtTunnelEntry 68091904}


pr1645v2BgrMVH2Perf OBJECT IDENTIFIER ::= {pr1645v2BgrMV 91}

pr1645v2BgrMVH2PerfSSCTable OBJECT-TYPE
   SYNTAX      SEQUENCE OF Pr1645v2BgrMVH2PerfEntry
   MAX-ACCESS  not-accessible
   STATUS      current
   DESCRIPTION
      "2 hour bridge stats"
   ::= {pr1645v2BgrMVH2Perf 1}

pr1645v2BgrMVH2PerfEntry OBJECT-TYPE
   SYNTAX      Pr1645v2BgrMVH2PerfEntry
   MAX-ACCESS  not-accessible
   STATUS      current
   DESCRIPTION
      ""
   INDEX      { pr1645v2BgrMVH2PerfTableIx }
   ::= {pr1645v2BgrMVH2PerfSSCTable 1}

Pr1645v2BgrMVH2PerfEntry ::=
   SEQUENCE
      {
      pr1645v2BgrMVH2PerfTableIx
         TableIndex,
      pr1645v2BgrMVH2PerfSysUpTime
         TimeTicks,
      pr1645v2BgrMVH2PerfRxPkts
         Counter32,
      pr1645v2BgrMVH2PerfTxPkts
         Counter32,
      pr1645v2BgrMVH2PerfDiscards
         Counter32,
      pr1645v2BgrMVH2PerfFloods
         Counter32,
      pr1645v2BgrMVH2PerfBroadcasts
         Counter32,
      pr1645v2BgrMVH2PerfMulticasts
         Counter32,
      pr1645v2BgrMVH2PerfCacheSizeOverflows
         Counter32,
      pr1645v2BgrMVH2PerfStaticCacheViolations
         Counter32,
      pr1645v2BgrMVH2PerfCacheRelearns
         Counter32,
      pr1645v2BgrMVH2PerfCacheRelearnDrops
         Counter32,
      pr1645v2BgrMVH2PerfLoopsDetected
         Counter32
      }

pr1645v2BgrMVH2PerfTableIx OBJECT-TYPE
   SYNTAX      TableIndex
   MAX-ACCESS  not-accessible
   STATUS      current
   DESCRIPTION
      ""
   ::= {pr1645v2BgrMVH2PerfEntry 11}

pr1645v2BgrMVH2PerfSysUpTime OBJECT-TYPE
   SYNTAX      TimeTicks
   MAX-ACCESS  read-only
   STATUS      current
   DESCRIPTION
      "Path: bridgeGroup.performance.h2Performance.sysUpTime

       Time in centi-second."
   ::= {pr1645v2BgrMVH2PerfEntry 16777216}

pr1645v2BgrMVH2PerfRxPkts OBJECT-TYPE
   SYNTAX      Counter32
   MAX-ACCESS  read-only
   STATUS      current
   DESCRIPTION
      "Path: bridgeGroup.performance.h2Performance.rxPkts

       32 bit unsigned wrappable counter."
   ::= {pr1645v2BgrMVH2PerfEntry 33554432}

pr1645v2BgrMVH2PerfTxPkts OBJECT-TYPE
   SYNTAX      Counter32
   MAX-ACCESS  read-only
   STATUS      current
   DESCRIPTION
      "Path: bridgeGroup.performance.h2Performance.txPkts

       32 bit unsigned wrappable counter."
   ::= {pr1645v2BgrMVH2PerfEntry 50331648}

pr1645v2BgrMVH2PerfDiscards OBJECT-TYPE
   SYNTAX      Counter32
   MAX-ACCESS  read-only
   STATUS      current
   DESCRIPTION
      "Path: bridgeGroup.performance.h2Performance.discards

       32 bit unsigned wrappable counter."
   ::= {pr1645v2BgrMVH2PerfEntry 67108864}

pr1645v2BgrMVH2PerfFloods OBJECT-TYPE
   SYNTAX      Counter32
   MAX-ACCESS  read-only
   STATUS      current
   DESCRIPTION
      "Path: bridgeGroup.performance.h2Performance.floods

       32 bit unsigned wrappable counter."
   ::= {pr1645v2BgrMVH2PerfEntry 83886080}

pr1645v2BgrMVH2PerfBroadcasts OBJECT-TYPE
   SYNTAX      Counter32
   MAX-ACCESS  read-only
   STATUS      current
   DESCRIPTION
      "Path: bridgeGroup.performance.h2Performance.broadcasts

       32 bit unsigned wrappable counter."
   ::= {pr1645v2BgrMVH2PerfEntry 100663296}

pr1645v2BgrMVH2PerfMulticasts OBJECT-TYPE
   SYNTAX      Counter32
   MAX-ACCESS  read-only
   STATUS      current
   DESCRIPTION
      "Path: bridgeGroup.performance.h2Performance.multicasts

       32 bit unsigned wrappable counter."
   ::= {pr1645v2BgrMVH2PerfEntry 117440512}

pr1645v2BgrMVH2PerfCacheSizeOverflows OBJECT-TYPE
   SYNTAX      Counter32
   MAX-ACCESS  read-only
   STATUS      current
   DESCRIPTION
      "Path: bridgeGroup.performance.h2Performance.cacheSizeOverflows

       32 bit unsigned wrappable counter."
   ::= {pr1645v2BgrMVH2PerfEntry 134217728}

pr1645v2BgrMVH2PerfStaticCacheViolations OBJECT-TYPE
   SYNTAX      Counter32
   MAX-ACCESS  read-only
   STATUS      current
   DESCRIPTION
      "Path: bridgeGroup.performance.h2Performance.staticCacheViolations

       32 bit unsigned wrappable counter."
   ::= {pr1645v2BgrMVH2PerfEntry 150994944}

pr1645v2BgrMVH2PerfCacheRelearns OBJECT-TYPE
   SYNTAX      Counter32
   MAX-ACCESS  read-only
   STATUS      current
   DESCRIPTION
      "Path: bridgeGroup.performance.h2Performance.cacheRelearns

       32 bit unsigned wrappable counter."
   ::= {pr1645v2BgrMVH2PerfEntry 167772160}

pr1645v2BgrMVH2PerfCacheRelearnDrops OBJECT-TYPE
   SYNTAX      Counter32
   MAX-ACCESS  read-only
   STATUS      current
   DESCRIPTION
      "Path: bridgeGroup.performance.h2Performance.cacheRelearnDrops

       32 bit unsigned wrappable counter."
   ::= {pr1645v2BgrMVH2PerfEntry 184549376}

pr1645v2BgrMVH2PerfLoopsDetected OBJECT-TYPE
   SYNTAX      Counter32
   MAX-ACCESS  read-only
   STATUS      current
   DESCRIPTION
      "Path: bridgeGroup.performance.h2Performance.loopsDetected

       32 bit unsigned wrappable counter."
   ::= {pr1645v2BgrMVH2PerfEntry 234881024}


pr1645v2BgrMVH24Perf OBJECT IDENTIFIER ::= {pr1645v2BgrMV 92}

pr1645v2BgrMVH24PerfSSCTable OBJECT-TYPE
   SYNTAX      SEQUENCE OF Pr1645v2BgrMVH24PerfEntry
   MAX-ACCESS  not-accessible
   STATUS      current
   DESCRIPTION
      "24 hour bridge stats"
   ::= {pr1645v2BgrMVH24Perf 1}

pr1645v2BgrMVH24PerfEntry OBJECT-TYPE
   SYNTAX      Pr1645v2BgrMVH24PerfEntry
   MAX-ACCESS  not-accessible
   STATUS      current
   DESCRIPTION
      ""
   INDEX      { pr1645v2BgrMVH24PerfTableIx }
   ::= {pr1645v2BgrMVH24PerfSSCTable 1}

Pr1645v2BgrMVH24PerfEntry ::=
   SEQUENCE
      {
      pr1645v2BgrMVH24PerfTableIx
         TableIndex,
      pr1645v2BgrMVH24PerfSysUpTime
         TimeTicks,
      pr1645v2BgrMVH24PerfRxPkts
         Counter32,
      pr1645v2BgrMVH24PerfTxPkts
         Counter32,
      pr1645v2BgrMVH24PerfDiscards
         Counter32,
      pr1645v2BgrMVH24PerfFloods
         Counter32,
      pr1645v2BgrMVH24PerfBroadcasts
         Counter32,
      pr1645v2BgrMVH24PerfMulticasts
         Counter32,
      pr1645v2BgrMVH24PerfCacheSizeOverflows
         Counter32,
      pr1645v2BgrMVH24PerfStaticCacheViolations
         Counter32,
      pr1645v2BgrMVH24PerfCacheRelearns
         Counter32,
      pr1645v2BgrMVH24PerfCacheRelearnDrops
         Counter32,
      pr1645v2BgrMVH24PerfLoopsDetected
         Counter32
      }

pr1645v2BgrMVH24PerfTableIx OBJECT-TYPE
   SYNTAX      TableIndex
   MAX-ACCESS  not-accessible
   STATUS      current
   DESCRIPTION
      ""
   ::= {pr1645v2BgrMVH24PerfEntry 11}

pr1645v2BgrMVH24PerfSysUpTime OBJECT-TYPE
   SYNTAX      TimeTicks
   MAX-ACCESS  read-only
   STATUS      current
   DESCRIPTION
      "Path: bridgeGroup.performance.h24Performance.sysUpTime

       Time in centi-second."
   ::= {pr1645v2BgrMVH24PerfEntry 16777216}

pr1645v2BgrMVH24PerfRxPkts OBJECT-TYPE
   SYNTAX      Counter32
   MAX-ACCESS  read-only
   STATUS      current
   DESCRIPTION
      "Path: bridgeGroup.performance.h24Performance.rxPkts

       32 bit unsigned wrappable counter."
   ::= {pr1645v2BgrMVH24PerfEntry 33554432}

pr1645v2BgrMVH24PerfTxPkts OBJECT-TYPE
   SYNTAX      Counter32
   MAX-ACCESS  read-only
   STATUS      current
   DESCRIPTION
      "Path: bridgeGroup.performance.h24Performance.txPkts

       32 bit unsigned wrappable counter."
   ::= {pr1645v2BgrMVH24PerfEntry 50331648}

pr1645v2BgrMVH24PerfDiscards OBJECT-TYPE
   SYNTAX      Counter32
   MAX-ACCESS  read-only
   STATUS      current
   DESCRIPTION
      "Path: bridgeGroup.performance.h24Performance.discards

       32 bit unsigned wrappable counter."
   ::= {pr1645v2BgrMVH24PerfEntry 67108864}

pr1645v2BgrMVH24PerfFloods OBJECT-TYPE
   SYNTAX      Counter32
   MAX-ACCESS  read-only
   STATUS      current
   DESCRIPTION
      "Path: bridgeGroup.performance.h24Performance.floods

       32 bit unsigned wrappable counter."
   ::= {pr1645v2BgrMVH24PerfEntry 83886080}

pr1645v2BgrMVH24PerfBroadcasts OBJECT-TYPE
   SYNTAX      Counter32
   MAX-ACCESS  read-only
   STATUS      current
   DESCRIPTION
      "Path: bridgeGroup.performance.h24Performance.broadcasts

       32 bit unsigned wrappable counter."
   ::= {pr1645v2BgrMVH24PerfEntry 100663296}

pr1645v2BgrMVH24PerfMulticasts OBJECT-TYPE
   SYNTAX      Counter32
   MAX-ACCESS  read-only
   STATUS      current
   DESCRIPTION
      "Path: bridgeGroup.performance.h24Performance.multicasts

       32 bit unsigned wrappable counter."
   ::= {pr1645v2BgrMVH24PerfEntry 117440512}

pr1645v2BgrMVH24PerfCacheSizeOverflows OBJECT-TYPE
   SYNTAX      Counter32
   MAX-ACCESS  read-only
   STATUS      current
   DESCRIPTION
      "Path: bridgeGroup.performance.h24Performance.cacheSizeOverflows

       32 bit unsigned wrappable counter."
   ::= {pr1645v2BgrMVH24PerfEntry 134217728}

pr1645v2BgrMVH24PerfStaticCacheViolations OBJECT-TYPE
   SYNTAX      Counter32
   MAX-ACCESS  read-only
   STATUS      current
   DESCRIPTION
      "Path: bridgeGroup.performance.h24Performance.staticCacheViolations

       32 bit unsigned wrappable counter."
   ::= {pr1645v2BgrMVH24PerfEntry 150994944}

pr1645v2BgrMVH24PerfCacheRelearns OBJECT-TYPE
   SYNTAX      Counter32
   MAX-ACCESS  read-only
   STATUS      current
   DESCRIPTION
      "Path: bridgeGroup.performance.h24Performance.cacheRelearns

       32 bit unsigned wrappable counter."
   ::= {pr1645v2BgrMVH24PerfEntry 167772160}

pr1645v2BgrMVH24PerfCacheRelearnDrops OBJECT-TYPE
   SYNTAX      Counter32
   MAX-ACCESS  read-only
   STATUS      current
   DESCRIPTION
      "Path: bridgeGroup.performance.h24Performance.cacheRelearnDrops

       32 bit unsigned wrappable counter."
   ::= {pr1645v2BgrMVH24PerfEntry 184549376}

pr1645v2BgrMVH24PerfLoopsDetected OBJECT-TYPE
   SYNTAX      Counter32
   MAX-ACCESS  read-only
   STATUS      current
   DESCRIPTION
      "Path: bridgeGroup.performance.h24Performance.loopsDetected

       32 bit unsigned wrappable counter."
   ::= {pr1645v2BgrMVH24PerfEntry 234881024}


pr1645v2BgrMVD7Perf OBJECT IDENTIFIER ::= {pr1645v2BgrMV 93}

pr1645v2BgrMVD7PerfSSCTable OBJECT-TYPE
   SYNTAX      SEQUENCE OF Pr1645v2BgrMVD7PerfEntry
   MAX-ACCESS  not-accessible
   STATUS      current
   DESCRIPTION
      "7 days bridge stats"
   ::= {pr1645v2BgrMVD7Perf 1}

pr1645v2BgrMVD7PerfEntry OBJECT-TYPE
   SYNTAX      Pr1645v2BgrMVD7PerfEntry
   MAX-ACCESS  not-accessible
   STATUS      current
   DESCRIPTION
      ""
   INDEX      { pr1645v2BgrMVD7PerfTableIx }
   ::= {pr1645v2BgrMVD7PerfSSCTable 1}

Pr1645v2BgrMVD7PerfEntry ::=
   SEQUENCE
      {
      pr1645v2BgrMVD7PerfTableIx
         TableIndex,
      pr1645v2BgrMVD7PerfSysUpTime
         TimeTicks,
      pr1645v2BgrMVD7PerfRxPkts
         Counter32,
      pr1645v2BgrMVD7PerfTxPkts
         Counter32,
      pr1645v2BgrMVD7PerfDiscards
         Counter32,
      pr1645v2BgrMVD7PerfFloods
         Counter32,
      pr1645v2BgrMVD7PerfBroadcasts
         Counter32,
      pr1645v2BgrMVD7PerfMulticasts
         Counter32,
      pr1645v2BgrMVD7PerfCacheSizeOverflows
         Counter32,
      pr1645v2BgrMVD7PerfStaticCacheViolations
         Counter32,
      pr1645v2BgrMVD7PerfCacheRelearns
         Counter32,
      pr1645v2BgrMVD7PerfCacheRelearnDrops
         Counter32,
      pr1645v2BgrMVD7PerfLoopsDetected
         Counter32
      }

pr1645v2BgrMVD7PerfTableIx OBJECT-TYPE
   SYNTAX      TableIndex
   MAX-ACCESS  not-accessible
   STATUS      current
   DESCRIPTION
      ""
   ::= {pr1645v2BgrMVD7PerfEntry 11}

pr1645v2BgrMVD7PerfSysUpTime OBJECT-TYPE
   SYNTAX      TimeTicks
   MAX-ACCESS  read-only
   STATUS      current
   DESCRIPTION
      "Path: bridgeGroup.performance.d7Performance.sysUpTime

       Time in centi-second."
   ::= {pr1645v2BgrMVD7PerfEntry 16777216}

pr1645v2BgrMVD7PerfRxPkts OBJECT-TYPE
   SYNTAX      Counter32
   MAX-ACCESS  read-only
   STATUS      current
   DESCRIPTION
      "Path: bridgeGroup.performance.d7Performance.rxPkts

       32 bit unsigned wrappable counter."
   ::= {pr1645v2BgrMVD7PerfEntry 33554432}

pr1645v2BgrMVD7PerfTxPkts OBJECT-TYPE
   SYNTAX      Counter32
   MAX-ACCESS  read-only
   STATUS      current
   DESCRIPTION
      "Path: bridgeGroup.performance.d7Performance.txPkts

       32 bit unsigned wrappable counter."
   ::= {pr1645v2BgrMVD7PerfEntry 50331648}

pr1645v2BgrMVD7PerfDiscards OBJECT-TYPE
   SYNTAX      Counter32
   MAX-ACCESS  read-only
   STATUS      current
   DESCRIPTION
      "Path: bridgeGroup.performance.d7Performance.discards

       32 bit unsigned wrappable counter."
   ::= {pr1645v2BgrMVD7PerfEntry 67108864}

pr1645v2BgrMVD7PerfFloods OBJECT-TYPE
   SYNTAX      Counter32
   MAX-ACCESS  read-only
   STATUS      current
   DESCRIPTION
      "Path: bridgeGroup.performance.d7Performance.floods

       32 bit unsigned wrappable counter."
   ::= {pr1645v2BgrMVD7PerfEntry 83886080}

pr1645v2BgrMVD7PerfBroadcasts OBJECT-TYPE
   SYNTAX      Counter32
   MAX-ACCESS  read-only
   STATUS      current
   DESCRIPTION
      "Path: bridgeGroup.performance.d7Performance.broadcasts

       32 bit unsigned wrappable counter."
   ::= {pr1645v2BgrMVD7PerfEntry 100663296}

pr1645v2BgrMVD7PerfMulticasts OBJECT-TYPE
   SYNTAX      Counter32
   MAX-ACCESS  read-only
   STATUS      current
   DESCRIPTION
      "Path: bridgeGroup.performance.d7Performance.multicasts

       32 bit unsigned wrappable counter."
   ::= {pr1645v2BgrMVD7PerfEntry 117440512}

pr1645v2BgrMVD7PerfCacheSizeOverflows OBJECT-TYPE
   SYNTAX      Counter32
   MAX-ACCESS  read-only
   STATUS      current
   DESCRIPTION
      "Path: bridgeGroup.performance.d7Performance.cacheSizeOverflows

       32 bit unsigned wrappable counter."
   ::= {pr1645v2BgrMVD7PerfEntry 134217728}

pr1645v2BgrMVD7PerfStaticCacheViolations OBJECT-TYPE
   SYNTAX      Counter32
   MAX-ACCESS  read-only
   STATUS      current
   DESCRIPTION
      "Path: bridgeGroup.performance.d7Performance.staticCacheViolations

       32 bit unsigned wrappable counter."
   ::= {pr1645v2BgrMVD7PerfEntry 150994944}

pr1645v2BgrMVD7PerfCacheRelearns OBJECT-TYPE
   SYNTAX      Counter32
   MAX-ACCESS  read-only
   STATUS      current
   DESCRIPTION
      "Path: bridgeGroup.performance.d7Performance.cacheRelearns

       32 bit unsigned wrappable counter."
   ::= {pr1645v2BgrMVD7PerfEntry 167772160}

pr1645v2BgrMVD7PerfCacheRelearnDrops OBJECT-TYPE
   SYNTAX      Counter32
   MAX-ACCESS  read-only
   STATUS      current
   DESCRIPTION
      "Path: bridgeGroup.performance.d7Performance.cacheRelearnDrops

       32 bit unsigned wrappable counter."
   ::= {pr1645v2BgrMVD7PerfEntry 184549376}

pr1645v2BgrMVD7PerfLoopsDetected OBJECT-TYPE
   SYNTAX      Counter32
   MAX-ACCESS  read-only
   STATUS      current
   DESCRIPTION
      "Path: bridgeGroup.performance.d7Performance.loopsDetected

       32 bit unsigned wrappable counter."
   ::= {pr1645v2BgrMVD7PerfEntry 234881024}


pr1645v2BgrMVVlan OBJECT IDENTIFIER ::= {pr1645v2BgrMV 310}

pr1645v2BgrMVVlanSSCTable OBJECT-TYPE
   SYNTAX      SEQUENCE OF Pr1645v2BgrMVVlanEntry
   MAX-ACCESS  not-accessible
   STATUS      current
   DESCRIPTION
      ""
   ::= {pr1645v2BgrMVVlan 1}

pr1645v2BgrMVVlanEntry OBJECT-TYPE
   SYNTAX      Pr1645v2BgrMVVlanEntry
   MAX-ACCESS  not-accessible
   STATUS      current
   DESCRIPTION
      ""
   INDEX      { pr1645v2BgrMVVlanTableIx }
   ::= {pr1645v2BgrMVVlanSSCTable 1}

Pr1645v2BgrMVVlanEntry ::=
   SEQUENCE
      {
      pr1645v2BgrMVVlanTableIx
         TableIndex,
      pr1645v2BgrMVVlanName
         DisplayString,
      pr1645v2BgrMVVlanMCInOctets
         Counter64,
      pr1645v2BgrMVVlanMCInUcast
         Counter64,
      pr1645v2BgrMVVlanMCInNUcastPkts
         Counter64,
      pr1645v2BgrMVVlanMCInBcastPkts
         Counter64,
      pr1645v2BgrMVVlanMCInMcastPkts
         Counter64,
      pr1645v2BgrMVVlanMCInDiscards
         Counter64,
      pr1645v2BgrMVVlanMCInErrors
         Counter64,
      pr1645v2BgrMVVlanMCInUnknownProtos
         Counter64,
      pr1645v2BgrMVVlanMCInDropEx
         Counter64,
      pr1645v2BgrMVVlanMCInDropNoMac
         Counter64,
      pr1645v2BgrMVVlanMCInDropNUCast
         Counter64,
      pr1645v2BgrMVVlanMCInDropFilter
         Counter64,
      pr1645v2BgrMVVlanMCInBandwidth15sec
         Integer32,
      pr1645v2BgrMVVlanMCInBandwidth30sec
         Integer32,
      pr1645v2BgrMVVlanMCInBandwidth1min
         Integer32,
      pr1645v2BgrMVVlanMCInBandwidth2min
         Integer32,
      pr1645v2BgrMVVlanMCInBandwidth5min
         Integer32,
      pr1645v2BgrMVVlanMCOutOctets
         Counter64,
      pr1645v2BgrMVVlanMCOutUcastPkts
         Counter64,
      pr1645v2BgrMVVlanMCOutNUcastPkts
         Counter64,
      pr1645v2BgrMVVlanMCOutBcastPkts
         Counter64,
      pr1645v2BgrMVVlanMCOutMcastPkts
         Counter64,
      pr1645v2BgrMVVlanMCOutDiscards
         Counter64,
      pr1645v2BgrMVVlanMCOutErrors
         Counter64,
      pr1645v2BgrMVVlanMCOutQLen
         Counter32,
      pr1645v2BgrMVVlanMCOutDropEx
         Counter64,
      pr1645v2BgrMVVlanMCOutDropNoArp
         Counter64,
      pr1645v2BgrMVVlanMCOutDropFilter
         Counter64,
      pr1645v2BgrMVVlanMCOutBandwidth15sec
         Integer32,
      pr1645v2BgrMVVlanMCOutBandwidth30sec
         Integer32,
      pr1645v2BgrMVVlanMCOutBandwidth1min
         Integer32,
      pr1645v2BgrMVVlanMCOutBandwidth2min
         Integer32,
      pr1645v2BgrMVVlanMCOutBandwidth5min
         Integer32,
      pr1645v2BgrMVVlanVlanVid
         Integer32
      }

pr1645v2BgrMVVlanTableIx OBJECT-TYPE
   SYNTAX      TableIndex
   MAX-ACCESS  not-accessible
   STATUS      current
   DESCRIPTION
      ""
   ::= {pr1645v2BgrMVVlanEntry 11}

pr1645v2BgrMVVlanName OBJECT-TYPE
   SYNTAX      DisplayString
   MAX-ACCESS  read-only
   STATUS      current
   DESCRIPTION
      "Path: bridgeGroup.performance.vlan.name"
   ::= {pr1645v2BgrMVVlanEntry 16777216}

pr1645v2BgrMVVlanMCInOctets OBJECT-TYPE
   SYNTAX      Counter64
   MAX-ACCESS  read-only
   STATUS      current
   DESCRIPTION
      "Path: bridgeGroup.performance.vlan.mibCounters.ifInOctets

       64 bit unsigned wrappable counter."
   ::= {pr1645v2BgrMVVlanEntry 40697856}

pr1645v2BgrMVVlanMCInUcast OBJECT-TYPE
   SYNTAX      Counter64
   MAX-ACCESS  read-only
   STATUS      current
   DESCRIPTION
      "Path: bridgeGroup.performance.vlan.mibCounters.ifInUcastPkts

       64 bit unsigned wrappable counter."
   ::= {pr1645v2BgrMVVlanEntry 40763392}

pr1645v2BgrMVVlanMCInNUcastPkts OBJECT-TYPE
   SYNTAX      Counter64
   MAX-ACCESS  read-only
   STATUS      current
   DESCRIPTION
      "Path: bridgeGroup.performance.vlan.mibCounters.ifInNUcastPkts

       64 bit unsigned wrappable counter."
   ::= {pr1645v2BgrMVVlanEntry 40828928}

pr1645v2BgrMVVlanMCInBcastPkts OBJECT-TYPE
   SYNTAX      Counter64
   MAX-ACCESS  read-only
   STATUS      current
   DESCRIPTION
      "Path: bridgeGroup.performance.vlan.mibCounters.ifInBcastPkts

       64 bit unsigned wrappable counter."
   ::= {pr1645v2BgrMVVlanEntry 47382528}

pr1645v2BgrMVVlanMCInMcastPkts OBJECT-TYPE
   SYNTAX      Counter64
   MAX-ACCESS  read-only
   STATUS      current
   DESCRIPTION
      "Path: bridgeGroup.performance.vlan.mibCounters.ifInMcastPkts

       64 bit unsigned wrappable counter."
   ::= {pr1645v2BgrMVVlanEntry 48037888}

pr1645v2BgrMVVlanMCInDiscards OBJECT-TYPE
   SYNTAX      Counter64
   MAX-ACCESS  read-only
   STATUS      current
   DESCRIPTION
      "Path: bridgeGroup.performance.vlan.mibCounters.ifInDiscards

       64 bit unsigned wrappable counter."
   ::= {pr1645v2BgrMVVlanEntry 40894464}

pr1645v2BgrMVVlanMCInErrors OBJECT-TYPE
   SYNTAX      Counter64
   MAX-ACCESS  read-only
   STATUS      current
   DESCRIPTION
      "Path: bridgeGroup.performance.vlan.mibCounters.ifInErrors

       64 bit unsigned wrappable counter."
   ::= {pr1645v2BgrMVVlanEntry 40960000}

pr1645v2BgrMVVlanMCInUnknownProtos OBJECT-TYPE
   SYNTAX      Counter64
   MAX-ACCESS  read-only
   STATUS      current
   DESCRIPTION
      "Path: bridgeGroup.performance.vlan.mibCounters.ifInUnknownProtos

       64 bit unsigned wrappable counter."
   ::= {pr1645v2BgrMVVlanEntry 41025536}

pr1645v2BgrMVVlanMCInDropEx OBJECT-TYPE
   SYNTAX      Counter64
   MAX-ACCESS  read-only
   STATUS      current
   DESCRIPTION
      "Path: bridgeGroup.performance.vlan.mibCounters.ifInDropLevelExceeded

       64 bit unsigned wrappable counter."
   ::= {pr1645v2BgrMVVlanEntry 42074112}

pr1645v2BgrMVVlanMCInDropNoMac OBJECT-TYPE
   SYNTAX      Counter64
   MAX-ACCESS  read-only
   STATUS      current
   DESCRIPTION
      "Path: bridgeGroup.performance.vlan.mibCounters.ifInDiscardsNoMacFit

       64 bit unsigned wrappable counter."
   ::= {pr1645v2BgrMVVlanEntry 42270720}

pr1645v2BgrMVVlanMCInDropNUCast OBJECT-TYPE
   SYNTAX      Counter64
   MAX-ACCESS  read-only
   STATUS      current
   DESCRIPTION
      "Path: bridgeGroup.performance.vlan.mibCounters.ifInDiscardsNUCast

       64 bit unsigned wrappable counter."
   ::= {pr1645v2BgrMVVlanEntry 42467328}

pr1645v2BgrMVVlanMCInDropFilter OBJECT-TYPE
   SYNTAX      Counter64
   MAX-ACCESS  read-only
   STATUS      current
   DESCRIPTION
      "Path: bridgeGroup.performance.vlan.mibCounters.ifInDiscardsFilter

       64 bit unsigned wrappable counter."
   ::= {pr1645v2BgrMVVlanEntry 42532864}

pr1645v2BgrMVVlanMCInBandwidth15sec OBJECT-TYPE
   SYNTAX      Integer32
   MAX-ACCESS  read-only
   STATUS      current
   DESCRIPTION
      "Path: bridgeGroup.performance.vlan.mibCounters.ifInBandwidth.15sec

       unit name = bps
       formula = 8 * ; 8 /"
   ::= {pr1645v2BgrMVVlanEntry 45417728}

pr1645v2BgrMVVlanMCInBandwidth30sec OBJECT-TYPE
   SYNTAX      Integer32
   MAX-ACCESS  read-only
   STATUS      current
   DESCRIPTION
      "Path: bridgeGroup.performance.vlan.mibCounters.ifInBandwidth.30sec

       unit name = bps
       formula = 8 * ; 8 /"
   ::= {pr1645v2BgrMVVlanEntry 45419008}

pr1645v2BgrMVVlanMCInBandwidth1min OBJECT-TYPE
   SYNTAX      Integer32
   MAX-ACCESS  read-only
   STATUS      current
   DESCRIPTION
      "Path: bridgeGroup.performance.vlan.mibCounters.ifInBandwidth.1min

       unit name = bps
       formula = 8 * ; 8 /"
   ::= {pr1645v2BgrMVVlanEntry 45421568}

pr1645v2BgrMVVlanMCInBandwidth2min OBJECT-TYPE
   SYNTAX      Integer32
   MAX-ACCESS  read-only
   STATUS      current
   DESCRIPTION
      "Path: bridgeGroup.performance.vlan.mibCounters.ifInBandwidth.2min

       unit name = bps
       formula = 8 * ; 8 /"
   ::= {pr1645v2BgrMVVlanEntry 45426688}

pr1645v2BgrMVVlanMCInBandwidth5min OBJECT-TYPE
   SYNTAX      Integer32
   MAX-ACCESS  read-only
   STATUS      current
   DESCRIPTION
      "Path: bridgeGroup.performance.vlan.mibCounters.ifInBandwidth.5min

       unit name = bps
       formula = 8 * ; 8 /"
   ::= {pr1645v2BgrMVVlanEntry 45442048}

pr1645v2BgrMVVlanMCOutOctets OBJECT-TYPE
   SYNTAX      Counter64
   MAX-ACCESS  read-only
   STATUS      current
   DESCRIPTION
      "Path: bridgeGroup.performance.vlan.mibCounters.ifOutOctets

       64 bit unsigned wrappable counter."
   ::= {pr1645v2BgrMVVlanEntry 41091072}

pr1645v2BgrMVVlanMCOutUcastPkts OBJECT-TYPE
   SYNTAX      Counter64
   MAX-ACCESS  read-only
   STATUS      current
   DESCRIPTION
      "Path: bridgeGroup.performance.vlan.mibCounters.ifOutUcastPkts

       64 bit unsigned wrappable counter."
   ::= {pr1645v2BgrMVVlanEntry 41156608}

pr1645v2BgrMVVlanMCOutNUcastPkts OBJECT-TYPE
   SYNTAX      Counter64
   MAX-ACCESS  read-only
   STATUS      current
   DESCRIPTION
      "Path: bridgeGroup.performance.vlan.mibCounters.ifOutNUcastPkts

       64 bit unsigned wrappable counter."
   ::= {pr1645v2BgrMVVlanEntry 41222144}

pr1645v2BgrMVVlanMCOutBcastPkts OBJECT-TYPE
   SYNTAX      Counter64
   MAX-ACCESS  read-only
   STATUS      current
   DESCRIPTION
      "Path: bridgeGroup.performance.vlan.mibCounters.ifOutBcastPkts

       64 bit unsigned wrappable counter."
   ::= {pr1645v2BgrMVVlanEntry 47775744}

pr1645v2BgrMVVlanMCOutMcastPkts OBJECT-TYPE
   SYNTAX      Counter64
   MAX-ACCESS  read-only
   STATUS      current
   DESCRIPTION
      "Path: bridgeGroup.performance.vlan.mibCounters.ifOutMcastPkts

       64 bit unsigned wrappable counter."
   ::= {pr1645v2BgrMVVlanEntry 48431104}

pr1645v2BgrMVVlanMCOutDiscards OBJECT-TYPE
   SYNTAX      Counter64
   MAX-ACCESS  read-only
   STATUS      current
   DESCRIPTION
      "Path: bridgeGroup.performance.vlan.mibCounters.ifOutDiscards

       64 bit unsigned wrappable counter."
   ::= {pr1645v2BgrMVVlanEntry 41287680}

pr1645v2BgrMVVlanMCOutErrors OBJECT-TYPE
   SYNTAX      Counter64
   MAX-ACCESS  read-only
   STATUS      current
   DESCRIPTION
      "Path: bridgeGroup.performance.vlan.mibCounters.ifOutErrors

       64 bit unsigned wrappable counter."
   ::= {pr1645v2BgrMVVlanEntry 41353216}

pr1645v2BgrMVVlanMCOutQLen OBJECT-TYPE
   SYNTAX      Counter32
   MAX-ACCESS  read-only
   STATUS      current
   DESCRIPTION
      "Path: bridgeGroup.performance.vlan.mibCounters.ifOutQLen

       32 bit unsigned wrappable counter."
   ::= {pr1645v2BgrMVVlanEntry 41418752}

pr1645v2BgrMVVlanMCOutDropEx OBJECT-TYPE
   SYNTAX      Counter64
   MAX-ACCESS  read-only
   STATUS      current
   DESCRIPTION
      "Path: bridgeGroup.performance.vlan.mibCounters.ifOutDropLevelExceeded

       64 bit unsigned wrappable counter."
   ::= {pr1645v2BgrMVVlanEntry 41484288}

pr1645v2BgrMVVlanMCOutDropNoArp OBJECT-TYPE
   SYNTAX      Counter64
   MAX-ACCESS  read-only
   STATUS      current
   DESCRIPTION
      "Path: bridgeGroup.performance.vlan.mibCounters.ifOutDiscardsNoArp

       64 bit unsigned wrappable counter."
   ::= {pr1645v2BgrMVVlanEntry 42336256}

pr1645v2BgrMVVlanMCOutDropFilter OBJECT-TYPE
   SYNTAX      Counter64
   MAX-ACCESS  read-only
   STATUS      current
   DESCRIPTION
      "Path: bridgeGroup.performance.vlan.mibCounters.ifOutDiscardsFilter

       64 bit unsigned wrappable counter."
   ::= {pr1645v2BgrMVVlanEntry 42598400}

pr1645v2BgrMVVlanMCOutBandwidth15sec OBJECT-TYPE
   SYNTAX      Integer32
   MAX-ACCESS  read-only
   STATUS      current
   DESCRIPTION
      "Path: bridgeGroup.performance.vlan.mibCounters.ifOutBandwidth.15sec

       unit name = bps
       formula = 8 * ; 8 /"
   ::= {pr1645v2BgrMVVlanEntry 45483264}

pr1645v2BgrMVVlanMCOutBandwidth30sec OBJECT-TYPE
   SYNTAX      Integer32
   MAX-ACCESS  read-only
   STATUS      current
   DESCRIPTION
      "Path: bridgeGroup.performance.vlan.mibCounters.ifOutBandwidth.30sec

       unit name = bps
       formula = 8 * ; 8 /"
   ::= {pr1645v2BgrMVVlanEntry 45484544}

pr1645v2BgrMVVlanMCOutBandwidth1min OBJECT-TYPE
   SYNTAX      Integer32
   MAX-ACCESS  read-only
   STATUS      current
   DESCRIPTION
      "Path: bridgeGroup.performance.vlan.mibCounters.ifOutBandwidth.1min

       unit name = bps
       formula = 8 * ; 8 /"
   ::= {pr1645v2BgrMVVlanEntry 45487104}

pr1645v2BgrMVVlanMCOutBandwidth2min OBJECT-TYPE
   SYNTAX      Integer32
   MAX-ACCESS  read-only
   STATUS      current
   DESCRIPTION
      "Path: bridgeGroup.performance.vlan.mibCounters.ifOutBandwidth.2min

       unit name = bps
       formula = 8 * ; 8 /"
   ::= {pr1645v2BgrMVVlanEntry 45492224}

pr1645v2BgrMVVlanMCOutBandwidth5min OBJECT-TYPE
   SYNTAX      Integer32
   MAX-ACCESS  read-only
   STATUS      current
   DESCRIPTION
      "Path: bridgeGroup.performance.vlan.mibCounters.ifOutBandwidth.5min

       unit name = bps
       formula = 8 * ; 8 /"
   ::= {pr1645v2BgrMVVlanEntry 45507584}

pr1645v2BgrMVVlanVlanVid OBJECT-TYPE
   SYNTAX      Integer32
   MAX-ACCESS  read-only
   STATUS      current
   DESCRIPTION
      "Path: bridgeGroup.performance.vlan.vlan.vid"
   ::= {pr1645v2BgrMVVlanEntry 234946560}

pr1645v2BgrMVVlanMCH2P OBJECT-TYPE
   SYNTAX      SEQUENCE OF Pr1645v2BgrMVVlanMCH2PEntry
   MAX-ACCESS  not-accessible
   STATUS      current
   DESCRIPTION
      ""
   ::= {pr1645v2BgrMVVlan 41549824}

pr1645v2BgrMVVlanMCH2PEntry OBJECT-TYPE
   SYNTAX      Pr1645v2BgrMVVlanMCH2PEntry
   MAX-ACCESS  not-accessible
   STATUS      current
   DESCRIPTION
      ""
   INDEX      { pr1645v2BgrMVVlanTableIx,
                pr1645v2BgrMVVlanMCH2PTableIx }
   ::= {pr1645v2BgrMVVlanMCH2P 1}

Pr1645v2BgrMVVlanMCH2PEntry ::=
   SEQUENCE
      {
      pr1645v2BgrMVVlanMCH2PTableIx
         TableIndex,
      pr1645v2BgrMVVlanMCH2PSysUpTime
         TimeTicks,
      pr1645v2BgrMVVlanMCH2PIfUpTime
         TimeTicks,
      pr1645v2BgrMVVlanMCH2PIfStatChanges
         Counter32,
      pr1645v2BgrMVVlanMCH2PIfInOctets
         Counter64,
      pr1645v2BgrMVVlanMCH2PIfInUCPkts
         Counter64,
      pr1645v2BgrMVVlanMCH2PIfInNUCPkts
         Counter64,
      pr1645v2BgrMVVlanMCH2PIfInBCPkts
         Counter64,
      pr1645v2BgrMVVlanMCH2PIfInMCPkts
         Counter64,
      pr1645v2BgrMVVlanMCH2PIfInDiscards
         Counter64,
      pr1645v2BgrMVVlanMCH2PIfInErrors
         Counter64,
      pr1645v2BgrMVVlanMCH2PIfInUnkwn
         Counter64,
      pr1645v2BgrMVVlanMCH2PInDropEx
         Counter64,
      pr1645v2BgrMVVlanMCH2PInDropNoMac
         Counter64,
      pr1645v2BgrMVVlanMCH2PInDropNUCast
         Counter64,
      pr1645v2BgrMVVlanMCH2PInDropFilter
         Counter64,
      pr1645v2BgrMVVlanMCH2PIfInBandwidth
         Integer32,
      pr1645v2BgrMVVlanMCH2PIfOutOctets
         Counter64,
      pr1645v2BgrMVVlanMCH2PIfOutUCPkts
         Counter64,
      pr1645v2BgrMVVlanMCH2PIfOutNUCPkts
         Counter64,
      pr1645v2BgrMVVlanMCH2PIfOutBCPkts
         Counter64,
      pr1645v2BgrMVVlanMCH2PIfOutMCPkts
         Counter64,
      pr1645v2BgrMVVlanMCH2PIfOutDiscards
         Counter64,
      pr1645v2BgrMVVlanMCH2PIfOutErrors
         Counter64,
      pr1645v2BgrMVVlanMCH2POutDropEx
         Counter64,
      pr1645v2BgrMVVlanMCH2POutDropNoArp
         Counter64,
      pr1645v2BgrMVVlanMCH2POutDropFilter
         Counter64,
      pr1645v2BgrMVVlanMCH2PIfOutBandwidth
         Integer32,
      pr1645v2BgrMVVlanMCH2PIfErrSec
         Counter32
      }

pr1645v2BgrMVVlanMCH2PTableIx OBJECT-TYPE
   SYNTAX      TableIndex
   MAX-ACCESS  not-accessible
   STATUS      current
   DESCRIPTION
      ""
   ::= {pr1645v2BgrMVVlanMCH2PEntry 11}

pr1645v2BgrMVVlanMCH2PSysUpTime OBJECT-TYPE
   SYNTAX      TimeTicks
   MAX-ACCESS  read-only
   STATUS      current
   DESCRIPTION
      "Path: bridgeGroup.performance.vlan.mibCounters.h2Performance.sysUpTime

       Time in centi-second."
   ::= {pr1645v2BgrMVVlanMCH2PEntry 16777216}

pr1645v2BgrMVVlanMCH2PIfUpTime OBJECT-TYPE
   SYNTAX      TimeTicks
   MAX-ACCESS  read-only
   STATUS      current
   DESCRIPTION
      "Path: bridgeGroup.performance.vlan.mibCounters.h2Performance.ifUpTime

       Time in centi-second."
   ::= {pr1645v2BgrMVVlanMCH2PEntry 33554432}

pr1645v2BgrMVVlanMCH2PIfStatChanges OBJECT-TYPE
   SYNTAX      Counter32
   MAX-ACCESS  read-only
   STATUS      current
   DESCRIPTION
      "Path: bridgeGroup.performance.vlan.mibCounters.h2Performance.ifStatusChanges

       32 bit unsigned wrappable counter."
   ::= {pr1645v2BgrMVVlanMCH2PEntry 50331648}

pr1645v2BgrMVVlanMCH2PIfInOctets OBJECT-TYPE
   SYNTAX      Counter64
   MAX-ACCESS  read-only
   STATUS      current
   DESCRIPTION
      "Path: bridgeGroup.performance.vlan.mibCounters.h2Performance.ifInOctets

       64 bit unsigned wrappable counter."
   ::= {pr1645v2BgrMVVlanMCH2PEntry 67108864}

pr1645v2BgrMVVlanMCH2PIfInUCPkts OBJECT-TYPE
   SYNTAX      Counter64
   MAX-ACCESS  read-only
   STATUS      current
   DESCRIPTION
      "Path: bridgeGroup.performance.vlan.mibCounters.h2Performance.ifInUcastPkts

       64 bit unsigned wrappable counter."
   ::= {pr1645v2BgrMVVlanMCH2PEntry 83886080}

pr1645v2BgrMVVlanMCH2PIfInNUCPkts OBJECT-TYPE
   SYNTAX      Counter64
   MAX-ACCESS  read-only
   STATUS      current
   DESCRIPTION
      "Path: bridgeGroup.performance.vlan.mibCounters.h2Performance.ifInNUcastPkts

       64 bit unsigned wrappable counter."
   ::= {pr1645v2BgrMVVlanMCH2PEntry 100663296}

pr1645v2BgrMVVlanMCH2PIfInBCPkts OBJECT-TYPE
   SYNTAX      Counter64
   MAX-ACCESS  read-only
   STATUS      current
   DESCRIPTION
      "Path: bridgeGroup.performance.vlan.mibCounters.h2Performance.ifInBcastPkts

       64 bit unsigned wrappable counter."
   ::= {pr1645v2BgrMVVlanMCH2PEntry 419430400}

pr1645v2BgrMVVlanMCH2PIfInMCPkts OBJECT-TYPE
   SYNTAX      Counter64
   MAX-ACCESS  read-only
   STATUS      current
   DESCRIPTION
      "Path: bridgeGroup.performance.vlan.mibCounters.h2Performance.ifInMcastPkts

       64 bit unsigned wrappable counter."
   ::= {pr1645v2BgrMVVlanMCH2PEntry 436207616}

pr1645v2BgrMVVlanMCH2PIfInDiscards OBJECT-TYPE
   SYNTAX      Counter64
   MAX-ACCESS  read-only
   STATUS      current
   DESCRIPTION
      "Path: bridgeGroup.performance.vlan.mibCounters.h2Performance.ifInDiscards

       64 bit unsigned wrappable counter."
   ::= {pr1645v2BgrMVVlanMCH2PEntry 117440512}

pr1645v2BgrMVVlanMCH2PIfInErrors OBJECT-TYPE
   SYNTAX      Counter64
   MAX-ACCESS  read-only
   STATUS      current
   DESCRIPTION
      "Path: bridgeGroup.performance.vlan.mibCounters.h2Performance.ifInErrors

       64 bit unsigned wrappable counter."
   ::= {pr1645v2BgrMVVlanMCH2PEntry 134217728}

pr1645v2BgrMVVlanMCH2PIfInUnkwn OBJECT-TYPE
   SYNTAX      Counter64
   MAX-ACCESS  read-only
   STATUS      current
   DESCRIPTION
      "Path: bridgeGroup.performance.vlan.mibCounters.h2Performance.ifInUnknownProtos

       64 bit unsigned wrappable counter."
   ::= {pr1645v2BgrMVVlanMCH2PEntry 150994944}

pr1645v2BgrMVVlanMCH2PInDropEx OBJECT-TYPE
   SYNTAX      Counter64
   MAX-ACCESS  read-only
   STATUS      current
   DESCRIPTION
      "Path: bridgeGroup.performance.vlan.mibCounters.h2Performance.ifInDropLevelExceeded

       64 bit unsigned wrappable counter."
   ::= {pr1645v2BgrMVVlanMCH2PEntry 335544320}

pr1645v2BgrMVVlanMCH2PInDropNoMac OBJECT-TYPE
   SYNTAX      Counter64
   MAX-ACCESS  read-only
   STATUS      current
   DESCRIPTION
      "Path: bridgeGroup.performance.vlan.mibCounters.h2Performance.fInDiscardsNoMacFit

       64 bit unsigned wrappable counter."
   ::= {pr1645v2BgrMVVlanMCH2PEntry 301989888}

pr1645v2BgrMVVlanMCH2PInDropNUCast OBJECT-TYPE
   SYNTAX      Counter64
   MAX-ACCESS  read-only
   STATUS      current
   DESCRIPTION
      "Path: bridgeGroup.performance.vlan.mibCounters.h2Performance.fInDiscardsNUCast

       64 bit unsigned wrappable counter."
   ::= {pr1645v2BgrMVVlanMCH2PEntry 318767104}

pr1645v2BgrMVVlanMCH2PInDropFilter OBJECT-TYPE
   SYNTAX      Counter64
   MAX-ACCESS  read-only
   STATUS      current
   DESCRIPTION
      "Path: bridgeGroup.performance.vlan.mibCounters.h2Performance.fInDiscardsFilter

       64 bit unsigned wrappable counter."
   ::= {pr1645v2BgrMVVlanMCH2PEntry 385875968}

pr1645v2BgrMVVlanMCH2PIfInBandwidth OBJECT-TYPE
   SYNTAX      Integer32
   MAX-ACCESS  read-only
   STATUS      current
   DESCRIPTION
      "Path: bridgeGroup.performance.vlan.mibCounters.h2Performance.ifInBandwidth

       unit name = bps
       formula = 8 * ; 8 /"
   ::= {pr1645v2BgrMVVlanMCH2PEntry 268435456}

pr1645v2BgrMVVlanMCH2PIfOutOctets OBJECT-TYPE
   SYNTAX      Counter64
   MAX-ACCESS  read-only
   STATUS      current
   DESCRIPTION
      "Path: bridgeGroup.performance.vlan.mibCounters.h2Performance.ifOutOctets

       64 bit unsigned wrappable counter."
   ::= {pr1645v2BgrMVVlanMCH2PEntry 167772160}

pr1645v2BgrMVVlanMCH2PIfOutUCPkts OBJECT-TYPE
   SYNTAX      Counter64
   MAX-ACCESS  read-only
   STATUS      current
   DESCRIPTION
      "Path: bridgeGroup.performance.vlan.mibCounters.h2Performance.ifOutUcastPkts

       64 bit unsigned wrappable counter."
   ::= {pr1645v2BgrMVVlanMCH2PEntry 184549376}

pr1645v2BgrMVVlanMCH2PIfOutNUCPkts OBJECT-TYPE
   SYNTAX      Counter64
   MAX-ACCESS  read-only
   STATUS      current
   DESCRIPTION
      "Path: bridgeGroup.performance.vlan.mibCounters.h2Performance.ifOutNUcastPkts

       64 bit unsigned wrappable counter."
   ::= {pr1645v2BgrMVVlanMCH2PEntry 201326592}

pr1645v2BgrMVVlanMCH2PIfOutBCPkts OBJECT-TYPE
   SYNTAX      Counter64
   MAX-ACCESS  read-only
   STATUS      current
   DESCRIPTION
      "Path: bridgeGroup.performance.vlan.mibCounters.h2Performance.ifOutBcastPkts

       64 bit unsigned wrappable counter."
   ::= {pr1645v2BgrMVVlanMCH2PEntry 452984832}

pr1645v2BgrMVVlanMCH2PIfOutMCPkts OBJECT-TYPE
   SYNTAX      Counter64
   MAX-ACCESS  read-only
   STATUS      current
   DESCRIPTION
      "Path: bridgeGroup.performance.vlan.mibCounters.h2Performance.ifOutMcastPkts

       64 bit unsigned wrappable counter."
   ::= {pr1645v2BgrMVVlanMCH2PEntry 469762048}

pr1645v2BgrMVVlanMCH2PIfOutDiscards OBJECT-TYPE
   SYNTAX      Counter64
   MAX-ACCESS  read-only
   STATUS      current
   DESCRIPTION
      "Path: bridgeGroup.performance.vlan.mibCounters.h2Performance.ifOutDiscards

       64 bit unsigned wrappable counter."
   ::= {pr1645v2BgrMVVlanMCH2PEntry 218103808}

pr1645v2BgrMVVlanMCH2PIfOutErrors OBJECT-TYPE
   SYNTAX      Counter64
   MAX-ACCESS  read-only
   STATUS      current
   DESCRIPTION
      "Path: bridgeGroup.performance.vlan.mibCounters.h2Performance.ifOutErrors

       64 bit unsigned wrappable counter."
   ::= {pr1645v2BgrMVVlanMCH2PEntry 234881024}

pr1645v2BgrMVVlanMCH2POutDropEx OBJECT-TYPE
   SYNTAX      Counter64
   MAX-ACCESS  read-only
   STATUS      current
   DESCRIPTION
      "Path: bridgeGroup.performance.vlan.mibCounters.h2Performance.ifOutDropLevelExceeded

       64 bit unsigned wrappable counter."
   ::= {pr1645v2BgrMVVlanMCH2PEntry 352321536}

pr1645v2BgrMVVlanMCH2POutDropNoArp OBJECT-TYPE
   SYNTAX      Counter64
   MAX-ACCESS  read-only
   STATUS      current
   DESCRIPTION
      "Path: bridgeGroup.performance.vlan.mibCounters.h2Performance.ifOutDiscardsNoArp

       64 bit unsigned wrappable counter."
   ::= {pr1645v2BgrMVVlanMCH2PEntry 369098752}

pr1645v2BgrMVVlanMCH2POutDropFilter OBJECT-TYPE
   SYNTAX      Counter64
   MAX-ACCESS  read-only
   STATUS      current
   DESCRIPTION
      "Path: bridgeGroup.performance.vlan.mibCounters.h2Performance.ifOutDiscardsFilter

       64 bit unsigned wrappable counter."
   ::= {pr1645v2BgrMVVlanMCH2PEntry 402653184}

pr1645v2BgrMVVlanMCH2PIfOutBandwidth OBJECT-TYPE
   SYNTAX      Integer32
   MAX-ACCESS  read-only
   STATUS      current
   DESCRIPTION
      "Path: bridgeGroup.performance.vlan.mibCounters.h2Performance.ifOutBandwidth

       unit name = bps
       formula = 8 * ; 8 /"
   ::= {pr1645v2BgrMVVlanMCH2PEntry 285212672}

pr1645v2BgrMVVlanMCH2PIfErrSec OBJECT-TYPE
   SYNTAX      Counter32
   MAX-ACCESS  read-only
   STATUS      current
   DESCRIPTION
      "Path: bridgeGroup.performance.vlan.mibCounters.h2Performance.ifErrSec

       32 bit unsigned wrappable counter."
   ::= {pr1645v2BgrMVVlanMCH2PEntry 251658240}

pr1645v2BgrMVVlanMCH24P OBJECT-TYPE
   SYNTAX      SEQUENCE OF Pr1645v2BgrMVVlanMCH24PEntry
   MAX-ACCESS  not-accessible
   STATUS      current
   DESCRIPTION
      ""
   ::= {pr1645v2BgrMVVlan 41615360}

pr1645v2BgrMVVlanMCH24PEntry OBJECT-TYPE
   SYNTAX      Pr1645v2BgrMVVlanMCH24PEntry
   MAX-ACCESS  not-accessible
   STATUS      current
   DESCRIPTION
      ""
   INDEX      { pr1645v2BgrMVVlanTableIx,
                pr1645v2BgrMVVlanMCH24PTableIx }
   ::= {pr1645v2BgrMVVlanMCH24P 1}

Pr1645v2BgrMVVlanMCH24PEntry ::=
   SEQUENCE
      {
      pr1645v2BgrMVVlanMCH24PTableIx
         TableIndex,
      pr1645v2BgrMVVlanMCH24PSysUpTime
         TimeTicks,
      pr1645v2BgrMVVlanMCH24PIfUpTime
         TimeTicks,
      pr1645v2BgrMVVlanMCH24PIfStatChanges
         Counter32,
      pr1645v2BgrMVVlanMCH24PIfInOctets
         Counter64,
      pr1645v2BgrMVVlanMCH24PIfInUCPkts
         Counter64,
      pr1645v2BgrMVVlanMCH24PIfInNUCPkts
         Counter64,
      pr1645v2BgrMVVlanMCH24PIfInBCPkts
         Counter64,
      pr1645v2BgrMVVlanMCH24PIfInMCPkts
         Counter64,
      pr1645v2BgrMVVlanMCH24PIfInDiscards
         Counter64,
      pr1645v2BgrMVVlanMCH24PIfInErrors
         Counter64,
      pr1645v2BgrMVVlanMCH24PIfInUnkwn
         Counter64,
      pr1645v2BgrMVVlanMCH24PInDropEx
         Counter64,
      pr1645v2BgrMVVlanMCH24PInDropNoMac
         Counter64,
      pr1645v2BgrMVVlanMCH24PInDropNUCast
         Counter64,
      pr1645v2BgrMVVlanMCH24PInDropFilter
         Counter64,
      pr1645v2BgrMVVlanMCH24PIfInBandwidth
         Integer32,
      pr1645v2BgrMVVlanMCH24PIfOutOctets
         Counter64,
      pr1645v2BgrMVVlanMCH24PIfOutUCPkts
         Counter64,
      pr1645v2BgrMVVlanMCH24PIfOutNUCPkts
         Counter64,
      pr1645v2BgrMVVlanMCH24PIfOutBCPkts
         Counter64,
      pr1645v2BgrMVVlanMCH24PIfOutMCPkts
         Counter64,
      pr1645v2BgrMVVlanMCH24PIfOutDiscards
         Counter64,
      pr1645v2BgrMVVlanMCH24PIfOutErrors
         Counter64,
      pr1645v2BgrMVVlanMCH24POutDropEx
         Counter64,
      pr1645v2BgrMVVlanMCH24POutDropNoArp
         Counter64,
      pr1645v2BgrMVVlanMCH24POutDropFilter
         Counter64,
      pr1645v2BgrMVVlanMCH24PIfOutBandwidth
         Integer32,
      pr1645v2BgrMVVlanMCH24PIfErrSec
         Counter32
      }

pr1645v2BgrMVVlanMCH24PTableIx OBJECT-TYPE
   SYNTAX      TableIndex
   MAX-ACCESS  not-accessible
   STATUS      current
   DESCRIPTION
      ""
   ::= {pr1645v2BgrMVVlanMCH24PEntry 11}

pr1645v2BgrMVVlanMCH24PSysUpTime OBJECT-TYPE
   SYNTAX      TimeTicks
   MAX-ACCESS  read-only
   STATUS      current
   DESCRIPTION
      "Path: bridgeGroup.performance.vlan.mibCounters.h24Performance.sysUpTime

       Time in centi-second."
   ::= {pr1645v2BgrMVVlanMCH24PEntry 16777216}

pr1645v2BgrMVVlanMCH24PIfUpTime OBJECT-TYPE
   SYNTAX      TimeTicks
   MAX-ACCESS  read-only
   STATUS      current
   DESCRIPTION
      "Path: bridgeGroup.performance.vlan.mibCounters.h24Performance.ifUpTime

       Time in centi-second."
   ::= {pr1645v2BgrMVVlanMCH24PEntry 33554432}

pr1645v2BgrMVVlanMCH24PIfStatChanges OBJECT-TYPE
   SYNTAX      Counter32
   MAX-ACCESS  read-only
   STATUS      current
   DESCRIPTION
      "Path: bridgeGroup.performance.vlan.mibCounters.h24Performance.ifStatusChanges

       32 bit unsigned wrappable counter."
   ::= {pr1645v2BgrMVVlanMCH24PEntry 50331648}

pr1645v2BgrMVVlanMCH24PIfInOctets OBJECT-TYPE
   SYNTAX      Counter64
   MAX-ACCESS  read-only
   STATUS      current
   DESCRIPTION
      "Path: bridgeGroup.performance.vlan.mibCounters.h24Performance.ifInOctets

       64 bit unsigned wrappable counter."
   ::= {pr1645v2BgrMVVlanMCH24PEntry 67108864}

pr1645v2BgrMVVlanMCH24PIfInUCPkts OBJECT-TYPE
   SYNTAX      Counter64
   MAX-ACCESS  read-only
   STATUS      current
   DESCRIPTION
      "Path: bridgeGroup.performance.vlan.mibCounters.h24Performance.ifInUcastPkts

       64 bit unsigned wrappable counter."
   ::= {pr1645v2BgrMVVlanMCH24PEntry 83886080}

pr1645v2BgrMVVlanMCH24PIfInNUCPkts OBJECT-TYPE
   SYNTAX      Counter64
   MAX-ACCESS  read-only
   STATUS      current
   DESCRIPTION
      "Path: bridgeGroup.performance.vlan.mibCounters.h24Performance.ifInNUcastPkts

       64 bit unsigned wrappable counter."
   ::= {pr1645v2BgrMVVlanMCH24PEntry 100663296}

pr1645v2BgrMVVlanMCH24PIfInBCPkts OBJECT-TYPE
   SYNTAX      Counter64
   MAX-ACCESS  read-only
   STATUS      current
   DESCRIPTION
      "Path: bridgeGroup.performance.vlan.mibCounters.h24Performance.ifInBcastPkts

       64 bit unsigned wrappable counter."
   ::= {pr1645v2BgrMVVlanMCH24PEntry 419430400}

pr1645v2BgrMVVlanMCH24PIfInMCPkts OBJECT-TYPE
   SYNTAX      Counter64
   MAX-ACCESS  read-only
   STATUS      current
   DESCRIPTION
      "Path: bridgeGroup.performance.vlan.mibCounters.h24Performance.ifInMcastPkts

       64 bit unsigned wrappable counter."
   ::= {pr1645v2BgrMVVlanMCH24PEntry 436207616}

pr1645v2BgrMVVlanMCH24PIfInDiscards OBJECT-TYPE
   SYNTAX      Counter64
   MAX-ACCESS  read-only
   STATUS      current
   DESCRIPTION
      "Path: bridgeGroup.performance.vlan.mibCounters.h24Performance.ifInDiscards

       64 bit unsigned wrappable counter."
   ::= {pr1645v2BgrMVVlanMCH24PEntry 117440512}

pr1645v2BgrMVVlanMCH24PIfInErrors OBJECT-TYPE
   SYNTAX      Counter64
   MAX-ACCESS  read-only
   STATUS      current
   DESCRIPTION
      "Path: bridgeGroup.performance.vlan.mibCounters.h24Performance.ifInErrors

       64 bit unsigned wrappable counter."
   ::= {pr1645v2BgrMVVlanMCH24PEntry 134217728}

pr1645v2BgrMVVlanMCH24PIfInUnkwn OBJECT-TYPE
   SYNTAX      Counter64
   MAX-ACCESS  read-only
   STATUS      current
   DESCRIPTION
      "Path: bridgeGroup.performance.vlan.mibCounters.h24Performance.ifInUnknownProtos

       64 bit unsigned wrappable counter."
   ::= {pr1645v2BgrMVVlanMCH24PEntry 150994944}

pr1645v2BgrMVVlanMCH24PInDropEx OBJECT-TYPE
   SYNTAX      Counter64
   MAX-ACCESS  read-only
   STATUS      current
   DESCRIPTION
      "Path: bridgeGroup.performance.vlan.mibCounters.h24Performance.ifInDropLevelExceeded

       64 bit unsigned wrappable counter."
   ::= {pr1645v2BgrMVVlanMCH24PEntry 335544320}

pr1645v2BgrMVVlanMCH24PInDropNoMac OBJECT-TYPE
   SYNTAX      Counter64
   MAX-ACCESS  read-only
   STATUS      current
   DESCRIPTION
      "Path: bridgeGroup.performance.vlan.mibCounters.h24Performance.fInDiscardsNoMacFit

       64 bit unsigned wrappable counter."
   ::= {pr1645v2BgrMVVlanMCH24PEntry 301989888}

pr1645v2BgrMVVlanMCH24PInDropNUCast OBJECT-TYPE
   SYNTAX      Counter64
   MAX-ACCESS  read-only
   STATUS      current
   DESCRIPTION
      "Path: bridgeGroup.performance.vlan.mibCounters.h24Performance.fInDiscardsNUCast

       64 bit unsigned wrappable counter."
   ::= {pr1645v2BgrMVVlanMCH24PEntry 318767104}

pr1645v2BgrMVVlanMCH24PInDropFilter OBJECT-TYPE
   SYNTAX      Counter64
   MAX-ACCESS  read-only
   STATUS      current
   DESCRIPTION
      "Path: bridgeGroup.performance.vlan.mibCounters.h24Performance.fInDiscardsFilter

       64 bit unsigned wrappable counter."
   ::= {pr1645v2BgrMVVlanMCH24PEntry 385875968}

pr1645v2BgrMVVlanMCH24PIfInBandwidth OBJECT-TYPE
   SYNTAX      Integer32
   MAX-ACCESS  read-only
   STATUS      current
   DESCRIPTION
      "Path: bridgeGroup.performance.vlan.mibCounters.h24Performance.ifInBandwidth

       unit name = bps
       formula = 8 * ; 8 /"
   ::= {pr1645v2BgrMVVlanMCH24PEntry 268435456}

pr1645v2BgrMVVlanMCH24PIfOutOctets OBJECT-TYPE
   SYNTAX      Counter64
   MAX-ACCESS  read-only
   STATUS      current
   DESCRIPTION
      "Path: bridgeGroup.performance.vlan.mibCounters.h24Performance.ifOutOctets

       64 bit unsigned wrappable counter."
   ::= {pr1645v2BgrMVVlanMCH24PEntry 167772160}

pr1645v2BgrMVVlanMCH24PIfOutUCPkts OBJECT-TYPE
   SYNTAX      Counter64
   MAX-ACCESS  read-only
   STATUS      current
   DESCRIPTION
      "Path: bridgeGroup.performance.vlan.mibCounters.h24Performance.ifOutUcastPkts

       64 bit unsigned wrappable counter."
   ::= {pr1645v2BgrMVVlanMCH24PEntry 184549376}

pr1645v2BgrMVVlanMCH24PIfOutNUCPkts OBJECT-TYPE
   SYNTAX      Counter64
   MAX-ACCESS  read-only
   STATUS      current
   DESCRIPTION
      "Path: bridgeGroup.performance.vlan.mibCounters.h24Performance.ifOutNUcastPkts

       64 bit unsigned wrappable counter."
   ::= {pr1645v2BgrMVVlanMCH24PEntry 201326592}

pr1645v2BgrMVVlanMCH24PIfOutBCPkts OBJECT-TYPE
   SYNTAX      Counter64
   MAX-ACCESS  read-only
   STATUS      current
   DESCRIPTION
      "Path: bridgeGroup.performance.vlan.mibCounters.h24Performance.ifOutBcastPkts

       64 bit unsigned wrappable counter."
   ::= {pr1645v2BgrMVVlanMCH24PEntry 452984832}

pr1645v2BgrMVVlanMCH24PIfOutMCPkts OBJECT-TYPE
   SYNTAX      Counter64
   MAX-ACCESS  read-only
   STATUS      current
   DESCRIPTION
      "Path: bridgeGroup.performance.vlan.mibCounters.h24Performance.ifOutMcastPkts

       64 bit unsigned wrappable counter."
   ::= {pr1645v2BgrMVVlanMCH24PEntry 469762048}

pr1645v2BgrMVVlanMCH24PIfOutDiscards OBJECT-TYPE
   SYNTAX      Counter64
   MAX-ACCESS  read-only
   STATUS      current
   DESCRIPTION
      "Path: bridgeGroup.performance.vlan.mibCounters.h24Performance.ifOutDiscards

       64 bit unsigned wrappable counter."
   ::= {pr1645v2BgrMVVlanMCH24PEntry 218103808}

pr1645v2BgrMVVlanMCH24PIfOutErrors OBJECT-TYPE
   SYNTAX      Counter64
   MAX-ACCESS  read-only
   STATUS      current
   DESCRIPTION
      "Path: bridgeGroup.performance.vlan.mibCounters.h24Performance.ifOutErrors

       64 bit unsigned wrappable counter."
   ::= {pr1645v2BgrMVVlanMCH24PEntry 234881024}

pr1645v2BgrMVVlanMCH24POutDropEx OBJECT-TYPE
   SYNTAX      Counter64
   MAX-ACCESS  read-only
   STATUS      current
   DESCRIPTION
      "Path: bridgeGroup.performance.vlan.mibCounters.h24Performance.ifOutDropLevelExceeded

       64 bit unsigned wrappable counter."
   ::= {pr1645v2BgrMVVlanMCH24PEntry 352321536}

pr1645v2BgrMVVlanMCH24POutDropNoArp OBJECT-TYPE
   SYNTAX      Counter64
   MAX-ACCESS  read-only
   STATUS      current
   DESCRIPTION
      "Path: bridgeGroup.performance.vlan.mibCounters.h24Performance.ifOutDiscardsNoArp

       64 bit unsigned wrappable counter."
   ::= {pr1645v2BgrMVVlanMCH24PEntry 369098752}

pr1645v2BgrMVVlanMCH24POutDropFilter OBJECT-TYPE
   SYNTAX      Counter64
   MAX-ACCESS  read-only
   STATUS      current
   DESCRIPTION
      "Path: bridgeGroup.performance.vlan.mibCounters.h24Performance.ifOutDiscardsFilter

       64 bit unsigned wrappable counter."
   ::= {pr1645v2BgrMVVlanMCH24PEntry 402653184}

pr1645v2BgrMVVlanMCH24PIfOutBandwidth OBJECT-TYPE
   SYNTAX      Integer32
   MAX-ACCESS  read-only
   STATUS      current
   DESCRIPTION
      "Path: bridgeGroup.performance.vlan.mibCounters.h24Performance.ifOutBandwidth

       unit name = bps
       formula = 8 * ; 8 /"
   ::= {pr1645v2BgrMVVlanMCH24PEntry 285212672}

pr1645v2BgrMVVlanMCH24PIfErrSec OBJECT-TYPE
   SYNTAX      Counter32
   MAX-ACCESS  read-only
   STATUS      current
   DESCRIPTION
      "Path: bridgeGroup.performance.vlan.mibCounters.h24Performance.ifErrSec

       32 bit unsigned wrappable counter."
   ::= {pr1645v2BgrMVVlanMCH24PEntry 251658240}

pr1645v2BgrMVVlanMCD7P OBJECT-TYPE
   SYNTAX      SEQUENCE OF Pr1645v2BgrMVVlanMCD7PEntry
   MAX-ACCESS  not-accessible
   STATUS      current
   DESCRIPTION
      ""
   ::= {pr1645v2BgrMVVlan 41680896}

pr1645v2BgrMVVlanMCD7PEntry OBJECT-TYPE
   SYNTAX      Pr1645v2BgrMVVlanMCD7PEntry
   MAX-ACCESS  not-accessible
   STATUS      current
   DESCRIPTION
      ""
   INDEX      { pr1645v2BgrMVVlanTableIx,
                pr1645v2BgrMVVlanMCD7PTableIx }
   ::= {pr1645v2BgrMVVlanMCD7P 1}

Pr1645v2BgrMVVlanMCD7PEntry ::=
   SEQUENCE
      {
      pr1645v2BgrMVVlanMCD7PTableIx
         TableIndex,
      pr1645v2BgrMVVlanMCD7PSysUpTime
         TimeTicks,
      pr1645v2BgrMVVlanMCD7PIfUpTime
         TimeTicks,
      pr1645v2BgrMVVlanMCD7PIfStatChanges
         Counter32,
      pr1645v2BgrMVVlanMCD7PIfInOctets
         Counter64,
      pr1645v2BgrMVVlanMCD7PIfInUCPkts
         Counter64,
      pr1645v2BgrMVVlanMCD7PIfInNUCPkts
         Counter64,
      pr1645v2BgrMVVlanMCD7PIfInBCPkts
         Counter64,
      pr1645v2BgrMVVlanMCD7PIfInMCPkts
         Counter64,
      pr1645v2BgrMVVlanMCD7PIfInDiscards
         Counter64,
      pr1645v2BgrMVVlanMCD7PIfInErrors
         Counter64,
      pr1645v2BgrMVVlanMCD7PIfInUnkwn
         Counter64,
      pr1645v2BgrMVVlanMCD7PInDropEx
         Counter64,
      pr1645v2BgrMVVlanMCD7PInDropNoMac
         Counter64,
      pr1645v2BgrMVVlanMCD7PInDropNUCast
         Counter64,
      pr1645v2BgrMVVlanMCD7PInDropFilter
         Counter64,
      pr1645v2BgrMVVlanMCD7PIfInBandwidth
         Integer32,
      pr1645v2BgrMVVlanMCD7PIfOutOctets
         Counter64,
      pr1645v2BgrMVVlanMCD7PIfOutUCPkts
         Counter64,
      pr1645v2BgrMVVlanMCD7PIfOutNUCPkts
         Counter64,
      pr1645v2BgrMVVlanMCD7PIfOutBCPkts
         Counter64,
      pr1645v2BgrMVVlanMCD7PIfOutMCPkts
         Counter64,
      pr1645v2BgrMVVlanMCD7PIfOutDiscards
         Counter64,
      pr1645v2BgrMVVlanMCD7PIfOutErrors
         Counter64,
      pr1645v2BgrMVVlanMCD7POutDropEx
         Counter64,
      pr1645v2BgrMVVlanMCD7POutDropNoArp
         Counter64,
      pr1645v2BgrMVVlanMCD7POutDropFilter
         Counter64,
      pr1645v2BgrMVVlanMCD7PIfOutBandwidth
         Integer32,
      pr1645v2BgrMVVlanMCD7PIfErrSec
         Counter32
      }

pr1645v2BgrMVVlanMCD7PTableIx OBJECT-TYPE
   SYNTAX      TableIndex
   MAX-ACCESS  not-accessible
   STATUS      current
   DESCRIPTION
      ""
   ::= {pr1645v2BgrMVVlanMCD7PEntry 11}

pr1645v2BgrMVVlanMCD7PSysUpTime OBJECT-TYPE
   SYNTAX      TimeTicks
   MAX-ACCESS  read-only
   STATUS      current
   DESCRIPTION
      "Path: bridgeGroup.performance.vlan.mibCounters.d7Performance.sysUpTime

       Time in centi-second."
   ::= {pr1645v2BgrMVVlanMCD7PEntry 16777216}

pr1645v2BgrMVVlanMCD7PIfUpTime OBJECT-TYPE
   SYNTAX      TimeTicks
   MAX-ACCESS  read-only
   STATUS      current
   DESCRIPTION
      "Path: bridgeGroup.performance.vlan.mibCounters.d7Performance.ifUpTime

       Time in centi-second."
   ::= {pr1645v2BgrMVVlanMCD7PEntry 33554432}

pr1645v2BgrMVVlanMCD7PIfStatChanges OBJECT-TYPE
   SYNTAX      Counter32
   MAX-ACCESS  read-only
   STATUS      current
   DESCRIPTION
      "Path: bridgeGroup.performance.vlan.mibCounters.d7Performance.ifStatusChanges

       32 bit unsigned wrappable counter."
   ::= {pr1645v2BgrMVVlanMCD7PEntry 50331648}

pr1645v2BgrMVVlanMCD7PIfInOctets OBJECT-TYPE
   SYNTAX      Counter64
   MAX-ACCESS  read-only
   STATUS      current
   DESCRIPTION
      "Path: bridgeGroup.performance.vlan.mibCounters.d7Performance.ifInOctets

       64 bit unsigned wrappable counter."
   ::= {pr1645v2BgrMVVlanMCD7PEntry 67108864}

pr1645v2BgrMVVlanMCD7PIfInUCPkts OBJECT-TYPE
   SYNTAX      Counter64
   MAX-ACCESS  read-only
   STATUS      current
   DESCRIPTION
      "Path: bridgeGroup.performance.vlan.mibCounters.d7Performance.ifInUcastPkts

       64 bit unsigned wrappable counter."
   ::= {pr1645v2BgrMVVlanMCD7PEntry 83886080}

pr1645v2BgrMVVlanMCD7PIfInNUCPkts OBJECT-TYPE
   SYNTAX      Counter64
   MAX-ACCESS  read-only
   STATUS      current
   DESCRIPTION
      "Path: bridgeGroup.performance.vlan.mibCounters.d7Performance.ifInNUcastPkts

       64 bit unsigned wrappable counter."
   ::= {pr1645v2BgrMVVlanMCD7PEntry 100663296}

pr1645v2BgrMVVlanMCD7PIfInBCPkts OBJECT-TYPE
   SYNTAX      Counter64
   MAX-ACCESS  read-only
   STATUS      current
   DESCRIPTION
      "Path: bridgeGroup.performance.vlan.mibCounters.d7Performance.ifInBcastPkts

       64 bit unsigned wrappable counter."
   ::= {pr1645v2BgrMVVlanMCD7PEntry 419430400}

pr1645v2BgrMVVlanMCD7PIfInMCPkts OBJECT-TYPE
   SYNTAX      Counter64
   MAX-ACCESS  read-only
   STATUS      current
   DESCRIPTION
      "Path: bridgeGroup.performance.vlan.mibCounters.d7Performance.ifInMcastPkts

       64 bit unsigned wrappable counter."
   ::= {pr1645v2BgrMVVlanMCD7PEntry 436207616}

pr1645v2BgrMVVlanMCD7PIfInDiscards OBJECT-TYPE
   SYNTAX      Counter64
   MAX-ACCESS  read-only
   STATUS      current
   DESCRIPTION
      "Path: bridgeGroup.performance.vlan.mibCounters.d7Performance.ifInDiscards

       64 bit unsigned wrappable counter."
   ::= {pr1645v2BgrMVVlanMCD7PEntry 117440512}

pr1645v2BgrMVVlanMCD7PIfInErrors OBJECT-TYPE
   SYNTAX      Counter64
   MAX-ACCESS  read-only
   STATUS      current
   DESCRIPTION
      "Path: bridgeGroup.performance.vlan.mibCounters.d7Performance.ifInErrors

       64 bit unsigned wrappable counter."
   ::= {pr1645v2BgrMVVlanMCD7PEntry 134217728}

pr1645v2BgrMVVlanMCD7PIfInUnkwn OBJECT-TYPE
   SYNTAX      Counter64
   MAX-ACCESS  read-only
   STATUS      current
   DESCRIPTION
      "Path: bridgeGroup.performance.vlan.mibCounters.d7Performance.ifInUnknownProtos

       64 bit unsigned wrappable counter."
   ::= {pr1645v2BgrMVVlanMCD7PEntry 150994944}

pr1645v2BgrMVVlanMCD7PInDropEx OBJECT-TYPE
   SYNTAX      Counter64
   MAX-ACCESS  read-only
   STATUS      current
   DESCRIPTION
      "Path: bridgeGroup.performance.vlan.mibCounters.d7Performance.ifInDropLevelExceeded

       64 bit unsigned wrappable counter."
   ::= {pr1645v2BgrMVVlanMCD7PEntry 335544320}

pr1645v2BgrMVVlanMCD7PInDropNoMac OBJECT-TYPE
   SYNTAX      Counter64
   MAX-ACCESS  read-only
   STATUS      current
   DESCRIPTION
      "Path: bridgeGroup.performance.vlan.mibCounters.d7Performance.fInDiscardsNoMacFit

       64 bit unsigned wrappable counter."
   ::= {pr1645v2BgrMVVlanMCD7PEntry 301989888}

pr1645v2BgrMVVlanMCD7PInDropNUCast OBJECT-TYPE
   SYNTAX      Counter64
   MAX-ACCESS  read-only
   STATUS      current
   DESCRIPTION
      "Path: bridgeGroup.performance.vlan.mibCounters.d7Performance.fInDiscardsNUCast

       64 bit unsigned wrappable counter."
   ::= {pr1645v2BgrMVVlanMCD7PEntry 318767104}

pr1645v2BgrMVVlanMCD7PInDropFilter OBJECT-TYPE
   SYNTAX      Counter64
   MAX-ACCESS  read-only
   STATUS      current
   DESCRIPTION
      "Path: bridgeGroup.performance.vlan.mibCounters.d7Performance.fInDiscardsFilter

       64 bit unsigned wrappable counter."
   ::= {pr1645v2BgrMVVlanMCD7PEntry 385875968}

pr1645v2BgrMVVlanMCD7PIfInBandwidth OBJECT-TYPE
   SYNTAX      Integer32
   MAX-ACCESS  read-only
   STATUS      current
   DESCRIPTION
      "Path: bridgeGroup.performance.vlan.mibCounters.d7Performance.ifInBandwidth

       unit name = bps
       formula = 8 * ; 8 /"
   ::= {pr1645v2BgrMVVlanMCD7PEntry 268435456}

pr1645v2BgrMVVlanMCD7PIfOutOctets OBJECT-TYPE
   SYNTAX      Counter64
   MAX-ACCESS  read-only
   STATUS      current
   DESCRIPTION
      "Path: bridgeGroup.performance.vlan.mibCounters.d7Performance.ifOutOctets

       64 bit unsigned wrappable counter."
   ::= {pr1645v2BgrMVVlanMCD7PEntry 167772160}

pr1645v2BgrMVVlanMCD7PIfOutUCPkts OBJECT-TYPE
   SYNTAX      Counter64
   MAX-ACCESS  read-only
   STATUS      current
   DESCRIPTION
      "Path: bridgeGroup.performance.vlan.mibCounters.d7Performance.ifOutUcastPkts

       64 bit unsigned wrappable counter."
   ::= {pr1645v2BgrMVVlanMCD7PEntry 184549376}

pr1645v2BgrMVVlanMCD7PIfOutNUCPkts OBJECT-TYPE
   SYNTAX      Counter64
   MAX-ACCESS  read-only
   STATUS      current
   DESCRIPTION
      "Path: bridgeGroup.performance.vlan.mibCounters.d7Performance.ifOutNUcastPkts

       64 bit unsigned wrappable counter."
   ::= {pr1645v2BgrMVVlanMCD7PEntry 201326592}

pr1645v2BgrMVVlanMCD7PIfOutBCPkts OBJECT-TYPE
   SYNTAX      Counter64
   MAX-ACCESS  read-only
   STATUS      current
   DESCRIPTION
      "Path: bridgeGroup.performance.vlan.mibCounters.d7Performance.ifOutBcastPkts

       64 bit unsigned wrappable counter."
   ::= {pr1645v2BgrMVVlanMCD7PEntry 452984832}

pr1645v2BgrMVVlanMCD7PIfOutMCPkts OBJECT-TYPE
   SYNTAX      Counter64
   MAX-ACCESS  read-only
   STATUS      current
   DESCRIPTION
      "Path: bridgeGroup.performance.vlan.mibCounters.d7Performance.ifOutMcastPkts

       64 bit unsigned wrappable counter."
   ::= {pr1645v2BgrMVVlanMCD7PEntry 469762048}

pr1645v2BgrMVVlanMCD7PIfOutDiscards OBJECT-TYPE
   SYNTAX      Counter64
   MAX-ACCESS  read-only
   STATUS      current
   DESCRIPTION
      "Path: bridgeGroup.performance.vlan.mibCounters.d7Performance.ifOutDiscards

       64 bit unsigned wrappable counter."
   ::= {pr1645v2BgrMVVlanMCD7PEntry 218103808}

pr1645v2BgrMVVlanMCD7PIfOutErrors OBJECT-TYPE
   SYNTAX      Counter64
   MAX-ACCESS  read-only
   STATUS      current
   DESCRIPTION
      "Path: bridgeGroup.performance.vlan.mibCounters.d7Performance.ifOutErrors

       64 bit unsigned wrappable counter."
   ::= {pr1645v2BgrMVVlanMCD7PEntry 234881024}

pr1645v2BgrMVVlanMCD7POutDropEx OBJECT-TYPE
   SYNTAX      Counter64
   MAX-ACCESS  read-only
   STATUS      current
   DESCRIPTION
      "Path: bridgeGroup.performance.vlan.mibCounters.d7Performance.ifOutDropLevelExceeded

       64 bit unsigned wrappable counter."
   ::= {pr1645v2BgrMVVlanMCD7PEntry 352321536}

pr1645v2BgrMVVlanMCD7POutDropNoArp OBJECT-TYPE
   SYNTAX      Counter64
   MAX-ACCESS  read-only
   STATUS      current
   DESCRIPTION
      "Path: bridgeGroup.performance.vlan.mibCounters.d7Performance.ifOutDiscardsNoArp

       64 bit unsigned wrappable counter."
   ::= {pr1645v2BgrMVVlanMCD7PEntry 369098752}

pr1645v2BgrMVVlanMCD7POutDropFilter OBJECT-TYPE
   SYNTAX      Counter64
   MAX-ACCESS  read-only
   STATUS      current
   DESCRIPTION
      "Path: bridgeGroup.performance.vlan.mibCounters.d7Performance.ifOutDiscardsFilter

       64 bit unsigned wrappable counter."
   ::= {pr1645v2BgrMVVlanMCD7PEntry 402653184}

pr1645v2BgrMVVlanMCD7PIfOutBandwidth OBJECT-TYPE
   SYNTAX      Integer32
   MAX-ACCESS  read-only
   STATUS      current
   DESCRIPTION
      "Path: bridgeGroup.performance.vlan.mibCounters.d7Performance.ifOutBandwidth

       unit name = bps
       formula = 8 * ; 8 /"
   ::= {pr1645v2BgrMVVlanMCD7PEntry 285212672}

pr1645v2BgrMVVlanMCD7PIfErrSec OBJECT-TYPE
   SYNTAX      Counter32
   MAX-ACCESS  read-only
   STATUS      current
   DESCRIPTION
      "Path: bridgeGroup.performance.vlan.mibCounters.d7Performance.ifErrSec

       32 bit unsigned wrappable counter."
   ::= {pr1645v2BgrMVVlanMCD7PEntry 251658240}


pr1645v2BgrMVPPPoE OBJECT IDENTIFIER ::= {pr1645v2BgrMV 82}

pr1645v2BgrMVPPPoESSCTable OBJECT-TYPE
   SYNTAX      SEQUENCE OF Pr1645v2BgrMVPPPoEEntry
   MAX-ACCESS  not-accessible
   STATUS      current
   DESCRIPTION
      ""
   ::= {pr1645v2BgrMVPPPoE 1}

pr1645v2BgrMVPPPoEEntry OBJECT-TYPE
   SYNTAX      Pr1645v2BgrMVPPPoEEntry
   MAX-ACCESS  not-accessible
   STATUS      current
   DESCRIPTION
      ""
   INDEX      { pr1645v2BgrMVPPPoETableIx }
   ::= {pr1645v2BgrMVPPPoESSCTable 1}

Pr1645v2BgrMVPPPoEEntry ::=
   SEQUENCE
      {
      pr1645v2BgrMVPPPoETableIx
         TableIndex,
      pr1645v2BgrMVPPPoEName
         DisplayString,
      pr1645v2BgrMVPPPoEMCInOctets
         Counter64,
      pr1645v2BgrMVPPPoEMCInUcast
         Counter64,
      pr1645v2BgrMVPPPoEMCInNUcastPkts
         Counter64,
      pr1645v2BgrMVPPPoEMCInBcastPkts
         Counter64,
      pr1645v2BgrMVPPPoEMCInMcastPkts
         Counter64,
      pr1645v2BgrMVPPPoEMCInDiscards
         Counter64,
      pr1645v2BgrMVPPPoEMCInErrors
         Counter64,
      pr1645v2BgrMVPPPoEMCInUnknownProtos
         Counter64,
      pr1645v2BgrMVPPPoEMCInDropEx
         Counter64,
      pr1645v2BgrMVPPPoEMCInDropNoMac
         Counter64,
      pr1645v2BgrMVPPPoEMCInDropNUCast
         Counter64,
      pr1645v2BgrMVPPPoEMCInDropFilter
         Counter64,
      pr1645v2BgrMVPPPoEMCInBandwidth15sec
         Integer32,
      pr1645v2BgrMVPPPoEMCInBandwidth30sec
         Integer32,
      pr1645v2BgrMVPPPoEMCInBandwidth1min
         Integer32,
      pr1645v2BgrMVPPPoEMCInBandwidth2min
         Integer32,
      pr1645v2BgrMVPPPoEMCInBandwidth5min
         Integer32,
      pr1645v2BgrMVPPPoEMCOutOctets
         Counter64,
      pr1645v2BgrMVPPPoEMCOutUcastPkts
         Counter64,
      pr1645v2BgrMVPPPoEMCOutNUcastPkts
         Counter64,
      pr1645v2BgrMVPPPoEMCOutBcastPkts
         Counter64,
      pr1645v2BgrMVPPPoEMCOutMcastPkts
         Counter64,
      pr1645v2BgrMVPPPoEMCOutDiscards
         Counter64,
      pr1645v2BgrMVPPPoEMCOutErrors
         Counter64,
      pr1645v2BgrMVPPPoEMCOutQLen
         Counter32,
      pr1645v2BgrMVPPPoEMCOutDropEx
         Counter64,
      pr1645v2BgrMVPPPoEMCOutDropNoArp
         Counter64,
      pr1645v2BgrMVPPPoEMCOutDropFilter
         Counter64,
      pr1645v2BgrMVPPPoEMCOutBandwidth15sec
         Integer32,
      pr1645v2BgrMVPPPoEMCOutBandwidth30sec
         Integer32,
      pr1645v2BgrMVPPPoEMCOutBandwidth1min
         Integer32,
      pr1645v2BgrMVPPPoEMCOutBandwidth2min
         Integer32,
      pr1645v2BgrMVPPPoEMCOutBandwidth5min
         Integer32,
      pr1645v2BgrMVPPPoEPppLinkMonitoringRequestsSent
         Gauge32,
      pr1645v2BgrMVPPPoEPppLinkMonitoringRepliesRcvd
         Gauge32,
      pr1645v2BgrMVPPPoEPppLinkMonitoringRequestsRcvd
         Gauge32,
      pr1645v2BgrMVPPPoEPppLinkMonitoringRepliesSent
         Gauge32
      }

pr1645v2BgrMVPPPoETableIx OBJECT-TYPE
   SYNTAX      TableIndex
   MAX-ACCESS  not-accessible
   STATUS      current
   DESCRIPTION
      ""
   ::= {pr1645v2BgrMVPPPoEEntry 11}

pr1645v2BgrMVPPPoEName OBJECT-TYPE
   SYNTAX      DisplayString
   MAX-ACCESS  read-only
   STATUS      current
   DESCRIPTION
      "Path: bridgeGroup.performance.pppoEClient.name"
   ::= {pr1645v2BgrMVPPPoEEntry 16777216}

pr1645v2BgrMVPPPoEMCInOctets OBJECT-TYPE
   SYNTAX      Counter64
   MAX-ACCESS  read-only
   STATUS      current
   DESCRIPTION
      "Path: bridgeGroup.performance.pppoEClient.mibCounters.ifInOctets

       64 bit unsigned wrappable counter."
   ::= {pr1645v2BgrMVPPPoEEntry 40697856}

pr1645v2BgrMVPPPoEMCInUcast OBJECT-TYPE
   SYNTAX      Counter64
   MAX-ACCESS  read-only
   STATUS      current
   DESCRIPTION
      "Path: bridgeGroup.performance.pppoEClient.mibCounters.ifInUcastPkts

       64 bit unsigned wrappable counter."
   ::= {pr1645v2BgrMVPPPoEEntry 40763392}

pr1645v2BgrMVPPPoEMCInNUcastPkts OBJECT-TYPE
   SYNTAX      Counter64
   MAX-ACCESS  read-only
   STATUS      current
   DESCRIPTION
      "Path: bridgeGroup.performance.pppoEClient.mibCounters.ifInNUcastPkts

       64 bit unsigned wrappable counter."
   ::= {pr1645v2BgrMVPPPoEEntry 40828928}

pr1645v2BgrMVPPPoEMCInBcastPkts OBJECT-TYPE
   SYNTAX      Counter64
   MAX-ACCESS  read-only
   STATUS      current
   DESCRIPTION
      "Path: bridgeGroup.performance.pppoEClient.mibCounters.ifInBcastPkts

       64 bit unsigned wrappable counter."
   ::= {pr1645v2BgrMVPPPoEEntry 47382528}

pr1645v2BgrMVPPPoEMCInMcastPkts OBJECT-TYPE
   SYNTAX      Counter64
   MAX-ACCESS  read-only
   STATUS      current
   DESCRIPTION
      "Path: bridgeGroup.performance.pppoEClient.mibCounters.ifInMcastPkts

       64 bit unsigned wrappable counter."
   ::= {pr1645v2BgrMVPPPoEEntry 48037888}

pr1645v2BgrMVPPPoEMCInDiscards OBJECT-TYPE
   SYNTAX      Counter64
   MAX-ACCESS  read-only
   STATUS      current
   DESCRIPTION
      "Path: bridgeGroup.performance.pppoEClient.mibCounters.ifInDiscards

       64 bit unsigned wrappable counter."
   ::= {pr1645v2BgrMVPPPoEEntry 40894464}

pr1645v2BgrMVPPPoEMCInErrors OBJECT-TYPE
   SYNTAX      Counter64
   MAX-ACCESS  read-only
   STATUS      current
   DESCRIPTION
      "Path: bridgeGroup.performance.pppoEClient.mibCounters.ifInErrors

       64 bit unsigned wrappable counter."
   ::= {pr1645v2BgrMVPPPoEEntry 40960000}

pr1645v2BgrMVPPPoEMCInUnknownProtos OBJECT-TYPE
   SYNTAX      Counter64
   MAX-ACCESS  read-only
   STATUS      current
   DESCRIPTION
      "Path: bridgeGroup.performance.pppoEClient.mibCounters.ifInUnknownProtos

       64 bit unsigned wrappable counter."
   ::= {pr1645v2BgrMVPPPoEEntry 41025536}

pr1645v2BgrMVPPPoEMCInDropEx OBJECT-TYPE
   SYNTAX      Counter64
   MAX-ACCESS  read-only
   STATUS      current
   DESCRIPTION
      "Path: bridgeGroup.performance.pppoEClient.mibCounters.ifInDropLevelExceeded

       64 bit unsigned wrappable counter."
   ::= {pr1645v2BgrMVPPPoEEntry 42074112}

pr1645v2BgrMVPPPoEMCInDropNoMac OBJECT-TYPE
   SYNTAX      Counter64
   MAX-ACCESS  read-only
   STATUS      current
   DESCRIPTION
      "Path: bridgeGroup.performance.pppoEClient.mibCounters.ifInDiscardsNoMacFit

       64 bit unsigned wrappable counter."
   ::= {pr1645v2BgrMVPPPoEEntry 42270720}

pr1645v2BgrMVPPPoEMCInDropNUCast OBJECT-TYPE
   SYNTAX      Counter64
   MAX-ACCESS  read-only
   STATUS      current
   DESCRIPTION
      "Path: bridgeGroup.performance.pppoEClient.mibCounters.ifInDiscardsNUCast

       64 bit unsigned wrappable counter."
   ::= {pr1645v2BgrMVPPPoEEntry 42467328}

pr1645v2BgrMVPPPoEMCInDropFilter OBJECT-TYPE
   SYNTAX      Counter64
   MAX-ACCESS  read-only
   STATUS      current
   DESCRIPTION
      "Path: bridgeGroup.performance.pppoEClient.mibCounters.ifInDiscardsFilter

       64 bit unsigned wrappable counter."
   ::= {pr1645v2BgrMVPPPoEEntry 42532864}

pr1645v2BgrMVPPPoEMCInBandwidth15sec OBJECT-TYPE
   SYNTAX      Integer32
   MAX-ACCESS  read-only
   STATUS      current
   DESCRIPTION
      "Path: bridgeGroup.performance.pppoEClient.mibCounters.ifInBandwidth.15sec

       unit name = bps
       formula = 8 * ; 8 /"
   ::= {pr1645v2BgrMVPPPoEEntry 45417728}

pr1645v2BgrMVPPPoEMCInBandwidth30sec OBJECT-TYPE
   SYNTAX      Integer32
   MAX-ACCESS  read-only
   STATUS      current
   DESCRIPTION
      "Path: bridgeGroup.performance.pppoEClient.mibCounters.ifInBandwidth.30sec

       unit name = bps
       formula = 8 * ; 8 /"
   ::= {pr1645v2BgrMVPPPoEEntry 45419008}

pr1645v2BgrMVPPPoEMCInBandwidth1min OBJECT-TYPE
   SYNTAX      Integer32
   MAX-ACCESS  read-only
   STATUS      current
   DESCRIPTION
      "Path: bridgeGroup.performance.pppoEClient.mibCounters.ifInBandwidth.1min

       unit name = bps
       formula = 8 * ; 8 /"
   ::= {pr1645v2BgrMVPPPoEEntry 45421568}

pr1645v2BgrMVPPPoEMCInBandwidth2min OBJECT-TYPE
   SYNTAX      Integer32
   MAX-ACCESS  read-only
   STATUS      current
   DESCRIPTION
      "Path: bridgeGroup.performance.pppoEClient.mibCounters.ifInBandwidth.2min

       unit name = bps
       formula = 8 * ; 8 /"
   ::= {pr1645v2BgrMVPPPoEEntry 45426688}

pr1645v2BgrMVPPPoEMCInBandwidth5min OBJECT-TYPE
   SYNTAX      Integer32
   MAX-ACCESS  read-only
   STATUS      current
   DESCRIPTION
      "Path: bridgeGroup.performance.pppoEClient.mibCounters.ifInBandwidth.5min

       unit name = bps
       formula = 8 * ; 8 /"
   ::= {pr1645v2BgrMVPPPoEEntry 45442048}

pr1645v2BgrMVPPPoEMCOutOctets OBJECT-TYPE
   SYNTAX      Counter64
   MAX-ACCESS  read-only
   STATUS      current
   DESCRIPTION
      "Path: bridgeGroup.performance.pppoEClient.mibCounters.ifOutOctets

       64 bit unsigned wrappable counter."
   ::= {pr1645v2BgrMVPPPoEEntry 41091072}

pr1645v2BgrMVPPPoEMCOutUcastPkts OBJECT-TYPE
   SYNTAX      Counter64
   MAX-ACCESS  read-only
   STATUS      current
   DESCRIPTION
      "Path: bridgeGroup.performance.pppoEClient.mibCounters.ifOutUcastPkts

       64 bit unsigned wrappable counter."
   ::= {pr1645v2BgrMVPPPoEEntry 41156608}

pr1645v2BgrMVPPPoEMCOutNUcastPkts OBJECT-TYPE
   SYNTAX      Counter64
   MAX-ACCESS  read-only
   STATUS      current
   DESCRIPTION
      "Path: bridgeGroup.performance.pppoEClient.mibCounters.ifOutNUcastPkts

       64 bit unsigned wrappable counter."
   ::= {pr1645v2BgrMVPPPoEEntry 41222144}

pr1645v2BgrMVPPPoEMCOutBcastPkts OBJECT-TYPE
   SYNTAX      Counter64
   MAX-ACCESS  read-only
   STATUS      current
   DESCRIPTION
      "Path: bridgeGroup.performance.pppoEClient.mibCounters.ifOutBcastPkts

       64 bit unsigned wrappable counter."
   ::= {pr1645v2BgrMVPPPoEEntry 47775744}

pr1645v2BgrMVPPPoEMCOutMcastPkts OBJECT-TYPE
   SYNTAX      Counter64
   MAX-ACCESS  read-only
   STATUS      current
   DESCRIPTION
      "Path: bridgeGroup.performance.pppoEClient.mibCounters.ifOutMcastPkts

       64 bit unsigned wrappable counter."
   ::= {pr1645v2BgrMVPPPoEEntry 48431104}

pr1645v2BgrMVPPPoEMCOutDiscards OBJECT-TYPE
   SYNTAX      Counter64
   MAX-ACCESS  read-only
   STATUS      current
   DESCRIPTION
      "Path: bridgeGroup.performance.pppoEClient.mibCounters.ifOutDiscards

       64 bit unsigned wrappable counter."
   ::= {pr1645v2BgrMVPPPoEEntry 41287680}

pr1645v2BgrMVPPPoEMCOutErrors OBJECT-TYPE
   SYNTAX      Counter64
   MAX-ACCESS  read-only
   STATUS      current
   DESCRIPTION
      "Path: bridgeGroup.performance.pppoEClient.mibCounters.ifOutErrors

       64 bit unsigned wrappable counter."
   ::= {pr1645v2BgrMVPPPoEEntry 41353216}

pr1645v2BgrMVPPPoEMCOutQLen OBJECT-TYPE
   SYNTAX      Counter32
   MAX-ACCESS  read-only
   STATUS      current
   DESCRIPTION
      "Path: bridgeGroup.performance.pppoEClient.mibCounters.ifOutQLen

       32 bit unsigned wrappable counter."
   ::= {pr1645v2BgrMVPPPoEEntry 41418752}

pr1645v2BgrMVPPPoEMCOutDropEx OBJECT-TYPE
   SYNTAX      Counter64
   MAX-ACCESS  read-only
   STATUS      current
   DESCRIPTION
      "Path: bridgeGroup.performance.pppoEClient.mibCounters.ifOutDropLevelExceeded

       64 bit unsigned wrappable counter."
   ::= {pr1645v2BgrMVPPPoEEntry 41484288}

pr1645v2BgrMVPPPoEMCOutDropNoArp OBJECT-TYPE
   SYNTAX      Counter64
   MAX-ACCESS  read-only
   STATUS      current
   DESCRIPTION
      "Path: bridgeGroup.performance.pppoEClient.mibCounters.ifOutDiscardsNoArp

       64 bit unsigned wrappable counter."
   ::= {pr1645v2BgrMVPPPoEEntry 42336256}

pr1645v2BgrMVPPPoEMCOutDropFilter OBJECT-TYPE
   SYNTAX      Counter64
   MAX-ACCESS  read-only
   STATUS      current
   DESCRIPTION
      "Path: bridgeGroup.performance.pppoEClient.mibCounters.ifOutDiscardsFilter

       64 bit unsigned wrappable counter."
   ::= {pr1645v2BgrMVPPPoEEntry 42598400}

pr1645v2BgrMVPPPoEMCOutBandwidth15sec OBJECT-TYPE
   SYNTAX      Integer32
   MAX-ACCESS  read-only
   STATUS      current
   DESCRIPTION
      "Path: bridgeGroup.performance.pppoEClient.mibCounters.ifOutBandwidth.15sec

       unit name = bps
       formula = 8 * ; 8 /"
   ::= {pr1645v2BgrMVPPPoEEntry 45483264}

pr1645v2BgrMVPPPoEMCOutBandwidth30sec OBJECT-TYPE
   SYNTAX      Integer32
   MAX-ACCESS  read-only
   STATUS      current
   DESCRIPTION
      "Path: bridgeGroup.performance.pppoEClient.mibCounters.ifOutBandwidth.30sec

       unit name = bps
       formula = 8 * ; 8 /"
   ::= {pr1645v2BgrMVPPPoEEntry 45484544}

pr1645v2BgrMVPPPoEMCOutBandwidth1min OBJECT-TYPE
   SYNTAX      Integer32
   MAX-ACCESS  read-only
   STATUS      current
   DESCRIPTION
      "Path: bridgeGroup.performance.pppoEClient.mibCounters.ifOutBandwidth.1min

       unit name = bps
       formula = 8 * ; 8 /"
   ::= {pr1645v2BgrMVPPPoEEntry 45487104}

pr1645v2BgrMVPPPoEMCOutBandwidth2min OBJECT-TYPE
   SYNTAX      Integer32
   MAX-ACCESS  read-only
   STATUS      current
   DESCRIPTION
      "Path: bridgeGroup.performance.pppoEClient.mibCounters.ifOutBandwidth.2min

       unit name = bps
       formula = 8 * ; 8 /"
   ::= {pr1645v2BgrMVPPPoEEntry 45492224}

pr1645v2BgrMVPPPoEMCOutBandwidth5min OBJECT-TYPE
   SYNTAX      Integer32
   MAX-ACCESS  read-only
   STATUS      current
   DESCRIPTION
      "Path: bridgeGroup.performance.pppoEClient.mibCounters.ifOutBandwidth.5min

       unit name = bps
       formula = 8 * ; 8 /"
   ::= {pr1645v2BgrMVPPPoEEntry 45507584}

pr1645v2BgrMVPPPoEPppLinkMonitoringRequestsSent OBJECT-TYPE
   SYNTAX      Gauge32
   MAX-ACCESS  read-only
   STATUS      current
   DESCRIPTION
      "Path: bridgeGroup.performance.pppoEClient.ppp.linkMonitoring.requestsSent

       32 bit unsigned gauge value."
   ::= {pr1645v2BgrMVPPPoEEntry 50397440}

pr1645v2BgrMVPPPoEPppLinkMonitoringRepliesRcvd OBJECT-TYPE
   SYNTAX      Gauge32
   MAX-ACCESS  read-only
   STATUS      current
   DESCRIPTION
      "Path: bridgeGroup.performance.pppoEClient.ppp.linkMonitoring.repliesRcvd

       32 bit unsigned gauge value."
   ::= {pr1645v2BgrMVPPPoEEntry 50397696}

pr1645v2BgrMVPPPoEPppLinkMonitoringRequestsRcvd OBJECT-TYPE
   SYNTAX      Gauge32
   MAX-ACCESS  read-only
   STATUS      current
   DESCRIPTION
      "Path: bridgeGroup.performance.pppoEClient.ppp.linkMonitoring.requestsRcvd

       32 bit unsigned gauge value."
   ::= {pr1645v2BgrMVPPPoEEntry 50397952}

pr1645v2BgrMVPPPoEPppLinkMonitoringRepliesSent OBJECT-TYPE
   SYNTAX      Gauge32
   MAX-ACCESS  read-only
   STATUS      current
   DESCRIPTION
      "Path: bridgeGroup.performance.pppoEClient.ppp.linkMonitoring.repliesSent

       32 bit unsigned gauge value."
   ::= {pr1645v2BgrMVPPPoEEntry 50398208}

pr1645v2BgrMVPPPoEMCH2P OBJECT-TYPE
   SYNTAX      SEQUENCE OF Pr1645v2BgrMVPPPoEMCH2PEntry
   MAX-ACCESS  not-accessible
   STATUS      current
   DESCRIPTION
      ""
   ::= {pr1645v2BgrMVPPPoE 41549824}

pr1645v2BgrMVPPPoEMCH2PEntry OBJECT-TYPE
   SYNTAX      Pr1645v2BgrMVPPPoEMCH2PEntry
   MAX-ACCESS  not-accessible
   STATUS      current
   DESCRIPTION
      ""
   INDEX      { pr1645v2BgrMVPPPoETableIx,
                pr1645v2BgrMVPPPoEMCH2PTableIx }
   ::= {pr1645v2BgrMVPPPoEMCH2P 1}

Pr1645v2BgrMVPPPoEMCH2PEntry ::=
   SEQUENCE
      {
      pr1645v2BgrMVPPPoEMCH2PTableIx
         TableIndex,
      pr1645v2BgrMVPPPoEMCH2PSysUpTime
         TimeTicks,
      pr1645v2BgrMVPPPoEMCH2PIfUpTime
         TimeTicks,
      pr1645v2BgrMVPPPoEMCH2PIfStatChanges
         Counter32,
      pr1645v2BgrMVPPPoEMCH2PIfInOctets
         Counter64,
      pr1645v2BgrMVPPPoEMCH2PIfInUCPkts
         Counter64,
      pr1645v2BgrMVPPPoEMCH2PIfInNUCPkts
         Counter64,
      pr1645v2BgrMVPPPoEMCH2PIfInBCPkts
         Counter64,
      pr1645v2BgrMVPPPoEMCH2PIfInMCPkts
         Counter64,
      pr1645v2BgrMVPPPoEMCH2PIfInDiscards
         Counter64,
      pr1645v2BgrMVPPPoEMCH2PIfInErrors
         Counter64,
      pr1645v2BgrMVPPPoEMCH2PIfInUnkwn
         Counter64,
      pr1645v2BgrMVPPPoEMCH2PInDropEx
         Counter64,
      pr1645v2BgrMVPPPoEMCH2PInDropNoMac
         Counter64,
      pr1645v2BgrMVPPPoEMCH2PInDropNUCast
         Counter64,
      pr1645v2BgrMVPPPoEMCH2PInDropFilter
         Counter64,
      pr1645v2BgrMVPPPoEMCH2PIfInBandwidth
         Integer32,
      pr1645v2BgrMVPPPoEMCH2PIfOutOctets
         Counter64,
      pr1645v2BgrMVPPPoEMCH2PIfOutUCPkts
         Counter64,
      pr1645v2BgrMVPPPoEMCH2PIfOutNUCPkts
         Counter64,
      pr1645v2BgrMVPPPoEMCH2PIfOutBCPkts
         Counter64,
      pr1645v2BgrMVPPPoEMCH2PIfOutMCPkts
         Counter64,
      pr1645v2BgrMVPPPoEMCH2PIfOutDiscards
         Counter64,
      pr1645v2BgrMVPPPoEMCH2PIfOutErrors
         Counter64,
      pr1645v2BgrMVPPPoEMCH2POutDropEx
         Counter64,
      pr1645v2BgrMVPPPoEMCH2POutDropNoArp
         Counter64,
      pr1645v2BgrMVPPPoEMCH2POutDropFilter
         Counter64,
      pr1645v2BgrMVPPPoEMCH2PIfOutBandwidth
         Integer32,
      pr1645v2BgrMVPPPoEMCH2PIfErrSec
         Counter32
      }

pr1645v2BgrMVPPPoEMCH2PTableIx OBJECT-TYPE
   SYNTAX      TableIndex
   MAX-ACCESS  not-accessible
   STATUS      current
   DESCRIPTION
      ""
   ::= {pr1645v2BgrMVPPPoEMCH2PEntry 11}

pr1645v2BgrMVPPPoEMCH2PSysUpTime OBJECT-TYPE
   SYNTAX      TimeTicks
   MAX-ACCESS  read-only
   STATUS      current
   DESCRIPTION
      "Path: bridgeGroup.performance.pppoEClient.mibCounters.h2Performance.sysUpTime

       Time in centi-second."
   ::= {pr1645v2BgrMVPPPoEMCH2PEntry 16777216}

pr1645v2BgrMVPPPoEMCH2PIfUpTime OBJECT-TYPE
   SYNTAX      TimeTicks
   MAX-ACCESS  read-only
   STATUS      current
   DESCRIPTION
      "Path: bridgeGroup.performance.pppoEClient.mibCounters.h2Performance.ifUpTime

       Time in centi-second."
   ::= {pr1645v2BgrMVPPPoEMCH2PEntry 33554432}

pr1645v2BgrMVPPPoEMCH2PIfStatChanges OBJECT-TYPE
   SYNTAX      Counter32
   MAX-ACCESS  read-only
   STATUS      current
   DESCRIPTION
      "Path: bridgeGroup.performance.pppoEClient.mibCounters.h2Performance.ifStatusChanges

       32 bit unsigned wrappable counter."
   ::= {pr1645v2BgrMVPPPoEMCH2PEntry 50331648}

pr1645v2BgrMVPPPoEMCH2PIfInOctets OBJECT-TYPE
   SYNTAX      Counter64
   MAX-ACCESS  read-only
   STATUS      current
   DESCRIPTION
      "Path: bridgeGroup.performance.pppoEClient.mibCounters.h2Performance.ifInOctets

       64 bit unsigned wrappable counter."
   ::= {pr1645v2BgrMVPPPoEMCH2PEntry 67108864}

pr1645v2BgrMVPPPoEMCH2PIfInUCPkts OBJECT-TYPE
   SYNTAX      Counter64
   MAX-ACCESS  read-only
   STATUS      current
   DESCRIPTION
      "Path: bridgeGroup.performance.pppoEClient.mibCounters.h2Performance.ifInUcastPkts

       64 bit unsigned wrappable counter."
   ::= {pr1645v2BgrMVPPPoEMCH2PEntry 83886080}

pr1645v2BgrMVPPPoEMCH2PIfInNUCPkts OBJECT-TYPE
   SYNTAX      Counter64
   MAX-ACCESS  read-only
   STATUS      current
   DESCRIPTION
      "Path: bridgeGroup.performance.pppoEClient.mibCounters.h2Performance.ifInNUcastPkts

       64 bit unsigned wrappable counter."
   ::= {pr1645v2BgrMVPPPoEMCH2PEntry 100663296}

pr1645v2BgrMVPPPoEMCH2PIfInBCPkts OBJECT-TYPE
   SYNTAX      Counter64
   MAX-ACCESS  read-only
   STATUS      current
   DESCRIPTION
      "Path: bridgeGroup.performance.pppoEClient.mibCounters.h2Performance.ifInBcastPkts

       64 bit unsigned wrappable counter."
   ::= {pr1645v2BgrMVPPPoEMCH2PEntry 419430400}

pr1645v2BgrMVPPPoEMCH2PIfInMCPkts OBJECT-TYPE
   SYNTAX      Counter64
   MAX-ACCESS  read-only
   STATUS      current
   DESCRIPTION
      "Path: bridgeGroup.performance.pppoEClient.mibCounters.h2Performance.ifInMcastPkts

       64 bit unsigned wrappable counter."
   ::= {pr1645v2BgrMVPPPoEMCH2PEntry 436207616}

pr1645v2BgrMVPPPoEMCH2PIfInDiscards OBJECT-TYPE
   SYNTAX      Counter64
   MAX-ACCESS  read-only
   STATUS      current
   DESCRIPTION
      "Path: bridgeGroup.performance.pppoEClient.mibCounters.h2Performance.ifInDiscards

       64 bit unsigned wrappable counter."
   ::= {pr1645v2BgrMVPPPoEMCH2PEntry 117440512}

pr1645v2BgrMVPPPoEMCH2PIfInErrors OBJECT-TYPE
   SYNTAX      Counter64
   MAX-ACCESS  read-only
   STATUS      current
   DESCRIPTION
      "Path: bridgeGroup.performance.pppoEClient.mibCounters.h2Performance.ifInErrors

       64 bit unsigned wrappable counter."
   ::= {pr1645v2BgrMVPPPoEMCH2PEntry 134217728}

pr1645v2BgrMVPPPoEMCH2PIfInUnkwn OBJECT-TYPE
   SYNTAX      Counter64
   MAX-ACCESS  read-only
   STATUS      current
   DESCRIPTION
      "Path: bridgeGroup.performance.pppoEClient.mibCounters.h2Performance.ifInUnknownProtos

       64 bit unsigned wrappable counter."
   ::= {pr1645v2BgrMVPPPoEMCH2PEntry 150994944}

pr1645v2BgrMVPPPoEMCH2PInDropEx OBJECT-TYPE
   SYNTAX      Counter64
   MAX-ACCESS  read-only
   STATUS      current
   DESCRIPTION
      "Path: bridgeGroup.performance.pppoEClient.mibCounters.h2Performance.ifInDropLevelExceeded

       64 bit unsigned wrappable counter."
   ::= {pr1645v2BgrMVPPPoEMCH2PEntry 335544320}

pr1645v2BgrMVPPPoEMCH2PInDropNoMac OBJECT-TYPE
   SYNTAX      Counter64
   MAX-ACCESS  read-only
   STATUS      current
   DESCRIPTION
      "Path: bridgeGroup.performance.pppoEClient.mibCounters.h2Performance.fInDiscardsNoMacFit

       64 bit unsigned wrappable counter."
   ::= {pr1645v2BgrMVPPPoEMCH2PEntry 301989888}

pr1645v2BgrMVPPPoEMCH2PInDropNUCast OBJECT-TYPE
   SYNTAX      Counter64
   MAX-ACCESS  read-only
   STATUS      current
   DESCRIPTION
      "Path: bridgeGroup.performance.pppoEClient.mibCounters.h2Performance.fInDiscardsNUCast

       64 bit unsigned wrappable counter."
   ::= {pr1645v2BgrMVPPPoEMCH2PEntry 318767104}

pr1645v2BgrMVPPPoEMCH2PInDropFilter OBJECT-TYPE
   SYNTAX      Counter64
   MAX-ACCESS  read-only
   STATUS      current
   DESCRIPTION
      "Path: bridgeGroup.performance.pppoEClient.mibCounters.h2Performance.fInDiscardsFilter

       64 bit unsigned wrappable counter."
   ::= {pr1645v2BgrMVPPPoEMCH2PEntry 385875968}

pr1645v2BgrMVPPPoEMCH2PIfInBandwidth OBJECT-TYPE
   SYNTAX      Integer32
   MAX-ACCESS  read-only
   STATUS      current
   DESCRIPTION
      "Path: bridgeGroup.performance.pppoEClient.mibCounters.h2Performance.ifInBandwidth

       unit name = bps
       formula = 8 * ; 8 /"
   ::= {pr1645v2BgrMVPPPoEMCH2PEntry 268435456}

pr1645v2BgrMVPPPoEMCH2PIfOutOctets OBJECT-TYPE
   SYNTAX      Counter64
   MAX-ACCESS  read-only
   STATUS      current
   DESCRIPTION
      "Path: bridgeGroup.performance.pppoEClient.mibCounters.h2Performance.ifOutOctets

       64 bit unsigned wrappable counter."
   ::= {pr1645v2BgrMVPPPoEMCH2PEntry 167772160}

pr1645v2BgrMVPPPoEMCH2PIfOutUCPkts OBJECT-TYPE
   SYNTAX      Counter64
   MAX-ACCESS  read-only
   STATUS      current
   DESCRIPTION
      "Path: bridgeGroup.performance.pppoEClient.mibCounters.h2Performance.ifOutUcastPkts

       64 bit unsigned wrappable counter."
   ::= {pr1645v2BgrMVPPPoEMCH2PEntry 184549376}

pr1645v2BgrMVPPPoEMCH2PIfOutNUCPkts OBJECT-TYPE
   SYNTAX      Counter64
   MAX-ACCESS  read-only
   STATUS      current
   DESCRIPTION
      "Path: bridgeGroup.performance.pppoEClient.mibCounters.h2Performance.ifOutNUcastPkts

       64 bit unsigned wrappable counter."
   ::= {pr1645v2BgrMVPPPoEMCH2PEntry 201326592}

pr1645v2BgrMVPPPoEMCH2PIfOutBCPkts OBJECT-TYPE
   SYNTAX      Counter64
   MAX-ACCESS  read-only
   STATUS      current
   DESCRIPTION
      "Path: bridgeGroup.performance.pppoEClient.mibCounters.h2Performance.ifOutBcastPkts

       64 bit unsigned wrappable counter."
   ::= {pr1645v2BgrMVPPPoEMCH2PEntry 452984832}

pr1645v2BgrMVPPPoEMCH2PIfOutMCPkts OBJECT-TYPE
   SYNTAX      Counter64
   MAX-ACCESS  read-only
   STATUS      current
   DESCRIPTION
      "Path: bridgeGroup.performance.pppoEClient.mibCounters.h2Performance.ifOutMcastPkts

       64 bit unsigned wrappable counter."
   ::= {pr1645v2BgrMVPPPoEMCH2PEntry 469762048}

pr1645v2BgrMVPPPoEMCH2PIfOutDiscards OBJECT-TYPE
   SYNTAX      Counter64
   MAX-ACCESS  read-only
   STATUS      current
   DESCRIPTION
      "Path: bridgeGroup.performance.pppoEClient.mibCounters.h2Performance.ifOutDiscards

       64 bit unsigned wrappable counter."
   ::= {pr1645v2BgrMVPPPoEMCH2PEntry 218103808}

pr1645v2BgrMVPPPoEMCH2PIfOutErrors OBJECT-TYPE
   SYNTAX      Counter64
   MAX-ACCESS  read-only
   STATUS      current
   DESCRIPTION
      "Path: bridgeGroup.performance.pppoEClient.mibCounters.h2Performance.ifOutErrors

       64 bit unsigned wrappable counter."
   ::= {pr1645v2BgrMVPPPoEMCH2PEntry 234881024}

pr1645v2BgrMVPPPoEMCH2POutDropEx OBJECT-TYPE
   SYNTAX      Counter64
   MAX-ACCESS  read-only
   STATUS      current
   DESCRIPTION
      "Path: bridgeGroup.performance.pppoEClient.mibCounters.h2Performance.ifOutDropLevelExceeded

       64 bit unsigned wrappable counter."
   ::= {pr1645v2BgrMVPPPoEMCH2PEntry 352321536}

pr1645v2BgrMVPPPoEMCH2POutDropNoArp OBJECT-TYPE
   SYNTAX      Counter64
   MAX-ACCESS  read-only
   STATUS      current
   DESCRIPTION
      "Path: bridgeGroup.performance.pppoEClient.mibCounters.h2Performance.ifOutDiscardsNoArp

       64 bit unsigned wrappable counter."
   ::= {pr1645v2BgrMVPPPoEMCH2PEntry 369098752}

pr1645v2BgrMVPPPoEMCH2POutDropFilter OBJECT-TYPE
   SYNTAX      Counter64
   MAX-ACCESS  read-only
   STATUS      current
   DESCRIPTION
      "Path: bridgeGroup.performance.pppoEClient.mibCounters.h2Performance.ifOutDiscardsFilter

       64 bit unsigned wrappable counter."
   ::= {pr1645v2BgrMVPPPoEMCH2PEntry 402653184}

pr1645v2BgrMVPPPoEMCH2PIfOutBandwidth OBJECT-TYPE
   SYNTAX      Integer32
   MAX-ACCESS  read-only
   STATUS      current
   DESCRIPTION
      "Path: bridgeGroup.performance.pppoEClient.mibCounters.h2Performance.ifOutBandwidth

       unit name = bps
       formula = 8 * ; 8 /"
   ::= {pr1645v2BgrMVPPPoEMCH2PEntry 285212672}

pr1645v2BgrMVPPPoEMCH2PIfErrSec OBJECT-TYPE
   SYNTAX      Counter32
   MAX-ACCESS  read-only
   STATUS      current
   DESCRIPTION
      "Path: bridgeGroup.performance.pppoEClient.mibCounters.h2Performance.ifErrSec

       32 bit unsigned wrappable counter."
   ::= {pr1645v2BgrMVPPPoEMCH2PEntry 251658240}

pr1645v2BgrMVPPPoEMCH24P OBJECT-TYPE
   SYNTAX      SEQUENCE OF Pr1645v2BgrMVPPPoEMCH24PEntry
   MAX-ACCESS  not-accessible
   STATUS      current
   DESCRIPTION
      ""
   ::= {pr1645v2BgrMVPPPoE 41615360}

pr1645v2BgrMVPPPoEMCH24PEntry OBJECT-TYPE
   SYNTAX      Pr1645v2BgrMVPPPoEMCH24PEntry
   MAX-ACCESS  not-accessible
   STATUS      current
   DESCRIPTION
      ""
   INDEX      { pr1645v2BgrMVPPPoETableIx,
                pr1645v2BgrMVPPPoEMCH24PTableIx }
   ::= {pr1645v2BgrMVPPPoEMCH24P 1}

Pr1645v2BgrMVPPPoEMCH24PEntry ::=
   SEQUENCE
      {
      pr1645v2BgrMVPPPoEMCH24PTableIx
         TableIndex,
      pr1645v2BgrMVPPPoEMCH24PSysUpTime
         TimeTicks,
      pr1645v2BgrMVPPPoEMCH24PIfUpTime
         TimeTicks,
      pr1645v2BgrMVPPPoEMCH24PIfStatChanges
         Counter32,
      pr1645v2BgrMVPPPoEMCH24PIfInOctets
         Counter64,
      pr1645v2BgrMVPPPoEMCH24PIfInUCPkts
         Counter64,
      pr1645v2BgrMVPPPoEMCH24PIfInNUCPkts
         Counter64,
      pr1645v2BgrMVPPPoEMCH24PIfInBCPkts
         Counter64,
      pr1645v2BgrMVPPPoEMCH24PIfInMCPkts
         Counter64,
      pr1645v2BgrMVPPPoEMCH24PIfInDiscards
         Counter64,
      pr1645v2BgrMVPPPoEMCH24PIfInErrors
         Counter64,
      pr1645v2BgrMVPPPoEMCH24PIfInUnkwn
         Counter64,
      pr1645v2BgrMVPPPoEMCH24PInDropEx
         Counter64,
      pr1645v2BgrMVPPPoEMCH24PInDropNoMac
         Counter64,
      pr1645v2BgrMVPPPoEMCH24PInDropNUCast
         Counter64,
      pr1645v2BgrMVPPPoEMCH24PInDropFilter
         Counter64,
      pr1645v2BgrMVPPPoEMCH24PIfInBandwidth
         Integer32,
      pr1645v2BgrMVPPPoEMCH24PIfOutOctets
         Counter64,
      pr1645v2BgrMVPPPoEMCH24PIfOutUCPkts
         Counter64,
      pr1645v2BgrMVPPPoEMCH24PIfOutNUCPkts
         Counter64,
      pr1645v2BgrMVPPPoEMCH24PIfOutBCPkts
         Counter64,
      pr1645v2BgrMVPPPoEMCH24PIfOutMCPkts
         Counter64,
      pr1645v2BgrMVPPPoEMCH24PIfOutDiscards
         Counter64,
      pr1645v2BgrMVPPPoEMCH24PIfOutErrors
         Counter64,
      pr1645v2BgrMVPPPoEMCH24POutDropEx
         Counter64,
      pr1645v2BgrMVPPPoEMCH24POutDropNoArp
         Counter64,
      pr1645v2BgrMVPPPoEMCH24POutDropFilter
         Counter64,
      pr1645v2BgrMVPPPoEMCH24PIfOutBandwidth
         Integer32,
      pr1645v2BgrMVPPPoEMCH24PIfErrSec
         Counter32
      }

pr1645v2BgrMVPPPoEMCH24PTableIx OBJECT-TYPE
   SYNTAX      TableIndex
   MAX-ACCESS  not-accessible
   STATUS      current
   DESCRIPTION
      ""
   ::= {pr1645v2BgrMVPPPoEMCH24PEntry 11}

pr1645v2BgrMVPPPoEMCH24PSysUpTime OBJECT-TYPE
   SYNTAX      TimeTicks
   MAX-ACCESS  read-only
   STATUS      current
   DESCRIPTION
      "Path: bridgeGroup.performance.pppoEClient.mibCounters.h24Performance.sysUpTime

       Time in centi-second."
   ::= {pr1645v2BgrMVPPPoEMCH24PEntry 16777216}

pr1645v2BgrMVPPPoEMCH24PIfUpTime OBJECT-TYPE
   SYNTAX      TimeTicks
   MAX-ACCESS  read-only
   STATUS      current
   DESCRIPTION
      "Path: bridgeGroup.performance.pppoEClient.mibCounters.h24Performance.ifUpTime

       Time in centi-second."
   ::= {pr1645v2BgrMVPPPoEMCH24PEntry 33554432}

pr1645v2BgrMVPPPoEMCH24PIfStatChanges OBJECT-TYPE
   SYNTAX      Counter32
   MAX-ACCESS  read-only
   STATUS      current
   DESCRIPTION
      "Path: bridgeGroup.performance.pppoEClient.mibCounters.h24Performance.ifStatusChanges

       32 bit unsigned wrappable counter."
   ::= {pr1645v2BgrMVPPPoEMCH24PEntry 50331648}

pr1645v2BgrMVPPPoEMCH24PIfInOctets OBJECT-TYPE
   SYNTAX      Counter64
   MAX-ACCESS  read-only
   STATUS      current
   DESCRIPTION
      "Path: bridgeGroup.performance.pppoEClient.mibCounters.h24Performance.ifInOctets

       64 bit unsigned wrappable counter."
   ::= {pr1645v2BgrMVPPPoEMCH24PEntry 67108864}

pr1645v2BgrMVPPPoEMCH24PIfInUCPkts OBJECT-TYPE
   SYNTAX      Counter64
   MAX-ACCESS  read-only
   STATUS      current
   DESCRIPTION
      "Path: bridgeGroup.performance.pppoEClient.mibCounters.h24Performance.ifInUcastPkts

       64 bit unsigned wrappable counter."
   ::= {pr1645v2BgrMVPPPoEMCH24PEntry 83886080}

pr1645v2BgrMVPPPoEMCH24PIfInNUCPkts OBJECT-TYPE
   SYNTAX      Counter64
   MAX-ACCESS  read-only
   STATUS      current
   DESCRIPTION
      "Path: bridgeGroup.performance.pppoEClient.mibCounters.h24Performance.ifInNUcastPkts

       64 bit unsigned wrappable counter."
   ::= {pr1645v2BgrMVPPPoEMCH24PEntry 100663296}

pr1645v2BgrMVPPPoEMCH24PIfInBCPkts OBJECT-TYPE
   SYNTAX      Counter64
   MAX-ACCESS  read-only
   STATUS      current
   DESCRIPTION
      "Path: bridgeGroup.performance.pppoEClient.mibCounters.h24Performance.ifInBcastPkts

       64 bit unsigned wrappable counter."
   ::= {pr1645v2BgrMVPPPoEMCH24PEntry 419430400}

pr1645v2BgrMVPPPoEMCH24PIfInMCPkts OBJECT-TYPE
   SYNTAX      Counter64
   MAX-ACCESS  read-only
   STATUS      current
   DESCRIPTION
      "Path: bridgeGroup.performance.pppoEClient.mibCounters.h24Performance.ifInMcastPkts

       64 bit unsigned wrappable counter."
   ::= {pr1645v2BgrMVPPPoEMCH24PEntry 436207616}

pr1645v2BgrMVPPPoEMCH24PIfInDiscards OBJECT-TYPE
   SYNTAX      Counter64
   MAX-ACCESS  read-only
   STATUS      current
   DESCRIPTION
      "Path: bridgeGroup.performance.pppoEClient.mibCounters.h24Performance.ifInDiscards

       64 bit unsigned wrappable counter."
   ::= {pr1645v2BgrMVPPPoEMCH24PEntry 117440512}

pr1645v2BgrMVPPPoEMCH24PIfInErrors OBJECT-TYPE
   SYNTAX      Counter64
   MAX-ACCESS  read-only
   STATUS      current
   DESCRIPTION
      "Path: bridgeGroup.performance.pppoEClient.mibCounters.h24Performance.ifInErrors

       64 bit unsigned wrappable counter."
   ::= {pr1645v2BgrMVPPPoEMCH24PEntry 134217728}

pr1645v2BgrMVPPPoEMCH24PIfInUnkwn OBJECT-TYPE
   SYNTAX      Counter64
   MAX-ACCESS  read-only
   STATUS      current
   DESCRIPTION
      "Path: bridgeGroup.performance.pppoEClient.mibCounters.h24Performance.ifInUnknownProtos

       64 bit unsigned wrappable counter."
   ::= {pr1645v2BgrMVPPPoEMCH24PEntry 150994944}

pr1645v2BgrMVPPPoEMCH24PInDropEx OBJECT-TYPE
   SYNTAX      Counter64
   MAX-ACCESS  read-only
   STATUS      current
   DESCRIPTION
      "Path: bridgeGroup.performance.pppoEClient.mibCounters.h24Performance.ifInDropLevelExceeded

       64 bit unsigned wrappable counter."
   ::= {pr1645v2BgrMVPPPoEMCH24PEntry 335544320}

pr1645v2BgrMVPPPoEMCH24PInDropNoMac OBJECT-TYPE
   SYNTAX      Counter64
   MAX-ACCESS  read-only
   STATUS      current
   DESCRIPTION
      "Path: bridgeGroup.performance.pppoEClient.mibCounters.h24Performance.fInDiscardsNoMacFit

       64 bit unsigned wrappable counter."
   ::= {pr1645v2BgrMVPPPoEMCH24PEntry 301989888}

pr1645v2BgrMVPPPoEMCH24PInDropNUCast OBJECT-TYPE
   SYNTAX      Counter64
   MAX-ACCESS  read-only
   STATUS      current
   DESCRIPTION
      "Path: bridgeGroup.performance.pppoEClient.mibCounters.h24Performance.fInDiscardsNUCast

       64 bit unsigned wrappable counter."
   ::= {pr1645v2BgrMVPPPoEMCH24PEntry 318767104}

pr1645v2BgrMVPPPoEMCH24PInDropFilter OBJECT-TYPE
   SYNTAX      Counter64
   MAX-ACCESS  read-only
   STATUS      current
   DESCRIPTION
      "Path: bridgeGroup.performance.pppoEClient.mibCounters.h24Performance.fInDiscardsFilter

       64 bit unsigned wrappable counter."
   ::= {pr1645v2BgrMVPPPoEMCH24PEntry 385875968}

pr1645v2BgrMVPPPoEMCH24PIfInBandwidth OBJECT-TYPE
   SYNTAX      Integer32
   MAX-ACCESS  read-only
   STATUS      current
   DESCRIPTION
      "Path: bridgeGroup.performance.pppoEClient.mibCounters.h24Performance.ifInBandwidth

       unit name = bps
       formula = 8 * ; 8 /"
   ::= {pr1645v2BgrMVPPPoEMCH24PEntry 268435456}

pr1645v2BgrMVPPPoEMCH24PIfOutOctets OBJECT-TYPE
   SYNTAX      Counter64
   MAX-ACCESS  read-only
   STATUS      current
   DESCRIPTION
      "Path: bridgeGroup.performance.pppoEClient.mibCounters.h24Performance.ifOutOctets

       64 bit unsigned wrappable counter."
   ::= {pr1645v2BgrMVPPPoEMCH24PEntry 167772160}

pr1645v2BgrMVPPPoEMCH24PIfOutUCPkts OBJECT-TYPE
   SYNTAX      Counter64
   MAX-ACCESS  read-only
   STATUS      current
   DESCRIPTION
      "Path: bridgeGroup.performance.pppoEClient.mibCounters.h24Performance.ifOutUcastPkts

       64 bit unsigned wrappable counter."
   ::= {pr1645v2BgrMVPPPoEMCH24PEntry 184549376}

pr1645v2BgrMVPPPoEMCH24PIfOutNUCPkts OBJECT-TYPE
   SYNTAX      Counter64
   MAX-ACCESS  read-only
   STATUS      current
   DESCRIPTION
      "Path: bridgeGroup.performance.pppoEClient.mibCounters.h24Performance.ifOutNUcastPkts

       64 bit unsigned wrappable counter."
   ::= {pr1645v2BgrMVPPPoEMCH24PEntry 201326592}

pr1645v2BgrMVPPPoEMCH24PIfOutBCPkts OBJECT-TYPE
   SYNTAX      Counter64
   MAX-ACCESS  read-only
   STATUS      current
   DESCRIPTION
      "Path: bridgeGroup.performance.pppoEClient.mibCounters.h24Performance.ifOutBcastPkts

       64 bit unsigned wrappable counter."
   ::= {pr1645v2BgrMVPPPoEMCH24PEntry 452984832}

pr1645v2BgrMVPPPoEMCH24PIfOutMCPkts OBJECT-TYPE
   SYNTAX      Counter64
   MAX-ACCESS  read-only
   STATUS      current
   DESCRIPTION
      "Path: bridgeGroup.performance.pppoEClient.mibCounters.h24Performance.ifOutMcastPkts

       64 bit unsigned wrappable counter."
   ::= {pr1645v2BgrMVPPPoEMCH24PEntry 469762048}

pr1645v2BgrMVPPPoEMCH24PIfOutDiscards OBJECT-TYPE
   SYNTAX      Counter64
   MAX-ACCESS  read-only
   STATUS      current
   DESCRIPTION
      "Path: bridgeGroup.performance.pppoEClient.mibCounters.h24Performance.ifOutDiscards

       64 bit unsigned wrappable counter."
   ::= {pr1645v2BgrMVPPPoEMCH24PEntry 218103808}

pr1645v2BgrMVPPPoEMCH24PIfOutErrors OBJECT-TYPE
   SYNTAX      Counter64
   MAX-ACCESS  read-only
   STATUS      current
   DESCRIPTION
      "Path: bridgeGroup.performance.pppoEClient.mibCounters.h24Performance.ifOutErrors

       64 bit unsigned wrappable counter."
   ::= {pr1645v2BgrMVPPPoEMCH24PEntry 234881024}

pr1645v2BgrMVPPPoEMCH24POutDropEx OBJECT-TYPE
   SYNTAX      Counter64
   MAX-ACCESS  read-only
   STATUS      current
   DESCRIPTION
      "Path: bridgeGroup.performance.pppoEClient.mibCounters.h24Performance.ifOutDropLevelExceeded

       64 bit unsigned wrappable counter."
   ::= {pr1645v2BgrMVPPPoEMCH24PEntry 352321536}

pr1645v2BgrMVPPPoEMCH24POutDropNoArp OBJECT-TYPE
   SYNTAX      Counter64
   MAX-ACCESS  read-only
   STATUS      current
   DESCRIPTION
      "Path: bridgeGroup.performance.pppoEClient.mibCounters.h24Performance.ifOutDiscardsNoArp

       64 bit unsigned wrappable counter."
   ::= {pr1645v2BgrMVPPPoEMCH24PEntry 369098752}

pr1645v2BgrMVPPPoEMCH24POutDropFilter OBJECT-TYPE
   SYNTAX      Counter64
   MAX-ACCESS  read-only
   STATUS      current
   DESCRIPTION
      "Path: bridgeGroup.performance.pppoEClient.mibCounters.h24Performance.ifOutDiscardsFilter

       64 bit unsigned wrappable counter."
   ::= {pr1645v2BgrMVPPPoEMCH24PEntry 402653184}

pr1645v2BgrMVPPPoEMCH24PIfOutBandwidth OBJECT-TYPE
   SYNTAX      Integer32
   MAX-ACCESS  read-only
   STATUS      current
   DESCRIPTION
      "Path: bridgeGroup.performance.pppoEClient.mibCounters.h24Performance.ifOutBandwidth

       unit name = bps
       formula = 8 * ; 8 /"
   ::= {pr1645v2BgrMVPPPoEMCH24PEntry 285212672}

pr1645v2BgrMVPPPoEMCH24PIfErrSec OBJECT-TYPE
   SYNTAX      Counter32
   MAX-ACCESS  read-only
   STATUS      current
   DESCRIPTION
      "Path: bridgeGroup.performance.pppoEClient.mibCounters.h24Performance.ifErrSec

       32 bit unsigned wrappable counter."
   ::= {pr1645v2BgrMVPPPoEMCH24PEntry 251658240}

pr1645v2BgrMVPPPoEMCD7P OBJECT-TYPE
   SYNTAX      SEQUENCE OF Pr1645v2BgrMVPPPoEMCD7PEntry
   MAX-ACCESS  not-accessible
   STATUS      current
   DESCRIPTION
      ""
   ::= {pr1645v2BgrMVPPPoE 41680896}

pr1645v2BgrMVPPPoEMCD7PEntry OBJECT-TYPE
   SYNTAX      Pr1645v2BgrMVPPPoEMCD7PEntry
   MAX-ACCESS  not-accessible
   STATUS      current
   DESCRIPTION
      ""
   INDEX      { pr1645v2BgrMVPPPoETableIx,
                pr1645v2BgrMVPPPoEMCD7PTableIx }
   ::= {pr1645v2BgrMVPPPoEMCD7P 1}

Pr1645v2BgrMVPPPoEMCD7PEntry ::=
   SEQUENCE
      {
      pr1645v2BgrMVPPPoEMCD7PTableIx
         TableIndex,
      pr1645v2BgrMVPPPoEMCD7PSysUpTime
         TimeTicks,
      pr1645v2BgrMVPPPoEMCD7PIfUpTime
         TimeTicks,
      pr1645v2BgrMVPPPoEMCD7PIfStatChanges
         Counter32,
      pr1645v2BgrMVPPPoEMCD7PIfInOctets
         Counter64,
      pr1645v2BgrMVPPPoEMCD7PIfInUCPkts
         Counter64,
      pr1645v2BgrMVPPPoEMCD7PIfInNUCPkts
         Counter64,
      pr1645v2BgrMVPPPoEMCD7PIfInBCPkts
         Counter64,
      pr1645v2BgrMVPPPoEMCD7PIfInMCPkts
         Counter64,
      pr1645v2BgrMVPPPoEMCD7PIfInDiscards
         Counter64,
      pr1645v2BgrMVPPPoEMCD7PIfInErrors
         Counter64,
      pr1645v2BgrMVPPPoEMCD7PIfInUnkwn
         Counter64,
      pr1645v2BgrMVPPPoEMCD7PInDropEx
         Counter64,
      pr1645v2BgrMVPPPoEMCD7PInDropNoMac
         Counter64,
      pr1645v2BgrMVPPPoEMCD7PInDropNUCast
         Counter64,
      pr1645v2BgrMVPPPoEMCD7PInDropFilter
         Counter64,
      pr1645v2BgrMVPPPoEMCD7PIfInBandwidth
         Integer32,
      pr1645v2BgrMVPPPoEMCD7PIfOutOctets
         Counter64,
      pr1645v2BgrMVPPPoEMCD7PIfOutUCPkts
         Counter64,
      pr1645v2BgrMVPPPoEMCD7PIfOutNUCPkts
         Counter64,
      pr1645v2BgrMVPPPoEMCD7PIfOutBCPkts
         Counter64,
      pr1645v2BgrMVPPPoEMCD7PIfOutMCPkts
         Counter64,
      pr1645v2BgrMVPPPoEMCD7PIfOutDiscards
         Counter64,
      pr1645v2BgrMVPPPoEMCD7PIfOutErrors
         Counter64,
      pr1645v2BgrMVPPPoEMCD7POutDropEx
         Counter64,
      pr1645v2BgrMVPPPoEMCD7POutDropNoArp
         Counter64,
      pr1645v2BgrMVPPPoEMCD7POutDropFilter
         Counter64,
      pr1645v2BgrMVPPPoEMCD7PIfOutBandwidth
         Integer32,
      pr1645v2BgrMVPPPoEMCD7PIfErrSec
         Counter32
      }

pr1645v2BgrMVPPPoEMCD7PTableIx OBJECT-TYPE
   SYNTAX      TableIndex
   MAX-ACCESS  not-accessible
   STATUS      current
   DESCRIPTION
      ""
   ::= {pr1645v2BgrMVPPPoEMCD7PEntry 11}

pr1645v2BgrMVPPPoEMCD7PSysUpTime OBJECT-TYPE
   SYNTAX      TimeTicks
   MAX-ACCESS  read-only
   STATUS      current
   DESCRIPTION
      "Path: bridgeGroup.performance.pppoEClient.mibCounters.d7Performance.sysUpTime

       Time in centi-second."
   ::= {pr1645v2BgrMVPPPoEMCD7PEntry 16777216}

pr1645v2BgrMVPPPoEMCD7PIfUpTime OBJECT-TYPE
   SYNTAX      TimeTicks
   MAX-ACCESS  read-only
   STATUS      current
   DESCRIPTION
      "Path: bridgeGroup.performance.pppoEClient.mibCounters.d7Performance.ifUpTime

       Time in centi-second."
   ::= {pr1645v2BgrMVPPPoEMCD7PEntry 33554432}

pr1645v2BgrMVPPPoEMCD7PIfStatChanges OBJECT-TYPE
   SYNTAX      Counter32
   MAX-ACCESS  read-only
   STATUS      current
   DESCRIPTION
      "Path: bridgeGroup.performance.pppoEClient.mibCounters.d7Performance.ifStatusChanges

       32 bit unsigned wrappable counter."
   ::= {pr1645v2BgrMVPPPoEMCD7PEntry 50331648}

pr1645v2BgrMVPPPoEMCD7PIfInOctets OBJECT-TYPE
   SYNTAX      Counter64
   MAX-ACCESS  read-only
   STATUS      current
   DESCRIPTION
      "Path: bridgeGroup.performance.pppoEClient.mibCounters.d7Performance.ifInOctets

       64 bit unsigned wrappable counter."
   ::= {pr1645v2BgrMVPPPoEMCD7PEntry 67108864}

pr1645v2BgrMVPPPoEMCD7PIfInUCPkts OBJECT-TYPE
   SYNTAX      Counter64
   MAX-ACCESS  read-only
   STATUS      current
   DESCRIPTION
      "Path: bridgeGroup.performance.pppoEClient.mibCounters.d7Performance.ifInUcastPkts

       64 bit unsigned wrappable counter."
   ::= {pr1645v2BgrMVPPPoEMCD7PEntry 83886080}

pr1645v2BgrMVPPPoEMCD7PIfInNUCPkts OBJECT-TYPE
   SYNTAX      Counter64
   MAX-ACCESS  read-only
   STATUS      current
   DESCRIPTION
      "Path: bridgeGroup.performance.pppoEClient.mibCounters.d7Performance.ifInNUcastPkts

       64 bit unsigned wrappable counter."
   ::= {pr1645v2BgrMVPPPoEMCD7PEntry 100663296}

pr1645v2BgrMVPPPoEMCD7PIfInBCPkts OBJECT-TYPE
   SYNTAX      Counter64
   MAX-ACCESS  read-only
   STATUS      current
   DESCRIPTION
      "Path: bridgeGroup.performance.pppoEClient.mibCounters.d7Performance.ifInBcastPkts

       64 bit unsigned wrappable counter."
   ::= {pr1645v2BgrMVPPPoEMCD7PEntry 419430400}

pr1645v2BgrMVPPPoEMCD7PIfInMCPkts OBJECT-TYPE
   SYNTAX      Counter64
   MAX-ACCESS  read-only
   STATUS      current
   DESCRIPTION
      "Path: bridgeGroup.performance.pppoEClient.mibCounters.d7Performance.ifInMcastPkts

       64 bit unsigned wrappable counter."
   ::= {pr1645v2BgrMVPPPoEMCD7PEntry 436207616}

pr1645v2BgrMVPPPoEMCD7PIfInDiscards OBJECT-TYPE
   SYNTAX      Counter64
   MAX-ACCESS  read-only
   STATUS      current
   DESCRIPTION
      "Path: bridgeGroup.performance.pppoEClient.mibCounters.d7Performance.ifInDiscards

       64 bit unsigned wrappable counter."
   ::= {pr1645v2BgrMVPPPoEMCD7PEntry 117440512}

pr1645v2BgrMVPPPoEMCD7PIfInErrors OBJECT-TYPE
   SYNTAX      Counter64
   MAX-ACCESS  read-only
   STATUS      current
   DESCRIPTION
      "Path: bridgeGroup.performance.pppoEClient.mibCounters.d7Performance.ifInErrors

       64 bit unsigned wrappable counter."
   ::= {pr1645v2BgrMVPPPoEMCD7PEntry 134217728}

pr1645v2BgrMVPPPoEMCD7PIfInUnkwn OBJECT-TYPE
   SYNTAX      Counter64
   MAX-ACCESS  read-only
   STATUS      current
   DESCRIPTION
      "Path: bridgeGroup.performance.pppoEClient.mibCounters.d7Performance.ifInUnknownProtos

       64 bit unsigned wrappable counter."
   ::= {pr1645v2BgrMVPPPoEMCD7PEntry 150994944}

pr1645v2BgrMVPPPoEMCD7PInDropEx OBJECT-TYPE
   SYNTAX      Counter64
   MAX-ACCESS  read-only
   STATUS      current
   DESCRIPTION
      "Path: bridgeGroup.performance.pppoEClient.mibCounters.d7Performance.ifInDropLevelExceeded

       64 bit unsigned wrappable counter."
   ::= {pr1645v2BgrMVPPPoEMCD7PEntry 335544320}

pr1645v2BgrMVPPPoEMCD7PInDropNoMac OBJECT-TYPE
   SYNTAX      Counter64
   MAX-ACCESS  read-only
   STATUS      current
   DESCRIPTION
      "Path: bridgeGroup.performance.pppoEClient.mibCounters.d7Performance.fInDiscardsNoMacFit

       64 bit unsigned wrappable counter."
   ::= {pr1645v2BgrMVPPPoEMCD7PEntry 301989888}

pr1645v2BgrMVPPPoEMCD7PInDropNUCast OBJECT-TYPE
   SYNTAX      Counter64
   MAX-ACCESS  read-only
   STATUS      current
   DESCRIPTION
      "Path: bridgeGroup.performance.pppoEClient.mibCounters.d7Performance.fInDiscardsNUCast

       64 bit unsigned wrappable counter."
   ::= {pr1645v2BgrMVPPPoEMCD7PEntry 318767104}

pr1645v2BgrMVPPPoEMCD7PInDropFilter OBJECT-TYPE
   SYNTAX      Counter64
   MAX-ACCESS  read-only
   STATUS      current
   DESCRIPTION
      "Path: bridgeGroup.performance.pppoEClient.mibCounters.d7Performance.fInDiscardsFilter

       64 bit unsigned wrappable counter."
   ::= {pr1645v2BgrMVPPPoEMCD7PEntry 385875968}

pr1645v2BgrMVPPPoEMCD7PIfInBandwidth OBJECT-TYPE
   SYNTAX      Integer32
   MAX-ACCESS  read-only
   STATUS      current
   DESCRIPTION
      "Path: bridgeGroup.performance.pppoEClient.mibCounters.d7Performance.ifInBandwidth

       unit name = bps
       formula = 8 * ; 8 /"
   ::= {pr1645v2BgrMVPPPoEMCD7PEntry 268435456}

pr1645v2BgrMVPPPoEMCD7PIfOutOctets OBJECT-TYPE
   SYNTAX      Counter64
   MAX-ACCESS  read-only
   STATUS      current
   DESCRIPTION
      "Path: bridgeGroup.performance.pppoEClient.mibCounters.d7Performance.ifOutOctets

       64 bit unsigned wrappable counter."
   ::= {pr1645v2BgrMVPPPoEMCD7PEntry 167772160}

pr1645v2BgrMVPPPoEMCD7PIfOutUCPkts OBJECT-TYPE
   SYNTAX      Counter64
   MAX-ACCESS  read-only
   STATUS      current
   DESCRIPTION
      "Path: bridgeGroup.performance.pppoEClient.mibCounters.d7Performance.ifOutUcastPkts

       64 bit unsigned wrappable counter."
   ::= {pr1645v2BgrMVPPPoEMCD7PEntry 184549376}

pr1645v2BgrMVPPPoEMCD7PIfOutNUCPkts OBJECT-TYPE
   SYNTAX      Counter64
   MAX-ACCESS  read-only
   STATUS      current
   DESCRIPTION
      "Path: bridgeGroup.performance.pppoEClient.mibCounters.d7Performance.ifOutNUcastPkts

       64 bit unsigned wrappable counter."
   ::= {pr1645v2BgrMVPPPoEMCD7PEntry 201326592}

pr1645v2BgrMVPPPoEMCD7PIfOutBCPkts OBJECT-TYPE
   SYNTAX      Counter64
   MAX-ACCESS  read-only
   STATUS      current
   DESCRIPTION
      "Path: bridgeGroup.performance.pppoEClient.mibCounters.d7Performance.ifOutBcastPkts

       64 bit unsigned wrappable counter."
   ::= {pr1645v2BgrMVPPPoEMCD7PEntry 452984832}

pr1645v2BgrMVPPPoEMCD7PIfOutMCPkts OBJECT-TYPE
   SYNTAX      Counter64
   MAX-ACCESS  read-only
   STATUS      current
   DESCRIPTION
      "Path: bridgeGroup.performance.pppoEClient.mibCounters.d7Performance.ifOutMcastPkts

       64 bit unsigned wrappable counter."
   ::= {pr1645v2BgrMVPPPoEMCD7PEntry 469762048}

pr1645v2BgrMVPPPoEMCD7PIfOutDiscards OBJECT-TYPE
   SYNTAX      Counter64
   MAX-ACCESS  read-only
   STATUS      current
   DESCRIPTION
      "Path: bridgeGroup.performance.pppoEClient.mibCounters.d7Performance.ifOutDiscards

       64 bit unsigned wrappable counter."
   ::= {pr1645v2BgrMVPPPoEMCD7PEntry 218103808}

pr1645v2BgrMVPPPoEMCD7PIfOutErrors OBJECT-TYPE
   SYNTAX      Counter64
   MAX-ACCESS  read-only
   STATUS      current
   DESCRIPTION
      "Path: bridgeGroup.performance.pppoEClient.mibCounters.d7Performance.ifOutErrors

       64 bit unsigned wrappable counter."
   ::= {pr1645v2BgrMVPPPoEMCD7PEntry 234881024}

pr1645v2BgrMVPPPoEMCD7POutDropEx OBJECT-TYPE
   SYNTAX      Counter64
   MAX-ACCESS  read-only
   STATUS      current
   DESCRIPTION
      "Path: bridgeGroup.performance.pppoEClient.mibCounters.d7Performance.ifOutDropLevelExceeded

       64 bit unsigned wrappable counter."
   ::= {pr1645v2BgrMVPPPoEMCD7PEntry 352321536}

pr1645v2BgrMVPPPoEMCD7POutDropNoArp OBJECT-TYPE
   SYNTAX      Counter64
   MAX-ACCESS  read-only
   STATUS      current
   DESCRIPTION
      "Path: bridgeGroup.performance.pppoEClient.mibCounters.d7Performance.ifOutDiscardsNoArp

       64 bit unsigned wrappable counter."
   ::= {pr1645v2BgrMVPPPoEMCD7PEntry 369098752}

pr1645v2BgrMVPPPoEMCD7POutDropFilter OBJECT-TYPE
   SYNTAX      Counter64
   MAX-ACCESS  read-only
   STATUS      current
   DESCRIPTION
      "Path: bridgeGroup.performance.pppoEClient.mibCounters.d7Performance.ifOutDiscardsFilter

       64 bit unsigned wrappable counter."
   ::= {pr1645v2BgrMVPPPoEMCD7PEntry 402653184}

pr1645v2BgrMVPPPoEMCD7PIfOutBandwidth OBJECT-TYPE
   SYNTAX      Integer32
   MAX-ACCESS  read-only
   STATUS      current
   DESCRIPTION
      "Path: bridgeGroup.performance.pppoEClient.mibCounters.d7Performance.ifOutBandwidth

       unit name = bps
       formula = 8 * ; 8 /"
   ::= {pr1645v2BgrMVPPPoEMCD7PEntry 285212672}

pr1645v2BgrMVPPPoEMCD7PIfErrSec OBJECT-TYPE
   SYNTAX      Counter32
   MAX-ACCESS  read-only
   STATUS      current
   DESCRIPTION
      "Path: bridgeGroup.performance.pppoEClient.mibCounters.d7Performance.ifErrSec

       32 bit unsigned wrappable counter."
   ::= {pr1645v2BgrMVPPPoEMCD7PEntry 251658240}



fr1645v2BgrMV OBJECT IDENTIFIER ::= {r1645v2BgrMV 13}


fr1645v2BgrMVAlarm OBJECT IDENTIFIER ::= {fr1645v2BgrMV 207}

fr1645v2BgrMVAlarmSSC OBJECT IDENTIFIER ::= {fr1645v2BgrMVAlarm 1}

fr1645v2BgrMVAlarmEntry OBJECT IDENTIFIER ::= {fr1645v2BgrMVAlarmSSC 1}

fr1645v2BgrMVAlarmDiscriminator OBJECT-TYPE
   SYNTAX      Integer32
   MAX-ACCESS  read-only
   STATUS      current
   DESCRIPTION
      "Path: bridgeGroup.alarms.alarmInfo.discriminator"
   ::= {fr1645v2BgrMVAlarmEntry 16777216}

fr1645v2BgrMVAlarmCurrent OBJECT-TYPE
   SYNTAX      Integer32
   MAX-ACCESS  read-only
   STATUS      current
   DESCRIPTION
      "Path: bridgeGroup.alarms.alarmInfo.currentAlarms

       Bit meanings:
               bit 0 = linkDown,
               bit 1 = linkShutdown"
   ::= {fr1645v2BgrMVAlarmEntry 33554432}

fr1645v2BgrMVAlarmPrevious OBJECT-TYPE
   SYNTAX      Integer32
   MAX-ACCESS  read-only
   STATUS      current
   DESCRIPTION
      "Path: bridgeGroup.alarms.alarmInfo.previousAlarms

       Bit meanings:
               bit 0 = linkDown,
               bit 1 = linkShutdown"
   ::= {fr1645v2BgrMVAlarmEntry 50331648}

fr1645v2BgrMVAlarmMask OBJECT-TYPE
   SYNTAX      Integer32
   MAX-ACCESS  read-only
   STATUS      current
   DESCRIPTION
      "Path: bridgeGroup.alarms.alarmInfo.alarmMask

       Bit meanings:
               bit 0 = linkDown,
               bit 1 = linkShutdown"
   ::= {fr1645v2BgrMVAlarmEntry 67108864}

fr1645v2BgrMVAlarmLevelLinkDown OBJECT-TYPE
   SYNTAX      Integer32
   MAX-ACCESS  read-only
   STATUS      current
   DESCRIPTION
      "Path: bridgeGroup.alarms.alarmInfo.alarmLevel.linkDown"
   ::= {fr1645v2BgrMVAlarmEntry 83951616}

fr1645v2BgrMVAlarmLevelLinkShutdown OBJECT-TYPE
   SYNTAX      Integer32
   MAX-ACCESS  read-only
   STATUS      current
   DESCRIPTION
      "Path: bridgeGroup.alarms.alarmInfo.alarmLevel.linkShutdown"
   ::= {fr1645v2BgrMVAlarmEntry 84017152}


fr1645v2BgrMVAlarmE2 OBJECT IDENTIFIER ::= {fr1645v2BgrMVAlarm 2}

fr1645v2BgrMVAlarmE2Entry OBJECT IDENTIFIER ::= {fr1645v2BgrMVAlarmE2 1}

fr1645v2BgrMVAlarmE2LinkDown OBJECT IDENTIFIER ::= {fr1645v2BgrMVAlarmE2Entry 10}

fr1645v2BgrMVAlarmE2LinkDownPfx OBJECT IDENTIFIER ::= {fr1645v2BgrMVAlarmE2LinkDown 0}

fr1645v2BgrMVAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'bridgeGroupMultiVlansMacEth1'
                (root='router1645') has changed from the ON to the OFF state."
   ::= {fr1645v2BgrMVAlarmE2LinkDownPfx 1}

fr1645v2BgrMVAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'bridgeGroupMultiVlansMacEth1'
                (root='router1645') has changed from the OFF to the ON state."
   ::= {fr1645v2BgrMVAlarmE2LinkDownPfx 2}

fr1645v2BgrMVAlarmE2LinkShutdown OBJECT IDENTIFIER ::= {fr1645v2BgrMVAlarmE2Entry 11}

fr1645v2BgrMVAlarmE2LinkShutdownPfx OBJECT IDENTIFIER ::= {fr1645v2BgrMVAlarmE2LinkShutdown 0}

fr1645v2BgrMVAlarmE2LinkShutdownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'bridgeGroupMultiVlansMacEth1'
                (root='router1645') has changed from the ON to the OFF state."
   ::= {fr1645v2BgrMVAlarmE2LinkShutdownPfx 1}

fr1645v2BgrMVAlarmE2LinkShutdownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'bridgeGroupMultiVlansMacEth1'
                (root='router1645') has changed from the OFF to the ON state."
   ::= {fr1645v2BgrMVAlarmE2LinkShutdownPfx 2}



ar1645v2BgrMV OBJECT IDENTIFIER ::= {r1645v2BgrMV 16}


ar1645v2BgrMVClearCounters OBJECT-TYPE
   SYNTAX      Integer32
   MAX-ACCESS  read-write
   STATUS      current
   DESCRIPTION
      "Path: bridgeGroup.actions.clearCounters
       Info: reset counters"
   ::= {ar1645v2BgrMV 263}


ar1645v2BgrMVClearBridgeCache OBJECT-TYPE
   SYNTAX      Integer32
   MAX-ACCESS  read-write
   STATUS      current
   DESCRIPTION
      "Path: bridgeGroup.actions.clearBridgeCache
       Info: clear all dynamic entries in bridge cache table"
   ::= {ar1645v2BgrMV 20}


ar1645v2BgrMVBridgeShutdown OBJECT-TYPE
   SYNTAX      Integer32
   MAX-ACCESS  read-write
   STATUS      current
   DESCRIPTION
      "Path: bridgeGroup.actions.bridgeShutdown
       Info: shutdown interface manually"
   ::= {ar1645v2BgrMV 72}


ar1645v2BgrMVInterface OBJECT-TYPE
   SYNTAX      DisplayString
   MAX-ACCESS  read-write
   STATUS      current
   DESCRIPTION
      "Path: bridgeGroup.actions.interface
       Info: interface name for action"
   ::= {ar1645v2BgrMV 73}


ar1645v2BgrMVBridgeRestart OBJECT-TYPE
   SYNTAX      Integer32
   MAX-ACCESS  read-write
   STATUS      current
   DESCRIPTION
      "Path: bridgeGroup.actions.bridgeRestart
       Info: restart interface blocked by security"
   ::= {ar1645v2BgrMV 70}


ar1645v2BgrMVBridgingInterface OBJECT-TYPE
   SYNTAX      DisplayString
   MAX-ACCESS  read-write
   STATUS      current
   DESCRIPTION
      "Path: bridgeGroup.actions.bridgingInterface
       Info: interface name for action"
   ::= {ar1645v2BgrMV 71}


ar1645v2BgrMVClearArpCache OBJECT-TYPE
   SYNTAX      Integer32
   MAX-ACCESS  read-write
   STATUS      current
   DESCRIPTION
      "Path: bridgeGroup.actions.clearArpCache
       Info: clear all dynamic enties in ARP cache table"
   ::= {ar1645v2BgrMV 25}



END
