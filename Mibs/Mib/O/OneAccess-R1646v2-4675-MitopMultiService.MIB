OneAccess-R1646v2-4675-MitopMultiService DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2MitopMultiService OBJECT IDENTIFIER ::= {r1646Rootv2 4675}

r1646v2MitopMultiServiceMOProp OBJECT-TYPE
   SYNTAX      SEQUENCE OF R1646v2MitopMultiServiceMOPropEntry
   MAX-ACCESS  not-accessible
   STATUS      current
   DESCRIPTION
      ""
   ::= {r1646v2MitopMultiService 1}

r1646v2MitopMultiServiceMOPropEntry OBJECT-TYPE
   SYNTAX      R1646v2MitopMultiServiceMOPropEntry
   MAX-ACCESS  not-accessible
   STATUS      current
   DESCRIPTION
      ""
   INDEX      { r1646v2MitopMultiServiceMOPropGlobalIx }
   ::= {r1646v2MitopMultiServiceMOProp 1}

R1646v2MitopMultiServiceMOPropEntry ::=
   SEQUENCE
      {
      r1646v2MitopMultiServiceMOPropPath
         ContainmentPath,
      r1646v2MitopMultiServiceMOPropRev
         ObjectRevision,
      r1646v2MitopMultiServiceMOPropGlobalIx
         GlobalIndex
      }

r1646v2MitopMultiServiceMOPropPath OBJECT-TYPE
   SYNTAX      ContainmentPath
   MAX-ACCESS  read-only
   STATUS      current
   DESCRIPTION
      "Textual description of the containment tree from the instance of
       the root object down to the instance of the current object."
   ::= {r1646v2MitopMultiServiceMOPropEntry 3}

r1646v2MitopMultiServiceMOPropRev OBJECT-TYPE
   SYNTAX      ObjectRevision
   MAX-ACCESS  read-only
   STATUS      current
   DESCRIPTION
      "This value corresponds with the revision of the MANAGED OBJECT."
   ::= {r1646v2MitopMultiServiceMOPropEntry 4}

r1646v2MitopMultiServiceMOPropGlobalIx OBJECT-TYPE
   SYNTAX      GlobalIndex
   MAX-ACCESS  read-only
   STATUS      current
   DESCRIPTION
      "The value of the tlsCntTreeGlobalIndex of the MANAGED OBJECT."
   ::= {r1646v2MitopMultiServiceMOPropEntry 10}



er1646v2MitopMultiService OBJECT IDENTIFIER ::= {r1646v2MitopMultiService 11}


er1646v2MitopMultiServiceJitterBuffer OBJECT IDENTIFIER ::= {er1646v2MitopMultiService 16}

er1646v2MitopMultiServiceJitterBufferTable OBJECT-TYPE
   SYNTAX      SEQUENCE OF Er1646v2MitopMultiServiceJitterBufferEntry
   MAX-ACCESS  not-accessible
   STATUS      current
   DESCRIPTION
      "MiTOP pseudowire jitter buffer size"
   ::= {er1646v2MitopMultiServiceJitterBuffer 1}

er1646v2MitopMultiServiceJitterBufferEntry OBJECT-TYPE
   SYNTAX      Er1646v2MitopMultiServiceJitterBufferEntry
   MAX-ACCESS  not-accessible
   STATUS      current
   DESCRIPTION
      ""
   INDEX      { er1646v2MitopMultiServiceJitterBufferGlobalIx }
   ::= {er1646v2MitopMultiServiceJitterBufferTable 1}

Er1646v2MitopMultiServiceJitterBufferEntry ::=
   SEQUENCE
      {
      er1646v2MitopMultiServiceJitterBufferGlobalIx
         GlobalIndex,
      er1646v2MitopMultiServiceJitterBufferValue
         Integer32
      }

er1646v2MitopMultiServiceJitterBufferGlobalIx OBJECT-TYPE
   SYNTAX      GlobalIndex
   MAX-ACCESS  not-accessible
   STATUS      current
   DESCRIPTION
      "The value of the tlsCntTreeGlobalIndex of the MANAGED OBJECT."
   ::= {er1646v2MitopMultiServiceJitterBufferEntry 10}

er1646v2MitopMultiServiceJitterBufferValue OBJECT-TYPE
   SYNTAX      Integer32
   MAX-ACCESS  read-write
   STATUS      current
   DESCRIPTION
      "Path: multiService.editConf.jitterBuffer"
   ::= {er1646v2MitopMultiServiceJitterBufferEntry 2147483648}


er1646v2MitopMultiServicePeer OBJECT IDENTIFIER ::= {er1646v2MitopMultiService 20}

er1646v2MitopMultiServicePeerSSCTable OBJECT-TYPE
   SYNTAX      SEQUENCE OF Er1646v2MitopMultiServicePeerEntry
   MAX-ACCESS  not-accessible
   STATUS      current
   DESCRIPTION
      "MiTOP peer device"
   ::= {er1646v2MitopMultiServicePeer 1}

er1646v2MitopMultiServicePeerEntry OBJECT-TYPE
   SYNTAX      Er1646v2MitopMultiServicePeerEntry
   MAX-ACCESS  not-accessible
   STATUS      current
   DESCRIPTION
      ""
   INDEX      { er1646v2MitopMultiServicePeerGlobalIx }
   ::= {er1646v2MitopMultiServicePeerSSCTable 1}

Er1646v2MitopMultiServicePeerEntry ::=
   SEQUENCE
      {
      er1646v2MitopMultiServicePeerGlobalIx
         GlobalIndex,
      er1646v2MitopMultiServicePeerName
         DisplayString,
      er1646v2MitopMultiServicePeerIpAddress
         IpAddress,
      er1646v2MitopMultiServicePeerNextHopAddress
         IpAddress,
      er1646v2MitopMultiServicePeerMacAddress
         OCTET STRING
      }

er1646v2MitopMultiServicePeerGlobalIx OBJECT-TYPE
   SYNTAX      GlobalIndex
   MAX-ACCESS  not-accessible
   STATUS      current
   DESCRIPTION
      "The value of the tlsCntTreeGlobalIndex of the MANAGED OBJECT."
   ::= {er1646v2MitopMultiServicePeerEntry 10}

er1646v2MitopMultiServicePeerName OBJECT-TYPE
   SYNTAX      DisplayString
   MAX-ACCESS  read-write
   STATUS      current
   DESCRIPTION
      "Path: multiService.editConf.peer.name"
   ::= {er1646v2MitopMultiServicePeerEntry 16777216}

er1646v2MitopMultiServicePeerIpAddress OBJECT-TYPE
   SYNTAX      IpAddress
   MAX-ACCESS  read-write
   STATUS      current
   DESCRIPTION
      "Path: multiService.editConf.peer.ipAddress"
   ::= {er1646v2MitopMultiServicePeerEntry 33554432}

er1646v2MitopMultiServicePeerNextHopAddress OBJECT-TYPE
   SYNTAX      IpAddress
   MAX-ACCESS  read-write
   STATUS      current
   DESCRIPTION
      "Path: multiService.editConf.peer.nextHopAddress"
   ::= {er1646v2MitopMultiServicePeerEntry 50331648}

er1646v2MitopMultiServicePeerMacAddress OBJECT-TYPE
   SYNTAX      OCTET STRING
   MAX-ACCESS  read-write
   STATUS      current
   DESCRIPTION
      "Path: multiService.editConf.peer.macAddress

       MAC address."
   ::= {er1646v2MitopMultiServicePeerEntry 67108864}


er1646v2MitopMultiServicePseudowire OBJECT IDENTIFIER ::= {er1646v2MitopMultiService 21}

er1646v2MitopMultiServicePseudowireSSCTable OBJECT-TYPE
   SYNTAX      SEQUENCE OF Er1646v2MitopMultiServicePseudowireEntry
   MAX-ACCESS  not-accessible
   STATUS      current
   DESCRIPTION
      "MiTOP pseudowire connection"
   ::= {er1646v2MitopMultiServicePseudowire 1}

er1646v2MitopMultiServicePseudowireEntry OBJECT-TYPE
   SYNTAX      Er1646v2MitopMultiServicePseudowireEntry
   MAX-ACCESS  not-accessible
   STATUS      current
   DESCRIPTION
      ""
   INDEX      { er1646v2MitopMultiServicePseudowireGlobalIx }
   ::= {er1646v2MitopMultiServicePseudowireSSCTable 1}

Er1646v2MitopMultiServicePseudowireEntry ::=
   SEQUENCE
      {
      er1646v2MitopMultiServicePseudowireGlobalIx
         GlobalIndex,
      er1646v2MitopMultiServicePseudowireName
         DisplayString,
      er1646v2MitopMultiServicePseudowireAdminStatus
         INTEGER,
      er1646v2MitopMultiServicePseudowireSourceIpAddress
         IpAddress,
      er1646v2MitopMultiServicePseudowireOutPwLabel
         Integer32,
      er1646v2MitopMultiServicePseudowireInPwLabel
         Integer32,
      er1646v2MitopMultiServicePseudowirePayloadFramed
         Integer32,
      er1646v2MitopMultiServicePseudowirePayloadUnframed
         Integer32
      }

er1646v2MitopMultiServicePseudowireGlobalIx OBJECT-TYPE
   SYNTAX      GlobalIndex
   MAX-ACCESS  not-accessible
   STATUS      current
   DESCRIPTION
      "The value of the tlsCntTreeGlobalIndex of the MANAGED OBJECT."
   ::= {er1646v2MitopMultiServicePseudowireEntry 10}

er1646v2MitopMultiServicePseudowireName OBJECT-TYPE
   SYNTAX      DisplayString
   MAX-ACCESS  read-write
   STATUS      current
   DESCRIPTION
      "Path: multiService.editConf.pseudowire.name"
   ::= {er1646v2MitopMultiServicePseudowireEntry 16777216}

er1646v2MitopMultiServicePseudowireAdminStatus OBJECT-TYPE
   SYNTAX      INTEGER
               {
               up (1),
               down (2)
               }
   MAX-ACCESS  read-write
   STATUS      current
   DESCRIPTION
      "Path: multiService.editConf.pseudowire.adminStatus

       Possibilities:
               up   (1)
               down   (2)"
   ::= {er1646v2MitopMultiServicePseudowireEntry 33554432}

er1646v2MitopMultiServicePseudowireSourceIpAddress OBJECT-TYPE
   SYNTAX      IpAddress
   MAX-ACCESS  read-write
   STATUS      current
   DESCRIPTION
      "Path: multiService.editConf.pseudowire.sourceIpAddress"
   ::= {er1646v2MitopMultiServicePseudowireEntry 50331648}

er1646v2MitopMultiServicePseudowireOutPwLabel OBJECT-TYPE
   SYNTAX      Integer32
   MAX-ACCESS  read-write
   STATUS      current
   DESCRIPTION
      "Path: multiService.editConf.pseudowire.outPwLabel"
   ::= {er1646v2MitopMultiServicePseudowireEntry 67108864}

er1646v2MitopMultiServicePseudowireInPwLabel OBJECT-TYPE
   SYNTAX      Integer32
   MAX-ACCESS  read-write
   STATUS      current
   DESCRIPTION
      "Path: multiService.editConf.pseudowire.inPwLabel"
   ::= {er1646v2MitopMultiServicePseudowireEntry 83886080}

er1646v2MitopMultiServicePseudowirePayloadFramed OBJECT-TYPE
   SYNTAX      Integer32
   UNITS       "frames"
   MAX-ACCESS  read-write
   STATUS      current
   DESCRIPTION
      "Path: multiService.editConf.pseudowire.payloadFramed

       unit name = frames"
   ::= {er1646v2MitopMultiServicePseudowireEntry 100663296}

er1646v2MitopMultiServicePseudowirePayloadUnframed OBJECT-TYPE
   SYNTAX      Integer32
   UNITS       "bytes"
   MAX-ACCESS  read-write
   STATUS      current
   DESCRIPTION
      "Path: multiService.editConf.pseudowire.payloadUnframed

       unit name = bytes"
   ::= {er1646v2MitopMultiServicePseudowireEntry 117440512}



sr1646v2MitopMultiService OBJECT IDENTIFIER ::= {r1646v2MitopMultiService 14}


sr1646v2MitopMultiServicePseudowireEncaps OBJECT IDENTIFIER ::= {sr1646v2MitopMultiService 33}

sr1646v2MitopMultiServicePseudowireEncapsTable OBJECT-TYPE
   SYNTAX      SEQUENCE OF Sr1646v2MitopMultiServicePseudowireEncapsEntry
   MAX-ACCESS  not-accessible
   STATUS      current
   DESCRIPTION
      "MiTOP pseudowire encapsulation"
   ::= {sr1646v2MitopMultiServicePseudowireEncaps 1}

sr1646v2MitopMultiServicePseudowireEncapsEntry OBJECT-TYPE
   SYNTAX      Sr1646v2MitopMultiServicePseudowireEncapsEntry
   MAX-ACCESS  not-accessible
   STATUS      current
   DESCRIPTION
      ""
   INDEX      { sr1646v2MitopMultiServicePseudowireEncapsGlobalIx }
   ::= {sr1646v2MitopMultiServicePseudowireEncapsTable 1}

Sr1646v2MitopMultiServicePseudowireEncapsEntry ::=
   SEQUENCE
      {
      sr1646v2MitopMultiServicePseudowireEncapsGlobalIx
         GlobalIndex,
      sr1646v2MitopMultiServicePseudowireEncapsValue
         INTEGER
      }

sr1646v2MitopMultiServicePseudowireEncapsGlobalIx OBJECT-TYPE
   SYNTAX      GlobalIndex
   MAX-ACCESS  not-accessible
   STATUS      current
   DESCRIPTION
      "The value of the tlsCntTreeGlobalIndex of the MANAGED OBJECT."
   ::= {sr1646v2MitopMultiServicePseudowireEncapsEntry 10}

sr1646v2MitopMultiServicePseudowireEncapsValue OBJECT-TYPE
   SYNTAX      INTEGER
               {
               satmomp (0),
               cesmompsn (1)
               }
   MAX-ACCESS  read-only
   STATUS      current
   DESCRIPTION
      "Path: multiService.status.pseudowireEncaps

       Possibilities:
               sat-o-p   (0)
               ces-o-psn   (1)"
   ::= {sr1646v2MitopMultiServicePseudowireEncapsEntry 2147483648}


sr1646v2MitopMultiServiceJitterBufferLevel OBJECT IDENTIFIER ::= {sr1646v2MitopMultiService 34}

sr1646v2MitopMultiServiceJitterBufferLevelTable OBJECT-TYPE
   SYNTAX      SEQUENCE OF Sr1646v2MitopMultiServiceJitterBufferLevelEntry
   MAX-ACCESS  not-accessible
   STATUS      current
   DESCRIPTION
      "MiTOP pseudowire jitter buffer level"
   ::= {sr1646v2MitopMultiServiceJitterBufferLevel 1}

sr1646v2MitopMultiServiceJitterBufferLevelEntry OBJECT-TYPE
   SYNTAX      Sr1646v2MitopMultiServiceJitterBufferLevelEntry
   MAX-ACCESS  not-accessible
   STATUS      current
   DESCRIPTION
      ""
   INDEX      { sr1646v2MitopMultiServiceJitterBufferLevelGlobalIx }
   ::= {sr1646v2MitopMultiServiceJitterBufferLevelTable 1}

Sr1646v2MitopMultiServiceJitterBufferLevelEntry ::=
   SEQUENCE
      {
      sr1646v2MitopMultiServiceJitterBufferLevelGlobalIx
         GlobalIndex,
      sr1646v2MitopMultiServiceJitterBufferLevelValue
         Integer32
      }

sr1646v2MitopMultiServiceJitterBufferLevelGlobalIx OBJECT-TYPE
   SYNTAX      GlobalIndex
   MAX-ACCESS  not-accessible
   STATUS      current
   DESCRIPTION
      "The value of the tlsCntTreeGlobalIndex of the MANAGED OBJECT."
   ::= {sr1646v2MitopMultiServiceJitterBufferLevelEntry 10}

sr1646v2MitopMultiServiceJitterBufferLevelValue OBJECT-TYPE
   SYNTAX      Integer32
   MAX-ACCESS  read-only
   STATUS      current
   DESCRIPTION
      "Path: multiService.status.jitterBufferLevel"
   ::= {sr1646v2MitopMultiServiceJitterBufferLevelEntry 2147483648}


sr1646v2MitopMultiServiceJitterBufferMinLevel OBJECT IDENTIFIER ::= {sr1646v2MitopMultiService 35}

sr1646v2MitopMultiServiceJitterBufferMinLevelTable OBJECT-TYPE
   SYNTAX      SEQUENCE OF Sr1646v2MitopMultiServiceJitterBufferMinLevelEntry
   MAX-ACCESS  not-accessible
   STATUS      current
   DESCRIPTION
      "MiTOP pseudowire jitter buffer level"
   ::= {sr1646v2MitopMultiServiceJitterBufferMinLevel 1}

sr1646v2MitopMultiServiceJitterBufferMinLevelEntry OBJECT-TYPE
   SYNTAX      Sr1646v2MitopMultiServiceJitterBufferMinLevelEntry
   MAX-ACCESS  not-accessible
   STATUS      current
   DESCRIPTION
      ""
   INDEX      { sr1646v2MitopMultiServiceJitterBufferMinLevelGlobalIx }
   ::= {sr1646v2MitopMultiServiceJitterBufferMinLevelTable 1}

Sr1646v2MitopMultiServiceJitterBufferMinLevelEntry ::=
   SEQUENCE
      {
      sr1646v2MitopMultiServiceJitterBufferMinLevelGlobalIx
         GlobalIndex,
      sr1646v2MitopMultiServiceJitterBufferMinLevelValue
         Integer32
      }

sr1646v2MitopMultiServiceJitterBufferMinLevelGlobalIx OBJECT-TYPE
   SYNTAX      GlobalIndex
   MAX-ACCESS  not-accessible
   STATUS      current
   DESCRIPTION
      "The value of the tlsCntTreeGlobalIndex of the MANAGED OBJECT."
   ::= {sr1646v2MitopMultiServiceJitterBufferMinLevelEntry 10}

sr1646v2MitopMultiServiceJitterBufferMinLevelValue OBJECT-TYPE
   SYNTAX      Integer32
   MAX-ACCESS  read-only
   STATUS      current
   DESCRIPTION
      "Path: multiService.status.jitterBufferMinLevel"
   ::= {sr1646v2MitopMultiServiceJitterBufferMinLevelEntry 2147483648}


sr1646v2MitopMultiServiceJitterBufferMaxLevel OBJECT IDENTIFIER ::= {sr1646v2MitopMultiService 36}

sr1646v2MitopMultiServiceJitterBufferMaxLevelTable OBJECT-TYPE
   SYNTAX      SEQUENCE OF Sr1646v2MitopMultiServiceJitterBufferMaxLevelEntry
   MAX-ACCESS  not-accessible
   STATUS      current
   DESCRIPTION
      "MiTOP pseudowire jitter buffer level"
   ::= {sr1646v2MitopMultiServiceJitterBufferMaxLevel 1}

sr1646v2MitopMultiServiceJitterBufferMaxLevelEntry OBJECT-TYPE
   SYNTAX      Sr1646v2MitopMultiServiceJitterBufferMaxLevelEntry
   MAX-ACCESS  not-accessible
   STATUS      current
   DESCRIPTION
      ""
   INDEX      { sr1646v2MitopMultiServiceJitterBufferMaxLevelGlobalIx }
   ::= {sr1646v2MitopMultiServiceJitterBufferMaxLevelTable 1}

Sr1646v2MitopMultiServiceJitterBufferMaxLevelEntry ::=
   SEQUENCE
      {
      sr1646v2MitopMultiServiceJitterBufferMaxLevelGlobalIx
         GlobalIndex,
      sr1646v2MitopMultiServiceJitterBufferMaxLevelValue
         Integer32
      }

sr1646v2MitopMultiServiceJitterBufferMaxLevelGlobalIx OBJECT-TYPE
   SYNTAX      GlobalIndex
   MAX-ACCESS  not-accessible
   STATUS      current
   DESCRIPTION
      "The value of the tlsCntTreeGlobalIndex of the MANAGED OBJECT."
   ::= {sr1646v2MitopMultiServiceJitterBufferMaxLevelEntry 10}

sr1646v2MitopMultiServiceJitterBufferMaxLevelValue OBJECT-TYPE
   SYNTAX      Integer32
   MAX-ACCESS  read-only
   STATUS      current
   DESCRIPTION
      "Path: multiService.status.jitterBufferMaxLevel"
   ::= {sr1646v2MitopMultiServiceJitterBufferMaxLevelEntry 2147483648}


sr1646v2MitopMultiServiceConnectivity OBJECT IDENTIFIER ::= {sr1646v2MitopMultiService 42}

sr1646v2MitopMultiServiceConnectivityTable OBJECT-TYPE
   SYNTAX      SEQUENCE OF Sr1646v2MitopMultiServiceConnectivityEntry
   MAX-ACCESS  not-accessible
   STATUS      current
   DESCRIPTION
      "MiTOP connectivity status"
   ::= {sr1646v2MitopMultiServiceConnectivity 1}

sr1646v2MitopMultiServiceConnectivityEntry OBJECT-TYPE
   SYNTAX      Sr1646v2MitopMultiServiceConnectivityEntry
   MAX-ACCESS  not-accessible
   STATUS      current
   DESCRIPTION
      ""
   INDEX      { sr1646v2MitopMultiServiceConnectivityGlobalIx }
   ::= {sr1646v2MitopMultiServiceConnectivityTable 1}

Sr1646v2MitopMultiServiceConnectivityEntry ::=
   SEQUENCE
      {
      sr1646v2MitopMultiServiceConnectivityGlobalIx
         GlobalIndex,
      sr1646v2MitopMultiServiceConnectivityValue
         INTEGER
      }

sr1646v2MitopMultiServiceConnectivityGlobalIx OBJECT-TYPE
   SYNTAX      GlobalIndex
   MAX-ACCESS  not-accessible
   STATUS      current
   DESCRIPTION
      "The value of the tlsCntTreeGlobalIndex of the MANAGED OBJECT."
   ::= {sr1646v2MitopMultiServiceConnectivityEntry 10}

sr1646v2MitopMultiServiceConnectivityValue OBJECT-TYPE
   SYNTAX      INTEGER
               {
               oamDisable (0),
               outOfSync (1),
               notValid (2),
               sync (3)
               }
   MAX-ACCESS  read-only
   STATUS      current
   DESCRIPTION
      "Path: multiService.status.connectivity

       Possibilities:
               oamDisable   (0)
               outOfSync   (1)
               notValid   (2)
               sync   (3)"
   ::= {sr1646v2MitopMultiServiceConnectivityEntry 2147483648}


sr1646v2MitopMultiServicePseudowireMacAddress OBJECT IDENTIFIER ::= {sr1646v2MitopMultiService 43}

sr1646v2MitopMultiServicePseudowireMacAddressTable OBJECT-TYPE
   SYNTAX      SEQUENCE OF Sr1646v2MitopMultiServicePseudowireMacAddressEntry
   MAX-ACCESS  not-accessible
   STATUS      current
   DESCRIPTION
      "MiTOP mac address"
   ::= {sr1646v2MitopMultiServicePseudowireMacAddress 1}

sr1646v2MitopMultiServicePseudowireMacAddressEntry OBJECT-TYPE
   SYNTAX      Sr1646v2MitopMultiServicePseudowireMacAddressEntry
   MAX-ACCESS  not-accessible
   STATUS      current
   DESCRIPTION
      ""
   INDEX      { sr1646v2MitopMultiServicePseudowireMacAddressGlobalIx }
   ::= {sr1646v2MitopMultiServicePseudowireMacAddressTable 1}

Sr1646v2MitopMultiServicePseudowireMacAddressEntry ::=
   SEQUENCE
      {
      sr1646v2MitopMultiServicePseudowireMacAddressGlobalIx
         GlobalIndex,
      sr1646v2MitopMultiServicePseudowireMacAddressValue
         OCTET STRING
      }

sr1646v2MitopMultiServicePseudowireMacAddressGlobalIx OBJECT-TYPE
   SYNTAX      GlobalIndex
   MAX-ACCESS  not-accessible
   STATUS      current
   DESCRIPTION
      "The value of the tlsCntTreeGlobalIndex of the MANAGED OBJECT."
   ::= {sr1646v2MitopMultiServicePseudowireMacAddressEntry 10}

sr1646v2MitopMultiServicePseudowireMacAddressValue OBJECT-TYPE
   SYNTAX      OCTET STRING
   MAX-ACCESS  read-only
   STATUS      current
   DESCRIPTION
      "Path: multiService.status.pseudowireMacAddress

       MAC address."
   ::= {sr1646v2MitopMultiServicePseudowireMacAddressEntry 2147483648}


sr1646v2MitopMultiServiceSnmpIndex OBJECT IDENTIFIER ::= {sr1646v2MitopMultiService 269}

sr1646v2MitopMultiServiceSnmpIndexTable OBJECT-TYPE
   SYNTAX      SEQUENCE OF Sr1646v2MitopMultiServiceSnmpIndexEntry
   MAX-ACCESS  not-accessible
   STATUS      current
   DESCRIPTION
      "SNMP index assigned to this object"
   ::= {sr1646v2MitopMultiServiceSnmpIndex 1}

sr1646v2MitopMultiServiceSnmpIndexEntry OBJECT-TYPE
   SYNTAX      Sr1646v2MitopMultiServiceSnmpIndexEntry
   MAX-ACCESS  not-accessible
   STATUS      current
   DESCRIPTION
      ""
   INDEX      { sr1646v2MitopMultiServiceSnmpIndexGlobalIx }
   ::= {sr1646v2MitopMultiServiceSnmpIndexTable 1}

Sr1646v2MitopMultiServiceSnmpIndexEntry ::=
   SEQUENCE
      {
      sr1646v2MitopMultiServiceSnmpIndexGlobalIx
         GlobalIndex,
      sr1646v2MitopMultiServiceSnmpIndexValue
         Integer32
      }

sr1646v2MitopMultiServiceSnmpIndexGlobalIx OBJECT-TYPE
   SYNTAX      GlobalIndex
   MAX-ACCESS  not-accessible
   STATUS      current
   DESCRIPTION
      "The value of the tlsCntTreeGlobalIndex of the MANAGED OBJECT."
   ::= {sr1646v2MitopMultiServiceSnmpIndexEntry 10}

sr1646v2MitopMultiServiceSnmpIndexValue OBJECT-TYPE
   SYNTAX      Integer32
   MAX-ACCESS  read-only
   STATUS      current
   DESCRIPTION
      "Path: multiService.status.snmpIndex"
   ::= {sr1646v2MitopMultiServiceSnmpIndexEntry 2147483648}



pr1646v2MitopMultiService OBJECT IDENTIFIER ::= {r1646v2MitopMultiService 12}


pr1646v2MitopMultiServiceRxGoodPackets OBJECT IDENTIFIER ::= {pr1646v2MitopMultiService 52}

pr1646v2MitopMultiServiceRxGoodPacketsTable OBJECT-TYPE
   SYNTAX      SEQUENCE OF Pr1646v2MitopMultiServiceRxGoodPacketsEntry
   MAX-ACCESS  not-accessible
   STATUS      current
   DESCRIPTION
      "MiTOP pseudowire statistics"
   ::= {pr1646v2MitopMultiServiceRxGoodPackets 1}

pr1646v2MitopMultiServiceRxGoodPacketsEntry OBJECT-TYPE
   SYNTAX      Pr1646v2MitopMultiServiceRxGoodPacketsEntry
   MAX-ACCESS  not-accessible
   STATUS      current
   DESCRIPTION
      ""
   INDEX      { pr1646v2MitopMultiServiceRxGoodPacketsGlobalIx }
   ::= {pr1646v2MitopMultiServiceRxGoodPacketsTable 1}

Pr1646v2MitopMultiServiceRxGoodPacketsEntry ::=
   SEQUENCE
      {
      pr1646v2MitopMultiServiceRxGoodPacketsGlobalIx
         GlobalIndex,
      pr1646v2MitopMultiServiceRxGoodPacketsValue
         Counter32
      }

pr1646v2MitopMultiServiceRxGoodPacketsGlobalIx OBJECT-TYPE
   SYNTAX      GlobalIndex
   MAX-ACCESS  not-accessible
   STATUS      current
   DESCRIPTION
      "The value of the tlsCntTreeGlobalIndex of the MANAGED OBJECT."
   ::= {pr1646v2MitopMultiServiceRxGoodPacketsEntry 10}

pr1646v2MitopMultiServiceRxGoodPacketsValue OBJECT-TYPE
   SYNTAX      Counter32
   MAX-ACCESS  read-only
   STATUS      current
   DESCRIPTION
      "Path: multiService.performance.rxGoodPackets

       32 bit unsigned wrappable counter."
   ::= {pr1646v2MitopMultiServiceRxGoodPacketsEntry 2147483648}


pr1646v2MitopMultiServiceTxGoodPackets OBJECT IDENTIFIER ::= {pr1646v2MitopMultiService 53}

pr1646v2MitopMultiServiceTxGoodPacketsTable OBJECT-TYPE
   SYNTAX      SEQUENCE OF Pr1646v2MitopMultiServiceTxGoodPacketsEntry
   MAX-ACCESS  not-accessible
   STATUS      current
   DESCRIPTION
      "MiTOP pseudowire statistics"
   ::= {pr1646v2MitopMultiServiceTxGoodPackets 1}

pr1646v2MitopMultiServiceTxGoodPacketsEntry OBJECT-TYPE
   SYNTAX      Pr1646v2MitopMultiServiceTxGoodPacketsEntry
   MAX-ACCESS  not-accessible
   STATUS      current
   DESCRIPTION
      ""
   INDEX      { pr1646v2MitopMultiServiceTxGoodPacketsGlobalIx }
   ::= {pr1646v2MitopMultiServiceTxGoodPacketsTable 1}

Pr1646v2MitopMultiServiceTxGoodPacketsEntry ::=
   SEQUENCE
      {
      pr1646v2MitopMultiServiceTxGoodPacketsGlobalIx
         GlobalIndex,
      pr1646v2MitopMultiServiceTxGoodPacketsValue
         Counter32
      }

pr1646v2MitopMultiServiceTxGoodPacketsGlobalIx OBJECT-TYPE
   SYNTAX      GlobalIndex
   MAX-ACCESS  not-accessible
   STATUS      current
   DESCRIPTION
      "The value of the tlsCntTreeGlobalIndex of the MANAGED OBJECT."
   ::= {pr1646v2MitopMultiServiceTxGoodPacketsEntry 10}

pr1646v2MitopMultiServiceTxGoodPacketsValue OBJECT-TYPE
   SYNTAX      Counter32
   MAX-ACCESS  read-only
   STATUS      current
   DESCRIPTION
      "Path: multiService.performance.txGoodPackets

       32 bit unsigned wrappable counter."
   ::= {pr1646v2MitopMultiServiceTxGoodPacketsEntry 2147483648}


pr1646v2MitopMultiServiceMissingPackets OBJECT IDENTIFIER ::= {pr1646v2MitopMultiService 54}

pr1646v2MitopMultiServiceMissingPacketsTable OBJECT-TYPE
   SYNTAX      SEQUENCE OF Pr1646v2MitopMultiServiceMissingPacketsEntry
   MAX-ACCESS  not-accessible
   STATUS      current
   DESCRIPTION
      "MiTOP pseudowire statistics"
   ::= {pr1646v2MitopMultiServiceMissingPackets 1}

pr1646v2MitopMultiServiceMissingPacketsEntry OBJECT-TYPE
   SYNTAX      Pr1646v2MitopMultiServiceMissingPacketsEntry
   MAX-ACCESS  not-accessible
   STATUS      current
   DESCRIPTION
      ""
   INDEX      { pr1646v2MitopMultiServiceMissingPacketsGlobalIx }
   ::= {pr1646v2MitopMultiServiceMissingPacketsTable 1}

Pr1646v2MitopMultiServiceMissingPacketsEntry ::=
   SEQUENCE
      {
      pr1646v2MitopMultiServiceMissingPacketsGlobalIx
         GlobalIndex,
      pr1646v2MitopMultiServiceMissingPacketsValue
         Counter32
      }

pr1646v2MitopMultiServiceMissingPacketsGlobalIx OBJECT-TYPE
   SYNTAX      GlobalIndex
   MAX-ACCESS  not-accessible
   STATUS      current
   DESCRIPTION
      "The value of the tlsCntTreeGlobalIndex of the MANAGED OBJECT."
   ::= {pr1646v2MitopMultiServiceMissingPacketsEntry 10}

pr1646v2MitopMultiServiceMissingPacketsValue OBJECT-TYPE
   SYNTAX      Counter32
   MAX-ACCESS  read-only
   STATUS      current
   DESCRIPTION
      "Path: multiService.performance.missingPackets

       32 bit unsigned wrappable counter."
   ::= {pr1646v2MitopMultiServiceMissingPacketsEntry 2147483648}


pr1646v2MitopMultiServiceMisorderedPackets OBJECT IDENTIFIER ::= {pr1646v2MitopMultiService 55}

pr1646v2MitopMultiServiceMisorderedPacketsTable OBJECT-TYPE
   SYNTAX      SEQUENCE OF Pr1646v2MitopMultiServiceMisorderedPacketsEntry
   MAX-ACCESS  not-accessible
   STATUS      current
   DESCRIPTION
      "MiTOP pseudowire statistics"
   ::= {pr1646v2MitopMultiServiceMisorderedPackets 1}

pr1646v2MitopMultiServiceMisorderedPacketsEntry OBJECT-TYPE
   SYNTAX      Pr1646v2MitopMultiServiceMisorderedPacketsEntry
   MAX-ACCESS  not-accessible
   STATUS      current
   DESCRIPTION
      ""
   INDEX      { pr1646v2MitopMultiServiceMisorderedPacketsGlobalIx }
   ::= {pr1646v2MitopMultiServiceMisorderedPacketsTable 1}

Pr1646v2MitopMultiServiceMisorderedPacketsEntry ::=
   SEQUENCE
      {
      pr1646v2MitopMultiServiceMisorderedPacketsGlobalIx
         GlobalIndex,
      pr1646v2MitopMultiServiceMisorderedPacketsValue
         Counter32
      }

pr1646v2MitopMultiServiceMisorderedPacketsGlobalIx OBJECT-TYPE
   SYNTAX      GlobalIndex
   MAX-ACCESS  not-accessible
   STATUS      current
   DESCRIPTION
      "The value of the tlsCntTreeGlobalIndex of the MANAGED OBJECT."
   ::= {pr1646v2MitopMultiServiceMisorderedPacketsEntry 10}

pr1646v2MitopMultiServiceMisorderedPacketsValue OBJECT-TYPE
   SYNTAX      Counter32
   MAX-ACCESS  read-only
   STATUS      current
   DESCRIPTION
      "Path: multiService.performance.misorderedPackets

       32 bit unsigned wrappable counter."
   ::= {pr1646v2MitopMultiServiceMisorderedPacketsEntry 2147483648}


pr1646v2MitopMultiServiceDiscardedPackets OBJECT IDENTIFIER ::= {pr1646v2MitopMultiService 56}

pr1646v2MitopMultiServiceDiscardedPacketsTable OBJECT-TYPE
   SYNTAX      SEQUENCE OF Pr1646v2MitopMultiServiceDiscardedPacketsEntry
   MAX-ACCESS  not-accessible
   STATUS      current
   DESCRIPTION
      "MiTOP pseudowire statistics"
   ::= {pr1646v2MitopMultiServiceDiscardedPackets 1}

pr1646v2MitopMultiServiceDiscardedPacketsEntry OBJECT-TYPE
   SYNTAX      Pr1646v2MitopMultiServiceDiscardedPacketsEntry
   MAX-ACCESS  not-accessible
   STATUS      current
   DESCRIPTION
      ""
   INDEX      { pr1646v2MitopMultiServiceDiscardedPacketsGlobalIx }
   ::= {pr1646v2MitopMultiServiceDiscardedPacketsTable 1}

Pr1646v2MitopMultiServiceDiscardedPacketsEntry ::=
   SEQUENCE
      {
      pr1646v2MitopMultiServiceDiscardedPacketsGlobalIx
         GlobalIndex,
      pr1646v2MitopMultiServiceDiscardedPacketsValue
         Counter32
      }

pr1646v2MitopMultiServiceDiscardedPacketsGlobalIx OBJECT-TYPE
   SYNTAX      GlobalIndex
   MAX-ACCESS  not-accessible
   STATUS      current
   DESCRIPTION
      "The value of the tlsCntTreeGlobalIndex of the MANAGED OBJECT."
   ::= {pr1646v2MitopMultiServiceDiscardedPacketsEntry 10}

pr1646v2MitopMultiServiceDiscardedPacketsValue OBJECT-TYPE
   SYNTAX      Counter32
   MAX-ACCESS  read-only
   STATUS      current
   DESCRIPTION
      "Path: multiService.performance.discardedPackets

       32 bit unsigned wrappable counter."
   ::= {pr1646v2MitopMultiServiceDiscardedPacketsEntry 2147483648}


pr1646v2MitopMultiServiceJitterBufferUnderruns OBJECT IDENTIFIER ::= {pr1646v2MitopMultiService 57}

pr1646v2MitopMultiServiceJitterBufferUnderrunsTable OBJECT-TYPE
   SYNTAX      SEQUENCE OF Pr1646v2MitopMultiServiceJitterBufferUnderrunsEntry
   MAX-ACCESS  not-accessible
   STATUS      current
   DESCRIPTION
      "MiTOP pseudowire statistics"
   ::= {pr1646v2MitopMultiServiceJitterBufferUnderruns 1}

pr1646v2MitopMultiServiceJitterBufferUnderrunsEntry OBJECT-TYPE
   SYNTAX      Pr1646v2MitopMultiServiceJitterBufferUnderrunsEntry
   MAX-ACCESS  not-accessible
   STATUS      current
   DESCRIPTION
      ""
   INDEX      { pr1646v2MitopMultiServiceJitterBufferUnderrunsGlobalIx }
   ::= {pr1646v2MitopMultiServiceJitterBufferUnderrunsTable 1}

Pr1646v2MitopMultiServiceJitterBufferUnderrunsEntry ::=
   SEQUENCE
      {
      pr1646v2MitopMultiServiceJitterBufferUnderrunsGlobalIx
         GlobalIndex,
      pr1646v2MitopMultiServiceJitterBufferUnderrunsValue
         Counter32
      }

pr1646v2MitopMultiServiceJitterBufferUnderrunsGlobalIx OBJECT-TYPE
   SYNTAX      GlobalIndex
   MAX-ACCESS  not-accessible
   STATUS      current
   DESCRIPTION
      "The value of the tlsCntTreeGlobalIndex of the MANAGED OBJECT."
   ::= {pr1646v2MitopMultiServiceJitterBufferUnderrunsEntry 10}

pr1646v2MitopMultiServiceJitterBufferUnderrunsValue OBJECT-TYPE
   SYNTAX      Counter32
   MAX-ACCESS  read-only
   STATUS      current
   DESCRIPTION
      "Path: multiService.performance.jitterBufferUnderruns

       32 bit unsigned wrappable counter."
   ::= {pr1646v2MitopMultiServiceJitterBufferUnderrunsEntry 2147483648}


pr1646v2MitopMultiServiceJitterBufferOverruns OBJECT IDENTIFIER ::= {pr1646v2MitopMultiService 58}

pr1646v2MitopMultiServiceJitterBufferOverrunsTable OBJECT-TYPE
   SYNTAX      SEQUENCE OF Pr1646v2MitopMultiServiceJitterBufferOverrunsEntry
   MAX-ACCESS  not-accessible
   STATUS      current
   DESCRIPTION
      "MiTOP pseudowire statistics"
   ::= {pr1646v2MitopMultiServiceJitterBufferOverruns 1}

pr1646v2MitopMultiServiceJitterBufferOverrunsEntry OBJECT-TYPE
   SYNTAX      Pr1646v2MitopMultiServiceJitterBufferOverrunsEntry
   MAX-ACCESS  not-accessible
   STATUS      current
   DESCRIPTION
      ""
   INDEX      { pr1646v2MitopMultiServiceJitterBufferOverrunsGlobalIx }
   ::= {pr1646v2MitopMultiServiceJitterBufferOverrunsTable 1}

Pr1646v2MitopMultiServiceJitterBufferOverrunsEntry ::=
   SEQUENCE
      {
      pr1646v2MitopMultiServiceJitterBufferOverrunsGlobalIx
         GlobalIndex,
      pr1646v2MitopMultiServiceJitterBufferOverrunsValue
         Counter32
      }

pr1646v2MitopMultiServiceJitterBufferOverrunsGlobalIx OBJECT-TYPE
   SYNTAX      GlobalIndex
   MAX-ACCESS  not-accessible
   STATUS      current
   DESCRIPTION
      "The value of the tlsCntTreeGlobalIndex of the MANAGED OBJECT."
   ::= {pr1646v2MitopMultiServiceJitterBufferOverrunsEntry 10}

pr1646v2MitopMultiServiceJitterBufferOverrunsValue OBJECT-TYPE
   SYNTAX      Counter32
   MAX-ACCESS  read-only
   STATUS      current
   DESCRIPTION
      "Path: multiService.performance.jitterBufferOverruns

       32 bit unsigned wrappable counter."
   ::= {pr1646v2MitopMultiServiceJitterBufferOverrunsEntry 2147483648}



ar1646v2MitopMultiService OBJECT IDENTIFIER ::= {r1646v2MitopMultiService 16}


ar1646v2MitopMultiServiceClearCounters OBJECT IDENTIFIER ::= {ar1646v2MitopMultiService 263}

ar1646v2MitopMultiServiceClearCountersTable OBJECT-TYPE
   SYNTAX      SEQUENCE OF Ar1646v2MitopMultiServiceClearCountersEntry
   MAX-ACCESS  not-accessible
   STATUS      current
   DESCRIPTION
      "reset counters"
   ::= {ar1646v2MitopMultiServiceClearCounters 1}

ar1646v2MitopMultiServiceClearCountersEntry OBJECT-TYPE
   SYNTAX      Ar1646v2MitopMultiServiceClearCountersEntry
   MAX-ACCESS  not-accessible
   STATUS      current
   DESCRIPTION
      ""
   INDEX      { ar1646v2MitopMultiServiceClearCountersGlobalIx }
   ::= {ar1646v2MitopMultiServiceClearCountersTable 1}

Ar1646v2MitopMultiServiceClearCountersEntry ::=
   SEQUENCE
      {
      ar1646v2MitopMultiServiceClearCountersGlobalIx
         GlobalIndex,
      ar1646v2MitopMultiServiceClearCountersValue
         Integer32
      }

ar1646v2MitopMultiServiceClearCountersGlobalIx OBJECT-TYPE
   SYNTAX      GlobalIndex
   MAX-ACCESS  not-accessible
   STATUS      current
   DESCRIPTION
      "The value of the tlsCntTreeGlobalIndex of the MANAGED OBJECT."
   ::= {ar1646v2MitopMultiServiceClearCountersEntry 10}

ar1646v2MitopMultiServiceClearCountersValue OBJECT-TYPE
   SYNTAX      Integer32
   MAX-ACCESS  read-write
   STATUS      current
   DESCRIPTION
      "Path: multiService.actions.clearCounters"
   ::= {ar1646v2MitopMultiServiceClearCountersEntry 2147483648}



END
