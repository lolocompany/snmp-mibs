OneAccess-R1646v2-4737-Lan3FG DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2Lan3FG OBJECT IDENTIFIER ::= {r1646Rootv2 4737}

r1646v2Lan3FGMOProp OBJECT IDENTIFIER ::= {r1646v2Lan3FG 1}

r1646v2Lan3FGMOPropEntry OBJECT IDENTIFIER ::= {r1646v2Lan3FGMOProp 1}

r1646v2Lan3FGMOPropPath OBJECT-TYPE
   SYNTAX      ContainmentPath
   MAX-ACCESS  read-only
   STATUS      current
   DESCRIPTION
      "Textual description of the containment tree from the instance of
       the root object down to the instance of the current object."
   ::= {r1646v2Lan3FGMOPropEntry 3}

r1646v2Lan3FGMOPropRev OBJECT-TYPE
   SYNTAX      ObjectRevision
   MAX-ACCESS  read-only
   STATUS      current
   DESCRIPTION
      "This value corresponds with the revision of the MANAGED OBJECT."
   ::= {r1646v2Lan3FGMOPropEntry 4}



er1646v2Lan3FG OBJECT IDENTIFIER ::= {r1646v2Lan3FG 11}


er1646v2Lan3FGRemark OBJECT-TYPE
   SYNTAX      DisplayString
   MAX-ACCESS  read-write
   STATUS      current
   DESCRIPTION
      "Path: ethernet3.editConf.remark
       Info: intfRemark"
   ::= {er1646v2Lan3FG 321}


er1646v2Lan3FGAdminStatus OBJECT-TYPE
   SYNTAX      INTEGER
               {
               up (1),
               down (2)
               }
   MAX-ACCESS  read-write
   STATUS      current
   DESCRIPTION
      "Path: ethernet3.editConf.adminStatus
       Info: ifAdminStatus

       Possibilities:
               up   (1)
               down   (2)"
   ::= {er1646v2Lan3FG 106}


er1646v2Lan3FGBw OBJECT IDENTIFIER ::= {er1646v2Lan3FG 5}

er1646v2Lan3FGBwSSC OBJECT IDENTIFIER ::= {er1646v2Lan3FGBw 1}

er1646v2Lan3FGBwEntry OBJECT IDENTIFIER ::= {er1646v2Lan3FGBwSSC 1}

er1646v2Lan3FGBwMode OBJECT-TYPE
   SYNTAX      INTEGER
               {
               reshaping (1),
               policing (2),
               policingReshape (3)
               }
   MAX-ACCESS  read-write
   STATUS      current
   DESCRIPTION
      "Path: ethernet3.editConf.bandwidth.mode

       Possibilities:
               reshaping   (1)
               policing   (2)
               policingReshape   (3)"
   ::= {er1646v2Lan3FGBwEntry 3758096384}

er1646v2Lan3FGBwCir OBJECT-TYPE
   SYNTAX      Integer32
   MAX-ACCESS  read-write
   STATUS      current
   DESCRIPTION
      "Path: ethernet3.editConf.bandwidth.cir"
   ::= {er1646v2Lan3FGBwEntry 268435456}

er1646v2Lan3FGBwEir OBJECT-TYPE
   SYNTAX      Integer32
   MAX-ACCESS  read-write
   STATUS      current
   DESCRIPTION
      "Path: ethernet3.editConf.bandwidth.eir"
   ::= {er1646v2Lan3FGBwEntry 1879048192}

er1646v2Lan3FGBwUnit OBJECT-TYPE
   SYNTAX      INTEGER
               {
               bitssec (1),
               percent (2)
               }
   MAX-ACCESS  read-write
   STATUS      current
   DESCRIPTION
      "Path: ethernet3.editConf.bandwidth.unit

       Possibilities:
               bits/sec   (1)
               percent   (2)"
   ::= {er1646v2Lan3FGBwEntry 1342177280}

er1646v2Lan3FGBwTc OBJECT-TYPE
   SYNTAX      INTEGER
               {
               auto (0)
               }
   MAX-ACCESS  read-write
   STATUS      current
   DESCRIPTION
      "Path: ethernet3.editConf.bandwidth.tc

       Possibilities:
               auto   (0)"
   ::= {er1646v2Lan3FGBwEntry 1610612736}

er1646v2Lan3FGBwTcFactor OBJECT-TYPE
   SYNTAX      INTEGER
               {
               ms (10),
               s100us (1)
               }
   MAX-ACCESS  read-write
   STATUS      current
   DESCRIPTION
      "Path: ethernet3.editConf.bandwidth.tcFactor

       Possibilities:
               ms   (10)
               *100us   (1)"
   ::= {er1646v2Lan3FGBwEntry 2147483648}

er1646v2Lan3FGBwCorrType OBJECT-TYPE
   SYNTAX      INTEGER
               {
               noCorrection (0),
               predefined (1),
               manual (2)
               }
   MAX-ACCESS  read-write
   STATUS      current
   DESCRIPTION
      "Path: ethernet3.editConf.bandwidth.correction.type

       Possibilities:
               noCorrection   (0)
               predefined   (1)
               manual   (2)"
   ::= {er1646v2Lan3FGBwEntry 570425344}

er1646v2Lan3FGBwCorrPredefEncapsFrameRelay OBJECT-TYPE
   SYNTAX      DisplayString
   MAX-ACCESS  read-write
   STATUS      current
   DESCRIPTION
      "Path: ethernet3.editConf.bandwidth.correction.predefined.encapsulation.frameRelay"
   ::= {er1646v2Lan3FGBwEntry 608436224}

er1646v2Lan3FGBwCorrPredefEncapsPpp OBJECT-TYPE
   SYNTAX      DisplayString
   MAX-ACCESS  read-write
   STATUS      current
   DESCRIPTION
      "Path: ethernet3.editConf.bandwidth.correction.predefined.encapsulation.ppp"
   ::= {er1646v2Lan3FGBwEntry 608698368}

er1646v2Lan3FGBwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.bandwidth.correction.predefined.encapsulation.atm.higherLayer

       Possibilities:
               rfc2684   (0)
               ppp   (1)
               pppOverEthernet   (2)"
   ::= {er1646v2Lan3FGBwEntry 608993280}

er1646v2Lan3FGBwCorrPredefEncapsAtmMp OBJECT-TYPE
   SYNTAX      INTEGER
               {
               llcEncapsulation (0),
               vcMultiplexing (1)
               }
   MAX-ACCESS  read-write
   STATUS      current
   DESCRIPTION
      "Path: ethernet3.editConf.bandwidth.correction.predefined.encapsulation.atm.multiProtocol

       Possibilities:
               llcEncapsulation   (0)
               vcMultiplexing   (1)"
   ::= {er1646v2Lan3FGBwEntry 609026048}

er1646v2Lan3FGBwCorrPredefEncapsHdlc OBJECT-TYPE
   SYNTAX      DisplayString
   MAX-ACCESS  read-write
   STATUS      current
   DESCRIPTION
      "Path: ethernet3.editConf.bandwidth.correction.predefined.encapsulation.hdlc"
   ::= {er1646v2Lan3FGBwEntry 609222656}

er1646v2Lan3FGBwCorrPredefEncapsEfmFs OBJECT-TYPE
   SYNTAX      Integer32
   MAX-ACCESS  read-write
   STATUS      current
   DESCRIPTION
      "Path: ethernet3.editConf.bandwidth.correction.predefined.encapsulation.efm.fragmentSize"
   ::= {er1646v2Lan3FGBwEntry 609517568}

er1646v2Lan3FGBwCorrPredefEncapsEfmIb OBJECT-TYPE
   SYNTAX      Integer32
   MAX-ACCESS  read-write
   STATUS      current
   DESCRIPTION
      "Path: ethernet3.editConf.bandwidth.correction.predefined.encapsulation.efm.idleBytes"
   ::= {er1646v2Lan3FGBwEntry 609550336}

er1646v2Lan3FGBwCorrPredefMode OBJECT-TYPE
   SYNTAX      INTEGER
               {
               routing (0),
               bridging (1)
               }
   MAX-ACCESS  read-write
   STATUS      current
   DESCRIPTION
      "Path: ethernet3.editConf.bandwidth.correction.predefined.mode

       Possibilities:
               routing   (0)
               bridging   (1)"
   ::= {er1646v2Lan3FGBwEntry 612368384}

er1646v2Lan3FGBwCorrManualOverhead OBJECT-TYPE
   SYNTAX      Integer32
   MAX-ACCESS  read-write
   STATUS      current
   DESCRIPTION
      "Path: ethernet3.editConf.bandwidth.correction.manual.overhead"
   ::= {er1646v2Lan3FGBwEntry 637665280}

er1646v2Lan3FGBwCorrManualFrameData OBJECT-TYPE
   SYNTAX      Counter32
   MAX-ACCESS  read-write
   STATUS      current
   DESCRIPTION
      "Path: ethernet3.editConf.bandwidth.correction.manual.frameData

       32 bit unsigned wrappable counter."
   ::= {er1646v2Lan3FGBwEntry 637796352}

er1646v2Lan3FGBwCorrManualFrameHeader OBJECT-TYPE
   SYNTAX      Counter32
   MAX-ACCESS  read-write
   STATUS      current
   DESCRIPTION
      "Path: ethernet3.editConf.bandwidth.correction.manual.frameHeader

       32 bit unsigned wrappable counter."
   ::= {er1646v2Lan3FGBwEntry 637927424}

er1646v2Lan3FGBwMaxFifoQLen OBJECT-TYPE
   SYNTAX      Integer32
   MAX-ACCESS  read-write
   STATUS      current
   DESCRIPTION
      "Path: ethernet3.editConf.bandwidth.maxFifoQLen"
   ::= {er1646v2Lan3FGBwEntry 805306368}

er1646v2Lan3FGBwDeFlagCir OBJECT-TYPE
   SYNTAX      INTEGER
               {
               allowed (1),
               notAllowed (2)
               }
   MAX-ACCESS  read-write
   STATUS      current
   DESCRIPTION
      "Path: ethernet3.editConf.bandwidth.deFlag.cir

       Possibilities:
               allowed   (1)
               notAllowed   (2)"
   ::= {er1646v2Lan3FGBwEntry 3490709504}

er1646v2Lan3FGBwDeFlagEir OBJECT-TYPE
   SYNTAX      INTEGER
               {
               allowed (1),
               notAllowed (2)
               }
   MAX-ACCESS  read-write
   STATUS      current
   DESCRIPTION
      "Path: ethernet3.editConf.bandwidth.deFlag.eir

       Possibilities:
               allowed   (1)
               notAllowed   (2)"
   ::= {er1646v2Lan3FGBwEntry 3491758080}

er1646v2Lan3FGBwDeFlagViolate OBJECT-TYPE
   SYNTAX      INTEGER
               {
               allowed (1),
               notAllowed (2)
               }
   MAX-ACCESS  read-write
   STATUS      current
   DESCRIPTION
      "Path: ethernet3.editConf.bandwidth.deFlag.violate

       Possibilities:
               allowed   (1)
               notAllowed   (2)"
   ::= {er1646v2Lan3FGBwEntry 3492806656}

er1646v2Lan3FGBwActCirActNone OBJECT-TYPE
   SYNTAX      OCTET STRING
   MAX-ACCESS  read-write
   STATUS      current
   DESCRIPTION
      "Path: ethernet3.editConf.bandwidth.action.cirAction.none"
   ::= {er1646v2Lan3FGBwEntry 4062183424}

er1646v2Lan3FGBwActCirActEthCos1 OBJECT-TYPE
   SYNTAX      INTEGER
               {
               unchanged (256)
               }
   MAX-ACCESS  read-write
   STATUS      current
   DESCRIPTION
      "Path: ethernet3.editConf.bandwidth.action.cirAction.ethernet.cosDepth1

       Possibilities:
               unchanged   (256)"
   ::= {er1646v2Lan3FGBwEntry 4064346112}

er1646v2Lan3FGBwActCirActEthDei1 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth1

       Possibilities:
               unchanged   (255)
               clear   (0)
               set   (1)"
   ::= {er1646v2Lan3FGBwEntry 4065656832}

er1646v2Lan3FGBwActCirActEthCos2 OBJECT-TYPE
   SYNTAX      INTEGER
               {
               unchanged (256)
               }
   MAX-ACCESS  read-write
   STATUS      current
   DESCRIPTION
      "Path: ethernet3.editConf.bandwidth.action.cirAction.ethernet.cosDepth2

       Possibilities:
               unchanged   (256)"
   ::= {er1646v2Lan3FGBwEntry 4064411648}

er1646v2Lan3FGBwActCirActEthDei2 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth2

       Possibilities:
               unchanged   (255)
               clear   (0)
               set   (1)"
   ::= {er1646v2Lan3FGBwEntry 4065722368}

er1646v2Lan3FGBwActCirActEthCos3 OBJECT-TYPE
   SYNTAX      INTEGER
               {
               unchanged (256)
               }
   MAX-ACCESS  read-write
   STATUS      current
   DESCRIPTION
      "Path: ethernet3.editConf.bandwidth.action.cirAction.ethernet.cosDepth3

       Possibilities:
               unchanged   (256)"
   ::= {er1646v2Lan3FGBwEntry 4064477184}

er1646v2Lan3FGBwActCirActEthDei3 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth3

       Possibilities:
               unchanged   (255)
               clear   (0)
               set   (1)"
   ::= {er1646v2Lan3FGBwEntry 4065787904}

er1646v2Lan3FGBwActCirActEthCos4 OBJECT-TYPE
   SYNTAX      INTEGER
               {
               unchanged (256)
               }
   MAX-ACCESS  read-write
   STATUS      current
   DESCRIPTION
      "Path: ethernet3.editConf.bandwidth.action.cirAction.ethernet.cosDepth4

       Possibilities:
               unchanged   (256)"
   ::= {er1646v2Lan3FGBwEntry 4064542720}

er1646v2Lan3FGBwActCirActEthDei4 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth4

       Possibilities:
               unchanged   (255)
               clear   (0)
               set   (1)"
   ::= {er1646v2Lan3FGBwEntry 4065853440}

er1646v2Lan3FGBwActCirActEthCos5 OBJECT-TYPE
   SYNTAX      INTEGER
               {
               unchanged (256)
               }
   MAX-ACCESS  read-write
   STATUS      current
   DESCRIPTION
      "Path: ethernet3.editConf.bandwidth.action.cirAction.ethernet.cosDepth5

       Possibilities:
               unchanged   (256)"
   ::= {er1646v2Lan3FGBwEntry 4064608256}

er1646v2Lan3FGBwActCirActEthDei5 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth5

       Possibilities:
               unchanged   (255)
               clear   (0)
               set   (1)"
   ::= {er1646v2Lan3FGBwEntry 4065918976}

er1646v2Lan3FGBwActCirActEthCos6 OBJECT-TYPE
   SYNTAX      INTEGER
               {
               unchanged (256)
               }
   MAX-ACCESS  read-write
   STATUS      current
   DESCRIPTION
      "Path: ethernet3.editConf.bandwidth.action.cirAction.ethernet.cosDepth6

       Possibilities:
               unchanged   (256)"
   ::= {er1646v2Lan3FGBwEntry 4064673792}

er1646v2Lan3FGBwActCirActEthDei6 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth6

       Possibilities:
               unchanged   (255)
               clear   (0)
               set   (1)"
   ::= {er1646v2Lan3FGBwEntry 4065984512}

er1646v2Lan3FGBwActCirActEthCos7 OBJECT-TYPE
   SYNTAX      INTEGER
               {
               unchanged (256)
               }
   MAX-ACCESS  read-write
   STATUS      current
   DESCRIPTION
      "Path: ethernet3.editConf.bandwidth.action.cirAction.ethernet.cosDepth7

       Possibilities:
               unchanged   (256)"
   ::= {er1646v2Lan3FGBwEntry 4064739328}

er1646v2Lan3FGBwActCirActEthDei7 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth7

       Possibilities:
               unchanged   (255)
               clear   (0)
               set   (1)"
   ::= {er1646v2Lan3FGBwEntry 4066050048}

er1646v2Lan3FGBwActCirActEthCos8 OBJECT-TYPE
   SYNTAX      INTEGER
               {
               unchanged (256)
               }
   MAX-ACCESS  read-write
   STATUS      current
   DESCRIPTION
      "Path: ethernet3.editConf.bandwidth.action.cirAction.ethernet.cosDepth8

       Possibilities:
               unchanged   (256)"
   ::= {er1646v2Lan3FGBwEntry 4064804864}

er1646v2Lan3FGBwActCirActEthDei8 OBJECT-TYPE
   SYNTAX      INTEGER
               {
               unchanged (255),
               clear (0),
               set (1)
               }
   MAX-ACCESS  read-write
   STATUS      current
   DESCRIPTION
      "Path: ethernet3.editConf.bandwidth.action.cirAction.ethernet.deiDepth8

       Possibilities:
               unchanged   (255)
               clear   (0)
               set   (1)"
   ::= {er1646v2Lan3FGBwEntry 4066115584}

er1646v2Lan3FGBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGBwEntry 4064870400}

er1646v2Lan3FGBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGBwEntry 4064935936}

er1646v2Lan3FGBwActCirActEthDrpLev OBJECT-TYPE
   SYNTAX      INTEGER
               {
               unchanged (0)
               }
   MAX-ACCESS  read-write
   STATUS      current
   DESCRIPTION
      "Path: ethernet3.editConf.bandwidth.action.cirAction.ethernet.dropLevel

       Possibilities:
               unchanged   (0)"
   ::= {er1646v2Lan3FGBwEntry 4065001472}

er1646v2Lan3FGBwActCirActEthDeFlag OBJECT-TYPE
   SYNTAX      INTEGER
               {
               unchanged (255),
               clear (0),
               set (1)
               }
   MAX-ACCESS  read-write
   STATUS      current
   DESCRIPTION
      "Path: ethernet3.editConf.bandwidth.action.cirAction.ethernet.deFlag

       Possibilities:
               unchanged   (255)
               clear   (0)
               set   (1)"
   ::= {er1646v2Lan3FGBwEntry 4065198080}

er1646v2Lan3FGBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGBwEntry 4071161856}

er1646v2Lan3FGBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGBwEntry 4071227392}

er1646v2Lan3FGBwActCirActIpDrpLev OBJECT-TYPE
   SYNTAX      INTEGER
               {
               unchanged (0)
               }
   MAX-ACCESS  read-write
   STATUS      current
   DESCRIPTION
      "Path: ethernet3.editConf.bandwidth.action.cirAction.ip.dropLevel

       Possibilities:
               unchanged   (0)"
   ::= {er1646v2Lan3FGBwEntry 4071292928}

er1646v2Lan3FGBwActCirActIpDeFlag OBJECT-TYPE
   SYNTAX      INTEGER
               {
               unchanged (255),
               clear (0),
               set (1)
               }
   MAX-ACCESS  read-write
   STATUS      current
   DESCRIPTION
      "Path: ethernet3.editConf.bandwidth.action.cirAction.ip.deFlag

       Possibilities:
               unchanged   (255)
               clear   (0)
               set   (1)"
   ::= {er1646v2Lan3FGBwEntry 4071489536}

er1646v2Lan3FGBwActEirActNone OBJECT-TYPE
   SYNTAX      OCTET STRING
   MAX-ACCESS  read-write
   STATUS      current
   DESCRIPTION
      "Path: ethernet3.editConf.bandwidth.action.eirAction.none"
   ::= {er1646v2Lan3FGBwEntry 4095737856}

er1646v2Lan3FGBwActEirActEthCos1 OBJECT-TYPE
   SYNTAX      INTEGER
               {
               unchanged (256)
               }
   MAX-ACCESS  read-write
   STATUS      current
   DESCRIPTION
      "Path: ethernet3.editConf.bandwidth.action.eirAction.ethernet.cosDepth1

       Possibilities:
               unchanged   (256)"
   ::= {er1646v2Lan3FGBwEntry 4097900544}

er1646v2Lan3FGBwActEirActEthDei1 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth1

       Possibilities:
               unchanged   (255)
               clear   (0)
               set   (1)"
   ::= {er1646v2Lan3FGBwEntry 4099211264}

er1646v2Lan3FGBwActEirActEthCos2 OBJECT-TYPE
   SYNTAX      INTEGER
               {
               unchanged (256)
               }
   MAX-ACCESS  read-write
   STATUS      current
   DESCRIPTION
      "Path: ethernet3.editConf.bandwidth.action.eirAction.ethernet.cosDepth2

       Possibilities:
               unchanged   (256)"
   ::= {er1646v2Lan3FGBwEntry 4097966080}

er1646v2Lan3FGBwActEirActEthDei2 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth2

       Possibilities:
               unchanged   (255)
               clear   (0)
               set   (1)"
   ::= {er1646v2Lan3FGBwEntry 4099276800}

er1646v2Lan3FGBwActEirActEthCos3 OBJECT-TYPE
   SYNTAX      INTEGER
               {
               unchanged (256)
               }
   MAX-ACCESS  read-write
   STATUS      current
   DESCRIPTION
      "Path: ethernet3.editConf.bandwidth.action.eirAction.ethernet.cosDepth3

       Possibilities:
               unchanged   (256)"
   ::= {er1646v2Lan3FGBwEntry 4098031616}

er1646v2Lan3FGBwActEirActEthDei3 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth3

       Possibilities:
               unchanged   (255)
               clear   (0)
               set   (1)"
   ::= {er1646v2Lan3FGBwEntry 4099342336}

er1646v2Lan3FGBwActEirActEthCos4 OBJECT-TYPE
   SYNTAX      INTEGER
               {
               unchanged (256)
               }
   MAX-ACCESS  read-write
   STATUS      current
   DESCRIPTION
      "Path: ethernet3.editConf.bandwidth.action.eirAction.ethernet.cosDepth4

       Possibilities:
               unchanged   (256)"
   ::= {er1646v2Lan3FGBwEntry 4098097152}

er1646v2Lan3FGBwActEirActEthDei4 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth4

       Possibilities:
               unchanged   (255)
               clear   (0)
               set   (1)"
   ::= {er1646v2Lan3FGBwEntry 4099407872}

er1646v2Lan3FGBwActEirActEthCos5 OBJECT-TYPE
   SYNTAX      INTEGER
               {
               unchanged (256)
               }
   MAX-ACCESS  read-write
   STATUS      current
   DESCRIPTION
      "Path: ethernet3.editConf.bandwidth.action.eirAction.ethernet.cosDepth5

       Possibilities:
               unchanged   (256)"
   ::= {er1646v2Lan3FGBwEntry 4098162688}

er1646v2Lan3FGBwActEirActEthDei5 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth5

       Possibilities:
               unchanged   (255)
               clear   (0)
               set   (1)"
   ::= {er1646v2Lan3FGBwEntry 4099473408}

er1646v2Lan3FGBwActEirActEthCos6 OBJECT-TYPE
   SYNTAX      INTEGER
               {
               unchanged (256)
               }
   MAX-ACCESS  read-write
   STATUS      current
   DESCRIPTION
      "Path: ethernet3.editConf.bandwidth.action.eirAction.ethernet.cosDepth6

       Possibilities:
               unchanged   (256)"
   ::= {er1646v2Lan3FGBwEntry 4098228224}

er1646v2Lan3FGBwActEirActEthDei6 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth6

       Possibilities:
               unchanged   (255)
               clear   (0)
               set   (1)"
   ::= {er1646v2Lan3FGBwEntry 4099538944}

er1646v2Lan3FGBwActEirActEthCos7 OBJECT-TYPE
   SYNTAX      INTEGER
               {
               unchanged (256)
               }
   MAX-ACCESS  read-write
   STATUS      current
   DESCRIPTION
      "Path: ethernet3.editConf.bandwidth.action.eirAction.ethernet.cosDepth7

       Possibilities:
               unchanged   (256)"
   ::= {er1646v2Lan3FGBwEntry 4098293760}

er1646v2Lan3FGBwActEirActEthDei7 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth7

       Possibilities:
               unchanged   (255)
               clear   (0)
               set   (1)"
   ::= {er1646v2Lan3FGBwEntry 4099604480}

er1646v2Lan3FGBwActEirActEthCos8 OBJECT-TYPE
   SYNTAX      INTEGER
               {
               unchanged (256)
               }
   MAX-ACCESS  read-write
   STATUS      current
   DESCRIPTION
      "Path: ethernet3.editConf.bandwidth.action.eirAction.ethernet.cosDepth8

       Possibilities:
               unchanged   (256)"
   ::= {er1646v2Lan3FGBwEntry 4098359296}

er1646v2Lan3FGBwActEirActEthDei8 OBJECT-TYPE
   SYNTAX      INTEGER
               {
               unchanged (255),
               clear (0),
               set (1)
               }
   MAX-ACCESS  read-write
   STATUS      current
   DESCRIPTION
      "Path: ethernet3.editConf.bandwidth.action.eirAction.ethernet.deiDepth8

       Possibilities:
               unchanged   (255)
               clear   (0)
               set   (1)"
   ::= {er1646v2Lan3FGBwEntry 4099670016}

er1646v2Lan3FGBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGBwEntry 4098424832}

er1646v2Lan3FGBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGBwEntry 4098490368}

er1646v2Lan3FGBwActEirActEthDrpLev OBJECT-TYPE
   SYNTAX      INTEGER
               {
               unchanged (0)
               }
   MAX-ACCESS  read-write
   STATUS      current
   DESCRIPTION
      "Path: ethernet3.editConf.bandwidth.action.eirAction.ethernet.dropLevel

       Possibilities:
               unchanged   (0)"
   ::= {er1646v2Lan3FGBwEntry 4098555904}

er1646v2Lan3FGBwActEirActEthDeFlag OBJECT-TYPE
   SYNTAX      INTEGER
               {
               unchanged (255),
               clear (0),
               set (1)
               }
   MAX-ACCESS  read-write
   STATUS      current
   DESCRIPTION
      "Path: ethernet3.editConf.bandwidth.action.eirAction.ethernet.deFlag

       Possibilities:
               unchanged   (255)
               clear   (0)
               set   (1)"
   ::= {er1646v2Lan3FGBwEntry 4098752512}

er1646v2Lan3FGBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGBwEntry 4104716288}

er1646v2Lan3FGBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGBwEntry 4104781824}

er1646v2Lan3FGBwActEirActIpDrpLev OBJECT-TYPE
   SYNTAX      INTEGER
               {
               unchanged (0)
               }
   MAX-ACCESS  read-write
   STATUS      current
   DESCRIPTION
      "Path: ethernet3.editConf.bandwidth.action.eirAction.ip.dropLevel

       Possibilities:
               unchanged   (0)"
   ::= {er1646v2Lan3FGBwEntry 4104847360}

er1646v2Lan3FGBwActEirActIpDeFlag OBJECT-TYPE
   SYNTAX      INTEGER
               {
               unchanged (255),
               clear (0),
               set (1)
               }
   MAX-ACCESS  read-write
   STATUS      current
   DESCRIPTION
      "Path: ethernet3.editConf.bandwidth.action.eirAction.ip.deFlag

       Possibilities:
               unchanged   (255)
               clear   (0)
               set   (1)"
   ::= {er1646v2Lan3FGBwEntry 4105043968}

er1646v2Lan3FGBwActViolActNone OBJECT-TYPE
   SYNTAX      OCTET STRING
   MAX-ACCESS  read-write
   STATUS      current
   DESCRIPTION
      "Path: ethernet3.editConf.bandwidth.action.violateAction.none"
   ::= {er1646v2Lan3FGBwEntry 4129292288}

er1646v2Lan3FGBwActViolActDrop OBJECT-TYPE
   SYNTAX      OCTET STRING
   MAX-ACCESS  read-write
   STATUS      current
   DESCRIPTION
      "Path: ethernet3.editConf.bandwidth.action.violateAction.drop"
   ::= {er1646v2Lan3FGBwEntry 4133486592}

er1646v2Lan3FGBwActViolActEthCos1 OBJECT-TYPE
   SYNTAX      INTEGER
               {
               unchanged (256)
               }
   MAX-ACCESS  read-write
   STATUS      current
   DESCRIPTION
      "Path: ethernet3.editConf.bandwidth.action.violateAction.ethernet.cosDepth1

       Possibilities:
               unchanged   (256)"
   ::= {er1646v2Lan3FGBwEntry 4131454976}

er1646v2Lan3FGBwActViolActEthDei1 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth1

       Possibilities:
               unchanged   (255)
               clear   (0)
               set   (1)"
   ::= {er1646v2Lan3FGBwEntry 4132765696}

er1646v2Lan3FGBwActViolActEthCos2 OBJECT-TYPE
   SYNTAX      INTEGER
               {
               unchanged (256)
               }
   MAX-ACCESS  read-write
   STATUS      current
   DESCRIPTION
      "Path: ethernet3.editConf.bandwidth.action.violateAction.ethernet.cosDepth2

       Possibilities:
               unchanged   (256)"
   ::= {er1646v2Lan3FGBwEntry 4131520512}

er1646v2Lan3FGBwActViolActEthDei2 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth2

       Possibilities:
               unchanged   (255)
               clear   (0)
               set   (1)"
   ::= {er1646v2Lan3FGBwEntry 4132831232}

er1646v2Lan3FGBwActViolActEthCos3 OBJECT-TYPE
   SYNTAX      INTEGER
               {
               unchanged (256)
               }
   MAX-ACCESS  read-write
   STATUS      current
   DESCRIPTION
      "Path: ethernet3.editConf.bandwidth.action.violateAction.ethernet.cosDepth3

       Possibilities:
               unchanged   (256)"
   ::= {er1646v2Lan3FGBwEntry 4131586048}

er1646v2Lan3FGBwActViolActEthDei3 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth3

       Possibilities:
               unchanged   (255)
               clear   (0)
               set   (1)"
   ::= {er1646v2Lan3FGBwEntry 4132896768}

er1646v2Lan3FGBwActViolActEthCos4 OBJECT-TYPE
   SYNTAX      INTEGER
               {
               unchanged (256)
               }
   MAX-ACCESS  read-write
   STATUS      current
   DESCRIPTION
      "Path: ethernet3.editConf.bandwidth.action.violateAction.ethernet.cosDepth4

       Possibilities:
               unchanged   (256)"
   ::= {er1646v2Lan3FGBwEntry 4131651584}

er1646v2Lan3FGBwActViolActEthDei4 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth4

       Possibilities:
               unchanged   (255)
               clear   (0)
               set   (1)"
   ::= {er1646v2Lan3FGBwEntry 4132962304}

er1646v2Lan3FGBwActViolActEthCos5 OBJECT-TYPE
   SYNTAX      INTEGER
               {
               unchanged (256)
               }
   MAX-ACCESS  read-write
   STATUS      current
   DESCRIPTION
      "Path: ethernet3.editConf.bandwidth.action.violateAction.ethernet.cosDepth5

       Possibilities:
               unchanged   (256)"
   ::= {er1646v2Lan3FGBwEntry 4131717120}

er1646v2Lan3FGBwActViolActEthDei5 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth5

       Possibilities:
               unchanged   (255)
               clear   (0)
               set   (1)"
   ::= {er1646v2Lan3FGBwEntry 4133027840}

er1646v2Lan3FGBwActViolActEthCos6 OBJECT-TYPE
   SYNTAX      INTEGER
               {
               unchanged (256)
               }
   MAX-ACCESS  read-write
   STATUS      current
   DESCRIPTION
      "Path: ethernet3.editConf.bandwidth.action.violateAction.ethernet.cosDepth6

       Possibilities:
               unchanged   (256)"
   ::= {er1646v2Lan3FGBwEntry 4131782656}

er1646v2Lan3FGBwActViolActEthDei6 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth6

       Possibilities:
               unchanged   (255)
               clear   (0)
               set   (1)"
   ::= {er1646v2Lan3FGBwEntry 4133093376}

er1646v2Lan3FGBwActViolActEthCos7 OBJECT-TYPE
   SYNTAX      INTEGER
               {
               unchanged (256)
               }
   MAX-ACCESS  read-write
   STATUS      current
   DESCRIPTION
      "Path: ethernet3.editConf.bandwidth.action.violateAction.ethernet.cosDepth7

       Possibilities:
               unchanged   (256)"
   ::= {er1646v2Lan3FGBwEntry 4131848192}

er1646v2Lan3FGBwActViolActEthDei7 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth7

       Possibilities:
               unchanged   (255)
               clear   (0)
               set   (1)"
   ::= {er1646v2Lan3FGBwEntry 4133158912}

er1646v2Lan3FGBwActViolActEthCos8 OBJECT-TYPE
   SYNTAX      INTEGER
               {
               unchanged (256)
               }
   MAX-ACCESS  read-write
   STATUS      current
   DESCRIPTION
      "Path: ethernet3.editConf.bandwidth.action.violateAction.ethernet.cosDepth8

       Possibilities:
               unchanged   (256)"
   ::= {er1646v2Lan3FGBwEntry 4131913728}

er1646v2Lan3FGBwActViolActEthDei8 OBJECT-TYPE
   SYNTAX      INTEGER
               {
               unchanged (255),
               clear (0),
               set (1)
               }
   MAX-ACCESS  read-write
   STATUS      current
   DESCRIPTION
      "Path: ethernet3.editConf.bandwidth.action.violateAction.ethernet.deiDepth8

       Possibilities:
               unchanged   (255)
               clear   (0)
               set   (1)"
   ::= {er1646v2Lan3FGBwEntry 4133224448}

er1646v2Lan3FGBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGBwEntry 4131979264}

er1646v2Lan3FGBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGBwEntry 4132044800}

er1646v2Lan3FGBwActViolActEthDrpLev OBJECT-TYPE
   SYNTAX      INTEGER
               {
               unchanged (0)
               }
   MAX-ACCESS  read-write
   STATUS      current
   DESCRIPTION
      "Path: ethernet3.editConf.bandwidth.action.violateAction.ethernet.dropLevel

       Possibilities:
               unchanged   (0)"
   ::= {er1646v2Lan3FGBwEntry 4132110336}

er1646v2Lan3FGBwActViolActEthDeFlag OBJECT-TYPE
   SYNTAX      INTEGER
               {
               unchanged (255),
               clear (0),
               set (1)
               }
   MAX-ACCESS  read-write
   STATUS      current
   DESCRIPTION
      "Path: ethernet3.editConf.bandwidth.action.violateAction.ethernet.deFlag

       Possibilities:
               unchanged   (255)
               clear   (0)
               set   (1)"
   ::= {er1646v2Lan3FGBwEntry 4132306944}

er1646v2Lan3FGBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGBwEntry 4138270720}

er1646v2Lan3FGBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGBwEntry 4138336256}

er1646v2Lan3FGBwActViolActIpDrpLev OBJECT-TYPE
   SYNTAX      INTEGER
               {
               unchanged (0)
               }
   MAX-ACCESS  read-write
   STATUS      current
   DESCRIPTION
      "Path: ethernet3.editConf.bandwidth.action.violateAction.ip.dropLevel

       Possibilities:
               unchanged   (0)"
   ::= {er1646v2Lan3FGBwEntry 4138401792}

er1646v2Lan3FGBwActViolActIpDeFlag OBJECT-TYPE
   SYNTAX      INTEGER
               {
               unchanged (255),
               clear (0),
               set (1)
               }
   MAX-ACCESS  read-write
   STATUS      current
   DESCRIPTION
      "Path: ethernet3.editConf.bandwidth.action.violateAction.ip.deFlag

       Possibilities:
               unchanged   (255)
               clear   (0)
               set   (1)"
   ::= {er1646v2Lan3FGBwEntry 4138598400}


er1646v2Lan3FGIbw OBJECT IDENTIFIER ::= {er1646v2Lan3FG 13}

er1646v2Lan3FGIbwSSC OBJECT IDENTIFIER ::= {er1646v2Lan3FGIbw 1}

er1646v2Lan3FGIbwEntry OBJECT IDENTIFIER ::= {er1646v2Lan3FGIbwSSC 1}

er1646v2Lan3FGIbwMode OBJECT-TYPE
   SYNTAX      INTEGER
               {
               reshaping (1),
               policing (2)
               }
   MAX-ACCESS  read-write
   STATUS      current
   DESCRIPTION
      "Path: ethernet3.editConf.inboundBandwidth.mode

       Possibilities:
               reshaping   (1)
               policing   (2)"
   ::= {er1646v2Lan3FGIbwEntry 3758096384}

er1646v2Lan3FGIbwCir OBJECT-TYPE
   SYNTAX      Integer32
   MAX-ACCESS  read-write
   STATUS      current
   DESCRIPTION
      "Path: ethernet3.editConf.inboundBandwidth.cir"
   ::= {er1646v2Lan3FGIbwEntry 268435456}

er1646v2Lan3FGIbwEir OBJECT-TYPE
   SYNTAX      Integer32
   MAX-ACCESS  read-write
   STATUS      current
   DESCRIPTION
      "Path: ethernet3.editConf.inboundBandwidth.eir"
   ::= {er1646v2Lan3FGIbwEntry 1879048192}

er1646v2Lan3FGIbwUnit OBJECT-TYPE
   SYNTAX      INTEGER
               {
               bitssec (1),
               percent (2)
               }
   MAX-ACCESS  read-write
   STATUS      current
   DESCRIPTION
      "Path: ethernet3.editConf.inboundBandwidth.unit

       Possibilities:
               bits/sec   (1)
               percent   (2)"
   ::= {er1646v2Lan3FGIbwEntry 1342177280}

er1646v2Lan3FGIbwTc OBJECT-TYPE
   SYNTAX      INTEGER
               {
               auto (0)
               }
   MAX-ACCESS  read-write
   STATUS      current
   DESCRIPTION
      "Path: ethernet3.editConf.inboundBandwidth.tc

       Possibilities:
               auto   (0)"
   ::= {er1646v2Lan3FGIbwEntry 1610612736}

er1646v2Lan3FGIbwTcFactor OBJECT-TYPE
   SYNTAX      INTEGER
               {
               ms (10),
               s100us (1)
               }
   MAX-ACCESS  read-write
   STATUS      current
   DESCRIPTION
      "Path: ethernet3.editConf.inboundBandwidth.tcFactor

       Possibilities:
               ms   (10)
               *100us   (1)"
   ::= {er1646v2Lan3FGIbwEntry 2147483648}

er1646v2Lan3FGIbwCorrType OBJECT-TYPE
   SYNTAX      INTEGER
               {
               noCorrection (0),
               predefined (1),
               manual (2)
               }
   MAX-ACCESS  read-write
   STATUS      current
   DESCRIPTION
      "Path: ethernet3.editConf.inboundBandwidth.correction.type

       Possibilities:
               noCorrection   (0)
               predefined   (1)
               manual   (2)"
   ::= {er1646v2Lan3FGIbwEntry 570425344}

er1646v2Lan3FGIbwCorrPredefEncapsFrameRelay OBJECT-TYPE
   SYNTAX      DisplayString
   MAX-ACCESS  read-write
   STATUS      current
   DESCRIPTION
      "Path: ethernet3.editConf.inboundBandwidth.correction.predefined.encapsulation.frameRelay"
   ::= {er1646v2Lan3FGIbwEntry 608436224}

er1646v2Lan3FGIbwCorrPredefEncapsPpp OBJECT-TYPE
   SYNTAX      DisplayString
   MAX-ACCESS  read-write
   STATUS      current
   DESCRIPTION
      "Path: ethernet3.editConf.inboundBandwidth.correction.predefined.encapsulation.ppp"
   ::= {er1646v2Lan3FGIbwEntry 608698368}

er1646v2Lan3FGIbwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.inboundBandwidth.correction.predefined.encapsulation.atm.higherLayer

       Possibilities:
               rfc2684   (0)
               ppp   (1)
               pppOverEthernet   (2)"
   ::= {er1646v2Lan3FGIbwEntry 608993280}

er1646v2Lan3FGIbwCorrPredefEncapsAtmMp OBJECT-TYPE
   SYNTAX      INTEGER
               {
               llcEncapsulation (0),
               vcMultiplexing (1)
               }
   MAX-ACCESS  read-write
   STATUS      current
   DESCRIPTION
      "Path: ethernet3.editConf.inboundBandwidth.correction.predefined.encapsulation.atm.multiProtocol

       Possibilities:
               llcEncapsulation   (0)
               vcMultiplexing   (1)"
   ::= {er1646v2Lan3FGIbwEntry 609026048}

er1646v2Lan3FGIbwCorrPredefEncapsHdlc OBJECT-TYPE
   SYNTAX      DisplayString
   MAX-ACCESS  read-write
   STATUS      current
   DESCRIPTION
      "Path: ethernet3.editConf.inboundBandwidth.correction.predefined.encapsulation.hdlc"
   ::= {er1646v2Lan3FGIbwEntry 609222656}

er1646v2Lan3FGIbwCorrPredefEncapsEfmFs OBJECT-TYPE
   SYNTAX      Integer32
   MAX-ACCESS  read-write
   STATUS      current
   DESCRIPTION
      "Path: ethernet3.editConf.inboundBandwidth.correction.predefined.encapsulation.efm.fragmentSize"
   ::= {er1646v2Lan3FGIbwEntry 609517568}

er1646v2Lan3FGIbwCorrPredefEncapsEfmIb OBJECT-TYPE
   SYNTAX      Integer32
   MAX-ACCESS  read-write
   STATUS      current
   DESCRIPTION
      "Path: ethernet3.editConf.inboundBandwidth.correction.predefined.encapsulation.efm.idleBytes"
   ::= {er1646v2Lan3FGIbwEntry 609550336}

er1646v2Lan3FGIbwCorrPredefMode OBJECT-TYPE
   SYNTAX      INTEGER
               {
               routing (0),
               bridging (1)
               }
   MAX-ACCESS  read-write
   STATUS      current
   DESCRIPTION
      "Path: ethernet3.editConf.inboundBandwidth.correction.predefined.mode

       Possibilities:
               routing   (0)
               bridging   (1)"
   ::= {er1646v2Lan3FGIbwEntry 612368384}

er1646v2Lan3FGIbwCorrManualOverhead OBJECT-TYPE
   SYNTAX      Integer32
   MAX-ACCESS  read-write
   STATUS      current
   DESCRIPTION
      "Path: ethernet3.editConf.inboundBandwidth.correction.manual.overhead"
   ::= {er1646v2Lan3FGIbwEntry 637665280}

er1646v2Lan3FGIbwCorrManualFrameData OBJECT-TYPE
   SYNTAX      Counter32
   MAX-ACCESS  read-write
   STATUS      current
   DESCRIPTION
      "Path: ethernet3.editConf.inboundBandwidth.correction.manual.frameData

       32 bit unsigned wrappable counter."
   ::= {er1646v2Lan3FGIbwEntry 637796352}

er1646v2Lan3FGIbwCorrManualFrameHeader OBJECT-TYPE
   SYNTAX      Counter32
   MAX-ACCESS  read-write
   STATUS      current
   DESCRIPTION
      "Path: ethernet3.editConf.inboundBandwidth.correction.manual.frameHeader

       32 bit unsigned wrappable counter."
   ::= {er1646v2Lan3FGIbwEntry 637927424}

er1646v2Lan3FGIbwMaxFifoQLen OBJECT-TYPE
   SYNTAX      Integer32
   MAX-ACCESS  read-write
   STATUS      current
   DESCRIPTION
      "Path: ethernet3.editConf.inboundBandwidth.maxFifoQLen"
   ::= {er1646v2Lan3FGIbwEntry 805306368}

er1646v2Lan3FGIbwPriorityPolicy OBJECT-TYPE
   SYNTAX      DisplayString
   MAX-ACCESS  read-write
   STATUS      current
   DESCRIPTION
      "Path: ethernet3.editConf.inboundBandwidth.priorityPolicy"
   ::= {er1646v2Lan3FGIbwEntry 1073741824}

er1646v2Lan3FGIbwDeFlagCir OBJECT-TYPE
   SYNTAX      INTEGER
               {
               allowed (1),
               notAllowed (2)
               }
   MAX-ACCESS  read-write
   STATUS      current
   DESCRIPTION
      "Path: ethernet3.editConf.inboundBandwidth.deFlag.cir

       Possibilities:
               allowed   (1)
               notAllowed   (2)"
   ::= {er1646v2Lan3FGIbwEntry 3490709504}

er1646v2Lan3FGIbwDeFlagEir OBJECT-TYPE
   SYNTAX      INTEGER
               {
               allowed (1),
               notAllowed (2)
               }
   MAX-ACCESS  read-write
   STATUS      current
   DESCRIPTION
      "Path: ethernet3.editConf.inboundBandwidth.deFlag.eir

       Possibilities:
               allowed   (1)
               notAllowed   (2)"
   ::= {er1646v2Lan3FGIbwEntry 3491758080}

er1646v2Lan3FGIbwDeFlagViolate OBJECT-TYPE
   SYNTAX      INTEGER
               {
               allowed (1),
               notAllowed (2)
               }
   MAX-ACCESS  read-write
   STATUS      current
   DESCRIPTION
      "Path: ethernet3.editConf.inboundBandwidth.deFlag.violate

       Possibilities:
               allowed   (1)
               notAllowed   (2)"
   ::= {er1646v2Lan3FGIbwEntry 3492806656}

er1646v2Lan3FGIbwActCirActNone OBJECT-TYPE
   SYNTAX      OCTET STRING
   MAX-ACCESS  read-write
   STATUS      current
   DESCRIPTION
      "Path: ethernet3.editConf.inboundBandwidth.action.cirAction.none"
   ::= {er1646v2Lan3FGIbwEntry 4062183424}

er1646v2Lan3FGIbwActCirActEthCos1 OBJECT-TYPE
   SYNTAX      INTEGER
               {
               unchanged (256)
               }
   MAX-ACCESS  read-write
   STATUS      current
   DESCRIPTION
      "Path: ethernet3.editConf.inboundBandwidth.action.cirAction.ethernet.cosDepth1

       Possibilities:
               unchanged   (256)"
   ::= {er1646v2Lan3FGIbwEntry 4064346112}

er1646v2Lan3FGIbwActCirActEthDei1 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth1

       Possibilities:
               unchanged   (255)
               clear   (0)
               set   (1)"
   ::= {er1646v2Lan3FGIbwEntry 4065656832}

er1646v2Lan3FGIbwActCirActEthCos2 OBJECT-TYPE
   SYNTAX      INTEGER
               {
               unchanged (256)
               }
   MAX-ACCESS  read-write
   STATUS      current
   DESCRIPTION
      "Path: ethernet3.editConf.inboundBandwidth.action.cirAction.ethernet.cosDepth2

       Possibilities:
               unchanged   (256)"
   ::= {er1646v2Lan3FGIbwEntry 4064411648}

er1646v2Lan3FGIbwActCirActEthDei2 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth2

       Possibilities:
               unchanged   (255)
               clear   (0)
               set   (1)"
   ::= {er1646v2Lan3FGIbwEntry 4065722368}

er1646v2Lan3FGIbwActCirActEthCos3 OBJECT-TYPE
   SYNTAX      INTEGER
               {
               unchanged (256)
               }
   MAX-ACCESS  read-write
   STATUS      current
   DESCRIPTION
      "Path: ethernet3.editConf.inboundBandwidth.action.cirAction.ethernet.cosDepth3

       Possibilities:
               unchanged   (256)"
   ::= {er1646v2Lan3FGIbwEntry 4064477184}

er1646v2Lan3FGIbwActCirActEthDei3 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth3

       Possibilities:
               unchanged   (255)
               clear   (0)
               set   (1)"
   ::= {er1646v2Lan3FGIbwEntry 4065787904}

er1646v2Lan3FGIbwActCirActEthCos4 OBJECT-TYPE
   SYNTAX      INTEGER
               {
               unchanged (256)
               }
   MAX-ACCESS  read-write
   STATUS      current
   DESCRIPTION
      "Path: ethernet3.editConf.inboundBandwidth.action.cirAction.ethernet.cosDepth4

       Possibilities:
               unchanged   (256)"
   ::= {er1646v2Lan3FGIbwEntry 4064542720}

er1646v2Lan3FGIbwActCirActEthDei4 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth4

       Possibilities:
               unchanged   (255)
               clear   (0)
               set   (1)"
   ::= {er1646v2Lan3FGIbwEntry 4065853440}

er1646v2Lan3FGIbwActCirActEthCos5 OBJECT-TYPE
   SYNTAX      INTEGER
               {
               unchanged (256)
               }
   MAX-ACCESS  read-write
   STATUS      current
   DESCRIPTION
      "Path: ethernet3.editConf.inboundBandwidth.action.cirAction.ethernet.cosDepth5

       Possibilities:
               unchanged   (256)"
   ::= {er1646v2Lan3FGIbwEntry 4064608256}

er1646v2Lan3FGIbwActCirActEthDei5 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth5

       Possibilities:
               unchanged   (255)
               clear   (0)
               set   (1)"
   ::= {er1646v2Lan3FGIbwEntry 4065918976}

er1646v2Lan3FGIbwActCirActEthCos6 OBJECT-TYPE
   SYNTAX      INTEGER
               {
               unchanged (256)
               }
   MAX-ACCESS  read-write
   STATUS      current
   DESCRIPTION
      "Path: ethernet3.editConf.inboundBandwidth.action.cirAction.ethernet.cosDepth6

       Possibilities:
               unchanged   (256)"
   ::= {er1646v2Lan3FGIbwEntry 4064673792}

er1646v2Lan3FGIbwActCirActEthDei6 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth6

       Possibilities:
               unchanged   (255)
               clear   (0)
               set   (1)"
   ::= {er1646v2Lan3FGIbwEntry 4065984512}

er1646v2Lan3FGIbwActCirActEthCos7 OBJECT-TYPE
   SYNTAX      INTEGER
               {
               unchanged (256)
               }
   MAX-ACCESS  read-write
   STATUS      current
   DESCRIPTION
      "Path: ethernet3.editConf.inboundBandwidth.action.cirAction.ethernet.cosDepth7

       Possibilities:
               unchanged   (256)"
   ::= {er1646v2Lan3FGIbwEntry 4064739328}

er1646v2Lan3FGIbwActCirActEthDei7 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth7

       Possibilities:
               unchanged   (255)
               clear   (0)
               set   (1)"
   ::= {er1646v2Lan3FGIbwEntry 4066050048}

er1646v2Lan3FGIbwActCirActEthCos8 OBJECT-TYPE
   SYNTAX      INTEGER
               {
               unchanged (256)
               }
   MAX-ACCESS  read-write
   STATUS      current
   DESCRIPTION
      "Path: ethernet3.editConf.inboundBandwidth.action.cirAction.ethernet.cosDepth8

       Possibilities:
               unchanged   (256)"
   ::= {er1646v2Lan3FGIbwEntry 4064804864}

er1646v2Lan3FGIbwActCirActEthDei8 OBJECT-TYPE
   SYNTAX      INTEGER
               {
               unchanged (255),
               clear (0),
               set (1)
               }
   MAX-ACCESS  read-write
   STATUS      current
   DESCRIPTION
      "Path: ethernet3.editConf.inboundBandwidth.action.cirAction.ethernet.deiDepth8

       Possibilities:
               unchanged   (255)
               clear   (0)
               set   (1)"
   ::= {er1646v2Lan3FGIbwEntry 4066115584}

er1646v2Lan3FGIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGIbwEntry 4064870400}

er1646v2Lan3FGIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGIbwEntry 4064935936}

er1646v2Lan3FGIbwActCirActEthDrpLev OBJECT-TYPE
   SYNTAX      INTEGER
               {
               unchanged (0)
               }
   MAX-ACCESS  read-write
   STATUS      current
   DESCRIPTION
      "Path: ethernet3.editConf.inboundBandwidth.action.cirAction.ethernet.dropLevel

       Possibilities:
               unchanged   (0)"
   ::= {er1646v2Lan3FGIbwEntry 4065001472}

er1646v2Lan3FGIbwActCirActEthDeFlag OBJECT-TYPE
   SYNTAX      INTEGER
               {
               unchanged (255),
               clear (0),
               set (1)
               }
   MAX-ACCESS  read-write
   STATUS      current
   DESCRIPTION
      "Path: ethernet3.editConf.inboundBandwidth.action.cirAction.ethernet.deFlag

       Possibilities:
               unchanged   (255)
               clear   (0)
               set   (1)"
   ::= {er1646v2Lan3FGIbwEntry 4065198080}

er1646v2Lan3FGIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGIbwEntry 4071161856}

er1646v2Lan3FGIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGIbwEntry 4071227392}

er1646v2Lan3FGIbwActCirActIpDrpLev OBJECT-TYPE
   SYNTAX      INTEGER
               {
               unchanged (0)
               }
   MAX-ACCESS  read-write
   STATUS      current
   DESCRIPTION
      "Path: ethernet3.editConf.inboundBandwidth.action.cirAction.ip.dropLevel

       Possibilities:
               unchanged   (0)"
   ::= {er1646v2Lan3FGIbwEntry 4071292928}

er1646v2Lan3FGIbwActCirActIpDeFlag OBJECT-TYPE
   SYNTAX      INTEGER
               {
               unchanged (255),
               clear (0),
               set (1)
               }
   MAX-ACCESS  read-write
   STATUS      current
   DESCRIPTION
      "Path: ethernet3.editConf.inboundBandwidth.action.cirAction.ip.deFlag

       Possibilities:
               unchanged   (255)
               clear   (0)
               set   (1)"
   ::= {er1646v2Lan3FGIbwEntry 4071489536}

er1646v2Lan3FGIbwActEirActNone OBJECT-TYPE
   SYNTAX      OCTET STRING
   MAX-ACCESS  read-write
   STATUS      current
   DESCRIPTION
      "Path: ethernet3.editConf.inboundBandwidth.action.eirAction.none"
   ::= {er1646v2Lan3FGIbwEntry 4095737856}

er1646v2Lan3FGIbwActEirActEthCos1 OBJECT-TYPE
   SYNTAX      INTEGER
               {
               unchanged (256)
               }
   MAX-ACCESS  read-write
   STATUS      current
   DESCRIPTION
      "Path: ethernet3.editConf.inboundBandwidth.action.eirAction.ethernet.cosDepth1

       Possibilities:
               unchanged   (256)"
   ::= {er1646v2Lan3FGIbwEntry 4097900544}

er1646v2Lan3FGIbwActEirActEthDei1 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth1

       Possibilities:
               unchanged   (255)
               clear   (0)
               set   (1)"
   ::= {er1646v2Lan3FGIbwEntry 4099211264}

er1646v2Lan3FGIbwActEirActEthCos2 OBJECT-TYPE
   SYNTAX      INTEGER
               {
               unchanged (256)
               }
   MAX-ACCESS  read-write
   STATUS      current
   DESCRIPTION
      "Path: ethernet3.editConf.inboundBandwidth.action.eirAction.ethernet.cosDepth2

       Possibilities:
               unchanged   (256)"
   ::= {er1646v2Lan3FGIbwEntry 4097966080}

er1646v2Lan3FGIbwActEirActEthDei2 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth2

       Possibilities:
               unchanged   (255)
               clear   (0)
               set   (1)"
   ::= {er1646v2Lan3FGIbwEntry 4099276800}

er1646v2Lan3FGIbwActEirActEthCos3 OBJECT-TYPE
   SYNTAX      INTEGER
               {
               unchanged (256)
               }
   MAX-ACCESS  read-write
   STATUS      current
   DESCRIPTION
      "Path: ethernet3.editConf.inboundBandwidth.action.eirAction.ethernet.cosDepth3

       Possibilities:
               unchanged   (256)"
   ::= {er1646v2Lan3FGIbwEntry 4098031616}

er1646v2Lan3FGIbwActEirActEthDei3 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth3

       Possibilities:
               unchanged   (255)
               clear   (0)
               set   (1)"
   ::= {er1646v2Lan3FGIbwEntry 4099342336}

er1646v2Lan3FGIbwActEirActEthCos4 OBJECT-TYPE
   SYNTAX      INTEGER
               {
               unchanged (256)
               }
   MAX-ACCESS  read-write
   STATUS      current
   DESCRIPTION
      "Path: ethernet3.editConf.inboundBandwidth.action.eirAction.ethernet.cosDepth4

       Possibilities:
               unchanged   (256)"
   ::= {er1646v2Lan3FGIbwEntry 4098097152}

er1646v2Lan3FGIbwActEirActEthDei4 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth4

       Possibilities:
               unchanged   (255)
               clear   (0)
               set   (1)"
   ::= {er1646v2Lan3FGIbwEntry 4099407872}

er1646v2Lan3FGIbwActEirActEthCos5 OBJECT-TYPE
   SYNTAX      INTEGER
               {
               unchanged (256)
               }
   MAX-ACCESS  read-write
   STATUS      current
   DESCRIPTION
      "Path: ethernet3.editConf.inboundBandwidth.action.eirAction.ethernet.cosDepth5

       Possibilities:
               unchanged   (256)"
   ::= {er1646v2Lan3FGIbwEntry 4098162688}

er1646v2Lan3FGIbwActEirActEthDei5 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth5

       Possibilities:
               unchanged   (255)
               clear   (0)
               set   (1)"
   ::= {er1646v2Lan3FGIbwEntry 4099473408}

er1646v2Lan3FGIbwActEirActEthCos6 OBJECT-TYPE
   SYNTAX      INTEGER
               {
               unchanged (256)
               }
   MAX-ACCESS  read-write
   STATUS      current
   DESCRIPTION
      "Path: ethernet3.editConf.inboundBandwidth.action.eirAction.ethernet.cosDepth6

       Possibilities:
               unchanged   (256)"
   ::= {er1646v2Lan3FGIbwEntry 4098228224}

er1646v2Lan3FGIbwActEirActEthDei6 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth6

       Possibilities:
               unchanged   (255)
               clear   (0)
               set   (1)"
   ::= {er1646v2Lan3FGIbwEntry 4099538944}

er1646v2Lan3FGIbwActEirActEthCos7 OBJECT-TYPE
   SYNTAX      INTEGER
               {
               unchanged (256)
               }
   MAX-ACCESS  read-write
   STATUS      current
   DESCRIPTION
      "Path: ethernet3.editConf.inboundBandwidth.action.eirAction.ethernet.cosDepth7

       Possibilities:
               unchanged   (256)"
   ::= {er1646v2Lan3FGIbwEntry 4098293760}

er1646v2Lan3FGIbwActEirActEthDei7 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth7

       Possibilities:
               unchanged   (255)
               clear   (0)
               set   (1)"
   ::= {er1646v2Lan3FGIbwEntry 4099604480}

er1646v2Lan3FGIbwActEirActEthCos8 OBJECT-TYPE
   SYNTAX      INTEGER
               {
               unchanged (256)
               }
   MAX-ACCESS  read-write
   STATUS      current
   DESCRIPTION
      "Path: ethernet3.editConf.inboundBandwidth.action.eirAction.ethernet.cosDepth8

       Possibilities:
               unchanged   (256)"
   ::= {er1646v2Lan3FGIbwEntry 4098359296}

er1646v2Lan3FGIbwActEirActEthDei8 OBJECT-TYPE
   SYNTAX      INTEGER
               {
               unchanged (255),
               clear (0),
               set (1)
               }
   MAX-ACCESS  read-write
   STATUS      current
   DESCRIPTION
      "Path: ethernet3.editConf.inboundBandwidth.action.eirAction.ethernet.deiDepth8

       Possibilities:
               unchanged   (255)
               clear   (0)
               set   (1)"
   ::= {er1646v2Lan3FGIbwEntry 4099670016}

er1646v2Lan3FGIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGIbwEntry 4098424832}

er1646v2Lan3FGIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGIbwEntry 4098490368}

er1646v2Lan3FGIbwActEirActEthDrpLev OBJECT-TYPE
   SYNTAX      INTEGER
               {
               unchanged (0)
               }
   MAX-ACCESS  read-write
   STATUS      current
   DESCRIPTION
      "Path: ethernet3.editConf.inboundBandwidth.action.eirAction.ethernet.dropLevel

       Possibilities:
               unchanged   (0)"
   ::= {er1646v2Lan3FGIbwEntry 4098555904}

er1646v2Lan3FGIbwActEirActEthDeFlag OBJECT-TYPE
   SYNTAX      INTEGER
               {
               unchanged (255),
               clear (0),
               set (1)
               }
   MAX-ACCESS  read-write
   STATUS      current
   DESCRIPTION
      "Path: ethernet3.editConf.inboundBandwidth.action.eirAction.ethernet.deFlag

       Possibilities:
               unchanged   (255)
               clear   (0)
               set   (1)"
   ::= {er1646v2Lan3FGIbwEntry 4098752512}

er1646v2Lan3FGIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGIbwEntry 4104716288}

er1646v2Lan3FGIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGIbwEntry 4104781824}

er1646v2Lan3FGIbwActEirActIpDrpLev OBJECT-TYPE
   SYNTAX      INTEGER
               {
               unchanged (0)
               }
   MAX-ACCESS  read-write
   STATUS      current
   DESCRIPTION
      "Path: ethernet3.editConf.inboundBandwidth.action.eirAction.ip.dropLevel

       Possibilities:
               unchanged   (0)"
   ::= {er1646v2Lan3FGIbwEntry 4104847360}

er1646v2Lan3FGIbwActEirActIpDeFlag OBJECT-TYPE
   SYNTAX      INTEGER
               {
               unchanged (255),
               clear (0),
               set (1)
               }
   MAX-ACCESS  read-write
   STATUS      current
   DESCRIPTION
      "Path: ethernet3.editConf.inboundBandwidth.action.eirAction.ip.deFlag

       Possibilities:
               unchanged   (255)
               clear   (0)
               set   (1)"
   ::= {er1646v2Lan3FGIbwEntry 4105043968}

er1646v2Lan3FGIbwActViolActNone OBJECT-TYPE
   SYNTAX      OCTET STRING
   MAX-ACCESS  read-write
   STATUS      current
   DESCRIPTION
      "Path: ethernet3.editConf.inboundBandwidth.action.violateAction.none"
   ::= {er1646v2Lan3FGIbwEntry 4129292288}

er1646v2Lan3FGIbwActViolActDrop OBJECT-TYPE
   SYNTAX      OCTET STRING
   MAX-ACCESS  read-write
   STATUS      current
   DESCRIPTION
      "Path: ethernet3.editConf.inboundBandwidth.action.violateAction.drop"
   ::= {er1646v2Lan3FGIbwEntry 4133486592}

er1646v2Lan3FGIbwActViolActEthCos1 OBJECT-TYPE
   SYNTAX      INTEGER
               {
               unchanged (256)
               }
   MAX-ACCESS  read-write
   STATUS      current
   DESCRIPTION
      "Path: ethernet3.editConf.inboundBandwidth.action.violateAction.ethernet.cosDepth1

       Possibilities:
               unchanged   (256)"
   ::= {er1646v2Lan3FGIbwEntry 4131454976}

er1646v2Lan3FGIbwActViolActEthDei1 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth1

       Possibilities:
               unchanged   (255)
               clear   (0)
               set   (1)"
   ::= {er1646v2Lan3FGIbwEntry 4132765696}

er1646v2Lan3FGIbwActViolActEthCos2 OBJECT-TYPE
   SYNTAX      INTEGER
               {
               unchanged (256)
               }
   MAX-ACCESS  read-write
   STATUS      current
   DESCRIPTION
      "Path: ethernet3.editConf.inboundBandwidth.action.violateAction.ethernet.cosDepth2

       Possibilities:
               unchanged   (256)"
   ::= {er1646v2Lan3FGIbwEntry 4131520512}

er1646v2Lan3FGIbwActViolActEthDei2 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth2

       Possibilities:
               unchanged   (255)
               clear   (0)
               set   (1)"
   ::= {er1646v2Lan3FGIbwEntry 4132831232}

er1646v2Lan3FGIbwActViolActEthCos3 OBJECT-TYPE
   SYNTAX      INTEGER
               {
               unchanged (256)
               }
   MAX-ACCESS  read-write
   STATUS      current
   DESCRIPTION
      "Path: ethernet3.editConf.inboundBandwidth.action.violateAction.ethernet.cosDepth3

       Possibilities:
               unchanged   (256)"
   ::= {er1646v2Lan3FGIbwEntry 4131586048}

er1646v2Lan3FGIbwActViolActEthDei3 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth3

       Possibilities:
               unchanged   (255)
               clear   (0)
               set   (1)"
   ::= {er1646v2Lan3FGIbwEntry 4132896768}

er1646v2Lan3FGIbwActViolActEthCos4 OBJECT-TYPE
   SYNTAX      INTEGER
               {
               unchanged (256)
               }
   MAX-ACCESS  read-write
   STATUS      current
   DESCRIPTION
      "Path: ethernet3.editConf.inboundBandwidth.action.violateAction.ethernet.cosDepth4

       Possibilities:
               unchanged   (256)"
   ::= {er1646v2Lan3FGIbwEntry 4131651584}

er1646v2Lan3FGIbwActViolActEthDei4 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth4

       Possibilities:
               unchanged   (255)
               clear   (0)
               set   (1)"
   ::= {er1646v2Lan3FGIbwEntry 4132962304}

er1646v2Lan3FGIbwActViolActEthCos5 OBJECT-TYPE
   SYNTAX      INTEGER
               {
               unchanged (256)
               }
   MAX-ACCESS  read-write
   STATUS      current
   DESCRIPTION
      "Path: ethernet3.editConf.inboundBandwidth.action.violateAction.ethernet.cosDepth5

       Possibilities:
               unchanged   (256)"
   ::= {er1646v2Lan3FGIbwEntry 4131717120}

er1646v2Lan3FGIbwActViolActEthDei5 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth5

       Possibilities:
               unchanged   (255)
               clear   (0)
               set   (1)"
   ::= {er1646v2Lan3FGIbwEntry 4133027840}

er1646v2Lan3FGIbwActViolActEthCos6 OBJECT-TYPE
   SYNTAX      INTEGER
               {
               unchanged (256)
               }
   MAX-ACCESS  read-write
   STATUS      current
   DESCRIPTION
      "Path: ethernet3.editConf.inboundBandwidth.action.violateAction.ethernet.cosDepth6

       Possibilities:
               unchanged   (256)"
   ::= {er1646v2Lan3FGIbwEntry 4131782656}

er1646v2Lan3FGIbwActViolActEthDei6 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth6

       Possibilities:
               unchanged   (255)
               clear   (0)
               set   (1)"
   ::= {er1646v2Lan3FGIbwEntry 4133093376}

er1646v2Lan3FGIbwActViolActEthCos7 OBJECT-TYPE
   SYNTAX      INTEGER
               {
               unchanged (256)
               }
   MAX-ACCESS  read-write
   STATUS      current
   DESCRIPTION
      "Path: ethernet3.editConf.inboundBandwidth.action.violateAction.ethernet.cosDepth7

       Possibilities:
               unchanged   (256)"
   ::= {er1646v2Lan3FGIbwEntry 4131848192}

er1646v2Lan3FGIbwActViolActEthDei7 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth7

       Possibilities:
               unchanged   (255)
               clear   (0)
               set   (1)"
   ::= {er1646v2Lan3FGIbwEntry 4133158912}

er1646v2Lan3FGIbwActViolActEthCos8 OBJECT-TYPE
   SYNTAX      INTEGER
               {
               unchanged (256)
               }
   MAX-ACCESS  read-write
   STATUS      current
   DESCRIPTION
      "Path: ethernet3.editConf.inboundBandwidth.action.violateAction.ethernet.cosDepth8

       Possibilities:
               unchanged   (256)"
   ::= {er1646v2Lan3FGIbwEntry 4131913728}

er1646v2Lan3FGIbwActViolActEthDei8 OBJECT-TYPE
   SYNTAX      INTEGER
               {
               unchanged (255),
               clear (0),
               set (1)
               }
   MAX-ACCESS  read-write
   STATUS      current
   DESCRIPTION
      "Path: ethernet3.editConf.inboundBandwidth.action.violateAction.ethernet.deiDepth8

       Possibilities:
               unchanged   (255)
               clear   (0)
               set   (1)"
   ::= {er1646v2Lan3FGIbwEntry 4133224448}

er1646v2Lan3FGIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGIbwEntry 4131979264}

er1646v2Lan3FGIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGIbwEntry 4132044800}

er1646v2Lan3FGIbwActViolActEthDrpLev OBJECT-TYPE
   SYNTAX      INTEGER
               {
               unchanged (0)
               }
   MAX-ACCESS  read-write
   STATUS      current
   DESCRIPTION
      "Path: ethernet3.editConf.inboundBandwidth.action.violateAction.ethernet.dropLevel

       Possibilities:
               unchanged   (0)"
   ::= {er1646v2Lan3FGIbwEntry 4132110336}

er1646v2Lan3FGIbwActViolActEthDeFlag OBJECT-TYPE
   SYNTAX      INTEGER
               {
               unchanged (255),
               clear (0),
               set (1)
               }
   MAX-ACCESS  read-write
   STATUS      current
   DESCRIPTION
      "Path: ethernet3.editConf.inboundBandwidth.action.violateAction.ethernet.deFlag

       Possibilities:
               unchanged   (255)
               clear   (0)
               set   (1)"
   ::= {er1646v2Lan3FGIbwEntry 4132306944}

er1646v2Lan3FGIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGIbwEntry 4138270720}

er1646v2Lan3FGIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGIbwEntry 4138336256}

er1646v2Lan3FGIbwActViolActIpDrpLev OBJECT-TYPE
   SYNTAX      INTEGER
               {
               unchanged (0)
               }
   MAX-ACCESS  read-write
   STATUS      current
   DESCRIPTION
      "Path: ethernet3.editConf.inboundBandwidth.action.violateAction.ip.dropLevel

       Possibilities:
               unchanged   (0)"
   ::= {er1646v2Lan3FGIbwEntry 4138401792}

er1646v2Lan3FGIbwActViolActIpDeFlag OBJECT-TYPE
   SYNTAX      INTEGER
               {
               unchanged (255),
               clear (0),
               set (1)
               }
   MAX-ACCESS  read-write
   STATUS      current
   DESCRIPTION
      "Path: ethernet3.editConf.inboundBandwidth.action.violateAction.ip.deFlag

       Possibilities:
               unchanged   (255)
               clear   (0)
               set   (1)"
   ::= {er1646v2Lan3FGIbwEntry 4138598400}

er1646v2Lan3FGIbwSubInterfacesExcluded OBJECT-TYPE
   SYNTAX      INTEGER
               {
               s (1)
               }
   MAX-ACCESS  read-write
   STATUS      current
   DESCRIPTION
      "Path: ethernet3.editConf.inboundBandwidth.subInterfaces.excluded

       Possibilities:
                  (1)"
   ::= {er1646v2Lan3FGIbwEntry 2416967680}

er1646v2Lan3FGIbwSubInterfacesIncludedInAccessList OBJECT-TYPE
   SYNTAX      DisplayString
   MAX-ACCESS  read-write
   STATUS      current
   DESCRIPTION
      "Path: ethernet3.editConf.inboundBandwidth.subInterfaces.included.inAccessList"
   ::= {er1646v2Lan3FGIbwEntry 2418020352}


er1646v2Lan3FGPriorityPolicy OBJECT-TYPE
   SYNTAX      DisplayString
   MAX-ACCESS  read-write
   STATUS      current
   DESCRIPTION
      "Path: ethernet3.editConf.priorityPolicy
       Info: Preferred Policy"
   ::= {er1646v2Lan3FG 39}


er1646v2Lan3FGMru OBJECT-TYPE
   SYNTAX      Integer32
   MAX-ACCESS  read-write
   STATUS      current
   DESCRIPTION
      "Path: ethernet3.editConf.mru"
   ::= {er1646v2Lan3FG 43}


er1646v2Lan3FGDelayOptimisation OBJECT-TYPE
   SYNTAX      INTEGER
               {
               disabled (0),
               enabled (1)
               }
   MAX-ACCESS  read-write
   STATUS      current
   DESCRIPTION
      "Path: ethernet3.editConf.delayOptimisation
       Info: optimise delay

       Possibilities:
               disabled   (0)
               enabled   (1)"
   ::= {er1646v2Lan3FG 80}


er1646v2Lan3FGAlarmMask OBJECT-TYPE
   SYNTAX      Integer32
   MAX-ACCESS  read-write
   STATUS      current
   DESCRIPTION
      "Path: ethernet3.editConf.alarmMask
       Info: ifAlarmMask

       Bit meanings:
               bit 0 = linkDown,
               bit 9 = pppoEDown"
   ::= {er1646v2Lan3FG 135}


er1646v2Lan3FGAlarmLev OBJECT IDENTIFIER ::= {er1646v2Lan3FG 170}

er1646v2Lan3FGAlarmLevSSC OBJECT IDENTIFIER ::= {er1646v2Lan3FGAlarmLev 1}

er1646v2Lan3FGAlarmLevEntry OBJECT IDENTIFIER ::= {er1646v2Lan3FGAlarmLevSSC 1}

er1646v2Lan3FGAlarmLevLinkDown OBJECT-TYPE
   SYNTAX      Integer32
   MAX-ACCESS  read-write
   STATUS      current
   DESCRIPTION
      "Path: ethernet3.editConf.alarmLevel.linkDown"
   ::= {er1646v2Lan3FGAlarmLevEntry 16777216}

er1646v2Lan3FGAlarmLevPppoEDown OBJECT-TYPE
   SYNTAX      Integer32
   MAX-ACCESS  read-write
   STATUS      current
   DESCRIPTION
      "Path: ethernet3.editConf.alarmLevel.pppoEDown"
   ::= {er1646v2Lan3FGAlarmLevEntry 167772160}


er1646v2Lan3FGArp OBJECT IDENTIFIER ::= {er1646v2Lan3FG 19}

er1646v2Lan3FGArpSSC OBJECT IDENTIFIER ::= {er1646v2Lan3FGArp 1}

er1646v2Lan3FGArpEntry OBJECT IDENTIFIER ::= {er1646v2Lan3FGArpSSC 1}

er1646v2Lan3FGArpTimeOut OBJECT-TYPE
   SYNTAX      TimeTicks
   MAX-ACCESS  read-write
   STATUS      current
   DESCRIPTION
      "Path: ethernet3.editConf.arp.timeOut

       Time in centi-second."
   ::= {er1646v2Lan3FGArpEntry 201326592}

er1646v2Lan3FGArpProxyArp OBJECT-TYPE
   SYNTAX      INTEGER
               {
               disabled (0),
               enabled (1)
               }
   MAX-ACCESS  read-write
   STATUS      current
   DESCRIPTION
      "Path: ethernet3.editConf.arp.proxyArp

       Possibilities:
               disabled   (0)
               enabled   (1)"
   ::= {er1646v2Lan3FGArpEntry 838860800}

er1646v2Lan3FGArpStaticArp OBJECT-TYPE
   SYNTAX      SEQUENCE OF Er1646v2Lan3FGArpStaticArpEntry
   MAX-ACCESS  not-accessible
   STATUS      current
   DESCRIPTION
      ""
   ::= {er1646v2Lan3FGArp 50331648}

er1646v2Lan3FGArpStaticArpEntry OBJECT-TYPE
   SYNTAX      Er1646v2Lan3FGArpStaticArpEntry
   MAX-ACCESS  not-accessible
   STATUS      current
   DESCRIPTION
      ""
   INDEX      { er1646v2Lan3FGArpStaticArpTableIx }
   ::= {er1646v2Lan3FGArpStaticArp 1}

Er1646v2Lan3FGArpStaticArpEntry ::=
   SEQUENCE
      {
      er1646v2Lan3FGArpStaticArpActions
         VariableLengthTableActions,
      er1646v2Lan3FGArpStaticArpTableIx
         TableIndex,
      er1646v2Lan3FGArpStaticArpMacAddress
         OCTET STRING,
      er1646v2Lan3FGArpStaticArpIpAddress
         IpAddress
      }

er1646v2Lan3FGArpStaticArpActions OBJECT-TYPE
   SYNTAX      VariableLengthTableActions
   MAX-ACCESS  read-write
   STATUS      current
   DESCRIPTION
      "By way of this field, some manipulations
       on this table may be performed."
   ::= {er1646v2Lan3FGArpStaticArpEntry 2}

er1646v2Lan3FGArpStaticArpTableIx OBJECT-TYPE
   SYNTAX      TableIndex
   MAX-ACCESS  not-accessible
   STATUS      current
   DESCRIPTION
      ""
   ::= {er1646v2Lan3FGArpStaticArpEntry 11}

er1646v2Lan3FGArpStaticArpMacAddress OBJECT-TYPE
   SYNTAX      OCTET STRING
   MAX-ACCESS  read-write
   STATUS      current
   DESCRIPTION
      "Path: ethernet3.editConf.arp.staticArp.macAddress

       MAC address."
   ::= {er1646v2Lan3FGArpStaticArpEntry 16777216}

er1646v2Lan3FGArpStaticArpIpAddress OBJECT-TYPE
   SYNTAX      IpAddress
   MAX-ACCESS  read-write
   STATUS      current
   DESCRIPTION
      "Path: ethernet3.editConf.arp.staticArp.ipAddress"
   ::= {er1646v2Lan3FGArpStaticArpEntry 33554432}


er1646v2Lan3FGBrC OBJECT IDENTIFIER ::= {er1646v2Lan3FG 27}

er1646v2Lan3FGBrCSSC OBJECT IDENTIFIER ::= {er1646v2Lan3FGBrC 1}

er1646v2Lan3FGBrCEntry OBJECT IDENTIFIER ::= {er1646v2Lan3FGBrCSSC 1}

er1646v2Lan3FGBrCAccessList OBJECT-TYPE
   SYNTAX      DisplayString
   MAX-ACCESS  read-write
   STATUS      current
   DESCRIPTION
      "Path: ethernet3.editConf.bridging.accessList"
   ::= {er1646v2Lan3FGBrCEntry 83886080}

er1646v2Lan3FGBrCInAccessList OBJECT-TYPE
   SYNTAX      DisplayString
   MAX-ACCESS  read-write
   STATUS      current
   DESCRIPTION
      "Path: ethernet3.editConf.bridging.inAccessList"
   ::= {er1646v2Lan3FGBrCEntry 251658240}

er1646v2Lan3FGBrCTp OBJECT-TYPE
   SYNTAX      DisplayString
   MAX-ACCESS  read-write
   STATUS      current
   DESCRIPTION
      "Path: ethernet3.editConf.bridging.trafficPolicy"
   ::= {er1646v2Lan3FGBrCEntry 100663296}

er1646v2Lan3FGBrCBridgeGroup OBJECT-TYPE
   SYNTAX      DisplayString
   MAX-ACCESS  read-write
   STATUS      current
   DESCRIPTION
      "Path: ethernet3.editConf.bridging.bridgeGroup"
   ::= {er1646v2Lan3FGBrCEntry 117440512}

er1646v2Lan3FGBrCLimBC OBJECT-TYPE
   SYNTAX      INTEGER
               {
               disabled (0),
               enabled (1)
               }
   MAX-ACCESS  read-write
   STATUS      current
   DESCRIPTION
      "Path: ethernet3.editConf.bridging.limitBroadcasts

       Possibilities:
               disabled   (0)
               enabled   (1)"
   ::= {er1646v2Lan3FGBrCEntry 134217728}

er1646v2Lan3FGBrCPrivateMode OBJECT-TYPE
   SYNTAX      INTEGER
               {
               disabled (0),
               enabled (1)
               }
   MAX-ACCESS  read-write
   STATUS      current
   DESCRIPTION
      "Path: ethernet3.editConf.bridging.privateMode

       Possibilities:
               disabled   (0)
               enabled   (1)"
   ::= {er1646v2Lan3FGBrCEntry 419430400}

er1646v2Lan3FGBrCLearning OBJECT-TYPE
   SYNTAX      INTEGER
               {
               disabled (0),
               enabled (1)
               }
   MAX-ACCESS  read-write
   STATUS      current
   DESCRIPTION
      "Path: ethernet3.editConf.bridging.learning

       Possibilities:
               disabled   (0)
               enabled   (1)"
   ::= {er1646v2Lan3FGBrCEntry 201326592}

er1646v2Lan3FGBrCMaxCacheSize OBJECT-TYPE
   SYNTAX      INTEGER
               {
               unlimited (0)
               }
   MAX-ACCESS  read-write
   STATUS      current
   DESCRIPTION
      "Path: ethernet3.editConf.bridging.maxCacheSize

       Possibilities:
               unlimited   (0)"
   ::= {er1646v2Lan3FGBrCEntry 218103808}

er1646v2Lan3FGBrCRelearnDropOnRelearn OBJECT-TYPE
   SYNTAX      INTEGER
               {
               disabled (0),
               enabled (1)
               }
   MAX-ACCESS  read-write
   STATUS      current
   DESCRIPTION
      "Path: ethernet3.editConf.bridging.relearn.dropOnRelearn

       Possibilities:
               disabled   (0)
               enabled   (1)"
   ::= {er1646v2Lan3FGBrCEntry 234946560}

er1646v2Lan3FGBrCRelearnShutdownThreshold OBJECT-TYPE
   SYNTAX      Integer32
   MAX-ACCESS  read-write
   STATUS      current
   DESCRIPTION
      "Path: ethernet3.editConf.bridging.relearn.shutdownThreshold"
   ::= {er1646v2Lan3FGBrCEntry 235012096}

er1646v2Lan3FGBrCRelearnShutdownTime OBJECT-TYPE
   SYNTAX      TimeTicks
   MAX-ACCESS  read-write
   STATUS      current
   DESCRIPTION
      "Path: ethernet3.editConf.bridging.relearn.shutdownTime

       Time in centi-second."
   ::= {er1646v2Lan3FGBrCEntry 235077632}

er1646v2Lan3FGBrCRelearnLoopDetection OBJECT-TYPE
   SYNTAX      INTEGER
               {
               disabled (0),
               passive (1),
               active (2)
               }
   MAX-ACCESS  read-write
   STATUS      current
   DESCRIPTION
      "Path: ethernet3.editConf.bridging.relearn.loopDetection

       Possibilities:
               disabled   (0)
               passive   (1)
               active   (2)"
   ::= {er1646v2Lan3FGBrCEntry 235143168}

er1646v2Lan3FGBrCRelearnLoopDetectionInterval OBJECT-TYPE
   SYNTAX      TimeTicks
   MAX-ACCESS  read-write
   STATUS      current
   DESCRIPTION
      "Path: ethernet3.editConf.bridging.relearn.loopDetectionInterval

       Time in centi-second."
   ::= {er1646v2Lan3FGBrCEntry 235208704}

er1646v2Lan3FGBrCVlanMemberShip OBJECT-TYPE
   SYNTAX      INTEGER
               {
               all (0),
               none (1),
               grouped (2)
               }
   MAX-ACCESS  read-write
   STATUS      current
   DESCRIPTION
      "Path: ethernet3.editConf.bridging.vlanMemberShip

       Possibilities:
               all   (0)
               none   (1)
               grouped   (2)"
   ::= {er1646v2Lan3FGBrCEntry 318767104}

er1646v2Lan3FGBrCDot1adType OBJECT-TYPE
   SYNTAX      INTEGER
               {
               slOPTg (0),
               cPort (4),
               sPort (1),
               nni (2)
               }
   MAX-ACCESS  read-write
   STATUS      current
   DESCRIPTION
      "Path: ethernet3.editConf.bridging.dot1ad.type

       Possibilities:
               <OPT>   (0)
               cPort   (4)
               sPort   (1)
               nni   (2)"
   ::= {er1646v2Lan3FGBrCEntry 503382016}

er1646v2Lan3FGBrCPriority OBJECT-TYPE
   SYNTAX      Integer32
   MAX-ACCESS  read-write
   STATUS      current
   DESCRIPTION
      "Path: ethernet3.editConf.bridging.priority"
   ::= {er1646v2Lan3FGBrCEntry 33554432}

er1646v2Lan3FGBrCPathCost OBJECT-TYPE
   SYNTAX      Integer32
   MAX-ACCESS  read-write
   STATUS      current
   DESCRIPTION
      "Path: ethernet3.editConf.bridging.pathCost"
   ::= {er1646v2Lan3FGBrCEntry 50331648}

er1646v2Lan3FGBrCInternalPathCost OBJECT-TYPE
   SYNTAX      Integer32
   MAX-ACCESS  read-write
   STATUS      current
   DESCRIPTION
      "Path: ethernet3.editConf.bridging.internalPathCost"
   ::= {er1646v2Lan3FGBrCEntry 301989888}

er1646v2Lan3FGBrCTCD OBJECT-TYPE
   SYNTAX      INTEGER
               {
               disabled (0),
               enabled (1)
               }
   MAX-ACCESS  read-write
   STATUS      current
   DESCRIPTION
      "Path: ethernet3.editConf.bridging.topologyChangeDetection

       Possibilities:
               disabled   (0)
               enabled   (1)"
   ::= {er1646v2Lan3FGBrCEntry 67108864}

er1646v2Lan3FGBrCRestrictedRole OBJECT-TYPE
   SYNTAX      INTEGER
               {
               disabled (0),
               enabled (1)
               }
   MAX-ACCESS  read-write
   STATUS      current
   DESCRIPTION
      "Path: ethernet3.editConf.bridging.restrictedRole

       Possibilities:
               disabled   (0)
               enabled   (1)"
   ::= {er1646v2Lan3FGBrCEntry 335544320}

er1646v2Lan3FGBrCAdminEdge OBJECT-TYPE
   SYNTAX      INTEGER
               {
               disabled (0),
               enabled (1)
               }
   MAX-ACCESS  read-write
   STATUS      current
   DESCRIPTION
      "Path: ethernet3.editConf.bridging.adminEdge

       Possibilities:
               disabled   (0)
               enabled   (1)"
   ::= {er1646v2Lan3FGBrCEntry 268435456}

er1646v2Lan3FGBrCMgmtInline OBJECT-TYPE
   SYNTAX      INTEGER
               {
               disabled (0),
               enabled (1)
               }
   MAX-ACCESS  read-write
   STATUS      current
   DESCRIPTION
      "Path: ethernet3.editConf.bridging.mgmtInline

       Possibilities:
               disabled   (0)
               enabled   (1)"
   ::= {er1646v2Lan3FGBrCEntry 369098752}

er1646v2Lan3FGBrCL2ptMode OBJECT-TYPE
   SYNTAX      INTEGER
               {
               disabled (0),
               enabled (1)
               }
   MAX-ACCESS  read-write
   STATUS      current
   DESCRIPTION
      "Path: ethernet3.editConf.bridging.l2ProtTunnel.mode

       Possibilities:
               disabled   (0)
               enabled   (1)"
   ::= {er1646v2Lan3FGBrCEntry 403701760}

er1646v2Lan3FGBrCL2ptProtocols OBJECT-TYPE
   SYNTAX      Integer32
   MAX-ACCESS  read-write
   STATUS      current
   DESCRIPTION
      "Path: ethernet3.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2Lan3FGBrCEntry 404750336}

er1646v2Lan3FGBrCL2ptDestMac OBJECT-TYPE
   SYNTAX      OCTET STRING
   MAX-ACCESS  read-write
   STATUS      current
   DESCRIPTION
      "Path: ethernet3.editConf.bridging.l2ProtTunnel.destinationMac

       MAC address."
   ::= {er1646v2Lan3FGBrCEntry 405798912}

er1646v2Lan3FGBrCL2ptCos OBJECT-TYPE
   SYNTAX      INTEGER
               {
               unchanged (255)
               }
   MAX-ACCESS  read-write
   STATUS      current
   DESCRIPTION
      "Path: ethernet3.editConf.bridging.l2ProtTunnel.cos

       Possibilities:
               unchanged   (255)"
   ::= {er1646v2Lan3FGBrCEntry 406847488}

er1646v2Lan3FGBrCL2ptDropThrStp OBJECT-TYPE
   SYNTAX      INTEGER
               {
               unlimited (0)
               }
   UNITS       "packets/sec"
   MAX-ACCESS  read-write
   STATUS      current
   DESCRIPTION
      "Path: ethernet3.editConf.bridging.l2ProtTunnel.dropThresholds.stp

       unit name = packets/sec

       Possibilities:
               unlimited   (0)"
   ::= {er1646v2Lan3FGBrCEntry 407900160}

er1646v2Lan3FGBrCL2ptDropThrLldp OBJECT-TYPE
   SYNTAX      INTEGER
               {
               unlimited (0)
               }
   UNITS       "packets/sec"
   MAX-ACCESS  read-write
   STATUS      current
   DESCRIPTION
      "Path: ethernet3.editConf.bridging.l2ProtTunnel.dropThresholds.lldp

       unit name = packets/sec

       Possibilities:
               unlimited   (0)"
   ::= {er1646v2Lan3FGBrCEntry 407904256}

er1646v2Lan3FGBrCL2ptDropThrOam OBJECT-TYPE
   SYNTAX      INTEGER
               {
               unlimited (0)
               }
   UNITS       "packets/sec"
   MAX-ACCESS  read-write
   STATUS      current
   DESCRIPTION
      "Path: ethernet3.editConf.bridging.l2ProtTunnel.dropThresholds.oam

       unit name = packets/sec

       Possibilities:
               unlimited   (0)"
   ::= {er1646v2Lan3FGBrCEntry 407908352}

er1646v2Lan3FGBrCL2ptDropThrCdp OBJECT-TYPE
   SYNTAX      INTEGER
               {
               unlimited (0)
               }
   UNITS       "packets/sec"
   MAX-ACCESS  read-write
   STATUS      current
   DESCRIPTION
      "Path: ethernet3.editConf.bridging.l2ProtTunnel.dropThresholds.cdp

       unit name = packets/sec

       Possibilities:
               unlimited   (0)"
   ::= {er1646v2Lan3FGBrCEntry 407912448}

er1646v2Lan3FGBrCL2ptDropThrVtp OBJECT-TYPE
   SYNTAX      INTEGER
               {
               unlimited (0)
               }
   UNITS       "packets/sec"
   MAX-ACCESS  read-write
   STATUS      current
   DESCRIPTION
      "Path: ethernet3.editConf.bridging.l2ProtTunnel.dropThresholds.vtp

       unit name = packets/sec

       Possibilities:
               unlimited   (0)"
   ::= {er1646v2Lan3FGBrCEntry 407916544}

er1646v2Lan3FGBrCL2ptDropThrLacp OBJECT-TYPE
   SYNTAX      INTEGER
               {
               unlimited (0)
               }
   UNITS       "packets/sec"
   MAX-ACCESS  read-write
   STATUS      current
   DESCRIPTION
      "Path: ethernet3.editConf.bridging.l2ProtTunnel.dropThresholds.lacp

       unit name = packets/sec

       Possibilities:
               unlimited   (0)"
   ::= {er1646v2Lan3FGBrCEntry 407920640}

er1646v2Lan3FGBrCL2ptDropThrEfmOam OBJECT-TYPE
   SYNTAX      INTEGER
               {
               unlimited (0)
               }
   UNITS       "packets/sec"
   MAX-ACCESS  read-write
   STATUS      current
   DESCRIPTION
      "Path: ethernet3.editConf.bridging.l2ProtTunnel.dropThresholds.efmOam

       unit name = packets/sec

       Possibilities:
               unlimited   (0)"
   ::= {er1646v2Lan3FGBrCEntry 407924736}

er1646v2Lan3FGBrCL2ptDropThrPvst OBJECT-TYPE
   SYNTAX      INTEGER
               {
               unlimited (0)
               }
   UNITS       "packets/sec"
   MAX-ACCESS  read-write
   STATUS      current
   DESCRIPTION
      "Path: ethernet3.editConf.bridging.l2ProtTunnel.dropThresholds.pvst

       unit name = packets/sec

       Possibilities:
               unlimited   (0)"
   ::= {er1646v2Lan3FGBrCEntry 407928832}

er1646v2Lan3FGBrCL2ptDropThrMmrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.mmrp

       unit name = packets/sec

       Possibilities:
               unlimited   (0)"
   ::= {er1646v2Lan3FGBrCEntry 407932928}

er1646v2Lan3FGBrCL2ptDropThrMvrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.mvrp

       unit name = packets/sec

       Possibilities:
               unlimited   (0)"
   ::= {er1646v2Lan3FGBrCEntry 407937024}

er1646v2Lan3FGBrCL2ptDropThrGvrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.gvrp

       unit name = packets/sec

       Possibilities:
               unlimited   (0)"
   ::= {er1646v2Lan3FGBrCEntry 407941120}

er1646v2Lan3FGBrCL2ptDropThrGmrp OBJECT-TYPE
   SYNTAX      INTEGER
               {
               unlimited (0)
               }
   UNITS       "packets/sec"
   MAX-ACCESS  read-write
   STATUS      current
   DESCRIPTION
      "Path: ethernet3.editConf.bridging.l2ProtTunnel.dropThresholds.gmrp

       unit name = packets/sec

       Possibilities:
               unlimited   (0)"
   ::= {er1646v2Lan3FGBrCEntry 407945216}

er1646v2Lan3FGBrCL2ptDropThrDtp OBJECT-TYPE
   SYNTAX      INTEGER
               {
               unlimited (0)
               }
   UNITS       "packets/sec"
   MAX-ACCESS  read-write
   STATUS      current
   DESCRIPTION
      "Path: ethernet3.editConf.bridging.l2ProtTunnel.dropThresholds.dtp

       unit name = packets/sec

       Possibilities:
               unlimited   (0)"
   ::= {er1646v2Lan3FGBrCEntry 407949312}

er1646v2Lan3FGBrCL2ptDropThrPagp OBJECT-TYPE
   SYNTAX      INTEGER
               {
               unlimited (0)
               }
   UNITS       "packets/sec"
   MAX-ACCESS  read-write
   STATUS      current
   DESCRIPTION
      "Path: ethernet3.editConf.bridging.l2ProtTunnel.dropThresholds.pagp

       unit name = packets/sec

       Possibilities:
               unlimited   (0)"
   ::= {er1646v2Lan3FGBrCEntry 407953408}

er1646v2Lan3FGBrCL2ptDropThrUdld OBJECT-TYPE
   SYNTAX      INTEGER
               {
               unlimited (0)
               }
   UNITS       "packets/sec"
   MAX-ACCESS  read-write
   STATUS      current
   DESCRIPTION
      "Path: ethernet3.editConf.bridging.l2ProtTunnel.dropThresholds.udld

       unit name = packets/sec

       Possibilities:
               unlimited   (0)"
   ::= {er1646v2Lan3FGBrCEntry 407957504}


er1646v2Lan3FGVlanTagging OBJECT IDENTIFIER ::= {er1646v2Lan3FG 14}

er1646v2Lan3FGVlanTaggingSSC OBJECT IDENTIFIER ::= {er1646v2Lan3FGVlanTagging 1}

er1646v2Lan3FGVlanTaggingEntry OBJECT IDENTIFIER ::= {er1646v2Lan3FGVlanTaggingSSC 1}

er1646v2Lan3FGVlanTaggingUntaggedAction OBJECT-TYPE
   SYNTAX      INTEGER
               {
               discard (0),
               accept (1),
               tag (2)
               }
   MAX-ACCESS  read-write
   STATUS      current
   DESCRIPTION
      "Path: ethernet3.editConf.vlanTagging.untagged.action

       Possibilities:
               discard   (0)
               accept   (1)
               tag   (2)"
   ::= {er1646v2Lan3FGVlanTaggingEntry 671088640}

er1646v2Lan3FGVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.untagged.tagInfo.tpid

       Possibilities:
               dot1Q   (33024)
               dot1ad   (34984)
               0x9100   (37120)
               0x9200   (37376)
               0x9300   (37632)"
   ::= {er1646v2Lan3FGVlanTaggingEntry 746586112}

er1646v2Lan3FGVlanTaggingUntaggedTagInfoVid OBJECT-TYPE
   SYNTAX      Integer32
   MAX-ACCESS  read-write
   STATUS      current
   DESCRIPTION
      "Path: ethernet3.editConf.vlanTagging.untagged.tagInfo.vid"
   ::= {er1646v2Lan3FGVlanTaggingEntry 754974720}

er1646v2Lan3FGVlanTaggingUnknownVlansAction OBJECT-TYPE
   SYNTAX      INTEGER
               {
               discard (0),
               accept (1),
               tag (2)
               }
   MAX-ACCESS  read-write
   STATUS      current
   DESCRIPTION
      "Path: ethernet3.editConf.vlanTagging.unknownVlans.action

       Possibilities:
               discard   (0)
               accept   (1)
               tag   (2)"
   ::= {er1646v2Lan3FGVlanTaggingEntry 1744830464}

er1646v2Lan3FGVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.unknownVlans.tagInfo.tpid

       Possibilities:
               dot1Q   (33024)
               dot1ad   (34984)
               0x9100   (37120)
               0x9200   (37376)
               0x9300   (37632)"
   ::= {er1646v2Lan3FGVlanTaggingEntry 1820327936}

er1646v2Lan3FGVlanTaggingUnknownVlansTagInfoVid OBJECT-TYPE
   SYNTAX      Integer32
   MAX-ACCESS  read-write
   STATUS      current
   DESCRIPTION
      "Path: ethernet3.editConf.vlanTagging.unknownVlans.tagInfo.vid"
   ::= {er1646v2Lan3FGVlanTaggingEntry 1828716544}

er1646v2Lan3FGVlanTaggingVlans OBJECT-TYPE
   SYNTAX      SEQUENCE OF Er1646v2Lan3FGVlanTaggingVlansEntry
   MAX-ACCESS  not-accessible
   STATUS      current
   DESCRIPTION
      ""
   ::= {er1646v2Lan3FGVlanTagging 1073741824}

er1646v2Lan3FGVlanTaggingVlansEntry OBJECT-TYPE
   SYNTAX      Er1646v2Lan3FGVlanTaggingVlansEntry
   MAX-ACCESS  not-accessible
   STATUS      current
   DESCRIPTION
      ""
   INDEX      { er1646v2Lan3FGVlanTaggingVlansTableIx }
   ::= {er1646v2Lan3FGVlanTaggingVlans 1}

Er1646v2Lan3FGVlanTaggingVlansEntry ::=
   SEQUENCE
      {
      er1646v2Lan3FGVlanTaggingVlansActions
         VariableLengthTableActions,
      er1646v2Lan3FGVlanTaggingVlansTableIx
         TableIndex,
      er1646v2Lan3FGVlanTaggingVlansVid
         Integer32,
      er1646v2Lan3FGVlanTaggingVlansEndVid
         Integer32,
      er1646v2Lan3FGVlanTaggingVlansAction
         INTEGER,
      er1646v2Lan3FGVlanTaggingVlansTagInfoTpid
         INTEGER,
      er1646v2Lan3FGVlanTaggingVlansTagInfoVid
         Integer32
      }

er1646v2Lan3FGVlanTaggingVlansActions OBJECT-TYPE
   SYNTAX      VariableLengthTableActions
   MAX-ACCESS  read-write
   STATUS      current
   DESCRIPTION
      "By way of this field, some manipulations
       on this table may be performed."
   ::= {er1646v2Lan3FGVlanTaggingVlansEntry 2}

er1646v2Lan3FGVlanTaggingVlansTableIx OBJECT-TYPE
   SYNTAX      TableIndex
   MAX-ACCESS  not-accessible
   STATUS      current
   DESCRIPTION
      ""
   ::= {er1646v2Lan3FGVlanTaggingVlansEntry 11}

er1646v2Lan3FGVlanTaggingVlansVid OBJECT-TYPE
   SYNTAX      Integer32
   MAX-ACCESS  read-write
   STATUS      current
   DESCRIPTION
      "Path: ethernet3.editConf.vlanTagging.vlans.vid"
   ::= {er1646v2Lan3FGVlanTaggingVlansEntry 536870912}

er1646v2Lan3FGVlanTaggingVlansEndVid OBJECT-TYPE
   SYNTAX      Integer32
   MAX-ACCESS  read-write
   STATUS      current
   DESCRIPTION
      "Path: ethernet3.editConf.vlanTagging.vlans.endVid"
   ::= {er1646v2Lan3FGVlanTaggingVlansEntry 2147483648}

er1646v2Lan3FGVlanTaggingVlansAction OBJECT-TYPE
   SYNTAX      INTEGER
               {
               discard (0),
               accept (1),
               tag (2)
               }
   MAX-ACCESS  read-write
   STATUS      current
   DESCRIPTION
      "Path: ethernet3.editConf.vlanTagging.vlans.action

       Possibilities:
               discard   (0)
               accept   (1)
               tag   (2)"
   ::= {er1646v2Lan3FGVlanTaggingVlansEntry 1073741824}

er1646v2Lan3FGVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlanTagging.vlans.tagInfo.tpid

       Possibilities:
               dot1Q   (33024)
               dot1ad   (34984)
               0x9100   (37120)
               0x9200   (37376)
               0x9300   (37632)"
   ::= {er1646v2Lan3FGVlanTaggingVlansEntry 1677721600}

er1646v2Lan3FGVlanTaggingVlansTagInfoVid OBJECT-TYPE
   SYNTAX      Integer32
   MAX-ACCESS  read-write
   STATUS      current
   DESCRIPTION
      "Path: ethernet3.editConf.vlanTagging.vlans.tagInfo.vid"
   ::= {er1646v2Lan3FGVlanTaggingVlansEntry 1744830464}


er1646v2Lan3FGOam OBJECT IDENTIFIER ::= {er1646v2Lan3FG 900}

er1646v2Lan3FGOamSSC OBJECT IDENTIFIER ::= {er1646v2Lan3FGOam 1}

er1646v2Lan3FGOamEntry OBJECT IDENTIFIER ::= {er1646v2Lan3FGOamSSC 1}

er1646v2Lan3FGOamMode OBJECT-TYPE
   SYNTAX      INTEGER
               {
               disabled (0),
               passive (3),
               active (2)
               }
   MAX-ACCESS  read-write
   STATUS      current
   DESCRIPTION
      "Path: ethernet3.editConf.oam.mode

       Possibilities:
               disabled   (0)
               passive   (3)
               active   (2)"
   ::= {er1646v2Lan3FGOamEntry 16777216}

er1646v2Lan3FGOamLpbkLocalParAction OBJECT-TYPE
   SYNTAX      INTEGER
               {
               discard (0),
               forward (1)
               }
   MAX-ACCESS  read-write
   STATUS      current
   DESCRIPTION
      "Path: ethernet3.editConf.oam.loopbackLocalParserAction

       Possibilities:
               discard   (0)
               forward   (1)"
   ::= {er1646v2Lan3FGOamEntry 33554432}

er1646v2Lan3FGOamLpbkSwapMacAddr OBJECT-TYPE
   SYNTAX      INTEGER
               {
               disabled (0),
               enabled (1)
               }
   MAX-ACCESS  read-write
   STATUS      current
   DESCRIPTION
      "Path: ethernet3.editConf.oam.loopbackSwapMacAddresses

       Possibilities:
               disabled   (0)
               enabled   (1)"
   ::= {er1646v2Lan3FGOamEntry 50331648}

er1646v2Lan3FGOamLoopbackIgnoreRx OBJECT-TYPE
   SYNTAX      INTEGER
               {
               no (0),
               yes (1)
               }
   MAX-ACCESS  read-write
   STATUS      current
   DESCRIPTION
      "Path: ethernet3.editConf.oam.loopbackIgnoreRx

       Possibilities:
               no   (0)
               yes   (1)"
   ::= {er1646v2Lan3FGOamEntry 67108864}

er1646v2Lan3FGOamEventsErroredSymbolEnabled OBJECT-TYPE
   SYNTAX      INTEGER
               {
               no (0),
               yes (1)
               }
   MAX-ACCESS  read-write
   STATUS      current
   DESCRIPTION
      "Path: ethernet3.editConf.oam.events.erroredSymbol.enabled

       Possibilities:
               no   (0)
               yes   (1)"
   ::= {er1646v2Lan3FGOamEntry 83951872}

er1646v2Lan3FGOamEventsErroredSymbolWindowHi OBJECT-TYPE
   SYNTAX      INTEGER
               {
               default (0)
               }
   UNITS       "symbols"
   MAX-ACCESS  read-write
   STATUS      current
   DESCRIPTION
      "Path: ethernet3.editConf.oam.events.erroredSymbol.windowHi

       unit name = symbols

       Possibilities:
               default   (0)"
   ::= {er1646v2Lan3FGOamEntry 83952128}

er1646v2Lan3FGOamEventsErroredSymbolWindowLo OBJECT-TYPE
   SYNTAX      INTEGER
               {
               default (0)
               }
   UNITS       "symbols"
   MAX-ACCESS  read-write
   STATUS      current
   DESCRIPTION
      "Path: ethernet3.editConf.oam.events.erroredSymbol.windowLo

       unit name = symbols

       Possibilities:
               default   (0)"
   ::= {er1646v2Lan3FGOamEntry 83952384}

er1646v2Lan3FGOamEventsErroredSymbolThresholdHi OBJECT-TYPE
   SYNTAX      Integer32
   UNITS       "symbols"
   MAX-ACCESS  read-write
   STATUS      current
   DESCRIPTION
      "Path: ethernet3.editConf.oam.events.erroredSymbol.thresholdHi

       unit name = symbols"
   ::= {er1646v2Lan3FGOamEntry 83952640}

er1646v2Lan3FGOamEventsErroredSymbolThresholdLo OBJECT-TYPE
   SYNTAX      Integer32
   UNITS       "symbols"
   MAX-ACCESS  read-write
   STATUS      current
   DESCRIPTION
      "Path: ethernet3.editConf.oam.events.erroredSymbol.thresholdLo

       unit name = symbols"
   ::= {er1646v2Lan3FGOamEntry 83952896}

er1646v2Lan3FGOamEventsErroredFramePeriodEnabled OBJECT-TYPE
   SYNTAX      INTEGER
               {
               no (0),
               yes (1)
               }
   MAX-ACCESS  read-write
   STATUS      current
   DESCRIPTION
      "Path: ethernet3.editConf.oam.events.erroredFramePeriod.enabled

       Possibilities:
               no   (0)
               yes   (1)"
   ::= {er1646v2Lan3FGOamEntry 84017408}

er1646v2Lan3FGOamEventsErroredFramePeriodWindow OBJECT-TYPE
   SYNTAX      INTEGER
               {
               default (0)
               }
   UNITS       "frames"
   MAX-ACCESS  read-write
   STATUS      current
   DESCRIPTION
      "Path: ethernet3.editConf.oam.events.erroredFramePeriod.window

       unit name = frames

       Possibilities:
               default   (0)"
   ::= {er1646v2Lan3FGOamEntry 84017664}

er1646v2Lan3FGOamEventsErroredFramePeriodThreshold OBJECT-TYPE
   SYNTAX      Integer32
   UNITS       "frames"
   MAX-ACCESS  read-write
   STATUS      current
   DESCRIPTION
      "Path: ethernet3.editConf.oam.events.erroredFramePeriod.threshold

       unit name = frames"
   ::= {er1646v2Lan3FGOamEntry 84017920}

er1646v2Lan3FGOamEventsErroredFrameEnabled OBJECT-TYPE
   SYNTAX      INTEGER
               {
               no (0),
               yes (1)
               }
   MAX-ACCESS  read-write
   STATUS      current
   DESCRIPTION
      "Path: ethernet3.editConf.oam.events.erroredFrame.enabled

       Possibilities:
               no   (0)
               yes   (1)"
   ::= {er1646v2Lan3FGOamEntry 84082944}

er1646v2Lan3FGOamEventsErroredFrameWindow OBJECT-TYPE
   SYNTAX      Integer32
   UNITS       "100msec"
   MAX-ACCESS  read-write
   STATUS      current
   DESCRIPTION
      "Path: ethernet3.editConf.oam.events.erroredFrame.window

       unit name = 100msec"
   ::= {er1646v2Lan3FGOamEntry 84083200}

er1646v2Lan3FGOamEventsErroredFrameThreshold OBJECT-TYPE
   SYNTAX      Integer32
   UNITS       "frames"
   MAX-ACCESS  read-write
   STATUS      current
   DESCRIPTION
      "Path: ethernet3.editConf.oam.events.erroredFrame.threshold

       unit name = frames"
   ::= {er1646v2Lan3FGOamEntry 84083456}

er1646v2Lan3FGOamEventsErroredFrameSecondsEnabled OBJECT-TYPE
   SYNTAX      INTEGER
               {
               no (0),
               yes (1)
               }
   MAX-ACCESS  read-write
   STATUS      current
   DESCRIPTION
      "Path: ethernet3.editConf.oam.events.erroredFrameSeconds.enabled

       Possibilities:
               no   (0)
               yes   (1)"
   ::= {er1646v2Lan3FGOamEntry 84148480}

er1646v2Lan3FGOamEventsErroredFrameSecondsWindow OBJECT-TYPE
   SYNTAX      Integer32
   UNITS       "100msec"
   MAX-ACCESS  read-write
   STATUS      current
   DESCRIPTION
      "Path: ethernet3.editConf.oam.events.erroredFrameSeconds.window

       unit name = 100msec"
   ::= {er1646v2Lan3FGOamEntry 84148736}

er1646v2Lan3FGOamEventsErroredFrameSecondsThreshold OBJECT-TYPE
   SYNTAX      Integer32
   UNITS       "frames"
   MAX-ACCESS  read-write
   STATUS      current
   DESCRIPTION
      "Path: ethernet3.editConf.oam.events.erroredFrameSeconds.threshold

       unit name = frames"
   ::= {er1646v2Lan3FGOamEntry 84148992}

er1646v2Lan3FGOamEventsDyingGasp OBJECT-TYPE
   SYNTAX      INTEGER
               {
               disabled (0),
               enabled (1)
               }
   MAX-ACCESS  read-write
   STATUS      current
   DESCRIPTION
      "Path: ethernet3.editConf.oam.events.dyingGasp

       Possibilities:
               disabled   (0)
               enabled   (1)"
   ::= {er1646v2Lan3FGOamEntry 84213760}

er1646v2Lan3FGOamEventsCriticalEvent OBJECT-TYPE
   SYNTAX      INTEGER
               {
               disabled (0),
               enabled (1)
               }
   MAX-ACCESS  read-write
   STATUS      current
   DESCRIPTION
      "Path: ethernet3.editConf.oam.events.criticalEvent

       Possibilities:
               disabled   (0)
               enabled   (1)"
   ::= {er1646v2Lan3FGOamEntry 84279296}


er1646v2Lan3FGLst OBJECT IDENTIFIER ::= {er1646v2Lan3FG 12}

er1646v2Lan3FGLstSSC OBJECT IDENTIFIER ::= {er1646v2Lan3FGLst 1}

er1646v2Lan3FGLstEntry OBJECT IDENTIFIER ::= {er1646v2Lan3FGLstSSC 1}

er1646v2Lan3FGLstTrackedInterface OBJECT-TYPE
   SYNTAX      DisplayString
   MAX-ACCESS  read-write
   STATUS      current
   DESCRIPTION
      "Path: ethernet3.editConf.linkStateTracking.trackedInterface"
   ::= {er1646v2Lan3FGLstEntry 16777216}


er1646v2Lan3FGDot1x OBJECT IDENTIFIER ::= {er1646v2Lan3FG 191}

er1646v2Lan3FGDot1xSSC OBJECT IDENTIFIER ::= {er1646v2Lan3FGDot1x 1}

er1646v2Lan3FGDot1xEntry OBJECT IDENTIFIER ::= {er1646v2Lan3FGDot1xSSC 1}

er1646v2Lan3FGDot1xMode OBJECT-TYPE
   SYNTAX      INTEGER
               {
               inactive (0),
               auto (1)
               }
   MAX-ACCESS  read-write
   STATUS      current
   DESCRIPTION
      "Path: ethernet3.editConf.dot1x.mode

       Possibilities:
               inactive   (0)
               auto   (1)"
   ::= {er1646v2Lan3FGDot1xEntry 16777216}

er1646v2Lan3FGDot1xMaxHosts OBJECT-TYPE
   SYNTAX      Integer32
   MAX-ACCESS  read-write
   STATUS      current
   DESCRIPTION
      "Path: ethernet3.editConf.dot1x.maxHosts"
   ::= {er1646v2Lan3FGDot1xEntry 33554432}

er1646v2Lan3FGDot1xReAuthentication OBJECT-TYPE
   SYNTAX      INTEGER
               {
               disabled (0),
               enabled (1)
               }
   MAX-ACCESS  read-write
   STATUS      current
   DESCRIPTION
      "Path: ethernet3.editConf.dot1x.reAuthentication

       Possibilities:
               disabled   (0)
               enabled   (1)"
   ::= {er1646v2Lan3FGDot1xEntry 50331648}

er1646v2Lan3FGDot1xReAuthPeriod OBJECT-TYPE
   SYNTAX      TimeTicks
   MAX-ACCESS  read-write
   STATUS      current
   DESCRIPTION
      "Path: ethernet3.editConf.dot1x.reAuthPeriod

       Time in centi-second."
   ::= {er1646v2Lan3FGDot1xEntry 67108864}

er1646v2Lan3FGDot1xQuietPeriod OBJECT-TYPE
   SYNTAX      TimeTicks
   MAX-ACCESS  read-write
   STATUS      current
   DESCRIPTION
      "Path: ethernet3.editConf.dot1x.quietPeriod

       Time in centi-second."
   ::= {er1646v2Lan3FGDot1xEntry 83886080}

er1646v2Lan3FGDot1xSupplTimeout OBJECT-TYPE
   SYNTAX      TimeTicks
   MAX-ACCESS  read-write
   STATUS      current
   DESCRIPTION
      "Path: ethernet3.editConf.dot1x.supplTimeout

       Time in centi-second."
   ::= {er1646v2Lan3FGDot1xEntry 100663296}

er1646v2Lan3FGDot1xServerTimeout OBJECT-TYPE
   SYNTAX      TimeTicks
   MAX-ACCESS  read-write
   STATUS      current
   DESCRIPTION
      "Path: ethernet3.editConf.dot1x.serverTimeout

       Time in centi-second."
   ::= {er1646v2Lan3FGDot1xEntry 117440512}

er1646v2Lan3FGDot1xMaxReqCount OBJECT-TYPE
   SYNTAX      Integer32
   MAX-ACCESS  read-write
   STATUS      current
   DESCRIPTION
      "Path: ethernet3.editConf.dot1x.maxReqCount"
   ::= {er1646v2Lan3FGDot1xEntry 134217728}


er1646v2Lan3FGMode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: ethernet3.editConf.mode
       Info: routing and/or bridging or ipV6 or multilink selection

       Possibilities:
               bridging   (0)
               routing   (1)
               routingAndBridging   (2)
               ipV6   (3)
               ipV6/ipV4   (4)
               multilink   (5)"
   ::= {er1646v2Lan3FG 29}


er1646v2Lan3FGIpV6 OBJECT IDENTIFIER ::= {er1646v2Lan3FG 15}

er1646v2Lan3FGIpV6SSC OBJECT IDENTIFIER ::= {er1646v2Lan3FGIpV6 1}

er1646v2Lan3FGIpV6Entry OBJECT IDENTIFIER ::= {er1646v2Lan3FGIpV6SSC 1}

er1646v2Lan3FGIpV6VrfRouter OBJECT-TYPE
   SYNTAX      DisplayString
   MAX-ACCESS  read-write
   STATUS      current
   DESCRIPTION
      "Path: ethernet3.editConf.ipV6.vrfRouter"
   ::= {er1646v2Lan3FGIpV6Entry 16777216}

er1646v2Lan3FGIpV6AddrAutoConfigNrDupAddrDetects OBJECT-TYPE
   SYNTAX      Integer32
   MAX-ACCESS  read-write
   STATUS      current
   DESCRIPTION
      "Path: ethernet3.editConf.ipV6.addrAutoConfig.nrDupAddrDetects"
   ::= {er1646v2Lan3FGIpV6Entry 67174400}

er1646v2Lan3FGIpV6AddrAutoConfigAcceptRa OBJECT-TYPE
   SYNTAX      INTEGER
               {
               disabled (0),
               enabled (1)
               }
   MAX-ACCESS  read-write
   STATUS      current
   DESCRIPTION
      "Path: ethernet3.editConf.ipV6.addrAutoConfig.acceptRa

       Possibilities:
               disabled   (0)
               enabled   (1)"
   ::= {er1646v2Lan3FGIpV6Entry 67239936}

er1646v2Lan3FGIpV6AddrAutoConfigAcceptRaRdnss OBJECT-TYPE
   SYNTAX      INTEGER
               {
               disabled (0),
               enabled (1)
               }
   MAX-ACCESS  read-write
   STATUS      current
   DESCRIPTION
      "Path: ethernet3.editConf.ipV6.addrAutoConfig.acceptRaRdnss

       Possibilities:
               disabled   (0)
               enabled   (1)"
   ::= {er1646v2Lan3FGIpV6Entry 67305472}

er1646v2Lan3FGIpV6AddrAutoConfigAcceptRaDnssl OBJECT-TYPE
   SYNTAX      INTEGER
               {
               disabled (0),
               enabled (1)
               }
   MAX-ACCESS  read-write
   STATUS      current
   DESCRIPTION
      "Path: ethernet3.editConf.ipV6.addrAutoConfig.acceptRaDnssl

       Possibilities:
               disabled   (0)
               enabled   (1)"
   ::= {er1646v2Lan3FGIpV6Entry 67371008}

er1646v2Lan3FGIpV6DefaultRoute OBJECT-TYPE
   SYNTAX      INTEGER
               {
               disabled (0),
               enabled (1)
               }
   MAX-ACCESS  read-write
   STATUS      current
   DESCRIPTION
      "Path: ethernet3.editConf.ipV6.defaultRoute

       Possibilities:
               disabled   (0)
               enabled   (1)"
   ::= {er1646v2Lan3FGIpV6Entry 83886080}

er1646v2Lan3FGIpV6RaSend OBJECT-TYPE
   SYNTAX      INTEGER
               {
               disabled (0),
               enabled (1)
               }
   MAX-ACCESS  read-write
   STATUS      current
   DESCRIPTION
      "Path: ethernet3.editConf.ipV6.ra.send

       Possibilities:
               disabled   (0)
               enabled   (1)"
   ::= {er1646v2Lan3FGIpV6Entry 100728832}

er1646v2Lan3FGIpV6RaMinInterval OBJECT-TYPE
   SYNTAX      TimeTicks
   MAX-ACCESS  read-write
   STATUS      current
   DESCRIPTION
      "Path: ethernet3.editConf.ipV6.ra.minInterval

       Time in centi-second."
   ::= {er1646v2Lan3FGIpV6Entry 100794368}

er1646v2Lan3FGIpV6RaMaxInterval OBJECT-TYPE
   SYNTAX      TimeTicks
   MAX-ACCESS  read-write
   STATUS      current
   DESCRIPTION
      "Path: ethernet3.editConf.ipV6.ra.maxInterval

       Time in centi-second."
   ::= {er1646v2Lan3FGIpV6Entry 100859904}

er1646v2Lan3FGIpV6RaManagedFlag OBJECT-TYPE
   SYNTAX      INTEGER
               {
               disabled (0),
               enabled (1)
               }
   MAX-ACCESS  read-write
   STATUS      current
   DESCRIPTION
      "Path: ethernet3.editConf.ipV6.ra.managedFlag

       Possibilities:
               disabled   (0)
               enabled   (1)"
   ::= {er1646v2Lan3FGIpV6Entry 100925440}

er1646v2Lan3FGIpV6RaOtherConfFlag OBJECT-TYPE
   SYNTAX      INTEGER
               {
               disabled (0),
               enabled (1)
               }
   MAX-ACCESS  read-write
   STATUS      current
   DESCRIPTION
      "Path: ethernet3.editConf.ipV6.ra.otherConfFlag

       Possibilities:
               disabled   (0)
               enabled   (1)"
   ::= {er1646v2Lan3FGIpV6Entry 100990976}

er1646v2Lan3FGIpV6RaLinkMtu OBJECT-TYPE
   SYNTAX      Integer32
   MAX-ACCESS  read-write
   STATUS      current
   DESCRIPTION
      "Path: ethernet3.editConf.ipV6.ra.linkMtu"
   ::= {er1646v2Lan3FGIpV6Entry 101056512}

er1646v2Lan3FGIpV6RaReachableTime OBJECT-TYPE
   SYNTAX      TimeTicks
   MAX-ACCESS  read-write
   STATUS      current
   DESCRIPTION
      "Path: ethernet3.editConf.ipV6.ra.reachableTime

       Time in centi-second."
   ::= {er1646v2Lan3FGIpV6Entry 101122048}

er1646v2Lan3FGIpV6RaRetransmitTime OBJECT-TYPE
   SYNTAX      TimeTicks
   MAX-ACCESS  read-write
   STATUS      current
   DESCRIPTION
      "Path: ethernet3.editConf.ipV6.ra.retransmitTime

       Time in centi-second."
   ::= {er1646v2Lan3FGIpV6Entry 101187584}

er1646v2Lan3FGIpV6RaHopLimit OBJECT-TYPE
   SYNTAX      Integer32
   MAX-ACCESS  read-write
   STATUS      current
   DESCRIPTION
      "Path: ethernet3.editConf.ipV6.ra.hopLimit"
   ::= {er1646v2Lan3FGIpV6Entry 101253120}

er1646v2Lan3FGIpV6RaDefaultLifeTime OBJECT-TYPE
   SYNTAX      TimeTicks
   MAX-ACCESS  read-write
   STATUS      current
   DESCRIPTION
      "Path: ethernet3.editConf.ipV6.ra.defaultLifeTime

       Time in centi-second."
   ::= {er1646v2Lan3FGIpV6Entry 101318656}

er1646v2Lan3FGIpV6RaDnsOptionsRdnssLifeTime OBJECT-TYPE
   SYNTAX      TimeTicks
   MAX-ACCESS  read-write
   STATUS      current
   DESCRIPTION
      "Path: ethernet3.editConf.ipV6.ra.dnsOptions.rdnss.lifeTime

       Time in centi-second."
   ::= {er1646v2Lan3FGIpV6Entry 101393408}

er1646v2Lan3FGIpV6RaDnsOptionsRdnssImportServers OBJECT-TYPE
   SYNTAX      INTEGER
               {
               disabled (0),
               enabled (1)
               }
   MAX-ACCESS  read-write
   STATUS      current
   DESCRIPTION
      "Path: ethernet3.editConf.ipV6.ra.dnsOptions.rdnss.importServers

       Possibilities:
               disabled   (0)
               enabled   (1)"
   ::= {er1646v2Lan3FGIpV6Entry 101395456}

er1646v2Lan3FGIpV6RaDnsOptionsDnsslLifeTime OBJECT-TYPE
   SYNTAX      TimeTicks
   MAX-ACCESS  read-write
   STATUS      current
   DESCRIPTION
      "Path: ethernet3.editConf.ipV6.ra.dnsOptions.dnssl.lifeTime

       Time in centi-second."
   ::= {er1646v2Lan3FGIpV6Entry 101401600}

er1646v2Lan3FGIpV6RaDnsOptionsDnsslImportDomains OBJECT-TYPE
   SYNTAX      INTEGER
               {
               disabled (0),
               enabled (1)
               }
   MAX-ACCESS  read-write
   STATUS      current
   DESCRIPTION
      "Path: ethernet3.editConf.ipV6.ra.dnsOptions.dnssl.importDomains

       Possibilities:
               disabled   (0)
               enabled   (1)"
   ::= {er1646v2Lan3FGIpV6Entry 101403648}

er1646v2Lan3FGIpV6RsSend OBJECT-TYPE
   SYNTAX      INTEGER
               {
               disabled (0),
               enabled (1)
               }
   MAX-ACCESS  read-write
   STATUS      current
   DESCRIPTION
      "Path: ethernet3.editConf.ipV6.rs.send

       Possibilities:
               disabled   (0)
               enabled   (1)"
   ::= {er1646v2Lan3FGIpV6Entry 335609856}

er1646v2Lan3FGIpV6RsMaxRandomDelay OBJECT-TYPE
   SYNTAX      TimeTicks
   MAX-ACCESS  read-write
   STATUS      current
   DESCRIPTION
      "Path: ethernet3.editConf.ipV6.rs.maxRandomDelay

       Time in centi-second."
   ::= {er1646v2Lan3FGIpV6Entry 335675392}

er1646v2Lan3FGIpV6RsInterval OBJECT-TYPE
   SYNTAX      TimeTicks
   MAX-ACCESS  read-write
   STATUS      current
   DESCRIPTION
      "Path: ethernet3.editConf.ipV6.rs.interval

       Time in centi-second."
   ::= {er1646v2Lan3FGIpV6Entry 335740928}

er1646v2Lan3FGIpV6RsMaxSolicitations OBJECT-TYPE
   SYNTAX      Integer32
   MAX-ACCESS  read-write
   STATUS      current
   DESCRIPTION
      "Path: ethernet3.editConf.ipV6.rs.maxSolicitations"
   ::= {er1646v2Lan3FGIpV6Entry 335806464}

er1646v2Lan3FGIpV6TrafficPolicyInbound OBJECT-TYPE
   SYNTAX      DisplayString
   MAX-ACCESS  read-write
   STATUS      current
   DESCRIPTION
      "Path: ethernet3.editConf.ipV6.trafficPolicy.inbound"
   ::= {er1646v2Lan3FGIpV6Entry 184614912}

er1646v2Lan3FGIpV6TrafficPolicyOutbound OBJECT-TYPE
   SYNTAX      DisplayString
   MAX-ACCESS  read-write
   STATUS      current
   DESCRIPTION
      "Path: ethernet3.editConf.ipV6.trafficPolicy.outbound"
   ::= {er1646v2Lan3FGIpV6Entry 184680448}

er1646v2Lan3FGIpV6FirewallZone OBJECT-TYPE
   SYNTAX      DisplayString
   MAX-ACCESS  read-write
   STATUS      current
   DESCRIPTION
      "Path: ethernet3.editConf.ipV6.firewall.zone"
   ::= {er1646v2Lan3FGIpV6Entry 201392128}

er1646v2Lan3FGIpV6DhcpClientAddrAC OBJECT-TYPE
   SYNTAX      INTEGER
               {
               disabled (0),
               enabled (1)
               }
   MAX-ACCESS  read-write
   STATUS      current
   DESCRIPTION
      "Path: ethernet3.editConf.ipV6.dhcp.client.addrAutoConfig

       Possibilities:
               disabled   (0)
               enabled   (1)"
   ::= {er1646v2Lan3FGIpV6Entry 170131456}

er1646v2Lan3FGIpV6DhcpClientPrDelMode OBJECT-TYPE
   SYNTAX      INTEGER
               {
               disabled (0),
               enabled (1)
               }
   MAX-ACCESS  read-write
   STATUS      current
   DESCRIPTION
      "Path: ethernet3.editConf.ipV6.dhcp.client.pd.mode

       Possibilities:
               disabled   (0)
               enabled   (1)"
   ::= {er1646v2Lan3FGIpV6Entry 170394624}

er1646v2Lan3FGIpV6DhcpClientPrDelPool OBJECT-TYPE
   SYNTAX      DisplayString
   MAX-ACCESS  read-write
   STATUS      current
   DESCRIPTION
      "Path: ethernet3.editConf.ipV6.dhcp.client.pd.pool"
   ::= {er1646v2Lan3FGIpV6Entry 170395648}

er1646v2Lan3FGIpV6DhcpClientPrDelPdExclOpt OBJECT-TYPE
   SYNTAX      INTEGER
               {
               disabled (0),
               enabled (1)
               }
   MAX-ACCESS  read-write
   STATUS      current
   DESCRIPTION
      "Path: ethernet3.editConf.ipV6.dhcp.client.pd.pdExclOpt

       Possibilities:
               disabled   (0)
               enabled   (1)"
   ::= {er1646v2Lan3FGIpV6Entry 170396672}

er1646v2Lan3FGIpV6DhcpClientDnsServerPref OBJECT-TYPE
   SYNTAX      Integer32
   MAX-ACCESS  read-write
   STATUS      current
   DESCRIPTION
      "Path: ethernet3.editConf.ipV6.dhcp.client.dns.serverPref"
   ::= {er1646v2Lan3FGIpV6Entry 170918912}

er1646v2Lan3FGIpV6DhcpClientRapidCommit OBJECT-TYPE
   SYNTAX      INTEGER
               {
               disabled (0),
               enabled (1)
               }
   MAX-ACCESS  read-write
   STATUS      current
   DESCRIPTION
      "Path: ethernet3.editConf.ipV6.dhcp.client.rapidCommit

       Possibilities:
               disabled   (0)
               enabled   (1)"
   ::= {er1646v2Lan3FGIpV6Entry 170655744}

er1646v2Lan3FGIpV6DhcpClientTimersSolTimeOut OBJECT-TYPE
   SYNTAX      TimeTicks
   MAX-ACCESS  read-write
   STATUS      current
   DESCRIPTION
      "Path: ethernet3.editConf.ipV6.dhcp.client.timers.solTimeOut

       Time in centi-second."
   ::= {er1646v2Lan3FGIpV6Entry 171181056}

er1646v2Lan3FGIpV6DhcpClientTimersSolMaxRt OBJECT-TYPE
   SYNTAX      TimeTicks
   MAX-ACCESS  read-write
   STATUS      current
   DESCRIPTION
      "Path: ethernet3.editConf.ipV6.dhcp.client.timers.solMaxRt

       Time in centi-second."
   ::= {er1646v2Lan3FGIpV6Entry 171182080}

er1646v2Lan3FGIpV6DhcpClientTimersInfoRefresh OBJECT-TYPE
   SYNTAX      TimeTicks
   MAX-ACCESS  read-write
   STATUS      current
   DESCRIPTION
      "Path: ethernet3.editConf.ipV6.dhcp.client.timers.infoRefresh

       Time in centi-second."
   ::= {er1646v2Lan3FGIpV6Entry 171183104}

er1646v2Lan3FGIpV6DhcpServerMode OBJECT-TYPE
   SYNTAX      INTEGER
               {
               disabled (0),
               enabled (1)
               }
   MAX-ACCESS  read-write
   STATUS      current
   DESCRIPTION
      "Path: ethernet3.editConf.ipV6.dhcp.server.mode

       Possibilities:
               disabled   (0)
               enabled   (1)"
   ::= {er1646v2Lan3FGIpV6Entry 172228608}

er1646v2Lan3FGIpV6DhcpServerPreference OBJECT-TYPE
   SYNTAX      Integer32
   MAX-ACCESS  read-write
   STATUS      current
   DESCRIPTION
      "Path: ethernet3.editConf.ipV6.dhcp.server.preference"
   ::= {er1646v2Lan3FGIpV6Entry 172490752}

er1646v2Lan3FGIpV6DhcpServerPool OBJECT-TYPE
   SYNTAX      DisplayString
   MAX-ACCESS  read-write
   STATUS      current
   DESCRIPTION
      "Path: ethernet3.editConf.ipV6.dhcp.server.pool"
   ::= {er1646v2Lan3FGIpV6Entry 172752896}

er1646v2Lan3FGIpV6DhcpServerRapidCommit OBJECT-TYPE
   SYNTAX      INTEGER
               {
               disabled (0),
               enabled (1)
               }
   MAX-ACCESS  read-write
   STATUS      current
   DESCRIPTION
      "Path: ethernet3.editConf.ipV6.dhcp.server.rapidCommit

       Possibilities:
               disabled   (0)
               enabled   (1)"
   ::= {er1646v2Lan3FGIpV6Entry 173015040}

er1646v2Lan3FGIpV6DhcpServerTimersInfoRefresh OBJECT-TYPE
   SYNTAX      TimeTicks
   MAX-ACCESS  read-write
   STATUS      current
   DESCRIPTION
      "Path: ethernet3.editConf.ipV6.dhcp.server.timers.infoRefresh

       Time in centi-second."
   ::= {er1646v2Lan3FGIpV6Entry 173278208}

er1646v2Lan3FGIpV6DhcpRelayMode OBJECT-TYPE
   SYNTAX      INTEGER
               {
               disabled (0),
               enabled (1)
               }
   MAX-ACCESS  read-write
   STATUS      current
   DESCRIPTION
      "Path: ethernet3.editConf.ipV6.dhcp.relay.mode

       Possibilities:
               disabled   (0)
               enabled   (1)"
   ::= {er1646v2Lan3FGIpV6Entry 174071808}

er1646v2Lan3FGIpV6SendRedirect OBJECT-TYPE
   SYNTAX      INTEGER
               {
               disabled (0),
               enabled (1)
               }
   MAX-ACCESS  read-write
   STATUS      current
   DESCRIPTION
      "Path: ethernet3.editConf.ipV6.sendRedirect

       Possibilities:
               disabled   (0)
               enabled   (1)"
   ::= {er1646v2Lan3FGIpV6Entry 117440512}

er1646v2Lan3FGIpV6LinkMtu OBJECT-TYPE
   SYNTAX      Integer32
   MAX-ACCESS  read-write
   STATUS      current
   DESCRIPTION
      "Path: ethernet3.editConf.ipV6.linkMtu"
   ::= {er1646v2Lan3FGIpV6Entry 134217728}

er1646v2Lan3FGIpV6InterfaceId OBJECT-TYPE
   SYNTAX      OCTET STRING
   MAX-ACCESS  read-write
   STATUS      current
   DESCRIPTION
      "Path: ethernet3.editConf.ipV6.interfaceId"
   ::= {er1646v2Lan3FGIpV6Entry 150994944}

er1646v2Lan3FGIpV6MF OBJECT-TYPE
   SYNTAX      Integer32
   MAX-ACCESS  read-write
   STATUS      current
   DESCRIPTION
      "Path: ethernet3.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2Lan3FGIpV6Entry 285212672}

er1646v2Lan3FGIpV6IcmpMessagesNoRoute OBJECT-TYPE
   SYNTAX      INTEGER
               {
               disabled (0),
               enabled (1)
               }
   MAX-ACCESS  read-write
   STATUS      current
   DESCRIPTION
      "Path: ethernet3.editConf.ipV6.icmpMessages.noRoute

       Possibilities:
               disabled   (0)
               enabled   (1)"
   ::= {er1646v2Lan3FGIpV6Entry 302055424}

er1646v2Lan3FGIpV6IcmpMessagesBeyondScope OBJECT-TYPE
   SYNTAX      INTEGER
               {
               disabled (0),
               enabled (1)
               }
   MAX-ACCESS  read-write
   STATUS      current
   DESCRIPTION
      "Path: ethernet3.editConf.ipV6.icmpMessages.beyondScope

       Possibilities:
               disabled   (0)
               enabled   (1)"
   ::= {er1646v2Lan3FGIpV6Entry 302186496}

er1646v2Lan3FGIpV6IcmpMessagesAddressUnreachable OBJECT-TYPE
   SYNTAX      INTEGER
               {
               disabled (0),
               enabled (1)
               }
   MAX-ACCESS  read-write
   STATUS      current
   DESCRIPTION
      "Path: ethernet3.editConf.ipV6.icmpMessages.addressUnreachable

       Possibilities:
               disabled   (0)
               enabled   (1)"
   ::= {er1646v2Lan3FGIpV6Entry 302252032}

er1646v2Lan3FGIpV6IcmpMessagesPortUnreachable OBJECT-TYPE
   SYNTAX      INTEGER
               {
               disabled (0),
               enabled (1)
               }
   MAX-ACCESS  read-write
   STATUS      current
   DESCRIPTION
      "Path: ethernet3.editConf.ipV6.icmpMessages.portUnreachable

       Possibilities:
               disabled   (0)
               enabled   (1)"
   ::= {er1646v2Lan3FGIpV6Entry 302317568}

er1646v2Lan3FGIpV6IcmpMessagesPacketTooBig OBJECT-TYPE
   SYNTAX      INTEGER
               {
               disabled (0),
               enabled (1)
               }
   MAX-ACCESS  read-write
   STATUS      current
   DESCRIPTION
      "Path: ethernet3.editConf.ipV6.icmpMessages.packetTooBig

       Possibilities:
               disabled   (0)
               enabled   (1)"
   ::= {er1646v2Lan3FGIpV6Entry 302645248}

er1646v2Lan3FGIpV6IcmpMessagesHopLimitExceeded OBJECT-TYPE
   SYNTAX      INTEGER
               {
               disabled (0),
               enabled (1)
               }
   MAX-ACCESS  read-write
   STATUS      current
   DESCRIPTION
      "Path: ethernet3.editConf.ipV6.icmpMessages.hopLimitExceeded

       Possibilities:
               disabled   (0)
               enabled   (1)"
   ::= {er1646v2Lan3FGIpV6Entry 303300608}

er1646v2Lan3FGIpV6IcmpMessagesFragTimeExceeded OBJECT-TYPE
   SYNTAX      INTEGER
               {
               disabled (0),
               enabled (1)
               }
   MAX-ACCESS  read-write
   STATUS      current
   DESCRIPTION
      "Path: ethernet3.editConf.ipV6.icmpMessages.fragTimeExceeded

       Possibilities:
               disabled   (0)
               enabled   (1)"
   ::= {er1646v2Lan3FGIpV6Entry 303366144}

er1646v2Lan3FGIpV6IcmpMessagesHeaderFieldErr OBJECT-TYPE
   SYNTAX      INTEGER
               {
               disabled (0),
               enabled (1)
               }
   MAX-ACCESS  read-write
   STATUS      current
   DESCRIPTION
      "Path: ethernet3.editConf.ipV6.icmpMessages.headerFieldErr

       Possibilities:
               disabled   (0)
               enabled   (1)"
   ::= {er1646v2Lan3FGIpV6Entry 303955968}

er1646v2Lan3FGIpV6IcmpMessagesOptionUnrecognized OBJECT-TYPE
   SYNTAX      INTEGER
               {
               disabled (0),
               enabled (1)
               }
   MAX-ACCESS  read-write
   STATUS      current
   DESCRIPTION
      "Path: ethernet3.editConf.ipV6.icmpMessages.optionUnrecognized

       Possibilities:
               disabled   (0)
               enabled   (1)"
   ::= {er1646v2Lan3FGIpV6Entry 304087040}

er1646v2Lan3FGIpV6IcmpMessagesRedirect OBJECT-TYPE
   SYNTAX      INTEGER
               {
               disabled (0),
               enabled (1)
               }
   MAX-ACCESS  read-write
   STATUS      current
   DESCRIPTION
      "Path: ethernet3.editConf.ipV6.icmpMessages.redirect

       Possibilities:
               disabled   (0)
               enabled   (1)"
   ::= {er1646v2Lan3FGIpV6Entry 304611328}

er1646v2Lan3FGIpV6Addresses OBJECT-TYPE
   SYNTAX      SEQUENCE OF Er1646v2Lan3FGIpV6AddressesEntry
   MAX-ACCESS  not-accessible
   STATUS      current
   DESCRIPTION
      ""
   ::= {er1646v2Lan3FGIpV6 50331648}

er1646v2Lan3FGIpV6AddressesEntry OBJECT-TYPE
   SYNTAX      Er1646v2Lan3FGIpV6AddressesEntry
   MAX-ACCESS  not-accessible
   STATUS      current
   DESCRIPTION
      ""
   INDEX      { er1646v2Lan3FGIpV6AddressesTableIx }
   ::= {er1646v2Lan3FGIpV6Addresses 1}

Er1646v2Lan3FGIpV6AddressesEntry ::=
   SEQUENCE
      {
      er1646v2Lan3FGIpV6AddressesActions
         VariableLengthTableActions,
      er1646v2Lan3FGIpV6AddressesTableIx
         TableIndex,
      er1646v2Lan3FGIpV6AddressesType
         INTEGER,
      er1646v2Lan3FGIpV6AddressesAddress
         Ipv6Address,
      er1646v2Lan3FGIpV6AddressesPrefixLength
         Integer32,
      er1646v2Lan3FGIpV6AddressesGeneralPrefix
         DisplayString,
      er1646v2Lan3FGIpV6AddressesRaSend
         INTEGER,
      er1646v2Lan3FGIpV6AddressesRaOnLinkFlag
         INTEGER,
      er1646v2Lan3FGIpV6AddressesRaAutoFlag
         INTEGER,
      er1646v2Lan3FGIpV6AddressesRaValidLifeTime
         TimeTicks,
      er1646v2Lan3FGIpV6AddressesRaValidLTMode
         INTEGER,
      er1646v2Lan3FGIpV6AddressesRaPrefLifeTime
         TimeTicks,
      er1646v2Lan3FGIpV6AddressesRaPrefLTMode
         INTEGER
      }

er1646v2Lan3FGIpV6AddressesActions OBJECT-TYPE
   SYNTAX      VariableLengthTableActions
   MAX-ACCESS  read-write
   STATUS      current
   DESCRIPTION
      "By way of this field, some manipulations
       on this table may be performed."
   ::= {er1646v2Lan3FGIpV6AddressesEntry 2}

er1646v2Lan3FGIpV6AddressesTableIx OBJECT-TYPE
   SYNTAX      TableIndex
   MAX-ACCESS  not-accessible
   STATUS      current
   DESCRIPTION
      ""
   ::= {er1646v2Lan3FGIpV6AddressesEntry 11}

er1646v2Lan3FGIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.ipV6.addresses.type

       Possibilities:
               unicast   (0)
               eui64   (1)
               anycast   (2)
               linkLocal   (3)
               generalPrefix   (4)"
   ::= {er1646v2Lan3FGIpV6AddressesEntry 50331648}

er1646v2Lan3FGIpV6AddressesAddress OBJECT-TYPE
   SYNTAX      Ipv6Address
   MAX-ACCESS  read-write
   STATUS      current
   DESCRIPTION
      "Path: ethernet3.editConf.ipV6.addresses.address

       ipv6 address"
   ::= {er1646v2Lan3FGIpV6AddressesEntry 16777216}

er1646v2Lan3FGIpV6AddressesPrefixLength OBJECT-TYPE
   SYNTAX      Integer32
   MAX-ACCESS  read-write
   STATUS      current
   DESCRIPTION
      "Path: ethernet3.editConf.ipV6.addresses.prefixLength"
   ::= {er1646v2Lan3FGIpV6AddressesEntry 33554432}

er1646v2Lan3FGIpV6AddressesGeneralPrefix OBJECT-TYPE
   SYNTAX      DisplayString
   MAX-ACCESS  read-write
   STATUS      current
   DESCRIPTION
      "Path: ethernet3.editConf.ipV6.addresses.generalPrefix"
   ::= {er1646v2Lan3FGIpV6AddressesEntry 83886080}

er1646v2Lan3FGIpV6AddressesRaSend OBJECT-TYPE
   SYNTAX      INTEGER
               {
               disabled (0),
               enabled (1)
               }
   MAX-ACCESS  read-write
   STATUS      current
   DESCRIPTION
      "Path: ethernet3.editConf.ipV6.addresses.ra.send

       Possibilities:
               disabled   (0)
               enabled   (1)"
   ::= {er1646v2Lan3FGIpV6AddressesEntry 67174400}

er1646v2Lan3FGIpV6AddressesRaOnLinkFlag OBJECT-TYPE
   SYNTAX      INTEGER
               {
               disabled (0),
               enabled (1)
               }
   MAX-ACCESS  read-write
   STATUS      current
   DESCRIPTION
      "Path: ethernet3.editConf.ipV6.addresses.ra.onLinkFlag

       Possibilities:
               disabled   (0)
               enabled   (1)"
   ::= {er1646v2Lan3FGIpV6AddressesEntry 67371008}

er1646v2Lan3FGIpV6AddressesRaAutoFlag OBJECT-TYPE
   SYNTAX      INTEGER
               {
               disabled (0),
               enabled (1)
               }
   MAX-ACCESS  read-write
   STATUS      current
   DESCRIPTION
      "Path: ethernet3.editConf.ipV6.addresses.ra.autonomousFlag

       Possibilities:
               disabled   (0)
               enabled   (1)"
   ::= {er1646v2Lan3FGIpV6AddressesEntry 67567616}

er1646v2Lan3FGIpV6AddressesRaValidLifeTime OBJECT-TYPE
   SYNTAX      TimeTicks
   MAX-ACCESS  read-write
   STATUS      current
   DESCRIPTION
      "Path: ethernet3.editConf.ipV6.addresses.ra.validLifeTime

       Time in centi-second."
   ::= {er1646v2Lan3FGIpV6AddressesEntry 67239936}

er1646v2Lan3FGIpV6AddressesRaValidLTMode OBJECT-TYPE
   SYNTAX      INTEGER
               {
               fixed (0),
               infinite (2)
               }
   MAX-ACCESS  read-write
   STATUS      current
   DESCRIPTION
      "Path: ethernet3.editConf.ipV6.addresses.ra.validLifeTimeMode

       Possibilities:
               fixed   (0)
               infinite   (2)"
   ::= {er1646v2Lan3FGIpV6AddressesEntry 67305472}

er1646v2Lan3FGIpV6AddressesRaPrefLifeTime OBJECT-TYPE
   SYNTAX      TimeTicks
   MAX-ACCESS  read-write
   STATUS      current
   DESCRIPTION
      "Path: ethernet3.editConf.ipV6.addresses.ra.prefLifeTime

       Time in centi-second."
   ::= {er1646v2Lan3FGIpV6AddressesEntry 67436544}

er1646v2Lan3FGIpV6AddressesRaPrefLTMode OBJECT-TYPE
   SYNTAX      INTEGER
               {
               fixed (0),
               infinite (2)
               }
   MAX-ACCESS  read-write
   STATUS      current
   DESCRIPTION
      "Path: ethernet3.editConf.ipV6.addresses.ra.prefLifeTimeMode

       Possibilities:
               fixed   (0)
               infinite   (2)"
   ::= {er1646v2Lan3FGIpV6AddressesEntry 67502080}

er1646v2Lan3FGIpV6RaDnsOptionsRdnssServers OBJECT-TYPE
   SYNTAX      SEQUENCE OF Er1646v2Lan3FGIpV6RaDnsOptionsRdnssServersEntry
   MAX-ACCESS  not-accessible
   STATUS      current
   DESCRIPTION
      ""
   ::= {er1646v2Lan3FGIpV6 101394432}

er1646v2Lan3FGIpV6RaDnsOptionsRdnssServersEntry OBJECT-TYPE
   SYNTAX      Er1646v2Lan3FGIpV6RaDnsOptionsRdnssServersEntry
   MAX-ACCESS  not-accessible
   STATUS      current
   DESCRIPTION
      ""
   INDEX      { er1646v2Lan3FGIpV6RaDnsOptionsRdnssServersTableIx }
   ::= {er1646v2Lan3FGIpV6RaDnsOptionsRdnssServers 1}

Er1646v2Lan3FGIpV6RaDnsOptionsRdnssServersEntry ::=
   SEQUENCE
      {
      er1646v2Lan3FGIpV6RaDnsOptionsRdnssServersActions
         VariableLengthTableActions,
      er1646v2Lan3FGIpV6RaDnsOptionsRdnssServersTableIx
         TableIndex,
      er1646v2Lan3FGIpV6RaDnsOptionsRdnssServersAddress
         Ipv6Address
      }

er1646v2Lan3FGIpV6RaDnsOptionsRdnssServersActions OBJECT-TYPE
   SYNTAX      VariableLengthTableActions
   MAX-ACCESS  read-write
   STATUS      current
   DESCRIPTION
      "By way of this field, some manipulations
       on this table may be performed."
   ::= {er1646v2Lan3FGIpV6RaDnsOptionsRdnssServersEntry 2}

er1646v2Lan3FGIpV6RaDnsOptionsRdnssServersTableIx OBJECT-TYPE
   SYNTAX      TableIndex
   MAX-ACCESS  not-accessible
   STATUS      current
   DESCRIPTION
      ""
   ::= {er1646v2Lan3FGIpV6RaDnsOptionsRdnssServersEntry 11}

er1646v2Lan3FGIpV6RaDnsOptionsRdnssServersAddress OBJECT-TYPE
   SYNTAX      Ipv6Address
   MAX-ACCESS  read-write
   STATUS      current
   DESCRIPTION
      "Path: ethernet3.editConf.ipV6.ra.dnsOptions.rdnss.servers.address

       ipv6 address"
   ::= {er1646v2Lan3FGIpV6RaDnsOptionsRdnssServersEntry 16777216}

er1646v2Lan3FGIpV6RaDnsOptionsDnsslDomains OBJECT-TYPE
   SYNTAX      SEQUENCE OF Er1646v2Lan3FGIpV6RaDnsOptionsDnsslDomainsEntry
   MAX-ACCESS  not-accessible
   STATUS      current
   DESCRIPTION
      ""
   ::= {er1646v2Lan3FGIpV6 101402624}

er1646v2Lan3FGIpV6RaDnsOptionsDnsslDomainsEntry OBJECT-TYPE
   SYNTAX      Er1646v2Lan3FGIpV6RaDnsOptionsDnsslDomainsEntry
   MAX-ACCESS  not-accessible
   STATUS      current
   DESCRIPTION
      ""
   INDEX      { er1646v2Lan3FGIpV6RaDnsOptionsDnsslDomainsTableIx }
   ::= {er1646v2Lan3FGIpV6RaDnsOptionsDnsslDomains 1}

Er1646v2Lan3FGIpV6RaDnsOptionsDnsslDomainsEntry ::=
   SEQUENCE
      {
      er1646v2Lan3FGIpV6RaDnsOptionsDnsslDomainsActions
         VariableLengthTableActions,
      er1646v2Lan3FGIpV6RaDnsOptionsDnsslDomainsTableIx
         TableIndex,
      er1646v2Lan3FGIpV6RaDnsOptionsDnsslDomainsName
         DisplayString
      }

er1646v2Lan3FGIpV6RaDnsOptionsDnsslDomainsActions OBJECT-TYPE
   SYNTAX      VariableLengthTableActions
   MAX-ACCESS  read-write
   STATUS      current
   DESCRIPTION
      "By way of this field, some manipulations
       on this table may be performed."
   ::= {er1646v2Lan3FGIpV6RaDnsOptionsDnsslDomainsEntry 2}

er1646v2Lan3FGIpV6RaDnsOptionsDnsslDomainsTableIx OBJECT-TYPE
   SYNTAX      TableIndex
   MAX-ACCESS  not-accessible
   STATUS      current
   DESCRIPTION
      ""
   ::= {er1646v2Lan3FGIpV6RaDnsOptionsDnsslDomainsEntry 11}

er1646v2Lan3FGIpV6RaDnsOptionsDnsslDomainsName OBJECT-TYPE
   SYNTAX      DisplayString
   MAX-ACCESS  read-write
   STATUS      current
   DESCRIPTION
      "Path: ethernet3.editConf.ipV6.ra.dnsOptions.dnssl.domains.name"
   ::= {er1646v2Lan3FGIpV6RaDnsOptionsDnsslDomainsEntry 16777216}

er1646v2Lan3FGIpV6DhcpClientUserClassOpt OBJECT-TYPE
   SYNTAX      SEQUENCE OF Er1646v2Lan3FGIpV6DhcpClientUserClassOptEntry
   MAX-ACCESS  not-accessible
   STATUS      current
   DESCRIPTION
      ""
   ::= {er1646v2Lan3FGIpV6 171442176}

er1646v2Lan3FGIpV6DhcpClientUserClassOptEntry OBJECT-TYPE
   SYNTAX      Er1646v2Lan3FGIpV6DhcpClientUserClassOptEntry
   MAX-ACCESS  not-accessible
   STATUS      current
   DESCRIPTION
      ""
   INDEX      { er1646v2Lan3FGIpV6DhcpClientUserClassOptTableIx }
   ::= {er1646v2Lan3FGIpV6DhcpClientUserClassOpt 1}

Er1646v2Lan3FGIpV6DhcpClientUserClassOptEntry ::=
   SEQUENCE
      {
      er1646v2Lan3FGIpV6DhcpClientUserClassOptActions
         VariableLengthTableActions,
      er1646v2Lan3FGIpV6DhcpClientUserClassOptTableIx
         TableIndex,
      er1646v2Lan3FGIpV6DhcpClientUserClassOptValueAscii
         DisplayString,
      er1646v2Lan3FGIpV6DhcpClientUserClassOptValueDecimal
         Integer32,
      er1646v2Lan3FGIpV6DhcpClientUserClassOptValueHexData
         OCTET STRING
      }

er1646v2Lan3FGIpV6DhcpClientUserClassOptActions OBJECT-TYPE
   SYNTAX      VariableLengthTableActions
   MAX-ACCESS  read-write
   STATUS      current
   DESCRIPTION
      "By way of this field, some manipulations
       on this table may be performed."
   ::= {er1646v2Lan3FGIpV6DhcpClientUserClassOptEntry 2}

er1646v2Lan3FGIpV6DhcpClientUserClassOptTableIx OBJECT-TYPE
   SYNTAX      TableIndex
   MAX-ACCESS  not-accessible
   STATUS      current
   DESCRIPTION
      ""
   ::= {er1646v2Lan3FGIpV6DhcpClientUserClassOptEntry 11}

er1646v2Lan3FGIpV6DhcpClientUserClassOptValueAscii OBJECT-TYPE
   SYNTAX      DisplayString
   MAX-ACCESS  read-write
   STATUS      current
   DESCRIPTION
      "Path: ethernet3.editConf.ipV6.dhcp.client.userClassOpt.value.ascii"
   ::= {er1646v2Lan3FGIpV6DhcpClientUserClassOptEntry 16842752}

er1646v2Lan3FGIpV6DhcpClientUserClassOptValueDecimal OBJECT-TYPE
   SYNTAX      Integer32
   MAX-ACCESS  read-write
   STATUS      current
   DESCRIPTION
      "Path: ethernet3.editConf.ipV6.dhcp.client.userClassOpt.value.decimal"
   ::= {er1646v2Lan3FGIpV6DhcpClientUserClassOptEntry 16908288}

er1646v2Lan3FGIpV6DhcpClientUserClassOptValueHexData OBJECT-TYPE
   SYNTAX      OCTET STRING
   MAX-ACCESS  read-write
   STATUS      current
   DESCRIPTION
      "Path: ethernet3.editConf.ipV6.dhcp.client.userClassOpt.value.hexData"
   ::= {er1646v2Lan3FGIpV6DhcpClientUserClassOptEntry 16973824}

er1646v2Lan3FGIpV6DhcpClientVendorCl OBJECT-TYPE
   SYNTAX      SEQUENCE OF Er1646v2Lan3FGIpV6DhcpClientVendorClEntry
   MAX-ACCESS  not-accessible
   STATUS      current
   DESCRIPTION
      ""
   ::= {er1646v2Lan3FGIpV6 171704320}

er1646v2Lan3FGIpV6DhcpClientVendorClEntry OBJECT-TYPE
   SYNTAX      Er1646v2Lan3FGIpV6DhcpClientVendorClEntry
   MAX-ACCESS  not-accessible
   STATUS      current
   DESCRIPTION
      ""
   INDEX      { er1646v2Lan3FGIpV6DhcpClientVendorClTableIx }
   ::= {er1646v2Lan3FGIpV6DhcpClientVendorCl 1}

Er1646v2Lan3FGIpV6DhcpClientVendorClEntry ::=
   SEQUENCE
      {
      er1646v2Lan3FGIpV6DhcpClientVendorClActions
         VariableLengthTableActions,
      er1646v2Lan3FGIpV6DhcpClientVendorClTableIx
         TableIndex,
      er1646v2Lan3FGIpV6DhcpClientVendorClValueAscii
         DisplayString,
      er1646v2Lan3FGIpV6DhcpClientVendorClValueDecimal
         Integer32,
      er1646v2Lan3FGIpV6DhcpClientVendorClValueHexData
         OCTET STRING
      }

er1646v2Lan3FGIpV6DhcpClientVendorClActions OBJECT-TYPE
   SYNTAX      VariableLengthTableActions
   MAX-ACCESS  read-write
   STATUS      current
   DESCRIPTION
      "By way of this field, some manipulations
       on this table may be performed."
   ::= {er1646v2Lan3FGIpV6DhcpClientVendorClEntry 2}

er1646v2Lan3FGIpV6DhcpClientVendorClTableIx OBJECT-TYPE
   SYNTAX      TableIndex
   MAX-ACCESS  not-accessible
   STATUS      current
   DESCRIPTION
      ""
   ::= {er1646v2Lan3FGIpV6DhcpClientVendorClEntry 11}

er1646v2Lan3FGIpV6DhcpClientVendorClValueAscii OBJECT-TYPE
   SYNTAX      DisplayString
   MAX-ACCESS  read-write
   STATUS      current
   DESCRIPTION
      "Path: ethernet3.editConf.ipV6.dhcp.client.vendorClassOpt.value.ascii"
   ::= {er1646v2Lan3FGIpV6DhcpClientVendorClEntry 16842752}

er1646v2Lan3FGIpV6DhcpClientVendorClValueDecimal OBJECT-TYPE
   SYNTAX      Integer32
   MAX-ACCESS  read-write
   STATUS      current
   DESCRIPTION
      "Path: ethernet3.editConf.ipV6.dhcp.client.vendorClassOpt.value.decimal"
   ::= {er1646v2Lan3FGIpV6DhcpClientVendorClEntry 16908288}

er1646v2Lan3FGIpV6DhcpClientVendorClValueHexData OBJECT-TYPE
   SYNTAX      OCTET STRING
   MAX-ACCESS  read-write
   STATUS      current
   DESCRIPTION
      "Path: ethernet3.editConf.ipV6.dhcp.client.vendorClassOpt.value.hexData"
   ::= {er1646v2Lan3FGIpV6DhcpClientVendorClEntry 16973824}

er1646v2Lan3FGIpV6DhcpRelayDestinations OBJECT-TYPE
   SYNTAX      SEQUENCE OF Er1646v2Lan3FGIpV6DhcpRelayDestinationsEntry
   MAX-ACCESS  not-accessible
   STATUS      current
   DESCRIPTION
      ""
   ::= {er1646v2Lan3FGIpV6 174080000}

er1646v2Lan3FGIpV6DhcpRelayDestinationsEntry OBJECT-TYPE
   SYNTAX      Er1646v2Lan3FGIpV6DhcpRelayDestinationsEntry
   MAX-ACCESS  not-accessible
   STATUS      current
   DESCRIPTION
      ""
   INDEX      { er1646v2Lan3FGIpV6DhcpRelayDestinationsTableIx }
   ::= {er1646v2Lan3FGIpV6DhcpRelayDestinations 1}

Er1646v2Lan3FGIpV6DhcpRelayDestinationsEntry ::=
   SEQUENCE
      {
      er1646v2Lan3FGIpV6DhcpRelayDestinationsActions
         VariableLengthTableActions,
      er1646v2Lan3FGIpV6DhcpRelayDestinationsTableIx
         TableIndex,
      er1646v2Lan3FGIpV6DhcpRelayDestinationsAddress
         Ipv6Address,
      er1646v2Lan3FGIpV6DhcpRelayDestinationsInterface
         DisplayString
      }

er1646v2Lan3FGIpV6DhcpRelayDestinationsActions OBJECT-TYPE
   SYNTAX      VariableLengthTableActions
   MAX-ACCESS  read-write
   STATUS      current
   DESCRIPTION
      "By way of this field, some manipulations
       on this table may be performed."
   ::= {er1646v2Lan3FGIpV6DhcpRelayDestinationsEntry 2}

er1646v2Lan3FGIpV6DhcpRelayDestinationsTableIx OBJECT-TYPE
   SYNTAX      TableIndex
   MAX-ACCESS  not-accessible
   STATUS      current
   DESCRIPTION
      ""
   ::= {er1646v2Lan3FGIpV6DhcpRelayDestinationsEntry 11}

er1646v2Lan3FGIpV6DhcpRelayDestinationsAddress OBJECT-TYPE
   SYNTAX      Ipv6Address
   MAX-ACCESS  read-write
   STATUS      current
   DESCRIPTION
      "Path: ethernet3.editConf.ipV6.dhcp.relay.destinations.address

       ipv6 address"
   ::= {er1646v2Lan3FGIpV6DhcpRelayDestinationsEntry 16777216}

er1646v2Lan3FGIpV6DhcpRelayDestinationsInterface OBJECT-TYPE
   SYNTAX      DisplayString
   MAX-ACCESS  read-write
   STATUS      current
   DESCRIPTION
      "Path: ethernet3.editConf.ipV6.dhcp.relay.destinations.interface"
   ::= {er1646v2Lan3FGIpV6DhcpRelayDestinationsEntry 33554432}


er1646v2Lan3FGFlowControl OBJECT-TYPE
   SYNTAX      INTEGER
               {
               disabled (1),
               rx (2),
               tx (3),
               rxAndTx (4)
               }
   MAX-ACCESS  read-write
   STATUS      current
   DESCRIPTION
      "Path: ethernet3.editConf.flowControl
       Info: LAN flow control

       Possibilities:
               disabled   (1)
               rx   (2)
               tx   (3)
               rxAndTx   (4)"
   ::= {er1646v2Lan3FG 7}


er1646v2Lan3FGInboundNUcastPriority OBJECT IDENTIFIER ::= {er1646v2Lan3FG 230}

er1646v2Lan3FGInboundNUcastPrioritySSC OBJECT IDENTIFIER ::= {er1646v2Lan3FGInboundNUcastPriority 1}

er1646v2Lan3FGInboundNUcastPriorityEntry OBJECT IDENTIFIER ::= {er1646v2Lan3FGInboundNUcastPrioritySSC 1}

er1646v2Lan3FGInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.broadcast

       Possibilities:
               queue1   (0)
               queue2   (1)
               queue3   (2)
               queue4   (3)
               queue5   (4)
               lowDelayQueue   (5)
               lowDelay2Queue   (6)
               systemQueue   (7)"
   ::= {er1646v2Lan3FGInboundNUcastPriorityEntry 16777216}

er1646v2Lan3FGInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.inboundNUcastPriority.multicast

       Possibilities:
               queue1   (0)
               queue2   (1)
               queue3   (2)
               queue4   (3)
               queue5   (4)
               lowDelayQueue   (5)
               lowDelay2Queue   (6)
               systemQueue   (7)"
   ::= {er1646v2Lan3FGInboundNUcastPriorityEntry 33554432}


er1646v2Lan3FGIp OBJECT IDENTIFIER ::= {er1646v2Lan3FG 1}

er1646v2Lan3FGIpSSC OBJECT IDENTIFIER ::= {er1646v2Lan3FGIp 1}

er1646v2Lan3FGIpEntry OBJECT IDENTIFIER ::= {er1646v2Lan3FGIpSSC 1}

er1646v2Lan3FGIpVrfRouter OBJECT-TYPE
   SYNTAX      DisplayString
   MAX-ACCESS  read-write
   STATUS      current
   DESCRIPTION
      "Path: ethernet3.editConf.ip.vrfRouter"
   ::= {er1646v2Lan3FGIpEntry 738197504}

er1646v2Lan3FGIpAdr OBJECT-TYPE
   SYNTAX      IpAddress
   MAX-ACCESS  read-write
   STATUS      current
   DESCRIPTION
      "Path: ethernet3.editConf.ip.address"
   ::= {er1646v2Lan3FGIpEntry 2030043136}

er1646v2Lan3FGIpNetm OBJECT-TYPE
   SYNTAX      IpAddress
   MAX-ACCESS  read-write
   STATUS      current
   DESCRIPTION
      "Path: ethernet3.editConf.ip.netMask"
   ::= {er1646v2Lan3FGIpEntry 2063597568}

er1646v2Lan3FGIpSNetName OBJECT-TYPE
   SYNTAX      INTEGER
               {
               slOPTg (0),
               corp (2),
               dmz (3),
               internet (1)
               }
   MAX-ACCESS  read-write
   STATUS      current
   DESCRIPTION
      "Path: ethernet3.editConf.ip.sNet.name

       Possibilities:
               <OPT>   (0)
               corp   (2)
               dmz   (3)
               internet   (1)"
   ::= {er1646v2Lan3FGIpEntry 855703552}

er1646v2Lan3FGIpSNetCust OBJECT-TYPE
   SYNTAX      DisplayString
   MAX-ACCESS  read-write
   STATUS      current
   DESCRIPTION
      "Path: ethernet3.editConf.ip.sNet.custom"
   ::= {er1646v2Lan3FGIpEntry 855769088}

er1646v2Lan3FGIpDhcpC OBJECT-TYPE
   SYNTAX      INTEGER
               {
               disabled (0),
               enabled (1)
               }
   MAX-ACCESS  read-write
   STATUS      current
   DESCRIPTION
      "Path: ethernet3.editConf.ip.dhcpClient

       Possibilities:
               disabled   (0)
               enabled   (1)"
   ::= {er1646v2Lan3FGIpEntry 838860800}

er1646v2Lan3FGIpDhcpGatewayPreference OBJECT-TYPE
   SYNTAX      Integer32
   MAX-ACCESS  read-write
   STATUS      current
   DESCRIPTION
      "Path: ethernet3.editConf.ip.dhcp.gatewayPreference"
   ::= {er1646v2Lan3FGIpEntry 872480768}

er1646v2Lan3FGIpDhcpRoutePreference OBJECT-TYPE
   SYNTAX      Integer32
   MAX-ACCESS  read-write
   STATUS      current
   DESCRIPTION
      "Path: ethernet3.editConf.ip.dhcp.routePreference"
   ::= {er1646v2Lan3FGIpEntry 872546304}

er1646v2Lan3FGIpDhcpDnsPreference OBJECT-TYPE
   SYNTAX      Integer32
   MAX-ACCESS  read-write
   STATUS      current
   DESCRIPTION
      "Path: ethernet3.editConf.ip.dhcp.dnsPreference"
   ::= {er1646v2Lan3FGIpEntry 872611840}

er1646v2Lan3FGIpMtu OBJECT-TYPE
   SYNTAX      Integer32
   MAX-ACCESS  read-write
   STATUS      current
   DESCRIPTION
      "Path: ethernet3.editConf.ip.mtu"
   ::= {er1646v2Lan3FGIpEntry 671088640}

er1646v2Lan3FGIpMssAdjust OBJECT-TYPE
   SYNTAX      INTEGER
               {
               disabled (0),
               auto (65536)
               }
   MAX-ACCESS  read-write
   STATUS      current
   DESCRIPTION
      "Path: ethernet3.editConf.ip.mssAdjust

       Possibilities:
               disabled   (0)
               auto   (65536)"
   ::= {er1646v2Lan3FGIpEntry 754974720}

er1646v2Lan3FGIpRipMetric OBJECT-TYPE
   SYNTAX      Integer32
   MAX-ACCESS  read-write
   STATUS      current
   DESCRIPTION
      "Path: ethernet3.editConf.ip.rip.metric"
   ::= {er1646v2Lan3FGIpEntry 353566720}

er1646v2Lan3FGIpRipMetricOut OBJECT-TYPE
   SYNTAX      Integer32
   MAX-ACCESS  read-write
   STATUS      current
   DESCRIPTION
      "Path: ethernet3.editConf.ip.rip.metricOut"
   ::= {er1646v2Lan3FGIpEntry 353632256}

er1646v2Lan3FGIpRipMode OBJECT-TYPE
   SYNTAX      INTEGER
               {
               disabled (0),
               passive (1),
               active (2)
               }
   MAX-ACCESS  read-write
   STATUS      current
   DESCRIPTION
      "Path: ethernet3.editConf.ip.rip.mode

       Possibilities:
               disabled   (0)
               passive   (1)
               active   (2)"
   ::= {er1646v2Lan3FGIpEntry 353697792}

er1646v2Lan3FGIpRipTxVer OBJECT-TYPE
   SYNTAX      INTEGER
               {
               rip1 (0),
               rip2 (1),
               rip1mcompatible (2)
               }
   MAX-ACCESS  read-write
   STATUS      current
   DESCRIPTION
      "Path: ethernet3.editConf.ip.rip.txVersion

       Possibilities:
               rip1   (0)
               rip2   (1)
               rip1-compatible   (2)"
   ::= {er1646v2Lan3FGIpEntry 354615296}

er1646v2Lan3FGIpRipRxVer OBJECT-TYPE
   SYNTAX      INTEGER
               {
               rip1only (0),
               rip2only (1),
               rip12 (2)
               }
   MAX-ACCESS  read-write
   STATUS      current
   DESCRIPTION
      "Path: ethernet3.editConf.ip.rip.rxVersion

       Possibilities:
               rip1only   (0)
               rip2only   (1)
               rip1&2   (2)"
   ::= {er1646v2Lan3FGIpEntry 354680832}

er1646v2Lan3FGIpRipSplitH OBJECT-TYPE
   SYNTAX      INTEGER
               {
               disabled (0),
               enabled (1),
               poisonedReverse (2)
               }
   MAX-ACCESS  read-write
   STATUS      current
   DESCRIPTION
      "Path: ethernet3.editConf.ip.rip.splitHorizon

       Possibilities:
               disabled   (0)
               enabled   (1)
               poisonedReverse   (2)"
   ::= {er1646v2Lan3FGIpEntry 353828864}

er1646v2Lan3FGIpRipAuth OBJECT-TYPE
   SYNTAX      INTEGER
               {
               disabled (0),
               texts (1),
               md5 (2)
               }
   MAX-ACCESS  read-write
   STATUS      current
   DESCRIPTION
      "Path: ethernet3.editConf.ip.rip.authentication

       Possibilities:
               disabled   (0)
               text    (1)
               md5   (2)"
   ::= {er1646v2Lan3FGIpEntry 353501184}

er1646v2Lan3FGIpRipFilter OBJECT-TYPE
   SYNTAX      DisplayString
   MAX-ACCESS  read-write
   STATUS      current
   DESCRIPTION
      "Path: ethernet3.editConf.ip.rip.filter"
   ::= {er1646v2Lan3FGIpEntry 354418688}

er1646v2Lan3FGIpRipFilterIn OBJECT-TYPE
   SYNTAX      DisplayString
   MAX-ACCESS  read-write
   STATUS      current
   DESCRIPTION
      "Path: ethernet3.editConf.ip.rip.filterIn"
   ::= {er1646v2Lan3FGIpEntry 354484224}

er1646v2Lan3FGIpRipClearNextHop OBJECT-TYPE
   SYNTAX      INTEGER
               {
               disabled (0),
               enabled (1)
               }
   MAX-ACCESS  read-write
   STATUS      current
   DESCRIPTION
      "Path: ethernet3.editConf.ip.rip.clearNextHop

       Possibilities:
               disabled   (0)
               enabled   (1)"
   ::= {er1646v2Lan3FGIpEntry 352452608}

er1646v2Lan3FGIpAccPol OBJECT-TYPE
   SYNTAX      DisplayString
   MAX-ACCESS  read-write
   STATUS      current
   DESCRIPTION
      "Path: ethernet3.editConf.ip.accessPolicy"
   ::= {er1646v2Lan3FGIpEntry 704643072}

er1646v2Lan3FGIpAB OBJECT-TYPE
   SYNTAX      DisplayString
   MAX-ACCESS  read-write
   STATUS      current
   DESCRIPTION
      "Path: ethernet3.editConf.ip.trafficPolicy"
   ::= {er1646v2Lan3FGIpEntry 234881024}

er1646v2Lan3FGIpMA OBJECT-TYPE
   SYNTAX      INTEGER
               {
               disabled (0),
               enabled (1)
               }
   MAX-ACCESS  read-write
   STATUS      current
   DESCRIPTION
      "Path: ethernet3.editConf.ip.mgmtAccess

       Possibilities:
               disabled   (0)
               enabled   (1)"
   ::= {er1646v2Lan3FGIpEntry 268435456}

er1646v2Lan3FGIpMF OBJECT-TYPE
   SYNTAX      Integer32
   MAX-ACCESS  read-write
   STATUS      current
   DESCRIPTION
      "Path: ethernet3.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2Lan3FGIpEntry 285212672}

er1646v2Lan3FGIpDB OBJECT-TYPE
   SYNTAX      INTEGER
               {
               disabled (0),
               enabled (1)
               }
   MAX-ACCESS  read-write
   STATUS      current
   DESCRIPTION
      "Path: ethernet3.editConf.ip.directedBroadcasts

       Possibilities:
               disabled   (0)
               enabled   (1)"
   ::= {er1646v2Lan3FGIpEntry 369098752}

er1646v2Lan3FGIpIR OBJECT-TYPE
   SYNTAX      INTEGER
               {
               disabled (0),
               enabled (1)
               }
   MAX-ACCESS  read-write
   STATUS      current
   DESCRIPTION
      "Path: ethernet3.editConf.ip.icmpRedirects

       Possibilities:
               disabled   (0)
               enabled   (1)"
   ::= {er1646v2Lan3FGIpEntry 436207616}

er1646v2Lan3FGIpIgmp OBJECT-TYPE
   SYNTAX      INTEGER
               {
               disabled (0),
               proxy (1),
               router (2),
               v3Router (5)
               }
   MAX-ACCESS  read-write
   STATUS      current
   DESCRIPTION
      "Path: ethernet3.editConf.ip.igmp

       Possibilities:
               disabled   (0)
               proxy   (1)
               router   (2)
               v3Router   (5)"
   ::= {er1646v2Lan3FGIpEntry 536870912}

er1646v2Lan3FGIpNN OBJECT-TYPE
   SYNTAX      DisplayString
   MAX-ACCESS  read-write
   STATUS      current
   DESCRIPTION
      "Path: ethernet3.editConf.ip.nat"
   ::= {er1646v2Lan3FGIpEntry 452984832}

er1646v2Lan3FGIpVrrp OBJECT-TYPE
   SYNTAX      INTEGER
               {
               disabled (0),
               enabled (1)
               }
   MAX-ACCESS  read-write
   STATUS      current
   DESCRIPTION
      "Path: ethernet3.editConf.ip.vrrp

       Possibilities:
               disabled   (0)
               enabled   (1)"
   ::= {er1646v2Lan3FGIpEntry 721420288}

er1646v2Lan3FGIpPimMode OBJECT-TYPE
   SYNTAX      INTEGER
               {
               disabled (0),
               sparse (1),
               passive (2)
               }
   MAX-ACCESS  read-write
   STATUS      current
   DESCRIPTION
      "Path: ethernet3.editConf.ip.pim.mode

       Possibilities:
               disabled   (0)
               sparse   (1)
               passive   (2)"
   ::= {er1646v2Lan3FGIpEntry 771817472}

er1646v2Lan3FGIpPimDrPriority OBJECT-TYPE
   SYNTAX      Counter32
   MAX-ACCESS  read-write
   STATUS      current
   DESCRIPTION
      "Path: ethernet3.editConf.ip.pim.drPriority

       32 bit unsigned wrappable counter."
   ::= {er1646v2Lan3FGIpEntry 771883008}

er1646v2Lan3FGIpPimHelloTime OBJECT-TYPE
   SYNTAX      TimeTicks
   MAX-ACCESS  read-write
   STATUS      current
   DESCRIPTION
      "Path: ethernet3.editConf.ip.pim.helloTime

       Time in centi-second."
   ::= {er1646v2Lan3FGIpEntry 771948544}

er1646v2Lan3FGIpPimPropagationDelay OBJECT-TYPE
   SYNTAX      TimeTicks
   MAX-ACCESS  read-write
   STATUS      current
   DESCRIPTION
      "Path: ethernet3.editConf.ip.pim.propagationDelay

       Time in centi-second."
   ::= {er1646v2Lan3FGIpEntry 772014080}

er1646v2Lan3FGIpPimOverrideInterval OBJECT-TYPE
   SYNTAX      TimeTicks
   MAX-ACCESS  read-write
   STATUS      current
   DESCRIPTION
      "Path: ethernet3.editConf.ip.pim.overrideInterval

       Time in centi-second."
   ::= {er1646v2Lan3FGIpEntry 772079616}

er1646v2Lan3FGIpPimBsrBorder OBJECT-TYPE
   SYNTAX      INTEGER
               {
               disabled (0),
               enabled (1)
               }
   MAX-ACCESS  read-write
   STATUS      current
   DESCRIPTION
      "Path: ethernet3.editConf.ip.pim.bsrBorder

       Possibilities:
               disabled   (0)
               enabled   (1)"
   ::= {er1646v2Lan3FGIpEntry 772145152}

er1646v2Lan3FGIpPimTtlThreshold OBJECT-TYPE
   SYNTAX      Integer32
   MAX-ACCESS  read-write
   STATUS      current
   DESCRIPTION
      "Path: ethernet3.editConf.ip.pim.ttlThreshold"
   ::= {er1646v2Lan3FGIpEntry 772210688}

er1646v2Lan3FGIpIMNetworkUnreachable OBJECT-TYPE
   SYNTAX      INTEGER
               {
               disabled (0),
               enabled (1)
               }
   MAX-ACCESS  read-write
   STATUS      current
   DESCRIPTION
      "Path: ethernet3.editConf.ip.icmpMessages.networkUnreachable

       Possibilities:
               disabled   (0)
               enabled   (1)"
   ::= {er1646v2Lan3FGIpEntry 788594688}

er1646v2Lan3FGIpIMHostUnreachable OBJECT-TYPE
   SYNTAX      INTEGER
               {
               disabled (0),
               enabled (1)
               }
   MAX-ACCESS  read-write
   STATUS      current
   DESCRIPTION
      "Path: ethernet3.editConf.ip.icmpMessages.hostUnreachable

       Possibilities:
               disabled   (0)
               enabled   (1)"
   ::= {er1646v2Lan3FGIpEntry 788660224}

er1646v2Lan3FGIpIMProtocolUnreachable OBJECT-TYPE
   SYNTAX      INTEGER
               {
               disabled (0),
               enabled (1)
               }
   MAX-ACCESS  read-write
   STATUS      current
   DESCRIPTION
      "Path: ethernet3.editConf.ip.icmpMessages.protocolUnreachable

       Possibilities:
               disabled   (0)
               enabled   (1)"
   ::= {er1646v2Lan3FGIpEntry 788725760}

er1646v2Lan3FGIpIMPortUnreachable OBJECT-TYPE
   SYNTAX      INTEGER
               {
               disabled (0),
               enabled (1)
               }
   MAX-ACCESS  read-write
   STATUS      current
   DESCRIPTION
      "Path: ethernet3.editConf.ip.icmpMessages.portUnreachable

       Possibilities:
               disabled   (0)
               enabled   (1)"
   ::= {er1646v2Lan3FGIpEntry 788791296}

er1646v2Lan3FGIpIMMtuExceeded OBJECT-TYPE
   SYNTAX      INTEGER
               {
               disabled (0),
               enabled (1)
               }
   MAX-ACCESS  read-write
   STATUS      current
   DESCRIPTION
      "Path: ethernet3.editConf.ip.icmpMessages.mtuExceeded

       Possibilities:
               disabled   (0)
               enabled   (1)"
   ::= {er1646v2Lan3FGIpEntry 788856832}

er1646v2Lan3FGIpIMAdminProhibited OBJECT-TYPE
   SYNTAX      INTEGER
               {
               disabled (0),
               enabled (1)
               }
   MAX-ACCESS  read-write
   STATUS      current
   DESCRIPTION
      "Path: ethernet3.editConf.ip.icmpMessages.adminProhibited

       Possibilities:
               disabled   (0)
               enabled   (1)"
   ::= {er1646v2Lan3FGIpEntry 788922368}

er1646v2Lan3FGIpIMTtlExceeded OBJECT-TYPE
   SYNTAX      INTEGER
               {
               disabled (0),
               enabled (1)
               }
   MAX-ACCESS  read-write
   STATUS      current
   DESCRIPTION
      "Path: ethernet3.editConf.ip.icmpMessages.ttlExceeded

       Possibilities:
               disabled   (0)
               enabled   (1)"
   ::= {er1646v2Lan3FGIpEntry 788987904}

er1646v2Lan3FGIpIMRedirect OBJECT-TYPE
   SYNTAX      INTEGER
               {
               disabled (0),
               enabled (1)
               }
   MAX-ACCESS  read-write
   STATUS      current
   DESCRIPTION
      "Path: ethernet3.editConf.ip.icmpMessages.redirect

       Possibilities:
               disabled   (0)
               enabled   (1)"
   ::= {er1646v2Lan3FGIpEntry 789053440}

er1646v2Lan3FGIpSaddr OBJECT-TYPE
   SYNTAX      SEQUENCE OF Er1646v2Lan3FGIpSaddrEntry
   MAX-ACCESS  not-accessible
   STATUS      current
   DESCRIPTION
      ""
   ::= {er1646v2Lan3FGIp 385875968}

er1646v2Lan3FGIpSaddrEntry OBJECT-TYPE
   SYNTAX      Er1646v2Lan3FGIpSaddrEntry
   MAX-ACCESS  not-accessible
   STATUS      current
   DESCRIPTION
      ""
   INDEX      { er1646v2Lan3FGIpSaddrTableIx }
   ::= {er1646v2Lan3FGIpSaddr 1}

Er1646v2Lan3FGIpSaddrEntry ::=
   SEQUENCE
      {
      er1646v2Lan3FGIpSaddrActions
         VariableLengthTableActions,
      er1646v2Lan3FGIpSaddrTableIx
         TableIndex,
      er1646v2Lan3FGIpSaddrAddress
         IpAddress,
      er1646v2Lan3FGIpSaddrNetMask
         IpAddress
      }

er1646v2Lan3FGIpSaddrActions OBJECT-TYPE
   SYNTAX      VariableLengthTableActions
   MAX-ACCESS  read-write
   STATUS      current
   DESCRIPTION
      "By way of this field, some manipulations
       on this table may be performed."
   ::= {er1646v2Lan3FGIpSaddrEntry 2}

er1646v2Lan3FGIpSaddrTableIx OBJECT-TYPE
   SYNTAX      TableIndex
   MAX-ACCESS  not-accessible
   STATUS      current
   DESCRIPTION
      ""
   ::= {er1646v2Lan3FGIpSaddrEntry 11}

er1646v2Lan3FGIpSaddrAddress OBJECT-TYPE
   SYNTAX      IpAddress
   MAX-ACCESS  read-write
   STATUS      current
   DESCRIPTION
      "Path: ethernet3.editConf.ip.secondaryIp.address"
   ::= {er1646v2Lan3FGIpSaddrEntry 2030043136}

er1646v2Lan3FGIpSaddrNetMask OBJECT-TYPE
   SYNTAX      IpAddress
   MAX-ACCESS  read-write
   STATUS      current
   DESCRIPTION
      "Path: ethernet3.editConf.ip.secondaryIp.netMask"
   ::= {er1646v2Lan3FGIpSaddrEntry 2063597568}

er1646v2Lan3FGIpH OBJECT-TYPE
   SYNTAX      SEQUENCE OF Er1646v2Lan3FGIpHEntry
   MAX-ACCESS  not-accessible
   STATUS      current
   DESCRIPTION
      ""
   ::= {er1646v2Lan3FGIp 251658240}

er1646v2Lan3FGIpHEntry OBJECT-TYPE
   SYNTAX      Er1646v2Lan3FGIpHEntry
   MAX-ACCESS  not-accessible
   STATUS      current
   DESCRIPTION
      ""
   INDEX      { er1646v2Lan3FGIpHTableIx }
   ::= {er1646v2Lan3FGIpH 1}

Er1646v2Lan3FGIpHEntry ::=
   SEQUENCE
      {
      er1646v2Lan3FGIpHActions
         VariableLengthTableActions,
      er1646v2Lan3FGIpHTableIx
         TableIndex,
      er1646v2Lan3FGIpHAddress
         IpAddress,
      er1646v2Lan3FGIpHDhcpRelayOptionSubscriberId
         DisplayString
      }

er1646v2Lan3FGIpHActions OBJECT-TYPE
   SYNTAX      VariableLengthTableActions
   MAX-ACCESS  read-write
   STATUS      current
   DESCRIPTION
      "By way of this field, some manipulations
       on this table may be performed."
   ::= {er1646v2Lan3FGIpHEntry 2}

er1646v2Lan3FGIpHTableIx OBJECT-TYPE
   SYNTAX      TableIndex
   MAX-ACCESS  not-accessible
   STATUS      current
   DESCRIPTION
      ""
   ::= {er1646v2Lan3FGIpHEntry 11}

er1646v2Lan3FGIpHAddress OBJECT-TYPE
   SYNTAX      IpAddress
   MAX-ACCESS  read-write
   STATUS      current
   DESCRIPTION
      "Path: ethernet3.editConf.ip.helpers.address"
   ::= {er1646v2Lan3FGIpHEntry 16777216}

er1646v2Lan3FGIpHDhcpRelayOptionSubscriberId OBJECT-TYPE
   SYNTAX      DisplayString
   MAX-ACCESS  read-write
   STATUS      current
   DESCRIPTION
      "Path: ethernet3.editConf.ip.helpers.dhcpRelayOption.subscriberId"
   ::= {er1646v2Lan3FGIpHEntry 33947648}


er1646v2Lan3FGAdapter OBJECT-TYPE
   SYNTAX      INTEGER
               {
               autoDetect (0),
               s10MbhalfDuplex (1),
               s10MbfullDuplex (2),
               s100MbhalfDuplex (3),
               s100MbfullDuplex (4),
               s1000MbfullDuplex (6)
               }
   MAX-ACCESS  read-write
   STATUS      current
   DESCRIPTION
      "Path: ethernet3.editConf.adapter

       Possibilities:
               autoDetect   (0)
               10Mb/halfDuplex   (1)
               10Mb/fullDuplex   (2)
               100Mb/halfDuplex   (3)
               100Mb/fullDuplex   (4)
               1000Mb/fullDuplex   (6)"
   ::= {er1646v2Lan3FG 32}


er1646v2Lan3FGVlan OBJECT IDENTIFIER ::= {er1646v2Lan3FG 33}

er1646v2Lan3FGVlanSSCTable OBJECT-TYPE
   SYNTAX      SEQUENCE OF Er1646v2Lan3FGVlanEntry
   MAX-ACCESS  not-accessible
   STATUS      current
   DESCRIPTION
      ""
   ::= {er1646v2Lan3FGVlan 1}

er1646v2Lan3FGVlanEntry OBJECT-TYPE
   SYNTAX      Er1646v2Lan3FGVlanEntry
   MAX-ACCESS  not-accessible
   STATUS      current
   DESCRIPTION
      ""
   INDEX      { er1646v2Lan3FGVlanTableIx }
   ::= {er1646v2Lan3FGVlanSSCTable 1}

Er1646v2Lan3FGVlanEntry ::=
   SEQUENCE
      {
      er1646v2Lan3FGVlanActions
         VariableLengthTableActions,
      er1646v2Lan3FGVlanTableIx
         TableIndex,
      er1646v2Lan3FGVlanName
         DisplayString,
      er1646v2Lan3FGVlanRemark
         DisplayString,
      er1646v2Lan3FGVlanAdminStatus
         INTEGER,
      er1646v2Lan3FGVlanMode
         INTEGER,
      er1646v2Lan3FGVlanPriorityPolicy
         DisplayString,
      er1646v2Lan3FGVlanIpVrfRouter
         DisplayString,
      er1646v2Lan3FGVlanIpAdr
         IpAddress,
      er1646v2Lan3FGVlanIpNetm
         IpAddress,
      er1646v2Lan3FGVlanIpSNetName
         INTEGER,
      er1646v2Lan3FGVlanIpSNetCust
         DisplayString,
      er1646v2Lan3FGVlanIpDhcpC
         INTEGER,
      er1646v2Lan3FGVlanIpDhcpGatewayPreference
         Integer32,
      er1646v2Lan3FGVlanIpDhcpRoutePreference
         Integer32,
      er1646v2Lan3FGVlanIpDhcpDnsPreference
         Integer32,
      er1646v2Lan3FGVlanIpMtu
         Integer32,
      er1646v2Lan3FGVlanIpMssAdjust
         INTEGER,
      er1646v2Lan3FGVlanIpRipMetric
         Integer32,
      er1646v2Lan3FGVlanIpRipMetricOut
         Integer32,
      er1646v2Lan3FGVlanIpRipMode
         INTEGER,
      er1646v2Lan3FGVlanIpRipTxVer
         INTEGER,
      er1646v2Lan3FGVlanIpRipRxVer
         INTEGER,
      er1646v2Lan3FGVlanIpRipSplitH
         INTEGER,
      er1646v2Lan3FGVlanIpRipAuth
         INTEGER,
      er1646v2Lan3FGVlanIpRipFilter
         DisplayString,
      er1646v2Lan3FGVlanIpRipFilterIn
         DisplayString,
      er1646v2Lan3FGVlanIpRipClearNextHop
         INTEGER,
      er1646v2Lan3FGVlanIpAccPol
         DisplayString,
      er1646v2Lan3FGVlanIpAB
         DisplayString,
      er1646v2Lan3FGVlanIpMA
         INTEGER,
      er1646v2Lan3FGVlanIpMF
         Integer32,
      er1646v2Lan3FGVlanIpDB
         INTEGER,
      er1646v2Lan3FGVlanIpIR
         INTEGER,
      er1646v2Lan3FGVlanIpIgmp
         INTEGER,
      er1646v2Lan3FGVlanIpNN
         DisplayString,
      er1646v2Lan3FGVlanIpVrrp
         INTEGER,
      er1646v2Lan3FGVlanIpPimMode
         INTEGER,
      er1646v2Lan3FGVlanIpPimDrPriority
         Counter32,
      er1646v2Lan3FGVlanIpPimHelloTime
         TimeTicks,
      er1646v2Lan3FGVlanIpPimPropagationDelay
         TimeTicks,
      er1646v2Lan3FGVlanIpPimOverrideInterval
         TimeTicks,
      er1646v2Lan3FGVlanIpPimBsrBorder
         INTEGER,
      er1646v2Lan3FGVlanIpPimTtlThreshold
         Integer32,
      er1646v2Lan3FGVlanIpIMNetworkUnreachable
         INTEGER,
      er1646v2Lan3FGVlanIpIMHostUnreachable
         INTEGER,
      er1646v2Lan3FGVlanIpIMProtocolUnreachable
         INTEGER,
      er1646v2Lan3FGVlanIpIMPortUnreachable
         INTEGER,
      er1646v2Lan3FGVlanIpIMMtuExceeded
         INTEGER,
      er1646v2Lan3FGVlanIpIMAdminProhibited
         INTEGER,
      er1646v2Lan3FGVlanIpIMTtlExceeded
         INTEGER,
      er1646v2Lan3FGVlanIpIMRedirect
         INTEGER,
      er1646v2Lan3FGVlanIpV6VrfRouter
         DisplayString,
      er1646v2Lan3FGVlanIpV6AddrAutoConfigNrDupAddrDetects
         Integer32,
      er1646v2Lan3FGVlanIpV6AddrAutoConfigAcceptRa
         INTEGER,
      er1646v2Lan3FGVlanIpV6AddrAutoConfigAcceptRaRdnss
         INTEGER,
      er1646v2Lan3FGVlanIpV6AddrAutoConfigAcceptRaDnssl
         INTEGER,
      er1646v2Lan3FGVlanIpV6DefaultRoute
         INTEGER,
      er1646v2Lan3FGVlanIpV6RaSend
         INTEGER,
      er1646v2Lan3FGVlanIpV6RaMinInterval
         TimeTicks,
      er1646v2Lan3FGVlanIpV6RaMaxInterval
         TimeTicks,
      er1646v2Lan3FGVlanIpV6RaManagedFlag
         INTEGER,
      er1646v2Lan3FGVlanIpV6RaOtherConfFlag
         INTEGER,
      er1646v2Lan3FGVlanIpV6RaLinkMtu
         Integer32,
      er1646v2Lan3FGVlanIpV6RaReachableTime
         TimeTicks,
      er1646v2Lan3FGVlanIpV6RaRetransmitTime
         TimeTicks,
      er1646v2Lan3FGVlanIpV6RaHopLimit
         Integer32,
      er1646v2Lan3FGVlanIpV6RaDefaultLifeTime
         TimeTicks,
      er1646v2Lan3FGVlanIpV6RaDnsOptionsRdnssLifeTime
         TimeTicks,
      er1646v2Lan3FGVlanIpV6RaDnsOptionsRdnssImportServers
         INTEGER,
      er1646v2Lan3FGVlanIpV6RaDnsOptionsDnsslLifeTime
         TimeTicks,
      er1646v2Lan3FGVlanIpV6RaDnsOptionsDnsslImportDomains
         INTEGER,
      er1646v2Lan3FGVlanIpV6RsSend
         INTEGER,
      er1646v2Lan3FGVlanIpV6RsMaxRandomDelay
         TimeTicks,
      er1646v2Lan3FGVlanIpV6RsInterval
         TimeTicks,
      er1646v2Lan3FGVlanIpV6RsMaxSolicitations
         Integer32,
      er1646v2Lan3FGVlanIpV6TrafficPolicyInbound
         DisplayString,
      er1646v2Lan3FGVlanIpV6TrafficPolicyOutbound
         DisplayString,
      er1646v2Lan3FGVlanIpV6FirewallZone
         DisplayString,
      er1646v2Lan3FGVlanIpV6DhcpClientAddrAC
         INTEGER,
      er1646v2Lan3FGVlanIpV6DhcpClientPrDelMode
         INTEGER,
      er1646v2Lan3FGVlanIpV6DhcpClientPrDelPool
         DisplayString,
      er1646v2Lan3FGVlanIpV6DhcpClientPrDelPdExclOpt
         INTEGER,
      er1646v2Lan3FGVlanIpV6DhcpClientDnsServerPref
         Integer32,
      er1646v2Lan3FGVlanIpV6DhcpClientRapidCommit
         INTEGER,
      er1646v2Lan3FGVlanIpV6DhcpClientTimersSolTimeOut
         TimeTicks,
      er1646v2Lan3FGVlanIpV6DhcpClientTimersSolMaxRt
         TimeTicks,
      er1646v2Lan3FGVlanIpV6DhcpClientTimersInfoRefresh
         TimeTicks,
      er1646v2Lan3FGVlanIpV6DhcpServerMode
         INTEGER,
      er1646v2Lan3FGVlanIpV6DhcpServerPreference
         Integer32,
      er1646v2Lan3FGVlanIpV6DhcpServerPool
         DisplayString,
      er1646v2Lan3FGVlanIpV6DhcpServerRapidCommit
         INTEGER,
      er1646v2Lan3FGVlanIpV6DhcpServerTimersInfoRefresh
         TimeTicks,
      er1646v2Lan3FGVlanIpV6DhcpRelayMode
         INTEGER,
      er1646v2Lan3FGVlanIpV6SendRedirect
         INTEGER,
      er1646v2Lan3FGVlanIpV6LinkMtu
         Integer32,
      er1646v2Lan3FGVlanIpV6InterfaceId
         OCTET STRING,
      er1646v2Lan3FGVlanIpV6MF
         Integer32,
      er1646v2Lan3FGVlanIpV6IcmpMessagesNoRoute
         INTEGER,
      er1646v2Lan3FGVlanIpV6IcmpMessagesBeyondScope
         INTEGER,
      er1646v2Lan3FGVlanIpV6IcmpMessagesAddressUnreachable
         INTEGER,
      er1646v2Lan3FGVlanIpV6IcmpMessagesPortUnreachable
         INTEGER,
      er1646v2Lan3FGVlanIpV6IcmpMessagesPacketTooBig
         INTEGER,
      er1646v2Lan3FGVlanIpV6IcmpMessagesHopLimitExceeded
         INTEGER,
      er1646v2Lan3FGVlanIpV6IcmpMessagesFragTimeExceeded
         INTEGER,
      er1646v2Lan3FGVlanIpV6IcmpMessagesHeaderFieldErr
         INTEGER,
      er1646v2Lan3FGVlanIpV6IcmpMessagesOptionUnrecognized
         INTEGER,
      er1646v2Lan3FGVlanIpV6IcmpMessagesRedirect
         INTEGER,
      er1646v2Lan3FGVlanBridgingAccList
         DisplayString,
      er1646v2Lan3FGVlanBridgingInACL
         DisplayString,
      er1646v2Lan3FGVlanBridgingTp
         DisplayString,
      er1646v2Lan3FGVlanBridgingBrGrp
         DisplayString,
      er1646v2Lan3FGVlanBridgingLimBC
         INTEGER,
      er1646v2Lan3FGVlanBridgingPrivateMode
         INTEGER,
      er1646v2Lan3FGVlanBridgingLearning
         INTEGER,
      er1646v2Lan3FGVlanBridgingMaxCacheSize
         INTEGER,
      er1646v2Lan3FGVlanBridgingRelearnDropOnRelearn
         INTEGER,
      er1646v2Lan3FGVlanBridgingRelearnShutdownThreshold
         Integer32,
      er1646v2Lan3FGVlanBridgingRelearnShutdownTime
         TimeTicks,
      er1646v2Lan3FGVlanBridgingRelearnLoopDetection
         INTEGER,
      er1646v2Lan3FGVlanBridgingRelearnLoopDetectionInterval
         TimeTicks,
      er1646v2Lan3FGVlanBridgingVlanMemberShip
         INTEGER,
      er1646v2Lan3FGVlanBridgingVlTUntaggedAction
         INTEGER,
      er1646v2Lan3FGVlanBridgingVlTUntaggedTagInfoTpid
         INTEGER,
      er1646v2Lan3FGVlanBridgingVlTUntaggedTagInfoVid
         Integer32,
      er1646v2Lan3FGVlanBridgingVlTUnknownVlansAction
         INTEGER,
      er1646v2Lan3FGVlanBridgingVlTUnknownVlansTagInfoTpid
         INTEGER,
      er1646v2Lan3FGVlanBridgingVlTUnknownVlansTagInfoVid
         Integer32,
      er1646v2Lan3FGVlanBridgingDot1adType
         INTEGER,
      er1646v2Lan3FGVlanBridgingPriority
         Integer32,
      er1646v2Lan3FGVlanBridgingPathCost
         Integer32,
      er1646v2Lan3FGVlanBridgingInternalPathCost
         Integer32,
      er1646v2Lan3FGVlanBridgingTCD
         INTEGER,
      er1646v2Lan3FGVlanBridgingRestrictedRole
         INTEGER,
      er1646v2Lan3FGVlanBridgingAdminEdge
         INTEGER,
      er1646v2Lan3FGVlanBridgingOamMacDeviceMac
         DisplayString,
      er1646v2Lan3FGVlanBridgingOamMacUserMac
         OCTET STRING,
      er1646v2Lan3FGVlanBridgingOamMacBridgeMac
         DisplayString,
      er1646v2Lan3FGVlanBridgingMgmtInline
         INTEGER,
      er1646v2Lan3FGVlanBridgingL2ptMode
         INTEGER,
      er1646v2Lan3FGVlanBridgingL2ptProtocols
         Integer32,
      er1646v2Lan3FGVlanBridgingL2ptDestMac
         OCTET STRING,
      er1646v2Lan3FGVlanBridgingL2ptCos
         INTEGER,
      er1646v2Lan3FGVlanBridgingL2ptDropThrStp
         INTEGER,
      er1646v2Lan3FGVlanBridgingL2ptDropThrLldp
         INTEGER,
      er1646v2Lan3FGVlanBridgingL2ptDropThrOam
         INTEGER,
      er1646v2Lan3FGVlanBridgingL2ptDropThrCdp
         INTEGER,
      er1646v2Lan3FGVlanBridgingL2ptDropThrVtp
         INTEGER,
      er1646v2Lan3FGVlanBridgingL2ptDropThrLacp
         INTEGER,
      er1646v2Lan3FGVlanBridgingL2ptDropThrEfmOam
         INTEGER,
      er1646v2Lan3FGVlanBridgingL2ptDropThrPvst
         INTEGER,
      er1646v2Lan3FGVlanBridgingL2ptDropThrMmrp
         INTEGER,
      er1646v2Lan3FGVlanBridgingL2ptDropThrMvrp
         INTEGER,
      er1646v2Lan3FGVlanBridgingL2ptDropThrGvrp
         INTEGER,
      er1646v2Lan3FGVlanBridgingL2ptDropThrGmrp
         INTEGER,
      er1646v2Lan3FGVlanBridgingL2ptDropThrDtp
         INTEGER,
      er1646v2Lan3FGVlanBridgingL2ptDropThrPagp
         INTEGER,
      er1646v2Lan3FGVlanBridgingL2ptDropThrUdld
         INTEGER,
      er1646v2Lan3FGVlanVlanVid
         INTEGER,
      er1646v2Lan3FGVlanVlanVidExtensionSingle
         OCTET STRING,
      er1646v2Lan3FGVlanVlanVidExtensionEndVid
         Integer32,
      er1646v2Lan3FGVlanVlanTpid
         INTEGER,
      er1646v2Lan3FGVlanVlanTagSign
         INTEGER,
      er1646v2Lan3FGVlanVlanChTos
         INTEGER,
      er1646v2Lan3FGVlanVlanCTMapP0
         INTEGER,
      er1646v2Lan3FGVlanVlanCTMapP1
         INTEGER,
      er1646v2Lan3FGVlanVlanCTMapP2
         INTEGER,
      er1646v2Lan3FGVlanVlanCTMapP3
         INTEGER,
      er1646v2Lan3FGVlanVlanCTMapP4
         INTEGER,
      er1646v2Lan3FGVlanVlanCTMapP5
         INTEGER,
      er1646v2Lan3FGVlanVlanCTMapP6
         INTEGER,
      er1646v2Lan3FGVlanVlanCTMapP7
         INTEGER,
      er1646v2Lan3FGVlanVlanTxCos
         INTEGER,
      er1646v2Lan3FGVlanVlanCCMapP0
         Integer32,
      er1646v2Lan3FGVlanVlanCCMapP1
         Integer32,
      er1646v2Lan3FGVlanVlanCCMapP2
         Integer32,
      er1646v2Lan3FGVlanVlanCCMapP3
         Integer32,
      er1646v2Lan3FGVlanVlanCCMapP4
         Integer32,
      er1646v2Lan3FGVlanVlanCCMapP5
         Integer32,
      er1646v2Lan3FGVlanVlanCCMapP6
         Integer32,
      er1646v2Lan3FGVlanVlanCCMapP7
         Integer32,
      er1646v2Lan3FGVlanVlanQCMapQueue1
         Integer32,
      er1646v2Lan3FGVlanVlanQCMapQueue2
         Integer32,
      er1646v2Lan3FGVlanVlanQCMapQueue3
         Integer32,
      er1646v2Lan3FGVlanVlanQCMapQueue4
         Integer32,
      er1646v2Lan3FGVlanVlanQCMapQueue5
         Integer32,
      er1646v2Lan3FGVlanVlanQCMapLowDelayQueue
         Integer32,
      er1646v2Lan3FGVlanVlanQCMapLowDelay2Queue
         Integer32,
      er1646v2Lan3FGVlanVlanQCMapSystemQueue
         Integer32,
      er1646v2Lan3FGVlanVlanQinQSVid
         Integer32,
      er1646v2Lan3FGVlanVlanQinQSTpid
         INTEGER,
      er1646v2Lan3FGVlanVlanArpTimeOut
         TimeTicks,
      er1646v2Lan3FGVlanVlanArpProxyArp
         INTEGER,
      er1646v2Lan3FGVlanBandwidthMode
         INTEGER,
      er1646v2Lan3FGVlanBandwidthCir
         Integer32,
      er1646v2Lan3FGVlanBandwidthEir
         Integer32,
      er1646v2Lan3FGVlanBandwidthUnit
         INTEGER,
      er1646v2Lan3FGVlanBandwidthTc
         INTEGER,
      er1646v2Lan3FGVlanBandwidthTcFactor
         INTEGER,
      er1646v2Lan3FGVlanBandwidthCorrType
         INTEGER,
      er1646v2Lan3FGVlanBandwidthCorrPredefEncapsFrameRelay
         DisplayString,
      er1646v2Lan3FGVlanBandwidthCorrPredefEncapsPpp
         DisplayString,
      er1646v2Lan3FGVlanBandwidthCorrPredefEncapsAtmHl
         INTEGER,
      er1646v2Lan3FGVlanBandwidthCorrPredefEncapsAtmMp
         INTEGER,
      er1646v2Lan3FGVlanBandwidthCorrPredefEncapsHdlc
         DisplayString,
      er1646v2Lan3FGVlanBandwidthCorrPredefEncapsEfmFs
         Integer32,
      er1646v2Lan3FGVlanBandwidthCorrPredefEncapsEfmIb
         Integer32,
      er1646v2Lan3FGVlanBandwidthCorrPredefMode
         INTEGER,
      er1646v2Lan3FGVlanBandwidthCorrManualOverhead
         Integer32,
      er1646v2Lan3FGVlanBandwidthCorrManualFrameData
         Counter32,
      er1646v2Lan3FGVlanBandwidthCorrManualFrameHeader
         Counter32,
      er1646v2Lan3FGVlanBandwidthMaxFifoQLen
         Integer32,
      er1646v2Lan3FGVlanBandwidthDeFlagCir
         INTEGER,
      er1646v2Lan3FGVlanBandwidthDeFlagEir
         INTEGER,
      er1646v2Lan3FGVlanBandwidthDeFlagViolate
         INTEGER,
      er1646v2Lan3FGVlanBandwidthActCirActNone
         OCTET STRING,
      er1646v2Lan3FGVlanBandwidthActCirActEthCos1
         INTEGER,
      er1646v2Lan3FGVlanBandwidthActCirActEthDei1
         INTEGER,
      er1646v2Lan3FGVlanBandwidthActCirActEthCos2
         INTEGER,
      er1646v2Lan3FGVlanBandwidthActCirActEthDei2
         INTEGER,
      er1646v2Lan3FGVlanBandwidthActCirActEthCos3
         INTEGER,
      er1646v2Lan3FGVlanBandwidthActCirActEthDei3
         INTEGER,
      er1646v2Lan3FGVlanBandwidthActCirActEthCos4
         INTEGER,
      er1646v2Lan3FGVlanBandwidthActCirActEthDei4
         INTEGER,
      er1646v2Lan3FGVlanBandwidthActCirActEthCos5
         INTEGER,
      er1646v2Lan3FGVlanBandwidthActCirActEthDei5
         INTEGER,
      er1646v2Lan3FGVlanBandwidthActCirActEthCos6
         INTEGER,
      er1646v2Lan3FGVlanBandwidthActCirActEthDei6
         INTEGER,
      er1646v2Lan3FGVlanBandwidthActCirActEthCos7
         INTEGER,
      er1646v2Lan3FGVlanBandwidthActCirActEthDei7
         INTEGER,
      er1646v2Lan3FGVlanBandwidthActCirActEthCos8
         INTEGER,
      er1646v2Lan3FGVlanBandwidthActCirActEthDei8
         INTEGER,
      er1646v2Lan3FGVlanBandwidthActCirActEthTos
         INTEGER,
      er1646v2Lan3FGVlanBandwidthActCirActEthQueue
         INTEGER,
      er1646v2Lan3FGVlanBandwidthActCirActEthDrpLev
         INTEGER,
      er1646v2Lan3FGVlanBandwidthActCirActEthDeFlag
         INTEGER,
      er1646v2Lan3FGVlanBandwidthActCirActIpTos
         INTEGER,
      er1646v2Lan3FGVlanBandwidthActCirActIpQueue
         INTEGER,
      er1646v2Lan3FGVlanBandwidthActCirActIpDrpLev
         INTEGER,
      er1646v2Lan3FGVlanBandwidthActCirActIpDeFlag
         INTEGER,
      er1646v2Lan3FGVlanBandwidthActEirActNone
         OCTET STRING,
      er1646v2Lan3FGVlanBandwidthActEirActEthCos1
         INTEGER,
      er1646v2Lan3FGVlanBandwidthActEirActEthDei1
         INTEGER,
      er1646v2Lan3FGVlanBandwidthActEirActEthCos2
         INTEGER,
      er1646v2Lan3FGVlanBandwidthActEirActEthDei2
         INTEGER,
      er1646v2Lan3FGVlanBandwidthActEirActEthCos3
         INTEGER,
      er1646v2Lan3FGVlanBandwidthActEirActEthDei3
         INTEGER,
      er1646v2Lan3FGVlanBandwidthActEirActEthCos4
         INTEGER,
      er1646v2Lan3FGVlanBandwidthActEirActEthDei4
         INTEGER,
      er1646v2Lan3FGVlanBandwidthActEirActEthCos5
         INTEGER,
      er1646v2Lan3FGVlanBandwidthActEirActEthDei5
         INTEGER,
      er1646v2Lan3FGVlanBandwidthActEirActEthCos6
         INTEGER,
      er1646v2Lan3FGVlanBandwidthActEirActEthDei6
         INTEGER,
      er1646v2Lan3FGVlanBandwidthActEirActEthCos7
         INTEGER,
      er1646v2Lan3FGVlanBandwidthActEirActEthDei7
         INTEGER,
      er1646v2Lan3FGVlanBandwidthActEirActEthCos8
         INTEGER,
      er1646v2Lan3FGVlanBandwidthActEirActEthDei8
         INTEGER,
      er1646v2Lan3FGVlanBandwidthActEirActEthTos
         INTEGER,
      er1646v2Lan3FGVlanBandwidthActEirActEthQueue
         INTEGER,
      er1646v2Lan3FGVlanBandwidthActEirActEthDrpLev
         INTEGER,
      er1646v2Lan3FGVlanBandwidthActEirActEthDeFlag
         INTEGER,
      er1646v2Lan3FGVlanBandwidthActEirActIpTos
         INTEGER,
      er1646v2Lan3FGVlanBandwidthActEirActIpQueue
         INTEGER,
      er1646v2Lan3FGVlanBandwidthActEirActIpDrpLev
         INTEGER,
      er1646v2Lan3FGVlanBandwidthActEirActIpDeFlag
         INTEGER,
      er1646v2Lan3FGVlanBandwidthActViolActNone
         OCTET STRING,
      er1646v2Lan3FGVlanBandwidthActViolActDrop
         OCTET STRING,
      er1646v2Lan3FGVlanBandwidthActViolActEthCos1
         INTEGER,
      er1646v2Lan3FGVlanBandwidthActViolActEthDei1
         INTEGER,
      er1646v2Lan3FGVlanBandwidthActViolActEthCos2
         INTEGER,
      er1646v2Lan3FGVlanBandwidthActViolActEthDei2
         INTEGER,
      er1646v2Lan3FGVlanBandwidthActViolActEthCos3
         INTEGER,
      er1646v2Lan3FGVlanBandwidthActViolActEthDei3
         INTEGER,
      er1646v2Lan3FGVlanBandwidthActViolActEthCos4
         INTEGER,
      er1646v2Lan3FGVlanBandwidthActViolActEthDei4
         INTEGER,
      er1646v2Lan3FGVlanBandwidthActViolActEthCos5
         INTEGER,
      er1646v2Lan3FGVlanBandwidthActViolActEthDei5
         INTEGER,
      er1646v2Lan3FGVlanBandwidthActViolActEthCos6
         INTEGER,
      er1646v2Lan3FGVlanBandwidthActViolActEthDei6
         INTEGER,
      er1646v2Lan3FGVlanBandwidthActViolActEthCos7
         INTEGER,
      er1646v2Lan3FGVlanBandwidthActViolActEthDei7
         INTEGER,
      er1646v2Lan3FGVlanBandwidthActViolActEthCos8
         INTEGER,
      er1646v2Lan3FGVlanBandwidthActViolActEthDei8
         INTEGER,
      er1646v2Lan3FGVlanBandwidthActViolActEthTos
         INTEGER,
      er1646v2Lan3FGVlanBandwidthActViolActEthQueue
         INTEGER,
      er1646v2Lan3FGVlanBandwidthActViolActEthDrpLev
         INTEGER,
      er1646v2Lan3FGVlanBandwidthActViolActEthDeFlag
         INTEGER,
      er1646v2Lan3FGVlanBandwidthActViolActIpTos
         INTEGER,
      er1646v2Lan3FGVlanBandwidthActViolActIpQueue
         INTEGER,
      er1646v2Lan3FGVlanBandwidthActViolActIpDrpLev
         INTEGER,
      er1646v2Lan3FGVlanBandwidthActViolActIpDeFlag
         INTEGER,
      er1646v2Lan3FGVlanInbBwMode
         INTEGER,
      er1646v2Lan3FGVlanInbBwCir
         Integer32,
      er1646v2Lan3FGVlanInbBwEir
         Integer32,
      er1646v2Lan3FGVlanInbBwUnit
         INTEGER,
      er1646v2Lan3FGVlanInbBwTc
         INTEGER,
      er1646v2Lan3FGVlanInbBwTcFactor
         INTEGER,
      er1646v2Lan3FGVlanInbBwCorrType
         INTEGER,
      er1646v2Lan3FGVlanInbBwCorrPredefEncapsFrameRelay
         DisplayString,
      er1646v2Lan3FGVlanInbBwCorrPredefEncapsPpp
         DisplayString,
      er1646v2Lan3FGVlanInbBwCorrPredefEncapsAtmHl
         INTEGER,
      er1646v2Lan3FGVlanInbBwCorrPredefEncapsAtmMp
         INTEGER,
      er1646v2Lan3FGVlanInbBwCorrPredefEncapsHdlc
         DisplayString,
      er1646v2Lan3FGVlanInbBwCorrPredefEncapsEfmFs
         Integer32,
      er1646v2Lan3FGVlanInbBwCorrPredefEncapsEfmIb
         Integer32,
      er1646v2Lan3FGVlanInbBwCorrPredefMode
         INTEGER,
      er1646v2Lan3FGVlanInbBwCorrManualOverhead
         Integer32,
      er1646v2Lan3FGVlanInbBwCorrManualFrameData
         Counter32,
      er1646v2Lan3FGVlanInbBwCorrManualFrameHeader
         Counter32,
      er1646v2Lan3FGVlanInbBwMaxFifoQLen
         Integer32,
      er1646v2Lan3FGVlanInbBwPriorityPolicy
         DisplayString,
      er1646v2Lan3FGVlanInbBwDeFlagCir
         INTEGER,
      er1646v2Lan3FGVlanInbBwDeFlagEir
         INTEGER,
      er1646v2Lan3FGVlanInbBwDeFlagViolate
         INTEGER,
      er1646v2Lan3FGVlanInbBwActCirActNone
         OCTET STRING,
      er1646v2Lan3FGVlanInbBwActCirActEthCos1
         INTEGER,
      er1646v2Lan3FGVlanInbBwActCirActEthDei1
         INTEGER,
      er1646v2Lan3FGVlanInbBwActCirActEthCos2
         INTEGER,
      er1646v2Lan3FGVlanInbBwActCirActEthDei2
         INTEGER,
      er1646v2Lan3FGVlanInbBwActCirActEthCos3
         INTEGER,
      er1646v2Lan3FGVlanInbBwActCirActEthDei3
         INTEGER,
      er1646v2Lan3FGVlanInbBwActCirActEthCos4
         INTEGER,
      er1646v2Lan3FGVlanInbBwActCirActEthDei4
         INTEGER,
      er1646v2Lan3FGVlanInbBwActCirActEthCos5
         INTEGER,
      er1646v2Lan3FGVlanInbBwActCirActEthDei5
         INTEGER,
      er1646v2Lan3FGVlanInbBwActCirActEthCos6
         INTEGER,
      er1646v2Lan3FGVlanInbBwActCirActEthDei6
         INTEGER,
      er1646v2Lan3FGVlanInbBwActCirActEthCos7
         INTEGER,
      er1646v2Lan3FGVlanInbBwActCirActEthDei7
         INTEGER,
      er1646v2Lan3FGVlanInbBwActCirActEthCos8
         INTEGER,
      er1646v2Lan3FGVlanInbBwActCirActEthDei8
         INTEGER,
      er1646v2Lan3FGVlanInbBwActCirActEthTos
         INTEGER,
      er1646v2Lan3FGVlanInbBwActCirActEthQueue
         INTEGER,
      er1646v2Lan3FGVlanInbBwActCirActEthDrpLev
         INTEGER,
      er1646v2Lan3FGVlanInbBwActCirActEthDeFlag
         INTEGER,
      er1646v2Lan3FGVlanInbBwActCirActIpTos
         INTEGER,
      er1646v2Lan3FGVlanInbBwActCirActIpQueue
         INTEGER,
      er1646v2Lan3FGVlanInbBwActCirActIpDrpLev
         INTEGER,
      er1646v2Lan3FGVlanInbBwActCirActIpDeFlag
         INTEGER,
      er1646v2Lan3FGVlanInbBwActEirActNone
         OCTET STRING,
      er1646v2Lan3FGVlanInbBwActEirActEthCos1
         INTEGER,
      er1646v2Lan3FGVlanInbBwActEirActEthDei1
         INTEGER,
      er1646v2Lan3FGVlanInbBwActEirActEthCos2
         INTEGER,
      er1646v2Lan3FGVlanInbBwActEirActEthDei2
         INTEGER,
      er1646v2Lan3FGVlanInbBwActEirActEthCos3
         INTEGER,
      er1646v2Lan3FGVlanInbBwActEirActEthDei3
         INTEGER,
      er1646v2Lan3FGVlanInbBwActEirActEthCos4
         INTEGER,
      er1646v2Lan3FGVlanInbBwActEirActEthDei4
         INTEGER,
      er1646v2Lan3FGVlanInbBwActEirActEthCos5
         INTEGER,
      er1646v2Lan3FGVlanInbBwActEirActEthDei5
         INTEGER,
      er1646v2Lan3FGVlanInbBwActEirActEthCos6
         INTEGER,
      er1646v2Lan3FGVlanInbBwActEirActEthDei6
         INTEGER,
      er1646v2Lan3FGVlanInbBwActEirActEthCos7
         INTEGER,
      er1646v2Lan3FGVlanInbBwActEirActEthDei7
         INTEGER,
      er1646v2Lan3FGVlanInbBwActEirActEthCos8
         INTEGER,
      er1646v2Lan3FGVlanInbBwActEirActEthDei8
         INTEGER,
      er1646v2Lan3FGVlanInbBwActEirActEthTos
         INTEGER,
      er1646v2Lan3FGVlanInbBwActEirActEthQueue
         INTEGER,
      er1646v2Lan3FGVlanInbBwActEirActEthDrpLev
         INTEGER,
      er1646v2Lan3FGVlanInbBwActEirActEthDeFlag
         INTEGER,
      er1646v2Lan3FGVlanInbBwActEirActIpTos
         INTEGER,
      er1646v2Lan3FGVlanInbBwActEirActIpQueue
         INTEGER,
      er1646v2Lan3FGVlanInbBwActEirActIpDrpLev
         INTEGER,
      er1646v2Lan3FGVlanInbBwActEirActIpDeFlag
         INTEGER,
      er1646v2Lan3FGVlanInbBwActViolActNone
         OCTET STRING,
      er1646v2Lan3FGVlanInbBwActViolActDrop
         OCTET STRING,
      er1646v2Lan3FGVlanInbBwActViolActEthCos1
         INTEGER,
      er1646v2Lan3FGVlanInbBwActViolActEthDei1
         INTEGER,
      er1646v2Lan3FGVlanInbBwActViolActEthCos2
         INTEGER,
      er1646v2Lan3FGVlanInbBwActViolActEthDei2
         INTEGER,
      er1646v2Lan3FGVlanInbBwActViolActEthCos3
         INTEGER,
      er1646v2Lan3FGVlanInbBwActViolActEthDei3
         INTEGER,
      er1646v2Lan3FGVlanInbBwActViolActEthCos4
         INTEGER,
      er1646v2Lan3FGVlanInbBwActViolActEthDei4
         INTEGER,
      er1646v2Lan3FGVlanInbBwActViolActEthCos5
         INTEGER,
      er1646v2Lan3FGVlanInbBwActViolActEthDei5
         INTEGER,
      er1646v2Lan3FGVlanInbBwActViolActEthCos6
         INTEGER,
      er1646v2Lan3FGVlanInbBwActViolActEthDei6
         INTEGER,
      er1646v2Lan3FGVlanInbBwActViolActEthCos7
         INTEGER,
      er1646v2Lan3FGVlanInbBwActViolActEthDei7
         INTEGER,
      er1646v2Lan3FGVlanInbBwActViolActEthCos8
         INTEGER,
      er1646v2Lan3FGVlanInbBwActViolActEthDei8
         INTEGER,
      er1646v2Lan3FGVlanInbBwActViolActEthTos
         INTEGER,
      er1646v2Lan3FGVlanInbBwActViolActEthQueue
         INTEGER,
      er1646v2Lan3FGVlanInbBwActViolActEthDrpLev
         INTEGER,
      er1646v2Lan3FGVlanInbBwActViolActEthDeFlag
         INTEGER,
      er1646v2Lan3FGVlanInbBwActViolActIpTos
         INTEGER,
      er1646v2Lan3FGVlanInbBwActViolActIpQueue
         INTEGER,
      er1646v2Lan3FGVlanInbBwActViolActIpDrpLev
         INTEGER,
      er1646v2Lan3FGVlanInbBwActViolActIpDeFlag
         INTEGER,
      er1646v2Lan3FGVlanPppoE
         INTEGER,
      er1646v2Lan3FGVlanPppLnkMOperation
         INTEGER,
      er1646v2Lan3FGVlanPppLnkMInterval
         TimeTicks,
      er1646v2Lan3FGVlanPppLnkMRepTimeOut
         TimeTicks,
      er1646v2Lan3FGVlanPppLnkMFailsPrmt
         Integer32,
      er1646v2Lan3FGVlanPppAuthentication
         INTEGER,
      er1646v2Lan3FGVlanPppAuthenPeriod
         TimeTicks,
      er1646v2Lan3FGVlanPppSessionName
         DisplayString,
      er1646v2Lan3FGVlanPppSessionSecret
         DisplayString,
      er1646v2Lan3FGVlanPppEncModeSessionSecret
         INTEGER,
      er1646v2Lan3FGVlanPppEncSessionSecret
         DisplayString,
      er1646v2Lan3FGVlanPppServiceName
         DisplayString,
      er1646v2Lan3FGVlanPbbMode
         INTEGER,
      er1646v2Lan3FGVlanPbbTxCos
         Integer32,
      er1646v2Lan3FGVlanPbbIsid
         Integer32,
      er1646v2Lan3FGVlanPbbDestMac
         OCTET STRING,
      er1646v2Lan3FGVlanPbbCustomGroupMac
         OCTET STRING
      }

er1646v2Lan3FGVlanActions OBJECT-TYPE
   SYNTAX      VariableLengthTableActions
   MAX-ACCESS  read-write
   STATUS      current
   DESCRIPTION
      "By way of this field, some manipulations
       on this table may be performed."
   ::= {er1646v2Lan3FGVlanEntry 2}

er1646v2Lan3FGVlanTableIx OBJECT-TYPE
   SYNTAX      TableIndex
   MAX-ACCESS  not-accessible
   STATUS      current
   DESCRIPTION
      ""
   ::= {er1646v2Lan3FGVlanEntry 11}

er1646v2Lan3FGVlanName OBJECT-TYPE
   SYNTAX      DisplayString
   MAX-ACCESS  read-write
   STATUS      current
   DESCRIPTION
      "Path: ethernet3.editConf.vlan.name"
   ::= {er1646v2Lan3FGVlanEntry 16777216}

er1646v2Lan3FGVlanRemark OBJECT-TYPE
   SYNTAX      DisplayString
   MAX-ACCESS  read-write
   STATUS      current
   DESCRIPTION
      "Path: ethernet3.editConf.vlan.remark"
   ::= {er1646v2Lan3FGVlanEntry 1157627904}

er1646v2Lan3FGVlanAdminStatus OBJECT-TYPE
   SYNTAX      INTEGER
               {
               up (1),
               down (2)
               }
   MAX-ACCESS  read-write
   STATUS      current
   DESCRIPTION
      "Path: ethernet3.editConf.vlan.adminStatus

       Possibilities:
               up   (1)
               down   (2)"
   ::= {er1646v2Lan3FGVlanEntry 33554432}

er1646v2Lan3FGVlanMode OBJECT-TYPE
   SYNTAX      INTEGER
               {
               routing (1),
               bridging (2),
               ipV6 (16),
               ipV6ipV4 (17),
               multilink (8)
               }
   MAX-ACCESS  read-write
   STATUS      current
   DESCRIPTION
      "Path: ethernet3.editConf.vlan.mode

       Possibilities:
               routing   (1)
               bridging   (2)
               ipV6   (16)
               ipV6/ipV4   (17)
               multilink   (8)"
   ::= {er1646v2Lan3FGVlanEntry 67108864}

er1646v2Lan3FGVlanPriorityPolicy OBJECT-TYPE
   SYNTAX      DisplayString
   MAX-ACCESS  read-write
   STATUS      current
   DESCRIPTION
      "Path: ethernet3.editConf.vlan.priorityPolicy"
   ::= {er1646v2Lan3FGVlanEntry 83886080}

er1646v2Lan3FGVlanIpVrfRouter OBJECT-TYPE
   SYNTAX      DisplayString
   MAX-ACCESS  read-write
   STATUS      current
   DESCRIPTION
      "Path: ethernet3.editConf.vlan.ip.vrfRouter"
   ::= {er1646v2Lan3FGVlanEntry 53215232}

er1646v2Lan3FGVlanIpAdr OBJECT-TYPE
   SYNTAX      IpAddress
   MAX-ACCESS  read-write
   STATUS      current
   DESCRIPTION
      "Path: ethernet3.editConf.vlan.ip.address"
   ::= {er1646v2Lan3FGVlanEntry 58261504}

er1646v2Lan3FGVlanIpNetm OBJECT-TYPE
   SYNTAX      IpAddress
   MAX-ACCESS  read-write
   STATUS      current
   DESCRIPTION
      "Path: ethernet3.editConf.vlan.ip.netMask"
   ::= {er1646v2Lan3FGVlanEntry 58392576}

er1646v2Lan3FGVlanIpSNetName OBJECT-TYPE
   SYNTAX      INTEGER
               {
               slOPTg (0),
               corp (2),
               dmz (3),
               internet (1)
               }
   MAX-ACCESS  read-write
   STATUS      current
   DESCRIPTION
      "Path: ethernet3.editConf.vlan.ip.sNet.name

       Possibilities:
               <OPT>   (0)
               corp   (2)
               dmz   (3)
               internet   (1)"
   ::= {er1646v2Lan3FGVlanEntry 53674240}

er1646v2Lan3FGVlanIpSNetCust OBJECT-TYPE
   SYNTAX      DisplayString
   MAX-ACCESS  read-write
   STATUS      current
   DESCRIPTION
      "Path: ethernet3.editConf.vlan.ip.sNet.custom"
   ::= {er1646v2Lan3FGVlanEntry 53674496}

er1646v2Lan3FGVlanIpDhcpC OBJECT-TYPE
   SYNTAX      INTEGER
               {
               disabled (0),
               enabled (1)
               }
   MAX-ACCESS  read-write
   STATUS      current
   DESCRIPTION
      "Path: ethernet3.editConf.vlan.ip.dhcpClient

       Possibilities:
               disabled   (0)
               enabled   (1)"
   ::= {er1646v2Lan3FGVlanEntry 53608448}

er1646v2Lan3FGVlanIpDhcpGatewayPreference OBJECT-TYPE
   SYNTAX      Integer32
   MAX-ACCESS  read-write
   STATUS      current
   DESCRIPTION
      "Path: ethernet3.editConf.vlan.ip.dhcp.gatewayPreference"
   ::= {er1646v2Lan3FGVlanEntry 53739776}

er1646v2Lan3FGVlanIpDhcpRoutePreference OBJECT-TYPE
   SYNTAX      Integer32
   MAX-ACCESS  read-write
   STATUS      current
   DESCRIPTION
      "Path: ethernet3.editConf.vlan.ip.dhcp.routePreference"
   ::= {er1646v2Lan3FGVlanEntry 53740032}

er1646v2Lan3FGVlanIpDhcpDnsPreference OBJECT-TYPE
   SYNTAX      Integer32
   MAX-ACCESS  read-write
   STATUS      current
   DESCRIPTION
      "Path: ethernet3.editConf.vlan.ip.dhcp.dnsPreference"
   ::= {er1646v2Lan3FGVlanEntry 53740288}

er1646v2Lan3FGVlanIpMtu OBJECT-TYPE
   SYNTAX      Integer32
   MAX-ACCESS  read-write
   STATUS      current
   DESCRIPTION
      "Path: ethernet3.editConf.vlan.ip.mtu"
   ::= {er1646v2Lan3FGVlanEntry 52953088}

er1646v2Lan3FGVlanIpMssAdjust OBJECT-TYPE
   SYNTAX      INTEGER
               {
               disabled (0),
               auto (65536)
               }
   MAX-ACCESS  read-write
   STATUS      current
   DESCRIPTION
      "Path: ethernet3.editConf.vlan.ip.mssAdjust

       Possibilities:
               disabled   (0)
               auto   (65536)"
   ::= {er1646v2Lan3FGVlanEntry 53280768}

er1646v2Lan3FGVlanIpRipMetric OBJECT-TYPE
   SYNTAX      Integer32
   MAX-ACCESS  read-write
   STATUS      current
   DESCRIPTION
      "Path: ethernet3.editConf.vlan.ip.rip.metric"
   ::= {er1646v2Lan3FGVlanEntry 51712768}

er1646v2Lan3FGVlanIpRipMetricOut OBJECT-TYPE
   SYNTAX      Integer32
   MAX-ACCESS  read-write
   STATUS      current
   DESCRIPTION
      "Path: ethernet3.editConf.vlan.ip.rip.metricOut"
   ::= {er1646v2Lan3FGVlanEntry 51713024}

er1646v2Lan3FGVlanIpRipMode OBJECT-TYPE
   SYNTAX      INTEGER
               {
               disabled (0),
               passive (1),
               active (2)
               }
   MAX-ACCESS  read-write
   STATUS      current
   DESCRIPTION
      "Path: ethernet3.editConf.vlan.ip.rip.mode

       Possibilities:
               disabled   (0)
               passive   (1)
               active   (2)"
   ::= {er1646v2Lan3FGVlanEntry 51713280}

er1646v2Lan3FGVlanIpRipTxVer OBJECT-TYPE
   SYNTAX      INTEGER
               {
               rip1 (0),
               rip2 (1),
               rip1mcompatible (2)
               }
   MAX-ACCESS  read-write
   STATUS      current
   DESCRIPTION
      "Path: ethernet3.editConf.vlan.ip.rip.txVersion

       Possibilities:
               rip1   (0)
               rip2   (1)
               rip1-compatible   (2)"
   ::= {er1646v2Lan3FGVlanEntry 51716864}

er1646v2Lan3FGVlanIpRipRxVer OBJECT-TYPE
   SYNTAX      INTEGER
               {
               rip1only (0),
               rip2only (1),
               rip12 (2)
               }
   MAX-ACCESS  read-write
   STATUS      current
   DESCRIPTION
      "Path: ethernet3.editConf.vlan.ip.rip.rxVersion

       Possibilities:
               rip1only   (0)
               rip2only   (1)
               rip1&2   (2)"
   ::= {er1646v2Lan3FGVlanEntry 51717120}

er1646v2Lan3FGVlanIpRipSplitH OBJECT-TYPE
   SYNTAX      INTEGER
               {
               disabled (0),
               enabled (1),
               poisonedReverse (2)
               }
   MAX-ACCESS  read-write
   STATUS      current
   DESCRIPTION
      "Path: ethernet3.editConf.vlan.ip.rip.splitHorizon

       Possibilities:
               disabled   (0)
               enabled   (1)
               poisonedReverse   (2)"
   ::= {er1646v2Lan3FGVlanEntry 51713792}

er1646v2Lan3FGVlanIpRipAuth OBJECT-TYPE
   SYNTAX      INTEGER
               {
               disabled (0),
               texts (1),
               md5 (2)
               }
   MAX-ACCESS  read-write
   STATUS      current
   DESCRIPTION
      "Path: ethernet3.editConf.vlan.ip.rip.authentication

       Possibilities:
               disabled   (0)
               text    (1)
               md5   (2)"
   ::= {er1646v2Lan3FGVlanEntry 51712512}

er1646v2Lan3FGVlanIpRipFilter OBJECT-TYPE
   SYNTAX      DisplayString
   MAX-ACCESS  read-write
   STATUS      current
   DESCRIPTION
      "Path: ethernet3.editConf.vlan.ip.rip.filter"
   ::= {er1646v2Lan3FGVlanEntry 51716096}

er1646v2Lan3FGVlanIpRipFilterIn OBJECT-TYPE
   SYNTAX      DisplayString
   MAX-ACCESS  read-write
   STATUS      current
   DESCRIPTION
      "Path: ethernet3.editConf.vlan.ip.rip.filterIn"
   ::= {er1646v2Lan3FGVlanEntry 51716352}

er1646v2Lan3FGVlanIpRipClearNextHop OBJECT-TYPE
   SYNTAX      INTEGER
               {
               disabled (0),
               enabled (1)
               }
   MAX-ACCESS  read-write
   STATUS      current
   DESCRIPTION
      "Path: ethernet3.editConf.vlan.ip.rip.clearNextHop

       Possibilities:
               disabled   (0)
               enabled   (1)"
   ::= {er1646v2Lan3FGVlanEntry 51708416}

er1646v2Lan3FGVlanIpAccPol OBJECT-TYPE
   SYNTAX      DisplayString
   MAX-ACCESS  read-write
   STATUS      current
   DESCRIPTION
      "Path: ethernet3.editConf.vlan.ip.accessPolicy"
   ::= {er1646v2Lan3FGVlanEntry 53084160}

er1646v2Lan3FGVlanIpAB OBJECT-TYPE
   SYNTAX      DisplayString
   MAX-ACCESS  read-write
   STATUS      current
   DESCRIPTION
      "Path: ethernet3.editConf.vlan.ip.trafficPolicy"
   ::= {er1646v2Lan3FGVlanEntry 51249152}

er1646v2Lan3FGVlanIpMA OBJECT-TYPE
   SYNTAX      INTEGER
               {
               disabled (0),
               enabled (1)
               }
   MAX-ACCESS  read-write
   STATUS      current
   DESCRIPTION
      "Path: ethernet3.editConf.vlan.ip.mgmtAccess

       Possibilities:
               disabled   (0)
               enabled   (1)"
   ::= {er1646v2Lan3FGVlanEntry 51380224}

er1646v2Lan3FGVlanIpMF OBJECT-TYPE
   SYNTAX      Integer32
   MAX-ACCESS  read-write
   STATUS      current
   DESCRIPTION
      "Path: ethernet3.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2Lan3FGVlanEntry 51445760}

er1646v2Lan3FGVlanIpDB OBJECT-TYPE
   SYNTAX      INTEGER
               {
               disabled (0),
               enabled (1)
               }
   MAX-ACCESS  read-write
   STATUS      current
   DESCRIPTION
      "Path: ethernet3.editConf.vlan.ip.directedBroadcasts

       Possibilities:
               disabled   (0)
               enabled   (1)"
   ::= {er1646v2Lan3FGVlanEntry 51773440}

er1646v2Lan3FGVlanIpIR OBJECT-TYPE
   SYNTAX      INTEGER
               {
               disabled (0),
               enabled (1)
               }
   MAX-ACCESS  read-write
   STATUS      current
   DESCRIPTION
      "Path: ethernet3.editConf.vlan.ip.icmpRedirects

       Possibilities:
               disabled   (0)
               enabled   (1)"
   ::= {er1646v2Lan3FGVlanEntry 52035584}

er1646v2Lan3FGVlanIpIgmp OBJECT-TYPE
   SYNTAX      INTEGER
               {
               disabled (0),
               proxy (1),
               router (2),
               v3Router (5)
               }
   MAX-ACCESS  read-write
   STATUS      current
   DESCRIPTION
      "Path: ethernet3.editConf.vlan.ip.igmp

       Possibilities:
               disabled   (0)
               proxy   (1)
               router   (2)
               v3Router   (5)"
   ::= {er1646v2Lan3FGVlanEntry 52428800}

er1646v2Lan3FGVlanIpNN OBJECT-TYPE
   SYNTAX      DisplayString
   MAX-ACCESS  read-write
   STATUS      current
   DESCRIPTION
      "Path: ethernet3.editConf.vlan.ip.nat"
   ::= {er1646v2Lan3FGVlanEntry 52101120}

er1646v2Lan3FGVlanIpVrrp OBJECT-TYPE
   SYNTAX      INTEGER
               {
               disabled (0),
               enabled (1)
               }
   MAX-ACCESS  read-write
   STATUS      current
   DESCRIPTION
      "Path: ethernet3.editConf.vlan.ip.vrrp

       Possibilities:
               disabled   (0)
               enabled   (1)"
   ::= {er1646v2Lan3FGVlanEntry 53149696}

er1646v2Lan3FGVlanIpPimMode OBJECT-TYPE
   SYNTAX      INTEGER
               {
               disabled (0),
               sparse (1),
               passive (2)
               }
   MAX-ACCESS  read-write
   STATUS      current
   DESCRIPTION
      "Path: ethernet3.editConf.vlan.ip.pim.mode

       Possibilities:
               disabled   (0)
               sparse   (1)
               passive   (2)"
   ::= {er1646v2Lan3FGVlanEntry 53346560}

er1646v2Lan3FGVlanIpPimDrPriority OBJECT-TYPE
   SYNTAX      Counter32
   MAX-ACCESS  read-write
   STATUS      current
   DESCRIPTION
      "Path: ethernet3.editConf.vlan.ip.pim.drPriority

       32 bit unsigned wrappable counter."
   ::= {er1646v2Lan3FGVlanEntry 53346816}

er1646v2Lan3FGVlanIpPimHelloTime OBJECT-TYPE
   SYNTAX      TimeTicks
   MAX-ACCESS  read-write
   STATUS      current
   DESCRIPTION
      "Path: ethernet3.editConf.vlan.ip.pim.helloTime

       Time in centi-second."
   ::= {er1646v2Lan3FGVlanEntry 53347072}

er1646v2Lan3FGVlanIpPimPropagationDelay OBJECT-TYPE
   SYNTAX      TimeTicks
   MAX-ACCESS  read-write
   STATUS      current
   DESCRIPTION
      "Path: ethernet3.editConf.vlan.ip.pim.propagationDelay

       Time in centi-second."
   ::= {er1646v2Lan3FGVlanEntry 53347328}

er1646v2Lan3FGVlanIpPimOverrideInterval OBJECT-TYPE
   SYNTAX      TimeTicks
   MAX-ACCESS  read-write
   STATUS      current
   DESCRIPTION
      "Path: ethernet3.editConf.vlan.ip.pim.overrideInterval

       Time in centi-second."
   ::= {er1646v2Lan3FGVlanEntry 53347584}

er1646v2Lan3FGVlanIpPimBsrBorder OBJECT-TYPE
   SYNTAX      INTEGER
               {
               disabled (0),
               enabled (1)
               }
   MAX-ACCESS  read-write
   STATUS      current
   DESCRIPTION
      "Path: ethernet3.editConf.vlan.ip.pim.bsrBorder

       Possibilities:
               disabled   (0)
               enabled   (1)"
   ::= {er1646v2Lan3FGVlanEntry 53347840}

er1646v2Lan3FGVlanIpPimTtlThreshold OBJECT-TYPE
   SYNTAX      Integer32
   MAX-ACCESS  read-write
   STATUS      current
   DESCRIPTION
      "Path: ethernet3.editConf.vlan.ip.pim.ttlThreshold"
   ::= {er1646v2Lan3FGVlanEntry 53348096}

er1646v2Lan3FGVlanIpIMNetworkUnreachable OBJECT-TYPE
   SYNTAX      INTEGER
               {
               disabled (0),
               enabled (1)
               }
   MAX-ACCESS  read-write
   STATUS      current
   DESCRIPTION
      "Path: ethernet3.editConf.vlan.ip.icmpMessages.networkUnreachable

       Possibilities:
               disabled   (0)
               enabled   (1)"
   ::= {er1646v2Lan3FGVlanEntry 53412096}

er1646v2Lan3FGVlanIpIMHostUnreachable OBJECT-TYPE
   SYNTAX      INTEGER
               {
               disabled (0),
               enabled (1)
               }
   MAX-ACCESS  read-write
   STATUS      current
   DESCRIPTION
      "Path: ethernet3.editConf.vlan.ip.icmpMessages.hostUnreachable

       Possibilities:
               disabled   (0)
               enabled   (1)"
   ::= {er1646v2Lan3FGVlanEntry 53412352}

er1646v2Lan3FGVlanIpIMProtocolUnreachable OBJECT-TYPE
   SYNTAX      INTEGER
               {
               disabled (0),
               enabled (1)
               }
   MAX-ACCESS  read-write
   STATUS      current
   DESCRIPTION
      "Path: ethernet3.editConf.vlan.ip.icmpMessages.protocolUnreachable

       Possibilities:
               disabled   (0)
               enabled   (1)"
   ::= {er1646v2Lan3FGVlanEntry 53412608}

er1646v2Lan3FGVlanIpIMPortUnreachable OBJECT-TYPE
   SYNTAX      INTEGER
               {
               disabled (0),
               enabled (1)
               }
   MAX-ACCESS  read-write
   STATUS      current
   DESCRIPTION
      "Path: ethernet3.editConf.vlan.ip.icmpMessages.portUnreachable

       Possibilities:
               disabled   (0)
               enabled   (1)"
   ::= {er1646v2Lan3FGVlanEntry 53412864}

er1646v2Lan3FGVlanIpIMMtuExceeded OBJECT-TYPE
   SYNTAX      INTEGER
               {
               disabled (0),
               enabled (1)
               }
   MAX-ACCESS  read-write
   STATUS      current
   DESCRIPTION
      "Path: ethernet3.editConf.vlan.ip.icmpMessages.mtuExceeded

       Possibilities:
               disabled   (0)
               enabled   (1)"
   ::= {er1646v2Lan3FGVlanEntry 53413120}

er1646v2Lan3FGVlanIpIMAdminProhibited OBJECT-TYPE
   SYNTAX      INTEGER
               {
               disabled (0),
               enabled (1)
               }
   MAX-ACCESS  read-write
   STATUS      current
   DESCRIPTION
      "Path: ethernet3.editConf.vlan.ip.icmpMessages.adminProhibited

       Possibilities:
               disabled   (0)
               enabled   (1)"
   ::= {er1646v2Lan3FGVlanEntry 53413376}

er1646v2Lan3FGVlanIpIMTtlExceeded OBJECT-TYPE
   SYNTAX      INTEGER
               {
               disabled (0),
               enabled (1)
               }
   MAX-ACCESS  read-write
   STATUS      current
   DESCRIPTION
      "Path: ethernet3.editConf.vlan.ip.icmpMessages.ttlExceeded

       Possibilities:
               disabled   (0)
               enabled   (1)"
   ::= {er1646v2Lan3FGVlanEntry 53413632}

er1646v2Lan3FGVlanIpIMRedirect OBJECT-TYPE
   SYNTAX      INTEGER
               {
               disabled (0),
               enabled (1)
               }
   MAX-ACCESS  read-write
   STATUS      current
   DESCRIPTION
      "Path: ethernet3.editConf.vlan.ip.icmpMessages.redirect

       Possibilities:
               disabled   (0)
               enabled   (1)"
   ::= {er1646v2Lan3FGVlanEntry 53413888}

er1646v2Lan3FGVlanIpV6VrfRouter OBJECT-TYPE
   SYNTAX      DisplayString
   MAX-ACCESS  read-write
   STATUS      current
   DESCRIPTION
      "Path: ethernet3.editConf.vlan.ipV6.vrfRouter"
   ::= {er1646v2Lan3FGVlanEntry 704708608}

er1646v2Lan3FGVlanIpV6AddrAutoConfigNrDupAddrDetects OBJECT-TYPE
   SYNTAX      Integer32
   MAX-ACCESS  read-write
   STATUS      current
   DESCRIPTION
      "Path: ethernet3.editConf.vlan.ipV6.addrAutoConfig.nrDupAddrDetects"
   ::= {er1646v2Lan3FGVlanEntry 704905472}

er1646v2Lan3FGVlanIpV6AddrAutoConfigAcceptRa OBJECT-TYPE
   SYNTAX      INTEGER
               {
               disabled (0),
               enabled (1)
               }
   MAX-ACCESS  read-write
   STATUS      current
   DESCRIPTION
      "Path: ethernet3.editConf.vlan.ipV6.addrAutoConfig.acceptRa

       Possibilities:
               disabled   (0)
               enabled   (1)"
   ::= {er1646v2Lan3FGVlanEntry 704905728}

er1646v2Lan3FGVlanIpV6AddrAutoConfigAcceptRaRdnss OBJECT-TYPE
   SYNTAX      INTEGER
               {
               disabled (0),
               enabled (1)
               }
   MAX-ACCESS  read-write
   STATUS      current
   DESCRIPTION
      "Path: ethernet3.editConf.vlan.ipV6.addrAutoConfig.acceptRaRdnss

       Possibilities:
               disabled   (0)
               enabled   (1)"
   ::= {er1646v2Lan3FGVlanEntry 704905984}

er1646v2Lan3FGVlanIpV6AddrAutoConfigAcceptRaDnssl OBJECT-TYPE
   SYNTAX      INTEGER
               {
               disabled (0),
               enabled (1)
               }
   MAX-ACCESS  read-write
   STATUS      current
   DESCRIPTION
      "Path: ethernet3.editConf.vlan.ipV6.addrAutoConfig.acceptRaDnssl

       Possibilities:
               disabled   (0)
               enabled   (1)"
   ::= {er1646v2Lan3FGVlanEntry 704906240}

er1646v2Lan3FGVlanIpV6DefaultRoute OBJECT-TYPE
   SYNTAX      INTEGER
               {
               disabled (0),
               enabled (1)
               }
   MAX-ACCESS  read-write
   STATUS      current
   DESCRIPTION
      "Path: ethernet3.editConf.vlan.ipV6.defaultRoute

       Possibilities:
               disabled   (0)
               enabled   (1)"
   ::= {er1646v2Lan3FGVlanEntry 704970752}

er1646v2Lan3FGVlanIpV6RaSend OBJECT-TYPE
   SYNTAX      INTEGER
               {
               disabled (0),
               enabled (1)
               }
   MAX-ACCESS  read-write
   STATUS      current
   DESCRIPTION
      "Path: ethernet3.editConf.vlan.ipV6.ra.send

       Possibilities:
               disabled   (0)
               enabled   (1)"
   ::= {er1646v2Lan3FGVlanEntry 705036544}

er1646v2Lan3FGVlanIpV6RaMinInterval OBJECT-TYPE
   SYNTAX      TimeTicks
   MAX-ACCESS  read-write
   STATUS      current
   DESCRIPTION
      "Path: ethernet3.editConf.vlan.ipV6.ra.minInterval

       Time in centi-second."
   ::= {er1646v2Lan3FGVlanEntry 705036800}

er1646v2Lan3FGVlanIpV6RaMaxInterval OBJECT-TYPE
   SYNTAX      TimeTicks
   MAX-ACCESS  read-write
   STATUS      current
   DESCRIPTION
      "Path: ethernet3.editConf.vlan.ipV6.ra.maxInterval

       Time in centi-second."
   ::= {er1646v2Lan3FGVlanEntry 705037056}

er1646v2Lan3FGVlanIpV6RaManagedFlag OBJECT-TYPE
   SYNTAX      INTEGER
               {
               disabled (0),
               enabled (1)
               }
   MAX-ACCESS  read-write
   STATUS      current
   DESCRIPTION
      "Path: ethernet3.editConf.vlan.ipV6.ra.managedFlag

       Possibilities:
               disabled   (0)
               enabled   (1)"
   ::= {er1646v2Lan3FGVlanEntry 705037312}

er1646v2Lan3FGVlanIpV6RaOtherConfFlag OBJECT-TYPE
   SYNTAX      INTEGER
               {
               disabled (0),
               enabled (1)
               }
   MAX-ACCESS  read-write
   STATUS      current
   DESCRIPTION
      "Path: ethernet3.editConf.vlan.ipV6.ra.otherConfFlag

       Possibilities:
               disabled   (0)
               enabled   (1)"
   ::= {er1646v2Lan3FGVlanEntry 705037568}

er1646v2Lan3FGVlanIpV6RaLinkMtu OBJECT-TYPE
   SYNTAX      Integer32
   MAX-ACCESS  read-write
   STATUS      current
   DESCRIPTION
      "Path: ethernet3.editConf.vlan.ipV6.ra.linkMtu"
   ::= {er1646v2Lan3FGVlanEntry 705037824}

er1646v2Lan3FGVlanIpV6RaReachableTime OBJECT-TYPE
   SYNTAX      TimeTicks
   MAX-ACCESS  read-write
   STATUS      current
   DESCRIPTION
      "Path: ethernet3.editConf.vlan.ipV6.ra.reachableTime

       Time in centi-second."
   ::= {er1646v2Lan3FGVlanEntry 705038080}

er1646v2Lan3FGVlanIpV6RaRetransmitTime OBJECT-TYPE
   SYNTAX      TimeTicks
   MAX-ACCESS  read-write
   STATUS      current
   DESCRIPTION
      "Path: ethernet3.editConf.vlan.ipV6.ra.retransmitTime

       Time in centi-second."
   ::= {er1646v2Lan3FGVlanEntry 705038336}

er1646v2Lan3FGVlanIpV6RaHopLimit OBJECT-TYPE
   SYNTAX      Integer32
   MAX-ACCESS  read-write
   STATUS      current
   DESCRIPTION
      "Path: ethernet3.editConf.vlan.ipV6.ra.hopLimit"
   ::= {er1646v2Lan3FGVlanEntry 705038592}

er1646v2Lan3FGVlanIpV6RaDefaultLifeTime OBJECT-TYPE
   SYNTAX      TimeTicks
   MAX-ACCESS  read-write
   STATUS      current
   DESCRIPTION
      "Path: ethernet3.editConf.vlan.ipV6.ra.defaultLifeTime

       Time in centi-second."
   ::= {er1646v2Lan3FGVlanEntry 705038848}

er1646v2Lan3FGVlanIpV6RaDnsOptionsRdnssLifeTime OBJECT-TYPE
   SYNTAX      TimeTicks
   MAX-ACCESS  read-write
   STATUS      current
   DESCRIPTION
      "Path: ethernet3.editConf.vlan.ipV6.ra.dnsOptions.rdnss.lifeTime

       Time in centi-second."
   ::= {er1646v2Lan3FGVlanEntry 705039140}

er1646v2Lan3FGVlanIpV6RaDnsOptionsRdnssImportServers OBJECT-TYPE
   SYNTAX      INTEGER
               {
               disabled (0),
               enabled (1)
               }
   MAX-ACCESS  read-write
   STATUS      current
   DESCRIPTION
      "Path: ethernet3.editConf.vlan.ipV6.ra.dnsOptions.rdnss.importServers

       Possibilities:
               disabled   (0)
               enabled   (1)"
   ::= {er1646v2Lan3FGVlanEntry 705039148}

er1646v2Lan3FGVlanIpV6RaDnsOptionsDnsslLifeTime OBJECT-TYPE
   SYNTAX      TimeTicks
   MAX-ACCESS  read-write
   STATUS      current
   DESCRIPTION
      "Path: ethernet3.editConf.vlan.ipV6.ra.dnsOptions.dnssl.lifeTime

       Time in centi-second."
   ::= {er1646v2Lan3FGVlanEntry 705039172}

er1646v2Lan3FGVlanIpV6RaDnsOptionsDnsslImportDomains OBJECT-TYPE
   SYNTAX      INTEGER
               {
               disabled (0),
               enabled (1)
               }
   MAX-ACCESS  read-write
   STATUS      current
   DESCRIPTION
      "Path: ethernet3.editConf.vlan.ipV6.ra.dnsOptions.dnssl.importDomains

       Possibilities:
               disabled   (0)
               enabled   (1)"
   ::= {er1646v2Lan3FGVlanEntry 705039180}

er1646v2Lan3FGVlanIpV6RsSend OBJECT-TYPE
   SYNTAX      INTEGER
               {
               disabled (0),
               enabled (1)
               }
   MAX-ACCESS  read-write
   STATUS      current
   DESCRIPTION
      "Path: ethernet3.editConf.vlan.ipV6.rs.send

       Possibilities:
               disabled   (0)
               enabled   (1)"
   ::= {er1646v2Lan3FGVlanEntry 705954048}

er1646v2Lan3FGVlanIpV6RsMaxRandomDelay OBJECT-TYPE
   SYNTAX      TimeTicks
   MAX-ACCESS  read-write
   STATUS      current
   DESCRIPTION
      "Path: ethernet3.editConf.vlan.ipV6.rs.maxRandomDelay

       Time in centi-second."
   ::= {er1646v2Lan3FGVlanEntry 705954304}

er1646v2Lan3FGVlanIpV6RsInterval OBJECT-TYPE
   SYNTAX      TimeTicks
   MAX-ACCESS  read-write
   STATUS      current
   DESCRIPTION
      "Path: ethernet3.editConf.vlan.ipV6.rs.interval

       Time in centi-second."
   ::= {er1646v2Lan3FGVlanEntry 705954560}

er1646v2Lan3FGVlanIpV6RsMaxSolicitations OBJECT-TYPE
   SYNTAX      Integer32
   MAX-ACCESS  read-write
   STATUS      current
   DESCRIPTION
      "Path: ethernet3.editConf.vlan.ipV6.rs.maxSolicitations"
   ::= {er1646v2Lan3FGVlanEntry 705954816}

er1646v2Lan3FGVlanIpV6TrafficPolicyInbound OBJECT-TYPE
   SYNTAX      DisplayString
   MAX-ACCESS  read-write
   STATUS      current
   DESCRIPTION
      "Path: ethernet3.editConf.vlan.ipV6.trafficPolicy.inbound"
   ::= {er1646v2Lan3FGVlanEntry 705364224}

er1646v2Lan3FGVlanIpV6TrafficPolicyOutbound OBJECT-TYPE
   SYNTAX      DisplayString
   MAX-ACCESS  read-write
   STATUS      current
   DESCRIPTION
      "Path: ethernet3.editConf.vlan.ipV6.trafficPolicy.outbound"
   ::= {er1646v2Lan3FGVlanEntry 705364480}

er1646v2Lan3FGVlanIpV6FirewallZone OBJECT-TYPE
   SYNTAX      DisplayString
   MAX-ACCESS  read-write
   STATUS      current
   DESCRIPTION
      "Path: ethernet3.editConf.vlan.ipV6.firewall.zone"
   ::= {er1646v2Lan3FGVlanEntry 705429760}

er1646v2Lan3FGVlanIpV6DhcpClientAddrAC OBJECT-TYPE
   SYNTAX      INTEGER
               {
               disabled (0),
               enabled (1)
               }
   MAX-ACCESS  read-write
   STATUS      current
   DESCRIPTION
      "Path: ethernet3.editConf.vlan.ipV6.dhcp.client.addrAutoConfig

       Possibilities:
               disabled   (0)
               enabled   (1)"
   ::= {er1646v2Lan3FGVlanEntry 705307648}

er1646v2Lan3FGVlanIpV6DhcpClientPrDelMode OBJECT-TYPE
   SYNTAX      INTEGER
               {
               disabled (0),
               enabled (1)
               }
   MAX-ACCESS  read-write
   STATUS      current
   DESCRIPTION
      "Path: ethernet3.editConf.vlan.ipV6.dhcp.client.pd.mode

       Possibilities:
               disabled   (0)
               enabled   (1)"
   ::= {er1646v2Lan3FGVlanEntry 705308676}

er1646v2Lan3FGVlanIpV6DhcpClientPrDelPool OBJECT-TYPE
   SYNTAX      DisplayString
   MAX-ACCESS  read-write
   STATUS      current
   DESCRIPTION
      "Path: ethernet3.editConf.vlan.ipV6.dhcp.client.pd.pool"
   ::= {er1646v2Lan3FGVlanEntry 705308680}

er1646v2Lan3FGVlanIpV6DhcpClientPrDelPdExclOpt OBJECT-TYPE
   SYNTAX      INTEGER
               {
               disabled (0),
               enabled (1)
               }
   MAX-ACCESS  read-write
   STATUS      current
   DESCRIPTION
      "Path: ethernet3.editConf.vlan.ipV6.dhcp.client.pd.pdExclOpt

       Possibilities:
               disabled   (0)
               enabled   (1)"
   ::= {er1646v2Lan3FGVlanEntry 705308684}

er1646v2Lan3FGVlanIpV6DhcpClientDnsServerPref OBJECT-TYPE
   SYNTAX      Integer32
   MAX-ACCESS  read-write
   STATUS      current
   DESCRIPTION
      "Path: ethernet3.editConf.vlan.ipV6.dhcp.client.dns.serverPref"
   ::= {er1646v2Lan3FGVlanEntry 705310724}

er1646v2Lan3FGVlanIpV6DhcpClientRapidCommit OBJECT-TYPE
   SYNTAX      INTEGER
               {
               disabled (0),
               enabled (1)
               }
   MAX-ACCESS  read-write
   STATUS      current
   DESCRIPTION
      "Path: ethernet3.editConf.vlan.ipV6.dhcp.client.rapidCommit

       Possibilities:
               disabled   (0)
               enabled   (1)"
   ::= {er1646v2Lan3FGVlanEntry 705309696}

er1646v2Lan3FGVlanIpV6DhcpClientTimersSolTimeOut OBJECT-TYPE
   SYNTAX      TimeTicks
   MAX-ACCESS  read-write
   STATUS      current
   DESCRIPTION
      "Path: ethernet3.editConf.vlan.ipV6.dhcp.client.timers.solTimeOut

       Time in centi-second."
   ::= {er1646v2Lan3FGVlanEntry 705311748}

er1646v2Lan3FGVlanIpV6DhcpClientTimersSolMaxRt OBJECT-TYPE
   SYNTAX      TimeTicks
   MAX-ACCESS  read-write
   STATUS      current
   DESCRIPTION
      "Path: ethernet3.editConf.vlan.ipV6.dhcp.client.timers.solMaxRt

       Time in centi-second."
   ::= {er1646v2Lan3FGVlanEntry 705311752}

er1646v2Lan3FGVlanIpV6DhcpClientTimersInfoRefresh OBJECT-TYPE
   SYNTAX      TimeTicks
   MAX-ACCESS  read-write
   STATUS      current
   DESCRIPTION
      "Path: ethernet3.editConf.vlan.ipV6.dhcp.client.timers.infoRefresh

       Time in centi-second."
   ::= {er1646v2Lan3FGVlanEntry 705311756}

er1646v2Lan3FGVlanIpV6DhcpServerMode OBJECT-TYPE
   SYNTAX      INTEGER
               {
               disabled (0),
               enabled (1)
               }
   MAX-ACCESS  read-write
   STATUS      current
   DESCRIPTION
      "Path: ethernet3.editConf.vlan.ipV6.dhcp.server.mode

       Possibilities:
               disabled   (0)
               enabled   (1)"
   ::= {er1646v2Lan3FGVlanEntry 705315840}

er1646v2Lan3FGVlanIpV6DhcpServerPreference OBJECT-TYPE
   SYNTAX      Integer32
   MAX-ACCESS  read-write
   STATUS      current
   DESCRIPTION
      "Path: ethernet3.editConf.vlan.ipV6.dhcp.server.preference"
   ::= {er1646v2Lan3FGVlanEntry 705316864}

er1646v2Lan3FGVlanIpV6DhcpServerPool OBJECT-TYPE
   SYNTAX      DisplayString
   MAX-ACCESS  read-write
   STATUS      current
   DESCRIPTION
      "Path: ethernet3.editConf.vlan.ipV6.dhcp.server.pool"
   ::= {er1646v2Lan3FGVlanEntry 705317888}

er1646v2Lan3FGVlanIpV6DhcpServerRapidCommit OBJECT-TYPE
   SYNTAX      INTEGER
               {
               disabled (0),
               enabled (1)
               }
   MAX-ACCESS  read-write
   STATUS      current
   DESCRIPTION
      "Path: ethernet3.editConf.vlan.ipV6.dhcp.server.rapidCommit

       Possibilities:
               disabled   (0)
               enabled   (1)"
   ::= {er1646v2Lan3FGVlanEntry 705318912}

er1646v2Lan3FGVlanIpV6DhcpServerTimersInfoRefresh OBJECT-TYPE
   SYNTAX      TimeTicks
   MAX-ACCESS  read-write
   STATUS      current
   DESCRIPTION
      "Path: ethernet3.editConf.vlan.ipV6.dhcp.server.timers.infoRefresh

       Time in centi-second."
   ::= {er1646v2Lan3FGVlanEntry 705319940}

er1646v2Lan3FGVlanIpV6DhcpRelayMode OBJECT-TYPE
   SYNTAX      INTEGER
               {
               disabled (0),
               enabled (1)
               }
   MAX-ACCESS  read-write
   STATUS      current
   DESCRIPTION
      "Path: ethernet3.editConf.vlan.ipV6.dhcp.relay.mode

       Possibilities:
               disabled   (0)
               enabled   (1)"
   ::= {er1646v2Lan3FGVlanEntry 705323040}

er1646v2Lan3FGVlanIpV6SendRedirect OBJECT-TYPE
   SYNTAX      INTEGER
               {
               disabled (0),
               enabled (1)
               }
   MAX-ACCESS  read-write
   STATUS      current
   DESCRIPTION
      "Path: ethernet3.editConf.vlan.ipV6.sendRedirect

       Possibilities:
               disabled   (0)
               enabled   (1)"
   ::= {er1646v2Lan3FGVlanEntry 705101824}

er1646v2Lan3FGVlanIpV6LinkMtu OBJECT-TYPE
   SYNTAX      Integer32
   MAX-ACCESS  read-write
   STATUS      current
   DESCRIPTION
      "Path: ethernet3.editConf.vlan.ipV6.linkMtu"
   ::= {er1646v2Lan3FGVlanEntry 705167360}

er1646v2Lan3FGVlanIpV6InterfaceId OBJECT-TYPE
   SYNTAX      OCTET STRING
   MAX-ACCESS  read-write
   STATUS      current
   DESCRIPTION
      "Path: ethernet3.editConf.vlan.ipV6.interfaceId"
   ::= {er1646v2Lan3FGVlanEntry 705232896}

er1646v2Lan3FGVlanIpV6MF OBJECT-TYPE
   SYNTAX      Integer32
   MAX-ACCESS  read-write
   STATUS      current
   DESCRIPTION
      "Path: ethernet3.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2Lan3FGVlanEntry 705757184}

er1646v2Lan3FGVlanIpV6IcmpMessagesNoRoute OBJECT-TYPE
   SYNTAX      INTEGER
               {
               disabled (0),
               enabled (1)
               }
   MAX-ACCESS  read-write
   STATUS      current
   DESCRIPTION
      "Path: ethernet3.editConf.vlan.ipV6.icmpMessages.noRoute

       Possibilities:
               disabled   (0)
               enabled   (1)"
   ::= {er1646v2Lan3FGVlanEntry 705822976}

er1646v2Lan3FGVlanIpV6IcmpMessagesBeyondScope OBJECT-TYPE
   SYNTAX      INTEGER
               {
               disabled (0),
               enabled (1)
               }
   MAX-ACCESS  read-write
   STATUS      current
   DESCRIPTION
      "Path: ethernet3.editConf.vlan.ipV6.icmpMessages.beyondScope

       Possibilities:
               disabled   (0)
               enabled   (1)"
   ::= {er1646v2Lan3FGVlanEntry 705823488}

er1646v2Lan3FGVlanIpV6IcmpMessagesAddressUnreachable OBJECT-TYPE
   SYNTAX      INTEGER
               {
               disabled (0),
               enabled (1)
               }
   MAX-ACCESS  read-write
   STATUS      current
   DESCRIPTION
      "Path: ethernet3.editConf.vlan.ipV6.icmpMessages.addressUnreachable

       Possibilities:
               disabled   (0)
               enabled   (1)"
   ::= {er1646v2Lan3FGVlanEntry 705823744}

er1646v2Lan3FGVlanIpV6IcmpMessagesPortUnreachable OBJECT-TYPE
   SYNTAX      INTEGER
               {
               disabled (0),
               enabled (1)
               }
   MAX-ACCESS  read-write
   STATUS      current
   DESCRIPTION
      "Path: ethernet3.editConf.vlan.ipV6.icmpMessages.portUnreachable

       Possibilities:
               disabled   (0)
               enabled   (1)"
   ::= {er1646v2Lan3FGVlanEntry 705824000}

er1646v2Lan3FGVlanIpV6IcmpMessagesPacketTooBig OBJECT-TYPE
   SYNTAX      INTEGER
               {
               disabled (0),
               enabled (1)
               }
   MAX-ACCESS  read-write
   STATUS      current
   DESCRIPTION
      "Path: ethernet3.editConf.vlan.ipV6.icmpMessages.packetTooBig

       Possibilities:
               disabled   (0)
               enabled   (1)"
   ::= {er1646v2Lan3FGVlanEntry 705825280}

er1646v2Lan3FGVlanIpV6IcmpMessagesHopLimitExceeded OBJECT-TYPE
   SYNTAX      INTEGER
               {
               disabled (0),
               enabled (1)
               }
   MAX-ACCESS  read-write
   STATUS      current
   DESCRIPTION
      "Path: ethernet3.editConf.vlan.ipV6.icmpMessages.hopLimitExceeded

       Possibilities:
               disabled   (0)
               enabled   (1)"
   ::= {er1646v2Lan3FGVlanEntry 705827840}

er1646v2Lan3FGVlanIpV6IcmpMessagesFragTimeExceeded OBJECT-TYPE
   SYNTAX      INTEGER
               {
               disabled (0),
               enabled (1)
               }
   MAX-ACCESS  read-write
   STATUS      current
   DESCRIPTION
      "Path: ethernet3.editConf.vlan.ipV6.icmpMessages.fragTimeExceeded

       Possibilities:
               disabled   (0)
               enabled   (1)"
   ::= {er1646v2Lan3FGVlanEntry 705828096}

er1646v2Lan3FGVlanIpV6IcmpMessagesHeaderFieldErr OBJECT-TYPE
   SYNTAX      INTEGER
               {
               disabled (0),
               enabled (1)
               }
   MAX-ACCESS  read-write
   STATUS      current
   DESCRIPTION
      "Path: ethernet3.editConf.vlan.ipV6.icmpMessages.headerFieldErr

       Possibilities:
               disabled   (0)
               enabled   (1)"
   ::= {er1646v2Lan3FGVlanEntry 705830400}

er1646v2Lan3FGVlanIpV6IcmpMessagesOptionUnrecognized OBJECT-TYPE
   SYNTAX      INTEGER
               {
               disabled (0),
               enabled (1)
               }
   MAX-ACCESS  read-write
   STATUS      current
   DESCRIPTION
      "Path: ethernet3.editConf.vlan.ipV6.icmpMessages.optionUnrecognized

       Possibilities:
               disabled   (0)
               enabled   (1)"
   ::= {er1646v2Lan3FGVlanEntry 705830912}

er1646v2Lan3FGVlanIpV6IcmpMessagesRedirect OBJECT-TYPE
   SYNTAX      INTEGER
               {
               disabled (0),
               enabled (1)
               }
   MAX-ACCESS  read-write
   STATUS      current
   DESCRIPTION
      "Path: ethernet3.editConf.vlan.ipV6.icmpMessages.redirect

       Possibilities:
               disabled   (0)
               enabled   (1)"
   ::= {er1646v2Lan3FGVlanEntry 705832960}

er1646v2Lan3FGVlanBridgingAccList OBJECT-TYPE
   SYNTAX      DisplayString
   MAX-ACCESS  read-write
   STATUS      current
   DESCRIPTION
      "Path: ethernet3.editConf.vlan.bridging.accessList"
   ::= {er1646v2Lan3FGVlanEntry 453246976}

er1646v2Lan3FGVlanBridgingInACL OBJECT-TYPE
   SYNTAX      DisplayString
   MAX-ACCESS  read-write
   STATUS      current
   DESCRIPTION
      "Path: ethernet3.editConf.vlan.bridging.inAccessList"
   ::= {er1646v2Lan3FGVlanEntry 456916992}

er1646v2Lan3FGVlanBridgingTp OBJECT-TYPE
   SYNTAX      DisplayString
   MAX-ACCESS  read-write
   STATUS      current
   DESCRIPTION
      "Path: ethernet3.editConf.vlan.bridging.trafficPolicy"
   ::= {er1646v2Lan3FGVlanEntry 454295552}

er1646v2Lan3FGVlanBridgingBrGrp OBJECT-TYPE
   SYNTAX      DisplayString
   MAX-ACCESS  read-write
   STATUS      current
   DESCRIPTION
      "Path: ethernet3.editConf.vlan.bridging.bridgeGroup"
   ::= {er1646v2Lan3FGVlanEntry 454819840}

er1646v2Lan3FGVlanBridgingLimBC OBJECT-TYPE
   SYNTAX      INTEGER
               {
               disabled (0),
               enabled (1)
               }
   MAX-ACCESS  read-write
   STATUS      current
   DESCRIPTION
      "Path: ethernet3.editConf.vlan.bridging.limitBroadcasts

       Possibilities:
               disabled   (0)
               enabled   (1)"
   ::= {er1646v2Lan3FGVlanEntry 455081984}

er1646v2Lan3FGVlanBridgingPrivateMode OBJECT-TYPE
   SYNTAX      INTEGER
               {
               disabled (0),
               enabled (1)
               }
   MAX-ACCESS  read-write
   STATUS      current
   DESCRIPTION
      "Path: ethernet3.editConf.vlan.bridging.privateMode

       Possibilities:
               disabled   (0)
               enabled   (1)"
   ::= {er1646v2Lan3FGVlanEntry 459538432}

er1646v2Lan3FGVlanBridgingLearning OBJECT-TYPE
   SYNTAX      INTEGER
               {
               disabled (0),
               enabled (1)
               }
   MAX-ACCESS  read-write
   STATUS      current
   DESCRIPTION
      "Path: ethernet3.editConf.vlan.bridging.learning

       Possibilities:
               disabled   (0)
               enabled   (1)"
   ::= {er1646v2Lan3FGVlanEntry 456130560}

er1646v2Lan3FGVlanBridgingMaxCacheSize OBJECT-TYPE
   SYNTAX      INTEGER
               {
               unlimited (0)
               }
   MAX-ACCESS  read-write
   STATUS      current
   DESCRIPTION
      "Path: ethernet3.editConf.vlan.bridging.maxCacheSize

       Possibilities:
               unlimited   (0)"
   ::= {er1646v2Lan3FGVlanEntry 456392704}

er1646v2Lan3FGVlanBridgingRelearnDropOnRelearn OBJECT-TYPE
   SYNTAX      INTEGER
               {
               disabled (0),
               enabled (1)
               }
   MAX-ACCESS  read-write
   STATUS      current
   DESCRIPTION
      "Path: ethernet3.editConf.vlan.bridging.relearn.dropOnRelearn

       Possibilities:
               disabled   (0)
               enabled   (1)"
   ::= {er1646v2Lan3FGVlanEntry 456655872}

er1646v2Lan3FGVlanBridgingRelearnShutdownThreshold OBJECT-TYPE
   SYNTAX      Integer32
   MAX-ACCESS  read-write
   STATUS      current
   DESCRIPTION
      "Path: ethernet3.editConf.vlan.bridging.relearn.shutdownThreshold"
   ::= {er1646v2Lan3FGVlanEntry 456656896}

er1646v2Lan3FGVlanBridgingRelearnShutdownTime OBJECT-TYPE
   SYNTAX      TimeTicks
   MAX-ACCESS  read-write
   STATUS      current
   DESCRIPTION
      "Path: ethernet3.editConf.vlan.bridging.relearn.shutdownTime

       Time in centi-second."
   ::= {er1646v2Lan3FGVlanEntry 456657920}

er1646v2Lan3FGVlanBridgingRelearnLoopDetection OBJECT-TYPE
   SYNTAX      INTEGER
               {
               disabled (0),
               passive (1),
               active (2)
               }
   MAX-ACCESS  read-write
   STATUS      current
   DESCRIPTION
      "Path: ethernet3.editConf.vlan.bridging.relearn.loopDetection

       Possibilities:
               disabled   (0)
               passive   (1)
               active   (2)"
   ::= {er1646v2Lan3FGVlanEntry 456658944}

er1646v2Lan3FGVlanBridgingRelearnLoopDetectionInterval OBJECT-TYPE
   SYNTAX      TimeTicks
   MAX-ACCESS  read-write
   STATUS      current
   DESCRIPTION
      "Path: ethernet3.editConf.vlan.bridging.relearn.loopDetectionInterval

       Time in centi-second."
   ::= {er1646v2Lan3FGVlanEntry 456659968}

er1646v2Lan3FGVlanBridgingVlanMemberShip OBJECT-TYPE
   SYNTAX      INTEGER
               {
               all (0),
               none (1),
               grouped (2)
               }
   MAX-ACCESS  read-write
   STATUS      current
   DESCRIPTION
      "Path: ethernet3.editConf.vlan.bridging.vlanMemberShip

       Possibilities:
               all   (0)
               none   (1)
               grouped   (2)"
   ::= {er1646v2Lan3FGVlanEntry 457965568}

er1646v2Lan3FGVlanBridgingVlTUntaggedAction OBJECT-TYPE
   SYNTAX      INTEGER
               {
               discard (0),
               accept (1),
               tag (2)
               }
   MAX-ACCESS  read-write
   STATUS      current
   DESCRIPTION
      "Path: ethernet3.editConf.vlan.bridging.vlanTagging.untagged.action

       Possibilities:
               discard   (0)
               accept   (1)
               tag   (2)"
   ::= {er1646v2Lan3FGVlanEntry 459055104}

er1646v2Lan3FGVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.untagged.tagInfo.tpid

       Possibilities:
               dot1Q   (33024)
               dot1ad   (34984)
               0x9100   (37120)
               0x9200   (37376)
               0x9300   (37632)"
   ::= {er1646v2Lan3FGVlanEntry 459059712}

er1646v2Lan3FGVlanBridgingVlTUntaggedTagInfoVid OBJECT-TYPE
   SYNTAX      Integer32
   MAX-ACCESS  read-write
   STATUS      current
   DESCRIPTION
      "Path: ethernet3.editConf.vlan.bridging.vlanTagging.untagged.tagInfo.vid"
   ::= {er1646v2Lan3FGVlanEntry 459060224}

er1646v2Lan3FGVlanBridgingVlTUnknownVlansAction OBJECT-TYPE
   SYNTAX      INTEGER
               {
               discard (0),
               accept (1),
               tag (2)
               }
   MAX-ACCESS  read-write
   STATUS      current
   DESCRIPTION
      "Path: ethernet3.editConf.vlan.bridging.vlanTagging.unknownVlans.action

       Possibilities:
               discard   (0)
               accept   (1)
               tag   (2)"
   ::= {er1646v2Lan3FGVlanEntry 459120640}

er1646v2Lan3FGVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.unknownVlans.tagInfo.tpid

       Possibilities:
               dot1Q   (33024)
               dot1ad   (34984)
               0x9100   (37120)
               0x9200   (37376)
               0x9300   (37632)"
   ::= {er1646v2Lan3FGVlanEntry 459125248}

er1646v2Lan3FGVlanBridgingVlTUnknownVlansTagInfoVid OBJECT-TYPE
   SYNTAX      Integer32
   MAX-ACCESS  read-write
   STATUS      current
   DESCRIPTION
      "Path: ethernet3.editConf.vlan.bridging.vlanTagging.unknownVlans.tagInfo.vid"
   ::= {er1646v2Lan3FGVlanEntry 459125760}

er1646v2Lan3FGVlanBridgingDot1adType OBJECT-TYPE
   SYNTAX      INTEGER
               {
               slOPTg (0),
               cPort (4),
               sPort (1),
               nni (2)
               }
   MAX-ACCESS  read-write
   STATUS      current
   DESCRIPTION
      "Path: ethernet3.editConf.vlan.bridging.dot1ad.type

       Possibilities:
               <OPT>   (0)
               cPort   (4)
               sPort   (1)
               nni   (2)"
   ::= {er1646v2Lan3FGVlanEntry 460850176}

er1646v2Lan3FGVlanBridgingPriority OBJECT-TYPE
   SYNTAX      Integer32
   MAX-ACCESS  read-write
   STATUS      current
   DESCRIPTION
      "Path: ethernet3.editConf.vlan.bridging.priority"
   ::= {er1646v2Lan3FGVlanEntry 453509120}

er1646v2Lan3FGVlanBridgingPathCost OBJECT-TYPE
   SYNTAX      Integer32
   MAX-ACCESS  read-write
   STATUS      current
   DESCRIPTION
      "Path: ethernet3.editConf.vlan.bridging.pathCost"
   ::= {er1646v2Lan3FGVlanEntry 453771264}

er1646v2Lan3FGVlanBridgingInternalPathCost OBJECT-TYPE
   SYNTAX      Integer32
   MAX-ACCESS  read-write
   STATUS      current
   DESCRIPTION
      "Path: ethernet3.editConf.vlan.bridging.internalPathCost"
   ::= {er1646v2Lan3FGVlanEntry 457703424}

er1646v2Lan3FGVlanBridgingTCD OBJECT-TYPE
   SYNTAX      INTEGER
               {
               disabled (0),
               enabled (1)
               }
   MAX-ACCESS  read-write
   STATUS      current
   DESCRIPTION
      "Path: ethernet3.editConf.vlan.bridging.topologyChangeDetection

       Possibilities:
               disabled   (0)
               enabled   (1)"
   ::= {er1646v2Lan3FGVlanEntry 454033408}

er1646v2Lan3FGVlanBridgingRestrictedRole OBJECT-TYPE
   SYNTAX      INTEGER
               {
               disabled (0),
               enabled (1)
               }
   MAX-ACCESS  read-write
   STATUS      current
   DESCRIPTION
      "Path: ethernet3.editConf.vlan.bridging.restrictedRole

       Possibilities:
               disabled   (0)
               enabled   (1)"
   ::= {er1646v2Lan3FGVlanEntry 458227712}

er1646v2Lan3FGVlanBridgingAdminEdge OBJECT-TYPE
   SYNTAX      INTEGER
               {
               disabled (0),
               enabled (1)
               }
   MAX-ACCESS  read-write
   STATUS      current
   DESCRIPTION
      "Path: ethernet3.editConf.vlan.bridging.adminEdge

       Possibilities:
               disabled   (0)
               enabled   (1)"
   ::= {er1646v2Lan3FGVlanEntry 457179136}

er1646v2Lan3FGVlanBridgingOamMacDeviceMac OBJECT-TYPE
   SYNTAX      DisplayString
   MAX-ACCESS  read-write
   STATUS      current
   DESCRIPTION
      "Path: ethernet3.editConf.vlan.bridging.ethOam.macAddress.deviceMac"
   ::= {er1646v2Lan3FGVlanEntry 458506496}

er1646v2Lan3FGVlanBridgingOamMacUserMac OBJECT-TYPE
   SYNTAX      OCTET STRING
   MAX-ACCESS  read-write
   STATUS      current
   DESCRIPTION
      "Path: ethernet3.editConf.vlan.bridging.ethOam.macAddress.userMac

       MAC address."
   ::= {er1646v2Lan3FGVlanEntry 458506368}

er1646v2Lan3FGVlanBridgingOamMacBridgeMac OBJECT-TYPE
   SYNTAX      DisplayString
   MAX-ACCESS  read-write
   STATUS      current
   DESCRIPTION
      "Path: ethernet3.editConf.vlan.bridging.ethOam.macAddress.bridgeMac"
   ::= {er1646v2Lan3FGVlanEntry 458506432}

er1646v2Lan3FGVlanBridgingMgmtInline OBJECT-TYPE
   SYNTAX      INTEGER
               {
               disabled (0),
               enabled (1)
               }
   MAX-ACCESS  read-write
   STATUS      current
   DESCRIPTION
      "Path: ethernet3.editConf.vlan.bridging.mgmtInline

       Possibilities:
               disabled   (0)
               enabled   (1)"
   ::= {er1646v2Lan3FGVlanEntry 458752000}

er1646v2Lan3FGVlanBridgingL2ptMode OBJECT-TYPE
   SYNTAX      INTEGER
               {
               disabled (0),
               enabled (1)
               }
   MAX-ACCESS  read-write
   STATUS      current
   DESCRIPTION
      "Path: ethernet3.editConf.vlan.bridging.l2ProtTunnel.mode

       Possibilities:
               disabled   (0)
               enabled   (1)"
   ::= {er1646v2Lan3FGVlanEntry 459292672}

er1646v2Lan3FGVlanBridgingL2ptProtocols OBJECT-TYPE
   SYNTAX      Integer32
   MAX-ACCESS  read-write
   STATUS      current
   DESCRIPTION
      "Path: ethernet3.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2Lan3FGVlanEntry 459309056}

er1646v2Lan3FGVlanBridgingL2ptDestMac OBJECT-TYPE
   SYNTAX      OCTET STRING
   MAX-ACCESS  read-write
   STATUS      current
   DESCRIPTION
      "Path: ethernet3.editConf.vlan.bridging.l2ProtTunnel.destinationMac

       MAC address."
   ::= {er1646v2Lan3FGVlanEntry 459325440}

er1646v2Lan3FGVlanBridgingL2ptCos OBJECT-TYPE
   SYNTAX      INTEGER
               {
               unchanged (255)
               }
   MAX-ACCESS  read-write
   STATUS      current
   DESCRIPTION
      "Path: ethernet3.editConf.vlan.bridging.l2ProtTunnel.cos

       Possibilities:
               unchanged   (255)"
   ::= {er1646v2Lan3FGVlanEntry 459341824}

er1646v2Lan3FGVlanBridgingL2ptDropThrStp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.stp

       unit name = packets/sec

       Possibilities:
               unlimited   (0)"
   ::= {er1646v2Lan3FGVlanEntry 459358272}

er1646v2Lan3FGVlanBridgingL2ptDropThrLldp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.lldp

       unit name = packets/sec

       Possibilities:
               unlimited   (0)"
   ::= {er1646v2Lan3FGVlanEntry 459358336}

er1646v2Lan3FGVlanBridgingL2ptDropThrOam OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.oam

       unit name = packets/sec

       Possibilities:
               unlimited   (0)"
   ::= {er1646v2Lan3FGVlanEntry 459358400}

er1646v2Lan3FGVlanBridgingL2ptDropThrCdp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.cdp

       unit name = packets/sec

       Possibilities:
               unlimited   (0)"
   ::= {er1646v2Lan3FGVlanEntry 459358464}

er1646v2Lan3FGVlanBridgingL2ptDropThrVtp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.vtp

       unit name = packets/sec

       Possibilities:
               unlimited   (0)"
   ::= {er1646v2Lan3FGVlanEntry 459358528}

er1646v2Lan3FGVlanBridgingL2ptDropThrLacp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.lacp

       unit name = packets/sec

       Possibilities:
               unlimited   (0)"
   ::= {er1646v2Lan3FGVlanEntry 459358592}

er1646v2Lan3FGVlanBridgingL2ptDropThrEfmOam OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.efmOam

       unit name = packets/sec

       Possibilities:
               unlimited   (0)"
   ::= {er1646v2Lan3FGVlanEntry 459358656}

er1646v2Lan3FGVlanBridgingL2ptDropThrPvst OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.pvst

       unit name = packets/sec

       Possibilities:
               unlimited   (0)"
   ::= {er1646v2Lan3FGVlanEntry 459358720}

er1646v2Lan3FGVlanBridgingL2ptDropThrMmrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.mmrp

       unit name = packets/sec

       Possibilities:
               unlimited   (0)"
   ::= {er1646v2Lan3FGVlanEntry 459358784}

er1646v2Lan3FGVlanBridgingL2ptDropThrMvrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.mvrp

       unit name = packets/sec

       Possibilities:
               unlimited   (0)"
   ::= {er1646v2Lan3FGVlanEntry 459358848}

er1646v2Lan3FGVlanBridgingL2ptDropThrGvrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.gvrp

       unit name = packets/sec

       Possibilities:
               unlimited   (0)"
   ::= {er1646v2Lan3FGVlanEntry 459358912}

er1646v2Lan3FGVlanBridgingL2ptDropThrGmrp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.gmrp

       unit name = packets/sec

       Possibilities:
               unlimited   (0)"
   ::= {er1646v2Lan3FGVlanEntry 459358976}

er1646v2Lan3FGVlanBridgingL2ptDropThrDtp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.dtp

       unit name = packets/sec

       Possibilities:
               unlimited   (0)"
   ::= {er1646v2Lan3FGVlanEntry 459359040}

er1646v2Lan3FGVlanBridgingL2ptDropThrPagp OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.pagp

       unit name = packets/sec

       Possibilities:
               unlimited   (0)"
   ::= {er1646v2Lan3FGVlanEntry 459359104}

er1646v2Lan3FGVlanBridgingL2ptDropThrUdld OBJECT-TYPE
   SYNTAX      INTEGER
               {
               unlimited (0)
               }
   UNITS       "packets/sec"
   MAX-ACCESS  read-write
   STATUS      current
   DESCRIPTION
      "Path: ethernet3.editConf.vlan.bridging.l2ProtTunnel.dropThresholds.udld

       unit name = packets/sec

       Possibilities:
               unlimited   (0)"
   ::= {er1646v2Lan3FGVlanEntry 459359168}

er1646v2Lan3FGVlanVlanVid OBJECT-TYPE
   SYNTAX      INTEGER
               {
               untagged (0),
               prioTagged (4096),
               notUsed (4097)
               }
   MAX-ACCESS  read-write
   STATUS      current
   DESCRIPTION
      "Path: ethernet3.editConf.vlan.vlan.vid

       Possibilities:
               untagged   (0)
               prioTagged   (4096)
               notUsed   (4097)"
   ::= {er1646v2Lan3FGVlanEntry 234946560}

er1646v2Lan3FGVlanVlanVidExtensionSingle OBJECT-TYPE
   SYNTAX      OCTET STRING
   MAX-ACCESS  read-write
   STATUS      current
   DESCRIPTION
      "Path: ethernet3.editConf.vlan.vlan.vidExtension.single"
   ::= {er1646v2Lan3FGVlanEntry 235340032}

er1646v2Lan3FGVlanVlanVidExtensionEndVid OBJECT-TYPE
   SYNTAX      Integer32
   MAX-ACCESS  read-write
   STATUS      current
   DESCRIPTION
      "Path: ethernet3.editConf.vlan.vlan.vidExtension.endVid"
   ::= {er1646v2Lan3FGVlanEntry 235340288}

er1646v2Lan3FGVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.tpid

       Possibilities:
               dot1Q   (33024)
               dot1ad   (34984)
               0x9100   (37120)
               0x9200   (37376)
               0x9300   (37632)"
   ::= {er1646v2Lan3FGVlanEntry 241238016}

er1646v2Lan3FGVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: ethernet3.editConf.vlan.vlan.tagSignificance

       Possibilities:
               global   (0)
               local   (1)
               sVlan   (2)
               sVlanGlobal   (6)
               cVlan   (3)
               scVlan   (5)
               cVlanLocal   (4)"
   ::= {er1646v2Lan3FGVlanEntry 235012096}

er1646v2Lan3FGVlanVlanChTos OBJECT-TYPE
   SYNTAX      INTEGER
               {
               disabled (0),
               enabled (1)
               }
   MAX-ACCESS  read-write
   STATUS      current
   DESCRIPTION
      "Path: ethernet3.editConf.vlan.vlan.changeTos

       Possibilities:
               disabled   (0)
               enabled   (1)"
   ::= {er1646v2Lan3FGVlanEntry 235208704}

er1646v2Lan3FGVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235143424}

er1646v2Lan3FGVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235143680}

er1646v2Lan3FGVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235143936}

er1646v2Lan3FGVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235144192}

er1646v2Lan3FGVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235144448}

er1646v2Lan3FGVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235144704}

er1646v2Lan3FGVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235144960}

er1646v2Lan3FGVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet3.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2Lan3FGVlanEntry 235145216}

er1646v2Lan3FGVlanVlanTxCos OBJECT-TYPE
   SYNTAX      INTEGER
               {
               tosCosMap (8),
               queueCosMap (16)
               }
   MAX-ACCESS  read-write
   STATUS      current
   DESCRIPTION
      "Path: ethernet3.editConf.vlan.vlan.txCos

       Possibilities:
               tosCosMap   (8)
               queueCosMap   (16)"
   ::= {er1646v2Lan3FGVlanEntry 235077632}

er1646v2Lan3FGVlanVlanCCMapP0 OBJECT-TYPE
   SYNTAX      Integer32
   MAX-ACCESS  read-write
   STATUS      current
   DESCRIPTION
      "Path: ethernet3.editConf.vlan.vlan.cosCosMap.p0"
   ::= {er1646v2Lan3FGVlanEntry 241303808}

er1646v2Lan3FGVlanVlanCCMapP1 OBJECT-TYPE
   SYNTAX      Integer32
   MAX-ACCESS  read-write
   STATUS      current
   DESCRIPTION
      "Path: ethernet3.editConf.vlan.vlan.cosCosMap.p1"
   ::= {er1646v2Lan3FGVlanEntry 241304064}

er1646v2Lan3FGVlanVlanCCMapP2 OBJECT-TYPE
   SYNTAX      Integer32
   MAX-ACCESS  read-write
   STATUS      current
   DESCRIPTION
      "Path: ethernet3.editConf.vlan.vlan.cosCosMap.p2"
   ::= {er1646v2Lan3FGVlanEntry 241304320}

er1646v2Lan3FGVlanVlanCCMapP3 OBJECT-TYPE
   SYNTAX      Integer32
   MAX-ACCESS  read-write
   STATUS      current
   DESCRIPTION
      "Path: ethernet3.editConf.vlan.vlan.cosCosMap.p3"
   ::= {er1646v2Lan3FGVlanEntry 241304576}

er1646v2Lan3FGVlanVlanCCMapP4 OBJECT-TYPE
   SYNTAX      Integer32
   MAX-ACCESS  read-write
   STATUS      current
   DESCRIPTION
      "Path: ethernet3.editConf.vlan.vlan.cosCosMap.p4"
   ::= {er1646v2Lan3FGVlanEntry 241304832}

er1646v2Lan3FGVlanVlanCCMapP5 OBJECT-TYPE
   SYNTAX      Integer32
   MAX-ACCESS  read-write
   STATUS      current
   DESCRIPTION
      "Path: ethernet3.editConf.vlan.vlan.cosCosMap.p5"
   ::= {er1646v2Lan3FGVlanEntry 241305088}

er1646v2Lan3FGVlanVlanCCMapP6 OBJECT-TYPE
   SYNTAX      Integer32
   MAX-ACCESS  read-write
   STATUS      current
   DESCRIPTION
      "Path: ethernet3.editConf.vlan.vlan.cosCosMap.p6"
   ::= {er1646v2Lan3FGVlanEntry 241305344}

er1646v2Lan3FGVlanVlanCCMapP7 OBJECT-TYPE
   SYNTAX      Integer32
   MAX-ACCESS  read-write
   STATUS      current
   DESCRIPTION
      "Path: ethernet3.editConf.vlan.vlan.cosCosMap.p7"
   ::= {er1646v2Lan3FGVlanEntry 241305600}

er1646v2Lan3FGVlanVlanQCMapQueue1 OBJECT-TYPE
   SYNTAX      Integer32
   MAX-ACCESS  read-write
   STATUS      current
   DESCRIPTION
      "Path: ethernet3.editConf.vlan.vlan.queueCosMap.queue1"
   ::= {er1646v2Lan3FGVlanEntry 241434880}

er1646v2Lan3FGVlanVlanQCMapQueue2 OBJECT-TYPE
   SYNTAX      Integer32
   MAX-ACCESS  read-write
   STATUS      current
   DESCRIPTION
      "Path: ethernet3.editConf.vlan.vlan.queueCosMap.queue2"
   ::= {er1646v2Lan3FGVlanEntry 241435136}

er1646v2Lan3FGVlanVlanQCMapQueue3 OBJECT-TYPE
   SYNTAX      Integer32
   MAX-ACCESS  read-write
   STATUS      current
   DESCRIPTION
      "Path: ethernet3.editConf.vlan.vlan.queueCosMap.queue3"
   ::= {er1646v2Lan3FGVlanEntry 241435392}

er1646v2Lan3FGVlanVlanQCMapQueue4 OBJECT-TYPE
   SYNTAX      Integer32
   MAX-ACCESS  read-write
   STATUS      current
   DESCRIPTION
      "Path: ethernet3.editConf.vlan.vlan.queueCosMap.queue4"
   ::= {er1646v2Lan3FGVlanEntry 241435648}

er1646v2Lan3FGVlanVlanQCMapQueue5 OBJECT-TYPE
   SYNTAX      Integer32
   MAX-ACCESS  read-write
   STATUS      current
   DESCRIPTION
      "Path: ethernet3.editConf.vlan.vlan.queueCosMap.queue5"
   ::= {er1646v2Lan3FGVlanEntry 241435904}

er1646v2Lan3FGVlanVlanQCMapLowDelayQueue OBJECT-TYPE
   SYNTAX      Integer32
   MAX-ACCESS  read-write
   STATUS      current
   DESCRIPTION
      "Path: ethernet3.editConf.vlan.vlan.queueCosMap.lowDelayQueue"
   ::= {er1646v2Lan3FGVlanEntry 241436160}

er1646v2Lan3FGVlanVlanQCMapLowDelay2Queue OBJECT-TYPE
   SYNTAX      Integer32
   MAX-ACCESS  read-write
   STATUS      current
   DESCRIPTION
      "Path: ethernet3.editConf.vlan.vlan.queueCosMap.lowDelay2Queue"
   ::= {er1646v2Lan3FGVlanEntry 241436416}

er1646v2Lan3FGVlanVlanQCMapSystemQueue OBJECT-TYPE
   SYNTAX      Integer32
   MAX-ACCESS  read-write
   STATUS      current
   DESCRIPTION
      "Path: ethernet3.editConf.vlan.vlan.queueCosMap.systemQueue"
   ::= {er1646v2Lan3FGVlanEntry 241436672}

er1646v2Lan3FGVlanVlanQinQSVid OBJECT-TYPE
   SYNTAX      Integer32
   MAX-ACCESS  read-write
   STATUS      current
   DESCRIPTION
      "Path: ethernet3.editConf.vlan.vlan.tunnel.sVid"
   ::= {er1646v2Lan3FGVlanEntry 241172736}

er1646v2Lan3FGVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.tunnel.sTpid

       Possibilities:
               dot1Q   (33024)
               dot1ad   (34984)
               0x9100   (37120)
               0x9200   (37376)
               0x9300   (37632)"
   ::= {er1646v2Lan3FGVlanEntry 241172992}

er1646v2Lan3FGVlanVlanArpTimeOut OBJECT-TYPE
   SYNTAX      TimeTicks
   MAX-ACCESS  read-write
   STATUS      current
   DESCRIPTION
      "Path: ethernet3.editConf.vlan.vlan.arp.timeOut

       Time in centi-second."
   ::= {er1646v2Lan3FGVlanEntry 235277312}

er1646v2Lan3FGVlanVlanArpProxyArp OBJECT-TYPE
   SYNTAX      INTEGER
               {
               disabled (0),
               enabled (1)
               }
   MAX-ACCESS  read-write
   STATUS      current
   DESCRIPTION
      "Path: ethernet3.editConf.vlan.vlan.arp.proxyArp

       Possibilities:
               disabled   (0)
               enabled   (1)"
   ::= {er1646v2Lan3FGVlanEntry 235287040}

er1646v2Lan3FGVlanBandwidthMode OBJECT-TYPE
   SYNTAX      INTEGER
               {
               reshaping (1),
               policing (2),
               policingReshape (3)
               }
   MAX-ACCESS  read-write
   STATUS      current
   DESCRIPTION
      "Path: ethernet3.editConf.vlan.bandwidth.mode

       Possibilities:
               reshaping   (1)
               policing   (2)
               policingReshape   (3)"
   ::= {er1646v2Lan3FGVlanEntry 148897792}

er1646v2Lan3FGVlanBandwidthCir OBJECT-TYPE
   SYNTAX      Integer32
   MAX-ACCESS  read-write
   STATUS      current
   DESCRIPTION
      "Path: ethernet3.editConf.vlan.bandwidth.cir"
   ::= {er1646v2Lan3FGVlanEntry 135266304}

er1646v2Lan3FGVlanBandwidthEir OBJECT-TYPE
   SYNTAX      Integer32
   MAX-ACCESS  read-write
   STATUS      current
   DESCRIPTION
      "Path: ethernet3.editConf.vlan.bandwidth.eir"
   ::= {er1646v2Lan3FGVlanEntry 141557760}

er1646v2Lan3FGVlanBandwidthUnit OBJECT-TYPE
   SYNTAX      INTEGER
               {
               bitssec (1),
               percent (2)
               }
   MAX-ACCESS  read-write
   STATUS      current
   DESCRIPTION
      "Path: ethernet3.editConf.vlan.bandwidth.unit

       Possibilities:
               bits/sec   (1)
               percent   (2)"
   ::= {er1646v2Lan3FGVlanEntry 139460608}

er1646v2Lan3FGVlanBandwidthTc OBJECT-TYPE
   SYNTAX      INTEGER
               {
               auto (0)
               }
   MAX-ACCESS  read-write
   STATUS      current
   DESCRIPTION
      "Path: ethernet3.editConf.vlan.bandwidth.tc

       Possibilities:
               auto   (0)"
   ::= {er1646v2Lan3FGVlanEntry 140509184}

er1646v2Lan3FGVlanBandwidthTcFactor OBJECT-TYPE
   SYNTAX      INTEGER
               {
               ms (10),
               s100us (1)
               }
   MAX-ACCESS  read-write
   STATUS      current
   DESCRIPTION
      "Path: ethernet3.editConf.vlan.bandwidth.tcFactor

       Possibilities:
               ms   (10)
               *100us   (1)"
   ::= {er1646v2Lan3FGVlanEntry 142606336}

er1646v2Lan3FGVlanBandwidthCorrType OBJECT-TYPE
   SYNTAX      INTEGER
               {
               noCorrection (0),
               predefined (1),
               manual (2)
               }
   MAX-ACCESS  read-write
   STATUS      current
   DESCRIPTION
      "Path: ethernet3.editConf.vlan.bandwidth.correction.type

       Possibilities:
               noCorrection   (0)
               predefined   (1)
               manual   (2)"
   ::= {er1646v2Lan3FGVlanEntry 136445952}

er1646v2Lan3FGVlanBandwidthCorrPredefEncapsFrameRelay OBJECT-TYPE
   SYNTAX      DisplayString
   MAX-ACCESS  read-write
   STATUS      current
   DESCRIPTION
      "Path: ethernet3.editConf.vlan.bandwidth.correction.predefined.encapsulation.frameRelay"
   ::= {er1646v2Lan3FGVlanEntry 136594432}

er1646v2Lan3FGVlanBandwidthCorrPredefEncapsPpp OBJECT-TYPE
   SYNTAX      DisplayString
   MAX-ACCESS  read-write
   STATUS      current
   DESCRIPTION
      "Path: ethernet3.editConf.vlan.bandwidth.correction.predefined.encapsulation.ppp"
   ::= {er1646v2Lan3FGVlanEntry 136595456}

er1646v2Lan3FGVlanBandwidthCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.vlan.bandwidth.correction.predefined.encapsulation.atm.higherLayer

       Possibilities:
               rfc2684   (0)
               ppp   (1)
               pppOverEthernet   (2)"
   ::= {er1646v2Lan3FGVlanEntry 136596608}

er1646v2Lan3FGVlanBandwidthCorrPredefEncapsAtmMp OBJECT-TYPE
   SYNTAX      INTEGER
               {
               llcEncapsulation (0),
               vcMultiplexing (1)
               }
   MAX-ACCESS  read-write
   STATUS      current
   DESCRIPTION
      "Path: ethernet3.editConf.vlan.bandwidth.correction.predefined.encapsulation.atm.multiProtocol

       Possibilities:
               llcEncapsulation   (0)
               vcMultiplexing   (1)"
   ::= {er1646v2Lan3FGVlanEntry 136596736}

er1646v2Lan3FGVlanBandwidthCorrPredefEncapsHdlc OBJECT-TYPE
   SYNTAX      DisplayString
   MAX-ACCESS  read-write
   STATUS      current
   DESCRIPTION
      "Path: ethernet3.editConf.vlan.bandwidth.correction.predefined.encapsulation.hdlc"
   ::= {er1646v2Lan3FGVlanEntry 136597504}

er1646v2Lan3FGVlanBandwidthCorrPredefEncapsEfmFs OBJECT-TYPE
   SYNTAX      Integer32
   MAX-ACCESS  read-write
   STATUS      current
   DESCRIPTION
      "Path: ethernet3.editConf.vlan.bandwidth.correction.predefined.encapsulation.efm.fragmentSize"
   ::= {er1646v2Lan3FGVlanEntry 136598656}

er1646v2Lan3FGVlanBandwidthCorrPredefEncapsEfmIb OBJECT-TYPE
   SYNTAX      Integer32
   MAX-ACCESS  read-write
   STATUS      current
   DESCRIPTION
      "Path: ethernet3.editConf.vlan.bandwidth.correction.predefined.encapsulation.efm.idleBytes"
   ::= {er1646v2Lan3FGVlanEntry 136598784}

er1646v2Lan3FGVlanBandwidthCorrPredefMode OBJECT-TYPE
   SYNTAX      INTEGER
               {
               routing (0),
               bridging (1)
               }
   MAX-ACCESS  read-write
   STATUS      current
   DESCRIPTION
      "Path: ethernet3.editConf.vlan.bandwidth.correction.predefined.mode

       Possibilities:
               routing   (0)
               bridging   (1)"
   ::= {er1646v2Lan3FGVlanEntry 136609792}

er1646v2Lan3FGVlanBandwidthCorrManualOverhead OBJECT-TYPE
   SYNTAX      Integer32
   MAX-ACCESS  read-write
   STATUS      current
   DESCRIPTION
      "Path: ethernet3.editConf.vlan.bandwidth.correction.manual.overhead"
   ::= {er1646v2Lan3FGVlanEntry 136708608}

er1646v2Lan3FGVlanBandwidthCorrManualFrameData OBJECT-TYPE
   SYNTAX      Counter32
   MAX-ACCESS  read-write
   STATUS      current
   DESCRIPTION
      "Path: ethernet3.editConf.vlan.bandwidth.correction.manual.frameData

       32 bit unsigned wrappable counter."
   ::= {er1646v2Lan3FGVlanEntry 136709120}

er1646v2Lan3FGVlanBandwidthCorrManualFrameHeader OBJECT-TYPE
   SYNTAX      Counter32
   MAX-ACCESS  read-write
   STATUS      current
   DESCRIPTION
      "Path: ethernet3.editConf.vlan.bandwidth.correction.manual.frameHeader

       32 bit unsigned wrappable counter."
   ::= {er1646v2Lan3FGVlanEntry 136709632}

er1646v2Lan3FGVlanBandwidthMaxFifoQLen OBJECT-TYPE
   SYNTAX      Integer32
   MAX-ACCESS  read-write
   STATUS      current
   DESCRIPTION
      "Path: ethernet3.editConf.vlan.bandwidth.maxFifoQLen"
   ::= {er1646v2Lan3FGVlanEntry 137363456}

er1646v2Lan3FGVlanBandwidthDeFlagCir OBJECT-TYPE
   SYNTAX      INTEGER
               {
               allowed (1),
               notAllowed (2)
               }
   MAX-ACCESS  read-write
   STATUS      current
   DESCRIPTION
      "Path: ethernet3.editConf.vlan.bandwidth.deFlag.cir

       Possibilities:
               allowed   (1)
               notAllowed   (2)"
   ::= {er1646v2Lan3FGVlanEntry 147853312}

er1646v2Lan3FGVlanBandwidthDeFlagEir OBJECT-TYPE
   SYNTAX      INTEGER
               {
               allowed (1),
               notAllowed (2)
               }
   MAX-ACCESS  read-write
   STATUS      current
   DESCRIPTION
      "Path: ethernet3.editConf.vlan.bandwidth.deFlag.eir

       Possibilities:
               allowed   (1)
               notAllowed   (2)"
   ::= {er1646v2Lan3FGVlanEntry 147857408}

er1646v2Lan3FGVlanBandwidthDeFlagViolate OBJECT-TYPE
   SYNTAX      INTEGER
               {
               allowed (1),
               notAllowed (2)
               }
   MAX-ACCESS  read-write
   STATUS      current
   DESCRIPTION
      "Path: ethernet3.editConf.vlan.bandwidth.deFlag.violate

       Possibilities:
               allowed   (1)
               notAllowed   (2)"
   ::= {er1646v2Lan3FGVlanEntry 147861504}

er1646v2Lan3FGVlanBandwidthActCirActNone OBJECT-TYPE
   SYNTAX      OCTET STRING
   MAX-ACCESS  read-write
   STATUS      current
   DESCRIPTION
      "Path: ethernet3.editConf.vlan.bandwidth.action.cirAction.none"
   ::= {er1646v2Lan3FGVlanEntry 150085632}

er1646v2Lan3FGVlanBandwidthActCirActEthCos1 OBJECT-TYPE
   SYNTAX      INTEGER
               {
               unchanged (256)
               }
   MAX-ACCESS  read-write
   STATUS      current
   DESCRIPTION
      "Path: ethernet3.editConf.vlan.bandwidth.action.cirAction.ethernet.cosDepth1

       Possibilities:
               unchanged   (256)"
   ::= {er1646v2Lan3FGVlanEntry 150094080}

er1646v2Lan3FGVlanBandwidthActCirActEthDei1 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth1

       Possibilities:
               unchanged   (255)
               clear   (0)
               set   (1)"
   ::= {er1646v2Lan3FGVlanEntry 150099200}

er1646v2Lan3FGVlanBandwidthActCirActEthCos2 OBJECT-TYPE
   SYNTAX      INTEGER
               {
               unchanged (256)
               }
   MAX-ACCESS  read-write
   STATUS      current
   DESCRIPTION
      "Path: ethernet3.editConf.vlan.bandwidth.action.cirAction.ethernet.cosDepth2

       Possibilities:
               unchanged   (256)"
   ::= {er1646v2Lan3FGVlanEntry 150094336}

er1646v2Lan3FGVlanBandwidthActCirActEthDei2 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth2

       Possibilities:
               unchanged   (255)
               clear   (0)
               set   (1)"
   ::= {er1646v2Lan3FGVlanEntry 150099456}

er1646v2Lan3FGVlanBandwidthActCirActEthCos3 OBJECT-TYPE
   SYNTAX      INTEGER
               {
               unchanged (256)
               }
   MAX-ACCESS  read-write
   STATUS      current
   DESCRIPTION
      "Path: ethernet3.editConf.vlan.bandwidth.action.cirAction.ethernet.cosDepth3

       Possibilities:
               unchanged   (256)"
   ::= {er1646v2Lan3FGVlanEntry 150094592}

er1646v2Lan3FGVlanBandwidthActCirActEthDei3 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth3

       Possibilities:
               unchanged   (255)
               clear   (0)
               set   (1)"
   ::= {er1646v2Lan3FGVlanEntry 150099712}

er1646v2Lan3FGVlanBandwidthActCirActEthCos4 OBJECT-TYPE
   SYNTAX      INTEGER
               {
               unchanged (256)
               }
   MAX-ACCESS  read-write
   STATUS      current
   DESCRIPTION
      "Path: ethernet3.editConf.vlan.bandwidth.action.cirAction.ethernet.cosDepth4

       Possibilities:
               unchanged   (256)"
   ::= {er1646v2Lan3FGVlanEntry 150094848}

er1646v2Lan3FGVlanBandwidthActCirActEthDei4 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth4

       Possibilities:
               unchanged   (255)
               clear   (0)
               set   (1)"
   ::= {er1646v2Lan3FGVlanEntry 150099968}

er1646v2Lan3FGVlanBandwidthActCirActEthCos5 OBJECT-TYPE
   SYNTAX      INTEGER
               {
               unchanged (256)
               }
   MAX-ACCESS  read-write
   STATUS      current
   DESCRIPTION
      "Path: ethernet3.editConf.vlan.bandwidth.action.cirAction.ethernet.cosDepth5

       Possibilities:
               unchanged   (256)"
   ::= {er1646v2Lan3FGVlanEntry 150095104}

er1646v2Lan3FGVlanBandwidthActCirActEthDei5 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth5

       Possibilities:
               unchanged   (255)
               clear   (0)
               set   (1)"
   ::= {er1646v2Lan3FGVlanEntry 150100224}

er1646v2Lan3FGVlanBandwidthActCirActEthCos6 OBJECT-TYPE
   SYNTAX      INTEGER
               {
               unchanged (256)
               }
   MAX-ACCESS  read-write
   STATUS      current
   DESCRIPTION
      "Path: ethernet3.editConf.vlan.bandwidth.action.cirAction.ethernet.cosDepth6

       Possibilities:
               unchanged   (256)"
   ::= {er1646v2Lan3FGVlanEntry 150095360}

er1646v2Lan3FGVlanBandwidthActCirActEthDei6 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth6

       Possibilities:
               unchanged   (255)
               clear   (0)
               set   (1)"
   ::= {er1646v2Lan3FGVlanEntry 150100480}

er1646v2Lan3FGVlanBandwidthActCirActEthCos7 OBJECT-TYPE
   SYNTAX      INTEGER
               {
               unchanged (256)
               }
   MAX-ACCESS  read-write
   STATUS      current
   DESCRIPTION
      "Path: ethernet3.editConf.vlan.bandwidth.action.cirAction.ethernet.cosDepth7

       Possibilities:
               unchanged   (256)"
   ::= {er1646v2Lan3FGVlanEntry 150095616}

er1646v2Lan3FGVlanBandwidthActCirActEthDei7 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth7

       Possibilities:
               unchanged   (255)
               clear   (0)
               set   (1)"
   ::= {er1646v2Lan3FGVlanEntry 150100736}

er1646v2Lan3FGVlanBandwidthActCirActEthCos8 OBJECT-TYPE
   SYNTAX      INTEGER
               {
               unchanged (256)
               }
   MAX-ACCESS  read-write
   STATUS      current
   DESCRIPTION
      "Path: ethernet3.editConf.vlan.bandwidth.action.cirAction.ethernet.cosDepth8

       Possibilities:
               unchanged   (256)"
   ::= {er1646v2Lan3FGVlanEntry 150095872}

er1646v2Lan3FGVlanBandwidthActCirActEthDei8 OBJECT-TYPE
   SYNTAX      INTEGER
               {
               unchanged (255),
               clear (0),
               set (1)
               }
   MAX-ACCESS  read-write
   STATUS      current
   DESCRIPTION
      "Path: ethernet3.editConf.vlan.bandwidth.action.cirAction.ethernet.deiDepth8

       Possibilities:
               unchanged   (255)
               clear   (0)
               set   (1)"
   ::= {er1646v2Lan3FGVlanEntry 150100992}

er1646v2Lan3FGVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 150096128}

er1646v2Lan3FGVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 150096384}

er1646v2Lan3FGVlanBandwidthActCirActEthDrpLev OBJECT-TYPE
   SYNTAX      INTEGER
               {
               unchanged (0)
               }
   MAX-ACCESS  read-write
   STATUS      current
   DESCRIPTION
      "Path: ethernet3.editConf.vlan.bandwidth.action.cirAction.ethernet.dropLevel

       Possibilities:
               unchanged   (0)"
   ::= {er1646v2Lan3FGVlanEntry 150096640}

er1646v2Lan3FGVlanBandwidthActCirActEthDeFlag OBJECT-TYPE
   SYNTAX      INTEGER
               {
               unchanged (255),
               clear (0),
               set (1)
               }
   MAX-ACCESS  read-write
   STATUS      current
   DESCRIPTION
      "Path: ethernet3.editConf.vlan.bandwidth.action.cirAction.ethernet.deFlag

       Possibilities:
               unchanged   (255)
               clear   (0)
               set   (1)"
   ::= {er1646v2Lan3FGVlanEntry 150097408}

er1646v2Lan3FGVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 150120704}

er1646v2Lan3FGVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 150120960}

er1646v2Lan3FGVlanBandwidthActCirActIpDrpLev OBJECT-TYPE
   SYNTAX      INTEGER
               {
               unchanged (0)
               }
   MAX-ACCESS  read-write
   STATUS      current
   DESCRIPTION
      "Path: ethernet3.editConf.vlan.bandwidth.action.cirAction.ip.dropLevel

       Possibilities:
               unchanged   (0)"
   ::= {er1646v2Lan3FGVlanEntry 150121216}

er1646v2Lan3FGVlanBandwidthActCirActIpDeFlag OBJECT-TYPE
   SYNTAX      INTEGER
               {
               unchanged (255),
               clear (0),
               set (1)
               }
   MAX-ACCESS  read-write
   STATUS      current
   DESCRIPTION
      "Path: ethernet3.editConf.vlan.bandwidth.action.cirAction.ip.deFlag

       Possibilities:
               unchanged   (255)
               clear   (0)
               set   (1)"
   ::= {er1646v2Lan3FGVlanEntry 150121984}

er1646v2Lan3FGVlanBandwidthActEirActNone OBJECT-TYPE
   SYNTAX      OCTET STRING
   MAX-ACCESS  read-write
   STATUS      current
   DESCRIPTION
      "Path: ethernet3.editConf.vlan.bandwidth.action.eirAction.none"
   ::= {er1646v2Lan3FGVlanEntry 150216704}

er1646v2Lan3FGVlanBandwidthActEirActEthCos1 OBJECT-TYPE
   SYNTAX      INTEGER
               {
               unchanged (256)
               }
   MAX-ACCESS  read-write
   STATUS      current
   DESCRIPTION
      "Path: ethernet3.editConf.vlan.bandwidth.action.eirAction.ethernet.cosDepth1

       Possibilities:
               unchanged   (256)"
   ::= {er1646v2Lan3FGVlanEntry 150225152}

er1646v2Lan3FGVlanBandwidthActEirActEthDei1 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth1

       Possibilities:
               unchanged   (255)
               clear   (0)
               set   (1)"
   ::= {er1646v2Lan3FGVlanEntry 150230272}

er1646v2Lan3FGVlanBandwidthActEirActEthCos2 OBJECT-TYPE
   SYNTAX      INTEGER
               {
               unchanged (256)
               }
   MAX-ACCESS  read-write
   STATUS      current
   DESCRIPTION
      "Path: ethernet3.editConf.vlan.bandwidth.action.eirAction.ethernet.cosDepth2

       Possibilities:
               unchanged   (256)"
   ::= {er1646v2Lan3FGVlanEntry 150225408}

er1646v2Lan3FGVlanBandwidthActEirActEthDei2 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth2

       Possibilities:
               unchanged   (255)
               clear   (0)
               set   (1)"
   ::= {er1646v2Lan3FGVlanEntry 150230528}

er1646v2Lan3FGVlanBandwidthActEirActEthCos3 OBJECT-TYPE
   SYNTAX      INTEGER
               {
               unchanged (256)
               }
   MAX-ACCESS  read-write
   STATUS      current
   DESCRIPTION
      "Path: ethernet3.editConf.vlan.bandwidth.action.eirAction.ethernet.cosDepth3

       Possibilities:
               unchanged   (256)"
   ::= {er1646v2Lan3FGVlanEntry 150225664}

er1646v2Lan3FGVlanBandwidthActEirActEthDei3 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth3

       Possibilities:
               unchanged   (255)
               clear   (0)
               set   (1)"
   ::= {er1646v2Lan3FGVlanEntry 150230784}

er1646v2Lan3FGVlanBandwidthActEirActEthCos4 OBJECT-TYPE
   SYNTAX      INTEGER
               {
               unchanged (256)
               }
   MAX-ACCESS  read-write
   STATUS      current
   DESCRIPTION
      "Path: ethernet3.editConf.vlan.bandwidth.action.eirAction.ethernet.cosDepth4

       Possibilities:
               unchanged   (256)"
   ::= {er1646v2Lan3FGVlanEntry 150225920}

er1646v2Lan3FGVlanBandwidthActEirActEthDei4 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth4

       Possibilities:
               unchanged   (255)
               clear   (0)
               set   (1)"
   ::= {er1646v2Lan3FGVlanEntry 150231040}

er1646v2Lan3FGVlanBandwidthActEirActEthCos5 OBJECT-TYPE
   SYNTAX      INTEGER
               {
               unchanged (256)
               }
   MAX-ACCESS  read-write
   STATUS      current
   DESCRIPTION
      "Path: ethernet3.editConf.vlan.bandwidth.action.eirAction.ethernet.cosDepth5

       Possibilities:
               unchanged   (256)"
   ::= {er1646v2Lan3FGVlanEntry 150226176}

er1646v2Lan3FGVlanBandwidthActEirActEthDei5 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth5

       Possibilities:
               unchanged   (255)
               clear   (0)
               set   (1)"
   ::= {er1646v2Lan3FGVlanEntry 150231296}

er1646v2Lan3FGVlanBandwidthActEirActEthCos6 OBJECT-TYPE
   SYNTAX      INTEGER
               {
               unchanged (256)
               }
   MAX-ACCESS  read-write
   STATUS      current
   DESCRIPTION
      "Path: ethernet3.editConf.vlan.bandwidth.action.eirAction.ethernet.cosDepth6

       Possibilities:
               unchanged   (256)"
   ::= {er1646v2Lan3FGVlanEntry 150226432}

er1646v2Lan3FGVlanBandwidthActEirActEthDei6 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth6

       Possibilities:
               unchanged   (255)
               clear   (0)
               set   (1)"
   ::= {er1646v2Lan3FGVlanEntry 150231552}

er1646v2Lan3FGVlanBandwidthActEirActEthCos7 OBJECT-TYPE
   SYNTAX      INTEGER
               {
               unchanged (256)
               }
   MAX-ACCESS  read-write
   STATUS      current
   DESCRIPTION
      "Path: ethernet3.editConf.vlan.bandwidth.action.eirAction.ethernet.cosDepth7

       Possibilities:
               unchanged   (256)"
   ::= {er1646v2Lan3FGVlanEntry 150226688}

er1646v2Lan3FGVlanBandwidthActEirActEthDei7 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth7

       Possibilities:
               unchanged   (255)
               clear   (0)
               set   (1)"
   ::= {er1646v2Lan3FGVlanEntry 150231808}

er1646v2Lan3FGVlanBandwidthActEirActEthCos8 OBJECT-TYPE
   SYNTAX      INTEGER
               {
               unchanged (256)
               }
   MAX-ACCESS  read-write
   STATUS      current
   DESCRIPTION
      "Path: ethernet3.editConf.vlan.bandwidth.action.eirAction.ethernet.cosDepth8

       Possibilities:
               unchanged   (256)"
   ::= {er1646v2Lan3FGVlanEntry 150226944}

er1646v2Lan3FGVlanBandwidthActEirActEthDei8 OBJECT-TYPE
   SYNTAX      INTEGER
               {
               unchanged (255),
               clear (0),
               set (1)
               }
   MAX-ACCESS  read-write
   STATUS      current
   DESCRIPTION
      "Path: ethernet3.editConf.vlan.bandwidth.action.eirAction.ethernet.deiDepth8

       Possibilities:
               unchanged   (255)
               clear   (0)
               set   (1)"
   ::= {er1646v2Lan3FGVlanEntry 150232064}

er1646v2Lan3FGVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 150227200}

er1646v2Lan3FGVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 150227456}

er1646v2Lan3FGVlanBandwidthActEirActEthDrpLev OBJECT-TYPE
   SYNTAX      INTEGER
               {
               unchanged (0)
               }
   MAX-ACCESS  read-write
   STATUS      current
   DESCRIPTION
      "Path: ethernet3.editConf.vlan.bandwidth.action.eirAction.ethernet.dropLevel

       Possibilities:
               unchanged   (0)"
   ::= {er1646v2Lan3FGVlanEntry 150227712}

er1646v2Lan3FGVlanBandwidthActEirActEthDeFlag OBJECT-TYPE
   SYNTAX      INTEGER
               {
               unchanged (255),
               clear (0),
               set (1)
               }
   MAX-ACCESS  read-write
   STATUS      current
   DESCRIPTION
      "Path: ethernet3.editConf.vlan.bandwidth.action.eirAction.ethernet.deFlag

       Possibilities:
               unchanged   (255)
               clear   (0)
               set   (1)"
   ::= {er1646v2Lan3FGVlanEntry 150228480}

er1646v2Lan3FGVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 150251776}

er1646v2Lan3FGVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 150252032}

er1646v2Lan3FGVlanBandwidthActEirActIpDrpLev OBJECT-TYPE
   SYNTAX      INTEGER
               {
               unchanged (0)
               }
   MAX-ACCESS  read-write
   STATUS      current
   DESCRIPTION
      "Path: ethernet3.editConf.vlan.bandwidth.action.eirAction.ip.dropLevel

       Possibilities:
               unchanged   (0)"
   ::= {er1646v2Lan3FGVlanEntry 150252288}

er1646v2Lan3FGVlanBandwidthActEirActIpDeFlag OBJECT-TYPE
   SYNTAX      INTEGER
               {
               unchanged (255),
               clear (0),
               set (1)
               }
   MAX-ACCESS  read-write
   STATUS      current
   DESCRIPTION
      "Path: ethernet3.editConf.vlan.bandwidth.action.eirAction.ip.deFlag

       Possibilities:
               unchanged   (255)
               clear   (0)
               set   (1)"
   ::= {er1646v2Lan3FGVlanEntry 150253056}

er1646v2Lan3FGVlanBandwidthActViolActNone OBJECT-TYPE
   SYNTAX      OCTET STRING
   MAX-ACCESS  read-write
   STATUS      current
   DESCRIPTION
      "Path: ethernet3.editConf.vlan.bandwidth.action.violateAction.none"
   ::= {er1646v2Lan3FGVlanEntry 150347776}

er1646v2Lan3FGVlanBandwidthActViolActDrop OBJECT-TYPE
   SYNTAX      OCTET STRING
   MAX-ACCESS  read-write
   STATUS      current
   DESCRIPTION
      "Path: ethernet3.editConf.vlan.bandwidth.action.violateAction.drop"
   ::= {er1646v2Lan3FGVlanEntry 150364160}

er1646v2Lan3FGVlanBandwidthActViolActEthCos1 OBJECT-TYPE
   SYNTAX      INTEGER
               {
               unchanged (256)
               }
   MAX-ACCESS  read-write
   STATUS      current
   DESCRIPTION
      "Path: ethernet3.editConf.vlan.bandwidth.action.violateAction.ethernet.cosDepth1

       Possibilities:
               unchanged   (256)"
   ::= {er1646v2Lan3FGVlanEntry 150356224}

er1646v2Lan3FGVlanBandwidthActViolActEthDei1 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth1

       Possibilities:
               unchanged   (255)
               clear   (0)
               set   (1)"
   ::= {er1646v2Lan3FGVlanEntry 150361344}

er1646v2Lan3FGVlanBandwidthActViolActEthCos2 OBJECT-TYPE
   SYNTAX      INTEGER
               {
               unchanged (256)
               }
   MAX-ACCESS  read-write
   STATUS      current
   DESCRIPTION
      "Path: ethernet3.editConf.vlan.bandwidth.action.violateAction.ethernet.cosDepth2

       Possibilities:
               unchanged   (256)"
   ::= {er1646v2Lan3FGVlanEntry 150356480}

er1646v2Lan3FGVlanBandwidthActViolActEthDei2 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth2

       Possibilities:
               unchanged   (255)
               clear   (0)
               set   (1)"
   ::= {er1646v2Lan3FGVlanEntry 150361600}

er1646v2Lan3FGVlanBandwidthActViolActEthCos3 OBJECT-TYPE
   SYNTAX      INTEGER
               {
               unchanged (256)
               }
   MAX-ACCESS  read-write
   STATUS      current
   DESCRIPTION
      "Path: ethernet3.editConf.vlan.bandwidth.action.violateAction.ethernet.cosDepth3

       Possibilities:
               unchanged   (256)"
   ::= {er1646v2Lan3FGVlanEntry 150356736}

er1646v2Lan3FGVlanBandwidthActViolActEthDei3 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth3

       Possibilities:
               unchanged   (255)
               clear   (0)
               set   (1)"
   ::= {er1646v2Lan3FGVlanEntry 150361856}

er1646v2Lan3FGVlanBandwidthActViolActEthCos4 OBJECT-TYPE
   SYNTAX      INTEGER
               {
               unchanged (256)
               }
   MAX-ACCESS  read-write
   STATUS      current
   DESCRIPTION
      "Path: ethernet3.editConf.vlan.bandwidth.action.violateAction.ethernet.cosDepth4

       Possibilities:
               unchanged   (256)"
   ::= {er1646v2Lan3FGVlanEntry 150356992}

er1646v2Lan3FGVlanBandwidthActViolActEthDei4 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth4

       Possibilities:
               unchanged   (255)
               clear   (0)
               set   (1)"
   ::= {er1646v2Lan3FGVlanEntry 150362112}

er1646v2Lan3FGVlanBandwidthActViolActEthCos5 OBJECT-TYPE
   SYNTAX      INTEGER
               {
               unchanged (256)
               }
   MAX-ACCESS  read-write
   STATUS      current
   DESCRIPTION
      "Path: ethernet3.editConf.vlan.bandwidth.action.violateAction.ethernet.cosDepth5

       Possibilities:
               unchanged   (256)"
   ::= {er1646v2Lan3FGVlanEntry 150357248}

er1646v2Lan3FGVlanBandwidthActViolActEthDei5 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth5

       Possibilities:
               unchanged   (255)
               clear   (0)
               set   (1)"
   ::= {er1646v2Lan3FGVlanEntry 150362368}

er1646v2Lan3FGVlanBandwidthActViolActEthCos6 OBJECT-TYPE
   SYNTAX      INTEGER
               {
               unchanged (256)
               }
   MAX-ACCESS  read-write
   STATUS      current
   DESCRIPTION
      "Path: ethernet3.editConf.vlan.bandwidth.action.violateAction.ethernet.cosDepth6

       Possibilities:
               unchanged   (256)"
   ::= {er1646v2Lan3FGVlanEntry 150357504}

er1646v2Lan3FGVlanBandwidthActViolActEthDei6 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth6

       Possibilities:
               unchanged   (255)
               clear   (0)
               set   (1)"
   ::= {er1646v2Lan3FGVlanEntry 150362624}

er1646v2Lan3FGVlanBandwidthActViolActEthCos7 OBJECT-TYPE
   SYNTAX      INTEGER
               {
               unchanged (256)
               }
   MAX-ACCESS  read-write
   STATUS      current
   DESCRIPTION
      "Path: ethernet3.editConf.vlan.bandwidth.action.violateAction.ethernet.cosDepth7

       Possibilities:
               unchanged   (256)"
   ::= {er1646v2Lan3FGVlanEntry 150357760}

er1646v2Lan3FGVlanBandwidthActViolActEthDei7 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth7

       Possibilities:
               unchanged   (255)
               clear   (0)
               set   (1)"
   ::= {er1646v2Lan3FGVlanEntry 150362880}

er1646v2Lan3FGVlanBandwidthActViolActEthCos8 OBJECT-TYPE
   SYNTAX      INTEGER
               {
               unchanged (256)
               }
   MAX-ACCESS  read-write
   STATUS      current
   DESCRIPTION
      "Path: ethernet3.editConf.vlan.bandwidth.action.violateAction.ethernet.cosDepth8

       Possibilities:
               unchanged   (256)"
   ::= {er1646v2Lan3FGVlanEntry 150358016}

er1646v2Lan3FGVlanBandwidthActViolActEthDei8 OBJECT-TYPE
   SYNTAX      INTEGER
               {
               unchanged (255),
               clear (0),
               set (1)
               }
   MAX-ACCESS  read-write
   STATUS      current
   DESCRIPTION
      "Path: ethernet3.editConf.vlan.bandwidth.action.violateAction.ethernet.deiDepth8

       Possibilities:
               unchanged   (255)
               clear   (0)
               set   (1)"
   ::= {er1646v2Lan3FGVlanEntry 150363136}

er1646v2Lan3FGVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 150358272}

er1646v2Lan3FGVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 150358528}

er1646v2Lan3FGVlanBandwidthActViolActEthDrpLev OBJECT-TYPE
   SYNTAX      INTEGER
               {
               unchanged (0)
               }
   MAX-ACCESS  read-write
   STATUS      current
   DESCRIPTION
      "Path: ethernet3.editConf.vlan.bandwidth.action.violateAction.ethernet.dropLevel

       Possibilities:
               unchanged   (0)"
   ::= {er1646v2Lan3FGVlanEntry 150358784}

er1646v2Lan3FGVlanBandwidthActViolActEthDeFlag OBJECT-TYPE
   SYNTAX      INTEGER
               {
               unchanged (255),
               clear (0),
               set (1)
               }
   MAX-ACCESS  read-write
   STATUS      current
   DESCRIPTION
      "Path: ethernet3.editConf.vlan.bandwidth.action.violateAction.ethernet.deFlag

       Possibilities:
               unchanged   (255)
               clear   (0)
               set   (1)"
   ::= {er1646v2Lan3FGVlanEntry 150359552}

er1646v2Lan3FGVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 150382848}

er1646v2Lan3FGVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 150383104}

er1646v2Lan3FGVlanBandwidthActViolActIpDrpLev OBJECT-TYPE
   SYNTAX      INTEGER
               {
               unchanged (0)
               }
   MAX-ACCESS  read-write
   STATUS      current
   DESCRIPTION
      "Path: ethernet3.editConf.vlan.bandwidth.action.violateAction.ip.dropLevel

       Possibilities:
               unchanged   (0)"
   ::= {er1646v2Lan3FGVlanEntry 150383360}

er1646v2Lan3FGVlanBandwidthActViolActIpDeFlag OBJECT-TYPE
   SYNTAX      INTEGER
               {
               unchanged (255),
               clear (0),
               set (1)
               }
   MAX-ACCESS  read-write
   STATUS      current
   DESCRIPTION
      "Path: ethernet3.editConf.vlan.bandwidth.action.violateAction.ip.deFlag

       Possibilities:
               unchanged   (255)
               clear   (0)
               set   (1)"
   ::= {er1646v2Lan3FGVlanEntry 150384128}

er1646v2Lan3FGVlanInbBwMode OBJECT-TYPE
   SYNTAX      INTEGER
               {
               reshaping (1),
               policing (2)
               }
   MAX-ACCESS  read-write
   STATUS      current
   DESCRIPTION
      "Path: ethernet3.editConf.vlan.inboundBandwidth.mode

       Possibilities:
               reshaping   (1)
               policing   (2)"
   ::= {er1646v2Lan3FGVlanEntry 132120576}

er1646v2Lan3FGVlanInbBwCir OBJECT-TYPE
   SYNTAX      Integer32
   MAX-ACCESS  read-write
   STATUS      current
   DESCRIPTION
      "Path: ethernet3.editConf.vlan.inboundBandwidth.cir"
   ::= {er1646v2Lan3FGVlanEntry 118489088}

er1646v2Lan3FGVlanInbBwEir OBJECT-TYPE
   SYNTAX      Integer32
   MAX-ACCESS  read-write
   STATUS      current
   DESCRIPTION
      "Path: ethernet3.editConf.vlan.inboundBandwidth.eir"
   ::= {er1646v2Lan3FGVlanEntry 124780544}

er1646v2Lan3FGVlanInbBwUnit OBJECT-TYPE
   SYNTAX      INTEGER
               {
               bitssec (1),
               percent (2)
               }
   MAX-ACCESS  read-write
   STATUS      current
   DESCRIPTION
      "Path: ethernet3.editConf.vlan.inboundBandwidth.unit

       Possibilities:
               bits/sec   (1)
               percent   (2)"
   ::= {er1646v2Lan3FGVlanEntry 122683392}

er1646v2Lan3FGVlanInbBwTc OBJECT-TYPE
   SYNTAX      INTEGER
               {
               auto (0)
               }
   MAX-ACCESS  read-write
   STATUS      current
   DESCRIPTION
      "Path: ethernet3.editConf.vlan.inboundBandwidth.tc

       Possibilities:
               auto   (0)"
   ::= {er1646v2Lan3FGVlanEntry 123731968}

er1646v2Lan3FGVlanInbBwTcFactor OBJECT-TYPE
   SYNTAX      INTEGER
               {
               ms (10),
               s100us (1)
               }
   MAX-ACCESS  read-write
   STATUS      current
   DESCRIPTION
      "Path: ethernet3.editConf.vlan.inboundBandwidth.tcFactor

       Possibilities:
               ms   (10)
               *100us   (1)"
   ::= {er1646v2Lan3FGVlanEntry 125829120}

er1646v2Lan3FGVlanInbBwCorrType OBJECT-TYPE
   SYNTAX      INTEGER
               {
               noCorrection (0),
               predefined (1),
               manual (2)
               }
   MAX-ACCESS  read-write
   STATUS      current
   DESCRIPTION
      "Path: ethernet3.editConf.vlan.inboundBandwidth.correction.type

       Possibilities:
               noCorrection   (0)
               predefined   (1)
               manual   (2)"
   ::= {er1646v2Lan3FGVlanEntry 119668736}

er1646v2Lan3FGVlanInbBwCorrPredefEncapsFrameRelay OBJECT-TYPE
   SYNTAX      DisplayString
   MAX-ACCESS  read-write
   STATUS      current
   DESCRIPTION
      "Path: ethernet3.editConf.vlan.inboundBandwidth.correction.predefined.encapsulation.frameRelay"
   ::= {er1646v2Lan3FGVlanEntry 119817216}

er1646v2Lan3FGVlanInbBwCorrPredefEncapsPpp OBJECT-TYPE
   SYNTAX      DisplayString
   MAX-ACCESS  read-write
   STATUS      current
   DESCRIPTION
      "Path: ethernet3.editConf.vlan.inboundBandwidth.correction.predefined.encapsulation.ppp"
   ::= {er1646v2Lan3FGVlanEntry 119818240}

er1646v2Lan3FGVlanInbBwCorrPredefEncapsAtmHl OBJECT-TYPE
   SYNTAX      INTEGER
               {
               rfc2684 (0),
               ppp (1),
               pppOverEthernet (2)
               }
   MAX-ACCESS  read-write
   STATUS      current
   DESCRIPTION
      "Path: ethernet3.editConf.vlan.inboundBandwidth.correction.predefined.encapsulation.atm.higherLayer

       Possibilities:
               rfc2684   (0)
               ppp   (1)
               pppOverEthernet   (2)"
   ::= {er1646v2Lan3FGVlanEntry 119819392}

er1646v2Lan3FGVlanInbBwCorrPredefEncapsAtmMp OBJECT-TYPE
   SYNTAX      INTEGER
               {
               llcEncapsulation (0),
               vcMultiplexing (1)
               }
   MAX-ACCESS  read-write
   STATUS      current
   DESCRIPTION
      "Path: ethernet3.editConf.vlan.inboundBandwidth.correction.predefined.encapsulation.atm.multiProtocol

       Possibilities:
               llcEncapsulation   (0)
               vcMultiplexing   (1)"
   ::= {er1646v2Lan3FGVlanEntry 119819520}

er1646v2Lan3FGVlanInbBwCorrPredefEncapsHdlc OBJECT-TYPE
   SYNTAX      DisplayString
   MAX-ACCESS  read-write
   STATUS      current
   DESCRIPTION
      "Path: ethernet3.editConf.vlan.inboundBandwidth.correction.predefined.encapsulation.hdlc"
   ::= {er1646v2Lan3FGVlanEntry 119820288}

er1646v2Lan3FGVlanInbBwCorrPredefEncapsEfmFs OBJECT-TYPE
   SYNTAX      Integer32
   MAX-ACCESS  read-write
   STATUS      current
   DESCRIPTION
      "Path: ethernet3.editConf.vlan.inboundBandwidth.correction.predefined.encapsulation.efm.fragmentSize"
   ::= {er1646v2Lan3FGVlanEntry 119821440}

er1646v2Lan3FGVlanInbBwCorrPredefEncapsEfmIb OBJECT-TYPE
   SYNTAX      Integer32
   MAX-ACCESS  read-write
   STATUS      current
   DESCRIPTION
      "Path: ethernet3.editConf.vlan.inboundBandwidth.correction.predefined.encapsulation.efm.idleBytes"
   ::= {er1646v2Lan3FGVlanEntry 119821568}

er1646v2Lan3FGVlanInbBwCorrPredefMode OBJECT-TYPE
   SYNTAX      INTEGER
               {
               routing (0),
               bridging (1)
               }
   MAX-ACCESS  read-write
   STATUS      current
   DESCRIPTION
      "Path: ethernet3.editConf.vlan.inboundBandwidth.correction.predefined.mode

       Possibilities:
               routing   (0)
               bridging   (1)"
   ::= {er1646v2Lan3FGVlanEntry 119832576}

er1646v2Lan3FGVlanInbBwCorrManualOverhead OBJECT-TYPE
   SYNTAX      Integer32
   MAX-ACCESS  read-write
   STATUS      current
   DESCRIPTION
      "Path: ethernet3.editConf.vlan.inboundBandwidth.correction.manual.overhead"
   ::= {er1646v2Lan3FGVlanEntry 119931392}

er1646v2Lan3FGVlanInbBwCorrManualFrameData OBJECT-TYPE
   SYNTAX      Counter32
   MAX-ACCESS  read-write
   STATUS      current
   DESCRIPTION
      "Path: ethernet3.editConf.vlan.inboundBandwidth.correction.manual.frameData

       32 bit unsigned wrappable counter."
   ::= {er1646v2Lan3FGVlanEntry 119931904}

er1646v2Lan3FGVlanInbBwCorrManualFrameHeader OBJECT-TYPE
   SYNTAX      Counter32
   MAX-ACCESS  read-write
   STATUS      current
   DESCRIPTION
      "Path: ethernet3.editConf.vlan.inboundBandwidth.correction.manual.frameHeader

       32 bit unsigned wrappable counter."
   ::= {er1646v2Lan3FGVlanEntry 119932416}

er1646v2Lan3FGVlanInbBwMaxFifoQLen OBJECT-TYPE
   SYNTAX      Integer32
   MAX-ACCESS  read-write
   STATUS      current
   DESCRIPTION
      "Path: ethernet3.editConf.vlan.inboundBandwidth.maxFifoQLen"
   ::= {er1646v2Lan3FGVlanEntry 120586240}

er1646v2Lan3FGVlanInbBwPriorityPolicy OBJECT-TYPE
   SYNTAX      DisplayString
   MAX-ACCESS  read-write
   STATUS      current
   DESCRIPTION
      "Path: ethernet3.editConf.vlan.inboundBandwidth.priorityPolicy"
   ::= {er1646v2Lan3FGVlanEntry 121634816}

er1646v2Lan3FGVlanInbBwDeFlagCir OBJECT-TYPE
   SYNTAX      INTEGER
               {
               allowed (1),
               notAllowed (2)
               }
   MAX-ACCESS  read-write
   STATUS      current
   DESCRIPTION
      "Path: ethernet3.editConf.vlan.inboundBandwidth.deFlag.cir

       Possibilities:
               allowed   (1)
               notAllowed   (2)"
   ::= {er1646v2Lan3FGVlanEntry 131076096}

er1646v2Lan3FGVlanInbBwDeFlagEir OBJECT-TYPE
   SYNTAX      INTEGER
               {
               allowed (1),
               notAllowed (2)
               }
   MAX-ACCESS  read-write
   STATUS      current
   DESCRIPTION
      "Path: ethernet3.editConf.vlan.inboundBandwidth.deFlag.eir

       Possibilities:
               allowed   (1)
               notAllowed   (2)"
   ::= {er1646v2Lan3FGVlanEntry 131080192}

er1646v2Lan3FGVlanInbBwDeFlagViolate OBJECT-TYPE
   SYNTAX      INTEGER
               {
               allowed (1),
               notAllowed (2)
               }
   MAX-ACCESS  read-write
   STATUS      current
   DESCRIPTION
      "Path: ethernet3.editConf.vlan.inboundBandwidth.deFlag.violate

       Possibilities:
               allowed   (1)
               notAllowed   (2)"
   ::= {er1646v2Lan3FGVlanEntry 131084288}

er1646v2Lan3FGVlanInbBwActCirActNone OBJECT-TYPE
   SYNTAX      OCTET STRING
   MAX-ACCESS  read-write
   STATUS      current
   DESCRIPTION
      "Path: ethernet3.editConf.vlan.inboundBandwidth.action.cirAction.none"
   ::= {er1646v2Lan3FGVlanEntry 133308416}

er1646v2Lan3FGVlanInbBwActCirActEthCos1 OBJECT-TYPE
   SYNTAX      INTEGER
               {
               unchanged (256)
               }
   MAX-ACCESS  read-write
   STATUS      current
   DESCRIPTION
      "Path: ethernet3.editConf.vlan.inboundBandwidth.action.cirAction.ethernet.cosDepth1

       Possibilities:
               unchanged   (256)"
   ::= {er1646v2Lan3FGVlanEntry 133316864}

er1646v2Lan3FGVlanInbBwActCirActEthDei1 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth1

       Possibilities:
               unchanged   (255)
               clear   (0)
               set   (1)"
   ::= {er1646v2Lan3FGVlanEntry 133321984}

er1646v2Lan3FGVlanInbBwActCirActEthCos2 OBJECT-TYPE
   SYNTAX      INTEGER
               {
               unchanged (256)
               }
   MAX-ACCESS  read-write
   STATUS      current
   DESCRIPTION
      "Path: ethernet3.editConf.vlan.inboundBandwidth.action.cirAction.ethernet.cosDepth2

       Possibilities:
               unchanged   (256)"
   ::= {er1646v2Lan3FGVlanEntry 133317120}

er1646v2Lan3FGVlanInbBwActCirActEthDei2 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth2

       Possibilities:
               unchanged   (255)
               clear   (0)
               set   (1)"
   ::= {er1646v2Lan3FGVlanEntry 133322240}

er1646v2Lan3FGVlanInbBwActCirActEthCos3 OBJECT-TYPE
   SYNTAX      INTEGER
               {
               unchanged (256)
               }
   MAX-ACCESS  read-write
   STATUS      current
   DESCRIPTION
      "Path: ethernet3.editConf.vlan.inboundBandwidth.action.cirAction.ethernet.cosDepth3

       Possibilities:
               unchanged   (256)"
   ::= {er1646v2Lan3FGVlanEntry 133317376}

er1646v2Lan3FGVlanInbBwActCirActEthDei3 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth3

       Possibilities:
               unchanged   (255)
               clear   (0)
               set   (1)"
   ::= {er1646v2Lan3FGVlanEntry 133322496}

er1646v2Lan3FGVlanInbBwActCirActEthCos4 OBJECT-TYPE
   SYNTAX      INTEGER
               {
               unchanged (256)
               }
   MAX-ACCESS  read-write
   STATUS      current
   DESCRIPTION
      "Path: ethernet3.editConf.vlan.inboundBandwidth.action.cirAction.ethernet.cosDepth4

       Possibilities:
               unchanged   (256)"
   ::= {er1646v2Lan3FGVlanEntry 133317632}

er1646v2Lan3FGVlanInbBwActCirActEthDei4 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth4

       Possibilities:
               unchanged   (255)
               clear   (0)
               set   (1)"
   ::= {er1646v2Lan3FGVlanEntry 133322752}

er1646v2Lan3FGVlanInbBwActCirActEthCos5 OBJECT-TYPE
   SYNTAX      INTEGER
               {
               unchanged (256)
               }
   MAX-ACCESS  read-write
   STATUS      current
   DESCRIPTION
      "Path: ethernet3.editConf.vlan.inboundBandwidth.action.cirAction.ethernet.cosDepth5

       Possibilities:
               unchanged   (256)"
   ::= {er1646v2Lan3FGVlanEntry 133317888}

er1646v2Lan3FGVlanInbBwActCirActEthDei5 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth5

       Possibilities:
               unchanged   (255)
               clear   (0)
               set   (1)"
   ::= {er1646v2Lan3FGVlanEntry 133323008}

er1646v2Lan3FGVlanInbBwActCirActEthCos6 OBJECT-TYPE
   SYNTAX      INTEGER
               {
               unchanged (256)
               }
   MAX-ACCESS  read-write
   STATUS      current
   DESCRIPTION
      "Path: ethernet3.editConf.vlan.inboundBandwidth.action.cirAction.ethernet.cosDepth6

       Possibilities:
               unchanged   (256)"
   ::= {er1646v2Lan3FGVlanEntry 133318144}

er1646v2Lan3FGVlanInbBwActCirActEthDei6 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth6

       Possibilities:
               unchanged   (255)
               clear   (0)
               set   (1)"
   ::= {er1646v2Lan3FGVlanEntry 133323264}

er1646v2Lan3FGVlanInbBwActCirActEthCos7 OBJECT-TYPE
   SYNTAX      INTEGER
               {
               unchanged (256)
               }
   MAX-ACCESS  read-write
   STATUS      current
   DESCRIPTION
      "Path: ethernet3.editConf.vlan.inboundBandwidth.action.cirAction.ethernet.cosDepth7

       Possibilities:
               unchanged   (256)"
   ::= {er1646v2Lan3FGVlanEntry 133318400}

er1646v2Lan3FGVlanInbBwActCirActEthDei7 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth7

       Possibilities:
               unchanged   (255)
               clear   (0)
               set   (1)"
   ::= {er1646v2Lan3FGVlanEntry 133323520}

er1646v2Lan3FGVlanInbBwActCirActEthCos8 OBJECT-TYPE
   SYNTAX      INTEGER
               {
               unchanged (256)
               }
   MAX-ACCESS  read-write
   STATUS      current
   DESCRIPTION
      "Path: ethernet3.editConf.vlan.inboundBandwidth.action.cirAction.ethernet.cosDepth8

       Possibilities:
               unchanged   (256)"
   ::= {er1646v2Lan3FGVlanEntry 133318656}

er1646v2Lan3FGVlanInbBwActCirActEthDei8 OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deiDepth8

       Possibilities:
               unchanged   (255)
               clear   (0)
               set   (1)"
   ::= {er1646v2Lan3FGVlanEntry 133323776}

er1646v2Lan3FGVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 133318912}

er1646v2Lan3FGVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 133319168}

er1646v2Lan3FGVlanInbBwActCirActEthDrpLev OBJECT-TYPE
   SYNTAX      INTEGER
               {
               unchanged (0)
               }
   MAX-ACCESS  read-write
   STATUS      current
   DESCRIPTION
      "Path: ethernet3.editConf.vlan.inboundBandwidth.action.cirAction.ethernet.dropLevel

       Possibilities:
               unchanged   (0)"
   ::= {er1646v2Lan3FGVlanEntry 133319424}

er1646v2Lan3FGVlanInbBwActCirActEthDeFlag OBJECT-TYPE
   SYNTAX      INTEGER
               {
               unchanged (255),
               clear (0),
               set (1)
               }
   MAX-ACCESS  read-write
   STATUS      current
   DESCRIPTION
      "Path: ethernet3.editConf.vlan.inboundBandwidth.action.cirAction.ethernet.deFlag

       Possibilities:
               unchanged   (255)
               clear   (0)
               set   (1)"
   ::= {er1646v2Lan3FGVlanEntry 133320192}

er1646v2Lan3FGVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 133343488}

er1646v2Lan3FGVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 133343744}

er1646v2Lan3FGVlanInbBwActCirActIpDrpLev OBJECT-TYPE
   SYNTAX      INTEGER
               {
               unchanged (0)
               }
   MAX-ACCESS  read-write
   STATUS      current
   DESCRIPTION
      "Path: ethernet3.editConf.vlan.inboundBandwidth.action.cirAction.ip.dropLevel

       Possibilities:
               unchanged   (0)"
   ::= {er1646v2Lan3FGVlanEntry 133344000}

er1646v2Lan3FGVlanInbBwActCirActIpDeFlag OBJECT-TYPE
   SYNTAX      INTEGER
               {
               unchanged (255),
               clear (0),
               set (1)
               }
   MAX-ACCESS  read-write
   STATUS      current
   DESCRIPTION
      "Path: ethernet3.editConf.vlan.inboundBandwidth.action.cirAction.ip.deFlag

       Possibilities:
               unchanged   (255)
               clear   (0)
               set   (1)"
   ::= {er1646v2Lan3FGVlanEntry 133344768}

er1646v2Lan3FGVlanInbBwActEirActNone OBJECT-TYPE
   SYNTAX      OCTET STRING
   MAX-ACCESS  read-write
   STATUS      current
   DESCRIPTION
      "Path: ethernet3.editConf.vlan.inboundBandwidth.action.eirAction.none"
   ::= {er1646v2Lan3FGVlanEntry 133439488}

er1646v2Lan3FGVlanInbBwActEirActEthCos1 OBJECT-TYPE
   SYNTAX      INTEGER
               {
               unchanged (256)
               }
   MAX-ACCESS  read-write
   STATUS      current
   DESCRIPTION
      "Path: ethernet3.editConf.vlan.inboundBandwidth.action.eirAction.ethernet.cosDepth1

       Possibilities:
               unchanged   (256)"
   ::= {er1646v2Lan3FGVlanEntry 133447936}

er1646v2Lan3FGVlanInbBwActEirActEthDei1 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth1

       Possibilities:
               unchanged   (255)
               clear   (0)
               set   (1)"
   ::= {er1646v2Lan3FGVlanEntry 133453056}

er1646v2Lan3FGVlanInbBwActEirActEthCos2 OBJECT-TYPE
   SYNTAX      INTEGER
               {
               unchanged (256)
               }
   MAX-ACCESS  read-write
   STATUS      current
   DESCRIPTION
      "Path: ethernet3.editConf.vlan.inboundBandwidth.action.eirAction.ethernet.cosDepth2

       Possibilities:
               unchanged   (256)"
   ::= {er1646v2Lan3FGVlanEntry 133448192}

er1646v2Lan3FGVlanInbBwActEirActEthDei2 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth2

       Possibilities:
               unchanged   (255)
               clear   (0)
               set   (1)"
   ::= {er1646v2Lan3FGVlanEntry 133453312}

er1646v2Lan3FGVlanInbBwActEirActEthCos3 OBJECT-TYPE
   SYNTAX      INTEGER
               {
               unchanged (256)
               }
   MAX-ACCESS  read-write
   STATUS      current
   DESCRIPTION
      "Path: ethernet3.editConf.vlan.inboundBandwidth.action.eirAction.ethernet.cosDepth3

       Possibilities:
               unchanged   (256)"
   ::= {er1646v2Lan3FGVlanEntry 133448448}

er1646v2Lan3FGVlanInbBwActEirActEthDei3 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth3

       Possibilities:
               unchanged   (255)
               clear   (0)
               set   (1)"
   ::= {er1646v2Lan3FGVlanEntry 133453568}

er1646v2Lan3FGVlanInbBwActEirActEthCos4 OBJECT-TYPE
   SYNTAX      INTEGER
               {
               unchanged (256)
               }
   MAX-ACCESS  read-write
   STATUS      current
   DESCRIPTION
      "Path: ethernet3.editConf.vlan.inboundBandwidth.action.eirAction.ethernet.cosDepth4

       Possibilities:
               unchanged   (256)"
   ::= {er1646v2Lan3FGVlanEntry 133448704}

er1646v2Lan3FGVlanInbBwActEirActEthDei4 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth4

       Possibilities:
               unchanged   (255)
               clear   (0)
               set   (1)"
   ::= {er1646v2Lan3FGVlanEntry 133453824}

er1646v2Lan3FGVlanInbBwActEirActEthCos5 OBJECT-TYPE
   SYNTAX      INTEGER
               {
               unchanged (256)
               }
   MAX-ACCESS  read-write
   STATUS      current
   DESCRIPTION
      "Path: ethernet3.editConf.vlan.inboundBandwidth.action.eirAction.ethernet.cosDepth5

       Possibilities:
               unchanged   (256)"
   ::= {er1646v2Lan3FGVlanEntry 133448960}

er1646v2Lan3FGVlanInbBwActEirActEthDei5 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth5

       Possibilities:
               unchanged   (255)
               clear   (0)
               set   (1)"
   ::= {er1646v2Lan3FGVlanEntry 133454080}

er1646v2Lan3FGVlanInbBwActEirActEthCos6 OBJECT-TYPE
   SYNTAX      INTEGER
               {
               unchanged (256)
               }
   MAX-ACCESS  read-write
   STATUS      current
   DESCRIPTION
      "Path: ethernet3.editConf.vlan.inboundBandwidth.action.eirAction.ethernet.cosDepth6

       Possibilities:
               unchanged   (256)"
   ::= {er1646v2Lan3FGVlanEntry 133449216}

er1646v2Lan3FGVlanInbBwActEirActEthDei6 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth6

       Possibilities:
               unchanged   (255)
               clear   (0)
               set   (1)"
   ::= {er1646v2Lan3FGVlanEntry 133454336}

er1646v2Lan3FGVlanInbBwActEirActEthCos7 OBJECT-TYPE
   SYNTAX      INTEGER
               {
               unchanged (256)
               }
   MAX-ACCESS  read-write
   STATUS      current
   DESCRIPTION
      "Path: ethernet3.editConf.vlan.inboundBandwidth.action.eirAction.ethernet.cosDepth7

       Possibilities:
               unchanged   (256)"
   ::= {er1646v2Lan3FGVlanEntry 133449472}

er1646v2Lan3FGVlanInbBwActEirActEthDei7 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth7

       Possibilities:
               unchanged   (255)
               clear   (0)
               set   (1)"
   ::= {er1646v2Lan3FGVlanEntry 133454592}

er1646v2Lan3FGVlanInbBwActEirActEthCos8 OBJECT-TYPE
   SYNTAX      INTEGER
               {
               unchanged (256)
               }
   MAX-ACCESS  read-write
   STATUS      current
   DESCRIPTION
      "Path: ethernet3.editConf.vlan.inboundBandwidth.action.eirAction.ethernet.cosDepth8

       Possibilities:
               unchanged   (256)"
   ::= {er1646v2Lan3FGVlanEntry 133449728}

er1646v2Lan3FGVlanInbBwActEirActEthDei8 OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deiDepth8

       Possibilities:
               unchanged   (255)
               clear   (0)
               set   (1)"
   ::= {er1646v2Lan3FGVlanEntry 133454848}

er1646v2Lan3FGVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 133449984}

er1646v2Lan3FGVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 133450240}

er1646v2Lan3FGVlanInbBwActEirActEthDrpLev OBJECT-TYPE
   SYNTAX      INTEGER
               {
               unchanged (0)
               }
   MAX-ACCESS  read-write
   STATUS      current
   DESCRIPTION
      "Path: ethernet3.editConf.vlan.inboundBandwidth.action.eirAction.ethernet.dropLevel

       Possibilities:
               unchanged   (0)"
   ::= {er1646v2Lan3FGVlanEntry 133450496}

er1646v2Lan3FGVlanInbBwActEirActEthDeFlag OBJECT-TYPE
   SYNTAX      INTEGER
               {
               unchanged (255),
               clear (0),
               set (1)
               }
   MAX-ACCESS  read-write
   STATUS      current
   DESCRIPTION
      "Path: ethernet3.editConf.vlan.inboundBandwidth.action.eirAction.ethernet.deFlag

       Possibilities:
               unchanged   (255)
               clear   (0)
               set   (1)"
   ::= {er1646v2Lan3FGVlanEntry 133451264}

er1646v2Lan3FGVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 133474560}

er1646v2Lan3FGVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 133474816}

er1646v2Lan3FGVlanInbBwActEirActIpDrpLev OBJECT-TYPE
   SYNTAX      INTEGER
               {
               unchanged (0)
               }
   MAX-ACCESS  read-write
   STATUS      current
   DESCRIPTION
      "Path: ethernet3.editConf.vlan.inboundBandwidth.action.eirAction.ip.dropLevel

       Possibilities:
               unchanged   (0)"
   ::= {er1646v2Lan3FGVlanEntry 133475072}

er1646v2Lan3FGVlanInbBwActEirActIpDeFlag OBJECT-TYPE
   SYNTAX      INTEGER
               {
               unchanged (255),
               clear (0),
               set (1)
               }
   MAX-ACCESS  read-write
   STATUS      current
   DESCRIPTION
      "Path: ethernet3.editConf.vlan.inboundBandwidth.action.eirAction.ip.deFlag

       Possibilities:
               unchanged   (255)
               clear   (0)
               set   (1)"
   ::= {er1646v2Lan3FGVlanEntry 133475840}

er1646v2Lan3FGVlanInbBwActViolActNone OBJECT-TYPE
   SYNTAX      OCTET STRING
   MAX-ACCESS  read-write
   STATUS      current
   DESCRIPTION
      "Path: ethernet3.editConf.vlan.inboundBandwidth.action.violateAction.none"
   ::= {er1646v2Lan3FGVlanEntry 133570560}

er1646v2Lan3FGVlanInbBwActViolActDrop OBJECT-TYPE
   SYNTAX      OCTET STRING
   MAX-ACCESS  read-write
   STATUS      current
   DESCRIPTION
      "Path: ethernet3.editConf.vlan.inboundBandwidth.action.violateAction.drop"
   ::= {er1646v2Lan3FGVlanEntry 133586944}

er1646v2Lan3FGVlanInbBwActViolActEthCos1 OBJECT-TYPE
   SYNTAX      INTEGER
               {
               unchanged (256)
               }
   MAX-ACCESS  read-write
   STATUS      current
   DESCRIPTION
      "Path: ethernet3.editConf.vlan.inboundBandwidth.action.violateAction.ethernet.cosDepth1

       Possibilities:
               unchanged   (256)"
   ::= {er1646v2Lan3FGVlanEntry 133579008}

er1646v2Lan3FGVlanInbBwActViolActEthDei1 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth1

       Possibilities:
               unchanged   (255)
               clear   (0)
               set   (1)"
   ::= {er1646v2Lan3FGVlanEntry 133584128}

er1646v2Lan3FGVlanInbBwActViolActEthCos2 OBJECT-TYPE
   SYNTAX      INTEGER
               {
               unchanged (256)
               }
   MAX-ACCESS  read-write
   STATUS      current
   DESCRIPTION
      "Path: ethernet3.editConf.vlan.inboundBandwidth.action.violateAction.ethernet.cosDepth2

       Possibilities:
               unchanged   (256)"
   ::= {er1646v2Lan3FGVlanEntry 133579264}

er1646v2Lan3FGVlanInbBwActViolActEthDei2 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth2

       Possibilities:
               unchanged   (255)
               clear   (0)
               set   (1)"
   ::= {er1646v2Lan3FGVlanEntry 133584384}

er1646v2Lan3FGVlanInbBwActViolActEthCos3 OBJECT-TYPE
   SYNTAX      INTEGER
               {
               unchanged (256)
               }
   MAX-ACCESS  read-write
   STATUS      current
   DESCRIPTION
      "Path: ethernet3.editConf.vlan.inboundBandwidth.action.violateAction.ethernet.cosDepth3

       Possibilities:
               unchanged   (256)"
   ::= {er1646v2Lan3FGVlanEntry 133579520}

er1646v2Lan3FGVlanInbBwActViolActEthDei3 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth3

       Possibilities:
               unchanged   (255)
               clear   (0)
               set   (1)"
   ::= {er1646v2Lan3FGVlanEntry 133584640}

er1646v2Lan3FGVlanInbBwActViolActEthCos4 OBJECT-TYPE
   SYNTAX      INTEGER
               {
               unchanged (256)
               }
   MAX-ACCESS  read-write
   STATUS      current
   DESCRIPTION
      "Path: ethernet3.editConf.vlan.inboundBandwidth.action.violateAction.ethernet.cosDepth4

       Possibilities:
               unchanged   (256)"
   ::= {er1646v2Lan3FGVlanEntry 133579776}

er1646v2Lan3FGVlanInbBwActViolActEthDei4 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth4

       Possibilities:
               unchanged   (255)
               clear   (0)
               set   (1)"
   ::= {er1646v2Lan3FGVlanEntry 133584896}

er1646v2Lan3FGVlanInbBwActViolActEthCos5 OBJECT-TYPE
   SYNTAX      INTEGER
               {
               unchanged (256)
               }
   MAX-ACCESS  read-write
   STATUS      current
   DESCRIPTION
      "Path: ethernet3.editConf.vlan.inboundBandwidth.action.violateAction.ethernet.cosDepth5

       Possibilities:
               unchanged   (256)"
   ::= {er1646v2Lan3FGVlanEntry 133580032}

er1646v2Lan3FGVlanInbBwActViolActEthDei5 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth5

       Possibilities:
               unchanged   (255)
               clear   (0)
               set   (1)"
   ::= {er1646v2Lan3FGVlanEntry 133585152}

er1646v2Lan3FGVlanInbBwActViolActEthCos6 OBJECT-TYPE
   SYNTAX      INTEGER
               {
               unchanged (256)
               }
   MAX-ACCESS  read-write
   STATUS      current
   DESCRIPTION
      "Path: ethernet3.editConf.vlan.inboundBandwidth.action.violateAction.ethernet.cosDepth6

       Possibilities:
               unchanged   (256)"
   ::= {er1646v2Lan3FGVlanEntry 133580288}

er1646v2Lan3FGVlanInbBwActViolActEthDei6 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth6

       Possibilities:
               unchanged   (255)
               clear   (0)
               set   (1)"
   ::= {er1646v2Lan3FGVlanEntry 133585408}

er1646v2Lan3FGVlanInbBwActViolActEthCos7 OBJECT-TYPE
   SYNTAX      INTEGER
               {
               unchanged (256)
               }
   MAX-ACCESS  read-write
   STATUS      current
   DESCRIPTION
      "Path: ethernet3.editConf.vlan.inboundBandwidth.action.violateAction.ethernet.cosDepth7

       Possibilities:
               unchanged   (256)"
   ::= {er1646v2Lan3FGVlanEntry 133580544}

er1646v2Lan3FGVlanInbBwActViolActEthDei7 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth7

       Possibilities:
               unchanged   (255)
               clear   (0)
               set   (1)"
   ::= {er1646v2Lan3FGVlanEntry 133585664}

er1646v2Lan3FGVlanInbBwActViolActEthCos8 OBJECT-TYPE
   SYNTAX      INTEGER
               {
               unchanged (256)
               }
   MAX-ACCESS  read-write
   STATUS      current
   DESCRIPTION
      "Path: ethernet3.editConf.vlan.inboundBandwidth.action.violateAction.ethernet.cosDepth8

       Possibilities:
               unchanged   (256)"
   ::= {er1646v2Lan3FGVlanEntry 133580800}

er1646v2Lan3FGVlanInbBwActViolActEthDei8 OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deiDepth8

       Possibilities:
               unchanged   (255)
               clear   (0)
               set   (1)"
   ::= {er1646v2Lan3FGVlanEntry 133585920}

er1646v2Lan3FGVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 133581056}

er1646v2Lan3FGVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 133581312}

er1646v2Lan3FGVlanInbBwActViolActEthDrpLev OBJECT-TYPE
   SYNTAX      INTEGER
               {
               unchanged (0)
               }
   MAX-ACCESS  read-write
   STATUS      current
   DESCRIPTION
      "Path: ethernet3.editConf.vlan.inboundBandwidth.action.violateAction.ethernet.dropLevel

       Possibilities:
               unchanged   (0)"
   ::= {er1646v2Lan3FGVlanEntry 133581568}

er1646v2Lan3FGVlanInbBwActViolActEthDeFlag OBJECT-TYPE
   SYNTAX      INTEGER
               {
               unchanged (255),
               clear (0),
               set (1)
               }
   MAX-ACCESS  read-write
   STATUS      current
   DESCRIPTION
      "Path: ethernet3.editConf.vlan.inboundBandwidth.action.violateAction.ethernet.deFlag

       Possibilities:
               unchanged   (255)
               clear   (0)
               set   (1)"
   ::= {er1646v2Lan3FGVlanEntry 133582336}

er1646v2Lan3FGVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanEntry 133605632}

er1646v2Lan3FGVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanEntry 133605888}

er1646v2Lan3FGVlanInbBwActViolActIpDrpLev OBJECT-TYPE
   SYNTAX      INTEGER
               {
               unchanged (0)
               }
   MAX-ACCESS  read-write
   STATUS      current
   DESCRIPTION
      "Path: ethernet3.editConf.vlan.inboundBandwidth.action.violateAction.ip.dropLevel

       Possibilities:
               unchanged   (0)"
   ::= {er1646v2Lan3FGVlanEntry 133606144}

er1646v2Lan3FGVlanInbBwActViolActIpDeFlag OBJECT-TYPE
   SYNTAX      INTEGER
               {
               unchanged (255),
               clear (0),
               set (1)
               }
   MAX-ACCESS  read-write
   STATUS      current
   DESCRIPTION
      "Path: ethernet3.editConf.vlan.inboundBandwidth.action.violateAction.ip.deFlag

       Possibilities:
               unchanged   (255)
               clear   (0)
               set   (1)"
   ::= {er1646v2Lan3FGVlanEntry 133606912}

er1646v2Lan3FGVlanPppoE OBJECT-TYPE
   SYNTAX      INTEGER
               {
               disabled (0),
               enabled (1)
               }
   MAX-ACCESS  read-write
   STATUS      current
   DESCRIPTION
      "Path: ethernet3.editConf.vlan.pppoE

       Possibilities:
               disabled   (0)
               enabled   (1)"
   ::= {er1646v2Lan3FGVlanEntry 838860800}

er1646v2Lan3FGVlanPppLnkMOperation OBJECT-TYPE
   SYNTAX      INTEGER
               {
               disabled (0),
               enabled (1)
               }
   MAX-ACCESS  read-write
   STATUS      current
   DESCRIPTION
      "Path: ethernet3.editConf.vlan.ppp.linkMonitoring.operation

       Possibilities:
               disabled   (0)
               enabled   (1)"
   ::= {er1646v2Lan3FGVlanEntry 251724032}

er1646v2Lan3FGVlanPppLnkMInterval OBJECT-TYPE
   SYNTAX      TimeTicks
   MAX-ACCESS  read-write
   STATUS      current
   DESCRIPTION
      "Path: ethernet3.editConf.vlan.ppp.linkMonitoring.interval

       Time in centi-second."
   ::= {er1646v2Lan3FGVlanEntry 251724288}

er1646v2Lan3FGVlanPppLnkMRepTimeOut OBJECT-TYPE
   SYNTAX      TimeTicks
   MAX-ACCESS  read-write
   STATUS      current
   DESCRIPTION
      "Path: ethernet3.editConf.vlan.ppp.linkMonitoring.replyTimeOut

       Time in centi-second."
   ::= {er1646v2Lan3FGVlanEntry 251724544}

er1646v2Lan3FGVlanPppLnkMFailsPrmt OBJECT-TYPE
   SYNTAX      Integer32
   MAX-ACCESS  read-write
   STATUS      current
   DESCRIPTION
      "Path: ethernet3.editConf.vlan.ppp.linkMonitoring.failsPermitted"
   ::= {er1646v2Lan3FGVlanEntry 251724800}

er1646v2Lan3FGVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet3.editConf.vlan.ppp.authentication

       Possibilities:
               disabled   (0)
               chap   (1)
               pap   (2)
               chapOrPap   (3)
               msChap   (4)
               msChapV2   (5)"
   ::= {er1646v2Lan3FGVlanEntry 251789312}

er1646v2Lan3FGVlanPppAuthenPeriod OBJECT-TYPE
   SYNTAX      TimeTicks
   MAX-ACCESS  read-write
   STATUS      current
   DESCRIPTION
      "Path: ethernet3.editConf.vlan.ppp.authenPeriod

       Time in centi-second."
   ::= {er1646v2Lan3FGVlanEntry 251854848}

er1646v2Lan3FGVlanPppSessionName OBJECT-TYPE
   SYNTAX      DisplayString
   MAX-ACCESS  read-write
   STATUS      current
   DESCRIPTION
      "Path: ethernet3.editConf.vlan.ppp.sessionName"
   ::= {er1646v2Lan3FGVlanEntry 251985920}

er1646v2Lan3FGVlanPppSessionSecret OBJECT-TYPE
   SYNTAX      DisplayString
   MAX-ACCESS  read-write
   STATUS      current
   DESCRIPTION
      "Path: ethernet3.editConf.vlan.ppp.sessionSecret"
   ::= {er1646v2Lan3FGVlanEntry 252051456}

er1646v2Lan3FGVlanPppEncModeSessionSecret OBJECT-TYPE
   SYNTAX      INTEGER
               {
               none (1),
               encrypt (2),
               encType1 (3),
               invalid (128)
               }
   MAX-ACCESS  read-write
   STATUS      current
   DESCRIPTION
      "Path: ethernet3.editConf.vlan.ppp.encModeSessionSecret

       Possibilities:
               none   (1)
               encrypt   (2)
               encType1   (3)
               invalid   (128)"
   ::= {er1646v2Lan3FGVlanEntry 252182528}

er1646v2Lan3FGVlanPppEncSessionSecret OBJECT-TYPE
   SYNTAX      DisplayString
   MAX-ACCESS  read-write
   STATUS      current
   DESCRIPTION
      "Path: ethernet3.editConf.vlan.ppp.encSessionSecret"
   ::= {er1646v2Lan3FGVlanEntry 252248064}

er1646v2Lan3FGVlanPppServiceName OBJECT-TYPE
   SYNTAX      DisplayString
   MAX-ACCESS  read-write
   STATUS      current
   DESCRIPTION
      "Path: ethernet3.editConf.vlan.ppp.serviceName"
   ::= {er1646v2Lan3FGVlanEntry 252116992}

er1646v2Lan3FGVlanPbbMode OBJECT-TYPE
   SYNTAX      INTEGER
               {
               disabled (0),
               static (1),
               dynamicPtp (2),
               dynamicPtmp (3)
               }
   MAX-ACCESS  read-write
   STATUS      current
   DESCRIPTION
      "Path: ethernet3.editConf.vlan.pbb.mode

       Possibilities:
               disabled   (0)
               static   (1)
               dynamicPtp   (2)
               dynamicPtmp   (3)"
   ::= {er1646v2Lan3FGVlanEntry 1174667264}

er1646v2Lan3FGVlanPbbTxCos OBJECT-TYPE
   SYNTAX      Integer32
   MAX-ACCESS  read-write
   STATUS      current
   DESCRIPTION
      "Path: ethernet3.editConf.vlan.pbb.txCos"
   ::= {er1646v2Lan3FGVlanEntry 1175191552}

er1646v2Lan3FGVlanPbbIsid OBJECT-TYPE
   SYNTAX      Integer32
   MAX-ACCESS  read-write
   STATUS      current
   DESCRIPTION
      "Path: ethernet3.editConf.vlan.pbb.isid"
   ::= {er1646v2Lan3FGVlanEntry 1175453696}

er1646v2Lan3FGVlanPbbDestMac OBJECT-TYPE
   SYNTAX      OCTET STRING
   MAX-ACCESS  read-write
   STATUS      current
   DESCRIPTION
      "Path: ethernet3.editConf.vlan.pbb.destMac

       MAC address."
   ::= {er1646v2Lan3FGVlanEntry 1175715840}

er1646v2Lan3FGVlanPbbCustomGroupMac OBJECT-TYPE
   SYNTAX      OCTET STRING
   MAX-ACCESS  read-write
   STATUS      current
   DESCRIPTION
      "Path: ethernet3.editConf.vlan.pbb.customGroupMac

       MAC address."
   ::= {er1646v2Lan3FGVlanEntry 1175977984}

er1646v2Lan3FGVlanIpSaddr OBJECT-TYPE
   SYNTAX      SEQUENCE OF Er1646v2Lan3FGVlanIpSaddrEntry
   MAX-ACCESS  not-accessible
   STATUS      current
   DESCRIPTION
      ""
   ::= {er1646v2Lan3FGVlan 51838976}

er1646v2Lan3FGVlanIpSaddrEntry OBJECT-TYPE
   SYNTAX      Er1646v2Lan3FGVlanIpSaddrEntry
   MAX-ACCESS  not-accessible
   STATUS      current
   DESCRIPTION
      ""
   INDEX      { er1646v2Lan3FGVlanTableIx,
                er1646v2Lan3FGVlanIpSaddrTableIx }
   ::= {er1646v2Lan3FGVlanIpSaddr 1}

Er1646v2Lan3FGVlanIpSaddrEntry ::=
   SEQUENCE
      {
      er1646v2Lan3FGVlanIpSaddrActions
         VariableLengthTableActions,
      er1646v2Lan3FGVlanIpSaddrTableIx
         TableIndex,
      er1646v2Lan3FGVlanIpSaddrAddress
         IpAddress,
      er1646v2Lan3FGVlanIpSaddrNetMask
         IpAddress
      }

er1646v2Lan3FGVlanIpSaddrActions OBJECT-TYPE
   SYNTAX      VariableLengthTableActions
   MAX-ACCESS  read-write
   STATUS      current
   DESCRIPTION
      "By way of this field, some manipulations
       on this table may be performed."
   ::= {er1646v2Lan3FGVlanIpSaddrEntry 2}

er1646v2Lan3FGVlanIpSaddrTableIx OBJECT-TYPE
   SYNTAX      TableIndex
   MAX-ACCESS  not-accessible
   STATUS      current
   DESCRIPTION
      ""
   ::= {er1646v2Lan3FGVlanIpSaddrEntry 11}

er1646v2Lan3FGVlanIpSaddrAddress OBJECT-TYPE
   SYNTAX      IpAddress
   MAX-ACCESS  read-write
   STATUS      current
   DESCRIPTION
      "Path: ethernet3.editConf.vlan.ip.secondaryIp.address"
   ::= {er1646v2Lan3FGVlanIpSaddrEntry 2030043136}

er1646v2Lan3FGVlanIpSaddrNetMask OBJECT-TYPE
   SYNTAX      IpAddress
   MAX-ACCESS  read-write
   STATUS      current
   DESCRIPTION
      "Path: ethernet3.editConf.vlan.ip.secondaryIp.netMask"
   ::= {er1646v2Lan3FGVlanIpSaddrEntry 2063597568}

er1646v2Lan3FGVlanIpH OBJECT-TYPE
   SYNTAX      SEQUENCE OF Er1646v2Lan3FGVlanIpHEntry
   MAX-ACCESS  not-accessible
   STATUS      current
   DESCRIPTION
      ""
   ::= {er1646v2Lan3FGVlan 51314688}

er1646v2Lan3FGVlanIpHEntry OBJECT-TYPE
   SYNTAX      Er1646v2Lan3FGVlanIpHEntry
   MAX-ACCESS  not-accessible
   STATUS      current
   DESCRIPTION
      ""
   INDEX      { er1646v2Lan3FGVlanTableIx,
                er1646v2Lan3FGVlanIpHTableIx }
   ::= {er1646v2Lan3FGVlanIpH 1}

Er1646v2Lan3FGVlanIpHEntry ::=
   SEQUENCE
      {
      er1646v2Lan3FGVlanIpHActions
         VariableLengthTableActions,
      er1646v2Lan3FGVlanIpHTableIx
         TableIndex,
      er1646v2Lan3FGVlanIpHAddress
         IpAddress,
      er1646v2Lan3FGVlanIpHDhcpRelayOptionSubscriberId
         DisplayString
      }

er1646v2Lan3FGVlanIpHActions OBJECT-TYPE
   SYNTAX      VariableLengthTableActions
   MAX-ACCESS  read-write
   STATUS      current
   DESCRIPTION
      "By way of this field, some manipulations
       on this table may be performed."
   ::= {er1646v2Lan3FGVlanIpHEntry 2}

er1646v2Lan3FGVlanIpHTableIx OBJECT-TYPE
   SYNTAX      TableIndex
   MAX-ACCESS  not-accessible
   STATUS      current
   DESCRIPTION
      ""
   ::= {er1646v2Lan3FGVlanIpHEntry 11}

er1646v2Lan3FGVlanIpHAddress OBJECT-TYPE
   SYNTAX      IpAddress
   MAX-ACCESS  read-write
   STATUS      current
   DESCRIPTION
      "Path: ethernet3.editConf.vlan.ip.helpers.address"
   ::= {er1646v2Lan3FGVlanIpHEntry 16777216}

er1646v2Lan3FGVlanIpHDhcpRelayOptionSubscriberId OBJECT-TYPE
   SYNTAX      DisplayString
   MAX-ACCESS  read-write
   STATUS      current
   DESCRIPTION
      "Path: ethernet3.editConf.vlan.ip.helpers.dhcpRelayOption.subscriberId"
   ::= {er1646v2Lan3FGVlanIpHEntry 33947648}

er1646v2Lan3FGVlanIpV6Addresses OBJECT-TYPE
   SYNTAX      SEQUENCE OF Er1646v2Lan3FGVlanIpV6AddressesEntry
   MAX-ACCESS  not-accessible
   STATUS      current
   DESCRIPTION
      ""
   ::= {er1646v2Lan3FGVlan 704839680}

er1646v2Lan3FGVlanIpV6AddressesEntry OBJECT-TYPE
   SYNTAX      Er1646v2Lan3FGVlanIpV6AddressesEntry
   MAX-ACCESS  not-accessible
   STATUS      current
   DESCRIPTION
      ""
   INDEX      { er1646v2Lan3FGVlanTableIx,
                er1646v2Lan3FGVlanIpV6AddressesTableIx }
   ::= {er1646v2Lan3FGVlanIpV6Addresses 1}

Er1646v2Lan3FGVlanIpV6AddressesEntry ::=
   SEQUENCE
      {
      er1646v2Lan3FGVlanIpV6AddressesActions
         VariableLengthTableActions,
      er1646v2Lan3FGVlanIpV6AddressesTableIx
         TableIndex,
      er1646v2Lan3FGVlanIpV6AddressesType
         INTEGER,
      er1646v2Lan3FGVlanIpV6AddressesAddress
         Ipv6Address,
      er1646v2Lan3FGVlanIpV6AddressesPrefixLength
         Integer32,
      er1646v2Lan3FGVlanIpV6AddressesGeneralPrefix
         DisplayString,
      er1646v2Lan3FGVlanIpV6AddressesRaSend
         INTEGER,
      er1646v2Lan3FGVlanIpV6AddressesRaOnLinkFlag
         INTEGER,
      er1646v2Lan3FGVlanIpV6AddressesRaAutoFlag
         INTEGER,
      er1646v2Lan3FGVlanIpV6AddressesRaValidLifeTime
         TimeTicks,
      er1646v2Lan3FGVlanIpV6AddressesRaValidLTMode
         INTEGER,
      er1646v2Lan3FGVlanIpV6AddressesRaPrefLifeTime
         TimeTicks,
      er1646v2Lan3FGVlanIpV6AddressesRaPrefLTMode
         INTEGER
      }

er1646v2Lan3FGVlanIpV6AddressesActions OBJECT-TYPE
   SYNTAX      VariableLengthTableActions
   MAX-ACCESS  read-write
   STATUS      current
   DESCRIPTION
      "By way of this field, some manipulations
       on this table may be performed."
   ::= {er1646v2Lan3FGVlanIpV6AddressesEntry 2}

er1646v2Lan3FGVlanIpV6AddressesTableIx OBJECT-TYPE
   SYNTAX      TableIndex
   MAX-ACCESS  not-accessible
   STATUS      current
   DESCRIPTION
      ""
   ::= {er1646v2Lan3FGVlanIpV6AddressesEntry 11}

er1646v2Lan3FGVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.vlan.ipV6.addresses.type

       Possibilities:
               unicast   (0)
               eui64   (1)
               anycast   (2)
               linkLocal   (3)
               generalPrefix   (4)"
   ::= {er1646v2Lan3FGVlanIpV6AddressesEntry 50331648}

er1646v2Lan3FGVlanIpV6AddressesAddress OBJECT-TYPE
   SYNTAX      Ipv6Address
   MAX-ACCESS  read-write
   STATUS      current
   DESCRIPTION
      "Path: ethernet3.editConf.vlan.ipV6.addresses.address

       ipv6 address"
   ::= {er1646v2Lan3FGVlanIpV6AddressesEntry 16777216}

er1646v2Lan3FGVlanIpV6AddressesPrefixLength OBJECT-TYPE
   SYNTAX      Integer32
   MAX-ACCESS  read-write
   STATUS      current
   DESCRIPTION
      "Path: ethernet3.editConf.vlan.ipV6.addresses.prefixLength"
   ::= {er1646v2Lan3FGVlanIpV6AddressesEntry 33554432}

er1646v2Lan3FGVlanIpV6AddressesGeneralPrefix OBJECT-TYPE
   SYNTAX      DisplayString
   MAX-ACCESS  read-write
   STATUS      current
   DESCRIPTION
      "Path: ethernet3.editConf.vlan.ipV6.addresses.generalPrefix"
   ::= {er1646v2Lan3FGVlanIpV6AddressesEntry 83886080}

er1646v2Lan3FGVlanIpV6AddressesRaSend OBJECT-TYPE
   SYNTAX      INTEGER
               {
               disabled (0),
               enabled (1)
               }
   MAX-ACCESS  read-write
   STATUS      current
   DESCRIPTION
      "Path: ethernet3.editConf.vlan.ipV6.addresses.ra.send

       Possibilities:
               disabled   (0)
               enabled   (1)"
   ::= {er1646v2Lan3FGVlanIpV6AddressesEntry 67174400}

er1646v2Lan3FGVlanIpV6AddressesRaOnLinkFlag OBJECT-TYPE
   SYNTAX      INTEGER
               {
               disabled (0),
               enabled (1)
               }
   MAX-ACCESS  read-write
   STATUS      current
   DESCRIPTION
      "Path: ethernet3.editConf.vlan.ipV6.addresses.ra.onLinkFlag

       Possibilities:
               disabled   (0)
               enabled   (1)"
   ::= {er1646v2Lan3FGVlanIpV6AddressesEntry 67371008}

er1646v2Lan3FGVlanIpV6AddressesRaAutoFlag OBJECT-TYPE
   SYNTAX      INTEGER
               {
               disabled (0),
               enabled (1)
               }
   MAX-ACCESS  read-write
   STATUS      current
   DESCRIPTION
      "Path: ethernet3.editConf.vlan.ipV6.addresses.ra.autonomousFlag

       Possibilities:
               disabled   (0)
               enabled   (1)"
   ::= {er1646v2Lan3FGVlanIpV6AddressesEntry 67567616}

er1646v2Lan3FGVlanIpV6AddressesRaValidLifeTime OBJECT-TYPE
   SYNTAX      TimeTicks
   MAX-ACCESS  read-write
   STATUS      current
   DESCRIPTION
      "Path: ethernet3.editConf.vlan.ipV6.addresses.ra.validLifeTime

       Time in centi-second."
   ::= {er1646v2Lan3FGVlanIpV6AddressesEntry 67239936}

er1646v2Lan3FGVlanIpV6AddressesRaValidLTMode OBJECT-TYPE
   SYNTAX      INTEGER
               {
               fixed (0),
               infinite (2)
               }
   MAX-ACCESS  read-write
   STATUS      current
   DESCRIPTION
      "Path: ethernet3.editConf.vlan.ipV6.addresses.ra.validLifeTimeMode

       Possibilities:
               fixed   (0)
               infinite   (2)"
   ::= {er1646v2Lan3FGVlanIpV6AddressesEntry 67305472}

er1646v2Lan3FGVlanIpV6AddressesRaPrefLifeTime OBJECT-TYPE
   SYNTAX      TimeTicks
   MAX-ACCESS  read-write
   STATUS      current
   DESCRIPTION
      "Path: ethernet3.editConf.vlan.ipV6.addresses.ra.prefLifeTime

       Time in centi-second."
   ::= {er1646v2Lan3FGVlanIpV6AddressesEntry 67436544}

er1646v2Lan3FGVlanIpV6AddressesRaPrefLTMode OBJECT-TYPE
   SYNTAX      INTEGER
               {
               fixed (0),
               infinite (2)
               }
   MAX-ACCESS  read-write
   STATUS      current
   DESCRIPTION
      "Path: ethernet3.editConf.vlan.ipV6.addresses.ra.prefLifeTimeMode

       Possibilities:
               fixed   (0)
               infinite   (2)"
   ::= {er1646v2Lan3FGVlanIpV6AddressesEntry 67502080}

er1646v2Lan3FGVlanIpV6RaDnsOptionsRdnssServers OBJECT-TYPE
   SYNTAX      SEQUENCE OF Er1646v2Lan3FGVlanIpV6RaDnsOptionsRdnssServersEntry
   MAX-ACCESS  not-accessible
   STATUS      current
   DESCRIPTION
      ""
   ::= {er1646v2Lan3FGVlan 705039144}

er1646v2Lan3FGVlanIpV6RaDnsOptionsRdnssServersEntry OBJECT-TYPE
   SYNTAX      Er1646v2Lan3FGVlanIpV6RaDnsOptionsRdnssServersEntry
   MAX-ACCESS  not-accessible
   STATUS      current
   DESCRIPTION
      ""
   INDEX      { er1646v2Lan3FGVlanTableIx,
                er1646v2Lan3FGVlanIpV6RaDnsOptionsRdnssServersTableIx }
   ::= {er1646v2Lan3FGVlanIpV6RaDnsOptionsRdnssServers 1}

Er1646v2Lan3FGVlanIpV6RaDnsOptionsRdnssServersEntry ::=
   SEQUENCE
      {
      er1646v2Lan3FGVlanIpV6RaDnsOptionsRdnssServersActions
         VariableLengthTableActions,
      er1646v2Lan3FGVlanIpV6RaDnsOptionsRdnssServersTableIx
         TableIndex,
      er1646v2Lan3FGVlanIpV6RaDnsOptionsRdnssServersAddress
         Ipv6Address
      }

er1646v2Lan3FGVlanIpV6RaDnsOptionsRdnssServersActions OBJECT-TYPE
   SYNTAX      VariableLengthTableActions
   MAX-ACCESS  read-write
   STATUS      current
   DESCRIPTION
      "By way of this field, some manipulations
       on this table may be performed."
   ::= {er1646v2Lan3FGVlanIpV6RaDnsOptionsRdnssServersEntry 2}

er1646v2Lan3FGVlanIpV6RaDnsOptionsRdnssServersTableIx OBJECT-TYPE
   SYNTAX      TableIndex
   MAX-ACCESS  not-accessible
   STATUS      current
   DESCRIPTION
      ""
   ::= {er1646v2Lan3FGVlanIpV6RaDnsOptionsRdnssServersEntry 11}

er1646v2Lan3FGVlanIpV6RaDnsOptionsRdnssServersAddress OBJECT-TYPE
   SYNTAX      Ipv6Address
   MAX-ACCESS  read-write
   STATUS      current
   DESCRIPTION
      "Path: ethernet3.editConf.vlan.ipV6.ra.dnsOptions.rdnss.servers.address

       ipv6 address"
   ::= {er1646v2Lan3FGVlanIpV6RaDnsOptionsRdnssServersEntry 16777216}

er1646v2Lan3FGVlanIpV6RaDnsOptionsDnsslDomains OBJECT-TYPE
   SYNTAX      SEQUENCE OF Er1646v2Lan3FGVlanIpV6RaDnsOptionsDnsslDomainsEntry
   MAX-ACCESS  not-accessible
   STATUS      current
   DESCRIPTION
      ""
   ::= {er1646v2Lan3FGVlan 705039176}

er1646v2Lan3FGVlanIpV6RaDnsOptionsDnsslDomainsEntry OBJECT-TYPE
   SYNTAX      Er1646v2Lan3FGVlanIpV6RaDnsOptionsDnsslDomainsEntry
   MAX-ACCESS  not-accessible
   STATUS      current
   DESCRIPTION
      ""
   INDEX      { er1646v2Lan3FGVlanTableIx,
                er1646v2Lan3FGVlanIpV6RaDnsOptionsDnsslDomainsTableIx }
   ::= {er1646v2Lan3FGVlanIpV6RaDnsOptionsDnsslDomains 1}

Er1646v2Lan3FGVlanIpV6RaDnsOptionsDnsslDomainsEntry ::=
   SEQUENCE
      {
      er1646v2Lan3FGVlanIpV6RaDnsOptionsDnsslDomainsActions
         VariableLengthTableActions,
      er1646v2Lan3FGVlanIpV6RaDnsOptionsDnsslDomainsTableIx
         TableIndex,
      er1646v2Lan3FGVlanIpV6RaDnsOptionsDnsslDomainsName
         DisplayString
      }

er1646v2Lan3FGVlanIpV6RaDnsOptionsDnsslDomainsActions OBJECT-TYPE
   SYNTAX      VariableLengthTableActions
   MAX-ACCESS  read-write
   STATUS      current
   DESCRIPTION
      "By way of this field, some manipulations
       on this table may be performed."
   ::= {er1646v2Lan3FGVlanIpV6RaDnsOptionsDnsslDomainsEntry 2}

er1646v2Lan3FGVlanIpV6RaDnsOptionsDnsslDomainsTableIx OBJECT-TYPE
   SYNTAX      TableIndex
   MAX-ACCESS  not-accessible
   STATUS      current
   DESCRIPTION
      ""
   ::= {er1646v2Lan3FGVlanIpV6RaDnsOptionsDnsslDomainsEntry 11}

er1646v2Lan3FGVlanIpV6RaDnsOptionsDnsslDomainsName OBJECT-TYPE
   SYNTAX      DisplayString
   MAX-ACCESS  read-write
   STATUS      current
   DESCRIPTION
      "Path: ethernet3.editConf.vlan.ipV6.ra.dnsOptions.dnssl.domains.name"
   ::= {er1646v2Lan3FGVlanIpV6RaDnsOptionsDnsslDomainsEntry 16777216}

er1646v2Lan3FGVlanIpV6DhcpClientUserClassOpt OBJECT-TYPE
   SYNTAX      SEQUENCE OF Er1646v2Lan3FGVlanIpV6DhcpClientUserClassOptEntry
   MAX-ACCESS  not-accessible
   STATUS      current
   DESCRIPTION
      ""
   ::= {er1646v2Lan3FGVlan 705312768}

er1646v2Lan3FGVlanIpV6DhcpClientUserClassOptEntry OBJECT-TYPE
   SYNTAX      Er1646v2Lan3FGVlanIpV6DhcpClientUserClassOptEntry
   MAX-ACCESS  not-accessible
   STATUS      current
   DESCRIPTION
      ""
   INDEX      { er1646v2Lan3FGVlanTableIx,
                er1646v2Lan3FGVlanIpV6DhcpClientUserClassOptTableIx }
   ::= {er1646v2Lan3FGVlanIpV6DhcpClientUserClassOpt 1}

Er1646v2Lan3FGVlanIpV6DhcpClientUserClassOptEntry ::=
   SEQUENCE
      {
      er1646v2Lan3FGVlanIpV6DhcpClientUserClassOptActions
         VariableLengthTableActions,
      er1646v2Lan3FGVlanIpV6DhcpClientUserClassOptTableIx
         TableIndex,
      er1646v2Lan3FGVlanIpV6DhcpClientUserClassOptValueAscii
         DisplayString,
      er1646v2Lan3FGVlanIpV6DhcpClientUserClassOptValueDecimal
         Integer32,
      er1646v2Lan3FGVlanIpV6DhcpClientUserClassOptValueHexData
         OCTET STRING
      }

er1646v2Lan3FGVlanIpV6DhcpClientUserClassOptActions OBJECT-TYPE
   SYNTAX      VariableLengthTableActions
   MAX-ACCESS  read-write
   STATUS      current
   DESCRIPTION
      "By way of this field, some manipulations
       on this table may be performed."
   ::= {er1646v2Lan3FGVlanIpV6DhcpClientUserClassOptEntry 2}

er1646v2Lan3FGVlanIpV6DhcpClientUserClassOptTableIx OBJECT-TYPE
   SYNTAX      TableIndex
   MAX-ACCESS  not-accessible
   STATUS      current
   DESCRIPTION
      ""
   ::= {er1646v2Lan3FGVlanIpV6DhcpClientUserClassOptEntry 11}

er1646v2Lan3FGVlanIpV6DhcpClientUserClassOptValueAscii OBJECT-TYPE
   SYNTAX      DisplayString
   MAX-ACCESS  read-write
   STATUS      current
   DESCRIPTION
      "Path: ethernet3.editConf.vlan.ipV6.dhcp.client.userClassOpt.value.ascii"
   ::= {er1646v2Lan3FGVlanIpV6DhcpClientUserClassOptEntry 16842752}

er1646v2Lan3FGVlanIpV6DhcpClientUserClassOptValueDecimal OBJECT-TYPE
   SYNTAX      Integer32
   MAX-ACCESS  read-write
   STATUS      current
   DESCRIPTION
      "Path: ethernet3.editConf.vlan.ipV6.dhcp.client.userClassOpt.value.decimal"
   ::= {er1646v2Lan3FGVlanIpV6DhcpClientUserClassOptEntry 16908288}

er1646v2Lan3FGVlanIpV6DhcpClientUserClassOptValueHexData OBJECT-TYPE
   SYNTAX      OCTET STRING
   MAX-ACCESS  read-write
   STATUS      current
   DESCRIPTION
      "Path: ethernet3.editConf.vlan.ipV6.dhcp.client.userClassOpt.value.hexData"
   ::= {er1646v2Lan3FGVlanIpV6DhcpClientUserClassOptEntry 16973824}

er1646v2Lan3FGVlanIpV6DhcpClientVendorCl OBJECT-TYPE
   SYNTAX      SEQUENCE OF Er1646v2Lan3FGVlanIpV6DhcpClientVendorClEntry
   MAX-ACCESS  not-accessible
   STATUS      current
   DESCRIPTION
      ""
   ::= {er1646v2Lan3FGVlan 705313792}

er1646v2Lan3FGVlanIpV6DhcpClientVendorClEntry OBJECT-TYPE
   SYNTAX      Er1646v2Lan3FGVlanIpV6DhcpClientVendorClEntry
   MAX-ACCESS  not-accessible
   STATUS      current
   DESCRIPTION
      ""
   INDEX      { er1646v2Lan3FGVlanTableIx,
                er1646v2Lan3FGVlanIpV6DhcpClientVendorClTableIx }
   ::= {er1646v2Lan3FGVlanIpV6DhcpClientVendorCl 1}

Er1646v2Lan3FGVlanIpV6DhcpClientVendorClEntry ::=
   SEQUENCE
      {
      er1646v2Lan3FGVlanIpV6DhcpClientVendorClActions
         VariableLengthTableActions,
      er1646v2Lan3FGVlanIpV6DhcpClientVendorClTableIx
         TableIndex,
      er1646v2Lan3FGVlanIpV6DhcpClientVendorClValueAscii
         DisplayString,
      er1646v2Lan3FGVlanIpV6DhcpClientVendorClValueDecimal
         Integer32,
      er1646v2Lan3FGVlanIpV6DhcpClientVendorClValueHexData
         OCTET STRING
      }

er1646v2Lan3FGVlanIpV6DhcpClientVendorClActions OBJECT-TYPE
   SYNTAX      VariableLengthTableActions
   MAX-ACCESS  read-write
   STATUS      current
   DESCRIPTION
      "By way of this field, some manipulations
       on this table may be performed."
   ::= {er1646v2Lan3FGVlanIpV6DhcpClientVendorClEntry 2}

er1646v2Lan3FGVlanIpV6DhcpClientVendorClTableIx OBJECT-TYPE
   SYNTAX      TableIndex
   MAX-ACCESS  not-accessible
   STATUS      current
   DESCRIPTION
      ""
   ::= {er1646v2Lan3FGVlanIpV6DhcpClientVendorClEntry 11}

er1646v2Lan3FGVlanIpV6DhcpClientVendorClValueAscii OBJECT-TYPE
   SYNTAX      DisplayString
   MAX-ACCESS  read-write
   STATUS      current
   DESCRIPTION
      "Path: ethernet3.editConf.vlan.ipV6.dhcp.client.vendorClassOpt.value.ascii"
   ::= {er1646v2Lan3FGVlanIpV6DhcpClientVendorClEntry 16842752}

er1646v2Lan3FGVlanIpV6DhcpClientVendorClValueDecimal OBJECT-TYPE
   SYNTAX      Integer32
   MAX-ACCESS  read-write
   STATUS      current
   DESCRIPTION
      "Path: ethernet3.editConf.vlan.ipV6.dhcp.client.vendorClassOpt.value.decimal"
   ::= {er1646v2Lan3FGVlanIpV6DhcpClientVendorClEntry 16908288}

er1646v2Lan3FGVlanIpV6DhcpClientVendorClValueHexData OBJECT-TYPE
   SYNTAX      OCTET STRING
   MAX-ACCESS  read-write
   STATUS      current
   DESCRIPTION
      "Path: ethernet3.editConf.vlan.ipV6.dhcp.client.vendorClassOpt.value.hexData"
   ::= {er1646v2Lan3FGVlanIpV6DhcpClientVendorClEntry 16973824}

er1646v2Lan3FGVlanIpV6DhcpRelayDestinations OBJECT-TYPE
   SYNTAX      SEQUENCE OF Er1646v2Lan3FGVlanIpV6DhcpRelayDestinationsEntry
   MAX-ACCESS  not-accessible
   STATUS      current
   DESCRIPTION
      ""
   ::= {er1646v2Lan3FGVlan 705323072}

er1646v2Lan3FGVlanIpV6DhcpRelayDestinationsEntry OBJECT-TYPE
   SYNTAX      Er1646v2Lan3FGVlanIpV6DhcpRelayDestinationsEntry
   MAX-ACCESS  not-accessible
   STATUS      current
   DESCRIPTION
      ""
   INDEX      { er1646v2Lan3FGVlanTableIx,
                er1646v2Lan3FGVlanIpV6DhcpRelayDestinationsTableIx }
   ::= {er1646v2Lan3FGVlanIpV6DhcpRelayDestinations 1}

Er1646v2Lan3FGVlanIpV6DhcpRelayDestinationsEntry ::=
   SEQUENCE
      {
      er1646v2Lan3FGVlanIpV6DhcpRelayDestinationsActions
         VariableLengthTableActions,
      er1646v2Lan3FGVlanIpV6DhcpRelayDestinationsTableIx
         TableIndex,
      er1646v2Lan3FGVlanIpV6DhcpRelayDestinationsAddress
         Ipv6Address,
      er1646v2Lan3FGVlanIpV6DhcpRelayDestinationsInterface
         DisplayString
      }

er1646v2Lan3FGVlanIpV6DhcpRelayDestinationsActions OBJECT-TYPE
   SYNTAX      VariableLengthTableActions
   MAX-ACCESS  read-write
   STATUS      current
   DESCRIPTION
      "By way of this field, some manipulations
       on this table may be performed."
   ::= {er1646v2Lan3FGVlanIpV6DhcpRelayDestinationsEntry 2}

er1646v2Lan3FGVlanIpV6DhcpRelayDestinationsTableIx OBJECT-TYPE
   SYNTAX      TableIndex
   MAX-ACCESS  not-accessible
   STATUS      current
   DESCRIPTION
      ""
   ::= {er1646v2Lan3FGVlanIpV6DhcpRelayDestinationsEntry 11}

er1646v2Lan3FGVlanIpV6DhcpRelayDestinationsAddress OBJECT-TYPE
   SYNTAX      Ipv6Address
   MAX-ACCESS  read-write
   STATUS      current
   DESCRIPTION
      "Path: ethernet3.editConf.vlan.ipV6.dhcp.relay.destinations.address

       ipv6 address"
   ::= {er1646v2Lan3FGVlanIpV6DhcpRelayDestinationsEntry 16777216}

er1646v2Lan3FGVlanIpV6DhcpRelayDestinationsInterface OBJECT-TYPE
   SYNTAX      DisplayString
   MAX-ACCESS  read-write
   STATUS      current
   DESCRIPTION
      "Path: ethernet3.editConf.vlan.ipV6.dhcp.relay.destinations.interface"
   ::= {er1646v2Lan3FGVlanIpV6DhcpRelayDestinationsEntry 33554432}

er1646v2Lan3FGVlanBridgingVlTVlans OBJECT-TYPE
   SYNTAX      SEQUENCE OF Er1646v2Lan3FGVlanBridgingVlTVlansEntry
   MAX-ACCESS  not-accessible
   STATUS      current
   DESCRIPTION
      ""
   ::= {er1646v2Lan3FGVlan 459079680}

er1646v2Lan3FGVlanBridgingVlTVlansEntry OBJECT-TYPE
   SYNTAX      Er1646v2Lan3FGVlanBridgingVlTVlansEntry
   MAX-ACCESS  not-accessible
   STATUS      current
   DESCRIPTION
      ""
   INDEX      { er1646v2Lan3FGVlanTableIx,
                er1646v2Lan3FGVlanBridgingVlTVlansTableIx }
   ::= {er1646v2Lan3FGVlanBridgingVlTVlans 1}

Er1646v2Lan3FGVlanBridgingVlTVlansEntry ::=
   SEQUENCE
      {
      er1646v2Lan3FGVlanBridgingVlTVlansActions
         VariableLengthTableActions,
      er1646v2Lan3FGVlanBridgingVlTVlansTableIx
         TableIndex,
      er1646v2Lan3FGVlanBridgingVlTVlansVid
         Integer32,
      er1646v2Lan3FGVlanBridgingVlTVlansEndVid
         Integer32,
      er1646v2Lan3FGVlanBridgingVlTVlansAction
         INTEGER,
      er1646v2Lan3FGVlanBridgingVlTVlansTagInfoTpid
         INTEGER,
      er1646v2Lan3FGVlanBridgingVlTVlansTagInfoVid
         Integer32
      }

er1646v2Lan3FGVlanBridgingVlTVlansActions OBJECT-TYPE
   SYNTAX      VariableLengthTableActions
   MAX-ACCESS  read-write
   STATUS      current
   DESCRIPTION
      "By way of this field, some manipulations
       on this table may be performed."
   ::= {er1646v2Lan3FGVlanBridgingVlTVlansEntry 2}

er1646v2Lan3FGVlanBridgingVlTVlansTableIx OBJECT-TYPE
   SYNTAX      TableIndex
   MAX-ACCESS  not-accessible
   STATUS      current
   DESCRIPTION
      ""
   ::= {er1646v2Lan3FGVlanBridgingVlTVlansEntry 11}

er1646v2Lan3FGVlanBridgingVlTVlansVid OBJECT-TYPE
   SYNTAX      Integer32
   MAX-ACCESS  read-write
   STATUS      current
   DESCRIPTION
      "Path: ethernet3.editConf.vlan.bridging.vlanTagging.vlans.vid"
   ::= {er1646v2Lan3FGVlanBridgingVlTVlansEntry 536870912}

er1646v2Lan3FGVlanBridgingVlTVlansEndVid OBJECT-TYPE
   SYNTAX      Integer32
   MAX-ACCESS  read-write
   STATUS      current
   DESCRIPTION
      "Path: ethernet3.editConf.vlan.bridging.vlanTagging.vlans.endVid"
   ::= {er1646v2Lan3FGVlanBridgingVlTVlansEntry 2147483648}

er1646v2Lan3FGVlanBridgingVlTVlansAction OBJECT-TYPE
   SYNTAX      INTEGER
               {
               discard (0),
               accept (1),
               tag (2)
               }
   MAX-ACCESS  read-write
   STATUS      current
   DESCRIPTION
      "Path: ethernet3.editConf.vlan.bridging.vlanTagging.vlans.action

       Possibilities:
               discard   (0)
               accept   (1)
               tag   (2)"
   ::= {er1646v2Lan3FGVlanBridgingVlTVlansEntry 1073741824}

er1646v2Lan3FGVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.bridging.vlanTagging.vlans.tagInfo.tpid

       Possibilities:
               dot1Q   (33024)
               dot1ad   (34984)
               0x9100   (37120)
               0x9200   (37376)
               0x9300   (37632)"
   ::= {er1646v2Lan3FGVlanBridgingVlTVlansEntry 1677721600}

er1646v2Lan3FGVlanBridgingVlTVlansTagInfoVid OBJECT-TYPE
   SYNTAX      Integer32
   MAX-ACCESS  read-write
   STATUS      current
   DESCRIPTION
      "Path: ethernet3.editConf.vlan.bridging.vlanTagging.vlans.tagInfo.vid"
   ::= {er1646v2Lan3FGVlanBridgingVlTVlansEntry 1744830464}

er1646v2Lan3FGVlanVlanVidExtensionTable OBJECT-TYPE
   SYNTAX      SEQUENCE OF Er1646v2Lan3FGVlanVlanVidExtensionTableEntry
   MAX-ACCESS  not-accessible
   STATUS      current
   DESCRIPTION
      ""
   ::= {er1646v2Lan3FGVlan 235340544}

er1646v2Lan3FGVlanVlanVidExtensionTableEntry OBJECT-TYPE
   SYNTAX      Er1646v2Lan3FGVlanVlanVidExtensionTableEntry
   MAX-ACCESS  not-accessible
   STATUS      current
   DESCRIPTION
      ""
   INDEX      { er1646v2Lan3FGVlanTableIx,
                er1646v2Lan3FGVlanVlanVidExtensionTableTableIx }
   ::= {er1646v2Lan3FGVlanVlanVidExtensionTable 1}

Er1646v2Lan3FGVlanVlanVidExtensionTableEntry ::=
   SEQUENCE
      {
      er1646v2Lan3FGVlanVlanVidExtensionTableActions
         VariableLengthTableActions,
      er1646v2Lan3FGVlanVlanVidExtensionTableTableIx
         TableIndex,
      er1646v2Lan3FGVlanVlanVidExtensionTableTpid
         INTEGER,
      er1646v2Lan3FGVlanVlanVidExtensionTableVid
         Integer32,
      er1646v2Lan3FGVlanVlanVidExtensionTableEndVid
         Integer32
      }

er1646v2Lan3FGVlanVlanVidExtensionTableActions OBJECT-TYPE
   SYNTAX      VariableLengthTableActions
   MAX-ACCESS  read-write
   STATUS      current
   DESCRIPTION
      "By way of this field, some manipulations
       on this table may be performed."
   ::= {er1646v2Lan3FGVlanVlanVidExtensionTableEntry 2}

er1646v2Lan3FGVlanVlanVidExtensionTableTableIx OBJECT-TYPE
   SYNTAX      TableIndex
   MAX-ACCESS  not-accessible
   STATUS      current
   DESCRIPTION
      ""
   ::= {er1646v2Lan3FGVlanVlanVidExtensionTableEntry 11}

er1646v2Lan3FGVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet3.editConf.vlan.vlan.vidExtension.table.tpid

       Possibilities:
               dot1Q   (33024)
               dot1ad   (34984)
               0x9100   (37120)
               0x9200   (37376)
               0x9300   (37632)"
   ::= {er1646v2Lan3FGVlanVlanVidExtensionTableEntry 16777216}

er1646v2Lan3FGVlanVlanVidExtensionTableVid OBJECT-TYPE
   SYNTAX      Integer32
   MAX-ACCESS  read-write
   STATUS      current
   DESCRIPTION
      "Path: ethernet3.editConf.vlan.vlan.vidExtension.table.vid"
   ::= {er1646v2Lan3FGVlanVlanVidExtensionTableEntry 33554432}

er1646v2Lan3FGVlanVlanVidExtensionTableEndVid OBJECT-TYPE
   SYNTAX      Integer32
   MAX-ACCESS  read-write
   STATUS      current
   DESCRIPTION
      "Path: ethernet3.editConf.vlan.vlan.vidExtension.table.endVid"
   ::= {er1646v2Lan3FGVlanVlanVidExtensionTableEntry 50331648}

er1646v2Lan3FGVlanVlanCSMap OBJECT-TYPE
   SYNTAX      SEQUENCE OF Er1646v2Lan3FGVlanVlanCSMapEntry
   MAX-ACCESS  not-accessible
   STATUS      current
   DESCRIPTION
      ""
   ::= {er1646v2Lan3FGVlan 235405312}

er1646v2Lan3FGVlanVlanCSMapEntry OBJECT-TYPE
   SYNTAX      Er1646v2Lan3FGVlanVlanCSMapEntry
   MAX-ACCESS  not-accessible
   STATUS      current
   DESCRIPTION
      ""
   INDEX      { er1646v2Lan3FGVlanTableIx,
                er1646v2Lan3FGVlanVlanCSMapTableIx }
   ::= {er1646v2Lan3FGVlanVlanCSMap 1}

Er1646v2Lan3FGVlanVlanCSMapEntry ::=
   SEQUENCE
      {
      er1646v2Lan3FGVlanVlanCSMapActions
         VariableLengthTableActions,
      er1646v2Lan3FGVlanVlanCSMapTableIx
         TableIndex,
      er1646v2Lan3FGVlanVlanCSMapCos
         INTEGER,
      er1646v2Lan3FGVlanVlanCSMapDei
         INTEGER,
      er1646v2Lan3FGVlanVlanCSMapTos
         INTEGER,
      er1646v2Lan3FGVlanVlanCSMapQueue
         INTEGER,
      er1646v2Lan3FGVlanVlanCSMapDropLevel
         INTEGER,
      er1646v2Lan3FGVlanVlanCSMapDeFlag
         INTEGER
      }

er1646v2Lan3FGVlanVlanCSMapActions OBJECT-TYPE
   SYNTAX      VariableLengthTableActions
   MAX-ACCESS  read-write
   STATUS      current
   DESCRIPTION
      "By way of this field, some manipulations
       on this table may be performed."
   ::= {er1646v2Lan3FGVlanVlanCSMapEntry 2}

er1646v2Lan3FGVlanVlanCSMapTableIx OBJECT-TYPE
   SYNTAX      TableIndex
   MAX-ACCESS  not-accessible
   STATUS      current
   DESCRIPTION
      ""
   ::= {er1646v2Lan3FGVlanVlanCSMapEntry 11}

er1646v2Lan3FGVlanVlanCSMapCos OBJECT-TYPE
   SYNTAX      INTEGER
               {
               any (8)
               }
   MAX-ACCESS  read-write
   STATUS      current
   DESCRIPTION
      "Path: ethernet3.editConf.vlan.vlan.cosMap.cos

       Possibilities:
               any   (8)"
   ::= {er1646v2Lan3FGVlanVlanCSMapEntry 16777216}

er1646v2Lan3FGVlanVlanCSMapDei OBJECT-TYPE
   SYNTAX      INTEGER
               {
               clear (0),
               set (1),
               any (2)
               }
   MAX-ACCESS  read-write
   STATUS      current
   DESCRIPTION
      "Path: ethernet3.editConf.vlan.vlan.cosMap.dei

       Possibilities:
               clear   (0)
               set   (1)
               any   (2)"
   ::= {er1646v2Lan3FGVlanVlanCSMapEntry 33554432}

er1646v2Lan3FGVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet3.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2Lan3FGVlanVlanCSMapEntry 50331648}

er1646v2Lan3FGVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet3.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1646v2Lan3FGVlanVlanCSMapEntry 67108864}

er1646v2Lan3FGVlanVlanCSMapDropLevel OBJECT-TYPE
   SYNTAX      INTEGER
               {
               unchanged (-1),
               dropOnQueue (0)
               }
   MAX-ACCESS  read-write
   STATUS      current
   DESCRIPTION
      "Path: ethernet3.editConf.vlan.vlan.cosMap.dropLevel

       Possibilities:
               unchanged   (-1)
               dropOnQueue   (0)"
   ::= {er1646v2Lan3FGVlanVlanCSMapEntry 83886080}

er1646v2Lan3FGVlanVlanCSMapDeFlag OBJECT-TYPE
   SYNTAX      INTEGER
               {
               unchanged (255),
               clear (0),
               set (1)
               }
   MAX-ACCESS  read-write
   STATUS      current
   DESCRIPTION
      "Path: ethernet3.editConf.vlan.vlan.cosMap.deFlag

       Possibilities:
               unchanged   (255)
               clear   (0)
               set   (1)"
   ::= {er1646v2Lan3FGVlanVlanCSMapEntry 117440512}

er1646v2Lan3FGVlanVlanTCMap OBJECT-TYPE
   SYNTAX      SEQUENCE OF Er1646v2Lan3FGVlanVlanTCMapEntry
   MAX-ACCESS  not-accessible
   STATUS      current
   DESCRIPTION
      ""
   ::= {er1646v2Lan3FGVlan 241369088}

er1646v2Lan3FGVlanVlanTCMapEntry OBJECT-TYPE
   SYNTAX      Er1646v2Lan3FGVlanVlanTCMapEntry
   MAX-ACCESS  not-accessible
   STATUS      current
   DESCRIPTION
      ""
   INDEX      { er1646v2Lan3FGVlanTableIx,
                er1646v2Lan3FGVlanVlanTCMapTableIx }
   ::= {er1646v2Lan3FGVlanVlanTCMap 1}

Er1646v2Lan3FGVlanVlanTCMapEntry ::=
   SEQUENCE
      {
      er1646v2Lan3FGVlanVlanTCMapActions
         VariableLengthTableActions,
      er1646v2Lan3FGVlanVlanTCMapTableIx
         TableIndex,
      er1646v2Lan3FGVlanVlanTCMapStartTos
         INTEGER,
      er1646v2Lan3FGVlanVlanTCMapEndTos
         INTEGER,
      er1646v2Lan3FGVlanVlanTCMapCos
         INTEGER
      }

er1646v2Lan3FGVlanVlanTCMapActions OBJECT-TYPE
   SYNTAX      VariableLengthTableActions
   MAX-ACCESS  read-write
   STATUS      current
   DESCRIPTION
      "By way of this field, some manipulations
       on this table may be performed."
   ::= {er1646v2Lan3FGVlanVlanTCMapEntry 2}

er1646v2Lan3FGVlanVlanTCMapTableIx OBJECT-TYPE
   SYNTAX      TableIndex
   MAX-ACCESS  not-accessible
   STATUS      current
   DESCRIPTION
      ""
   ::= {er1646v2Lan3FGVlanVlanTCMapEntry 11}

er1646v2Lan3FGVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet3.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2Lan3FGVlanVlanTCMapEntry 16777216}

er1646v2Lan3FGVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet3.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2Lan3FGVlanVlanTCMapEntry 33554432}

er1646v2Lan3FGVlanVlanTCMapCos OBJECT-TYPE
   SYNTAX      INTEGER
               {
               queueCosMap (8)
               }
   MAX-ACCESS  read-write
   STATUS      current
   DESCRIPTION
      "Path: ethernet3.editConf.vlan.vlan.tosCosMap.cos

       Possibilities:
               queueCosMap   (8)"
   ::= {er1646v2Lan3FGVlanVlanTCMapEntry 50331648}

er1646v2Lan3FGVlanVlanArpStaticArp OBJECT-TYPE
   SYNTAX      SEQUENCE OF Er1646v2Lan3FGVlanVlanArpStaticArpEntry
   MAX-ACCESS  not-accessible
   STATUS      current
   DESCRIPTION
      ""
   ::= {er1646v2Lan3FGVlan 235275008}

er1646v2Lan3FGVlanVlanArpStaticArpEntry OBJECT-TYPE
   SYNTAX      Er1646v2Lan3FGVlanVlanArpStaticArpEntry
   MAX-ACCESS  not-accessible
   STATUS      current
   DESCRIPTION
      ""
   INDEX      { er1646v2Lan3FGVlanTableIx,
                er1646v2Lan3FGVlanVlanArpStaticArpTableIx }
   ::= {er1646v2Lan3FGVlanVlanArpStaticArp 1}

Er1646v2Lan3FGVlanVlanArpStaticArpEntry ::=
   SEQUENCE
      {
      er1646v2Lan3FGVlanVlanArpStaticArpActions
         VariableLengthTableActions,
      er1646v2Lan3FGVlanVlanArpStaticArpTableIx
         TableIndex,
      er1646v2Lan3FGVlanVlanArpStaticArpMacAddress
         OCTET STRING,
      er1646v2Lan3FGVlanVlanArpStaticArpIpAddress
         IpAddress
      }

er1646v2Lan3FGVlanVlanArpStaticArpActions OBJECT-TYPE
   SYNTAX      VariableLengthTableActions
   MAX-ACCESS  read-write
   STATUS      current
   DESCRIPTION
      "By way of this field, some manipulations
       on this table may be performed."
   ::= {er1646v2Lan3FGVlanVlanArpStaticArpEntry 2}

er1646v2Lan3FGVlanVlanArpStaticArpTableIx OBJECT-TYPE
   SYNTAX      TableIndex
   MAX-ACCESS  not-accessible
   STATUS      current
   DESCRIPTION
      ""
   ::= {er1646v2Lan3FGVlanVlanArpStaticArpEntry 11}

er1646v2Lan3FGVlanVlanArpStaticArpMacAddress OBJECT-TYPE
   SYNTAX      OCTET STRING
   MAX-ACCESS  read-write
   STATUS      current
   DESCRIPTION
      "Path: ethernet3.editConf.vlan.vlan.arp.staticArp.macAddress

       MAC address."
   ::= {er1646v2Lan3FGVlanVlanArpStaticArpEntry 16777216}

er1646v2Lan3FGVlanVlanArpStaticArpIpAddress OBJECT-TYPE
   SYNTAX      IpAddress
   MAX-ACCESS  read-write
   STATUS      current
   DESCRIPTION
      "Path: ethernet3.editConf.vlan.vlan.arp.staticArp.ipAddress"
   ::= {er1646v2Lan3FGVlanVlanArpStaticArpEntry 33554432}


er1646v2Lan3FGPppOE OBJECT IDENTIFIER ::= {er1646v2Lan3FG 35}

er1646v2Lan3FGPppOESSCTable OBJECT-TYPE
   SYNTAX      SEQUENCE OF Er1646v2Lan3FGPppOEEntry
   MAX-ACCESS  not-accessible
   STATUS      current
   DESCRIPTION
      ""
   ::= {er1646v2Lan3FGPppOE 1}

er1646v2Lan3FGPppOEEntry OBJECT-TYPE
   SYNTAX      Er1646v2Lan3FGPppOEEntry
   MAX-ACCESS  not-accessible
   STATUS      current
   DESCRIPTION
      ""
   INDEX      { er1646v2Lan3FGPppOETableIx }
   ::= {er1646v2Lan3FGPppOESSCTable 1}

Er1646v2Lan3FGPppOEEntry ::=
   SEQUENCE
      {
      er1646v2Lan3FGPppOEActions
         VariableLengthTableActions,
      er1646v2Lan3FGPppOETableIx
         TableIndex,
      er1646v2Lan3FGPppOEName
         DisplayString,
      er1646v2Lan3FGPppOERemark
         DisplayString,
      er1646v2Lan3FGPppOEAdminStatus
         INTEGER,
      er1646v2Lan3FGPppOEMode
         INTEGER,
      er1646v2Lan3FGPppOEIpVrfRouter
         DisplayString,
      er1646v2Lan3FGPppOEIpAdr
         IpAddress,
      er1646v2Lan3FGPppOEIpNetm
         IpAddress,
      er1646v2Lan3FGPppOEIpSNetName
         INTEGER,
      er1646v2Lan3FGPppOEIpSNetCust
         DisplayString,
      er1646v2Lan3FGPppOEIpRem
         IpAddress,
      er1646v2Lan3FGPppOEIpUnnumbered
         DisplayString,
      er1646v2Lan3FGPppOEIpGwPref
         Integer32,
      er1646v2Lan3FGPppOEIpRsn
         INTEGER,
      er1646v2Lan3FGPppOEIpMtu
         Integer32,
      er1646v2Lan3FGPppOEIpMssAdjust
         INTEGER,
      er1646v2Lan3FGPppOEIpRipMetric
         Integer32,
      er1646v2Lan3FGPppOEIpRipMetricOut
         Integer32,
      er1646v2Lan3FGPppOEIpRipMode
         INTEGER,
      er1646v2Lan3FGPppOEIpRipTxVer
         INTEGER,
      er1646v2Lan3FGPppOEIpRipRxVer
         INTEGER,
      er1646v2Lan3FGPppOEIpRipSplitH
         INTEGER,
      er1646v2Lan3FGPppOEIpRipAuth
         INTEGER,
      er1646v2Lan3FGPppOEIpRipFilter
         DisplayString,
      er1646v2Lan3FGPppOEIpRipFilterIn
         DisplayString,
      er1646v2Lan3FGPppOEIpRipClearNextHop
         INTEGER,
      er1646v2Lan3FGPppOEIpAccPol
         DisplayString,
      er1646v2Lan3FGPppOEIpAB
         DisplayString,
      er1646v2Lan3FGPppOEIpMA
         INTEGER,
      er1646v2Lan3FGPppOEIpMF
         Integer32,
      er1646v2Lan3FGPppOEIpDB
         INTEGER,
      er1646v2Lan3FGPppOEIpIR
         INTEGER,
      er1646v2Lan3FGPppOEIpIgmp
         INTEGER,
      er1646v2Lan3FGPppOEIpNN
         DisplayString,
      er1646v2Lan3FGPppOEIpPimMode
         INTEGER,
      er1646v2Lan3FGPppOEIpPimDrPriority
         Counter32,
      er1646v2Lan3FGPppOEIpPimHelloTime
         TimeTicks,
      er1646v2Lan3FGPppOEIpPimPropagationDelay
         TimeTicks,
      er1646v2Lan3FGPppOEIpPimOverrideInterval
         TimeTicks,
      er1646v2Lan3FGPppOEIpPimBsrBorder
         INTEGER,
      er1646v2Lan3FGPppOEIpPimTtlThreshold
         Integer32,
      er1646v2Lan3FGPppOEIpIMNetworkUnreachable
         INTEGER,
      er1646v2Lan3FGPppOEIpIMHostUnreachable
         INTEGER,
      er1646v2Lan3FGPppOEIpIMProtocolUnreachable
         INTEGER,
      er1646v2Lan3FGPppOEIpIMPortUnreachable
         INTEGER,
      er1646v2Lan3FGPppOEIpIMMtuExceeded
         INTEGER,
      er1646v2Lan3FGPppOEIpIMAdminProhibited
         INTEGER,
      er1646v2Lan3FGPppOEIpIMTtlExceeded
         INTEGER,
      er1646v2Lan3FGPppOEIpIMRedirect
         INTEGER,
      er1646v2Lan3FGPppOEIpV6VrfRouter
         DisplayString,
      er1646v2Lan3FGPppOEIpV6AddrAutoConfigNrDupAddrDetects
         Integer32,
      er1646v2Lan3FGPppOEIpV6AddrAutoConfigAcceptRa
         INTEGER,
      er1646v2Lan3FGPppOEIpV6AddrAutoConfigAcceptRaRdnss
         INTEGER,
      er1646v2Lan3FGPppOEIpV6AddrAutoConfigAcceptRaDnssl
         INTEGER,
      er1646v2Lan3FGPppOEIpV6DefaultRoute
         INTEGER,
      er1646v2Lan3FGPppOEIpV6RaSend
         INTEGER,
      er1646v2Lan3FGPppOEIpV6RaMinInterval
         TimeTicks,
      er1646v2Lan3FGPppOEIpV6RaMaxInterval
         TimeTicks,
      er1646v2Lan3FGPppOEIpV6RaManagedFlag
         INTEGER,
      er1646v2Lan3FGPppOEIpV6RaOtherConfFlag
         INTEGER,
      er1646v2Lan3FGPppOEIpV6RaLinkMtu
         Integer32,
      er1646v2Lan3FGPppOEIpV6RaReachableTime
         TimeTicks,
      er1646v2Lan3FGPppOEIpV6RaRetransmitTime
         TimeTicks,
      er1646v2Lan3FGPppOEIpV6RaHopLimit
         Integer32,
      er1646v2Lan3FGPppOEIpV6RaDefaultLifeTime
         TimeTicks,
      er1646v2Lan3FGPppOEIpV6RaDnsOptionsRdnssLifeTime
         TimeTicks,
      er1646v2Lan3FGPppOEIpV6RaDnsOptionsRdnssImportServers
         INTEGER,
      er1646v2Lan3FGPppOEIpV6RaDnsOptionsDnsslLifeTime
         TimeTicks,
      er1646v2Lan3FGPppOEIpV6RaDnsOptionsDnsslImportDomains
         INTEGER,
      er1646v2Lan3FGPppOEIpV6RsSend
         INTEGER,
      er1646v2Lan3FGPppOEIpV6RsMaxRandomDelay
         TimeTicks,
      er1646v2Lan3FGPppOEIpV6RsInterval
         TimeTicks,
      er1646v2Lan3FGPppOEIpV6RsMaxSolicitations
         Integer32,
      er1646v2Lan3FGPppOEIpV6TrafficPolicyInbound
         DisplayString,
      er1646v2Lan3FGPppOEIpV6TrafficPolicyOutbound
         DisplayString,
      er1646v2Lan3FGPppOEIpV6FirewallZone
         DisplayString,
      er1646v2Lan3FGPppOEIpV6DhcpClientAddrAC
         INTEGER,
      er1646v2Lan3FGPppOEIpV6DhcpClientPrDelMode
         INTEGER,
      er1646v2Lan3FGPppOEIpV6DhcpClientPrDelPool
         DisplayString,
      er1646v2Lan3FGPppOEIpV6DhcpClientPrDelPdExclOpt
         INTEGER,
      er1646v2Lan3FGPppOEIpV6DhcpClientDnsServerPref
         Integer32,
      er1646v2Lan3FGPppOEIpV6DhcpClientRapidCommit
         INTEGER,
      er1646v2Lan3FGPppOEIpV6DhcpClientTimersSolTimeOut
         TimeTicks,
      er1646v2Lan3FGPppOEIpV6DhcpClientTimersSolMaxRt
         TimeTicks,
      er1646v2Lan3FGPppOEIpV6DhcpClientTimersInfoRefresh
         TimeTicks,
      er1646v2Lan3FGPppOEIpV6DhcpServerMode
         INTEGER,
      er1646v2Lan3FGPppOEIpV6DhcpServerPreference
         Integer32,
      er1646v2Lan3FGPppOEIpV6DhcpServerPool
         DisplayString,
      er1646v2Lan3FGPppOEIpV6DhcpServerRapidCommit
         INTEGER,
      er1646v2Lan3FGPppOEIpV6DhcpServerTimersInfoRefresh
         TimeTicks,
      er1646v2Lan3FGPppOEIpV6DhcpRelayMode
         INTEGER,
      er1646v2Lan3FGPppOEIpV6SendRedirect
         INTEGER,
      er1646v2Lan3FGPppOEIpV6LinkMtu
         Integer32,
      er1646v2Lan3FGPppOEIpV6InterfaceId
         OCTET STRING,
      er1646v2Lan3FGPppOEIpV6MF
         Integer32,
      er1646v2Lan3FGPppOEIpV6IcmpMessagesNoRoute
         INTEGER,
      er1646v2Lan3FGPppOEIpV6IcmpMessagesBeyondScope
         INTEGER,
      er1646v2Lan3FGPppOEIpV6IcmpMessagesAddressUnreachable
         INTEGER,
      er1646v2Lan3FGPppOEIpV6IcmpMessagesPortUnreachable
         INTEGER,
      er1646v2Lan3FGPppOEIpV6IcmpMessagesPacketTooBig
         INTEGER,
      er1646v2Lan3FGPppOEIpV6IcmpMessagesHopLimitExceeded
         INTEGER,
      er1646v2Lan3FGPppOEIpV6IcmpMessagesFragTimeExceeded
         INTEGER,
      er1646v2Lan3FGPppOEIpV6IcmpMessagesHeaderFieldErr
         INTEGER,
      er1646v2Lan3FGPppOEIpV6IcmpMessagesOptionUnrecognized
         INTEGER,
      er1646v2Lan3FGPppOEIpV6IcmpMessagesRedirect
         INTEGER,
      er1646v2Lan3FGPppOEPppLnkMOperation
         INTEGER,
      er1646v2Lan3FGPppOEPppLnkMInterval
         TimeTicks,
      er1646v2Lan3FGPppOEPppLnkMRepTimeOut
         TimeTicks,
      er1646v2Lan3FGPppOEPppLnkMFailsPrmt
         Integer32,
      er1646v2Lan3FGPppOEPppAuthentication
         INTEGER,
      er1646v2Lan3FGPppOEPppAuthenPeriod
         TimeTicks,
      er1646v2Lan3FGPppOEPppSessionName
         DisplayString,
      er1646v2Lan3FGPppOEPppSessionSecret
         DisplayString,
      er1646v2Lan3FGPppOEPppEncModeSessionSecret
         INTEGER,
      er1646v2Lan3FGPppOEPppEncSessionSecret
         DisplayString,
      er1646v2Lan3FGPppOEPppServiceName
         DisplayString
      }

er1646v2Lan3FGPppOEActions OBJECT-TYPE
   SYNTAX      VariableLengthTableActions
   MAX-ACCESS  read-write
   STATUS      current
   DESCRIPTION
      "By way of this field, some manipulations
       on this table may be performed."
   ::= {er1646v2Lan3FGPppOEEntry 2}

er1646v2Lan3FGPppOETableIx OBJECT-TYPE
   SYNTAX      TableIndex
   MAX-ACCESS  not-accessible
   STATUS      current
   DESCRIPTION
      ""
   ::= {er1646v2Lan3FGPppOEEntry 11}

er1646v2Lan3FGPppOEName OBJECT-TYPE
   SYNTAX      DisplayString
   MAX-ACCESS  read-write
   STATUS      current
   DESCRIPTION
      "Path: ethernet3.editConf.pppoEClient.name"
   ::= {er1646v2Lan3FGPppOEEntry 16777216}

er1646v2Lan3FGPppOERemark OBJECT-TYPE
   SYNTAX      DisplayString
   MAX-ACCESS  read-write
   STATUS      current
   DESCRIPTION
      "Path: ethernet3.editConf.pppoEClient.remark"
   ::= {er1646v2Lan3FGPppOEEntry 1157627904}

er1646v2Lan3FGPppOEAdminStatus OBJECT-TYPE
   SYNTAX      INTEGER
               {
               up (1),
               down (2)
               }
   MAX-ACCESS  read-write
   STATUS      current
   DESCRIPTION
      "Path: ethernet3.editConf.pppoEClient.adminStatus

       Possibilities:
               up   (1)
               down   (2)"
   ::= {er1646v2Lan3FGPppOEEntry 33554432}

er1646v2Lan3FGPppOEMode OBJECT-TYPE
   SYNTAX      INTEGER
               {
               routing (1),
               multilink (8),
               ipV6 (16),
               ipV6ipV4 (17)
               }
   MAX-ACCESS  read-write
   STATUS      current
   DESCRIPTION
      "Path: ethernet3.editConf.pppoEClient.mode

       Possibilities:
               routing   (1)
               multilink   (8)
               ipV6   (16)
               ipV6/ipV4   (17)"
   ::= {er1646v2Lan3FGPppOEEntry 67108864}

er1646v2Lan3FGPppOEIpVrfRouter OBJECT-TYPE
   SYNTAX      DisplayString
   MAX-ACCESS  read-write
   STATUS      current
   DESCRIPTION
      "Path: ethernet3.editConf.pppoEClient.ip.vrfRouter"
   ::= {er1646v2Lan3FGPppOEEntry 53215232}

er1646v2Lan3FGPppOEIpAdr OBJECT-TYPE
   SYNTAX      IpAddress
   MAX-ACCESS  read-write
   STATUS      current
   DESCRIPTION
      "Path: ethernet3.editConf.pppoEClient.ip.address"
   ::= {er1646v2Lan3FGPppOEEntry 58261504}

er1646v2Lan3FGPppOEIpNetm OBJECT-TYPE
   SYNTAX      IpAddress
   MAX-ACCESS  read-write
   STATUS      current
   DESCRIPTION
      "Path: ethernet3.editConf.pppoEClient.ip.netMask"
   ::= {er1646v2Lan3FGPppOEEntry 58392576}

er1646v2Lan3FGPppOEIpSNetName OBJECT-TYPE
   SYNTAX      INTEGER
               {
               slOPTg (0),
               corp (2),
               dmz (3),
               internet (1)
               }
   MAX-ACCESS  read-write
   STATUS      current
   DESCRIPTION
      "Path: ethernet3.editConf.pppoEClient.ip.sNet.name

       Possibilities:
               <OPT>   (0)
               corp   (2)
               dmz   (3)
               internet   (1)"
   ::= {er1646v2Lan3FGPppOEEntry 53674240}

er1646v2Lan3FGPppOEIpSNetCust OBJECT-TYPE
   SYNTAX      DisplayString
   MAX-ACCESS  read-write
   STATUS      current
   DESCRIPTION
      "Path: ethernet3.editConf.pppoEClient.ip.sNet.custom"
   ::= {er1646v2Lan3FGPppOEEntry 53674496}

er1646v2Lan3FGPppOEIpRem OBJECT-TYPE
   SYNTAX      IpAddress
   MAX-ACCESS  read-write
   STATUS      current
   DESCRIPTION
      "Path: ethernet3.editConf.pppoEClient.ip.remote"
   ::= {er1646v2Lan3FGPppOEEntry 58458112}

er1646v2Lan3FGPppOEIpUnnumbered OBJECT-TYPE
   SYNTAX      DisplayString
   MAX-ACCESS  read-write
   STATUS      current
   DESCRIPTION
      "Path: ethernet3.editConf.pppoEClient.ip.unnumbered"
   ::= {er1646v2Lan3FGPppOEEntry 52625408}

er1646v2Lan3FGPppOEIpGwPref OBJECT-TYPE
   SYNTAX      Integer32
   MAX-ACCESS  read-write
   STATUS      current
   DESCRIPTION
      "Path: ethernet3.editConf.pppoEClient.ip.gatewayPreference"
   ::= {er1646v2Lan3FGPppOEEntry 52690944}

er1646v2Lan3FGPppOEIpRsn OBJECT-TYPE
   SYNTAX      INTEGER
               {
               disabled (0),
               enabled (1)
               }
   MAX-ACCESS  read-write
   STATUS      current
   DESCRIPTION
      "Path: ethernet3.editConf.pppoEClient.ip.requestSubnet

       Possibilities:
               disabled   (0)
               enabled   (1)"
   ::= {er1646v2Lan3FGPppOEEntry 56688640}

er1646v2Lan3FGPppOEIpMtu OBJECT-TYPE
   SYNTAX      Integer32
   MAX-ACCESS  read-write
   STATUS      current
   DESCRIPTION
      "Path: ethernet3.editConf.pppoEClient.ip.mtu"
   ::= {er1646v2Lan3FGPppOEEntry 52953088}

er1646v2Lan3FGPppOEIpMssAdjust OBJECT-TYPE
   SYNTAX      INTEGER
               {
               disabled (0),
               auto (65536)
               }
   MAX-ACCESS  read-write
   STATUS      current
   DESCRIPTION
      "Path: ethernet3.editConf.pppoEClient.ip.mssAdjust

       Possibilities:
               disabled   (0)
               auto   (65536)"
   ::= {er1646v2Lan3FGPppOEEntry 53280768}

er1646v2Lan3FGPppOEIpRipMetric OBJECT-TYPE
   SYNTAX      Integer32
   MAX-ACCESS  read-write
   STATUS      current
   DESCRIPTION
      "Path: ethernet3.editConf.pppoEClient.ip.rip.metric"
   ::= {er1646v2Lan3FGPppOEEntry 51712768}

er1646v2Lan3FGPppOEIpRipMetricOut OBJECT-TYPE
   SYNTAX      Integer32
   MAX-ACCESS  read-write
   STATUS      current
   DESCRIPTION
      "Path: ethernet3.editConf.pppoEClient.ip.rip.metricOut"
   ::= {er1646v2Lan3FGPppOEEntry 51713024}

er1646v2Lan3FGPppOEIpRipMode OBJECT-TYPE
   SYNTAX      INTEGER
               {
               disabled (0),
               passive (1),
               active (2)
               }
   MAX-ACCESS  read-write
   STATUS      current
   DESCRIPTION
      "Path: ethernet3.editConf.pppoEClient.ip.rip.mode

       Possibilities:
               disabled   (0)
               passive   (1)
               active   (2)"
   ::= {er1646v2Lan3FGPppOEEntry 51713280}

er1646v2Lan3FGPppOEIpRipTxVer OBJECT-TYPE
   SYNTAX      INTEGER
               {
               rip1 (0),
               rip2 (1),
               rip1mcompatible (2)
               }
   MAX-ACCESS  read-write
   STATUS      current
   DESCRIPTION
      "Path: ethernet3.editConf.pppoEClient.ip.rip.txVersion

       Possibilities:
               rip1   (0)
               rip2   (1)
               rip1-compatible   (2)"
   ::= {er1646v2Lan3FGPppOEEntry 51716864}

er1646v2Lan3FGPppOEIpRipRxVer OBJECT-TYPE
   SYNTAX      INTEGER
               {
               rip1only (0),
               rip2only (1),
               rip12 (2)
               }
   MAX-ACCESS  read-write
   STATUS      current
   DESCRIPTION
      "Path: ethernet3.editConf.pppoEClient.ip.rip.rxVersion

       Possibilities:
               rip1only   (0)
               rip2only   (1)
               rip1&2   (2)"
   ::= {er1646v2Lan3FGPppOEEntry 51717120}

er1646v2Lan3FGPppOEIpRipSplitH OBJECT-TYPE
   SYNTAX      INTEGER
               {
               disabled (0),
               enabled (1),
               poisonedReverse (2)
               }
   MAX-ACCESS  read-write
   STATUS      current
   DESCRIPTION
      "Path: ethernet3.editConf.pppoEClient.ip.rip.splitHorizon

       Possibilities:
               disabled   (0)
               enabled   (1)
               poisonedReverse   (2)"
   ::= {er1646v2Lan3FGPppOEEntry 51713792}

er1646v2Lan3FGPppOEIpRipAuth OBJECT-TYPE
   SYNTAX      INTEGER
               {
               disabled (0),
               texts (1),
               md5 (2)
               }
   MAX-ACCESS  read-write
   STATUS      current
   DESCRIPTION
      "Path: ethernet3.editConf.pppoEClient.ip.rip.authentication

       Possibilities:
               disabled   (0)
               text    (1)
               md5   (2)"
   ::= {er1646v2Lan3FGPppOEEntry 51712512}

er1646v2Lan3FGPppOEIpRipFilter OBJECT-TYPE
   SYNTAX      DisplayString
   MAX-ACCESS  read-write
   STATUS      current
   DESCRIPTION
      "Path: ethernet3.editConf.pppoEClient.ip.rip.filter"
   ::= {er1646v2Lan3FGPppOEEntry 51716096}

er1646v2Lan3FGPppOEIpRipFilterIn OBJECT-TYPE
   SYNTAX      DisplayString
   MAX-ACCESS  read-write
   STATUS      current
   DESCRIPTION
      "Path: ethernet3.editConf.pppoEClient.ip.rip.filterIn"
   ::= {er1646v2Lan3FGPppOEEntry 51716352}

er1646v2Lan3FGPppOEIpRipClearNextHop OBJECT-TYPE
   SYNTAX      INTEGER
               {
               disabled (0),
               enabled (1)
               }
   MAX-ACCESS  read-write
   STATUS      current
   DESCRIPTION
      "Path: ethernet3.editConf.pppoEClient.ip.rip.clearNextHop

       Possibilities:
               disabled   (0)
               enabled   (1)"
   ::= {er1646v2Lan3FGPppOEEntry 51708416}

er1646v2Lan3FGPppOEIpAccPol OBJECT-TYPE
   SYNTAX      DisplayString
   MAX-ACCESS  read-write
   STATUS      current
   DESCRIPTION
      "Path: ethernet3.editConf.pppoEClient.ip.accessPolicy"
   ::= {er1646v2Lan3FGPppOEEntry 53084160}

er1646v2Lan3FGPppOEIpAB OBJECT-TYPE
   SYNTAX      DisplayString
   MAX-ACCESS  read-write
   STATUS      current
   DESCRIPTION
      "Path: ethernet3.editConf.pppoEClient.ip.trafficPolicy"
   ::= {er1646v2Lan3FGPppOEEntry 51249152}

er1646v2Lan3FGPppOEIpMA OBJECT-TYPE
   SYNTAX      INTEGER
               {
               disabled (0),
               enabled (1)
               }
   MAX-ACCESS  read-write
   STATUS      current
   DESCRIPTION
      "Path: ethernet3.editConf.pppoEClient.ip.mgmtAccess

       Possibilities:
               disabled   (0)
               enabled   (1)"
   ::= {er1646v2Lan3FGPppOEEntry 51380224}

er1646v2Lan3FGPppOEIpMF OBJECT-TYPE
   SYNTAX      Integer32
   MAX-ACCESS  read-write
   STATUS      current
   DESCRIPTION
      "Path: ethernet3.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2Lan3FGPppOEEntry 51445760}

er1646v2Lan3FGPppOEIpDB OBJECT-TYPE
   SYNTAX      INTEGER
               {
               disabled (0),
               enabled (1)
               }
   MAX-ACCESS  read-write
   STATUS      current
   DESCRIPTION
      "Path: ethernet3.editConf.pppoEClient.ip.directedBroadcasts

       Possibilities:
               disabled   (0)
               enabled   (1)"
   ::= {er1646v2Lan3FGPppOEEntry 51773440}

er1646v2Lan3FGPppOEIpIR OBJECT-TYPE
   SYNTAX      INTEGER
               {
               disabled (0),
               enabled (1)
               }
   MAX-ACCESS  read-write
   STATUS      current
   DESCRIPTION
      "Path: ethernet3.editConf.pppoEClient.ip.icmpRedirects

       Possibilities:
               disabled   (0)
               enabled   (1)"
   ::= {er1646v2Lan3FGPppOEEntry 52035584}

er1646v2Lan3FGPppOEIpIgmp OBJECT-TYPE
   SYNTAX      INTEGER
               {
               disabled (0),
               proxy (1),
               router (2),
               v3Router (5)
               }
   MAX-ACCESS  read-write
   STATUS      current
   DESCRIPTION
      "Path: ethernet3.editConf.pppoEClient.ip.igmp

       Possibilities:
               disabled   (0)
               proxy   (1)
               router   (2)
               v3Router   (5)"
   ::= {er1646v2Lan3FGPppOEEntry 52428800}

er1646v2Lan3FGPppOEIpNN OBJECT-TYPE
   SYNTAX      DisplayString
   MAX-ACCESS  read-write
   STATUS      current
   DESCRIPTION
      "Path: ethernet3.editConf.pppoEClient.ip.nat"
   ::= {er1646v2Lan3FGPppOEEntry 52101120}

er1646v2Lan3FGPppOEIpPimMode OBJECT-TYPE
   SYNTAX      INTEGER
               {
               disabled (0),
               sparse (1),
               passive (2)
               }
   MAX-ACCESS  read-write
   STATUS      current
   DESCRIPTION
      "Path: ethernet3.editConf.pppoEClient.ip.pim.mode

       Possibilities:
               disabled   (0)
               sparse   (1)
               passive   (2)"
   ::= {er1646v2Lan3FGPppOEEntry 53346560}

er1646v2Lan3FGPppOEIpPimDrPriority OBJECT-TYPE
   SYNTAX      Counter32
   MAX-ACCESS  read-write
   STATUS      current
   DESCRIPTION
      "Path: ethernet3.editConf.pppoEClient.ip.pim.drPriority

       32 bit unsigned wrappable counter."
   ::= {er1646v2Lan3FGPppOEEntry 53346816}

er1646v2Lan3FGPppOEIpPimHelloTime OBJECT-TYPE
   SYNTAX      TimeTicks
   MAX-ACCESS  read-write
   STATUS      current
   DESCRIPTION
      "Path: ethernet3.editConf.pppoEClient.ip.pim.helloTime

       Time in centi-second."
   ::= {er1646v2Lan3FGPppOEEntry 53347072}

er1646v2Lan3FGPppOEIpPimPropagationDelay OBJECT-TYPE
   SYNTAX      TimeTicks
   MAX-ACCESS  read-write
   STATUS      current
   DESCRIPTION
      "Path: ethernet3.editConf.pppoEClient.ip.pim.propagationDelay

       Time in centi-second."
   ::= {er1646v2Lan3FGPppOEEntry 53347328}

er1646v2Lan3FGPppOEIpPimOverrideInterval OBJECT-TYPE
   SYNTAX      TimeTicks
   MAX-ACCESS  read-write
   STATUS      current
   DESCRIPTION
      "Path: ethernet3.editConf.pppoEClient.ip.pim.overrideInterval

       Time in centi-second."
   ::= {er1646v2Lan3FGPppOEEntry 53347584}

er1646v2Lan3FGPppOEIpPimBsrBorder OBJECT-TYPE
   SYNTAX      INTEGER
               {
               disabled (0),
               enabled (1)
               }
   MAX-ACCESS  read-write
   STATUS      current
   DESCRIPTION
      "Path: ethernet3.editConf.pppoEClient.ip.pim.bsrBorder

       Possibilities:
               disabled   (0)
               enabled   (1)"
   ::= {er1646v2Lan3FGPppOEEntry 53347840}

er1646v2Lan3FGPppOEIpPimTtlThreshold OBJECT-TYPE
   SYNTAX      Integer32
   MAX-ACCESS  read-write
   STATUS      current
   DESCRIPTION
      "Path: ethernet3.editConf.pppoEClient.ip.pim.ttlThreshold"
   ::= {er1646v2Lan3FGPppOEEntry 53348096}

er1646v2Lan3FGPppOEIpIMNetworkUnreachable OBJECT-TYPE
   SYNTAX      INTEGER
               {
               disabled (0),
               enabled (1)
               }
   MAX-ACCESS  read-write
   STATUS      current
   DESCRIPTION
      "Path: ethernet3.editConf.pppoEClient.ip.icmpMessages.networkUnreachable

       Possibilities:
               disabled   (0)
               enabled   (1)"
   ::= {er1646v2Lan3FGPppOEEntry 53412096}

er1646v2Lan3FGPppOEIpIMHostUnreachable OBJECT-TYPE
   SYNTAX      INTEGER
               {
               disabled (0),
               enabled (1)
               }
   MAX-ACCESS  read-write
   STATUS      current
   DESCRIPTION
      "Path: ethernet3.editConf.pppoEClient.ip.icmpMessages.hostUnreachable

       Possibilities:
               disabled   (0)
               enabled   (1)"
   ::= {er1646v2Lan3FGPppOEEntry 53412352}

er1646v2Lan3FGPppOEIpIMProtocolUnreachable OBJECT-TYPE
   SYNTAX      INTEGER
               {
               disabled (0),
               enabled (1)
               }
   MAX-ACCESS  read-write
   STATUS      current
   DESCRIPTION
      "Path: ethernet3.editConf.pppoEClient.ip.icmpMessages.protocolUnreachable

       Possibilities:
               disabled   (0)
               enabled   (1)"
   ::= {er1646v2Lan3FGPppOEEntry 53412608}

er1646v2Lan3FGPppOEIpIMPortUnreachable OBJECT-TYPE
   SYNTAX      INTEGER
               {
               disabled (0),
               enabled (1)
               }
   MAX-ACCESS  read-write
   STATUS      current
   DESCRIPTION
      "Path: ethernet3.editConf.pppoEClient.ip.icmpMessages.portUnreachable

       Possibilities:
               disabled   (0)
               enabled   (1)"
   ::= {er1646v2Lan3FGPppOEEntry 53412864}

er1646v2Lan3FGPppOEIpIMMtuExceeded OBJECT-TYPE
   SYNTAX      INTEGER
               {
               disabled (0),
               enabled (1)
               }
   MAX-ACCESS  read-write
   STATUS      current
   DESCRIPTION
      "Path: ethernet3.editConf.pppoEClient.ip.icmpMessages.mtuExceeded

       Possibilities:
               disabled   (0)
               enabled   (1)"
   ::= {er1646v2Lan3FGPppOEEntry 53413120}

er1646v2Lan3FGPppOEIpIMAdminProhibited OBJECT-TYPE
   SYNTAX      INTEGER
               {
               disabled (0),
               enabled (1)
               }
   MAX-ACCESS  read-write
   STATUS      current
   DESCRIPTION
      "Path: ethernet3.editConf.pppoEClient.ip.icmpMessages.adminProhibited

       Possibilities:
               disabled   (0)
               enabled   (1)"
   ::= {er1646v2Lan3FGPppOEEntry 53413376}

er1646v2Lan3FGPppOEIpIMTtlExceeded OBJECT-TYPE
   SYNTAX      INTEGER
               {
               disabled (0),
               enabled (1)
               }
   MAX-ACCESS  read-write
   STATUS      current
   DESCRIPTION
      "Path: ethernet3.editConf.pppoEClient.ip.icmpMessages.ttlExceeded

       Possibilities:
               disabled   (0)
               enabled   (1)"
   ::= {er1646v2Lan3FGPppOEEntry 53413632}

er1646v2Lan3FGPppOEIpIMRedirect OBJECT-TYPE
   SYNTAX      INTEGER
               {
               disabled (0),
               enabled (1)
               }
   MAX-ACCESS  read-write
   STATUS      current
   DESCRIPTION
      "Path: ethernet3.editConf.pppoEClient.ip.icmpMessages.redirect

       Possibilities:
               disabled   (0)
               enabled   (1)"
   ::= {er1646v2Lan3FGPppOEEntry 53413888}

er1646v2Lan3FGPppOEIpV6VrfRouter OBJECT-TYPE
   SYNTAX      DisplayString
   MAX-ACCESS  read-write
   STATUS      current
   DESCRIPTION
      "Path: ethernet3.editConf.pppoEClient.ipV6.vrfRouter"
   ::= {er1646v2Lan3FGPppOEEntry 704708608}

er1646v2Lan3FGPppOEIpV6AddrAutoConfigNrDupAddrDetects OBJECT-TYPE
   SYNTAX      Integer32
   MAX-ACCESS  read-write
   STATUS      current
   DESCRIPTION
      "Path: ethernet3.editConf.pppoEClient.ipV6.addrAutoConfig.nrDupAddrDetects"
   ::= {er1646v2Lan3FGPppOEEntry 704905472}

er1646v2Lan3FGPppOEIpV6AddrAutoConfigAcceptRa OBJECT-TYPE
   SYNTAX      INTEGER
               {
               disabled (0),
               enabled (1)
               }
   MAX-ACCESS  read-write
   STATUS      current
   DESCRIPTION
      "Path: ethernet3.editConf.pppoEClient.ipV6.addrAutoConfig.acceptRa

       Possibilities:
               disabled   (0)
               enabled   (1)"
   ::= {er1646v2Lan3FGPppOEEntry 704905728}

er1646v2Lan3FGPppOEIpV6AddrAutoConfigAcceptRaRdnss OBJECT-TYPE
   SYNTAX      INTEGER
               {
               disabled (0),
               enabled (1)
               }
   MAX-ACCESS  read-write
   STATUS      current
   DESCRIPTION
      "Path: ethernet3.editConf.pppoEClient.ipV6.addrAutoConfig.acceptRaRdnss

       Possibilities:
               disabled   (0)
               enabled   (1)"
   ::= {er1646v2Lan3FGPppOEEntry 704905984}

er1646v2Lan3FGPppOEIpV6AddrAutoConfigAcceptRaDnssl OBJECT-TYPE
   SYNTAX      INTEGER
               {
               disabled (0),
               enabled (1)
               }
   MAX-ACCESS  read-write
   STATUS      current
   DESCRIPTION
      "Path: ethernet3.editConf.pppoEClient.ipV6.addrAutoConfig.acceptRaDnssl

       Possibilities:
               disabled   (0)
               enabled   (1)"
   ::= {er1646v2Lan3FGPppOEEntry 704906240}

er1646v2Lan3FGPppOEIpV6DefaultRoute OBJECT-TYPE
   SYNTAX      INTEGER
               {
               disabled (0),
               enabled (1)
               }
   MAX-ACCESS  read-write
   STATUS      current
   DESCRIPTION
      "Path: ethernet3.editConf.pppoEClient.ipV6.defaultRoute

       Possibilities:
               disabled   (0)
               enabled   (1)"
   ::= {er1646v2Lan3FGPppOEEntry 704970752}

er1646v2Lan3FGPppOEIpV6RaSend OBJECT-TYPE
   SYNTAX      INTEGER
               {
               disabled (0),
               enabled (1)
               }
   MAX-ACCESS  read-write
   STATUS      current
   DESCRIPTION
      "Path: ethernet3.editConf.pppoEClient.ipV6.ra.send

       Possibilities:
               disabled   (0)
               enabled   (1)"
   ::= {er1646v2Lan3FGPppOEEntry 705036544}

er1646v2Lan3FGPppOEIpV6RaMinInterval OBJECT-TYPE
   SYNTAX      TimeTicks
   MAX-ACCESS  read-write
   STATUS      current
   DESCRIPTION
      "Path: ethernet3.editConf.pppoEClient.ipV6.ra.minInterval

       Time in centi-second."
   ::= {er1646v2Lan3FGPppOEEntry 705036800}

er1646v2Lan3FGPppOEIpV6RaMaxInterval OBJECT-TYPE
   SYNTAX      TimeTicks
   MAX-ACCESS  read-write
   STATUS      current
   DESCRIPTION
      "Path: ethernet3.editConf.pppoEClient.ipV6.ra.maxInterval

       Time in centi-second."
   ::= {er1646v2Lan3FGPppOEEntry 705037056}

er1646v2Lan3FGPppOEIpV6RaManagedFlag OBJECT-TYPE
   SYNTAX      INTEGER
               {
               disabled (0),
               enabled (1)
               }
   MAX-ACCESS  read-write
   STATUS      current
   DESCRIPTION
      "Path: ethernet3.editConf.pppoEClient.ipV6.ra.managedFlag

       Possibilities:
               disabled   (0)
               enabled   (1)"
   ::= {er1646v2Lan3FGPppOEEntry 705037312}

er1646v2Lan3FGPppOEIpV6RaOtherConfFlag OBJECT-TYPE
   SYNTAX      INTEGER
               {
               disabled (0),
               enabled (1)
               }
   MAX-ACCESS  read-write
   STATUS      current
   DESCRIPTION
      "Path: ethernet3.editConf.pppoEClient.ipV6.ra.otherConfFlag

       Possibilities:
               disabled   (0)
               enabled   (1)"
   ::= {er1646v2Lan3FGPppOEEntry 705037568}

er1646v2Lan3FGPppOEIpV6RaLinkMtu OBJECT-TYPE
   SYNTAX      Integer32
   MAX-ACCESS  read-write
   STATUS      current
   DESCRIPTION
      "Path: ethernet3.editConf.pppoEClient.ipV6.ra.linkMtu"
   ::= {er1646v2Lan3FGPppOEEntry 705037824}

er1646v2Lan3FGPppOEIpV6RaReachableTime OBJECT-TYPE
   SYNTAX      TimeTicks
   MAX-ACCESS  read-write
   STATUS      current
   DESCRIPTION
      "Path: ethernet3.editConf.pppoEClient.ipV6.ra.reachableTime

       Time in centi-second."
   ::= {er1646v2Lan3FGPppOEEntry 705038080}

er1646v2Lan3FGPppOEIpV6RaRetransmitTime OBJECT-TYPE
   SYNTAX      TimeTicks
   MAX-ACCESS  read-write
   STATUS      current
   DESCRIPTION
      "Path: ethernet3.editConf.pppoEClient.ipV6.ra.retransmitTime

       Time in centi-second."
   ::= {er1646v2Lan3FGPppOEEntry 705038336}

er1646v2Lan3FGPppOEIpV6RaHopLimit OBJECT-TYPE
   SYNTAX      Integer32
   MAX-ACCESS  read-write
   STATUS      current
   DESCRIPTION
      "Path: ethernet3.editConf.pppoEClient.ipV6.ra.hopLimit"
   ::= {er1646v2Lan3FGPppOEEntry 705038592}

er1646v2Lan3FGPppOEIpV6RaDefaultLifeTime OBJECT-TYPE
   SYNTAX      TimeTicks
   MAX-ACCESS  read-write
   STATUS      current
   DESCRIPTION
      "Path: ethernet3.editConf.pppoEClient.ipV6.ra.defaultLifeTime

       Time in centi-second."
   ::= {er1646v2Lan3FGPppOEEntry 705038848}

er1646v2Lan3FGPppOEIpV6RaDnsOptionsRdnssLifeTime OBJECT-TYPE
   SYNTAX      TimeTicks
   MAX-ACCESS  read-write
   STATUS      current
   DESCRIPTION
      "Path: ethernet3.editConf.pppoEClient.ipV6.ra.dnsOptions.rdnss.lifeTime

       Time in centi-second."
   ::= {er1646v2Lan3FGPppOEEntry 705039140}

er1646v2Lan3FGPppOEIpV6RaDnsOptionsRdnssImportServers OBJECT-TYPE
   SYNTAX      INTEGER
               {
               disabled (0),
               enabled (1)
               }
   MAX-ACCESS  read-write
   STATUS      current
   DESCRIPTION
      "Path: ethernet3.editConf.pppoEClient.ipV6.ra.dnsOptions.rdnss.importServers

       Possibilities:
               disabled   (0)
               enabled   (1)"
   ::= {er1646v2Lan3FGPppOEEntry 705039148}

er1646v2Lan3FGPppOEIpV6RaDnsOptionsDnsslLifeTime OBJECT-TYPE
   SYNTAX      TimeTicks
   MAX-ACCESS  read-write
   STATUS      current
   DESCRIPTION
      "Path: ethernet3.editConf.pppoEClient.ipV6.ra.dnsOptions.dnssl.lifeTime

       Time in centi-second."
   ::= {er1646v2Lan3FGPppOEEntry 705039172}

er1646v2Lan3FGPppOEIpV6RaDnsOptionsDnsslImportDomains OBJECT-TYPE
   SYNTAX      INTEGER
               {
               disabled (0),
               enabled (1)
               }
   MAX-ACCESS  read-write
   STATUS      current
   DESCRIPTION
      "Path: ethernet3.editConf.pppoEClient.ipV6.ra.dnsOptions.dnssl.importDomains

       Possibilities:
               disabled   (0)
               enabled   (1)"
   ::= {er1646v2Lan3FGPppOEEntry 705039180}

er1646v2Lan3FGPppOEIpV6RsSend OBJECT-TYPE
   SYNTAX      INTEGER
               {
               disabled (0),
               enabled (1)
               }
   MAX-ACCESS  read-write
   STATUS      current
   DESCRIPTION
      "Path: ethernet3.editConf.pppoEClient.ipV6.rs.send

       Possibilities:
               disabled   (0)
               enabled   (1)"
   ::= {er1646v2Lan3FGPppOEEntry 705954048}

er1646v2Lan3FGPppOEIpV6RsMaxRandomDelay OBJECT-TYPE
   SYNTAX      TimeTicks
   MAX-ACCESS  read-write
   STATUS      current
   DESCRIPTION
      "Path: ethernet3.editConf.pppoEClient.ipV6.rs.maxRandomDelay

       Time in centi-second."
   ::= {er1646v2Lan3FGPppOEEntry 705954304}

er1646v2Lan3FGPppOEIpV6RsInterval OBJECT-TYPE
   SYNTAX      TimeTicks
   MAX-ACCESS  read-write
   STATUS      current
   DESCRIPTION
      "Path: ethernet3.editConf.pppoEClient.ipV6.rs.interval

       Time in centi-second."
   ::= {er1646v2Lan3FGPppOEEntry 705954560}

er1646v2Lan3FGPppOEIpV6RsMaxSolicitations OBJECT-TYPE
   SYNTAX      Integer32
   MAX-ACCESS  read-write
   STATUS      current
   DESCRIPTION
      "Path: ethernet3.editConf.pppoEClient.ipV6.rs.maxSolicitations"
   ::= {er1646v2Lan3FGPppOEEntry 705954816}

er1646v2Lan3FGPppOEIpV6TrafficPolicyInbound OBJECT-TYPE
   SYNTAX      DisplayString
   MAX-ACCESS  read-write
   STATUS      current
   DESCRIPTION
      "Path: ethernet3.editConf.pppoEClient.ipV6.trafficPolicy.inbound"
   ::= {er1646v2Lan3FGPppOEEntry 705364224}

er1646v2Lan3FGPppOEIpV6TrafficPolicyOutbound OBJECT-TYPE
   SYNTAX      DisplayString
   MAX-ACCESS  read-write
   STATUS      current
   DESCRIPTION
      "Path: ethernet3.editConf.pppoEClient.ipV6.trafficPolicy.outbound"
   ::= {er1646v2Lan3FGPppOEEntry 705364480}

er1646v2Lan3FGPppOEIpV6FirewallZone OBJECT-TYPE
   SYNTAX      DisplayString
   MAX-ACCESS  read-write
   STATUS      current
   DESCRIPTION
      "Path: ethernet3.editConf.pppoEClient.ipV6.firewall.zone"
   ::= {er1646v2Lan3FGPppOEEntry 705429760}

er1646v2Lan3FGPppOEIpV6DhcpClientAddrAC OBJECT-TYPE
   SYNTAX      INTEGER
               {
               disabled (0),
               enabled (1)
               }
   MAX-ACCESS  read-write
   STATUS      current
   DESCRIPTION
      "Path: ethernet3.editConf.pppoEClient.ipV6.dhcp.client.addrAutoConfig

       Possibilities:
               disabled   (0)
               enabled   (1)"
   ::= {er1646v2Lan3FGPppOEEntry 705307648}

er1646v2Lan3FGPppOEIpV6DhcpClientPrDelMode OBJECT-TYPE
   SYNTAX      INTEGER
               {
               disabled (0),
               enabled (1)
               }
   MAX-ACCESS  read-write
   STATUS      current
   DESCRIPTION
      "Path: ethernet3.editConf.pppoEClient.ipV6.dhcp.client.pd.mode

       Possibilities:
               disabled   (0)
               enabled   (1)"
   ::= {er1646v2Lan3FGPppOEEntry 705308676}

er1646v2Lan3FGPppOEIpV6DhcpClientPrDelPool OBJECT-TYPE
   SYNTAX      DisplayString
   MAX-ACCESS  read-write
   STATUS      current
   DESCRIPTION
      "Path: ethernet3.editConf.pppoEClient.ipV6.dhcp.client.pd.pool"
   ::= {er1646v2Lan3FGPppOEEntry 705308680}

er1646v2Lan3FGPppOEIpV6DhcpClientPrDelPdExclOpt OBJECT-TYPE
   SYNTAX      INTEGER
               {
               disabled (0),
               enabled (1)
               }
   MAX-ACCESS  read-write
   STATUS      current
   DESCRIPTION
      "Path: ethernet3.editConf.pppoEClient.ipV6.dhcp.client.pd.pdExclOpt

       Possibilities:
               disabled   (0)
               enabled   (1)"
   ::= {er1646v2Lan3FGPppOEEntry 705308684}

er1646v2Lan3FGPppOEIpV6DhcpClientDnsServerPref OBJECT-TYPE
   SYNTAX      Integer32
   MAX-ACCESS  read-write
   STATUS      current
   DESCRIPTION
      "Path: ethernet3.editConf.pppoEClient.ipV6.dhcp.client.dns.serverPref"
   ::= {er1646v2Lan3FGPppOEEntry 705310724}

er1646v2Lan3FGPppOEIpV6DhcpClientRapidCommit OBJECT-TYPE
   SYNTAX      INTEGER
               {
               disabled (0),
               enabled (1)
               }
   MAX-ACCESS  read-write
   STATUS      current
   DESCRIPTION
      "Path: ethernet3.editConf.pppoEClient.ipV6.dhcp.client.rapidCommit

       Possibilities:
               disabled   (0)
               enabled   (1)"
   ::= {er1646v2Lan3FGPppOEEntry 705309696}

er1646v2Lan3FGPppOEIpV6DhcpClientTimersSolTimeOut OBJECT-TYPE
   SYNTAX      TimeTicks
   MAX-ACCESS  read-write
   STATUS      current
   DESCRIPTION
      "Path: ethernet3.editConf.pppoEClient.ipV6.dhcp.client.timers.solTimeOut

       Time in centi-second."
   ::= {er1646v2Lan3FGPppOEEntry 705311748}

er1646v2Lan3FGPppOEIpV6DhcpClientTimersSolMaxRt OBJECT-TYPE
   SYNTAX      TimeTicks
   MAX-ACCESS  read-write
   STATUS      current
   DESCRIPTION
      "Path: ethernet3.editConf.pppoEClient.ipV6.dhcp.client.timers.solMaxRt

       Time in centi-second."
   ::= {er1646v2Lan3FGPppOEEntry 705311752}

er1646v2Lan3FGPppOEIpV6DhcpClientTimersInfoRefresh OBJECT-TYPE
   SYNTAX      TimeTicks
   MAX-ACCESS  read-write
   STATUS      current
   DESCRIPTION
      "Path: ethernet3.editConf.pppoEClient.ipV6.dhcp.client.timers.infoRefresh

       Time in centi-second."
   ::= {er1646v2Lan3FGPppOEEntry 705311756}

er1646v2Lan3FGPppOEIpV6DhcpServerMode OBJECT-TYPE
   SYNTAX      INTEGER
               {
               disabled (0),
               enabled (1)
               }
   MAX-ACCESS  read-write
   STATUS      current
   DESCRIPTION
      "Path: ethernet3.editConf.pppoEClient.ipV6.dhcp.server.mode

       Possibilities:
               disabled   (0)
               enabled   (1)"
   ::= {er1646v2Lan3FGPppOEEntry 705315840}

er1646v2Lan3FGPppOEIpV6DhcpServerPreference OBJECT-TYPE
   SYNTAX      Integer32
   MAX-ACCESS  read-write
   STATUS      current
   DESCRIPTION
      "Path: ethernet3.editConf.pppoEClient.ipV6.dhcp.server.preference"
   ::= {er1646v2Lan3FGPppOEEntry 705316864}

er1646v2Lan3FGPppOEIpV6DhcpServerPool OBJECT-TYPE
   SYNTAX      DisplayString
   MAX-ACCESS  read-write
   STATUS      current
   DESCRIPTION
      "Path: ethernet3.editConf.pppoEClient.ipV6.dhcp.server.pool"
   ::= {er1646v2Lan3FGPppOEEntry 705317888}

er1646v2Lan3FGPppOEIpV6DhcpServerRapidCommit OBJECT-TYPE
   SYNTAX      INTEGER
               {
               disabled (0),
               enabled (1)
               }
   MAX-ACCESS  read-write
   STATUS      current
   DESCRIPTION
      "Path: ethernet3.editConf.pppoEClient.ipV6.dhcp.server.rapidCommit

       Possibilities:
               disabled   (0)
               enabled   (1)"
   ::= {er1646v2Lan3FGPppOEEntry 705318912}

er1646v2Lan3FGPppOEIpV6DhcpServerTimersInfoRefresh OBJECT-TYPE
   SYNTAX      TimeTicks
   MAX-ACCESS  read-write
   STATUS      current
   DESCRIPTION
      "Path: ethernet3.editConf.pppoEClient.ipV6.dhcp.server.timers.infoRefresh

       Time in centi-second."
   ::= {er1646v2Lan3FGPppOEEntry 705319940}

er1646v2Lan3FGPppOEIpV6DhcpRelayMode OBJECT-TYPE
   SYNTAX      INTEGER
               {
               disabled (0),
               enabled (1)
               }
   MAX-ACCESS  read-write
   STATUS      current
   DESCRIPTION
      "Path: ethernet3.editConf.pppoEClient.ipV6.dhcp.relay.mode

       Possibilities:
               disabled   (0)
               enabled   (1)"
   ::= {er1646v2Lan3FGPppOEEntry 705323040}

er1646v2Lan3FGPppOEIpV6SendRedirect OBJECT-TYPE
   SYNTAX      INTEGER
               {
               disabled (0),
               enabled (1)
               }
   MAX-ACCESS  read-write
   STATUS      current
   DESCRIPTION
      "Path: ethernet3.editConf.pppoEClient.ipV6.sendRedirect

       Possibilities:
               disabled   (0)
               enabled   (1)"
   ::= {er1646v2Lan3FGPppOEEntry 705101824}

er1646v2Lan3FGPppOEIpV6LinkMtu OBJECT-TYPE
   SYNTAX      Integer32
   MAX-ACCESS  read-write
   STATUS      current
   DESCRIPTION
      "Path: ethernet3.editConf.pppoEClient.ipV6.linkMtu"
   ::= {er1646v2Lan3FGPppOEEntry 705167360}

er1646v2Lan3FGPppOEIpV6InterfaceId OBJECT-TYPE
   SYNTAX      OCTET STRING
   MAX-ACCESS  read-write
   STATUS      current
   DESCRIPTION
      "Path: ethernet3.editConf.pppoEClient.ipV6.interfaceId"
   ::= {er1646v2Lan3FGPppOEEntry 705232896}

er1646v2Lan3FGPppOEIpV6MF OBJECT-TYPE
   SYNTAX      Integer32
   MAX-ACCESS  read-write
   STATUS      current
   DESCRIPTION
      "Path: ethernet3.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2Lan3FGPppOEEntry 705757184}

er1646v2Lan3FGPppOEIpV6IcmpMessagesNoRoute OBJECT-TYPE
   SYNTAX      INTEGER
               {
               disabled (0),
               enabled (1)
               }
   MAX-ACCESS  read-write
   STATUS      current
   DESCRIPTION
      "Path: ethernet3.editConf.pppoEClient.ipV6.icmpMessages.noRoute

       Possibilities:
               disabled   (0)
               enabled   (1)"
   ::= {er1646v2Lan3FGPppOEEntry 705822976}

er1646v2Lan3FGPppOEIpV6IcmpMessagesBeyondScope OBJECT-TYPE
   SYNTAX      INTEGER
               {
               disabled (0),
               enabled (1)
               }
   MAX-ACCESS  read-write
   STATUS      current
   DESCRIPTION
      "Path: ethernet3.editConf.pppoEClient.ipV6.icmpMessages.beyondScope

       Possibilities:
               disabled   (0)
               enabled   (1)"
   ::= {er1646v2Lan3FGPppOEEntry 705823488}

er1646v2Lan3FGPppOEIpV6IcmpMessagesAddressUnreachable OBJECT-TYPE
   SYNTAX      INTEGER
               {
               disabled (0),
               enabled (1)
               }
   MAX-ACCESS  read-write
   STATUS      current
   DESCRIPTION
      "Path: ethernet3.editConf.pppoEClient.ipV6.icmpMessages.addressUnreachable

       Possibilities:
               disabled   (0)
               enabled   (1)"
   ::= {er1646v2Lan3FGPppOEEntry 705823744}

er1646v2Lan3FGPppOEIpV6IcmpMessagesPortUnreachable OBJECT-TYPE
   SYNTAX      INTEGER
               {
               disabled (0),
               enabled (1)
               }
   MAX-ACCESS  read-write
   STATUS      current
   DESCRIPTION
      "Path: ethernet3.editConf.pppoEClient.ipV6.icmpMessages.portUnreachable

       Possibilities:
               disabled   (0)
               enabled   (1)"
   ::= {er1646v2Lan3FGPppOEEntry 705824000}

er1646v2Lan3FGPppOEIpV6IcmpMessagesPacketTooBig OBJECT-TYPE
   SYNTAX      INTEGER
               {
               disabled (0),
               enabled (1)
               }
   MAX-ACCESS  read-write
   STATUS      current
   DESCRIPTION
      "Path: ethernet3.editConf.pppoEClient.ipV6.icmpMessages.packetTooBig

       Possibilities:
               disabled   (0)
               enabled   (1)"
   ::= {er1646v2Lan3FGPppOEEntry 705825280}

er1646v2Lan3FGPppOEIpV6IcmpMessagesHopLimitExceeded OBJECT-TYPE
   SYNTAX      INTEGER
               {
               disabled (0),
               enabled (1)
               }
   MAX-ACCESS  read-write
   STATUS      current
   DESCRIPTION
      "Path: ethernet3.editConf.pppoEClient.ipV6.icmpMessages.hopLimitExceeded

       Possibilities:
               disabled   (0)
               enabled   (1)"
   ::= {er1646v2Lan3FGPppOEEntry 705827840}

er1646v2Lan3FGPppOEIpV6IcmpMessagesFragTimeExceeded OBJECT-TYPE
   SYNTAX      INTEGER
               {
               disabled (0),
               enabled (1)
               }
   MAX-ACCESS  read-write
   STATUS      current
   DESCRIPTION
      "Path: ethernet3.editConf.pppoEClient.ipV6.icmpMessages.fragTimeExceeded

       Possibilities:
               disabled   (0)
               enabled   (1)"
   ::= {er1646v2Lan3FGPppOEEntry 705828096}

er1646v2Lan3FGPppOEIpV6IcmpMessagesHeaderFieldErr OBJECT-TYPE
   SYNTAX      INTEGER
               {
               disabled (0),
               enabled (1)
               }
   MAX-ACCESS  read-write
   STATUS      current
   DESCRIPTION
      "Path: ethernet3.editConf.pppoEClient.ipV6.icmpMessages.headerFieldErr

       Possibilities:
               disabled   (0)
               enabled   (1)"
   ::= {er1646v2Lan3FGPppOEEntry 705830400}

er1646v2Lan3FGPppOEIpV6IcmpMessagesOptionUnrecognized OBJECT-TYPE
   SYNTAX      INTEGER
               {
               disabled (0),
               enabled (1)
               }
   MAX-ACCESS  read-write
   STATUS      current
   DESCRIPTION
      "Path: ethernet3.editConf.pppoEClient.ipV6.icmpMessages.optionUnrecognized

       Possibilities:
               disabled   (0)
               enabled   (1)"
   ::= {er1646v2Lan3FGPppOEEntry 705830912}

er1646v2Lan3FGPppOEIpV6IcmpMessagesRedirect OBJECT-TYPE
   SYNTAX      INTEGER
               {
               disabled (0),
               enabled (1)
               }
   MAX-ACCESS  read-write
   STATUS      current
   DESCRIPTION
      "Path: ethernet3.editConf.pppoEClient.ipV6.icmpMessages.redirect

       Possibilities:
               disabled   (0)
               enabled   (1)"
   ::= {er1646v2Lan3FGPppOEEntry 705832960}

er1646v2Lan3FGPppOEPppLnkMOperation OBJECT-TYPE
   SYNTAX      INTEGER
               {
               disabled (0),
               enabled (1)
               }
   MAX-ACCESS  read-write
   STATUS      current
   DESCRIPTION
      "Path: ethernet3.editConf.pppoEClient.ppp.linkMonitoring.operation

       Possibilities:
               disabled   (0)
               enabled   (1)"
   ::= {er1646v2Lan3FGPppOEEntry 251724032}

er1646v2Lan3FGPppOEPppLnkMInterval OBJECT-TYPE
   SYNTAX      TimeTicks
   MAX-ACCESS  read-write
   STATUS      current
   DESCRIPTION
      "Path: ethernet3.editConf.pppoEClient.ppp.linkMonitoring.interval

       Time in centi-second."
   ::= {er1646v2Lan3FGPppOEEntry 251724288}

er1646v2Lan3FGPppOEPppLnkMRepTimeOut OBJECT-TYPE
   SYNTAX      TimeTicks
   MAX-ACCESS  read-write
   STATUS      current
   DESCRIPTION
      "Path: ethernet3.editConf.pppoEClient.ppp.linkMonitoring.replyTimeOut

       Time in centi-second."
   ::= {er1646v2Lan3FGPppOEEntry 251724544}

er1646v2Lan3FGPppOEPppLnkMFailsPrmt OBJECT-TYPE
   SYNTAX      Integer32
   MAX-ACCESS  read-write
   STATUS      current
   DESCRIPTION
      "Path: ethernet3.editConf.pppoEClient.ppp.linkMonitoring.failsPermitted"
   ::= {er1646v2Lan3FGPppOEEntry 251724800}

er1646v2Lan3FGPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet3.editConf.pppoEClient.ppp.authentication

       Possibilities:
               disabled   (0)
               chap   (1)
               pap   (2)
               chapOrPap   (3)
               msChap   (4)
               msChapV2   (5)"
   ::= {er1646v2Lan3FGPppOEEntry 251789312}

er1646v2Lan3FGPppOEPppAuthenPeriod OBJECT-TYPE
   SYNTAX      TimeTicks
   MAX-ACCESS  read-write
   STATUS      current
   DESCRIPTION
      "Path: ethernet3.editConf.pppoEClient.ppp.authenPeriod

       Time in centi-second."
   ::= {er1646v2Lan3FGPppOEEntry 251854848}

er1646v2Lan3FGPppOEPppSessionName OBJECT-TYPE
   SYNTAX      DisplayString
   MAX-ACCESS  read-write
   STATUS      current
   DESCRIPTION
      "Path: ethernet3.editConf.pppoEClient.ppp.sessionName"
   ::= {er1646v2Lan3FGPppOEEntry 251985920}

er1646v2Lan3FGPppOEPppSessionSecret OBJECT-TYPE
   SYNTAX      DisplayString
   MAX-ACCESS  read-write
   STATUS      current
   DESCRIPTION
      "Path: ethernet3.editConf.pppoEClient.ppp.sessionSecret"
   ::= {er1646v2Lan3FGPppOEEntry 252051456}

er1646v2Lan3FGPppOEPppEncModeSessionSecret OBJECT-TYPE
   SYNTAX      INTEGER
               {
               none (1),
               encrypt (2),
               encType1 (3),
               invalid (128)
               }
   MAX-ACCESS  read-write
   STATUS      current
   DESCRIPTION
      "Path: ethernet3.editConf.pppoEClient.ppp.encModeSessionSecret

       Possibilities:
               none   (1)
               encrypt   (2)
               encType1   (3)
               invalid   (128)"
   ::= {er1646v2Lan3FGPppOEEntry 252182528}

er1646v2Lan3FGPppOEPppEncSessionSecret OBJECT-TYPE
   SYNTAX      DisplayString
   MAX-ACCESS  read-write
   STATUS      current
   DESCRIPTION
      "Path: ethernet3.editConf.pppoEClient.ppp.encSessionSecret"
   ::= {er1646v2Lan3FGPppOEEntry 252248064}

er1646v2Lan3FGPppOEPppServiceName OBJECT-TYPE
   SYNTAX      DisplayString
   MAX-ACCESS  read-write
   STATUS      current
   DESCRIPTION
      "Path: ethernet3.editConf.pppoEClient.ppp.serviceName"
   ::= {er1646v2Lan3FGPppOEEntry 252116992}

er1646v2Lan3FGPppOEIpH OBJECT-TYPE
   SYNTAX      SEQUENCE OF Er1646v2Lan3FGPppOEIpHEntry
   MAX-ACCESS  not-accessible
   STATUS      current
   DESCRIPTION
      ""
   ::= {er1646v2Lan3FGPppOE 51314688}

er1646v2Lan3FGPppOEIpHEntry OBJECT-TYPE
   SYNTAX      Er1646v2Lan3FGPppOEIpHEntry
   MAX-ACCESS  not-accessible
   STATUS      current
   DESCRIPTION
      ""
   INDEX      { er1646v2Lan3FGPppOETableIx,
                er1646v2Lan3FGPppOEIpHTableIx }
   ::= {er1646v2Lan3FGPppOEIpH 1}

Er1646v2Lan3FGPppOEIpHEntry ::=
   SEQUENCE
      {
      er1646v2Lan3FGPppOEIpHActions
         VariableLengthTableActions,
      er1646v2Lan3FGPppOEIpHTableIx
         TableIndex,
      er1646v2Lan3FGPppOEIpHAddress
         IpAddress,
      er1646v2Lan3FGPppOEIpHDhcpRelayOptionSubscriberId
         DisplayString
      }

er1646v2Lan3FGPppOEIpHActions OBJECT-TYPE
   SYNTAX      VariableLengthTableActions
   MAX-ACCESS  read-write
   STATUS      current
   DESCRIPTION
      "By way of this field, some manipulations
       on this table may be performed."
   ::= {er1646v2Lan3FGPppOEIpHEntry 2}

er1646v2Lan3FGPppOEIpHTableIx OBJECT-TYPE
   SYNTAX      TableIndex
   MAX-ACCESS  not-accessible
   STATUS      current
   DESCRIPTION
      ""
   ::= {er1646v2Lan3FGPppOEIpHEntry 11}

er1646v2Lan3FGPppOEIpHAddress OBJECT-TYPE
   SYNTAX      IpAddress
   MAX-ACCESS  read-write
   STATUS      current
   DESCRIPTION
      "Path: ethernet3.editConf.pppoEClient.ip.helpers.address"
   ::= {er1646v2Lan3FGPppOEIpHEntry 16777216}

er1646v2Lan3FGPppOEIpHDhcpRelayOptionSubscriberId OBJECT-TYPE
   SYNTAX      DisplayString
   MAX-ACCESS  read-write
   STATUS      current
   DESCRIPTION
      "Path: ethernet3.editConf.pppoEClient.ip.helpers.dhcpRelayOption.subscriberId"
   ::= {er1646v2Lan3FGPppOEIpHEntry 33947648}

er1646v2Lan3FGPppOEIpV6Addresses OBJECT-TYPE
   SYNTAX      SEQUENCE OF Er1646v2Lan3FGPppOEIpV6AddressesEntry
   MAX-ACCESS  not-accessible
   STATUS      current
   DESCRIPTION
      ""
   ::= {er1646v2Lan3FGPppOE 704839680}

er1646v2Lan3FGPppOEIpV6AddressesEntry OBJECT-TYPE
   SYNTAX      Er1646v2Lan3FGPppOEIpV6AddressesEntry
   MAX-ACCESS  not-accessible
   STATUS      current
   DESCRIPTION
      ""
   INDEX      { er1646v2Lan3FGPppOETableIx,
                er1646v2Lan3FGPppOEIpV6AddressesTableIx }
   ::= {er1646v2Lan3FGPppOEIpV6Addresses 1}

Er1646v2Lan3FGPppOEIpV6AddressesEntry ::=
   SEQUENCE
      {
      er1646v2Lan3FGPppOEIpV6AddressesActions
         VariableLengthTableActions,
      er1646v2Lan3FGPppOEIpV6AddressesTableIx
         TableIndex,
      er1646v2Lan3FGPppOEIpV6AddressesType
         INTEGER,
      er1646v2Lan3FGPppOEIpV6AddressesAddress
         Ipv6Address,
      er1646v2Lan3FGPppOEIpV6AddressesPrefixLength
         Integer32,
      er1646v2Lan3FGPppOEIpV6AddressesGeneralPrefix
         DisplayString,
      er1646v2Lan3FGPppOEIpV6AddressesRaSend
         INTEGER,
      er1646v2Lan3FGPppOEIpV6AddressesRaOnLinkFlag
         INTEGER,
      er1646v2Lan3FGPppOEIpV6AddressesRaAutoFlag
         INTEGER,
      er1646v2Lan3FGPppOEIpV6AddressesRaValidLifeTime
         TimeTicks,
      er1646v2Lan3FGPppOEIpV6AddressesRaValidLTMode
         INTEGER,
      er1646v2Lan3FGPppOEIpV6AddressesRaPrefLifeTime
         TimeTicks,
      er1646v2Lan3FGPppOEIpV6AddressesRaPrefLTMode
         INTEGER
      }

er1646v2Lan3FGPppOEIpV6AddressesActions OBJECT-TYPE
   SYNTAX      VariableLengthTableActions
   MAX-ACCESS  read-write
   STATUS      current
   DESCRIPTION
      "By way of this field, some manipulations
       on this table may be performed."
   ::= {er1646v2Lan3FGPppOEIpV6AddressesEntry 2}

er1646v2Lan3FGPppOEIpV6AddressesTableIx OBJECT-TYPE
   SYNTAX      TableIndex
   MAX-ACCESS  not-accessible
   STATUS      current
   DESCRIPTION
      ""
   ::= {er1646v2Lan3FGPppOEIpV6AddressesEntry 11}

er1646v2Lan3FGPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet3.editConf.pppoEClient.ipV6.addresses.type

       Possibilities:
               unicast   (0)
               eui64   (1)
               anycast   (2)
               linkLocal   (3)
               generalPrefix   (4)"
   ::= {er1646v2Lan3FGPppOEIpV6AddressesEntry 50331648}

er1646v2Lan3FGPppOEIpV6AddressesAddress OBJECT-TYPE
   SYNTAX      Ipv6Address
   MAX-ACCESS  read-write
   STATUS      current
   DESCRIPTION
      "Path: ethernet3.editConf.pppoEClient.ipV6.addresses.address

       ipv6 address"
   ::= {er1646v2Lan3FGPppOEIpV6AddressesEntry 16777216}

er1646v2Lan3FGPppOEIpV6AddressesPrefixLength OBJECT-TYPE
   SYNTAX      Integer32
   MAX-ACCESS  read-write
   STATUS      current
   DESCRIPTION
      "Path: ethernet3.editConf.pppoEClient.ipV6.addresses.prefixLength"
   ::= {er1646v2Lan3FGPppOEIpV6AddressesEntry 33554432}

er1646v2Lan3FGPppOEIpV6AddressesGeneralPrefix OBJECT-TYPE
   SYNTAX      DisplayString
   MAX-ACCESS  read-write
   STATUS      current
   DESCRIPTION
      "Path: ethernet3.editConf.pppoEClient.ipV6.addresses.generalPrefix"
   ::= {er1646v2Lan3FGPppOEIpV6AddressesEntry 83886080}

er1646v2Lan3FGPppOEIpV6AddressesRaSend OBJECT-TYPE
   SYNTAX      INTEGER
               {
               disabled (0),
               enabled (1)
               }
   MAX-ACCESS  read-write
   STATUS      current
   DESCRIPTION
      "Path: ethernet3.editConf.pppoEClient.ipV6.addresses.ra.send

       Possibilities:
               disabled   (0)
               enabled   (1)"
   ::= {er1646v2Lan3FGPppOEIpV6AddressesEntry 67174400}

er1646v2Lan3FGPppOEIpV6AddressesRaOnLinkFlag OBJECT-TYPE
   SYNTAX      INTEGER
               {
               disabled (0),
               enabled (1)
               }
   MAX-ACCESS  read-write
   STATUS      current
   DESCRIPTION
      "Path: ethernet3.editConf.pppoEClient.ipV6.addresses.ra.onLinkFlag

       Possibilities:
               disabled   (0)
               enabled   (1)"
   ::= {er1646v2Lan3FGPppOEIpV6AddressesEntry 67371008}

er1646v2Lan3FGPppOEIpV6AddressesRaAutoFlag OBJECT-TYPE
   SYNTAX      INTEGER
               {
               disabled (0),
               enabled (1)
               }
   MAX-ACCESS  read-write
   STATUS      current
   DESCRIPTION
      "Path: ethernet3.editConf.pppoEClient.ipV6.addresses.ra.autonomousFlag

       Possibilities:
               disabled   (0)
               enabled   (1)"
   ::= {er1646v2Lan3FGPppOEIpV6AddressesEntry 67567616}

er1646v2Lan3FGPppOEIpV6AddressesRaValidLifeTime OBJECT-TYPE
   SYNTAX      TimeTicks
   MAX-ACCESS  read-write
   STATUS      current
   DESCRIPTION
      "Path: ethernet3.editConf.pppoEClient.ipV6.addresses.ra.validLifeTime

       Time in centi-second."
   ::= {er1646v2Lan3FGPppOEIpV6AddressesEntry 67239936}

er1646v2Lan3FGPppOEIpV6AddressesRaValidLTMode OBJECT-TYPE
   SYNTAX      INTEGER
               {
               fixed (0),
               infinite (2)
               }
   MAX-ACCESS  read-write
   STATUS      current
   DESCRIPTION
      "Path: ethernet3.editConf.pppoEClient.ipV6.addresses.ra.validLifeTimeMode

       Possibilities:
               fixed   (0)
               infinite   (2)"
   ::= {er1646v2Lan3FGPppOEIpV6AddressesEntry 67305472}

er1646v2Lan3FGPppOEIpV6AddressesRaPrefLifeTime OBJECT-TYPE
   SYNTAX      TimeTicks
   MAX-ACCESS  read-write
   STATUS      current
   DESCRIPTION
      "Path: ethernet3.editConf.pppoEClient.ipV6.addresses.ra.prefLifeTime

       Time in centi-second."
   ::= {er1646v2Lan3FGPppOEIpV6AddressesEntry 67436544}

er1646v2Lan3FGPppOEIpV6AddressesRaPrefLTMode OBJECT-TYPE
   SYNTAX      INTEGER
               {
               fixed (0),
               infinite (2)
               }
   MAX-ACCESS  read-write
   STATUS      current
   DESCRIPTION
      "Path: ethernet3.editConf.pppoEClient.ipV6.addresses.ra.prefLifeTimeMode

       Possibilities:
               fixed   (0)
               infinite   (2)"
   ::= {er1646v2Lan3FGPppOEIpV6AddressesEntry 67502080}

er1646v2Lan3FGPppOEIpV6RaDnsOptionsRdnssServers OBJECT-TYPE
   SYNTAX      SEQUENCE OF Er1646v2Lan3FGPppOEIpV6RaDnsOptionsRdnssServersEntry
   MAX-ACCESS  not-accessible
   STATUS      current
   DESCRIPTION
      ""
   ::= {er1646v2Lan3FGPppOE 705039144}

er1646v2Lan3FGPppOEIpV6RaDnsOptionsRdnssServersEntry OBJECT-TYPE
   SYNTAX      Er1646v2Lan3FGPppOEIpV6RaDnsOptionsRdnssServersEntry
   MAX-ACCESS  not-accessible
   STATUS      current
   DESCRIPTION
      ""
   INDEX      { er1646v2Lan3FGPppOETableIx,
                er1646v2Lan3FGPppOEIpV6RaDnsOptionsRdnssServersTableIx }
   ::= {er1646v2Lan3FGPppOEIpV6RaDnsOptionsRdnssServers 1}

Er1646v2Lan3FGPppOEIpV6RaDnsOptionsRdnssServersEntry ::=
   SEQUENCE
      {
      er1646v2Lan3FGPppOEIpV6RaDnsOptionsRdnssServersActions
         VariableLengthTableActions,
      er1646v2Lan3FGPppOEIpV6RaDnsOptionsRdnssServersTableIx
         TableIndex,
      er1646v2Lan3FGPppOEIpV6RaDnsOptionsRdnssServersAddress
         Ipv6Address
      }

er1646v2Lan3FGPppOEIpV6RaDnsOptionsRdnssServersActions OBJECT-TYPE
   SYNTAX      VariableLengthTableActions
   MAX-ACCESS  read-write
   STATUS      current
   DESCRIPTION
      "By way of this field, some manipulations
       on this table may be performed."
   ::= {er1646v2Lan3FGPppOEIpV6RaDnsOptionsRdnssServersEntry 2}

er1646v2Lan3FGPppOEIpV6RaDnsOptionsRdnssServersTableIx OBJECT-TYPE
   SYNTAX      TableIndex
   MAX-ACCESS  not-accessible
   STATUS      current
   DESCRIPTION
      ""
   ::= {er1646v2Lan3FGPppOEIpV6RaDnsOptionsRdnssServersEntry 11}

er1646v2Lan3FGPppOEIpV6RaDnsOptionsRdnssServersAddress OBJECT-TYPE
   SYNTAX      Ipv6Address
   MAX-ACCESS  read-write
   STATUS      current
   DESCRIPTION
      "Path: ethernet3.editConf.pppoEClient.ipV6.ra.dnsOptions.rdnss.servers.address

       ipv6 address"
   ::= {er1646v2Lan3FGPppOEIpV6RaDnsOptionsRdnssServersEntry 16777216}

er1646v2Lan3FGPppOEIpV6RaDnsOptionsDnsslDomains OBJECT-TYPE
   SYNTAX      SEQUENCE OF Er1646v2Lan3FGPppOEIpV6RaDnsOptionsDnsslDomainsEntry
   MAX-ACCESS  not-accessible
   STATUS      current
   DESCRIPTION
      ""
   ::= {er1646v2Lan3FGPppOE 705039176}

er1646v2Lan3FGPppOEIpV6RaDnsOptionsDnsslDomainsEntry OBJECT-TYPE
   SYNTAX      Er1646v2Lan3FGPppOEIpV6RaDnsOptionsDnsslDomainsEntry
   MAX-ACCESS  not-accessible
   STATUS      current
   DESCRIPTION
      ""
   INDEX      { er1646v2Lan3FGPppOETableIx,
                er1646v2Lan3FGPppOEIpV6RaDnsOptionsDnsslDomainsTableIx }
   ::= {er1646v2Lan3FGPppOEIpV6RaDnsOptionsDnsslDomains 1}

Er1646v2Lan3FGPppOEIpV6RaDnsOptionsDnsslDomainsEntry ::=
   SEQUENCE
      {
      er1646v2Lan3FGPppOEIpV6RaDnsOptionsDnsslDomainsActions
         VariableLengthTableActions,
      er1646v2Lan3FGPppOEIpV6RaDnsOptionsDnsslDomainsTableIx
         TableIndex,
      er1646v2Lan3FGPppOEIpV6RaDnsOptionsDnsslDomainsName
         DisplayString
      }

er1646v2Lan3FGPppOEIpV6RaDnsOptionsDnsslDomainsActions OBJECT-TYPE
   SYNTAX      VariableLengthTableActions
   MAX-ACCESS  read-write
   STATUS      current
   DESCRIPTION
      "By way of this field, some manipulations
       on this table may be performed."
   ::= {er1646v2Lan3FGPppOEIpV6RaDnsOptionsDnsslDomainsEntry 2}

er1646v2Lan3FGPppOEIpV6RaDnsOptionsDnsslDomainsTableIx OBJECT-TYPE
   SYNTAX      TableIndex
   MAX-ACCESS  not-accessible
   STATUS      current
   DESCRIPTION
      ""
   ::= {er1646v2Lan3FGPppOEIpV6RaDnsOptionsDnsslDomainsEntry 11}

er1646v2Lan3FGPppOEIpV6RaDnsOptionsDnsslDomainsName OBJECT-TYPE
   SYNTAX      DisplayString
   MAX-ACCESS  read-write
   STATUS      current
   DESCRIPTION
      "Path: ethernet3.editConf.pppoEClient.ipV6.ra.dnsOptions.dnssl.domains.name"
   ::= {er1646v2Lan3FGPppOEIpV6RaDnsOptionsDnsslDomainsEntry 16777216}

er1646v2Lan3FGPppOEIpV6DhcpClientUserClassOpt OBJECT-TYPE
   SYNTAX      SEQUENCE OF Er1646v2Lan3FGPppOEIpV6DhcpClientUserClassOptEntry
   MAX-ACCESS  not-accessible
   STATUS      current
   DESCRIPTION
      ""
   ::= {er1646v2Lan3FGPppOE 705312768}

er1646v2Lan3FGPppOEIpV6DhcpClientUserClassOptEntry OBJECT-TYPE
   SYNTAX      Er1646v2Lan3FGPppOEIpV6DhcpClientUserClassOptEntry
   MAX-ACCESS  not-accessible
   STATUS      current
   DESCRIPTION
      ""
   INDEX      { er1646v2Lan3FGPppOETableIx,
                er1646v2Lan3FGPppOEIpV6DhcpClientUserClassOptTableIx }
   ::= {er1646v2Lan3FGPppOEIpV6DhcpClientUserClassOpt 1}

Er1646v2Lan3FGPppOEIpV6DhcpClientUserClassOptEntry ::=
   SEQUENCE
      {
      er1646v2Lan3FGPppOEIpV6DhcpClientUserClassOptActions
         VariableLengthTableActions,
      er1646v2Lan3FGPppOEIpV6DhcpClientUserClassOptTableIx
         TableIndex,
      er1646v2Lan3FGPppOEIpV6DhcpClientUserClassOptValueAscii
         DisplayString,
      er1646v2Lan3FGPppOEIpV6DhcpClientUserClassOptValueDecimal
         Integer32,
      er1646v2Lan3FGPppOEIpV6DhcpClientUserClassOptValueHexData
         OCTET STRING
      }

er1646v2Lan3FGPppOEIpV6DhcpClientUserClassOptActions OBJECT-TYPE
   SYNTAX      VariableLengthTableActions
   MAX-ACCESS  read-write
   STATUS      current
   DESCRIPTION
      "By way of this field, some manipulations
       on this table may be performed."
   ::= {er1646v2Lan3FGPppOEIpV6DhcpClientUserClassOptEntry 2}

er1646v2Lan3FGPppOEIpV6DhcpClientUserClassOptTableIx OBJECT-TYPE
   SYNTAX      TableIndex
   MAX-ACCESS  not-accessible
   STATUS      current
   DESCRIPTION
      ""
   ::= {er1646v2Lan3FGPppOEIpV6DhcpClientUserClassOptEntry 11}

er1646v2Lan3FGPppOEIpV6DhcpClientUserClassOptValueAscii OBJECT-TYPE
   SYNTAX      DisplayString
   MAX-ACCESS  read-write
   STATUS      current
   DESCRIPTION
      "Path: ethernet3.editConf.pppoEClient.ipV6.dhcp.client.userClassOpt.value.ascii"
   ::= {er1646v2Lan3FGPppOEIpV6DhcpClientUserClassOptEntry 16842752}

er1646v2Lan3FGPppOEIpV6DhcpClientUserClassOptValueDecimal OBJECT-TYPE
   SYNTAX      Integer32
   MAX-ACCESS  read-write
   STATUS      current
   DESCRIPTION
      "Path: ethernet3.editConf.pppoEClient.ipV6.dhcp.client.userClassOpt.value.decimal"
   ::= {er1646v2Lan3FGPppOEIpV6DhcpClientUserClassOptEntry 16908288}

er1646v2Lan3FGPppOEIpV6DhcpClientUserClassOptValueHexData OBJECT-TYPE
   SYNTAX      OCTET STRING
   MAX-ACCESS  read-write
   STATUS      current
   DESCRIPTION
      "Path: ethernet3.editConf.pppoEClient.ipV6.dhcp.client.userClassOpt.value.hexData"
   ::= {er1646v2Lan3FGPppOEIpV6DhcpClientUserClassOptEntry 16973824}

er1646v2Lan3FGPppOEIpV6DhcpClientVendorCl OBJECT-TYPE
   SYNTAX      SEQUENCE OF Er1646v2Lan3FGPppOEIpV6DhcpClientVendorClEntry
   MAX-ACCESS  not-accessible
   STATUS      current
   DESCRIPTION
      ""
   ::= {er1646v2Lan3FGPppOE 705313792}

er1646v2Lan3FGPppOEIpV6DhcpClientVendorClEntry OBJECT-TYPE
   SYNTAX      Er1646v2Lan3FGPppOEIpV6DhcpClientVendorClEntry
   MAX-ACCESS  not-accessible
   STATUS      current
   DESCRIPTION
      ""
   INDEX      { er1646v2Lan3FGPppOETableIx,
                er1646v2Lan3FGPppOEIpV6DhcpClientVendorClTableIx }
   ::= {er1646v2Lan3FGPppOEIpV6DhcpClientVendorCl 1}

Er1646v2Lan3FGPppOEIpV6DhcpClientVendorClEntry ::=
   SEQUENCE
      {
      er1646v2Lan3FGPppOEIpV6DhcpClientVendorClActions
         VariableLengthTableActions,
      er1646v2Lan3FGPppOEIpV6DhcpClientVendorClTableIx
         TableIndex,
      er1646v2Lan3FGPppOEIpV6DhcpClientVendorClValueAscii
         DisplayString,
      er1646v2Lan3FGPppOEIpV6DhcpClientVendorClValueDecimal
         Integer32,
      er1646v2Lan3FGPppOEIpV6DhcpClientVendorClValueHexData
         OCTET STRING
      }

er1646v2Lan3FGPppOEIpV6DhcpClientVendorClActions OBJECT-TYPE
   SYNTAX      VariableLengthTableActions
   MAX-ACCESS  read-write
   STATUS      current
   DESCRIPTION
      "By way of this field, some manipulations
       on this table may be performed."
   ::= {er1646v2Lan3FGPppOEIpV6DhcpClientVendorClEntry 2}

er1646v2Lan3FGPppOEIpV6DhcpClientVendorClTableIx OBJECT-TYPE
   SYNTAX      TableIndex
   MAX-ACCESS  not-accessible
   STATUS      current
   DESCRIPTION
      ""
   ::= {er1646v2Lan3FGPppOEIpV6DhcpClientVendorClEntry 11}

er1646v2Lan3FGPppOEIpV6DhcpClientVendorClValueAscii OBJECT-TYPE
   SYNTAX      DisplayString
   MAX-ACCESS  read-write
   STATUS      current
   DESCRIPTION
      "Path: ethernet3.editConf.pppoEClient.ipV6.dhcp.client.vendorClassOpt.value.ascii"
   ::= {er1646v2Lan3FGPppOEIpV6DhcpClientVendorClEntry 16842752}

er1646v2Lan3FGPppOEIpV6DhcpClientVendorClValueDecimal OBJECT-TYPE
   SYNTAX      Integer32
   MAX-ACCESS  read-write
   STATUS      current
   DESCRIPTION
      "Path: ethernet3.editConf.pppoEClient.ipV6.dhcp.client.vendorClassOpt.value.decimal"
   ::= {er1646v2Lan3FGPppOEIpV6DhcpClientVendorClEntry 16908288}

er1646v2Lan3FGPppOEIpV6DhcpClientVendorClValueHexData OBJECT-TYPE
   SYNTAX      OCTET STRING
   MAX-ACCESS  read-write
   STATUS      current
   DESCRIPTION
      "Path: ethernet3.editConf.pppoEClient.ipV6.dhcp.client.vendorClassOpt.value.hexData"
   ::= {er1646v2Lan3FGPppOEIpV6DhcpClientVendorClEntry 16973824}

er1646v2Lan3FGPppOEIpV6DhcpRelayDestinations OBJECT-TYPE
   SYNTAX      SEQUENCE OF Er1646v2Lan3FGPppOEIpV6DhcpRelayDestinationsEntry
   MAX-ACCESS  not-accessible
   STATUS      current
   DESCRIPTION
      ""
   ::= {er1646v2Lan3FGPppOE 705323072}

er1646v2Lan3FGPppOEIpV6DhcpRelayDestinationsEntry OBJECT-TYPE
   SYNTAX      Er1646v2Lan3FGPppOEIpV6DhcpRelayDestinationsEntry
   MAX-ACCESS  not-accessible
   STATUS      current
   DESCRIPTION
      ""
   INDEX      { er1646v2Lan3FGPppOETableIx,
                er1646v2Lan3FGPppOEIpV6DhcpRelayDestinationsTableIx }
   ::= {er1646v2Lan3FGPppOEIpV6DhcpRelayDestinations 1}

Er1646v2Lan3FGPppOEIpV6DhcpRelayDestinationsEntry ::=
   SEQUENCE
      {
      er1646v2Lan3FGPppOEIpV6DhcpRelayDestinationsActions
         VariableLengthTableActions,
      er1646v2Lan3FGPppOEIpV6DhcpRelayDestinationsTableIx
         TableIndex,
      er1646v2Lan3FGPppOEIpV6DhcpRelayDestinationsAddress
         Ipv6Address,
      er1646v2Lan3FGPppOEIpV6DhcpRelayDestinationsInterface
         DisplayString
      }

er1646v2Lan3FGPppOEIpV6DhcpRelayDestinationsActions OBJECT-TYPE
   SYNTAX      VariableLengthTableActions
   MAX-ACCESS  read-write
   STATUS      current
   DESCRIPTION
      "By way of this field, some manipulations
       on this table may be performed."
   ::= {er1646v2Lan3FGPppOEIpV6DhcpRelayDestinationsEntry 2}

er1646v2Lan3FGPppOEIpV6DhcpRelayDestinationsTableIx OBJECT-TYPE
   SYNTAX      TableIndex
   MAX-ACCESS  not-accessible
   STATUS      current
   DESCRIPTION
      ""
   ::= {er1646v2Lan3FGPppOEIpV6DhcpRelayDestinationsEntry 11}

er1646v2Lan3FGPppOEIpV6DhcpRelayDestinationsAddress OBJECT-TYPE
   SYNTAX      Ipv6Address
   MAX-ACCESS  read-write
   STATUS      current
   DESCRIPTION
      "Path: ethernet3.editConf.pppoEClient.ipV6.dhcp.relay.destinations.address

       ipv6 address"
   ::= {er1646v2Lan3FGPppOEIpV6DhcpRelayDestinationsEntry 16777216}

er1646v2Lan3FGPppOEIpV6DhcpRelayDestinationsInterface OBJECT-TYPE
   SYNTAX      DisplayString
   MAX-ACCESS  read-write
   STATUS      current
   DESCRIPTION
      "Path: ethernet3.editConf.pppoEClient.ipV6.dhcp.relay.destinations.interface"
   ::= {er1646v2Lan3FGPppOEIpV6DhcpRelayDestinationsEntry 33554432}


er1646v2Lan3FGPppoEServer OBJECT-TYPE
   SYNTAX      DisplayString
   MAX-ACCESS  read-write
   STATUS      current
   DESCRIPTION
      "Path: ethernet3.editConf.pppoEServer
       Info: ppp server name on interface"
   ::= {er1646v2Lan3FG 37}


er1646v2Lan3FGMediaType OBJECT-TYPE
   SYNTAX      INTEGER
               {
               utp (1),
               sfp (2),
               auto (3)
               }
   MAX-ACCESS  read-write
   STATUS      current
   DESCRIPTION
      "Path: ethernet3.editConf.mediaType

       Possibilities:
               utp   (1)
               sfp   (2)
               auto   (3)"
   ::= {er1646v2Lan3FG 38}


er1646v2Lan3FGInboundHwPriority OBJECT IDENTIFIER ::= {er1646v2Lan3FG 231}

er1646v2Lan3FGInboundHwPrioritySSC OBJECT IDENTIFIER ::= {er1646v2Lan3FGInboundHwPriority 1}

er1646v2Lan3FGInboundHwPriorityEntry OBJECT IDENTIFIER ::= {er1646v2Lan3FGInboundHwPrioritySSC 1}

er1646v2Lan3FGInboundHwPriorityNone OBJECT-TYPE
   SYNTAX      OCTET STRING
   MAX-ACCESS  read-write
   STATUS      current
   DESCRIPTION
      "Path: ethernet3.editConf.inboundHwPriority.none"
   ::= {er1646v2Lan3FGInboundHwPriorityEntry 16777216}

er1646v2Lan3FGInboundHwPriorityMapCosToQueueP0 OBJECT-TYPE
   SYNTAX      INTEGER
               {
               queue1 (1),
               queue2 (2)
               }
   MAX-ACCESS  read-write
   STATUS      current
   DESCRIPTION
      "Path: ethernet3.editConf.inboundHwPriority.mapCosToQueue.p0

       Possibilities:
               queue1   (1)
               queue2   (2)"
   ::= {er1646v2Lan3FGInboundHwPriorityEntry 33619968}

er1646v2Lan3FGInboundHwPriorityMapCosToQueueP1 OBJECT-TYPE
   SYNTAX      INTEGER
               {
               queue1 (1),
               queue2 (2)
               }
   MAX-ACCESS  read-write
   STATUS      current
   DESCRIPTION
      "Path: ethernet3.editConf.inboundHwPriority.mapCosToQueue.p1

       Possibilities:
               queue1   (1)
               queue2   (2)"
   ::= {er1646v2Lan3FGInboundHwPriorityEntry 33685504}

er1646v2Lan3FGInboundHwPriorityMapCosToQueueP2 OBJECT-TYPE
   SYNTAX      INTEGER
               {
               queue1 (1),
               queue2 (2)
               }
   MAX-ACCESS  read-write
   STATUS      current
   DESCRIPTION
      "Path: ethernet3.editConf.inboundHwPriority.mapCosToQueue.p2

       Possibilities:
               queue1   (1)
               queue2   (2)"
   ::= {er1646v2Lan3FGInboundHwPriorityEntry 33751040}

er1646v2Lan3FGInboundHwPriorityMapCosToQueueP3 OBJECT-TYPE
   SYNTAX      INTEGER
               {
               queue1 (1),
               queue2 (2)
               }
   MAX-ACCESS  read-write
   STATUS      current
   DESCRIPTION
      "Path: ethernet3.editConf.inboundHwPriority.mapCosToQueue.p3

       Possibilities:
               queue1   (1)
               queue2   (2)"
   ::= {er1646v2Lan3FGInboundHwPriorityEntry 33816576}

er1646v2Lan3FGInboundHwPriorityMapCosToQueueP4 OBJECT-TYPE
   SYNTAX      INTEGER
               {
               queue1 (1),
               queue2 (2)
               }
   MAX-ACCESS  read-write
   STATUS      current
   DESCRIPTION
      "Path: ethernet3.editConf.inboundHwPriority.mapCosToQueue.p4

       Possibilities:
               queue1   (1)
               queue2   (2)"
   ::= {er1646v2Lan3FGInboundHwPriorityEntry 33882112}

er1646v2Lan3FGInboundHwPriorityMapCosToQueueP5 OBJECT-TYPE
   SYNTAX      INTEGER
               {
               queue1 (1),
               queue2 (2)
               }
   MAX-ACCESS  read-write
   STATUS      current
   DESCRIPTION
      "Path: ethernet3.editConf.inboundHwPriority.mapCosToQueue.p5

       Possibilities:
               queue1   (1)
               queue2   (2)"
   ::= {er1646v2Lan3FGInboundHwPriorityEntry 33947648}

er1646v2Lan3FGInboundHwPriorityMapCosToQueueP6 OBJECT-TYPE
   SYNTAX      INTEGER
               {
               queue1 (1),
               queue2 (2)
               }
   MAX-ACCESS  read-write
   STATUS      current
   DESCRIPTION
      "Path: ethernet3.editConf.inboundHwPriority.mapCosToQueue.p6

       Possibilities:
               queue1   (1)
               queue2   (2)"
   ::= {er1646v2Lan3FGInboundHwPriorityEntry 34013184}

er1646v2Lan3FGInboundHwPriorityMapCosToQueueP7 OBJECT-TYPE
   SYNTAX      INTEGER
               {
               queue1 (1),
               queue2 (2)
               }
   MAX-ACCESS  read-write
   STATUS      current
   DESCRIPTION
      "Path: ethernet3.editConf.inboundHwPriority.mapCosToQueue.p7

       Possibilities:
               queue1   (1)
               queue2   (2)"
   ::= {er1646v2Lan3FGInboundHwPriorityEntry 34078720}

er1646v2Lan3FGInboundHwPriorityMapDscpToQueue OBJECT-TYPE
   SYNTAX      SEQUENCE OF Er1646v2Lan3FGInboundHwPriorityMapDscpToQueueEntry
   MAX-ACCESS  not-accessible
   STATUS      current
   DESCRIPTION
      ""
   ::= {er1646v2Lan3FGInboundHwPriority 50331648}

er1646v2Lan3FGInboundHwPriorityMapDscpToQueueEntry OBJECT-TYPE
   SYNTAX      Er1646v2Lan3FGInboundHwPriorityMapDscpToQueueEntry
   MAX-ACCESS  not-accessible
   STATUS      current
   DESCRIPTION
      ""
   INDEX      { er1646v2Lan3FGInboundHwPriorityMapDscpToQueueTableIx }
   ::= {er1646v2Lan3FGInboundHwPriorityMapDscpToQueue 1}

Er1646v2Lan3FGInboundHwPriorityMapDscpToQueueEntry ::=
   SEQUENCE
      {
      er1646v2Lan3FGInboundHwPriorityMapDscpToQueueActions
         VariableLengthTableActions,
      er1646v2Lan3FGInboundHwPriorityMapDscpToQueueTableIx
         TableIndex,
      er1646v2Lan3FGInboundHwPriorityMapDscpToQueueStartDscp
         INTEGER,
      er1646v2Lan3FGInboundHwPriorityMapDscpToQueueEndDscp
         INTEGER,
      er1646v2Lan3FGInboundHwPriorityMapDscpToQueueQueue
         INTEGER
      }

er1646v2Lan3FGInboundHwPriorityMapDscpToQueueActions OBJECT-TYPE
   SYNTAX      VariableLengthTableActions
   MAX-ACCESS  read-write
   STATUS      current
   DESCRIPTION
      "By way of this field, some manipulations
       on this table may be performed."
   ::= {er1646v2Lan3FGInboundHwPriorityMapDscpToQueueEntry 2}

er1646v2Lan3FGInboundHwPriorityMapDscpToQueueTableIx OBJECT-TYPE
   SYNTAX      TableIndex
   MAX-ACCESS  not-accessible
   STATUS      current
   DESCRIPTION
      ""
   ::= {er1646v2Lan3FGInboundHwPriorityMapDscpToQueueEntry 11}

er1646v2Lan3FGInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1646v2Lan3FGInboundHwPriorityMapDscpToQueueEntry 16777216}

er1646v2Lan3FGInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet3.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1646v2Lan3FGInboundHwPriorityMapDscpToQueueEntry 33554432}

er1646v2Lan3FGInboundHwPriorityMapDscpToQueueQueue OBJECT-TYPE
   SYNTAX      INTEGER
               {
               queue1 (1),
               queue2 (2)
               }
   MAX-ACCESS  read-write
   STATUS      current
   DESCRIPTION
      "Path: ethernet3.editConf.inboundHwPriority.mapDscpToQueue.queue

       Possibilities:
               queue1   (1)
               queue2   (2)"
   ::= {er1646v2Lan3FGInboundHwPriorityMapDscpToQueueEntry 50331648}


er1646v2Lan3FGName OBJECT-TYPE
   SYNTAX      DisplayString
   MAX-ACCESS  read-write
   STATUS      current
   DESCRIPTION
      "Path: ethernet3.editConf.name
       Info: config interface name"
   ::= {er1646v2Lan3FG 2}



sr1646v2Lan3FG OBJECT IDENTIFIER ::= {r1646v2Lan3FG 14}


sr1646v2Lan3FGDescr OBJECT-TYPE
   SYNTAX      DisplayString
   MAX-ACCESS  read-only
   STATUS      current
   DESCRIPTION
      "Path: ethernet3.status.ifDescr
       Info: ifDescr"
   ::= {sr1646v2Lan3FG 101}


sr1646v2Lan3FGType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet3.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2Lan3FG 102}


sr1646v2Lan3FGMtu OBJECT-TYPE
   SYNTAX      Integer32
   MAX-ACCESS  read-only
   STATUS      current
   DESCRIPTION
      "Path: ethernet3.status.ifMtu
       Info: ifMtu"
   ::= {sr1646v2Lan3FG 103}


sr1646v2Lan3FGOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ifOperStatus
       Info: ifOperStatus

       Possibilities:
               up   (1)
               down   (2)
               testing   (3)
               unknown   (4)
               dormant   (5)
               notPresent   (6)
               lowerLayerDown   (7)"
   ::= {sr1646v2Lan3FG 107}


sr1646v2Lan3FGLastChange OBJECT-TYPE
   SYNTAX      TimeTicks
   MAX-ACCESS  read-only
   STATUS      current
   DESCRIPTION
      "Path: ethernet3.status.ifLastChange
       Info: ifLastChange

       Time in centi-second."
   ::= {sr1646v2Lan3FG 108}


sr1646v2Lan3FGLastChangeD OBJECT-TYPE
   SYNTAX      DisplayString
   MAX-ACCESS  read-only
   STATUS      current
   DESCRIPTION
      "Path: ethernet3.status.ifLastChangeDate
       Info: ifLastChangeDate"
   ::= {sr1646v2Lan3FG 183}


sr1646v2Lan3FGSpeed OBJECT-TYPE
   SYNTAX      Gauge32
   MAX-ACCESS  read-only
   STATUS      current
   DESCRIPTION
      "Path: ethernet3.status.ifSpeed
       Info: ifSpeed

       32 bit unsigned gauge value."
   ::= {sr1646v2Lan3FG 104}


sr1646v2Lan3FGSnmpIndex OBJECT-TYPE
   SYNTAX      Integer32
   MAX-ACCESS  read-only
   STATUS      current
   DESCRIPTION
      "Path: ethernet3.status.snmpIndex
       Info: SNMP index assigned to this object"
   ::= {sr1646v2Lan3FG 269}


sr1646v2Lan3FGIp OBJECT IDENTIFIER ::= {sr1646v2Lan3FG 16}

sr1646v2Lan3FGIpSSC OBJECT IDENTIFIER ::= {sr1646v2Lan3FGIp 1}

sr1646v2Lan3FGIpEntry OBJECT IDENTIFIER ::= {sr1646v2Lan3FGIpSSC 1}

sr1646v2Lan3FGIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.ip.status

       Possibilities:
               up   (1)
               down   (2)
               testing   (3)
               unknown   (4)
               dormant   (5)
               notPresent   (6)
               lowerLayerDown   (7)"
   ::= {sr1646v2Lan3FGIpEntry 1795162112}

sr1646v2Lan3FGIpAddress OBJECT-TYPE
   SYNTAX      IpAddress
   MAX-ACCESS  read-only
   STATUS      current
   DESCRIPTION
      "Path: ethernet3.status.ip.address"
   ::= {sr1646v2Lan3FGIpEntry 2030043136}

sr1646v2Lan3FGIpNetMask OBJECT-TYPE
   SYNTAX      IpAddress
   MAX-ACCESS  read-only
   STATUS      current
   DESCRIPTION
      "Path: ethernet3.status.ip.netMask"
   ::= {sr1646v2Lan3FGIpEntry 2063597568}

sr1646v2Lan3FGIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet3.status.ip.dhcp.status

       Possibilities:
               none   (0)
               selecting   (1)
               requesting   (2)
               rebinding   (3)
               bound   (4)
               renewing   (5)
               rebooting   (6)
               initreboot   (7)"
   ::= {sr1646v2Lan3FGIpEntry 402718720}

sr1646v2Lan3FGIpDhcpLeaseTime OBJECT-TYPE
   SYNTAX      TimeTicks
   MAX-ACCESS  read-only
   STATUS      current
   DESCRIPTION
      "Path: ethernet3.status.ip.dhcp.leaseTime

       Time in centi-second."
   ::= {sr1646v2Lan3FGIpEntry 402784256}

sr1646v2Lan3FGIpSecondaryIp OBJECT-TYPE
   SYNTAX      SEQUENCE OF Sr1646v2Lan3FGIpSecondaryIpEntry
   MAX-ACCESS  not-accessible
   STATUS      current
   DESCRIPTION
      ""
   ::= {sr1646v2Lan3FGIp 385875968}

sr1646v2Lan3FGIpSecondaryIpEntry OBJECT-TYPE
   SYNTAX      Sr1646v2Lan3FGIpSecondaryIpEntry
   MAX-ACCESS  not-accessible
   STATUS      current
   DESCRIPTION
      ""
   INDEX      { sr1646v2Lan3FGIpSecondaryIpTableIx }
   ::= {sr1646v2Lan3FGIpSecondaryIp 1}

Sr1646v2Lan3FGIpSecondaryIpEntry ::=
   SEQUENCE
      {
      sr1646v2Lan3FGIpSecondaryIpTableIx
         TableIndex,
      sr1646v2Lan3FGIpSecondaryIpAddress
         IpAddress,
      sr1646v2Lan3FGIpSecondaryIpNetMask
         IpAddress
      }

sr1646v2Lan3FGIpSecondaryIpTableIx OBJECT-TYPE
   SYNTAX      TableIndex
   MAX-ACCESS  not-accessible
   STATUS      current
   DESCRIPTION
      ""
   ::= {sr1646v2Lan3FGIpSecondaryIpEntry 11}

sr1646v2Lan3FGIpSecondaryIpAddress OBJECT-TYPE
   SYNTAX      IpAddress
   MAX-ACCESS  read-only
   STATUS      current
   DESCRIPTION
      "Path: ethernet3.status.ip.secondaryIp.address"
   ::= {sr1646v2Lan3FGIpSecondaryIpEntry 2030043136}

sr1646v2Lan3FGIpSecondaryIpNetMask OBJECT-TYPE
   SYNTAX      IpAddress
   MAX-ACCESS  read-only
   STATUS      current
   DESCRIPTION
      "Path: ethernet3.status.ip.secondaryIp.netMask"
   ::= {sr1646v2Lan3FGIpSecondaryIpEntry 2063597568}


sr1646v2Lan3FGArpCache OBJECT IDENTIFIER ::= {sr1646v2Lan3FG 11}

sr1646v2Lan3FGArpCacheSSCTable OBJECT-TYPE
   SYNTAX      SEQUENCE OF Sr1646v2Lan3FGArpCacheEntry
   MAX-ACCESS  not-accessible
   STATUS      current
   DESCRIPTION
      "arp cache of ethernet interface"
   ::= {sr1646v2Lan3FGArpCache 1}

sr1646v2Lan3FGArpCacheEntry OBJECT-TYPE
   SYNTAX      Sr1646v2Lan3FGArpCacheEntry
   MAX-ACCESS  not-accessible
   STATUS      current
   DESCRIPTION
      ""
   INDEX      { sr1646v2Lan3FGArpCacheTableIx }
   ::= {sr1646v2Lan3FGArpCacheSSCTable 1}

Sr1646v2Lan3FGArpCacheEntry ::=
   SEQUENCE
      {
      sr1646v2Lan3FGArpCacheTableIx
         TableIndex,
      sr1646v2Lan3FGArpCacheMacAddress
         OCTET STRING,
      sr1646v2Lan3FGArpCacheIpAddress
         IpAddress,
      sr1646v2Lan3FGArpCacheType
         INTEGER,
      sr1646v2Lan3FGArpCacheTimeOut
         TimeTicks
      }

sr1646v2Lan3FGArpCacheTableIx OBJECT-TYPE
   SYNTAX      TableIndex
   MAX-ACCESS  not-accessible
   STATUS      current
   DESCRIPTION
      ""
   ::= {sr1646v2Lan3FGArpCacheEntry 11}

sr1646v2Lan3FGArpCacheMacAddress OBJECT-TYPE
   SYNTAX      OCTET STRING
   MAX-ACCESS  read-only
   STATUS      current
   DESCRIPTION
      "Path: ethernet3.status.arpCache.macAddress

       MAC address."
   ::= {sr1646v2Lan3FGArpCacheEntry 16777216}

sr1646v2Lan3FGArpCacheIpAddress OBJECT-TYPE
   SYNTAX      IpAddress
   MAX-ACCESS  read-only
   STATUS      current
   DESCRIPTION
      "Path: ethernet3.status.arpCache.ipAddress"
   ::= {sr1646v2Lan3FGArpCacheEntry 33554432}

sr1646v2Lan3FGArpCacheType OBJECT-TYPE
   SYNTAX      INTEGER
               {
               static (0),
               dynamic (1)
               }
   MAX-ACCESS  read-only
   STATUS      current
   DESCRIPTION
      "Path: ethernet3.status.arpCache.type

       Possibilities:
               static   (0)
               dynamic   (1)"
   ::= {sr1646v2Lan3FGArpCacheEntry 50331648}

sr1646v2Lan3FGArpCacheTimeOut OBJECT-TYPE
   SYNTAX      TimeTicks
   MAX-ACCESS  read-only
   STATUS      current
   DESCRIPTION
      "Path: ethernet3.status.arpCache.timeOut

       Time in centi-second."
   ::= {sr1646v2Lan3FGArpCacheEntry 67108864}


sr1646v2Lan3FGBrS OBJECT IDENTIFIER ::= {sr1646v2Lan3FG 28}

sr1646v2Lan3FGBrSSSC OBJECT IDENTIFIER ::= {sr1646v2Lan3FGBrS 1}

sr1646v2Lan3FGBrSEntry OBJECT IDENTIFIER ::= {sr1646v2Lan3FGBrSSSC 1}

sr1646v2Lan3FGBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet3.status.bridging.status

       Possibilities:
               disabled   (0)
               discarding   (1)
               learning   (2)
               forwarding   (3)
               backupBlockedIntfDown   (256)
               backupBlockedIntfUp   (259)
               shutdown   (255)"
   ::= {sr1646v2Lan3FGBrSEntry 16777216}

sr1646v2Lan3FGBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: ethernet3.status.bridging.spanningTree.portRole

       Possibilities:
               none   (0)
               root   (1)
               designated   (2)
               alternate   (3)
               backup   (4)
               disabled   (5)
               master   (6)"
   ::= {sr1646v2Lan3FGBrSEntry 33619968}

sr1646v2Lan3FGBrSStPortId OBJECT-TYPE
   SYNTAX      Integer32
   MAX-ACCESS  read-only
   STATUS      current
   DESCRIPTION
      "Path: ethernet3.status.bridging.spanningTree.portId"
   ::= {sr1646v2Lan3FGBrSEntry 33685504}

sr1646v2Lan3FGBrSStPpCostExtPathCost OBJECT-TYPE
   SYNTAX      Integer32
   MAX-ACCESS  read-only
   STATUS      current
   DESCRIPTION
      "Path: ethernet3.status.bridging.spanningTree.portPathCosts.extPathCost"
   ::= {sr1646v2Lan3FGBrSEntry 33751296}

sr1646v2Lan3FGBrSStPpCostIntPathCost OBJECT-TYPE
   SYNTAX      Integer32
   MAX-ACCESS  read-only
   STATUS      current
   DESCRIPTION
      "Path: ethernet3.status.bridging.spanningTree.portPathCosts.intPathCost"
   ::= {sr1646v2Lan3FGBrSEntry 33751552}

sr1646v2Lan3FGBrSStExtRpCost OBJECT-TYPE
   SYNTAX      Integer32
   MAX-ACCESS  read-only
   STATUS      current
   DESCRIPTION
      "Path: ethernet3.status.bridging.spanningTree.extRootPathCost"
   ::= {sr1646v2Lan3FGBrSEntry 33816576}

sr1646v2Lan3FGBrSStIntRpCost OBJECT-TYPE
   SYNTAX      Integer32
   MAX-ACCESS  read-only
   STATUS      current
   DESCRIPTION
      "Path: ethernet3.status.bridging.spanningTree.intRootPathCost"
   ::= {sr1646v2Lan3FGBrSEntry 33882112}

sr1646v2Lan3FGBrSStDesBrIdPriority OBJECT-TYPE
   SYNTAX      Integer32
   MAX-ACCESS  read-only
   STATUS      current
   DESCRIPTION
      "Path: ethernet3.status.bridging.spanningTree.designatedBridgeId.priority"
   ::= {sr1646v2Lan3FGBrSEntry 33947904}

sr1646v2Lan3FGBrSStDesBrIdMacAddress OBJECT-TYPE
   SYNTAX      OCTET STRING
   MAX-ACCESS  read-only
   STATUS      current
   DESCRIPTION
      "Path: ethernet3.status.bridging.spanningTree.designatedBridgeId.macAddress

       MAC address."
   ::= {sr1646v2Lan3FGBrSEntry 33948160}

sr1646v2Lan3FGBrSStDesPrtId OBJECT-TYPE
   SYNTAX      Integer32
   MAX-ACCESS  read-only
   STATUS      current
   DESCRIPTION
      "Path: ethernet3.status.bridging.spanningTree.designatedPortId"
   ::= {sr1646v2Lan3FGBrSEntry 34013184}

sr1646v2Lan3FGBrSStDesInt OBJECT-TYPE
   SYNTAX      INTEGER
               {
               no (0),
               yes (1)
               }
   MAX-ACCESS  read-only
   STATUS      current
   DESCRIPTION
      "Path: ethernet3.status.bridging.spanningTree.designatedOrInternal

       Possibilities:
               no   (0)
               yes   (1)"
   ::= {sr1646v2Lan3FGBrSEntry 34078720}

sr1646v2Lan3FGBrSStEdgeDetection OBJECT-TYPE
   SYNTAX      INTEGER
               {
               none (0),
               edge (1),
               notEdge (2)
               }
   MAX-ACCESS  read-only
   STATUS      current
   DESCRIPTION
      "Path: ethernet3.status.bridging.spanningTree.edgeDetection

       Possibilities:
               none   (0)
               edge   (1)
               notEdge   (2)"
   ::= {sr1646v2Lan3FGBrSEntry 34144256}


sr1646v2Lan3FGMacAddress OBJECT-TYPE
   SYNTAX      OCTET STRING
   MAX-ACCESS  read-only
   STATUS      current
   DESCRIPTION
      "Path: ethernet3.status.macAddress
       Info: ifPhysAddress

       MAC address."
   ::= {sr1646v2Lan3FG 105}


sr1646v2Lan3FGIpAdEntBcastAddr OBJECT-TYPE
   SYNTAX      Integer32
   MAX-ACCESS  read-only
   STATUS      current
   DESCRIPTION
      "Path: ethernet3.status.ipAdEntBcastAddr
       Info: ipAdEntBcastAddr"
   ::= {sr1646v2Lan3FG 124}


sr1646v2Lan3FGIpAdEntReasmMaxSize OBJECT-TYPE
   SYNTAX      Integer32
   MAX-ACCESS  read-only
   STATUS      current
   DESCRIPTION
      "Path: ethernet3.status.ipAdEntReasmMaxSize
       Info: ipAdEntReasmMaxSize"
   ::= {sr1646v2Lan3FG 125}


sr1646v2Lan3FGAdapter OBJECT IDENTIFIER ::= {sr1646v2Lan3FG 145}

sr1646v2Lan3FGAdapterSSC OBJECT IDENTIFIER ::= {sr1646v2Lan3FGAdapter 1}

sr1646v2Lan3FGAdapterEntry OBJECT IDENTIFIER ::= {sr1646v2Lan3FGAdapterSSC 1}

sr1646v2Lan3FGAdapterSpeed OBJECT-TYPE
   SYNTAX      INTEGER
               {
               s10 (0),
               s100 (1),
               s1000 (2),
               s200 (3)
               }
   MAX-ACCESS  read-only
   STATUS      current
   DESCRIPTION
      "Path: ethernet3.status.adapter.speed

       Possibilities:
               10   (0)
               100   (1)
               1000   (2)
               200   (3)"
   ::= {sr1646v2Lan3FGAdapterEntry 16777216}

sr1646v2Lan3FGAdapterDuplex OBJECT-TYPE
   SYNTAX      INTEGER
               {
               halfDuplex (0),
               fullDuplex (1)
               }
   MAX-ACCESS  read-only
   STATUS      current
   DESCRIPTION
      "Path: ethernet3.status.adapter.duplex

       Possibilities:
               halfDuplex   (0)
               fullDuplex   (1)"
   ::= {sr1646v2Lan3FGAdapterEntry 33554432}


sr1646v2Lan3FGOam OBJECT IDENTIFIER ::= {sr1646v2Lan3FG 901}

sr1646v2Lan3FGOamSSC OBJECT IDENTIFIER ::= {sr1646v2Lan3FGOam 1}

sr1646v2Lan3FGOamEntry OBJECT IDENTIFIER ::= {sr1646v2Lan3FGOamSSC 1}

sr1646v2Lan3FGOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: ethernet3.status.oam.discovery

       Possibilities:
               fault   (0)
               sendLocal   (1)
               passiveWait   (2)
               sendLocalRemote   (3)
               sendLocalRemoteOk   (4)
               sendAny   (5)"
   ::= {sr1646v2Lan3FGOamEntry 16777216}

sr1646v2Lan3FGOamLoopback OBJECT-TYPE
   SYNTAX      INTEGER
               {
               idle (0),
               waiting (1),
               localRunning (2),
               remoteRunning (3)
               }
   MAX-ACCESS  read-only
   STATUS      current
   DESCRIPTION
      "Path: ethernet3.status.oam.loopback

       Possibilities:
               idle   (0)
               waiting   (1)
               localRunning   (2)
               remoteRunning   (3)"
   ::= {sr1646v2Lan3FGOamEntry 33554432}

sr1646v2Lan3FGOamLocalInfoVersion OBJECT-TYPE
   SYNTAX      Integer32
   MAX-ACCESS  read-only
   STATUS      current
   DESCRIPTION
      "Path: ethernet3.status.oam.localInfo.version"
   ::= {sr1646v2Lan3FGOamEntry 50397184}

sr1646v2Lan3FGOamLocalInfoRevision OBJECT-TYPE
   SYNTAX      Integer32
   MAX-ACCESS  read-only
   STATUS      current
   DESCRIPTION
      "Path: ethernet3.status.oam.localInfo.revision"
   ::= {sr1646v2Lan3FGOamEntry 50462720}

sr1646v2Lan3FGOamLocalInfoStateMuxAction OBJECT-TYPE
   SYNTAX      INTEGER
               {
               forwarding (0),
               discarding (1)
               }
   MAX-ACCESS  read-only
   STATUS      current
   DESCRIPTION
      "Path: ethernet3.status.oam.localInfo.state.muxAction

       Possibilities:
               forwarding   (0)
               discarding   (1)"
   ::= {sr1646v2Lan3FGOamEntry 50528512}

sr1646v2Lan3FGOamLocalInfoStateParserAction OBJECT-TYPE
   SYNTAX      INTEGER
               {
               forwarding (0),
               loopback (1),
               discarding (2),
               reserved (3)
               }
   MAX-ACCESS  read-only
   STATUS      current
   DESCRIPTION
      "Path: ethernet3.status.oam.localInfo.state.parserAction

       Possibilities:
               forwarding   (0)
               loopback   (1)
               discarding   (2)
               reserved   (3)"
   ::= {sr1646v2Lan3FGOamEntry 50528768}

sr1646v2Lan3FGOamLocalInfoOui OBJECT-TYPE
   SYNTAX      OCTET STRING
   MAX-ACCESS  read-only
   STATUS      current
   DESCRIPTION
      "Path: ethernet3.status.oam.localInfo.oui"
   ::= {sr1646v2Lan3FGOamEntry 50593792}

sr1646v2Lan3FGOamLocalInfoVendorInfo OBJECT-TYPE
   SYNTAX      OCTET STRING
   MAX-ACCESS  read-only
   STATUS      current
   DESCRIPTION
      "Path: ethernet3.status.oam.localInfo.vendorInfo"
   ::= {sr1646v2Lan3FGOamEntry 50659328}

sr1646v2Lan3FGOamLocalInfoVarRetrieval OBJECT-TYPE
   SYNTAX      INTEGER
               {
               notSupported (0),
               supported (1)
               }
   MAX-ACCESS  read-only
   STATUS      current
   DESCRIPTION
      "Path: ethernet3.status.oam.localInfo.varRetrieval

       Possibilities:
               notSupported   (0)
               supported   (1)"
   ::= {sr1646v2Lan3FGOamEntry 50724864}

sr1646v2Lan3FGOamLocalInfoLinkEvents OBJECT-TYPE
   SYNTAX      INTEGER
               {
               ignored (0),
               interpreted (1)
               }
   MAX-ACCESS  read-only
   STATUS      current
   DESCRIPTION
      "Path: ethernet3.status.oam.localInfo.linkEvents

       Possibilities:
               ignored   (0)
               interpreted   (1)"
   ::= {sr1646v2Lan3FGOamEntry 50790400}

sr1646v2Lan3FGOamLocalInfoLoopback OBJECT-TYPE
   SYNTAX      INTEGER
               {
               notSupported (0),
               supported (1)
               }
   MAX-ACCESS  read-only
   STATUS      current
   DESCRIPTION
      "Path: ethernet3.status.oam.localInfo.loopback

       Possibilities:
               notSupported   (0)
               supported   (1)"
   ::= {sr1646v2Lan3FGOamEntry 50855936}

sr1646v2Lan3FGOamLocalInfoUnidirectional OBJECT-TYPE
   SYNTAX      INTEGER
               {
               notSupported (0),
               supported (1)
               }
   MAX-ACCESS  read-only
   STATUS      current
   DESCRIPTION
      "Path: ethernet3.status.oam.localInfo.unidirectional

       Possibilities:
               notSupported   (0)
               supported   (1)"
   ::= {sr1646v2Lan3FGOamEntry 50921472}

sr1646v2Lan3FGOamLocalInfoMode OBJECT-TYPE
   SYNTAX      INTEGER
               {
               passive (0),
               active (1)
               }
   MAX-ACCESS  read-only
   STATUS      current
   DESCRIPTION
      "Path: ethernet3.status.oam.localInfo.mode

       Possibilities:
               passive   (0)
               active   (1)"
   ::= {sr1646v2Lan3FGOamEntry 50987008}

sr1646v2Lan3FGOamLocalInfoMaxPduSize OBJECT-TYPE
   SYNTAX      Integer32
   MAX-ACCESS  read-only
   STATUS      current
   DESCRIPTION
      "Path: ethernet3.status.oam.localInfo.maxPduSize"
   ::= {sr1646v2Lan3FGOamEntry 51052544}

sr1646v2Lan3FGOamRemoteInfoVersion OBJECT-TYPE
   SYNTAX      Integer32
   MAX-ACCESS  read-only
   STATUS      current
   DESCRIPTION
      "Path: ethernet3.status.oam.remoteInfo.version"
   ::= {sr1646v2Lan3FGOamEntry 67174400}

sr1646v2Lan3FGOamRemoteInfoRevision OBJECT-TYPE
   SYNTAX      Integer32
   MAX-ACCESS  read-only
   STATUS      current
   DESCRIPTION
      "Path: ethernet3.status.oam.remoteInfo.revision"
   ::= {sr1646v2Lan3FGOamEntry 67239936}

sr1646v2Lan3FGOamRemoteInfoStateMuxAction OBJECT-TYPE
   SYNTAX      INTEGER
               {
               forwarding (0),
               discarding (1)
               }
   MAX-ACCESS  read-only
   STATUS      current
   DESCRIPTION
      "Path: ethernet3.status.oam.remoteInfo.state.muxAction

       Possibilities:
               forwarding   (0)
               discarding   (1)"
   ::= {sr1646v2Lan3FGOamEntry 67305728}

sr1646v2Lan3FGOamRemoteInfoStateParserAction OBJECT-TYPE
   SYNTAX      INTEGER
               {
               forwarding (0),
               loopback (1),
               discarding (2),
               reserved (3)
               }
   MAX-ACCESS  read-only
   STATUS      current
   DESCRIPTION
      "Path: ethernet3.status.oam.remoteInfo.state.parserAction

       Possibilities:
               forwarding   (0)
               loopback   (1)
               discarding   (2)
               reserved   (3)"
   ::= {sr1646v2Lan3FGOamEntry 67305984}

sr1646v2Lan3FGOamRemoteInfoOui OBJECT-TYPE
   SYNTAX      OCTET STRING
   MAX-ACCESS  read-only
   STATUS      current
   DESCRIPTION
      "Path: ethernet3.status.oam.remoteInfo.oui"
   ::= {sr1646v2Lan3FGOamEntry 67371008}

sr1646v2Lan3FGOamRemoteInfoVendorInfo OBJECT-TYPE
   SYNTAX      OCTET STRING
   MAX-ACCESS  read-only
   STATUS      current
   DESCRIPTION
      "Path: ethernet3.status.oam.remoteInfo.vendorInfo"
   ::= {sr1646v2Lan3FGOamEntry 67436544}

sr1646v2Lan3FGOamRemoteInfoVarRetrieval OBJECT-TYPE
   SYNTAX      INTEGER
               {
               notSupported (0),
               supported (1)
               }
   MAX-ACCESS  read-only
   STATUS      current
   DESCRIPTION
      "Path: ethernet3.status.oam.remoteInfo.varRetrieval

       Possibilities:
               notSupported   (0)
               supported   (1)"
   ::= {sr1646v2Lan3FGOamEntry 67502080}

sr1646v2Lan3FGOamRemoteInfoLinkEvents OBJECT-TYPE
   SYNTAX      INTEGER
               {
               ignored (0),
               interpreted (1)
               }
   MAX-ACCESS  read-only
   STATUS      current
   DESCRIPTION
      "Path: ethernet3.status.oam.remoteInfo.linkEvents

       Possibilities:
               ignored   (0)
               interpreted   (1)"
   ::= {sr1646v2Lan3FGOamEntry 67567616}

sr1646v2Lan3FGOamRemoteInfoLoopback OBJECT-TYPE
   SYNTAX      INTEGER
               {
               notSupported (0),
               supported (1)
               }
   MAX-ACCESS  read-only
   STATUS      current
   DESCRIPTION
      "Path: ethernet3.status.oam.remoteInfo.loopback

       Possibilities:
               notSupported   (0)
               supported   (1)"
   ::= {sr1646v2Lan3FGOamEntry 67633152}

sr1646v2Lan3FGOamRemoteInfoUnidirectional OBJECT-TYPE
   SYNTAX      INTEGER
               {
               notSupported (0),
               supported (1)
               }
   MAX-ACCESS  read-only
   STATUS      current
   DESCRIPTION
      "Path: ethernet3.status.oam.remoteInfo.unidirectional

       Possibilities:
               notSupported   (0)
               supported   (1)"
   ::= {sr1646v2Lan3FGOamEntry 67698688}

sr1646v2Lan3FGOamRemoteInfoMode OBJECT-TYPE
   SYNTAX      INTEGER
               {
               passive (0),
               active (1)
               }
   MAX-ACCESS  read-only
   STATUS      current
   DESCRIPTION
      "Path: ethernet3.status.oam.remoteInfo.mode

       Possibilities:
               passive   (0)
               active   (1)"
   ::= {sr1646v2Lan3FGOamEntry 67764224}

sr1646v2Lan3FGOamRemoteInfoMaxPduSize OBJECT-TYPE
   SYNTAX      Integer32
   MAX-ACCESS  read-only
   STATUS      current
   DESCRIPTION
      "Path: ethernet3.status.oam.remoteInfo.maxPduSize"
   ::= {sr1646v2Lan3FGOamEntry 67829760}

sr1646v2Lan3FGOamEventsErroredSymbolWindow OBJECT-TYPE
   SYNTAX      Integer32
   UNITS       "symbols"
   MAX-ACCESS  read-only
   STATUS      current
   DESCRIPTION
      "Path: ethernet3.status.oam.events.erroredSymbol.window

       unit name = symbols"
   ::= {sr1646v2Lan3FGOamEntry 83951872}

sr1646v2Lan3FGOamEventsErroredSymbolThreshold OBJECT-TYPE
   SYNTAX      OCTET STRING
   UNITS       "symbols"
   MAX-ACCESS  read-only
   STATUS      current
   DESCRIPTION
      "Path: ethernet3.status.oam.events.erroredSymbol.threshold

       unit name = symbols"
   ::= {sr1646v2Lan3FGOamEntry 83952128}

sr1646v2Lan3FGOamEventsErroredFramePeriodWindow OBJECT-TYPE
   SYNTAX      INTEGER
               {
               default (0)
               }
   UNITS       "frames"
   MAX-ACCESS  read-only
   STATUS      current
   DESCRIPTION
      "Path: ethernet3.status.oam.events.erroredFramePeriod.window

       unit name = frames

       Possibilities:
               default   (0)"
   ::= {sr1646v2Lan3FGOamEntry 84017408}

sr1646v2Lan3FGOamEventsErroredFramePeriodThreshold OBJECT-TYPE
   SYNTAX      Integer32
   UNITS       "frames"
   MAX-ACCESS  read-only
   STATUS      current
   DESCRIPTION
      "Path: ethernet3.status.oam.events.erroredFramePeriod.threshold

       unit name = frames"
   ::= {sr1646v2Lan3FGOamEntry 84017664}

sr1646v2Lan3FGOamEventsErroredFrameWindow OBJECT-TYPE
   SYNTAX      Integer32
   UNITS       "100msec"
   MAX-ACCESS  read-only
   STATUS      current
   DESCRIPTION
      "Path: ethernet3.status.oam.events.erroredFrame.window

       unit name = 100msec"
   ::= {sr1646v2Lan3FGOamEntry 84082944}

sr1646v2Lan3FGOamEventsErroredFrameThreshold OBJECT-TYPE
   SYNTAX      Integer32
   UNITS       "frames"
   MAX-ACCESS  read-only
   STATUS      current
   DESCRIPTION
      "Path: ethernet3.status.oam.events.erroredFrame.threshold

       unit name = frames"
   ::= {sr1646v2Lan3FGOamEntry 84083200}

sr1646v2Lan3FGOamEventsErroredFrameSecondsWindow OBJECT-TYPE
   SYNTAX      Integer32
   UNITS       "100msec"
   MAX-ACCESS  read-only
   STATUS      current
   DESCRIPTION
      "Path: ethernet3.status.oam.events.erroredFrameSeconds.window

       unit name = 100msec"
   ::= {sr1646v2Lan3FGOamEntry 84148480}

sr1646v2Lan3FGOamEventsErroredFrameSecondsThreshold OBJECT-TYPE
   SYNTAX      Integer32
   UNITS       "frames"
   MAX-ACCESS  read-only
   STATUS      current
   DESCRIPTION
      "Path: ethernet3.status.oam.events.erroredFrameSeconds.threshold

       unit name = frames"
   ::= {sr1646v2Lan3FGOamEntry 84148736}


sr1646v2Lan3FGOamEventLog OBJECT IDENTIFIER ::= {sr1646v2Lan3FG 911}

sr1646v2Lan3FGOamEventLogSSCTable OBJECT-TYPE
   SYNTAX      SEQUENCE OF Sr1646v2Lan3FGOamEventLogEntry
   MAX-ACCESS  not-accessible
   STATUS      current
   DESCRIPTION
      "OAM event log"
   ::= {sr1646v2Lan3FGOamEventLog 1}

sr1646v2Lan3FGOamEventLogEntry OBJECT-TYPE
   SYNTAX      Sr1646v2Lan3FGOamEventLogEntry
   MAX-ACCESS  not-accessible
   STATUS      current
   DESCRIPTION
      ""
   INDEX      { sr1646v2Lan3FGOamEventLogTableIx }
   ::= {sr1646v2Lan3FGOamEventLogSSCTable 1}

Sr1646v2Lan3FGOamEventLogEntry ::=
   SEQUENCE
      {
      sr1646v2Lan3FGOamEventLogTableIx
         TableIndex,
      sr1646v2Lan3FGOamEventLogSysUpTime
         TimeTicks,
      sr1646v2Lan3FGOamEventLogLocation
         INTEGER,
      sr1646v2Lan3FGOamEventLogType
         INTEGER,
      sr1646v2Lan3FGOamEventLogOui
         OCTET STRING,
      sr1646v2Lan3FGOamEventLogWindow
         Counter64,
      sr1646v2Lan3FGOamEventLogThreshold
         Counter64,
      sr1646v2Lan3FGOamEventLogTotal
         Counter32,
      sr1646v2Lan3FGOamEventLogValue
         Counter64,
      sr1646v2Lan3FGOamEventLogRunningTotal
         Counter64
      }

sr1646v2Lan3FGOamEventLogTableIx OBJECT-TYPE
   SYNTAX      TableIndex
   MAX-ACCESS  not-accessible
   STATUS      current
   DESCRIPTION
      ""
   ::= {sr1646v2Lan3FGOamEventLogEntry 11}

sr1646v2Lan3FGOamEventLogSysUpTime OBJECT-TYPE
   SYNTAX      TimeTicks
   MAX-ACCESS  read-only
   STATUS      current
   DESCRIPTION
      "Path: ethernet3.status.oamEventLog.sysUpTime

       Time in centi-second."
   ::= {sr1646v2Lan3FGOamEventLogEntry 16777216}

sr1646v2Lan3FGOamEventLogLocation OBJECT-TYPE
   SYNTAX      INTEGER
               {
               local (1),
               remote (2)
               }
   MAX-ACCESS  read-only
   STATUS      current
   DESCRIPTION
      "Path: ethernet3.status.oamEventLog.location

       Possibilities:
               local   (1)
               remote   (2)"
   ::= {sr1646v2Lan3FGOamEventLogEntry 33554432}

sr1646v2Lan3FGOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: ethernet3.status.oamEventLog.type

       Possibilities:
               erroredSymbols   (1)
               erroredFramePeriod   (2)
               erroredFrame   (3)
               erroredFrameSeconds   (4)
               linkFault   (256)
               dyingGasp   (257)
               criticalLink   (258)"
   ::= {sr1646v2Lan3FGOamEventLogEntry 50331648}

sr1646v2Lan3FGOamEventLogOui OBJECT-TYPE
   SYNTAX      OCTET STRING
   MAX-ACCESS  read-only
   STATUS      current
   DESCRIPTION
      "Path: ethernet3.status.oamEventLog.oui"
   ::= {sr1646v2Lan3FGOamEventLogEntry 67108864}

sr1646v2Lan3FGOamEventLogWindow OBJECT-TYPE
   SYNTAX      Counter64
   MAX-ACCESS  read-only
   STATUS      current
   DESCRIPTION
      "Path: ethernet3.status.oamEventLog.window

       64 bit unsigned wrappable counter."
   ::= {sr1646v2Lan3FGOamEventLogEntry 83886080}

sr1646v2Lan3FGOamEventLogThreshold OBJECT-TYPE
   SYNTAX      Counter64
   MAX-ACCESS  read-only
   STATUS      current
   DESCRIPTION
      "Path: ethernet3.status.oamEventLog.threshold

       64 bit unsigned wrappable counter."
   ::= {sr1646v2Lan3FGOamEventLogEntry 100663296}

sr1646v2Lan3FGOamEventLogTotal OBJECT-TYPE
   SYNTAX      Counter32
   MAX-ACCESS  read-only
   STATUS      current
   DESCRIPTION
      "Path: ethernet3.status.oamEventLog.total

       32 bit unsigned wrappable counter."
   ::= {sr1646v2Lan3FGOamEventLogEntry 117440512}

sr1646v2Lan3FGOamEventLogValue OBJECT-TYPE
   SYNTAX      Counter64
   MAX-ACCESS  read-only
   STATUS      current
   DESCRIPTION
      "Path: ethernet3.status.oamEventLog.value

       64 bit unsigned wrappable counter."
   ::= {sr1646v2Lan3FGOamEventLogEntry 134217728}

sr1646v2Lan3FGOamEventLogRunningTotal OBJECT-TYPE
   SYNTAX      Counter64
   MAX-ACCESS  read-only
   STATUS      current
   DESCRIPTION
      "Path: ethernet3.status.oamEventLog.runningTotal

       64 bit unsigned wrappable counter."
   ::= {sr1646v2Lan3FGOamEventLogEntry 150994944}


sr1646v2Lan3FGLst OBJECT IDENTIFIER ::= {sr1646v2Lan3FG 18}

sr1646v2Lan3FGLstSSC OBJECT IDENTIFIER ::= {sr1646v2Lan3FGLst 1}

sr1646v2Lan3FGLstEntry OBJECT IDENTIFIER ::= {sr1646v2Lan3FGLstSSC 1}

sr1646v2Lan3FGLstTrackedInterface OBJECT-TYPE
   SYNTAX      DisplayString
   MAX-ACCESS  read-only
   STATUS      current
   DESCRIPTION
      "Path: ethernet3.status.linkStateTracking.trackedInterface"
   ::= {sr1646v2Lan3FGLstEntry 16777216}

sr1646v2Lan3FGLstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: ethernet3.status.linkStateTracking.ifOperStatus

       Possibilities:
               up   (1)
               down   (2)
               testing   (3)
               unknown   (4)
               dormant   (5)
               notPresent   (6)
               lowerLayerDown   (7)
                  (255)"
   ::= {sr1646v2Lan3FGLstEntry 50331648}


sr1646v2Lan3FGVlan OBJECT IDENTIFIER ::= {sr1646v2Lan3FG 34}

sr1646v2Lan3FGVlanSSCTable OBJECT-TYPE
   SYNTAX      SEQUENCE OF Sr1646v2Lan3FGVlanEntry
   MAX-ACCESS  not-accessible
   STATUS      current
   DESCRIPTION
      ""
   ::= {sr1646v2Lan3FGVlan 1}

sr1646v2Lan3FGVlanEntry OBJECT-TYPE
   SYNTAX      Sr1646v2Lan3FGVlanEntry
   MAX-ACCESS  not-accessible
   STATUS      current
   DESCRIPTION
      ""
   INDEX      { sr1646v2Lan3FGVlanTableIx }
   ::= {sr1646v2Lan3FGVlanSSCTable 1}

Sr1646v2Lan3FGVlanEntry ::=
   SEQUENCE
      {
      sr1646v2Lan3FGVlanTableIx
         TableIndex,
      sr1646v2Lan3FGVlanName
         DisplayString,
      sr1646v2Lan3FGVlanMode
         INTEGER,
      sr1646v2Lan3FGVlanIfOperStatus
         INTEGER,
      sr1646v2Lan3FGVlanIfLastChange
         TimeTicks,
      sr1646v2Lan3FGVlanIfLastChangeDate
         DisplayString,
      sr1646v2Lan3FGVlanIpAddress
         IpAddress,
      sr1646v2Lan3FGVlanIpNetMask
         IpAddress,
      sr1646v2Lan3FGVlanIpRemote
         IpAddress,
      sr1646v2Lan3FGVlanIpDhcpStatus
         INTEGER,
      sr1646v2Lan3FGVlanIpDhcpLeaseTime
         TimeTicks,
      sr1646v2Lan3FGVlanIpV6State
         INTEGER,
      sr1646v2Lan3FGVlanIpV6InterfaceId
         OCTET STRING,
      sr1646v2Lan3FGVlanIpV6LinkMtu
         Integer32,
      sr1646v2Lan3FGVlanIpV6HopLimit
         Integer32,
      sr1646v2Lan3FGVlanIpV6DhcpIaid
         Counter32,
      sr1646v2Lan3FGVlanIpV6RaRcvOption
         Integer32,
      sr1646v2Lan3FGVlanBridgingStatus
         INTEGER,
      sr1646v2Lan3FGVlanBridgingSpanningTreePortRole
         INTEGER,
      sr1646v2Lan3FGVlanBridgingSpanningTreePortId
         Integer32,
      sr1646v2Lan3FGVlanBridgingSpanningTreePpCostExtPathCost
         Integer32,
      sr1646v2Lan3FGVlanBridgingSpanningTreePpCostIntPathCost
         Integer32,
      sr1646v2Lan3FGVlanBridgingSpanningTreeExtRpCost
         Integer32,
      sr1646v2Lan3FGVlanBridgingSpanningTreeIntRpCost
         Integer32,
      sr1646v2Lan3FGVlanBridgingSpanningTreeDesBrIdPriority
         Integer32,
      sr1646v2Lan3FGVlanBridgingSpanningTreeDesBrIdMacAddress
         OCTET STRING,
      sr1646v2Lan3FGVlanBridgingSpanningTreeDesPrtId
         Integer32,
      sr1646v2Lan3FGVlanBridgingSpanningTreeDesInt
         INTEGER,
      sr1646v2Lan3FGVlanBridgingSpanningTreeEdgeDetection
         INTEGER,
      sr1646v2Lan3FGVlanVlanVid
         Integer32,
      sr1646v2Lan3FGVlanPppOEthDiscState
         INTEGER,
      sr1646v2Lan3FGVlanPppOEthPeerMac
         OCTET STRING,
      sr1646v2Lan3FGVlanPppOEthServiceName
         DisplayString,
      sr1646v2Lan3FGVlanPppLcpState
         INTEGER,
      sr1646v2Lan3FGVlanPppIpcpState
         INTEGER,
      sr1646v2Lan3FGVlanPppIp6cpState
         INTEGER,
      sr1646v2Lan3FGVlanPppMyAutSt
         INTEGER,
      sr1646v2Lan3FGVlanPppHisAutSt
         INTEGER,
      sr1646v2Lan3FGVlanPppMru
         Integer32
      }

sr1646v2Lan3FGVlanTableIx OBJECT-TYPE
   SYNTAX      TableIndex
   MAX-ACCESS  not-accessible
   STATUS      current
   DESCRIPTION
      ""
   ::= {sr1646v2Lan3FGVlanEntry 11}

sr1646v2Lan3FGVlanName OBJECT-TYPE
   SYNTAX      DisplayString
   MAX-ACCESS  read-only
   STATUS      current
   DESCRIPTION
      "Path: ethernet3.status.vlan.name"
   ::= {sr1646v2Lan3FGVlanEntry 16777216}

sr1646v2Lan3FGVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet3.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2Lan3FGVlanEntry 335544320}

sr1646v2Lan3FGVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.vlan.ifOperStatus

       Possibilities:
               up   (1)
               down   (2)
               testing   (3)
               unknown   (4)
               dormant   (5)
               notPresent   (6)
               lowerLayerDown   (7)"
   ::= {sr1646v2Lan3FGVlanEntry 1795162112}

sr1646v2Lan3FGVlanIfLastChange OBJECT-TYPE
   SYNTAX      TimeTicks
   MAX-ACCESS  read-only
   STATUS      current
   DESCRIPTION
      "Path: ethernet3.status.vlan.ifLastChange

       Time in centi-second."
   ::= {sr1646v2Lan3FGVlanEntry 1811939328}

sr1646v2Lan3FGVlanIfLastChangeDate OBJECT-TYPE
   SYNTAX      DisplayString
   MAX-ACCESS  read-only
   STATUS      current
   DESCRIPTION
      "Path: ethernet3.status.vlan.ifLastChangeDate"
   ::= {sr1646v2Lan3FGVlanEntry 3070230528}

sr1646v2Lan3FGVlanIpAddress OBJECT-TYPE
   SYNTAX      IpAddress
   MAX-ACCESS  read-only
   STATUS      current
   DESCRIPTION
      "Path: ethernet3.status.vlan.ip.address"
   ::= {sr1646v2Lan3FGVlanEntry 51380224}

sr1646v2Lan3FGVlanIpNetMask OBJECT-TYPE
   SYNTAX      IpAddress
   MAX-ACCESS  read-only
   STATUS      current
   DESCRIPTION
      "Path: ethernet3.status.vlan.ip.netMask"
   ::= {sr1646v2Lan3FGVlanEntry 51445760}

sr1646v2Lan3FGVlanIpRemote OBJECT-TYPE
   SYNTAX      IpAddress
   MAX-ACCESS  read-only
   STATUS      current
   DESCRIPTION
      "Path: ethernet3.status.vlan.ip.remote"
   ::= {sr1646v2Lan3FGVlanEntry 51511296}

sr1646v2Lan3FGVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet3.status.vlan.ip.dhcp.status

       Possibilities:
               none   (0)
               selecting   (1)
               requesting   (2)
               rebinding   (3)
               bound   (4)
               renewing   (5)
               rebooting   (6)
               initreboot   (7)"
   ::= {sr1646v2Lan3FGVlanEntry 51904768}

sr1646v2Lan3FGVlanIpDhcpLeaseTime OBJECT-TYPE
   SYNTAX      TimeTicks
   MAX-ACCESS  read-only
   STATUS      current
   DESCRIPTION
      "Path: ethernet3.status.vlan.ip.dhcp.leaseTime

       Time in centi-second."
   ::= {sr1646v2Lan3FGVlanEntry 51905024}

sr1646v2Lan3FGVlanIpV6State OBJECT-TYPE
   SYNTAX      INTEGER
               {
               disabled (0),
               enabled (1)
               }
   MAX-ACCESS  read-only
   STATUS      current
   DESCRIPTION
      "Path: ethernet3.status.vlan.ipV6.state

       Possibilities:
               disabled   (0)
               enabled   (1)"
   ::= {sr1646v2Lan3FGVlanEntry 100728832}

sr1646v2Lan3FGVlanIpV6InterfaceId OBJECT-TYPE
   SYNTAX      OCTET STRING
   MAX-ACCESS  read-only
   STATUS      current
   DESCRIPTION
      "Path: ethernet3.status.vlan.ipV6.interfaceId"
   ::= {sr1646v2Lan3FGVlanEntry 100794368}

sr1646v2Lan3FGVlanIpV6LinkMtu OBJECT-TYPE
   SYNTAX      Integer32
   MAX-ACCESS  read-only
   STATUS      current
   DESCRIPTION
      "Path: ethernet3.status.vlan.ipV6.linkMtu"
   ::= {sr1646v2Lan3FGVlanEntry 100925440}

sr1646v2Lan3FGVlanIpV6HopLimit OBJECT-TYPE
   SYNTAX      Integer32
   MAX-ACCESS  read-only
   STATUS      current
   DESCRIPTION
      "Path: ethernet3.status.vlan.ipV6.hopLimit"
   ::= {sr1646v2Lan3FGVlanEntry 100990976}

sr1646v2Lan3FGVlanIpV6DhcpIaid OBJECT-TYPE
   SYNTAX      Counter32
   MAX-ACCESS  read-only
   STATUS      current
   DESCRIPTION
      "Path: ethernet3.status.vlan.ipV6.dhcp.iaid

       32 bit unsigned wrappable counter."
   ::= {sr1646v2Lan3FGVlanEntry 101056768}

sr1646v2Lan3FGVlanIpV6RaRcvOption OBJECT-TYPE
   SYNTAX      Integer32
   MAX-ACCESS  read-only
   STATUS      current
   DESCRIPTION
      "Path: ethernet3.status.vlan.ipV6.raRcvOption

       Bit meanings:
               bit 0 = linkMtu,
               bit 1 = srcLinkLayer,
               bit 2 = prefixInfo,
               bit 3 = rdnss,
               bit 4 = dnssl"
   ::= {sr1646v2Lan3FGVlanEntry 101122048}

sr1646v2Lan3FGVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet3.status.vlan.bridging.status

       Possibilities:
               disabled   (0)
               discarding   (1)
               learning   (2)
               forwarding   (3)
               backupBlockedIntfDown   (256)
               backupBlockedIntfUp   (259)
               shutdown   (255)"
   ::= {sr1646v2Lan3FGVlanEntry 453050368}

sr1646v2Lan3FGVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: ethernet3.status.vlan.bridging.spanningTree.portRole

       Possibilities:
               none   (0)
               root   (1)
               designated   (2)
               alternate   (3)
               backup   (4)
               disabled   (5)
               master   (6)"
   ::= {sr1646v2Lan3FGVlanEntry 453116160}

sr1646v2Lan3FGVlanBridgingSpanningTreePortId OBJECT-TYPE
   SYNTAX      Integer32
   MAX-ACCESS  read-only
   STATUS      current
   DESCRIPTION
      "Path: ethernet3.status.vlan.bridging.spanningTree.portId"
   ::= {sr1646v2Lan3FGVlanEntry 453116416}

sr1646v2Lan3FGVlanBridgingSpanningTreePpCostExtPathCost OBJECT-TYPE
   SYNTAX      Integer32
   MAX-ACCESS  read-only
   STATUS      current
   DESCRIPTION
      "Path: ethernet3.status.vlan.bridging.spanningTree.portPathCosts.extPathCost"
   ::= {sr1646v2Lan3FGVlanEntry 453116673}

sr1646v2Lan3FGVlanBridgingSpanningTreePpCostIntPathCost OBJECT-TYPE
   SYNTAX      Integer32
   MAX-ACCESS  read-only
   STATUS      current
   DESCRIPTION
      "Path: ethernet3.status.vlan.bridging.spanningTree.portPathCosts.intPathCost"
   ::= {sr1646v2Lan3FGVlanEntry 453116674}

sr1646v2Lan3FGVlanBridgingSpanningTreeExtRpCost OBJECT-TYPE
   SYNTAX      Integer32
   MAX-ACCESS  read-only
   STATUS      current
   DESCRIPTION
      "Path: ethernet3.status.vlan.bridging.spanningTree.extRootPathCost"
   ::= {sr1646v2Lan3FGVlanEntry 453116928}

sr1646v2Lan3FGVlanBridgingSpanningTreeIntRpCost OBJECT-TYPE
   SYNTAX      Integer32
   MAX-ACCESS  read-only
   STATUS      current
   DESCRIPTION
      "Path: ethernet3.status.vlan.bridging.spanningTree.intRootPathCost"
   ::= {sr1646v2Lan3FGVlanEntry 453117184}

sr1646v2Lan3FGVlanBridgingSpanningTreeDesBrIdPriority OBJECT-TYPE
   SYNTAX      Integer32
   MAX-ACCESS  read-only
   STATUS      current
   DESCRIPTION
      "Path: ethernet3.status.vlan.bridging.spanningTree.designatedBridgeId.priority"
   ::= {sr1646v2Lan3FGVlanEntry 453117441}

sr1646v2Lan3FGVlanBridgingSpanningTreeDesBrIdMacAddress OBJECT-TYPE
   SYNTAX      OCTET STRING
   MAX-ACCESS  read-only
   STATUS      current
   DESCRIPTION
      "Path: ethernet3.status.vlan.bridging.spanningTree.designatedBridgeId.macAddress

       MAC address."
   ::= {sr1646v2Lan3FGVlanEntry 453117442}

sr1646v2Lan3FGVlanBridgingSpanningTreeDesPrtId OBJECT-TYPE
   SYNTAX      Integer32
   MAX-ACCESS  read-only
   STATUS      current
   DESCRIPTION
      "Path: ethernet3.status.vlan.bridging.spanningTree.designatedPortId"
   ::= {sr1646v2Lan3FGVlanEntry 453117696}

sr1646v2Lan3FGVlanBridgingSpanningTreeDesInt OBJECT-TYPE
   SYNTAX      INTEGER
               {
               no (0),
               yes (1)
               }
   MAX-ACCESS  read-only
   STATUS      current
   DESCRIPTION
      "Path: ethernet3.status.vlan.bridging.spanningTree.designatedOrInternal

       Possibilities:
               no   (0)
               yes   (1)"
   ::= {sr1646v2Lan3FGVlanEntry 453117952}

sr1646v2Lan3FGVlanBridgingSpanningTreeEdgeDetection OBJECT-TYPE
   SYNTAX      INTEGER
               {
               none (0),
               edge (1),
               notEdge (2)
               }
   MAX-ACCESS  read-only
   STATUS      current
   DESCRIPTION
      "Path: ethernet3.status.vlan.bridging.spanningTree.edgeDetection

       Possibilities:
               none   (0)
               edge   (1)
               notEdge   (2)"
   ::= {sr1646v2Lan3FGVlanEntry 453118208}

sr1646v2Lan3FGVlanVlanVid OBJECT-TYPE
   SYNTAX      Integer32
   MAX-ACCESS  read-only
   STATUS      current
   DESCRIPTION
      "Path: ethernet3.status.vlan.vlan.vid"
   ::= {sr1646v2Lan3FGVlanEntry 234946560}

sr1646v2Lan3FGVlanPppOEthDiscState OBJECT-TYPE
   SYNTAX      INTEGER
               {
               idle (0),
               waitForPADO (1),
               waitForPADS (2),
               established (3)
               }
   MAX-ACCESS  read-only
   STATUS      current
   DESCRIPTION
      "Path: ethernet3.status.vlan.pppOverEth.discState

       Possibilities:
               idle   (0)
               waitForPADO   (1)
               waitForPADS   (2)
               established   (3)"
   ::= {sr1646v2Lan3FGVlanEntry 67174400}

sr1646v2Lan3FGVlanPppOEthPeerMac OBJECT-TYPE
   SYNTAX      OCTET STRING
   MAX-ACCESS  read-only
   STATUS      current
   DESCRIPTION
      "Path: ethernet3.status.vlan.pppOverEth.remoteMacAddress

       MAC address."
   ::= {sr1646v2Lan3FGVlanEntry 67239936}

sr1646v2Lan3FGVlanPppOEthServiceName OBJECT-TYPE
   SYNTAX      DisplayString
   MAX-ACCESS  read-only
   STATUS      current
   DESCRIPTION
      "Path: ethernet3.status.vlan.pppOverEth.serviceName"
   ::= {sr1646v2Lan3FGVlanEntry 67305472}

sr1646v2Lan3FGVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2Lan3FGVlanEntry 83951616}

sr1646v2Lan3FGVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2Lan3FGVlanEntry 84017152}

sr1646v2Lan3FGVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2Lan3FGVlanEntry 84869120}

sr1646v2Lan3FGVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet3.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2Lan3FGVlanEntry 84541440}

sr1646v2Lan3FGVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet3.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2Lan3FGVlanEntry 84606976}

sr1646v2Lan3FGVlanPppMru OBJECT-TYPE
   SYNTAX      Integer32
   MAX-ACCESS  read-only
   STATUS      current
   DESCRIPTION
      "Path: ethernet3.status.vlan.ppp.mru"
   ::= {sr1646v2Lan3FGVlanEntry 84934656}

sr1646v2Lan3FGVlanIpSecondaryIp OBJECT-TYPE
   SYNTAX      SEQUENCE OF Sr1646v2Lan3FGVlanIpSecondaryIpEntry
   MAX-ACCESS  not-accessible
   STATUS      current
   DESCRIPTION
      ""
   ::= {sr1646v2Lan3FGVlan 51838976}

sr1646v2Lan3FGVlanIpSecondaryIpEntry OBJECT-TYPE
   SYNTAX      Sr1646v2Lan3FGVlanIpSecondaryIpEntry
   MAX-ACCESS  not-accessible
   STATUS      current
   DESCRIPTION
      ""
   INDEX      { sr1646v2Lan3FGVlanTableIx,
                sr1646v2Lan3FGVlanIpSecondaryIpTableIx }
   ::= {sr1646v2Lan3FGVlanIpSecondaryIp 1}

Sr1646v2Lan3FGVlanIpSecondaryIpEntry ::=
   SEQUENCE
      {
      sr1646v2Lan3FGVlanIpSecondaryIpTableIx
         TableIndex,
      sr1646v2Lan3FGVlanIpSecondaryIpAddress
         IpAddress,
      sr1646v2Lan3FGVlanIpSecondaryIpNetMask
         IpAddress
      }

sr1646v2Lan3FGVlanIpSecondaryIpTableIx OBJECT-TYPE
   SYNTAX      TableIndex
   MAX-ACCESS  not-accessible
   STATUS      current
   DESCRIPTION
      ""
   ::= {sr1646v2Lan3FGVlanIpSecondaryIpEntry 11}

sr1646v2Lan3FGVlanIpSecondaryIpAddress OBJECT-TYPE
   SYNTAX      IpAddress
   MAX-ACCESS  read-only
   STATUS      current
   DESCRIPTION
      "Path: ethernet3.status.vlan.ip.secondaryIp.address"
   ::= {sr1646v2Lan3FGVlanIpSecondaryIpEntry 2030043136}

sr1646v2Lan3FGVlanIpSecondaryIpNetMask OBJECT-TYPE
   SYNTAX      IpAddress
   MAX-ACCESS  read-only
   STATUS      current
   DESCRIPTION
      "Path: ethernet3.status.vlan.ip.secondaryIp.netMask"
   ::= {sr1646v2Lan3FGVlanIpSecondaryIpEntry 2063597568}

sr1646v2Lan3FGVlanIpV6Addresses OBJECT-TYPE
   SYNTAX      SEQUENCE OF Sr1646v2Lan3FGVlanIpV6AddressesEntry
   MAX-ACCESS  not-accessible
   STATUS      current
   DESCRIPTION
      ""
   ::= {sr1646v2Lan3FGVlan 100859904}

sr1646v2Lan3FGVlanIpV6AddressesEntry OBJECT-TYPE
   SYNTAX      Sr1646v2Lan3FGVlanIpV6AddressesEntry
   MAX-ACCESS  not-accessible
   STATUS      current
   DESCRIPTION
      ""
   INDEX      { sr1646v2Lan3FGVlanTableIx,
                sr1646v2Lan3FGVlanIpV6AddressesTableIx }
   ::= {sr1646v2Lan3FGVlanIpV6Addresses 1}

Sr1646v2Lan3FGVlanIpV6AddressesEntry ::=
   SEQUENCE
      {
      sr1646v2Lan3FGVlanIpV6AddressesTableIx
         TableIndex,
      sr1646v2Lan3FGVlanIpV6AddressesAddress
         Ipv6Address,
      sr1646v2Lan3FGVlanIpV6AddressesPrefixLength
         Integer32,
      sr1646v2Lan3FGVlanIpV6AddressesStatus
         INTEGER,
      sr1646v2Lan3FGVlanIpV6AddressesOrigin
         INTEGER,
      sr1646v2Lan3FGVlanIpV6AddressesFlagsInterfaceId
         INTEGER,
      sr1646v2Lan3FGVlanIpV6AddressesFlagsAnycast
         INTEGER,
      sr1646v2Lan3FGVlanIpV6AddressesTimersValidLifeTime
         TimeTicks,
      sr1646v2Lan3FGVlanIpV6AddressesTimersPrefLifeTime
         TimeTicks
      }

sr1646v2Lan3FGVlanIpV6AddressesTableIx OBJECT-TYPE
   SYNTAX      TableIndex
   MAX-ACCESS  not-accessible
   STATUS      current
   DESCRIPTION
      ""
   ::= {sr1646v2Lan3FGVlanIpV6AddressesEntry 11}

sr1646v2Lan3FGVlanIpV6AddressesAddress OBJECT-TYPE
   SYNTAX      Ipv6Address
   MAX-ACCESS  read-only
   STATUS      current
   DESCRIPTION
      "Path: ethernet3.status.vlan.ipV6.addresses.address

       ipv6 address"
   ::= {sr1646v2Lan3FGVlanIpV6AddressesEntry 16777216}

sr1646v2Lan3FGVlanIpV6AddressesPrefixLength OBJECT-TYPE
   SYNTAX      Integer32
   MAX-ACCESS  read-only
   STATUS      current
   DESCRIPTION
      "Path: ethernet3.status.vlan.ipV6.addresses.prefixLength"
   ::= {sr1646v2Lan3FGVlanIpV6AddressesEntry 33554432}

sr1646v2Lan3FGVlanIpV6AddressesStatus OBJECT-TYPE
   SYNTAX      INTEGER
               {
               invalid (0),
               tentative (1),
               deprecated (2),
               preferred (3)
               }
   MAX-ACCESS  read-only
   STATUS      current
   DESCRIPTION
      "Path: ethernet3.status.vlan.ipV6.addresses.status

       Possibilities:
               invalid   (0)
               tentative   (1)
               deprecated   (2)
               preferred   (3)"
   ::= {sr1646v2Lan3FGVlanIpV6AddressesEntry 50331648}

sr1646v2Lan3FGVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.vlan.ipV6.addresses.origin

       Possibilities:
               unknown   (0)
               manual   (1)
               generalPrefix   (2)
               statelessAuto   (3)
               statefullAuto   (4)"
   ::= {sr1646v2Lan3FGVlanIpV6AddressesEntry 67108864}

sr1646v2Lan3FGVlanIpV6AddressesFlagsInterfaceId OBJECT-TYPE
   SYNTAX      INTEGER
               {
               no (0),
               yes (1)
               }
   MAX-ACCESS  read-only
   STATUS      current
   DESCRIPTION
      "Path: ethernet3.status.vlan.ipV6.addresses.flags.interfaceId

       Possibilities:
               no   (0)
               yes   (1)"
   ::= {sr1646v2Lan3FGVlanIpV6AddressesEntry 83951616}

sr1646v2Lan3FGVlanIpV6AddressesFlagsAnycast OBJECT-TYPE
   SYNTAX      INTEGER
               {
               no (0),
               yes (1)
               }
   MAX-ACCESS  read-only
   STATUS      current
   DESCRIPTION
      "Path: ethernet3.status.vlan.ipV6.addresses.flags.anycast

       Possibilities:
               no   (0)
               yes   (1)"
   ::= {sr1646v2Lan3FGVlanIpV6AddressesEntry 84017152}

sr1646v2Lan3FGVlanIpV6AddressesTimersValidLifeTime OBJECT-TYPE
   SYNTAX      TimeTicks
   MAX-ACCESS  read-only
   STATUS      current
   DESCRIPTION
      "Path: ethernet3.status.vlan.ipV6.addresses.timers.validLifeTime

       Time in centi-second."
   ::= {sr1646v2Lan3FGVlanIpV6AddressesEntry 100794368}

sr1646v2Lan3FGVlanIpV6AddressesTimersPrefLifeTime OBJECT-TYPE
   SYNTAX      TimeTicks
   MAX-ACCESS  read-only
   STATUS      current
   DESCRIPTION
      "Path: ethernet3.status.vlan.ipV6.addresses.timers.prefLifeTime

       Time in centi-second."
   ::= {sr1646v2Lan3FGVlanIpV6AddressesEntry 100728832}

sr1646v2Lan3FGVlanVlanArpCache OBJECT-TYPE
   SYNTAX      SEQUENCE OF Sr1646v2Lan3FGVlanVlanArpCacheEntry
   MAX-ACCESS  not-accessible
   STATUS      current
   DESCRIPTION
      ""
   ::= {sr1646v2Lan3FGVlan 235601920}

sr1646v2Lan3FGVlanVlanArpCacheEntry OBJECT-TYPE
   SYNTAX      Sr1646v2Lan3FGVlanVlanArpCacheEntry
   MAX-ACCESS  not-accessible
   STATUS      current
   DESCRIPTION
      ""
   INDEX      { sr1646v2Lan3FGVlanTableIx,
                sr1646v2Lan3FGVlanVlanArpCacheTableIx }
   ::= {sr1646v2Lan3FGVlanVlanArpCache 1}

Sr1646v2Lan3FGVlanVlanArpCacheEntry ::=
   SEQUENCE
      {
      sr1646v2Lan3FGVlanVlanArpCacheTableIx
         TableIndex,
      sr1646v2Lan3FGVlanVlanArpCacheMacAddress
         OCTET STRING,
      sr1646v2Lan3FGVlanVlanArpCacheIpAddress
         IpAddress,
      sr1646v2Lan3FGVlanVlanArpCacheType
         INTEGER,
      sr1646v2Lan3FGVlanVlanArpCacheTimeOut
         TimeTicks
      }

sr1646v2Lan3FGVlanVlanArpCacheTableIx OBJECT-TYPE
   SYNTAX      TableIndex
   MAX-ACCESS  not-accessible
   STATUS      current
   DESCRIPTION
      ""
   ::= {sr1646v2Lan3FGVlanVlanArpCacheEntry 11}

sr1646v2Lan3FGVlanVlanArpCacheMacAddress OBJECT-TYPE
   SYNTAX      OCTET STRING
   MAX-ACCESS  read-only
   STATUS      current
   DESCRIPTION
      "Path: ethernet3.status.vlan.vlan.arpCache.macAddress

       MAC address."
   ::= {sr1646v2Lan3FGVlanVlanArpCacheEntry 16777216}

sr1646v2Lan3FGVlanVlanArpCacheIpAddress OBJECT-TYPE
   SYNTAX      IpAddress
   MAX-ACCESS  read-only
   STATUS      current
   DESCRIPTION
      "Path: ethernet3.status.vlan.vlan.arpCache.ipAddress"
   ::= {sr1646v2Lan3FGVlanVlanArpCacheEntry 33554432}

sr1646v2Lan3FGVlanVlanArpCacheType OBJECT-TYPE
   SYNTAX      INTEGER
               {
               static (0),
               dynamic (1)
               }
   MAX-ACCESS  read-only
   STATUS      current
   DESCRIPTION
      "Path: ethernet3.status.vlan.vlan.arpCache.type

       Possibilities:
               static   (0)
               dynamic   (1)"
   ::= {sr1646v2Lan3FGVlanVlanArpCacheEntry 50331648}

sr1646v2Lan3FGVlanVlanArpCacheTimeOut OBJECT-TYPE
   SYNTAX      TimeTicks
   MAX-ACCESS  read-only
   STATUS      current
   DESCRIPTION
      "Path: ethernet3.status.vlan.vlan.arpCache.timeOut

       Time in centi-second."
   ::= {sr1646v2Lan3FGVlanVlanArpCacheEntry 67108864}


sr1646v2Lan3FGPppOE OBJECT IDENTIFIER ::= {sr1646v2Lan3FG 36}

sr1646v2Lan3FGPppOESSCTable OBJECT-TYPE
   SYNTAX      SEQUENCE OF Sr1646v2Lan3FGPppOEEntry
   MAX-ACCESS  not-accessible
   STATUS      current
   DESCRIPTION
      ""
   ::= {sr1646v2Lan3FGPppOE 1}

sr1646v2Lan3FGPppOEEntry OBJECT-TYPE
   SYNTAX      Sr1646v2Lan3FGPppOEEntry
   MAX-ACCESS  not-accessible
   STATUS      current
   DESCRIPTION
      ""
   INDEX      { sr1646v2Lan3FGPppOETableIx }
   ::= {sr1646v2Lan3FGPppOESSCTable 1}

Sr1646v2Lan3FGPppOEEntry ::=
   SEQUENCE
      {
      sr1646v2Lan3FGPppOETableIx
         TableIndex,
      sr1646v2Lan3FGPppOEName
         DisplayString,
      sr1646v2Lan3FGPppOEMode
         INTEGER,
      sr1646v2Lan3FGPppOEIfOperStatus
         INTEGER,
      sr1646v2Lan3FGPppOEIfLastChange
         TimeTicks,
      sr1646v2Lan3FGPppOEIfLastChangeDate
         DisplayString,
      sr1646v2Lan3FGPppOEIpAddress
         IpAddress,
      sr1646v2Lan3FGPppOEIpNetMask
         IpAddress,
      sr1646v2Lan3FGPppOEIpRemote
         IpAddress,
      sr1646v2Lan3FGPppOEPppOEthDiscState
         INTEGER,
      sr1646v2Lan3FGPppOEPppOEthPeerMac
         OCTET STRING,
      sr1646v2Lan3FGPppOEPppOEthServiceName
         DisplayString,
      sr1646v2Lan3FGPppOEPppLcpState
         INTEGER,
      sr1646v2Lan3FGPppOEPppIpcpState
         INTEGER,
      sr1646v2Lan3FGPppOEPppIp6cpState
         INTEGER,
      sr1646v2Lan3FGPppOEPppMyAutSt
         INTEGER,
      sr1646v2Lan3FGPppOEPppHisAutSt
         INTEGER,
      sr1646v2Lan3FGPppOEPppMru
         Integer32,
      sr1646v2Lan3FGPppOEIpV6State
         INTEGER,
      sr1646v2Lan3FGPppOEIpV6InterfaceId
         OCTET STRING,
      sr1646v2Lan3FGPppOEIpV6LinkMtu
         Integer32,
      sr1646v2Lan3FGPppOEIpV6HopLimit
         Integer32,
      sr1646v2Lan3FGPppOEIpV6DhcpIaid
         Counter32,
      sr1646v2Lan3FGPppOEIpV6RaRcvOption
         Integer32
      }

sr1646v2Lan3FGPppOETableIx OBJECT-TYPE
   SYNTAX      TableIndex
   MAX-ACCESS  not-accessible
   STATUS      current
   DESCRIPTION
      ""
   ::= {sr1646v2Lan3FGPppOEEntry 11}

sr1646v2Lan3FGPppOEName OBJECT-TYPE
   SYNTAX      DisplayString
   MAX-ACCESS  read-only
   STATUS      current
   DESCRIPTION
      "Path: ethernet3.status.pppoEClient.name"
   ::= {sr1646v2Lan3FGPppOEEntry 16777216}

sr1646v2Lan3FGPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet3.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2Lan3FGPppOEEntry 335544320}

sr1646v2Lan3FGPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet3.status.pppoEClient.ifOperStatus

       Possibilities:
               up   (1)
               down   (2)
               testing   (3)
               unknown   (4)
               dormant   (5)
               notPresent   (6)
               lowerLayerDown   (7)"
   ::= {sr1646v2Lan3FGPppOEEntry 1795162112}

sr1646v2Lan3FGPppOEIfLastChange OBJECT-TYPE
   SYNTAX      TimeTicks
   MAX-ACCESS  read-only
   STATUS      current
   DESCRIPTION
      "Path: ethernet3.status.pppoEClient.ifLastChange

       Time in centi-second."
   ::= {sr1646v2Lan3FGPppOEEntry 1811939328}

sr1646v2Lan3FGPppOEIfLastChangeDate OBJECT-TYPE
   SYNTAX      DisplayString
   MAX-ACCESS  read-only
   STATUS      current
   DESCRIPTION
      "Path: ethernet3.status.pppoEClient.ifLastChangeDate"
   ::= {sr1646v2Lan3FGPppOEEntry 3070230528}

sr1646v2Lan3FGPppOEIpAddress OBJECT-TYPE
   SYNTAX      IpAddress
   MAX-ACCESS  read-only
   STATUS      current
   DESCRIPTION
      "Path: ethernet3.status.pppoEClient.ip.address"
   ::= {sr1646v2Lan3FGPppOEEntry 51380224}

sr1646v2Lan3FGPppOEIpNetMask OBJECT-TYPE
   SYNTAX      IpAddress
   MAX-ACCESS  read-only
   STATUS      current
   DESCRIPTION
      "Path: ethernet3.status.pppoEClient.ip.netMask"
   ::= {sr1646v2Lan3FGPppOEEntry 51445760}

sr1646v2Lan3FGPppOEIpRemote OBJECT-TYPE
   SYNTAX      IpAddress
   MAX-ACCESS  read-only
   STATUS      current
   DESCRIPTION
      "Path: ethernet3.status.pppoEClient.ip.remote"
   ::= {sr1646v2Lan3FGPppOEEntry 51511296}

sr1646v2Lan3FGPppOEPppOEthDiscState OBJECT-TYPE
   SYNTAX      INTEGER
               {
               idle (0),
               waitForPADO (1),
               waitForPADS (2),
               established (3)
               }
   MAX-ACCESS  read-only
   STATUS      current
   DESCRIPTION
      "Path: ethernet3.status.pppoEClient.pppOverEth.discState

       Possibilities:
               idle   (0)
               waitForPADO   (1)
               waitForPADS   (2)
               established   (3)"
   ::= {sr1646v2Lan3FGPppOEEntry 67174400}

sr1646v2Lan3FGPppOEPppOEthPeerMac OBJECT-TYPE
   SYNTAX      OCTET STRING
   MAX-ACCESS  read-only
   STATUS      current
   DESCRIPTION
      "Path: ethernet3.status.pppoEClient.pppOverEth.remoteMacAddress

       MAC address."
   ::= {sr1646v2Lan3FGPppOEEntry 67239936}

sr1646v2Lan3FGPppOEPppOEthServiceName OBJECT-TYPE
   SYNTAX      DisplayString
   MAX-ACCESS  read-only
   STATUS      current
   DESCRIPTION
      "Path: ethernet3.status.pppoEClient.pppOverEth.serviceName"
   ::= {sr1646v2Lan3FGPppOEEntry 67305472}

sr1646v2Lan3FGPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2Lan3FGPppOEEntry 83951616}

sr1646v2Lan3FGPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2Lan3FGPppOEEntry 84017152}

sr1646v2Lan3FGPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet3.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2Lan3FGPppOEEntry 84869120}

sr1646v2Lan3FGPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet3.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2Lan3FGPppOEEntry 84541440}

sr1646v2Lan3FGPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet3.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2Lan3FGPppOEEntry 84606976}

sr1646v2Lan3FGPppOEPppMru OBJECT-TYPE
   SYNTAX      Integer32
   MAX-ACCESS  read-only
   STATUS      current
   DESCRIPTION
      "Path: ethernet3.status.pppoEClient.ppp.mru"
   ::= {sr1646v2Lan3FGPppOEEntry 84934656}

sr1646v2Lan3FGPppOEIpV6State OBJECT-TYPE
   SYNTAX      INTEGER
               {
               disabled (0),
               enabled (1)
               }
   MAX-ACCESS  read-only
   STATUS      current
   DESCRIPTION
      "Path: ethernet3.status.pppoEClient.ipV6.state

       Possibilities:
               disabled   (0)
               enabled   (1)"
   ::= {sr1646v2Lan3FGPppOEEntry 100728832}

sr1646v2Lan3FGPppOEIpV6InterfaceId OBJECT-TYPE
   SYNTAX      OCTET STRING
   MAX-ACCESS  read-only
   STATUS      current
   DESCRIPTION
      "Path: ethernet3.status.pppoEClient.ipV6.interfaceId"
   ::= {sr1646v2Lan3FGPppOEEntry 100794368}

sr1646v2Lan3FGPppOEIpV6LinkMtu OBJECT-TYPE
   SYNTAX      Integer32
   MAX-ACCESS  read-only
   STATUS      current
   DESCRIPTION
      "Path: ethernet3.status.pppoEClient.ipV6.linkMtu"
   ::= {sr1646v2Lan3FGPppOEEntry 100925440}

sr1646v2Lan3FGPppOEIpV6HopLimit OBJECT-TYPE
   SYNTAX      Integer32
   MAX-ACCESS  read-only
   STATUS      current
   DESCRIPTION
      "Path: ethernet3.status.pppoEClient.ipV6.hopLimit"
   ::= {sr1646v2Lan3FGPppOEEntry 100990976}

sr1646v2Lan3FGPppOEIpV6DhcpIaid OBJECT-TYPE
   SYNTAX      Counter32
   MAX-ACCESS  read-only
   STATUS      current
   DESCRIPTION
      "Path: ethernet3.status.pppoEClient.ipV6.dhcp.iaid

       32 bit unsigned wrappable counter."
   ::= {sr1646v2Lan3FGPppOEEntry 101056768}

sr1646v2Lan3FGPppOEIpV6RaRcvOption OBJECT-TYPE
   SYNTAX      Integer32
   MAX-ACCESS  read-only
   STATUS      current
   DESCRIPTION
      "Path: ethernet3.status.pppoEClient.ipV6.raRcvOption

       Bit meanings:
               bit 0 = linkMtu,
               bit 1 = srcLinkLayer,
               bit 2 = prefixInfo,
               bit 3 = rdnss,
               bit 4 = dnssl"
   ::= {sr1646v2Lan3FGPppOEEntry 101122048}

sr1646v2Lan3FGPppOEIpV6Addresses OBJECT-TYPE
   SYNTAX      SEQUENCE OF Sr1646v2Lan3FGPppOEIpV6AddressesEntry
   MAX-ACCESS  not-accessible
   STATUS      current
   DESCRIPTION
      ""
   ::= {sr1646v2Lan3FGPppOE 100859904}

sr1646v2Lan3FGPppOEIpV6AddressesEntry OBJECT-TYPE
   SYNTAX      Sr1646v2Lan3FGPppOEIpV6AddressesEntry
   MAX-ACCESS  not-accessible
   STATUS      current
   DESCRIPTION
      ""
   INDEX      { sr1646v2Lan3FGPppOETableIx,
                sr1646v2Lan3FGPppOEIpV6AddressesTableIx }
   ::= {sr1646v2Lan3FGPppOEIpV6Addresses 1}

Sr1646v2Lan3FGPppOEIpV6AddressesEntry ::=
   SEQUENCE
      {
      sr1646v2Lan3FGPppOEIpV6AddressesTableIx
         TableIndex,
      sr1646v2Lan3FGPppOEIpV6AddressesAddress
         Ipv6Address,
      sr1646v2Lan3FGPppOEIpV6AddressesPrefixLength
         Integer32,
      sr1646v2Lan3FGPppOEIpV6AddressesStatus
         INTEGER,
      sr1646v2Lan3FGPppOEIpV6AddressesOrigin
         INTEGER,
      sr1646v2Lan3FGPppOEIpV6AddressesFlagsInterfaceId
         INTEGER,
      sr1646v2Lan3FGPppOEIpV6AddressesFlagsAnycast
         INTEGER,
      sr1646v2Lan3FGPppOEIpV6AddressesTimersValidLifeTime
         TimeTicks,
      sr1646v2Lan3FGPppOEIpV6AddressesTimersPrefLifeTime
         TimeTicks
      }

sr1646v2Lan3FGPppOEIpV6AddressesTableIx OBJECT-TYPE
   SYNTAX      TableIndex
   MAX-ACCESS  not-accessible
   STATUS      current
   DESCRIPTION
      ""
   ::= {sr1646v2Lan3FGPppOEIpV6AddressesEntry 11}

sr1646v2Lan3FGPppOEIpV6AddressesAddress OBJECT-TYPE
   SYNTAX      Ipv6Address
   MAX-ACCESS  read-only
   STATUS      current
   DESCRIPTION
      "Path: ethernet3.status.pppoEClient.ipV6.addresses.address

       ipv6 address"
   ::= {sr1646v2Lan3FGPppOEIpV6AddressesEntry 16777216}

sr1646v2Lan3FGPppOEIpV6AddressesPrefixLength OBJECT-TYPE
   SYNTAX      Integer32
   MAX-ACCESS  read-only
   STATUS      current
   DESCRIPTION
      "Path: ethernet3.status.pppoEClient.ipV6.addresses.prefixLength"
   ::= {sr1646v2Lan3FGPppOEIpV6AddressesEntry 33554432}

sr1646v2Lan3FGPppOEIpV6AddressesStatus OBJECT-TYPE
   SYNTAX      INTEGER
               {
               invalid (0),
               tentative (1),
               deprecated (2),
               preferred (3)
               }
   MAX-ACCESS  read-only
   STATUS      current
   DESCRIPTION
      "Path: ethernet3.status.pppoEClient.ipV6.addresses.status

       Possibilities:
               invalid   (0)
               tentative   (1)
               deprecated   (2)
               preferred   (3)"
   ::= {sr1646v2Lan3FGPppOEIpV6AddressesEntry 50331648}

sr1646v2Lan3FGPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.pppoEClient.ipV6.addresses.origin

       Possibilities:
               unknown   (0)
               manual   (1)
               generalPrefix   (2)
               statelessAuto   (3)
               statefullAuto   (4)"
   ::= {sr1646v2Lan3FGPppOEIpV6AddressesEntry 67108864}

sr1646v2Lan3FGPppOEIpV6AddressesFlagsInterfaceId OBJECT-TYPE
   SYNTAX      INTEGER
               {
               no (0),
               yes (1)
               }
   MAX-ACCESS  read-only
   STATUS      current
   DESCRIPTION
      "Path: ethernet3.status.pppoEClient.ipV6.addresses.flags.interfaceId

       Possibilities:
               no   (0)
               yes   (1)"
   ::= {sr1646v2Lan3FGPppOEIpV6AddressesEntry 83951616}

sr1646v2Lan3FGPppOEIpV6AddressesFlagsAnycast OBJECT-TYPE
   SYNTAX      INTEGER
               {
               no (0),
               yes (1)
               }
   MAX-ACCESS  read-only
   STATUS      current
   DESCRIPTION
      "Path: ethernet3.status.pppoEClient.ipV6.addresses.flags.anycast

       Possibilities:
               no   (0)
               yes   (1)"
   ::= {sr1646v2Lan3FGPppOEIpV6AddressesEntry 84017152}

sr1646v2Lan3FGPppOEIpV6AddressesTimersValidLifeTime OBJECT-TYPE
   SYNTAX      TimeTicks
   MAX-ACCESS  read-only
   STATUS      current
   DESCRIPTION
      "Path: ethernet3.status.pppoEClient.ipV6.addresses.timers.validLifeTime

       Time in centi-second."
   ::= {sr1646v2Lan3FGPppOEIpV6AddressesEntry 100794368}

sr1646v2Lan3FGPppOEIpV6AddressesTimersPrefLifeTime OBJECT-TYPE
   SYNTAX      TimeTicks
   MAX-ACCESS  read-only
   STATUS      current
   DESCRIPTION
      "Path: ethernet3.status.pppoEClient.ipV6.addresses.timers.prefLifeTime

       Time in centi-second."
   ::= {sr1646v2Lan3FGPppOEIpV6AddressesEntry 100728832}


sr1646v2Lan3FGDot1x OBJECT IDENTIFIER ::= {sr1646v2Lan3FG 190}

sr1646v2Lan3FGDot1xSSCTable OBJECT-TYPE
   SYNTAX      SEQUENCE OF Sr1646v2Lan3FGDot1xEntry
   MAX-ACCESS  not-accessible
   STATUS      current
   DESCRIPTION
      "Ethernet Switch VLAN Table"
   ::= {sr1646v2Lan3FGDot1x 1}

sr1646v2Lan3FGDot1xEntry OBJECT-TYPE
   SYNTAX      Sr1646v2Lan3FGDot1xEntry
   MAX-ACCESS  not-accessible
   STATUS      current
   DESCRIPTION
      ""
   INDEX      { sr1646v2Lan3FGDot1xTableIx }
   ::= {sr1646v2Lan3FGDot1xSSCTable 1}

Sr1646v2Lan3FGDot1xEntry ::=
   SEQUENCE
      {
      sr1646v2Lan3FGDot1xTableIx
         TableIndex,
      sr1646v2Lan3FGDot1xRemote
         OCTET STRING,
      sr1646v2Lan3FGDot1xAuthorized
         INTEGER,
      sr1646v2Lan3FGDot1xAuthenticator
         INTEGER,
      sr1646v2Lan3FGDot1xBackEnd
         INTEGER,
      sr1646v2Lan3FGDot1xRetries
         Integer32,
      sr1646v2Lan3FGDot1xReAuthTime
         TimeTicks,
      sr1646v2Lan3FGDot1xHoldTime
         TimeTicks
      }

sr1646v2Lan3FGDot1xTableIx OBJECT-TYPE
   SYNTAX      TableIndex
   MAX-ACCESS  not-accessible
   STATUS      current
   DESCRIPTION
      ""
   ::= {sr1646v2Lan3FGDot1xEntry 11}

sr1646v2Lan3FGDot1xRemote OBJECT-TYPE
   SYNTAX      OCTET STRING
   MAX-ACCESS  read-only
   STATUS      current
   DESCRIPTION
      "Path: ethernet3.status.dot1x.remote

       MAC address."
   ::= {sr1646v2Lan3FGDot1xEntry 16777216}

sr1646v2Lan3FGDot1xAuthorized OBJECT-TYPE
   SYNTAX      INTEGER
               {
               no (0),
               yes (1)
               }
   MAX-ACCESS  read-only
   STATUS      current
   DESCRIPTION
      "Path: ethernet3.status.dot1x.authorized

       Possibilities:
               no   (0)
               yes   (1)"
   ::= {sr1646v2Lan3FGDot1xEntry 33554432}

sr1646v2Lan3FGDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: ethernet3.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1646v2Lan3FGDot1xEntry 50331648}

sr1646v2Lan3FGDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: ethernet3.status.dot1x.backEnd

       Possibilities:
               preInit   (0)
               initialize   (1)
               idle   (2)
               request   (3)
               response   (4)
               success   (5)
               failure   (6)
               radiusTimeout   (7)
               timeout   (8)"
   ::= {sr1646v2Lan3FGDot1xEntry 67108864}

sr1646v2Lan3FGDot1xRetries OBJECT-TYPE
   SYNTAX      Integer32
   MAX-ACCESS  read-only
   STATUS      current
   DESCRIPTION
      "Path: ethernet3.status.dot1x.retries"
   ::= {sr1646v2Lan3FGDot1xEntry 83886080}

sr1646v2Lan3FGDot1xReAuthTime OBJECT-TYPE
   SYNTAX      TimeTicks
   MAX-ACCESS  read-only
   STATUS      current
   DESCRIPTION
      "Path: ethernet3.status.dot1x.reAuthTime

       Time in centi-second."
   ::= {sr1646v2Lan3FGDot1xEntry 100663296}

sr1646v2Lan3FGDot1xHoldTime OBJECT-TYPE
   SYNTAX      TimeTicks
   MAX-ACCESS  read-only
   STATUS      current
   DESCRIPTION
      "Path: ethernet3.status.dot1x.holdTime

       Time in centi-second."
   ::= {sr1646v2Lan3FGDot1xEntry 117440512}


sr1646v2Lan3FGIpV6 OBJECT IDENTIFIER ::= {sr1646v2Lan3FG 17}

sr1646v2Lan3FGIpV6SSC OBJECT IDENTIFIER ::= {sr1646v2Lan3FGIpV6 1}

sr1646v2Lan3FGIpV6Entry OBJECT IDENTIFIER ::= {sr1646v2Lan3FGIpV6SSC 1}

sr1646v2Lan3FGIpV6State OBJECT-TYPE
   SYNTAX      INTEGER
               {
               disabled (0),
               enabled (1)
               }
   MAX-ACCESS  read-only
   STATUS      current
   DESCRIPTION
      "Path: ethernet3.status.ipV6.state

       Possibilities:
               disabled   (0)
               enabled   (1)"
   ::= {sr1646v2Lan3FGIpV6Entry 16777216}

sr1646v2Lan3FGIpV6InterfaceId OBJECT-TYPE
   SYNTAX      OCTET STRING
   MAX-ACCESS  read-only
   STATUS      current
   DESCRIPTION
      "Path: ethernet3.status.ipV6.interfaceId"
   ::= {sr1646v2Lan3FGIpV6Entry 33554432}

sr1646v2Lan3FGIpV6LinkMtu OBJECT-TYPE
   SYNTAX      Integer32
   MAX-ACCESS  read-only
   STATUS      current
   DESCRIPTION
      "Path: ethernet3.status.ipV6.linkMtu"
   ::= {sr1646v2Lan3FGIpV6Entry 67108864}

sr1646v2Lan3FGIpV6HopLimit OBJECT-TYPE
   SYNTAX      Integer32
   MAX-ACCESS  read-only
   STATUS      current
   DESCRIPTION
      "Path: ethernet3.status.ipV6.hopLimit"
   ::= {sr1646v2Lan3FGIpV6Entry 83886080}

sr1646v2Lan3FGIpV6DhcpIaid OBJECT-TYPE
   SYNTAX      Counter32
   MAX-ACCESS  read-only
   STATUS      current
   DESCRIPTION
      "Path: ethernet3.status.ipV6.dhcp.iaid

       32 bit unsigned wrappable counter."
   ::= {sr1646v2Lan3FGIpV6Entry 100728832}

sr1646v2Lan3FGIpV6RaRcvOption OBJECT-TYPE
   SYNTAX      Integer32
   MAX-ACCESS  read-only
   STATUS      current
   DESCRIPTION
      "Path: ethernet3.status.ipV6.raRcvOption

       Bit meanings:
               bit 0 = linkMtu,
               bit 1 = srcLinkLayer,
               bit 2 = prefixInfo,
               bit 3 = rdnss,
               bit 4 = dnssl"
   ::= {sr1646v2Lan3FGIpV6Entry 117440512}

sr1646v2Lan3FGIpV6Addresses OBJECT-TYPE
   SYNTAX      SEQUENCE OF Sr1646v2Lan3FGIpV6AddressesEntry
   MAX-ACCESS  not-accessible
   STATUS      current
   DESCRIPTION
      ""
   ::= {sr1646v2Lan3FGIpV6 50331648}

sr1646v2Lan3FGIpV6AddressesEntry OBJECT-TYPE
   SYNTAX      Sr1646v2Lan3FGIpV6AddressesEntry
   MAX-ACCESS  not-accessible
   STATUS      current
   DESCRIPTION
      ""
   INDEX      { sr1646v2Lan3FGIpV6AddressesTableIx }
   ::= {sr1646v2Lan3FGIpV6Addresses 1}

Sr1646v2Lan3FGIpV6AddressesEntry ::=
   SEQUENCE
      {
      sr1646v2Lan3FGIpV6AddressesTableIx
         TableIndex,
      sr1646v2Lan3FGIpV6AddressesAddress
         Ipv6Address,
      sr1646v2Lan3FGIpV6AddressesPrefixLength
         Integer32,
      sr1646v2Lan3FGIpV6AddressesStatus
         INTEGER,
      sr1646v2Lan3FGIpV6AddressesOrigin
         INTEGER,
      sr1646v2Lan3FGIpV6AddressesFlagsInterfaceId
         INTEGER,
      sr1646v2Lan3FGIpV6AddressesFlagsAnycast
         INTEGER,
      sr1646v2Lan3FGIpV6AddressesTimersValidLifeTime
         TimeTicks,
      sr1646v2Lan3FGIpV6AddressesTimersPrefLifeTime
         TimeTicks
      }

sr1646v2Lan3FGIpV6AddressesTableIx OBJECT-TYPE
   SYNTAX      TableIndex
   MAX-ACCESS  not-accessible
   STATUS      current
   DESCRIPTION
      ""
   ::= {sr1646v2Lan3FGIpV6AddressesEntry 11}

sr1646v2Lan3FGIpV6AddressesAddress OBJECT-TYPE
   SYNTAX      Ipv6Address
   MAX-ACCESS  read-only
   STATUS      current
   DESCRIPTION
      "Path: ethernet3.status.ipV6.addresses.address

       ipv6 address"
   ::= {sr1646v2Lan3FGIpV6AddressesEntry 16777216}

sr1646v2Lan3FGIpV6AddressesPrefixLength OBJECT-TYPE
   SYNTAX      Integer32
   MAX-ACCESS  read-only
   STATUS      current
   DESCRIPTION
      "Path: ethernet3.status.ipV6.addresses.prefixLength"
   ::= {sr1646v2Lan3FGIpV6AddressesEntry 33554432}

sr1646v2Lan3FGIpV6AddressesStatus OBJECT-TYPE
   SYNTAX      INTEGER
               {
               invalid (0),
               tentative (1),
               deprecated (2),
               preferred (3)
               }
   MAX-ACCESS  read-only
   STATUS      current
   DESCRIPTION
      "Path: ethernet3.status.ipV6.addresses.status

       Possibilities:
               invalid   (0)
               tentative   (1)
               deprecated   (2)
               preferred   (3)"
   ::= {sr1646v2Lan3FGIpV6AddressesEntry 50331648}

sr1646v2Lan3FGIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet3.status.ipV6.addresses.origin

       Possibilities:
               unknown   (0)
               manual   (1)
               generalPrefix   (2)
               statelessAuto   (3)
               statefullAuto   (4)"
   ::= {sr1646v2Lan3FGIpV6AddressesEntry 67108864}

sr1646v2Lan3FGIpV6AddressesFlagsInterfaceId OBJECT-TYPE
   SYNTAX      INTEGER
               {
               no (0),
               yes (1)
               }
   MAX-ACCESS  read-only
   STATUS      current
   DESCRIPTION
      "Path: ethernet3.status.ipV6.addresses.flags.interfaceId

       Possibilities:
               no   (0)
               yes   (1)"
   ::= {sr1646v2Lan3FGIpV6AddressesEntry 83951616}

sr1646v2Lan3FGIpV6AddressesFlagsAnycast OBJECT-TYPE
   SYNTAX      INTEGER
               {
               no (0),
               yes (1)
               }
   MAX-ACCESS  read-only
   STATUS      current
   DESCRIPTION
      "Path: ethernet3.status.ipV6.addresses.flags.anycast

       Possibilities:
               no   (0)
               yes   (1)"
   ::= {sr1646v2Lan3FGIpV6AddressesEntry 84017152}

sr1646v2Lan3FGIpV6AddressesTimersValidLifeTime OBJECT-TYPE
   SYNTAX      TimeTicks
   MAX-ACCESS  read-only
   STATUS      current
   DESCRIPTION
      "Path: ethernet3.status.ipV6.addresses.timers.validLifeTime

       Time in centi-second."
   ::= {sr1646v2Lan3FGIpV6AddressesEntry 100794368}

sr1646v2Lan3FGIpV6AddressesTimersPrefLifeTime OBJECT-TYPE
   SYNTAX      TimeTicks
   MAX-ACCESS  read-only
   STATUS      current
   DESCRIPTION
      "Path: ethernet3.status.ipV6.addresses.timers.prefLifeTime

       Time in centi-second."
   ::= {sr1646v2Lan3FGIpV6AddressesEntry 100728832}


sr1646v2Lan3FGMediaType OBJECT-TYPE
   SYNTAX      INTEGER
               {
               utp (1),
               sfp (2),
               down (255)
               }
   MAX-ACCESS  read-only
   STATUS      current
   DESCRIPTION
      "Path: ethernet3.status.mediaType

       Possibilities:
               utp   (1)
               sfp   (2)
               down   (255)"
   ::= {sr1646v2Lan3FG 500}



pr1646v2Lan3FG OBJECT IDENTIFIER ::= {r1646v2Lan3FG 12}


pr1646v2Lan3FGInOctets OBJECT-TYPE
   SYNTAX      Counter64
   MAX-ACCESS  read-only
   STATUS      current
   DESCRIPTION
      "Path: ethernet3.performance.ifInOctets
       Info: ifInOctets

       64 bit unsigned wrappable counter."
   ::= {pr1646v2Lan3FG 109}


pr1646v2Lan3FGInUcast OBJECT-TYPE
   SYNTAX      Counter64
   MAX-ACCESS  read-only
   STATUS      current
   DESCRIPTION
      "Path: ethernet3.performance.ifInUcastPkts
       Info: ifInUcastPkts

       64 bit unsigned wrappable counter."
   ::= {pr1646v2Lan3FG 110}


pr1646v2Lan3FGInNUcastPkts OBJECT-TYPE
   SYNTAX      Counter64
   MAX-ACCESS  read-only
   STATUS      current
   DESCRIPTION
      "Path: ethernet3.performance.ifInNUcastPkts
       Info: ifInNUcastPkts

       64 bit unsigned wrappable counter."
   ::= {pr1646v2Lan3FG 111}


pr1646v2Lan3FGInBcastPkts OBJECT-TYPE
   SYNTAX      Counter64
   MAX-ACCESS  read-only
   STATUS      current
   DESCRIPTION
      "Path: ethernet3.performance.ifInBcastPkts
       Info: ifInBcastPkts

       64 bit unsigned wrappable counter."
   ::= {pr1646v2Lan3FG 211}


pr1646v2Lan3FGInMcastPkts OBJECT-TYPE
   SYNTAX      Counter64
   MAX-ACCESS  read-only
   STATUS      current
   DESCRIPTION
      "Path: ethernet3.performance.ifInMcastPkts
       Info: ifInNUcastPkts

       64 bit unsigned wrappable counter."
   ::= {pr1646v2Lan3FG 221}


pr1646v2Lan3FGInDiscards OBJECT-TYPE
   SYNTAX      Counter64
   MAX-ACCESS  read-only
   STATUS      current
   DESCRIPTION
      "Path: ethernet3.performance.ifInDiscards
       Info: ifInDiscards

       64 bit unsigned wrappable counter."
   ::= {pr1646v2Lan3FG 112}


pr1646v2Lan3FGInErrors OBJECT-TYPE
   SYNTAX      Counter64
   MAX-ACCESS  read-only
   STATUS      current
   DESCRIPTION
      "Path: ethernet3.performance.ifInErrors
       Info: ifInErrors

       64 bit unsigned wrappable counter."
   ::= {pr1646v2Lan3FG 113}


pr1646v2Lan3FGInUnknownProtos OBJECT-TYPE
   SYNTAX      Counter64
   MAX-ACCESS  read-only
   STATUS      current
   DESCRIPTION
      "Path: ethernet3.performance.ifInUnknownProtos
       Info: ifInUnknownprotos

       64 bit unsigned wrappable counter."
   ::= {pr1646v2Lan3FG 114}


pr1646v2Lan3FGInQLen OBJECT-TYPE
   SYNTAX      Gauge32
   MAX-ACCESS  read-only
   STATUS      current
   DESCRIPTION
      "Path: ethernet3.performance.ifInQLen
       Info: ifInQLen

       32 bit unsigned gauge value."
   ::= {pr1646v2Lan3FG 128}


pr1646v2Lan3FGInDropEx OBJECT-TYPE
   SYNTAX      Counter64
   MAX-ACCESS  read-only
   STATUS      current
   DESCRIPTION
      "Path: ethernet3.performance.ifInDropLevelExceeded
       Info: ifInDiscards

       64 bit unsigned wrappable counter."
   ::= {pr1646v2Lan3FG 130}


pr1646v2Lan3FGInDropNoMac OBJECT-TYPE
   SYNTAX      Counter64
   MAX-ACCESS  read-only
   STATUS      current
   DESCRIPTION
      "Path: ethernet3.performance.ifInDiscardsNoMacFit
       Info: ifInDiscards

       64 bit unsigned wrappable counter."
   ::= {pr1646v2Lan3FG 133}


pr1646v2Lan3FGInDropNUCast OBJECT-TYPE
   SYNTAX      Counter64
   MAX-ACCESS  read-only
   STATUS      current
   DESCRIPTION
      "Path: ethernet3.performance.ifInDiscardsNUCast
       Info: ifInDiscards

       64 bit unsigned wrappable counter."
   ::= {pr1646v2Lan3FG 136}


pr1646v2Lan3FGInDropFilter OBJECT-TYPE
   SYNTAX      Counter64
   MAX-ACCESS  read-only
   STATUS      current
   DESCRIPTION
      "Path: ethernet3.performance.ifInDiscardsFilter
       Info: ifInDiscards

       64 bit unsigned wrappable counter."
   ::= {pr1646v2Lan3FG 137}


pr1646v2Lan3FGInQueues OBJECT IDENTIFIER ::= {pr1646v2Lan3FG 131}

pr1646v2Lan3FGInQueuesSSCTable OBJECT-TYPE
   SYNTAX      SEQUENCE OF Pr1646v2Lan3FGInQueuesEntry
   MAX-ACCESS  not-accessible
   STATUS      current
   DESCRIPTION
      "Queue Lengths"
   ::= {pr1646v2Lan3FGInQueues 1}

pr1646v2Lan3FGInQueuesEntry OBJECT-TYPE
   SYNTAX      Pr1646v2Lan3FGInQueuesEntry
   MAX-ACCESS  not-accessible
   STATUS      current
   DESCRIPTION
      ""
   INDEX      { pr1646v2Lan3FGInQueuesTableIx }
   ::= {pr1646v2Lan3FGInQueuesSSCTable 1}

Pr1646v2Lan3FGInQueuesEntry ::=
   SEQUENCE
      {
      pr1646v2Lan3FGInQueuesTableIx
         TableIndex,
      pr1646v2Lan3FGInQueuesName
         INTEGER,
      pr1646v2Lan3FGInQueuesLength
         Integer32,
      pr1646v2Lan3FGInQueuesOctetLength
         Integer32,
      pr1646v2Lan3FGInQueuesRedLength
         Integer32,
      pr1646v2Lan3FGInQueuesPacketsTotal
         Counter64,
      pr1646v2Lan3FGInQueuesPacketsDirectTx
         Counter64,
      pr1646v2Lan3FGInQueuesPacketsQueued
         Counter64,
      pr1646v2Lan3FGInQueuesPacketsDropped
         Counter64,
      pr1646v2Lan3FGInQueuesPacketsRedDropped
         Counter64,
      pr1646v2Lan3FGInQueuesPacketsCirTx
         Counter64,
      pr1646v2Lan3FGInQueuesPacketsEirTx
         Counter64,
      pr1646v2Lan3FGInQueuesPacketsViolateTx
         Counter64,
      pr1646v2Lan3FGInQueuesOctetsTotal
         Counter64,
      pr1646v2Lan3FGInQueuesOctetsDirectTx
         Counter64,
      pr1646v2Lan3FGInQueuesOctetsQueued
         Counter64,
      pr1646v2Lan3FGInQueuesOctetsDropped
         Counter64,
      pr1646v2Lan3FGInQueuesOctetsRedDropped
         Counter64,
      pr1646v2Lan3FGInQueuesOctetsCirTx
         Counter64,
      pr1646v2Lan3FGInQueuesOctetsEirTx
         Counter64,
      pr1646v2Lan3FGInQueuesOctetsViolateTx
         Counter64,
      pr1646v2Lan3FGInQueuesOctetsBandwidth15sec
         Integer32,
      pr1646v2Lan3FGInQueuesOctetsBandwidth30sec
         Integer32,
      pr1646v2Lan3FGInQueuesOctetsBandwidth1min
         Integer32,
      pr1646v2Lan3FGInQueuesOctetsBandwidth2min
         Integer32,
      pr1646v2Lan3FGInQueuesOctetsBandwidth5min
         Integer32
      }

pr1646v2Lan3FGInQueuesTableIx OBJECT-TYPE
   SYNTAX      TableIndex
   MAX-ACCESS  not-accessible
   STATUS      current
   DESCRIPTION
      ""
   ::= {pr1646v2Lan3FGInQueuesEntry 11}

pr1646v2Lan3FGInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2Lan3FGInQueuesEntry 16777216}

pr1646v2Lan3FGInQueuesLength OBJECT-TYPE
   SYNTAX      Integer32
   MAX-ACCESS  read-only
   STATUS      current
   DESCRIPTION
      "Path: ethernet3.performance.ifInPriorityQueues.length"
   ::= {pr1646v2Lan3FGInQueuesEntry 33554432}

pr1646v2Lan3FGInQueuesOctetLength OBJECT-TYPE
   SYNTAX      Integer32
   MAX-ACCESS  read-only
   STATUS      current
   DESCRIPTION
      "Path: ethernet3.performance.ifInPriorityQueues.octetLength"
   ::= {pr1646v2Lan3FGInQueuesEntry 150994944}

pr1646v2Lan3FGInQueuesRedLength OBJECT-TYPE
   SYNTAX      Integer32
   MAX-ACCESS  read-only
   STATUS      current
   DESCRIPTION
      "Path: ethernet3.performance.ifInPriorityQueues.redLength"
   ::= {pr1646v2Lan3FGInQueuesEntry 134217728}

pr1646v2Lan3FGInQueuesPacketsTotal OBJECT-TYPE
   SYNTAX      Counter64
   MAX-ACCESS  read-only
   STATUS      current
   DESCRIPTION
      "Path: ethernet3.performance.ifInPriorityQueues.packets.total

       64 bit unsigned wrappable counter."
   ::= {pr1646v2Lan3FGInQueuesEntry 50790400}

pr1646v2Lan3FGInQueuesPacketsDirectTx OBJECT-TYPE
   SYNTAX      Counter64
   MAX-ACCESS  read-only
   STATUS      current
   DESCRIPTION
      "Path: ethernet3.performance.ifInPriorityQueues.packets.directTx

       64 bit unsigned wrappable counter."
   ::= {pr1646v2Lan3FGInQueuesEntry 50397184}

pr1646v2Lan3FGInQueuesPacketsQueued OBJECT-TYPE
   SYNTAX      Counter64
   MAX-ACCESS  read-only
   STATUS      current
   DESCRIPTION
      "Path: ethernet3.performance.ifInPriorityQueues.packets.queued

       64 bit unsigned wrappable counter."
   ::= {pr1646v2Lan3FGInQueuesEntry 50462720}

pr1646v2Lan3FGInQueuesPacketsDropped OBJECT-TYPE
   SYNTAX      Counter64
   MAX-ACCESS  read-only
   STATUS      current
   DESCRIPTION
      "Path: ethernet3.performance.ifInPriorityQueues.packets.dropped

       64 bit unsigned wrappable counter."
   ::= {pr1646v2Lan3FGInQueuesEntry 50528256}

pr1646v2Lan3FGInQueuesPacketsRedDropped OBJECT-TYPE
   SYNTAX      Counter64
   MAX-ACCESS  read-only
   STATUS      current
   DESCRIPTION
      "Path: ethernet3.performance.ifInPriorityQueues.packets.redDropped

       64 bit unsigned wrappable counter."
   ::= {pr1646v2Lan3FGInQueuesEntry 50724864}

pr1646v2Lan3FGInQueuesPacketsCirTx OBJECT-TYPE
   SYNTAX      Counter64
   MAX-ACCESS  read-only
   STATUS      current
   DESCRIPTION
      "Path: ethernet3.performance.ifInPriorityQueues.packets.cirTx

       64 bit unsigned wrappable counter."
   ::= {pr1646v2Lan3FGInQueuesEntry 50593792}

pr1646v2Lan3FGInQueuesPacketsEirTx OBJECT-TYPE
   SYNTAX      Counter64
   MAX-ACCESS  read-only
   STATUS      current
   DESCRIPTION
      "Path: ethernet3.performance.ifInPriorityQueues.packets.eirTx

       64 bit unsigned wrappable counter."
   ::= {pr1646v2Lan3FGInQueuesEntry 50659328}

pr1646v2Lan3FGInQueuesPacketsViolateTx OBJECT-TYPE
   SYNTAX      Counter64
   MAX-ACCESS  read-only
   STATUS      current
   DESCRIPTION
      "Path: ethernet3.performance.ifInPriorityQueues.packets.violateTx

       64 bit unsigned wrappable counter."
   ::= {pr1646v2Lan3FGInQueuesEntry 50855936}

pr1646v2Lan3FGInQueuesOctetsTotal OBJECT-TYPE
   SYNTAX      Counter64
   MAX-ACCESS  read-only
   STATUS      current
   DESCRIPTION
      "Path: ethernet3.performance.ifInPriorityQueues.octets.total

       64 bit unsigned wrappable counter."
   ::= {pr1646v2Lan3FGInQueuesEntry 67567616}

pr1646v2Lan3FGInQueuesOctetsDirectTx OBJECT-TYPE
   SYNTAX      Counter64
   MAX-ACCESS  read-only
   STATUS      current
   DESCRIPTION
      "Path: ethernet3.performance.ifInPriorityQueues.octets.directTx

       64 bit unsigned wrappable counter."
   ::= {pr1646v2Lan3FGInQueuesEntry 67174400}

pr1646v2Lan3FGInQueuesOctetsQueued OBJECT-TYPE
   SYNTAX      Counter64
   MAX-ACCESS  read-only
   STATUS      current
   DESCRIPTION
      "Path: ethernet3.performance.ifInPriorityQueues.octets.queued

       64 bit unsigned wrappable counter."
   ::= {pr1646v2Lan3FGInQueuesEntry 67239936}

pr1646v2Lan3FGInQueuesOctetsDropped OBJECT-TYPE
   SYNTAX      Counter64
   MAX-ACCESS  read-only
   STATUS      current
   DESCRIPTION
      "Path: ethernet3.performance.ifInPriorityQueues.octets.dropped

       64 bit unsigned wrappable counter."
   ::= {pr1646v2Lan3FGInQueuesEntry 67305472}

pr1646v2Lan3FGInQueuesOctetsRedDropped OBJECT-TYPE
   SYNTAX      Counter64
   MAX-ACCESS  read-only
   STATUS      current
   DESCRIPTION
      "Path: ethernet3.performance.ifInPriorityQueues.octets.redDropped

       64 bit unsigned wrappable counter."
   ::= {pr1646v2Lan3FGInQueuesEntry 67502080}

pr1646v2Lan3FGInQueuesOctetsCirTx OBJECT-TYPE
   SYNTAX      Counter64
   MAX-ACCESS  read-only
   STATUS      current
   DESCRIPTION
      "Path: ethernet3.performance.ifInPriorityQueues.octets.cirTx

       64 bit unsigned wrappable counter."
   ::= {pr1646v2Lan3FGInQueuesEntry 67371008}

pr1646v2Lan3FGInQueuesOctetsEirTx OBJECT-TYPE
   SYNTAX      Counter64
   MAX-ACCESS  read-only
   STATUS      current
   DESCRIPTION
      "Path: ethernet3.performance.ifInPriorityQueues.octets.eirTx

       64 bit unsigned wrappable counter."
   ::= {pr1646v2Lan3FGInQueuesEntry 67436544}

pr1646v2Lan3FGInQueuesOctetsViolateTx OBJECT-TYPE
   SYNTAX      Counter64
   MAX-ACCESS  read-only
   STATUS      current
   DESCRIPTION
      "Path: ethernet3.performance.ifInPriorityQueues.octets.violateTx

       64 bit unsigned wrappable counter."
   ::= {pr1646v2Lan3FGInQueuesEntry 67633152}

pr1646v2Lan3FGInQueuesOctetsBandwidth15sec OBJECT-TYPE
   SYNTAX      Integer32
   MAX-ACCESS  read-only
   STATUS      current
   DESCRIPTION
      "Path: ethernet3.performance.ifInPriorityQueues.octets.bandwidth.15sec

       unit name = bps
       formula = 8 * ; 8 /"
   ::= {pr1646v2Lan3FGInQueuesEntry 70386944}

pr1646v2Lan3FGInQueuesOctetsBandwidth30sec OBJECT-TYPE
   SYNTAX      Integer32
   MAX-ACCESS  read-only
   STATUS      current
   DESCRIPTION
      "Path: ethernet3.performance.ifInPriorityQueues.octets.bandwidth.30sec

       unit name = bps
       formula = 8 * ; 8 /"
   ::= {pr1646v2Lan3FGInQueuesEntry 70388224}

pr1646v2Lan3FGInQueuesOctetsBandwidth1min OBJECT-TYPE
   SYNTAX      Integer32
   MAX-ACCESS  read-only
   STATUS      current
   DESCRIPTION
      "Path: ethernet3.performance.ifInPriorityQueues.octets.bandwidth.1min

       unit name = bps
       formula = 8 * ; 8 /"
   ::= {pr1646v2Lan3FGInQueuesEntry 70390784}

pr1646v2Lan3FGInQueuesOctetsBandwidth2min OBJECT-TYPE
   SYNTAX      Integer32
   MAX-ACCESS  read-only
   STATUS      current
   DESCRIPTION
      "Path: ethernet3.performance.ifInPriorityQueues.octets.bandwidth.2min

       unit name = bps
       formula = 8 * ; 8 /"
   ::= {pr1646v2Lan3FGInQueuesEntry 70395904}

pr1646v2Lan3FGInQueuesOctetsBandwidth5min OBJECT-TYPE
   SYNTAX      Integer32
   MAX-ACCESS  read-only
   STATUS      current
   DESCRIPTION
      "Path: ethernet3.performance.ifInPriorityQueues.octets.bandwidth.5min

       unit name = bps
       formula = 8 * ; 8 /"
   ::= {pr1646v2Lan3FGInQueuesEntry 70411264}

pr1646v2Lan3FGInQueuesH2Performance OBJECT-TYPE
   SYNTAX      SEQUENCE OF Pr1646v2Lan3FGInQueuesH2PerformanceEntry
   MAX-ACCESS  not-accessible
   STATUS      current
   DESCRIPTION
      ""
   ::= {pr1646v2Lan3FGInQueues 83886080}

pr1646v2Lan3FGInQueuesH2PerformanceEntry OBJECT-TYPE
   SYNTAX      Pr1646v2Lan3FGInQueuesH2PerformanceEntry
   MAX-ACCESS  not-accessible
   STATUS      current
   DESCRIPTION
      ""
   INDEX      { pr1646v2Lan3FGInQueuesTableIx,
                pr1646v2Lan3FGInQueuesH2PerformanceTableIx }
   ::= {pr1646v2Lan3FGInQueuesH2Performance 1}

Pr1646v2Lan3FGInQueuesH2PerformanceEntry ::=
   SEQUENCE
      {
      pr1646v2Lan3FGInQueuesH2PerformanceTableIx
         TableIndex,
      pr1646v2Lan3FGInQueuesH2PerformanceSysUpTime
         TimeTicks,
      pr1646v2Lan3FGInQueuesH2PerformanceTotPkts
         Counter64,
      pr1646v2Lan3FGInQueuesH2PerformanceDirTxPkts
         Counter64,
      pr1646v2Lan3FGInQueuesH2PerformanceQdPkts
         Counter64,
      pr1646v2Lan3FGInQueuesH2PerformanceDropPkts
         Counter64,
      pr1646v2Lan3FGInQueuesH2PerformanceRDropPkts
         Counter64,
      pr1646v2Lan3FGInQueuesH2PerformanceCirTxPkts
         Counter64,
      pr1646v2Lan3FGInQueuesH2PerformanceEirTxPkts
         Counter64,
      pr1646v2Lan3FGInQueuesH2PerformanceViolTxPkts
         Counter64,
      pr1646v2Lan3FGInQueuesH2PerformanceTotOcts
         Counter64,
      pr1646v2Lan3FGInQueuesH2PerformanceDirTxOcts
         Counter64,
      pr1646v2Lan3FGInQueuesH2PerformanceQdOcts
         Counter64,
      pr1646v2Lan3FGInQueuesH2PerformanceDropOcts
         Counter64,
      pr1646v2Lan3FGInQueuesH2PerformanceRDropOcts
         Counter64,
      pr1646v2Lan3FGInQueuesH2PerformanceCirTxOcts
         Counter64,
      pr1646v2Lan3FGInQueuesH2PerformanceEirTxOcts
         Counter64,
      pr1646v2Lan3FGInQueuesH2PerformanceViolTxOcts
         Counter64,
      pr1646v2Lan3FGInQueuesH2PerformanceBandwidth
         Integer32
      }

pr1646v2Lan3FGInQueuesH2PerformanceTableIx OBJECT-TYPE
   SYNTAX      TableIndex
   MAX-ACCESS  not-accessible
   STATUS      current
   DESCRIPTION
      ""
   ::= {pr1646v2Lan3FGInQueuesH2PerformanceEntry 11}

pr1646v2Lan3FGInQueuesH2PerformanceSysUpTime OBJECT-TYPE
   SYNTAX      TimeTicks
   MAX-ACCESS  read-only
   STATUS      current
   DESCRIPTION
      "Path: ethernet3.performance.ifInPriorityQueues.h2Performance.sysUpTime

       Time in centi-second."
   ::= {pr1646v2Lan3FGInQueuesH2PerformanceEntry 16777216}

pr1646v2Lan3FGInQueuesH2PerformanceTotPkts OBJECT-TYPE
   SYNTAX      Counter64
   MAX-ACCESS  read-only
   STATUS      current
   DESCRIPTION
      "Path: ethernet3.performance.ifInPriorityQueues.h2Performance.totalPkts

       64 bit unsigned wrappable counter."
   ::= {pr1646v2Lan3FGInQueuesH2PerformanceEntry 234881024}

pr1646v2Lan3FGInQueuesH2PerformanceDirTxPkts OBJECT-TYPE
   SYNTAX      Counter64
   MAX-ACCESS  read-only
   STATUS      current
   DESCRIPTION
      "Path: ethernet3.performance.ifInPriorityQueues.h2Performance.directTxPkts

       64 bit unsigned wrappable counter."
   ::= {pr1646v2Lan3FGInQueuesH2PerformanceEntry 33554432}

pr1646v2Lan3FGInQueuesH2PerformanceQdPkts OBJECT-TYPE
   SYNTAX      Counter64
   MAX-ACCESS  read-only
   STATUS      current
   DESCRIPTION
      "Path: ethernet3.performance.ifInPriorityQueues.h2Performance.queuedPkts

       64 bit unsigned wrappable counter."
   ::= {pr1646v2Lan3FGInQueuesH2PerformanceEntry 50331648}

pr1646v2Lan3FGInQueuesH2PerformanceDropPkts OBJECT-TYPE
   SYNTAX      Counter64
   MAX-ACCESS  read-only
   STATUS      current
   DESCRIPTION
      "Path: ethernet3.performance.ifInPriorityQueues.h2Performance.droppedPkts

       64 bit unsigned wrappable counter."
   ::= {pr1646v2Lan3FGInQueuesH2PerformanceEntry 67108864}

pr1646v2Lan3FGInQueuesH2PerformanceRDropPkts OBJECT-TYPE
   SYNTAX      Counter64
   MAX-ACCESS  read-only
   STATUS      current
   DESCRIPTION
      "Path: ethernet3.performance.ifInPriorityQueues.h2Performance.redDroppedPkts

       64 bit unsigned wrappable counter."
   ::= {pr1646v2Lan3FGInQueuesH2PerformanceEntry 201326592}

pr1646v2Lan3FGInQueuesH2PerformanceCirTxPkts OBJECT-TYPE
   SYNTAX      Counter64
   MAX-ACCESS  read-only
   STATUS      current
   DESCRIPTION
      "Path: ethernet3.performance.ifInPriorityQueues.h2Performance.cirTxPkts

       64 bit unsigned wrappable counter."
   ::= {pr1646v2Lan3FGInQueuesH2PerformanceEntry 83886080}

pr1646v2Lan3FGInQueuesH2PerformanceEirTxPkts OBJECT-TYPE
   SYNTAX      Counter64
   MAX-ACCESS  read-only
   STATUS      current
   DESCRIPTION
      "Path: ethernet3.performance.ifInPriorityQueues.h2Performance.eirTxPkts

       64 bit unsigned wrappable counter."
   ::= {pr1646v2Lan3FGInQueuesH2PerformanceEntry 100663296}

pr1646v2Lan3FGInQueuesH2PerformanceViolTxPkts OBJECT-TYPE
   SYNTAX      Counter64
   MAX-ACCESS  read-only
   STATUS      current
   DESCRIPTION
      "Path: ethernet3.performance.ifInPriorityQueues.h2Performance.violateTxPkts

       64 bit unsigned wrappable counter."
   ::= {pr1646v2Lan3FGInQueuesH2PerformanceEntry 301989888}

pr1646v2Lan3FGInQueuesH2PerformanceTotOcts OBJECT-TYPE
   SYNTAX      Counter64
   MAX-ACCESS  read-only
   STATUS      current
   DESCRIPTION
      "Path: ethernet3.performance.ifInPriorityQueues.h2Performance.totalOctets

       64 bit unsigned wrappable counter."
   ::= {pr1646v2Lan3FGInQueuesH2PerformanceEntry 251658240}

pr1646v2Lan3FGInQueuesH2PerformanceDirTxOcts OBJECT-TYPE
   SYNTAX      Counter64
   MAX-ACCESS  read-only
   STATUS      current
   DESCRIPTION
      "Path: ethernet3.performance.ifInPriorityQueues.h2Performance.directTxOctets

       64 bit unsigned wrappable counter."
   ::= {pr1646v2Lan3FGInQueuesH2PerformanceEntry 117440512}

pr1646v2Lan3FGInQueuesH2PerformanceQdOcts OBJECT-TYPE
   SYNTAX      Counter64
   MAX-ACCESS  read-only
   STATUS      current
   DESCRIPTION
      "Path: ethernet3.performance.ifInPriorityQueues.h2Performance.queuedOctets

       64 bit unsigned wrappable counter."
   ::= {pr1646v2Lan3FGInQueuesH2PerformanceEntry 134217728}

pr1646v2Lan3FGInQueuesH2PerformanceDropOcts OBJECT-TYPE
   SYNTAX      Counter64
   MAX-ACCESS  read-only
   STATUS      current
   DESCRIPTION
      "Path: ethernet3.performance.ifInPriorityQueues.h2Performance.droppedOctets

       64 bit unsigned wrappable counter."
   ::= {pr1646v2Lan3FGInQueuesH2PerformanceEntry 150994944}

pr1646v2Lan3FGInQueuesH2PerformanceRDropOcts OBJECT-TYPE
   SYNTAX      Counter64
   MAX-ACCESS  read-only
   STATUS      current
   DESCRIPTION
      "Path: ethernet3.performance.ifInPriorityQueues.h2Performance.redDroppedOctets

       64 bit unsigned wrappable counter."
   ::= {pr1646v2Lan3FGInQueuesH2PerformanceEntry 218103808}

pr1646v2Lan3FGInQueuesH2PerformanceCirTxOcts OBJECT-TYPE
   SYNTAX      Counter64
   MAX-ACCESS  read-only
   STATUS      current
   DESCRIPTION
      "Path: ethernet3.performance.ifInPriorityQueues.h2Performance.cirTxOctets

       64 bit unsigned wrappable counter."
   ::= {pr1646v2Lan3FGInQueuesH2PerformanceEntry 167772160}

pr1646v2Lan3FGInQueuesH2PerformanceEirTxOcts OBJECT-TYPE
   SYNTAX      Counter64
   MAX-ACCESS  read-only
   STATUS      current
   DESCRIPTION
      "Path: ethernet3.performance.ifInPriorityQueues.h2Performance.eirTxOctets

       64 bit unsigned wrappable counter."
   ::= {pr1646v2Lan3FGInQueuesH2PerformanceEntry 184549376}

pr1646v2Lan3FGInQueuesH2PerformanceViolTxOcts OBJECT-TYPE
   SYNTAX      Counter64
   MAX-ACCESS  read-only
   STATUS      current
   DESCRIPTION
      "Path: ethernet3.performance.ifInPriorityQueues.h2Performance.violateTxOctets

       64 bit unsigned wrappable counter."
   ::= {pr1646v2Lan3FGInQueuesH2PerformanceEntry 318767104}

pr1646v2Lan3FGInQueuesH2PerformanceBandwidth OBJECT-TYPE
   SYNTAX      Integer32
   MAX-ACCESS  read-only
   STATUS      current
   DESCRIPTION
      "Path: ethernet3.performance.ifInPriorityQueues.h2Performance.bandwidth

       unit name = bps
       formula = 8 * ; 8 /"
   ::= {pr1646v2Lan3FGInQueuesH2PerformanceEntry 268435456}

pr1646v2Lan3FGInQueuesH24Performance OBJECT-TYPE
   SYNTAX      SEQUENCE OF Pr1646v2Lan3FGInQueuesH24PerformanceEntry
   MAX-ACCESS  not-accessible
   STATUS      current
   DESCRIPTION
      ""
   ::= {pr1646v2Lan3FGInQueues 100663296}

pr1646v2Lan3FGInQueuesH24PerformanceEntry OBJECT-TYPE
   SYNTAX      Pr1646v2Lan3FGInQueuesH24PerformanceEntry
   MAX-ACCESS  not-accessible
   STATUS      current
   DESCRIPTION
      ""
   INDEX      { pr1646v2Lan3FGInQueuesTableIx,
                pr1646v2Lan3FGInQueuesH24PerformanceTableIx }
   ::= {pr1646v2Lan3FGInQueuesH24Performance 1}

Pr1646v2Lan3FGInQueuesH24PerformanceEntry ::=
   SEQUENCE
      {
      pr1646v2Lan3FGInQueuesH24PerformanceTableIx
         TableIndex,
      pr1646v2Lan3FGInQueuesH24PerformanceSysUpTime
         TimeTicks,
      pr1646v2Lan3FGInQueuesH24PerformanceTotPkts
         Counter64,
      pr1646v2Lan3FGInQueuesH24PerformanceDirTxPkts
         Counter64,
      pr1646v2Lan3FGInQueuesH24PerformanceQdPkts
         Counter64,
      pr1646v2Lan3FGInQueuesH24PerformanceDropPkts
         Counter64,
      pr1646v2Lan3FGInQueuesH24PerformanceRDropPkts
         Counter64,
      pr1646v2Lan3FGInQueuesH24PerformanceCirTxPkts
         Counter64,
      pr1646v2Lan3FGInQueuesH24PerformanceEirTxPkts
         Counter64,
      pr1646v2Lan3FGInQueuesH24PerformanceViolTxPkts
         Counter64,
      pr1646v2Lan3FGInQueuesH24PerformanceTotOcts
         Counter64,
      pr1646v2Lan3FGInQueuesH24PerformanceDirTxOcts
         Counter64,
      pr1646v2Lan3FGInQueuesH24PerformanceQdOcts
         Counter64,
      pr1646v2Lan3FGInQueuesH24PerformanceDropOcts
         Counter64,
      pr1646v2Lan3FGInQueuesH24PerformanceRDropOcts
         Counter64,
      pr1646v2Lan3FGInQueuesH24PerformanceCirTxOcts
         Counter64,
      pr1646v2Lan3FGInQueuesH24PerformanceEirTxOcts
         Counter64,
      pr1646v2Lan3FGInQueuesH24PerformanceViolTxOcts
         Counter64,
      pr1646v2Lan3FGInQueuesH24PerformanceBandwidth
         Integer32
      }

pr1646v2Lan3FGInQueuesH24PerformanceTableIx OBJECT-TYPE
   SYNTAX      TableIndex
   MAX-ACCESS  not-accessible
   STATUS      current
   DESCRIPTION
      ""
   ::= {pr1646v2Lan3FGInQueuesH24PerformanceEntry 11}

pr1646v2Lan3FGInQueuesH24PerformanceSysUpTime OBJECT-TYPE
   SYNTAX      TimeTicks
   MAX-ACCESS  read-only
   STATUS      current
   DESCRIPTION
      "Path: ethernet3.performance.ifInPriorityQueues.h24Performance.sysUpTime

       Time in centi-second."
   ::= {pr1646v2Lan3FGInQueuesH24PerformanceEntry 16777216}

pr1646v2Lan3FGInQueuesH24PerformanceTotPkts OBJECT-TYPE
   SYNTAX      Counter64
   MAX-ACCESS  read-only
   STATUS      current
   DESCRIPTION
      "Path: ethernet3.performance.ifInPriorityQueues.h24Performance.totalPkts

       64 bit unsigned wrappable counter."
   ::= {pr1646v2Lan3FGInQueuesH24PerformanceEntry 234881024}

pr1646v2Lan3FGInQueuesH24PerformanceDirTxPkts OBJECT-TYPE
   SYNTAX      Counter64
   MAX-ACCESS  read-only
   STATUS      current
   DESCRIPTION
      "Path: ethernet3.performance.ifInPriorityQueues.h24Performance.directTxPkts

       64 bit unsigned wrappable counter."
   ::= {pr1646v2Lan3FGInQueuesH24PerformanceEntry 33554432}

pr1646v2Lan3FGInQueuesH24PerformanceQdPkts OBJECT-TYPE
   SYNTAX      Counter64
   MAX-ACCESS  read-only
   STATUS      current
   DESCRIPTION
      "Path: ethernet3.performance.ifInPriorityQueues.h24Performance.queuedPkts

       64 bit unsigned wrappable counter."
   ::= {pr1646v2Lan3FGInQueuesH24PerformanceEntry 50331648}

pr1646v2Lan3FGInQueuesH24PerformanceDropPkts OBJECT-TYPE
   SYNTAX      Counter64
   MAX-ACCESS  read-only
   STATUS      current
   DESCRIPTION
      "Path: ethernet3.performance.ifInPriorityQueues.h24Performance.droppedPkts

       64 bit unsigned wrappable counter."
   ::= {pr1646v2Lan3FGInQueuesH24PerformanceEntry 67108864}

pr1646v2Lan3FGInQueuesH24PerformanceRDropPkts OBJECT-TYPE
   SYNTAX      Counter64
   MAX-ACCESS  read-only
   STATUS      current
   DESCRIPTION
      "Path: ethernet3.performance.ifInPriorityQueues.h24Performance.redDroppedPkts

       64 bit unsigned wrappable counter."
   ::= {pr1646v2Lan3FGInQueuesH24PerformanceEntry 201326592}

pr1646v2Lan3FGInQueuesH24PerformanceCirTxPkts OBJECT-TYPE
   SYNTAX      Counter64
   MAX-ACCESS  read-only
   STATUS      current
   DESCRIPTION
      "Path: ethernet3.performance.ifInPriorityQueues.h24Performance.cirTxPkts

       64 bit unsigned wrappable counter."
   ::= {pr1646v2Lan3FGInQueuesH24PerformanceEntry 83886080}

pr1646v2Lan3FGInQueuesH24PerformanceEirTxPkts OBJECT-TYPE
   SYNTAX      Counter64
   MAX-ACCESS  read-only
   STATUS      current
   DESCRIPTION
      "Path: ethernet3.performance.ifInPriorityQueues.h24Performance.eirTxPkts

       64 bit unsigned wrappable counter."
   ::= {pr1646v2Lan3FGInQueuesH24PerformanceEntry 100663296}

pr1646v2Lan3FGInQueuesH24PerformanceViolTxPkts OBJECT-TYPE
   SYNTAX      Counter64
   MAX-ACCESS  read-only
   STATUS      current
   DESCRIPTION
      "Path: ethernet3.performance.ifInPriorityQueues.h24Performance.violateTxPkts

       64 bit unsigned wrappable counter."
   ::= {pr1646v2Lan3FGInQueuesH24PerformanceEntry 301989888}

pr1646v2Lan3FGInQueuesH24PerformanceTotOcts OBJECT-TYPE
   SYNTAX      Counter64
   MAX-ACCESS  read-only
   STATUS      current
   DESCRIPTION
      "Path: ethernet3.performance.ifInPriorityQueues.h24Performance.totalOctets

       64 bit unsigned wrappable counter."
   ::= {pr1646v2Lan3FGInQueuesH24PerformanceEntry 251658240}

pr1646v2Lan3FGInQueuesH24PerformanceDirTxOcts OBJECT-TYPE
   SYNTAX      Counter64
   MAX-ACCESS  read-only
   STATUS      current
   DESCRIPTION
      "Path: ethernet3.performance.ifInPriorityQueues.h24Performance.directTxOctets

       64 bit unsigned wrappable counter."
   ::= {pr1646v2Lan3FGInQueuesH24PerformanceEntry 117440512}

pr1646v2Lan3FGInQueuesH24PerformanceQdOcts OBJECT-TYPE
   SYNTAX      Counter64
   MAX-ACCESS  read-only
   STATUS      current
   DESCRIPTION
      "Path: ethernet3.performance.ifInPriorityQueues.h24Performance.queuedOctets

       64 bit unsigned wrappable counter."
   ::= {pr1646v2Lan3FGInQueuesH24PerformanceEntry 134217728}

pr1646v2Lan3FGInQueuesH24PerformanceDropOcts OBJECT-TYPE
   SYNTAX      Counter64
   MAX-ACCESS  read-only
   STATUS      current
   DESCRIPTION
      "Path: ethernet3.performance.ifInPriorityQueues.h24Performance.droppedOctets

       64 bit unsigned wrappable counter."
   ::= {pr1646v2Lan3FGInQueuesH24PerformanceEntry 150994944}

pr1646v2Lan3FGInQueuesH24PerformanceRDropOcts OBJECT-TYPE
   SYNTAX      Counter64
   MAX-ACCESS  read-only
   STATUS      current
   DESCRIPTION
      "Path: ethernet3.performance.ifInPriorityQueues.h24Performance.redDroppedOctets

       64 bit unsigned wrappable counter."
   ::= {pr1646v2Lan3FGInQueuesH24PerformanceEntry 218103808}

pr1646v2Lan3FGInQueuesH24PerformanceCirTxOcts OBJECT-TYPE
   SYNTAX      Counter64
   MAX-ACCESS  read-only
   STATUS      current
   DESCRIPTION
      "Path: ethernet3.performance.ifInPriorityQueues.h24Performance.cirTxOctets

       64 bit unsigned wrappable counter."
   ::= {pr1646v2Lan3FGInQueuesH24PerformanceEntry 167772160}

pr1646v2Lan3FGInQueuesH24PerformanceEirTxOcts OBJECT-TYPE
   SYNTAX      Counter64
   MAX-ACCESS  read-only
   STATUS      current
   DESCRIPTION
      "Path: ethernet3.performance.ifInPriorityQueues.h24Performance.eirTxOctets

       64 bit unsigned wrappable counter."
   ::= {pr1646v2Lan3FGInQueuesH24PerformanceEntry 184549376}

pr1646v2Lan3FGInQueuesH24PerformanceViolTxOcts OBJECT-TYPE
   SYNTAX      Counter64
   MAX-ACCESS  read-only
   STATUS      current
   DESCRIPTION
      "Path: ethernet3.performance.ifInPriorityQueues.h24Performance.violateTxOctets

       64 bit unsigned wrappable counter."
   ::= {pr1646v2Lan3FGInQueuesH24PerformanceEntry 318767104}

pr1646v2Lan3FGInQueuesH24PerformanceBandwidth OBJECT-TYPE
   SYNTAX      Integer32
   MAX-ACCESS  read-only
   STATUS      current
   DESCRIPTION
      "Path: ethernet3.performance.ifInPriorityQueues.h24Performance.bandwidth

       unit name = bps
       formula = 8 * ; 8 /"
   ::= {pr1646v2Lan3FGInQueuesH24PerformanceEntry 268435456}

pr1646v2Lan3FGInQueuesD7Performance OBJECT-TYPE
   SYNTAX      SEQUENCE OF Pr1646v2Lan3FGInQueuesD7PerformanceEntry
   MAX-ACCESS  not-accessible
   STATUS      current
   DESCRIPTION
      ""
   ::= {pr1646v2Lan3FGInQueues 117440512}

pr1646v2Lan3FGInQueuesD7PerformanceEntry OBJECT-TYPE
   SYNTAX      Pr1646v2Lan3FGInQueuesD7PerformanceEntry
   MAX-ACCESS  not-accessible
   STATUS      current
   DESCRIPTION
      ""
   INDEX      { pr1646v2Lan3FGInQueuesTableIx,
                pr1646v2Lan3FGInQueuesD7PerformanceTableIx }
   ::= {pr1646v2Lan3FGInQueuesD7Performance 1}

Pr1646v2Lan3FGInQueuesD7PerformanceEntry ::=
   SEQUENCE
      {
      pr1646v2Lan3FGInQueuesD7PerformanceTableIx
         TableIndex,
      pr1646v2Lan3FGInQueuesD7PerformanceSysUpTime
         TimeTicks,
      pr1646v2Lan3FGInQueuesD7PerformanceTotPkts
         Counter64,
      pr1646v2Lan3FGInQueuesD7PerformanceDirTxPkts
         Counter64,
      pr1646v2Lan3FGInQueuesD7PerformanceQdPkts
         Counter64,
      pr1646v2Lan3FGInQueuesD7PerformanceDropPkts
         Counter64,
      pr1646v2Lan3FGInQueuesD7PerformanceRDropPkts
         Counter64,
      pr1646v2Lan3FGInQueuesD7PerformanceCirTxPkts
         Counter64,
      pr1646v2Lan3FGInQueuesD7PerformanceEirTxPkts
         Counter64,
      pr1646v2Lan3FGInQueuesD7PerformanceViolTxPkts
         Counter64,
      pr1646v2Lan3FGInQueuesD7PerformanceTotOcts
         Counter64,
      pr1646v2Lan3FGInQueuesD7PerformanceDirTxOcts
         Counter64,
      pr1646v2Lan3FGInQueuesD7PerformanceQdOcts
         Counter64,
      pr1646v2Lan3FGInQueuesD7PerformanceDropOcts
         Counter64,
      pr1646v2Lan3FGInQueuesD7PerformanceRDropOcts
         Counter64,
      pr1646v2Lan3FGInQueuesD7PerformanceCirTxOcts
         Counter64,
      pr1646v2Lan3FGInQueuesD7PerformanceEirTxOcts
         Counter64,
      pr1646v2Lan3FGInQueuesD7PerformanceViolTxOcts
         Counter64,
      pr1646v2Lan3FGInQueuesD7PerformanceBandwidth
         Integer32
      }

pr1646v2Lan3FGInQueuesD7PerformanceTableIx OBJECT-TYPE
   SYNTAX      TableIndex
   MAX-ACCESS  not-accessible
   STATUS      current
   DESCRIPTION
      ""
   ::= {pr1646v2Lan3FGInQueuesD7PerformanceEntry 11}

pr1646v2Lan3FGInQueuesD7PerformanceSysUpTime OBJECT-TYPE
   SYNTAX      TimeTicks
   MAX-ACCESS  read-only
   STATUS      current
   DESCRIPTION
      "Path: ethernet3.performance.ifInPriorityQueues.d7Performance.sysUpTime

       Time in centi-second."
   ::= {pr1646v2Lan3FGInQueuesD7PerformanceEntry 16777216}

pr1646v2Lan3FGInQueuesD7PerformanceTotPkts OBJECT-TYPE
   SYNTAX      Counter64
   MAX-ACCESS  read-only
   STATUS      current
   DESCRIPTION
      "Path: ethernet3.performance.ifInPriorityQueues.d7Performance.totalPkts

       64 bit unsigned wrappable counter."
   ::= {pr1646v2Lan3FGInQueuesD7PerformanceEntry 234881024}

pr1646v2Lan3FGInQueuesD7PerformanceDirTxPkts OBJECT-TYPE
   SYNTAX      Counter64
   MAX-ACCESS  read-only
   STATUS      current
   DESCRIPTION
      "Path: ethernet3.performance.ifInPriorityQueues.d7Performance.directTxPkts

       64 bit unsigned wrappable counter."
   ::= {pr1646v2Lan3FGInQueuesD7PerformanceEntry 33554432}

pr1646v2Lan3FGInQueuesD7PerformanceQdPkts OBJECT-TYPE
   SYNTAX      Counter64
   MAX-ACCESS  read-only
   STATUS      current
   DESCRIPTION
      "Path: ethernet3.performance.ifInPriorityQueues.d7Performance.queuedPkts

       64 bit unsigned wrappable counter."
   ::= {pr1646v2Lan3FGInQueuesD7PerformanceEntry 50331648}

pr1646v2Lan3FGInQueuesD7PerformanceDropPkts OBJECT-TYPE
   SYNTAX      Counter64
   MAX-ACCESS  read-only
   STATUS      current
   DESCRIPTION
      "Path: ethernet3.performance.ifInPriorityQueues.d7Performance.droppedPkts

       64 bit unsigned wrappable counter."
   ::= {pr1646v2Lan3FGInQueuesD7PerformanceEntry 67108864}

pr1646v2Lan3FGInQueuesD7PerformanceRDropPkts OBJECT-TYPE
   SYNTAX      Counter64
   MAX-ACCESS  read-only
   STATUS      current
   DESCRIPTION
      "Path: ethernet3.performance.ifInPriorityQueues.d7Performance.redDroppedPkts

       64 bit unsigned wrappable counter."
   ::= {pr1646v2Lan3FGInQueuesD7PerformanceEntry 201326592}

pr1646v2Lan3FGInQueuesD7PerformanceCirTxPkts OBJECT-TYPE
   SYNTAX      Counter64
   MAX-ACCESS  read-only
   STATUS      current
   DESCRIPTION
      "Path: ethernet3.performance.ifInPriorityQueues.d7Performance.cirTxPkts

       64 bit unsigned wrappable counter."
   ::= {pr1646v2Lan3FGInQueuesD7PerformanceEntry 83886080}

pr1646v2Lan3FGInQueuesD7PerformanceEirTxPkts OBJECT-TYPE
   SYNTAX      Counter64
   MAX-ACCESS  read-only
   STATUS      current
   DESCRIPTION
      "Path: ethernet3.performance.ifInPriorityQueues.d7Performance.eirTxPkts

       64 bit unsigned wrappable counter."
   ::= {pr1646v2Lan3FGInQueuesD7PerformanceEntry 100663296}

pr1646v2Lan3FGInQueuesD7PerformanceViolTxPkts OBJECT-TYPE
   SYNTAX      Counter64
   MAX-ACCESS  read-only
   STATUS      current
   DESCRIPTION
      "Path: ethernet3.performance.ifInPriorityQueues.d7Performance.violateTxPkts

       64 bit unsigned wrappable counter."
   ::= {pr1646v2Lan3FGInQueuesD7PerformanceEntry 301989888}

pr1646v2Lan3FGInQueuesD7PerformanceTotOcts OBJECT-TYPE
   SYNTAX      Counter64
   MAX-ACCESS  read-only
   STATUS      current
   DESCRIPTION
      "Path: ethernet3.performance.ifInPriorityQueues.d7Performance.totalOctets

       64 bit unsigned wrappable counter."
   ::= {pr1646v2Lan3FGInQueuesD7PerformanceEntry 251658240}

pr1646v2Lan3FGInQueuesD7PerformanceDirTxOcts OBJECT-TYPE
   SYNTAX      Counter64
   MAX-ACCESS  read-only
   STATUS      current
   DESCRIPTION
      "Path: ethernet3.performance.ifInPriorityQueues.d7Performance.directTxOctets

       64 bit unsigned wrappable counter."
   ::= {pr1646v2Lan3FGInQueuesD7PerformanceEntry 117440512}

pr1646v2Lan3FGInQueuesD7PerformanceQdOcts OBJECT-TYPE
   SYNTAX      Counter64
   MAX-ACCESS  read-only
   STATUS      current
   DESCRIPTION
      "Path: ethernet3.performance.ifInPriorityQueues.d7Performance.queuedOctets

       64 bit unsigned wrappable counter."
   ::= {pr1646v2Lan3FGInQueuesD7PerformanceEntry 134217728}

pr1646v2Lan3FGInQueuesD7PerformanceDropOcts OBJECT-TYPE
   SYNTAX      Counter64
   MAX-ACCESS  read-only
   STATUS      current
   DESCRIPTION
      "Path: ethernet3.performance.ifInPriorityQueues.d7Performance.droppedOctets

       64 bit unsigned wrappable counter."
   ::= {pr1646v2Lan3FGInQueuesD7PerformanceEntry 150994944}

pr1646v2Lan3FGInQueuesD7PerformanceRDropOcts OBJECT-TYPE
   SYNTAX      Counter64
   MAX-ACCESS  read-only
   STATUS      current
   DESCRIPTION
      "Path: ethernet3.performance.ifInPriorityQueues.d7Performance.redDroppedOctets

       64 bit unsigned wrappable counter."
   ::= {pr1646v2Lan3FGInQueuesD7PerformanceEntry 218103808}

pr1646v2Lan3FGInQueuesD7PerformanceCirTxOcts OBJECT-TYPE
   SYNTAX      Counter64
   MAX-ACCESS  read-only
   STATUS      current
   DESCRIPTION
      "Path: ethernet3.performance.ifInPriorityQueues.d7Performance.cirTxOctets

       64 bit unsigned wrappable counter."
   ::= {pr1646v2Lan3FGInQueuesD7PerformanceEntry 167772160}

pr1646v2Lan3FGInQueuesD7PerformanceEirTxOcts OBJECT-TYPE
   SYNTAX      Counter64
   MAX-ACCESS  read-only
   STATUS      current
   DESCRIPTION
      "Path: ethernet3.performance.ifInPriorityQueues.d7Performance.eirTxOctets

       64 bit unsigned wrappable counter."
   ::= {pr1646v2Lan3FGInQueuesD7PerformanceEntry 184549376}

pr1646v2Lan3FGInQueuesD7PerformanceViolTxOcts OBJECT-TYPE
   SYNTAX      Counter64
   MAX-ACCESS  read-only
   STATUS      current
   DESCRIPTION
      "Path: ethernet3.performance.ifInPriorityQueues.d7Performance.violateTxOctets

       64 bit unsigned wrappable counter."
   ::= {pr1646v2Lan3FGInQueuesD7PerformanceEntry 318767104}

pr1646v2Lan3FGInQueuesD7PerformanceBandwidth OBJECT-TYPE
   SYNTAX      Integer32
   MAX-ACCESS  read-only
   STATUS      current
   DESCRIPTION
      "Path: ethernet3.performance.ifInPriorityQueues.d7Performance.bandwidth

       unit name = bps
       formula = 8 * ; 8 /"
   ::= {pr1646v2Lan3FGInQueuesD7PerformanceEntry 268435456}


pr1646v2Lan3FGInBandwidth OBJECT IDENTIFIER ::= {pr1646v2Lan3FG 181}

pr1646v2Lan3FGInBandwidthSSC OBJECT IDENTIFIER ::= {pr1646v2Lan3FGInBandwidth 1}

pr1646v2Lan3FGInBandwidthEntry OBJECT IDENTIFIER ::= {pr1646v2Lan3FGInBandwidthSSC 1}

pr1646v2Lan3FGInBandwidth15sec OBJECT-TYPE
   SYNTAX      Integer32
   MAX-ACCESS  read-only
   STATUS      current
   DESCRIPTION
      "Path: ethernet3.performance.ifInBandwidth.15sec

       unit name = bps
       formula = 8 * ; 8 /"
   ::= {pr1646v2Lan3FGInBandwidthEntry 83886080}

pr1646v2Lan3FGInBandwidth30sec OBJECT-TYPE
   SYNTAX      Integer32
   MAX-ACCESS  read-only
   STATUS      current
   DESCRIPTION
      "Path: ethernet3.performance.ifInBandwidth.30sec

       unit name = bps
       formula = 8 * ; 8 /"
   ::= {pr1646v2Lan3FGInBandwidthEntry 167772160}

pr1646v2Lan3FGInBandwidth1min OBJECT-TYPE
   SYNTAX      Integer32
   MAX-ACCESS  read-only
   STATUS      current
   DESCRIPTION
      "Path: ethernet3.performance.ifInBandwidth.1min

       unit name = bps
       formula = 8 * ; 8 /"
   ::= {pr1646v2Lan3FGInBandwidthEntry 335544320}

pr1646v2Lan3FGInBandwidth2min OBJECT-TYPE
   SYNTAX      Integer32
   MAX-ACCESS  read-only
   STATUS      current
   DESCRIPTION
      "Path: ethernet3.performance.ifInBandwidth.2min

       unit name = bps
       formula = 8 * ; 8 /"
   ::= {pr1646v2Lan3FGInBandwidthEntry 671088640}

pr1646v2Lan3FGInBandwidth5min OBJECT-TYPE
   SYNTAX      Integer32
   MAX-ACCESS  read-only
   STATUS      current
   DESCRIPTION
      "Path: ethernet3.performance.ifInBandwidth.5min

       unit name = bps
       formula = 8 * ; 8 /"
   ::= {pr1646v2Lan3FGInBandwidthEntry 1677721600}


pr1646v2Lan3FGOutOctets OBJECT-TYPE
   SYNTAX      Counter64
   MAX-ACCESS  read-only
   STATUS      current
   DESCRIPTION
      "Path: ethernet3.performance.ifOutOctets
       Info: ifOutOctets

       64 bit unsigned wrappable counter."
   ::= {pr1646v2Lan3FG 115}


pr1646v2Lan3FGOutUcastPkts OBJECT-TYPE
   SYNTAX      Counter64
   MAX-ACCESS  read-only
   STATUS      current
   DESCRIPTION
      "Path: ethernet3.performance.ifOutUcastPkts
       Info: ifOutUcastPkts

       64 bit unsigned wrappable counter."
   ::= {pr1646v2Lan3FG 116}


pr1646v2Lan3FGOutNUcastPkts OBJECT-TYPE
   SYNTAX      Counter64
   MAX-ACCESS  read-only
   STATUS      current
   DESCRIPTION
      "Path: ethernet3.performance.ifOutNUcastPkts
       Info: ifOutNUcastPkts

       64 bit unsigned wrappable counter."
   ::= {pr1646v2Lan3FG 117}


pr1646v2Lan3FGOutBcastPkts OBJECT-TYPE
   SYNTAX      Counter64
   MAX-ACCESS  read-only
   STATUS      current
   DESCRIPTION
      "Path: ethernet3.performance.ifOutBcastPkts
       Info: ifOutBcastPkts

       64 bit unsigned wrappable counter."
   ::= {pr1646v2Lan3FG 217}


pr1646v2Lan3FGOutMcastPkts OBJECT-TYPE
   SYNTAX      Counter64
   MAX-ACCESS  read-only
   STATUS      current
   DESCRIPTION
      "Path: ethernet3.performance.ifOutMcastPkts
       Info: ifOutMcastPkts

       64 bit unsigned wrappable counter."
   ::= {pr1646v2Lan3FG 227}


pr1646v2Lan3FGOutDiscards OBJECT-TYPE
   SYNTAX      Counter64
   MAX-ACCESS  read-only
   STATUS      current
   DESCRIPTION
      "Path: ethernet3.performance.ifOutDiscards
       Info: ifOutDiscards

       64 bit unsigned wrappable counter."
   ::= {pr1646v2Lan3FG 118}


pr1646v2Lan3FGOutErrors OBJECT-TYPE
   SYNTAX      Counter64
   MAX-ACCESS  read-only
   STATUS      current
   DESCRIPTION
      "Path: ethernet3.performance.ifOutErrors
       Info: ifOutErrors

       64 bit unsigned wrappable counter."
   ::= {pr1646v2Lan3FG 119}


pr1646v2Lan3FGOutQLen OBJECT-TYPE
   SYNTAX      Gauge32
   MAX-ACCESS  read-only
   STATUS      current
   DESCRIPTION
      "Path: ethernet3.performance.ifOutQLen
       Info: ifOutQLen

       32 bit unsigned gauge value."
   ::= {pr1646v2Lan3FG 120}


pr1646v2Lan3FGOutDropEx OBJECT-TYPE
   SYNTAX      Counter64
   MAX-ACCESS  read-only
   STATUS      current
   DESCRIPTION
      "Path: ethernet3.performance.ifOutDropLevelExceeded
       Info: ifOutDiscards

       64 bit unsigned wrappable counter."
   ::= {pr1646v2Lan3FG 127}


pr1646v2Lan3FGOutDropNoArp OBJECT-TYPE
   SYNTAX      Counter64
   MAX-ACCESS  read-only
   STATUS      current
   DESCRIPTION
      "Path: ethernet3.performance.ifOutDiscardsNoArp
       Info: ifOutDiscards

       64 bit unsigned wrappable counter."
   ::= {pr1646v2Lan3FG 134}


pr1646v2Lan3FGOutDropFilter OBJECT-TYPE
   SYNTAX      Counter64
   MAX-ACCESS  read-only
   STATUS      current
   DESCRIPTION
      "Path: ethernet3.performance.ifOutDiscardsFilter
       Info: ifOutDiscards

       64 bit unsigned wrappable counter."
   ::= {pr1646v2Lan3FG 138}


pr1646v2Lan3FGOutQueues OBJECT IDENTIFIER ::= {pr1646v2Lan3FG 129}

pr1646v2Lan3FGOutQueuesSSCTable OBJECT-TYPE
   SYNTAX      SEQUENCE OF Pr1646v2Lan3FGOutQueuesEntry
   MAX-ACCESS  not-accessible
   STATUS      current
   DESCRIPTION
      "Queue Lengths"
   ::= {pr1646v2Lan3FGOutQueues 1}

pr1646v2Lan3FGOutQueuesEntry OBJECT-TYPE
   SYNTAX      Pr1646v2Lan3FGOutQueuesEntry
   MAX-ACCESS  not-accessible
   STATUS      current
   DESCRIPTION
      ""
   INDEX      { pr1646v2Lan3FGOutQueuesTableIx }
   ::= {pr1646v2Lan3FGOutQueuesSSCTable 1}

Pr1646v2Lan3FGOutQueuesEntry ::=
   SEQUENCE
      {
      pr1646v2Lan3FGOutQueuesTableIx
         TableIndex,
      pr1646v2Lan3FGOutQueuesName
         INTEGER,
      pr1646v2Lan3FGOutQueuesLength
         Integer32,
      pr1646v2Lan3FGOutQueuesOctetLength
         Integer32,
      pr1646v2Lan3FGOutQueuesRedLength
         Integer32,
      pr1646v2Lan3FGOutQueuesPacketsTotal
         Counter64,
      pr1646v2Lan3FGOutQueuesPacketsDirectTx
         Counter64,
      pr1646v2Lan3FGOutQueuesPacketsQueued
         Counter64,
      pr1646v2Lan3FGOutQueuesPacketsDropped
         Counter64,
      pr1646v2Lan3FGOutQueuesPacketsRedDropped
         Counter64,
      pr1646v2Lan3FGOutQueuesPacketsCirTx
         Counter64,
      pr1646v2Lan3FGOutQueuesPacketsEirTx
         Counter64,
      pr1646v2Lan3FGOutQueuesPacketsViolateTx
         Counter64,
      pr1646v2Lan3FGOutQueuesOctetsTotal
         Counter64,
      pr1646v2Lan3FGOutQueuesOctetsDirectTx
         Counter64,
      pr1646v2Lan3FGOutQueuesOctetsQueued
         Counter64,
      pr1646v2Lan3FGOutQueuesOctetsDropped
         Counter64,
      pr1646v2Lan3FGOutQueuesOctetsRedDropped
         Counter64,
      pr1646v2Lan3FGOutQueuesOctetsCirTx
         Counter64,
      pr1646v2Lan3FGOutQueuesOctetsEirTx
         Counter64,
      pr1646v2Lan3FGOutQueuesOctetsViolateTx
         Counter64,
      pr1646v2Lan3FGOutQueuesOctetsBandwidth15sec
         Integer32,
      pr1646v2Lan3FGOutQueuesOctetsBandwidth30sec
         Integer32,
      pr1646v2Lan3FGOutQueuesOctetsBandwidth1min
         Integer32,
      pr1646v2Lan3FGOutQueuesOctetsBandwidth2min
         Integer32,
      pr1646v2Lan3FGOutQueuesOctetsBandwidth5min
         Integer32
      }

pr1646v2Lan3FGOutQueuesTableIx OBJECT-TYPE
   SYNTAX      TableIndex
   MAX-ACCESS  not-accessible
   STATUS      current
   DESCRIPTION
      ""
   ::= {pr1646v2Lan3FGOutQueuesEntry 11}

pr1646v2Lan3FGOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2Lan3FGOutQueuesEntry 16777216}

pr1646v2Lan3FGOutQueuesLength OBJECT-TYPE
   SYNTAX      Integer32
   MAX-ACCESS  read-only
   STATUS      current
   DESCRIPTION
      "Path: ethernet3.performance.ifOutPriorityQueues.length"
   ::= {pr1646v2Lan3FGOutQueuesEntry 33554432}

pr1646v2Lan3FGOutQueuesOctetLength OBJECT-TYPE
   SYNTAX      Integer32
   MAX-ACCESS  read-only
   STATUS      current
   DESCRIPTION
      "Path: ethernet3.performance.ifOutPriorityQueues.octetLength"
   ::= {pr1646v2Lan3FGOutQueuesEntry 150994944}

pr1646v2Lan3FGOutQueuesRedLength OBJECT-TYPE
   SYNTAX      Integer32
   MAX-ACCESS  read-only
   STATUS      current
   DESCRIPTION
      "Path: ethernet3.performance.ifOutPriorityQueues.redLength"
   ::= {pr1646v2Lan3FGOutQueuesEntry 134217728}

pr1646v2Lan3FGOutQueuesPacketsTotal OBJECT-TYPE
   SYNTAX      Counter64
   MAX-ACCESS  read-only
   STATUS      current
   DESCRIPTION
      "Path: ethernet3.performance.ifOutPriorityQueues.packets.total

       64 bit unsigned wrappable counter."
   ::= {pr1646v2Lan3FGOutQueuesEntry 50790400}

pr1646v2Lan3FGOutQueuesPacketsDirectTx OBJECT-TYPE
   SYNTAX      Counter64
   MAX-ACCESS  read-only
   STATUS      current
   DESCRIPTION
      "Path: ethernet3.performance.ifOutPriorityQueues.packets.directTx

       64 bit unsigned wrappable counter."
   ::= {pr1646v2Lan3FGOutQueuesEntry 50397184}

pr1646v2Lan3FGOutQueuesPacketsQueued OBJECT-TYPE
   SYNTAX      Counter64
   MAX-ACCESS  read-only
   STATUS      current
   DESCRIPTION
      "Path: ethernet3.performance.ifOutPriorityQueues.packets.queued

       64 bit unsigned wrappable counter."
   ::= {pr1646v2Lan3FGOutQueuesEntry 50462720}

pr1646v2Lan3FGOutQueuesPacketsDropped OBJECT-TYPE
   SYNTAX      Counter64
   MAX-ACCESS  read-only
   STATUS      current
   DESCRIPTION
      "Path: ethernet3.performance.ifOutPriorityQueues.packets.dropped

       64 bit unsigned wrappable counter."
   ::= {pr1646v2Lan3FGOutQueuesEntry 50528256}

pr1646v2Lan3FGOutQueuesPacketsRedDropped OBJECT-TYPE
   SYNTAX      Counter64
   MAX-ACCESS  read-only
   STATUS      current
   DESCRIPTION
      "Path: ethernet3.performance.ifOutPriorityQueues.packets.redDropped

       64 bit unsigned wrappable counter."
   ::= {pr1646v2Lan3FGOutQueuesEntry 50724864}

pr1646v2Lan3FGOutQueuesPacketsCirTx OBJECT-TYPE
   SYNTAX      Counter64
   MAX-ACCESS  read-only
   STATUS      current
   DESCRIPTION
      "Path: ethernet3.performance.ifOutPriorityQueues.packets.cirTx

       64 bit unsigned wrappable counter."
   ::= {pr1646v2Lan3FGOutQueuesEntry 50593792}

pr1646v2Lan3FGOutQueuesPacketsEirTx OBJECT-TYPE
   SYNTAX      Counter64
   MAX-ACCESS  read-only
   STATUS      current
   DESCRIPTION
      "Path: ethernet3.performance.ifOutPriorityQueues.packets.eirTx

       64 bit unsigned wrappable counter."
   ::= {pr1646v2Lan3FGOutQueuesEntry 50659328}

pr1646v2Lan3FGOutQueuesPacketsViolateTx OBJECT-TYPE
   SYNTAX      Counter64
   MAX-ACCESS  read-only
   STATUS      current
   DESCRIPTION
      "Path: ethernet3.performance.ifOutPriorityQueues.packets.violateTx

       64 bit unsigned wrappable counter."
   ::= {pr1646v2Lan3FGOutQueuesEntry 50855936}

pr1646v2Lan3FGOutQueuesOctetsTotal OBJECT-TYPE
   SYNTAX      Counter64
   MAX-ACCESS  read-only
   STATUS      current
   DESCRIPTION
      "Path: ethernet3.performance.ifOutPriorityQueues.octets.total

       64 bit unsigned wrappable counter."
   ::= {pr1646v2Lan3FGOutQueuesEntry 67567616}

pr1646v2Lan3FGOutQueuesOctetsDirectTx OBJECT-TYPE
   SYNTAX      Counter64
   MAX-ACCESS  read-only
   STATUS      current
   DESCRIPTION
      "Path: ethernet3.performance.ifOutPriorityQueues.octets.directTx

       64 bit unsigned wrappable counter."
   ::= {pr1646v2Lan3FGOutQueuesEntry 67174400}

pr1646v2Lan3FGOutQueuesOctetsQueued OBJECT-TYPE
   SYNTAX      Counter64
   MAX-ACCESS  read-only
   STATUS      current
   DESCRIPTION
      "Path: ethernet3.performance.ifOutPriorityQueues.octets.queued

       64 bit unsigned wrappable counter."
   ::= {pr1646v2Lan3FGOutQueuesEntry 67239936}

pr1646v2Lan3FGOutQueuesOctetsDropped OBJECT-TYPE
   SYNTAX      Counter64
   MAX-ACCESS  read-only
   STATUS      current
   DESCRIPTION
      "Path: ethernet3.performance.ifOutPriorityQueues.octets.dropped

       64 bit unsigned wrappable counter."
   ::= {pr1646v2Lan3FGOutQueuesEntry 67305472}

pr1646v2Lan3FGOutQueuesOctetsRedDropped OBJECT-TYPE
   SYNTAX      Counter64
   MAX-ACCESS  read-only
   STATUS      current
   DESCRIPTION
      "Path: ethernet3.performance.ifOutPriorityQueues.octets.redDropped

       64 bit unsigned wrappable counter."
   ::= {pr1646v2Lan3FGOutQueuesEntry 67502080}

pr1646v2Lan3FGOutQueuesOctetsCirTx OBJECT-TYPE
   SYNTAX      Counter64
   MAX-ACCESS  read-only
   STATUS      current
   DESCRIPTION
      "Path: ethernet3.performance.ifOutPriorityQueues.octets.cirTx

       64 bit unsigned wrappable counter."
   ::= {pr1646v2Lan3FGOutQueuesEntry 67371008}

pr1646v2Lan3FGOutQueuesOctetsEirTx OBJECT-TYPE
   SYNTAX      Counter64
   MAX-ACCESS  read-only
   STATUS      current
   DESCRIPTION
      "Path: ethernet3.performance.ifOutPriorityQueues.octets.eirTx

       64 bit unsigned wrappable counter."
   ::= {pr1646v2Lan3FGOutQueuesEntry 67436544}

pr1646v2Lan3FGOutQueuesOctetsViolateTx OBJECT-TYPE
   SYNTAX      Counter64
   MAX-ACCESS  read-only
   STATUS      current
   DESCRIPTION
      "Path: ethernet3.performance.ifOutPriorityQueues.octets.violateTx

       64 bit unsigned wrappable counter."
   ::= {pr1646v2Lan3FGOutQueuesEntry 67633152}

pr1646v2Lan3FGOutQueuesOctetsBandwidth15sec OBJECT-TYPE
   SYNTAX      Integer32
   MAX-ACCESS  read-only
   STATUS      current
   DESCRIPTION
      "Path: ethernet3.performance.ifOutPriorityQueues.octets.bandwidth.15sec

       unit name = bps
       formula = 8 * ; 8 /"
   ::= {pr1646v2Lan3FGOutQueuesEntry 70386944}

pr1646v2Lan3FGOutQueuesOctetsBandwidth30sec OBJECT-TYPE
   SYNTAX      Integer32
   MAX-ACCESS  read-only
   STATUS      current
   DESCRIPTION
      "Path: ethernet3.performance.ifOutPriorityQueues.octets.bandwidth.30sec

       unit name = bps
       formula = 8 * ; 8 /"
   ::= {pr1646v2Lan3FGOutQueuesEntry 70388224}

pr1646v2Lan3FGOutQueuesOctetsBandwidth1min OBJECT-TYPE
   SYNTAX      Integer32
   MAX-ACCESS  read-only
   STATUS      current
   DESCRIPTION
      "Path: ethernet3.performance.ifOutPriorityQueues.octets.bandwidth.1min

       unit name = bps
       formula = 8 * ; 8 /"
   ::= {pr1646v2Lan3FGOutQueuesEntry 70390784}

pr1646v2Lan3FGOutQueuesOctetsBandwidth2min OBJECT-TYPE
   SYNTAX      Integer32
   MAX-ACCESS  read-only
   STATUS      current
   DESCRIPTION
      "Path: ethernet3.performance.ifOutPriorityQueues.octets.bandwidth.2min

       unit name = bps
       formula = 8 * ; 8 /"
   ::= {pr1646v2Lan3FGOutQueuesEntry 70395904}

pr1646v2Lan3FGOutQueuesOctetsBandwidth5min OBJECT-TYPE
   SYNTAX      Integer32
   MAX-ACCESS  read-only
   STATUS      current
   DESCRIPTION
      "Path: ethernet3.performance.ifOutPriorityQueues.octets.bandwidth.5min

       unit name = bps
       formula = 8 * ; 8 /"
   ::= {pr1646v2Lan3FGOutQueuesEntry 70411264}

pr1646v2Lan3FGOutQueuesH2Performance OBJECT-TYPE
   SYNTAX      SEQUENCE OF Pr1646v2Lan3FGOutQueuesH2PerformanceEntry
   MAX-ACCESS  not-accessible
   STATUS      current
   DESCRIPTION
      ""
   ::= {pr1646v2Lan3FGOutQueues 83886080}

pr1646v2Lan3FGOutQueuesH2PerformanceEntry OBJECT-TYPE
   SYNTAX      Pr1646v2Lan3FGOutQueuesH2PerformanceEntry
   MAX-ACCESS  not-accessible
   STATUS      current
   DESCRIPTION
      ""
   INDEX      { pr1646v2Lan3FGOutQueuesTableIx,
                pr1646v2Lan3FGOutQueuesH2PerformanceTableIx }
   ::= {pr1646v2Lan3FGOutQueuesH2Performance 1}

Pr1646v2Lan3FGOutQueuesH2PerformanceEntry ::=
   SEQUENCE
      {
      pr1646v2Lan3FGOutQueuesH2PerformanceTableIx
         TableIndex,
      pr1646v2Lan3FGOutQueuesH2PerformanceSysUpTime
         TimeTicks,
      pr1646v2Lan3FGOutQueuesH2PerformanceTotPkts
         Counter64,
      pr1646v2Lan3FGOutQueuesH2PerformanceDirTxPkts
         Counter64,
      pr1646v2Lan3FGOutQueuesH2PerformanceQdPkts
         Counter64,
      pr1646v2Lan3FGOutQueuesH2PerformanceDropPkts
         Counter64,
      pr1646v2Lan3FGOutQueuesH2PerformanceRDropPkts
         Counter64,
      pr1646v2Lan3FGOutQueuesH2PerformanceCirTxPkts
         Counter64,
      pr1646v2Lan3FGOutQueuesH2PerformanceEirTxPkts
         Counter64,
      pr1646v2Lan3FGOutQueuesH2PerformanceViolTxPkts
         Counter64,
      pr1646v2Lan3FGOutQueuesH2PerformanceTotOcts
         Counter64,
      pr1646v2Lan3FGOutQueuesH2PerformanceDirTxOcts
         Counter64,
      pr1646v2Lan3FGOutQueuesH2PerformanceQdOcts
         Counter64,
      pr1646v2Lan3FGOutQueuesH2PerformanceDropOcts
         Counter64,
      pr1646v2Lan3FGOutQueuesH2PerformanceRDropOcts
         Counter64,
      pr1646v2Lan3FGOutQueuesH2PerformanceCirTxOcts
         Counter64,
      pr1646v2Lan3FGOutQueuesH2PerformanceEirTxOcts
         Counter64,
      pr1646v2Lan3FGOutQueuesH2PerformanceViolTxOcts
         Counter64,
      pr1646v2Lan3FGOutQueuesH2PerformanceBandwidth
         Integer32
      }

pr1646v2Lan3FGOutQueuesH2PerformanceTableIx OBJECT-TYPE
   SYNTAX      TableIndex
   MAX-ACCESS  not-accessible
   STATUS      current
   DESCRIPTION
      ""
   ::= {pr1646v2Lan3FGOutQueuesH2PerformanceEntry 11}

pr1646v2Lan3FGOutQueuesH2PerformanceSysUpTime OBJECT-TYPE
   SYNTAX      TimeTicks
   MAX-ACCESS  read-only
   STATUS      current
   DESCRIPTION
      "Path: ethernet3.performance.ifOutPriorityQueues.h2Performance.sysUpTime

       Time in centi-second."
   ::= {pr1646v2Lan3FGOutQueuesH2PerformanceEntry 16777216}

pr1646v2Lan3FGOutQueuesH2PerformanceTotPkts OBJECT-TYPE
   SYNTAX      Counter64
   MAX-ACCESS  read-only
   STATUS      current
   DESCRIPTION
      "Path: ethernet3.performance.ifOutPriorityQueues.h2Performance.totalPkts

       64 bit unsigned wrappable counter."
   ::= {pr1646v2Lan3FGOutQueuesH2PerformanceEntry 234881024}

pr1646v2Lan3FGOutQueuesH2PerformanceDirTxPkts OBJECT-TYPE
   SYNTAX      Counter64
   MAX-ACCESS  read-only
   STATUS      current
   DESCRIPTION
      "Path: ethernet3.performance.ifOutPriorityQueues.h2Performance.directTxPkts

       64 bit unsigned wrappable counter."
   ::= {pr1646v2Lan3FGOutQueuesH2PerformanceEntry 33554432}

pr1646v2Lan3FGOutQueuesH2PerformanceQdPkts OBJECT-TYPE
   SYNTAX      Counter64
   MAX-ACCESS  read-only
   STATUS      current
   DESCRIPTION
      "Path: ethernet3.performance.ifOutPriorityQueues.h2Performance.queuedPkts

       64 bit unsigned wrappable counter."
   ::= {pr1646v2Lan3FGOutQueuesH2PerformanceEntry 50331648}

pr1646v2Lan3FGOutQueuesH2PerformanceDropPkts OBJECT-TYPE
   SYNTAX      Counter64
   MAX-ACCESS  read-only
   STATUS      current
   DESCRIPTION
      "Path: ethernet3.performance.ifOutPriorityQueues.h2Performance.droppedPkts

       64 bit unsigned wrappable counter."
   ::= {pr1646v2Lan3FGOutQueuesH2PerformanceEntry 67108864}

pr1646v2Lan3FGOutQueuesH2PerformanceRDropPkts OBJECT-TYPE
   SYNTAX      Counter64
   MAX-ACCESS  read-only
   STATUS      current
   DESCRIPTION
      "Path: ethernet3.performance.ifOutPriorityQueues.h2Performance.redDroppedPkts

       64 bit unsigned wrappable counter."
   ::= {pr1646v2Lan3FGOutQueuesH2PerformanceEntry 201326592}

pr1646v2Lan3FGOutQueuesH2PerformanceCirTxPkts OBJECT-TYPE
   SYNTAX      Counter64
   MAX-ACCESS  read-only
   STATUS      current
   DESCRIPTION
      "Path: ethernet3.performance.ifOutPriorityQueues.h2Performance.cirTxPkts

       64 bit unsigned wrappable counter."
   ::= {pr1646v2Lan3FGOutQueuesH2PerformanceEntry 83886080}

pr1646v2Lan3FGOutQueuesH2PerformanceEirTxPkts OBJECT-TYPE
   SYNTAX      Counter64
   MAX-ACCESS  read-only
   STATUS      current
   DESCRIPTION
      "Path: ethernet3.performance.ifOutPriorityQueues.h2Performance.eirTxPkts

       64 bit unsigned wrappable counter."
   ::= {pr1646v2Lan3FGOutQueuesH2PerformanceEntry 100663296}

pr1646v2Lan3FGOutQueuesH2PerformanceViolTxPkts OBJECT-TYPE
   SYNTAX      Counter64
   MAX-ACCESS  read-only
   STATUS      current
   DESCRIPTION
      "Path: ethernet3.performance.ifOutPriorityQueues.h2Performance.violateTxPkts

       64 bit unsigned wrappable counter."
   ::= {pr1646v2Lan3FGOutQueuesH2PerformanceEntry 301989888}

pr1646v2Lan3FGOutQueuesH2PerformanceTotOcts OBJECT-TYPE
   SYNTAX      Counter64
   MAX-ACCESS  read-only
   STATUS      current
   DESCRIPTION
      "Path: ethernet3.performance.ifOutPriorityQueues.h2Performance.totalOctets

       64 bit unsigned wrappable counter."
   ::= {pr1646v2Lan3FGOutQueuesH2PerformanceEntry 251658240}

pr1646v2Lan3FGOutQueuesH2PerformanceDirTxOcts OBJECT-TYPE
   SYNTAX      Counter64
   MAX-ACCESS  read-only
   STATUS      current
   DESCRIPTION
      "Path: ethernet3.performance.ifOutPriorityQueues.h2Performance.directTxOctets

       64 bit unsigned wrappable counter."
   ::= {pr1646v2Lan3FGOutQueuesH2PerformanceEntry 117440512}

pr1646v2Lan3FGOutQueuesH2PerformanceQdOcts OBJECT-TYPE
   SYNTAX      Counter64
   MAX-ACCESS  read-only
   STATUS      current
   DESCRIPTION
      "Path: ethernet3.performance.ifOutPriorityQueues.h2Performance.queuedOctets

       64 bit unsigned wrappable counter."
   ::= {pr1646v2Lan3FGOutQueuesH2PerformanceEntry 134217728}

pr1646v2Lan3FGOutQueuesH2PerformanceDropOcts OBJECT-TYPE
   SYNTAX      Counter64
   MAX-ACCESS  read-only
   STATUS      current
   DESCRIPTION
      "Path: ethernet3.performance.ifOutPriorityQueues.h2Performance.droppedOctets

       64 bit unsigned wrappable counter."
   ::= {pr1646v2Lan3FGOutQueuesH2PerformanceEntry 150994944}

pr1646v2Lan3FGOutQueuesH2PerformanceRDropOcts OBJECT-TYPE
   SYNTAX      Counter64
   MAX-ACCESS  read-only
   STATUS      current
   DESCRIPTION
      "Path: ethernet3.performance.ifOutPriorityQueues.h2Performance.redDroppedOctets

       64 bit unsigned wrappable counter."
   ::= {pr1646v2Lan3FGOutQueuesH2PerformanceEntry 218103808}

pr1646v2Lan3FGOutQueuesH2PerformanceCirTxOcts OBJECT-TYPE
   SYNTAX      Counter64
   MAX-ACCESS  read-only
   STATUS      current
   DESCRIPTION
      "Path: ethernet3.performance.ifOutPriorityQueues.h2Performance.cirTxOctets

       64 bit unsigned wrappable counter."
   ::= {pr1646v2Lan3FGOutQueuesH2PerformanceEntry 167772160}

pr1646v2Lan3FGOutQueuesH2PerformanceEirTxOcts OBJECT-TYPE
   SYNTAX      Counter64
   MAX-ACCESS  read-only
   STATUS      current
   DESCRIPTION
      "Path: ethernet3.performance.ifOutPriorityQueues.h2Performance.eirTxOctets

       64 bit unsigned wrappable counter."
   ::= {pr1646v2Lan3FGOutQueuesH2PerformanceEntry 184549376}

pr1646v2Lan3FGOutQueuesH2PerformanceViolTxOcts OBJECT-TYPE
   SYNTAX      Counter64
   MAX-ACCESS  read-only
   STATUS      current
   DESCRIPTION
      "Path: ethernet3.performance.ifOutPriorityQueues.h2Performance.violateTxOctets

       64 bit unsigned wrappable counter."
   ::= {pr1646v2Lan3FGOutQueuesH2PerformanceEntry 318767104}

pr1646v2Lan3FGOutQueuesH2PerformanceBandwidth OBJECT-TYPE
   SYNTAX      Integer32
   MAX-ACCESS  read-only
   STATUS      current
   DESCRIPTION
      "Path: ethernet3.performance.ifOutPriorityQueues.h2Performance.bandwidth

       unit name = bps
       formula = 8 * ; 8 /"
   ::= {pr1646v2Lan3FGOutQueuesH2PerformanceEntry 268435456}

pr1646v2Lan3FGOutQueuesH24Performance OBJECT-TYPE
   SYNTAX      SEQUENCE OF Pr1646v2Lan3FGOutQueuesH24PerformanceEntry
   MAX-ACCESS  not-accessible
   STATUS      current
   DESCRIPTION
      ""
   ::= {pr1646v2Lan3FGOutQueues 100663296}

pr1646v2Lan3FGOutQueuesH24PerformanceEntry OBJECT-TYPE
   SYNTAX      Pr1646v2Lan3FGOutQueuesH24PerformanceEntry
   MAX-ACCESS  not-accessible
   STATUS      current
   DESCRIPTION
      ""
   INDEX      { pr1646v2Lan3FGOutQueuesTableIx,
                pr1646v2Lan3FGOutQueuesH24PerformanceTableIx }
   ::= {pr1646v2Lan3FGOutQueuesH24Performance 1}

Pr1646v2Lan3FGOutQueuesH24PerformanceEntry ::=
   SEQUENCE
      {
      pr1646v2Lan3FGOutQueuesH24PerformanceTableIx
         TableIndex,
      pr1646v2Lan3FGOutQueuesH24PerformanceSysUpTime
         TimeTicks,
      pr1646v2Lan3FGOutQueuesH24PerformanceTotPkts
         Counter64,
      pr1646v2Lan3FGOutQueuesH24PerformanceDirTxPkts
         Counter64,
      pr1646v2Lan3FGOutQueuesH24PerformanceQdPkts
         Counter64,
      pr1646v2Lan3FGOutQueuesH24PerformanceDropPkts
         Counter64,
      pr1646v2Lan3FGOutQueuesH24PerformanceRDropPkts
         Counter64,
      pr1646v2Lan3FGOutQueuesH24PerformanceCirTxPkts
         Counter64,
      pr1646v2Lan3FGOutQueuesH24PerformanceEirTxPkts
         Counter64,
      pr1646v2Lan3FGOutQueuesH24PerformanceViolTxPkts
         Counter64,
      pr1646v2Lan3FGOutQueuesH24PerformanceTotOcts
         Counter64,
      pr1646v2Lan3FGOutQueuesH24PerformanceDirTxOcts
         Counter64,
      pr1646v2Lan3FGOutQueuesH24PerformanceQdOcts
         Counter64,
      pr1646v2Lan3FGOutQueuesH24PerformanceDropOcts
         Counter64,
      pr1646v2Lan3FGOutQueuesH24PerformanceRDropOcts
         Counter64,
      pr1646v2Lan3FGOutQueuesH24PerformanceCirTxOcts
         Counter64,
      pr1646v2Lan3FGOutQueuesH24PerformanceEirTxOcts
         Counter64,
      pr1646v2Lan3FGOutQueuesH24PerformanceViolTxOcts
         Counter64,
      pr1646v2Lan3FGOutQueuesH24PerformanceBandwidth
         Integer32
      }

pr1646v2Lan3FGOutQueuesH24PerformanceTableIx OBJECT-TYPE
   SYNTAX      TableIndex
   MAX-ACCESS  not-accessible
   STATUS      current
   DESCRIPTION
      ""
   ::= {pr1646v2Lan3FGOutQueuesH24PerformanceEntry 11}

pr1646v2Lan3FGOutQueuesH24PerformanceSysUpTime OBJECT-TYPE
   SYNTAX      TimeTicks
   MAX-ACCESS  read-only
   STATUS      current
   DESCRIPTION
      "Path: ethernet3.performance.ifOutPriorityQueues.h24Performance.sysUpTime

       Time in centi-second."
   ::= {pr1646v2Lan3FGOutQueuesH24PerformanceEntry 16777216}

pr1646v2Lan3FGOutQueuesH24PerformanceTotPkts OBJECT-TYPE
   SYNTAX      Counter64
   MAX-ACCESS  read-only
   STATUS      current
   DESCRIPTION
      "Path: ethernet3.performance.ifOutPriorityQueues.h24Performance.totalPkts

       64 bit unsigned wrappable counter."
   ::= {pr1646v2Lan3FGOutQueuesH24PerformanceEntry 234881024}

pr1646v2Lan3FGOutQueuesH24PerformanceDirTxPkts OBJECT-TYPE
   SYNTAX      Counter64
   MAX-ACCESS  read-only
   STATUS      current
   DESCRIPTION
      "Path: ethernet3.performance.ifOutPriorityQueues.h24Performance.directTxPkts

       64 bit unsigned wrappable counter."
   ::= {pr1646v2Lan3FGOutQueuesH24PerformanceEntry 33554432}

pr1646v2Lan3FGOutQueuesH24PerformanceQdPkts OBJECT-TYPE
   SYNTAX      Counter64
   MAX-ACCESS  read-only
   STATUS      current
   DESCRIPTION
      "Path: ethernet3.performance.ifOutPriorityQueues.h24Performance.queuedPkts

       64 bit unsigned wrappable counter."
   ::= {pr1646v2Lan3FGOutQueuesH24PerformanceEntry 50331648}

pr1646v2Lan3FGOutQueuesH24PerformanceDropPkts OBJECT-TYPE
   SYNTAX      Counter64
   MAX-ACCESS  read-only
   STATUS      current
   DESCRIPTION
      "Path: ethernet3.performance.ifOutPriorityQueues.h24Performance.droppedPkts

       64 bit unsigned wrappable counter."
   ::= {pr1646v2Lan3FGOutQueuesH24PerformanceEntry 67108864}

pr1646v2Lan3FGOutQueuesH24PerformanceRDropPkts OBJECT-TYPE
   SYNTAX      Counter64
   MAX-ACCESS  read-only
   STATUS      current
   DESCRIPTION
      "Path: ethernet3.performance.ifOutPriorityQueues.h24Performance.redDroppedPkts

       64 bit unsigned wrappable counter."
   ::= {pr1646v2Lan3FGOutQueuesH24PerformanceEntry 201326592}

pr1646v2Lan3FGOutQueuesH24PerformanceCirTxPkts OBJECT-TYPE
   SYNTAX      Counter64
   MAX-ACCESS  read-only
   STATUS      current
   DESCRIPTION
      "Path: ethernet3.performance.ifOutPriorityQueues.h24Performance.cirTxPkts

       64 bit unsigned wrappable counter."
   ::= {pr1646v2Lan3FGOutQueuesH24PerformanceEntry 83886080}

pr1646v2Lan3FGOutQueuesH24PerformanceEirTxPkts OBJECT-TYPE
   SYNTAX      Counter64
   MAX-ACCESS  read-only
   STATUS      current
   DESCRIPTION
      "Path: ethernet3.performance.ifOutPriorityQueues.h24Performance.eirTxPkts

       64 bit unsigned wrappable counter."
   ::= {pr1646v2Lan3FGOutQueuesH24PerformanceEntry 100663296}

pr1646v2Lan3FGOutQueuesH24PerformanceViolTxPkts OBJECT-TYPE
   SYNTAX      Counter64
   MAX-ACCESS  read-only
   STATUS      current
   DESCRIPTION
      "Path: ethernet3.performance.ifOutPriorityQueues.h24Performance.violateTxPkts

       64 bit unsigned wrappable counter."
   ::= {pr1646v2Lan3FGOutQueuesH24PerformanceEntry 301989888}

pr1646v2Lan3FGOutQueuesH24PerformanceTotOcts OBJECT-TYPE
   SYNTAX      Counter64
   MAX-ACCESS  read-only
   STATUS      current
   DESCRIPTION
      "Path: ethernet3.performance.ifOutPriorityQueues.h24Performance.totalOctets

       64 bit unsigned wrappable counter."
   ::= {pr1646v2Lan3FGOutQueuesH24PerformanceEntry 251658240}

pr1646v2Lan3FGOutQueuesH24PerformanceDirTxOcts OBJECT-TYPE
   SYNTAX      Counter64
   MAX-ACCESS  read-only
   STATUS      current
   DESCRIPTION
      "Path: ethernet3.performance.ifOutPriorityQueues.h24Performance.directTxOctets

       64 bit unsigned wrappable counter."
   ::= {pr1646v2Lan3FGOutQueuesH24PerformanceEntry 117440512}

pr1646v2Lan3FGOutQueuesH24PerformanceQdOcts OBJECT-TYPE
   SYNTAX      Counter64
   MAX-ACCESS  read-only
   STATUS      current
   DESCRIPTION
      "Path: ethernet3.performance.ifOutPriorityQueues.h24Performance.queuedOctets

       64 bit unsigned wrappable counter."
   ::= {pr1646v2Lan3FGOutQueuesH24PerformanceEntry 134217728}

pr1646v2Lan3FGOutQueuesH24PerformanceDropOcts OBJECT-TYPE
   SYNTAX      Counter64
   MAX-ACCESS  read-only
   STATUS      current
   DESCRIPTION
      "Path: ethernet3.performance.ifOutPriorityQueues.h24Performance.droppedOctets

       64 bit unsigned wrappable counter."
   ::= {pr1646v2Lan3FGOutQueuesH24PerformanceEntry 150994944}

pr1646v2Lan3FGOutQueuesH24PerformanceRDropOcts OBJECT-TYPE
   SYNTAX      Counter64
   MAX-ACCESS  read-only
   STATUS      current
   DESCRIPTION
      "Path: ethernet3.performance.ifOutPriorityQueues.h24Performance.redDroppedOctets

       64 bit unsigned wrappable counter."
   ::= {pr1646v2Lan3FGOutQueuesH24PerformanceEntry 218103808}

pr1646v2Lan3FGOutQueuesH24PerformanceCirTxOcts OBJECT-TYPE
   SYNTAX      Counter64
   MAX-ACCESS  read-only
   STATUS      current
   DESCRIPTION
      "Path: ethernet3.performance.ifOutPriorityQueues.h24Performance.cirTxOctets

       64 bit unsigned wrappable counter."
   ::= {pr1646v2Lan3FGOutQueuesH24PerformanceEntry 167772160}

pr1646v2Lan3FGOutQueuesH24PerformanceEirTxOcts OBJECT-TYPE
   SYNTAX      Counter64
   MAX-ACCESS  read-only
   STATUS      current
   DESCRIPTION
      "Path: ethernet3.performance.ifOutPriorityQueues.h24Performance.eirTxOctets

       64 bit unsigned wrappable counter."
   ::= {pr1646v2Lan3FGOutQueuesH24PerformanceEntry 184549376}

pr1646v2Lan3FGOutQueuesH24PerformanceViolTxOcts OBJECT-TYPE
   SYNTAX      Counter64
   MAX-ACCESS  read-only
   STATUS      current
   DESCRIPTION
      "Path: ethernet3.performance.ifOutPriorityQueues.h24Performance.violateTxOctets

       64 bit unsigned wrappable counter."
   ::= {pr1646v2Lan3FGOutQueuesH24PerformanceEntry 318767104}

pr1646v2Lan3FGOutQueuesH24PerformanceBandwidth OBJECT-TYPE
   SYNTAX      Integer32
   MAX-ACCESS  read-only
   STATUS      current
   DESCRIPTION
      "Path: ethernet3.performance.ifOutPriorityQueues.h24Performance.bandwidth

       unit name = bps
       formula = 8 * ; 8 /"
   ::= {pr1646v2Lan3FGOutQueuesH24PerformanceEntry 268435456}

pr1646v2Lan3FGOutQueuesD7Performance OBJECT-TYPE
   SYNTAX      SEQUENCE OF Pr1646v2Lan3FGOutQueuesD7PerformanceEntry
   MAX-ACCESS  not-accessible
   STATUS      current
   DESCRIPTION
      ""
   ::= {pr1646v2Lan3FGOutQueues 117440512}

pr1646v2Lan3FGOutQueuesD7PerformanceEntry OBJECT-TYPE
   SYNTAX      Pr1646v2Lan3FGOutQueuesD7PerformanceEntry
   MAX-ACCESS  not-accessible
   STATUS      current
   DESCRIPTION
      ""
   INDEX      { pr1646v2Lan3FGOutQueuesTableIx,
                pr1646v2Lan3FGOutQueuesD7PerformanceTableIx }
   ::= {pr1646v2Lan3FGOutQueuesD7Performance 1}

Pr1646v2Lan3FGOutQueuesD7PerformanceEntry ::=
   SEQUENCE
      {
      pr1646v2Lan3FGOutQueuesD7PerformanceTableIx
         TableIndex,
      pr1646v2Lan3FGOutQueuesD7PerformanceSysUpTime
         TimeTicks,
      pr1646v2Lan3FGOutQueuesD7PerformanceTotPkts
         Counter64,
      pr1646v2Lan3FGOutQueuesD7PerformanceDirTxPkts
         Counter64,
      pr1646v2Lan3FGOutQueuesD7PerformanceQdPkts
         Counter64,
      pr1646v2Lan3FGOutQueuesD7PerformanceDropPkts
         Counter64,
      pr1646v2Lan3FGOutQueuesD7PerformanceRDropPkts
         Counter64,
      pr1646v2Lan3FGOutQueuesD7PerformanceCirTxPkts
         Counter64,
      pr1646v2Lan3FGOutQueuesD7PerformanceEirTxPkts
         Counter64,
      pr1646v2Lan3FGOutQueuesD7PerformanceViolTxPkts
         Counter64,
      pr1646v2Lan3FGOutQueuesD7PerformanceTotOcts
         Counter64,
      pr1646v2Lan3FGOutQueuesD7PerformanceDirTxOcts
         Counter64,
      pr1646v2Lan3FGOutQueuesD7PerformanceQdOcts
         Counter64,
      pr1646v2Lan3FGOutQueuesD7PerformanceDropOcts
         Counter64,
      pr1646v2Lan3FGOutQueuesD7PerformanceRDropOcts
         Counter64,
      pr1646v2Lan3FGOutQueuesD7PerformanceCirTxOcts
         Counter64,
      pr1646v2Lan3FGOutQueuesD7PerformanceEirTxOcts
         Counter64,
      pr1646v2Lan3FGOutQueuesD7PerformanceViolTxOcts
         Counter64,
      pr1646v2Lan3FGOutQueuesD7PerformanceBandwidth
         Integer32
      }

pr1646v2Lan3FGOutQueuesD7PerformanceTableIx OBJECT-TYPE
   SYNTAX      TableIndex
   MAX-ACCESS  not-accessible
   STATUS      current
   DESCRIPTION
      ""
   ::= {pr1646v2Lan3FGOutQueuesD7PerformanceEntry 11}

pr1646v2Lan3FGOutQueuesD7PerformanceSysUpTime OBJECT-TYPE
   SYNTAX      TimeTicks
   MAX-ACCESS  read-only
   STATUS      current
   DESCRIPTION
      "Path: ethernet3.performance.ifOutPriorityQueues.d7Performance.sysUpTime

       Time in centi-second."
   ::= {pr1646v2Lan3FGOutQueuesD7PerformanceEntry 16777216}

pr1646v2Lan3FGOutQueuesD7PerformanceTotPkts OBJECT-TYPE
   SYNTAX      Counter64
   MAX-ACCESS  read-only
   STATUS      current
   DESCRIPTION
      "Path: ethernet3.performance.ifOutPriorityQueues.d7Performance.totalPkts

       64 bit unsigned wrappable counter."
   ::= {pr1646v2Lan3FGOutQueuesD7PerformanceEntry 234881024}

pr1646v2Lan3FGOutQueuesD7PerformanceDirTxPkts OBJECT-TYPE
   SYNTAX      Counter64
   MAX-ACCESS  read-only
   STATUS      current
   DESCRIPTION
      "Path: ethernet3.performance.ifOutPriorityQueues.d7Performance.directTxPkts

       64 bit unsigned wrappable counter."
   ::= {pr1646v2Lan3FGOutQueuesD7PerformanceEntry 33554432}

pr1646v2Lan3FGOutQueuesD7PerformanceQdPkts OBJECT-TYPE
   SYNTAX      Counter64
   MAX-ACCESS  read-only
   STATUS      current
   DESCRIPTION
      "Path: ethernet3.performance.ifOutPriorityQueues.d7Performance.queuedPkts

       64 bit unsigned wrappable counter."
   ::= {pr1646v2Lan3FGOutQueuesD7PerformanceEntry 50331648}

pr1646v2Lan3FGOutQueuesD7PerformanceDropPkts OBJECT-TYPE
   SYNTAX      Counter64
   MAX-ACCESS  read-only
   STATUS      current
   DESCRIPTION
      "Path: ethernet3.performance.ifOutPriorityQueues.d7Performance.droppedPkts

       64 bit unsigned wrappable counter."
   ::= {pr1646v2Lan3FGOutQueuesD7PerformanceEntry 67108864}

pr1646v2Lan3FGOutQueuesD7PerformanceRDropPkts OBJECT-TYPE
   SYNTAX      Counter64
   MAX-ACCESS  read-only
   STATUS      current
   DESCRIPTION
      "Path: ethernet3.performance.ifOutPriorityQueues.d7Performance.redDroppedPkts

       64 bit unsigned wrappable counter."
   ::= {pr1646v2Lan3FGOutQueuesD7PerformanceEntry 201326592}

pr1646v2Lan3FGOutQueuesD7PerformanceCirTxPkts OBJECT-TYPE
   SYNTAX      Counter64
   MAX-ACCESS  read-only
   STATUS      current
   DESCRIPTION
      "Path: ethernet3.performance.ifOutPriorityQueues.d7Performance.cirTxPkts

       64 bit unsigned wrappable counter."
   ::= {pr1646v2Lan3FGOutQueuesD7PerformanceEntry 83886080}

pr1646v2Lan3FGOutQueuesD7PerformanceEirTxPkts OBJECT-TYPE
   SYNTAX      Counter64
   MAX-ACCESS  read-only
   STATUS      current
   DESCRIPTION
      "Path: ethernet3.performance.ifOutPriorityQueues.d7Performance.eirTxPkts

       64 bit unsigned wrappable counter."
   ::= {pr1646v2Lan3FGOutQueuesD7PerformanceEntry 100663296}

pr1646v2Lan3FGOutQueuesD7PerformanceViolTxPkts OBJECT-TYPE
   SYNTAX      Counter64
   MAX-ACCESS  read-only
   STATUS      current
   DESCRIPTION
      "Path: ethernet3.performance.ifOutPriorityQueues.d7Performance.violateTxPkts

       64 bit unsigned wrappable counter."
   ::= {pr1646v2Lan3FGOutQueuesD7PerformanceEntry 301989888}

pr1646v2Lan3FGOutQueuesD7PerformanceTotOcts OBJECT-TYPE
   SYNTAX      Counter64
   MAX-ACCESS  read-only
   STATUS      current
   DESCRIPTION
      "Path: ethernet3.performance.ifOutPriorityQueues.d7Performance.totalOctets

       64 bit unsigned wrappable counter."
   ::= {pr1646v2Lan3FGOutQueuesD7PerformanceEntry 251658240}

pr1646v2Lan3FGOutQueuesD7PerformanceDirTxOcts OBJECT-TYPE
   SYNTAX      Counter64
   MAX-ACCESS  read-only
   STATUS      current
   DESCRIPTION
      "Path: ethernet3.performance.ifOutPriorityQueues.d7Performance.directTxOctets

       64 bit unsigned wrappable counter."
   ::= {pr1646v2Lan3FGOutQueuesD7PerformanceEntry 117440512}

pr1646v2Lan3FGOutQueuesD7PerformanceQdOcts OBJECT-TYPE
   SYNTAX      Counter64
   MAX-ACCESS  read-only
   STATUS      current
   DESCRIPTION
      "Path: ethernet3.performance.ifOutPriorityQueues.d7Performance.queuedOctets

       64 bit unsigned wrappable counter."
   ::= {pr1646v2Lan3FGOutQueuesD7PerformanceEntry 134217728}

pr1646v2Lan3FGOutQueuesD7PerformanceDropOcts OBJECT-TYPE
   SYNTAX      Counter64
   MAX-ACCESS  read-only
   STATUS      current
   DESCRIPTION
      "Path: ethernet3.performance.ifOutPriorityQueues.d7Performance.droppedOctets

       64 bit unsigned wrappable counter."
   ::= {pr1646v2Lan3FGOutQueuesD7PerformanceEntry 150994944}

pr1646v2Lan3FGOutQueuesD7PerformanceRDropOcts OBJECT-TYPE
   SYNTAX      Counter64
   MAX-ACCESS  read-only
   STATUS      current
   DESCRIPTION
      "Path: ethernet3.performance.ifOutPriorityQueues.d7Performance.redDroppedOctets

       64 bit unsigned wrappable counter."
   ::= {pr1646v2Lan3FGOutQueuesD7PerformanceEntry 218103808}

pr1646v2Lan3FGOutQueuesD7PerformanceCirTxOcts OBJECT-TYPE
   SYNTAX      Counter64
   MAX-ACCESS  read-only
   STATUS      current
   DESCRIPTION
      "Path: ethernet3.performance.ifOutPriorityQueues.d7Performance.cirTxOctets

       64 bit unsigned wrappable counter."
   ::= {pr1646v2Lan3FGOutQueuesD7PerformanceEntry 167772160}

pr1646v2Lan3FGOutQueuesD7PerformanceEirTxOcts OBJECT-TYPE
   SYNTAX      Counter64
   MAX-ACCESS  read-only
   STATUS      current
   DESCRIPTION
      "Path: ethernet3.performance.ifOutPriorityQueues.d7Performance.eirTxOctets

       64 bit unsigned wrappable counter."
   ::= {pr1646v2Lan3FGOutQueuesD7PerformanceEntry 184549376}

pr1646v2Lan3FGOutQueuesD7PerformanceViolTxOcts OBJECT-TYPE
   SYNTAX      Counter64
   MAX-ACCESS  read-only
   STATUS      current
   DESCRIPTION
      "Path: ethernet3.performance.ifOutPriorityQueues.d7Performance.violateTxOctets

       64 bit unsigned wrappable counter."
   ::= {pr1646v2Lan3FGOutQueuesD7PerformanceEntry 318767104}

pr1646v2Lan3FGOutQueuesD7PerformanceBandwidth OBJECT-TYPE
   SYNTAX      Integer32
   MAX-ACCESS  read-only
   STATUS      current
   DESCRIPTION
      "Path: ethernet3.performance.ifOutPriorityQueues.d7Performance.bandwidth

       unit name = bps
       formula = 8 * ; 8 /"
   ::= {pr1646v2Lan3FGOutQueuesD7PerformanceEntry 268435456}


pr1646v2Lan3FGOutBandwidth OBJECT IDENTIFIER ::= {pr1646v2Lan3FG 182}

pr1646v2Lan3FGOutBandwidthSSC OBJECT IDENTIFIER ::= {pr1646v2Lan3FGOutBandwidth 1}

pr1646v2Lan3FGOutBandwidthEntry OBJECT IDENTIFIER ::= {pr1646v2Lan3FGOutBandwidthSSC 1}

pr1646v2Lan3FGOutBandwidth15sec OBJECT-TYPE
   SYNTAX      Integer32
   MAX-ACCESS  read-only
   STATUS      current
   DESCRIPTION
      "Path: ethernet3.performance.ifOutBandwidth.15sec

       unit name = bps
       formula = 8 * ; 8 /"
   ::= {pr1646v2Lan3FGOutBandwidthEntry 83886080}

pr1646v2Lan3FGOutBandwidth30sec OBJECT-TYPE
   SYNTAX      Integer32
   MAX-ACCESS  read-only
   STATUS      current
   DESCRIPTION
      "Path: ethernet3.performance.ifOutBandwidth.30sec

       unit name = bps
       formula = 8 * ; 8 /"
   ::= {pr1646v2Lan3FGOutBandwidthEntry 167772160}

pr1646v2Lan3FGOutBandwidth1min OBJECT-TYPE
   SYNTAX      Integer32
   MAX-ACCESS  read-only
   STATUS      current
   DESCRIPTION
      "Path: ethernet3.performance.ifOutBandwidth.1min

       unit name = bps
       formula = 8 * ; 8 /"
   ::= {pr1646v2Lan3FGOutBandwidthEntry 335544320}

pr1646v2Lan3FGOutBandwidth2min OBJECT-TYPE
   SYNTAX      Integer32
   MAX-ACCESS  read-only
   STATUS      current
   DESCRIPTION
      "Path: ethernet3.performance.ifOutBandwidth.2min

       unit name = bps
       formula = 8 * ; 8 /"
   ::= {pr1646v2Lan3FGOutBandwidthEntry 671088640}

pr1646v2Lan3FGOutBandwidth5min OBJECT-TYPE
   SYNTAX      Integer32
   MAX-ACCESS  read-only
   STATUS      current
   DESCRIPTION
      "Path: ethernet3.performance.ifOutBandwidth.5min

       unit name = bps
       formula = 8 * ; 8 /"
   ::= {pr1646v2Lan3FGOutBandwidthEntry 1677721600}


pr1646v2Lan3FGInP OBJECT IDENTIFIER ::= {pr1646v2Lan3FG 307}

pr1646v2Lan3FGInPSSCTable OBJECT-TYPE
   SYNTAX      SEQUENCE OF Pr1646v2Lan3FGInPEntry
   MAX-ACCESS  not-accessible
   STATUS      current
   DESCRIPTION
      "h2IfInPerformance"
   ::= {pr1646v2Lan3FGInP 1}

pr1646v2Lan3FGInPEntry OBJECT-TYPE
   SYNTAX      Pr1646v2Lan3FGInPEntry
   MAX-ACCESS  not-accessible
   STATUS      current
   DESCRIPTION
      ""
   INDEX      { pr1646v2Lan3FGInPTableIx }
   ::= {pr1646v2Lan3FGInPSSCTable 1}

Pr1646v2Lan3FGInPEntry ::=
   SEQUENCE
      {
      pr1646v2Lan3FGInPTableIx
         TableIndex,
      pr1646v2Lan3FGInPSysUpTime
         TimeTicks,
      pr1646v2Lan3FGInPIfUpTime
         TimeTicks,
      pr1646v2Lan3FGInPIfStatChanges
         Counter32,
      pr1646v2Lan3FGInPIfInOctets
         Counter64,
      pr1646v2Lan3FGInPIfInUCPkts
         Counter64,
      pr1646v2Lan3FGInPIfInNUCPkts
         Counter64,
      pr1646v2Lan3FGInPIfInBCPkts
         Counter64,
      pr1646v2Lan3FGInPIfInMCPkts
         Counter64,
      pr1646v2Lan3FGInPIfInDiscards
         Counter64,
      pr1646v2Lan3FGInPIfInErrors
         Counter64,
      pr1646v2Lan3FGInPIfInUnkwn
         Counter64,
      pr1646v2Lan3FGInPInDropEx
         Counter64,
      pr1646v2Lan3FGInPInDropNoMac
         Counter64,
      pr1646v2Lan3FGInPInDropNUCast
         Counter64,
      pr1646v2Lan3FGInPInDropFilter
         Counter64,
      pr1646v2Lan3FGInPIfInBandwidth
         Integer32,
      pr1646v2Lan3FGInPIfOutOctets
         Counter64,
      pr1646v2Lan3FGInPIfOutUCPkts
         Counter64,
      pr1646v2Lan3FGInPIfOutNUCPkts
         Counter64,
      pr1646v2Lan3FGInPIfOutBCPkts
         Counter64,
      pr1646v2Lan3FGInPIfOutMCPkts
         Counter64,
      pr1646v2Lan3FGInPIfOutDiscards
         Counter64,
      pr1646v2Lan3FGInPIfOutErrors
         Counter64,
      pr1646v2Lan3FGInPOutDropEx
         Counter64,
      pr1646v2Lan3FGInPOutDropNoArp
         Counter64,
      pr1646v2Lan3FGInPOutDropFilter
         Counter64,
      pr1646v2Lan3FGInPIfOutBandwidth
         Integer32,
      pr1646v2Lan3FGInPIfErrSec
         Counter32
      }

pr1646v2Lan3FGInPTableIx OBJECT-TYPE
   SYNTAX      TableIndex
   MAX-ACCESS  not-accessible
   STATUS      current
   DESCRIPTION
      ""
   ::= {pr1646v2Lan3FGInPEntry 11}

pr1646v2Lan3FGInPSysUpTime OBJECT-TYPE
   SYNTAX      TimeTicks
   MAX-ACCESS  read-only
   STATUS      current
   DESCRIPTION
      "Path: ethernet3.performance.h2Performance.sysUpTime

       Time in centi-second."
   ::= {pr1646v2Lan3FGInPEntry 16777216}

pr1646v2Lan3FGInPIfUpTime OBJECT-TYPE
   SYNTAX      TimeTicks
   MAX-ACCESS  read-only
   STATUS      current
   DESCRIPTION
      "Path: ethernet3.performance.h2Performance.ifUpTime

       Time in centi-second."
   ::= {pr1646v2Lan3FGInPEntry 33554432}

pr1646v2Lan3FGInPIfStatChanges OBJECT-TYPE
   SYNTAX      Counter32
   MAX-ACCESS  read-only
   STATUS      current
   DESCRIPTION
      "Path: ethernet3.performance.h2Performance.ifStatusChanges

       32 bit unsigned wrappable counter."
   ::= {pr1646v2Lan3FGInPEntry 50331648}

pr1646v2Lan3FGInPIfInOctets OBJECT-TYPE
   SYNTAX      Counter64
   MAX-ACCESS  read-only
   STATUS      current
   DESCRIPTION
      "Path: ethernet3.performance.h2Performance.ifInOctets

       64 bit unsigned wrappable counter."
   ::= {pr1646v2Lan3FGInPEntry 67108864}

pr1646v2Lan3FGInPIfInUCPkts OBJECT-TYPE
   SYNTAX      Counter64
   MAX-ACCESS  read-only
   STATUS      current
   DESCRIPTION
      "Path: ethernet3.performance.h2Performance.ifInUcastPkts

       64 bit unsigned wrappable counter."
   ::= {pr1646v2Lan3FGInPEntry 83886080}

pr1646v2Lan3FGInPIfInNUCPkts OBJECT-TYPE
   SYNTAX      Counter64
   MAX-ACCESS  read-only
   STATUS      current
   DESCRIPTION
      "Path: ethernet3.performance.h2Performance.ifInNUcastPkts

       64 bit unsigned wrappable counter."
   ::= {pr1646v2Lan3FGInPEntry 100663296}

pr1646v2Lan3FGInPIfInBCPkts OBJECT-TYPE
   SYNTAX      Counter64
   MAX-ACCESS  read-only
   STATUS      current
   DESCRIPTION
      "Path: ethernet3.performance.h2Performance.ifInBcastPkts

       64 bit unsigned wrappable counter."
   ::= {pr1646v2Lan3FGInPEntry 419430400}

pr1646v2Lan3FGInPIfInMCPkts OBJECT-TYPE
   SYNTAX      Counter64
   MAX-ACCESS  read-only
   STATUS      current
   DESCRIPTION
      "Path: ethernet3.performance.h2Performance.ifInMcastPkts

       64 bit unsigned wrappable counter."
   ::= {pr1646v2Lan3FGInPEntry 436207616}

pr1646v2Lan3FGInPIfInDiscards OBJECT-TYPE
   SYNTAX      Counter64
   MAX-ACCESS  read-only
   STATUS      current
   DESCRIPTION
      "Path: ethernet3.performance.h2Performance.ifInDiscards

       64 bit unsigned wrappable counter."
   ::= {pr1646v2Lan3FGInPEntry 117440512}

pr1646v2Lan3FGInPIfInErrors OBJECT-TYPE
   SYNTAX      Counter64
   MAX-ACCESS  read-only
   STATUS      current
   DESCRIPTION
      "Path: ethernet3.performance.h2Performance.ifInErrors

       64 bit unsigned wrappable counter."
   ::= {pr1646v2Lan3FGInPEntry 134217728}

pr1646v2Lan3FGInPIfInUnkwn OBJECT-TYPE
   SYNTAX      Counter64
   MAX-ACCESS  read-only
   STATUS      current
   DESCRIPTION
      "Path: ethernet3.performance.h2Performance.ifInUnknownProtos

       64 bit unsigned wrappable counter."
   ::= {pr1646v2Lan3FGInPEntry 150994944}

pr1646v2Lan3FGInPInDropEx OBJECT-TYPE
   SYNTAX      Counter64
   MAX-ACCESS  read-only
   STATUS      current
   DESCRIPTION
      "Path: ethernet3.performance.h2Performance.ifInDropLevelExceeded

       64 bit unsigned wrappable counter."
   ::= {pr1646v2Lan3FGInPEntry 335544320}

pr1646v2Lan3FGInPInDropNoMac OBJECT-TYPE
   SYNTAX      Counter64
   MAX-ACCESS  read-only
   STATUS      current
   DESCRIPTION
      "Path: ethernet3.performance.h2Performance.fInDiscardsNoMacFit

       64 bit unsigned wrappable counter."
   ::= {pr1646v2Lan3FGInPEntry 301989888}

pr1646v2Lan3FGInPInDropNUCast OBJECT-TYPE
   SYNTAX      Counter64
   MAX-ACCESS  read-only
   STATUS      current
   DESCRIPTION
      "Path: ethernet3.performance.h2Performance.fInDiscardsNUCast

       64 bit unsigned wrappable counter."
   ::= {pr1646v2Lan3FGInPEntry 318767104}

pr1646v2Lan3FGInPInDropFilter OBJECT-TYPE
   SYNTAX      Counter64
   MAX-ACCESS  read-only
   STATUS      current
   DESCRIPTION
      "Path: ethernet3.performance.h2Performance.fInDiscardsFilter

       64 bit unsigned wrappable counter."
   ::= {pr1646v2Lan3FGInPEntry 385875968}

pr1646v2Lan3FGInPIfInBandwidth OBJECT-TYPE
   SYNTAX      Integer32
   MAX-ACCESS  read-only
   STATUS      current
   DESCRIPTION
      "Path: ethernet3.performance.h2Performance.ifInBandwidth

       unit name = bps
       formula = 8 * ; 8 /"
   ::= {pr1646v2Lan3FGInPEntry 268435456}

pr1646v2Lan3FGInPIfOutOctets OBJECT-TYPE
   SYNTAX      Counter64
   MAX-ACCESS  read-only
   STATUS      current
   DESCRIPTION
      "Path: ethernet3.performance.h2Performance.ifOutOctets

       64 bit unsigned wrappable counter."
   ::= {pr1646v2Lan3FGInPEntry 167772160}

pr1646v2Lan3FGInPIfOutUCPkts OBJECT-TYPE
   SYNTAX      Counter64
   MAX-ACCESS  read-only
   STATUS      current
   DESCRIPTION
      "Path: ethernet3.performance.h2Performance.ifOutUcastPkts

       64 bit unsigned wrappable counter."
   ::= {pr1646v2Lan3FGInPEntry 184549376}

pr1646v2Lan3FGInPIfOutNUCPkts OBJECT-TYPE
   SYNTAX      Counter64
   MAX-ACCESS  read-only
   STATUS      current
   DESCRIPTION
      "Path: ethernet3.performance.h2Performance.ifOutNUcastPkts

       64 bit unsigned wrappable counter."
   ::= {pr1646v2Lan3FGInPEntry 201326592}

pr1646v2Lan3FGInPIfOutBCPkts OBJECT-TYPE
   SYNTAX      Counter64
   MAX-ACCESS  read-only
   STATUS      current
   DESCRIPTION
      "Path: ethernet3.performance.h2Performance.ifOutBcastPkts

       64 bit unsigned wrappable counter."
   ::= {pr1646v2Lan3FGInPEntry 452984832}

pr1646v2Lan3FGInPIfOutMCPkts OBJECT-TYPE
   SYNTAX      Counter64
   MAX-ACCESS  read-only
   STATUS      current
   DESCRIPTION
      "Path: ethernet3.performance.h2Performance.ifOutMcastPkts

       64 bit unsigned wrappable counter."
   ::= {pr1646v2Lan3FGInPEntry 469762048}

pr1646v2Lan3FGInPIfOutDiscards OBJECT-TYPE
   SYNTAX      Counter64
   MAX-ACCESS  read-only
   STATUS      current
   DESCRIPTION
      "Path: ethernet3.performance.h2Performance.ifOutDiscards

       64 bit unsigned wrappable counter."
   ::= {pr1646v2Lan3FGInPEntry 218103808}

pr1646v2Lan3FGInPIfOutErrors OBJECT-TYPE
   SYNTAX      Counter64
   MAX-ACCESS  read-only
   STATUS      current
   DESCRIPTION
      "Path: ethernet3.performance.h2Performance.ifOutErrors

       64 bit unsigned wrappable counter."
   ::= {pr1646v2Lan3FGInPEntry 234881024}

pr1646v2Lan3FGInPOutDropEx OBJECT-TYPE
   SYNTAX      Counter64
   MAX-ACCESS  read-only
   STATUS      current
   DESCRIPTION
      "Path: ethernet3.performance.h2Performance.ifOutDropLevelExceeded

       64 bit unsigned wrappable counter."
   ::= {pr1646v2Lan3FGInPEntry 352321536}

pr1646v2Lan3FGInPOutDropNoArp OBJECT-TYPE
   SYNTAX      Counter64
   MAX-ACCESS  read-only
   STATUS      current
   DESCRIPTION
      "Path: ethernet3.performance.h2Performance.ifOutDiscardsNoArp

       64 bit unsigned wrappable counter."
   ::= {pr1646v2Lan3FGInPEntry 369098752}

pr1646v2Lan3FGInPOutDropFilter OBJECT-TYPE
   SYNTAX      Counter64
   MAX-ACCESS  read-only
   STATUS      current
   DESCRIPTION
      "Path: ethernet3.performance.h2Performance.ifOutDiscardsFilter

       64 bit unsigned wrappable counter."
   ::= {pr1646v2Lan3FGInPEntry 402653184}

pr1646v2Lan3FGInPIfOutBandwidth OBJECT-TYPE
   SYNTAX      Integer32
   MAX-ACCESS  read-only
   STATUS      current
   DESCRIPTION
      "Path: ethernet3.performance.h2Performance.ifOutBandwidth

       unit name = bps
       formula = 8 * ; 8 /"
   ::= {pr1646v2Lan3FGInPEntry 285212672}

pr1646v2Lan3FGInPIfErrSec OBJECT-TYPE
   SYNTAX      Counter32
   MAX-ACCESS  read-only
   STATUS      current
   DESCRIPTION
      "Path: ethernet3.performance.h2Performance.ifErrSec

       32 bit unsigned wrappable counter."
   ::= {pr1646v2Lan3FGInPEntry 251658240}


pr1646v2Lan3FGH24InP OBJECT IDENTIFIER ::= {pr1646v2Lan3FG 308}

pr1646v2Lan3FGH24InPSSCTable OBJECT-TYPE
   SYNTAX      SEQUENCE OF Pr1646v2Lan3FGH24InPEntry
   MAX-ACCESS  not-accessible
   STATUS      current
   DESCRIPTION
      "h24IfInPerformance"
   ::= {pr1646v2Lan3FGH24InP 1}

pr1646v2Lan3FGH24InPEntry OBJECT-TYPE
   SYNTAX      Pr1646v2Lan3FGH24InPEntry
   MAX-ACCESS  not-accessible
   STATUS      current
   DESCRIPTION
      ""
   INDEX      { pr1646v2Lan3FGH24InPTableIx }
   ::= {pr1646v2Lan3FGH24InPSSCTable 1}

Pr1646v2Lan3FGH24InPEntry ::=
   SEQUENCE
      {
      pr1646v2Lan3FGH24InPTableIx
         TableIndex,
      pr1646v2Lan3FGH24InPSysUpTime
         TimeTicks,
      pr1646v2Lan3FGH24InPIfUpTime
         TimeTicks,
      pr1646v2Lan3FGH24InPIfStatChanges
         Counter32,
      pr1646v2Lan3FGH24InPIfInOctets
         Counter64,
      pr1646v2Lan3FGH24InPIfInUCPkts
         Counter64,
      pr1646v2Lan3FGH24InPIfInNUCPkts
         Counter64,
      pr1646v2Lan3FGH24InPIfInBCPkts
         Counter64,
      pr1646v2Lan3FGH24InPIfInMCPkts
         Counter64,
      pr1646v2Lan3FGH24InPIfInDiscards
         Counter64,
      pr1646v2Lan3FGH24InPIfInErrors
         Counter64,
      pr1646v2Lan3FGH24InPIfInUnkwn
         Counter64,
      pr1646v2Lan3FGH24InPInDropEx
         Counter64,
      pr1646v2Lan3FGH24InPInDropNoMac
         Counter64,
      pr1646v2Lan3FGH24InPInDropNUCast
         Counter64,
      pr1646v2Lan3FGH24InPInDropFilter
         Counter64,
      pr1646v2Lan3FGH24InPIfInBandwidth
         Integer32,
      pr1646v2Lan3FGH24InPIfOutOctets
         Counter64,
      pr1646v2Lan3FGH24InPIfOutUCPkts
         Counter64,
      pr1646v2Lan3FGH24InPIfOutNUCPkts
         Counter64,
      pr1646v2Lan3FGH24InPIfOutBCPkts
         Counter64,
      pr1646v2Lan3FGH24InPIfOutMCPkts
         Counter64,
      pr1646v2Lan3FGH24InPIfOutDiscards
         Counter64,
      pr1646v2Lan3FGH24InPIfOutErrors
         Counter64,
      pr1646v2Lan3FGH24InPOutDropEx
         Counter64,
      pr1646v2Lan3FGH24InPOutDropNoArp
         Counter64,
      pr1646v2Lan3FGH24InPOutDropFilter
         Counter64,
      pr1646v2Lan3FGH24InPIfOutBandwidth
         Integer32,
      pr1646v2Lan3FGH24InPIfErrSec
         Counter32
      }

pr1646v2Lan3FGH24InPTableIx OBJECT-TYPE
   SYNTAX      TableIndex
   MAX-ACCESS  not-accessible
   STATUS      current
   DESCRIPTION
      ""
   ::= {pr1646v2Lan3FGH24InPEntry 11}

pr1646v2Lan3FGH24InPSysUpTime OBJECT-TYPE
   SYNTAX      TimeTicks
   MAX-ACCESS  read-only
   STATUS      current
   DESCRIPTION
      "Path: ethernet3.performance.h24Performance.sysUpTime

       Time in centi-second."
   ::= {pr1646v2Lan3FGH24InPEntry 16777216}

pr1646v2Lan3FGH24InPIfUpTime OBJECT-TYPE
   SYNTAX      TimeTicks
   MAX-ACCESS  read-only
   STATUS      current
   DESCRIPTION
      "Path: ethernet3.performance.h24Performance.ifUpTime

       Time in centi-second."
   ::= {pr1646v2Lan3FGH24InPEntry 33554432}

pr1646v2Lan3FGH24InPIfStatChanges OBJECT-TYPE
   SYNTAX      Counter32
   MAX-ACCESS  read-only
   STATUS      current
   DESCRIPTION
      "Path: ethernet3.performance.h24Performance.ifStatusChanges

       32 bit unsigned wrappable counter."
   ::= {pr1646v2Lan3FGH24InPEntry 50331648}

pr1646v2Lan3FGH24InPIfInOctets OBJECT-TYPE
   SYNTAX      Counter64
   MAX-ACCESS  read-only
   STATUS      current
   DESCRIPTION
      "Path: ethernet3.performance.h24Performance.ifInOctets

       64 bit unsigned wrappable counter."
   ::= {pr1646v2Lan3FGH24InPEntry 67108864}

pr1646v2Lan3FGH24InPIfInUCPkts OBJECT-TYPE
   SYNTAX      Counter64
   MAX-ACCESS  read-only
   STATUS      current
   DESCRIPTION
      "Path: ethernet3.performance.h24Performance.ifInUcastPkts

       64 bit unsigned wrappable counter."
   ::= {pr1646v2Lan3FGH24InPEntry 83886080}

pr1646v2Lan3FGH24InPIfInNUCPkts OBJECT-TYPE
   SYNTAX      Counter64
   MAX-ACCESS  read-only
   STATUS      current
   DESCRIPTION
      "Path: ethernet3.performance.h24Performance.ifInNUcastPkts

       64 bit unsigned wrappable counter."
   ::= {pr1646v2Lan3FGH24InPEntry 100663296}

pr1646v2Lan3FGH24InPIfInBCPkts OBJECT-TYPE
   SYNTAX      Counter64
   MAX-ACCESS  read-only
   STATUS      current
   DESCRIPTION
      "Path: ethernet3.performance.h24Performance.ifInBcastPkts

       64 bit unsigned wrappable counter."
   ::= {pr1646v2Lan3FGH24InPEntry 419430400}

pr1646v2Lan3FGH24InPIfInMCPkts OBJECT-TYPE
   SYNTAX      Counter64
   MAX-ACCESS  read-only
   STATUS      current
   DESCRIPTION
      "Path: ethernet3.performance.h24Performance.ifInMcastPkts

       64 bit unsigned wrappable counter."
   ::= {pr1646v2Lan3FGH24InPEntry 436207616}

pr1646v2Lan3FGH24InPIfInDiscards OBJECT-TYPE
   SYNTAX      Counter64
   MAX-ACCESS  read-only
   STATUS      current
   DESCRIPTION
      "Path: ethernet3.performance.h24Performance.ifInDiscards

       64 bit unsigned wrappable counter."
   ::= {pr1646v2Lan3FGH24InPEntry 117440512}

pr1646v2Lan3FGH24InPIfInErrors OBJECT-TYPE
   SYNTAX      Counter64
   MAX-ACCESS  read-only
   STATUS      current
   DESCRIPTION
      "Path: ethernet3.performance.h24Performance.ifInErrors

       64 bit unsigned wrappable counter."
   ::= {pr1646v2Lan3FGH24InPEntry 134217728}

pr1646v2Lan3FGH24InPIfInUnkwn OBJECT-TYPE
   SYNTAX      Counter64
   MAX-ACCESS  read-only
   STATUS      current
   DESCRIPTION
      "Path: ethernet3.performance.h24Performance.ifInUnknownProtos

       64 bit unsigned wrappable counter."
   ::= {pr1646v2Lan3FGH24InPEntry 150994944}

pr1646v2Lan3FGH24InPInDropEx OBJECT-TYPE
   SYNTAX      Counter64
   MAX-ACCESS  read-only
   STATUS      current
   DESCRIPTION
      "Path: ethernet3.performance.h24Performance.ifInDropLevelExceeded

       64 bit unsigned wrappable counter."
   ::= {pr1646v2Lan3FGH24InPEntry 335544320}

pr1646v2Lan3FGH24InPInDropNoMac OBJECT-TYPE
   SYNTAX      Counter64
   MAX-ACCESS  read-only
   STATUS      current
   DESCRIPTION
      "Path: ethernet3.performance.h24Performance.fInDiscardsNoMacFit

       64 bit unsigned wrappable counter."
   ::= {pr1646v2Lan3FGH24InPEntry 301989888}

pr1646v2Lan3FGH24InPInDropNUCast OBJECT-TYPE
   SYNTAX      Counter64
   MAX-ACCESS  read-only
   STATUS      current
   DESCRIPTION
      "Path: ethernet3.performance.h24Performance.fInDiscardsNUCast

       64 bit unsigned wrappable counter."
   ::= {pr1646v2Lan3FGH24InPEntry 318767104}

pr1646v2Lan3FGH24InPInDropFilter OBJECT-TYPE
   SYNTAX      Counter64
   MAX-ACCESS  read-only
   STATUS      current
   DESCRIPTION
      "Path: ethernet3.performance.h24Performance.fInDiscardsFilter

       64 bit unsigned wrappable counter."
   ::= {pr1646v2Lan3FGH24InPEntry 385875968}

pr1646v2Lan3FGH24InPIfInBandwidth OBJECT-TYPE
   SYNTAX      Integer32
   MAX-ACCESS  read-only
   STATUS      current
   DESCRIPTION
      "Path: ethernet3.performance.h24Performance.ifInBandwidth

       unit name = bps
       formula = 8 * ; 8 /"
   ::= {pr1646v2Lan3FGH24InPEntry 268435456}

pr1646v2Lan3FGH24InPIfOutOctets OBJECT-TYPE
   SYNTAX      Counter64
   MAX-ACCESS  read-only
   STATUS      current
   DESCRIPTION
      "Path: ethernet3.performance.h24Performance.ifOutOctets

       64 bit unsigned wrappable counter."
   ::= {pr1646v2Lan3FGH24InPEntry 167772160}

pr1646v2Lan3FGH24InPIfOutUCPkts OBJECT-TYPE
   SYNTAX      Counter64
   MAX-ACCESS  read-only
   STATUS      current
   DESCRIPTION
      "Path: ethernet3.performance.h24Performance.ifOutUcastPkts

       64 bit unsigned wrappable counter."
   ::= {pr1646v2Lan3FGH24InPEntry 184549376}

pr1646v2Lan3FGH24InPIfOutNUCPkts OBJECT-TYPE
   SYNTAX      Counter64
   MAX-ACCESS  read-only
   STATUS      current
   DESCRIPTION
      "Path: ethernet3.performance.h24Performance.ifOutNUcastPkts

       64 bit unsigned wrappable counter."
   ::= {pr1646v2Lan3FGH24InPEntry 201326592}

pr1646v2Lan3FGH24InPIfOutBCPkts OBJECT-TYPE
   SYNTAX      Counter64
   MAX-ACCESS  read-only
   STATUS      current
   DESCRIPTION
      "Path: ethernet3.performance.h24Performance.ifOutBcastPkts

       64 bit unsigned wrappable counter."
   ::= {pr1646v2Lan3FGH24InPEntry 452984832}

pr1646v2Lan3FGH24InPIfOutMCPkts OBJECT-TYPE
   SYNTAX      Counter64
   MAX-ACCESS  read-only
   STATUS      current
   DESCRIPTION
      "Path: ethernet3.performance.h24Performance.ifOutMcastPkts

       64 bit unsigned wrappable counter."
   ::= {pr1646v2Lan3FGH24InPEntry 469762048}

pr1646v2Lan3FGH24InPIfOutDiscards OBJECT-TYPE
   SYNTAX      Counter64
   MAX-ACCESS  read-only
   STATUS      current
   DESCRIPTION
      "Path: ethernet3.performance.h24Performance.ifOutDiscards

       64 bit unsigned wrappable counter."
   ::= {pr1646v2Lan3FGH24InPEntry 218103808}

pr1646v2Lan3FGH24InPIfOutErrors OBJECT-TYPE
   SYNTAX      Counter64
   MAX-ACCESS  read-only
   STATUS      current
   DESCRIPTION
      "Path: ethernet3.performance.h24Performance.ifOutErrors

       64 bit unsigned wrappable counter."
   ::= {pr1646v2Lan3FGH24InPEntry 234881024}

pr1646v2Lan3FGH24InPOutDropEx OBJECT-TYPE
   SYNTAX      Counter64
   MAX-ACCESS  read-only
   STATUS      current
   DESCRIPTION
      "Path: ethernet3.performance.h24Performance.ifOutDropLevelExceeded

       64 bit unsigned wrappable counter."
   ::= {pr1646v2Lan3FGH24InPEntry 352321536}

pr1646v2Lan3FGH24InPOutDropNoArp OBJECT-TYPE
   SYNTAX      Counter64
   MAX-ACCESS  read-only
   STATUS      current
   DESCRIPTION
      "Path: ethernet3.performance.h24Performance.ifOutDiscardsNoArp

       64 bit unsigned wrappable counter."
   ::= {pr1646v2Lan3FGH24InPEntry 369098752}

pr1646v2Lan3FGH24InPOutDropFilter OBJECT-TYPE
   SYNTAX      Counter64
   MAX-ACCESS  read-only
   STATUS      current
   DESCRIPTION
      "Path: ethernet3.performance.h24Performance.ifOutDiscardsFilter

       64 bit unsigned wrappable counter."
   ::= {pr1646v2Lan3FGH24InPEntry 402653184}

pr1646v2Lan3FGH24InPIfOutBandwidth OBJECT-TYPE
   SYNTAX      Integer32
   MAX-ACCESS  read-only
   STATUS      current
   DESCRIPTION
      "Path: ethernet3.performance.h24Performance.ifOutBandwidth

       unit name = bps
       formula = 8 * ; 8 /"
   ::= {pr1646v2Lan3FGH24InPEntry 285212672}

pr1646v2Lan3FGH24InPIfErrSec OBJECT-TYPE
   SYNTAX      Counter32
   MAX-ACCESS  read-only
   STATUS      current
   DESCRIPTION
      "Path: ethernet3.performance.h24Performance.ifErrSec

       32 bit unsigned wrappable counter."
   ::= {pr1646v2Lan3FGH24InPEntry 251658240}


pr1646v2Lan3FGD7InP OBJECT IDENTIFIER ::= {pr1646v2Lan3FG 309}

pr1646v2Lan3FGD7InPSSCTable OBJECT-TYPE
   SYNTAX      SEQUENCE OF Pr1646v2Lan3FGD7InPEntry
   MAX-ACCESS  not-accessible
   STATUS      current
   DESCRIPTION
      "d7IfInPerformance"
   ::= {pr1646v2Lan3FGD7InP 1}

pr1646v2Lan3FGD7InPEntry OBJECT-TYPE
   SYNTAX      Pr1646v2Lan3FGD7InPEntry
   MAX-ACCESS  not-accessible
   STATUS      current
   DESCRIPTION
      ""
   INDEX      { pr1646v2Lan3FGD7InPTableIx }
   ::= {pr1646v2Lan3FGD7InPSSCTable 1}

Pr1646v2Lan3FGD7InPEntry ::=
   SEQUENCE
      {
      pr1646v2Lan3FGD7InPTableIx
         TableIndex,
      pr1646v2Lan3FGD7InPSysUpTime
         TimeTicks,
      pr1646v2Lan3FGD7InPIfUpTime
         TimeTicks,
      pr1646v2Lan3FGD7InPIfStatChanges
         Counter32,
      pr1646v2Lan3FGD7InPIfInOctets
         Counter64,
      pr1646v2Lan3FGD7InPIfInUCPkts
         Counter64,
      pr1646v2Lan3FGD7InPIfInNUCPkts
         Counter64,
      pr1646v2Lan3FGD7InPIfInBCPkts
         Counter64,
      pr1646v2Lan3FGD7InPIfInMCPkts
         Counter64,
      pr1646v2Lan3FGD7InPIfInDiscards
         Counter64,
      pr1646v2Lan3FGD7InPIfInErrors
         Counter64,
      pr1646v2Lan3FGD7InPIfInUnkwn
         Counter64,
      pr1646v2Lan3FGD7InPInDropEx
         Counter64,
      pr1646v2Lan3FGD7InPInDropNoMac
         Counter64,
      pr1646v2Lan3FGD7InPInDropNUCast
         Counter64,
      pr1646v2Lan3FGD7InPInDropFilter
         Counter64,
      pr1646v2Lan3FGD7InPIfInBandwidth
         Integer32,
      pr1646v2Lan3FGD7InPIfOutOctets
         Counter64,
      pr1646v2Lan3FGD7InPIfOutUCPkts
         Counter64,
      pr1646v2Lan3FGD7InPIfOutNUCPkts
         Counter64,
      pr1646v2Lan3FGD7InPIfOutBCPkts
         Counter64,
      pr1646v2Lan3FGD7InPIfOutMCPkts
         Counter64,
      pr1646v2Lan3FGD7InPIfOutDiscards
         Counter64,
      pr1646v2Lan3FGD7InPIfOutErrors
         Counter64,
      pr1646v2Lan3FGD7InPOutDropEx
         Counter64,
      pr1646v2Lan3FGD7InPOutDropNoArp
         Counter64,
      pr1646v2Lan3FGD7InPOutDropFilter
         Counter64,
      pr1646v2Lan3FGD7InPIfOutBandwidth
         Integer32,
      pr1646v2Lan3FGD7InPIfErrSec
         Counter32
      }

pr1646v2Lan3FGD7InPTableIx OBJECT-TYPE
   SYNTAX      TableIndex
   MAX-ACCESS  not-accessible
   STATUS      current
   DESCRIPTION
      ""
   ::= {pr1646v2Lan3FGD7InPEntry 11}

pr1646v2Lan3FGD7InPSysUpTime OBJECT-TYPE
   SYNTAX      TimeTicks
   MAX-ACCESS  read-only
   STATUS      current
   DESCRIPTION
      "Path: ethernet3.performance.d7Performance.sysUpTime

       Time in centi-second."
   ::= {pr1646v2Lan3FGD7InPEntry 16777216}

pr1646v2Lan3FGD7InPIfUpTime OBJECT-TYPE
   SYNTAX      TimeTicks
   MAX-ACCESS  read-only
   STATUS      current
   DESCRIPTION
      "Path: ethernet3.performance.d7Performance.ifUpTime

       Time in centi-second."
   ::= {pr1646v2Lan3FGD7InPEntry 33554432}

pr1646v2Lan3FGD7InPIfStatChanges OBJECT-TYPE
   SYNTAX      Counter32
   MAX-ACCESS  read-only
   STATUS      current
   DESCRIPTION
      "Path: ethernet3.performance.d7Performance.ifStatusChanges

       32 bit unsigned wrappable counter."
   ::= {pr1646v2Lan3FGD7InPEntry 50331648}

pr1646v2Lan3FGD7InPIfInOctets OBJECT-TYPE
   SYNTAX      Counter64
   MAX-ACCESS  read-only
   STATUS      current
   DESCRIPTION
      "Path: ethernet3.performance.d7Performance.ifInOctets

       64 bit unsigned wrappable counter."
   ::= {pr1646v2Lan3FGD7InPEntry 67108864}

pr1646v2Lan3FGD7InPIfInUCPkts OBJECT-TYPE
   SYNTAX      Counter64
   MAX-ACCESS  read-only
   STATUS      current
   DESCRIPTION
      "Path: ethernet3.performance.d7Performance.ifInUcastPkts

       64 bit unsigned wrappable counter."
   ::= {pr1646v2Lan3FGD7InPEntry 83886080}

pr1646v2Lan3FGD7InPIfInNUCPkts OBJECT-TYPE
   SYNTAX      Counter64
   MAX-ACCESS  read-only
   STATUS      current
   DESCRIPTION
      "Path: ethernet3.performance.d7Performance.ifInNUcastPkts

       64 bit unsigned wrappable counter."
   ::= {pr1646v2Lan3FGD7InPEntry 100663296}

pr1646v2Lan3FGD7InPIfInBCPkts OBJECT-TYPE
   SYNTAX      Counter64
   MAX-ACCESS  read-only
   STATUS      current
   DESCRIPTION
      "Path: ethernet3.performance.d7Performance.ifInBcastPkts

       64 bit unsigned wrappable counter."
   ::= {pr1646v2Lan3FGD7InPEntry 419430400}

pr1646v2Lan3FGD7InPIfInMCPkts OBJECT-TYPE
   SYNTAX      Counter64
   MAX-ACCESS  read-only
   STATUS      current
   DESCRIPTION
      "Path: ethernet3.performance.d7Performance.ifInMcastPkts

       64 bit unsigned wrappable counter."
   ::= {pr1646v2Lan3FGD7InPEntry 436207616}

pr1646v2Lan3FGD7InPIfInDiscards OBJECT-TYPE
   SYNTAX      Counter64
   MAX-ACCESS  read-only
   STATUS      current
   DESCRIPTION
      "Path: ethernet3.performance.d7Performance.ifInDiscards

       64 bit unsigned wrappable counter."
   ::= {pr1646v2Lan3FGD7InPEntry 117440512}

pr1646v2Lan3FGD7InPIfInErrors OBJECT-TYPE
   SYNTAX      Counter64
   MAX-ACCESS  read-only
   STATUS      current
   DESCRIPTION
      "Path: ethernet3.performance.d7Performance.ifInErrors

       64 bit unsigned wrappable counter."
   ::= {pr1646v2Lan3FGD7InPEntry 134217728}

pr1646v2Lan3FGD7InPIfInUnkwn OBJECT-TYPE
   SYNTAX      Counter64
   MAX-ACCESS  read-only
   STATUS      current
   DESCRIPTION
      "Path: ethernet3.performance.d7Performance.ifInUnknownProtos

       64 bit unsigned wrappable counter."
   ::= {pr1646v2Lan3FGD7InPEntry 150994944}

pr1646v2Lan3FGD7InPInDropEx OBJECT-TYPE
   SYNTAX      Counter64
   MAX-ACCESS  read-only
   STATUS      current
   DESCRIPTION
      "Path: ethernet3.performance.d7Performance.ifInDropLevelExceeded

       64 bit unsigned wrappable counter."
   ::= {pr1646v2Lan3FGD7InPEntry 335544320}

pr1646v2Lan3FGD7InPInDropNoMac OBJECT-TYPE
   SYNTAX      Counter64
   MAX-ACCESS  read-only
   STATUS      current
   DESCRIPTION
      "Path: ethernet3.performance.d7Performance.fInDiscardsNoMacFit

       64 bit unsigned wrappable counter."
   ::= {pr1646v2Lan3FGD7InPEntry 301989888}

pr1646v2Lan3FGD7InPInDropNUCast OBJECT-TYPE
   SYNTAX      Counter64
   MAX-ACCESS  read-only
   STATUS      current
   DESCRIPTION
      "Path: ethernet3.performance.d7Performance.fInDiscardsNUCast

       64 bit unsigned wrappable counter."
   ::= {pr1646v2Lan3FGD7InPEntry 318767104}

pr1646v2Lan3FGD7InPInDropFilter OBJECT-TYPE
   SYNTAX      Counter64
   MAX-ACCESS  read-only
   STATUS      current
   DESCRIPTION
      "Path: ethernet3.performance.d7Performance.fInDiscardsFilter

       64 bit unsigned wrappable counter."
   ::= {pr1646v2Lan3FGD7InPEntry 385875968}

pr1646v2Lan3FGD7InPIfInBandwidth OBJECT-TYPE
   SYNTAX      Integer32
   MAX-ACCESS  read-only
   STATUS      current
   DESCRIPTION
      "Path: ethernet3.performance.d7Performance.ifInBandwidth

       unit name = bps
       formula = 8 * ; 8 /"
   ::= {pr1646v2Lan3FGD7InPEntry 268435456}

pr1646v2Lan3FGD7InPIfOutOctets OBJECT-TYPE
   SYNTAX      Counter64
   MAX-ACCESS  read-only
   STATUS      current
   DESCRIPTION
      "Path: ethernet3.performance.d7Performance.ifOutOctets

       64 bit unsigned wrappable counter."
   ::= {pr1646v2Lan3FGD7InPEntry 167772160}

pr1646v2Lan3FGD7InPIfOutUCPkts OBJECT-TYPE
   SYNTAX      Counter64
   MAX-ACCESS  read-only
   STATUS      current
   DESCRIPTION
      "Path: ethernet3.performance.d7Performance.ifOutUcastPkts

       64 bit unsigned wrappable counter."
   ::= {pr1646v2Lan3FGD7InPEntry 184549376}

pr1646v2Lan3FGD7InPIfOutNUCPkts OBJECT-TYPE
   SYNTAX      Counter64
   MAX-ACCESS  read-only
   STATUS      current
   DESCRIPTION
      "Path: ethernet3.performance.d7Performance.ifOutNUcastPkts

       64 bit unsigned wrappable counter."
   ::= {pr1646v2Lan3FGD7InPEntry 201326592}

pr1646v2Lan3FGD7InPIfOutBCPkts OBJECT-TYPE
   SYNTAX      Counter64
   MAX-ACCESS  read-only
   STATUS      current
   DESCRIPTION
      "Path: ethernet3.performance.d7Performance.ifOutBcastPkts

       64 bit unsigned wrappable counter."
   ::= {pr1646v2Lan3FGD7InPEntry 452984832}

pr1646v2Lan3FGD7InPIfOutMCPkts OBJECT-TYPE
   SYNTAX      Counter64
   MAX-ACCESS  read-only
   STATUS      current
   DESCRIPTION
      "Path: ethernet3.performance.d7Performance.ifOutMcastPkts

       64 bit unsigned wrappable counter."
   ::= {pr1646v2Lan3FGD7InPEntry 469762048}

pr1646v2Lan3FGD7InPIfOutDiscards OBJECT-TYPE
   SYNTAX      Counter64
   MAX-ACCESS  read-only
   STATUS      current
   DESCRIPTION
      "Path: ethernet3.performance.d7Performance.ifOutDiscards

       64 bit unsigned wrappable counter."
   ::= {pr1646v2Lan3FGD7InPEntry 218103808}

pr1646v2Lan3FGD7InPIfOutErrors OBJECT-TYPE
   SYNTAX      Counter64
   MAX-ACCESS  read-only
   STATUS      current
   DESCRIPTION
      "Path: ethernet3.performance.d7Performance.ifOutErrors

       64 bit unsigned wrappable counter."
   ::= {pr1646v2Lan3FGD7InPEntry 234881024}

pr1646v2Lan3FGD7InPOutDropEx OBJECT-TYPE
   SYNTAX      Counter64
   MAX-ACCESS  read-only
   STATUS      current
   DESCRIPTION
      "Path: ethernet3.performance.d7Performance.ifOutDropLevelExceeded

       64 bit unsigned wrappable counter."
   ::= {pr1646v2Lan3FGD7InPEntry 352321536}

pr1646v2Lan3FGD7InPOutDropNoArp OBJECT-TYPE
   SYNTAX      Counter64
   MAX-ACCESS  read-only
   STATUS      current
   DESCRIPTION
      "Path: ethernet3.performance.d7Performance.ifOutDiscardsNoArp

       64 bit unsigned wrappable counter."
   ::= {pr1646v2Lan3FGD7InPEntry 369098752}

pr1646v2Lan3FGD7InPOutDropFilter OBJECT-TYPE
   SYNTAX      Counter64
   MAX-ACCESS  read-only
   STATUS      current
   DESCRIPTION
      "Path: ethernet3.performance.d7Performance.ifOutDiscardsFilter

       64 bit unsigned wrappable counter."
   ::= {pr1646v2Lan3FGD7InPEntry 402653184}

pr1646v2Lan3FGD7InPIfOutBandwidth OBJECT-TYPE
   SYNTAX      Integer32
   MAX-ACCESS  read-only
   STATUS      current
   DESCRIPTION
      "Path: ethernet3.performance.d7Performance.ifOutBandwidth

       unit name = bps
       formula = 8 * ; 8 /"
   ::= {pr1646v2Lan3FGD7InPEntry 285212672}

pr1646v2Lan3FGD7InPIfErrSec OBJECT-TYPE
   SYNTAX      Counter32
   MAX-ACCESS  read-only
   STATUS      current
   DESCRIPTION
      "Path: ethernet3.performance.d7Performance.ifErrSec

       32 bit unsigned wrappable counter."
   ::= {pr1646v2Lan3FGD7InPEntry 251658240}


pr1646v2Lan3FGOam OBJECT IDENTIFIER ::= {pr1646v2Lan3FG 910}

pr1646v2Lan3FGOamSSC OBJECT IDENTIFIER ::= {pr1646v2Lan3FGOam 1}

pr1646v2Lan3FGOamEntry OBJECT IDENTIFIER ::= {pr1646v2Lan3FGOamSSC 1}

pr1646v2Lan3FGOamInformationTx OBJECT-TYPE
   SYNTAX      Counter32
   MAX-ACCESS  read-only
   STATUS      current
   DESCRIPTION
      "Path: ethernet3.performance.oam.informationTx

       32 bit unsigned wrappable counter."
   ::= {pr1646v2Lan3FGOamEntry 16777216}

pr1646v2Lan3FGOamInformationRx OBJECT-TYPE
   SYNTAX      Counter32
   MAX-ACCESS  read-only
   STATUS      current
   DESCRIPTION
      "Path: ethernet3.performance.oam.informationRx

       32 bit unsigned wrappable counter."
   ::= {pr1646v2Lan3FGOamEntry 33554432}

pr1646v2Lan3FGOamUniqueEventNotifTx OBJECT-TYPE
   SYNTAX      Counter32
   MAX-ACCESS  read-only
   STATUS      current
   DESCRIPTION
      "Path: ethernet3.performance.oam.uniqueEventNotifTx

       32 bit unsigned wrappable counter."
   ::= {pr1646v2Lan3FGOamEntry 50331648}

pr1646v2Lan3FGOamUniqueEventNotifRx OBJECT-TYPE
   SYNTAX      Counter32
   MAX-ACCESS  read-only
   STATUS      current
   DESCRIPTION
      "Path: ethernet3.performance.oam.uniqueEventNotifRx

       32 bit unsigned wrappable counter."
   ::= {pr1646v2Lan3FGOamEntry 67108864}

pr1646v2Lan3FGOamLoopbackCtrlTx OBJECT-TYPE
   SYNTAX      Counter32
   MAX-ACCESS  read-only
   STATUS      current
   DESCRIPTION
      "Path: ethernet3.performance.oam.loopbackCtrlTx

       32 bit unsigned wrappable counter."
   ::= {pr1646v2Lan3FGOamEntry 117440512}

pr1646v2Lan3FGOamLoopbackCtrlRx OBJECT-TYPE
   SYNTAX      Counter32
   MAX-ACCESS  read-only
   STATUS      current
   DESCRIPTION
      "Path: ethernet3.performance.oam.loopbackCtrlRx

       32 bit unsigned wrappable counter."
   ::= {pr1646v2Lan3FGOamEntry 134217728}

pr1646v2Lan3FGOamVarReqTx OBJECT-TYPE
   SYNTAX      Counter32
   MAX-ACCESS  read-only
   STATUS      current
   DESCRIPTION
      "Path: ethernet3.performance.oam.varReqTx

       32 bit unsigned wrappable counter."
   ::= {pr1646v2Lan3FGOamEntry 150994944}

pr1646v2Lan3FGOamVarReqRx OBJECT-TYPE
   SYNTAX      Counter32
   MAX-ACCESS  read-only
   STATUS      current
   DESCRIPTION
      "Path: ethernet3.performance.oam.varReqRx

       32 bit unsigned wrappable counter."
   ::= {pr1646v2Lan3FGOamEntry 167772160}

pr1646v2Lan3FGOamVarRespTx OBJECT-TYPE
   SYNTAX      Counter32
   MAX-ACCESS  read-only
   STATUS      current
   DESCRIPTION
      "Path: ethernet3.performance.oam.varRespTx

       32 bit unsigned wrappable counter."
   ::= {pr1646v2Lan3FGOamEntry 184549376}

pr1646v2Lan3FGOamVarRespRx OBJECT-TYPE
   SYNTAX      Counter32
   MAX-ACCESS  read-only
   STATUS      current
   DESCRIPTION
      "Path: ethernet3.performance.oam.varRespRx

       32 bit unsigned wrappable counter."
   ::= {pr1646v2Lan3FGOamEntry 201326592}

pr1646v2Lan3FGOamOrgSpecificTx OBJECT-TYPE
   SYNTAX      Counter32
   MAX-ACCESS  read-only
   STATUS      current
   DESCRIPTION
      "Path: ethernet3.performance.oam.orgSpecificTx

       32 bit unsigned wrappable counter."
   ::= {pr1646v2Lan3FGOamEntry 218103808}

pr1646v2Lan3FGOamOrgSpecificRx OBJECT-TYPE
   SYNTAX      Counter32
   MAX-ACCESS  read-only
   STATUS      current
   DESCRIPTION
      "Path: ethernet3.performance.oam.orgSpecificRx

       32 bit unsigned wrappable counter."
   ::= {pr1646v2Lan3FGOamEntry 234881024}

pr1646v2Lan3FGOamUnsupportedCodesTx OBJECT-TYPE
   SYNTAX      Counter32
   MAX-ACCESS  read-only
   STATUS      current
   DESCRIPTION
      "Path: ethernet3.performance.oam.unsupportedCodesTx

       32 bit unsigned wrappable counter."
   ::= {pr1646v2Lan3FGOamEntry 251658240}

pr1646v2Lan3FGOamUnsupportedCodesRx OBJECT-TYPE
   SYNTAX      Counter32
   MAX-ACCESS  read-only
   STATUS      current
   DESCRIPTION
      "Path: ethernet3.performance.oam.unsupportedCodesRx

       32 bit unsigned wrappable counter."
   ::= {pr1646v2Lan3FGOamEntry 268435456}

pr1646v2Lan3FGOamPduDiscardRx OBJECT-TYPE
   SYNTAX      Counter32
   MAX-ACCESS  read-only
   STATUS      current
   DESCRIPTION
      "Path: ethernet3.performance.oam.pduDiscardRx

       32 bit unsigned wrappable counter."
   ::= {pr1646v2Lan3FGOamEntry 1694498816}

pr1646v2Lan3FGOamDataDiscardTx OBJECT-TYPE
   SYNTAX      Counter32
   MAX-ACCESS  read-only
   STATUS      current
   DESCRIPTION
      "Path: ethernet3.performance.oam.dataDiscardTx

       32 bit unsigned wrappable counter."
   ::= {pr1646v2Lan3FGOamEntry 1711276032}

pr1646v2Lan3FGOamDataDiscardRx OBJECT-TYPE
   SYNTAX      Counter32
   MAX-ACCESS  read-only
   STATUS      current
   DESCRIPTION
      "Path: ethernet3.performance.oam.dataDiscardRx

       32 bit unsigned wrappable counter."
   ::= {pr1646v2Lan3FGOamEntry 1728053248}


pr1646v2Lan3FGVlan OBJECT IDENTIFIER ::= {pr1646v2Lan3FG 310}

pr1646v2Lan3FGVlanSSCTable OBJECT-TYPE
   SYNTAX      SEQUENCE OF Pr1646v2Lan3FGVlanEntry
   MAX-ACCESS  not-accessible
   STATUS      current
   DESCRIPTION
      ""
   ::= {pr1646v2Lan3FGVlan 1}

pr1646v2Lan3FGVlanEntry OBJECT-TYPE
   SYNTAX      Pr1646v2Lan3FGVlanEntry
   MAX-ACCESS  not-accessible
   STATUS      current
   DESCRIPTION
      ""
   INDEX      { pr1646v2Lan3FGVlanTableIx }
   ::= {pr1646v2Lan3FGVlanSSCTable 1}

Pr1646v2Lan3FGVlanEntry ::=
   SEQUENCE
      {
      pr1646v2Lan3FGVlanTableIx
         TableIndex,
      pr1646v2Lan3FGVlanName
         DisplayString,
      pr1646v2Lan3FGVlanMCInOctets
         Counter64,
      pr1646v2Lan3FGVlanMCInUcast
         Counter64,
      pr1646v2Lan3FGVlanMCInNUcastPkts
         Counter64,
      pr1646v2Lan3FGVlanMCInBcastPkts
         Counter64,
      pr1646v2Lan3FGVlanMCInMcastPkts
         Counter64,
      pr1646v2Lan3FGVlanMCInDiscards
         Counter64,
      pr1646v2Lan3FGVlanMCInErrors
         Counter64,
      pr1646v2Lan3FGVlanMCInUnknownProtos
         Counter64,
      pr1646v2Lan3FGVlanMCInDropEx
         Counter64,
      pr1646v2Lan3FGVlanMCInDropNoMac
         Counter64,
      pr1646v2Lan3FGVlanMCInDropNUCast
         Counter64,
      pr1646v2Lan3FGVlanMCInDropFilter
         Counter64,
      pr1646v2Lan3FGVlanMCInBandwidth15sec
         Integer32,
      pr1646v2Lan3FGVlanMCInBandwidth30sec
         Integer32,
      pr1646v2Lan3FGVlanMCInBandwidth1min
         Integer32,
      pr1646v2Lan3FGVlanMCInBandwidth2min
         Integer32,
      pr1646v2Lan3FGVlanMCInBandwidth5min
         Integer32,
      pr1646v2Lan3FGVlanMCOutOctets
         Counter64,
      pr1646v2Lan3FGVlanMCOutUcastPkts
         Counter64,
      pr1646v2Lan3FGVlanMCOutNUcastPkts
         Counter64,
      pr1646v2Lan3FGVlanMCOutBcastPkts
         Counter64,
      pr1646v2Lan3FGVlanMCOutMcastPkts
         Counter64,
      pr1646v2Lan3FGVlanMCOutDiscards
         Counter64,
      pr1646v2Lan3FGVlanMCOutErrors
         Counter64,
      pr1646v2Lan3FGVlanMCOutQLen
         Counter32,
      pr1646v2Lan3FGVlanMCOutDropEx
         Counter64,
      pr1646v2Lan3FGVlanMCOutDropNoArp
         Counter64,
      pr1646v2Lan3FGVlanMCOutDropFilter
         Counter64,
      pr1646v2Lan3FGVlanMCOutBandwidth15sec
         Integer32,
      pr1646v2Lan3FGVlanMCOutBandwidth30sec
         Integer32,
      pr1646v2Lan3FGVlanMCOutBandwidth1min
         Integer32,
      pr1646v2Lan3FGVlanMCOutBandwidth2min
         Integer32,
      pr1646v2Lan3FGVlanMCOutBandwidth5min
         Integer32,
      pr1646v2Lan3FGVlanVlanVid
         Integer32,
      pr1646v2Lan3FGVlanPppLinkMonitoringRequestsSent
         Gauge32,
      pr1646v2Lan3FGVlanPppLinkMonitoringRepliesRcvd
         Gauge32,
      pr1646v2Lan3FGVlanPppLinkMonitoringRequestsRcvd
         Gauge32,
      pr1646v2Lan3FGVlanPppLinkMonitoringRepliesSent
         Gauge32
      }

pr1646v2Lan3FGVlanTableIx OBJECT-TYPE
   SYNTAX      TableIndex
   MAX-ACCESS  not-accessible
   STATUS      current
   DESCRIPTION
      ""
   ::= {pr1646v2Lan3FGVlanEntry 11}

pr1646v2Lan3FGVlanName OBJECT-TYPE
   SYNTAX      DisplayString
   MAX-ACCESS  read-only
   STATUS      current
   DESCRIPTION
      "Path: ethernet3.performance.vlan.name"
   ::= {pr1646v2Lan3FGVlanEntry 16777216}

pr1646v2Lan3FGVlanMCInOctets OBJECT-TYPE
   SYNTAX      Counter64
   MAX-ACCESS  read-only
   STATUS      current
   DESCRIPTION
      "Path: ethernet3.performance.vlan.mibCounters.ifInOctets

       64 bit unsigned wrappable counter."
   ::= {pr1646v2Lan3FGVlanEntry 40697856}

pr1646v2Lan3FGVlanMCInUcast OBJECT-TYPE
   SYNTAX      Counter64
   MAX-ACCESS  read-only
   STATUS      current
   DESCRIPTION
      "Path: ethernet3.performance.vlan.mibCounters.ifInUcastPkts

       64 bit unsigned wrappable counter."
   ::= {pr1646v2Lan3FGVlanEntry 40763392}

pr1646v2Lan3FGVlanMCInNUcastPkts OBJECT-TYPE
   SYNTAX      Counter64
   MAX-ACCESS  read-only
   STATUS      current
   DESCRIPTION
      "Path: ethernet3.performance.vlan.mibCounters.ifInNUcastPkts

       64 bit unsigned wrappable counter."
   ::= {pr1646v2Lan3FGVlanEntry 40828928}

pr1646v2Lan3FGVlanMCInBcastPkts OBJECT-TYPE
   SYNTAX      Counter64
   MAX-ACCESS  read-only
   STATUS      current
   DESCRIPTION
      "Path: ethernet3.performance.vlan.mibCounters.ifInBcastPkts

       64 bit unsigned wrappable counter."
   ::= {pr1646v2Lan3FGVlanEntry 47382528}

pr1646v2Lan3FGVlanMCInMcastPkts OBJECT-TYPE
   SYNTAX      Counter64
   MAX-ACCESS  read-only
   STATUS      current
   DESCRIPTION
      "Path: ethernet3.performance.vlan.mibCounters.ifInMcastPkts

       64 bit unsigned wrappable counter."
   ::= {pr1646v2Lan3FGVlanEntry 48037888}

pr1646v2Lan3FGVlanMCInDiscards OBJECT-TYPE
   SYNTAX      Counter64
   MAX-ACCESS  read-only
   STATUS      current
   DESCRIPTION
      "Path: ethernet3.performance.vlan.mibCounters.ifInDiscards

       64 bit unsigned wrappable counter."
   ::= {pr1646v2Lan3FGVlanEntry 40894464}

pr1646v2Lan3FGVlanMCInErrors OBJECT-TYPE
   SYNTAX      Counter64
   MAX-ACCESS  read-only
   STATUS      current
   DESCRIPTION
      "Path: ethernet3.performance.vlan.mibCounters.ifInErrors

       64 bit unsigned wrappable counter."
   ::= {pr1646v2Lan3FGVlanEntry 40960000}

pr1646v2Lan3FGVlanMCInUnknownProtos OBJECT-TYPE
   SYNTAX      Counter64
   MAX-ACCESS  read-only
   STATUS      current
   DESCRIPTION
      "Path: ethernet3.performance.vlan.mibCounters.ifInUnknownProtos

       64 bit unsigned wrappable counter."
   ::= {pr1646v2Lan3FGVlanEntry 41025536}

pr1646v2Lan3FGVlanMCInDropEx OBJECT-TYPE
   SYNTAX      Counter64
   MAX-ACCESS  read-only
   STATUS      current
   DESCRIPTION
      "Path: ethernet3.performance.vlan.mibCounters.ifInDropLevelExceeded

       64 bit unsigned wrappable counter."
   ::= {pr1646v2Lan3FGVlanEntry 42074112}

pr1646v2Lan3FGVlanMCInDropNoMac OBJECT-TYPE
   SYNTAX      Counter64
   MAX-ACCESS  read-only
   STATUS      current
   DESCRIPTION
      "Path: ethernet3.performance.vlan.mibCounters.ifInDiscardsNoMacFit

       64 bit unsigned wrappable counter."
   ::= {pr1646v2Lan3FGVlanEntry 42270720}

pr1646v2Lan3FGVlanMCInDropNUCast OBJECT-TYPE
   SYNTAX      Counter64
   MAX-ACCESS  read-only
   STATUS      current
   DESCRIPTION
      "Path: ethernet3.performance.vlan.mibCounters.ifInDiscardsNUCast

       64 bit unsigned wrappable counter."
   ::= {pr1646v2Lan3FGVlanEntry 42467328}

pr1646v2Lan3FGVlanMCInDropFilter OBJECT-TYPE
   SYNTAX      Counter64
   MAX-ACCESS  read-only
   STATUS      current
   DESCRIPTION
      "Path: ethernet3.performance.vlan.mibCounters.ifInDiscardsFilter

       64 bit unsigned wrappable counter."
   ::= {pr1646v2Lan3FGVlanEntry 42532864}

pr1646v2Lan3FGVlanMCInBandwidth15sec OBJECT-TYPE
   SYNTAX      Integer32
   MAX-ACCESS  read-only
   STATUS      current
   DESCRIPTION
      "Path: ethernet3.performance.vlan.mibCounters.ifInBandwidth.15sec

       unit name = bps
       formula = 8 * ; 8 /"
   ::= {pr1646v2Lan3FGVlanEntry 45417728}

pr1646v2Lan3FGVlanMCInBandwidth30sec OBJECT-TYPE
   SYNTAX      Integer32
   MAX-ACCESS  read-only
   STATUS      current
   DESCRIPTION
      "Path: ethernet3.performance.vlan.mibCounters.ifInBandwidth.30sec

       unit name = bps
       formula = 8 * ; 8 /"
   ::= {pr1646v2Lan3FGVlanEntry 45419008}

pr1646v2Lan3FGVlanMCInBandwidth1min OBJECT-TYPE
   SYNTAX      Integer32
   MAX-ACCESS  read-only
   STATUS      current
   DESCRIPTION
      "Path: ethernet3.performance.vlan.mibCounters.ifInBandwidth.1min

       unit name = bps
       formula = 8 * ; 8 /"
   ::= {pr1646v2Lan3FGVlanEntry 45421568}

pr1646v2Lan3FGVlanMCInBandwidth2min OBJECT-TYPE
   SYNTAX      Integer32
   MAX-ACCESS  read-only
   STATUS      current
   DESCRIPTION
      "Path: ethernet3.performance.vlan.mibCounters.ifInBandwidth.2min

       unit name = bps
       formula = 8 * ; 8 /"
   ::= {pr1646v2Lan3FGVlanEntry 45426688}

pr1646v2Lan3FGVlanMCInBandwidth5min OBJECT-TYPE
   SYNTAX      Integer32
   MAX-ACCESS  read-only
   STATUS      current
   DESCRIPTION
      "Path: ethernet3.performance.vlan.mibCounters.ifInBandwidth.5min

       unit name = bps
       formula = 8 * ; 8 /"
   ::= {pr1646v2Lan3FGVlanEntry 45442048}

pr1646v2Lan3FGVlanMCOutOctets OBJECT-TYPE
   SYNTAX      Counter64
   MAX-ACCESS  read-only
   STATUS      current
   DESCRIPTION
      "Path: ethernet3.performance.vlan.mibCounters.ifOutOctets

       64 bit unsigned wrappable counter."
   ::= {pr1646v2Lan3FGVlanEntry 41091072}

pr1646v2Lan3FGVlanMCOutUcastPkts OBJECT-TYPE
   SYNTAX      Counter64
   MAX-ACCESS  read-only
   STATUS      current
   DESCRIPTION
      "Path: ethernet3.performance.vlan.mibCounters.ifOutUcastPkts

       64 bit unsigned wrappable counter."
   ::= {pr1646v2Lan3FGVlanEntry 41156608}

pr1646v2Lan3FGVlanMCOutNUcastPkts OBJECT-TYPE
   SYNTAX      Counter64
   MAX-ACCESS  read-only
   STATUS      current
   DESCRIPTION
      "Path: ethernet3.performance.vlan.mibCounters.ifOutNUcastPkts

       64 bit unsigned wrappable counter."
   ::= {pr1646v2Lan3FGVlanEntry 41222144}

pr1646v2Lan3FGVlanMCOutBcastPkts OBJECT-TYPE
   SYNTAX      Counter64
   MAX-ACCESS  read-only
   STATUS      current
   DESCRIPTION
      "Path: ethernet3.performance.vlan.mibCounters.ifOutBcastPkts

       64 bit unsigned wrappable counter."
   ::= {pr1646v2Lan3FGVlanEntry 47775744}

pr1646v2Lan3FGVlanMCOutMcastPkts OBJECT-TYPE
   SYNTAX      Counter64
   MAX-ACCESS  read-only
   STATUS      current
   DESCRIPTION
      "Path: ethernet3.performance.vlan.mibCounters.ifOutMcastPkts

       64 bit unsigned wrappable counter."
   ::= {pr1646v2Lan3FGVlanEntry 48431104}

pr1646v2Lan3FGVlanMCOutDiscards OBJECT-TYPE
   SYNTAX      Counter64
   MAX-ACCESS  read-only
   STATUS      current
   DESCRIPTION
      "Path: ethernet3.performance.vlan.mibCounters.ifOutDiscards

       64 bit unsigned wrappable counter."
   ::= {pr1646v2Lan3FGVlanEntry 41287680}

pr1646v2Lan3FGVlanMCOutErrors OBJECT-TYPE
   SYNTAX      Counter64
   MAX-ACCESS  read-only
   STATUS      current
   DESCRIPTION
      "Path: ethernet3.performance.vlan.mibCounters.ifOutErrors

       64 bit unsigned wrappable counter."
   ::= {pr1646v2Lan3FGVlanEntry 41353216}

pr1646v2Lan3FGVlanMCOutQLen OBJECT-TYPE
   SYNTAX      Counter32
   MAX-ACCESS  read-only
   STATUS      current
   DESCRIPTION
      "Path: ethernet3.performance.vlan.mibCounters.ifOutQLen

       32 bit unsigned wrappable counter."
   ::= {pr1646v2Lan3FGVlanEntry 41418752}

pr1646v2Lan3FGVlanMCOutDropEx OBJECT-TYPE
   SYNTAX      Counter64
   MAX-ACCESS  read-only
   STATUS      current
   DESCRIPTION
      "Path: ethernet3.performance.vlan.mibCounters.ifOutDropLevelExceeded

       64 bit unsigned wrappable counter."
   ::= {pr1646v2Lan3FGVlanEntry 41484288}

pr1646v2Lan3FGVlanMCOutDropNoArp OBJECT-TYPE
   SYNTAX      Counter64
   MAX-ACCESS  read-only
   STATUS      current
   DESCRIPTION
      "Path: ethernet3.performance.vlan.mibCounters.ifOutDiscardsNoArp

       64 bit unsigned wrappable counter."
   ::= {pr1646v2Lan3FGVlanEntry 42336256}

pr1646v2Lan3FGVlanMCOutDropFilter OBJECT-TYPE
   SYNTAX      Counter64
   MAX-ACCESS  read-only
   STATUS      current
   DESCRIPTION
      "Path: ethernet3.performance.vlan.mibCounters.ifOutDiscardsFilter

       64 bit unsigned wrappable counter."
   ::= {pr1646v2Lan3FGVlanEntry 42598400}

pr1646v2Lan3FGVlanMCOutBandwidth15sec OBJECT-TYPE
   SYNTAX      Integer32
   MAX-ACCESS  read-only
   STATUS      current
   DESCRIPTION
      "Path: ethernet3.performance.vlan.mibCounters.ifOutBandwidth.15sec

       unit name = bps
       formula = 8 * ; 8 /"
   ::= {pr1646v2Lan3FGVlanEntry 45483264}

pr1646v2Lan3FGVlanMCOutBandwidth30sec OBJECT-TYPE
   SYNTAX      Integer32
   MAX-ACCESS  read-only
   STATUS      current
   DESCRIPTION
      "Path: ethernet3.performance.vlan.mibCounters.ifOutBandwidth.30sec

       unit name = bps
       formula = 8 * ; 8 /"
   ::= {pr1646v2Lan3FGVlanEntry 45484544}

pr1646v2Lan3FGVlanMCOutBandwidth1min OBJECT-TYPE
   SYNTAX      Integer32
   MAX-ACCESS  read-only
   STATUS      current
   DESCRIPTION
      "Path: ethernet3.performance.vlan.mibCounters.ifOutBandwidth.1min

       unit name = bps
       formula = 8 * ; 8 /"
   ::= {pr1646v2Lan3FGVlanEntry 45487104}

pr1646v2Lan3FGVlanMCOutBandwidth2min OBJECT-TYPE
   SYNTAX      Integer32
   MAX-ACCESS  read-only
   STATUS      current
   DESCRIPTION
      "Path: ethernet3.performance.vlan.mibCounters.ifOutBandwidth.2min

       unit name = bps
       formula = 8 * ; 8 /"
   ::= {pr1646v2Lan3FGVlanEntry 45492224}

pr1646v2Lan3FGVlanMCOutBandwidth5min OBJECT-TYPE
   SYNTAX      Integer32
   MAX-ACCESS  read-only
   STATUS      current
   DESCRIPTION
      "Path: ethernet3.performance.vlan.mibCounters.ifOutBandwidth.5min

       unit name = bps
       formula = 8 * ; 8 /"
   ::= {pr1646v2Lan3FGVlanEntry 45507584}

pr1646v2Lan3FGVlanVlanVid OBJECT-TYPE
   SYNTAX      Integer32
   MAX-ACCESS  read-only
   STATUS      current
   DESCRIPTION
      "Path: ethernet3.performance.vlan.vlan.vid"
   ::= {pr1646v2Lan3FGVlanEntry 234946560}

pr1646v2Lan3FGVlanPppLinkMonitoringRequestsSent OBJECT-TYPE
   SYNTAX      Gauge32
   MAX-ACCESS  read-only
   STATUS      current
   DESCRIPTION
      "Path: ethernet3.performance.vlan.ppp.linkMonitoring.requestsSent

       32 bit unsigned gauge value."
   ::= {pr1646v2Lan3FGVlanEntry 50397440}

pr1646v2Lan3FGVlanPppLinkMonitoringRepliesRcvd OBJECT-TYPE
   SYNTAX      Gauge32
   MAX-ACCESS  read-only
   STATUS      current
   DESCRIPTION
      "Path: ethernet3.performance.vlan.ppp.linkMonitoring.repliesRcvd

       32 bit unsigned gauge value."
   ::= {pr1646v2Lan3FGVlanEntry 50397696}

pr1646v2Lan3FGVlanPppLinkMonitoringRequestsRcvd OBJECT-TYPE
   SYNTAX      Gauge32
   MAX-ACCESS  read-only
   STATUS      current
   DESCRIPTION
      "Path: ethernet3.performance.vlan.ppp.linkMonitoring.requestsRcvd

       32 bit unsigned gauge value."
   ::= {pr1646v2Lan3FGVlanEntry 50397952}

pr1646v2Lan3FGVlanPppLinkMonitoringRepliesSent OBJECT-TYPE
   SYNTAX      Gauge32
   MAX-ACCESS  read-only
   STATUS      current
   DESCRIPTION
      "Path: ethernet3.performance.vlan.ppp.linkMonitoring.repliesSent

       32 bit unsigned gauge value."
   ::= {pr1646v2Lan3FGVlanEntry 50398208}

pr1646v2Lan3FGVlanMCH2P OBJECT-TYPE
   SYNTAX      SEQUENCE OF Pr1646v2Lan3FGVlanMCH2PEntry
   MAX-ACCESS  not-accessible
   STATUS      current
   DESCRIPTION
      ""
   ::= {pr1646v2Lan3FGVlan 41549824}

pr1646v2Lan3FGVlanMCH2PEntry OBJECT-TYPE
   SYNTAX      Pr1646v2Lan3FGVlanMCH2PEntry
   MAX-ACCESS  not-accessible
   STATUS      current
   DESCRIPTION
      ""
   INDEX      { pr1646v2Lan3FGVlanTableIx,
                pr1646v2Lan3FGVlanMCH2PTableIx }
   ::= {pr1646v2Lan3FGVlanMCH2P 1}

Pr1646v2Lan3FGVlanMCH2PEntry ::=
   SEQUENCE
      {
      pr1646v2Lan3FGVlanMCH2PTableIx
         TableIndex,
      pr1646v2Lan3FGVlanMCH2PSysUpTime
         TimeTicks,
      pr1646v2Lan3FGVlanMCH2PIfUpTime
         TimeTicks,
      pr1646v2Lan3FGVlanMCH2PIfStatChanges
         Counter32,
      pr1646v2Lan3FGVlanMCH2PIfInOctets
         Counter64,
      pr1646v2Lan3FGVlanMCH2PIfInUCPkts
         Counter64,
      pr1646v2Lan3FGVlanMCH2PIfInNUCPkts
         Counter64,
      pr1646v2Lan3FGVlanMCH2PIfInBCPkts
         Counter64,
      pr1646v2Lan3FGVlanMCH2PIfInMCPkts
         Counter64,
      pr1646v2Lan3FGVlanMCH2PIfInDiscards
         Counter64,
      pr1646v2Lan3FGVlanMCH2PIfInErrors
         Counter64,
      pr1646v2Lan3FGVlanMCH2PIfInUnkwn
         Counter64,
      pr1646v2Lan3FGVlanMCH2PInDropEx
         Counter64,
      pr1646v2Lan3FGVlanMCH2PInDropNoMac
         Counter64,
      pr1646v2Lan3FGVlanMCH2PInDropNUCast
         Counter64,
      pr1646v2Lan3FGVlanMCH2PInDropFilter
         Counter64,
      pr1646v2Lan3FGVlanMCH2PIfInBandwidth
         Integer32,
      pr1646v2Lan3FGVlanMCH2PIfOutOctets
         Counter64,
      pr1646v2Lan3FGVlanMCH2PIfOutUCPkts
         Counter64,
      pr1646v2Lan3FGVlanMCH2PIfOutNUCPkts
         Counter64,
      pr1646v2Lan3FGVlanMCH2PIfOutBCPkts
         Counter64,
      pr1646v2Lan3FGVlanMCH2PIfOutMCPkts
         Counter64,
      pr1646v2Lan3FGVlanMCH2PIfOutDiscards
         Counter64,
      pr1646v2Lan3FGVlanMCH2PIfOutErrors
         Counter64,
      pr1646v2Lan3FGVlanMCH2POutDropEx
         Counter64,
      pr1646v2Lan3FGVlanMCH2POutDropNoArp
         Counter64,
      pr1646v2Lan3FGVlanMCH2POutDropFilter
         Counter64,
      pr1646v2Lan3FGVlanMCH2PIfOutBandwidth
         Integer32,
      pr1646v2Lan3FGVlanMCH2PIfErrSec
         Counter32
      }

pr1646v2Lan3FGVlanMCH2PTableIx OBJECT-TYPE
   SYNTAX      TableIndex
   MAX-ACCESS  not-accessible
   STATUS      current
   DESCRIPTION
      ""
   ::= {pr1646v2Lan3FGVlanMCH2PEntry 11}

pr1646v2Lan3FGVlanMCH2PSysUpTime OBJECT-TYPE
   SYNTAX      TimeTicks
   MAX-ACCESS  read-only
   STATUS      current
   DESCRIPTION
      "Path: ethernet3.performance.vlan.mibCounters.h2Performance.sysUpTime

       Time in centi-second."
   ::= {pr1646v2Lan3FGVlanMCH2PEntry 16777216}

pr1646v2Lan3FGVlanMCH2PIfUpTime OBJECT-TYPE
   SYNTAX      TimeTicks
   MAX-ACCESS  read-only
   STATUS      current
   DESCRIPTION
      "Path: ethernet3.performance.vlan.mibCounters.h2Performance.ifUpTime

       Time in centi-second."
   ::= {pr1646v2Lan3FGVlanMCH2PEntry 33554432}

pr1646v2Lan3FGVlanMCH2PIfStatChanges OBJECT-TYPE
   SYNTAX      Counter32
   MAX-ACCESS  read-only
   STATUS      current
   DESCRIPTION
      "Path: ethernet3.performance.vlan.mibCounters.h2Performance.ifStatusChanges

       32 bit unsigned wrappable counter."
   ::= {pr1646v2Lan3FGVlanMCH2PEntry 50331648}

pr1646v2Lan3FGVlanMCH2PIfInOctets OBJECT-TYPE
   SYNTAX      Counter64
   MAX-ACCESS  read-only
   STATUS      current
   DESCRIPTION
      "Path: ethernet3.performance.vlan.mibCounters.h2Performance.ifInOctets

       64 bit unsigned wrappable counter."
   ::= {pr1646v2Lan3FGVlanMCH2PEntry 67108864}

pr1646v2Lan3FGVlanMCH2PIfInUCPkts OBJECT-TYPE
   SYNTAX      Counter64
   MAX-ACCESS  read-only
   STATUS      current
   DESCRIPTION
      "Path: ethernet3.performance.vlan.mibCounters.h2Performance.ifInUcastPkts

       64 bit unsigned wrappable counter."
   ::= {pr1646v2Lan3FGVlanMCH2PEntry 83886080}

pr1646v2Lan3FGVlanMCH2PIfInNUCPkts OBJECT-TYPE
   SYNTAX      Counter64
   MAX-ACCESS  read-only
   STATUS      current
   DESCRIPTION
      "Path: ethernet3.performance.vlan.mibCounters.h2Performance.ifInNUcastPkts

       64 bit unsigned wrappable counter."
   ::= {pr1646v2Lan3FGVlanMCH2PEntry 100663296}

pr1646v2Lan3FGVlanMCH2PIfInBCPkts OBJECT-TYPE
   SYNTAX      Counter64
   MAX-ACCESS  read-only
   STATUS      current
   DESCRIPTION
      "Path: ethernet3.performance.vlan.mibCounters.h2Performance.ifInBcastPkts

       64 bit unsigned wrappable counter."
   ::= {pr1646v2Lan3FGVlanMCH2PEntry 419430400}

pr1646v2Lan3FGVlanMCH2PIfInMCPkts OBJECT-TYPE
   SYNTAX      Counter64
   MAX-ACCESS  read-only
   STATUS      current
   DESCRIPTION
      "Path: ethernet3.performance.vlan.mibCounters.h2Performance.ifInMcastPkts

       64 bit unsigned wrappable counter."
   ::= {pr1646v2Lan3FGVlanMCH2PEntry 436207616}

pr1646v2Lan3FGVlanMCH2PIfInDiscards OBJECT-TYPE
   SYNTAX      Counter64
   MAX-ACCESS  read-only
   STATUS      current
   DESCRIPTION
      "Path: ethernet3.performance.vlan.mibCounters.h2Performance.ifInDiscards

       64 bit unsigned wrappable counter."
   ::= {pr1646v2Lan3FGVlanMCH2PEntry 117440512}

pr1646v2Lan3FGVlanMCH2PIfInErrors OBJECT-TYPE
   SYNTAX      Counter64
   MAX-ACCESS  read-only
   STATUS      current
   DESCRIPTION
      "Path: ethernet3.performance.vlan.mibCounters.h2Performance.ifInErrors

       64 bit unsigned wrappable counter."
   ::= {pr1646v2Lan3FGVlanMCH2PEntry 134217728}

pr1646v2Lan3FGVlanMCH2PIfInUnkwn OBJECT-TYPE
   SYNTAX      Counter64
   MAX-ACCESS  read-only
   STATUS      current
   DESCRIPTION
      "Path: ethernet3.performance.vlan.mibCounters.h2Performance.ifInUnknownProtos

       64 bit unsigned wrappable counter."
   ::= {pr1646v2Lan3FGVlanMCH2PEntry 150994944}

pr1646v2Lan3FGVlanMCH2PInDropEx OBJECT-TYPE
   SYNTAX      Counter64
   MAX-ACCESS  read-only
   STATUS      current
   DESCRIPTION
      "Path: ethernet3.performance.vlan.mibCounters.h2Performance.ifInDropLevelExceeded

       64 bit unsigned wrappable counter."
   ::= {pr1646v2Lan3FGVlanMCH2PEntry 335544320}

pr1646v2Lan3FGVlanMCH2PInDropNoMac OBJECT-TYPE
   SYNTAX      Counter64
   MAX-ACCESS  read-only
   STATUS      current
   DESCRIPTION
      "Path: ethernet3.performance.vlan.mibCounters.h2Performance.fInDiscardsNoMacFit

       64 bit unsigned wrappable counter."
   ::= {pr1646v2Lan3FGVlanMCH2PEntry 301989888}

pr1646v2Lan3FGVlanMCH2PInDropNUCast OBJECT-TYPE
   SYNTAX      Counter64
   MAX-ACCESS  read-only
   STATUS      current
   DESCRIPTION
      "Path: ethernet3.performance.vlan.mibCounters.h2Performance.fInDiscardsNUCast

       64 bit unsigned wrappable counter."
   ::= {pr1646v2Lan3FGVlanMCH2PEntry 318767104}

pr1646v2Lan3FGVlanMCH2PInDropFilter OBJECT-TYPE
   SYNTAX      Counter64
   MAX-ACCESS  read-only
   STATUS      current
   DESCRIPTION
      "Path: ethernet3.performance.vlan.mibCounters.h2Performance.fInDiscardsFilter

       64 bit unsigned wrappable counter."
   ::= {pr1646v2Lan3FGVlanMCH2PEntry 385875968}

pr1646v2Lan3FGVlanMCH2PIfInBandwidth OBJECT-TYPE
   SYNTAX      Integer32
   MAX-ACCESS  read-only
   STATUS      current
   DESCRIPTION
      "Path: ethernet3.performance.vlan.mibCounters.h2Performance.ifInBandwidth

       unit name = bps
       formula = 8 * ; 8 /"
   ::= {pr1646v2Lan3FGVlanMCH2PEntry 268435456}

pr1646v2Lan3FGVlanMCH2PIfOutOctets OBJECT-TYPE
   SYNTAX      Counter64
   MAX-ACCESS  read-only
   STATUS      current
   DESCRIPTION
      "Path: ethernet3.performance.vlan.mibCounters.h2Performance.ifOutOctets

       64 bit unsigned wrappable counter."
   ::= {pr1646v2Lan3FGVlanMCH2PEntry 167772160}

pr1646v2Lan3FGVlanMCH2PIfOutUCPkts OBJECT-TYPE
   SYNTAX      Counter64
   MAX-ACCESS  read-only
   STATUS      current
   DESCRIPTION
      "Path: ethernet3.performance.vlan.mibCounters.h2Performance.ifOutUcastPkts

       64 bit unsigned wrappable counter."
   ::= {pr1646v2Lan3FGVlanMCH2PEntry 184549376}

pr1646v2Lan3FGVlanMCH2PIfOutNUCPkts OBJECT-TYPE
   SYNTAX      Counter64
   MAX-ACCESS  read-only
   STATUS      current
   DESCRIPTION
      "Path: ethernet3.performance.vlan.mibCounters.h2Performance.ifOutNUcastPkts

       64 bit unsigned wrappable counter."
   ::= {pr1646v2Lan3FGVlanMCH2PEntry 201326592}

pr1646v2Lan3FGVlanMCH2PIfOutBCPkts OBJECT-TYPE
   SYNTAX      Counter64
   MAX-ACCESS  read-only
   STATUS      current
   DESCRIPTION
      "Path: ethernet3.performance.vlan.mibCounters.h2Performance.ifOutBcastPkts

       64 bit unsigned wrappable counter."
   ::= {pr1646v2Lan3FGVlanMCH2PEntry 452984832}

pr1646v2Lan3FGVlanMCH2PIfOutMCPkts OBJECT-TYPE
   SYNTAX      Counter64
   MAX-ACCESS  read-only
   STATUS      current
   DESCRIPTION
      "Path: ethernet3.performance.vlan.mibCounters.h2Performance.ifOutMcastPkts

       64 bit unsigned wrappable counter."
   ::= {pr1646v2Lan3FGVlanMCH2PEntry 469762048}

pr1646v2Lan3FGVlanMCH2PIfOutDiscards OBJECT-TYPE
   SYNTAX      Counter64
   MAX-ACCESS  read-only
   STATUS      current
   DESCRIPTION
      "Path: ethernet3.performance.vlan.mibCounters.h2Performance.ifOutDiscards

       64 bit unsigned wrappable counter."
   ::= {pr1646v2Lan3FGVlanMCH2PEntry 218103808}

pr1646v2Lan3FGVlanMCH2PIfOutErrors OBJECT-TYPE
   SYNTAX      Counter64
   MAX-ACCESS  read-only
   STATUS      current
   DESCRIPTION
      "Path: ethernet3.performance.vlan.mibCounters.h2Performance.ifOutErrors

       64 bit unsigned wrappable counter."
   ::= {pr1646v2Lan3FGVlanMCH2PEntry 234881024}

pr1646v2Lan3FGVlanMCH2POutDropEx OBJECT-TYPE
   SYNTAX      Counter64
   MAX-ACCESS  read-only
   STATUS      current
   DESCRIPTION
      "Path: ethernet3.performance.vlan.mibCounters.h2Performance.ifOutDropLevelExceeded

       64 bit unsigned wrappable counter."
   ::= {pr1646v2Lan3FGVlanMCH2PEntry 352321536}

pr1646v2Lan3FGVlanMCH2POutDropNoArp OBJECT-TYPE
   SYNTAX      Counter64
   MAX-ACCESS  read-only
   STATUS      current
   DESCRIPTION
      "Path: ethernet3.performance.vlan.mibCounters.h2Performance.ifOutDiscardsNoArp

       64 bit unsigned wrappable counter."
   ::= {pr1646v2Lan3FGVlanMCH2PEntry 369098752}

pr1646v2Lan3FGVlanMCH2POutDropFilter OBJECT-TYPE
   SYNTAX      Counter64
   MAX-ACCESS  read-only
   STATUS      current
   DESCRIPTION
      "Path: ethernet3.performance.vlan.mibCounters.h2Performance.ifOutDiscardsFilter

       64 bit unsigned wrappable counter."
   ::= {pr1646v2Lan3FGVlanMCH2PEntry 402653184}

pr1646v2Lan3FGVlanMCH2PIfOutBandwidth OBJECT-TYPE
   SYNTAX      Integer32
   MAX-ACCESS  read-only
   STATUS      current
   DESCRIPTION
      "Path: ethernet3.performance.vlan.mibCounters.h2Performance.ifOutBandwidth

       unit name = bps
       formula = 8 * ; 8 /"
   ::= {pr1646v2Lan3FGVlanMCH2PEntry 285212672}

pr1646v2Lan3FGVlanMCH2PIfErrSec OBJECT-TYPE
   SYNTAX      Counter32
   MAX-ACCESS  read-only
   STATUS      current
   DESCRIPTION
      "Path: ethernet3.performance.vlan.mibCounters.h2Performance.ifErrSec

       32 bit unsigned wrappable counter."
   ::= {pr1646v2Lan3FGVlanMCH2PEntry 251658240}

pr1646v2Lan3FGVlanMCH24P OBJECT-TYPE
   SYNTAX      SEQUENCE OF Pr1646v2Lan3FGVlanMCH24PEntry
   MAX-ACCESS  not-accessible
   STATUS      current
   DESCRIPTION
      ""
   ::= {pr1646v2Lan3FGVlan 41615360}

pr1646v2Lan3FGVlanMCH24PEntry OBJECT-TYPE
   SYNTAX      Pr1646v2Lan3FGVlanMCH24PEntry
   MAX-ACCESS  not-accessible
   STATUS      current
   DESCRIPTION
      ""
   INDEX      { pr1646v2Lan3FGVlanTableIx,
                pr1646v2Lan3FGVlanMCH24PTableIx }
   ::= {pr1646v2Lan3FGVlanMCH24P 1}

Pr1646v2Lan3FGVlanMCH24PEntry ::=
   SEQUENCE
      {
      pr1646v2Lan3FGVlanMCH24PTableIx
         TableIndex,
      pr1646v2Lan3FGVlanMCH24PSysUpTime
         TimeTicks,
      pr1646v2Lan3FGVlanMCH24PIfUpTime
         TimeTicks,
      pr1646v2Lan3FGVlanMCH24PIfStatChanges
         Counter32,
      pr1646v2Lan3FGVlanMCH24PIfInOctets
         Counter64,
      pr1646v2Lan3FGVlanMCH24PIfInUCPkts
         Counter64,
      pr1646v2Lan3FGVlanMCH24PIfInNUCPkts
         Counter64,
      pr1646v2Lan3FGVlanMCH24PIfInBCPkts
         Counter64,
      pr1646v2Lan3FGVlanMCH24PIfInMCPkts
         Counter64,
      pr1646v2Lan3FGVlanMCH24PIfInDiscards
         Counter64,
      pr1646v2Lan3FGVlanMCH24PIfInErrors
         Counter64,
      pr1646v2Lan3FGVlanMCH24PIfInUnkwn
         Counter64,
      pr1646v2Lan3FGVlanMCH24PInDropEx
         Counter64,
      pr1646v2Lan3FGVlanMCH24PInDropNoMac
         Counter64,
      pr1646v2Lan3FGVlanMCH24PInDropNUCast
         Counter64,
      pr1646v2Lan3FGVlanMCH24PInDropFilter
         Counter64,
      pr1646v2Lan3FGVlanMCH24PIfInBandwidth
         Integer32,
      pr1646v2Lan3FGVlanMCH24PIfOutOctets
         Counter64,
      pr1646v2Lan3FGVlanMCH24PIfOutUCPkts
         Counter64,
      pr1646v2Lan3FGVlanMCH24PIfOutNUCPkts
         Counter64,
      pr1646v2Lan3FGVlanMCH24PIfOutBCPkts
         Counter64,
      pr1646v2Lan3FGVlanMCH24PIfOutMCPkts
         Counter64,
      pr1646v2Lan3FGVlanMCH24PIfOutDiscards
         Counter64,
      pr1646v2Lan3FGVlanMCH24PIfOutErrors
         Counter64,
      pr1646v2Lan3FGVlanMCH24POutDropEx
         Counter64,
      pr1646v2Lan3FGVlanMCH24POutDropNoArp
         Counter64,
      pr1646v2Lan3FGVlanMCH24POutDropFilter
         Counter64,
      pr1646v2Lan3FGVlanMCH24PIfOutBandwidth
         Integer32,
      pr1646v2Lan3FGVlanMCH24PIfErrSec
         Counter32
      }

pr1646v2Lan3FGVlanMCH24PTableIx OBJECT-TYPE
   SYNTAX      TableIndex
   MAX-ACCESS  not-accessible
   STATUS      current
   DESCRIPTION
      ""
   ::= {pr1646v2Lan3FGVlanMCH24PEntry 11}

pr1646v2Lan3FGVlanMCH24PSysUpTime OBJECT-TYPE
   SYNTAX      TimeTicks
   MAX-ACCESS  read-only
   STATUS      current
   DESCRIPTION
      "Path: ethernet3.performance.vlan.mibCounters.h24Performance.sysUpTime

       Time in centi-second."
   ::= {pr1646v2Lan3FGVlanMCH24PEntry 16777216}

pr1646v2Lan3FGVlanMCH24PIfUpTime OBJECT-TYPE
   SYNTAX      TimeTicks
   MAX-ACCESS  read-only
   STATUS      current
   DESCRIPTION
      "Path: ethernet3.performance.vlan.mibCounters.h24Performance.ifUpTime

       Time in centi-second."
   ::= {pr1646v2Lan3FGVlanMCH24PEntry 33554432}

pr1646v2Lan3FGVlanMCH24PIfStatChanges OBJECT-TYPE
   SYNTAX      Counter32
   MAX-ACCESS  read-only
   STATUS      current
   DESCRIPTION
      "Path: ethernet3.performance.vlan.mibCounters.h24Performance.ifStatusChanges

       32 bit unsigned wrappable counter."
   ::= {pr1646v2Lan3FGVlanMCH24PEntry 50331648}

pr1646v2Lan3FGVlanMCH24PIfInOctets OBJECT-TYPE
   SYNTAX      Counter64
   MAX-ACCESS  read-only
   STATUS      current
   DESCRIPTION
      "Path: ethernet3.performance.vlan.mibCounters.h24Performance.ifInOctets

       64 bit unsigned wrappable counter."
   ::= {pr1646v2Lan3FGVlanMCH24PEntry 67108864}

pr1646v2Lan3FGVlanMCH24PIfInUCPkts OBJECT-TYPE
   SYNTAX      Counter64
   MAX-ACCESS  read-only
   STATUS      current
   DESCRIPTION
      "Path: ethernet3.performance.vlan.mibCounters.h24Performance.ifInUcastPkts

       64 bit unsigned wrappable counter."
   ::= {pr1646v2Lan3FGVlanMCH24PEntry 83886080}

pr1646v2Lan3FGVlanMCH24PIfInNUCPkts OBJECT-TYPE
   SYNTAX      Counter64
   MAX-ACCESS  read-only
   STATUS      current
   DESCRIPTION
      "Path: ethernet3.performance.vlan.mibCounters.h24Performance.ifInNUcastPkts

       64 bit unsigned wrappable counter."
   ::= {pr1646v2Lan3FGVlanMCH24PEntry 100663296}

pr1646v2Lan3FGVlanMCH24PIfInBCPkts OBJECT-TYPE
   SYNTAX      Counter64
   MAX-ACCESS  read-only
   STATUS      current
   DESCRIPTION
      "Path: ethernet3.performance.vlan.mibCounters.h24Performance.ifInBcastPkts

       64 bit unsigned wrappable counter."
   ::= {pr1646v2Lan3FGVlanMCH24PEntry 419430400}

pr1646v2Lan3FGVlanMCH24PIfInMCPkts OBJECT-TYPE
   SYNTAX      Counter64
   MAX-ACCESS  read-only
   STATUS      current
   DESCRIPTION
      "Path: ethernet3.performance.vlan.mibCounters.h24Performance.ifInMcastPkts

       64 bit unsigned wrappable counter."
   ::= {pr1646v2Lan3FGVlanMCH24PEntry 436207616}

pr1646v2Lan3FGVlanMCH24PIfInDiscards OBJECT-TYPE
   SYNTAX      Counter64
   MAX-ACCESS  read-only
   STATUS      current
   DESCRIPTION
      "Path: ethernet3.performance.vlan.mibCounters.h24Performance.ifInDiscards

       64 bit unsigned wrappable counter."
   ::= {pr1646v2Lan3FGVlanMCH24PEntry 117440512}

pr1646v2Lan3FGVlanMCH24PIfInErrors OBJECT-TYPE
   SYNTAX      Counter64
   MAX-ACCESS  read-only
   STATUS      current
   DESCRIPTION
      "Path: ethernet3.performance.vlan.mibCounters.h24Performance.ifInErrors

       64 bit unsigned wrappable counter."
   ::= {pr1646v2Lan3FGVlanMCH24PEntry 134217728}

pr1646v2Lan3FGVlanMCH24PIfInUnkwn OBJECT-TYPE
   SYNTAX      Counter64
   MAX-ACCESS  read-only
   STATUS      current
   DESCRIPTION
      "Path: ethernet3.performance.vlan.mibCounters.h24Performance.ifInUnknownProtos

       64 bit unsigned wrappable counter."
   ::= {pr1646v2Lan3FGVlanMCH24PEntry 150994944}

pr1646v2Lan3FGVlanMCH24PInDropEx OBJECT-TYPE
   SYNTAX      Counter64
   MAX-ACCESS  read-only
   STATUS      current
   DESCRIPTION
      "Path: ethernet3.performance.vlan.mibCounters.h24Performance.ifInDropLevelExceeded

       64 bit unsigned wrappable counter."
   ::= {pr1646v2Lan3FGVlanMCH24PEntry 335544320}

pr1646v2Lan3FGVlanMCH24PInDropNoMac OBJECT-TYPE
   SYNTAX      Counter64
   MAX-ACCESS  read-only
   STATUS      current
   DESCRIPTION
      "Path: ethernet3.performance.vlan.mibCounters.h24Performance.fInDiscardsNoMacFit

       64 bit unsigned wrappable counter."
   ::= {pr1646v2Lan3FGVlanMCH24PEntry 301989888}

pr1646v2Lan3FGVlanMCH24PInDropNUCast OBJECT-TYPE
   SYNTAX      Counter64
   MAX-ACCESS  read-only
   STATUS      current
   DESCRIPTION
      "Path: ethernet3.performance.vlan.mibCounters.h24Performance.fInDiscardsNUCast

       64 bit unsigned wrappable counter."
   ::= {pr1646v2Lan3FGVlanMCH24PEntry 318767104}

pr1646v2Lan3FGVlanMCH24PInDropFilter OBJECT-TYPE
   SYNTAX      Counter64
   MAX-ACCESS  read-only
   STATUS      current
   DESCRIPTION
      "Path: ethernet3.performance.vlan.mibCounters.h24Performance.fInDiscardsFilter

       64 bit unsigned wrappable counter."
   ::= {pr1646v2Lan3FGVlanMCH24PEntry 385875968}

pr1646v2Lan3FGVlanMCH24PIfInBandwidth OBJECT-TYPE
   SYNTAX      Integer32
   MAX-ACCESS  read-only
   STATUS      current
   DESCRIPTION
      "Path: ethernet3.performance.vlan.mibCounters.h24Performance.ifInBandwidth

       unit name = bps
       formula = 8 * ; 8 /"
   ::= {pr1646v2Lan3FGVlanMCH24PEntry 268435456}

pr1646v2Lan3FGVlanMCH24PIfOutOctets OBJECT-TYPE
   SYNTAX      Counter64
   MAX-ACCESS  read-only
   STATUS      current
   DESCRIPTION
      "Path: ethernet3.performance.vlan.mibCounters.h24Performance.ifOutOctets

       64 bit unsigned wrappable counter."
   ::= {pr1646v2Lan3FGVlanMCH24PEntry 167772160}

pr1646v2Lan3FGVlanMCH24PIfOutUCPkts OBJECT-TYPE
   SYNTAX      Counter64
   MAX-ACCESS  read-only
   STATUS      current
   DESCRIPTION
      "Path: ethernet3.performance.vlan.mibCounters.h24Performance.ifOutUcastPkts

       64 bit unsigned wrappable counter."
   ::= {pr1646v2Lan3FGVlanMCH24PEntry 184549376}

pr1646v2Lan3FGVlanMCH24PIfOutNUCPkts OBJECT-TYPE
   SYNTAX      Counter64
   MAX-ACCESS  read-only
   STATUS      current
   DESCRIPTION
      "Path: ethernet3.performance.vlan.mibCounters.h24Performance.ifOutNUcastPkts

       64 bit unsigned wrappable counter."
   ::= {pr1646v2Lan3FGVlanMCH24PEntry 201326592}

pr1646v2Lan3FGVlanMCH24PIfOutBCPkts OBJECT-TYPE
   SYNTAX      Counter64
   MAX-ACCESS  read-only
   STATUS      current
   DESCRIPTION
      "Path: ethernet3.performance.vlan.mibCounters.h24Performance.ifOutBcastPkts

       64 bit unsigned wrappable counter."
   ::= {pr1646v2Lan3FGVlanMCH24PEntry 452984832}

pr1646v2Lan3FGVlanMCH24PIfOutMCPkts OBJECT-TYPE
   SYNTAX      Counter64
   MAX-ACCESS  read-only
   STATUS      current
   DESCRIPTION
      "Path: ethernet3.performance.vlan.mibCounters.h24Performance.ifOutMcastPkts

       64 bit unsigned wrappable counter."
   ::= {pr1646v2Lan3FGVlanMCH24PEntry 469762048}

pr1646v2Lan3FGVlanMCH24PIfOutDiscards OBJECT-TYPE
   SYNTAX      Counter64
   MAX-ACCESS  read-only
   STATUS      current
   DESCRIPTION
      "Path: ethernet3.performance.vlan.mibCounters.h24Performance.ifOutDiscards

       64 bit unsigned wrappable counter."
   ::= {pr1646v2Lan3FGVlanMCH24PEntry 218103808}

pr1646v2Lan3FGVlanMCH24PIfOutErrors OBJECT-TYPE
   SYNTAX      Counter64
   MAX-ACCESS  read-only
   STATUS      current
   DESCRIPTION
      "Path: ethernet3.performance.vlan.mibCounters.h24Performance.ifOutErrors

       64 bit unsigned wrappable counter."
   ::= {pr1646v2Lan3FGVlanMCH24PEntry 234881024}

pr1646v2Lan3FGVlanMCH24POutDropEx OBJECT-TYPE
   SYNTAX      Counter64
   MAX-ACCESS  read-only
   STATUS      current
   DESCRIPTION
      "Path: ethernet3.performance.vlan.mibCounters.h24Performance.ifOutDropLevelExceeded

       64 bit unsigned wrappable counter."
   ::= {pr1646v2Lan3FGVlanMCH24PEntry 352321536}

pr1646v2Lan3FGVlanMCH24POutDropNoArp OBJECT-TYPE
   SYNTAX      Counter64
   MAX-ACCESS  read-only
   STATUS      current
   DESCRIPTION
      "Path: ethernet3.performance.vlan.mibCounters.h24Performance.ifOutDiscardsNoArp

       64 bit unsigned wrappable counter."
   ::= {pr1646v2Lan3FGVlanMCH24PEntry 369098752}

pr1646v2Lan3FGVlanMCH24POutDropFilter OBJECT-TYPE
   SYNTAX      Counter64
   MAX-ACCESS  read-only
   STATUS      current
   DESCRIPTION
      "Path: ethernet3.performance.vlan.mibCounters.h24Performance.ifOutDiscardsFilter

       64 bit unsigned wrappable counter."
   ::= {pr1646v2Lan3FGVlanMCH24PEntry 402653184}

pr1646v2Lan3FGVlanMCH24PIfOutBandwidth OBJECT-TYPE
   SYNTAX      Integer32
   MAX-ACCESS  read-only
   STATUS      current
   DESCRIPTION
      "Path: ethernet3.performance.vlan.mibCounters.h24Performance.ifOutBandwidth

       unit name = bps
       formula = 8 * ; 8 /"
   ::= {pr1646v2Lan3FGVlanMCH24PEntry 285212672}

pr1646v2Lan3FGVlanMCH24PIfErrSec OBJECT-TYPE
   SYNTAX      Counter32
   MAX-ACCESS  read-only
   STATUS      current
   DESCRIPTION
      "Path: ethernet3.performance.vlan.mibCounters.h24Performance.ifErrSec

       32 bit unsigned wrappable counter."
   ::= {pr1646v2Lan3FGVlanMCH24PEntry 251658240}

pr1646v2Lan3FGVlanMCD7P OBJECT-TYPE
   SYNTAX      SEQUENCE OF Pr1646v2Lan3FGVlanMCD7PEntry
   MAX-ACCESS  not-accessible
   STATUS      current
   DESCRIPTION
      ""
   ::= {pr1646v2Lan3FGVlan 41680896}

pr1646v2Lan3FGVlanMCD7PEntry OBJECT-TYPE
   SYNTAX      Pr1646v2Lan3FGVlanMCD7PEntry
   MAX-ACCESS  not-accessible
   STATUS      current
   DESCRIPTION
      ""
   INDEX      { pr1646v2Lan3FGVlanTableIx,
                pr1646v2Lan3FGVlanMCD7PTableIx }
   ::= {pr1646v2Lan3FGVlanMCD7P 1}

Pr1646v2Lan3FGVlanMCD7PEntry ::=
   SEQUENCE
      {
      pr1646v2Lan3FGVlanMCD7PTableIx
         TableIndex,
      pr1646v2Lan3FGVlanMCD7PSysUpTime
         TimeTicks,
      pr1646v2Lan3FGVlanMCD7PIfUpTime
         TimeTicks,
      pr1646v2Lan3FGVlanMCD7PIfStatChanges
         Counter32,
      pr1646v2Lan3FGVlanMCD7PIfInOctets
         Counter64,
      pr1646v2Lan3FGVlanMCD7PIfInUCPkts
         Counter64,
      pr1646v2Lan3FGVlanMCD7PIfInNUCPkts
         Counter64,
      pr1646v2Lan3FGVlanMCD7PIfInBCPkts
         Counter64,
      pr1646v2Lan3FGVlanMCD7PIfInMCPkts
         Counter64,
      pr1646v2Lan3FGVlanMCD7PIfInDiscards
         Counter64,
      pr1646v2Lan3FGVlanMCD7PIfInErrors
         Counter64,
      pr1646v2Lan3FGVlanMCD7PIfInUnkwn
         Counter64,
      pr1646v2Lan3FGVlanMCD7PInDropEx
         Counter64,
      pr1646v2Lan3FGVlanMCD7PInDropNoMac
         Counter64,
      pr1646v2Lan3FGVlanMCD7PInDropNUCast
         Counter64,
      pr1646v2Lan3FGVlanMCD7PInDropFilter
         Counter64,
      pr1646v2Lan3FGVlanMCD7PIfInBandwidth
         Integer32,
      pr1646v2Lan3FGVlanMCD7PIfOutOctets
         Counter64,
      pr1646v2Lan3FGVlanMCD7PIfOutUCPkts
         Counter64,
      pr1646v2Lan3FGVlanMCD7PIfOutNUCPkts
         Counter64,
      pr1646v2Lan3FGVlanMCD7PIfOutBCPkts
         Counter64,
      pr1646v2Lan3FGVlanMCD7PIfOutMCPkts
         Counter64,
      pr1646v2Lan3FGVlanMCD7PIfOutDiscards
         Counter64,
      pr1646v2Lan3FGVlanMCD7PIfOutErrors
         Counter64,
      pr1646v2Lan3FGVlanMCD7POutDropEx
         Counter64,
      pr1646v2Lan3FGVlanMCD7POutDropNoArp
         Counter64,
      pr1646v2Lan3FGVlanMCD7POutDropFilter
         Counter64,
      pr1646v2Lan3FGVlanMCD7PIfOutBandwidth
         Integer32,
      pr1646v2Lan3FGVlanMCD7PIfErrSec
         Counter32
      }

pr1646v2Lan3FGVlanMCD7PTableIx OBJECT-TYPE
   SYNTAX      TableIndex
   MAX-ACCESS  not-accessible
   STATUS      current
   DESCRIPTION
      ""
   ::= {pr1646v2Lan3FGVlanMCD7PEntry 11}

pr1646v2Lan3FGVlanMCD7PSysUpTime OBJECT-TYPE
   SYNTAX      TimeTicks
   MAX-ACCESS  read-only
   STATUS      current
   DESCRIPTION
      "Path: ethernet3.performance.vlan.mibCounters.d7Performance.sysUpTime

       Time in centi-second."
   ::= {pr1646v2Lan3FGVlanMCD7PEntry 16777216}

pr1646v2Lan3FGVlanMCD7PIfUpTime OBJECT-TYPE
   SYNTAX      TimeTicks
   MAX-ACCESS  read-only
   STATUS      current
   DESCRIPTION
      "Path: ethernet3.performance.vlan.mibCounters.d7Performance.ifUpTime

       Time in centi-second."
   ::= {pr1646v2Lan3FGVlanMCD7PEntry 33554432}

pr1646v2Lan3FGVlanMCD7PIfStatChanges OBJECT-TYPE
   SYNTAX      Counter32
   MAX-ACCESS  read-only
   STATUS      current
   DESCRIPTION
      "Path: ethernet3.performance.vlan.mibCounters.d7Performance.ifStatusChanges

       32 bit unsigned wrappable counter."
   ::= {pr1646v2Lan3FGVlanMCD7PEntry 50331648}

pr1646v2Lan3FGVlanMCD7PIfInOctets OBJECT-TYPE
   SYNTAX      Counter64
   MAX-ACCESS  read-only
   STATUS      current
   DESCRIPTION
      "Path: ethernet3.performance.vlan.mibCounters.d7Performance.ifInOctets

       64 bit unsigned wrappable counter."
   ::= {pr1646v2Lan3FGVlanMCD7PEntry 67108864}

pr1646v2Lan3FGVlanMCD7PIfInUCPkts OBJECT-TYPE
   SYNTAX      Counter64
   MAX-ACCESS  read-only
   STATUS      current
   DESCRIPTION
      "Path: ethernet3.performance.vlan.mibCounters.d7Performance.ifInUcastPkts

       64 bit unsigned wrappable counter."
   ::= {pr1646v2Lan3FGVlanMCD7PEntry 83886080}

pr1646v2Lan3FGVlanMCD7PIfInNUCPkts OBJECT-TYPE
   SYNTAX      Counter64
   MAX-ACCESS  read-only
   STATUS      current
   DESCRIPTION
      "Path: ethernet3.performance.vlan.mibCounters.d7Performance.ifInNUcastPkts

       64 bit unsigned wrappable counter."
   ::= {pr1646v2Lan3FGVlanMCD7PEntry 100663296}

pr1646v2Lan3FGVlanMCD7PIfInBCPkts OBJECT-TYPE
   SYNTAX      Counter64
   MAX-ACCESS  read-only
   STATUS      current
   DESCRIPTION
      "Path: ethernet3.performance.vlan.mibCounters.d7Performance.ifInBcastPkts

       64 bit unsigned wrappable counter."
   ::= {pr1646v2Lan3FGVlanMCD7PEntry 419430400}

pr1646v2Lan3FGVlanMCD7PIfInMCPkts OBJECT-TYPE
   SYNTAX      Counter64
   MAX-ACCESS  read-only
   STATUS      current
   DESCRIPTION
      "Path: ethernet3.performance.vlan.mibCounters.d7Performance.ifInMcastPkts

       64 bit unsigned wrappable counter."
   ::= {pr1646v2Lan3FGVlanMCD7PEntry 436207616}

pr1646v2Lan3FGVlanMCD7PIfInDiscards OBJECT-TYPE
   SYNTAX      Counter64
   MAX-ACCESS  read-only
   STATUS      current
   DESCRIPTION
      "Path: ethernet3.performance.vlan.mibCounters.d7Performance.ifInDiscards

       64 bit unsigned wrappable counter."
   ::= {pr1646v2Lan3FGVlanMCD7PEntry 117440512}

pr1646v2Lan3FGVlanMCD7PIfInErrors OBJECT-TYPE
   SYNTAX      Counter64
   MAX-ACCESS  read-only
   STATUS      current
   DESCRIPTION
      "Path: ethernet3.performance.vlan.mibCounters.d7Performance.ifInErrors

       64 bit unsigned wrappable counter."
   ::= {pr1646v2Lan3FGVlanMCD7PEntry 134217728}

pr1646v2Lan3FGVlanMCD7PIfInUnkwn OBJECT-TYPE
   SYNTAX      Counter64
   MAX-ACCESS  read-only
   STATUS      current
   DESCRIPTION
      "Path: ethernet3.performance.vlan.mibCounters.d7Performance.ifInUnknownProtos

       64 bit unsigned wrappable counter."
   ::= {pr1646v2Lan3FGVlanMCD7PEntry 150994944}

pr1646v2Lan3FGVlanMCD7PInDropEx OBJECT-TYPE
   SYNTAX      Counter64
   MAX-ACCESS  read-only
   STATUS      current
   DESCRIPTION
      "Path: ethernet3.performance.vlan.mibCounters.d7Performance.ifInDropLevelExceeded

       64 bit unsigned wrappable counter."
   ::= {pr1646v2Lan3FGVlanMCD7PEntry 335544320}

pr1646v2Lan3FGVlanMCD7PInDropNoMac OBJECT-TYPE
   SYNTAX      Counter64
   MAX-ACCESS  read-only
   STATUS      current
   DESCRIPTION
      "Path: ethernet3.performance.vlan.mibCounters.d7Performance.fInDiscardsNoMacFit

       64 bit unsigned wrappable counter."
   ::= {pr1646v2Lan3FGVlanMCD7PEntry 301989888}

pr1646v2Lan3FGVlanMCD7PInDropNUCast OBJECT-TYPE
   SYNTAX      Counter64
   MAX-ACCESS  read-only
   STATUS      current
   DESCRIPTION
      "Path: ethernet3.performance.vlan.mibCounters.d7Performance.fInDiscardsNUCast

       64 bit unsigned wrappable counter."
   ::= {pr1646v2Lan3FGVlanMCD7PEntry 318767104}

pr1646v2Lan3FGVlanMCD7PInDropFilter OBJECT-TYPE
   SYNTAX      Counter64
   MAX-ACCESS  read-only
   STATUS      current
   DESCRIPTION
      "Path: ethernet3.performance.vlan.mibCounters.d7Performance.fInDiscardsFilter

       64 bit unsigned wrappable counter."
   ::= {pr1646v2Lan3FGVlanMCD7PEntry 385875968}

pr1646v2Lan3FGVlanMCD7PIfInBandwidth OBJECT-TYPE
   SYNTAX      Integer32
   MAX-ACCESS  read-only
   STATUS      current
   DESCRIPTION
      "Path: ethernet3.performance.vlan.mibCounters.d7Performance.ifInBandwidth

       unit name = bps
       formula = 8 * ; 8 /"
   ::= {pr1646v2Lan3FGVlanMCD7PEntry 268435456}

pr1646v2Lan3FGVlanMCD7PIfOutOctets OBJECT-TYPE
   SYNTAX      Counter64
   MAX-ACCESS  read-only
   STATUS      current
   DESCRIPTION
      "Path: ethernet3.performance.vlan.mibCounters.d7Performance.ifOutOctets

       64 bit unsigned wrappable counter."
   ::= {pr1646v2Lan3FGVlanMCD7PEntry 167772160}

pr1646v2Lan3FGVlanMCD7PIfOutUCPkts OBJECT-TYPE
   SYNTAX      Counter64
   MAX-ACCESS  read-only
   STATUS      current
   DESCRIPTION
      "Path: ethernet3.performance.vlan.mibCounters.d7Performance.ifOutUcastPkts

       64 bit unsigned wrappable counter."
   ::= {pr1646v2Lan3FGVlanMCD7PEntry 184549376}

pr1646v2Lan3FGVlanMCD7PIfOutNUCPkts OBJECT-TYPE
   SYNTAX      Counter64
   MAX-ACCESS  read-only
   STATUS      current
   DESCRIPTION
      "Path: ethernet3.performance.vlan.mibCounters.d7Performance.ifOutNUcastPkts

       64 bit unsigned wrappable counter."
   ::= {pr1646v2Lan3FGVlanMCD7PEntry 201326592}

pr1646v2Lan3FGVlanMCD7PIfOutBCPkts OBJECT-TYPE
   SYNTAX      Counter64
   MAX-ACCESS  read-only
   STATUS      current
   DESCRIPTION
      "Path: ethernet3.performance.vlan.mibCounters.d7Performance.ifOutBcastPkts

       64 bit unsigned wrappable counter."
   ::= {pr1646v2Lan3FGVlanMCD7PEntry 452984832}

pr1646v2Lan3FGVlanMCD7PIfOutMCPkts OBJECT-TYPE
   SYNTAX      Counter64
   MAX-ACCESS  read-only
   STATUS      current
   DESCRIPTION
      "Path: ethernet3.performance.vlan.mibCounters.d7Performance.ifOutMcastPkts

       64 bit unsigned wrappable counter."
   ::= {pr1646v2Lan3FGVlanMCD7PEntry 469762048}

pr1646v2Lan3FGVlanMCD7PIfOutDiscards OBJECT-TYPE
   SYNTAX      Counter64
   MAX-ACCESS  read-only
   STATUS      current
   DESCRIPTION
      "Path: ethernet3.performance.vlan.mibCounters.d7Performance.ifOutDiscards

       64 bit unsigned wrappable counter."
   ::= {pr1646v2Lan3FGVlanMCD7PEntry 218103808}

pr1646v2Lan3FGVlanMCD7PIfOutErrors OBJECT-TYPE
   SYNTAX      Counter64
   MAX-ACCESS  read-only
   STATUS      current
   DESCRIPTION
      "Path: ethernet3.performance.vlan.mibCounters.d7Performance.ifOutErrors

       64 bit unsigned wrappable counter."
   ::= {pr1646v2Lan3FGVlanMCD7PEntry 234881024}

pr1646v2Lan3FGVlanMCD7POutDropEx OBJECT-TYPE
   SYNTAX      Counter64
   MAX-ACCESS  read-only
   STATUS      current
   DESCRIPTION
      "Path: ethernet3.performance.vlan.mibCounters.d7Performance.ifOutDropLevelExceeded

       64 bit unsigned wrappable counter."
   ::= {pr1646v2Lan3FGVlanMCD7PEntry 352321536}

pr1646v2Lan3FGVlanMCD7POutDropNoArp OBJECT-TYPE
   SYNTAX      Counter64
   MAX-ACCESS  read-only
   STATUS      current
   DESCRIPTION
      "Path: ethernet3.performance.vlan.mibCounters.d7Performance.ifOutDiscardsNoArp

       64 bit unsigned wrappable counter."
   ::= {pr1646v2Lan3FGVlanMCD7PEntry 369098752}

pr1646v2Lan3FGVlanMCD7POutDropFilter OBJECT-TYPE
   SYNTAX      Counter64
   MAX-ACCESS  read-only
   STATUS      current
   DESCRIPTION
      "Path: ethernet3.performance.vlan.mibCounters.d7Performance.ifOutDiscardsFilter

       64 bit unsigned wrappable counter."
   ::= {pr1646v2Lan3FGVlanMCD7PEntry 402653184}

pr1646v2Lan3FGVlanMCD7PIfOutBandwidth OBJECT-TYPE
   SYNTAX      Integer32
   MAX-ACCESS  read-only
   STATUS      current
   DESCRIPTION
      "Path: ethernet3.performance.vlan.mibCounters.d7Performance.ifOutBandwidth

       unit name = bps
       formula = 8 * ; 8 /"
   ::= {pr1646v2Lan3FGVlanMCD7PEntry 285212672}

pr1646v2Lan3FGVlanMCD7PIfErrSec OBJECT-TYPE
   SYNTAX      Counter32
   MAX-ACCESS  read-only
   STATUS      current
   DESCRIPTION
      "Path: ethernet3.performance.vlan.mibCounters.d7Performance.ifErrSec

       32 bit unsigned wrappable counter."
   ::= {pr1646v2Lan3FGVlanMCD7PEntry 251658240}

pr1646v2Lan3FGVlanInPQs OBJECT-TYPE
   SYNTAX      SEQUENCE OF Pr1646v2Lan3FGVlanInPQsEntry
   MAX-ACCESS  not-accessible
   STATUS      current
   DESCRIPTION
      ""
   ::= {pr1646v2Lan3FGVlan 100663296}

pr1646v2Lan3FGVlanInPQsEntry OBJECT-TYPE
   SYNTAX      Pr1646v2Lan3FGVlanInPQsEntry
   MAX-ACCESS  not-accessible
   STATUS      current
   DESCRIPTION
      ""
   INDEX      { pr1646v2Lan3FGVlanTableIx,
                pr1646v2Lan3FGVlanInPQsTableIx }
   ::= {pr1646v2Lan3FGVlanInPQs 1}

Pr1646v2Lan3FGVlanInPQsEntry ::=
   SEQUENCE
      {
      pr1646v2Lan3FGVlanInPQsTableIx
         TableIndex,
      pr1646v2Lan3FGVlanInPQsName
         INTEGER,
      pr1646v2Lan3FGVlanInPQsLength
         Integer32,
      pr1646v2Lan3FGVlanInPQsOctetLength
         Integer32,
      pr1646v2Lan3FGVlanInPQsRedLength
         Integer32,
      pr1646v2Lan3FGVlanInPQsPacketsTotal
         Counter64,
      pr1646v2Lan3FGVlanInPQsPacketsDirectTx
         Counter64,
      pr1646v2Lan3FGVlanInPQsPacketsQueued
         Counter64,
      pr1646v2Lan3FGVlanInPQsPacketsDropped
         Counter64,
      pr1646v2Lan3FGVlanInPQsPacketsRedDropped
         Counter64,
      pr1646v2Lan3FGVlanInPQsPacketsCirTx
         Counter64,
      pr1646v2Lan3FGVlanInPQsPacketsEirTx
         Counter64,
      pr1646v2Lan3FGVlanInPQsPacketsViolateTx
         Counter64,
      pr1646v2Lan3FGVlanInPQsOctetsTotal
         Counter64,
      pr1646v2Lan3FGVlanInPQsOctetsDirectTx
         Counter64,
      pr1646v2Lan3FGVlanInPQsOctetsQueued
         Counter64,
      pr1646v2Lan3FGVlanInPQsOctetsDropped
         Counter64,
      pr1646v2Lan3FGVlanInPQsOctetsRedDropped
         Counter64,
      pr1646v2Lan3FGVlanInPQsOctetsCirTx
         Counter64,
      pr1646v2Lan3FGVlanInPQsOctetsEirTx
         Counter64,
      pr1646v2Lan3FGVlanInPQsOctetsViolateTx
         Counter64,
      pr1646v2Lan3FGVlanInPQsOctetsBandwidth15sec
         Integer32,
      pr1646v2Lan3FGVlanInPQsOctetsBandwidth30sec
         Integer32,
      pr1646v2Lan3FGVlanInPQsOctetsBandwidth1min
         Integer32,
      pr1646v2Lan3FGVlanInPQsOctetsBandwidth2min
         Integer32,
      pr1646v2Lan3FGVlanInPQsOctetsBandwidth5min
         Integer32
      }

pr1646v2Lan3FGVlanInPQsTableIx OBJECT-TYPE
   SYNTAX      TableIndex
   MAX-ACCESS  not-accessible
   STATUS      current
   DESCRIPTION
      ""
   ::= {pr1646v2Lan3FGVlanInPQsEntry 11}

pr1646v2Lan3FGVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2Lan3FGVlanInPQsEntry 16777216}

pr1646v2Lan3FGVlanInPQsLength OBJECT-TYPE
   SYNTAX      Integer32
   MAX-ACCESS  read-only
   STATUS      current
   DESCRIPTION
      "Path: ethernet3.performance.vlan.inPriorityQueues.length"
   ::= {pr1646v2Lan3FGVlanInPQsEntry 33554432}

pr1646v2Lan3FGVlanInPQsOctetLength OBJECT-TYPE
   SYNTAX      Integer32
   MAX-ACCESS  read-only
   STATUS      current
   DESCRIPTION
      "Path: ethernet3.performance.vlan.inPriorityQueues.octetLength"
   ::= {pr1646v2Lan3FGVlanInPQsEntry 150994944}

pr1646v2Lan3FGVlanInPQsRedLength OBJECT-TYPE
   SYNTAX      Integer32
   MAX-ACCESS  read-only
   STATUS      current
   DESCRIPTION
      "Path: ethernet3.performance.vlan.inPriorityQueues.redLength"
   ::= {pr1646v2Lan3FGVlanInPQsEntry 134217728}

pr1646v2Lan3FGVlanInPQsPacketsTotal OBJECT-TYPE
   SYNTAX      Counter64
   MAX-ACCESS  read-only
   STATUS      current
   DESCRIPTION
      "Path: ethernet3.performance.vlan.inPriorityQueues.packets.total

       64 bit unsigned wrappable counter."
   ::= {pr1646v2Lan3FGVlanInPQsEntry 50790400}

pr1646v2Lan3FGVlanInPQsPacketsDirectTx OBJECT-TYPE
   SYNTAX      Counter64
   MAX-ACCESS  read-only
   STATUS      current
   DESCRIPTION
      "Path: ethernet3.performance.vlan.inPriorityQueues.packets.directTx

       64 bit unsigned wrappable counter."
   ::= {pr1646v2Lan3FGVlanInPQsEntry 50397184}

pr1646v2Lan3FGVlanInPQsPacketsQueued OBJECT-TYPE
   SYNTAX      Counter64
   MAX-ACCESS  read-only
   STATUS      current
   DESCRIPTION
      "Path: ethernet3.performance.vlan.inPriorityQueues.packets.queued

       64 bit unsigned wrappable counter."
   ::= {pr1646v2Lan3FGVlanInPQsEntry 50462720}

pr1646v2Lan3FGVlanInPQsPacketsDropped OBJECT-TYPE
   SYNTAX      Counter64
   MAX-ACCESS  read-only
   STATUS      current
   DESCRIPTION
      "Path: ethernet3.performance.vlan.inPriorityQueues.packets.dropped

       64 bit unsigned wrappable counter."
   ::= {pr1646v2Lan3FGVlanInPQsEntry 50528256}

pr1646v2Lan3FGVlanInPQsPacketsRedDropped OBJECT-TYPE
   SYNTAX      Counter64
   MAX-ACCESS  read-only
   STATUS      current
   DESCRIPTION
      "Path: ethernet3.performance.vlan.inPriorityQueues.packets.redDropped

       64 bit unsigned wrappable counter."
   ::= {pr1646v2Lan3FGVlanInPQsEntry 50724864}

pr1646v2Lan3FGVlanInPQsPacketsCirTx OBJECT-TYPE
   SYNTAX      Counter64
   MAX-ACCESS  read-only
   STATUS      current
   DESCRIPTION
      "Path: ethernet3.performance.vlan.inPriorityQueues.packets.cirTx

       64 bit unsigned wrappable counter."
   ::= {pr1646v2Lan3FGVlanInPQsEntry 50593792}

pr1646v2Lan3FGVlanInPQsPacketsEirTx OBJECT-TYPE
   SYNTAX      Counter64
   MAX-ACCESS  read-only
   STATUS      current
   DESCRIPTION
      "Path: ethernet3.performance.vlan.inPriorityQueues.packets.eirTx

       64 bit unsigned wrappable counter."
   ::= {pr1646v2Lan3FGVlanInPQsEntry 50659328}

pr1646v2Lan3FGVlanInPQsPacketsViolateTx OBJECT-TYPE
   SYNTAX      Counter64
   MAX-ACCESS  read-only
   STATUS      current
   DESCRIPTION
      "Path: ethernet3.performance.vlan.inPriorityQueues.packets.violateTx

       64 bit unsigned wrappable counter."
   ::= {pr1646v2Lan3FGVlanInPQsEntry 50855936}

pr1646v2Lan3FGVlanInPQsOctetsTotal OBJECT-TYPE
   SYNTAX      Counter64
   MAX-ACCESS  read-only
   STATUS      current
   DESCRIPTION
      "Path: ethernet3.performance.vlan.inPriorityQueues.octets.total

       64 bit unsigned wrappable counter."
   ::= {pr1646v2Lan3FGVlanInPQsEntry 67567616}

pr1646v2Lan3FGVlanInPQsOctetsDirectTx OBJECT-TYPE
   SYNTAX      Counter64
   MAX-ACCESS  read-only
   STATUS      current
   DESCRIPTION
      "Path: ethernet3.performance.vlan.inPriorityQueues.octets.directTx

       64 bit unsigned wrappable counter."
   ::= {pr1646v2Lan3FGVlanInPQsEntry 67174400}

pr1646v2Lan3FGVlanInPQsOctetsQueued OBJECT-TYPE
   SYNTAX      Counter64
   MAX-ACCESS  read-only
   STATUS      current
   DESCRIPTION
      "Path: ethernet3.performance.vlan.inPriorityQueues.octets.queued

       64 bit unsigned wrappable counter."
   ::= {pr1646v2Lan3FGVlanInPQsEntry 67239936}

pr1646v2Lan3FGVlanInPQsOctetsDropped OBJECT-TYPE
   SYNTAX      Counter64
   MAX-ACCESS  read-only
   STATUS      current
   DESCRIPTION
      "Path: ethernet3.performance.vlan.inPriorityQueues.octets.dropped

       64 bit unsigned wrappable counter."
   ::= {pr1646v2Lan3FGVlanInPQsEntry 67305472}

pr1646v2Lan3FGVlanInPQsOctetsRedDropped OBJECT-TYPE
   SYNTAX      Counter64
   MAX-ACCESS  read-only
   STATUS      current
   DESCRIPTION
      "Path: ethernet3.performance.vlan.inPriorityQueues.octets.redDropped

       64 bit unsigned wrappable counter."
   ::= {pr1646v2Lan3FGVlanInPQsEntry 67502080}

pr1646v2Lan3FGVlanInPQsOctetsCirTx OBJECT-TYPE
   SYNTAX      Counter64
   MAX-ACCESS  read-only
   STATUS      current
   DESCRIPTION
      "Path: ethernet3.performance.vlan.inPriorityQueues.octets.cirTx

       64 bit unsigned wrappable counter."
   ::= {pr1646v2Lan3FGVlanInPQsEntry 67371008}

pr1646v2Lan3FGVlanInPQsOctetsEirTx OBJECT-TYPE
   SYNTAX      Counter64
   MAX-ACCESS  read-only
   STATUS      current
   DESCRIPTION
      "Path: ethernet3.performance.vlan.inPriorityQueues.octets.eirTx

       64 bit unsigned wrappable counter."
   ::= {pr1646v2Lan3FGVlanInPQsEntry 67436544}

pr1646v2Lan3FGVlanInPQsOctetsViolateTx OBJECT-TYPE
   SYNTAX      Counter64
   MAX-ACCESS  read-only
   STATUS      current
   DESCRIPTION
      "Path: ethernet3.performance.vlan.inPriorityQueues.octets.violateTx

       64 bit unsigned wrappable counter."
   ::= {pr1646v2Lan3FGVlanInPQsEntry 67633152}

pr1646v2Lan3FGVlanInPQsOctetsBandwidth15sec OBJECT-TYPE
   SYNTAX      Integer32
   MAX-ACCESS  read-only
   STATUS      current
   DESCRIPTION
      "Path: ethernet3.performance.vlan.inPriorityQueues.octets.bandwidth.15sec

       unit name = bps
       formula = 8 * ; 8 /"
   ::= {pr1646v2Lan3FGVlanInPQsEntry 70386944}

pr1646v2Lan3FGVlanInPQsOctetsBandwidth30sec OBJECT-TYPE
   SYNTAX      Integer32
   MAX-ACCESS  read-only
   STATUS      current
   DESCRIPTION
      "Path: ethernet3.performance.vlan.inPriorityQueues.octets.bandwidth.30sec

       unit name = bps
       formula = 8 * ; 8 /"
   ::= {pr1646v2Lan3FGVlanInPQsEntry 70388224}

pr1646v2Lan3FGVlanInPQsOctetsBandwidth1min OBJECT-TYPE
   SYNTAX      Integer32
   MAX-ACCESS  read-only
   STATUS      current
   DESCRIPTION
      "Path: ethernet3.performance.vlan.inPriorityQueues.octets.bandwidth.1min

       unit name = bps
       formula = 8 * ; 8 /"
   ::= {pr1646v2Lan3FGVlanInPQsEntry 70390784}

pr1646v2Lan3FGVlanInPQsOctetsBandwidth2min OBJECT-TYPE
   SYNTAX      Integer32
   MAX-ACCESS  read-only
   STATUS      current
   DESCRIPTION
      "Path: ethernet3.performance.vlan.inPriorityQueues.octets.bandwidth.2min

       unit name = bps
       formula = 8 * ; 8 /"
   ::= {pr1646v2Lan3FGVlanInPQsEntry 70395904}

pr1646v2Lan3FGVlanInPQsOctetsBandwidth5min OBJECT-TYPE
   SYNTAX      Integer32
   MAX-ACCESS  read-only
   STATUS      current
   DESCRIPTION
      "Path: ethernet3.performance.vlan.inPriorityQueues.octets.bandwidth.5min

       unit name = bps
       formula = 8 * ; 8 /"
   ::= {pr1646v2Lan3FGVlanInPQsEntry 70411264}

pr1646v2Lan3FGVlanInPQsH2Performance OBJECT-TYPE
   SYNTAX      SEQUENCE OF Pr1646v2Lan3FGVlanInPQsH2PerformanceEntry
   MAX-ACCESS  not-accessible
   STATUS      current
   DESCRIPTION
      ""
   ::= {pr1646v2Lan3FGVlan 100990976}

pr1646v2Lan3FGVlanInPQsH2PerformanceEntry OBJECT-TYPE
   SYNTAX      Pr1646v2Lan3FGVlanInPQsH2PerformanceEntry
   MAX-ACCESS  not-accessible
   STATUS      current
   DESCRIPTION
      ""
   INDEX      { pr1646v2Lan3FGVlanTableIx,
                pr1646v2Lan3FGVlanInPQsTableIx,
                pr1646v2Lan3FGVlanInPQsH2PerformanceTableIx }
   ::= {pr1646v2Lan3FGVlanInPQsH2Performance 1}

Pr1646v2Lan3FGVlanInPQsH2PerformanceEntry ::=
   SEQUENCE
      {
      pr1646v2Lan3FGVlanInPQsH2PerformanceTableIx
         TableIndex,
      pr1646v2Lan3FGVlanInPQsH2PerformanceSysUpTime
         TimeTicks,
      pr1646v2Lan3FGVlanInPQsH2PerformanceTotPkts
         Counter64,
      pr1646v2Lan3FGVlanInPQsH2PerformanceDirTxPkts
         Counter64,
      pr1646v2Lan3FGVlanInPQsH2PerformanceQdPkts
         Counter64,
      pr1646v2Lan3FGVlanInPQsH2PerformanceDropPkts
         Counter64,
      pr1646v2Lan3FGVlanInPQsH2PerformanceRDropPkts
         Counter64,
      pr1646v2Lan3FGVlanInPQsH2PerformanceCirTxPkts
         Counter64,
      pr1646v2Lan3FGVlanInPQsH2PerformanceEirTxPkts
         Counter64,
      pr1646v2Lan3FGVlanInPQsH2PerformanceViolTxPkts
         Counter64,
      pr1646v2Lan3FGVlanInPQsH2PerformanceTotOcts
         Counter64,
      pr1646v2Lan3FGVlanInPQsH2PerformanceDirTxOcts
         Counter64,
      pr1646v2Lan3FGVlanInPQsH2PerformanceQdOcts
         Counter64,
      pr1646v2Lan3FGVlanInPQsH2PerformanceDropOcts
         Counter64,
      pr1646v2Lan3FGVlanInPQsH2PerformanceRDropOcts
         Counter64,
      pr1646v2Lan3FGVlanInPQsH2PerformanceCirTxOcts
         Counter64,
      pr1646v2Lan3FGVlanInPQsH2PerformanceEirTxOcts
         Counter64,
      pr1646v2Lan3FGVlanInPQsH2PerformanceViolTxOcts
         Counter64,
      pr1646v2Lan3FGVlanInPQsH2PerformanceBandwidth
         Integer32
      }

pr1646v2Lan3FGVlanInPQsH2PerformanceTableIx OBJECT-TYPE
   SYNTAX      TableIndex
   MAX-ACCESS  not-accessible
   STATUS      current
   DESCRIPTION
      ""
   ::= {pr1646v2Lan3FGVlanInPQsH2PerformanceEntry 11}

pr1646v2Lan3FGVlanInPQsH2PerformanceSysUpTime OBJECT-TYPE
   SYNTAX      TimeTicks
   MAX-ACCESS  read-only
   STATUS      current
   DESCRIPTION
      "Path: ethernet3.performance.vlan.inPriorityQueues.h2Performance.sysUpTime

       Time in centi-second."
   ::= {pr1646v2Lan3FGVlanInPQsH2PerformanceEntry 16777216}

pr1646v2Lan3FGVlanInPQsH2PerformanceTotPkts OBJECT-TYPE
   SYNTAX      Counter64
   MAX-ACCESS  read-only
   STATUS      current
   DESCRIPTION
      "Path: ethernet3.performance.vlan.inPriorityQueues.h2Performance.totalPkts

       64 bit unsigned wrappable counter."
   ::= {pr1646v2Lan3FGVlanInPQsH2PerformanceEntry 234881024}

pr1646v2Lan3FGVlanInPQsH2PerformanceDirTxPkts OBJECT-TYPE
   SYNTAX      Counter64
   MAX-ACCESS  read-only
   STATUS      current
   DESCRIPTION
      "Path: ethernet3.performance.vlan.inPriorityQueues.h2Performance.directTxPkts

       64 bit unsigned wrappable counter."
   ::= {pr1646v2Lan3FGVlanInPQsH2PerformanceEntry 33554432}

pr1646v2Lan3FGVlanInPQsH2PerformanceQdPkts OBJECT-TYPE
   SYNTAX      Counter64
   MAX-ACCESS  read-only
   STATUS      current
   DESCRIPTION
      "Path: ethernet3.performance.vlan.inPriorityQueues.h2Performance.queuedPkts

       64 bit unsigned wrappable counter."
   ::= {pr1646v2Lan3FGVlanInPQsH2PerformanceEntry 50331648}

pr1646v2Lan3FGVlanInPQsH2PerformanceDropPkts OBJECT-TYPE
   SYNTAX      Counter64
   MAX-ACCESS  read-only
   STATUS      current
   DESCRIPTION
      "Path: ethernet3.performance.vlan.inPriorityQueues.h2Performance.droppedPkts

       64 bit unsigned wrappable counter."
   ::= {pr1646v2Lan3FGVlanInPQsH2PerformanceEntry 67108864}

pr1646v2Lan3FGVlanInPQsH2PerformanceRDropPkts OBJECT-TYPE
   SYNTAX      Counter64
   MAX-ACCESS  read-only
   STATUS      current
   DESCRIPTION
      "Path: ethernet3.performance.vlan.inPriorityQueues.h2Performance.redDroppedPkts

       64 bit unsigned wrappable counter."
   ::= {pr1646v2Lan3FGVlanInPQsH2PerformanceEntry 201326592}

pr1646v2Lan3FGVlanInPQsH2PerformanceCirTxPkts OBJECT-TYPE
   SYNTAX      Counter64
   MAX-ACCESS  read-only
   STATUS      current
   DESCRIPTION
      "Path: ethernet3.performance.vlan.inPriorityQueues.h2Performance.cirTxPkts

       64 bit unsigned wrappable counter."
   ::= {pr1646v2Lan3FGVlanInPQsH2PerformanceEntry 83886080}

pr1646v2Lan3FGVlanInPQsH2PerformanceEirTxPkts OBJECT-TYPE
   SYNTAX      Counter64
   MAX-ACCESS  read-only
   STATUS      current
   DESCRIPTION
      "Path: ethernet3.performance.vlan.inPriorityQueues.h2Performance.eirTxPkts

       64 bit unsigned wrappable counter."
   ::= {pr1646v2Lan3FGVlanInPQsH2PerformanceEntry 100663296}

pr1646v2Lan3FGVlanInPQsH2PerformanceViolTxPkts OBJECT-TYPE
   SYNTAX      Counter64
   MAX-ACCESS  read-only
   STATUS      current
   DESCRIPTION
      "Path: ethernet3.performance.vlan.inPriorityQueues.h2Performance.violateTxPkts

       64 bit unsigned wrappable counter."
   ::= {pr1646v2Lan3FGVlanInPQsH2PerformanceEntry 301989888}

pr1646v2Lan3FGVlanInPQsH2PerformanceTotOcts OBJECT-TYPE
   SYNTAX      Counter64
   MAX-ACCESS  read-only
   STATUS      current
   DESCRIPTION
      "Path: ethernet3.performance.vlan.inPriorityQueues.h2Performance.totalOctets

       64 bit unsigned wrappable counter."
   ::= {pr1646v2Lan3FGVlanInPQsH2PerformanceEntry 251658240}

pr1646v2Lan3FGVlanInPQsH2PerformanceDirTxOcts OBJECT-TYPE
   SYNTAX      Counter64
   MAX-ACCESS  read-only
   STATUS      current
   DESCRIPTION
      "Path: ethernet3.performance.vlan.inPriorityQueues.h2Performance.directTxOctets

       64 bit unsigned wrappable counter."
   ::= {pr1646v2Lan3FGVlanInPQsH2PerformanceEntry 117440512}

pr1646v2Lan3FGVlanInPQsH2PerformanceQdOcts OBJECT-TYPE
   SYNTAX      Counter64
   MAX-ACCESS  read-only
   STATUS      current
   DESCRIPTION
      "Path: ethernet3.performance.vlan.inPriorityQueues.h2Performance.queuedOctets

       64 bit unsigned wrappable counter."
   ::= {pr1646v2Lan3FGVlanInPQsH2PerformanceEntry 134217728}

pr1646v2Lan3FGVlanInPQsH2PerformanceDropOcts OBJECT-TYPE
   SYNTAX      Counter64
   MAX-ACCESS  read-only
   STATUS      current
   DESCRIPTION
      "Path: ethernet3.performance.vlan.inPriorityQueues.h2Performance.droppedOctets

       64 bit unsigned wrappable counter."
   ::= {pr1646v2Lan3FGVlanInPQsH2PerformanceEntry 150994944}

pr1646v2Lan3FGVlanInPQsH2PerformanceRDropOcts OBJECT-TYPE
   SYNTAX      Counter64
   MAX-ACCESS  read-only
   STATUS      current
   DESCRIPTION
      "Path: ethernet3.performance.vlan.inPriorityQueues.h2Performance.redDroppedOctets

       64 bit unsigned wrappable counter."
   ::= {pr1646v2Lan3FGVlanInPQsH2PerformanceEntry 218103808}

pr1646v2Lan3FGVlanInPQsH2PerformanceCirTxOcts OBJECT-TYPE
   SYNTAX      Counter64
   MAX-ACCESS  read-only
   STATUS      current
   DESCRIPTION
      "Path: ethernet3.performance.vlan.inPriorityQueues.h2Performance.cirTxOctets

       64 bit unsigned wrappable counter."
   ::= {pr1646v2Lan3FGVlanInPQsH2PerformanceEntry 167772160}

pr1646v2Lan3FGVlanInPQsH2PerformanceEirTxOcts OBJECT-TYPE
   SYNTAX      Counter64
   MAX-ACCESS  read-only
   STATUS      current
   DESCRIPTION
      "Path: ethernet3.performance.vlan.inPriorityQueues.h2Performance.eirTxOctets

       64 bit unsigned wrappable counter."
   ::= {pr1646v2Lan3FGVlanInPQsH2PerformanceEntry 184549376}

pr1646v2Lan3FGVlanInPQsH2PerformanceViolTxOcts OBJECT-TYPE
   SYNTAX      Counter64
   MAX-ACCESS  read-only
   STATUS      current
   DESCRIPTION
      "Path: ethernet3.performance.vlan.inPriorityQueues.h2Performance.violateTxOctets

       64 bit unsigned wrappable counter."
   ::= {pr1646v2Lan3FGVlanInPQsH2PerformanceEntry 318767104}

pr1646v2Lan3FGVlanInPQsH2PerformanceBandwidth OBJECT-TYPE
   SYNTAX      Integer32
   MAX-ACCESS  read-only
   STATUS      current
   DESCRIPTION
      "Path: ethernet3.performance.vlan.inPriorityQueues.h2Performance.bandwidth

       unit name = bps
       formula = 8 * ; 8 /"
   ::= {pr1646v2Lan3FGVlanInPQsH2PerformanceEntry 268435456}

pr1646v2Lan3FGVlanInPQsH24Performance OBJECT-TYPE
   SYNTAX      SEQUENCE OF Pr1646v2Lan3FGVlanInPQsH24PerformanceEntry
   MAX-ACCESS  not-accessible
   STATUS      current
   DESCRIPTION
      ""
   ::= {pr1646v2Lan3FGVlan 101056512}

pr1646v2Lan3FGVlanInPQsH24PerformanceEntry OBJECT-TYPE
   SYNTAX      Pr1646v2Lan3FGVlanInPQsH24PerformanceEntry
   MAX-ACCESS  not-accessible
   STATUS      current
   DESCRIPTION
      ""
   INDEX      { pr1646v2Lan3FGVlanTableIx,
                pr1646v2Lan3FGVlanInPQsTableIx,
                pr1646v2Lan3FGVlanInPQsH24PerformanceTableIx }
   ::= {pr1646v2Lan3FGVlanInPQsH24Performance 1}

Pr1646v2Lan3FGVlanInPQsH24PerformanceEntry ::=
   SEQUENCE
      {
      pr1646v2Lan3FGVlanInPQsH24PerformanceTableIx
         TableIndex,
      pr1646v2Lan3FGVlanInPQsH24PerformanceSysUpTime
         TimeTicks,
      pr1646v2Lan3FGVlanInPQsH24PerformanceTotPkts
         Counter64,
      pr1646v2Lan3FGVlanInPQsH24PerformanceDirTxPkts
         Counter64,
      pr1646v2Lan3FGVlanInPQsH24PerformanceQdPkts
         Counter64,
      pr1646v2Lan3FGVlanInPQsH24PerformanceDropPkts
         Counter64,
      pr1646v2Lan3FGVlanInPQsH24PerformanceRDropPkts
         Counter64,
      pr1646v2Lan3FGVlanInPQsH24PerformanceCirTxPkts
         Counter64,
      pr1646v2Lan3FGVlanInPQsH24PerformanceEirTxPkts
         Counter64,
      pr1646v2Lan3FGVlanInPQsH24PerformanceViolTxPkts
         Counter64,
      pr1646v2Lan3FGVlanInPQsH24PerformanceTotOcts
         Counter64,
      pr1646v2Lan3FGVlanInPQsH24PerformanceDirTxOcts
         Counter64,
      pr1646v2Lan3FGVlanInPQsH24PerformanceQdOcts
         Counter64,
      pr1646v2Lan3FGVlanInPQsH24PerformanceDropOcts
         Counter64,
      pr1646v2Lan3FGVlanInPQsH24PerformanceRDropOcts
         Counter64,
      pr1646v2Lan3FGVlanInPQsH24PerformanceCirTxOcts
         Counter64,
      pr1646v2Lan3FGVlanInPQsH24PerformanceEirTxOcts
         Counter64,
      pr1646v2Lan3FGVlanInPQsH24PerformanceViolTxOcts
         Counter64,
      pr1646v2Lan3FGVlanInPQsH24PerformanceBandwidth
         Integer32
      }

pr1646v2Lan3FGVlanInPQsH24PerformanceTableIx OBJECT-TYPE
   SYNTAX      TableIndex
   MAX-ACCESS  not-accessible
   STATUS      current
   DESCRIPTION
      ""
   ::= {pr1646v2Lan3FGVlanInPQsH24PerformanceEntry 11}

pr1646v2Lan3FGVlanInPQsH24PerformanceSysUpTime OBJECT-TYPE
   SYNTAX      TimeTicks
   MAX-ACCESS  read-only
   STATUS      current
   DESCRIPTION
      "Path: ethernet3.performance.vlan.inPriorityQueues.h24Performance.sysUpTime

       Time in centi-second."
   ::= {pr1646v2Lan3FGVlanInPQsH24PerformanceEntry 16777216}

pr1646v2Lan3FGVlanInPQsH24PerformanceTotPkts OBJECT-TYPE
   SYNTAX      Counter64
   MAX-ACCESS  read-only
   STATUS      current
   DESCRIPTION
      "Path: ethernet3.performance.vlan.inPriorityQueues.h24Performance.totalPkts

       64 bit unsigned wrappable counter."
   ::= {pr1646v2Lan3FGVlanInPQsH24PerformanceEntry 234881024}

pr1646v2Lan3FGVlanInPQsH24PerformanceDirTxPkts OBJECT-TYPE
   SYNTAX      Counter64
   MAX-ACCESS  read-only
   STATUS      current
   DESCRIPTION
      "Path: ethernet3.performance.vlan.inPriorityQueues.h24Performance.directTxPkts

       64 bit unsigned wrappable counter."
   ::= {pr1646v2Lan3FGVlanInPQsH24PerformanceEntry 33554432}

pr1646v2Lan3FGVlanInPQsH24PerformanceQdPkts OBJECT-TYPE
   SYNTAX      Counter64
   MAX-ACCESS  read-only
   STATUS      current
   DESCRIPTION
      "Path: ethernet3.performance.vlan.inPriorityQueues.h24Performance.queuedPkts

       64 bit unsigned wrappable counter."
   ::= {pr1646v2Lan3FGVlanInPQsH24PerformanceEntry 50331648}

pr1646v2Lan3FGVlanInPQsH24PerformanceDropPkts OBJECT-TYPE
   SYNTAX      Counter64
   MAX-ACCESS  read-only
   STATUS      current
   DESCRIPTION
      "Path: ethernet3.performance.vlan.inPriorityQueues.h24Performance.droppedPkts

       64 bit unsigned wrappable counter."
   ::= {pr1646v2Lan3FGVlanInPQsH24PerformanceEntry 67108864}

pr1646v2Lan3FGVlanInPQsH24PerformanceRDropPkts OBJECT-TYPE
   SYNTAX      Counter64
   MAX-ACCESS  read-only
   STATUS      current
   DESCRIPTION
      "Path: ethernet3.performance.vlan.inPriorityQueues.h24Performance.redDroppedPkts

       64 bit unsigned wrappable counter."
   ::= {pr1646v2Lan3FGVlanInPQsH24PerformanceEntry 201326592}

pr1646v2Lan3FGVlanInPQsH24PerformanceCirTxPkts OBJECT-TYPE
   SYNTAX      Counter64
   MAX-ACCESS  read-only
   STATUS      current
   DESCRIPTION
      "Path: ethernet3.performance.vlan.inPriorityQueues.h24Performance.cirTxPkts

       64 bit unsigned wrappable counter."
   ::= {pr1646v2Lan3FGVlanInPQsH24PerformanceEntry 83886080}

pr1646v2Lan3FGVlanInPQsH24PerformanceEirTxPkts OBJECT-TYPE
   SYNTAX      Counter64
   MAX-ACCESS  read-only
   STATUS      current
   DESCRIPTION
      "Path: ethernet3.performance.vlan.inPriorityQueues.h24Performance.eirTxPkts

       64 bit unsigned wrappable counter."
   ::= {pr1646v2Lan3FGVlanInPQsH24PerformanceEntry 100663296}

pr1646v2Lan3FGVlanInPQsH24PerformanceViolTxPkts OBJECT-TYPE
   SYNTAX      Counter64
   MAX-ACCESS  read-only
   STATUS      current
   DESCRIPTION
      "Path: ethernet3.performance.vlan.inPriorityQueues.h24Performance.violateTxPkts

       64 bit unsigned wrappable counter."
   ::= {pr1646v2Lan3FGVlanInPQsH24PerformanceEntry 301989888}

pr1646v2Lan3FGVlanInPQsH24PerformanceTotOcts OBJECT-TYPE
   SYNTAX      Counter64
   MAX-ACCESS  read-only
   STATUS      current
   DESCRIPTION
      "Path: ethernet3.performance.vlan.inPriorityQueues.h24Performance.totalOctets

       64 bit unsigned wrappable counter."
   ::= {pr1646v2Lan3FGVlanInPQsH24PerformanceEntry 251658240}

pr1646v2Lan3FGVlanInPQsH24PerformanceDirTxOcts OBJECT-TYPE
   SYNTAX      Counter64
   MAX-ACCESS  read-only
   STATUS      current
   DESCRIPTION
      "Path: ethernet3.performance.vlan.inPriorityQueues.h24Performance.directTxOctets

       64 bit unsigned wrappable counter."
   ::= {pr1646v2Lan3FGVlanInPQsH24PerformanceEntry 117440512}

pr1646v2Lan3FGVlanInPQsH24PerformanceQdOcts OBJECT-TYPE
   SYNTAX      Counter64
   MAX-ACCESS  read-only
   STATUS      current
   DESCRIPTION
      "Path: ethernet3.performance.vlan.inPriorityQueues.h24Performance.queuedOctets

       64 bit unsigned wrappable counter."
   ::= {pr1646v2Lan3FGVlanInPQsH24PerformanceEntry 134217728}

pr1646v2Lan3FGVlanInPQsH24PerformanceDropOcts OBJECT-TYPE
   SYNTAX      Counter64
   MAX-ACCESS  read-only
   STATUS      current
   DESCRIPTION
      "Path: ethernet3.performance.vlan.inPriorityQueues.h24Performance.droppedOctets

       64 bit unsigned wrappable counter."
   ::= {pr1646v2Lan3FGVlanInPQsH24PerformanceEntry 150994944}

pr1646v2Lan3FGVlanInPQsH24PerformanceRDropOcts OBJECT-TYPE
   SYNTAX      Counter64
   MAX-ACCESS  read-only
   STATUS      current
   DESCRIPTION
      "Path: ethernet3.performance.vlan.inPriorityQueues.h24Performance.redDroppedOctets

       64 bit unsigned wrappable counter."
   ::= {pr1646v2Lan3FGVlanInPQsH24PerformanceEntry 218103808}

pr1646v2Lan3FGVlanInPQsH24PerformanceCirTxOcts OBJECT-TYPE
   SYNTAX      Counter64
   MAX-ACCESS  read-only
   STATUS      current
   DESCRIPTION
      "Path: ethernet3.performance.vlan.inPriorityQueues.h24Performance.cirTxOctets

       64 bit unsigned wrappable counter."
   ::= {pr1646v2Lan3FGVlanInPQsH24PerformanceEntry 167772160}

pr1646v2Lan3FGVlanInPQsH24PerformanceEirTxOcts OBJECT-TYPE
   SYNTAX      Counter64
   MAX-ACCESS  read-only
   STATUS      current
   DESCRIPTION
      "Path: ethernet3.performance.vlan.inPriorityQueues.h24Performance.eirTxOctets

       64 bit unsigned wrappable counter."
   ::= {pr1646v2Lan3FGVlanInPQsH24PerformanceEntry 184549376}

pr1646v2Lan3FGVlanInPQsH24PerformanceViolTxOcts OBJECT-TYPE
   SYNTAX      Counter64
   MAX-ACCESS  read-only
   STATUS      current
   DESCRIPTION
      "Path: ethernet3.performance.vlan.inPriorityQueues.h24Performance.violateTxOctets

       64 bit unsigned wrappable counter."
   ::= {pr1646v2Lan3FGVlanInPQsH24PerformanceEntry 318767104}

pr1646v2Lan3FGVlanInPQsH24PerformanceBandwidth OBJECT-TYPE
   SYNTAX      Integer32
   MAX-ACCESS  read-only
   STATUS      current
   DESCRIPTION
      "Path: ethernet3.performance.vlan.inPriorityQueues.h24Performance.bandwidth

       unit name = bps
       formula = 8 * ; 8 /"
   ::= {pr1646v2Lan3FGVlanInPQsH24PerformanceEntry 268435456}

pr1646v2Lan3FGVlanInPQsD7Performance OBJECT-TYPE
   SYNTAX      SEQUENCE OF Pr1646v2Lan3FGVlanInPQsD7PerformanceEntry
   MAX-ACCESS  not-accessible
   STATUS      current
   DESCRIPTION
      ""
   ::= {pr1646v2Lan3FGVlan 101122048}

pr1646v2Lan3FGVlanInPQsD7PerformanceEntry OBJECT-TYPE
   SYNTAX      Pr1646v2Lan3FGVlanInPQsD7PerformanceEntry
   MAX-ACCESS  not-accessible
   STATUS      current
   DESCRIPTION
      ""
   INDEX      { pr1646v2Lan3FGVlanTableIx,
                pr1646v2Lan3FGVlanInPQsTableIx,
                pr1646v2Lan3FGVlanInPQsD7PerformanceTableIx }
   ::= {pr1646v2Lan3FGVlanInPQsD7Performance 1}

Pr1646v2Lan3FGVlanInPQsD7PerformanceEntry ::=
   SEQUENCE
      {
      pr1646v2Lan3FGVlanInPQsD7PerformanceTableIx
         TableIndex,
      pr1646v2Lan3FGVlanInPQsD7PerformanceSysUpTime
         TimeTicks,
      pr1646v2Lan3FGVlanInPQsD7PerformanceTotPkts
         Counter64,
      pr1646v2Lan3FGVlanInPQsD7PerformanceDirTxPkts
         Counter64,
      pr1646v2Lan3FGVlanInPQsD7PerformanceQdPkts
         Counter64,
      pr1646v2Lan3FGVlanInPQsD7PerformanceDropPkts
         Counter64,
      pr1646v2Lan3FGVlanInPQsD7PerformanceRDropPkts
         Counter64,
      pr1646v2Lan3FGVlanInPQsD7PerformanceCirTxPkts
         Counter64,
      pr1646v2Lan3FGVlanInPQsD7PerformanceEirTxPkts
         Counter64,
      pr1646v2Lan3FGVlanInPQsD7PerformanceViolTxPkts
         Counter64,
      pr1646v2Lan3FGVlanInPQsD7PerformanceTotOcts
         Counter64,
      pr1646v2Lan3FGVlanInPQsD7PerformanceDirTxOcts
         Counter64,
      pr1646v2Lan3FGVlanInPQsD7PerformanceQdOcts
         Counter64,
      pr1646v2Lan3FGVlanInPQsD7PerformanceDropOcts
         Counter64,
      pr1646v2Lan3FGVlanInPQsD7PerformanceRDropOcts
         Counter64,
      pr1646v2Lan3FGVlanInPQsD7PerformanceCirTxOcts
         Counter64,
      pr1646v2Lan3FGVlanInPQsD7PerformanceEirTxOcts
         Counter64,
      pr1646v2Lan3FGVlanInPQsD7PerformanceViolTxOcts
         Counter64,
      pr1646v2Lan3FGVlanInPQsD7PerformanceBandwidth
         Integer32
      }

pr1646v2Lan3FGVlanInPQsD7PerformanceTableIx OBJECT-TYPE
   SYNTAX      TableIndex
   MAX-ACCESS  not-accessible
   STATUS      current
   DESCRIPTION
      ""
   ::= {pr1646v2Lan3FGVlanInPQsD7PerformanceEntry 11}

pr1646v2Lan3FGVlanInPQsD7PerformanceSysUpTime OBJECT-TYPE
   SYNTAX      TimeTicks
   MAX-ACCESS  read-only
   STATUS      current
   DESCRIPTION
      "Path: ethernet3.performance.vlan.inPriorityQueues.d7Performance.sysUpTime

       Time in centi-second."
   ::= {pr1646v2Lan3FGVlanInPQsD7PerformanceEntry 16777216}

pr1646v2Lan3FGVlanInPQsD7PerformanceTotPkts OBJECT-TYPE
   SYNTAX      Counter64
   MAX-ACCESS  read-only
   STATUS      current
   DESCRIPTION
      "Path: ethernet3.performance.vlan.inPriorityQueues.d7Performance.totalPkts

       64 bit unsigned wrappable counter."
   ::= {pr1646v2Lan3FGVlanInPQsD7PerformanceEntry 234881024}

pr1646v2Lan3FGVlanInPQsD7PerformanceDirTxPkts OBJECT-TYPE
   SYNTAX      Counter64
   MAX-ACCESS  read-only
   STATUS      current
   DESCRIPTION
      "Path: ethernet3.performance.vlan.inPriorityQueues.d7Performance.directTxPkts

       64 bit unsigned wrappable counter."
   ::= {pr1646v2Lan3FGVlanInPQsD7PerformanceEntry 33554432}

pr1646v2Lan3FGVlanInPQsD7PerformanceQdPkts OBJECT-TYPE
   SYNTAX      Counter64
   MAX-ACCESS  read-only
   STATUS      current
   DESCRIPTION
      "Path: ethernet3.performance.vlan.inPriorityQueues.d7Performance.queuedPkts

       64 bit unsigned wrappable counter."
   ::= {pr1646v2Lan3FGVlanInPQsD7PerformanceEntry 50331648}

pr1646v2Lan3FGVlanInPQsD7PerformanceDropPkts OBJECT-TYPE
   SYNTAX      Counter64
   MAX-ACCESS  read-only
   STATUS      current
   DESCRIPTION
      "Path: ethernet3.performance.vlan.inPriorityQueues.d7Performance.droppedPkts

       64 bit unsigned wrappable counter."
   ::= {pr1646v2Lan3FGVlanInPQsD7PerformanceEntry 67108864}

pr1646v2Lan3FGVlanInPQsD7PerformanceRDropPkts OBJECT-TYPE
   SYNTAX      Counter64
   MAX-ACCESS  read-only
   STATUS      current
   DESCRIPTION
      "Path: ethernet3.performance.vlan.inPriorityQueues.d7Performance.redDroppedPkts

       64 bit unsigned wrappable counter."
   ::= {pr1646v2Lan3FGVlanInPQsD7PerformanceEntry 201326592}

pr1646v2Lan3FGVlanInPQsD7PerformanceCirTxPkts OBJECT-TYPE
   SYNTAX      Counter64
   MAX-ACCESS  read-only
   STATUS      current
   DESCRIPTION
      "Path: ethernet3.performance.vlan.inPriorityQueues.d7Performance.cirTxPkts

       64 bit unsigned wrappable counter."
   ::= {pr1646v2Lan3FGVlanInPQsD7PerformanceEntry 83886080}

pr1646v2Lan3FGVlanInPQsD7PerformanceEirTxPkts OBJECT-TYPE
   SYNTAX      Counter64
   MAX-ACCESS  read-only
   STATUS      current
   DESCRIPTION
      "Path: ethernet3.performance.vlan.inPriorityQueues.d7Performance.eirTxPkts

       64 bit unsigned wrappable counter."
   ::= {pr1646v2Lan3FGVlanInPQsD7PerformanceEntry 100663296}

pr1646v2Lan3FGVlanInPQsD7PerformanceViolTxPkts OBJECT-TYPE
   SYNTAX      Counter64
   MAX-ACCESS  read-only
   STATUS      current
   DESCRIPTION
      "Path: ethernet3.performance.vlan.inPriorityQueues.d7Performance.violateTxPkts

       64 bit unsigned wrappable counter."
   ::= {pr1646v2Lan3FGVlanInPQsD7PerformanceEntry 301989888}

pr1646v2Lan3FGVlanInPQsD7PerformanceTotOcts OBJECT-TYPE
   SYNTAX      Counter64
   MAX-ACCESS  read-only
   STATUS      current
   DESCRIPTION
      "Path: ethernet3.performance.vlan.inPriorityQueues.d7Performance.totalOctets

       64 bit unsigned wrappable counter."
   ::= {pr1646v2Lan3FGVlanInPQsD7PerformanceEntry 251658240}

pr1646v2Lan3FGVlanInPQsD7PerformanceDirTxOcts OBJECT-TYPE
   SYNTAX      Counter64
   MAX-ACCESS  read-only
   STATUS      current
   DESCRIPTION
      "Path: ethernet3.performance.vlan.inPriorityQueues.d7Performance.directTxOctets

       64 bit unsigned wrappable counter."
   ::= {pr1646v2Lan3FGVlanInPQsD7PerformanceEntry 117440512}

pr1646v2Lan3FGVlanInPQsD7PerformanceQdOcts OBJECT-TYPE
   SYNTAX      Counter64
   MAX-ACCESS  read-only
   STATUS      current
   DESCRIPTION
      "Path: ethernet3.performance.vlan.inPriorityQueues.d7Performance.queuedOctets

       64 bit unsigned wrappable counter."
   ::= {pr1646v2Lan3FGVlanInPQsD7PerformanceEntry 134217728}

pr1646v2Lan3FGVlanInPQsD7PerformanceDropOcts OBJECT-TYPE
   SYNTAX      Counter64
   MAX-ACCESS  read-only
   STATUS      current
   DESCRIPTION
      "Path: ethernet3.performance.vlan.inPriorityQueues.d7Performance.droppedOctets

       64 bit unsigned wrappable counter."
   ::= {pr1646v2Lan3FGVlanInPQsD7PerformanceEntry 150994944}

pr1646v2Lan3FGVlanInPQsD7PerformanceRDropOcts OBJECT-TYPE
   SYNTAX      Counter64
   MAX-ACCESS  read-only
   STATUS      current
   DESCRIPTION
      "Path: ethernet3.performance.vlan.inPriorityQueues.d7Performance.redDroppedOctets

       64 bit unsigned wrappable counter."
   ::= {pr1646v2Lan3FGVlanInPQsD7PerformanceEntry 218103808}

pr1646v2Lan3FGVlanInPQsD7PerformanceCirTxOcts OBJECT-TYPE
   SYNTAX      Counter64
   MAX-ACCESS  read-only
   STATUS      current
   DESCRIPTION
      "Path: ethernet3.performance.vlan.inPriorityQueues.d7Performance.cirTxOctets

       64 bit unsigned wrappable counter."
   ::= {pr1646v2Lan3FGVlanInPQsD7PerformanceEntry 167772160}

pr1646v2Lan3FGVlanInPQsD7PerformanceEirTxOcts OBJECT-TYPE
   SYNTAX      Counter64
   MAX-ACCESS  read-only
   STATUS      current
   DESCRIPTION
      "Path: ethernet3.performance.vlan.inPriorityQueues.d7Performance.eirTxOctets

       64 bit unsigned wrappable counter."
   ::= {pr1646v2Lan3FGVlanInPQsD7PerformanceEntry 184549376}

pr1646v2Lan3FGVlanInPQsD7PerformanceViolTxOcts OBJECT-TYPE
   SYNTAX      Counter64
   MAX-ACCESS  read-only
   STATUS      current
   DESCRIPTION
      "Path: ethernet3.performance.vlan.inPriorityQueues.d7Performance.violateTxOctets

       64 bit unsigned wrappable counter."
   ::= {pr1646v2Lan3FGVlanInPQsD7PerformanceEntry 318767104}

pr1646v2Lan3FGVlanInPQsD7PerformanceBandwidth OBJECT-TYPE
   SYNTAX      Integer32
   MAX-ACCESS  read-only
   STATUS      current
   DESCRIPTION
      "Path: ethernet3.performance.vlan.inPriorityQueues.d7Performance.bandwidth

       unit name = bps
       formula = 8 * ; 8 /"
   ::= {pr1646v2Lan3FGVlanInPQsD7PerformanceEntry 268435456}

pr1646v2Lan3FGVlanOutPQs OBJECT-TYPE
   SYNTAX      SEQUENCE OF Pr1646v2Lan3FGVlanOutPQsEntry
   MAX-ACCESS  not-accessible
   STATUS      current
   DESCRIPTION
      ""
   ::= {pr1646v2Lan3FGVlan 83886080}

pr1646v2Lan3FGVlanOutPQsEntry OBJECT-TYPE
   SYNTAX      Pr1646v2Lan3FGVlanOutPQsEntry
   MAX-ACCESS  not-accessible
   STATUS      current
   DESCRIPTION
      ""
   INDEX      { pr1646v2Lan3FGVlanTableIx,
                pr1646v2Lan3FGVlanOutPQsTableIx }
   ::= {pr1646v2Lan3FGVlanOutPQs 1}

Pr1646v2Lan3FGVlanOutPQsEntry ::=
   SEQUENCE
      {
      pr1646v2Lan3FGVlanOutPQsTableIx
         TableIndex,
      pr1646v2Lan3FGVlanOutPQsName
         INTEGER,
      pr1646v2Lan3FGVlanOutPQsLength
         Integer32,
      pr1646v2Lan3FGVlanOutPQsOctetLength
         Integer32,
      pr1646v2Lan3FGVlanOutPQsRedLength
         Integer32,
      pr1646v2Lan3FGVlanOutPQsPacketsTotal
         Counter64,
      pr1646v2Lan3FGVlanOutPQsPacketsDirectTx
         Counter64,
      pr1646v2Lan3FGVlanOutPQsPacketsQueued
         Counter64,
      pr1646v2Lan3FGVlanOutPQsPacketsDropped
         Counter64,
      pr1646v2Lan3FGVlanOutPQsPacketsRedDropped
         Counter64,
      pr1646v2Lan3FGVlanOutPQsPacketsCirTx
         Counter64,
      pr1646v2Lan3FGVlanOutPQsPacketsEirTx
         Counter64,
      pr1646v2Lan3FGVlanOutPQsPacketsViolateTx
         Counter64,
      pr1646v2Lan3FGVlanOutPQsOctetsTotal
         Counter64,
      pr1646v2Lan3FGVlanOutPQsOctetsDirectTx
         Counter64,
      pr1646v2Lan3FGVlanOutPQsOctetsQueued
         Counter64,
      pr1646v2Lan3FGVlanOutPQsOctetsDropped
         Counter64,
      pr1646v2Lan3FGVlanOutPQsOctetsRedDropped
         Counter64,
      pr1646v2Lan3FGVlanOutPQsOctetsCirTx
         Counter64,
      pr1646v2Lan3FGVlanOutPQsOctetsEirTx
         Counter64,
      pr1646v2Lan3FGVlanOutPQsOctetsViolateTx
         Counter64,
      pr1646v2Lan3FGVlanOutPQsOctetsBandwidth15sec
         Integer32,
      pr1646v2Lan3FGVlanOutPQsOctetsBandwidth30sec
         Integer32,
      pr1646v2Lan3FGVlanOutPQsOctetsBandwidth1min
         Integer32,
      pr1646v2Lan3FGVlanOutPQsOctetsBandwidth2min
         Integer32,
      pr1646v2Lan3FGVlanOutPQsOctetsBandwidth5min
         Integer32
      }

pr1646v2Lan3FGVlanOutPQsTableIx OBJECT-TYPE
   SYNTAX      TableIndex
   MAX-ACCESS  not-accessible
   STATUS      current
   DESCRIPTION
      ""
   ::= {pr1646v2Lan3FGVlanOutPQsEntry 11}

pr1646v2Lan3FGVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2Lan3FGVlanOutPQsEntry 16777216}

pr1646v2Lan3FGVlanOutPQsLength OBJECT-TYPE
   SYNTAX      Integer32
   MAX-ACCESS  read-only
   STATUS      current
   DESCRIPTION
      "Path: ethernet3.performance.vlan.outPriorityQueues.length"
   ::= {pr1646v2Lan3FGVlanOutPQsEntry 33554432}

pr1646v2Lan3FGVlanOutPQsOctetLength OBJECT-TYPE
   SYNTAX      Integer32
   MAX-ACCESS  read-only
   STATUS      current
   DESCRIPTION
      "Path: ethernet3.performance.vlan.outPriorityQueues.octetLength"
   ::= {pr1646v2Lan3FGVlanOutPQsEntry 150994944}

pr1646v2Lan3FGVlanOutPQsRedLength OBJECT-TYPE
   SYNTAX      Integer32
   MAX-ACCESS  read-only
   STATUS      current
   DESCRIPTION
      "Path: ethernet3.performance.vlan.outPriorityQueues.redLength"
   ::= {pr1646v2Lan3FGVlanOutPQsEntry 134217728}

pr1646v2Lan3FGVlanOutPQsPacketsTotal OBJECT-TYPE
   SYNTAX      Counter64
   MAX-ACCESS  read-only
   STATUS      current
   DESCRIPTION
      "Path: ethernet3.performance.vlan.outPriorityQueues.packets.total

       64 bit unsigned wrappable counter."
   ::= {pr1646v2Lan3FGVlanOutPQsEntry 50790400}

pr1646v2Lan3FGVlanOutPQsPacketsDirectTx OBJECT-TYPE
   SYNTAX      Counter64
   MAX-ACCESS  read-only
   STATUS      current
   DESCRIPTION
      "Path: ethernet3.performance.vlan.outPriorityQueues.packets.directTx

       64 bit unsigned wrappable counter."
   ::= {pr1646v2Lan3FGVlanOutPQsEntry 50397184}

pr1646v2Lan3FGVlanOutPQsPacketsQueued OBJECT-TYPE
   SYNTAX      Counter64
   MAX-ACCESS  read-only
   STATUS      current
   DESCRIPTION
      "Path: ethernet3.performance.vlan.outPriorityQueues.packets.queued

       64 bit unsigned wrappable counter."
   ::= {pr1646v2Lan3FGVlanOutPQsEntry 50462720}

pr1646v2Lan3FGVlanOutPQsPacketsDropped OBJECT-TYPE
   SYNTAX      Counter64
   MAX-ACCESS  read-only
   STATUS      current
   DESCRIPTION
      "Path: ethernet3.performance.vlan.outPriorityQueues.packets.dropped

       64 bit unsigned wrappable counter."
   ::= {pr1646v2Lan3FGVlanOutPQsEntry 50528256}

pr1646v2Lan3FGVlanOutPQsPacketsRedDropped OBJECT-TYPE
   SYNTAX      Counter64
   MAX-ACCESS  read-only
   STATUS      current
   DESCRIPTION
      "Path: ethernet3.performance.vlan.outPriorityQueues.packets.redDropped

       64 bit unsigned wrappable counter."
   ::= {pr1646v2Lan3FGVlanOutPQsEntry 50724864}

pr1646v2Lan3FGVlanOutPQsPacketsCirTx OBJECT-TYPE
   SYNTAX      Counter64
   MAX-ACCESS  read-only
   STATUS      current
   DESCRIPTION
      "Path: ethernet3.performance.vlan.outPriorityQueues.packets.cirTx

       64 bit unsigned wrappable counter."
   ::= {pr1646v2Lan3FGVlanOutPQsEntry 50593792}

pr1646v2Lan3FGVlanOutPQsPacketsEirTx OBJECT-TYPE
   SYNTAX      Counter64
   MAX-ACCESS  read-only
   STATUS      current
   DESCRIPTION
      "Path: ethernet3.performance.vlan.outPriorityQueues.packets.eirTx

       64 bit unsigned wrappable counter."
   ::= {pr1646v2Lan3FGVlanOutPQsEntry 50659328}

pr1646v2Lan3FGVlanOutPQsPacketsViolateTx OBJECT-TYPE
   SYNTAX      Counter64
   MAX-ACCESS  read-only
   STATUS      current
   DESCRIPTION
      "Path: ethernet3.performance.vlan.outPriorityQueues.packets.violateTx

       64 bit unsigned wrappable counter."
   ::= {pr1646v2Lan3FGVlanOutPQsEntry 50855936}

pr1646v2Lan3FGVlanOutPQsOctetsTotal OBJECT-TYPE
   SYNTAX      Counter64
   MAX-ACCESS  read-only
   STATUS      current
   DESCRIPTION
      "Path: ethernet3.performance.vlan.outPriorityQueues.octets.total

       64 bit unsigned wrappable counter."
   ::= {pr1646v2Lan3FGVlanOutPQsEntry 67567616}

pr1646v2Lan3FGVlanOutPQsOctetsDirectTx OBJECT-TYPE
   SYNTAX      Counter64
   MAX-ACCESS  read-only
   STATUS      current
   DESCRIPTION
      "Path: ethernet3.performance.vlan.outPriorityQueues.octets.directTx

       64 bit unsigned wrappable counter."
   ::= {pr1646v2Lan3FGVlanOutPQsEntry 67174400}

pr1646v2Lan3FGVlanOutPQsOctetsQueued OBJECT-TYPE
   SYNTAX      Counter64
   MAX-ACCESS  read-only
   STATUS      current
   DESCRIPTION
      "Path: ethernet3.performance.vlan.outPriorityQueues.octets.queued

       64 bit unsigned wrappable counter."
   ::= {pr1646v2Lan3FGVlanOutPQsEntry 67239936}

pr1646v2Lan3FGVlanOutPQsOctetsDropped OBJECT-TYPE
   SYNTAX      Counter64
   MAX-ACCESS  read-only
   STATUS      current
   DESCRIPTION
      "Path: ethernet3.performance.vlan.outPriorityQueues.octets.dropped

       64 bit unsigned wrappable counter."
   ::= {pr1646v2Lan3FGVlanOutPQsEntry 67305472}

pr1646v2Lan3FGVlanOutPQsOctetsRedDropped OBJECT-TYPE
   SYNTAX      Counter64
   MAX-ACCESS  read-only
   STATUS      current
   DESCRIPTION
      "Path: ethernet3.performance.vlan.outPriorityQueues.octets.redDropped

       64 bit unsigned wrappable counter."
   ::= {pr1646v2Lan3FGVlanOutPQsEntry 67502080}

pr1646v2Lan3FGVlanOutPQsOctetsCirTx OBJECT-TYPE
   SYNTAX      Counter64
   MAX-ACCESS  read-only
   STATUS      current
   DESCRIPTION
      "Path: ethernet3.performance.vlan.outPriorityQueues.octets.cirTx

       64 bit unsigned wrappable counter."
   ::= {pr1646v2Lan3FGVlanOutPQsEntry 67371008}

pr1646v2Lan3FGVlanOutPQsOctetsEirTx OBJECT-TYPE
   SYNTAX      Counter64
   MAX-ACCESS  read-only
   STATUS      current
   DESCRIPTION
      "Path: ethernet3.performance.vlan.outPriorityQueues.octets.eirTx

       64 bit unsigned wrappable counter."
   ::= {pr1646v2Lan3FGVlanOutPQsEntry 67436544}

pr1646v2Lan3FGVlanOutPQsOctetsViolateTx OBJECT-TYPE
   SYNTAX      Counter64
   MAX-ACCESS  read-only
   STATUS      current
   DESCRIPTION
      "Path: ethernet3.performance.vlan.outPriorityQueues.octets.violateTx

       64 bit unsigned wrappable counter."
   ::= {pr1646v2Lan3FGVlanOutPQsEntry 67633152}

pr1646v2Lan3FGVlanOutPQsOctetsBandwidth15sec OBJECT-TYPE
   SYNTAX      Integer32
   MAX-ACCESS  read-only
   STATUS      current
   DESCRIPTION
      "Path: ethernet3.performance.vlan.outPriorityQueues.octets.bandwidth.15sec

       unit name = bps
       formula = 8 * ; 8 /"
   ::= {pr1646v2Lan3FGVlanOutPQsEntry 70386944}

pr1646v2Lan3FGVlanOutPQsOctetsBandwidth30sec OBJECT-TYPE
   SYNTAX      Integer32
   MAX-ACCESS  read-only
   STATUS      current
   DESCRIPTION
      "Path: ethernet3.performance.vlan.outPriorityQueues.octets.bandwidth.30sec

       unit name = bps
       formula = 8 * ; 8 /"
   ::= {pr1646v2Lan3FGVlanOutPQsEntry 70388224}

pr1646v2Lan3FGVlanOutPQsOctetsBandwidth1min OBJECT-TYPE
   SYNTAX      Integer32
   MAX-ACCESS  read-only
   STATUS      current
   DESCRIPTION
      "Path: ethernet3.performance.vlan.outPriorityQueues.octets.bandwidth.1min

       unit name = bps
       formula = 8 * ; 8 /"
   ::= {pr1646v2Lan3FGVlanOutPQsEntry 70390784}

pr1646v2Lan3FGVlanOutPQsOctetsBandwidth2min OBJECT-TYPE
   SYNTAX      Integer32
   MAX-ACCESS  read-only
   STATUS      current
   DESCRIPTION
      "Path: ethernet3.performance.vlan.outPriorityQueues.octets.bandwidth.2min

       unit name = bps
       formula = 8 * ; 8 /"
   ::= {pr1646v2Lan3FGVlanOutPQsEntry 70395904}

pr1646v2Lan3FGVlanOutPQsOctetsBandwidth5min OBJECT-TYPE
   SYNTAX      Integer32
   MAX-ACCESS  read-only
   STATUS      current
   DESCRIPTION
      "Path: ethernet3.performance.vlan.outPriorityQueues.octets.bandwidth.5min

       unit name = bps
       formula = 8 * ; 8 /"
   ::= {pr1646v2Lan3FGVlanOutPQsEntry 70411264}

pr1646v2Lan3FGVlanOutPQsH2Performance OBJECT-TYPE
   SYNTAX      SEQUENCE OF Pr1646v2Lan3FGVlanOutPQsH2PerformanceEntry
   MAX-ACCESS  not-accessible
   STATUS      current
   DESCRIPTION
      ""
   ::= {pr1646v2Lan3FGVlan 84213760}

pr1646v2Lan3FGVlanOutPQsH2PerformanceEntry OBJECT-TYPE
   SYNTAX      Pr1646v2Lan3FGVlanOutPQsH2PerformanceEntry
   MAX-ACCESS  not-accessible
   STATUS      current
   DESCRIPTION
      ""
   INDEX      { pr1646v2Lan3FGVlanTableIx,
                pr1646v2Lan3FGVlanOutPQsTableIx,
                pr1646v2Lan3FGVlanOutPQsH2PerformanceTableIx }
   ::= {pr1646v2Lan3FGVlanOutPQsH2Performance 1}

Pr1646v2Lan3FGVlanOutPQsH2PerformanceEntry ::=
   SEQUENCE
      {
      pr1646v2Lan3FGVlanOutPQsH2PerformanceTableIx
         TableIndex,
      pr1646v2Lan3FGVlanOutPQsH2PerformanceSysUpTime
         TimeTicks,
      pr1646v2Lan3FGVlanOutPQsH2PerformanceTotPkts
         Counter64,
      pr1646v2Lan3FGVlanOutPQsH2PerformanceDirTxPkts
         Counter64,
      pr1646v2Lan3FGVlanOutPQsH2PerformanceQdPkts
         Counter64,
      pr1646v2Lan3FGVlanOutPQsH2PerformanceDropPkts
         Counter64,
      pr1646v2Lan3FGVlanOutPQsH2PerformanceRDropPkts
         Counter64,
      pr1646v2Lan3FGVlanOutPQsH2PerformanceCirTxPkts
         Counter64,
      pr1646v2Lan3FGVlanOutPQsH2PerformanceEirTxPkts
         Counter64,
      pr1646v2Lan3FGVlanOutPQsH2PerformanceViolTxPkts
         Counter64,
      pr1646v2Lan3FGVlanOutPQsH2PerformanceTotOcts
         Counter64,
      pr1646v2Lan3FGVlanOutPQsH2PerformanceDirTxOcts
         Counter64,
      pr1646v2Lan3FGVlanOutPQsH2PerformanceQdOcts
         Counter64,
      pr1646v2Lan3FGVlanOutPQsH2PerformanceDropOcts
         Counter64,
      pr1646v2Lan3FGVlanOutPQsH2PerformanceRDropOcts
         Counter64,
      pr1646v2Lan3FGVlanOutPQsH2PerformanceCirTxOcts
         Counter64,
      pr1646v2Lan3FGVlanOutPQsH2PerformanceEirTxOcts
         Counter64,
      pr1646v2Lan3FGVlanOutPQsH2PerformanceViolTxOcts
         Counter64,
      pr1646v2Lan3FGVlanOutPQsH2PerformanceBandwidth
         Integer32
      }

pr1646v2Lan3FGVlanOutPQsH2PerformanceTableIx OBJECT-TYPE
   SYNTAX      TableIndex
   MAX-ACCESS  not-accessible
   STATUS      current
   DESCRIPTION
      ""
   ::= {pr1646v2Lan3FGVlanOutPQsH2PerformanceEntry 11}

pr1646v2Lan3FGVlanOutPQsH2PerformanceSysUpTime OBJECT-TYPE
   SYNTAX      TimeTicks
   MAX-ACCESS  read-only
   STATUS      current
   DESCRIPTION
      "Path: ethernet3.performance.vlan.outPriorityQueues.h2Performance.sysUpTime

       Time in centi-second."
   ::= {pr1646v2Lan3FGVlanOutPQsH2PerformanceEntry 16777216}

pr1646v2Lan3FGVlanOutPQsH2PerformanceTotPkts OBJECT-TYPE
   SYNTAX      Counter64
   MAX-ACCESS  read-only
   STATUS      current
   DESCRIPTION
      "Path: ethernet3.performance.vlan.outPriorityQueues.h2Performance.totalPkts

       64 bit unsigned wrappable counter."
   ::= {pr1646v2Lan3FGVlanOutPQsH2PerformanceEntry 234881024}

pr1646v2Lan3FGVlanOutPQsH2PerformanceDirTxPkts OBJECT-TYPE
   SYNTAX      Counter64
   MAX-ACCESS  read-only
   STATUS      current
   DESCRIPTION
      "Path: ethernet3.performance.vlan.outPriorityQueues.h2Performance.directTxPkts

       64 bit unsigned wrappable counter."
   ::= {pr1646v2Lan3FGVlanOutPQsH2PerformanceEntry 33554432}

pr1646v2Lan3FGVlanOutPQsH2PerformanceQdPkts OBJECT-TYPE
   SYNTAX      Counter64
   MAX-ACCESS  read-only
   STATUS      current
   DESCRIPTION
      "Path: ethernet3.performance.vlan.outPriorityQueues.h2Performance.queuedPkts

       64 bit unsigned wrappable counter."
   ::= {pr1646v2Lan3FGVlanOutPQsH2PerformanceEntry 50331648}

pr1646v2Lan3FGVlanOutPQsH2PerformanceDropPkts OBJECT-TYPE
   SYNTAX      Counter64
   MAX-ACCESS  read-only
   STATUS      current
   DESCRIPTION
      "Path: ethernet3.performance.vlan.outPriorityQueues.h2Performance.droppedPkts

       64 bit unsigned wrappable counter."
   ::= {pr1646v2Lan3FGVlanOutPQsH2PerformanceEntry 67108864}

pr1646v2Lan3FGVlanOutPQsH2PerformanceRDropPkts OBJECT-TYPE
   SYNTAX      Counter64
   MAX-ACCESS  read-only
   STATUS      current
   DESCRIPTION
      "Path: ethernet3.performance.vlan.outPriorityQueues.h2Performance.redDroppedPkts

       64 bit unsigned wrappable counter."
   ::= {pr1646v2Lan3FGVlanOutPQsH2PerformanceEntry 201326592}

pr1646v2Lan3FGVlanOutPQsH2PerformanceCirTxPkts OBJECT-TYPE
   SYNTAX      Counter64
   MAX-ACCESS  read-only
   STATUS      current
   DESCRIPTION
      "Path: ethernet3.performance.vlan.outPriorityQueues.h2Performance.cirTxPkts

       64 bit unsigned wrappable counter."
   ::= {pr1646v2Lan3FGVlanOutPQsH2PerformanceEntry 83886080}

pr1646v2Lan3FGVlanOutPQsH2PerformanceEirTxPkts OBJECT-TYPE
   SYNTAX      Counter64
   MAX-ACCESS  read-only
   STATUS      current
   DESCRIPTION
      "Path: ethernet3.performance.vlan.outPriorityQueues.h2Performance.eirTxPkts

       64 bit unsigned wrappable counter."
   ::= {pr1646v2Lan3FGVlanOutPQsH2PerformanceEntry 100663296}

pr1646v2Lan3FGVlanOutPQsH2PerformanceViolTxPkts OBJECT-TYPE
   SYNTAX      Counter64
   MAX-ACCESS  read-only
   STATUS      current
   DESCRIPTION
      "Path: ethernet3.performance.vlan.outPriorityQueues.h2Performance.violateTxPkts

       64 bit unsigned wrappable counter."
   ::= {pr1646v2Lan3FGVlanOutPQsH2PerformanceEntry 301989888}

pr1646v2Lan3FGVlanOutPQsH2PerformanceTotOcts OBJECT-TYPE
   SYNTAX      Counter64
   MAX-ACCESS  read-only
   STATUS      current
   DESCRIPTION
      "Path: ethernet3.performance.vlan.outPriorityQueues.h2Performance.totalOctets

       64 bit unsigned wrappable counter."
   ::= {pr1646v2Lan3FGVlanOutPQsH2PerformanceEntry 251658240}

pr1646v2Lan3FGVlanOutPQsH2PerformanceDirTxOcts OBJECT-TYPE
   SYNTAX      Counter64
   MAX-ACCESS  read-only
   STATUS      current
   DESCRIPTION
      "Path: ethernet3.performance.vlan.outPriorityQueues.h2Performance.directTxOctets

       64 bit unsigned wrappable counter."
   ::= {pr1646v2Lan3FGVlanOutPQsH2PerformanceEntry 117440512}

pr1646v2Lan3FGVlanOutPQsH2PerformanceQdOcts OBJECT-TYPE
   SYNTAX      Counter64
   MAX-ACCESS  read-only
   STATUS      current
   DESCRIPTION
      "Path: ethernet3.performance.vlan.outPriorityQueues.h2Performance.queuedOctets

       64 bit unsigned wrappable counter."
   ::= {pr1646v2Lan3FGVlanOutPQsH2PerformanceEntry 134217728}

pr1646v2Lan3FGVlanOutPQsH2PerformanceDropOcts OBJECT-TYPE
   SYNTAX      Counter64
   MAX-ACCESS  read-only
   STATUS      current
   DESCRIPTION
      "Path: ethernet3.performance.vlan.outPriorityQueues.h2Performance.droppedOctets

       64 bit unsigned wrappable counter."
   ::= {pr1646v2Lan3FGVlanOutPQsH2PerformanceEntry 150994944}

pr1646v2Lan3FGVlanOutPQsH2PerformanceRDropOcts OBJECT-TYPE
   SYNTAX      Counter64
   MAX-ACCESS  read-only
   STATUS      current
   DESCRIPTION
      "Path: ethernet3.performance.vlan.outPriorityQueues.h2Performance.redDroppedOctets

       64 bit unsigned wrappable counter."
   ::= {pr1646v2Lan3FGVlanOutPQsH2PerformanceEntry 218103808}

pr1646v2Lan3FGVlanOutPQsH2PerformanceCirTxOcts OBJECT-TYPE
   SYNTAX      Counter64
   MAX-ACCESS  read-only
   STATUS      current
   DESCRIPTION
      "Path: ethernet3.performance.vlan.outPriorityQueues.h2Performance.cirTxOctets

       64 bit unsigned wrappable counter."
   ::= {pr1646v2Lan3FGVlanOutPQsH2PerformanceEntry 167772160}

pr1646v2Lan3FGVlanOutPQsH2PerformanceEirTxOcts OBJECT-TYPE
   SYNTAX      Counter64
   MAX-ACCESS  read-only
   STATUS      current
   DESCRIPTION
      "Path: ethernet3.performance.vlan.outPriorityQueues.h2Performance.eirTxOctets

       64 bit unsigned wrappable counter."
   ::= {pr1646v2Lan3FGVlanOutPQsH2PerformanceEntry 184549376}

pr1646v2Lan3FGVlanOutPQsH2PerformanceViolTxOcts OBJECT-TYPE
   SYNTAX      Counter64
   MAX-ACCESS  read-only
   STATUS      current
   DESCRIPTION
      "Path: ethernet3.performance.vlan.outPriorityQueues.h2Performance.violateTxOctets

       64 bit unsigned wrappable counter."
   ::= {pr1646v2Lan3FGVlanOutPQsH2PerformanceEntry 318767104}

pr1646v2Lan3FGVlanOutPQsH2PerformanceBandwidth OBJECT-TYPE
   SYNTAX      Integer32
   MAX-ACCESS  read-only
   STATUS      current
   DESCRIPTION
      "Path: ethernet3.performance.vlan.outPriorityQueues.h2Performance.bandwidth

       unit name = bps
       formula = 8 * ; 8 /"
   ::= {pr1646v2Lan3FGVlanOutPQsH2PerformanceEntry 268435456}

pr1646v2Lan3FGVlanOutPQsH24Performance OBJECT-TYPE
   SYNTAX      SEQUENCE OF Pr1646v2Lan3FGVlanOutPQsH24PerformanceEntry
   MAX-ACCESS  not-accessible
   STATUS      current
   DESCRIPTION
      ""
   ::= {pr1646v2Lan3FGVlan 84279296}

pr1646v2Lan3FGVlanOutPQsH24PerformanceEntry OBJECT-TYPE
   SYNTAX      Pr1646v2Lan3FGVlanOutPQsH24PerformanceEntry
   MAX-ACCESS  not-accessible
   STATUS      current
   DESCRIPTION
      ""
   INDEX      { pr1646v2Lan3FGVlanTableIx,
                pr1646v2Lan3FGVlanOutPQsTableIx,
                pr1646v2Lan3FGVlanOutPQsH24PerformanceTableIx }
   ::= {pr1646v2Lan3FGVlanOutPQsH24Performance 1}

Pr1646v2Lan3FGVlanOutPQsH24PerformanceEntry ::=
   SEQUENCE
      {
      pr1646v2Lan3FGVlanOutPQsH24PerformanceTableIx
         TableIndex,
      pr1646v2Lan3FGVlanOutPQsH24PerformanceSysUpTime
         TimeTicks,
      pr1646v2Lan3FGVlanOutPQsH24PerformanceTotPkts
         Counter64,
      pr1646v2Lan3FGVlanOutPQsH24PerformanceDirTxPkts
         Counter64,
      pr1646v2Lan3FGVlanOutPQsH24PerformanceQdPkts
         Counter64,
      pr1646v2Lan3FGVlanOutPQsH24PerformanceDropPkts
         Counter64,
      pr1646v2Lan3FGVlanOutPQsH24PerformanceRDropPkts
         Counter64,
      pr1646v2Lan3FGVlanOutPQsH24PerformanceCirTxPkts
         Counter64,
      pr1646v2Lan3FGVlanOutPQsH24PerformanceEirTxPkts
         Counter64,
      pr1646v2Lan3FGVlanOutPQsH24PerformanceViolTxPkts
         Counter64,
      pr1646v2Lan3FGVlanOutPQsH24PerformanceTotOcts
         Counter64,
      pr1646v2Lan3FGVlanOutPQsH24PerformanceDirTxOcts
         Counter64,
      pr1646v2Lan3FGVlanOutPQsH24PerformanceQdOcts
         Counter64,
      pr1646v2Lan3FGVlanOutPQsH24PerformanceDropOcts
         Counter64,
      pr1646v2Lan3FGVlanOutPQsH24PerformanceRDropOcts
         Counter64,
      pr1646v2Lan3FGVlanOutPQsH24PerformanceCirTxOcts
         Counter64,
      pr1646v2Lan3FGVlanOutPQsH24PerformanceEirTxOcts
         Counter64,
      pr1646v2Lan3FGVlanOutPQsH24PerformanceViolTxOcts
         Counter64,
      pr1646v2Lan3FGVlanOutPQsH24PerformanceBandwidth
         Integer32
      }

pr1646v2Lan3FGVlanOutPQsH24PerformanceTableIx OBJECT-TYPE
   SYNTAX      TableIndex
   MAX-ACCESS  not-accessible
   STATUS      current
   DESCRIPTION
      ""
   ::= {pr1646v2Lan3FGVlanOutPQsH24PerformanceEntry 11}

pr1646v2Lan3FGVlanOutPQsH24PerformanceSysUpTime OBJECT-TYPE
   SYNTAX      TimeTicks
   MAX-ACCESS  read-only
   STATUS      current
   DESCRIPTION
      "Path: ethernet3.performance.vlan.outPriorityQueues.h24Performance.sysUpTime

       Time in centi-second."
   ::= {pr1646v2Lan3FGVlanOutPQsH24PerformanceEntry 16777216}

pr1646v2Lan3FGVlanOutPQsH24PerformanceTotPkts OBJECT-TYPE
   SYNTAX      Counter64
   MAX-ACCESS  read-only
   STATUS      current
   DESCRIPTION
      "Path: ethernet3.performance.vlan.outPriorityQueues.h24Performance.totalPkts

       64 bit unsigned wrappable counter."
   ::= {pr1646v2Lan3FGVlanOutPQsH24PerformanceEntry 234881024}

pr1646v2Lan3FGVlanOutPQsH24PerformanceDirTxPkts OBJECT-TYPE
   SYNTAX      Counter64
   MAX-ACCESS  read-only
   STATUS      current
   DESCRIPTION
      "Path: ethernet3.performance.vlan.outPriorityQueues.h24Performance.directTxPkts

       64 bit unsigned wrappable counter."
   ::= {pr1646v2Lan3FGVlanOutPQsH24PerformanceEntry 33554432}

pr1646v2Lan3FGVlanOutPQsH24PerformanceQdPkts OBJECT-TYPE
   SYNTAX      Counter64
   MAX-ACCESS  read-only
   STATUS      current
   DESCRIPTION
      "Path: ethernet3.performance.vlan.outPriorityQueues.h24Performance.queuedPkts

       64 bit unsigned wrappable counter."
   ::= {pr1646v2Lan3FGVlanOutPQsH24PerformanceEntry 50331648}

pr1646v2Lan3FGVlanOutPQsH24PerformanceDropPkts OBJECT-TYPE
   SYNTAX      Counter64
   MAX-ACCESS  read-only
   STATUS      current
   DESCRIPTION
      "Path: ethernet3.performance.vlan.outPriorityQueues.h24Performance.droppedPkts

       64 bit unsigned wrappable counter."
   ::= {pr1646v2Lan3FGVlanOutPQsH24PerformanceEntry 67108864}

pr1646v2Lan3FGVlanOutPQsH24PerformanceRDropPkts OBJECT-TYPE
   SYNTAX      Counter64
   MAX-ACCESS  read-only
   STATUS      current
   DESCRIPTION
      "Path: ethernet3.performance.vlan.outPriorityQueues.h24Performance.redDroppedPkts

       64 bit unsigned wrappable counter."
   ::= {pr1646v2Lan3FGVlanOutPQsH24PerformanceEntry 201326592}

pr1646v2Lan3FGVlanOutPQsH24PerformanceCirTxPkts OBJECT-TYPE
   SYNTAX      Counter64
   MAX-ACCESS  read-only
   STATUS      current
   DESCRIPTION
      "Path: ethernet3.performance.vlan.outPriorityQueues.h24Performance.cirTxPkts

       64 bit unsigned wrappable counter."
   ::= {pr1646v2Lan3FGVlanOutPQsH24PerformanceEntry 83886080}

pr1646v2Lan3FGVlanOutPQsH24PerformanceEirTxPkts OBJECT-TYPE
   SYNTAX      Counter64
   MAX-ACCESS  read-only
   STATUS      current
   DESCRIPTION
      "Path: ethernet3.performance.vlan.outPriorityQueues.h24Performance.eirTxPkts

       64 bit unsigned wrappable counter."
   ::= {pr1646v2Lan3FGVlanOutPQsH24PerformanceEntry 100663296}

pr1646v2Lan3FGVlanOutPQsH24PerformanceViolTxPkts OBJECT-TYPE
   SYNTAX      Counter64
   MAX-ACCESS  read-only
   STATUS      current
   DESCRIPTION
      "Path: ethernet3.performance.vlan.outPriorityQueues.h24Performance.violateTxPkts

       64 bit unsigned wrappable counter."
   ::= {pr1646v2Lan3FGVlanOutPQsH24PerformanceEntry 301989888}

pr1646v2Lan3FGVlanOutPQsH24PerformanceTotOcts OBJECT-TYPE
   SYNTAX      Counter64
   MAX-ACCESS  read-only
   STATUS      current
   DESCRIPTION
      "Path: ethernet3.performance.vlan.outPriorityQueues.h24Performance.totalOctets

       64 bit unsigned wrappable counter."
   ::= {pr1646v2Lan3FGVlanOutPQsH24PerformanceEntry 251658240}

pr1646v2Lan3FGVlanOutPQsH24PerformanceDirTxOcts OBJECT-TYPE
   SYNTAX      Counter64
   MAX-ACCESS  read-only
   STATUS      current
   DESCRIPTION
      "Path: ethernet3.performance.vlan.outPriorityQueues.h24Performance.directTxOctets

       64 bit unsigned wrappable counter."
   ::= {pr1646v2Lan3FGVlanOutPQsH24PerformanceEntry 117440512}

pr1646v2Lan3FGVlanOutPQsH24PerformanceQdOcts OBJECT-TYPE
   SYNTAX      Counter64
   MAX-ACCESS  read-only
   STATUS      current
   DESCRIPTION
      "Path: ethernet3.performance.vlan.outPriorityQueues.h24Performance.queuedOctets

       64 bit unsigned wrappable counter."
   ::= {pr1646v2Lan3FGVlanOutPQsH24PerformanceEntry 134217728}

pr1646v2Lan3FGVlanOutPQsH24PerformanceDropOcts OBJECT-TYPE
   SYNTAX      Counter64
   MAX-ACCESS  read-only
   STATUS      current
   DESCRIPTION
      "Path: ethernet3.performance.vlan.outPriorityQueues.h24Performance.droppedOctets

       64 bit unsigned wrappable counter."
   ::= {pr1646v2Lan3FGVlanOutPQsH24PerformanceEntry 150994944}

pr1646v2Lan3FGVlanOutPQsH24PerformanceRDropOcts OBJECT-TYPE
   SYNTAX      Counter64
   MAX-ACCESS  read-only
   STATUS      current
   DESCRIPTION
      "Path: ethernet3.performance.vlan.outPriorityQueues.h24Performance.redDroppedOctets

       64 bit unsigned wrappable counter."
   ::= {pr1646v2Lan3FGVlanOutPQsH24PerformanceEntry 218103808}

pr1646v2Lan3FGVlanOutPQsH24PerformanceCirTxOcts OBJECT-TYPE
   SYNTAX      Counter64
   MAX-ACCESS  read-only
   STATUS      current
   DESCRIPTION
      "Path: ethernet3.performance.vlan.outPriorityQueues.h24Performance.cirTxOctets

       64 bit unsigned wrappable counter."
   ::= {pr1646v2Lan3FGVlanOutPQsH24PerformanceEntry 167772160}

pr1646v2Lan3FGVlanOutPQsH24PerformanceEirTxOcts OBJECT-TYPE
   SYNTAX      Counter64
   MAX-ACCESS  read-only
   STATUS      current
   DESCRIPTION
      "Path: ethernet3.performance.vlan.outPriorityQueues.h24Performance.eirTxOctets

       64 bit unsigned wrappable counter."
   ::= {pr1646v2Lan3FGVlanOutPQsH24PerformanceEntry 184549376}

pr1646v2Lan3FGVlanOutPQsH24PerformanceViolTxOcts OBJECT-TYPE
   SYNTAX      Counter64
   MAX-ACCESS  read-only
   STATUS      current
   DESCRIPTION
      "Path: ethernet3.performance.vlan.outPriorityQueues.h24Performance.violateTxOctets

       64 bit unsigned wrappable counter."
   ::= {pr1646v2Lan3FGVlanOutPQsH24PerformanceEntry 318767104}

pr1646v2Lan3FGVlanOutPQsH24PerformanceBandwidth OBJECT-TYPE
   SYNTAX      Integer32
   MAX-ACCESS  read-only
   STATUS      current
   DESCRIPTION
      "Path: ethernet3.performance.vlan.outPriorityQueues.h24Performance.bandwidth

       unit name = bps
       formula = 8 * ; 8 /"
   ::= {pr1646v2Lan3FGVlanOutPQsH24PerformanceEntry 268435456}

pr1646v2Lan3FGVlanOutPQsD7Performance OBJECT-TYPE
   SYNTAX      SEQUENCE OF Pr1646v2Lan3FGVlanOutPQsD7PerformanceEntry
   MAX-ACCESS  not-accessible
   STATUS      current
   DESCRIPTION
      ""
   ::= {pr1646v2Lan3FGVlan 84344832}

pr1646v2Lan3FGVlanOutPQsD7PerformanceEntry OBJECT-TYPE
   SYNTAX      Pr1646v2Lan3FGVlanOutPQsD7PerformanceEntry
   MAX-ACCESS  not-accessible
   STATUS      current
   DESCRIPTION
      ""
   INDEX      { pr1646v2Lan3FGVlanTableIx,
                pr1646v2Lan3FGVlanOutPQsTableIx,
                pr1646v2Lan3FGVlanOutPQsD7PerformanceTableIx }
   ::= {pr1646v2Lan3FGVlanOutPQsD7Performance 1}

Pr1646v2Lan3FGVlanOutPQsD7PerformanceEntry ::=
   SEQUENCE
      {
      pr1646v2Lan3FGVlanOutPQsD7PerformanceTableIx
         TableIndex,
      pr1646v2Lan3FGVlanOutPQsD7PerformanceSysUpTime
         TimeTicks,
      pr1646v2Lan3FGVlanOutPQsD7PerformanceTotPkts
         Counter64,
      pr1646v2Lan3FGVlanOutPQsD7PerformanceDirTxPkts
         Counter64,
      pr1646v2Lan3FGVlanOutPQsD7PerformanceQdPkts
         Counter64,
      pr1646v2Lan3FGVlanOutPQsD7PerformanceDropPkts
         Counter64,
      pr1646v2Lan3FGVlanOutPQsD7PerformanceRDropPkts
         Counter64,
      pr1646v2Lan3FGVlanOutPQsD7PerformanceCirTxPkts
         Counter64,
      pr1646v2Lan3FGVlanOutPQsD7PerformanceEirTxPkts
         Counter64,
      pr1646v2Lan3FGVlanOutPQsD7PerformanceViolTxPkts
         Counter64,
      pr1646v2Lan3FGVlanOutPQsD7PerformanceTotOcts
         Counter64,
      pr1646v2Lan3FGVlanOutPQsD7PerformanceDirTxOcts
         Counter64,
      pr1646v2Lan3FGVlanOutPQsD7PerformanceQdOcts
         Counter64,
      pr1646v2Lan3FGVlanOutPQsD7PerformanceDropOcts
         Counter64,
      pr1646v2Lan3FGVlanOutPQsD7PerformanceRDropOcts
         Counter64,
      pr1646v2Lan3FGVlanOutPQsD7PerformanceCirTxOcts
         Counter64,
      pr1646v2Lan3FGVlanOutPQsD7PerformanceEirTxOcts
         Counter64,
      pr1646v2Lan3FGVlanOutPQsD7PerformanceViolTxOcts
         Counter64,
      pr1646v2Lan3FGVlanOutPQsD7PerformanceBandwidth
         Integer32
      }

pr1646v2Lan3FGVlanOutPQsD7PerformanceTableIx OBJECT-TYPE
   SYNTAX      TableIndex
   MAX-ACCESS  not-accessible
   STATUS      current
   DESCRIPTION
      ""
   ::= {pr1646v2Lan3FGVlanOutPQsD7PerformanceEntry 11}

pr1646v2Lan3FGVlanOutPQsD7PerformanceSysUpTime OBJECT-TYPE
   SYNTAX      TimeTicks
   MAX-ACCESS  read-only
   STATUS      current
   DESCRIPTION
      "Path: ethernet3.performance.vlan.outPriorityQueues.d7Performance.sysUpTime

       Time in centi-second."
   ::= {pr1646v2Lan3FGVlanOutPQsD7PerformanceEntry 16777216}

pr1646v2Lan3FGVlanOutPQsD7PerformanceTotPkts OBJECT-TYPE
   SYNTAX      Counter64
   MAX-ACCESS  read-only
   STATUS      current
   DESCRIPTION
      "Path: ethernet3.performance.vlan.outPriorityQueues.d7Performance.totalPkts

       64 bit unsigned wrappable counter."
   ::= {pr1646v2Lan3FGVlanOutPQsD7PerformanceEntry 234881024}

pr1646v2Lan3FGVlanOutPQsD7PerformanceDirTxPkts OBJECT-TYPE
   SYNTAX      Counter64
   MAX-ACCESS  read-only
   STATUS      current
   DESCRIPTION
      "Path: ethernet3.performance.vlan.outPriorityQueues.d7Performance.directTxPkts

       64 bit unsigned wrappable counter."
   ::= {pr1646v2Lan3FGVlanOutPQsD7PerformanceEntry 33554432}

pr1646v2Lan3FGVlanOutPQsD7PerformanceQdPkts OBJECT-TYPE
   SYNTAX      Counter64
   MAX-ACCESS  read-only
   STATUS      current
   DESCRIPTION
      "Path: ethernet3.performance.vlan.outPriorityQueues.d7Performance.queuedPkts

       64 bit unsigned wrappable counter."
   ::= {pr1646v2Lan3FGVlanOutPQsD7PerformanceEntry 50331648}

pr1646v2Lan3FGVlanOutPQsD7PerformanceDropPkts OBJECT-TYPE
   SYNTAX      Counter64
   MAX-ACCESS  read-only
   STATUS      current
   DESCRIPTION
      "Path: ethernet3.performance.vlan.outPriorityQueues.d7Performance.droppedPkts

       64 bit unsigned wrappable counter."
   ::= {pr1646v2Lan3FGVlanOutPQsD7PerformanceEntry 67108864}

pr1646v2Lan3FGVlanOutPQsD7PerformanceRDropPkts OBJECT-TYPE
   SYNTAX      Counter64
   MAX-ACCESS  read-only
   STATUS      current
   DESCRIPTION
      "Path: ethernet3.performance.vlan.outPriorityQueues.d7Performance.redDroppedPkts

       64 bit unsigned wrappable counter."
   ::= {pr1646v2Lan3FGVlanOutPQsD7PerformanceEntry 201326592}

pr1646v2Lan3FGVlanOutPQsD7PerformanceCirTxPkts OBJECT-TYPE
   SYNTAX      Counter64
   MAX-ACCESS  read-only
   STATUS      current
   DESCRIPTION
      "Path: ethernet3.performance.vlan.outPriorityQueues.d7Performance.cirTxPkts

       64 bit unsigned wrappable counter."
   ::= {pr1646v2Lan3FGVlanOutPQsD7PerformanceEntry 83886080}

pr1646v2Lan3FGVlanOutPQsD7PerformanceEirTxPkts OBJECT-TYPE
   SYNTAX      Counter64
   MAX-ACCESS  read-only
   STATUS      current
   DESCRIPTION
      "Path: ethernet3.performance.vlan.outPriorityQueues.d7Performance.eirTxPkts

       64 bit unsigned wrappable counter."
   ::= {pr1646v2Lan3FGVlanOutPQsD7PerformanceEntry 100663296}

pr1646v2Lan3FGVlanOutPQsD7PerformanceViolTxPkts OBJECT-TYPE
   SYNTAX      Counter64
   MAX-ACCESS  read-only
   STATUS      current
   DESCRIPTION
      "Path: ethernet3.performance.vlan.outPriorityQueues.d7Performance.violateTxPkts

       64 bit unsigned wrappable counter."
   ::= {pr1646v2Lan3FGVlanOutPQsD7PerformanceEntry 301989888}

pr1646v2Lan3FGVlanOutPQsD7PerformanceTotOcts OBJECT-TYPE
   SYNTAX      Counter64
   MAX-ACCESS  read-only
   STATUS      current
   DESCRIPTION
      "Path: ethernet3.performance.vlan.outPriorityQueues.d7Performance.totalOctets

       64 bit unsigned wrappable counter."
   ::= {pr1646v2Lan3FGVlanOutPQsD7PerformanceEntry 251658240}

pr1646v2Lan3FGVlanOutPQsD7PerformanceDirTxOcts OBJECT-TYPE
   SYNTAX      Counter64
   MAX-ACCESS  read-only
   STATUS      current
   DESCRIPTION
      "Path: ethernet3.performance.vlan.outPriorityQueues.d7Performance.directTxOctets

       64 bit unsigned wrappable counter."
   ::= {pr1646v2Lan3FGVlanOutPQsD7PerformanceEntry 117440512}

pr1646v2Lan3FGVlanOutPQsD7PerformanceQdOcts OBJECT-TYPE
   SYNTAX      Counter64
   MAX-ACCESS  read-only
   STATUS      current
   DESCRIPTION
      "Path: ethernet3.performance.vlan.outPriorityQueues.d7Performance.queuedOctets

       64 bit unsigned wrappable counter."
   ::= {pr1646v2Lan3FGVlanOutPQsD7PerformanceEntry 134217728}

pr1646v2Lan3FGVlanOutPQsD7PerformanceDropOcts OBJECT-TYPE
   SYNTAX      Counter64
   MAX-ACCESS  read-only
   STATUS      current
   DESCRIPTION
      "Path: ethernet3.performance.vlan.outPriorityQueues.d7Performance.droppedOctets

       64 bit unsigned wrappable counter."
   ::= {pr1646v2Lan3FGVlanOutPQsD7PerformanceEntry 150994944}

pr1646v2Lan3FGVlanOutPQsD7PerformanceRDropOcts OBJECT-TYPE
   SYNTAX      Counter64
   MAX-ACCESS  read-only
   STATUS      current
   DESCRIPTION
      "Path: ethernet3.performance.vlan.outPriorityQueues.d7Performance.redDroppedOctets

       64 bit unsigned wrappable counter."
   ::= {pr1646v2Lan3FGVlanOutPQsD7PerformanceEntry 218103808}

pr1646v2Lan3FGVlanOutPQsD7PerformanceCirTxOcts OBJECT-TYPE
   SYNTAX      Counter64
   MAX-ACCESS  read-only
   STATUS      current
   DESCRIPTION
      "Path: ethernet3.performance.vlan.outPriorityQueues.d7Performance.cirTxOctets

       64 bit unsigned wrappable counter."
   ::= {pr1646v2Lan3FGVlanOutPQsD7PerformanceEntry 167772160}

pr1646v2Lan3FGVlanOutPQsD7PerformanceEirTxOcts OBJECT-TYPE
   SYNTAX      Counter64
   MAX-ACCESS  read-only
   STATUS      current
   DESCRIPTION
      "Path: ethernet3.performance.vlan.outPriorityQueues.d7Performance.eirTxOctets

       64 bit unsigned wrappable counter."
   ::= {pr1646v2Lan3FGVlanOutPQsD7PerformanceEntry 184549376}

pr1646v2Lan3FGVlanOutPQsD7PerformanceViolTxOcts OBJECT-TYPE
   SYNTAX      Counter64
   MAX-ACCESS  read-only
   STATUS      current
   DESCRIPTION
      "Path: ethernet3.performance.vlan.outPriorityQueues.d7Performance.violateTxOctets

       64 bit unsigned wrappable counter."
   ::= {pr1646v2Lan3FGVlanOutPQsD7PerformanceEntry 318767104}

pr1646v2Lan3FGVlanOutPQsD7PerformanceBandwidth OBJECT-TYPE
   SYNTAX      Integer32
   MAX-ACCESS  read-only
   STATUS      current
   DESCRIPTION
      "Path: ethernet3.performance.vlan.outPriorityQueues.d7Performance.bandwidth

       unit name = bps
       formula = 8 * ; 8 /"
   ::= {pr1646v2Lan3FGVlanOutPQsD7PerformanceEntry 268435456}


pr1646v2Lan3FGPPPoE OBJECT IDENTIFIER ::= {pr1646v2Lan3FG 53}

pr1646v2Lan3FGPPPoESSCTable OBJECT-TYPE
   SYNTAX      SEQUENCE OF Pr1646v2Lan3FGPPPoEEntry
   MAX-ACCESS  not-accessible
   STATUS      current
   DESCRIPTION
      ""
   ::= {pr1646v2Lan3FGPPPoE 1}

pr1646v2Lan3FGPPPoEEntry OBJECT-TYPE
   SYNTAX      Pr1646v2Lan3FGPPPoEEntry
   MAX-ACCESS  not-accessible
   STATUS      current
   DESCRIPTION
      ""
   INDEX      { pr1646v2Lan3FGPPPoETableIx }
   ::= {pr1646v2Lan3FGPPPoESSCTable 1}

Pr1646v2Lan3FGPPPoEEntry ::=
   SEQUENCE
      {
      pr1646v2Lan3FGPPPoETableIx
         TableIndex,
      pr1646v2Lan3FGPPPoEName
         DisplayString,
      pr1646v2Lan3FGPPPoEMCInOctets
         Counter64,
      pr1646v2Lan3FGPPPoEMCInUcast
         Counter64,
      pr1646v2Lan3FGPPPoEMCInNUcastPkts
         Counter64,
      pr1646v2Lan3FGPPPoEMCInBcastPkts
         Counter64,
      pr1646v2Lan3FGPPPoEMCInMcastPkts
         Counter64,
      pr1646v2Lan3FGPPPoEMCInDiscards
         Counter64,
      pr1646v2Lan3FGPPPoEMCInErrors
         Counter64,
      pr1646v2Lan3FGPPPoEMCInUnknownProtos
         Counter64,
      pr1646v2Lan3FGPPPoEMCInDropEx
         Counter64,
      pr1646v2Lan3FGPPPoEMCInDropNoMac
         Counter64,
      pr1646v2Lan3FGPPPoEMCInDropNUCast
         Counter64,
      pr1646v2Lan3FGPPPoEMCInDropFilter
         Counter64,
      pr1646v2Lan3FGPPPoEMCInBandwidth15sec
         Integer32,
      pr1646v2Lan3FGPPPoEMCInBandwidth30sec
         Integer32,
      pr1646v2Lan3FGPPPoEMCInBandwidth1min
         Integer32,
      pr1646v2Lan3FGPPPoEMCInBandwidth2min
         Integer32,
      pr1646v2Lan3FGPPPoEMCInBandwidth5min
         Integer32,
      pr1646v2Lan3FGPPPoEMCOutOctets
         Counter64,
      pr1646v2Lan3FGPPPoEMCOutUcastPkts
         Counter64,
      pr1646v2Lan3FGPPPoEMCOutNUcastPkts
         Counter64,
      pr1646v2Lan3FGPPPoEMCOutBcastPkts
         Counter64,
      pr1646v2Lan3FGPPPoEMCOutMcastPkts
         Counter64,
      pr1646v2Lan3FGPPPoEMCOutDiscards
         Counter64,
      pr1646v2Lan3FGPPPoEMCOutErrors
         Counter64,
      pr1646v2Lan3FGPPPoEMCOutQLen
         Counter32,
      pr1646v2Lan3FGPPPoEMCOutDropEx
         Counter64,
      pr1646v2Lan3FGPPPoEMCOutDropNoArp
         Counter64,
      pr1646v2Lan3FGPPPoEMCOutDropFilter
         Counter64,
      pr1646v2Lan3FGPPPoEMCOutBandwidth15sec
         Integer32,
      pr1646v2Lan3FGPPPoEMCOutBandwidth30sec
         Integer32,
      pr1646v2Lan3FGPPPoEMCOutBandwidth1min
         Integer32,
      pr1646v2Lan3FGPPPoEMCOutBandwidth2min
         Integer32,
      pr1646v2Lan3FGPPPoEMCOutBandwidth5min
         Integer32,
      pr1646v2Lan3FGPPPoEPppLinkMonitoringRequestsSent
         Gauge32,
      pr1646v2Lan3FGPPPoEPppLinkMonitoringRepliesRcvd
         Gauge32,
      pr1646v2Lan3FGPPPoEPppLinkMonitoringRequestsRcvd
         Gauge32,
      pr1646v2Lan3FGPPPoEPppLinkMonitoringRepliesSent
         Gauge32
      }

pr1646v2Lan3FGPPPoETableIx OBJECT-TYPE
   SYNTAX      TableIndex
   MAX-ACCESS  not-accessible
   STATUS      current
   DESCRIPTION
      ""
   ::= {pr1646v2Lan3FGPPPoEEntry 11}

pr1646v2Lan3FGPPPoEName OBJECT-TYPE
   SYNTAX      DisplayString
   MAX-ACCESS  read-only
   STATUS      current
   DESCRIPTION
      "Path: ethernet3.performance.pppoEClient.name"
   ::= {pr1646v2Lan3FGPPPoEEntry 16777216}

pr1646v2Lan3FGPPPoEMCInOctets OBJECT-TYPE
   SYNTAX      Counter64
   MAX-ACCESS  read-only
   STATUS      current
   DESCRIPTION
      "Path: ethernet3.performance.pppoEClient.mibCounters.ifInOctets

       64 bit unsigned wrappable counter."
   ::= {pr1646v2Lan3FGPPPoEEntry 40697856}

pr1646v2Lan3FGPPPoEMCInUcast OBJECT-TYPE
   SYNTAX      Counter64
   MAX-ACCESS  read-only
   STATUS      current
   DESCRIPTION
      "Path: ethernet3.performance.pppoEClient.mibCounters.ifInUcastPkts

       64 bit unsigned wrappable counter."
   ::= {pr1646v2Lan3FGPPPoEEntry 40763392}

pr1646v2Lan3FGPPPoEMCInNUcastPkts OBJECT-TYPE
   SYNTAX      Counter64
   MAX-ACCESS  read-only
   STATUS      current
   DESCRIPTION
      "Path: ethernet3.performance.pppoEClient.mibCounters.ifInNUcastPkts

       64 bit unsigned wrappable counter."
   ::= {pr1646v2Lan3FGPPPoEEntry 40828928}

pr1646v2Lan3FGPPPoEMCInBcastPkts OBJECT-TYPE
   SYNTAX      Counter64
   MAX-ACCESS  read-only
   STATUS      current
   DESCRIPTION
      "Path: ethernet3.performance.pppoEClient.mibCounters.ifInBcastPkts

       64 bit unsigned wrappable counter."
   ::= {pr1646v2Lan3FGPPPoEEntry 47382528}

pr1646v2Lan3FGPPPoEMCInMcastPkts OBJECT-TYPE
   SYNTAX      Counter64
   MAX-ACCESS  read-only
   STATUS      current
   DESCRIPTION
      "Path: ethernet3.performance.pppoEClient.mibCounters.ifInMcastPkts

       64 bit unsigned wrappable counter."
   ::= {pr1646v2Lan3FGPPPoEEntry 48037888}

pr1646v2Lan3FGPPPoEMCInDiscards OBJECT-TYPE
   SYNTAX      Counter64
   MAX-ACCESS  read-only
   STATUS      current
   DESCRIPTION
      "Path: ethernet3.performance.pppoEClient.mibCounters.ifInDiscards

       64 bit unsigned wrappable counter."
   ::= {pr1646v2Lan3FGPPPoEEntry 40894464}

pr1646v2Lan3FGPPPoEMCInErrors OBJECT-TYPE
   SYNTAX      Counter64
   MAX-ACCESS  read-only
   STATUS      current
   DESCRIPTION
      "Path: ethernet3.performance.pppoEClient.mibCounters.ifInErrors

       64 bit unsigned wrappable counter."
   ::= {pr1646v2Lan3FGPPPoEEntry 40960000}

pr1646v2Lan3FGPPPoEMCInUnknownProtos OBJECT-TYPE
   SYNTAX      Counter64
   MAX-ACCESS  read-only
   STATUS      current
   DESCRIPTION
      "Path: ethernet3.performance.pppoEClient.mibCounters.ifInUnknownProtos

       64 bit unsigned wrappable counter."
   ::= {pr1646v2Lan3FGPPPoEEntry 41025536}

pr1646v2Lan3FGPPPoEMCInDropEx OBJECT-TYPE
   SYNTAX      Counter64
   MAX-ACCESS  read-only
   STATUS      current
   DESCRIPTION
      "Path: ethernet3.performance.pppoEClient.mibCounters.ifInDropLevelExceeded

       64 bit unsigned wrappable counter."
   ::= {pr1646v2Lan3FGPPPoEEntry 42074112}

pr1646v2Lan3FGPPPoEMCInDropNoMac OBJECT-TYPE
   SYNTAX      Counter64
   MAX-ACCESS  read-only
   STATUS      current
   DESCRIPTION
      "Path: ethernet3.performance.pppoEClient.mibCounters.ifInDiscardsNoMacFit

       64 bit unsigned wrappable counter."
   ::= {pr1646v2Lan3FGPPPoEEntry 42270720}

pr1646v2Lan3FGPPPoEMCInDropNUCast OBJECT-TYPE
   SYNTAX      Counter64
   MAX-ACCESS  read-only
   STATUS      current
   DESCRIPTION
      "Path: ethernet3.performance.pppoEClient.mibCounters.ifInDiscardsNUCast

       64 bit unsigned wrappable counter."
   ::= {pr1646v2Lan3FGPPPoEEntry 42467328}

pr1646v2Lan3FGPPPoEMCInDropFilter OBJECT-TYPE
   SYNTAX      Counter64
   MAX-ACCESS  read-only
   STATUS      current
   DESCRIPTION
      "Path: ethernet3.performance.pppoEClient.mibCounters.ifInDiscardsFilter

       64 bit unsigned wrappable counter."
   ::= {pr1646v2Lan3FGPPPoEEntry 42532864}

pr1646v2Lan3FGPPPoEMCInBandwidth15sec OBJECT-TYPE
   SYNTAX      Integer32
   MAX-ACCESS  read-only
   STATUS      current
   DESCRIPTION
      "Path: ethernet3.performance.pppoEClient.mibCounters.ifInBandwidth.15sec

       unit name = bps
       formula = 8 * ; 8 /"
   ::= {pr1646v2Lan3FGPPPoEEntry 45417728}

pr1646v2Lan3FGPPPoEMCInBandwidth30sec OBJECT-TYPE
   SYNTAX      Integer32
   MAX-ACCESS  read-only
   STATUS      current
   DESCRIPTION
      "Path: ethernet3.performance.pppoEClient.mibCounters.ifInBandwidth.30sec

       unit name = bps
       formula = 8 * ; 8 /"
   ::= {pr1646v2Lan3FGPPPoEEntry 45419008}

pr1646v2Lan3FGPPPoEMCInBandwidth1min OBJECT-TYPE
   SYNTAX      Integer32
   MAX-ACCESS  read-only
   STATUS      current
   DESCRIPTION
      "Path: ethernet3.performance.pppoEClient.mibCounters.ifInBandwidth.1min

       unit name = bps
       formula = 8 * ; 8 /"
   ::= {pr1646v2Lan3FGPPPoEEntry 45421568}

pr1646v2Lan3FGPPPoEMCInBandwidth2min OBJECT-TYPE
   SYNTAX      Integer32
   MAX-ACCESS  read-only
   STATUS      current
   DESCRIPTION
      "Path: ethernet3.performance.pppoEClient.mibCounters.ifInBandwidth.2min

       unit name = bps
       formula = 8 * ; 8 /"
   ::= {pr1646v2Lan3FGPPPoEEntry 45426688}

pr1646v2Lan3FGPPPoEMCInBandwidth5min OBJECT-TYPE
   SYNTAX      Integer32
   MAX-ACCESS  read-only
   STATUS      current
   DESCRIPTION
      "Path: ethernet3.performance.pppoEClient.mibCounters.ifInBandwidth.5min

       unit name = bps
       formula = 8 * ; 8 /"
   ::= {pr1646v2Lan3FGPPPoEEntry 45442048}

pr1646v2Lan3FGPPPoEMCOutOctets OBJECT-TYPE
   SYNTAX      Counter64
   MAX-ACCESS  read-only
   STATUS      current
   DESCRIPTION
      "Path: ethernet3.performance.pppoEClient.mibCounters.ifOutOctets

       64 bit unsigned wrappable counter."
   ::= {pr1646v2Lan3FGPPPoEEntry 41091072}

pr1646v2Lan3FGPPPoEMCOutUcastPkts OBJECT-TYPE
   SYNTAX      Counter64
   MAX-ACCESS  read-only
   STATUS      current
   DESCRIPTION
      "Path: ethernet3.performance.pppoEClient.mibCounters.ifOutUcastPkts

       64 bit unsigned wrappable counter."
   ::= {pr1646v2Lan3FGPPPoEEntry 41156608}

pr1646v2Lan3FGPPPoEMCOutNUcastPkts OBJECT-TYPE
   SYNTAX      Counter64
   MAX-ACCESS  read-only
   STATUS      current
   DESCRIPTION
      "Path: ethernet3.performance.pppoEClient.mibCounters.ifOutNUcastPkts

       64 bit unsigned wrappable counter."
   ::= {pr1646v2Lan3FGPPPoEEntry 41222144}

pr1646v2Lan3FGPPPoEMCOutBcastPkts OBJECT-TYPE
   SYNTAX      Counter64
   MAX-ACCESS  read-only
   STATUS      current
   DESCRIPTION
      "Path: ethernet3.performance.pppoEClient.mibCounters.ifOutBcastPkts

       64 bit unsigned wrappable counter."
   ::= {pr1646v2Lan3FGPPPoEEntry 47775744}

pr1646v2Lan3FGPPPoEMCOutMcastPkts OBJECT-TYPE
   SYNTAX      Counter64
   MAX-ACCESS  read-only
   STATUS      current
   DESCRIPTION
      "Path: ethernet3.performance.pppoEClient.mibCounters.ifOutMcastPkts

       64 bit unsigned wrappable counter."
   ::= {pr1646v2Lan3FGPPPoEEntry 48431104}

pr1646v2Lan3FGPPPoEMCOutDiscards OBJECT-TYPE
   SYNTAX      Counter64
   MAX-ACCESS  read-only
   STATUS      current
   DESCRIPTION
      "Path: ethernet3.performance.pppoEClient.mibCounters.ifOutDiscards

       64 bit unsigned wrappable counter."
   ::= {pr1646v2Lan3FGPPPoEEntry 41287680}

pr1646v2Lan3FGPPPoEMCOutErrors OBJECT-TYPE
   SYNTAX      Counter64
   MAX-ACCESS  read-only
   STATUS      current
   DESCRIPTION
      "Path: ethernet3.performance.pppoEClient.mibCounters.ifOutErrors

       64 bit unsigned wrappable counter."
   ::= {pr1646v2Lan3FGPPPoEEntry 41353216}

pr1646v2Lan3FGPPPoEMCOutQLen OBJECT-TYPE
   SYNTAX      Counter32
   MAX-ACCESS  read-only
   STATUS      current
   DESCRIPTION
      "Path: ethernet3.performance.pppoEClient.mibCounters.ifOutQLen

       32 bit unsigned wrappable counter."
   ::= {pr1646v2Lan3FGPPPoEEntry 41418752}

pr1646v2Lan3FGPPPoEMCOutDropEx OBJECT-TYPE
   SYNTAX      Counter64
   MAX-ACCESS  read-only
   STATUS      current
   DESCRIPTION
      "Path: ethernet3.performance.pppoEClient.mibCounters.ifOutDropLevelExceeded

       64 bit unsigned wrappable counter."
   ::= {pr1646v2Lan3FGPPPoEEntry 41484288}

pr1646v2Lan3FGPPPoEMCOutDropNoArp OBJECT-TYPE
   SYNTAX      Counter64
   MAX-ACCESS  read-only
   STATUS      current
   DESCRIPTION
      "Path: ethernet3.performance.pppoEClient.mibCounters.ifOutDiscardsNoArp

       64 bit unsigned wrappable counter."
   ::= {pr1646v2Lan3FGPPPoEEntry 42336256}

pr1646v2Lan3FGPPPoEMCOutDropFilter OBJECT-TYPE
   SYNTAX      Counter64
   MAX-ACCESS  read-only
   STATUS      current
   DESCRIPTION
      "Path: ethernet3.performance.pppoEClient.mibCounters.ifOutDiscardsFilter

       64 bit unsigned wrappable counter."
   ::= {pr1646v2Lan3FGPPPoEEntry 42598400}

pr1646v2Lan3FGPPPoEMCOutBandwidth15sec OBJECT-TYPE
   SYNTAX      Integer32
   MAX-ACCESS  read-only
   STATUS      current
   DESCRIPTION
      "Path: ethernet3.performance.pppoEClient.mibCounters.ifOutBandwidth.15sec

       unit name = bps
       formula = 8 * ; 8 /"
   ::= {pr1646v2Lan3FGPPPoEEntry 45483264}

pr1646v2Lan3FGPPPoEMCOutBandwidth30sec OBJECT-TYPE
   SYNTAX      Integer32
   MAX-ACCESS  read-only
   STATUS      current
   DESCRIPTION
      "Path: ethernet3.performance.pppoEClient.mibCounters.ifOutBandwidth.30sec

       unit name = bps
       formula = 8 * ; 8 /"
   ::= {pr1646v2Lan3FGPPPoEEntry 45484544}

pr1646v2Lan3FGPPPoEMCOutBandwidth1min OBJECT-TYPE
   SYNTAX      Integer32
   MAX-ACCESS  read-only
   STATUS      current
   DESCRIPTION
      "Path: ethernet3.performance.pppoEClient.mibCounters.ifOutBandwidth.1min

       unit name = bps
       formula = 8 * ; 8 /"
   ::= {pr1646v2Lan3FGPPPoEEntry 45487104}

pr1646v2Lan3FGPPPoEMCOutBandwidth2min OBJECT-TYPE
   SYNTAX      Integer32
   MAX-ACCESS  read-only
   STATUS      current
   DESCRIPTION
      "Path: ethernet3.performance.pppoEClient.mibCounters.ifOutBandwidth.2min

       unit name = bps
       formula = 8 * ; 8 /"
   ::= {pr1646v2Lan3FGPPPoEEntry 45492224}

pr1646v2Lan3FGPPPoEMCOutBandwidth5min OBJECT-TYPE
   SYNTAX      Integer32
   MAX-ACCESS  read-only
   STATUS      current
   DESCRIPTION
      "Path: ethernet3.performance.pppoEClient.mibCounters.ifOutBandwidth.5min

       unit name = bps
       formula = 8 * ; 8 /"
   ::= {pr1646v2Lan3FGPPPoEEntry 45507584}

pr1646v2Lan3FGPPPoEPppLinkMonitoringRequestsSent OBJECT-TYPE
   SYNTAX      Gauge32
   MAX-ACCESS  read-only
   STATUS      current
   DESCRIPTION
      "Path: ethernet3.performance.pppoEClient.ppp.linkMonitoring.requestsSent

       32 bit unsigned gauge value."
   ::= {pr1646v2Lan3FGPPPoEEntry 50397440}

pr1646v2Lan3FGPPPoEPppLinkMonitoringRepliesRcvd OBJECT-TYPE
   SYNTAX      Gauge32
   MAX-ACCESS  read-only
   STATUS      current
   DESCRIPTION
      "Path: ethernet3.performance.pppoEClient.ppp.linkMonitoring.repliesRcvd

       32 bit unsigned gauge value."
   ::= {pr1646v2Lan3FGPPPoEEntry 50397696}

pr1646v2Lan3FGPPPoEPppLinkMonitoringRequestsRcvd OBJECT-TYPE
   SYNTAX      Gauge32
   MAX-ACCESS  read-only
   STATUS      current
   DESCRIPTION
      "Path: ethernet3.performance.pppoEClient.ppp.linkMonitoring.requestsRcvd

       32 bit unsigned gauge value."
   ::= {pr1646v2Lan3FGPPPoEEntry 50397952}

pr1646v2Lan3FGPPPoEPppLinkMonitoringRepliesSent OBJECT-TYPE
   SYNTAX      Gauge32
   MAX-ACCESS  read-only
   STATUS      current
   DESCRIPTION
      "Path: ethernet3.performance.pppoEClient.ppp.linkMonitoring.repliesSent

       32 bit unsigned gauge value."
   ::= {pr1646v2Lan3FGPPPoEEntry 50398208}

pr1646v2Lan3FGPPPoEMCH2P OBJECT-TYPE
   SYNTAX      SEQUENCE OF Pr1646v2Lan3FGPPPoEMCH2PEntry
   MAX-ACCESS  not-accessible
   STATUS      current
   DESCRIPTION
      ""
   ::= {pr1646v2Lan3FGPPPoE 41549824}

pr1646v2Lan3FGPPPoEMCH2PEntry OBJECT-TYPE
   SYNTAX      Pr1646v2Lan3FGPPPoEMCH2PEntry
   MAX-ACCESS  not-accessible
   STATUS      current
   DESCRIPTION
      ""
   INDEX      { pr1646v2Lan3FGPPPoETableIx,
                pr1646v2Lan3FGPPPoEMCH2PTableIx }
   ::= {pr1646v2Lan3FGPPPoEMCH2P 1}

Pr1646v2Lan3FGPPPoEMCH2PEntry ::=
   SEQUENCE
      {
      pr1646v2Lan3FGPPPoEMCH2PTableIx
         TableIndex,
      pr1646v2Lan3FGPPPoEMCH2PSysUpTime
         TimeTicks,
      pr1646v2Lan3FGPPPoEMCH2PIfUpTime
         TimeTicks,
      pr1646v2Lan3FGPPPoEMCH2PIfStatChanges
         Counter32,
      pr1646v2Lan3FGPPPoEMCH2PIfInOctets
         Counter64,
      pr1646v2Lan3FGPPPoEMCH2PIfInUCPkts
         Counter64,
      pr1646v2Lan3FGPPPoEMCH2PIfInNUCPkts
         Counter64,
      pr1646v2Lan3FGPPPoEMCH2PIfInBCPkts
         Counter64,
      pr1646v2Lan3FGPPPoEMCH2PIfInMCPkts
         Counter64,
      pr1646v2Lan3FGPPPoEMCH2PIfInDiscards
         Counter64,
      pr1646v2Lan3FGPPPoEMCH2PIfInErrors
         Counter64,
      pr1646v2Lan3FGPPPoEMCH2PIfInUnkwn
         Counter64,
      pr1646v2Lan3FGPPPoEMCH2PInDropEx
         Counter64,
      pr1646v2Lan3FGPPPoEMCH2PInDropNoMac
         Counter64,
      pr1646v2Lan3FGPPPoEMCH2PInDropNUCast
         Counter64,
      pr1646v2Lan3FGPPPoEMCH2PInDropFilter
         Counter64,
      pr1646v2Lan3FGPPPoEMCH2PIfInBandwidth
         Integer32,
      pr1646v2Lan3FGPPPoEMCH2PIfOutOctets
         Counter64,
      pr1646v2Lan3FGPPPoEMCH2PIfOutUCPkts
         Counter64,
      pr1646v2Lan3FGPPPoEMCH2PIfOutNUCPkts
         Counter64,
      pr1646v2Lan3FGPPPoEMCH2PIfOutBCPkts
         Counter64,
      pr1646v2Lan3FGPPPoEMCH2PIfOutMCPkts
         Counter64,
      pr1646v2Lan3FGPPPoEMCH2PIfOutDiscards
         Counter64,
      pr1646v2Lan3FGPPPoEMCH2PIfOutErrors
         Counter64,
      pr1646v2Lan3FGPPPoEMCH2POutDropEx
         Counter64,
      pr1646v2Lan3FGPPPoEMCH2POutDropNoArp
         Counter64,
      pr1646v2Lan3FGPPPoEMCH2POutDropFilter
         Counter64,
      pr1646v2Lan3FGPPPoEMCH2PIfOutBandwidth
         Integer32,
      pr1646v2Lan3FGPPPoEMCH2PIfErrSec
         Counter32
      }

pr1646v2Lan3FGPPPoEMCH2PTableIx OBJECT-TYPE
   SYNTAX      TableIndex
   MAX-ACCESS  not-accessible
   STATUS      current
   DESCRIPTION
      ""
   ::= {pr1646v2Lan3FGPPPoEMCH2PEntry 11}

pr1646v2Lan3FGPPPoEMCH2PSysUpTime OBJECT-TYPE
   SYNTAX      TimeTicks
   MAX-ACCESS  read-only
   STATUS      current
   DESCRIPTION
      "Path: ethernet3.performance.pppoEClient.mibCounters.h2Performance.sysUpTime

       Time in centi-second."
   ::= {pr1646v2Lan3FGPPPoEMCH2PEntry 16777216}

pr1646v2Lan3FGPPPoEMCH2PIfUpTime OBJECT-TYPE
   SYNTAX      TimeTicks
   MAX-ACCESS  read-only
   STATUS      current
   DESCRIPTION
      "Path: ethernet3.performance.pppoEClient.mibCounters.h2Performance.ifUpTime

       Time in centi-second."
   ::= {pr1646v2Lan3FGPPPoEMCH2PEntry 33554432}

pr1646v2Lan3FGPPPoEMCH2PIfStatChanges OBJECT-TYPE
   SYNTAX      Counter32
   MAX-ACCESS  read-only
   STATUS      current
   DESCRIPTION
      "Path: ethernet3.performance.pppoEClient.mibCounters.h2Performance.ifStatusChanges

       32 bit unsigned wrappable counter."
   ::= {pr1646v2Lan3FGPPPoEMCH2PEntry 50331648}

pr1646v2Lan3FGPPPoEMCH2PIfInOctets OBJECT-TYPE
   SYNTAX      Counter64
   MAX-ACCESS  read-only
   STATUS      current
   DESCRIPTION
      "Path: ethernet3.performance.pppoEClient.mibCounters.h2Performance.ifInOctets

       64 bit unsigned wrappable counter."
   ::= {pr1646v2Lan3FGPPPoEMCH2PEntry 67108864}

pr1646v2Lan3FGPPPoEMCH2PIfInUCPkts OBJECT-TYPE
   SYNTAX      Counter64
   MAX-ACCESS  read-only
   STATUS      current
   DESCRIPTION
      "Path: ethernet3.performance.pppoEClient.mibCounters.h2Performance.ifInUcastPkts

       64 bit unsigned wrappable counter."
   ::= {pr1646v2Lan3FGPPPoEMCH2PEntry 83886080}

pr1646v2Lan3FGPPPoEMCH2PIfInNUCPkts OBJECT-TYPE
   SYNTAX      Counter64
   MAX-ACCESS  read-only
   STATUS      current
   DESCRIPTION
      "Path: ethernet3.performance.pppoEClient.mibCounters.h2Performance.ifInNUcastPkts

       64 bit unsigned wrappable counter."
   ::= {pr1646v2Lan3FGPPPoEMCH2PEntry 100663296}

pr1646v2Lan3FGPPPoEMCH2PIfInBCPkts OBJECT-TYPE
   SYNTAX      Counter64
   MAX-ACCESS  read-only
   STATUS      current
   DESCRIPTION
      "Path: ethernet3.performance.pppoEClient.mibCounters.h2Performance.ifInBcastPkts

       64 bit unsigned wrappable counter."
   ::= {pr1646v2Lan3FGPPPoEMCH2PEntry 419430400}

pr1646v2Lan3FGPPPoEMCH2PIfInMCPkts OBJECT-TYPE
   SYNTAX      Counter64
   MAX-ACCESS  read-only
   STATUS      current
   DESCRIPTION
      "Path: ethernet3.performance.pppoEClient.mibCounters.h2Performance.ifInMcastPkts

       64 bit unsigned wrappable counter."
   ::= {pr1646v2Lan3FGPPPoEMCH2PEntry 436207616}

pr1646v2Lan3FGPPPoEMCH2PIfInDiscards OBJECT-TYPE
   SYNTAX      Counter64
   MAX-ACCESS  read-only
   STATUS      current
   DESCRIPTION
      "Path: ethernet3.performance.pppoEClient.mibCounters.h2Performance.ifInDiscards

       64 bit unsigned wrappable counter."
   ::= {pr1646v2Lan3FGPPPoEMCH2PEntry 117440512}

pr1646v2Lan3FGPPPoEMCH2PIfInErrors OBJECT-TYPE
   SYNTAX      Counter64
   MAX-ACCESS  read-only
   STATUS      current
   DESCRIPTION
      "Path: ethernet3.performance.pppoEClient.mibCounters.h2Performance.ifInErrors

       64 bit unsigned wrappable counter."
   ::= {pr1646v2Lan3FGPPPoEMCH2PEntry 134217728}

pr1646v2Lan3FGPPPoEMCH2PIfInUnkwn OBJECT-TYPE
   SYNTAX      Counter64
   MAX-ACCESS  read-only
   STATUS      current
   DESCRIPTION
      "Path: ethernet3.performance.pppoEClient.mibCounters.h2Performance.ifInUnknownProtos

       64 bit unsigned wrappable counter."
   ::= {pr1646v2Lan3FGPPPoEMCH2PEntry 150994944}

pr1646v2Lan3FGPPPoEMCH2PInDropEx OBJECT-TYPE
   SYNTAX      Counter64
   MAX-ACCESS  read-only
   STATUS      current
   DESCRIPTION
      "Path: ethernet3.performance.pppoEClient.mibCounters.h2Performance.ifInDropLevelExceeded

       64 bit unsigned wrappable counter."
   ::= {pr1646v2Lan3FGPPPoEMCH2PEntry 335544320}

pr1646v2Lan3FGPPPoEMCH2PInDropNoMac OBJECT-TYPE
   SYNTAX      Counter64
   MAX-ACCESS  read-only
   STATUS      current
   DESCRIPTION
      "Path: ethernet3.performance.pppoEClient.mibCounters.h2Performance.fInDiscardsNoMacFit

       64 bit unsigned wrappable counter."
   ::= {pr1646v2Lan3FGPPPoEMCH2PEntry 301989888}

pr1646v2Lan3FGPPPoEMCH2PInDropNUCast OBJECT-TYPE
   SYNTAX      Counter64
   MAX-ACCESS  read-only
   STATUS      current
   DESCRIPTION
      "Path: ethernet3.performance.pppoEClient.mibCounters.h2Performance.fInDiscardsNUCast

       64 bit unsigned wrappable counter."
   ::= {pr1646v2Lan3FGPPPoEMCH2PEntry 318767104}

pr1646v2Lan3FGPPPoEMCH2PInDropFilter OBJECT-TYPE
   SYNTAX      Counter64
   MAX-ACCESS  read-only
   STATUS      current
   DESCRIPTION
      "Path: ethernet3.performance.pppoEClient.mibCounters.h2Performance.fInDiscardsFilter

       64 bit unsigned wrappable counter."
   ::= {pr1646v2Lan3FGPPPoEMCH2PEntry 385875968}

pr1646v2Lan3FGPPPoEMCH2PIfInBandwidth OBJECT-TYPE
   SYNTAX      Integer32
   MAX-ACCESS  read-only
   STATUS      current
   DESCRIPTION
      "Path: ethernet3.performance.pppoEClient.mibCounters.h2Performance.ifInBandwidth

       unit name = bps
       formula = 8 * ; 8 /"
   ::= {pr1646v2Lan3FGPPPoEMCH2PEntry 268435456}

pr1646v2Lan3FGPPPoEMCH2PIfOutOctets OBJECT-TYPE
   SYNTAX      Counter64
   MAX-ACCESS  read-only
   STATUS      current
   DESCRIPTION
      "Path: ethernet3.performance.pppoEClient.mibCounters.h2Performance.ifOutOctets

       64 bit unsigned wrappable counter."
   ::= {pr1646v2Lan3FGPPPoEMCH2PEntry 167772160}

pr1646v2Lan3FGPPPoEMCH2PIfOutUCPkts OBJECT-TYPE
   SYNTAX      Counter64
   MAX-ACCESS  read-only
   STATUS      current
   DESCRIPTION
      "Path: ethernet3.performance.pppoEClient.mibCounters.h2Performance.ifOutUcastPkts

       64 bit unsigned wrappable counter."
   ::= {pr1646v2Lan3FGPPPoEMCH2PEntry 184549376}

pr1646v2Lan3FGPPPoEMCH2PIfOutNUCPkts OBJECT-TYPE
   SYNTAX      Counter64
   MAX-ACCESS  read-only
   STATUS      current
   DESCRIPTION
      "Path: ethernet3.performance.pppoEClient.mibCounters.h2Performance.ifOutNUcastPkts

       64 bit unsigned wrappable counter."
   ::= {pr1646v2Lan3FGPPPoEMCH2PEntry 201326592}

pr1646v2Lan3FGPPPoEMCH2PIfOutBCPkts OBJECT-TYPE
   SYNTAX      Counter64
   MAX-ACCESS  read-only
   STATUS      current
   DESCRIPTION
      "Path: ethernet3.performance.pppoEClient.mibCounters.h2Performance.ifOutBcastPkts

       64 bit unsigned wrappable counter."
   ::= {pr1646v2Lan3FGPPPoEMCH2PEntry 452984832}

pr1646v2Lan3FGPPPoEMCH2PIfOutMCPkts OBJECT-TYPE
   SYNTAX      Counter64
   MAX-ACCESS  read-only
   STATUS      current
   DESCRIPTION
      "Path: ethernet3.performance.pppoEClient.mibCounters.h2Performance.ifOutMcastPkts

       64 bit unsigned wrappable counter."
   ::= {pr1646v2Lan3FGPPPoEMCH2PEntry 469762048}

pr1646v2Lan3FGPPPoEMCH2PIfOutDiscards OBJECT-TYPE
   SYNTAX      Counter64
   MAX-ACCESS  read-only
   STATUS      current
   DESCRIPTION
      "Path: ethernet3.performance.pppoEClient.mibCounters.h2Performance.ifOutDiscards

       64 bit unsigned wrappable counter."
   ::= {pr1646v2Lan3FGPPPoEMCH2PEntry 218103808}

pr1646v2Lan3FGPPPoEMCH2PIfOutErrors OBJECT-TYPE
   SYNTAX      Counter64
   MAX-ACCESS  read-only
   STATUS      current
   DESCRIPTION
      "Path: ethernet3.performance.pppoEClient.mibCounters.h2Performance.ifOutErrors

       64 bit unsigned wrappable counter."
   ::= {pr1646v2Lan3FGPPPoEMCH2PEntry 234881024}

pr1646v2Lan3FGPPPoEMCH2POutDropEx OBJECT-TYPE
   SYNTAX      Counter64
   MAX-ACCESS  read-only
   STATUS      current
   DESCRIPTION
      "Path: ethernet3.performance.pppoEClient.mibCounters.h2Performance.ifOutDropLevelExceeded

       64 bit unsigned wrappable counter."
   ::= {pr1646v2Lan3FGPPPoEMCH2PEntry 352321536}

pr1646v2Lan3FGPPPoEMCH2POutDropNoArp OBJECT-TYPE
   SYNTAX      Counter64
   MAX-ACCESS  read-only
   STATUS      current
   DESCRIPTION
      "Path: ethernet3.performance.pppoEClient.mibCounters.h2Performance.ifOutDiscardsNoArp

       64 bit unsigned wrappable counter."
   ::= {pr1646v2Lan3FGPPPoEMCH2PEntry 369098752}

pr1646v2Lan3FGPPPoEMCH2POutDropFilter OBJECT-TYPE
   SYNTAX      Counter64
   MAX-ACCESS  read-only
   STATUS      current
   DESCRIPTION
      "Path: ethernet3.performance.pppoEClient.mibCounters.h2Performance.ifOutDiscardsFilter

       64 bit unsigned wrappable counter."
   ::= {pr1646v2Lan3FGPPPoEMCH2PEntry 402653184}

pr1646v2Lan3FGPPPoEMCH2PIfOutBandwidth OBJECT-TYPE
   SYNTAX      Integer32
   MAX-ACCESS  read-only
   STATUS      current
   DESCRIPTION
      "Path: ethernet3.performance.pppoEClient.mibCounters.h2Performance.ifOutBandwidth

       unit name = bps
       formula = 8 * ; 8 /"
   ::= {pr1646v2Lan3FGPPPoEMCH2PEntry 285212672}

pr1646v2Lan3FGPPPoEMCH2PIfErrSec OBJECT-TYPE
   SYNTAX      Counter32
   MAX-ACCESS  read-only
   STATUS      current
   DESCRIPTION
      "Path: ethernet3.performance.pppoEClient.mibCounters.h2Performance.ifErrSec

       32 bit unsigned wrappable counter."
   ::= {pr1646v2Lan3FGPPPoEMCH2PEntry 251658240}

pr1646v2Lan3FGPPPoEMCH24P OBJECT-TYPE
   SYNTAX      SEQUENCE OF Pr1646v2Lan3FGPPPoEMCH24PEntry
   MAX-ACCESS  not-accessible
   STATUS      current
   DESCRIPTION
      ""
   ::= {pr1646v2Lan3FGPPPoE 41615360}

pr1646v2Lan3FGPPPoEMCH24PEntry OBJECT-TYPE
   SYNTAX      Pr1646v2Lan3FGPPPoEMCH24PEntry
   MAX-ACCESS  not-accessible
   STATUS      current
   DESCRIPTION
      ""
   INDEX      { pr1646v2Lan3FGPPPoETableIx,
                pr1646v2Lan3FGPPPoEMCH24PTableIx }
   ::= {pr1646v2Lan3FGPPPoEMCH24P 1}

Pr1646v2Lan3FGPPPoEMCH24PEntry ::=
   SEQUENCE
      {
      pr1646v2Lan3FGPPPoEMCH24PTableIx
         TableIndex,
      pr1646v2Lan3FGPPPoEMCH24PSysUpTime
         TimeTicks,
      pr1646v2Lan3FGPPPoEMCH24PIfUpTime
         TimeTicks,
      pr1646v2Lan3FGPPPoEMCH24PIfStatChanges
         Counter32,
      pr1646v2Lan3FGPPPoEMCH24PIfInOctets
         Counter64,
      pr1646v2Lan3FGPPPoEMCH24PIfInUCPkts
         Counter64,
      pr1646v2Lan3FGPPPoEMCH24PIfInNUCPkts
         Counter64,
      pr1646v2Lan3FGPPPoEMCH24PIfInBCPkts
         Counter64,
      pr1646v2Lan3FGPPPoEMCH24PIfInMCPkts
         Counter64,
      pr1646v2Lan3FGPPPoEMCH24PIfInDiscards
         Counter64,
      pr1646v2Lan3FGPPPoEMCH24PIfInErrors
         Counter64,
      pr1646v2Lan3FGPPPoEMCH24PIfInUnkwn
         Counter64,
      pr1646v2Lan3FGPPPoEMCH24PInDropEx
         Counter64,
      pr1646v2Lan3FGPPPoEMCH24PInDropNoMac
         Counter64,
      pr1646v2Lan3FGPPPoEMCH24PInDropNUCast
         Counter64,
      pr1646v2Lan3FGPPPoEMCH24PInDropFilter
         Counter64,
      pr1646v2Lan3FGPPPoEMCH24PIfInBandwidth
         Integer32,
      pr1646v2Lan3FGPPPoEMCH24PIfOutOctets
         Counter64,
      pr1646v2Lan3FGPPPoEMCH24PIfOutUCPkts
         Counter64,
      pr1646v2Lan3FGPPPoEMCH24PIfOutNUCPkts
         Counter64,
      pr1646v2Lan3FGPPPoEMCH24PIfOutBCPkts
         Counter64,
      pr1646v2Lan3FGPPPoEMCH24PIfOutMCPkts
         Counter64,
      pr1646v2Lan3FGPPPoEMCH24PIfOutDiscards
         Counter64,
      pr1646v2Lan3FGPPPoEMCH24PIfOutErrors
         Counter64,
      pr1646v2Lan3FGPPPoEMCH24POutDropEx
         Counter64,
      pr1646v2Lan3FGPPPoEMCH24POutDropNoArp
         Counter64,
      pr1646v2Lan3FGPPPoEMCH24POutDropFilter
         Counter64,
      pr1646v2Lan3FGPPPoEMCH24PIfOutBandwidth
         Integer32,
      pr1646v2Lan3FGPPPoEMCH24PIfErrSec
         Counter32
      }

pr1646v2Lan3FGPPPoEMCH24PTableIx OBJECT-TYPE
   SYNTAX      TableIndex
   MAX-ACCESS  not-accessible
   STATUS      current
   DESCRIPTION
      ""
   ::= {pr1646v2Lan3FGPPPoEMCH24PEntry 11}

pr1646v2Lan3FGPPPoEMCH24PSysUpTime OBJECT-TYPE
   SYNTAX      TimeTicks
   MAX-ACCESS  read-only
   STATUS      current
   DESCRIPTION
      "Path: ethernet3.performance.pppoEClient.mibCounters.h24Performance.sysUpTime

       Time in centi-second."
   ::= {pr1646v2Lan3FGPPPoEMCH24PEntry 16777216}

pr1646v2Lan3FGPPPoEMCH24PIfUpTime OBJECT-TYPE
   SYNTAX      TimeTicks
   MAX-ACCESS  read-only
   STATUS      current
   DESCRIPTION
      "Path: ethernet3.performance.pppoEClient.mibCounters.h24Performance.ifUpTime

       Time in centi-second."
   ::= {pr1646v2Lan3FGPPPoEMCH24PEntry 33554432}

pr1646v2Lan3FGPPPoEMCH24PIfStatChanges OBJECT-TYPE
   SYNTAX      Counter32
   MAX-ACCESS  read-only
   STATUS      current
   DESCRIPTION
      "Path: ethernet3.performance.pppoEClient.mibCounters.h24Performance.ifStatusChanges

       32 bit unsigned wrappable counter."
   ::= {pr1646v2Lan3FGPPPoEMCH24PEntry 50331648}

pr1646v2Lan3FGPPPoEMCH24PIfInOctets OBJECT-TYPE
   SYNTAX      Counter64
   MAX-ACCESS  read-only
   STATUS      current
   DESCRIPTION
      "Path: ethernet3.performance.pppoEClient.mibCounters.h24Performance.ifInOctets

       64 bit unsigned wrappable counter."
   ::= {pr1646v2Lan3FGPPPoEMCH24PEntry 67108864}

pr1646v2Lan3FGPPPoEMCH24PIfInUCPkts OBJECT-TYPE
   SYNTAX      Counter64
   MAX-ACCESS  read-only
   STATUS      current
   DESCRIPTION
      "Path: ethernet3.performance.pppoEClient.mibCounters.h24Performance.ifInUcastPkts

       64 bit unsigned wrappable counter."
   ::= {pr1646v2Lan3FGPPPoEMCH24PEntry 83886080}

pr1646v2Lan3FGPPPoEMCH24PIfInNUCPkts OBJECT-TYPE
   SYNTAX      Counter64
   MAX-ACCESS  read-only
   STATUS      current
   DESCRIPTION
      "Path: ethernet3.performance.pppoEClient.mibCounters.h24Performance.ifInNUcastPkts

       64 bit unsigned wrappable counter."
   ::= {pr1646v2Lan3FGPPPoEMCH24PEntry 100663296}

pr1646v2Lan3FGPPPoEMCH24PIfInBCPkts OBJECT-TYPE
   SYNTAX      Counter64
   MAX-ACCESS  read-only
   STATUS      current
   DESCRIPTION
      "Path: ethernet3.performance.pppoEClient.mibCounters.h24Performance.ifInBcastPkts

       64 bit unsigned wrappable counter."
   ::= {pr1646v2Lan3FGPPPoEMCH24PEntry 419430400}

pr1646v2Lan3FGPPPoEMCH24PIfInMCPkts OBJECT-TYPE
   SYNTAX      Counter64
   MAX-ACCESS  read-only
   STATUS      current
   DESCRIPTION
      "Path: ethernet3.performance.pppoEClient.mibCounters.h24Performance.ifInMcastPkts

       64 bit unsigned wrappable counter."
   ::= {pr1646v2Lan3FGPPPoEMCH24PEntry 436207616}

pr1646v2Lan3FGPPPoEMCH24PIfInDiscards OBJECT-TYPE
   SYNTAX      Counter64
   MAX-ACCESS  read-only
   STATUS      current
   DESCRIPTION
      "Path: ethernet3.performance.pppoEClient.mibCounters.h24Performance.ifInDiscards

       64 bit unsigned wrappable counter."
   ::= {pr1646v2Lan3FGPPPoEMCH24PEntry 117440512}

pr1646v2Lan3FGPPPoEMCH24PIfInErrors OBJECT-TYPE
   SYNTAX      Counter64
   MAX-ACCESS  read-only
   STATUS      current
   DESCRIPTION
      "Path: ethernet3.performance.pppoEClient.mibCounters.h24Performance.ifInErrors

       64 bit unsigned wrappable counter."
   ::= {pr1646v2Lan3FGPPPoEMCH24PEntry 134217728}

pr1646v2Lan3FGPPPoEMCH24PIfInUnkwn OBJECT-TYPE
   SYNTAX      Counter64
   MAX-ACCESS  read-only
   STATUS      current
   DESCRIPTION
      "Path: ethernet3.performance.pppoEClient.mibCounters.h24Performance.ifInUnknownProtos

       64 bit unsigned wrappable counter."
   ::= {pr1646v2Lan3FGPPPoEMCH24PEntry 150994944}

pr1646v2Lan3FGPPPoEMCH24PInDropEx OBJECT-TYPE
   SYNTAX      Counter64
   MAX-ACCESS  read-only
   STATUS      current
   DESCRIPTION
      "Path: ethernet3.performance.pppoEClient.mibCounters.h24Performance.ifInDropLevelExceeded

       64 bit unsigned wrappable counter."
   ::= {pr1646v2Lan3FGPPPoEMCH24PEntry 335544320}

pr1646v2Lan3FGPPPoEMCH24PInDropNoMac OBJECT-TYPE
   SYNTAX      Counter64
   MAX-ACCESS  read-only
   STATUS      current
   DESCRIPTION
      "Path: ethernet3.performance.pppoEClient.mibCounters.h24Performance.fInDiscardsNoMacFit

       64 bit unsigned wrappable counter."
   ::= {pr1646v2Lan3FGPPPoEMCH24PEntry 301989888}

pr1646v2Lan3FGPPPoEMCH24PInDropNUCast OBJECT-TYPE
   SYNTAX      Counter64
   MAX-ACCESS  read-only
   STATUS      current
   DESCRIPTION
      "Path: ethernet3.performance.pppoEClient.mibCounters.h24Performance.fInDiscardsNUCast

       64 bit unsigned wrappable counter."
   ::= {pr1646v2Lan3FGPPPoEMCH24PEntry 318767104}

pr1646v2Lan3FGPPPoEMCH24PInDropFilter OBJECT-TYPE
   SYNTAX      Counter64
   MAX-ACCESS  read-only
   STATUS      current
   DESCRIPTION
      "Path: ethernet3.performance.pppoEClient.mibCounters.h24Performance.fInDiscardsFilter

       64 bit unsigned wrappable counter."
   ::= {pr1646v2Lan3FGPPPoEMCH24PEntry 385875968}

pr1646v2Lan3FGPPPoEMCH24PIfInBandwidth OBJECT-TYPE
   SYNTAX      Integer32
   MAX-ACCESS  read-only
   STATUS      current
   DESCRIPTION
      "Path: ethernet3.performance.pppoEClient.mibCounters.h24Performance.ifInBandwidth

       unit name = bps
       formula = 8 * ; 8 /"
   ::= {pr1646v2Lan3FGPPPoEMCH24PEntry 268435456}

pr1646v2Lan3FGPPPoEMCH24PIfOutOctets OBJECT-TYPE
   SYNTAX      Counter64
   MAX-ACCESS  read-only
   STATUS      current
   DESCRIPTION
      "Path: ethernet3.performance.pppoEClient.mibCounters.h24Performance.ifOutOctets

       64 bit unsigned wrappable counter."
   ::= {pr1646v2Lan3FGPPPoEMCH24PEntry 167772160}

pr1646v2Lan3FGPPPoEMCH24PIfOutUCPkts OBJECT-TYPE
   SYNTAX      Counter64
   MAX-ACCESS  read-only
   STATUS      current
   DESCRIPTION
      "Path: ethernet3.performance.pppoEClient.mibCounters.h24Performance.ifOutUcastPkts

       64 bit unsigned wrappable counter."
   ::= {pr1646v2Lan3FGPPPoEMCH24PEntry 184549376}

pr1646v2Lan3FGPPPoEMCH24PIfOutNUCPkts OBJECT-TYPE
   SYNTAX      Counter64
   MAX-ACCESS  read-only
   STATUS      current
   DESCRIPTION
      "Path: ethernet3.performance.pppoEClient.mibCounters.h24Performance.ifOutNUcastPkts

       64 bit unsigned wrappable counter."
   ::= {pr1646v2Lan3FGPPPoEMCH24PEntry 201326592}

pr1646v2Lan3FGPPPoEMCH24PIfOutBCPkts OBJECT-TYPE
   SYNTAX      Counter64
   MAX-ACCESS  read-only
   STATUS      current
   DESCRIPTION
      "Path: ethernet3.performance.pppoEClient.mibCounters.h24Performance.ifOutBcastPkts

       64 bit unsigned wrappable counter."
   ::= {pr1646v2Lan3FGPPPoEMCH24PEntry 452984832}

pr1646v2Lan3FGPPPoEMCH24PIfOutMCPkts OBJECT-TYPE
   SYNTAX      Counter64
   MAX-ACCESS  read-only
   STATUS      current
   DESCRIPTION
      "Path: ethernet3.performance.pppoEClient.mibCounters.h24Performance.ifOutMcastPkts

       64 bit unsigned wrappable counter."
   ::= {pr1646v2Lan3FGPPPoEMCH24PEntry 469762048}

pr1646v2Lan3FGPPPoEMCH24PIfOutDiscards OBJECT-TYPE
   SYNTAX      Counter64
   MAX-ACCESS  read-only
   STATUS      current
   DESCRIPTION
      "Path: ethernet3.performance.pppoEClient.mibCounters.h24Performance.ifOutDiscards

       64 bit unsigned wrappable counter."
   ::= {pr1646v2Lan3FGPPPoEMCH24PEntry 218103808}

pr1646v2Lan3FGPPPoEMCH24PIfOutErrors OBJECT-TYPE
   SYNTAX      Counter64
   MAX-ACCESS  read-only
   STATUS      current
   DESCRIPTION
      "Path: ethernet3.performance.pppoEClient.mibCounters.h24Performance.ifOutErrors

       64 bit unsigned wrappable counter."
   ::= {pr1646v2Lan3FGPPPoEMCH24PEntry 234881024}

pr1646v2Lan3FGPPPoEMCH24POutDropEx OBJECT-TYPE
   SYNTAX      Counter64
   MAX-ACCESS  read-only
   STATUS      current
   DESCRIPTION
      "Path: ethernet3.performance.pppoEClient.mibCounters.h24Performance.ifOutDropLevelExceeded

       64 bit unsigned wrappable counter."
   ::= {pr1646v2Lan3FGPPPoEMCH24PEntry 352321536}

pr1646v2Lan3FGPPPoEMCH24POutDropNoArp OBJECT-TYPE
   SYNTAX      Counter64
   MAX-ACCESS  read-only
   STATUS      current
   DESCRIPTION
      "Path: ethernet3.performance.pppoEClient.mibCounters.h24Performance.ifOutDiscardsNoArp

       64 bit unsigned wrappable counter."
   ::= {pr1646v2Lan3FGPPPoEMCH24PEntry 369098752}

pr1646v2Lan3FGPPPoEMCH24POutDropFilter OBJECT-TYPE
   SYNTAX      Counter64
   MAX-ACCESS  read-only
   STATUS      current
   DESCRIPTION
      "Path: ethernet3.performance.pppoEClient.mibCounters.h24Performance.ifOutDiscardsFilter

       64 bit unsigned wrappable counter."
   ::= {pr1646v2Lan3FGPPPoEMCH24PEntry 402653184}

pr1646v2Lan3FGPPPoEMCH24PIfOutBandwidth OBJECT-TYPE
   SYNTAX      Integer32
   MAX-ACCESS  read-only
   STATUS      current
   DESCRIPTION
      "Path: ethernet3.performance.pppoEClient.mibCounters.h24Performance.ifOutBandwidth

       unit name = bps
       formula = 8 * ; 8 /"
   ::= {pr1646v2Lan3FGPPPoEMCH24PEntry 285212672}

pr1646v2Lan3FGPPPoEMCH24PIfErrSec OBJECT-TYPE
   SYNTAX      Counter32
   MAX-ACCESS  read-only
   STATUS      current
   DESCRIPTION
      "Path: ethernet3.performance.pppoEClient.mibCounters.h24Performance.ifErrSec

       32 bit unsigned wrappable counter."
   ::= {pr1646v2Lan3FGPPPoEMCH24PEntry 251658240}

pr1646v2Lan3FGPPPoEMCD7P OBJECT-TYPE
   SYNTAX      SEQUENCE OF Pr1646v2Lan3FGPPPoEMCD7PEntry
   MAX-ACCESS  not-accessible
   STATUS      current
   DESCRIPTION
      ""
   ::= {pr1646v2Lan3FGPPPoE 41680896}

pr1646v2Lan3FGPPPoEMCD7PEntry OBJECT-TYPE
   SYNTAX      Pr1646v2Lan3FGPPPoEMCD7PEntry
   MAX-ACCESS  not-accessible
   STATUS      current
   DESCRIPTION
      ""
   INDEX      { pr1646v2Lan3FGPPPoETableIx,
                pr1646v2Lan3FGPPPoEMCD7PTableIx }
   ::= {pr1646v2Lan3FGPPPoEMCD7P 1}

Pr1646v2Lan3FGPPPoEMCD7PEntry ::=
   SEQUENCE
      {
      pr1646v2Lan3FGPPPoEMCD7PTableIx
         TableIndex,
      pr1646v2Lan3FGPPPoEMCD7PSysUpTime
         TimeTicks,
      pr1646v2Lan3FGPPPoEMCD7PIfUpTime
         TimeTicks,
      pr1646v2Lan3FGPPPoEMCD7PIfStatChanges
         Counter32,
      pr1646v2Lan3FGPPPoEMCD7PIfInOctets
         Counter64,
      pr1646v2Lan3FGPPPoEMCD7PIfInUCPkts
         Counter64,
      pr1646v2Lan3FGPPPoEMCD7PIfInNUCPkts
         Counter64,
      pr1646v2Lan3FGPPPoEMCD7PIfInBCPkts
         Counter64,
      pr1646v2Lan3FGPPPoEMCD7PIfInMCPkts
         Counter64,
      pr1646v2Lan3FGPPPoEMCD7PIfInDiscards
         Counter64,
      pr1646v2Lan3FGPPPoEMCD7PIfInErrors
         Counter64,
      pr1646v2Lan3FGPPPoEMCD7PIfInUnkwn
         Counter64,
      pr1646v2Lan3FGPPPoEMCD7PInDropEx
         Counter64,
      pr1646v2Lan3FGPPPoEMCD7PInDropNoMac
         Counter64,
      pr1646v2Lan3FGPPPoEMCD7PInDropNUCast
         Counter64,
      pr1646v2Lan3FGPPPoEMCD7PInDropFilter
         Counter64,
      pr1646v2Lan3FGPPPoEMCD7PIfInBandwidth
         Integer32,
      pr1646v2Lan3FGPPPoEMCD7PIfOutOctets
         Counter64,
      pr1646v2Lan3FGPPPoEMCD7PIfOutUCPkts
         Counter64,
      pr1646v2Lan3FGPPPoEMCD7PIfOutNUCPkts
         Counter64,
      pr1646v2Lan3FGPPPoEMCD7PIfOutBCPkts
         Counter64,
      pr1646v2Lan3FGPPPoEMCD7PIfOutMCPkts
         Counter64,
      pr1646v2Lan3FGPPPoEMCD7PIfOutDiscards
         Counter64,
      pr1646v2Lan3FGPPPoEMCD7PIfOutErrors
         Counter64,
      pr1646v2Lan3FGPPPoEMCD7POutDropEx
         Counter64,
      pr1646v2Lan3FGPPPoEMCD7POutDropNoArp
         Counter64,
      pr1646v2Lan3FGPPPoEMCD7POutDropFilter
         Counter64,
      pr1646v2Lan3FGPPPoEMCD7PIfOutBandwidth
         Integer32,
      pr1646v2Lan3FGPPPoEMCD7PIfErrSec
         Counter32
      }

pr1646v2Lan3FGPPPoEMCD7PTableIx OBJECT-TYPE
   SYNTAX      TableIndex
   MAX-ACCESS  not-accessible
   STATUS      current
   DESCRIPTION
      ""
   ::= {pr1646v2Lan3FGPPPoEMCD7PEntry 11}

pr1646v2Lan3FGPPPoEMCD7PSysUpTime OBJECT-TYPE
   SYNTAX      TimeTicks
   MAX-ACCESS  read-only
   STATUS      current
   DESCRIPTION
      "Path: ethernet3.performance.pppoEClient.mibCounters.d7Performance.sysUpTime

       Time in centi-second."
   ::= {pr1646v2Lan3FGPPPoEMCD7PEntry 16777216}

pr1646v2Lan3FGPPPoEMCD7PIfUpTime OBJECT-TYPE
   SYNTAX      TimeTicks
   MAX-ACCESS  read-only
   STATUS      current
   DESCRIPTION
      "Path: ethernet3.performance.pppoEClient.mibCounters.d7Performance.ifUpTime

       Time in centi-second."
   ::= {pr1646v2Lan3FGPPPoEMCD7PEntry 33554432}

pr1646v2Lan3FGPPPoEMCD7PIfStatChanges OBJECT-TYPE
   SYNTAX      Counter32
   MAX-ACCESS  read-only
   STATUS      current
   DESCRIPTION
      "Path: ethernet3.performance.pppoEClient.mibCounters.d7Performance.ifStatusChanges

       32 bit unsigned wrappable counter."
   ::= {pr1646v2Lan3FGPPPoEMCD7PEntry 50331648}

pr1646v2Lan3FGPPPoEMCD7PIfInOctets OBJECT-TYPE
   SYNTAX      Counter64
   MAX-ACCESS  read-only
   STATUS      current
   DESCRIPTION
      "Path: ethernet3.performance.pppoEClient.mibCounters.d7Performance.ifInOctets

       64 bit unsigned wrappable counter."
   ::= {pr1646v2Lan3FGPPPoEMCD7PEntry 67108864}

pr1646v2Lan3FGPPPoEMCD7PIfInUCPkts OBJECT-TYPE
   SYNTAX      Counter64
   MAX-ACCESS  read-only
   STATUS      current
   DESCRIPTION
      "Path: ethernet3.performance.pppoEClient.mibCounters.d7Performance.ifInUcastPkts

       64 bit unsigned wrappable counter."
   ::= {pr1646v2Lan3FGPPPoEMCD7PEntry 83886080}

pr1646v2Lan3FGPPPoEMCD7PIfInNUCPkts OBJECT-TYPE
   SYNTAX      Counter64
   MAX-ACCESS  read-only
   STATUS      current
   DESCRIPTION
      "Path: ethernet3.performance.pppoEClient.mibCounters.d7Performance.ifInNUcastPkts

       64 bit unsigned wrappable counter."
   ::= {pr1646v2Lan3FGPPPoEMCD7PEntry 100663296}

pr1646v2Lan3FGPPPoEMCD7PIfInBCPkts OBJECT-TYPE
   SYNTAX      Counter64
   MAX-ACCESS  read-only
   STATUS      current
   DESCRIPTION
      "Path: ethernet3.performance.pppoEClient.mibCounters.d7Performance.ifInBcastPkts

       64 bit unsigned wrappable counter."
   ::= {pr1646v2Lan3FGPPPoEMCD7PEntry 419430400}

pr1646v2Lan3FGPPPoEMCD7PIfInMCPkts OBJECT-TYPE
   SYNTAX      Counter64
   MAX-ACCESS  read-only
   STATUS      current
   DESCRIPTION
      "Path: ethernet3.performance.pppoEClient.mibCounters.d7Performance.ifInMcastPkts

       64 bit unsigned wrappable counter."
   ::= {pr1646v2Lan3FGPPPoEMCD7PEntry 436207616}

pr1646v2Lan3FGPPPoEMCD7PIfInDiscards OBJECT-TYPE
   SYNTAX      Counter64
   MAX-ACCESS  read-only
   STATUS      current
   DESCRIPTION
      "Path: ethernet3.performance.pppoEClient.mibCounters.d7Performance.ifInDiscards

       64 bit unsigned wrappable counter."
   ::= {pr1646v2Lan3FGPPPoEMCD7PEntry 117440512}

pr1646v2Lan3FGPPPoEMCD7PIfInErrors OBJECT-TYPE
   SYNTAX      Counter64
   MAX-ACCESS  read-only
   STATUS      current
   DESCRIPTION
      "Path: ethernet3.performance.pppoEClient.mibCounters.d7Performance.ifInErrors

       64 bit unsigned wrappable counter."
   ::= {pr1646v2Lan3FGPPPoEMCD7PEntry 134217728}

pr1646v2Lan3FGPPPoEMCD7PIfInUnkwn OBJECT-TYPE
   SYNTAX      Counter64
   MAX-ACCESS  read-only
   STATUS      current
   DESCRIPTION
      "Path: ethernet3.performance.pppoEClient.mibCounters.d7Performance.ifInUnknownProtos

       64 bit unsigned wrappable counter."
   ::= {pr1646v2Lan3FGPPPoEMCD7PEntry 150994944}

pr1646v2Lan3FGPPPoEMCD7PInDropEx OBJECT-TYPE
   SYNTAX      Counter64
   MAX-ACCESS  read-only
   STATUS      current
   DESCRIPTION
      "Path: ethernet3.performance.pppoEClient.mibCounters.d7Performance.ifInDropLevelExceeded

       64 bit unsigned wrappable counter."
   ::= {pr1646v2Lan3FGPPPoEMCD7PEntry 335544320}

pr1646v2Lan3FGPPPoEMCD7PInDropNoMac OBJECT-TYPE
   SYNTAX      Counter64
   MAX-ACCESS  read-only
   STATUS      current
   DESCRIPTION
      "Path: ethernet3.performance.pppoEClient.mibCounters.d7Performance.fInDiscardsNoMacFit

       64 bit unsigned wrappable counter."
   ::= {pr1646v2Lan3FGPPPoEMCD7PEntry 301989888}

pr1646v2Lan3FGPPPoEMCD7PInDropNUCast OBJECT-TYPE
   SYNTAX      Counter64
   MAX-ACCESS  read-only
   STATUS      current
   DESCRIPTION
      "Path: ethernet3.performance.pppoEClient.mibCounters.d7Performance.fInDiscardsNUCast

       64 bit unsigned wrappable counter."
   ::= {pr1646v2Lan3FGPPPoEMCD7PEntry 318767104}

pr1646v2Lan3FGPPPoEMCD7PInDropFilter OBJECT-TYPE
   SYNTAX      Counter64
   MAX-ACCESS  read-only
   STATUS      current
   DESCRIPTION
      "Path: ethernet3.performance.pppoEClient.mibCounters.d7Performance.fInDiscardsFilter

       64 bit unsigned wrappable counter."
   ::= {pr1646v2Lan3FGPPPoEMCD7PEntry 385875968}

pr1646v2Lan3FGPPPoEMCD7PIfInBandwidth OBJECT-TYPE
   SYNTAX      Integer32
   MAX-ACCESS  read-only
   STATUS      current
   DESCRIPTION
      "Path: ethernet3.performance.pppoEClient.mibCounters.d7Performance.ifInBandwidth

       unit name = bps
       formula = 8 * ; 8 /"
   ::= {pr1646v2Lan3FGPPPoEMCD7PEntry 268435456}

pr1646v2Lan3FGPPPoEMCD7PIfOutOctets OBJECT-TYPE
   SYNTAX      Counter64
   MAX-ACCESS  read-only
   STATUS      current
   DESCRIPTION
      "Path: ethernet3.performance.pppoEClient.mibCounters.d7Performance.ifOutOctets

       64 bit unsigned wrappable counter."
   ::= {pr1646v2Lan3FGPPPoEMCD7PEntry 167772160}

pr1646v2Lan3FGPPPoEMCD7PIfOutUCPkts OBJECT-TYPE
   SYNTAX      Counter64
   MAX-ACCESS  read-only
   STATUS      current
   DESCRIPTION
      "Path: ethernet3.performance.pppoEClient.mibCounters.d7Performance.ifOutUcastPkts

       64 bit unsigned wrappable counter."
   ::= {pr1646v2Lan3FGPPPoEMCD7PEntry 184549376}

pr1646v2Lan3FGPPPoEMCD7PIfOutNUCPkts OBJECT-TYPE
   SYNTAX      Counter64
   MAX-ACCESS  read-only
   STATUS      current
   DESCRIPTION
      "Path: ethernet3.performance.pppoEClient.mibCounters.d7Performance.ifOutNUcastPkts

       64 bit unsigned wrappable counter."
   ::= {pr1646v2Lan3FGPPPoEMCD7PEntry 201326592}

pr1646v2Lan3FGPPPoEMCD7PIfOutBCPkts OBJECT-TYPE
   SYNTAX      Counter64
   MAX-ACCESS  read-only
   STATUS      current
   DESCRIPTION
      "Path: ethernet3.performance.pppoEClient.mibCounters.d7Performance.ifOutBcastPkts

       64 bit unsigned wrappable counter."
   ::= {pr1646v2Lan3FGPPPoEMCD7PEntry 452984832}

pr1646v2Lan3FGPPPoEMCD7PIfOutMCPkts OBJECT-TYPE
   SYNTAX      Counter64
   MAX-ACCESS  read-only
   STATUS      current
   DESCRIPTION
      "Path: ethernet3.performance.pppoEClient.mibCounters.d7Performance.ifOutMcastPkts

       64 bit unsigned wrappable counter."
   ::= {pr1646v2Lan3FGPPPoEMCD7PEntry 469762048}

pr1646v2Lan3FGPPPoEMCD7PIfOutDiscards OBJECT-TYPE
   SYNTAX      Counter64
   MAX-ACCESS  read-only
   STATUS      current
   DESCRIPTION
      "Path: ethernet3.performance.pppoEClient.mibCounters.d7Performance.ifOutDiscards

       64 bit unsigned wrappable counter."
   ::= {pr1646v2Lan3FGPPPoEMCD7PEntry 218103808}

pr1646v2Lan3FGPPPoEMCD7PIfOutErrors OBJECT-TYPE
   SYNTAX      Counter64
   MAX-ACCESS  read-only
   STATUS      current
   DESCRIPTION
      "Path: ethernet3.performance.pppoEClient.mibCounters.d7Performance.ifOutErrors

       64 bit unsigned wrappable counter."
   ::= {pr1646v2Lan3FGPPPoEMCD7PEntry 234881024}

pr1646v2Lan3FGPPPoEMCD7POutDropEx OBJECT-TYPE
   SYNTAX      Counter64
   MAX-ACCESS  read-only
   STATUS      current
   DESCRIPTION
      "Path: ethernet3.performance.pppoEClient.mibCounters.d7Performance.ifOutDropLevelExceeded

       64 bit unsigned wrappable counter."
   ::= {pr1646v2Lan3FGPPPoEMCD7PEntry 352321536}

pr1646v2Lan3FGPPPoEMCD7POutDropNoArp OBJECT-TYPE
   SYNTAX      Counter64
   MAX-ACCESS  read-only
   STATUS      current
   DESCRIPTION
      "Path: ethernet3.performance.pppoEClient.mibCounters.d7Performance.ifOutDiscardsNoArp

       64 bit unsigned wrappable counter."
   ::= {pr1646v2Lan3FGPPPoEMCD7PEntry 369098752}

pr1646v2Lan3FGPPPoEMCD7POutDropFilter OBJECT-TYPE
   SYNTAX      Counter64
   MAX-ACCESS  read-only
   STATUS      current
   DESCRIPTION
      "Path: ethernet3.performance.pppoEClient.mibCounters.d7Performance.ifOutDiscardsFilter

       64 bit unsigned wrappable counter."
   ::= {pr1646v2Lan3FGPPPoEMCD7PEntry 402653184}

pr1646v2Lan3FGPPPoEMCD7PIfOutBandwidth OBJECT-TYPE
   SYNTAX      Integer32
   MAX-ACCESS  read-only
   STATUS      current
   DESCRIPTION
      "Path: ethernet3.performance.pppoEClient.mibCounters.d7Performance.ifOutBandwidth

       unit name = bps
       formula = 8 * ; 8 /"
   ::= {pr1646v2Lan3FGPPPoEMCD7PEntry 285212672}

pr1646v2Lan3FGPPPoEMCD7PIfErrSec OBJECT-TYPE
   SYNTAX      Counter32
   MAX-ACCESS  read-only
   STATUS      current
   DESCRIPTION
      "Path: ethernet3.performance.pppoEClient.mibCounters.d7Performance.ifErrSec

       32 bit unsigned wrappable counter."
   ::= {pr1646v2Lan3FGPPPoEMCD7PEntry 251658240}


pr1646v2Lan3FGIfInHwPriorityQueues OBJECT IDENTIFIER ::= {pr1646v2Lan3FG 132}

pr1646v2Lan3FGIfInHwPriorityQueuesSSCTable OBJECT-TYPE
   SYNTAX      SEQUENCE OF Pr1646v2Lan3FGIfInHwPriorityQueuesEntry
   MAX-ACCESS  not-accessible
   STATUS      current
   DESCRIPTION
      "hwPriorityQueues"
   ::= {pr1646v2Lan3FGIfInHwPriorityQueues 1}

pr1646v2Lan3FGIfInHwPriorityQueuesEntry OBJECT-TYPE
   SYNTAX      Pr1646v2Lan3FGIfInHwPriorityQueuesEntry
   MAX-ACCESS  not-accessible
   STATUS      current
   DESCRIPTION
      ""
   INDEX      { pr1646v2Lan3FGIfInHwPriorityQueuesTableIx }
   ::= {pr1646v2Lan3FGIfInHwPriorityQueuesSSCTable 1}

Pr1646v2Lan3FGIfInHwPriorityQueuesEntry ::=
   SEQUENCE
      {
      pr1646v2Lan3FGIfInHwPriorityQueuesTableIx
         TableIndex,
      pr1646v2Lan3FGIfInHwPriorityQueuesName
         INTEGER,
      pr1646v2Lan3FGIfInHwPriorityQueuesLength
         Integer32,
      pr1646v2Lan3FGIfInHwPriorityQueuesPacketsTotal
         Counter64,
      pr1646v2Lan3FGIfInHwPriorityQueuesOctetsTotal
         Counter64,
      pr1646v2Lan3FGIfInHwPriorityQueuesOctetsBandwidth15sec
         Integer32,
      pr1646v2Lan3FGIfInHwPriorityQueuesOctetsBandwidth30sec
         Integer32,
      pr1646v2Lan3FGIfInHwPriorityQueuesOctetsBandwidth1min
         Integer32,
      pr1646v2Lan3FGIfInHwPriorityQueuesOctetsBandwidth2min
         Integer32,
      pr1646v2Lan3FGIfInHwPriorityQueuesOctetsBandwidth5min
         Integer32
      }

pr1646v2Lan3FGIfInHwPriorityQueuesTableIx OBJECT-TYPE
   SYNTAX      TableIndex
   MAX-ACCESS  not-accessible
   STATUS      current
   DESCRIPTION
      ""
   ::= {pr1646v2Lan3FGIfInHwPriorityQueuesEntry 11}

pr1646v2Lan3FGIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet3.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2Lan3FGIfInHwPriorityQueuesEntry 16777216}

pr1646v2Lan3FGIfInHwPriorityQueuesLength OBJECT-TYPE
   SYNTAX      Integer32
   MAX-ACCESS  read-only
   STATUS      current
   DESCRIPTION
      "Path: ethernet3.performance.ifInHwPriorityQueues.length"
   ::= {pr1646v2Lan3FGIfInHwPriorityQueuesEntry 33554432}

pr1646v2Lan3FGIfInHwPriorityQueuesPacketsTotal OBJECT-TYPE
   SYNTAX      Counter64
   MAX-ACCESS  read-only
   STATUS      current
   DESCRIPTION
      "Path: ethernet3.performance.ifInHwPriorityQueues.packets.total

       64 bit unsigned wrappable counter."
   ::= {pr1646v2Lan3FGIfInHwPriorityQueuesEntry 50790400}

pr1646v2Lan3FGIfInHwPriorityQueuesOctetsTotal OBJECT-TYPE
   SYNTAX      Counter64
   MAX-ACCESS  read-only
   STATUS      current
   DESCRIPTION
      "Path: ethernet3.performance.ifInHwPriorityQueues.octets.total

       64 bit unsigned wrappable counter."
   ::= {pr1646v2Lan3FGIfInHwPriorityQueuesEntry 67567616}

pr1646v2Lan3FGIfInHwPriorityQueuesOctetsBandwidth15sec OBJECT-TYPE
   SYNTAX      Integer32
   MAX-ACCESS  read-only
   STATUS      current
   DESCRIPTION
      "Path: ethernet3.performance.ifInHwPriorityQueues.octets.bandwidth.15sec

       unit name = bps
       formula = 8 * ; 8 /"
   ::= {pr1646v2Lan3FGIfInHwPriorityQueuesEntry 70386944}

pr1646v2Lan3FGIfInHwPriorityQueuesOctetsBandwidth30sec OBJECT-TYPE
   SYNTAX      Integer32
   MAX-ACCESS  read-only
   STATUS      current
   DESCRIPTION
      "Path: ethernet3.performance.ifInHwPriorityQueues.octets.bandwidth.30sec

       unit name = bps
       formula = 8 * ; 8 /"
   ::= {pr1646v2Lan3FGIfInHwPriorityQueuesEntry 70388224}

pr1646v2Lan3FGIfInHwPriorityQueuesOctetsBandwidth1min OBJECT-TYPE
   SYNTAX      Integer32
   MAX-ACCESS  read-only
   STATUS      current
   DESCRIPTION
      "Path: ethernet3.performance.ifInHwPriorityQueues.octets.bandwidth.1min

       unit name = bps
       formula = 8 * ; 8 /"
   ::= {pr1646v2Lan3FGIfInHwPriorityQueuesEntry 70390784}

pr1646v2Lan3FGIfInHwPriorityQueuesOctetsBandwidth2min OBJECT-TYPE
   SYNTAX      Integer32
   MAX-ACCESS  read-only
   STATUS      current
   DESCRIPTION
      "Path: ethernet3.performance.ifInHwPriorityQueues.octets.bandwidth.2min

       unit name = bps
       formula = 8 * ; 8 /"
   ::= {pr1646v2Lan3FGIfInHwPriorityQueuesEntry 70395904}

pr1646v2Lan3FGIfInHwPriorityQueuesOctetsBandwidth5min OBJECT-TYPE
   SYNTAX      Integer32
   MAX-ACCESS  read-only
   STATUS      current
   DESCRIPTION
      "Path: ethernet3.performance.ifInHwPriorityQueues.octets.bandwidth.5min

       unit name = bps
       formula = 8 * ; 8 /"
   ::= {pr1646v2Lan3FGIfInHwPriorityQueuesEntry 70411264}

pr1646v2Lan3FGIfInHwPriorityQueuesH2Performance OBJECT-TYPE
   SYNTAX      SEQUENCE OF Pr1646v2Lan3FGIfInHwPriorityQueuesH2PerformanceEntry
   MAX-ACCESS  not-accessible
   STATUS      current
   DESCRIPTION
      ""
   ::= {pr1646v2Lan3FGIfInHwPriorityQueues 83886080}

pr1646v2Lan3FGIfInHwPriorityQueuesH2PerformanceEntry OBJECT-TYPE
   SYNTAX      Pr1646v2Lan3FGIfInHwPriorityQueuesH2PerformanceEntry
   MAX-ACCESS  not-accessible
   STATUS      current
   DESCRIPTION
      ""
   INDEX      { pr1646v2Lan3FGIfInHwPriorityQueuesTableIx,
                pr1646v2Lan3FGIfInHwPriorityQueuesH2PerformanceTableIx }
   ::= {pr1646v2Lan3FGIfInHwPriorityQueuesH2Performance 1}

Pr1646v2Lan3FGIfInHwPriorityQueuesH2PerformanceEntry ::=
   SEQUENCE
      {
      pr1646v2Lan3FGIfInHwPriorityQueuesH2PerformanceTableIx
         TableIndex,
      pr1646v2Lan3FGIfInHwPriorityQueuesH2PerformanceSysUpTime
         TimeTicks,
      pr1646v2Lan3FGIfInHwPriorityQueuesH2PerformanceTotPkts
         Counter64,
      pr1646v2Lan3FGIfInHwPriorityQueuesH2PerformanceTotOcts
         Counter64,
      pr1646v2Lan3FGIfInHwPriorityQueuesH2PerformanceBandwidth
         Integer32
      }

pr1646v2Lan3FGIfInHwPriorityQueuesH2PerformanceTableIx OBJECT-TYPE
   SYNTAX      TableIndex
   MAX-ACCESS  not-accessible
   STATUS      current
   DESCRIPTION
      ""
   ::= {pr1646v2Lan3FGIfInHwPriorityQueuesH2PerformanceEntry 11}

pr1646v2Lan3FGIfInHwPriorityQueuesH2PerformanceSysUpTime OBJECT-TYPE
   SYNTAX      TimeTicks
   MAX-ACCESS  read-only
   STATUS      current
   DESCRIPTION
      "Path: ethernet3.performance.ifInHwPriorityQueues.h2Performance.sysUpTime

       Time in centi-second."
   ::= {pr1646v2Lan3FGIfInHwPriorityQueuesH2PerformanceEntry 16777216}

pr1646v2Lan3FGIfInHwPriorityQueuesH2PerformanceTotPkts OBJECT-TYPE
   SYNTAX      Counter64
   MAX-ACCESS  read-only
   STATUS      current
   DESCRIPTION
      "Path: ethernet3.performance.ifInHwPriorityQueues.h2Performance.totalPkts

       64 bit unsigned wrappable counter."
   ::= {pr1646v2Lan3FGIfInHwPriorityQueuesH2PerformanceEntry 234881024}

pr1646v2Lan3FGIfInHwPriorityQueuesH2PerformanceTotOcts OBJECT-TYPE
   SYNTAX      Counter64
   MAX-ACCESS  read-only
   STATUS      current
   DESCRIPTION
      "Path: ethernet3.performance.ifInHwPriorityQueues.h2Performance.totalOctets

       64 bit unsigned wrappable counter."
   ::= {pr1646v2Lan3FGIfInHwPriorityQueuesH2PerformanceEntry 251658240}

pr1646v2Lan3FGIfInHwPriorityQueuesH2PerformanceBandwidth OBJECT-TYPE
   SYNTAX      Integer32
   MAX-ACCESS  read-only
   STATUS      current
   DESCRIPTION
      "Path: ethernet3.performance.ifInHwPriorityQueues.h2Performance.bandwidth

       unit name = bps
       formula = 8 * ; 8 /"
   ::= {pr1646v2Lan3FGIfInHwPriorityQueuesH2PerformanceEntry 268435456}

pr1646v2Lan3FGIfInHwPriorityQueuesH24Performance OBJECT-TYPE
   SYNTAX      SEQUENCE OF Pr1646v2Lan3FGIfInHwPriorityQueuesH24PerformanceEntry
   MAX-ACCESS  not-accessible
   STATUS      current
   DESCRIPTION
      ""
   ::= {pr1646v2Lan3FGIfInHwPriorityQueues 100663296}

pr1646v2Lan3FGIfInHwPriorityQueuesH24PerformanceEntry OBJECT-TYPE
   SYNTAX      Pr1646v2Lan3FGIfInHwPriorityQueuesH24PerformanceEntry
   MAX-ACCESS  not-accessible
   STATUS      current
   DESCRIPTION
      ""
   INDEX      { pr1646v2Lan3FGIfInHwPriorityQueuesTableIx,
                pr1646v2Lan3FGIfInHwPriorityQueuesH24PerformanceTableIx }
   ::= {pr1646v2Lan3FGIfInHwPriorityQueuesH24Performance 1}

Pr1646v2Lan3FGIfInHwPriorityQueuesH24PerformanceEntry ::=
   SEQUENCE
      {
      pr1646v2Lan3FGIfInHwPriorityQueuesH24PerformanceTableIx
         TableIndex,
      pr1646v2Lan3FGIfInHwPriorityQueuesH24PerformanceSysUpTime
         TimeTicks,
      pr1646v2Lan3FGIfInHwPriorityQueuesH24PerformanceTotPkts
         Counter64,
      pr1646v2Lan3FGIfInHwPriorityQueuesH24PerformanceTotOcts
         Counter64,
      pr1646v2Lan3FGIfInHwPriorityQueuesH24PerformanceBandwidth
         Integer32
      }

pr1646v2Lan3FGIfInHwPriorityQueuesH24PerformanceTableIx OBJECT-TYPE
   SYNTAX      TableIndex
   MAX-ACCESS  not-accessible
   STATUS      current
   DESCRIPTION
      ""
   ::= {pr1646v2Lan3FGIfInHwPriorityQueuesH24PerformanceEntry 11}

pr1646v2Lan3FGIfInHwPriorityQueuesH24PerformanceSysUpTime OBJECT-TYPE
   SYNTAX      TimeTicks
   MAX-ACCESS  read-only
   STATUS      current
   DESCRIPTION
      "Path: ethernet3.performance.ifInHwPriorityQueues.h24Performance.sysUpTime

       Time in centi-second."
   ::= {pr1646v2Lan3FGIfInHwPriorityQueuesH24PerformanceEntry 16777216}

pr1646v2Lan3FGIfInHwPriorityQueuesH24PerformanceTotPkts OBJECT-TYPE
   SYNTAX      Counter64
   MAX-ACCESS  read-only
   STATUS      current
   DESCRIPTION
      "Path: ethernet3.performance.ifInHwPriorityQueues.h24Performance.totalPkts

       64 bit unsigned wrappable counter."
   ::= {pr1646v2Lan3FGIfInHwPriorityQueuesH24PerformanceEntry 234881024}

pr1646v2Lan3FGIfInHwPriorityQueuesH24PerformanceTotOcts OBJECT-TYPE
   SYNTAX      Counter64
   MAX-ACCESS  read-only
   STATUS      current
   DESCRIPTION
      "Path: ethernet3.performance.ifInHwPriorityQueues.h24Performance.totalOctets

       64 bit unsigned wrappable counter."
   ::= {pr1646v2Lan3FGIfInHwPriorityQueuesH24PerformanceEntry 251658240}

pr1646v2Lan3FGIfInHwPriorityQueuesH24PerformanceBandwidth OBJECT-TYPE
   SYNTAX      Integer32
   MAX-ACCESS  read-only
   STATUS      current
   DESCRIPTION
      "Path: ethernet3.performance.ifInHwPriorityQueues.h24Performance.bandwidth

       unit name = bps
       formula = 8 * ; 8 /"
   ::= {pr1646v2Lan3FGIfInHwPriorityQueuesH24PerformanceEntry 268435456}

pr1646v2Lan3FGIfInHwPriorityQueuesD7Performance OBJECT-TYPE
   SYNTAX      SEQUENCE OF Pr1646v2Lan3FGIfInHwPriorityQueuesD7PerformanceEntry
   MAX-ACCESS  not-accessible
   STATUS      current
   DESCRIPTION
      ""
   ::= {pr1646v2Lan3FGIfInHwPriorityQueues 117440512}

pr1646v2Lan3FGIfInHwPriorityQueuesD7PerformanceEntry OBJECT-TYPE
   SYNTAX      Pr1646v2Lan3FGIfInHwPriorityQueuesD7PerformanceEntry
   MAX-ACCESS  not-accessible
   STATUS      current
   DESCRIPTION
      ""
   INDEX      { pr1646v2Lan3FGIfInHwPriorityQueuesTableIx,
                pr1646v2Lan3FGIfInHwPriorityQueuesD7PerformanceTableIx }
   ::= {pr1646v2Lan3FGIfInHwPriorityQueuesD7Performance 1}

Pr1646v2Lan3FGIfInHwPriorityQueuesD7PerformanceEntry ::=
   SEQUENCE
      {
      pr1646v2Lan3FGIfInHwPriorityQueuesD7PerformanceTableIx
         TableIndex,
      pr1646v2Lan3FGIfInHwPriorityQueuesD7PerformanceSysUpTime
         TimeTicks,
      pr1646v2Lan3FGIfInHwPriorityQueuesD7PerformanceTotPkts
         Counter64,
      pr1646v2Lan3FGIfInHwPriorityQueuesD7PerformanceTotOcts
         Counter64,
      pr1646v2Lan3FGIfInHwPriorityQueuesD7PerformanceBandwidth
         Integer32
      }

pr1646v2Lan3FGIfInHwPriorityQueuesD7PerformanceTableIx OBJECT-TYPE
   SYNTAX      TableIndex
   MAX-ACCESS  not-accessible
   STATUS      current
   DESCRIPTION
      ""
   ::= {pr1646v2Lan3FGIfInHwPriorityQueuesD7PerformanceEntry 11}

pr1646v2Lan3FGIfInHwPriorityQueuesD7PerformanceSysUpTime OBJECT-TYPE
   SYNTAX      TimeTicks
   MAX-ACCESS  read-only
   STATUS      current
   DESCRIPTION
      "Path: ethernet3.performance.ifInHwPriorityQueues.d7Performance.sysUpTime

       Time in centi-second."
   ::= {pr1646v2Lan3FGIfInHwPriorityQueuesD7PerformanceEntry 16777216}

pr1646v2Lan3FGIfInHwPriorityQueuesD7PerformanceTotPkts OBJECT-TYPE
   SYNTAX      Counter64
   MAX-ACCESS  read-only
   STATUS      current
   DESCRIPTION
      "Path: ethernet3.performance.ifInHwPriorityQueues.d7Performance.totalPkts

       64 bit unsigned wrappable counter."
   ::= {pr1646v2Lan3FGIfInHwPriorityQueuesD7PerformanceEntry 234881024}

pr1646v2Lan3FGIfInHwPriorityQueuesD7PerformanceTotOcts OBJECT-TYPE
   SYNTAX      Counter64
   MAX-ACCESS  read-only
   STATUS      current
   DESCRIPTION
      "Path: ethernet3.performance.ifInHwPriorityQueues.d7Performance.totalOctets

       64 bit unsigned wrappable counter."
   ::= {pr1646v2Lan3FGIfInHwPriorityQueuesD7PerformanceEntry 251658240}

pr1646v2Lan3FGIfInHwPriorityQueuesD7PerformanceBandwidth OBJECT-TYPE
   SYNTAX      Integer32
   MAX-ACCESS  read-only
   STATUS      current
   DESCRIPTION
      "Path: ethernet3.performance.ifInHwPriorityQueues.d7Performance.bandwidth

       unit name = bps
       formula = 8 * ; 8 /"
   ::= {pr1646v2Lan3FGIfInHwPriorityQueuesD7PerformanceEntry 268435456}



ar1646v2Lan3FG OBJECT IDENTIFIER ::= {r1646v2Lan3FG 16}


ar1646v2Lan3FGClearCounters OBJECT-TYPE
   SYNTAX      Integer32
   MAX-ACCESS  read-write
   STATUS      current
   DESCRIPTION
      "Path: ethernet3.actions.clearCounters
       Info: reset counters"
   ::= {ar1646v2Lan3FG 263}


ar1646v2Lan3FGPowerToggle OBJECT-TYPE
   SYNTAX      Integer32
   MAX-ACCESS  read-write
   STATUS      current
   DESCRIPTION
      "Path: ethernet3.actions.powerToggle
       Info: action in the debug group"
   ::= {ar1646v2Lan3FG 68}


ar1646v2Lan3FGRestartIntf OBJECT-TYPE
   SYNTAX      Integer32
   MAX-ACCESS  read-write
   STATUS      current
   DESCRIPTION
      "Path: ethernet3.actions.restartIntf
       Info: action in the debug group"
   ::= {ar1646v2Lan3FG 67}


ar1646v2Lan3FGClearOamEventLog OBJECT-TYPE
   SYNTAX      Integer32
   MAX-ACCESS  read-write
   STATUS      current
   DESCRIPTION
      "Path: ethernet3.actions.clearOamEventLog
       Info: clear the OAM event log"
   ::= {ar1646v2Lan3FG 916}


ar1646v2Lan3FGLoopback OBJECT-TYPE
   SYNTAX      Integer32
   MAX-ACCESS  read-write
   STATUS      current
   DESCRIPTION
      "Path: ethernet3.actions.loopback
       Info: ethernet loopback"
   ::= {ar1646v2Lan3FG 914}


ar1646v2Lan3FGLoop OBJECT IDENTIFIER ::= {ar1646v2Lan3FG 915}

ar1646v2Lan3FGLoopSSC OBJECT IDENTIFIER ::= {ar1646v2Lan3FGLoop 1}

ar1646v2Lan3FGLoopEntry OBJECT IDENTIFIER ::= {ar1646v2Lan3FGLoopSSC 1}

ar1646v2Lan3FGLoopAction OBJECT-TYPE
   SYNTAX      INTEGER
               {
               start (1),
               stop (2)
               }
   MAX-ACCESS  read-write
   STATUS      current
   DESCRIPTION
      "Path: ethernet3.actions.loop.action

       Possibilities:
               start   (1)
               stop   (2)"
   ::= {ar1646v2Lan3FGLoopEntry 16777216}

ar1646v2Lan3FGLoopTime OBJECT-TYPE
   SYNTAX      TimeTicks
   MAX-ACCESS  read-write
   STATUS      current
   DESCRIPTION
      "Path: ethernet3.actions.loop.time

       Time in centi-second."
   ::= {ar1646v2Lan3FGLoopEntry 50331648}

ar1646v2Lan3FGLoopIntfName OBJECT-TYPE
   SYNTAX      DisplayString
   MAX-ACCESS  read-write
   STATUS      current
   DESCRIPTION
      "Path: ethernet3.actions.loop.intfName"
   ::= {ar1646v2Lan3FGLoopEntry 67108864}


ar1646v2Lan3FGOamRemLoopback OBJECT-TYPE
   SYNTAX      Integer32
   MAX-ACCESS  read-write
   STATUS      current
   DESCRIPTION
      "Path: ethernet3.actions.oamRemLoopback
       Info: OAM Remote Loopback"
   ::= {ar1646v2Lan3FG 912}


ar1646v2Lan3FGType OBJECT-TYPE
   SYNTAX      INTEGER
               {
               start (0),
               stop (1)
               }
   MAX-ACCESS  read-write
   STATUS      current
   DESCRIPTION
      "Path: ethernet3.actions.type
       Info: OAM Remote Loopback type

       Possibilities:
               start   (0)
               stop   (1)"
   ::= {ar1646v2Lan3FG 913}


ar1646v2Lan3FGSendWOL OBJECT-TYPE
   SYNTAX      Integer32
   MAX-ACCESS  read-write
   STATUS      current
   DESCRIPTION
      "Path: ethernet3.actions.sendWOL
       Info: send a WakeOnLan message on this interface"
   ::= {ar1646v2Lan3FG 333}


ar1646v2Lan3FGWolInfo OBJECT IDENTIFIER ::= {ar1646v2Lan3FG 332}

ar1646v2Lan3FGWolInfoSSC OBJECT IDENTIFIER ::= {ar1646v2Lan3FGWolInfo 1}

ar1646v2Lan3FGWolInfoEntry OBJECT IDENTIFIER ::= {ar1646v2Lan3FGWolInfoSSC 1}

ar1646v2Lan3FGWolInfoTargetMAC OBJECT-TYPE
   SYNTAX      OCTET STRING
   MAX-ACCESS  read-write
   STATUS      current
   DESCRIPTION
      "Path: ethernet3.actions.wolInfo.targetMAC

       MAC address."
   ::= {ar1646v2Lan3FGWolInfoEntry 16777216}

ar1646v2Lan3FGWolInfoPassword OBJECT-TYPE
   SYNTAX      OCTET STRING
   MAX-ACCESS  read-write
   STATUS      current
   DESCRIPTION
      "Path: ethernet3.actions.wolInfo.password"
   ::= {ar1646v2Lan3FGWolInfoEntry 33554432}


ar1646v2Lan3FGClearArpCache OBJECT-TYPE
   SYNTAX      Integer32
   MAX-ACCESS  read-write
   STATUS      current
   DESCRIPTION
      "Path: ethernet3.actions.clearArpCache
       Info: clear all dynamic enties in ARP cache table"
   ::= {ar1646v2Lan3FG 25}


ar1646v2Lan3FGClearDebugCounters OBJECT-TYPE
   SYNTAX      Integer32
   MAX-ACCESS  read-write
   STATUS      current
   DESCRIPTION
      "Path: ethernet3.actions.clearDebugCounters
       Info: action in the debug group"
   ::= {ar1646v2Lan3FG 76}


ar1646v2Lan3FGEnableRds OBJECT-TYPE
   SYNTAX      Integer32
   MAX-ACCESS  read-write
   STATUS      current
   DESCRIPTION
      "Path: ethernet3.actions.enableRds
       Info: action in the debug group"
   ::= {ar1646v2Lan3FG 367}


ar1646v2Lan3FGDisableRds OBJECT-TYPE
   SYNTAX      Integer32
   MAX-ACCESS  read-write
   STATUS      current
   DESCRIPTION
      "Path: ethernet3.actions.disableRds
       Info: action in the debug group"
   ::= {ar1646v2Lan3FG 366}


ar1646v2Lan3FGEnableTds OBJECT-TYPE
   SYNTAX      Integer32
   MAX-ACCESS  read-write
   STATUS      current
   DESCRIPTION
      "Path: ethernet3.actions.enableTds
       Info: action in the debug group"
   ::= {ar1646v2Lan3FG 365}


ar1646v2Lan3FGDisableTds OBJECT-TYPE
   SYNTAX      Integer32
   MAX-ACCESS  read-write
   STATUS      current
   DESCRIPTION
      "Path: ethernet3.actions.disableTds
       Info: action in the debug group"
   ::= {ar1646v2Lan3FG 364}


ar1646v2Lan3FGClearTsecStats OBJECT-TYPE
   SYNTAX      Integer32
   MAX-ACCESS  read-write
   STATUS      current
   DESCRIPTION
      "Path: ethernet3.actions.clearTsecStats
       Info: action in the debug group"
   ::= {ar1646v2Lan3FG 363}


ar1646v2Lan3FGStopTsecStats OBJECT-TYPE
   SYNTAX      Integer32
   MAX-ACCESS  read-write
   STATUS      current
   DESCRIPTION
      "Path: ethernet3.actions.stopTsecStats
       Info: action in the debug group"
   ::= {ar1646v2Lan3FG 362}


ar1646v2Lan3FGStartTsecStats OBJECT-TYPE
   SYNTAX      Integer32
   MAX-ACCESS  read-write
   STATUS      current
   DESCRIPTION
      "Path: ethernet3.actions.startTsecStats
       Info: action in the debug group"
   ::= {ar1646v2Lan3FG 361}


ar1646v2Lan3FGPhyAction OBJECT-TYPE
   SYNTAX      Integer32
   MAX-ACCESS  read-write
   STATUS      current
   DESCRIPTION
      "Path: ethernet3.actions.phyAction
       Info: action in the debug group"
   ::= {ar1646v2Lan3FG 90}


ar1646v2Lan3FGMbPhyAction OBJECT-TYPE
   SYNTAX      Integer32
   MAX-ACCESS  read-write
   STATUS      current
   DESCRIPTION
      "Path: ethernet3.actions.mbPhyAction
       Info: action in the debug group"
   ::= {ar1646v2Lan3FG 92}



fr1646v2Lan3FG OBJECT IDENTIFIER ::= {r1646v2Lan3FG 13}


fr1646v2Lan3FGAlarm OBJECT IDENTIFIER ::= {fr1646v2Lan3FG 207}

fr1646v2Lan3FGAlarmSSC OBJECT IDENTIFIER ::= {fr1646v2Lan3FGAlarm 1}

fr1646v2Lan3FGAlarmEntry OBJECT IDENTIFIER ::= {fr1646v2Lan3FGAlarmSSC 1}

fr1646v2Lan3FGAlarmDiscriminator OBJECT-TYPE
   SYNTAX      Integer32
   MAX-ACCESS  read-only
   STATUS      current
   DESCRIPTION
      "Path: ethernet3.alarms.alarmInfo.discriminator"
   ::= {fr1646v2Lan3FGAlarmEntry 16777216}

fr1646v2Lan3FGAlarmCurrent OBJECT-TYPE
   SYNTAX      Integer32
   MAX-ACCESS  read-only
   STATUS      current
   DESCRIPTION
      "Path: ethernet3.alarms.alarmInfo.currentAlarms

       Bit meanings:
               bit 0 = linkDown,
               bit 9 = pppoEDown"
   ::= {fr1646v2Lan3FGAlarmEntry 33554432}

fr1646v2Lan3FGAlarmPrevious OBJECT-TYPE
   SYNTAX      Integer32
   MAX-ACCESS  read-only
   STATUS      current
   DESCRIPTION
      "Path: ethernet3.alarms.alarmInfo.previousAlarms

       Bit meanings:
               bit 0 = linkDown,
               bit 9 = pppoEDown"
   ::= {fr1646v2Lan3FGAlarmEntry 50331648}

fr1646v2Lan3FGAlarmMask OBJECT-TYPE
   SYNTAX      Integer32
   MAX-ACCESS  read-only
   STATUS      current
   DESCRIPTION
      "Path: ethernet3.alarms.alarmInfo.alarmMask

       Bit meanings:
               bit 0 = linkDown,
               bit 9 = pppoEDown"
   ::= {fr1646v2Lan3FGAlarmEntry 67108864}

fr1646v2Lan3FGAlarmLevLinkDown OBJECT-TYPE
   SYNTAX      Integer32
   MAX-ACCESS  read-only
   STATUS      current
   DESCRIPTION
      "Path: ethernet3.alarms.alarmInfo.alarmLevel.linkDown"
   ::= {fr1646v2Lan3FGAlarmEntry 83951616}

fr1646v2Lan3FGAlarmLevPppoEDown OBJECT-TYPE
   SYNTAX      Integer32
   MAX-ACCESS  read-only
   STATUS      current
   DESCRIPTION
      "Path: ethernet3.alarms.alarmInfo.alarmLevel.pppoEDown"
   ::= {fr1646v2Lan3FGAlarmEntry 84541440}


fr1646v2Lan3FGAlarmE2 OBJECT IDENTIFIER ::= {fr1646v2Lan3FGAlarm 2}

fr1646v2Lan3FGAlarmE2Entry OBJECT IDENTIFIER ::= {fr1646v2Lan3FGAlarmE2 1}

fr1646v2Lan3FGAlarmE2LinkDown OBJECT IDENTIFIER ::= {fr1646v2Lan3FGAlarmE2Entry 10}

fr1646v2Lan3FGAlarmE2LinkDownPfx OBJECT IDENTIFIER ::= {fr1646v2Lan3FGAlarmE2LinkDown 0}

fr1646v2Lan3FGAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg3Giga'
                (root='router1646') has changed from the ON to the OFF state."
   ::= {fr1646v2Lan3FGAlarmE2LinkDownPfx 1}

fr1646v2Lan3FGAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg3Giga'
                (root='router1646') has changed from the OFF to the ON state."
   ::= {fr1646v2Lan3FGAlarmE2LinkDownPfx 2}

fr1646v2Lan3FGAlarmE2PppoEDown OBJECT IDENTIFIER ::= {fr1646v2Lan3FGAlarmE2Entry 19}

fr1646v2Lan3FGAlarmE2PppoEDownPfx OBJECT IDENTIFIER ::= {fr1646v2Lan3FGAlarmE2PppoEDown 0}

fr1646v2Lan3FGAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg3Giga'
                (root='router1646') has changed from the ON to the OFF state."
   ::= {fr1646v2Lan3FGAlarmE2PppoEDownPfx 1}

fr1646v2Lan3FGAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg3Giga'
                (root='router1646') has changed from the OFF to the ON state."
   ::= {fr1646v2Lan3FGAlarmE2PppoEDownPfx 2}



END
