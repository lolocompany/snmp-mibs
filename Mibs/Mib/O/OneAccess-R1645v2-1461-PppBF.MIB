OneAccess-R1645v2-1461-PppBF DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2PppBF OBJECT IDENTIFIER ::= {r1645Rootv2 1461}

r1645v2PppBFMOProp OBJECT-TYPE
   SYNTAX      SEQUENCE OF R1645v2PppBFMOPropEntry
   MAX-ACCESS  not-accessible
   STATUS      current
   DESCRIPTION
      ""
   ::= {r1645v2PppBF 1}

r1645v2PppBFMOPropEntry OBJECT-TYPE
   SYNTAX      R1645v2PppBFMOPropEntry
   MAX-ACCESS  not-accessible
   STATUS      current
   DESCRIPTION
      ""
   INDEX      { r1645v2PppBFMOPropGlobalIx }
   ::= {r1645v2PppBFMOProp 1}

R1645v2PppBFMOPropEntry ::=
   SEQUENCE
      {
      r1645v2PppBFMOPropPath
         ContainmentPath,
      r1645v2PppBFMOPropRev
         ObjectRevision,
      r1645v2PppBFMOPropGlobalIx
         GlobalIndex
      }

r1645v2PppBFMOPropPath OBJECT-TYPE
   SYNTAX      ContainmentPath
   MAX-ACCESS  read-only
   STATUS      current
   DESCRIPTION
      "Textual description of the containment tree from the instance of
       the root object down to the instance of the current object."
   ::= {r1645v2PppBFMOPropEntry 3}

r1645v2PppBFMOPropRev OBJECT-TYPE
   SYNTAX      ObjectRevision
   MAX-ACCESS  read-only
   STATUS      current
   DESCRIPTION
      "This value corresponds with the revision of the MANAGED OBJECT."
   ::= {r1645v2PppBFMOPropEntry 4}

r1645v2PppBFMOPropGlobalIx OBJECT-TYPE
   SYNTAX      GlobalIndex
   MAX-ACCESS  read-only
   STATUS      current
   DESCRIPTION
      "The value of the tlsCntTreeGlobalIndex of the MANAGED OBJECT."
   ::= {r1645v2PppBFMOPropEntry 10}



er1645v2PppBF OBJECT IDENTIFIER ::= {r1645v2PppBF 11}


er1645v2PppBFSnmpIndexOffset OBJECT IDENTIFIER ::= {er1645v2PppBF 268}

er1645v2PppBFSnmpIndexOffsetTable OBJECT-TYPE
   SYNTAX      SEQUENCE OF Er1645v2PppBFSnmpIndexOffsetEntry
   MAX-ACCESS  not-accessible
   STATUS      current
   DESCRIPTION
      "Preferred offset in the range of SNMP indices for this SWinst, 0 means automatic"
   ::= {er1645v2PppBFSnmpIndexOffset 1}

er1645v2PppBFSnmpIndexOffsetEntry OBJECT-TYPE
   SYNTAX      Er1645v2PppBFSnmpIndexOffsetEntry
   MAX-ACCESS  not-accessible
   STATUS      current
   DESCRIPTION
      ""
   INDEX      { er1645v2PppBFSnmpIndexOffsetGlobalIx }
   ::= {er1645v2PppBFSnmpIndexOffsetTable 1}

Er1645v2PppBFSnmpIndexOffsetEntry ::=
   SEQUENCE
      {
      er1645v2PppBFSnmpIndexOffsetGlobalIx
         GlobalIndex,
      er1645v2PppBFSnmpIndexOffsetValue
         Integer32
      }

er1645v2PppBFSnmpIndexOffsetGlobalIx OBJECT-TYPE
   SYNTAX      GlobalIndex
   MAX-ACCESS  not-accessible
   STATUS      current
   DESCRIPTION
      "The value of the tlsCntTreeGlobalIndex of the MANAGED OBJECT."
   ::= {er1645v2PppBFSnmpIndexOffsetEntry 10}

er1645v2PppBFSnmpIndexOffsetValue OBJECT-TYPE
   SYNTAX      Integer32
   MAX-ACCESS  read-write
   STATUS      current
   DESCRIPTION
      "Path: pppBundle.editConf.snmpIndexOffset"
   ::= {er1645v2PppBFSnmpIndexOffsetEntry 2147483648}


er1645v2PppBFRemark OBJECT IDENTIFIER ::= {er1645v2PppBF 321}

er1645v2PppBFRemarkTable OBJECT-TYPE
   SYNTAX      SEQUENCE OF Er1645v2PppBFRemarkEntry
   MAX-ACCESS  not-accessible
   STATUS      current
   DESCRIPTION
      "intfRemark"
   ::= {er1645v2PppBFRemark 1}

er1645v2PppBFRemarkEntry OBJECT-TYPE
   SYNTAX      Er1645v2PppBFRemarkEntry
   MAX-ACCESS  not-accessible
   STATUS      current
   DESCRIPTION
      ""
   INDEX      { er1645v2PppBFRemarkGlobalIx }
   ::= {er1645v2PppBFRemarkTable 1}

Er1645v2PppBFRemarkEntry ::=
   SEQUENCE
      {
      er1645v2PppBFRemarkGlobalIx
         GlobalIndex,
      er1645v2PppBFRemarkValue
         DisplayString
      }

er1645v2PppBFRemarkGlobalIx OBJECT-TYPE
   SYNTAX      GlobalIndex
   MAX-ACCESS  not-accessible
   STATUS      current
   DESCRIPTION
      "The value of the tlsCntTreeGlobalIndex of the MANAGED OBJECT."
   ::= {er1645v2PppBFRemarkEntry 10}

er1645v2PppBFRemarkValue OBJECT-TYPE
   SYNTAX      DisplayString
   MAX-ACCESS  read-write
   STATUS      current
   DESCRIPTION
      "Path: pppBundle.editConf.remark"
   ::= {er1645v2PppBFRemarkEntry 2147483648}


er1645v2PppBFBrC OBJECT IDENTIFIER ::= {er1645v2PppBF 2}

er1645v2PppBFBrCSSCTable OBJECT-TYPE
   SYNTAX      SEQUENCE OF Er1645v2PppBFBrCEntry
   MAX-ACCESS  not-accessible
   STATUS      current
   DESCRIPTION
      "Set bridging parameters"
   ::= {er1645v2PppBFBrC 1}

er1645v2PppBFBrCEntry OBJECT-TYPE
   SYNTAX      Er1645v2PppBFBrCEntry
   MAX-ACCESS  not-accessible
   STATUS      current
   DESCRIPTION
      ""
   INDEX      { er1645v2PppBFBrCGlobalIx }
   ::= {er1645v2PppBFBrCSSCTable 1}

Er1645v2PppBFBrCEntry ::=
   SEQUENCE
      {
      er1645v2PppBFBrCGlobalIx
         GlobalIndex,
      er1645v2PppBFBrCAccessList
         DisplayString,
      er1645v2PppBFBrCInAccessList
         DisplayString,
      er1645v2PppBFBrCTp
         DisplayString,
      er1645v2PppBFBrCBridgeGroup
         DisplayString,
      er1645v2PppBFBrCLimBC
         INTEGER,
      er1645v2PppBFBrCPrivateMode
         INTEGER,
      er1645v2PppBFBrCLearning
         INTEGER,
      er1645v2PppBFBrCMaxCacheSize
         INTEGER,
      er1645v2PppBFBrCRelearnDropOnRelearn
         INTEGER,
      er1645v2PppBFBrCRelearnShutdownThreshold
         Integer32,
      er1645v2PppBFBrCRelearnShutdownTime
         TimeTicks,
      er1645v2PppBFBrCRelearnLoopDetection
         INTEGER,
      er1645v2PppBFBrCRelearnLoopDetectionInterval
         TimeTicks,
      er1645v2PppBFBrCVlanMemberShip
         INTEGER,
      er1645v2PppBFBrCVlTUntaggedAction
         INTEGER,
      er1645v2PppBFBrCVlTUntaggedTagInfoTpid
         INTEGER,
      er1645v2PppBFBrCVlTUntaggedTagInfoVid
         Integer32,
      er1645v2PppBFBrCVlTUnknownVlansAction
         INTEGER,
      er1645v2PppBFBrCVlTUnknownVlansTagInfoTpid
         INTEGER,
      er1645v2PppBFBrCVlTUnknownVlansTagInfoVid
         Integer32,
      er1645v2PppBFBrCDot1adType
         INTEGER,
      er1645v2PppBFBrCPriority
         Integer32,
      er1645v2PppBFBrCPathCost
         Integer32,
      er1645v2PppBFBrCInternalPathCost
         Integer32,
      er1645v2PppBFBrCTCD
         INTEGER,
      er1645v2PppBFBrCRestrictedRole
         INTEGER,
      er1645v2PppBFBrCAdminEdge
         INTEGER,
      er1645v2PppBFBrCOamMacDeviceMac
         DisplayString,
      er1645v2PppBFBrCOamMacUserMac
         OCTET STRING,
      er1645v2PppBFBrCOamMacBridgeMac
         DisplayString,
      er1645v2PppBFBrCMgmtInline
         INTEGER,
      er1645v2PppBFBrCL2ptMode
         INTEGER,
      er1645v2PppBFBrCL2ptProtocols
         Integer32,
      er1645v2PppBFBrCL2ptDestMac
         OCTET STRING,
      er1645v2PppBFBrCL2ptCos
         INTEGER,
      er1645v2PppBFBrCL2ptDropThrStp
         INTEGER,
      er1645v2PppBFBrCL2ptDropThrLldp
         INTEGER,
      er1645v2PppBFBrCL2ptDropThrOam
         INTEGER,
      er1645v2PppBFBrCL2ptDropThrCdp
         INTEGER,
      er1645v2PppBFBrCL2ptDropThrVtp
         INTEGER,
      er1645v2PppBFBrCL2ptDropThrLacp
         INTEGER,
      er1645v2PppBFBrCL2ptDropThrEfmOam
         INTEGER,
      er1645v2PppBFBrCL2ptDropThrPvst
         INTEGER,
      er1645v2PppBFBrCL2ptDropThrMmrp
         INTEGER,
      er1645v2PppBFBrCL2ptDropThrMvrp
         INTEGER,
      er1645v2PppBFBrCL2ptDropThrGvrp
         INTEGER,
      er1645v2PppBFBrCL2ptDropThrGmrp
         INTEGER,
      er1645v2PppBFBrCL2ptDropThrDtp
         INTEGER,
      er1645v2PppBFBrCL2ptDropThrPagp
         INTEGER,
      er1645v2PppBFBrCL2ptDropThrUdld
         INTEGER
      }

er1645v2PppBFBrCGlobalIx OBJECT-TYPE
   SYNTAX      GlobalIndex
   MAX-ACCESS  not-accessible
   STATUS      current
   DESCRIPTION
      "The value of the tlsCntTreeGlobalIndex of the MANAGED OBJECT."
   ::= {er1645v2PppBFBrCEntry 10}

er1645v2PppBFBrCAccessList OBJECT-TYPE
   SYNTAX      DisplayString
   MAX-ACCESS  read-write
   STATUS      current
   DESCRIPTION
      "Path: pppBundle.editConf.bridging.accessList"
   ::= {er1645v2PppBFBrCEntry 83886080}

er1645v2PppBFBrCInAccessList OBJECT-TYPE
   SYNTAX      DisplayString
   MAX-ACCESS  read-write
   STATUS      current
   DESCRIPTION
      "Path: pppBundle.editConf.bridging.inAccessList"
   ::= {er1645v2PppBFBrCEntry 251658240}

er1645v2PppBFBrCTp OBJECT-TYPE
   SYNTAX      DisplayString
   MAX-ACCESS  read-write
   STATUS      current
   DESCRIPTION
      "Path: pppBundle.editConf.bridging.trafficPolicy"
   ::= {er1645v2PppBFBrCEntry 100663296}

er1645v2PppBFBrCBridgeGroup OBJECT-TYPE
   SYNTAX      DisplayString
   MAX-ACCESS  read-write
   STATUS      current
   DESCRIPTION
      "Path: pppBundle.editConf.bridging.bridgeGroup"
   ::= {er1645v2PppBFBrCEntry 117440512}

er1645v2PppBFBrCLimBC OBJECT-TYPE
   SYNTAX      INTEGER
               {
               disabled (0),
               enabled (1)
               }
   MAX-ACCESS  read-write
   STATUS      current
   DESCRIPTION
      "Path: pppBundle.editConf.bridging.limitBroadcasts

       Possibilities:
               disabled   (0)
               enabled   (1)"
   ::= {er1645v2PppBFBrCEntry 134217728}

er1645v2PppBFBrCPrivateMode OBJECT-TYPE
   SYNTAX      INTEGER
               {
               disabled (0),
               enabled (1)
               }
   MAX-ACCESS  read-write
   STATUS      current
   DESCRIPTION
      "Path: pppBundle.editConf.bridging.privateMode

       Possibilities:
               disabled   (0)
               enabled   (1)"
   ::= {er1645v2PppBFBrCEntry 419430400}

er1645v2PppBFBrCLearning OBJECT-TYPE
   SYNTAX      INTEGER
               {
               disabled (0),
               enabled (1)
               }
   MAX-ACCESS  read-write
   STATUS      current
   DESCRIPTION
      "Path: pppBundle.editConf.bridging.learning

       Possibilities:
               disabled   (0)
               enabled   (1)"
   ::= {er1645v2PppBFBrCEntry 201326592}

er1645v2PppBFBrCMaxCacheSize OBJECT-TYPE
   SYNTAX      INTEGER
               {
               unlimited (0)
               }
   MAX-ACCESS  read-write
   STATUS      current
   DESCRIPTION
      "Path: pppBundle.editConf.bridging.maxCacheSize

       Possibilities:
               unlimited   (0)"
   ::= {er1645v2PppBFBrCEntry 218103808}

er1645v2PppBFBrCRelearnDropOnRelearn OBJECT-TYPE
   SYNTAX      INTEGER
               {
               disabled (0),
               enabled (1)
               }
   MAX-ACCESS  read-write
   STATUS      current
   DESCRIPTION
      "Path: pppBundle.editConf.bridging.relearn.dropOnRelearn

       Possibilities:
               disabled   (0)
               enabled   (1)"
   ::= {er1645v2PppBFBrCEntry 234946560}

er1645v2PppBFBrCRelearnShutdownThreshold OBJECT-TYPE
   SYNTAX      Integer32
   MAX-ACCESS  read-write
   STATUS      current
   DESCRIPTION
      "Path: pppBundle.editConf.bridging.relearn.shutdownThreshold"
   ::= {er1645v2PppBFBrCEntry 235012096}

er1645v2PppBFBrCRelearnShutdownTime OBJECT-TYPE
   SYNTAX      TimeTicks
   MAX-ACCESS  read-write
   STATUS      current
   DESCRIPTION
      "Path: pppBundle.editConf.bridging.relearn.shutdownTime

       Time in centi-second."
   ::= {er1645v2PppBFBrCEntry 235077632}

er1645v2PppBFBrCRelearnLoopDetection OBJECT-TYPE
   SYNTAX      INTEGER
               {
               disabled (0),
               passive (1),
               active (2)
               }
   MAX-ACCESS  read-write
   STATUS      current
   DESCRIPTION
      "Path: pppBundle.editConf.bridging.relearn.loopDetection

       Possibilities:
               disabled   (0)
               passive   (1)
               active   (2)"
   ::= {er1645v2PppBFBrCEntry 235143168}

er1645v2PppBFBrCRelearnLoopDetectionInterval OBJECT-TYPE
   SYNTAX      TimeTicks
   MAX-ACCESS  read-write
   STATUS      current
   DESCRIPTION
      "Path: pppBundle.editConf.bridging.relearn.loopDetectionInterval

       Time in centi-second."
   ::= {er1645v2PppBFBrCEntry 235208704}

er1645v2PppBFBrCVlanMemberShip OBJECT-TYPE
   SYNTAX      INTEGER
               {
               all (0),
               none (1),
               grouped (2)
               }
   MAX-ACCESS  read-write
   STATUS      current
   DESCRIPTION
      "Path: pppBundle.editConf.bridging.vlanMemberShip

       Possibilities:
               all   (0)
               none   (1)
               grouped   (2)"
   ::= {er1645v2PppBFBrCEntry 318767104}

er1645v2PppBFBrCVlTUntaggedAction OBJECT-TYPE
   SYNTAX      INTEGER
               {
               discard (0),
               accept (1),
               tag (2)
               }
   MAX-ACCESS  read-write
   STATUS      current
   DESCRIPTION
      "Path: pppBundle.editConf.bridging.vlanTagging.untagged.action

       Possibilities:
               discard   (0)
               accept   (1)
               tag   (2)"
   ::= {er1645v2PppBFBrCEntry 388497408}

er1645v2PppBFBrCVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: pppBundle.editConf.bridging.vlanTagging.untagged.tagInfo.tpid

       Possibilities:
               dot1Q   (33024)
               dot1ad   (34984)
               0x9100   (37120)
               0x9200   (37376)
               0x9300   (37632)"
   ::= {er1645v2PppBFBrCEntry 388792320}

er1645v2PppBFBrCVlTUntaggedTagInfoVid OBJECT-TYPE
   SYNTAX      Integer32
   MAX-ACCESS  read-write
   STATUS      current
   DESCRIPTION
      "Path: pppBundle.editConf.bridging.vlanTagging.untagged.tagInfo.vid"
   ::= {er1645v2PppBFBrCEntry 388825088}

er1645v2PppBFBrCVlTUnknownVlansAction OBJECT-TYPE
   SYNTAX      INTEGER
               {
               discard (0),
               accept (1),
               tag (2)
               }
   MAX-ACCESS  read-write
   STATUS      current
   DESCRIPTION
      "Path: pppBundle.editConf.bridging.vlanTagging.unknownVlans.action

       Possibilities:
               discard   (0)
               accept   (1)
               tag   (2)"
   ::= {er1645v2PppBFBrCEntry 392691712}

er1645v2PppBFBrCVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: pppBundle.editConf.bridging.vlanTagging.unknownVlans.tagInfo.tpid

       Possibilities:
               dot1Q   (33024)
               dot1ad   (34984)
               0x9100   (37120)
               0x9200   (37376)
               0x9300   (37632)"
   ::= {er1645v2PppBFBrCEntry 392986624}

er1645v2PppBFBrCVlTUnknownVlansTagInfoVid OBJECT-TYPE
   SYNTAX      Integer32
   MAX-ACCESS  read-write
   STATUS      current
   DESCRIPTION
      "Path: pppBundle.editConf.bridging.vlanTagging.unknownVlans.tagInfo.vid"
   ::= {er1645v2PppBFBrCEntry 393019392}

er1645v2PppBFBrCDot1adType OBJECT-TYPE
   SYNTAX      INTEGER
               {
               slOPTg (0),
               cPort (4),
               sPort (1),
               nni (2)
               }
   MAX-ACCESS  read-write
   STATUS      current
   DESCRIPTION
      "Path: pppBundle.editConf.bridging.dot1ad.type

       Possibilities:
               <OPT>   (0)
               cPort   (4)
               sPort   (1)
               nni   (2)"
   ::= {er1645v2PppBFBrCEntry 503382016}

er1645v2PppBFBrCPriority OBJECT-TYPE
   SYNTAX      Integer32
   MAX-ACCESS  read-write
   STATUS      current
   DESCRIPTION
      "Path: pppBundle.editConf.bridging.priority"
   ::= {er1645v2PppBFBrCEntry 33554432}

er1645v2PppBFBrCPathCost OBJECT-TYPE
   SYNTAX      Integer32
   MAX-ACCESS  read-write
   STATUS      current
   DESCRIPTION
      "Path: pppBundle.editConf.bridging.pathCost"
   ::= {er1645v2PppBFBrCEntry 50331648}

er1645v2PppBFBrCInternalPathCost OBJECT-TYPE
   SYNTAX      Integer32
   MAX-ACCESS  read-write
   STATUS      current
   DESCRIPTION
      "Path: pppBundle.editConf.bridging.internalPathCost"
   ::= {er1645v2PppBFBrCEntry 301989888}

er1645v2PppBFBrCTCD OBJECT-TYPE
   SYNTAX      INTEGER
               {
               disabled (0),
               enabled (1)
               }
   MAX-ACCESS  read-write
   STATUS      current
   DESCRIPTION
      "Path: pppBundle.editConf.bridging.topologyChangeDetection

       Possibilities:
               disabled   (0)
               enabled   (1)"
   ::= {er1645v2PppBFBrCEntry 67108864}

er1645v2PppBFBrCRestrictedRole OBJECT-TYPE
   SYNTAX      INTEGER
               {
               disabled (0),
               enabled (1)
               }
   MAX-ACCESS  read-write
   STATUS      current
   DESCRIPTION
      "Path: pppBundle.editConf.bridging.restrictedRole

       Possibilities:
               disabled   (0)
               enabled   (1)"
   ::= {er1645v2PppBFBrCEntry 335544320}

er1645v2PppBFBrCAdminEdge OBJECT-TYPE
   SYNTAX      INTEGER
               {
               disabled (0),
               enabled (1)
               }
   MAX-ACCESS  read-write
   STATUS      current
   DESCRIPTION
      "Path: pppBundle.editConf.bridging.adminEdge

       Possibilities:
               disabled   (0)
               enabled   (1)"
   ::= {er1645v2PppBFBrCEntry 268435456}

er1645v2PppBFBrCOamMacDeviceMac OBJECT-TYPE
   SYNTAX      DisplayString
   MAX-ACCESS  read-write
   STATUS      current
   DESCRIPTION
      "Path: pppBundle.editConf.bridging.ethOam.macAddress.deviceMac"
   ::= {er1645v2PppBFBrCEntry 353386496}

er1645v2PppBFBrCOamMacUserMac OBJECT-TYPE
   SYNTAX      OCTET STRING
   MAX-ACCESS  read-write
   STATUS      current
   DESCRIPTION
      "Path: pppBundle.editConf.bridging.ethOam.macAddress.userMac

       MAC address."
   ::= {er1645v2PppBFBrCEntry 353378304}

er1645v2PppBFBrCOamMacBridgeMac OBJECT-TYPE
   SYNTAX      DisplayString
   MAX-ACCESS  read-write
   STATUS      current
   DESCRIPTION
      "Path: pppBundle.editConf.bridging.ethOam.macAddress.bridgeMac"
   ::= {er1645v2PppBFBrCEntry 353382400}

er1645v2PppBFBrCMgmtInline OBJECT-TYPE
   SYNTAX      INTEGER
               {
               disabled (0),
               enabled (1)
               }
   MAX-ACCESS  read-write
   STATUS      current
   DESCRIPTION
      "Path: pppBundle.editConf.bridging.mgmtInline

       Possibilities:
               disabled   (0)
               enabled   (1)"
   ::= {er1645v2PppBFBrCEntry 369098752}

er1645v2PppBFBrCL2ptMode OBJECT-TYPE
   SYNTAX      INTEGER
               {
               disabled (0),
               enabled (1)
               }
   MAX-ACCESS  read-write
   STATUS      current
   DESCRIPTION
      "Path: pppBundle.editConf.bridging.l2ProtTunnel.mode

       Possibilities:
               disabled   (0)
               enabled   (1)"
   ::= {er1645v2PppBFBrCEntry 403701760}

er1645v2PppBFBrCL2ptProtocols OBJECT-TYPE
   SYNTAX      Integer32
   MAX-ACCESS  read-write
   STATUS      current
   DESCRIPTION
      "Path: pppBundle.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2PppBFBrCEntry 404750336}

er1645v2PppBFBrCL2ptDestMac OBJECT-TYPE
   SYNTAX      OCTET STRING
   MAX-ACCESS  read-write
   STATUS      current
   DESCRIPTION
      "Path: pppBundle.editConf.bridging.l2ProtTunnel.destinationMac

       MAC address."
   ::= {er1645v2PppBFBrCEntry 405798912}

er1645v2PppBFBrCL2ptCos OBJECT-TYPE
   SYNTAX      INTEGER
               {
               unchanged (255)
               }
   MAX-ACCESS  read-write
   STATUS      current
   DESCRIPTION
      "Path: pppBundle.editConf.bridging.l2ProtTunnel.cos

       Possibilities:
               unchanged   (255)"
   ::= {er1645v2PppBFBrCEntry 406847488}

er1645v2PppBFBrCL2ptDropThrStp OBJECT-TYPE
   SYNTAX      INTEGER
               {
               unlimited (0)
               }
   UNITS       "packets/sec"
   MAX-ACCESS  read-write
   STATUS      current
   DESCRIPTION
      "Path: pppBundle.editConf.bridging.l2ProtTunnel.dropThresholds.stp

       unit name = packets/sec

       Possibilities:
               unlimited   (0)"
   ::= {er1645v2PppBFBrCEntry 407900160}

er1645v2PppBFBrCL2ptDropThrLldp OBJECT-TYPE
   SYNTAX      INTEGER
               {
               unlimited (0)
               }
   UNITS       "packets/sec"
   MAX-ACCESS  read-write
   STATUS      current
   DESCRIPTION
      "Path: pppBundle.editConf.bridging.l2ProtTunnel.dropThresholds.lldp

       unit name = packets/sec

       Possibilities:
               unlimited   (0)"
   ::= {er1645v2PppBFBrCEntry 407904256}

er1645v2PppBFBrCL2ptDropThrOam OBJECT-TYPE
   SYNTAX      INTEGER
               {
               unlimited (0)
               }
   UNITS       "packets/sec"
   MAX-ACCESS  read-write
   STATUS      current
   DESCRIPTION
      "Path: pppBundle.editConf.bridging.l2ProtTunnel.dropThresholds.oam

       unit name = packets/sec

       Possibilities:
               unlimited   (0)"
   ::= {er1645v2PppBFBrCEntry 407908352}

er1645v2PppBFBrCL2ptDropThrCdp OBJECT-TYPE
   SYNTAX      INTEGER
               {
               unlimited (0)
               }
   UNITS       "packets/sec"
   MAX-ACCESS  read-write
   STATUS      current
   DESCRIPTION
      "Path: pppBundle.editConf.bridging.l2ProtTunnel.dropThresholds.cdp

       unit name = packets/sec

       Possibilities:
               unlimited   (0)"
   ::= {er1645v2PppBFBrCEntry 407912448}

er1645v2PppBFBrCL2ptDropThrVtp OBJECT-TYPE
   SYNTAX      INTEGER
               {
               unlimited (0)
               }
   UNITS       "packets/sec"
   MAX-ACCESS  read-write
   STATUS      current
   DESCRIPTION
      "Path: pppBundle.editConf.bridging.l2ProtTunnel.dropThresholds.vtp

       unit name = packets/sec

       Possibilities:
               unlimited   (0)"
   ::= {er1645v2PppBFBrCEntry 407916544}

er1645v2PppBFBrCL2ptDropThrLacp OBJECT-TYPE
   SYNTAX      INTEGER
               {
               unlimited (0)
               }
   UNITS       "packets/sec"
   MAX-ACCESS  read-write
   STATUS      current
   DESCRIPTION
      "Path: pppBundle.editConf.bridging.l2ProtTunnel.dropThresholds.lacp

       unit name = packets/sec

       Possibilities:
               unlimited   (0)"
   ::= {er1645v2PppBFBrCEntry 407920640}

er1645v2PppBFBrCL2ptDropThrEfmOam OBJECT-TYPE
   SYNTAX      INTEGER
               {
               unlimited (0)
               }
   UNITS       "packets/sec"
   MAX-ACCESS  read-write
   STATUS      current
   DESCRIPTION
      "Path: pppBundle.editConf.bridging.l2ProtTunnel.dropThresholds.efmOam

       unit name = packets/sec

       Possibilities:
               unlimited   (0)"
   ::= {er1645v2PppBFBrCEntry 407924736}

er1645v2PppBFBrCL2ptDropThrPvst OBJECT-TYPE
   SYNTAX      INTEGER
               {
               unlimited (0)
               }
   UNITS       "packets/sec"
   MAX-ACCESS  read-write
   STATUS      current
   DESCRIPTION
      "Path: pppBundle.editConf.bridging.l2ProtTunnel.dropThresholds.pvst

       unit name = packets/sec

       Possibilities:
               unlimited   (0)"
   ::= {er1645v2PppBFBrCEntry 407928832}

er1645v2PppBFBrCL2ptDropThrMmrp OBJECT-TYPE
   SYNTAX      INTEGER
               {
               unlimited (0)
               }
   UNITS       "packets/sec"
   MAX-ACCESS  read-write
   STATUS      current
   DESCRIPTION
      "Path: pppBundle.editConf.bridging.l2ProtTunnel.dropThresholds.mmrp

       unit name = packets/sec

       Possibilities:
               unlimited   (0)"
   ::= {er1645v2PppBFBrCEntry 407932928}

er1645v2PppBFBrCL2ptDropThrMvrp OBJECT-TYPE
   SYNTAX      INTEGER
               {
               unlimited (0)
               }
   UNITS       "packets/sec"
   MAX-ACCESS  read-write
   STATUS      current
   DESCRIPTION
      "Path: pppBundle.editConf.bridging.l2ProtTunnel.dropThresholds.mvrp

       unit name = packets/sec

       Possibilities:
               unlimited   (0)"
   ::= {er1645v2PppBFBrCEntry 407937024}

er1645v2PppBFBrCL2ptDropThrGvrp OBJECT-TYPE
   SYNTAX      INTEGER
               {
               unlimited (0)
               }
   UNITS       "packets/sec"
   MAX-ACCESS  read-write
   STATUS      current
   DESCRIPTION
      "Path: pppBundle.editConf.bridging.l2ProtTunnel.dropThresholds.gvrp

       unit name = packets/sec

       Possibilities:
               unlimited   (0)"
   ::= {er1645v2PppBFBrCEntry 407941120}

er1645v2PppBFBrCL2ptDropThrGmrp OBJECT-TYPE
   SYNTAX      INTEGER
               {
               unlimited (0)
               }
   UNITS       "packets/sec"
   MAX-ACCESS  read-write
   STATUS      current
   DESCRIPTION
      "Path: pppBundle.editConf.bridging.l2ProtTunnel.dropThresholds.gmrp

       unit name = packets/sec

       Possibilities:
               unlimited   (0)"
   ::= {er1645v2PppBFBrCEntry 407945216}

er1645v2PppBFBrCL2ptDropThrDtp OBJECT-TYPE
   SYNTAX      INTEGER
               {
               unlimited (0)
               }
   UNITS       "packets/sec"
   MAX-ACCESS  read-write
   STATUS      current
   DESCRIPTION
      "Path: pppBundle.editConf.bridging.l2ProtTunnel.dropThresholds.dtp

       unit name = packets/sec

       Possibilities:
               unlimited   (0)"
   ::= {er1645v2PppBFBrCEntry 407949312}

er1645v2PppBFBrCL2ptDropThrPagp OBJECT-TYPE
   SYNTAX      INTEGER
               {
               unlimited (0)
               }
   UNITS       "packets/sec"
   MAX-ACCESS  read-write
   STATUS      current
   DESCRIPTION
      "Path: pppBundle.editConf.bridging.l2ProtTunnel.dropThresholds.pagp

       unit name = packets/sec

       Possibilities:
               unlimited   (0)"
   ::= {er1645v2PppBFBrCEntry 407953408}

er1645v2PppBFBrCL2ptDropThrUdld OBJECT-TYPE
   SYNTAX      INTEGER
               {
               unlimited (0)
               }
   UNITS       "packets/sec"
   MAX-ACCESS  read-write
   STATUS      current
   DESCRIPTION
      "Path: pppBundle.editConf.bridging.l2ProtTunnel.dropThresholds.udld

       unit name = packets/sec

       Possibilities:
               unlimited   (0)"
   ::= {er1645v2PppBFBrCEntry 407957504}

er1645v2PppBFBrCVlTVlans OBJECT-TYPE
   SYNTAX      SEQUENCE OF Er1645v2PppBFBrCVlTVlansEntry
   MAX-ACCESS  not-accessible
   STATUS      current
   DESCRIPTION
      ""
   ::= {er1645v2PppBFBrC 390070272}

er1645v2PppBFBrCVlTVlansEntry OBJECT-TYPE
   SYNTAX      Er1645v2PppBFBrCVlTVlansEntry
   MAX-ACCESS  not-accessible
   STATUS      current
   DESCRIPTION
      ""
   INDEX      { er1645v2PppBFBrCVlTVlansGlobalIx,
                er1645v2PppBFBrCVlTVlansTableIx }
   ::= {er1645v2PppBFBrCVlTVlans 1}

Er1645v2PppBFBrCVlTVlansEntry ::=
   SEQUENCE
      {
      er1645v2PppBFBrCVlTVlansActions
         VariableLengthTableActions,
      er1645v2PppBFBrCVlTVlansGlobalIx
         GlobalIndex,
      er1645v2PppBFBrCVlTVlansTableIx
         TableIndex,
      er1645v2PppBFBrCVlTVlansVid
         Integer32,
      er1645v2PppBFBrCVlTVlansEndVid
         Integer32,
      er1645v2PppBFBrCVlTVlansAction
         INTEGER,
      er1645v2PppBFBrCVlTVlansTagInfoTpid
         INTEGER,
      er1645v2PppBFBrCVlTVlansTagInfoVid
         Integer32
      }

er1645v2PppBFBrCVlTVlansActions OBJECT-TYPE
   SYNTAX      VariableLengthTableActions
   MAX-ACCESS  read-write
   STATUS      current
   DESCRIPTION
      "By way of this field, some manipulations
       on this table may be performed."
   ::= {er1645v2PppBFBrCVlTVlansEntry 2}

er1645v2PppBFBrCVlTVlansGlobalIx OBJECT-TYPE
   SYNTAX      GlobalIndex
   MAX-ACCESS  not-accessible
   STATUS      current
   DESCRIPTION
      "The value of the tlsCntTreeGlobalIndex of the MANAGED OBJECT."
   ::= {er1645v2PppBFBrCVlTVlansEntry 10}

er1645v2PppBFBrCVlTVlansTableIx OBJECT-TYPE
   SYNTAX      TableIndex
   MAX-ACCESS  not-accessible
   STATUS      current
   DESCRIPTION
      ""
   ::= {er1645v2PppBFBrCVlTVlansEntry 11}

er1645v2PppBFBrCVlTVlansVid OBJECT-TYPE
   SYNTAX      Integer32
   MAX-ACCESS  read-write
   STATUS      current
   DESCRIPTION
      "Path: pppBundle.editConf.bridging.vlanTagging.vlans.vid"
   ::= {er1645v2PppBFBrCVlTVlansEntry 536870912}

er1645v2PppBFBrCVlTVlansEndVid OBJECT-TYPE
   SYNTAX      Integer32
   MAX-ACCESS  read-write
   STATUS      current
   DESCRIPTION
      "Path: pppBundle.editConf.bridging.vlanTagging.vlans.endVid"
   ::= {er1645v2PppBFBrCVlTVlansEntry 2147483648}

er1645v2PppBFBrCVlTVlansAction OBJECT-TYPE
   SYNTAX      INTEGER
               {
               discard (0),
               accept (1),
               tag (2)
               }
   MAX-ACCESS  read-write
   STATUS      current
   DESCRIPTION
      "Path: pppBundle.editConf.bridging.vlanTagging.vlans.action

       Possibilities:
               discard   (0)
               accept   (1)
               tag   (2)"
   ::= {er1645v2PppBFBrCVlTVlansEntry 1073741824}

er1645v2PppBFBrCVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: pppBundle.editConf.bridging.vlanTagging.vlans.tagInfo.tpid

       Possibilities:
               dot1Q   (33024)
               dot1ad   (34984)
               0x9100   (37120)
               0x9200   (37376)
               0x9300   (37632)"
   ::= {er1645v2PppBFBrCVlTVlansEntry 1677721600}

er1645v2PppBFBrCVlTVlansTagInfoVid OBJECT-TYPE
   SYNTAX      Integer32
   MAX-ACCESS  read-write
   STATUS      current
   DESCRIPTION
      "Path: pppBundle.editConf.bridging.vlanTagging.vlans.tagInfo.vid"
   ::= {er1645v2PppBFBrCVlTVlansEntry 1744830464}


er1645v2PppBFMode OBJECT IDENTIFIER ::= {er1645v2PppBF 3}

er1645v2PppBFModeTable OBJECT-TYPE
   SYNTAX      SEQUENCE OF Er1645v2PppBFModeEntry
   MAX-ACCESS  not-accessible
   STATUS      current
   DESCRIPTION
      "routing and/or bridging or ipV6 selection"
   ::= {er1645v2PppBFMode 1}

er1645v2PppBFModeEntry OBJECT-TYPE
   SYNTAX      Er1645v2PppBFModeEntry
   MAX-ACCESS  not-accessible
   STATUS      current
   DESCRIPTION
      ""
   INDEX      { er1645v2PppBFModeGlobalIx }
   ::= {er1645v2PppBFModeTable 1}

Er1645v2PppBFModeEntry ::=
   SEQUENCE
      {
      er1645v2PppBFModeGlobalIx
         GlobalIndex,
      er1645v2PppBFModeValue
         INTEGER
      }

er1645v2PppBFModeGlobalIx OBJECT-TYPE
   SYNTAX      GlobalIndex
   MAX-ACCESS  not-accessible
   STATUS      current
   DESCRIPTION
      "The value of the tlsCntTreeGlobalIndex of the MANAGED OBJECT."
   ::= {er1645v2PppBFModeEntry 10}

er1645v2PppBFModeValue OBJECT-TYPE
   SYNTAX      INTEGER
               {
               bridging (0),
               routing (1),
               routingAndBridging (2),
               ipV6 (3),
               ipV6ipV4 (4)
               }
   MAX-ACCESS  read-write
   STATUS      current
   DESCRIPTION
      "Path: pppBundle.editConf.mode

       Possibilities:
               bridging   (0)
               routing   (1)
               routingAndBridging   (2)
               ipV6   (3)
               ipV6/ipV4   (4)"
   ::= {er1645v2PppBFModeEntry 2147483648}


er1645v2PppBFIpV6 OBJECT IDENTIFIER ::= {er1645v2PppBF 39}

er1645v2PppBFIpV6SSCTable OBJECT-TYPE
   SYNTAX      SEQUENCE OF Er1645v2PppBFIpV6Entry
   MAX-ACCESS  not-accessible
   STATUS      current
   DESCRIPTION
      "IPv6 interface config parameters"
   ::= {er1645v2PppBFIpV6 1}

er1645v2PppBFIpV6Entry OBJECT-TYPE
   SYNTAX      Er1645v2PppBFIpV6Entry
   MAX-ACCESS  not-accessible
   STATUS      current
   DESCRIPTION
      ""
   INDEX      { er1645v2PppBFIpV6GlobalIx }
   ::= {er1645v2PppBFIpV6SSCTable 1}

Er1645v2PppBFIpV6Entry ::=
   SEQUENCE
      {
      er1645v2PppBFIpV6GlobalIx
         GlobalIndex,
      er1645v2PppBFIpV6VrfRouter
         DisplayString,
      er1645v2PppBFIpV6AddrAutoConfigNrDupAddrDetects
         Integer32,
      er1645v2PppBFIpV6AddrAutoConfigAcceptRa
         INTEGER,
      er1645v2PppBFIpV6AddrAutoConfigAcceptRaRdnss
         INTEGER,
      er1645v2PppBFIpV6AddrAutoConfigAcceptRaDnssl
         INTEGER,
      er1645v2PppBFIpV6DefaultRoute
         INTEGER,
      er1645v2PppBFIpV6RaSend
         INTEGER,
      er1645v2PppBFIpV6RaMinInterval
         TimeTicks,
      er1645v2PppBFIpV6RaMaxInterval
         TimeTicks,
      er1645v2PppBFIpV6RaManagedFlag
         INTEGER,
      er1645v2PppBFIpV6RaOtherConfFlag
         INTEGER,
      er1645v2PppBFIpV6RaLinkMtu
         Integer32,
      er1645v2PppBFIpV6RaReachableTime
         TimeTicks,
      er1645v2PppBFIpV6RaRetransmitTime
         TimeTicks,
      er1645v2PppBFIpV6RaHopLimit
         Integer32,
      er1645v2PppBFIpV6RaDefaultLifeTime
         TimeTicks,
      er1645v2PppBFIpV6RaDnsOptionsRdnssLifeTime
         TimeTicks,
      er1645v2PppBFIpV6RaDnsOptionsRdnssImportServers
         INTEGER,
      er1645v2PppBFIpV6RaDnsOptionsDnsslLifeTime
         TimeTicks,
      er1645v2PppBFIpV6RaDnsOptionsDnsslImportDomains
         INTEGER,
      er1645v2PppBFIpV6RsSend
         INTEGER,
      er1645v2PppBFIpV6RsMaxRandomDelay
         TimeTicks,
      er1645v2PppBFIpV6RsInterval
         TimeTicks,
      er1645v2PppBFIpV6RsMaxSolicitations
         Integer32,
      er1645v2PppBFIpV6TrafficPolicyInbound
         DisplayString,
      er1645v2PppBFIpV6TrafficPolicyOutbound
         DisplayString,
      er1645v2PppBFIpV6FirewallZone
         DisplayString,
      er1645v2PppBFIpV6DhcpClientAddrAC
         INTEGER,
      er1645v2PppBFIpV6DhcpClientPrDelMode
         INTEGER,
      er1645v2PppBFIpV6DhcpClientPrDelPool
         DisplayString,
      er1645v2PppBFIpV6DhcpClientPrDelPdExclOpt
         INTEGER,
      er1645v2PppBFIpV6DhcpClientDnsServerPref
         Integer32,
      er1645v2PppBFIpV6DhcpClientRapidCommit
         INTEGER,
      er1645v2PppBFIpV6DhcpClientTimersSolTimeOut
         TimeTicks,
      er1645v2PppBFIpV6DhcpClientTimersSolMaxRt
         TimeTicks,
      er1645v2PppBFIpV6DhcpClientTimersInfoRefresh
         TimeTicks,
      er1645v2PppBFIpV6DhcpServerMode
         INTEGER,
      er1645v2PppBFIpV6DhcpServerPreference
         Integer32,
      er1645v2PppBFIpV6DhcpServerPool
         DisplayString,
      er1645v2PppBFIpV6DhcpServerRapidCommit
         INTEGER,
      er1645v2PppBFIpV6DhcpServerTimersInfoRefresh
         TimeTicks,
      er1645v2PppBFIpV6DhcpRelayMode
         INTEGER,
      er1645v2PppBFIpV6SendRedirect
         INTEGER,
      er1645v2PppBFIpV6LinkMtu
         Integer32,
      er1645v2PppBFIpV6InterfaceId
         OCTET STRING,
      er1645v2PppBFIpV6MF
         Integer32,
      er1645v2PppBFIpV6IcmpMessagesNoRoute
         INTEGER,
      er1645v2PppBFIpV6IcmpMessagesBeyondScope
         INTEGER,
      er1645v2PppBFIpV6IcmpMessagesAddressUnreachable
         INTEGER,
      er1645v2PppBFIpV6IcmpMessagesPortUnreachable
         INTEGER,
      er1645v2PppBFIpV6IcmpMessagesPacketTooBig
         INTEGER,
      er1645v2PppBFIpV6IcmpMessagesHopLimitExceeded
         INTEGER,
      er1645v2PppBFIpV6IcmpMessagesFragTimeExceeded
         INTEGER,
      er1645v2PppBFIpV6IcmpMessagesHeaderFieldErr
         INTEGER,
      er1645v2PppBFIpV6IcmpMessagesOptionUnrecognized
         INTEGER,
      er1645v2PppBFIpV6IcmpMessagesRedirect
         INTEGER
      }

er1645v2PppBFIpV6GlobalIx OBJECT-TYPE
   SYNTAX      GlobalIndex
   MAX-ACCESS  not-accessible
   STATUS      current
   DESCRIPTION
      "The value of the tlsCntTreeGlobalIndex of the MANAGED OBJECT."
   ::= {er1645v2PppBFIpV6Entry 10}

er1645v2PppBFIpV6VrfRouter OBJECT-TYPE
   SYNTAX      DisplayString
   MAX-ACCESS  read-write
   STATUS      current
   DESCRIPTION
      "Path: pppBundle.editConf.ipV6.vrfRouter"
   ::= {er1645v2PppBFIpV6Entry 16777216}

er1645v2PppBFIpV6AddrAutoConfigNrDupAddrDetects OBJECT-TYPE
   SYNTAX      Integer32
   MAX-ACCESS  read-write
   STATUS      current
   DESCRIPTION
      "Path: pppBundle.editConf.ipV6.addrAutoConfig.nrDupAddrDetects"
   ::= {er1645v2PppBFIpV6Entry 67174400}

er1645v2PppBFIpV6AddrAutoConfigAcceptRa OBJECT-TYPE
   SYNTAX      INTEGER
               {
               disabled (0),
               enabled (1)
               }
   MAX-ACCESS  read-write
   STATUS      current
   DESCRIPTION
      "Path: pppBundle.editConf.ipV6.addrAutoConfig.acceptRa

       Possibilities:
               disabled   (0)
               enabled   (1)"
   ::= {er1645v2PppBFIpV6Entry 67239936}

er1645v2PppBFIpV6AddrAutoConfigAcceptRaRdnss OBJECT-TYPE
   SYNTAX      INTEGER
               {
               disabled (0),
               enabled (1)
               }
   MAX-ACCESS  read-write
   STATUS      current
   DESCRIPTION
      "Path: pppBundle.editConf.ipV6.addrAutoConfig.acceptRaRdnss

       Possibilities:
               disabled   (0)
               enabled   (1)"
   ::= {er1645v2PppBFIpV6Entry 67305472}

er1645v2PppBFIpV6AddrAutoConfigAcceptRaDnssl OBJECT-TYPE
   SYNTAX      INTEGER
               {
               disabled (0),
               enabled (1)
               }
   MAX-ACCESS  read-write
   STATUS      current
   DESCRIPTION
      "Path: pppBundle.editConf.ipV6.addrAutoConfig.acceptRaDnssl

       Possibilities:
               disabled   (0)
               enabled   (1)"
   ::= {er1645v2PppBFIpV6Entry 67371008}

er1645v2PppBFIpV6DefaultRoute OBJECT-TYPE
   SYNTAX      INTEGER
               {
               disabled (0),
               enabled (1)
               }
   MAX-ACCESS  read-write
   STATUS      current
   DESCRIPTION
      "Path: pppBundle.editConf.ipV6.defaultRoute

       Possibilities:
               disabled   (0)
               enabled   (1)"
   ::= {er1645v2PppBFIpV6Entry 83886080}

er1645v2PppBFIpV6RaSend OBJECT-TYPE
   SYNTAX      INTEGER
               {
               disabled (0),
               enabled (1)
               }
   MAX-ACCESS  read-write
   STATUS      current
   DESCRIPTION
      "Path: pppBundle.editConf.ipV6.ra.send

       Possibilities:
               disabled   (0)
               enabled   (1)"
   ::= {er1645v2PppBFIpV6Entry 100728832}

er1645v2PppBFIpV6RaMinInterval OBJECT-TYPE
   SYNTAX      TimeTicks
   MAX-ACCESS  read-write
   STATUS      current
   DESCRIPTION
      "Path: pppBundle.editConf.ipV6.ra.minInterval

       Time in centi-second."
   ::= {er1645v2PppBFIpV6Entry 100794368}

er1645v2PppBFIpV6RaMaxInterval OBJECT-TYPE
   SYNTAX      TimeTicks
   MAX-ACCESS  read-write
   STATUS      current
   DESCRIPTION
      "Path: pppBundle.editConf.ipV6.ra.maxInterval

       Time in centi-second."
   ::= {er1645v2PppBFIpV6Entry 100859904}

er1645v2PppBFIpV6RaManagedFlag OBJECT-TYPE
   SYNTAX      INTEGER
               {
               disabled (0),
               enabled (1)
               }
   MAX-ACCESS  read-write
   STATUS      current
   DESCRIPTION
      "Path: pppBundle.editConf.ipV6.ra.managedFlag

       Possibilities:
               disabled   (0)
               enabled   (1)"
   ::= {er1645v2PppBFIpV6Entry 100925440}

er1645v2PppBFIpV6RaOtherConfFlag OBJECT-TYPE
   SYNTAX      INTEGER
               {
               disabled (0),
               enabled (1)
               }
   MAX-ACCESS  read-write
   STATUS      current
   DESCRIPTION
      "Path: pppBundle.editConf.ipV6.ra.otherConfFlag

       Possibilities:
               disabled   (0)
               enabled   (1)"
   ::= {er1645v2PppBFIpV6Entry 100990976}

er1645v2PppBFIpV6RaLinkMtu OBJECT-TYPE
   SYNTAX      Integer32
   MAX-ACCESS  read-write
   STATUS      current
   DESCRIPTION
      "Path: pppBundle.editConf.ipV6.ra.linkMtu"
   ::= {er1645v2PppBFIpV6Entry 101056512}

er1645v2PppBFIpV6RaReachableTime OBJECT-TYPE
   SYNTAX      TimeTicks
   MAX-ACCESS  read-write
   STATUS      current
   DESCRIPTION
      "Path: pppBundle.editConf.ipV6.ra.reachableTime

       Time in centi-second."
   ::= {er1645v2PppBFIpV6Entry 101122048}

er1645v2PppBFIpV6RaRetransmitTime OBJECT-TYPE
   SYNTAX      TimeTicks
   MAX-ACCESS  read-write
   STATUS      current
   DESCRIPTION
      "Path: pppBundle.editConf.ipV6.ra.retransmitTime

       Time in centi-second."
   ::= {er1645v2PppBFIpV6Entry 101187584}

er1645v2PppBFIpV6RaHopLimit OBJECT-TYPE
   SYNTAX      Integer32
   MAX-ACCESS  read-write
   STATUS      current
   DESCRIPTION
      "Path: pppBundle.editConf.ipV6.ra.hopLimit"
   ::= {er1645v2PppBFIpV6Entry 101253120}

er1645v2PppBFIpV6RaDefaultLifeTime OBJECT-TYPE
   SYNTAX      TimeTicks
   MAX-ACCESS  read-write
   STATUS      current
   DESCRIPTION
      "Path: pppBundle.editConf.ipV6.ra.defaultLifeTime

       Time in centi-second."
   ::= {er1645v2PppBFIpV6Entry 101318656}

er1645v2PppBFIpV6RaDnsOptionsRdnssLifeTime OBJECT-TYPE
   SYNTAX      TimeTicks
   MAX-ACCESS  read-write
   STATUS      current
   DESCRIPTION
      "Path: pppBundle.editConf.ipV6.ra.dnsOptions.rdnss.lifeTime

       Time in centi-second."
   ::= {er1645v2PppBFIpV6Entry 101393408}

er1645v2PppBFIpV6RaDnsOptionsRdnssImportServers OBJECT-TYPE
   SYNTAX      INTEGER
               {
               disabled (0),
               enabled (1)
               }
   MAX-ACCESS  read-write
   STATUS      current
   DESCRIPTION
      "Path: pppBundle.editConf.ipV6.ra.dnsOptions.rdnss.importServers

       Possibilities:
               disabled   (0)
               enabled   (1)"
   ::= {er1645v2PppBFIpV6Entry 101395456}

er1645v2PppBFIpV6RaDnsOptionsDnsslLifeTime OBJECT-TYPE
   SYNTAX      TimeTicks
   MAX-ACCESS  read-write
   STATUS      current
   DESCRIPTION
      "Path: pppBundle.editConf.ipV6.ra.dnsOptions.dnssl.lifeTime

       Time in centi-second."
   ::= {er1645v2PppBFIpV6Entry 101401600}

er1645v2PppBFIpV6RaDnsOptionsDnsslImportDomains OBJECT-TYPE
   SYNTAX      INTEGER
               {
               disabled (0),
               enabled (1)
               }
   MAX-ACCESS  read-write
   STATUS      current
   DESCRIPTION
      "Path: pppBundle.editConf.ipV6.ra.dnsOptions.dnssl.importDomains

       Possibilities:
               disabled   (0)
               enabled   (1)"
   ::= {er1645v2PppBFIpV6Entry 101403648}

er1645v2PppBFIpV6RsSend OBJECT-TYPE
   SYNTAX      INTEGER
               {
               disabled (0),
               enabled (1)
               }
   MAX-ACCESS  read-write
   STATUS      current
   DESCRIPTION
      "Path: pppBundle.editConf.ipV6.rs.send

       Possibilities:
               disabled   (0)
               enabled   (1)"
   ::= {er1645v2PppBFIpV6Entry 335609856}

er1645v2PppBFIpV6RsMaxRandomDelay OBJECT-TYPE
   SYNTAX      TimeTicks
   MAX-ACCESS  read-write
   STATUS      current
   DESCRIPTION
      "Path: pppBundle.editConf.ipV6.rs.maxRandomDelay

       Time in centi-second."
   ::= {er1645v2PppBFIpV6Entry 335675392}

er1645v2PppBFIpV6RsInterval OBJECT-TYPE
   SYNTAX      TimeTicks
   MAX-ACCESS  read-write
   STATUS      current
   DESCRIPTION
      "Path: pppBundle.editConf.ipV6.rs.interval

       Time in centi-second."
   ::= {er1645v2PppBFIpV6Entry 335740928}

er1645v2PppBFIpV6RsMaxSolicitations OBJECT-TYPE
   SYNTAX      Integer32
   MAX-ACCESS  read-write
   STATUS      current
   DESCRIPTION
      "Path: pppBundle.editConf.ipV6.rs.maxSolicitations"
   ::= {er1645v2PppBFIpV6Entry 335806464}

er1645v2PppBFIpV6TrafficPolicyInbound OBJECT-TYPE
   SYNTAX      DisplayString
   MAX-ACCESS  read-write
   STATUS      current
   DESCRIPTION
      "Path: pppBundle.editConf.ipV6.trafficPolicy.inbound"
   ::= {er1645v2PppBFIpV6Entry 184614912}

er1645v2PppBFIpV6TrafficPolicyOutbound OBJECT-TYPE
   SYNTAX      DisplayString
   MAX-ACCESS  read-write
   STATUS      current
   DESCRIPTION
      "Path: pppBundle.editConf.ipV6.trafficPolicy.outbound"
   ::= {er1645v2PppBFIpV6Entry 184680448}

er1645v2PppBFIpV6FirewallZone OBJECT-TYPE
   SYNTAX      DisplayString
   MAX-ACCESS  read-write
   STATUS      current
   DESCRIPTION
      "Path: pppBundle.editConf.ipV6.firewall.zone"
   ::= {er1645v2PppBFIpV6Entry 201392128}

er1645v2PppBFIpV6DhcpClientAddrAC OBJECT-TYPE
   SYNTAX      INTEGER
               {
               disabled (0),
               enabled (1)
               }
   MAX-ACCESS  read-write
   STATUS      current
   DESCRIPTION
      "Path: pppBundle.editConf.ipV6.dhcp.client.addrAutoConfig

       Possibilities:
               disabled   (0)
               enabled   (1)"
   ::= {er1645v2PppBFIpV6Entry 170131456}

er1645v2PppBFIpV6DhcpClientPrDelMode OBJECT-TYPE
   SYNTAX      INTEGER
               {
               disabled (0),
               enabled (1)
               }
   MAX-ACCESS  read-write
   STATUS      current
   DESCRIPTION
      "Path: pppBundle.editConf.ipV6.dhcp.client.pd.mode

       Possibilities:
               disabled   (0)
               enabled   (1)"
   ::= {er1645v2PppBFIpV6Entry 170394624}

er1645v2PppBFIpV6DhcpClientPrDelPool OBJECT-TYPE
   SYNTAX      DisplayString
   MAX-ACCESS  read-write
   STATUS      current
   DESCRIPTION
      "Path: pppBundle.editConf.ipV6.dhcp.client.pd.pool"
   ::= {er1645v2PppBFIpV6Entry 170395648}

er1645v2PppBFIpV6DhcpClientPrDelPdExclOpt OBJECT-TYPE
   SYNTAX      INTEGER
               {
               disabled (0),
               enabled (1)
               }
   MAX-ACCESS  read-write
   STATUS      current
   DESCRIPTION
      "Path: pppBundle.editConf.ipV6.dhcp.client.pd.pdExclOpt

       Possibilities:
               disabled   (0)
               enabled   (1)"
   ::= {er1645v2PppBFIpV6Entry 170396672}

er1645v2PppBFIpV6DhcpClientDnsServerPref OBJECT-TYPE
   SYNTAX      Integer32
   MAX-ACCESS  read-write
   STATUS      current
   DESCRIPTION
      "Path: pppBundle.editConf.ipV6.dhcp.client.dns.serverPref"
   ::= {er1645v2PppBFIpV6Entry 170918912}

er1645v2PppBFIpV6DhcpClientRapidCommit OBJECT-TYPE
   SYNTAX      INTEGER
               {
               disabled (0),
               enabled (1)
               }
   MAX-ACCESS  read-write
   STATUS      current
   DESCRIPTION
      "Path: pppBundle.editConf.ipV6.dhcp.client.rapidCommit

       Possibilities:
               disabled   (0)
               enabled   (1)"
   ::= {er1645v2PppBFIpV6Entry 170655744}

er1645v2PppBFIpV6DhcpClientTimersSolTimeOut OBJECT-TYPE
   SYNTAX      TimeTicks
   MAX-ACCESS  read-write
   STATUS      current
   DESCRIPTION
      "Path: pppBundle.editConf.ipV6.dhcp.client.timers.solTimeOut

       Time in centi-second."
   ::= {er1645v2PppBFIpV6Entry 171181056}

er1645v2PppBFIpV6DhcpClientTimersSolMaxRt OBJECT-TYPE
   SYNTAX      TimeTicks
   MAX-ACCESS  read-write
   STATUS      current
   DESCRIPTION
      "Path: pppBundle.editConf.ipV6.dhcp.client.timers.solMaxRt

       Time in centi-second."
   ::= {er1645v2PppBFIpV6Entry 171182080}

er1645v2PppBFIpV6DhcpClientTimersInfoRefresh OBJECT-TYPE
   SYNTAX      TimeTicks
   MAX-ACCESS  read-write
   STATUS      current
   DESCRIPTION
      "Path: pppBundle.editConf.ipV6.dhcp.client.timers.infoRefresh

       Time in centi-second."
   ::= {er1645v2PppBFIpV6Entry 171183104}

er1645v2PppBFIpV6DhcpServerMode OBJECT-TYPE
   SYNTAX      INTEGER
               {
               disabled (0),
               enabled (1)
               }
   MAX-ACCESS  read-write
   STATUS      current
   DESCRIPTION
      "Path: pppBundle.editConf.ipV6.dhcp.server.mode

       Possibilities:
               disabled   (0)
               enabled   (1)"
   ::= {er1645v2PppBFIpV6Entry 172228608}

er1645v2PppBFIpV6DhcpServerPreference OBJECT-TYPE
   SYNTAX      Integer32
   MAX-ACCESS  read-write
   STATUS      current
   DESCRIPTION
      "Path: pppBundle.editConf.ipV6.dhcp.server.preference"
   ::= {er1645v2PppBFIpV6Entry 172490752}

er1645v2PppBFIpV6DhcpServerPool OBJECT-TYPE
   SYNTAX      DisplayString
   MAX-ACCESS  read-write
   STATUS      current
   DESCRIPTION
      "Path: pppBundle.editConf.ipV6.dhcp.server.pool"
   ::= {er1645v2PppBFIpV6Entry 172752896}

er1645v2PppBFIpV6DhcpServerRapidCommit OBJECT-TYPE
   SYNTAX      INTEGER
               {
               disabled (0),
               enabled (1)
               }
   MAX-ACCESS  read-write
   STATUS      current
   DESCRIPTION
      "Path: pppBundle.editConf.ipV6.dhcp.server.rapidCommit

       Possibilities:
               disabled   (0)
               enabled   (1)"
   ::= {er1645v2PppBFIpV6Entry 173015040}

er1645v2PppBFIpV6DhcpServerTimersInfoRefresh OBJECT-TYPE
   SYNTAX      TimeTicks
   MAX-ACCESS  read-write
   STATUS      current
   DESCRIPTION
      "Path: pppBundle.editConf.ipV6.dhcp.server.timers.infoRefresh

       Time in centi-second."
   ::= {er1645v2PppBFIpV6Entry 173278208}

er1645v2PppBFIpV6DhcpRelayMode OBJECT-TYPE
   SYNTAX      INTEGER
               {
               disabled (0),
               enabled (1)
               }
   MAX-ACCESS  read-write
   STATUS      current
   DESCRIPTION
      "Path: pppBundle.editConf.ipV6.dhcp.relay.mode

       Possibilities:
               disabled   (0)
               enabled   (1)"
   ::= {er1645v2PppBFIpV6Entry 174071808}

er1645v2PppBFIpV6SendRedirect OBJECT-TYPE
   SYNTAX      INTEGER
               {
               disabled (0),
               enabled (1)
               }
   MAX-ACCESS  read-write
   STATUS      current
   DESCRIPTION
      "Path: pppBundle.editConf.ipV6.sendRedirect

       Possibilities:
               disabled   (0)
               enabled   (1)"
   ::= {er1645v2PppBFIpV6Entry 117440512}

er1645v2PppBFIpV6LinkMtu OBJECT-TYPE
   SYNTAX      Integer32
   MAX-ACCESS  read-write
   STATUS      current
   DESCRIPTION
      "Path: pppBundle.editConf.ipV6.linkMtu"
   ::= {er1645v2PppBFIpV6Entry 134217728}

er1645v2PppBFIpV6InterfaceId OBJECT-TYPE
   SYNTAX      OCTET STRING
   MAX-ACCESS  read-write
   STATUS      current
   DESCRIPTION
      "Path: pppBundle.editConf.ipV6.interfaceId"
   ::= {er1645v2PppBFIpV6Entry 150994944}

er1645v2PppBFIpV6MF OBJECT-TYPE
   SYNTAX      Integer32
   MAX-ACCESS  read-write
   STATUS      current
   DESCRIPTION
      "Path: pppBundle.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2PppBFIpV6Entry 285212672}

er1645v2PppBFIpV6IcmpMessagesNoRoute OBJECT-TYPE
   SYNTAX      INTEGER
               {
               disabled (0),
               enabled (1)
               }
   MAX-ACCESS  read-write
   STATUS      current
   DESCRIPTION
      "Path: pppBundle.editConf.ipV6.icmpMessages.noRoute

       Possibilities:
               disabled   (0)
               enabled   (1)"
   ::= {er1645v2PppBFIpV6Entry 302055424}

er1645v2PppBFIpV6IcmpMessagesBeyondScope OBJECT-TYPE
   SYNTAX      INTEGER
               {
               disabled (0),
               enabled (1)
               }
   MAX-ACCESS  read-write
   STATUS      current
   DESCRIPTION
      "Path: pppBundle.editConf.ipV6.icmpMessages.beyondScope

       Possibilities:
               disabled   (0)
               enabled   (1)"
   ::= {er1645v2PppBFIpV6Entry 302186496}

er1645v2PppBFIpV6IcmpMessagesAddressUnreachable OBJECT-TYPE
   SYNTAX      INTEGER
               {
               disabled (0),
               enabled (1)
               }
   MAX-ACCESS  read-write
   STATUS      current
   DESCRIPTION
      "Path: pppBundle.editConf.ipV6.icmpMessages.addressUnreachable

       Possibilities:
               disabled   (0)
               enabled   (1)"
   ::= {er1645v2PppBFIpV6Entry 302252032}

er1645v2PppBFIpV6IcmpMessagesPortUnreachable OBJECT-TYPE
   SYNTAX      INTEGER
               {
               disabled (0),
               enabled (1)
               }
   MAX-ACCESS  read-write
   STATUS      current
   DESCRIPTION
      "Path: pppBundle.editConf.ipV6.icmpMessages.portUnreachable

       Possibilities:
               disabled   (0)
               enabled   (1)"
   ::= {er1645v2PppBFIpV6Entry 302317568}

er1645v2PppBFIpV6IcmpMessagesPacketTooBig OBJECT-TYPE
   SYNTAX      INTEGER
               {
               disabled (0),
               enabled (1)
               }
   MAX-ACCESS  read-write
   STATUS      current
   DESCRIPTION
      "Path: pppBundle.editConf.ipV6.icmpMessages.packetTooBig

       Possibilities:
               disabled   (0)
               enabled   (1)"
   ::= {er1645v2PppBFIpV6Entry 302645248}

er1645v2PppBFIpV6IcmpMessagesHopLimitExceeded OBJECT-TYPE
   SYNTAX      INTEGER
               {
               disabled (0),
               enabled (1)
               }
   MAX-ACCESS  read-write
   STATUS      current
   DESCRIPTION
      "Path: pppBundle.editConf.ipV6.icmpMessages.hopLimitExceeded

       Possibilities:
               disabled   (0)
               enabled   (1)"
   ::= {er1645v2PppBFIpV6Entry 303300608}

er1645v2PppBFIpV6IcmpMessagesFragTimeExceeded OBJECT-TYPE
   SYNTAX      INTEGER
               {
               disabled (0),
               enabled (1)
               }
   MAX-ACCESS  read-write
   STATUS      current
   DESCRIPTION
      "Path: pppBundle.editConf.ipV6.icmpMessages.fragTimeExceeded

       Possibilities:
               disabled   (0)
               enabled   (1)"
   ::= {er1645v2PppBFIpV6Entry 303366144}

er1645v2PppBFIpV6IcmpMessagesHeaderFieldErr OBJECT-TYPE
   SYNTAX      INTEGER
               {
               disabled (0),
               enabled (1)
               }
   MAX-ACCESS  read-write
   STATUS      current
   DESCRIPTION
      "Path: pppBundle.editConf.ipV6.icmpMessages.headerFieldErr

       Possibilities:
               disabled   (0)
               enabled   (1)"
   ::= {er1645v2PppBFIpV6Entry 303955968}

er1645v2PppBFIpV6IcmpMessagesOptionUnrecognized OBJECT-TYPE
   SYNTAX      INTEGER
               {
               disabled (0),
               enabled (1)
               }
   MAX-ACCESS  read-write
   STATUS      current
   DESCRIPTION
      "Path: pppBundle.editConf.ipV6.icmpMessages.optionUnrecognized

       Possibilities:
               disabled   (0)
               enabled   (1)"
   ::= {er1645v2PppBFIpV6Entry 304087040}

er1645v2PppBFIpV6IcmpMessagesRedirect OBJECT-TYPE
   SYNTAX      INTEGER
               {
               disabled (0),
               enabled (1)
               }
   MAX-ACCESS  read-write
   STATUS      current
   DESCRIPTION
      "Path: pppBundle.editConf.ipV6.icmpMessages.redirect

       Possibilities:
               disabled   (0)
               enabled   (1)"
   ::= {er1645v2PppBFIpV6Entry 304611328}

er1645v2PppBFIpV6Addresses OBJECT-TYPE
   SYNTAX      SEQUENCE OF Er1645v2PppBFIpV6AddressesEntry
   MAX-ACCESS  not-accessible
   STATUS      current
   DESCRIPTION
      ""
   ::= {er1645v2PppBFIpV6 50331648}

er1645v2PppBFIpV6AddressesEntry OBJECT-TYPE
   SYNTAX      Er1645v2PppBFIpV6AddressesEntry
   MAX-ACCESS  not-accessible
   STATUS      current
   DESCRIPTION
      ""
   INDEX      { er1645v2PppBFIpV6AddressesGlobalIx,
                er1645v2PppBFIpV6AddressesTableIx }
   ::= {er1645v2PppBFIpV6Addresses 1}

Er1645v2PppBFIpV6AddressesEntry ::=
   SEQUENCE
      {
      er1645v2PppBFIpV6AddressesActions
         VariableLengthTableActions,
      er1645v2PppBFIpV6AddressesGlobalIx
         GlobalIndex,
      er1645v2PppBFIpV6AddressesTableIx
         TableIndex,
      er1645v2PppBFIpV6AddressesType
         INTEGER,
      er1645v2PppBFIpV6AddressesAddress
         Ipv6Address,
      er1645v2PppBFIpV6AddressesPrefixLength
         Integer32,
      er1645v2PppBFIpV6AddressesGeneralPrefix
         DisplayString,
      er1645v2PppBFIpV6AddressesRaSend
         INTEGER,
      er1645v2PppBFIpV6AddressesRaOnLinkFlag
         INTEGER,
      er1645v2PppBFIpV6AddressesRaAutoFlag
         INTEGER,
      er1645v2PppBFIpV6AddressesRaValidLifeTime
         TimeTicks,
      er1645v2PppBFIpV6AddressesRaValidLTMode
         INTEGER,
      er1645v2PppBFIpV6AddressesRaPrefLifeTime
         TimeTicks,
      er1645v2PppBFIpV6AddressesRaPrefLTMode
         INTEGER
      }

er1645v2PppBFIpV6AddressesActions OBJECT-TYPE
   SYNTAX      VariableLengthTableActions
   MAX-ACCESS  read-write
   STATUS      current
   DESCRIPTION
      "By way of this field, some manipulations
       on this table may be performed."
   ::= {er1645v2PppBFIpV6AddressesEntry 2}

er1645v2PppBFIpV6AddressesGlobalIx OBJECT-TYPE
   SYNTAX      GlobalIndex
   MAX-ACCESS  not-accessible
   STATUS      current
   DESCRIPTION
      "The value of the tlsCntTreeGlobalIndex of the MANAGED OBJECT."
   ::= {er1645v2PppBFIpV6AddressesEntry 10}

er1645v2PppBFIpV6AddressesTableIx OBJECT-TYPE
   SYNTAX      TableIndex
   MAX-ACCESS  not-accessible
   STATUS      current
   DESCRIPTION
      ""
   ::= {er1645v2PppBFIpV6AddressesEntry 11}

er1645v2PppBFIpV6AddressesType OBJECT-TYPE
   SYNTAX      INTEGER
               {
               unicast (0),
               eui64 (1),
               anycast (2),
               linkLocal (3),
               generalPrefix (4)
               }
   MAX-ACCESS  read-write
   STATUS      current
   DESCRIPTION
      "Path: pppBundle.editConf.ipV6.addresses.type

       Possibilities:
               unicast   (0)
               eui64   (1)
               anycast   (2)
               linkLocal   (3)
               generalPrefix   (4)"
   ::= {er1645v2PppBFIpV6AddressesEntry 50331648}

er1645v2PppBFIpV6AddressesAddress OBJECT-TYPE
   SYNTAX      Ipv6Address
   MAX-ACCESS  read-write
   STATUS      current
   DESCRIPTION
      "Path: pppBundle.editConf.ipV6.addresses.address

       ipv6 address"
   ::= {er1645v2PppBFIpV6AddressesEntry 16777216}

er1645v2PppBFIpV6AddressesPrefixLength OBJECT-TYPE
   SYNTAX      Integer32
   MAX-ACCESS  read-write
   STATUS      current
   DESCRIPTION
      "Path: pppBundle.editConf.ipV6.addresses.prefixLength"
   ::= {er1645v2PppBFIpV6AddressesEntry 33554432}

er1645v2PppBFIpV6AddressesGeneralPrefix OBJECT-TYPE
   SYNTAX      DisplayString
   MAX-ACCESS  read-write
   STATUS      current
   DESCRIPTION
      "Path: pppBundle.editConf.ipV6.addresses.generalPrefix"
   ::= {er1645v2PppBFIpV6AddressesEntry 83886080}

er1645v2PppBFIpV6AddressesRaSend OBJECT-TYPE
   SYNTAX      INTEGER
               {
               disabled (0),
               enabled (1)
               }
   MAX-ACCESS  read-write
   STATUS      current
   DESCRIPTION
      "Path: pppBundle.editConf.ipV6.addresses.ra.send

       Possibilities:
               disabled   (0)
               enabled   (1)"
   ::= {er1645v2PppBFIpV6AddressesEntry 67174400}

er1645v2PppBFIpV6AddressesRaOnLinkFlag OBJECT-TYPE
   SYNTAX      INTEGER
               {
               disabled (0),
               enabled (1)
               }
   MAX-ACCESS  read-write
   STATUS      current
   DESCRIPTION
      "Path: pppBundle.editConf.ipV6.addresses.ra.onLinkFlag

       Possibilities:
               disabled   (0)
               enabled   (1)"
   ::= {er1645v2PppBFIpV6AddressesEntry 67371008}

er1645v2PppBFIpV6AddressesRaAutoFlag OBJECT-TYPE
   SYNTAX      INTEGER
               {
               disabled (0),
               enabled (1)
               }
   MAX-ACCESS  read-write
   STATUS      current
   DESCRIPTION
      "Path: pppBundle.editConf.ipV6.addresses.ra.autonomousFlag

       Possibilities:
               disabled   (0)
               enabled   (1)"
   ::= {er1645v2PppBFIpV6AddressesEntry 67567616}

er1645v2PppBFIpV6AddressesRaValidLifeTime OBJECT-TYPE
   SYNTAX      TimeTicks
   MAX-ACCESS  read-write
   STATUS      current
   DESCRIPTION
      "Path: pppBundle.editConf.ipV6.addresses.ra.validLifeTime

       Time in centi-second."
   ::= {er1645v2PppBFIpV6AddressesEntry 67239936}

er1645v2PppBFIpV6AddressesRaValidLTMode OBJECT-TYPE
   SYNTAX      INTEGER
               {
               fixed (0),
               infinite (2)
               }
   MAX-ACCESS  read-write
   STATUS      current
   DESCRIPTION
      "Path: pppBundle.editConf.ipV6.addresses.ra.validLifeTimeMode

       Possibilities:
               fixed   (0)
               infinite   (2)"
   ::= {er1645v2PppBFIpV6AddressesEntry 67305472}

er1645v2PppBFIpV6AddressesRaPrefLifeTime OBJECT-TYPE
   SYNTAX      TimeTicks
   MAX-ACCESS  read-write
   STATUS      current
   DESCRIPTION
      "Path: pppBundle.editConf.ipV6.addresses.ra.prefLifeTime

       Time in centi-second."
   ::= {er1645v2PppBFIpV6AddressesEntry 67436544}

er1645v2PppBFIpV6AddressesRaPrefLTMode OBJECT-TYPE
   SYNTAX      INTEGER
               {
               fixed (0),
               infinite (2)
               }
   MAX-ACCESS  read-write
   STATUS      current
   DESCRIPTION
      "Path: pppBundle.editConf.ipV6.addresses.ra.prefLifeTimeMode

       Possibilities:
               fixed   (0)
               infinite   (2)"
   ::= {er1645v2PppBFIpV6AddressesEntry 67502080}

er1645v2PppBFIpV6RaDnsOptionsRdnssServers OBJECT-TYPE
   SYNTAX      SEQUENCE OF Er1645v2PppBFIpV6RaDnsOptionsRdnssServersEntry
   MAX-ACCESS  not-accessible
   STATUS      current
   DESCRIPTION
      ""
   ::= {er1645v2PppBFIpV6 101394432}

er1645v2PppBFIpV6RaDnsOptionsRdnssServersEntry OBJECT-TYPE
   SYNTAX      Er1645v2PppBFIpV6RaDnsOptionsRdnssServersEntry
   MAX-ACCESS  not-accessible
   STATUS      current
   DESCRIPTION
      ""
   INDEX      { er1645v2PppBFIpV6RaDnsOptionsRdnssServersGlobalIx,
                er1645v2PppBFIpV6RaDnsOptionsRdnssServersTableIx }
   ::= {er1645v2PppBFIpV6RaDnsOptionsRdnssServers 1}

Er1645v2PppBFIpV6RaDnsOptionsRdnssServersEntry ::=
   SEQUENCE
      {
      er1645v2PppBFIpV6RaDnsOptionsRdnssServersActions
         VariableLengthTableActions,
      er1645v2PppBFIpV6RaDnsOptionsRdnssServersGlobalIx
         GlobalIndex,
      er1645v2PppBFIpV6RaDnsOptionsRdnssServersTableIx
         TableIndex,
      er1645v2PppBFIpV6RaDnsOptionsRdnssServersAddress
         Ipv6Address
      }

er1645v2PppBFIpV6RaDnsOptionsRdnssServersActions OBJECT-TYPE
   SYNTAX      VariableLengthTableActions
   MAX-ACCESS  read-write
   STATUS      current
   DESCRIPTION
      "By way of this field, some manipulations
       on this table may be performed."
   ::= {er1645v2PppBFIpV6RaDnsOptionsRdnssServersEntry 2}

er1645v2PppBFIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2PppBFIpV6RaDnsOptionsRdnssServersEntry 10}

er1645v2PppBFIpV6RaDnsOptionsRdnssServersTableIx OBJECT-TYPE
   SYNTAX      TableIndex
   MAX-ACCESS  not-accessible
   STATUS      current
   DESCRIPTION
      ""
   ::= {er1645v2PppBFIpV6RaDnsOptionsRdnssServersEntry 11}

er1645v2PppBFIpV6RaDnsOptionsRdnssServersAddress OBJECT-TYPE
   SYNTAX      Ipv6Address
   MAX-ACCESS  read-write
   STATUS      current
   DESCRIPTION
      "Path: pppBundle.editConf.ipV6.ra.dnsOptions.rdnss.servers.address

       ipv6 address"
   ::= {er1645v2PppBFIpV6RaDnsOptionsRdnssServersEntry 16777216}

er1645v2PppBFIpV6RaDnsOptionsDnsslDomains OBJECT-TYPE
   SYNTAX      SEQUENCE OF Er1645v2PppBFIpV6RaDnsOptionsDnsslDomainsEntry
   MAX-ACCESS  not-accessible
   STATUS      current
   DESCRIPTION
      ""
   ::= {er1645v2PppBFIpV6 101402624}

er1645v2PppBFIpV6RaDnsOptionsDnsslDomainsEntry OBJECT-TYPE
   SYNTAX      Er1645v2PppBFIpV6RaDnsOptionsDnsslDomainsEntry
   MAX-ACCESS  not-accessible
   STATUS      current
   DESCRIPTION
      ""
   INDEX      { er1645v2PppBFIpV6RaDnsOptionsDnsslDomainsGlobalIx,
                er1645v2PppBFIpV6RaDnsOptionsDnsslDomainsTableIx }
   ::= {er1645v2PppBFIpV6RaDnsOptionsDnsslDomains 1}

Er1645v2PppBFIpV6RaDnsOptionsDnsslDomainsEntry ::=
   SEQUENCE
      {
      er1645v2PppBFIpV6RaDnsOptionsDnsslDomainsActions
         VariableLengthTableActions,
      er1645v2PppBFIpV6RaDnsOptionsDnsslDomainsGlobalIx
         GlobalIndex,
      er1645v2PppBFIpV6RaDnsOptionsDnsslDomainsTableIx
         TableIndex,
      er1645v2PppBFIpV6RaDnsOptionsDnsslDomainsName
         DisplayString
      }

er1645v2PppBFIpV6RaDnsOptionsDnsslDomainsActions OBJECT-TYPE
   SYNTAX      VariableLengthTableActions
   MAX-ACCESS  read-write
   STATUS      current
   DESCRIPTION
      "By way of this field, some manipulations
       on this table may be performed."
   ::= {er1645v2PppBFIpV6RaDnsOptionsDnsslDomainsEntry 2}

er1645v2PppBFIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2PppBFIpV6RaDnsOptionsDnsslDomainsEntry 10}

er1645v2PppBFIpV6RaDnsOptionsDnsslDomainsTableIx OBJECT-TYPE
   SYNTAX      TableIndex
   MAX-ACCESS  not-accessible
   STATUS      current
   DESCRIPTION
      ""
   ::= {er1645v2PppBFIpV6RaDnsOptionsDnsslDomainsEntry 11}

er1645v2PppBFIpV6RaDnsOptionsDnsslDomainsName OBJECT-TYPE
   SYNTAX      DisplayString
   MAX-ACCESS  read-write
   STATUS      current
   DESCRIPTION
      "Path: pppBundle.editConf.ipV6.ra.dnsOptions.dnssl.domains.name"
   ::= {er1645v2PppBFIpV6RaDnsOptionsDnsslDomainsEntry 16777216}

er1645v2PppBFIpV6DhcpClientUserClassOpt OBJECT-TYPE
   SYNTAX      SEQUENCE OF Er1645v2PppBFIpV6DhcpClientUserClassOptEntry
   MAX-ACCESS  not-accessible
   STATUS      current
   DESCRIPTION
      ""
   ::= {er1645v2PppBFIpV6 171442176}

er1645v2PppBFIpV6DhcpClientUserClassOptEntry OBJECT-TYPE
   SYNTAX      Er1645v2PppBFIpV6DhcpClientUserClassOptEntry
   MAX-ACCESS  not-accessible
   STATUS      current
   DESCRIPTION
      ""
   INDEX      { er1645v2PppBFIpV6DhcpClientUserClassOptGlobalIx,
                er1645v2PppBFIpV6DhcpClientUserClassOptTableIx }
   ::= {er1645v2PppBFIpV6DhcpClientUserClassOpt 1}

Er1645v2PppBFIpV6DhcpClientUserClassOptEntry ::=
   SEQUENCE
      {
      er1645v2PppBFIpV6DhcpClientUserClassOptActions
         VariableLengthTableActions,
      er1645v2PppBFIpV6DhcpClientUserClassOptGlobalIx
         GlobalIndex,
      er1645v2PppBFIpV6DhcpClientUserClassOptTableIx
         TableIndex,
      er1645v2PppBFIpV6DhcpClientUserClassOptValueAscii
         DisplayString,
      er1645v2PppBFIpV6DhcpClientUserClassOptValueDecimal
         Integer32,
      er1645v2PppBFIpV6DhcpClientUserClassOptValueHexData
         OCTET STRING
      }

er1645v2PppBFIpV6DhcpClientUserClassOptActions OBJECT-TYPE
   SYNTAX      VariableLengthTableActions
   MAX-ACCESS  read-write
   STATUS      current
   DESCRIPTION
      "By way of this field, some manipulations
       on this table may be performed."
   ::= {er1645v2PppBFIpV6DhcpClientUserClassOptEntry 2}

er1645v2PppBFIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2PppBFIpV6DhcpClientUserClassOptEntry 10}

er1645v2PppBFIpV6DhcpClientUserClassOptTableIx OBJECT-TYPE
   SYNTAX      TableIndex
   MAX-ACCESS  not-accessible
   STATUS      current
   DESCRIPTION
      ""
   ::= {er1645v2PppBFIpV6DhcpClientUserClassOptEntry 11}

er1645v2PppBFIpV6DhcpClientUserClassOptValueAscii OBJECT-TYPE
   SYNTAX      DisplayString
   MAX-ACCESS  read-write
   STATUS      current
   DESCRIPTION
      "Path: pppBundle.editConf.ipV6.dhcp.client.userClassOpt.value.ascii"
   ::= {er1645v2PppBFIpV6DhcpClientUserClassOptEntry 16842752}

er1645v2PppBFIpV6DhcpClientUserClassOptValueDecimal OBJECT-TYPE
   SYNTAX      Integer32
   MAX-ACCESS  read-write
   STATUS      current
   DESCRIPTION
      "Path: pppBundle.editConf.ipV6.dhcp.client.userClassOpt.value.decimal"
   ::= {er1645v2PppBFIpV6DhcpClientUserClassOptEntry 16908288}

er1645v2PppBFIpV6DhcpClientUserClassOptValueHexData OBJECT-TYPE
   SYNTAX      OCTET STRING
   MAX-ACCESS  read-write
   STATUS      current
   DESCRIPTION
      "Path: pppBundle.editConf.ipV6.dhcp.client.userClassOpt.value.hexData"
   ::= {er1645v2PppBFIpV6DhcpClientUserClassOptEntry 16973824}

er1645v2PppBFIpV6DhcpClientVendorCl OBJECT-TYPE
   SYNTAX      SEQUENCE OF Er1645v2PppBFIpV6DhcpClientVendorClEntry
   MAX-ACCESS  not-accessible
   STATUS      current
   DESCRIPTION
      ""
   ::= {er1645v2PppBFIpV6 171704320}

er1645v2PppBFIpV6DhcpClientVendorClEntry OBJECT-TYPE
   SYNTAX      Er1645v2PppBFIpV6DhcpClientVendorClEntry
   MAX-ACCESS  not-accessible
   STATUS      current
   DESCRIPTION
      ""
   INDEX      { er1645v2PppBFIpV6DhcpClientVendorClGlobalIx,
                er1645v2PppBFIpV6DhcpClientVendorClTableIx }
   ::= {er1645v2PppBFIpV6DhcpClientVendorCl 1}

Er1645v2PppBFIpV6DhcpClientVendorClEntry ::=
   SEQUENCE
      {
      er1645v2PppBFIpV6DhcpClientVendorClActions
         VariableLengthTableActions,
      er1645v2PppBFIpV6DhcpClientVendorClGlobalIx
         GlobalIndex,
      er1645v2PppBFIpV6DhcpClientVendorClTableIx
         TableIndex,
      er1645v2PppBFIpV6DhcpClientVendorClValueAscii
         DisplayString,
      er1645v2PppBFIpV6DhcpClientVendorClValueDecimal
         Integer32,
      er1645v2PppBFIpV6DhcpClientVendorClValueHexData
         OCTET STRING
      }

er1645v2PppBFIpV6DhcpClientVendorClActions OBJECT-TYPE
   SYNTAX      VariableLengthTableActions
   MAX-ACCESS  read-write
   STATUS      current
   DESCRIPTION
      "By way of this field, some manipulations
       on this table may be performed."
   ::= {er1645v2PppBFIpV6DhcpClientVendorClEntry 2}

er1645v2PppBFIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2PppBFIpV6DhcpClientVendorClEntry 10}

er1645v2PppBFIpV6DhcpClientVendorClTableIx OBJECT-TYPE
   SYNTAX      TableIndex
   MAX-ACCESS  not-accessible
   STATUS      current
   DESCRIPTION
      ""
   ::= {er1645v2PppBFIpV6DhcpClientVendorClEntry 11}

er1645v2PppBFIpV6DhcpClientVendorClValueAscii OBJECT-TYPE
   SYNTAX      DisplayString
   MAX-ACCESS  read-write
   STATUS      current
   DESCRIPTION
      "Path: pppBundle.editConf.ipV6.dhcp.client.vendorClassOpt.value.ascii"
   ::= {er1645v2PppBFIpV6DhcpClientVendorClEntry 16842752}

er1645v2PppBFIpV6DhcpClientVendorClValueDecimal OBJECT-TYPE
   SYNTAX      Integer32
   MAX-ACCESS  read-write
   STATUS      current
   DESCRIPTION
      "Path: pppBundle.editConf.ipV6.dhcp.client.vendorClassOpt.value.decimal"
   ::= {er1645v2PppBFIpV6DhcpClientVendorClEntry 16908288}

er1645v2PppBFIpV6DhcpClientVendorClValueHexData OBJECT-TYPE
   SYNTAX      OCTET STRING
   MAX-ACCESS  read-write
   STATUS      current
   DESCRIPTION
      "Path: pppBundle.editConf.ipV6.dhcp.client.vendorClassOpt.value.hexData"
   ::= {er1645v2PppBFIpV6DhcpClientVendorClEntry 16973824}

er1645v2PppBFIpV6DhcpRelayDestinations OBJECT-TYPE
   SYNTAX      SEQUENCE OF Er1645v2PppBFIpV6DhcpRelayDestinationsEntry
   MAX-ACCESS  not-accessible
   STATUS      current
   DESCRIPTION
      ""
   ::= {er1645v2PppBFIpV6 174080000}

er1645v2PppBFIpV6DhcpRelayDestinationsEntry OBJECT-TYPE
   SYNTAX      Er1645v2PppBFIpV6DhcpRelayDestinationsEntry
   MAX-ACCESS  not-accessible
   STATUS      current
   DESCRIPTION
      ""
   INDEX      { er1645v2PppBFIpV6DhcpRelayDestinationsGlobalIx,
                er1645v2PppBFIpV6DhcpRelayDestinationsTableIx }
   ::= {er1645v2PppBFIpV6DhcpRelayDestinations 1}

Er1645v2PppBFIpV6DhcpRelayDestinationsEntry ::=
   SEQUENCE
      {
      er1645v2PppBFIpV6DhcpRelayDestinationsActions
         VariableLengthTableActions,
      er1645v2PppBFIpV6DhcpRelayDestinationsGlobalIx
         GlobalIndex,
      er1645v2PppBFIpV6DhcpRelayDestinationsTableIx
         TableIndex,
      er1645v2PppBFIpV6DhcpRelayDestinationsAddress
         Ipv6Address,
      er1645v2PppBFIpV6DhcpRelayDestinationsInterface
         DisplayString
      }

er1645v2PppBFIpV6DhcpRelayDestinationsActions OBJECT-TYPE
   SYNTAX      VariableLengthTableActions
   MAX-ACCESS  read-write
   STATUS      current
   DESCRIPTION
      "By way of this field, some manipulations
       on this table may be performed."
   ::= {er1645v2PppBFIpV6DhcpRelayDestinationsEntry 2}

er1645v2PppBFIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2PppBFIpV6DhcpRelayDestinationsEntry 10}

er1645v2PppBFIpV6DhcpRelayDestinationsTableIx OBJECT-TYPE
   SYNTAX      TableIndex
   MAX-ACCESS  not-accessible
   STATUS      current
   DESCRIPTION
      ""
   ::= {er1645v2PppBFIpV6DhcpRelayDestinationsEntry 11}

er1645v2PppBFIpV6DhcpRelayDestinationsAddress OBJECT-TYPE
   SYNTAX      Ipv6Address
   MAX-ACCESS  read-write
   STATUS      current
   DESCRIPTION
      "Path: pppBundle.editConf.ipV6.dhcp.relay.destinations.address

       ipv6 address"
   ::= {er1645v2PppBFIpV6DhcpRelayDestinationsEntry 16777216}

er1645v2PppBFIpV6DhcpRelayDestinationsInterface OBJECT-TYPE
   SYNTAX      DisplayString
   MAX-ACCESS  read-write
   STATUS      current
   DESCRIPTION
      "Path: pppBundle.editConf.ipV6.dhcp.relay.destinations.interface"
   ::= {er1645v2PppBFIpV6DhcpRelayDestinationsEntry 33554432}


er1645v2PppBFMembers OBJECT IDENTIFIER ::= {er1645v2PppBF 4}

er1645v2PppBFMembersSSCTable OBJECT-TYPE
   SYNTAX      SEQUENCE OF Er1645v2PppBFMembersEntry
   MAX-ACCESS  not-accessible
   STATUS      current
   DESCRIPTION
      ""
   ::= {er1645v2PppBFMembers 1}

er1645v2PppBFMembersEntry OBJECT-TYPE
   SYNTAX      Er1645v2PppBFMembersEntry
   MAX-ACCESS  not-accessible
   STATUS      current
   DESCRIPTION
      ""
   INDEX      { er1645v2PppBFMembersGlobalIx,
                er1645v2PppBFMembersTableIx }
   ::= {er1645v2PppBFMembersSSCTable 1}

Er1645v2PppBFMembersEntry ::=
   SEQUENCE
      {
      er1645v2PppBFMembersActions
         VariableLengthTableActions,
      er1645v2PppBFMembersGlobalIx
         GlobalIndex,
      er1645v2PppBFMembersTableIx
         TableIndex,
      er1645v2PppBFMembersInterface
         DisplayString
      }

er1645v2PppBFMembersActions OBJECT-TYPE
   SYNTAX      VariableLengthTableActions
   MAX-ACCESS  read-write
   STATUS      current
   DESCRIPTION
      "By way of this field, some manipulations
       on this table may be performed."
   ::= {er1645v2PppBFMembersEntry 2}

er1645v2PppBFMembersGlobalIx OBJECT-TYPE
   SYNTAX      GlobalIndex
   MAX-ACCESS  not-accessible
   STATUS      current
   DESCRIPTION
      "The value of the tlsCntTreeGlobalIndex of the MANAGED OBJECT."
   ::= {er1645v2PppBFMembersEntry 10}

er1645v2PppBFMembersTableIx OBJECT-TYPE
   SYNTAX      TableIndex
   MAX-ACCESS  not-accessible
   STATUS      current
   DESCRIPTION
      ""
   ::= {er1645v2PppBFMembersEntry 11}

er1645v2PppBFMembersInterface OBJECT-TYPE
   SYNTAX      DisplayString
   MAX-ACCESS  read-write
   STATUS      current
   DESCRIPTION
      "Path: pppBundle.editConf.members.interface"
   ::= {er1645v2PppBFMembersEntry 16777216}


er1645v2PppBFFragmentation OBJECT IDENTIFIER ::= {er1645v2PppBF 8}

er1645v2PppBFFragmentationTable OBJECT-TYPE
   SYNTAX      SEQUENCE OF Er1645v2PppBFFragmentationEntry
   MAX-ACCESS  not-accessible
   STATUS      current
   DESCRIPTION
      ""
   ::= {er1645v2PppBFFragmentation 1}

er1645v2PppBFFragmentationEntry OBJECT-TYPE
   SYNTAX      Er1645v2PppBFFragmentationEntry
   MAX-ACCESS  not-accessible
   STATUS      current
   DESCRIPTION
      ""
   INDEX      { er1645v2PppBFFragmentationGlobalIx }
   ::= {er1645v2PppBFFragmentationTable 1}

Er1645v2PppBFFragmentationEntry ::=
   SEQUENCE
      {
      er1645v2PppBFFragmentationGlobalIx
         GlobalIndex,
      er1645v2PppBFFragmentationValue
         INTEGER
      }

er1645v2PppBFFragmentationGlobalIx OBJECT-TYPE
   SYNTAX      GlobalIndex
   MAX-ACCESS  not-accessible
   STATUS      current
   DESCRIPTION
      "The value of the tlsCntTreeGlobalIndex of the MANAGED OBJECT."
   ::= {er1645v2PppBFFragmentationEntry 10}

er1645v2PppBFFragmentationValue OBJECT-TYPE
   SYNTAX      INTEGER
               {
               disabled (0),
               enabled (1),
               s256 (256),
               s384 (384),
               s512 (512),
               s640 (640),
               s768 (768),
               s896 (896),
               s1024 (1024)
               }
   MAX-ACCESS  read-write
   STATUS      current
   DESCRIPTION
      "Path: pppBundle.editConf.fragmentation

       Possibilities:
               disabled   (0)
               enabled   (1)
               256   (256)
               384   (384)
               512   (512)
               640   (640)
               768   (768)
               896   (896)
               1024   (1024)"
   ::= {er1645v2PppBFFragmentationEntry 2147483648}


er1645v2PppBFInterleaving OBJECT IDENTIFIER ::= {er1645v2PppBF 17}

er1645v2PppBFInterleavingTable OBJECT-TYPE
   SYNTAX      SEQUENCE OF Er1645v2PppBFInterleavingEntry
   MAX-ACCESS  not-accessible
   STATUS      current
   DESCRIPTION
      ""
   ::= {er1645v2PppBFInterleaving 1}

er1645v2PppBFInterleavingEntry OBJECT-TYPE
   SYNTAX      Er1645v2PppBFInterleavingEntry
   MAX-ACCESS  not-accessible
   STATUS      current
   DESCRIPTION
      ""
   INDEX      { er1645v2PppBFInterleavingGlobalIx }
   ::= {er1645v2PppBFInterleavingTable 1}

Er1645v2PppBFInterleavingEntry ::=
   SEQUENCE
      {
      er1645v2PppBFInterleavingGlobalIx
         GlobalIndex,
      er1645v2PppBFInterleavingValue
         INTEGER
      }

er1645v2PppBFInterleavingGlobalIx OBJECT-TYPE
   SYNTAX      GlobalIndex
   MAX-ACCESS  not-accessible
   STATUS      current
   DESCRIPTION
      "The value of the tlsCntTreeGlobalIndex of the MANAGED OBJECT."
   ::= {er1645v2PppBFInterleavingEntry 10}

er1645v2PppBFInterleavingValue OBJECT-TYPE
   SYNTAX      INTEGER
               {
               disabled (0),
               enabled (1)
               }
   MAX-ACCESS  read-write
   STATUS      current
   DESCRIPTION
      "Path: pppBundle.editConf.interleaving

       Possibilities:
               disabled   (0)
               enabled   (1)"
   ::= {er1645v2PppBFInterleavingEntry 2147483648}


er1645v2PppBFMyMrru OBJECT IDENTIFIER ::= {er1645v2PppBF 18}

er1645v2PppBFMyMrruTable OBJECT-TYPE
   SYNTAX      SEQUENCE OF Er1645v2PppBFMyMrruEntry
   MAX-ACCESS  not-accessible
   STATUS      current
   DESCRIPTION
      "Maximum Receive Reconstructed Unit"
   ::= {er1645v2PppBFMyMrru 1}

er1645v2PppBFMyMrruEntry OBJECT-TYPE
   SYNTAX      Er1645v2PppBFMyMrruEntry
   MAX-ACCESS  not-accessible
   STATUS      current
   DESCRIPTION
      ""
   INDEX      { er1645v2PppBFMyMrruGlobalIx }
   ::= {er1645v2PppBFMyMrruTable 1}

Er1645v2PppBFMyMrruEntry ::=
   SEQUENCE
      {
      er1645v2PppBFMyMrruGlobalIx
         GlobalIndex,
      er1645v2PppBFMyMrruValue
         Integer32
      }

er1645v2PppBFMyMrruGlobalIx OBJECT-TYPE
   SYNTAX      GlobalIndex
   MAX-ACCESS  not-accessible
   STATUS      current
   DESCRIPTION
      "The value of the tlsCntTreeGlobalIndex of the MANAGED OBJECT."
   ::= {er1645v2PppBFMyMrruEntry 10}

er1645v2PppBFMyMrruValue OBJECT-TYPE
   SYNTAX      Integer32
   MAX-ACCESS  read-write
   STATUS      current
   DESCRIPTION
      "Path: pppBundle.editConf.myMrru"
   ::= {er1645v2PppBFMyMrruEntry 2147483648}


er1645v2PppBFEpDisc OBJECT IDENTIFIER ::= {er1645v2PppBF 10}

er1645v2PppBFEpDiscTable OBJECT-TYPE
   SYNTAX      SEQUENCE OF Er1645v2PppBFEpDiscEntry
   MAX-ACCESS  not-accessible
   STATUS      current
   DESCRIPTION
      ""
   ::= {er1645v2PppBFEpDisc 1}

er1645v2PppBFEpDiscEntry OBJECT-TYPE
   SYNTAX      Er1645v2PppBFEpDiscEntry
   MAX-ACCESS  not-accessible
   STATUS      current
   DESCRIPTION
      ""
   INDEX      { er1645v2PppBFEpDiscGlobalIx }
   ::= {er1645v2PppBFEpDiscTable 1}

Er1645v2PppBFEpDiscEntry ::=
   SEQUENCE
      {
      er1645v2PppBFEpDiscGlobalIx
         GlobalIndex,
      er1645v2PppBFEpDiscValue
         INTEGER
      }

er1645v2PppBFEpDiscGlobalIx OBJECT-TYPE
   SYNTAX      GlobalIndex
   MAX-ACCESS  not-accessible
   STATUS      current
   DESCRIPTION
      "The value of the tlsCntTreeGlobalIndex of the MANAGED OBJECT."
   ::= {er1645v2PppBFEpDiscEntry 10}

er1645v2PppBFEpDiscValue OBJECT-TYPE
   SYNTAX      INTEGER
               {
               localAssignedAddress (1),
               macAddress (3)
               }
   MAX-ACCESS  read-write
   STATUS      current
   DESCRIPTION
      "Path: pppBundle.editConf.endpointDiscrClass

       Possibilities:
               localAssignedAddress   (1)
               macAddress   (3)"
   ::= {er1645v2PppBFEpDiscEntry 2147483648}


er1645v2PppBFPriorityPolicy OBJECT IDENTIFIER ::= {er1645v2PppBF 33}

er1645v2PppBFPriorityPolicyTable OBJECT-TYPE
   SYNTAX      SEQUENCE OF Er1645v2PppBFPriorityPolicyEntry
   MAX-ACCESS  not-accessible
   STATUS      current
   DESCRIPTION
      "Preferred Policy"
   ::= {er1645v2PppBFPriorityPolicy 1}

er1645v2PppBFPriorityPolicyEntry OBJECT-TYPE
   SYNTAX      Er1645v2PppBFPriorityPolicyEntry
   MAX-ACCESS  not-accessible
   STATUS      current
   DESCRIPTION
      ""
   INDEX      { er1645v2PppBFPriorityPolicyGlobalIx }
   ::= {er1645v2PppBFPriorityPolicyTable 1}

Er1645v2PppBFPriorityPolicyEntry ::=
   SEQUENCE
      {
      er1645v2PppBFPriorityPolicyGlobalIx
         GlobalIndex,
      er1645v2PppBFPriorityPolicyValue
         DisplayString
      }

er1645v2PppBFPriorityPolicyGlobalIx OBJECT-TYPE
   SYNTAX      GlobalIndex
   MAX-ACCESS  not-accessible
   STATUS      current
   DESCRIPTION
      "The value of the tlsCntTreeGlobalIndex of the MANAGED OBJECT."
   ::= {er1645v2PppBFPriorityPolicyEntry 10}

er1645v2PppBFPriorityPolicyValue OBJECT-TYPE
   SYNTAX      DisplayString
   MAX-ACCESS  read-write
   STATUS      current
   DESCRIPTION
      "Path: pppBundle.editConf.priorityPolicy"
   ::= {er1645v2PppBFPriorityPolicyEntry 2147483648}


er1645v2PppBFDelayOptimisation OBJECT IDENTIFIER ::= {er1645v2PppBF 80}

er1645v2PppBFDelayOptimisationTable OBJECT-TYPE
   SYNTAX      SEQUENCE OF Er1645v2PppBFDelayOptimisationEntry
   MAX-ACCESS  not-accessible
   STATUS      current
   DESCRIPTION
      "optimise delay"
   ::= {er1645v2PppBFDelayOptimisation 1}

er1645v2PppBFDelayOptimisationEntry OBJECT-TYPE
   SYNTAX      Er1645v2PppBFDelayOptimisationEntry
   MAX-ACCESS  not-accessible
   STATUS      current
   DESCRIPTION
      ""
   INDEX      { er1645v2PppBFDelayOptimisationGlobalIx }
   ::= {er1645v2PppBFDelayOptimisationTable 1}

Er1645v2PppBFDelayOptimisationEntry ::=
   SEQUENCE
      {
      er1645v2PppBFDelayOptimisationGlobalIx
         GlobalIndex,
      er1645v2PppBFDelayOptimisationValue
         INTEGER
      }

er1645v2PppBFDelayOptimisationGlobalIx OBJECT-TYPE
   SYNTAX      GlobalIndex
   MAX-ACCESS  not-accessible
   STATUS      current
   DESCRIPTION
      "The value of the tlsCntTreeGlobalIndex of the MANAGED OBJECT."
   ::= {er1645v2PppBFDelayOptimisationEntry 10}

er1645v2PppBFDelayOptimisationValue OBJECT-TYPE
   SYNTAX      INTEGER
               {
               disabled (0),
               enabled (1)
               }
   MAX-ACCESS  read-write
   STATUS      current
   DESCRIPTION
      "Path: pppBundle.editConf.delayOptimisation

       Possibilities:
               disabled   (0)
               enabled   (1)"
   ::= {er1645v2PppBFDelayOptimisationEntry 2147483648}


er1645v2PppBFMaxFifoQLen OBJECT IDENTIFIER ::= {er1645v2PppBF 34}

er1645v2PppBFMaxFifoQLenTable OBJECT-TYPE
   SYNTAX      SEQUENCE OF Er1645v2PppBFMaxFifoQLenEntry
   MAX-ACCESS  not-accessible
   STATUS      current
   DESCRIPTION
      "maximun queue length for fifo"
   ::= {er1645v2PppBFMaxFifoQLen 1}

er1645v2PppBFMaxFifoQLenEntry OBJECT-TYPE
   SYNTAX      Er1645v2PppBFMaxFifoQLenEntry
   MAX-ACCESS  not-accessible
   STATUS      current
   DESCRIPTION
      ""
   INDEX      { er1645v2PppBFMaxFifoQLenGlobalIx }
   ::= {er1645v2PppBFMaxFifoQLenTable 1}

Er1645v2PppBFMaxFifoQLenEntry ::=
   SEQUENCE
      {
      er1645v2PppBFMaxFifoQLenGlobalIx
         GlobalIndex,
      er1645v2PppBFMaxFifoQLenValue
         Integer32
      }

er1645v2PppBFMaxFifoQLenGlobalIx OBJECT-TYPE
   SYNTAX      GlobalIndex
   MAX-ACCESS  not-accessible
   STATUS      current
   DESCRIPTION
      "The value of the tlsCntTreeGlobalIndex of the MANAGED OBJECT."
   ::= {er1645v2PppBFMaxFifoQLenEntry 10}

er1645v2PppBFMaxFifoQLenValue OBJECT-TYPE
   SYNTAX      Integer32
   MAX-ACCESS  read-write
   STATUS      current
   DESCRIPTION
      "Path: pppBundle.editConf.maxFifoQLen"
   ::= {er1645v2PppBFMaxFifoQLenEntry 2147483648}


er1645v2PppBFDQueue OBJECT IDENTIFIER ::= {er1645v2PppBF 35}

er1645v2PppBFDQueueTable OBJECT-TYPE
   SYNTAX      SEQUENCE OF Er1645v2PppBFDQueueEntry
   MAX-ACCESS  not-accessible
   STATUS      current
   DESCRIPTION
      "default priority queue"
   ::= {er1645v2PppBFDQueue 1}

er1645v2PppBFDQueueEntry OBJECT-TYPE
   SYNTAX      Er1645v2PppBFDQueueEntry
   MAX-ACCESS  not-accessible
   STATUS      current
   DESCRIPTION
      ""
   INDEX      { er1645v2PppBFDQueueGlobalIx }
   ::= {er1645v2PppBFDQueueTable 1}

Er1645v2PppBFDQueueEntry ::=
   SEQUENCE
      {
      er1645v2PppBFDQueueGlobalIx
         GlobalIndex,
      er1645v2PppBFDQueueValue
         INTEGER
      }

er1645v2PppBFDQueueGlobalIx OBJECT-TYPE
   SYNTAX      GlobalIndex
   MAX-ACCESS  not-accessible
   STATUS      current
   DESCRIPTION
      "The value of the tlsCntTreeGlobalIndex of the MANAGED OBJECT."
   ::= {er1645v2PppBFDQueueEntry 10}

er1645v2PppBFDQueueValue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.defaultQueue

       Possibilities:
               queue1   (0)
               queue2   (1)
               queue3   (2)
               queue4   (3)
               queue5   (4)
               lowDelayQueue   (5)
               lowDelay2Queue   (6)
               systemQueue   (7)"
   ::= {er1645v2PppBFDQueueEntry 2147483648}


er1645v2PppBFBw OBJECT IDENTIFIER ::= {er1645v2PppBF 5}

er1645v2PppBFBwSSCTable OBJECT-TYPE
   SYNTAX      SEQUENCE OF Er1645v2PppBFBwEntry
   MAX-ACCESS  not-accessible
   STATUS      current
   DESCRIPTION
      ""
   ::= {er1645v2PppBFBw 1}

er1645v2PppBFBwEntry OBJECT-TYPE
   SYNTAX      Er1645v2PppBFBwEntry
   MAX-ACCESS  not-accessible
   STATUS      current
   DESCRIPTION
      ""
   INDEX      { er1645v2PppBFBwGlobalIx }
   ::= {er1645v2PppBFBwSSCTable 1}

Er1645v2PppBFBwEntry ::=
   SEQUENCE
      {
      er1645v2PppBFBwGlobalIx
         GlobalIndex,
      er1645v2PppBFBwMode
         INTEGER,
      er1645v2PppBFBwCir
         Integer32,
      er1645v2PppBFBwEir
         Integer32,
      er1645v2PppBFBwUnit
         INTEGER,
      er1645v2PppBFBwTc
         INTEGER,
      er1645v2PppBFBwTcFactor
         INTEGER,
      er1645v2PppBFBwCorrType
         INTEGER,
      er1645v2PppBFBwCorrPredefEncapsFrameRelay
         DisplayString,
      er1645v2PppBFBwCorrPredefEncapsPpp
         DisplayString,
      er1645v2PppBFBwCorrPredefEncapsAtmHl
         INTEGER,
      er1645v2PppBFBwCorrPredefEncapsAtmMp
         INTEGER,
      er1645v2PppBFBwCorrPredefEncapsHdlc
         DisplayString,
      er1645v2PppBFBwCorrPredefEncapsEfmFs
         Integer32,
      er1645v2PppBFBwCorrPredefEncapsEfmIb
         Integer32,
      er1645v2PppBFBwCorrPredefMode
         INTEGER,
      er1645v2PppBFBwCorrManualOverhead
         Integer32,
      er1645v2PppBFBwCorrManualFrameData
         Counter32,
      er1645v2PppBFBwCorrManualFrameHeader
         Counter32,
      er1645v2PppBFBwMaxFifoQLen
         Integer32,
      er1645v2PppBFBwDeFlagCir
         INTEGER,
      er1645v2PppBFBwDeFlagEir
         INTEGER,
      er1645v2PppBFBwDeFlagViolate
         INTEGER,
      er1645v2PppBFBwActCirActNone
         OCTET STRING,
      er1645v2PppBFBwActCirActEthCos1
         INTEGER,
      er1645v2PppBFBwActCirActEthDei1
         INTEGER,
      er1645v2PppBFBwActCirActEthCos2
         INTEGER,
      er1645v2PppBFBwActCirActEthDei2
         INTEGER,
      er1645v2PppBFBwActCirActEthCos3
         INTEGER,
      er1645v2PppBFBwActCirActEthDei3
         INTEGER,
      er1645v2PppBFBwActCirActEthCos4
         INTEGER,
      er1645v2PppBFBwActCirActEthDei4
         INTEGER,
      er1645v2PppBFBwActCirActEthCos5
         INTEGER,
      er1645v2PppBFBwActCirActEthDei5
         INTEGER,
      er1645v2PppBFBwActCirActEthCos6
         INTEGER,
      er1645v2PppBFBwActCirActEthDei6
         INTEGER,
      er1645v2PppBFBwActCirActEthCos7
         INTEGER,
      er1645v2PppBFBwActCirActEthDei7
         INTEGER,
      er1645v2PppBFBwActCirActEthCos8
         INTEGER,
      er1645v2PppBFBwActCirActEthDei8
         INTEGER,
      er1645v2PppBFBwActCirActEthTos
         INTEGER,
      er1645v2PppBFBwActCirActEthQueue
         INTEGER,
      er1645v2PppBFBwActCirActEthDrpLev
         INTEGER,
      er1645v2PppBFBwActCirActEthDeFlag
         INTEGER,
      er1645v2PppBFBwActCirActIpTos
         INTEGER,
      er1645v2PppBFBwActCirActIpQueue
         INTEGER,
      er1645v2PppBFBwActCirActIpDrpLev
         INTEGER,
      er1645v2PppBFBwActCirActIpDeFlag
         INTEGER,
      er1645v2PppBFBwActEirActNone
         OCTET STRING,
      er1645v2PppBFBwActEirActEthCos1
         INTEGER,
      er1645v2PppBFBwActEirActEthDei1
         INTEGER,
      er1645v2PppBFBwActEirActEthCos2
         INTEGER,
      er1645v2PppBFBwActEirActEthDei2
         INTEGER,
      er1645v2PppBFBwActEirActEthCos3
         INTEGER,
      er1645v2PppBFBwActEirActEthDei3
         INTEGER,
      er1645v2PppBFBwActEirActEthCos4
         INTEGER,
      er1645v2PppBFBwActEirActEthDei4
         INTEGER,
      er1645v2PppBFBwActEirActEthCos5
         INTEGER,
      er1645v2PppBFBwActEirActEthDei5
         INTEGER,
      er1645v2PppBFBwActEirActEthCos6
         INTEGER,
      er1645v2PppBFBwActEirActEthDei6
         INTEGER,
      er1645v2PppBFBwActEirActEthCos7
         INTEGER,
      er1645v2PppBFBwActEirActEthDei7
         INTEGER,
      er1645v2PppBFBwActEirActEthCos8
         INTEGER,
      er1645v2PppBFBwActEirActEthDei8
         INTEGER,
      er1645v2PppBFBwActEirActEthTos
         INTEGER,
      er1645v2PppBFBwActEirActEthQueue
         INTEGER,
      er1645v2PppBFBwActEirActEthDrpLev
         INTEGER,
      er1645v2PppBFBwActEirActEthDeFlag
         INTEGER,
      er1645v2PppBFBwActEirActIpTos
         INTEGER,
      er1645v2PppBFBwActEirActIpQueue
         INTEGER,
      er1645v2PppBFBwActEirActIpDrpLev
         INTEGER,
      er1645v2PppBFBwActEirActIpDeFlag
         INTEGER,
      er1645v2PppBFBwActViolActNone
         OCTET STRING,
      er1645v2PppBFBwActViolActDrop
         OCTET STRING,
      er1645v2PppBFBwActViolActEthCos1
         INTEGER,
      er1645v2PppBFBwActViolActEthDei1
         INTEGER,
      er1645v2PppBFBwActViolActEthCos2
         INTEGER,
      er1645v2PppBFBwActViolActEthDei2
         INTEGER,
      er1645v2PppBFBwActViolActEthCos3
         INTEGER,
      er1645v2PppBFBwActViolActEthDei3
         INTEGER,
      er1645v2PppBFBwActViolActEthCos4
         INTEGER,
      er1645v2PppBFBwActViolActEthDei4
         INTEGER,
      er1645v2PppBFBwActViolActEthCos5
         INTEGER,
      er1645v2PppBFBwActViolActEthDei5
         INTEGER,
      er1645v2PppBFBwActViolActEthCos6
         INTEGER,
      er1645v2PppBFBwActViolActEthDei6
         INTEGER,
      er1645v2PppBFBwActViolActEthCos7
         INTEGER,
      er1645v2PppBFBwActViolActEthDei7
         INTEGER,
      er1645v2PppBFBwActViolActEthCos8
         INTEGER,
      er1645v2PppBFBwActViolActEthDei8
         INTEGER,
      er1645v2PppBFBwActViolActEthTos
         INTEGER,
      er1645v2PppBFBwActViolActEthQueue
         INTEGER,
      er1645v2PppBFBwActViolActEthDrpLev
         INTEGER,
      er1645v2PppBFBwActViolActEthDeFlag
         INTEGER,
      er1645v2PppBFBwActViolActIpTos
         INTEGER,
      er1645v2PppBFBwActViolActIpQueue
         INTEGER,
      er1645v2PppBFBwActViolActIpDrpLev
         INTEGER,
      er1645v2PppBFBwActViolActIpDeFlag
         INTEGER
      }

er1645v2PppBFBwGlobalIx OBJECT-TYPE
   SYNTAX      GlobalIndex
   MAX-ACCESS  not-accessible
   STATUS      current
   DESCRIPTION
      "The value of the tlsCntTreeGlobalIndex of the MANAGED OBJECT."
   ::= {er1645v2PppBFBwEntry 10}

er1645v2PppBFBwMode OBJECT-TYPE
   SYNTAX      INTEGER
               {
               reshaping (1),
               policing (2),
               policingReshape (3)
               }
   MAX-ACCESS  read-write
   STATUS      current
   DESCRIPTION
      "Path: pppBundle.editConf.bandwidth.mode

       Possibilities:
               reshaping   (1)
               policing   (2)
               policingReshape   (3)"
   ::= {er1645v2PppBFBwEntry 3758096384}

er1645v2PppBFBwCir OBJECT-TYPE
   SYNTAX      Integer32
   MAX-ACCESS  read-write
   STATUS      current
   DESCRIPTION
      "Path: pppBundle.editConf.bandwidth.cir"
   ::= {er1645v2PppBFBwEntry 268435456}

er1645v2PppBFBwEir OBJECT-TYPE
   SYNTAX      Integer32
   MAX-ACCESS  read-write
   STATUS      current
   DESCRIPTION
      "Path: pppBundle.editConf.bandwidth.eir"
   ::= {er1645v2PppBFBwEntry 1879048192}

er1645v2PppBFBwUnit OBJECT-TYPE
   SYNTAX      INTEGER
               {
               bitssec (1),
               percent (2)
               }
   MAX-ACCESS  read-write
   STATUS      current
   DESCRIPTION
      "Path: pppBundle.editConf.bandwidth.unit

       Possibilities:
               bits/sec   (1)
               percent   (2)"
   ::= {er1645v2PppBFBwEntry 1342177280}

er1645v2PppBFBwTc OBJECT-TYPE
   SYNTAX      INTEGER
               {
               auto (0)
               }
   MAX-ACCESS  read-write
   STATUS      current
   DESCRIPTION
      "Path: pppBundle.editConf.bandwidth.tc

       Possibilities:
               auto   (0)"
   ::= {er1645v2PppBFBwEntry 1610612736}

er1645v2PppBFBwTcFactor OBJECT-TYPE
   SYNTAX      INTEGER
               {
               ms (10),
               s100us (1)
               }
   MAX-ACCESS  read-write
   STATUS      current
   DESCRIPTION
      "Path: pppBundle.editConf.bandwidth.tcFactor

       Possibilities:
               ms   (10)
               *100us   (1)"
   ::= {er1645v2PppBFBwEntry 2147483648}

er1645v2PppBFBwCorrType OBJECT-TYPE
   SYNTAX      INTEGER
               {
               noCorrection (0),
               predefined (1),
               manual (2)
               }
   MAX-ACCESS  read-write
   STATUS      current
   DESCRIPTION
      "Path: pppBundle.editConf.bandwidth.correction.type

       Possibilities:
               noCorrection   (0)
               predefined   (1)
               manual   (2)"
   ::= {er1645v2PppBFBwEntry 570425344}

er1645v2PppBFBwCorrPredefEncapsFrameRelay OBJECT-TYPE
   SYNTAX      DisplayString
   MAX-ACCESS  read-write
   STATUS      current
   DESCRIPTION
      "Path: pppBundle.editConf.bandwidth.correction.predefined.encapsulation.frameRelay"
   ::= {er1645v2PppBFBwEntry 608436224}

er1645v2PppBFBwCorrPredefEncapsPpp OBJECT-TYPE
   SYNTAX      DisplayString
   MAX-ACCESS  read-write
   STATUS      current
   DESCRIPTION
      "Path: pppBundle.editConf.bandwidth.correction.predefined.encapsulation.ppp"
   ::= {er1645v2PppBFBwEntry 608698368}

er1645v2PppBFBwCorrPredefEncapsAtmHl OBJECT-TYPE
   SYNTAX      INTEGER
               {
               rfc2684 (0),
               ppp (1),
               pppOverEthernet (2)
               }
   MAX-ACCESS  read-write
   STATUS      current
   DESCRIPTION
      "Path: pppBundle.editConf.bandwidth.correction.predefined.encapsulation.atm.higherLayer

       Possibilities:
               rfc2684   (0)
               ppp   (1)
               pppOverEthernet   (2)"
   ::= {er1645v2PppBFBwEntry 608993280}

er1645v2PppBFBwCorrPredefEncapsAtmMp OBJECT-TYPE
   SYNTAX      INTEGER
               {
               llcEncapsulation (0),
               vcMultiplexing (1)
               }
   MAX-ACCESS  read-write
   STATUS      current
   DESCRIPTION
      "Path: pppBundle.editConf.bandwidth.correction.predefined.encapsulation.atm.multiProtocol

       Possibilities:
               llcEncapsulation   (0)
               vcMultiplexing   (1)"
   ::= {er1645v2PppBFBwEntry 609026048}

er1645v2PppBFBwCorrPredefEncapsHdlc OBJECT-TYPE
   SYNTAX      DisplayString
   MAX-ACCESS  read-write
   STATUS      current
   DESCRIPTION
      "Path: pppBundle.editConf.bandwidth.correction.predefined.encapsulation.hdlc"
   ::= {er1645v2PppBFBwEntry 609222656}

er1645v2PppBFBwCorrPredefEncapsEfmFs OBJECT-TYPE
   SYNTAX      Integer32
   MAX-ACCESS  read-write
   STATUS      current
   DESCRIPTION
      "Path: pppBundle.editConf.bandwidth.correction.predefined.encapsulation.efm.fragmentSize"
   ::= {er1645v2PppBFBwEntry 609517568}

er1645v2PppBFBwCorrPredefEncapsEfmIb OBJECT-TYPE
   SYNTAX      Integer32
   MAX-ACCESS  read-write
   STATUS      current
   DESCRIPTION
      "Path: pppBundle.editConf.bandwidth.correction.predefined.encapsulation.efm.idleBytes"
   ::= {er1645v2PppBFBwEntry 609550336}

er1645v2PppBFBwCorrPredefMode OBJECT-TYPE
   SYNTAX      INTEGER
               {
               routing (0),
               bridging (1)
               }
   MAX-ACCESS  read-write
   STATUS      current
   DESCRIPTION
      "Path: pppBundle.editConf.bandwidth.correction.predefined.mode

       Possibilities:
               routing   (0)
               bridging   (1)"
   ::= {er1645v2PppBFBwEntry 612368384}

er1645v2PppBFBwCorrManualOverhead OBJECT-TYPE
   SYNTAX      Integer32
   MAX-ACCESS  read-write
   STATUS      current
   DESCRIPTION
      "Path: pppBundle.editConf.bandwidth.correction.manual.overhead"
   ::= {er1645v2PppBFBwEntry 637665280}

er1645v2PppBFBwCorrManualFrameData OBJECT-TYPE
   SYNTAX      Counter32
   MAX-ACCESS  read-write
   STATUS      current
   DESCRIPTION
      "Path: pppBundle.editConf.bandwidth.correction.manual.frameData

       32 bit unsigned wrappable counter."
   ::= {er1645v2PppBFBwEntry 637796352}

er1645v2PppBFBwCorrManualFrameHeader OBJECT-TYPE
   SYNTAX      Counter32
   MAX-ACCESS  read-write
   STATUS      current
   DESCRIPTION
      "Path: pppBundle.editConf.bandwidth.correction.manual.frameHeader

       32 bit unsigned wrappable counter."
   ::= {er1645v2PppBFBwEntry 637927424}

er1645v2PppBFBwMaxFifoQLen OBJECT-TYPE
   SYNTAX      Integer32
   MAX-ACCESS  read-write
   STATUS      current
   DESCRIPTION
      "Path: pppBundle.editConf.bandwidth.maxFifoQLen"
   ::= {er1645v2PppBFBwEntry 805306368}

er1645v2PppBFBwDeFlagCir OBJECT-TYPE
   SYNTAX      INTEGER
               {
               allowed (1),
               notAllowed (2)
               }
   MAX-ACCESS  read-write
   STATUS      current
   DESCRIPTION
      "Path: pppBundle.editConf.bandwidth.deFlag.cir

       Possibilities:
               allowed   (1)
               notAllowed   (2)"
   ::= {er1645v2PppBFBwEntry 3490709504}

er1645v2PppBFBwDeFlagEir OBJECT-TYPE
   SYNTAX      INTEGER
               {
               allowed (1),
               notAllowed (2)
               }
   MAX-ACCESS  read-write
   STATUS      current
   DESCRIPTION
      "Path: pppBundle.editConf.bandwidth.deFlag.eir

       Possibilities:
               allowed   (1)
               notAllowed   (2)"
   ::= {er1645v2PppBFBwEntry 3491758080}

er1645v2PppBFBwDeFlagViolate OBJECT-TYPE
   SYNTAX      INTEGER
               {
               allowed (1),
               notAllowed (2)
               }
   MAX-ACCESS  read-write
   STATUS      current
   DESCRIPTION
      "Path: pppBundle.editConf.bandwidth.deFlag.violate

       Possibilities:
               allowed   (1)
               notAllowed   (2)"
   ::= {er1645v2PppBFBwEntry 3492806656}

er1645v2PppBFBwActCirActNone OBJECT-TYPE
   SYNTAX      OCTET STRING
   MAX-ACCESS  read-write
   STATUS      current
   DESCRIPTION
      "Path: pppBundle.editConf.bandwidth.action.cirAction.none"
   ::= {er1645v2PppBFBwEntry 4062183424}

er1645v2PppBFBwActCirActEthCos1 OBJECT-TYPE
   SYNTAX      INTEGER
               {
               unchanged (256)
               }
   MAX-ACCESS  read-write
   STATUS      current
   DESCRIPTION
      "Path: pppBundle.editConf.bandwidth.action.cirAction.ethernet.cosDepth1

       Possibilities:
               unchanged   (256)"
   ::= {er1645v2PppBFBwEntry 4064346112}

er1645v2PppBFBwActCirActEthDei1 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth1

       Possibilities:
               unchanged   (255)
               clear   (0)
               set   (1)"
   ::= {er1645v2PppBFBwEntry 4065656832}

er1645v2PppBFBwActCirActEthCos2 OBJECT-TYPE
   SYNTAX      INTEGER
               {
               unchanged (256)
               }
   MAX-ACCESS  read-write
   STATUS      current
   DESCRIPTION
      "Path: pppBundle.editConf.bandwidth.action.cirAction.ethernet.cosDepth2

       Possibilities:
               unchanged   (256)"
   ::= {er1645v2PppBFBwEntry 4064411648}

er1645v2PppBFBwActCirActEthDei2 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth2

       Possibilities:
               unchanged   (255)
               clear   (0)
               set   (1)"
   ::= {er1645v2PppBFBwEntry 4065722368}

er1645v2PppBFBwActCirActEthCos3 OBJECT-TYPE
   SYNTAX      INTEGER
               {
               unchanged (256)
               }
   MAX-ACCESS  read-write
   STATUS      current
   DESCRIPTION
      "Path: pppBundle.editConf.bandwidth.action.cirAction.ethernet.cosDepth3

       Possibilities:
               unchanged   (256)"
   ::= {er1645v2PppBFBwEntry 4064477184}

er1645v2PppBFBwActCirActEthDei3 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth3

       Possibilities:
               unchanged   (255)
               clear   (0)
               set   (1)"
   ::= {er1645v2PppBFBwEntry 4065787904}

er1645v2PppBFBwActCirActEthCos4 OBJECT-TYPE
   SYNTAX      INTEGER
               {
               unchanged (256)
               }
   MAX-ACCESS  read-write
   STATUS      current
   DESCRIPTION
      "Path: pppBundle.editConf.bandwidth.action.cirAction.ethernet.cosDepth4

       Possibilities:
               unchanged   (256)"
   ::= {er1645v2PppBFBwEntry 4064542720}

er1645v2PppBFBwActCirActEthDei4 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth4

       Possibilities:
               unchanged   (255)
               clear   (0)
               set   (1)"
   ::= {er1645v2PppBFBwEntry 4065853440}

er1645v2PppBFBwActCirActEthCos5 OBJECT-TYPE
   SYNTAX      INTEGER
               {
               unchanged (256)
               }
   MAX-ACCESS  read-write
   STATUS      current
   DESCRIPTION
      "Path: pppBundle.editConf.bandwidth.action.cirAction.ethernet.cosDepth5

       Possibilities:
               unchanged   (256)"
   ::= {er1645v2PppBFBwEntry 4064608256}

er1645v2PppBFBwActCirActEthDei5 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth5

       Possibilities:
               unchanged   (255)
               clear   (0)
               set   (1)"
   ::= {er1645v2PppBFBwEntry 4065918976}

er1645v2PppBFBwActCirActEthCos6 OBJECT-TYPE
   SYNTAX      INTEGER
               {
               unchanged (256)
               }
   MAX-ACCESS  read-write
   STATUS      current
   DESCRIPTION
      "Path: pppBundle.editConf.bandwidth.action.cirAction.ethernet.cosDepth6

       Possibilities:
               unchanged   (256)"
   ::= {er1645v2PppBFBwEntry 4064673792}

er1645v2PppBFBwActCirActEthDei6 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth6

       Possibilities:
               unchanged   (255)
               clear   (0)
               set   (1)"
   ::= {er1645v2PppBFBwEntry 4065984512}

er1645v2PppBFBwActCirActEthCos7 OBJECT-TYPE
   SYNTAX      INTEGER
               {
               unchanged (256)
               }
   MAX-ACCESS  read-write
   STATUS      current
   DESCRIPTION
      "Path: pppBundle.editConf.bandwidth.action.cirAction.ethernet.cosDepth7

       Possibilities:
               unchanged   (256)"
   ::= {er1645v2PppBFBwEntry 4064739328}

er1645v2PppBFBwActCirActEthDei7 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth7

       Possibilities:
               unchanged   (255)
               clear   (0)
               set   (1)"
   ::= {er1645v2PppBFBwEntry 4066050048}

er1645v2PppBFBwActCirActEthCos8 OBJECT-TYPE
   SYNTAX      INTEGER
               {
               unchanged (256)
               }
   MAX-ACCESS  read-write
   STATUS      current
   DESCRIPTION
      "Path: pppBundle.editConf.bandwidth.action.cirAction.ethernet.cosDepth8

       Possibilities:
               unchanged   (256)"
   ::= {er1645v2PppBFBwEntry 4064804864}

er1645v2PppBFBwActCirActEthDei8 OBJECT-TYPE
   SYNTAX      INTEGER
               {
               unchanged (255),
               clear (0),
               set (1)
               }
   MAX-ACCESS  read-write
   STATUS      current
   DESCRIPTION
      "Path: pppBundle.editConf.bandwidth.action.cirAction.ethernet.deiDepth8

       Possibilities:
               unchanged   (255)
               clear   (0)
               set   (1)"
   ::= {er1645v2PppBFBwEntry 4066115584}

er1645v2PppBFBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: pppBundle.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PppBFBwEntry 4064870400}

er1645v2PppBFBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PppBFBwEntry 4064935936}

er1645v2PppBFBwActCirActEthDrpLev OBJECT-TYPE
   SYNTAX      INTEGER
               {
               unchanged (0)
               }
   MAX-ACCESS  read-write
   STATUS      current
   DESCRIPTION
      "Path: pppBundle.editConf.bandwidth.action.cirAction.ethernet.dropLevel

       Possibilities:
               unchanged   (0)"
   ::= {er1645v2PppBFBwEntry 4065001472}

er1645v2PppBFBwActCirActEthDeFlag OBJECT-TYPE
   SYNTAX      INTEGER
               {
               unchanged (255),
               clear (0),
               set (1)
               }
   MAX-ACCESS  read-write
   STATUS      current
   DESCRIPTION
      "Path: pppBundle.editConf.bandwidth.action.cirAction.ethernet.deFlag

       Possibilities:
               unchanged   (255)
               clear   (0)
               set   (1)"
   ::= {er1645v2PppBFBwEntry 4065198080}

er1645v2PppBFBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: pppBundle.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PppBFBwEntry 4071161856}

er1645v2PppBFBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PppBFBwEntry 4071227392}

er1645v2PppBFBwActCirActIpDrpLev OBJECT-TYPE
   SYNTAX      INTEGER
               {
               unchanged (0)
               }
   MAX-ACCESS  read-write
   STATUS      current
   DESCRIPTION
      "Path: pppBundle.editConf.bandwidth.action.cirAction.ip.dropLevel

       Possibilities:
               unchanged   (0)"
   ::= {er1645v2PppBFBwEntry 4071292928}

er1645v2PppBFBwActCirActIpDeFlag OBJECT-TYPE
   SYNTAX      INTEGER
               {
               unchanged (255),
               clear (0),
               set (1)
               }
   MAX-ACCESS  read-write
   STATUS      current
   DESCRIPTION
      "Path: pppBundle.editConf.bandwidth.action.cirAction.ip.deFlag

       Possibilities:
               unchanged   (255)
               clear   (0)
               set   (1)"
   ::= {er1645v2PppBFBwEntry 4071489536}

er1645v2PppBFBwActEirActNone OBJECT-TYPE
   SYNTAX      OCTET STRING
   MAX-ACCESS  read-write
   STATUS      current
   DESCRIPTION
      "Path: pppBundle.editConf.bandwidth.action.eirAction.none"
   ::= {er1645v2PppBFBwEntry 4095737856}

er1645v2PppBFBwActEirActEthCos1 OBJECT-TYPE
   SYNTAX      INTEGER
               {
               unchanged (256)
               }
   MAX-ACCESS  read-write
   STATUS      current
   DESCRIPTION
      "Path: pppBundle.editConf.bandwidth.action.eirAction.ethernet.cosDepth1

       Possibilities:
               unchanged   (256)"
   ::= {er1645v2PppBFBwEntry 4097900544}

er1645v2PppBFBwActEirActEthDei1 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth1

       Possibilities:
               unchanged   (255)
               clear   (0)
               set   (1)"
   ::= {er1645v2PppBFBwEntry 4099211264}

er1645v2PppBFBwActEirActEthCos2 OBJECT-TYPE
   SYNTAX      INTEGER
               {
               unchanged (256)
               }
   MAX-ACCESS  read-write
   STATUS      current
   DESCRIPTION
      "Path: pppBundle.editConf.bandwidth.action.eirAction.ethernet.cosDepth2

       Possibilities:
               unchanged   (256)"
   ::= {er1645v2PppBFBwEntry 4097966080}

er1645v2PppBFBwActEirActEthDei2 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth2

       Possibilities:
               unchanged   (255)
               clear   (0)
               set   (1)"
   ::= {er1645v2PppBFBwEntry 4099276800}

er1645v2PppBFBwActEirActEthCos3 OBJECT-TYPE
   SYNTAX      INTEGER
               {
               unchanged (256)
               }
   MAX-ACCESS  read-write
   STATUS      current
   DESCRIPTION
      "Path: pppBundle.editConf.bandwidth.action.eirAction.ethernet.cosDepth3

       Possibilities:
               unchanged   (256)"
   ::= {er1645v2PppBFBwEntry 4098031616}

er1645v2PppBFBwActEirActEthDei3 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth3

       Possibilities:
               unchanged   (255)
               clear   (0)
               set   (1)"
   ::= {er1645v2PppBFBwEntry 4099342336}

er1645v2PppBFBwActEirActEthCos4 OBJECT-TYPE
   SYNTAX      INTEGER
               {
               unchanged (256)
               }
   MAX-ACCESS  read-write
   STATUS      current
   DESCRIPTION
      "Path: pppBundle.editConf.bandwidth.action.eirAction.ethernet.cosDepth4

       Possibilities:
               unchanged   (256)"
   ::= {er1645v2PppBFBwEntry 4098097152}

er1645v2PppBFBwActEirActEthDei4 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth4

       Possibilities:
               unchanged   (255)
               clear   (0)
               set   (1)"
   ::= {er1645v2PppBFBwEntry 4099407872}

er1645v2PppBFBwActEirActEthCos5 OBJECT-TYPE
   SYNTAX      INTEGER
               {
               unchanged (256)
               }
   MAX-ACCESS  read-write
   STATUS      current
   DESCRIPTION
      "Path: pppBundle.editConf.bandwidth.action.eirAction.ethernet.cosDepth5

       Possibilities:
               unchanged   (256)"
   ::= {er1645v2PppBFBwEntry 4098162688}

er1645v2PppBFBwActEirActEthDei5 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth5

       Possibilities:
               unchanged   (255)
               clear   (0)
               set   (1)"
   ::= {er1645v2PppBFBwEntry 4099473408}

er1645v2PppBFBwActEirActEthCos6 OBJECT-TYPE
   SYNTAX      INTEGER
               {
               unchanged (256)
               }
   MAX-ACCESS  read-write
   STATUS      current
   DESCRIPTION
      "Path: pppBundle.editConf.bandwidth.action.eirAction.ethernet.cosDepth6

       Possibilities:
               unchanged   (256)"
   ::= {er1645v2PppBFBwEntry 4098228224}

er1645v2PppBFBwActEirActEthDei6 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth6

       Possibilities:
               unchanged   (255)
               clear   (0)
               set   (1)"
   ::= {er1645v2PppBFBwEntry 4099538944}

er1645v2PppBFBwActEirActEthCos7 OBJECT-TYPE
   SYNTAX      INTEGER
               {
               unchanged (256)
               }
   MAX-ACCESS  read-write
   STATUS      current
   DESCRIPTION
      "Path: pppBundle.editConf.bandwidth.action.eirAction.ethernet.cosDepth7

       Possibilities:
               unchanged   (256)"
   ::= {er1645v2PppBFBwEntry 4098293760}

er1645v2PppBFBwActEirActEthDei7 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth7

       Possibilities:
               unchanged   (255)
               clear   (0)
               set   (1)"
   ::= {er1645v2PppBFBwEntry 4099604480}

er1645v2PppBFBwActEirActEthCos8 OBJECT-TYPE
   SYNTAX      INTEGER
               {
               unchanged (256)
               }
   MAX-ACCESS  read-write
   STATUS      current
   DESCRIPTION
      "Path: pppBundle.editConf.bandwidth.action.eirAction.ethernet.cosDepth8

       Possibilities:
               unchanged   (256)"
   ::= {er1645v2PppBFBwEntry 4098359296}

er1645v2PppBFBwActEirActEthDei8 OBJECT-TYPE
   SYNTAX      INTEGER
               {
               unchanged (255),
               clear (0),
               set (1)
               }
   MAX-ACCESS  read-write
   STATUS      current
   DESCRIPTION
      "Path: pppBundle.editConf.bandwidth.action.eirAction.ethernet.deiDepth8

       Possibilities:
               unchanged   (255)
               clear   (0)
               set   (1)"
   ::= {er1645v2PppBFBwEntry 4099670016}

er1645v2PppBFBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: pppBundle.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PppBFBwEntry 4098424832}

er1645v2PppBFBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PppBFBwEntry 4098490368}

er1645v2PppBFBwActEirActEthDrpLev OBJECT-TYPE
   SYNTAX      INTEGER
               {
               unchanged (0)
               }
   MAX-ACCESS  read-write
   STATUS      current
   DESCRIPTION
      "Path: pppBundle.editConf.bandwidth.action.eirAction.ethernet.dropLevel

       Possibilities:
               unchanged   (0)"
   ::= {er1645v2PppBFBwEntry 4098555904}

er1645v2PppBFBwActEirActEthDeFlag OBJECT-TYPE
   SYNTAX      INTEGER
               {
               unchanged (255),
               clear (0),
               set (1)
               }
   MAX-ACCESS  read-write
   STATUS      current
   DESCRIPTION
      "Path: pppBundle.editConf.bandwidth.action.eirAction.ethernet.deFlag

       Possibilities:
               unchanged   (255)
               clear   (0)
               set   (1)"
   ::= {er1645v2PppBFBwEntry 4098752512}

er1645v2PppBFBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: pppBundle.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PppBFBwEntry 4104716288}

er1645v2PppBFBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PppBFBwEntry 4104781824}

er1645v2PppBFBwActEirActIpDrpLev OBJECT-TYPE
   SYNTAX      INTEGER
               {
               unchanged (0)
               }
   MAX-ACCESS  read-write
   STATUS      current
   DESCRIPTION
      "Path: pppBundle.editConf.bandwidth.action.eirAction.ip.dropLevel

       Possibilities:
               unchanged   (0)"
   ::= {er1645v2PppBFBwEntry 4104847360}

er1645v2PppBFBwActEirActIpDeFlag OBJECT-TYPE
   SYNTAX      INTEGER
               {
               unchanged (255),
               clear (0),
               set (1)
               }
   MAX-ACCESS  read-write
   STATUS      current
   DESCRIPTION
      "Path: pppBundle.editConf.bandwidth.action.eirAction.ip.deFlag

       Possibilities:
               unchanged   (255)
               clear   (0)
               set   (1)"
   ::= {er1645v2PppBFBwEntry 4105043968}

er1645v2PppBFBwActViolActNone OBJECT-TYPE
   SYNTAX      OCTET STRING
   MAX-ACCESS  read-write
   STATUS      current
   DESCRIPTION
      "Path: pppBundle.editConf.bandwidth.action.violateAction.none"
   ::= {er1645v2PppBFBwEntry 4129292288}

er1645v2PppBFBwActViolActDrop OBJECT-TYPE
   SYNTAX      OCTET STRING
   MAX-ACCESS  read-write
   STATUS      current
   DESCRIPTION
      "Path: pppBundle.editConf.bandwidth.action.violateAction.drop"
   ::= {er1645v2PppBFBwEntry 4133486592}

er1645v2PppBFBwActViolActEthCos1 OBJECT-TYPE
   SYNTAX      INTEGER
               {
               unchanged (256)
               }
   MAX-ACCESS  read-write
   STATUS      current
   DESCRIPTION
      "Path: pppBundle.editConf.bandwidth.action.violateAction.ethernet.cosDepth1

       Possibilities:
               unchanged   (256)"
   ::= {er1645v2PppBFBwEntry 4131454976}

er1645v2PppBFBwActViolActEthDei1 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth1

       Possibilities:
               unchanged   (255)
               clear   (0)
               set   (1)"
   ::= {er1645v2PppBFBwEntry 4132765696}

er1645v2PppBFBwActViolActEthCos2 OBJECT-TYPE
   SYNTAX      INTEGER
               {
               unchanged (256)
               }
   MAX-ACCESS  read-write
   STATUS      current
   DESCRIPTION
      "Path: pppBundle.editConf.bandwidth.action.violateAction.ethernet.cosDepth2

       Possibilities:
               unchanged   (256)"
   ::= {er1645v2PppBFBwEntry 4131520512}

er1645v2PppBFBwActViolActEthDei2 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth2

       Possibilities:
               unchanged   (255)
               clear   (0)
               set   (1)"
   ::= {er1645v2PppBFBwEntry 4132831232}

er1645v2PppBFBwActViolActEthCos3 OBJECT-TYPE
   SYNTAX      INTEGER
               {
               unchanged (256)
               }
   MAX-ACCESS  read-write
   STATUS      current
   DESCRIPTION
      "Path: pppBundle.editConf.bandwidth.action.violateAction.ethernet.cosDepth3

       Possibilities:
               unchanged   (256)"
   ::= {er1645v2PppBFBwEntry 4131586048}

er1645v2PppBFBwActViolActEthDei3 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth3

       Possibilities:
               unchanged   (255)
               clear   (0)
               set   (1)"
   ::= {er1645v2PppBFBwEntry 4132896768}

er1645v2PppBFBwActViolActEthCos4 OBJECT-TYPE
   SYNTAX      INTEGER
               {
               unchanged (256)
               }
   MAX-ACCESS  read-write
   STATUS      current
   DESCRIPTION
      "Path: pppBundle.editConf.bandwidth.action.violateAction.ethernet.cosDepth4

       Possibilities:
               unchanged   (256)"
   ::= {er1645v2PppBFBwEntry 4131651584}

er1645v2PppBFBwActViolActEthDei4 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth4

       Possibilities:
               unchanged   (255)
               clear   (0)
               set   (1)"
   ::= {er1645v2PppBFBwEntry 4132962304}

er1645v2PppBFBwActViolActEthCos5 OBJECT-TYPE
   SYNTAX      INTEGER
               {
               unchanged (256)
               }
   MAX-ACCESS  read-write
   STATUS      current
   DESCRIPTION
      "Path: pppBundle.editConf.bandwidth.action.violateAction.ethernet.cosDepth5

       Possibilities:
               unchanged   (256)"
   ::= {er1645v2PppBFBwEntry 4131717120}

er1645v2PppBFBwActViolActEthDei5 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth5

       Possibilities:
               unchanged   (255)
               clear   (0)
               set   (1)"
   ::= {er1645v2PppBFBwEntry 4133027840}

er1645v2PppBFBwActViolActEthCos6 OBJECT-TYPE
   SYNTAX      INTEGER
               {
               unchanged (256)
               }
   MAX-ACCESS  read-write
   STATUS      current
   DESCRIPTION
      "Path: pppBundle.editConf.bandwidth.action.violateAction.ethernet.cosDepth6

       Possibilities:
               unchanged   (256)"
   ::= {er1645v2PppBFBwEntry 4131782656}

er1645v2PppBFBwActViolActEthDei6 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth6

       Possibilities:
               unchanged   (255)
               clear   (0)
               set   (1)"
   ::= {er1645v2PppBFBwEntry 4133093376}

er1645v2PppBFBwActViolActEthCos7 OBJECT-TYPE
   SYNTAX      INTEGER
               {
               unchanged (256)
               }
   MAX-ACCESS  read-write
   STATUS      current
   DESCRIPTION
      "Path: pppBundle.editConf.bandwidth.action.violateAction.ethernet.cosDepth7

       Possibilities:
               unchanged   (256)"
   ::= {er1645v2PppBFBwEntry 4131848192}

er1645v2PppBFBwActViolActEthDei7 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth7

       Possibilities:
               unchanged   (255)
               clear   (0)
               set   (1)"
   ::= {er1645v2PppBFBwEntry 4133158912}

er1645v2PppBFBwActViolActEthCos8 OBJECT-TYPE
   SYNTAX      INTEGER
               {
               unchanged (256)
               }
   MAX-ACCESS  read-write
   STATUS      current
   DESCRIPTION
      "Path: pppBundle.editConf.bandwidth.action.violateAction.ethernet.cosDepth8

       Possibilities:
               unchanged   (256)"
   ::= {er1645v2PppBFBwEntry 4131913728}

er1645v2PppBFBwActViolActEthDei8 OBJECT-TYPE
   SYNTAX      INTEGER
               {
               unchanged (255),
               clear (0),
               set (1)
               }
   MAX-ACCESS  read-write
   STATUS      current
   DESCRIPTION
      "Path: pppBundle.editConf.bandwidth.action.violateAction.ethernet.deiDepth8

       Possibilities:
               unchanged   (255)
               clear   (0)
               set   (1)"
   ::= {er1645v2PppBFBwEntry 4133224448}

er1645v2PppBFBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: pppBundle.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PppBFBwEntry 4131979264}

er1645v2PppBFBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2PppBFBwEntry 4132044800}

er1645v2PppBFBwActViolActEthDrpLev OBJECT-TYPE
   SYNTAX      INTEGER
               {
               unchanged (0)
               }
   MAX-ACCESS  read-write
   STATUS      current
   DESCRIPTION
      "Path: pppBundle.editConf.bandwidth.action.violateAction.ethernet.dropLevel

       Possibilities:
               unchanged   (0)"
   ::= {er1645v2PppBFBwEntry 4132110336}

er1645v2PppBFBwActViolActEthDeFlag OBJECT-TYPE
   SYNTAX      INTEGER
               {
               unchanged (255),
               clear (0),
               set (1)
               }
   MAX-ACCESS  read-write
   STATUS      current
   DESCRIPTION
      "Path: pppBundle.editConf.bandwidth.action.violateAction.ethernet.deFlag

       Possibilities:
               unchanged   (255)
               clear   (0)
               set   (1)"
   ::= {er1645v2PppBFBwEntry 4132306944}

er1645v2PppBFBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: pppBundle.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2PppBFBwEntry 4138270720}

er1645v2PppBFBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2PppBFBwEntry 4138336256}

er1645v2PppBFBwActViolActIpDrpLev OBJECT-TYPE
   SYNTAX      INTEGER
               {
               unchanged (0)
               }
   MAX-ACCESS  read-write
   STATUS      current
   DESCRIPTION
      "Path: pppBundle.editConf.bandwidth.action.violateAction.ip.dropLevel

       Possibilities:
               unchanged   (0)"
   ::= {er1645v2PppBFBwEntry 4138401792}

er1645v2PppBFBwActViolActIpDeFlag OBJECT-TYPE
   SYNTAX      INTEGER
               {
               unchanged (255),
               clear (0),
               set (1)
               }
   MAX-ACCESS  read-write
   STATUS      current
   DESCRIPTION
      "Path: pppBundle.editConf.bandwidth.action.violateAction.ip.deFlag

       Possibilities:
               unchanged   (255)
               clear   (0)
               set   (1)"
   ::= {er1645v2PppBFBwEntry 4138598400}


er1645v2PppBFIbw OBJECT IDENTIFIER ::= {er1645v2PppBF 13}

er1645v2PppBFIbwSSCTable OBJECT-TYPE
   SYNTAX      SEQUENCE OF Er1645v2PppBFIbwEntry
   MAX-ACCESS  not-accessible
   STATUS      current
   DESCRIPTION
      ""
   ::= {er1645v2PppBFIbw 1}

er1645v2PppBFIbwEntry OBJECT-TYPE
   SYNTAX      Er1645v2PppBFIbwEntry
   MAX-ACCESS  not-accessible
   STATUS      current
   DESCRIPTION
      ""
   INDEX      { er1645v2PppBFIbwGlobalIx }
   ::= {er1645v2PppBFIbwSSCTable 1}

Er1645v2PppBFIbwEntry ::=
   SEQUENCE
      {
      er1645v2PppBFIbwGlobalIx
         GlobalIndex,
      er1645v2PppBFIbwCir
         Integer32,
      er1645v2PppBFIbwTc
         INTEGER,
      er1645v2PppBFIbwCorrType
         INTEGER,
      er1645v2PppBFIbwCorrPredefEncapsFrameRelay
         DisplayString,
      er1645v2PppBFIbwCorrPredefEncapsPpp
         DisplayString,
      er1645v2PppBFIbwCorrPredefEncapsAtmHl
         INTEGER,
      er1645v2PppBFIbwCorrPredefEncapsAtmMp
         INTEGER,
      er1645v2PppBFIbwCorrPredefEncapsHdlc
         DisplayString,
      er1645v2PppBFIbwCorrPredefEncapsEfmFs
         Integer32,
      er1645v2PppBFIbwCorrPredefEncapsEfmIb
         Integer32,
      er1645v2PppBFIbwCorrPredefMode
         INTEGER,
      er1645v2PppBFIbwCorrManualOverhead
         Integer32,
      er1645v2PppBFIbwCorrManualFrameData
         Counter32,
      er1645v2PppBFIbwCorrManualFrameHeader
         Counter32,
      er1645v2PppBFIbwMaxFifoQLen
         Integer32,
      er1645v2PppBFIbwPriorityPolicy
         DisplayString
      }

er1645v2PppBFIbwGlobalIx OBJECT-TYPE
   SYNTAX      GlobalIndex
   MAX-ACCESS  not-accessible
   STATUS      current
   DESCRIPTION
      "The value of the tlsCntTreeGlobalIndex of the MANAGED OBJECT."
   ::= {er1645v2PppBFIbwEntry 10}

er1645v2PppBFIbwCir OBJECT-TYPE
   SYNTAX      Integer32
   MAX-ACCESS  read-write
   STATUS      current
   DESCRIPTION
      "Path: pppBundle.editConf.inboundBandwidth.cir"
   ::= {er1645v2PppBFIbwEntry 16777216}

er1645v2PppBFIbwTc OBJECT-TYPE
   SYNTAX      INTEGER
               {
               auto (0)
               }
   MAX-ACCESS  read-write
   STATUS      current
   DESCRIPTION
      "Path: pppBundle.editConf.inboundBandwidth.tc

       Possibilities:
               auto   (0)"
   ::= {er1645v2PppBFIbwEntry 100663296}

er1645v2PppBFIbwCorrType OBJECT-TYPE
   SYNTAX      INTEGER
               {
               noCorrection (0),
               predefined (1),
               manual (2)
               }
   MAX-ACCESS  read-write
   STATUS      current
   DESCRIPTION
      "Path: pppBundle.editConf.inboundBandwidth.correction.type

       Possibilities:
               noCorrection   (0)
               predefined   (1)
               manual   (2)"
   ::= {er1645v2PppBFIbwEntry 35651584}

er1645v2PppBFIbwCorrPredefEncapsFrameRelay OBJECT-TYPE
   SYNTAX      DisplayString
   MAX-ACCESS  read-write
   STATUS      current
   DESCRIPTION
      "Path: pppBundle.editConf.inboundBandwidth.correction.predefined.encapsulation.frameRelay"
   ::= {er1645v2PppBFIbwEntry 38027264}

er1645v2PppBFIbwCorrPredefEncapsPpp OBJECT-TYPE
   SYNTAX      DisplayString
   MAX-ACCESS  read-write
   STATUS      current
   DESCRIPTION
      "Path: pppBundle.editConf.inboundBandwidth.correction.predefined.encapsulation.ppp"
   ::= {er1645v2PppBFIbwEntry 38043648}

er1645v2PppBFIbwCorrPredefEncapsAtmHl OBJECT-TYPE
   SYNTAX      INTEGER
               {
               rfc2684 (0),
               ppp (1),
               pppOverEthernet (2)
               }
   MAX-ACCESS  read-write
   STATUS      current
   DESCRIPTION
      "Path: pppBundle.editConf.inboundBandwidth.correction.predefined.encapsulation.atm.higherLayer

       Possibilities:
               rfc2684   (0)
               ppp   (1)
               pppOverEthernet   (2)"
   ::= {er1645v2PppBFIbwEntry 38062080}

er1645v2PppBFIbwCorrPredefEncapsAtmMp OBJECT-TYPE
   SYNTAX      INTEGER
               {
               llcEncapsulation (0),
               vcMultiplexing (1)
               }
   MAX-ACCESS  read-write
   STATUS      current
   DESCRIPTION
      "Path: pppBundle.editConf.inboundBandwidth.correction.predefined.encapsulation.atm.multiProtocol

       Possibilities:
               llcEncapsulation   (0)
               vcMultiplexing   (1)"
   ::= {er1645v2PppBFIbwEntry 38064128}

er1645v2PppBFIbwCorrPredefEncapsHdlc OBJECT-TYPE
   SYNTAX      DisplayString
   MAX-ACCESS  read-write
   STATUS      current
   DESCRIPTION
      "Path: pppBundle.editConf.inboundBandwidth.correction.predefined.encapsulation.hdlc"
   ::= {er1645v2PppBFIbwEntry 38076416}

er1645v2PppBFIbwCorrPredefEncapsEfmFs OBJECT-TYPE
   SYNTAX      Integer32
   MAX-ACCESS  read-write
   STATUS      current
   DESCRIPTION
      "Path: pppBundle.editConf.inboundBandwidth.correction.predefined.encapsulation.efm.fragmentSize"
   ::= {er1645v2PppBFIbwEntry 38094848}

er1645v2PppBFIbwCorrPredefEncapsEfmIb OBJECT-TYPE
   SYNTAX      Integer32
   MAX-ACCESS  read-write
   STATUS      current
   DESCRIPTION
      "Path: pppBundle.editConf.inboundBandwidth.correction.predefined.encapsulation.efm.idleBytes"
   ::= {er1645v2PppBFIbwEntry 38096896}

er1645v2PppBFIbwCorrPredefMode OBJECT-TYPE
   SYNTAX      INTEGER
               {
               routing (0),
               bridging (1)
               }
   MAX-ACCESS  read-write
   STATUS      current
   DESCRIPTION
      "Path: pppBundle.editConf.inboundBandwidth.correction.predefined.mode

       Possibilities:
               routing   (0)
               bridging   (1)"
   ::= {er1645v2PppBFIbwEntry 38273024}

er1645v2PppBFIbwCorrManualOverhead OBJECT-TYPE
   SYNTAX      Integer32
   MAX-ACCESS  read-write
   STATUS      current
   DESCRIPTION
      "Path: pppBundle.editConf.inboundBandwidth.correction.manual.overhead"
   ::= {er1645v2PppBFIbwEntry 39854080}

er1645v2PppBFIbwCorrManualFrameData OBJECT-TYPE
   SYNTAX      Counter32
   MAX-ACCESS  read-write
   STATUS      current
   DESCRIPTION
      "Path: pppBundle.editConf.inboundBandwidth.correction.manual.frameData

       32 bit unsigned wrappable counter."
   ::= {er1645v2PppBFIbwEntry 39862272}

er1645v2PppBFIbwCorrManualFrameHeader OBJECT-TYPE
   SYNTAX      Counter32
   MAX-ACCESS  read-write
   STATUS      current
   DESCRIPTION
      "Path: pppBundle.editConf.inboundBandwidth.correction.manual.frameHeader

       32 bit unsigned wrappable counter."
   ::= {er1645v2PppBFIbwEntry 39870464}

er1645v2PppBFIbwMaxFifoQLen OBJECT-TYPE
   SYNTAX      Integer32
   MAX-ACCESS  read-write
   STATUS      current
   DESCRIPTION
      "Path: pppBundle.editConf.inboundBandwidth.maxFifoQLen"
   ::= {er1645v2PppBFIbwEntry 50331648}

er1645v2PppBFIbwPriorityPolicy OBJECT-TYPE
   SYNTAX      DisplayString
   MAX-ACCESS  read-write
   STATUS      current
   DESCRIPTION
      "Path: pppBundle.editConf.inboundBandwidth.priorityPolicy"
   ::= {er1645v2PppBFIbwEntry 67108864}


er1645v2PppBFAlarmMask OBJECT IDENTIFIER ::= {er1645v2PppBF 135}

er1645v2PppBFAlarmMaskTable OBJECT-TYPE
   SYNTAX      SEQUENCE OF Er1645v2PppBFAlarmMaskEntry
   MAX-ACCESS  not-accessible
   STATUS      current
   DESCRIPTION
      "ifAlarmMask"
   ::= {er1645v2PppBFAlarmMask 1}

er1645v2PppBFAlarmMaskEntry OBJECT-TYPE
   SYNTAX      Er1645v2PppBFAlarmMaskEntry
   MAX-ACCESS  not-accessible
   STATUS      current
   DESCRIPTION
      ""
   INDEX      { er1645v2PppBFAlarmMaskGlobalIx }
   ::= {er1645v2PppBFAlarmMaskTable 1}

Er1645v2PppBFAlarmMaskEntry ::=
   SEQUENCE
      {
      er1645v2PppBFAlarmMaskGlobalIx
         GlobalIndex,
      er1645v2PppBFAlarmMaskValue
         Integer32
      }

er1645v2PppBFAlarmMaskGlobalIx OBJECT-TYPE
   SYNTAX      GlobalIndex
   MAX-ACCESS  not-accessible
   STATUS      current
   DESCRIPTION
      "The value of the tlsCntTreeGlobalIndex of the MANAGED OBJECT."
   ::= {er1645v2PppBFAlarmMaskEntry 10}

er1645v2PppBFAlarmMaskValue OBJECT-TYPE
   SYNTAX      Integer32
   MAX-ACCESS  read-write
   STATUS      current
   DESCRIPTION
      "Path: pppBundle.editConf.alarmMask

       Bit meanings:
               bit 0 = linkDown"
   ::= {er1645v2PppBFAlarmMaskEntry 2147483648}


er1645v2PppBFAlarmLev OBJECT IDENTIFIER ::= {er1645v2PppBF 170}

er1645v2PppBFAlarmLevSSCTable OBJECT-TYPE
   SYNTAX      SEQUENCE OF Er1645v2PppBFAlarmLevEntry
   MAX-ACCESS  not-accessible
   STATUS      current
   DESCRIPTION
      "IfAlarmLevels"
   ::= {er1645v2PppBFAlarmLev 1}

er1645v2PppBFAlarmLevEntry OBJECT-TYPE
   SYNTAX      Er1645v2PppBFAlarmLevEntry
   MAX-ACCESS  not-accessible
   STATUS      current
   DESCRIPTION
      ""
   INDEX      { er1645v2PppBFAlarmLevGlobalIx }
   ::= {er1645v2PppBFAlarmLevSSCTable 1}

Er1645v2PppBFAlarmLevEntry ::=
   SEQUENCE
      {
      er1645v2PppBFAlarmLevGlobalIx
         GlobalIndex,
      er1645v2PppBFAlarmLevLinkDown
         Integer32
      }

er1645v2PppBFAlarmLevGlobalIx OBJECT-TYPE
   SYNTAX      GlobalIndex
   MAX-ACCESS  not-accessible
   STATUS      current
   DESCRIPTION
      "The value of the tlsCntTreeGlobalIndex of the MANAGED OBJECT."
   ::= {er1645v2PppBFAlarmLevEntry 10}

er1645v2PppBFAlarmLevLinkDown OBJECT-TYPE
   SYNTAX      Integer32
   MAX-ACCESS  read-write
   STATUS      current
   DESCRIPTION
      "Path: pppBundle.editConf.alarmLevel.linkDown"
   ::= {er1645v2PppBFAlarmLevEntry 16777216}


er1645v2PppBFIp OBJECT IDENTIFIER ::= {er1645v2PppBF 1}

er1645v2PppBFIpSSCTable OBJECT-TYPE
   SYNTAX      SEQUENCE OF Er1645v2PppBFIpEntry
   MAX-ACCESS  not-accessible
   STATUS      current
   DESCRIPTION
      "ip interface config parameters"
   ::= {er1645v2PppBFIp 1}

er1645v2PppBFIpEntry OBJECT-TYPE
   SYNTAX      Er1645v2PppBFIpEntry
   MAX-ACCESS  not-accessible
   STATUS      current
   DESCRIPTION
      ""
   INDEX      { er1645v2PppBFIpGlobalIx }
   ::= {er1645v2PppBFIpSSCTable 1}

Er1645v2PppBFIpEntry ::=
   SEQUENCE
      {
      er1645v2PppBFIpGlobalIx
         GlobalIndex,
      er1645v2PppBFIpVrfRouter
         DisplayString,
      er1645v2PppBFIpAdr
         IpAddress,
      er1645v2PppBFIpNetm
         IpAddress,
      er1645v2PppBFIpSNetName
         INTEGER,
      er1645v2PppBFIpSNetCust
         DisplayString,
      er1645v2PppBFIpRem
         IpAddress,
      er1645v2PppBFIpUnnumbered
         DisplayString,
      er1645v2PppBFIpAcceptLocAddr
         INTEGER,
      er1645v2PppBFIpAcceptRemAddr
         INTEGER,
      er1645v2PppBFIpGatewayPref
         Integer32,
      er1645v2PppBFIpRsn
         INTEGER,
      er1645v2PppBFIpMtu
         Integer32,
      er1645v2PppBFIpMssAdjust
         INTEGER,
      er1645v2PppBFIpRipMetric
         Integer32,
      er1645v2PppBFIpRipMetricOut
         Integer32,
      er1645v2PppBFIpRipMode
         INTEGER,
      er1645v2PppBFIpRipTxVer
         INTEGER,
      er1645v2PppBFIpRipRxVer
         INTEGER,
      er1645v2PppBFIpRipSplitH
         INTEGER,
      er1645v2PppBFIpRipAuth
         INTEGER,
      er1645v2PppBFIpRipFilter
         DisplayString,
      er1645v2PppBFIpRipFilterIn
         DisplayString,
      er1645v2PppBFIpRipClearNextHop
         INTEGER,
      er1645v2PppBFIpAccPol
         DisplayString,
      er1645v2PppBFIpAB
         DisplayString,
      er1645v2PppBFIpMA
         INTEGER,
      er1645v2PppBFIpMF
         Integer32,
      er1645v2PppBFIpDB
         INTEGER,
      er1645v2PppBFIpIR
         INTEGER,
      er1645v2PppBFIpIgmp
         INTEGER,
      er1645v2PppBFIpNN
         DisplayString,
      er1645v2PppBFIpPimMode
         INTEGER,
      er1645v2PppBFIpPimDrPriority
         Counter32,
      er1645v2PppBFIpPimHelloTime
         TimeTicks,
      er1645v2PppBFIpPimPropagationDelay
         TimeTicks,
      er1645v2PppBFIpPimOverrideInterval
         TimeTicks,
      er1645v2PppBFIpPimBsrBorder
         INTEGER,
      er1645v2PppBFIpPimTtlThreshold
         Integer32,
      er1645v2PppBFIpIMNetworkUnreachable
         INTEGER,
      er1645v2PppBFIpIMHostUnreachable
         INTEGER,
      er1645v2PppBFIpIMProtocolUnreachable
         INTEGER,
      er1645v2PppBFIpIMPortUnreachable
         INTEGER,
      er1645v2PppBFIpIMMtuExceeded
         INTEGER,
      er1645v2PppBFIpIMAdminProhibited
         INTEGER,
      er1645v2PppBFIpIMTtlExceeded
         INTEGER,
      er1645v2PppBFIpIMRedirect
         INTEGER
      }

er1645v2PppBFIpGlobalIx OBJECT-TYPE
   SYNTAX      GlobalIndex
   MAX-ACCESS  not-accessible
   STATUS      current
   DESCRIPTION
      "The value of the tlsCntTreeGlobalIndex of the MANAGED OBJECT."
   ::= {er1645v2PppBFIpEntry 10}

er1645v2PppBFIpVrfRouter OBJECT-TYPE
   SYNTAX      DisplayString
   MAX-ACCESS  read-write
   STATUS      current
   DESCRIPTION
      "Path: pppBundle.editConf.ip.vrfRouter"
   ::= {er1645v2PppBFIpEntry 738197504}

er1645v2PppBFIpAdr OBJECT-TYPE
   SYNTAX      IpAddress
   MAX-ACCESS  read-write
   STATUS      current
   DESCRIPTION
      "Path: pppBundle.editConf.ip.address"
   ::= {er1645v2PppBFIpEntry 2030043136}

er1645v2PppBFIpNetm OBJECT-TYPE
   SYNTAX      IpAddress
   MAX-ACCESS  read-write
   STATUS      current
   DESCRIPTION
      "Path: pppBundle.editConf.ip.netMask"
   ::= {er1645v2PppBFIpEntry 2063597568}

er1645v2PppBFIpSNetName OBJECT-TYPE
   SYNTAX      INTEGER
               {
               slOPTg (0),
               corp (2),
               dmz (3),
               internet (1)
               }
   MAX-ACCESS  read-write
   STATUS      current
   DESCRIPTION
      "Path: pppBundle.editConf.ip.sNet.name

       Possibilities:
               <OPT>   (0)
               corp   (2)
               dmz   (3)
               internet   (1)"
   ::= {er1645v2PppBFIpEntry 855703552}

er1645v2PppBFIpSNetCust OBJECT-TYPE
   SYNTAX      DisplayString
   MAX-ACCESS  read-write
   STATUS      current
   DESCRIPTION
      "Path: pppBundle.editConf.ip.sNet.custom"
   ::= {er1645v2PppBFIpEntry 855769088}

er1645v2PppBFIpRem OBJECT-TYPE
   SYNTAX      IpAddress
   MAX-ACCESS  read-write
   STATUS      current
   DESCRIPTION
      "Path: pppBundle.editConf.ip.remote"
   ::= {er1645v2PppBFIpEntry 2080374784}

er1645v2PppBFIpUnnumbered OBJECT-TYPE
   SYNTAX      DisplayString
   MAX-ACCESS  read-write
   STATUS      current
   DESCRIPTION
      "Path: pppBundle.editConf.ip.unnumbered"
   ::= {er1645v2PppBFIpEntry 587202560}

er1645v2PppBFIpAcceptLocAddr OBJECT-TYPE
   SYNTAX      INTEGER
               {
               disabled (0),
               enabled (1)
               }
   MAX-ACCESS  read-write
   STATUS      current
   DESCRIPTION
      "Path: pppBundle.editConf.ip.acceptLocAddr

       Possibilities:
               disabled   (0)
               enabled   (1)"
   ::= {er1645v2PppBFIpEntry 67108864}

er1645v2PppBFIpAcceptRemAddr OBJECT-TYPE
   SYNTAX      INTEGER
               {
               disabled (0),
               enabled (1)
               }
   MAX-ACCESS  read-write
   STATUS      current
   DESCRIPTION
      "Path: pppBundle.editConf.ip.acceptRemAddr

       Possibilities:
               disabled   (0)
               enabled   (1)"
   ::= {er1645v2PppBFIpEntry 100663296}

er1645v2PppBFIpGatewayPref OBJECT-TYPE
   SYNTAX      Integer32
   MAX-ACCESS  read-write
   STATUS      current
   DESCRIPTION
      "Path: pppBundle.editConf.ip.gatewayPreference"
   ::= {er1645v2PppBFIpEntry 603979776}

er1645v2PppBFIpRsn OBJECT-TYPE
   SYNTAX      INTEGER
               {
               disabled (0),
               enabled (1)
               }
   MAX-ACCESS  read-write
   STATUS      current
   DESCRIPTION
      "Path: pppBundle.editConf.ip.requestSubnet

       Possibilities:
               disabled   (0)
               enabled   (1)"
   ::= {er1645v2PppBFIpEntry 1627389952}

er1645v2PppBFIpMtu OBJECT-TYPE
   SYNTAX      Integer32
   MAX-ACCESS  read-write
   STATUS      current
   DESCRIPTION
      "Path: pppBundle.editConf.ip.mtu"
   ::= {er1645v2PppBFIpEntry 671088640}

er1645v2PppBFIpMssAdjust OBJECT-TYPE
   SYNTAX      INTEGER
               {
               disabled (0),
               auto (65536)
               }
   MAX-ACCESS  read-write
   STATUS      current
   DESCRIPTION
      "Path: pppBundle.editConf.ip.mssAdjust

       Possibilities:
               disabled   (0)
               auto   (65536)"
   ::= {er1645v2PppBFIpEntry 754974720}

er1645v2PppBFIpRipMetric OBJECT-TYPE
   SYNTAX      Integer32
   MAX-ACCESS  read-write
   STATUS      current
   DESCRIPTION
      "Path: pppBundle.editConf.ip.rip.metric"
   ::= {er1645v2PppBFIpEntry 353566720}

er1645v2PppBFIpRipMetricOut OBJECT-TYPE
   SYNTAX      Integer32
   MAX-ACCESS  read-write
   STATUS      current
   DESCRIPTION
      "Path: pppBundle.editConf.ip.rip.metricOut"
   ::= {er1645v2PppBFIpEntry 353632256}

er1645v2PppBFIpRipMode OBJECT-TYPE
   SYNTAX      INTEGER
               {
               disabled (0),
               passive (1),
               active (2)
               }
   MAX-ACCESS  read-write
   STATUS      current
   DESCRIPTION
      "Path: pppBundle.editConf.ip.rip.mode

       Possibilities:
               disabled   (0)
               passive   (1)
               active   (2)"
   ::= {er1645v2PppBFIpEntry 353697792}

er1645v2PppBFIpRipTxVer OBJECT-TYPE
   SYNTAX      INTEGER
               {
               rip1 (0),
               rip2 (1),
               rip1mcompatible (2)
               }
   MAX-ACCESS  read-write
   STATUS      current
   DESCRIPTION
      "Path: pppBundle.editConf.ip.rip.txVersion

       Possibilities:
               rip1   (0)
               rip2   (1)
               rip1-compatible   (2)"
   ::= {er1645v2PppBFIpEntry 354615296}

er1645v2PppBFIpRipRxVer OBJECT-TYPE
   SYNTAX      INTEGER
               {
               rip1only (0),
               rip2only (1),
               rip12 (2)
               }
   MAX-ACCESS  read-write
   STATUS      current
   DESCRIPTION
      "Path: pppBundle.editConf.ip.rip.rxVersion

       Possibilities:
               rip1only   (0)
               rip2only   (1)
               rip1&2   (2)"
   ::= {er1645v2PppBFIpEntry 354680832}

er1645v2PppBFIpRipSplitH OBJECT-TYPE
   SYNTAX      INTEGER
               {
               disabled (0),
               enabled (1),
               poisonedReverse (2)
               }
   MAX-ACCESS  read-write
   STATUS      current
   DESCRIPTION
      "Path: pppBundle.editConf.ip.rip.splitHorizon

       Possibilities:
               disabled   (0)
               enabled   (1)
               poisonedReverse   (2)"
   ::= {er1645v2PppBFIpEntry 353828864}

er1645v2PppBFIpRipAuth OBJECT-TYPE
   SYNTAX      INTEGER
               {
               disabled (0),
               texts (1),
               md5 (2)
               }
   MAX-ACCESS  read-write
   STATUS      current
   DESCRIPTION
      "Path: pppBundle.editConf.ip.rip.authentication

       Possibilities:
               disabled   (0)
               text    (1)
               md5   (2)"
   ::= {er1645v2PppBFIpEntry 353501184}

er1645v2PppBFIpRipFilter OBJECT-TYPE
   SYNTAX      DisplayString
   MAX-ACCESS  read-write
   STATUS      current
   DESCRIPTION
      "Path: pppBundle.editConf.ip.rip.filter"
   ::= {er1645v2PppBFIpEntry 354418688}

er1645v2PppBFIpRipFilterIn OBJECT-TYPE
   SYNTAX      DisplayString
   MAX-ACCESS  read-write
   STATUS      current
   DESCRIPTION
      "Path: pppBundle.editConf.ip.rip.filterIn"
   ::= {er1645v2PppBFIpEntry 354484224}

er1645v2PppBFIpRipClearNextHop OBJECT-TYPE
   SYNTAX      INTEGER
               {
               disabled (0),
               enabled (1)
               }
   MAX-ACCESS  read-write
   STATUS      current
   DESCRIPTION
      "Path: pppBundle.editConf.ip.rip.clearNextHop

       Possibilities:
               disabled   (0)
               enabled   (1)"
   ::= {er1645v2PppBFIpEntry 352452608}

er1645v2PppBFIpAccPol OBJECT-TYPE
   SYNTAX      DisplayString
   MAX-ACCESS  read-write
   STATUS      current
   DESCRIPTION
      "Path: pppBundle.editConf.ip.accessPolicy"
   ::= {er1645v2PppBFIpEntry 704643072}

er1645v2PppBFIpAB OBJECT-TYPE
   SYNTAX      DisplayString
   MAX-ACCESS  read-write
   STATUS      current
   DESCRIPTION
      "Path: pppBundle.editConf.ip.trafficPolicy"
   ::= {er1645v2PppBFIpEntry 234881024}

er1645v2PppBFIpMA OBJECT-TYPE
   SYNTAX      INTEGER
               {
               disabled (0),
               enabled (1)
               }
   MAX-ACCESS  read-write
   STATUS      current
   DESCRIPTION
      "Path: pppBundle.editConf.ip.mgmtAccess

       Possibilities:
               disabled   (0)
               enabled   (1)"
   ::= {er1645v2PppBFIpEntry 268435456}

er1645v2PppBFIpMF OBJECT-TYPE
   SYNTAX      Integer32
   MAX-ACCESS  read-write
   STATUS      current
   DESCRIPTION
      "Path: pppBundle.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2PppBFIpEntry 285212672}

er1645v2PppBFIpDB OBJECT-TYPE
   SYNTAX      INTEGER
               {
               disabled (0),
               enabled (1)
               }
   MAX-ACCESS  read-write
   STATUS      current
   DESCRIPTION
      "Path: pppBundle.editConf.ip.directedBroadcasts

       Possibilities:
               disabled   (0)
               enabled   (1)"
   ::= {er1645v2PppBFIpEntry 369098752}

er1645v2PppBFIpIR OBJECT-TYPE
   SYNTAX      INTEGER
               {
               disabled (0),
               enabled (1)
               }
   MAX-ACCESS  read-write
   STATUS      current
   DESCRIPTION
      "Path: pppBundle.editConf.ip.icmpRedirects

       Possibilities:
               disabled   (0)
               enabled   (1)"
   ::= {er1645v2PppBFIpEntry 436207616}

er1645v2PppBFIpIgmp OBJECT-TYPE
   SYNTAX      INTEGER
               {
               disabled (0),
               proxy (1),
               router (2),
               v3Router (5)
               }
   MAX-ACCESS  read-write
   STATUS      current
   DESCRIPTION
      "Path: pppBundle.editConf.ip.igmp

       Possibilities:
               disabled   (0)
               proxy   (1)
               router   (2)
               v3Router   (5)"
   ::= {er1645v2PppBFIpEntry 536870912}

er1645v2PppBFIpNN OBJECT-TYPE
   SYNTAX      DisplayString
   MAX-ACCESS  read-write
   STATUS      current
   DESCRIPTION
      "Path: pppBundle.editConf.ip.nat"
   ::= {er1645v2PppBFIpEntry 452984832}

er1645v2PppBFIpPimMode OBJECT-TYPE
   SYNTAX      INTEGER
               {
               disabled (0),
               sparse (1),
               passive (2)
               }
   MAX-ACCESS  read-write
   STATUS      current
   DESCRIPTION
      "Path: pppBundle.editConf.ip.pim.mode

       Possibilities:
               disabled   (0)
               sparse   (1)
               passive   (2)"
   ::= {er1645v2PppBFIpEntry 771817472}

er1645v2PppBFIpPimDrPriority OBJECT-TYPE
   SYNTAX      Counter32
   MAX-ACCESS  read-write
   STATUS      current
   DESCRIPTION
      "Path: pppBundle.editConf.ip.pim.drPriority

       32 bit unsigned wrappable counter."
   ::= {er1645v2PppBFIpEntry 771883008}

er1645v2PppBFIpPimHelloTime OBJECT-TYPE
   SYNTAX      TimeTicks
   MAX-ACCESS  read-write
   STATUS      current
   DESCRIPTION
      "Path: pppBundle.editConf.ip.pim.helloTime

       Time in centi-second."
   ::= {er1645v2PppBFIpEntry 771948544}

er1645v2PppBFIpPimPropagationDelay OBJECT-TYPE
   SYNTAX      TimeTicks
   MAX-ACCESS  read-write
   STATUS      current
   DESCRIPTION
      "Path: pppBundle.editConf.ip.pim.propagationDelay

       Time in centi-second."
   ::= {er1645v2PppBFIpEntry 772014080}

er1645v2PppBFIpPimOverrideInterval OBJECT-TYPE
   SYNTAX      TimeTicks
   MAX-ACCESS  read-write
   STATUS      current
   DESCRIPTION
      "Path: pppBundle.editConf.ip.pim.overrideInterval

       Time in centi-second."
   ::= {er1645v2PppBFIpEntry 772079616}

er1645v2PppBFIpPimBsrBorder OBJECT-TYPE
   SYNTAX      INTEGER
               {
               disabled (0),
               enabled (1)
               }
   MAX-ACCESS  read-write
   STATUS      current
   DESCRIPTION
      "Path: pppBundle.editConf.ip.pim.bsrBorder

       Possibilities:
               disabled   (0)
               enabled   (1)"
   ::= {er1645v2PppBFIpEntry 772145152}

er1645v2PppBFIpPimTtlThreshold OBJECT-TYPE
   SYNTAX      Integer32
   MAX-ACCESS  read-write
   STATUS      current
   DESCRIPTION
      "Path: pppBundle.editConf.ip.pim.ttlThreshold"
   ::= {er1645v2PppBFIpEntry 772210688}

er1645v2PppBFIpIMNetworkUnreachable OBJECT-TYPE
   SYNTAX      INTEGER
               {
               disabled (0),
               enabled (1)
               }
   MAX-ACCESS  read-write
   STATUS      current
   DESCRIPTION
      "Path: pppBundle.editConf.ip.icmpMessages.networkUnreachable

       Possibilities:
               disabled   (0)
               enabled   (1)"
   ::= {er1645v2PppBFIpEntry 788594688}

er1645v2PppBFIpIMHostUnreachable OBJECT-TYPE
   SYNTAX      INTEGER
               {
               disabled (0),
               enabled (1)
               }
   MAX-ACCESS  read-write
   STATUS      current
   DESCRIPTION
      "Path: pppBundle.editConf.ip.icmpMessages.hostUnreachable

       Possibilities:
               disabled   (0)
               enabled   (1)"
   ::= {er1645v2PppBFIpEntry 788660224}

er1645v2PppBFIpIMProtocolUnreachable OBJECT-TYPE
   SYNTAX      INTEGER
               {
               disabled (0),
               enabled (1)
               }
   MAX-ACCESS  read-write
   STATUS      current
   DESCRIPTION
      "Path: pppBundle.editConf.ip.icmpMessages.protocolUnreachable

       Possibilities:
               disabled   (0)
               enabled   (1)"
   ::= {er1645v2PppBFIpEntry 788725760}

er1645v2PppBFIpIMPortUnreachable OBJECT-TYPE
   SYNTAX      INTEGER
               {
               disabled (0),
               enabled (1)
               }
   MAX-ACCESS  read-write
   STATUS      current
   DESCRIPTION
      "Path: pppBundle.editConf.ip.icmpMessages.portUnreachable

       Possibilities:
               disabled   (0)
               enabled   (1)"
   ::= {er1645v2PppBFIpEntry 788791296}

er1645v2PppBFIpIMMtuExceeded OBJECT-TYPE
   SYNTAX      INTEGER
               {
               disabled (0),
               enabled (1)
               }
   MAX-ACCESS  read-write
   STATUS      current
   DESCRIPTION
      "Path: pppBundle.editConf.ip.icmpMessages.mtuExceeded

       Possibilities:
               disabled   (0)
               enabled   (1)"
   ::= {er1645v2PppBFIpEntry 788856832}

er1645v2PppBFIpIMAdminProhibited OBJECT-TYPE
   SYNTAX      INTEGER
               {
               disabled (0),
               enabled (1)
               }
   MAX-ACCESS  read-write
   STATUS      current
   DESCRIPTION
      "Path: pppBundle.editConf.ip.icmpMessages.adminProhibited

       Possibilities:
               disabled   (0)
               enabled   (1)"
   ::= {er1645v2PppBFIpEntry 788922368}

er1645v2PppBFIpIMTtlExceeded OBJECT-TYPE
   SYNTAX      INTEGER
               {
               disabled (0),
               enabled (1)
               }
   MAX-ACCESS  read-write
   STATUS      current
   DESCRIPTION
      "Path: pppBundle.editConf.ip.icmpMessages.ttlExceeded

       Possibilities:
               disabled   (0)
               enabled   (1)"
   ::= {er1645v2PppBFIpEntry 788987904}

er1645v2PppBFIpIMRedirect OBJECT-TYPE
   SYNTAX      INTEGER
               {
               disabled (0),
               enabled (1)
               }
   MAX-ACCESS  read-write
   STATUS      current
   DESCRIPTION
      "Path: pppBundle.editConf.ip.icmpMessages.redirect

       Possibilities:
               disabled   (0)
               enabled   (1)"
   ::= {er1645v2PppBFIpEntry 789053440}


er1645v2PppBFMcIf OBJECT IDENTIFIER ::= {er1645v2PppBF 9}

er1645v2PppBFMcIfSSCTable OBJECT-TYPE
   SYNTAX      SEQUENCE OF Er1645v2PppBFMcIfEntry
   MAX-ACCESS  not-accessible
   STATUS      current
   DESCRIPTION
      ""
   ::= {er1645v2PppBFMcIf 1}

er1645v2PppBFMcIfEntry OBJECT-TYPE
   SYNTAX      Er1645v2PppBFMcIfEntry
   MAX-ACCESS  not-accessible
   STATUS      current
   DESCRIPTION
      ""
   INDEX      { er1645v2PppBFMcIfGlobalIx,
                er1645v2PppBFMcIfTableIx }
   ::= {er1645v2PppBFMcIfSSCTable 1}

Er1645v2PppBFMcIfEntry ::=
   SEQUENCE
      {
      er1645v2PppBFMcIfActions
         VariableLengthTableActions,
      er1645v2PppBFMcIfGlobalIx
         GlobalIndex,
      er1645v2PppBFMcIfTableIx
         TableIndex,
      er1645v2PppBFMcIfName
         DisplayString,
      er1645v2PppBFMcIfAdminStatus
         INTEGER,
      er1645v2PppBFMcIfMode
         INTEGER,
      er1645v2PppBFMcIfIpVrfRouter
         DisplayString,
      er1645v2PppBFMcIfIpAdr
         IpAddress,
      er1645v2PppBFMcIfIpNetm
         IpAddress,
      er1645v2PppBFMcIfIpSNetName
         INTEGER,
      er1645v2PppBFMcIfIpSNetCust
         DisplayString,
      er1645v2PppBFMcIfIpRem
         IpAddress,
      er1645v2PppBFMcIfIpUnnumbered
         DisplayString,
      er1645v2PppBFMcIfIpAcceptLocAddr
         INTEGER,
      er1645v2PppBFMcIfIpAcceptRemAddr
         INTEGER,
      er1645v2PppBFMcIfIpGatewayPref
         Integer32,
      er1645v2PppBFMcIfIpRsn
         INTEGER,
      er1645v2PppBFMcIfIpMtu
         Integer32,
      er1645v2PppBFMcIfIpMssAdjust
         INTEGER,
      er1645v2PppBFMcIfIpRipMetric
         Integer32,
      er1645v2PppBFMcIfIpRipMetricOut
         Integer32,
      er1645v2PppBFMcIfIpRipMode
         INTEGER,
      er1645v2PppBFMcIfIpRipTxVer
         INTEGER,
      er1645v2PppBFMcIfIpRipRxVer
         INTEGER,
      er1645v2PppBFMcIfIpRipSplitH
         INTEGER,
      er1645v2PppBFMcIfIpRipAuth
         INTEGER,
      er1645v2PppBFMcIfIpRipFilter
         DisplayString,
      er1645v2PppBFMcIfIpRipFilterIn
         DisplayString,
      er1645v2PppBFMcIfIpRipClearNextHop
         INTEGER,
      er1645v2PppBFMcIfIpAccPol
         DisplayString,
      er1645v2PppBFMcIfIpAB
         DisplayString,
      er1645v2PppBFMcIfIpMA
         INTEGER,
      er1645v2PppBFMcIfIpMF
         Integer32,
      er1645v2PppBFMcIfIpDB
         INTEGER,
      er1645v2PppBFMcIfIpIR
         INTEGER,
      er1645v2PppBFMcIfIpIgmp
         INTEGER,
      er1645v2PppBFMcIfIpNN
         DisplayString,
      er1645v2PppBFMcIfIpPimMode
         INTEGER,
      er1645v2PppBFMcIfIpPimDrPriority
         Counter32,
      er1645v2PppBFMcIfIpPimHelloTime
         TimeTicks,
      er1645v2PppBFMcIfIpPimPropagationDelay
         TimeTicks,
      er1645v2PppBFMcIfIpPimOverrideInterval
         TimeTicks,
      er1645v2PppBFMcIfIpPimBsrBorder
         INTEGER,
      er1645v2PppBFMcIfIpPimTtlThreshold
         Integer32,
      er1645v2PppBFMcIfIpIMNetworkUnreachable
         INTEGER,
      er1645v2PppBFMcIfIpIMHostUnreachable
         INTEGER,
      er1645v2PppBFMcIfIpIMProtocolUnreachable
         INTEGER,
      er1645v2PppBFMcIfIpIMPortUnreachable
         INTEGER,
      er1645v2PppBFMcIfIpIMMtuExceeded
         INTEGER,
      er1645v2PppBFMcIfIpIMAdminProhibited
         INTEGER,
      er1645v2PppBFMcIfIpIMTtlExceeded
         INTEGER,
      er1645v2PppBFMcIfIpIMRedirect
         INTEGER,
      er1645v2PppBFMcIfBridgingAccList
         DisplayString,
      er1645v2PppBFMcIfBridgingInACL
         DisplayString,
      er1645v2PppBFMcIfBridgingTp
         DisplayString,
      er1645v2PppBFMcIfBridgingBrGrp
         DisplayString,
      er1645v2PppBFMcIfBridgingLimBC
         INTEGER,
      er1645v2PppBFMcIfBridgingPrivateMode
         INTEGER,
      er1645v2PppBFMcIfBridgingLearning
         INTEGER,
      er1645v2PppBFMcIfBridgingMaxCacheSize
         INTEGER,
      er1645v2PppBFMcIfBridgingRelearnDropOnRelearn
         INTEGER,
      er1645v2PppBFMcIfBridgingRelearnShutdownThreshold
         Integer32,
      er1645v2PppBFMcIfBridgingRelearnShutdownTime
         TimeTicks,
      er1645v2PppBFMcIfBridgingRelearnLoopDetection
         INTEGER,
      er1645v2PppBFMcIfBridgingRelearnLoopDetectionInterval
         TimeTicks,
      er1645v2PppBFMcIfBridgingVlanMemberShip
         INTEGER,
      er1645v2PppBFMcIfBridgingVlTUntaggedAction
         INTEGER,
      er1645v2PppBFMcIfBridgingVlTUntaggedTagInfoTpid
         INTEGER,
      er1645v2PppBFMcIfBridgingVlTUntaggedTagInfoVid
         Integer32,
      er1645v2PppBFMcIfBridgingVlTUnknownVlansAction
         INTEGER,
      er1645v2PppBFMcIfBridgingVlTUnknownVlansTagInfoTpid
         INTEGER,
      er1645v2PppBFMcIfBridgingVlTUnknownVlansTagInfoVid
         Integer32,
      er1645v2PppBFMcIfBridgingDot1adType
         INTEGER,
      er1645v2PppBFMcIfBridgingPriority
         Integer32,
      er1645v2PppBFMcIfBridgingPathCost
         Integer32,
      er1645v2PppBFMcIfBridgingInternalPathCost
         Integer32,
      er1645v2PppBFMcIfBridgingTCD
         INTEGER,
      er1645v2PppBFMcIfBridgingRestrictedRole
         INTEGER,
      er1645v2PppBFMcIfBridgingAdminEdge
         INTEGER,
      er1645v2PppBFMcIfBridgingOamMacDeviceMac
         DisplayString,
      er1645v2PppBFMcIfBridgingOamMacUserMac
         OCTET STRING,
      er1645v2PppBFMcIfBridgingOamMacBridgeMac
         DisplayString,
      er1645v2PppBFMcIfBridgingMgmtInline
         INTEGER,
      er1645v2PppBFMcIfBridgingL2ptMode
         INTEGER,
      er1645v2PppBFMcIfBridgingL2ptProtocols
         Integer32,
      er1645v2PppBFMcIfBridgingL2ptDestMac
         OCTET STRING,
      er1645v2PppBFMcIfBridgingL2ptCos
         INTEGER,
      er1645v2PppBFMcIfBridgingL2ptDropThrStp
         INTEGER,
      er1645v2PppBFMcIfBridgingL2ptDropThrLldp
         INTEGER,
      er1645v2PppBFMcIfBridgingL2ptDropThrOam
         INTEGER,
      er1645v2PppBFMcIfBridgingL2ptDropThrCdp
         INTEGER,
      er1645v2PppBFMcIfBridgingL2ptDropThrVtp
         INTEGER,
      er1645v2PppBFMcIfBridgingL2ptDropThrLacp
         INTEGER,
      er1645v2PppBFMcIfBridgingL2ptDropThrEfmOam
         INTEGER,
      er1645v2PppBFMcIfBridgingL2ptDropThrPvst
         INTEGER,
      er1645v2PppBFMcIfBridgingL2ptDropThrMmrp
         INTEGER,
      er1645v2PppBFMcIfBridgingL2ptDropThrMvrp
         INTEGER,
      er1645v2PppBFMcIfBridgingL2ptDropThrGvrp
         INTEGER,
      er1645v2PppBFMcIfBridgingL2ptDropThrGmrp
         INTEGER,
      er1645v2PppBFMcIfBridgingL2ptDropThrDtp
         INTEGER,
      er1645v2PppBFMcIfBridgingL2ptDropThrPagp
         INTEGER,
      er1645v2PppBFMcIfBridgingL2ptDropThrUdld
         INTEGER,
      er1645v2PppBFMcIfMulticlassMulticlass
         Integer32,
      er1645v2PppBFMcIfMulticlassDQueue
         INTEGER
      }

er1645v2PppBFMcIfActions OBJECT-TYPE
   SYNTAX      VariableLengthTableActions
   MAX-ACCESS  read-write
   STATUS      current
   DESCRIPTION
      "By way of this field, some manipulations
       on this table may be performed."
   ::= {er1645v2PppBFMcIfEntry 2}

er1645v2PppBFMcIfGlobalIx OBJECT-TYPE
   SYNTAX      GlobalIndex
   MAX-ACCESS  not-accessible
   STATUS      current
   DESCRIPTION
      "The value of the tlsCntTreeGlobalIndex of the MANAGED OBJECT."
   ::= {er1645v2PppBFMcIfEntry 10}

er1645v2PppBFMcIfTableIx OBJECT-TYPE
   SYNTAX      TableIndex
   MAX-ACCESS  not-accessible
   STATUS      current
   DESCRIPTION
      ""
   ::= {er1645v2PppBFMcIfEntry 11}

er1645v2PppBFMcIfName OBJECT-TYPE
   SYNTAX      DisplayString
   MAX-ACCESS  read-write
   STATUS      current
   DESCRIPTION
      "Path: pppBundle.editConf.multiclassInterfaces.name"
   ::= {er1645v2PppBFMcIfEntry 16777216}

er1645v2PppBFMcIfAdminStatus OBJECT-TYPE
   SYNTAX      INTEGER
               {
               up (1),
               down (2)
               }
   MAX-ACCESS  read-write
   STATUS      current
   DESCRIPTION
      "Path: pppBundle.editConf.multiclassInterfaces.adminStatus

       Possibilities:
               up   (1)
               down   (2)"
   ::= {er1645v2PppBFMcIfEntry 33554432}

er1645v2PppBFMcIfMode OBJECT-TYPE
   SYNTAX      INTEGER
               {
               routing (1),
               bridging (2),
               routingAndBridging (3)
               }
   MAX-ACCESS  read-write
   STATUS      current
   DESCRIPTION
      "Path: pppBundle.editConf.multiclassInterfaces.mode

       Possibilities:
               routing   (1)
               bridging   (2)
               routingAndBridging   (3)"
   ::= {er1645v2PppBFMcIfEntry 67108864}

er1645v2PppBFMcIfIpVrfRouter OBJECT-TYPE
   SYNTAX      DisplayString
   MAX-ACCESS  read-write
   STATUS      current
   DESCRIPTION
      "Path: pppBundle.editConf.multiclassInterfaces.ip.vrfRouter"
   ::= {er1645v2PppBFMcIfEntry 53215232}

er1645v2PppBFMcIfIpAdr OBJECT-TYPE
   SYNTAX      IpAddress
   MAX-ACCESS  read-write
   STATUS      current
   DESCRIPTION
      "Path: pppBundle.editConf.multiclassInterfaces.ip.address"
   ::= {er1645v2PppBFMcIfEntry 58261504}

er1645v2PppBFMcIfIpNetm OBJECT-TYPE
   SYNTAX      IpAddress
   MAX-ACCESS  read-write
   STATUS      current
   DESCRIPTION
      "Path: pppBundle.editConf.multiclassInterfaces.ip.netMask"
   ::= {er1645v2PppBFMcIfEntry 58392576}

er1645v2PppBFMcIfIpSNetName OBJECT-TYPE
   SYNTAX      INTEGER
               {
               slOPTg (0),
               corp (2),
               dmz (3),
               internet (1)
               }
   MAX-ACCESS  read-write
   STATUS      current
   DESCRIPTION
      "Path: pppBundle.editConf.multiclassInterfaces.ip.sNet.name

       Possibilities:
               <OPT>   (0)
               corp   (2)
               dmz   (3)
               internet   (1)"
   ::= {er1645v2PppBFMcIfEntry 53674240}

er1645v2PppBFMcIfIpSNetCust OBJECT-TYPE
   SYNTAX      DisplayString
   MAX-ACCESS  read-write
   STATUS      current
   DESCRIPTION
      "Path: pppBundle.editConf.multiclassInterfaces.ip.sNet.custom"
   ::= {er1645v2PppBFMcIfEntry 53674496}

er1645v2PppBFMcIfIpRem OBJECT-TYPE
   SYNTAX      IpAddress
   MAX-ACCESS  read-write
   STATUS      current
   DESCRIPTION
      "Path: pppBundle.editConf.multiclassInterfaces.ip.remote"
   ::= {er1645v2PppBFMcIfEntry 58458112}

er1645v2PppBFMcIfIpUnnumbered OBJECT-TYPE
   SYNTAX      DisplayString
   MAX-ACCESS  read-write
   STATUS      current
   DESCRIPTION
      "Path: pppBundle.editConf.multiclassInterfaces.ip.unnumbered"
   ::= {er1645v2PppBFMcIfEntry 52625408}

er1645v2PppBFMcIfIpAcceptLocAddr OBJECT-TYPE
   SYNTAX      INTEGER
               {
               disabled (0),
               enabled (1)
               }
   MAX-ACCESS  read-write
   STATUS      current
   DESCRIPTION
      "Path: pppBundle.editConf.multiclassInterfaces.ip.acceptLocAddr

       Possibilities:
               disabled   (0)
               enabled   (1)"
   ::= {er1645v2PppBFMcIfEntry 50593792}

er1645v2PppBFMcIfIpAcceptRemAddr OBJECT-TYPE
   SYNTAX      INTEGER
               {
               disabled (0),
               enabled (1)
               }
   MAX-ACCESS  read-write
   STATUS      current
   DESCRIPTION
      "Path: pppBundle.editConf.multiclassInterfaces.ip.acceptRemAddr

       Possibilities:
               disabled   (0)
               enabled   (1)"
   ::= {er1645v2PppBFMcIfEntry 50724864}

er1645v2PppBFMcIfIpGatewayPref OBJECT-TYPE
   SYNTAX      Integer32
   MAX-ACCESS  read-write
   STATUS      current
   DESCRIPTION
      "Path: pppBundle.editConf.multiclassInterfaces.ip.gatewayPreference"
   ::= {er1645v2PppBFMcIfEntry 52690944}

er1645v2PppBFMcIfIpRsn OBJECT-TYPE
   SYNTAX      INTEGER
               {
               disabled (0),
               enabled (1)
               }
   MAX-ACCESS  read-write
   STATUS      current
   DESCRIPTION
      "Path: pppBundle.editConf.multiclassInterfaces.ip.requestSubnet

       Possibilities:
               disabled   (0)
               enabled   (1)"
   ::= {er1645v2PppBFMcIfEntry 56688640}

er1645v2PppBFMcIfIpMtu OBJECT-TYPE
   SYNTAX      Integer32
   MAX-ACCESS  read-write
   STATUS      current
   DESCRIPTION
      "Path: pppBundle.editConf.multiclassInterfaces.ip.mtu"
   ::= {er1645v2PppBFMcIfEntry 52953088}

er1645v2PppBFMcIfIpMssAdjust OBJECT-TYPE
   SYNTAX      INTEGER
               {
               disabled (0),
               auto (65536)
               }
   MAX-ACCESS  read-write
   STATUS      current
   DESCRIPTION
      "Path: pppBundle.editConf.multiclassInterfaces.ip.mssAdjust

       Possibilities:
               disabled   (0)
               auto   (65536)"
   ::= {er1645v2PppBFMcIfEntry 53280768}

er1645v2PppBFMcIfIpRipMetric OBJECT-TYPE
   SYNTAX      Integer32
   MAX-ACCESS  read-write
   STATUS      current
   DESCRIPTION
      "Path: pppBundle.editConf.multiclassInterfaces.ip.rip.metric"
   ::= {er1645v2PppBFMcIfEntry 51712768}

er1645v2PppBFMcIfIpRipMetricOut OBJECT-TYPE
   SYNTAX      Integer32
   MAX-ACCESS  read-write
   STATUS      current
   DESCRIPTION
      "Path: pppBundle.editConf.multiclassInterfaces.ip.rip.metricOut"
   ::= {er1645v2PppBFMcIfEntry 51713024}

er1645v2PppBFMcIfIpRipMode OBJECT-TYPE
   SYNTAX      INTEGER
               {
               disabled (0),
               passive (1),
               active (2)
               }
   MAX-ACCESS  read-write
   STATUS      current
   DESCRIPTION
      "Path: pppBundle.editConf.multiclassInterfaces.ip.rip.mode

       Possibilities:
               disabled   (0)
               passive   (1)
               active   (2)"
   ::= {er1645v2PppBFMcIfEntry 51713280}

er1645v2PppBFMcIfIpRipTxVer OBJECT-TYPE
   SYNTAX      INTEGER
               {
               rip1 (0),
               rip2 (1),
               rip1mcompatible (2)
               }
   MAX-ACCESS  read-write
   STATUS      current
   DESCRIPTION
      "Path: pppBundle.editConf.multiclassInterfaces.ip.rip.txVersion

       Possibilities:
               rip1   (0)
               rip2   (1)
               rip1-compatible   (2)"
   ::= {er1645v2PppBFMcIfEntry 51716864}

er1645v2PppBFMcIfIpRipRxVer OBJECT-TYPE
   SYNTAX      INTEGER
               {
               rip1only (0),
               rip2only (1),
               rip12 (2)
               }
   MAX-ACCESS  read-write
   STATUS      current
   DESCRIPTION
      "Path: pppBundle.editConf.multiclassInterfaces.ip.rip.rxVersion

       Possibilities:
               rip1only   (0)
               rip2only   (1)
               rip1&2   (2)"
   ::= {er1645v2PppBFMcIfEntry 51717120}

er1645v2PppBFMcIfIpRipSplitH OBJECT-TYPE
   SYNTAX      INTEGER
               {
               disabled (0),
               enabled (1),
               poisonedReverse (2)
               }
   MAX-ACCESS  read-write
   STATUS      current
   DESCRIPTION
      "Path: pppBundle.editConf.multiclassInterfaces.ip.rip.splitHorizon

       Possibilities:
               disabled   (0)
               enabled   (1)
               poisonedReverse   (2)"
   ::= {er1645v2PppBFMcIfEntry 51713792}

er1645v2PppBFMcIfIpRipAuth OBJECT-TYPE
   SYNTAX      INTEGER
               {
               disabled (0),
               texts (1),
               md5 (2)
               }
   MAX-ACCESS  read-write
   STATUS      current
   DESCRIPTION
      "Path: pppBundle.editConf.multiclassInterfaces.ip.rip.authentication

       Possibilities:
               disabled   (0)
               text    (1)
               md5   (2)"
   ::= {er1645v2PppBFMcIfEntry 51712512}

er1645v2PppBFMcIfIpRipFilter OBJECT-TYPE
   SYNTAX      DisplayString
   MAX-ACCESS  read-write
   STATUS      current
   DESCRIPTION
      "Path: pppBundle.editConf.multiclassInterfaces.ip.rip.filter"
   ::= {er1645v2PppBFMcIfEntry 51716096}

er1645v2PppBFMcIfIpRipFilterIn OBJECT-TYPE
   SYNTAX      DisplayString
   MAX-ACCESS  read-write
   STATUS      current
   DESCRIPTION
      "Path: pppBundle.editConf.multiclassInterfaces.ip.rip.filterIn"
   ::= {er1645v2PppBFMcIfEntry 51716352}

er1645v2PppBFMcIfIpRipClearNextHop OBJECT-TYPE
   SYNTAX      INTEGER
               {
               disabled (0),
               enabled (1)
               }
   MAX-ACCESS  read-write
   STATUS      current
   DESCRIPTION
      "Path: pppBundle.editConf.multiclassInterfaces.ip.rip.clearNextHop

       Possibilities:
               disabled   (0)
               enabled   (1)"
   ::= {er1645v2PppBFMcIfEntry 51708416}

er1645v2PppBFMcIfIpAccPol OBJECT-TYPE
   SYNTAX      DisplayString
   MAX-ACCESS  read-write
   STATUS      current
   DESCRIPTION
      "Path: pppBundle.editConf.multiclassInterfaces.ip.accessPolicy"
   ::= {er1645v2PppBFMcIfEntry 53084160}

er1645v2PppBFMcIfIpAB OBJECT-TYPE
   SYNTAX      DisplayString
   MAX-ACCESS  read-write
   STATUS      current
   DESCRIPTION
      "Path: pppBundle.editConf.multiclassInterfaces.ip.trafficPolicy"
   ::= {er1645v2PppBFMcIfEntry 51249152}

er1645v2PppBFMcIfIpMA OBJECT-TYPE
   SYNTAX      INTEGER
               {
               disabled (0),
               enabled (1)
               }
   MAX-ACCESS  read-write
   STATUS      current
   DESCRIPTION
      "Path: pppBundle.editConf.multiclassInterfaces.ip.mgmtAccess

       Possibilities:
               disabled   (0)
               enabled   (1)"
   ::= {er1645v2PppBFMcIfEntry 51380224}

er1645v2PppBFMcIfIpMF OBJECT-TYPE
   SYNTAX      Integer32
   MAX-ACCESS  read-write
   STATUS      current
   DESCRIPTION
      "Path: pppBundle.editConf.multiclassInterfaces.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2PppBFMcIfEntry 51445760}

er1645v2PppBFMcIfIpDB OBJECT-TYPE
   SYNTAX      INTEGER
               {
               disabled (0),
               enabled (1)
               }
   MAX-ACCESS  read-write
   STATUS      current
   DESCRIPTION
      "Path: pppBundle.editConf.multiclassInterfaces.ip.directedBroadcasts

       Possibilities:
               disabled   (0)
               enabled   (1)"
   ::= {er1645v2PppBFMcIfEntry 51773440}

er1645v2PppBFMcIfIpIR OBJECT-TYPE
   SYNTAX      INTEGER
               {
               disabled (0),
               enabled (1)
               }
   MAX-ACCESS  read-write
   STATUS      current
   DESCRIPTION
      "Path: pppBundle.editConf.multiclassInterfaces.ip.icmpRedirects

       Possibilities:
               disabled   (0)
               enabled   (1)"
   ::= {er1645v2PppBFMcIfEntry 52035584}

er1645v2PppBFMcIfIpIgmp OBJECT-TYPE
   SYNTAX      INTEGER
               {
               disabled (0),
               proxy (1),
               router (2),
               v3Router (5)
               }
   MAX-ACCESS  read-write
   STATUS      current
   DESCRIPTION
      "Path: pppBundle.editConf.multiclassInterfaces.ip.igmp

       Possibilities:
               disabled   (0)
               proxy   (1)
               router   (2)
               v3Router   (5)"
   ::= {er1645v2PppBFMcIfEntry 52428800}

er1645v2PppBFMcIfIpNN OBJECT-TYPE
   SYNTAX      DisplayString
   MAX-ACCESS  read-write
   STATUS      current
   DESCRIPTION
      "Path: pppBundle.editConf.multiclassInterfaces.ip.nat"
   ::= {er1645v2PppBFMcIfEntry 52101120}

er1645v2PppBFMcIfIpPimMode OBJECT-TYPE
   SYNTAX      INTEGER
               {
               disabled (0),
               sparse (1),
               passive (2)
               }
   MAX-ACCESS  read-write
   STATUS      current
   DESCRIPTION
      "Path: pppBundle.editConf.multiclassInterfaces.ip.pim.mode

       Possibilities:
               disabled   (0)
               sparse   (1)
               passive   (2)"
   ::= {er1645v2PppBFMcIfEntry 53346560}

er1645v2PppBFMcIfIpPimDrPriority OBJECT-TYPE
   SYNTAX      Counter32
   MAX-ACCESS  read-write
   STATUS      current
   DESCRIPTION
      "Path: pppBundle.editConf.multiclassInterfaces.ip.pim.drPriority

       32 bit unsigned wrappable counter."
   ::= {er1645v2PppBFMcIfEntry 53346816}

er1645v2PppBFMcIfIpPimHelloTime OBJECT-TYPE
   SYNTAX      TimeTicks
   MAX-ACCESS  read-write
   STATUS      current
   DESCRIPTION
      "Path: pppBundle.editConf.multiclassInterfaces.ip.pim.helloTime

       Time in centi-second."
   ::= {er1645v2PppBFMcIfEntry 53347072}

er1645v2PppBFMcIfIpPimPropagationDelay OBJECT-TYPE
   SYNTAX      TimeTicks
   MAX-ACCESS  read-write
   STATUS      current
   DESCRIPTION
      "Path: pppBundle.editConf.multiclassInterfaces.ip.pim.propagationDelay

       Time in centi-second."
   ::= {er1645v2PppBFMcIfEntry 53347328}

er1645v2PppBFMcIfIpPimOverrideInterval OBJECT-TYPE
   SYNTAX      TimeTicks
   MAX-ACCESS  read-write
   STATUS      current
   DESCRIPTION
      "Path: pppBundle.editConf.multiclassInterfaces.ip.pim.overrideInterval

       Time in centi-second."
   ::= {er1645v2PppBFMcIfEntry 53347584}

er1645v2PppBFMcIfIpPimBsrBorder OBJECT-TYPE
   SYNTAX      INTEGER
               {
               disabled (0),
               enabled (1)
               }
   MAX-ACCESS  read-write
   STATUS      current
   DESCRIPTION
      "Path: pppBundle.editConf.multiclassInterfaces.ip.pim.bsrBorder

       Possibilities:
               disabled   (0)
               enabled   (1)"
   ::= {er1645v2PppBFMcIfEntry 53347840}

er1645v2PppBFMcIfIpPimTtlThreshold OBJECT-TYPE
   SYNTAX      Integer32
   MAX-ACCESS  read-write
   STATUS      current
   DESCRIPTION
      "Path: pppBundle.editConf.multiclassInterfaces.ip.pim.ttlThreshold"
   ::= {er1645v2PppBFMcIfEntry 53348096}

er1645v2PppBFMcIfIpIMNetworkUnreachable OBJECT-TYPE
   SYNTAX      INTEGER
               {
               disabled (0),
               enabled (1)
               }
   MAX-ACCESS  read-write
   STATUS      current
   DESCRIPTION
      "Path: pppBundle.editConf.multiclassInterfaces.ip.icmpMessages.networkUnreachable

       Possibilities:
               disabled   (0)
               enabled   (1)"
   ::= {er1645v2PppBFMcIfEntry 53412096}

er1645v2PppBFMcIfIpIMHostUnreachable OBJECT-TYPE
   SYNTAX      INTEGER
               {
               disabled (0),
               enabled (1)
               }
   MAX-ACCESS  read-write
   STATUS      current
   DESCRIPTION
      "Path: pppBundle.editConf.multiclassInterfaces.ip.icmpMessages.hostUnreachable

       Possibilities:
               disabled   (0)
               enabled   (1)"
   ::= {er1645v2PppBFMcIfEntry 53412352}

er1645v2PppBFMcIfIpIMProtocolUnreachable OBJECT-TYPE
   SYNTAX      INTEGER
               {
               disabled (0),
               enabled (1)
               }
   MAX-ACCESS  read-write
   STATUS      current
   DESCRIPTION
      "Path: pppBundle.editConf.multiclassInterfaces.ip.icmpMessages.protocolUnreachable

       Possibilities:
               disabled   (0)
               enabled   (1)"
   ::= {er1645v2PppBFMcIfEntry 53412608}

er1645v2PppBFMcIfIpIMPortUnreachable OBJECT-TYPE
   SYNTAX      INTEGER
               {
               disabled (0),
               enabled (1)
               }
   MAX-ACCESS  read-write
   STATUS      current
   DESCRIPTION
      "Path: pppBundle.editConf.multiclassInterfaces.ip.icmpMessages.portUnreachable

       Possibilities:
               disabled   (0)
               enabled   (1)"
   ::= {er1645v2PppBFMcIfEntry 53412864}

er1645v2PppBFMcIfIpIMMtuExceeded OBJECT-TYPE
   SYNTAX      INTEGER
               {
               disabled (0),
               enabled (1)
               }
   MAX-ACCESS  read-write
   STATUS      current
   DESCRIPTION
      "Path: pppBundle.editConf.multiclassInterfaces.ip.icmpMessages.mtuExceeded

       Possibilities:
               disabled   (0)
               enabled   (1)"
   ::= {er1645v2PppBFMcIfEntry 53413120}

er1645v2PppBFMcIfIpIMAdminProhibited OBJECT-TYPE
   SYNTAX      INTEGER
               {
               disabled (0),
               enabled (1)
               }
   MAX-ACCESS  read-write
   STATUS      current
   DESCRIPTION
      "Path: pppBundle.editConf.multiclassInterfaces.ip.icmpMessages.adminProhibited

       Possibilities:
               disabled   (0)
               enabled   (1)"
   ::= {er1645v2PppBFMcIfEntry 53413376}

er1645v2PppBFMcIfIpIMTtlExceeded OBJECT-TYPE
   SYNTAX      INTEGER
               {
               disabled (0),
               enabled (1)
               }
   MAX-ACCESS  read-write
   STATUS      current
   DESCRIPTION
      "Path: pppBundle.editConf.multiclassInterfaces.ip.icmpMessages.ttlExceeded

       Possibilities:
               disabled   (0)
               enabled   (1)"
   ::= {er1645v2PppBFMcIfEntry 53413632}

er1645v2PppBFMcIfIpIMRedirect OBJECT-TYPE
   SYNTAX      INTEGER
               {
               disabled (0),
               enabled (1)
               }
   MAX-ACCESS  read-write
   STATUS      current
   DESCRIPTION
      "Path: pppBundle.editConf.multiclassInterfaces.ip.icmpMessages.redirect

       Possibilities:
               disabled   (0)
               enabled   (1)"
   ::= {er1645v2PppBFMcIfEntry 53413888}

er1645v2PppBFMcIfBridgingAccList OBJECT-TYPE
   SYNTAX      DisplayString
   MAX-ACCESS  read-write
   STATUS      current
   DESCRIPTION
      "Path: pppBundle.editConf.multiclassInterfaces.bridging.accessList"
   ::= {er1645v2PppBFMcIfEntry 453246976}

er1645v2PppBFMcIfBridgingInACL OBJECT-TYPE
   SYNTAX      DisplayString
   MAX-ACCESS  read-write
   STATUS      current
   DESCRIPTION
      "Path: pppBundle.editConf.multiclassInterfaces.bridging.inAccessList"
   ::= {er1645v2PppBFMcIfEntry 456916992}

er1645v2PppBFMcIfBridgingTp OBJECT-TYPE
   SYNTAX      DisplayString
   MAX-ACCESS  read-write
   STATUS      current
   DESCRIPTION
      "Path: pppBundle.editConf.multiclassInterfaces.bridging.trafficPolicy"
   ::= {er1645v2PppBFMcIfEntry 454295552}

er1645v2PppBFMcIfBridgingBrGrp OBJECT-TYPE
   SYNTAX      DisplayString
   MAX-ACCESS  read-write
   STATUS      current
   DESCRIPTION
      "Path: pppBundle.editConf.multiclassInterfaces.bridging.bridgeGroup"
   ::= {er1645v2PppBFMcIfEntry 454819840}

er1645v2PppBFMcIfBridgingLimBC OBJECT-TYPE
   SYNTAX      INTEGER
               {
               disabled (0),
               enabled (1)
               }
   MAX-ACCESS  read-write
   STATUS      current
   DESCRIPTION
      "Path: pppBundle.editConf.multiclassInterfaces.bridging.limitBroadcasts

       Possibilities:
               disabled   (0)
               enabled   (1)"
   ::= {er1645v2PppBFMcIfEntry 455081984}

er1645v2PppBFMcIfBridgingPrivateMode OBJECT-TYPE
   SYNTAX      INTEGER
               {
               disabled (0),
               enabled (1)
               }
   MAX-ACCESS  read-write
   STATUS      current
   DESCRIPTION
      "Path: pppBundle.editConf.multiclassInterfaces.bridging.privateMode

       Possibilities:
               disabled   (0)
               enabled   (1)"
   ::= {er1645v2PppBFMcIfEntry 459538432}

er1645v2PppBFMcIfBridgingLearning OBJECT-TYPE
   SYNTAX      INTEGER
               {
               disabled (0),
               enabled (1)
               }
   MAX-ACCESS  read-write
   STATUS      current
   DESCRIPTION
      "Path: pppBundle.editConf.multiclassInterfaces.bridging.learning

       Possibilities:
               disabled   (0)
               enabled   (1)"
   ::= {er1645v2PppBFMcIfEntry 456130560}

er1645v2PppBFMcIfBridgingMaxCacheSize OBJECT-TYPE
   SYNTAX      INTEGER
               {
               unlimited (0)
               }
   MAX-ACCESS  read-write
   STATUS      current
   DESCRIPTION
      "Path: pppBundle.editConf.multiclassInterfaces.bridging.maxCacheSize

       Possibilities:
               unlimited   (0)"
   ::= {er1645v2PppBFMcIfEntry 456392704}

er1645v2PppBFMcIfBridgingRelearnDropOnRelearn OBJECT-TYPE
   SYNTAX      INTEGER
               {
               disabled (0),
               enabled (1)
               }
   MAX-ACCESS  read-write
   STATUS      current
   DESCRIPTION
      "Path: pppBundle.editConf.multiclassInterfaces.bridging.relearn.dropOnRelearn

       Possibilities:
               disabled   (0)
               enabled   (1)"
   ::= {er1645v2PppBFMcIfEntry 456655872}

er1645v2PppBFMcIfBridgingRelearnShutdownThreshold OBJECT-TYPE
   SYNTAX      Integer32
   MAX-ACCESS  read-write
   STATUS      current
   DESCRIPTION
      "Path: pppBundle.editConf.multiclassInterfaces.bridging.relearn.shutdownThreshold"
   ::= {er1645v2PppBFMcIfEntry 456656896}

er1645v2PppBFMcIfBridgingRelearnShutdownTime OBJECT-TYPE
   SYNTAX      TimeTicks
   MAX-ACCESS  read-write
   STATUS      current
   DESCRIPTION
      "Path: pppBundle.editConf.multiclassInterfaces.bridging.relearn.shutdownTime

       Time in centi-second."
   ::= {er1645v2PppBFMcIfEntry 456657920}

er1645v2PppBFMcIfBridgingRelearnLoopDetection OBJECT-TYPE
   SYNTAX      INTEGER
               {
               disabled (0),
               passive (1),
               active (2)
               }
   MAX-ACCESS  read-write
   STATUS      current
   DESCRIPTION
      "Path: pppBundle.editConf.multiclassInterfaces.bridging.relearn.loopDetection

       Possibilities:
               disabled   (0)
               passive   (1)
               active   (2)"
   ::= {er1645v2PppBFMcIfEntry 456658944}

er1645v2PppBFMcIfBridgingRelearnLoopDetectionInterval OBJECT-TYPE
   SYNTAX      TimeTicks
   MAX-ACCESS  read-write
   STATUS      current
   DESCRIPTION
      "Path: pppBundle.editConf.multiclassInterfaces.bridging.relearn.loopDetectionInterval

       Time in centi-second."
   ::= {er1645v2PppBFMcIfEntry 456659968}

er1645v2PppBFMcIfBridgingVlanMemberShip OBJECT-TYPE
   SYNTAX      INTEGER
               {
               all (0),
               none (1),
               grouped (2)
               }
   MAX-ACCESS  read-write
   STATUS      current
   DESCRIPTION
      "Path: pppBundle.editConf.multiclassInterfaces.bridging.vlanMemberShip

       Possibilities:
               all   (0)
               none   (1)
               grouped   (2)"
   ::= {er1645v2PppBFMcIfEntry 457965568}

er1645v2PppBFMcIfBridgingVlTUntaggedAction OBJECT-TYPE
   SYNTAX      INTEGER
               {
               discard (0),
               accept (1),
               tag (2)
               }
   MAX-ACCESS  read-write
   STATUS      current
   DESCRIPTION
      "Path: pppBundle.editConf.multiclassInterfaces.bridging.vlanTagging.untagged.action

       Possibilities:
               discard   (0)
               accept   (1)
               tag   (2)"
   ::= {er1645v2PppBFMcIfEntry 459055104}

er1645v2PppBFMcIfBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: pppBundle.editConf.multiclassInterfaces.bridging.vlanTagging.untagged.tagInfo.tpid

       Possibilities:
               dot1Q   (33024)
               dot1ad   (34984)
               0x9100   (37120)
               0x9200   (37376)
               0x9300   (37632)"
   ::= {er1645v2PppBFMcIfEntry 459059712}

er1645v2PppBFMcIfBridgingVlTUntaggedTagInfoVid OBJECT-TYPE
   SYNTAX      Integer32
   MAX-ACCESS  read-write
   STATUS      current
   DESCRIPTION
      "Path: pppBundle.editConf.multiclassInterfaces.bridging.vlanTagging.untagged.tagInfo.vid"
   ::= {er1645v2PppBFMcIfEntry 459060224}

er1645v2PppBFMcIfBridgingVlTUnknownVlansAction OBJECT-TYPE
   SYNTAX      INTEGER
               {
               discard (0),
               accept (1),
               tag (2)
               }
   MAX-ACCESS  read-write
   STATUS      current
   DESCRIPTION
      "Path: pppBundle.editConf.multiclassInterfaces.bridging.vlanTagging.unknownVlans.action

       Possibilities:
               discard   (0)
               accept   (1)
               tag   (2)"
   ::= {er1645v2PppBFMcIfEntry 459120640}

er1645v2PppBFMcIfBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: pppBundle.editConf.multiclassInterfaces.bridging.vlanTagging.unknownVlans.tagInfo.tpid

       Possibilities:
               dot1Q   (33024)
               dot1ad   (34984)
               0x9100   (37120)
               0x9200   (37376)
               0x9300   (37632)"
   ::= {er1645v2PppBFMcIfEntry 459125248}

er1645v2PppBFMcIfBridgingVlTUnknownVlansTagInfoVid OBJECT-TYPE
   SYNTAX      Integer32
   MAX-ACCESS  read-write
   STATUS      current
   DESCRIPTION
      "Path: pppBundle.editConf.multiclassInterfaces.bridging.vlanTagging.unknownVlans.tagInfo.vid"
   ::= {er1645v2PppBFMcIfEntry 459125760}

er1645v2PppBFMcIfBridgingDot1adType OBJECT-TYPE
   SYNTAX      INTEGER
               {
               slOPTg (0),
               cPort (4),
               sPort (1),
               nni (2)
               }
   MAX-ACCESS  read-write
   STATUS      current
   DESCRIPTION
      "Path: pppBundle.editConf.multiclassInterfaces.bridging.dot1ad.type

       Possibilities:
               <OPT>   (0)
               cPort   (4)
               sPort   (1)
               nni   (2)"
   ::= {er1645v2PppBFMcIfEntry 460850176}

er1645v2PppBFMcIfBridgingPriority OBJECT-TYPE
   SYNTAX      Integer32
   MAX-ACCESS  read-write
   STATUS      current
   DESCRIPTION
      "Path: pppBundle.editConf.multiclassInterfaces.bridging.priority"
   ::= {er1645v2PppBFMcIfEntry 453509120}

er1645v2PppBFMcIfBridgingPathCost OBJECT-TYPE
   SYNTAX      Integer32
   MAX-ACCESS  read-write
   STATUS      current
   DESCRIPTION
      "Path: pppBundle.editConf.multiclassInterfaces.bridging.pathCost"
   ::= {er1645v2PppBFMcIfEntry 453771264}

er1645v2PppBFMcIfBridgingInternalPathCost OBJECT-TYPE
   SYNTAX      Integer32
   MAX-ACCESS  read-write
   STATUS      current
   DESCRIPTION
      "Path: pppBundle.editConf.multiclassInterfaces.bridging.internalPathCost"
   ::= {er1645v2PppBFMcIfEntry 457703424}

er1645v2PppBFMcIfBridgingTCD OBJECT-TYPE
   SYNTAX      INTEGER
               {
               disabled (0),
               enabled (1)
               }
   MAX-ACCESS  read-write
   STATUS      current
   DESCRIPTION
      "Path: pppBundle.editConf.multiclassInterfaces.bridging.topologyChangeDetection

       Possibilities:
               disabled   (0)
               enabled   (1)"
   ::= {er1645v2PppBFMcIfEntry 454033408}

er1645v2PppBFMcIfBridgingRestrictedRole OBJECT-TYPE
   SYNTAX      INTEGER
               {
               disabled (0),
               enabled (1)
               }
   MAX-ACCESS  read-write
   STATUS      current
   DESCRIPTION
      "Path: pppBundle.editConf.multiclassInterfaces.bridging.restrictedRole

       Possibilities:
               disabled   (0)
               enabled   (1)"
   ::= {er1645v2PppBFMcIfEntry 458227712}

er1645v2PppBFMcIfBridgingAdminEdge OBJECT-TYPE
   SYNTAX      INTEGER
               {
               disabled (0),
               enabled (1)
               }
   MAX-ACCESS  read-write
   STATUS      current
   DESCRIPTION
      "Path: pppBundle.editConf.multiclassInterfaces.bridging.adminEdge

       Possibilities:
               disabled   (0)
               enabled   (1)"
   ::= {er1645v2PppBFMcIfEntry 457179136}

er1645v2PppBFMcIfBridgingOamMacDeviceMac OBJECT-TYPE
   SYNTAX      DisplayString
   MAX-ACCESS  read-write
   STATUS      current
   DESCRIPTION
      "Path: pppBundle.editConf.multiclassInterfaces.bridging.ethOam.macAddress.deviceMac"
   ::= {er1645v2PppBFMcIfEntry 458506496}

er1645v2PppBFMcIfBridgingOamMacUserMac OBJECT-TYPE
   SYNTAX      OCTET STRING
   MAX-ACCESS  read-write
   STATUS      current
   DESCRIPTION
      "Path: pppBundle.editConf.multiclassInterfaces.bridging.ethOam.macAddress.userMac

       MAC address."
   ::= {er1645v2PppBFMcIfEntry 458506368}

er1645v2PppBFMcIfBridgingOamMacBridgeMac OBJECT-TYPE
   SYNTAX      DisplayString
   MAX-ACCESS  read-write
   STATUS      current
   DESCRIPTION
      "Path: pppBundle.editConf.multiclassInterfaces.bridging.ethOam.macAddress.bridgeMac"
   ::= {er1645v2PppBFMcIfEntry 458506432}

er1645v2PppBFMcIfBridgingMgmtInline OBJECT-TYPE
   SYNTAX      INTEGER
               {
               disabled (0),
               enabled (1)
               }
   MAX-ACCESS  read-write
   STATUS      current
   DESCRIPTION
      "Path: pppBundle.editConf.multiclassInterfaces.bridging.mgmtInline

       Possibilities:
               disabled   (0)
               enabled   (1)"
   ::= {er1645v2PppBFMcIfEntry 458752000}

er1645v2PppBFMcIfBridgingL2ptMode OBJECT-TYPE
   SYNTAX      INTEGER
               {
               disabled (0),
               enabled (1)
               }
   MAX-ACCESS  read-write
   STATUS      current
   DESCRIPTION
      "Path: pppBundle.editConf.multiclassInterfaces.bridging.l2ProtTunnel.mode

       Possibilities:
               disabled   (0)
               enabled   (1)"
   ::= {er1645v2PppBFMcIfEntry 459292672}

er1645v2PppBFMcIfBridgingL2ptProtocols OBJECT-TYPE
   SYNTAX      Integer32
   MAX-ACCESS  read-write
   STATUS      current
   DESCRIPTION
      "Path: pppBundle.editConf.multiclassInterfaces.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2PppBFMcIfEntry 459309056}

er1645v2PppBFMcIfBridgingL2ptDestMac OBJECT-TYPE
   SYNTAX      OCTET STRING
   MAX-ACCESS  read-write
   STATUS      current
   DESCRIPTION
      "Path: pppBundle.editConf.multiclassInterfaces.bridging.l2ProtTunnel.destinationMac

       MAC address."
   ::= {er1645v2PppBFMcIfEntry 459325440}

er1645v2PppBFMcIfBridgingL2ptCos OBJECT-TYPE
   SYNTAX      INTEGER
               {
               unchanged (255)
               }
   MAX-ACCESS  read-write
   STATUS      current
   DESCRIPTION
      "Path: pppBundle.editConf.multiclassInterfaces.bridging.l2ProtTunnel.cos

       Possibilities:
               unchanged   (255)"
   ::= {er1645v2PppBFMcIfEntry 459341824}

er1645v2PppBFMcIfBridgingL2ptDropThrStp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.stp

       unit name = packets/sec

       Possibilities:
               unlimited   (0)"
   ::= {er1645v2PppBFMcIfEntry 459358272}

er1645v2PppBFMcIfBridgingL2ptDropThrLldp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.lldp

       unit name = packets/sec

       Possibilities:
               unlimited   (0)"
   ::= {er1645v2PppBFMcIfEntry 459358336}

er1645v2PppBFMcIfBridgingL2ptDropThrOam OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.oam

       unit name = packets/sec

       Possibilities:
               unlimited   (0)"
   ::= {er1645v2PppBFMcIfEntry 459358400}

er1645v2PppBFMcIfBridgingL2ptDropThrCdp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.cdp

       unit name = packets/sec

       Possibilities:
               unlimited   (0)"
   ::= {er1645v2PppBFMcIfEntry 459358464}

er1645v2PppBFMcIfBridgingL2ptDropThrVtp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.vtp

       unit name = packets/sec

       Possibilities:
               unlimited   (0)"
   ::= {er1645v2PppBFMcIfEntry 459358528}

er1645v2PppBFMcIfBridgingL2ptDropThrLacp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.lacp

       unit name = packets/sec

       Possibilities:
               unlimited   (0)"
   ::= {er1645v2PppBFMcIfEntry 459358592}

er1645v2PppBFMcIfBridgingL2ptDropThrEfmOam OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.efmOam

       unit name = packets/sec

       Possibilities:
               unlimited   (0)"
   ::= {er1645v2PppBFMcIfEntry 459358656}

er1645v2PppBFMcIfBridgingL2ptDropThrPvst OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.pvst

       unit name = packets/sec

       Possibilities:
               unlimited   (0)"
   ::= {er1645v2PppBFMcIfEntry 459358720}

er1645v2PppBFMcIfBridgingL2ptDropThrMmrp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.mmrp

       unit name = packets/sec

       Possibilities:
               unlimited   (0)"
   ::= {er1645v2PppBFMcIfEntry 459358784}

er1645v2PppBFMcIfBridgingL2ptDropThrMvrp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.mvrp

       unit name = packets/sec

       Possibilities:
               unlimited   (0)"
   ::= {er1645v2PppBFMcIfEntry 459358848}

er1645v2PppBFMcIfBridgingL2ptDropThrGvrp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.gvrp

       unit name = packets/sec

       Possibilities:
               unlimited   (0)"
   ::= {er1645v2PppBFMcIfEntry 459358912}

er1645v2PppBFMcIfBridgingL2ptDropThrGmrp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.gmrp

       unit name = packets/sec

       Possibilities:
               unlimited   (0)"
   ::= {er1645v2PppBFMcIfEntry 459358976}

er1645v2PppBFMcIfBridgingL2ptDropThrDtp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.dtp

       unit name = packets/sec

       Possibilities:
               unlimited   (0)"
   ::= {er1645v2PppBFMcIfEntry 459359040}

er1645v2PppBFMcIfBridgingL2ptDropThrPagp OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.pagp

       unit name = packets/sec

       Possibilities:
               unlimited   (0)"
   ::= {er1645v2PppBFMcIfEntry 459359104}

er1645v2PppBFMcIfBridgingL2ptDropThrUdld OBJECT-TYPE
   SYNTAX      INTEGER
               {
               unlimited (0)
               }
   UNITS       "packets/sec"
   MAX-ACCESS  read-write
   STATUS      current
   DESCRIPTION
      "Path: pppBundle.editConf.multiclassInterfaces.bridging.l2ProtTunnel.dropThresholds.udld

       unit name = packets/sec

       Possibilities:
               unlimited   (0)"
   ::= {er1645v2PppBFMcIfEntry 459359168}

er1645v2PppBFMcIfMulticlassMulticlass OBJECT-TYPE
   SYNTAX      Integer32
   MAX-ACCESS  read-write
   STATUS      current
   DESCRIPTION
      "Path: pppBundle.editConf.multiclassInterfaces.multiclass.multiclass"
   ::= {er1645v2PppBFMcIfEntry 503382016}

er1645v2PppBFMcIfMulticlassDQueue OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: pppBundle.editConf.multiclassInterfaces.multiclass.defaultQueue

       Possibilities:
               queue1   (0)
               queue2   (1)
               queue3   (2)
               queue4   (3)
               queue5   (4)
               lowDelayQueue   (5)
               lowDelay2Queue   (6)
               systemQueue   (7)"
   ::= {er1645v2PppBFMcIfEntry 503447552}

er1645v2PppBFMcIfBridgingVlTVlans OBJECT-TYPE
   SYNTAX      SEQUENCE OF Er1645v2PppBFMcIfBridgingVlTVlansEntry
   MAX-ACCESS  not-accessible
   STATUS      current
   DESCRIPTION
      ""
   ::= {er1645v2PppBFMcIf 459079680}

er1645v2PppBFMcIfBridgingVlTVlansEntry OBJECT-TYPE
   SYNTAX      Er1645v2PppBFMcIfBridgingVlTVlansEntry
   MAX-ACCESS  not-accessible
   STATUS      current
   DESCRIPTION
      ""
   INDEX      { er1645v2PppBFMcIfBridgingVlTVlansGlobalIx,
                er1645v2PppBFMcIfTableIx,
                er1645v2PppBFMcIfBridgingVlTVlansTableIx }
   ::= {er1645v2PppBFMcIfBridgingVlTVlans 1}

Er1645v2PppBFMcIfBridgingVlTVlansEntry ::=
   SEQUENCE
      {
      er1645v2PppBFMcIfBridgingVlTVlansActions
         VariableLengthTableActions,
      er1645v2PppBFMcIfBridgingVlTVlansGlobalIx
         GlobalIndex,
      er1645v2PppBFMcIfBridgingVlTVlansTableIx
         TableIndex,
      er1645v2PppBFMcIfBridgingVlTVlansVid
         Integer32,
      er1645v2PppBFMcIfBridgingVlTVlansEndVid
         Integer32,
      er1645v2PppBFMcIfBridgingVlTVlansAction
         INTEGER,
      er1645v2PppBFMcIfBridgingVlTVlansTagInfoTpid
         INTEGER,
      er1645v2PppBFMcIfBridgingVlTVlansTagInfoVid
         Integer32
      }

er1645v2PppBFMcIfBridgingVlTVlansActions OBJECT-TYPE
   SYNTAX      VariableLengthTableActions
   MAX-ACCESS  read-write
   STATUS      current
   DESCRIPTION
      "By way of this field, some manipulations
       on this table may be performed."
   ::= {er1645v2PppBFMcIfBridgingVlTVlansEntry 2}

er1645v2PppBFMcIfBridgingVlTVlansGlobalIx OBJECT-TYPE
   SYNTAX      GlobalIndex
   MAX-ACCESS  not-accessible
   STATUS      current
   DESCRIPTION
      "The value of the tlsCntTreeGlobalIndex of the MANAGED OBJECT."
   ::= {er1645v2PppBFMcIfBridgingVlTVlansEntry 10}

er1645v2PppBFMcIfBridgingVlTVlansTableIx OBJECT-TYPE
   SYNTAX      TableIndex
   MAX-ACCESS  not-accessible
   STATUS      current
   DESCRIPTION
      ""
   ::= {er1645v2PppBFMcIfBridgingVlTVlansEntry 11}

er1645v2PppBFMcIfBridgingVlTVlansVid OBJECT-TYPE
   SYNTAX      Integer32
   MAX-ACCESS  read-write
   STATUS      current
   DESCRIPTION
      "Path: pppBundle.editConf.multiclassInterfaces.bridging.vlanTagging.vlans.vid"
   ::= {er1645v2PppBFMcIfBridgingVlTVlansEntry 536870912}

er1645v2PppBFMcIfBridgingVlTVlansEndVid OBJECT-TYPE
   SYNTAX      Integer32
   MAX-ACCESS  read-write
   STATUS      current
   DESCRIPTION
      "Path: pppBundle.editConf.multiclassInterfaces.bridging.vlanTagging.vlans.endVid"
   ::= {er1645v2PppBFMcIfBridgingVlTVlansEntry 2147483648}

er1645v2PppBFMcIfBridgingVlTVlansAction OBJECT-TYPE
   SYNTAX      INTEGER
               {
               discard (0),
               accept (1),
               tag (2)
               }
   MAX-ACCESS  read-write
   STATUS      current
   DESCRIPTION
      "Path: pppBundle.editConf.multiclassInterfaces.bridging.vlanTagging.vlans.action

       Possibilities:
               discard   (0)
               accept   (1)
               tag   (2)"
   ::= {er1645v2PppBFMcIfBridgingVlTVlansEntry 1073741824}

er1645v2PppBFMcIfBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: pppBundle.editConf.multiclassInterfaces.bridging.vlanTagging.vlans.tagInfo.tpid

       Possibilities:
               dot1Q   (33024)
               dot1ad   (34984)
               0x9100   (37120)
               0x9200   (37376)
               0x9300   (37632)"
   ::= {er1645v2PppBFMcIfBridgingVlTVlansEntry 1677721600}

er1645v2PppBFMcIfBridgingVlTVlansTagInfoVid OBJECT-TYPE
   SYNTAX      Integer32
   MAX-ACCESS  read-write
   STATUS      current
   DESCRIPTION
      "Path: pppBundle.editConf.multiclassInterfaces.bridging.vlanTagging.vlans.tagInfo.vid"
   ::= {er1645v2PppBFMcIfBridgingVlTVlansEntry 1744830464}



sr1645v2PppBF OBJECT IDENTIFIER ::= {r1645v2PppBF 14}


sr1645v2PppBFSnmpIndex OBJECT IDENTIFIER ::= {sr1645v2PppBF 269}

sr1645v2PppBFSnmpIndexTable OBJECT-TYPE
   SYNTAX      SEQUENCE OF Sr1645v2PppBFSnmpIndexEntry
   MAX-ACCESS  not-accessible
   STATUS      current
   DESCRIPTION
      "SNMP index assigned to this object"
   ::= {sr1645v2PppBFSnmpIndex 1}

sr1645v2PppBFSnmpIndexEntry OBJECT-TYPE
   SYNTAX      Sr1645v2PppBFSnmpIndexEntry
   MAX-ACCESS  not-accessible
   STATUS      current
   DESCRIPTION
      ""
   INDEX      { sr1645v2PppBFSnmpIndexGlobalIx }
   ::= {sr1645v2PppBFSnmpIndexTable 1}

Sr1645v2PppBFSnmpIndexEntry ::=
   SEQUENCE
      {
      sr1645v2PppBFSnmpIndexGlobalIx
         GlobalIndex,
      sr1645v2PppBFSnmpIndexValue
         Integer32
      }

sr1645v2PppBFSnmpIndexGlobalIx OBJECT-TYPE
   SYNTAX      GlobalIndex
   MAX-ACCESS  not-accessible
   STATUS      current
   DESCRIPTION
      "The value of the tlsCntTreeGlobalIndex of the MANAGED OBJECT."
   ::= {sr1645v2PppBFSnmpIndexEntry 10}

sr1645v2PppBFSnmpIndexValue OBJECT-TYPE
   SYNTAX      Integer32
   MAX-ACCESS  read-only
   STATUS      current
   DESCRIPTION
      "Path: pppBundle.status.snmpIndex"
   ::= {sr1645v2PppBFSnmpIndexEntry 2147483648}


sr1645v2PppBFIp OBJECT IDENTIFIER ::= {sr1645v2PppBF 6}

sr1645v2PppBFIpSSCTable OBJECT-TYPE
   SYNTAX      SEQUENCE OF Sr1645v2PppBFIpEntry
   MAX-ACCESS  not-accessible
   STATUS      current
   DESCRIPTION
      "ip interface config parameters"
   ::= {sr1645v2PppBFIp 1}

sr1645v2PppBFIpEntry OBJECT-TYPE
   SYNTAX      Sr1645v2PppBFIpEntry
   MAX-ACCESS  not-accessible
   STATUS      current
   DESCRIPTION
      ""
   INDEX      { sr1645v2PppBFIpGlobalIx }
   ::= {sr1645v2PppBFIpSSCTable 1}

Sr1645v2PppBFIpEntry ::=
   SEQUENCE
      {
      sr1645v2PppBFIpGlobalIx
         GlobalIndex,
      sr1645v2PppBFIpStatus
         INTEGER,
      sr1645v2PppBFIpAddress
         IpAddress,
      sr1645v2PppBFIpNetMask
         IpAddress,
      sr1645v2PppBFIpRemote
         IpAddress
      }

sr1645v2PppBFIpGlobalIx OBJECT-TYPE
   SYNTAX      GlobalIndex
   MAX-ACCESS  not-accessible
   STATUS      current
   DESCRIPTION
      "The value of the tlsCntTreeGlobalIndex of the MANAGED OBJECT."
   ::= {sr1645v2PppBFIpEntry 10}

sr1645v2PppBFIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: pppBundle.status.ip.status

       Possibilities:
               up   (1)
               down   (2)
               testing   (3)
               unknown   (4)
               dormant   (5)
               notPresent   (6)
               lowerLayerDown   (7)"
   ::= {sr1645v2PppBFIpEntry 1795162112}

sr1645v2PppBFIpAddress OBJECT-TYPE
   SYNTAX      IpAddress
   MAX-ACCESS  read-only
   STATUS      current
   DESCRIPTION
      "Path: pppBundle.status.ip.address"
   ::= {sr1645v2PppBFIpEntry 2030043136}

sr1645v2PppBFIpNetMask OBJECT-TYPE
   SYNTAX      IpAddress
   MAX-ACCESS  read-only
   STATUS      current
   DESCRIPTION
      "Path: pppBundle.status.ip.netMask"
   ::= {sr1645v2PppBFIpEntry 2063597568}

sr1645v2PppBFIpRemote OBJECT-TYPE
   SYNTAX      IpAddress
   MAX-ACCESS  read-only
   STATUS      current
   DESCRIPTION
      "Path: pppBundle.status.ip.remote"
   ::= {sr1645v2PppBFIpEntry 301989888}


sr1645v2PppBFIpV6 OBJECT IDENTIFIER ::= {sr1645v2PppBF 47}

sr1645v2PppBFIpV6SSCTable OBJECT-TYPE
   SYNTAX      SEQUENCE OF Sr1645v2PppBFIpV6Entry
   MAX-ACCESS  not-accessible
   STATUS      current
   DESCRIPTION
      "IPv6 interface config parameters"
   ::= {sr1645v2PppBFIpV6 1}

sr1645v2PppBFIpV6Entry OBJECT-TYPE
   SYNTAX      Sr1645v2PppBFIpV6Entry
   MAX-ACCESS  not-accessible
   STATUS      current
   DESCRIPTION
      ""
   INDEX      { sr1645v2PppBFIpV6GlobalIx }
   ::= {sr1645v2PppBFIpV6SSCTable 1}

Sr1645v2PppBFIpV6Entry ::=
   SEQUENCE
      {
      sr1645v2PppBFIpV6GlobalIx
         GlobalIndex,
      sr1645v2PppBFIpV6State
         INTEGER,
      sr1645v2PppBFIpV6InterfaceId
         OCTET STRING,
      sr1645v2PppBFIpV6LinkMtu
         Integer32,
      sr1645v2PppBFIpV6HopLimit
         Integer32,
      sr1645v2PppBFIpV6DhcpIaid
         Counter32,
      sr1645v2PppBFIpV6RaRcvOption
         Integer32
      }

sr1645v2PppBFIpV6GlobalIx OBJECT-TYPE
   SYNTAX      GlobalIndex
   MAX-ACCESS  not-accessible
   STATUS      current
   DESCRIPTION
      "The value of the tlsCntTreeGlobalIndex of the MANAGED OBJECT."
   ::= {sr1645v2PppBFIpV6Entry 10}

sr1645v2PppBFIpV6State OBJECT-TYPE
   SYNTAX      INTEGER
               {
               disabled (0),
               enabled (1)
               }
   MAX-ACCESS  read-only
   STATUS      current
   DESCRIPTION
      "Path: pppBundle.status.ipV6.state

       Possibilities:
               disabled   (0)
               enabled   (1)"
   ::= {sr1645v2PppBFIpV6Entry 16777216}

sr1645v2PppBFIpV6InterfaceId OBJECT-TYPE
   SYNTAX      OCTET STRING
   MAX-ACCESS  read-only
   STATUS      current
   DESCRIPTION
      "Path: pppBundle.status.ipV6.interfaceId"
   ::= {sr1645v2PppBFIpV6Entry 33554432}

sr1645v2PppBFIpV6LinkMtu OBJECT-TYPE
   SYNTAX      Integer32
   MAX-ACCESS  read-only
   STATUS      current
   DESCRIPTION
      "Path: pppBundle.status.ipV6.linkMtu"
   ::= {sr1645v2PppBFIpV6Entry 67108864}

sr1645v2PppBFIpV6HopLimit OBJECT-TYPE
   SYNTAX      Integer32
   MAX-ACCESS  read-only
   STATUS      current
   DESCRIPTION
      "Path: pppBundle.status.ipV6.hopLimit"
   ::= {sr1645v2PppBFIpV6Entry 83886080}

sr1645v2PppBFIpV6DhcpIaid OBJECT-TYPE
   SYNTAX      Counter32
   MAX-ACCESS  read-only
   STATUS      current
   DESCRIPTION
      "Path: pppBundle.status.ipV6.dhcp.iaid

       32 bit unsigned wrappable counter."
   ::= {sr1645v2PppBFIpV6Entry 100728832}

sr1645v2PppBFIpV6RaRcvOption OBJECT-TYPE
   SYNTAX      Integer32
   MAX-ACCESS  read-only
   STATUS      current
   DESCRIPTION
      "Path: pppBundle.status.ipV6.raRcvOption

       Bit meanings:
               bit 0 = linkMtu,
               bit 1 = srcLinkLayer,
               bit 2 = prefixInfo,
               bit 3 = rdnss,
               bit 4 = dnssl"
   ::= {sr1645v2PppBFIpV6Entry 117440512}

sr1645v2PppBFIpV6Addresses OBJECT-TYPE
   SYNTAX      SEQUENCE OF Sr1645v2PppBFIpV6AddressesEntry
   MAX-ACCESS  not-accessible
   STATUS      current
   DESCRIPTION
      ""
   ::= {sr1645v2PppBFIpV6 50331648}

sr1645v2PppBFIpV6AddressesEntry OBJECT-TYPE
   SYNTAX      Sr1645v2PppBFIpV6AddressesEntry
   MAX-ACCESS  not-accessible
   STATUS      current
   DESCRIPTION
      ""
   INDEX      { sr1645v2PppBFIpV6AddressesGlobalIx,
                sr1645v2PppBFIpV6AddressesTableIx }
   ::= {sr1645v2PppBFIpV6Addresses 1}

Sr1645v2PppBFIpV6AddressesEntry ::=
   SEQUENCE
      {
      sr1645v2PppBFIpV6AddressesGlobalIx
         GlobalIndex,
      sr1645v2PppBFIpV6AddressesTableIx
         TableIndex,
      sr1645v2PppBFIpV6AddressesAddress
         Ipv6Address,
      sr1645v2PppBFIpV6AddressesPrefixLength
         Integer32,
      sr1645v2PppBFIpV6AddressesStatus
         INTEGER,
      sr1645v2PppBFIpV6AddressesOrigin
         INTEGER,
      sr1645v2PppBFIpV6AddressesFlagsInterfaceId
         INTEGER,
      sr1645v2PppBFIpV6AddressesFlagsAnycast
         INTEGER,
      sr1645v2PppBFIpV6AddressesTimersValidLifeTime
         TimeTicks,
      sr1645v2PppBFIpV6AddressesTimersPrefLifeTime
         TimeTicks
      }

sr1645v2PppBFIpV6AddressesGlobalIx OBJECT-TYPE
   SYNTAX      GlobalIndex
   MAX-ACCESS  not-accessible
   STATUS      current
   DESCRIPTION
      "The value of the tlsCntTreeGlobalIndex of the MANAGED OBJECT."
   ::= {sr1645v2PppBFIpV6AddressesEntry 10}

sr1645v2PppBFIpV6AddressesTableIx OBJECT-TYPE
   SYNTAX      TableIndex
   MAX-ACCESS  not-accessible
   STATUS      current
   DESCRIPTION
      ""
   ::= {sr1645v2PppBFIpV6AddressesEntry 11}

sr1645v2PppBFIpV6AddressesAddress OBJECT-TYPE
   SYNTAX      Ipv6Address
   MAX-ACCESS  read-only
   STATUS      current
   DESCRIPTION
      "Path: pppBundle.status.ipV6.addresses.address

       ipv6 address"
   ::= {sr1645v2PppBFIpV6AddressesEntry 16777216}

sr1645v2PppBFIpV6AddressesPrefixLength OBJECT-TYPE
   SYNTAX      Integer32
   MAX-ACCESS  read-only
   STATUS      current
   DESCRIPTION
      "Path: pppBundle.status.ipV6.addresses.prefixLength"
   ::= {sr1645v2PppBFIpV6AddressesEntry 33554432}

sr1645v2PppBFIpV6AddressesStatus OBJECT-TYPE
   SYNTAX      INTEGER
               {
               invalid (0),
               tentative (1),
               deprecated (2),
               preferred (3)
               }
   MAX-ACCESS  read-only
   STATUS      current
   DESCRIPTION
      "Path: pppBundle.status.ipV6.addresses.status

       Possibilities:
               invalid   (0)
               tentative   (1)
               deprecated   (2)
               preferred   (3)"
   ::= {sr1645v2PppBFIpV6AddressesEntry 50331648}

sr1645v2PppBFIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: pppBundle.status.ipV6.addresses.origin

       Possibilities:
               unknown   (0)
               manual   (1)
               generalPrefix   (2)
               statelessAuto   (3)
               statefullAuto   (4)"
   ::= {sr1645v2PppBFIpV6AddressesEntry 67108864}

sr1645v2PppBFIpV6AddressesFlagsInterfaceId OBJECT-TYPE
   SYNTAX      INTEGER
               {
               no (0),
               yes (1)
               }
   MAX-ACCESS  read-only
   STATUS      current
   DESCRIPTION
      "Path: pppBundle.status.ipV6.addresses.flags.interfaceId

       Possibilities:
               no   (0)
               yes   (1)"
   ::= {sr1645v2PppBFIpV6AddressesEntry 83951616}

sr1645v2PppBFIpV6AddressesFlagsAnycast OBJECT-TYPE
   SYNTAX      INTEGER
               {
               no (0),
               yes (1)
               }
   MAX-ACCESS  read-only
   STATUS      current
   DESCRIPTION
      "Path: pppBundle.status.ipV6.addresses.flags.anycast

       Possibilities:
               no   (0)
               yes   (1)"
   ::= {sr1645v2PppBFIpV6AddressesEntry 84017152}

sr1645v2PppBFIpV6AddressesTimersValidLifeTime OBJECT-TYPE
   SYNTAX      TimeTicks
   MAX-ACCESS  read-only
   STATUS      current
   DESCRIPTION
      "Path: pppBundle.status.ipV6.addresses.timers.validLifeTime

       Time in centi-second."
   ::= {sr1645v2PppBFIpV6AddressesEntry 100794368}

sr1645v2PppBFIpV6AddressesTimersPrefLifeTime OBJECT-TYPE
   SYNTAX      TimeTicks
   MAX-ACCESS  read-only
   STATUS      current
   DESCRIPTION
      "Path: pppBundle.status.ipV6.addresses.timers.prefLifeTime

       Time in centi-second."
   ::= {sr1645v2PppBFIpV6AddressesEntry 100728832}


sr1645v2PppBFBrS OBJECT IDENTIFIER ::= {sr1645v2PppBF 7}

sr1645v2PppBFBrSSSCTable OBJECT-TYPE
   SYNTAX      SEQUENCE OF Sr1645v2PppBFBrSEntry
   MAX-ACCESS  not-accessible
   STATUS      current
   DESCRIPTION
      "spanning tree status PPP interface"
   ::= {sr1645v2PppBFBrS 1}

sr1645v2PppBFBrSEntry OBJECT-TYPE
   SYNTAX      Sr1645v2PppBFBrSEntry
   MAX-ACCESS  not-accessible
   STATUS      current
   DESCRIPTION
      ""
   INDEX      { sr1645v2PppBFBrSGlobalIx }
   ::= {sr1645v2PppBFBrSSSCTable 1}

Sr1645v2PppBFBrSEntry ::=
   SEQUENCE
      {
      sr1645v2PppBFBrSGlobalIx
         GlobalIndex,
      sr1645v2PppBFBrSState
         INTEGER,
      sr1645v2PppBFBrSSpanningTreePortRole
         INTEGER,
      sr1645v2PppBFBrSSpanningTreePortId
         Integer32,
      sr1645v2PppBFBrSSpanningTreePpCostExtPathCost
         Integer32,
      sr1645v2PppBFBrSSpanningTreePpCostIntPathCost
         Integer32,
      sr1645v2PppBFBrSSpanningTreeExtRpCost
         Integer32,
      sr1645v2PppBFBrSSpanningTreeIntRpCost
         Integer32,
      sr1645v2PppBFBrSSpanningTreeDesBrIdPriority
         Integer32,
      sr1645v2PppBFBrSSpanningTreeDesBrIdMacAddress
         OCTET STRING,
      sr1645v2PppBFBrSSpanningTreeDesPrtId
         Integer32,
      sr1645v2PppBFBrSSpanningTreeDesInt
         INTEGER,
      sr1645v2PppBFBrSSpanningTreeEdgeDetection
         INTEGER
      }

sr1645v2PppBFBrSGlobalIx OBJECT-TYPE
   SYNTAX      GlobalIndex
   MAX-ACCESS  not-accessible
   STATUS      current
   DESCRIPTION
      "The value of the tlsCntTreeGlobalIndex of the MANAGED OBJECT."
   ::= {sr1645v2PppBFBrSEntry 10}

sr1645v2PppBFBrSState OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: pppBundle.status.bridging.state

       Possibilities:
               disabled   (0)
               discarding   (1)
               learning   (2)
               forwarding   (3)
               backupBlockedIntfDown   (256)
               backupBlockedIntfUp   (259)
               shutdown   (255)"
   ::= {sr1645v2PppBFBrSEntry 16777216}

sr1645v2PppBFBrSSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: pppBundle.status.bridging.spanningTree.portRole

       Possibilities:
               none   (0)
               root   (1)
               designated   (2)
               alternate   (3)
               backup   (4)
               disabled   (5)
               master   (6)"
   ::= {sr1645v2PppBFBrSEntry 33619968}

sr1645v2PppBFBrSSpanningTreePortId OBJECT-TYPE
   SYNTAX      Integer32
   MAX-ACCESS  read-only
   STATUS      current
   DESCRIPTION
      "Path: pppBundle.status.bridging.spanningTree.portId"
   ::= {sr1645v2PppBFBrSEntry 33685504}

sr1645v2PppBFBrSSpanningTreePpCostExtPathCost OBJECT-TYPE
   SYNTAX      Integer32
   MAX-ACCESS  read-only
   STATUS      current
   DESCRIPTION
      "Path: pppBundle.status.bridging.spanningTree.portPathCosts.extPathCost"
   ::= {sr1645v2PppBFBrSEntry 33751296}

sr1645v2PppBFBrSSpanningTreePpCostIntPathCost OBJECT-TYPE
   SYNTAX      Integer32
   MAX-ACCESS  read-only
   STATUS      current
   DESCRIPTION
      "Path: pppBundle.status.bridging.spanningTree.portPathCosts.intPathCost"
   ::= {sr1645v2PppBFBrSEntry 33751552}

sr1645v2PppBFBrSSpanningTreeExtRpCost OBJECT-TYPE
   SYNTAX      Integer32
   MAX-ACCESS  read-only
   STATUS      current
   DESCRIPTION
      "Path: pppBundle.status.bridging.spanningTree.extRootPathCost"
   ::= {sr1645v2PppBFBrSEntry 33816576}

sr1645v2PppBFBrSSpanningTreeIntRpCost OBJECT-TYPE
   SYNTAX      Integer32
   MAX-ACCESS  read-only
   STATUS      current
   DESCRIPTION
      "Path: pppBundle.status.bridging.spanningTree.intRootPathCost"
   ::= {sr1645v2PppBFBrSEntry 33882112}

sr1645v2PppBFBrSSpanningTreeDesBrIdPriority OBJECT-TYPE
   SYNTAX      Integer32
   MAX-ACCESS  read-only
   STATUS      current
   DESCRIPTION
      "Path: pppBundle.status.bridging.spanningTree.designatedBridgeId.priority"
   ::= {sr1645v2PppBFBrSEntry 33947904}

sr1645v2PppBFBrSSpanningTreeDesBrIdMacAddress OBJECT-TYPE
   SYNTAX      OCTET STRING
   MAX-ACCESS  read-only
   STATUS      current
   DESCRIPTION
      "Path: pppBundle.status.bridging.spanningTree.designatedBridgeId.macAddress

       MAC address."
   ::= {sr1645v2PppBFBrSEntry 33948160}

sr1645v2PppBFBrSSpanningTreeDesPrtId OBJECT-TYPE
   SYNTAX      Integer32
   MAX-ACCESS  read-only
   STATUS      current
   DESCRIPTION
      "Path: pppBundle.status.bridging.spanningTree.designatedPortId"
   ::= {sr1645v2PppBFBrSEntry 34013184}

sr1645v2PppBFBrSSpanningTreeDesInt OBJECT-TYPE
   SYNTAX      INTEGER
               {
               no (0),
               yes (1)
               }
   MAX-ACCESS  read-only
   STATUS      current
   DESCRIPTION
      "Path: pppBundle.status.bridging.spanningTree.designatedOrInternal

       Possibilities:
               no   (0)
               yes   (1)"
   ::= {sr1645v2PppBFBrSEntry 34078720}

sr1645v2PppBFBrSSpanningTreeEdgeDetection OBJECT-TYPE
   SYNTAX      INTEGER
               {
               none (0),
               edge (1),
               notEdge (2)
               }
   MAX-ACCESS  read-only
   STATUS      current
   DESCRIPTION
      "Path: pppBundle.status.bridging.spanningTree.edgeDetection

       Possibilities:
               none   (0)
               edge   (1)
               notEdge   (2)"
   ::= {sr1645v2PppBFBrSEntry 34144256}


sr1645v2PppBFSpeed OBJECT IDENTIFIER ::= {sr1645v2PppBF 104}

sr1645v2PppBFSpeedTable OBJECT-TYPE
   SYNTAX      SEQUENCE OF Sr1645v2PppBFSpeedEntry
   MAX-ACCESS  not-accessible
   STATUS      current
   DESCRIPTION
      "ifSpeed"
   ::= {sr1645v2PppBFSpeed 1}

sr1645v2PppBFSpeedEntry OBJECT-TYPE
   SYNTAX      Sr1645v2PppBFSpeedEntry
   MAX-ACCESS  not-accessible
   STATUS      current
   DESCRIPTION
      ""
   INDEX      { sr1645v2PppBFSpeedGlobalIx }
   ::= {sr1645v2PppBFSpeedTable 1}

Sr1645v2PppBFSpeedEntry ::=
   SEQUENCE
      {
      sr1645v2PppBFSpeedGlobalIx
         GlobalIndex,
      sr1645v2PppBFSpeedValue
         Gauge32
      }

sr1645v2PppBFSpeedGlobalIx OBJECT-TYPE
   SYNTAX      GlobalIndex
   MAX-ACCESS  not-accessible
   STATUS      current
   DESCRIPTION
      "The value of the tlsCntTreeGlobalIndex of the MANAGED OBJECT."
   ::= {sr1645v2PppBFSpeedEntry 10}

sr1645v2PppBFSpeedValue OBJECT-TYPE
   SYNTAX      Gauge32
   MAX-ACCESS  read-only
   STATUS      current
   DESCRIPTION
      "Path: pppBundle.status.ifSpeed

       32 bit unsigned gauge value."
   ::= {sr1645v2PppBFSpeedEntry 2147483648}


sr1645v2PppBFMembers OBJECT IDENTIFIER ::= {sr1645v2PppBF 12}

sr1645v2PppBFMembersSSCTable OBJECT-TYPE
   SYNTAX      SEQUENCE OF Sr1645v2PppBFMembersEntry
   MAX-ACCESS  not-accessible
   STATUS      current
   DESCRIPTION
      ""
   ::= {sr1645v2PppBFMembers 1}

sr1645v2PppBFMembersEntry OBJECT-TYPE
   SYNTAX      Sr1645v2PppBFMembersEntry
   MAX-ACCESS  not-accessible
   STATUS      current
   DESCRIPTION
      ""
   INDEX      { sr1645v2PppBFMembersGlobalIx,
                sr1645v2PppBFMembersTableIx }
   ::= {sr1645v2PppBFMembersSSCTable 1}

Sr1645v2PppBFMembersEntry ::=
   SEQUENCE
      {
      sr1645v2PppBFMembersGlobalIx
         GlobalIndex,
      sr1645v2PppBFMembersTableIx
         TableIndex,
      sr1645v2PppBFMembersDescr
         DisplayString,
      sr1645v2PppBFMembersMemberStatus
         INTEGER,
      sr1645v2PppBFMembersIfLastChange
         TimeTicks,
      sr1645v2PppBFMembersIfLastChangeDate
         DisplayString,
      sr1645v2PppBFMembersSpeed
         Gauge32,
      sr1645v2PppBFMembersMyMru
         Integer32,
      sr1645v2PppBFMembersHisMru
         Integer32,
      sr1645v2PppBFMembersMyMrru
         Integer32,
      sr1645v2PppBFMembersHisMrru
         Integer32
      }

sr1645v2PppBFMembersGlobalIx OBJECT-TYPE
   SYNTAX      GlobalIndex
   MAX-ACCESS  not-accessible
   STATUS      current
   DESCRIPTION
      "The value of the tlsCntTreeGlobalIndex of the MANAGED OBJECT."
   ::= {sr1645v2PppBFMembersEntry 10}

sr1645v2PppBFMembersTableIx OBJECT-TYPE
   SYNTAX      TableIndex
   MAX-ACCESS  not-accessible
   STATUS      current
   DESCRIPTION
      ""
   ::= {sr1645v2PppBFMembersEntry 11}

sr1645v2PppBFMembersDescr OBJECT-TYPE
   SYNTAX      DisplayString
   MAX-ACCESS  read-only
   STATUS      current
   DESCRIPTION
      "Path: pppBundle.status.members.ifDescr"
   ::= {sr1645v2PppBFMembersEntry 1694498816}

sr1645v2PppBFMembersMemberStatus OBJECT-TYPE
   SYNTAX      INTEGER
               {
               notFound (0),
               joined (1),
               notJoined (2)
               }
   MAX-ACCESS  read-only
   STATUS      current
   DESCRIPTION
      "Path: pppBundle.status.members.memberStatus

       Possibilities:
               notFound   (0)
               joined   (1)
               notJoined   (2)"
   ::= {sr1645v2PppBFMembersEntry 1795162112}

sr1645v2PppBFMembersIfLastChange OBJECT-TYPE
   SYNTAX      TimeTicks
   MAX-ACCESS  read-only
   STATUS      current
   DESCRIPTION
      "Path: pppBundle.status.members.ifLastChange

       Time in centi-second."
   ::= {sr1645v2PppBFMembersEntry 1811939328}

sr1645v2PppBFMembersIfLastChangeDate OBJECT-TYPE
   SYNTAX      DisplayString
   MAX-ACCESS  read-only
   STATUS      current
   DESCRIPTION
      "Path: pppBundle.status.members.ifLastChangeDate"
   ::= {sr1645v2PppBFMembersEntry 3070230528}

sr1645v2PppBFMembersSpeed OBJECT-TYPE
   SYNTAX      Gauge32
   MAX-ACCESS  read-only
   STATUS      current
   DESCRIPTION
      "Path: pppBundle.status.members.ifSpeed

       32 bit unsigned gauge value."
   ::= {sr1645v2PppBFMembersEntry 1744830464}

sr1645v2PppBFMembersMyMru OBJECT-TYPE
   SYNTAX      Integer32
   MAX-ACCESS  read-only
   STATUS      current
   DESCRIPTION
      "Path: pppBundle.status.members.myMru"
   ::= {sr1645v2PppBFMembersEntry 16777216}

sr1645v2PppBFMembersHisMru OBJECT-TYPE
   SYNTAX      Integer32
   MAX-ACCESS  read-only
   STATUS      current
   DESCRIPTION
      "Path: pppBundle.status.members.hisMru"
   ::= {sr1645v2PppBFMembersEntry 33554432}

sr1645v2PppBFMembersMyMrru OBJECT-TYPE
   SYNTAX      Integer32
   MAX-ACCESS  read-only
   STATUS      current
   DESCRIPTION
      "Path: pppBundle.status.members.myMrru"
   ::= {sr1645v2PppBFMembersEntry 50331648}

sr1645v2PppBFMembersHisMrru OBJECT-TYPE
   SYNTAX      Integer32
   MAX-ACCESS  read-only
   STATUS      current
   DESCRIPTION
      "Path: pppBundle.status.members.hisMrru"
   ::= {sr1645v2PppBFMembersEntry 67108864}


sr1645v2PppBFIpcpState OBJECT IDENTIFIER ::= {sr1645v2PppBF 11}

sr1645v2PppBFIpcpStateTable OBJECT-TYPE
   SYNTAX      SEQUENCE OF Sr1645v2PppBFIpcpStateEntry
   MAX-ACCESS  not-accessible
   STATUS      current
   DESCRIPTION
      "pppState"
   ::= {sr1645v2PppBFIpcpState 1}

sr1645v2PppBFIpcpStateEntry OBJECT-TYPE
   SYNTAX      Sr1645v2PppBFIpcpStateEntry
   MAX-ACCESS  not-accessible
   STATUS      current
   DESCRIPTION
      ""
   INDEX      { sr1645v2PppBFIpcpStateGlobalIx }
   ::= {sr1645v2PppBFIpcpStateTable 1}

Sr1645v2PppBFIpcpStateEntry ::=
   SEQUENCE
      {
      sr1645v2PppBFIpcpStateGlobalIx
         GlobalIndex,
      sr1645v2PppBFIpcpStateValue
         INTEGER
      }

sr1645v2PppBFIpcpStateGlobalIx OBJECT-TYPE
   SYNTAX      GlobalIndex
   MAX-ACCESS  not-accessible
   STATUS      current
   DESCRIPTION
      "The value of the tlsCntTreeGlobalIndex of the MANAGED OBJECT."
   ::= {sr1645v2PppBFIpcpStateEntry 10}

sr1645v2PppBFIpcpStateValue OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pppBundle.status.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppBFIpcpStateEntry 2147483648}


sr1645v2PppBFIp6cpState OBJECT IDENTIFIER ::= {sr1645v2PppBF 44}

sr1645v2PppBFIp6cpStateTable OBJECT-TYPE
   SYNTAX      SEQUENCE OF Sr1645v2PppBFIp6cpStateEntry
   MAX-ACCESS  not-accessible
   STATUS      current
   DESCRIPTION
      "pppState"
   ::= {sr1645v2PppBFIp6cpState 1}

sr1645v2PppBFIp6cpStateEntry OBJECT-TYPE
   SYNTAX      Sr1645v2PppBFIp6cpStateEntry
   MAX-ACCESS  not-accessible
   STATUS      current
   DESCRIPTION
      ""
   INDEX      { sr1645v2PppBFIp6cpStateGlobalIx }
   ::= {sr1645v2PppBFIp6cpStateTable 1}

Sr1645v2PppBFIp6cpStateEntry ::=
   SEQUENCE
      {
      sr1645v2PppBFIp6cpStateGlobalIx
         GlobalIndex,
      sr1645v2PppBFIp6cpStateValue
         INTEGER
      }

sr1645v2PppBFIp6cpStateGlobalIx OBJECT-TYPE
   SYNTAX      GlobalIndex
   MAX-ACCESS  not-accessible
   STATUS      current
   DESCRIPTION
      "The value of the tlsCntTreeGlobalIndex of the MANAGED OBJECT."
   ::= {sr1645v2PppBFIp6cpStateEntry 10}

sr1645v2PppBFIp6cpStateValue OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pppBundle.status.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppBFIp6cpStateEntry 2147483648}


sr1645v2PppBFIpcpMy OBJECT IDENTIFIER ::= {sr1645v2PppBF 15}

sr1645v2PppBFIpcpMySSCTable OBJECT-TYPE
   SYNTAX      SEQUENCE OF Sr1645v2PppBFIpcpMyEntry
   MAX-ACCESS  not-accessible
   STATUS      current
   DESCRIPTION
      "ipcpOptions"
   ::= {sr1645v2PppBFIpcpMy 1}

sr1645v2PppBFIpcpMyEntry OBJECT-TYPE
   SYNTAX      Sr1645v2PppBFIpcpMyEntry
   MAX-ACCESS  not-accessible
   STATUS      current
   DESCRIPTION
      ""
   INDEX      { sr1645v2PppBFIpcpMyGlobalIx,
                sr1645v2PppBFIpcpMyTableIx }
   ::= {sr1645v2PppBFIpcpMySSCTable 1}

Sr1645v2PppBFIpcpMyEntry ::=
   SEQUENCE
      {
      sr1645v2PppBFIpcpMyGlobalIx
         GlobalIndex,
      sr1645v2PppBFIpcpMyTableIx
         TableIndex,
      sr1645v2PppBFIpcpMyOption
         INTEGER,
      sr1645v2PppBFIpcpMyLength
         Integer32,
      sr1645v2PppBFIpcpMyValue
         OCTET STRING
      }

sr1645v2PppBFIpcpMyGlobalIx OBJECT-TYPE
   SYNTAX      GlobalIndex
   MAX-ACCESS  not-accessible
   STATUS      current
   DESCRIPTION
      "The value of the tlsCntTreeGlobalIndex of the MANAGED OBJECT."
   ::= {sr1645v2PppBFIpcpMyEntry 10}

sr1645v2PppBFIpcpMyTableIx OBJECT-TYPE
   SYNTAX      TableIndex
   MAX-ACCESS  not-accessible
   STATUS      current
   DESCRIPTION
      ""
   ::= {sr1645v2PppBFIpcpMyEntry 11}

sr1645v2PppBFIpcpMyOption OBJECT-TYPE
   SYNTAX      INTEGER
               {
               iPmVSO (0),
               iPmAddresses (1),
               iPmCompressionmProtocol (2),
               iPmAddress (3),
               iPmPrimaryDNS (129),
               iPmPrimaryNBNS (130),
               iPmSecondaryDNS (131),
               iPmSecondaryNBNS (132)
               }
   MAX-ACCESS  read-only
   STATUS      current
   DESCRIPTION
      "Path: pppBundle.status.ipcpMyOptions.option

       Possibilities:
               IP-VSO   (0)
               IP-Addresses   (1)
               IP-Compression-Protocol   (2)
               IP-Address   (3)
               IP-PrimaryDNS   (129)
               IP-PrimaryNBNS   (130)
               IP-SecondaryDNS   (131)
               IP-SecondaryNBNS   (132)"
   ::= {sr1645v2PppBFIpcpMyEntry 16777216}

sr1645v2PppBFIpcpMyLength OBJECT-TYPE
   SYNTAX      Integer32
   MAX-ACCESS  read-only
   STATUS      current
   DESCRIPTION
      "Path: pppBundle.status.ipcpMyOptions.length"
   ::= {sr1645v2PppBFIpcpMyEntry 33554432}

sr1645v2PppBFIpcpMyValue OBJECT-TYPE
   SYNTAX      OCTET STRING
   MAX-ACCESS  read-only
   STATUS      current
   DESCRIPTION
      "Path: pppBundle.status.ipcpMyOptions.value"
   ::= {sr1645v2PppBFIpcpMyEntry 50331648}


sr1645v2PppBFIpcpHis OBJECT IDENTIFIER ::= {sr1645v2PppBF 16}

sr1645v2PppBFIpcpHisSSCTable OBJECT-TYPE
   SYNTAX      SEQUENCE OF Sr1645v2PppBFIpcpHisEntry
   MAX-ACCESS  not-accessible
   STATUS      current
   DESCRIPTION
      "ipcpOptions"
   ::= {sr1645v2PppBFIpcpHis 1}

sr1645v2PppBFIpcpHisEntry OBJECT-TYPE
   SYNTAX      Sr1645v2PppBFIpcpHisEntry
   MAX-ACCESS  not-accessible
   STATUS      current
   DESCRIPTION
      ""
   INDEX      { sr1645v2PppBFIpcpHisGlobalIx,
                sr1645v2PppBFIpcpHisTableIx }
   ::= {sr1645v2PppBFIpcpHisSSCTable 1}

Sr1645v2PppBFIpcpHisEntry ::=
   SEQUENCE
      {
      sr1645v2PppBFIpcpHisGlobalIx
         GlobalIndex,
      sr1645v2PppBFIpcpHisTableIx
         TableIndex,
      sr1645v2PppBFIpcpHisOption
         INTEGER,
      sr1645v2PppBFIpcpHisLength
         Integer32,
      sr1645v2PppBFIpcpHisValue
         OCTET STRING
      }

sr1645v2PppBFIpcpHisGlobalIx OBJECT-TYPE
   SYNTAX      GlobalIndex
   MAX-ACCESS  not-accessible
   STATUS      current
   DESCRIPTION
      "The value of the tlsCntTreeGlobalIndex of the MANAGED OBJECT."
   ::= {sr1645v2PppBFIpcpHisEntry 10}

sr1645v2PppBFIpcpHisTableIx OBJECT-TYPE
   SYNTAX      TableIndex
   MAX-ACCESS  not-accessible
   STATUS      current
   DESCRIPTION
      ""
   ::= {sr1645v2PppBFIpcpHisEntry 11}

sr1645v2PppBFIpcpHisOption OBJECT-TYPE
   SYNTAX      INTEGER
               {
               iPmVSO (0),
               iPmAddresses (1),
               iPmCompressionmProtocol (2),
               iPmAddress (3),
               iPmPrimaryDNS (129),
               iPmPrimaryNBNS (130),
               iPmSecondaryDNS (131),
               iPmSecondaryNBNS (132)
               }
   MAX-ACCESS  read-only
   STATUS      current
   DESCRIPTION
      "Path: pppBundle.status.ipcpHisOptions.option

       Possibilities:
               IP-VSO   (0)
               IP-Addresses   (1)
               IP-Compression-Protocol   (2)
               IP-Address   (3)
               IP-PrimaryDNS   (129)
               IP-PrimaryNBNS   (130)
               IP-SecondaryDNS   (131)
               IP-SecondaryNBNS   (132)"
   ::= {sr1645v2PppBFIpcpHisEntry 16777216}

sr1645v2PppBFIpcpHisLength OBJECT-TYPE
   SYNTAX      Integer32
   MAX-ACCESS  read-only
   STATUS      current
   DESCRIPTION
      "Path: pppBundle.status.ipcpHisOptions.length"
   ::= {sr1645v2PppBFIpcpHisEntry 33554432}

sr1645v2PppBFIpcpHisValue OBJECT-TYPE
   SYNTAX      OCTET STRING
   MAX-ACCESS  read-only
   STATUS      current
   DESCRIPTION
      "Path: pppBundle.status.ipcpHisOptions.value"
   ::= {sr1645v2PppBFIpcpHisEntry 50331648}


sr1645v2PppBFIp6cpMy OBJECT IDENTIFIER ::= {sr1645v2PppBF 45}

sr1645v2PppBFIp6cpMySSCTable OBJECT-TYPE
   SYNTAX      SEQUENCE OF Sr1645v2PppBFIp6cpMyEntry
   MAX-ACCESS  not-accessible
   STATUS      current
   DESCRIPTION
      "ip6cpOptions"
   ::= {sr1645v2PppBFIp6cpMy 1}

sr1645v2PppBFIp6cpMyEntry OBJECT-TYPE
   SYNTAX      Sr1645v2PppBFIp6cpMyEntry
   MAX-ACCESS  not-accessible
   STATUS      current
   DESCRIPTION
      ""
   INDEX      { sr1645v2PppBFIp6cpMyGlobalIx,
                sr1645v2PppBFIp6cpMyTableIx }
   ::= {sr1645v2PppBFIp6cpMySSCTable 1}

Sr1645v2PppBFIp6cpMyEntry ::=
   SEQUENCE
      {
      sr1645v2PppBFIp6cpMyGlobalIx
         GlobalIndex,
      sr1645v2PppBFIp6cpMyTableIx
         TableIndex,
      sr1645v2PppBFIp6cpMyOption
         INTEGER,
      sr1645v2PppBFIp6cpMyLength
         Integer32,
      sr1645v2PppBFIp6cpMyValue
         OCTET STRING
      }

sr1645v2PppBFIp6cpMyGlobalIx OBJECT-TYPE
   SYNTAX      GlobalIndex
   MAX-ACCESS  not-accessible
   STATUS      current
   DESCRIPTION
      "The value of the tlsCntTreeGlobalIndex of the MANAGED OBJECT."
   ::= {sr1645v2PppBFIp6cpMyEntry 10}

sr1645v2PppBFIp6cpMyTableIx OBJECT-TYPE
   SYNTAX      TableIndex
   MAX-ACCESS  not-accessible
   STATUS      current
   DESCRIPTION
      ""
   ::= {sr1645v2PppBFIp6cpMyEntry 11}

sr1645v2PppBFIp6cpMyOption OBJECT-TYPE
   SYNTAX      INTEGER
               {
               iPv6mInterfaceId (1),
               iPv6mCompression (2)
               }
   MAX-ACCESS  read-only
   STATUS      current
   DESCRIPTION
      "Path: pppBundle.status.ip6cpMyOptions.option

       Possibilities:
               IPv6-InterfaceId   (1)
               IPv6-Compression   (2)"
   ::= {sr1645v2PppBFIp6cpMyEntry 16777216}

sr1645v2PppBFIp6cpMyLength OBJECT-TYPE
   SYNTAX      Integer32
   MAX-ACCESS  read-only
   STATUS      current
   DESCRIPTION
      "Path: pppBundle.status.ip6cpMyOptions.length"
   ::= {sr1645v2PppBFIp6cpMyEntry 33554432}

sr1645v2PppBFIp6cpMyValue OBJECT-TYPE
   SYNTAX      OCTET STRING
   MAX-ACCESS  read-only
   STATUS      current
   DESCRIPTION
      "Path: pppBundle.status.ip6cpMyOptions.value"
   ::= {sr1645v2PppBFIp6cpMyEntry 50331648}


sr1645v2PppBFIp6cpHis OBJECT IDENTIFIER ::= {sr1645v2PppBF 46}

sr1645v2PppBFIp6cpHisSSCTable OBJECT-TYPE
   SYNTAX      SEQUENCE OF Sr1645v2PppBFIp6cpHisEntry
   MAX-ACCESS  not-accessible
   STATUS      current
   DESCRIPTION
      "ip6cpOptions"
   ::= {sr1645v2PppBFIp6cpHis 1}

sr1645v2PppBFIp6cpHisEntry OBJECT-TYPE
   SYNTAX      Sr1645v2PppBFIp6cpHisEntry
   MAX-ACCESS  not-accessible
   STATUS      current
   DESCRIPTION
      ""
   INDEX      { sr1645v2PppBFIp6cpHisGlobalIx,
                sr1645v2PppBFIp6cpHisTableIx }
   ::= {sr1645v2PppBFIp6cpHisSSCTable 1}

Sr1645v2PppBFIp6cpHisEntry ::=
   SEQUENCE
      {
      sr1645v2PppBFIp6cpHisGlobalIx
         GlobalIndex,
      sr1645v2PppBFIp6cpHisTableIx
         TableIndex,
      sr1645v2PppBFIp6cpHisOption
         INTEGER,
      sr1645v2PppBFIp6cpHisLength
         Integer32,
      sr1645v2PppBFIp6cpHisValue
         OCTET STRING
      }

sr1645v2PppBFIp6cpHisGlobalIx OBJECT-TYPE
   SYNTAX      GlobalIndex
   MAX-ACCESS  not-accessible
   STATUS      current
   DESCRIPTION
      "The value of the tlsCntTreeGlobalIndex of the MANAGED OBJECT."
   ::= {sr1645v2PppBFIp6cpHisEntry 10}

sr1645v2PppBFIp6cpHisTableIx OBJECT-TYPE
   SYNTAX      TableIndex
   MAX-ACCESS  not-accessible
   STATUS      current
   DESCRIPTION
      ""
   ::= {sr1645v2PppBFIp6cpHisEntry 11}

sr1645v2PppBFIp6cpHisOption OBJECT-TYPE
   SYNTAX      INTEGER
               {
               iPv6mInterfaceId (1),
               iPv6mCompression (2)
               }
   MAX-ACCESS  read-only
   STATUS      current
   DESCRIPTION
      "Path: pppBundle.status.ip6cpHisOptions.option

       Possibilities:
               IPv6-InterfaceId   (1)
               IPv6-Compression   (2)"
   ::= {sr1645v2PppBFIp6cpHisEntry 16777216}

sr1645v2PppBFIp6cpHisLength OBJECT-TYPE
   SYNTAX      Integer32
   MAX-ACCESS  read-only
   STATUS      current
   DESCRIPTION
      "Path: pppBundle.status.ip6cpHisOptions.length"
   ::= {sr1645v2PppBFIp6cpHisEntry 33554432}

sr1645v2PppBFIp6cpHisValue OBJECT-TYPE
   SYNTAX      OCTET STRING
   MAX-ACCESS  read-only
   STATUS      current
   DESCRIPTION
      "Path: pppBundle.status.ip6cpHisOptions.value"
   ::= {sr1645v2PppBFIp6cpHisEntry 50331648}


sr1645v2PppBFBcpState OBJECT IDENTIFIER ::= {sr1645v2PppBF 24}

sr1645v2PppBFBcpStateTable OBJECT-TYPE
   SYNTAX      SEQUENCE OF Sr1645v2PppBFBcpStateEntry
   MAX-ACCESS  not-accessible
   STATUS      current
   DESCRIPTION
      "pppState"
   ::= {sr1645v2PppBFBcpState 1}

sr1645v2PppBFBcpStateEntry OBJECT-TYPE
   SYNTAX      Sr1645v2PppBFBcpStateEntry
   MAX-ACCESS  not-accessible
   STATUS      current
   DESCRIPTION
      ""
   INDEX      { sr1645v2PppBFBcpStateGlobalIx }
   ::= {sr1645v2PppBFBcpStateTable 1}

Sr1645v2PppBFBcpStateEntry ::=
   SEQUENCE
      {
      sr1645v2PppBFBcpStateGlobalIx
         GlobalIndex,
      sr1645v2PppBFBcpStateValue
         INTEGER
      }

sr1645v2PppBFBcpStateGlobalIx OBJECT-TYPE
   SYNTAX      GlobalIndex
   MAX-ACCESS  not-accessible
   STATUS      current
   DESCRIPTION
      "The value of the tlsCntTreeGlobalIndex of the MANAGED OBJECT."
   ::= {sr1645v2PppBFBcpStateEntry 10}

sr1645v2PppBFBcpStateValue OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pppBundle.status.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppBFBcpStateEntry 2147483648}


sr1645v2PppBFBcpMy OBJECT IDENTIFIER ::= {sr1645v2PppBF 25}

sr1645v2PppBFBcpMySSCTable OBJECT-TYPE
   SYNTAX      SEQUENCE OF Sr1645v2PppBFBcpMyEntry
   MAX-ACCESS  not-accessible
   STATUS      current
   DESCRIPTION
      "bcpOptions"
   ::= {sr1645v2PppBFBcpMy 1}

sr1645v2PppBFBcpMyEntry OBJECT-TYPE
   SYNTAX      Sr1645v2PppBFBcpMyEntry
   MAX-ACCESS  not-accessible
   STATUS      current
   DESCRIPTION
      ""
   INDEX      { sr1645v2PppBFBcpMyGlobalIx,
                sr1645v2PppBFBcpMyTableIx }
   ::= {sr1645v2PppBFBcpMySSCTable 1}

Sr1645v2PppBFBcpMyEntry ::=
   SEQUENCE
      {
      sr1645v2PppBFBcpMyGlobalIx
         GlobalIndex,
      sr1645v2PppBFBcpMyTableIx
         TableIndex,
      sr1645v2PppBFBcpMyOption
         INTEGER,
      sr1645v2PppBFBcpMyLength
         Integer32,
      sr1645v2PppBFBcpMyValue
         OCTET STRING
      }

sr1645v2PppBFBcpMyGlobalIx OBJECT-TYPE
   SYNTAX      GlobalIndex
   MAX-ACCESS  not-accessible
   STATUS      current
   DESCRIPTION
      "The value of the tlsCntTreeGlobalIndex of the MANAGED OBJECT."
   ::= {sr1645v2PppBFBcpMyEntry 10}

sr1645v2PppBFBcpMyTableIx OBJECT-TYPE
   SYNTAX      TableIndex
   MAX-ACCESS  not-accessible
   STATUS      current
   DESCRIPTION
      ""
   ::= {sr1645v2PppBFBcpMyEntry 11}

sr1645v2PppBFBcpMyOption OBJECT-TYPE
   SYNTAX      INTEGER
               {
               bridgemIdentification (1),
               linemIdentification (2),
               mACmSupport (3),
               tinygrammCompression (4),
               lANmIdentification (5),
               mACmAddress (6),
               spanningmTreemProtocol (7),
               iEEEm802mTaggedmFrame (8)
               }
   MAX-ACCESS  read-only
   STATUS      current
   DESCRIPTION
      "Path: pppBundle.status.bcpMyOptions.option

       Possibilities:
               Bridge-Identification   (1)
               Line-Identification   (2)
               MAC-Support   (3)
               Tinygram-Compression   (4)
               LAN-Identification   (5)
               MAC-Address   (6)
               Spanning-Tree-Protocol   (7)
               IEEE-802-Tagged-Frame   (8)"
   ::= {sr1645v2PppBFBcpMyEntry 16777216}

sr1645v2PppBFBcpMyLength OBJECT-TYPE
   SYNTAX      Integer32
   MAX-ACCESS  read-only
   STATUS      current
   DESCRIPTION
      "Path: pppBundle.status.bcpMyOptions.length"
   ::= {sr1645v2PppBFBcpMyEntry 33554432}

sr1645v2PppBFBcpMyValue OBJECT-TYPE
   SYNTAX      OCTET STRING
   MAX-ACCESS  read-only
   STATUS      current
   DESCRIPTION
      "Path: pppBundle.status.bcpMyOptions.value"
   ::= {sr1645v2PppBFBcpMyEntry 50331648}


sr1645v2PppBFBcpHis OBJECT IDENTIFIER ::= {sr1645v2PppBF 26}

sr1645v2PppBFBcpHisSSCTable OBJECT-TYPE
   SYNTAX      SEQUENCE OF Sr1645v2PppBFBcpHisEntry
   MAX-ACCESS  not-accessible
   STATUS      current
   DESCRIPTION
      "bcpOptions"
   ::= {sr1645v2PppBFBcpHis 1}

sr1645v2PppBFBcpHisEntry OBJECT-TYPE
   SYNTAX      Sr1645v2PppBFBcpHisEntry
   MAX-ACCESS  not-accessible
   STATUS      current
   DESCRIPTION
      ""
   INDEX      { sr1645v2PppBFBcpHisGlobalIx,
                sr1645v2PppBFBcpHisTableIx }
   ::= {sr1645v2PppBFBcpHisSSCTable 1}

Sr1645v2PppBFBcpHisEntry ::=
   SEQUENCE
      {
      sr1645v2PppBFBcpHisGlobalIx
         GlobalIndex,
      sr1645v2PppBFBcpHisTableIx
         TableIndex,
      sr1645v2PppBFBcpHisOption
         INTEGER,
      sr1645v2PppBFBcpHisLength
         Integer32,
      sr1645v2PppBFBcpHisValue
         OCTET STRING
      }

sr1645v2PppBFBcpHisGlobalIx OBJECT-TYPE
   SYNTAX      GlobalIndex
   MAX-ACCESS  not-accessible
   STATUS      current
   DESCRIPTION
      "The value of the tlsCntTreeGlobalIndex of the MANAGED OBJECT."
   ::= {sr1645v2PppBFBcpHisEntry 10}

sr1645v2PppBFBcpHisTableIx OBJECT-TYPE
   SYNTAX      TableIndex
   MAX-ACCESS  not-accessible
   STATUS      current
   DESCRIPTION
      ""
   ::= {sr1645v2PppBFBcpHisEntry 11}

sr1645v2PppBFBcpHisOption OBJECT-TYPE
   SYNTAX      INTEGER
               {
               bridgemIdentification (1),
               linemIdentification (2),
               mACmSupport (3),
               tinygrammCompression (4),
               lANmIdentification (5),
               mACmAddress (6),
               spanningmTreemProtocol (7),
               iEEEm802mTaggedmFrame (8)
               }
   MAX-ACCESS  read-only
   STATUS      current
   DESCRIPTION
      "Path: pppBundle.status.bcpHisOptions.option

       Possibilities:
               Bridge-Identification   (1)
               Line-Identification   (2)
               MAC-Support   (3)
               Tinygram-Compression   (4)
               LAN-Identification   (5)
               MAC-Address   (6)
               Spanning-Tree-Protocol   (7)
               IEEE-802-Tagged-Frame   (8)"
   ::= {sr1645v2PppBFBcpHisEntry 16777216}

sr1645v2PppBFBcpHisLength OBJECT-TYPE
   SYNTAX      Integer32
   MAX-ACCESS  read-only
   STATUS      current
   DESCRIPTION
      "Path: pppBundle.status.bcpHisOptions.length"
   ::= {sr1645v2PppBFBcpHisEntry 33554432}

sr1645v2PppBFBcpHisValue OBJECT-TYPE
   SYNTAX      OCTET STRING
   MAX-ACCESS  read-only
   STATUS      current
   DESCRIPTION
      "Path: pppBundle.status.bcpHisOptions.value"
   ::= {sr1645v2PppBFBcpHisEntry 50331648}


sr1645v2PppBFMcIfS OBJECT IDENTIFIER ::= {sr1645v2PppBF 28}

sr1645v2PppBFMcIfSSSCTable OBJECT-TYPE
   SYNTAX      SEQUENCE OF Sr1645v2PppBFMcIfSEntry
   MAX-ACCESS  not-accessible
   STATUS      current
   DESCRIPTION
      ""
   ::= {sr1645v2PppBFMcIfS 1}

sr1645v2PppBFMcIfSEntry OBJECT-TYPE
   SYNTAX      Sr1645v2PppBFMcIfSEntry
   MAX-ACCESS  not-accessible
   STATUS      current
   DESCRIPTION
      ""
   INDEX      { sr1645v2PppBFMcIfSGlobalIx,
                sr1645v2PppBFMcIfSTableIx }
   ::= {sr1645v2PppBFMcIfSSSCTable 1}

Sr1645v2PppBFMcIfSEntry ::=
   SEQUENCE
      {
      sr1645v2PppBFMcIfSGlobalIx
         GlobalIndex,
      sr1645v2PppBFMcIfSTableIx
         TableIndex,
      sr1645v2PppBFMcIfSName
         DisplayString,
      sr1645v2PppBFMcIfSMode
         INTEGER,
      sr1645v2PppBFMcIfSIfOperStatus
         INTEGER,
      sr1645v2PppBFMcIfSIfLastChange
         TimeTicks,
      sr1645v2PppBFMcIfSIfLastChangeDate
         DisplayString,
      sr1645v2PppBFMcIfSIpAddress
         IpAddress,
      sr1645v2PppBFMcIfSIpNetMask
         IpAddress,
      sr1645v2PppBFMcIfSIpRemote
         IpAddress,
      sr1645v2PppBFMcIfSBrStatus
         INTEGER,
      sr1645v2PppBFMcIfSBrSpanningTreePortRole
         INTEGER,
      sr1645v2PppBFMcIfSBrSpanningTreePortId
         Integer32,
      sr1645v2PppBFMcIfSBrSpanningTreePpCostExtPathCost
         Integer32,
      sr1645v2PppBFMcIfSBrSpanningTreePpCostIntPathCost
         Integer32,
      sr1645v2PppBFMcIfSBrSpanningTreeExtRpCost
         Integer32,
      sr1645v2PppBFMcIfSBrSpanningTreeIntRpCost
         Integer32,
      sr1645v2PppBFMcIfSBrSpanningTreeDesBrIdPriority
         Integer32,
      sr1645v2PppBFMcIfSBrSpanningTreeDesBrIdMacAddress
         OCTET STRING,
      sr1645v2PppBFMcIfSBrSpanningTreeDesPrtId
         Integer32,
      sr1645v2PppBFMcIfSBrSpanningTreeDesInt
         INTEGER,
      sr1645v2PppBFMcIfSBrSpanningTreeEdgeDetection
         INTEGER,
      sr1645v2PppBFMcIfSPppLcpState
         INTEGER,
      sr1645v2PppBFMcIfSPppIpcpState
         INTEGER,
      sr1645v2PppBFMcIfSPppBcpState
         INTEGER,
      sr1645v2PppBFMcIfSPppMyAutSt
         INTEGER,
      sr1645v2PppBFMcIfSPppMyAutUsr
         DisplayString,
      sr1645v2PppBFMcIfSPppHisAutSt
         INTEGER,
      sr1645v2PppBFMcIfSMcMulticlass
         Integer32
      }

sr1645v2PppBFMcIfSGlobalIx OBJECT-TYPE
   SYNTAX      GlobalIndex
   MAX-ACCESS  not-accessible
   STATUS      current
   DESCRIPTION
      "The value of the tlsCntTreeGlobalIndex of the MANAGED OBJECT."
   ::= {sr1645v2PppBFMcIfSEntry 10}

sr1645v2PppBFMcIfSTableIx OBJECT-TYPE
   SYNTAX      TableIndex
   MAX-ACCESS  not-accessible
   STATUS      current
   DESCRIPTION
      ""
   ::= {sr1645v2PppBFMcIfSEntry 11}

sr1645v2PppBFMcIfSName OBJECT-TYPE
   SYNTAX      DisplayString
   MAX-ACCESS  read-only
   STATUS      current
   DESCRIPTION
      "Path: pppBundle.status.multiclassInterfaces.name"
   ::= {sr1645v2PppBFMcIfSEntry 16777216}

sr1645v2PppBFMcIfSMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: pppBundle.status.multiclassInterfaces.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2PppBFMcIfSEntry 335544320}

sr1645v2PppBFMcIfSIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: pppBundle.status.multiclassInterfaces.ifOperStatus

       Possibilities:
               up   (1)
               down   (2)
               testing   (3)
               unknown   (4)
               dormant   (5)
               notPresent   (6)
               lowerLayerDown   (7)"
   ::= {sr1645v2PppBFMcIfSEntry 1795162112}

sr1645v2PppBFMcIfSIfLastChange OBJECT-TYPE
   SYNTAX      TimeTicks
   MAX-ACCESS  read-only
   STATUS      current
   DESCRIPTION
      "Path: pppBundle.status.multiclassInterfaces.ifLastChange

       Time in centi-second."
   ::= {sr1645v2PppBFMcIfSEntry 1811939328}

sr1645v2PppBFMcIfSIfLastChangeDate OBJECT-TYPE
   SYNTAX      DisplayString
   MAX-ACCESS  read-only
   STATUS      current
   DESCRIPTION
      "Path: pppBundle.status.multiclassInterfaces.ifLastChangeDate"
   ::= {sr1645v2PppBFMcIfSEntry 3070230528}

sr1645v2PppBFMcIfSIpAddress OBJECT-TYPE
   SYNTAX      IpAddress
   MAX-ACCESS  read-only
   STATUS      current
   DESCRIPTION
      "Path: pppBundle.status.multiclassInterfaces.ip.address"
   ::= {sr1645v2PppBFMcIfSEntry 51380224}

sr1645v2PppBFMcIfSIpNetMask OBJECT-TYPE
   SYNTAX      IpAddress
   MAX-ACCESS  read-only
   STATUS      current
   DESCRIPTION
      "Path: pppBundle.status.multiclassInterfaces.ip.netMask"
   ::= {sr1645v2PppBFMcIfSEntry 51445760}

sr1645v2PppBFMcIfSIpRemote OBJECT-TYPE
   SYNTAX      IpAddress
   MAX-ACCESS  read-only
   STATUS      current
   DESCRIPTION
      "Path: pppBundle.status.multiclassInterfaces.ip.remote"
   ::= {sr1645v2PppBFMcIfSEntry 51511296}

sr1645v2PppBFMcIfSBrStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: pppBundle.status.multiclassInterfaces.bridging.status

       Possibilities:
               disabled   (0)
               discarding   (1)
               learning   (2)
               forwarding   (3)
               backupBlockedIntfDown   (256)
               backupBlockedIntfUp   (259)
               shutdown   (255)"
   ::= {sr1645v2PppBFMcIfSEntry 453050368}

sr1645v2PppBFMcIfSBrSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: pppBundle.status.multiclassInterfaces.bridging.spanningTree.portRole

       Possibilities:
               none   (0)
               root   (1)
               designated   (2)
               alternate   (3)
               backup   (4)
               disabled   (5)
               master   (6)"
   ::= {sr1645v2PppBFMcIfSEntry 453116160}

sr1645v2PppBFMcIfSBrSpanningTreePortId OBJECT-TYPE
   SYNTAX      Integer32
   MAX-ACCESS  read-only
   STATUS      current
   DESCRIPTION
      "Path: pppBundle.status.multiclassInterfaces.bridging.spanningTree.portId"
   ::= {sr1645v2PppBFMcIfSEntry 453116416}

sr1645v2PppBFMcIfSBrSpanningTreePpCostExtPathCost OBJECT-TYPE
   SYNTAX      Integer32
   MAX-ACCESS  read-only
   STATUS      current
   DESCRIPTION
      "Path: pppBundle.status.multiclassInterfaces.bridging.spanningTree.portPathCosts.extPathCost"
   ::= {sr1645v2PppBFMcIfSEntry 453116673}

sr1645v2PppBFMcIfSBrSpanningTreePpCostIntPathCost OBJECT-TYPE
   SYNTAX      Integer32
   MAX-ACCESS  read-only
   STATUS      current
   DESCRIPTION
      "Path: pppBundle.status.multiclassInterfaces.bridging.spanningTree.portPathCosts.intPathCost"
   ::= {sr1645v2PppBFMcIfSEntry 453116674}

sr1645v2PppBFMcIfSBrSpanningTreeExtRpCost OBJECT-TYPE
   SYNTAX      Integer32
   MAX-ACCESS  read-only
   STATUS      current
   DESCRIPTION
      "Path: pppBundle.status.multiclassInterfaces.bridging.spanningTree.extRootPathCost"
   ::= {sr1645v2PppBFMcIfSEntry 453116928}

sr1645v2PppBFMcIfSBrSpanningTreeIntRpCost OBJECT-TYPE
   SYNTAX      Integer32
   MAX-ACCESS  read-only
   STATUS      current
   DESCRIPTION
      "Path: pppBundle.status.multiclassInterfaces.bridging.spanningTree.intRootPathCost"
   ::= {sr1645v2PppBFMcIfSEntry 453117184}

sr1645v2PppBFMcIfSBrSpanningTreeDesBrIdPriority OBJECT-TYPE
   SYNTAX      Integer32
   MAX-ACCESS  read-only
   STATUS      current
   DESCRIPTION
      "Path: pppBundle.status.multiclassInterfaces.bridging.spanningTree.designatedBridgeId.priority"
   ::= {sr1645v2PppBFMcIfSEntry 453117441}

sr1645v2PppBFMcIfSBrSpanningTreeDesBrIdMacAddress OBJECT-TYPE
   SYNTAX      OCTET STRING
   MAX-ACCESS  read-only
   STATUS      current
   DESCRIPTION
      "Path: pppBundle.status.multiclassInterfaces.bridging.spanningTree.designatedBridgeId.macAddress

       MAC address."
   ::= {sr1645v2PppBFMcIfSEntry 453117442}

sr1645v2PppBFMcIfSBrSpanningTreeDesPrtId OBJECT-TYPE
   SYNTAX      Integer32
   MAX-ACCESS  read-only
   STATUS      current
   DESCRIPTION
      "Path: pppBundle.status.multiclassInterfaces.bridging.spanningTree.designatedPortId"
   ::= {sr1645v2PppBFMcIfSEntry 453117696}

sr1645v2PppBFMcIfSBrSpanningTreeDesInt OBJECT-TYPE
   SYNTAX      INTEGER
               {
               no (0),
               yes (1)
               }
   MAX-ACCESS  read-only
   STATUS      current
   DESCRIPTION
      "Path: pppBundle.status.multiclassInterfaces.bridging.spanningTree.designatedOrInternal

       Possibilities:
               no   (0)
               yes   (1)"
   ::= {sr1645v2PppBFMcIfSEntry 453117952}

sr1645v2PppBFMcIfSBrSpanningTreeEdgeDetection OBJECT-TYPE
   SYNTAX      INTEGER
               {
               none (0),
               edge (1),
               notEdge (2)
               }
   MAX-ACCESS  read-only
   STATUS      current
   DESCRIPTION
      "Path: pppBundle.status.multiclassInterfaces.bridging.spanningTree.edgeDetection

       Possibilities:
               none   (0)
               edge   (1)
               notEdge   (2)"
   ::= {sr1645v2PppBFMcIfSEntry 453118208}

sr1645v2PppBFMcIfSPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pppBundle.status.multiclassInterfaces.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppBFMcIfSEntry 184614912}

sr1645v2PppBFMcIfSPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pppBundle.status.multiclassInterfaces.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppBFMcIfSEntry 184680448}

sr1645v2PppBFMcIfSPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pppBundle.status.multiclassInterfaces.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PppBFMcIfSEntry 184745984}

sr1645v2PppBFMcIfSPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: pppBundle.status.multiclassInterfaces.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2PppBFMcIfSEntry 185204736}

sr1645v2PppBFMcIfSPppMyAutUsr OBJECT-TYPE
   SYNTAX      DisplayString
   MAX-ACCESS  read-only
   STATUS      current
   DESCRIPTION
      "Path: pppBundle.status.multiclassInterfaces.ppp.myAuthenUser"
   ::= {sr1645v2PppBFMcIfSEntry 185335808}

sr1645v2PppBFMcIfSPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: pppBundle.status.multiclassInterfaces.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2PppBFMcIfSEntry 185270272}

sr1645v2PppBFMcIfSMcMulticlass OBJECT-TYPE
   SYNTAX      Integer32
   MAX-ACCESS  read-only
   STATUS      current
   DESCRIPTION
      "Path: pppBundle.status.multiclassInterfaces.multiclass.multiclass"
   ::= {sr1645v2PppBFMcIfSEntry 503382016}


sr1645v2PppBFDescr OBJECT IDENTIFIER ::= {sr1645v2PppBF 101}

sr1645v2PppBFDescrTable OBJECT-TYPE
   SYNTAX      SEQUENCE OF Sr1645v2PppBFDescrEntry
   MAX-ACCESS  not-accessible
   STATUS      current
   DESCRIPTION
      "ifDescr"
   ::= {sr1645v2PppBFDescr 1}

sr1645v2PppBFDescrEntry OBJECT-TYPE
   SYNTAX      Sr1645v2PppBFDescrEntry
   MAX-ACCESS  not-accessible
   STATUS      current
   DESCRIPTION
      ""
   INDEX      { sr1645v2PppBFDescrGlobalIx }
   ::= {sr1645v2PppBFDescrTable 1}

Sr1645v2PppBFDescrEntry ::=
   SEQUENCE
      {
      sr1645v2PppBFDescrGlobalIx
         GlobalIndex,
      sr1645v2PppBFDescrValue
         DisplayString
      }

sr1645v2PppBFDescrGlobalIx OBJECT-TYPE
   SYNTAX      GlobalIndex
   MAX-ACCESS  not-accessible
   STATUS      current
   DESCRIPTION
      "The value of the tlsCntTreeGlobalIndex of the MANAGED OBJECT."
   ::= {sr1645v2PppBFDescrEntry 10}

sr1645v2PppBFDescrValue OBJECT-TYPE
   SYNTAX      DisplayString
   MAX-ACCESS  read-only
   STATUS      current
   DESCRIPTION
      "Path: pppBundle.status.ifDescr"
   ::= {sr1645v2PppBFDescrEntry 2147483648}


sr1645v2PppBFType OBJECT IDENTIFIER ::= {sr1645v2PppBF 102}

sr1645v2PppBFTypeTable OBJECT-TYPE
   SYNTAX      SEQUENCE OF Sr1645v2PppBFTypeEntry
   MAX-ACCESS  not-accessible
   STATUS      current
   DESCRIPTION
      "ifType"
   ::= {sr1645v2PppBFType 1}

sr1645v2PppBFTypeEntry OBJECT-TYPE
   SYNTAX      Sr1645v2PppBFTypeEntry
   MAX-ACCESS  not-accessible
   STATUS      current
   DESCRIPTION
      ""
   INDEX      { sr1645v2PppBFTypeGlobalIx }
   ::= {sr1645v2PppBFTypeTable 1}

Sr1645v2PppBFTypeEntry ::=
   SEQUENCE
      {
      sr1645v2PppBFTypeGlobalIx
         GlobalIndex,
      sr1645v2PppBFTypeValue
         INTEGER
      }

sr1645v2PppBFTypeGlobalIx OBJECT-TYPE
   SYNTAX      GlobalIndex
   MAX-ACCESS  not-accessible
   STATUS      current
   DESCRIPTION
      "The value of the tlsCntTreeGlobalIndex of the MANAGED OBJECT."
   ::= {sr1645v2PppBFTypeEntry 10}

sr1645v2PppBFTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: pppBundle.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2PppBFTypeEntry 2147483648}


sr1645v2PppBFOperStatus OBJECT IDENTIFIER ::= {sr1645v2PppBF 107}

sr1645v2PppBFOperStatusTable OBJECT-TYPE
   SYNTAX      SEQUENCE OF Sr1645v2PppBFOperStatusEntry
   MAX-ACCESS  not-accessible
   STATUS      current
   DESCRIPTION
      "ifOperStatus"
   ::= {sr1645v2PppBFOperStatus 1}

sr1645v2PppBFOperStatusEntry OBJECT-TYPE
   SYNTAX      Sr1645v2PppBFOperStatusEntry
   MAX-ACCESS  not-accessible
   STATUS      current
   DESCRIPTION
      ""
   INDEX      { sr1645v2PppBFOperStatusGlobalIx }
   ::= {sr1645v2PppBFOperStatusTable 1}

Sr1645v2PppBFOperStatusEntry ::=
   SEQUENCE
      {
      sr1645v2PppBFOperStatusGlobalIx
         GlobalIndex,
      sr1645v2PppBFOperStatusValue
         INTEGER
      }

sr1645v2PppBFOperStatusGlobalIx OBJECT-TYPE
   SYNTAX      GlobalIndex
   MAX-ACCESS  not-accessible
   STATUS      current
   DESCRIPTION
      "The value of the tlsCntTreeGlobalIndex of the MANAGED OBJECT."
   ::= {sr1645v2PppBFOperStatusEntry 10}

sr1645v2PppBFOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: pppBundle.status.ifOperStatus

       Possibilities:
               up   (1)
               down   (2)
               testing   (3)
               unknown   (4)
               dormant   (5)
               notPresent   (6)
               lowerLayerDown   (7)"
   ::= {sr1645v2PppBFOperStatusEntry 2147483648}


sr1645v2PppBFEd OBJECT IDENTIFIER ::= {sr1645v2PppBF 82}

sr1645v2PppBFEdTable OBJECT-TYPE
   SYNTAX      SEQUENCE OF Sr1645v2PppBFEdEntry
   MAX-ACCESS  not-accessible
   STATUS      current
   DESCRIPTION
      "ifDescr"
   ::= {sr1645v2PppBFEd 1}

sr1645v2PppBFEdEntry OBJECT-TYPE
   SYNTAX      Sr1645v2PppBFEdEntry
   MAX-ACCESS  not-accessible
   STATUS      current
   DESCRIPTION
      ""
   INDEX      { sr1645v2PppBFEdGlobalIx }
   ::= {sr1645v2PppBFEdTable 1}

Sr1645v2PppBFEdEntry ::=
   SEQUENCE
      {
      sr1645v2PppBFEdGlobalIx
         GlobalIndex,
      sr1645v2PppBFEdValue
         DisplayString
      }

sr1645v2PppBFEdGlobalIx OBJECT-TYPE
   SYNTAX      GlobalIndex
   MAX-ACCESS  not-accessible
   STATUS      current
   DESCRIPTION
      "The value of the tlsCntTreeGlobalIndex of the MANAGED OBJECT."
   ::= {sr1645v2PppBFEdEntry 10}

sr1645v2PppBFEdValue OBJECT-TYPE
   SYNTAX      DisplayString
   MAX-ACCESS  read-only
   STATUS      current
   DESCRIPTION
      "Path: pppBundle.status.endpointDiscr"
   ::= {sr1645v2PppBFEdEntry 2147483648}



pr1645v2PppBF OBJECT IDENTIFIER ::= {r1645v2PppBF 12}


pr1645v2PppBFInOctets OBJECT IDENTIFIER ::= {pr1645v2PppBF 109}

pr1645v2PppBFInOctetsTable OBJECT-TYPE
   SYNTAX      SEQUENCE OF Pr1645v2PppBFInOctetsEntry
   MAX-ACCESS  not-accessible
   STATUS      current
   DESCRIPTION
      "ifInOctets"
   ::= {pr1645v2PppBFInOctets 1}

pr1645v2PppBFInOctetsEntry OBJECT-TYPE
   SYNTAX      Pr1645v2PppBFInOctetsEntry
   MAX-ACCESS  not-accessible
   STATUS      current
   DESCRIPTION
      ""
   INDEX      { pr1645v2PppBFInOctetsGlobalIx }
   ::= {pr1645v2PppBFInOctetsTable 1}

Pr1645v2PppBFInOctetsEntry ::=
   SEQUENCE
      {
      pr1645v2PppBFInOctetsGlobalIx
         GlobalIndex,
      pr1645v2PppBFInOctetsValue
         Counter64
      }

pr1645v2PppBFInOctetsGlobalIx OBJECT-TYPE
   SYNTAX      GlobalIndex
   MAX-ACCESS  not-accessible
   STATUS      current
   DESCRIPTION
      "The value of the tlsCntTreeGlobalIndex of the MANAGED OBJECT."
   ::= {pr1645v2PppBFInOctetsEntry 10}

pr1645v2PppBFInOctetsValue OBJECT-TYPE
   SYNTAX      Counter64
   MAX-ACCESS  read-only
   STATUS      current
   DESCRIPTION
      "Path: pppBundle.performance.ifInOctets

       64 bit unsigned wrappable counter."
   ::= {pr1645v2PppBFInOctetsEntry 2147483648}


pr1645v2PppBFInUcastPkts OBJECT IDENTIFIER ::= {pr1645v2PppBF 110}

pr1645v2PppBFInUcastPktsTable OBJECT-TYPE
   SYNTAX      SEQUENCE OF Pr1645v2PppBFInUcastPktsEntry
   MAX-ACCESS  not-accessible
   STATUS      current
   DESCRIPTION
      "ifInUcastPkts"
   ::= {pr1645v2PppBFInUcastPkts 1}

pr1645v2PppBFInUcastPktsEntry OBJECT-TYPE
   SYNTAX      Pr1645v2PppBFInUcastPktsEntry
   MAX-ACCESS  not-accessible
   STATUS      current
   DESCRIPTION
      ""
   INDEX      { pr1645v2PppBFInUcastPktsGlobalIx }
   ::= {pr1645v2PppBFInUcastPktsTable 1}

Pr1645v2PppBFInUcastPktsEntry ::=
   SEQUENCE
      {
      pr1645v2PppBFInUcastPktsGlobalIx
         GlobalIndex,
      pr1645v2PppBFInUcastPktsValue
         Counter64
      }

pr1645v2PppBFInUcastPktsGlobalIx OBJECT-TYPE
   SYNTAX      GlobalIndex
   MAX-ACCESS  not-accessible
   STATUS      current
   DESCRIPTION
      "The value of the tlsCntTreeGlobalIndex of the MANAGED OBJECT."
   ::= {pr1645v2PppBFInUcastPktsEntry 10}

pr1645v2PppBFInUcastPktsValue OBJECT-TYPE
   SYNTAX      Counter64
   MAX-ACCESS  read-only
   STATUS      current
   DESCRIPTION
      "Path: pppBundle.performance.ifInUcastPkts

       64 bit unsigned wrappable counter."
   ::= {pr1645v2PppBFInUcastPktsEntry 2147483648}


pr1645v2PppBFInNUcastPkts OBJECT IDENTIFIER ::= {pr1645v2PppBF 111}

pr1645v2PppBFInNUcastPktsTable OBJECT-TYPE
   SYNTAX      SEQUENCE OF Pr1645v2PppBFInNUcastPktsEntry
   MAX-ACCESS  not-accessible
   STATUS      current
   DESCRIPTION
      "ifInNUcastPkts"
   ::= {pr1645v2PppBFInNUcastPkts 1}

pr1645v2PppBFInNUcastPktsEntry OBJECT-TYPE
   SYNTAX      Pr1645v2PppBFInNUcastPktsEntry
   MAX-ACCESS  not-accessible
   STATUS      current
   DESCRIPTION
      ""
   INDEX      { pr1645v2PppBFInNUcastPktsGlobalIx }
   ::= {pr1645v2PppBFInNUcastPktsTable 1}

Pr1645v2PppBFInNUcastPktsEntry ::=
   SEQUENCE
      {
      pr1645v2PppBFInNUcastPktsGlobalIx
         GlobalIndex,
      pr1645v2PppBFInNUcastPktsValue
         Counter64
      }

pr1645v2PppBFInNUcastPktsGlobalIx OBJECT-TYPE
   SYNTAX      GlobalIndex
   MAX-ACCESS  not-accessible
   STATUS      current
   DESCRIPTION
      "The value of the tlsCntTreeGlobalIndex of the MANAGED OBJECT."
   ::= {pr1645v2PppBFInNUcastPktsEntry 10}

pr1645v2PppBFInNUcastPktsValue OBJECT-TYPE
   SYNTAX      Counter64
   MAX-ACCESS  read-only
   STATUS      current
   DESCRIPTION
      "Path: pppBundle.performance.ifInNUcastPkts

       64 bit unsigned wrappable counter."
   ::= {pr1645v2PppBFInNUcastPktsEntry 2147483648}


pr1645v2PppBFInBcastPkts OBJECT IDENTIFIER ::= {pr1645v2PppBF 211}

pr1645v2PppBFInBcastPktsTable OBJECT-TYPE
   SYNTAX      SEQUENCE OF Pr1645v2PppBFInBcastPktsEntry
   MAX-ACCESS  not-accessible
   STATUS      current
   DESCRIPTION
      "ifInBcastPkts"
   ::= {pr1645v2PppBFInBcastPkts 1}

pr1645v2PppBFInBcastPktsEntry OBJECT-TYPE
   SYNTAX      Pr1645v2PppBFInBcastPktsEntry
   MAX-ACCESS  not-accessible
   STATUS      current
   DESCRIPTION
      ""
   INDEX      { pr1645v2PppBFInBcastPktsGlobalIx }
   ::= {pr1645v2PppBFInBcastPktsTable 1}

Pr1645v2PppBFInBcastPktsEntry ::=
   SEQUENCE
      {
      pr1645v2PppBFInBcastPktsGlobalIx
         GlobalIndex,
      pr1645v2PppBFInBcastPktsValue
         Counter64
      }

pr1645v2PppBFInBcastPktsGlobalIx OBJECT-TYPE
   SYNTAX      GlobalIndex
   MAX-ACCESS  not-accessible
   STATUS      current
   DESCRIPTION
      "The value of the tlsCntTreeGlobalIndex of the MANAGED OBJECT."
   ::= {pr1645v2PppBFInBcastPktsEntry 10}

pr1645v2PppBFInBcastPktsValue OBJECT-TYPE
   SYNTAX      Counter64
   MAX-ACCESS  read-only
   STATUS      current
   DESCRIPTION
      "Path: pppBundle.performance.ifInBcastPkts

       64 bit unsigned wrappable counter."
   ::= {pr1645v2PppBFInBcastPktsEntry 2147483648}


pr1645v2PppBFInMcastPkts OBJECT IDENTIFIER ::= {pr1645v2PppBF 221}

pr1645v2PppBFInMcastPktsTable OBJECT-TYPE
   SYNTAX      SEQUENCE OF Pr1645v2PppBFInMcastPktsEntry
   MAX-ACCESS  not-accessible
   STATUS      current
   DESCRIPTION
      "ifInNUcastPkts"
   ::= {pr1645v2PppBFInMcastPkts 1}

pr1645v2PppBFInMcastPktsEntry OBJECT-TYPE
   SYNTAX      Pr1645v2PppBFInMcastPktsEntry
   MAX-ACCESS  not-accessible
   STATUS      current
   DESCRIPTION
      ""
   INDEX      { pr1645v2PppBFInMcastPktsGlobalIx }
   ::= {pr1645v2PppBFInMcastPktsTable 1}

Pr1645v2PppBFInMcastPktsEntry ::=
   SEQUENCE
      {
      pr1645v2PppBFInMcastPktsGlobalIx
         GlobalIndex,
      pr1645v2PppBFInMcastPktsValue
         Counter64
      }

pr1645v2PppBFInMcastPktsGlobalIx OBJECT-TYPE
   SYNTAX      GlobalIndex
   MAX-ACCESS  not-accessible
   STATUS      current
   DESCRIPTION
      "The value of the tlsCntTreeGlobalIndex of the MANAGED OBJECT."
   ::= {pr1645v2PppBFInMcastPktsEntry 10}

pr1645v2PppBFInMcastPktsValue OBJECT-TYPE
   SYNTAX      Counter64
   MAX-ACCESS  read-only
   STATUS      current
   DESCRIPTION
      "Path: pppBundle.performance.ifInMcastPkts

       64 bit unsigned wrappable counter."
   ::= {pr1645v2PppBFInMcastPktsEntry 2147483648}


pr1645v2PppBFInDiscards OBJECT IDENTIFIER ::= {pr1645v2PppBF 112}

pr1645v2PppBFInDiscardsTable OBJECT-TYPE
   SYNTAX      SEQUENCE OF Pr1645v2PppBFInDiscardsEntry
   MAX-ACCESS  not-accessible
   STATUS      current
   DESCRIPTION
      "ifInDiscards"
   ::= {pr1645v2PppBFInDiscards 1}

pr1645v2PppBFInDiscardsEntry OBJECT-TYPE
   SYNTAX      Pr1645v2PppBFInDiscardsEntry
   MAX-ACCESS  not-accessible
   STATUS      current
   DESCRIPTION
      ""
   INDEX      { pr1645v2PppBFInDiscardsGlobalIx }
   ::= {pr1645v2PppBFInDiscardsTable 1}

Pr1645v2PppBFInDiscardsEntry ::=
   SEQUENCE
      {
      pr1645v2PppBFInDiscardsGlobalIx
         GlobalIndex,
      pr1645v2PppBFInDiscardsValue
         Counter64
      }

pr1645v2PppBFInDiscardsGlobalIx OBJECT-TYPE
   SYNTAX      GlobalIndex
   MAX-ACCESS  not-accessible
   STATUS      current
   DESCRIPTION
      "The value of the tlsCntTreeGlobalIndex of the MANAGED OBJECT."
   ::= {pr1645v2PppBFInDiscardsEntry 10}

pr1645v2PppBFInDiscardsValue OBJECT-TYPE
   SYNTAX      Counter64
   MAX-ACCESS  read-only
   STATUS      current
   DESCRIPTION
      "Path: pppBundle.performance.ifInDiscards

       64 bit unsigned wrappable counter."
   ::= {pr1645v2PppBFInDiscardsEntry 2147483648}


pr1645v2PppBFInErrors OBJECT IDENTIFIER ::= {pr1645v2PppBF 113}

pr1645v2PppBFInErrorsTable OBJECT-TYPE
   SYNTAX      SEQUENCE OF Pr1645v2PppBFInErrorsEntry
   MAX-ACCESS  not-accessible
   STATUS      current
   DESCRIPTION
      "ifInErrors"
   ::= {pr1645v2PppBFInErrors 1}

pr1645v2PppBFInErrorsEntry OBJECT-TYPE
   SYNTAX      Pr1645v2PppBFInErrorsEntry
   MAX-ACCESS  not-accessible
   STATUS      current
   DESCRIPTION
      ""
   INDEX      { pr1645v2PppBFInErrorsGlobalIx }
   ::= {pr1645v2PppBFInErrorsTable 1}

Pr1645v2PppBFInErrorsEntry ::=
   SEQUENCE
      {
      pr1645v2PppBFInErrorsGlobalIx
         GlobalIndex,
      pr1645v2PppBFInErrorsValue
         Counter64
      }

pr1645v2PppBFInErrorsGlobalIx OBJECT-TYPE
   SYNTAX      GlobalIndex
   MAX-ACCESS  not-accessible
   STATUS      current
   DESCRIPTION
      "The value of the tlsCntTreeGlobalIndex of the MANAGED OBJECT."
   ::= {pr1645v2PppBFInErrorsEntry 10}

pr1645v2PppBFInErrorsValue OBJECT-TYPE
   SYNTAX      Counter64
   MAX-ACCESS  read-only
   STATUS      current
   DESCRIPTION
      "Path: pppBundle.performance.ifInErrors

       64 bit unsigned wrappable counter."
   ::= {pr1645v2PppBFInErrorsEntry 2147483648}


pr1645v2PppBFInUnknownProt OBJECT IDENTIFIER ::= {pr1645v2PppBF 114}

pr1645v2PppBFInUnknownProtTable OBJECT-TYPE
   SYNTAX      SEQUENCE OF Pr1645v2PppBFInUnknownProtEntry
   MAX-ACCESS  not-accessible
   STATUS      current
   DESCRIPTION
      "ifInUnknownprotos"
   ::= {pr1645v2PppBFInUnknownProt 1}

pr1645v2PppBFInUnknownProtEntry OBJECT-TYPE
   SYNTAX      Pr1645v2PppBFInUnknownProtEntry
   MAX-ACCESS  not-accessible
   STATUS      current
   DESCRIPTION
      ""
   INDEX      { pr1645v2PppBFInUnknownProtGlobalIx }
   ::= {pr1645v2PppBFInUnknownProtTable 1}

Pr1645v2PppBFInUnknownProtEntry ::=
   SEQUENCE
      {
      pr1645v2PppBFInUnknownProtGlobalIx
         GlobalIndex,
      pr1645v2PppBFInUnknownProtValue
         Counter64
      }

pr1645v2PppBFInUnknownProtGlobalIx OBJECT-TYPE
   SYNTAX      GlobalIndex
   MAX-ACCESS  not-accessible
   STATUS      current
   DESCRIPTION
      "The value of the tlsCntTreeGlobalIndex of the MANAGED OBJECT."
   ::= {pr1645v2PppBFInUnknownProtEntry 10}

pr1645v2PppBFInUnknownProtValue OBJECT-TYPE
   SYNTAX      Counter64
   MAX-ACCESS  read-only
   STATUS      current
   DESCRIPTION
      "Path: pppBundle.performance.ifInUnknownProtos

       64 bit unsigned wrappable counter."
   ::= {pr1645v2PppBFInUnknownProtEntry 2147483648}


pr1645v2PppBFInDropEx OBJECT IDENTIFIER ::= {pr1645v2PppBF 130}

pr1645v2PppBFInDropExTable OBJECT-TYPE
   SYNTAX      SEQUENCE OF Pr1645v2PppBFInDropExEntry
   MAX-ACCESS  not-accessible
   STATUS      current
   DESCRIPTION
      "ifInDiscards"
   ::= {pr1645v2PppBFInDropEx 1}

pr1645v2PppBFInDropExEntry OBJECT-TYPE
   SYNTAX      Pr1645v2PppBFInDropExEntry
   MAX-ACCESS  not-accessible
   STATUS      current
   DESCRIPTION
      ""
   INDEX      { pr1645v2PppBFInDropExGlobalIx }
   ::= {pr1645v2PppBFInDropExTable 1}

Pr1645v2PppBFInDropExEntry ::=
   SEQUENCE
      {
      pr1645v2PppBFInDropExGlobalIx
         GlobalIndex,
      pr1645v2PppBFInDropExValue
         Counter64
      }

pr1645v2PppBFInDropExGlobalIx OBJECT-TYPE
   SYNTAX      GlobalIndex
   MAX-ACCESS  not-accessible
   STATUS      current
   DESCRIPTION
      "The value of the tlsCntTreeGlobalIndex of the MANAGED OBJECT."
   ::= {pr1645v2PppBFInDropExEntry 10}

pr1645v2PppBFInDropExValue OBJECT-TYPE
   SYNTAX      Counter64
   MAX-ACCESS  read-only
   STATUS      current
   DESCRIPTION
      "Path: pppBundle.performance.ifInDropLevelExceeded

       64 bit unsigned wrappable counter."
   ::= {pr1645v2PppBFInDropExEntry 2147483648}


pr1645v2PppBFInDropNoMac OBJECT IDENTIFIER ::= {pr1645v2PppBF 133}

pr1645v2PppBFInDropNoMacTable OBJECT-TYPE
   SYNTAX      SEQUENCE OF Pr1645v2PppBFInDropNoMacEntry
   MAX-ACCESS  not-accessible
   STATUS      current
   DESCRIPTION
      "ifInDiscards"
   ::= {pr1645v2PppBFInDropNoMac 1}

pr1645v2PppBFInDropNoMacEntry OBJECT-TYPE
   SYNTAX      Pr1645v2PppBFInDropNoMacEntry
   MAX-ACCESS  not-accessible
   STATUS      current
   DESCRIPTION
      ""
   INDEX      { pr1645v2PppBFInDropNoMacGlobalIx }
   ::= {pr1645v2PppBFInDropNoMacTable 1}

Pr1645v2PppBFInDropNoMacEntry ::=
   SEQUENCE
      {
      pr1645v2PppBFInDropNoMacGlobalIx
         GlobalIndex,
      pr1645v2PppBFInDropNoMacValue
         Counter64
      }

pr1645v2PppBFInDropNoMacGlobalIx OBJECT-TYPE
   SYNTAX      GlobalIndex
   MAX-ACCESS  not-accessible
   STATUS      current
   DESCRIPTION
      "The value of the tlsCntTreeGlobalIndex of the MANAGED OBJECT."
   ::= {pr1645v2PppBFInDropNoMacEntry 10}

pr1645v2PppBFInDropNoMacValue OBJECT-TYPE
   SYNTAX      Counter64
   MAX-ACCESS  read-only
   STATUS      current
   DESCRIPTION
      "Path: pppBundle.performance.ifInDiscardsNoMacFit

       64 bit unsigned wrappable counter."
   ::= {pr1645v2PppBFInDropNoMacEntry 2147483648}


pr1645v2PppBFInDropNUCast OBJECT IDENTIFIER ::= {pr1645v2PppBF 136}

pr1645v2PppBFInDropNUCastTable OBJECT-TYPE
   SYNTAX      SEQUENCE OF Pr1645v2PppBFInDropNUCastEntry
   MAX-ACCESS  not-accessible
   STATUS      current
   DESCRIPTION
      "ifInDiscards"
   ::= {pr1645v2PppBFInDropNUCast 1}

pr1645v2PppBFInDropNUCastEntry OBJECT-TYPE
   SYNTAX      Pr1645v2PppBFInDropNUCastEntry
   MAX-ACCESS  not-accessible
   STATUS      current
   DESCRIPTION
      ""
   INDEX      { pr1645v2PppBFInDropNUCastGlobalIx }
   ::= {pr1645v2PppBFInDropNUCastTable 1}

Pr1645v2PppBFInDropNUCastEntry ::=
   SEQUENCE
      {
      pr1645v2PppBFInDropNUCastGlobalIx
         GlobalIndex,
      pr1645v2PppBFInDropNUCastValue
         Counter64
      }

pr1645v2PppBFInDropNUCastGlobalIx OBJECT-TYPE
   SYNTAX      GlobalIndex
   MAX-ACCESS  not-accessible
   STATUS      current
   DESCRIPTION
      "The value of the tlsCntTreeGlobalIndex of the MANAGED OBJECT."
   ::= {pr1645v2PppBFInDropNUCastEntry 10}

pr1645v2PppBFInDropNUCastValue OBJECT-TYPE
   SYNTAX      Counter64
   MAX-ACCESS  read-only
   STATUS      current
   DESCRIPTION
      "Path: pppBundle.performance.ifInDiscardsNUCast

       64 bit unsigned wrappable counter."
   ::= {pr1645v2PppBFInDropNUCastEntry 2147483648}


pr1645v2PppBFInDropFilter OBJECT IDENTIFIER ::= {pr1645v2PppBF 137}

pr1645v2PppBFInDropFilterTable OBJECT-TYPE
   SYNTAX      SEQUENCE OF Pr1645v2PppBFInDropFilterEntry
   MAX-ACCESS  not-accessible
   STATUS      current
   DESCRIPTION
      "ifInDiscards"
   ::= {pr1645v2PppBFInDropFilter 1}

pr1645v2PppBFInDropFilterEntry OBJECT-TYPE
   SYNTAX      Pr1645v2PppBFInDropFilterEntry
   MAX-ACCESS  not-accessible
   STATUS      current
   DESCRIPTION
      ""
   INDEX      { pr1645v2PppBFInDropFilterGlobalIx }
   ::= {pr1645v2PppBFInDropFilterTable 1}

Pr1645v2PppBFInDropFilterEntry ::=
   SEQUENCE
      {
      pr1645v2PppBFInDropFilterGlobalIx
         GlobalIndex,
      pr1645v2PppBFInDropFilterValue
         Counter64
      }

pr1645v2PppBFInDropFilterGlobalIx OBJECT-TYPE
   SYNTAX      GlobalIndex
   MAX-ACCESS  not-accessible
   STATUS      current
   DESCRIPTION
      "The value of the tlsCntTreeGlobalIndex of the MANAGED OBJECT."
   ::= {pr1645v2PppBFInDropFilterEntry 10}

pr1645v2PppBFInDropFilterValue OBJECT-TYPE
   SYNTAX      Counter64
   MAX-ACCESS  read-only
   STATUS      current
   DESCRIPTION
      "Path: pppBundle.performance.ifInDiscardsFilter

       64 bit unsigned wrappable counter."
   ::= {pr1645v2PppBFInDropFilterEntry 2147483648}


pr1645v2PppBFIfInPriorityQueues OBJECT IDENTIFIER ::= {pr1645v2PppBF 131}

pr1645v2PppBFIfInPriorityQueuesSSCTable OBJECT-TYPE
   SYNTAX      SEQUENCE OF Pr1645v2PppBFIfInPriorityQueuesEntry
   MAX-ACCESS  not-accessible
   STATUS      current
   DESCRIPTION
      "Queue Lengths"
   ::= {pr1645v2PppBFIfInPriorityQueues 1}

pr1645v2PppBFIfInPriorityQueuesEntry OBJECT-TYPE
   SYNTAX      Pr1645v2PppBFIfInPriorityQueuesEntry
   MAX-ACCESS  not-accessible
   STATUS      current
   DESCRIPTION
      ""
   INDEX      { pr1645v2PppBFIfInPriorityQueuesGlobalIx,
                pr1645v2PppBFIfInPriorityQueuesTableIx }
   ::= {pr1645v2PppBFIfInPriorityQueuesSSCTable 1}

Pr1645v2PppBFIfInPriorityQueuesEntry ::=
   SEQUENCE
      {
      pr1645v2PppBFIfInPriorityQueuesGlobalIx
         GlobalIndex,
      pr1645v2PppBFIfInPriorityQueuesTableIx
         TableIndex,
      pr1645v2PppBFIfInPriorityQueuesName
         INTEGER,
      pr1645v2PppBFIfInPriorityQueuesLength
         Integer32,
      pr1645v2PppBFIfInPriorityQueuesOctetLength
         Integer32,
      pr1645v2PppBFIfInPriorityQueuesRedLength
         Integer32,
      pr1645v2PppBFIfInPriorityQueuesPacketsTotal
         Counter64,
      pr1645v2PppBFIfInPriorityQueuesPacketsDirectTx
         Counter64,
      pr1645v2PppBFIfInPriorityQueuesPacketsQueued
         Counter64,
      pr1645v2PppBFIfInPriorityQueuesPacketsDropped
         Counter64,
      pr1645v2PppBFIfInPriorityQueuesPacketsRedDropped
         Counter64,
      pr1645v2PppBFIfInPriorityQueuesPacketsCirTx
         Counter64,
      pr1645v2PppBFIfInPriorityQueuesPacketsEirTx
         Counter64,
      pr1645v2PppBFIfInPriorityQueuesPacketsViolateTx
         Counter64,
      pr1645v2PppBFIfInPriorityQueuesOctetsTotal
         Counter64,
      pr1645v2PppBFIfInPriorityQueuesOctetsDirectTx
         Counter64,
      pr1645v2PppBFIfInPriorityQueuesOctetsQueued
         Counter64,
      pr1645v2PppBFIfInPriorityQueuesOctetsDropped
         Counter64,
      pr1645v2PppBFIfInPriorityQueuesOctetsRedDropped
         Counter64,
      pr1645v2PppBFIfInPriorityQueuesOctetsCirTx
         Counter64,
      pr1645v2PppBFIfInPriorityQueuesOctetsEirTx
         Counter64,
      pr1645v2PppBFIfInPriorityQueuesOctetsViolateTx
         Counter64,
      pr1645v2PppBFIfInPriorityQueuesOctetsBandwidth15sec
         Integer32,
      pr1645v2PppBFIfInPriorityQueuesOctetsBandwidth30sec
         Integer32,
      pr1645v2PppBFIfInPriorityQueuesOctetsBandwidth1min
         Integer32,
      pr1645v2PppBFIfInPriorityQueuesOctetsBandwidth2min
         Integer32,
      pr1645v2PppBFIfInPriorityQueuesOctetsBandwidth5min
         Integer32
      }

pr1645v2PppBFIfInPriorityQueuesGlobalIx OBJECT-TYPE
   SYNTAX      GlobalIndex
   MAX-ACCESS  not-accessible
   STATUS      current
   DESCRIPTION
      "The value of the tlsCntTreeGlobalIndex of the MANAGED OBJECT."
   ::= {pr1645v2PppBFIfInPriorityQueuesEntry 10}

pr1645v2PppBFIfInPriorityQueuesTableIx OBJECT-TYPE
   SYNTAX      TableIndex
   MAX-ACCESS  not-accessible
   STATUS      current
   DESCRIPTION
      ""
   ::= {pr1645v2PppBFIfInPriorityQueuesEntry 11}

pr1645v2PppBFIfInPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: pppBundle.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PppBFIfInPriorityQueuesEntry 16777216}

pr1645v2PppBFIfInPriorityQueuesLength OBJECT-TYPE
   SYNTAX      Integer32
   MAX-ACCESS  read-only
   STATUS      current
   DESCRIPTION
      "Path: pppBundle.performance.ifInPriorityQueues.length"
   ::= {pr1645v2PppBFIfInPriorityQueuesEntry 33554432}

pr1645v2PppBFIfInPriorityQueuesOctetLength OBJECT-TYPE
   SYNTAX      Integer32
   MAX-ACCESS  read-only
   STATUS      current
   DESCRIPTION
      "Path: pppBundle.performance.ifInPriorityQueues.octetLength"
   ::= {pr1645v2PppBFIfInPriorityQueuesEntry 150994944}

pr1645v2PppBFIfInPriorityQueuesRedLength OBJECT-TYPE
   SYNTAX      Integer32
   MAX-ACCESS  read-only
   STATUS      current
   DESCRIPTION
      "Path: pppBundle.performance.ifInPriorityQueues.redLength"
   ::= {pr1645v2PppBFIfInPriorityQueuesEntry 134217728}

pr1645v2PppBFIfInPriorityQueuesPacketsTotal OBJECT-TYPE
   SYNTAX      Counter64
   MAX-ACCESS  read-only
   STATUS      current
   DESCRIPTION
      "Path: pppBundle.performance.ifInPriorityQueues.packets.total

       64 bit unsigned wrappable counter."
   ::= {pr1645v2PppBFIfInPriorityQueuesEntry 50790400}

pr1645v2PppBFIfInPriorityQueuesPacketsDirectTx OBJECT-TYPE
   SYNTAX      Counter64
   MAX-ACCESS  read-only
   STATUS      current
   DESCRIPTION
      "Path: pppBundle.performance.ifInPriorityQueues.packets.directTx

       64 bit unsigned wrappable counter."
   ::= {pr1645v2PppBFIfInPriorityQueuesEntry 50397184}

pr1645v2PppBFIfInPriorityQueuesPacketsQueued OBJECT-TYPE
   SYNTAX      Counter64
   MAX-ACCESS  read-only
   STATUS      current
   DESCRIPTION
      "Path: pppBundle.performance.ifInPriorityQueues.packets.queued

       64 bit unsigned wrappable counter."
   ::= {pr1645v2PppBFIfInPriorityQueuesEntry 50462720}

pr1645v2PppBFIfInPriorityQueuesPacketsDropped OBJECT-TYPE
   SYNTAX      Counter64
   MAX-ACCESS  read-only
   STATUS      current
   DESCRIPTION
      "Path: pppBundle.performance.ifInPriorityQueues.packets.dropped

       64 bit unsigned wrappable counter."
   ::= {pr1645v2PppBFIfInPriorityQueuesEntry 50528256}

pr1645v2PppBFIfInPriorityQueuesPacketsRedDropped OBJECT-TYPE
   SYNTAX      Counter64
   MAX-ACCESS  read-only
   STATUS      current
   DESCRIPTION
      "Path: pppBundle.performance.ifInPriorityQueues.packets.redDropped

       64 bit unsigned wrappable counter."
   ::= {pr1645v2PppBFIfInPriorityQueuesEntry 50724864}

pr1645v2PppBFIfInPriorityQueuesPacketsCirTx OBJECT-TYPE
   SYNTAX      Counter64
   MAX-ACCESS  read-only
   STATUS      current
   DESCRIPTION
      "Path: pppBundle.performance.ifInPriorityQueues.packets.cirTx

       64 bit unsigned wrappable counter."
   ::= {pr1645v2PppBFIfInPriorityQueuesEntry 50593792}

pr1645v2PppBFIfInPriorityQueuesPacketsEirTx OBJECT-TYPE
   SYNTAX      Counter64
   MAX-ACCESS  read-only
   STATUS      current
   DESCRIPTION
      "Path: pppBundle.performance.ifInPriorityQueues.packets.eirTx

       64 bit unsigned wrappable counter."
   ::= {pr1645v2PppBFIfInPriorityQueuesEntry 50659328}

pr1645v2PppBFIfInPriorityQueuesPacketsViolateTx OBJECT-TYPE
   SYNTAX      Counter64
   MAX-ACCESS  read-only
   STATUS      current
   DESCRIPTION
      "Path: pppBundle.performance.ifInPriorityQueues.packets.violateTx

       64 bit unsigned wrappable counter."
   ::= {pr1645v2PppBFIfInPriorityQueuesEntry 50855936}

pr1645v2PppBFIfInPriorityQueuesOctetsTotal OBJECT-TYPE
   SYNTAX      Counter64
   MAX-ACCESS  read-only
   STATUS      current
   DESCRIPTION
      "Path: pppBundle.performance.ifInPriorityQueues.octets.total

       64 bit unsigned wrappable counter."
   ::= {pr1645v2PppBFIfInPriorityQueuesEntry 67567616}

pr1645v2PppBFIfInPriorityQueuesOctetsDirectTx OBJECT-TYPE
   SYNTAX      Counter64
   MAX-ACCESS  read-only
   STATUS      current
   DESCRIPTION
      "Path: pppBundle.performance.ifInPriorityQueues.octets.directTx

       64 bit unsigned wrappable counter."
   ::= {pr1645v2PppBFIfInPriorityQueuesEntry 67174400}

pr1645v2PppBFIfInPriorityQueuesOctetsQueued OBJECT-TYPE
   SYNTAX      Counter64
   MAX-ACCESS  read-only
   STATUS      current
   DESCRIPTION
      "Path: pppBundle.performance.ifInPriorityQueues.octets.queued

       64 bit unsigned wrappable counter."
   ::= {pr1645v2PppBFIfInPriorityQueuesEntry 67239936}

pr1645v2PppBFIfInPriorityQueuesOctetsDropped OBJECT-TYPE
   SYNTAX      Counter64
   MAX-ACCESS  read-only
   STATUS      current
   DESCRIPTION
      "Path: pppBundle.performance.ifInPriorityQueues.octets.dropped

       64 bit unsigned wrappable counter."
   ::= {pr1645v2PppBFIfInPriorityQueuesEntry 67305472}

pr1645v2PppBFIfInPriorityQueuesOctetsRedDropped OBJECT-TYPE
   SYNTAX      Counter64
   MAX-ACCESS  read-only
   STATUS      current
   DESCRIPTION
      "Path: pppBundle.performance.ifInPriorityQueues.octets.redDropped

       64 bit unsigned wrappable counter."
   ::= {pr1645v2PppBFIfInPriorityQueuesEntry 67502080}

pr1645v2PppBFIfInPriorityQueuesOctetsCirTx OBJECT-TYPE
   SYNTAX      Counter64
   MAX-ACCESS  read-only
   STATUS      current
   DESCRIPTION
      "Path: pppBundle.performance.ifInPriorityQueues.octets.cirTx

       64 bit unsigned wrappable counter."
   ::= {pr1645v2PppBFIfInPriorityQueuesEntry 67371008}

pr1645v2PppBFIfInPriorityQueuesOctetsEirTx OBJECT-TYPE
   SYNTAX      Counter64
   MAX-ACCESS  read-only
   STATUS      current
   DESCRIPTION
      "Path: pppBundle.performance.ifInPriorityQueues.octets.eirTx

       64 bit unsigned wrappable counter."
   ::= {pr1645v2PppBFIfInPriorityQueuesEntry 67436544}

pr1645v2PppBFIfInPriorityQueuesOctetsViolateTx OBJECT-TYPE
   SYNTAX      Counter64
   MAX-ACCESS  read-only
   STATUS      current
   DESCRIPTION
      "Path: pppBundle.performance.ifInPriorityQueues.octets.violateTx

       64 bit unsigned wrappable counter."
   ::= {pr1645v2PppBFIfInPriorityQueuesEntry 67633152}

pr1645v2PppBFIfInPriorityQueuesOctetsBandwidth15sec OBJECT-TYPE
   SYNTAX      Integer32
   MAX-ACCESS  read-only
   STATUS      current
   DESCRIPTION
      "Path: pppBundle.performance.ifInPriorityQueues.octets.bandwidth.15sec

       unit name = bps
       formula = 8 * ; 8 /"
   ::= {pr1645v2PppBFIfInPriorityQueuesEntry 70386944}

pr1645v2PppBFIfInPriorityQueuesOctetsBandwidth30sec OBJECT-TYPE
   SYNTAX      Integer32
   MAX-ACCESS  read-only
   STATUS      current
   DESCRIPTION
      "Path: pppBundle.performance.ifInPriorityQueues.octets.bandwidth.30sec

       unit name = bps
       formula = 8 * ; 8 /"
   ::= {pr1645v2PppBFIfInPriorityQueuesEntry 70388224}

pr1645v2PppBFIfInPriorityQueuesOctetsBandwidth1min OBJECT-TYPE
   SYNTAX      Integer32
   MAX-ACCESS  read-only
   STATUS      current
   DESCRIPTION
      "Path: pppBundle.performance.ifInPriorityQueues.octets.bandwidth.1min

       unit name = bps
       formula = 8 * ; 8 /"
   ::= {pr1645v2PppBFIfInPriorityQueuesEntry 70390784}

pr1645v2PppBFIfInPriorityQueuesOctetsBandwidth2min OBJECT-TYPE
   SYNTAX      Integer32
   MAX-ACCESS  read-only
   STATUS      current
   DESCRIPTION
      "Path: pppBundle.performance.ifInPriorityQueues.octets.bandwidth.2min

       unit name = bps
       formula = 8 * ; 8 /"
   ::= {pr1645v2PppBFIfInPriorityQueuesEntry 70395904}

pr1645v2PppBFIfInPriorityQueuesOctetsBandwidth5min OBJECT-TYPE
   SYNTAX      Integer32
   MAX-ACCESS  read-only
   STATUS      current
   DESCRIPTION
      "Path: pppBundle.performance.ifInPriorityQueues.octets.bandwidth.5min

       unit name = bps
       formula = 8 * ; 8 /"
   ::= {pr1645v2PppBFIfInPriorityQueuesEntry 70411264}

pr1645v2PppBFIfInPriorityQueuesH2Performance OBJECT-TYPE
   SYNTAX      SEQUENCE OF Pr1645v2PppBFIfInPriorityQueuesH2PerformanceEntry
   MAX-ACCESS  not-accessible
   STATUS      current
   DESCRIPTION
      ""
   ::= {pr1645v2PppBFIfInPriorityQueues 83886080}

pr1645v2PppBFIfInPriorityQueuesH2PerformanceEntry OBJECT-TYPE
   SYNTAX      Pr1645v2PppBFIfInPriorityQueuesH2PerformanceEntry
   MAX-ACCESS  not-accessible
   STATUS      current
   DESCRIPTION
      ""
   INDEX      { pr1645v2PppBFIfInPriorityQueuesH2PerformanceGlobalIx,
                pr1645v2PppBFIfInPriorityQueuesTableIx,
                pr1645v2PppBFIfInPriorityQueuesH2PerformanceTableIx }
   ::= {pr1645v2PppBFIfInPriorityQueuesH2Performance 1}

Pr1645v2PppBFIfInPriorityQueuesH2PerformanceEntry ::=
   SEQUENCE
      {
      pr1645v2PppBFIfInPriorityQueuesH2PerformanceGlobalIx
         GlobalIndex,
      pr1645v2PppBFIfInPriorityQueuesH2PerformanceTableIx
         TableIndex,
      pr1645v2PppBFIfInPriorityQueuesH2PerformanceSysUpTime
         TimeTicks,
      pr1645v2PppBFIfInPriorityQueuesH2PerformanceTotPkts
         Counter64,
      pr1645v2PppBFIfInPriorityQueuesH2PerformanceDirTxPkts
         Counter64,
      pr1645v2PppBFIfInPriorityQueuesH2PerformanceQdPkts
         Counter64,
      pr1645v2PppBFIfInPriorityQueuesH2PerformanceDropPkts
         Counter64,
      pr1645v2PppBFIfInPriorityQueuesH2PerformanceRDropPkts
         Counter64,
      pr1645v2PppBFIfInPriorityQueuesH2PerformanceCirTxPkts
         Counter64,
      pr1645v2PppBFIfInPriorityQueuesH2PerformanceEirTxPkts
         Counter64,
      pr1645v2PppBFIfInPriorityQueuesH2PerformanceViolTxPkts
         Counter64,
      pr1645v2PppBFIfInPriorityQueuesH2PerformanceTotOcts
         Counter64,
      pr1645v2PppBFIfInPriorityQueuesH2PerformanceDirTxOcts
         Counter64,
      pr1645v2PppBFIfInPriorityQueuesH2PerformanceQdOcts
         Counter64,
      pr1645v2PppBFIfInPriorityQueuesH2PerformanceDropOcts
         Counter64,
      pr1645v2PppBFIfInPriorityQueuesH2PerformanceRDropOcts
         Counter64,
      pr1645v2PppBFIfInPriorityQueuesH2PerformanceCirTxOcts
         Counter64,
      pr1645v2PppBFIfInPriorityQueuesH2PerformanceEirTxOcts
         Counter64,
      pr1645v2PppBFIfInPriorityQueuesH2PerformanceViolTxOcts
         Counter64,
      pr1645v2PppBFIfInPriorityQueuesH2PerformanceBandwidth
         Integer32
      }

pr1645v2PppBFIfInPriorityQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2PppBFIfInPriorityQueuesH2PerformanceEntry 10}

pr1645v2PppBFIfInPriorityQueuesH2PerformanceTableIx OBJECT-TYPE
   SYNTAX      TableIndex
   MAX-ACCESS  not-accessible
   STATUS      current
   DESCRIPTION
      ""
   ::= {pr1645v2PppBFIfInPriorityQueuesH2PerformanceEntry 11}

pr1645v2PppBFIfInPriorityQueuesH2PerformanceSysUpTime OBJECT-TYPE
   SYNTAX      TimeTicks
   MAX-ACCESS  read-only
   STATUS      current
   DESCRIPTION
      "Path: pppBundle.performance.ifInPriorityQueues.h2Performance.sysUpTime

       Time in centi-second."
   ::= {pr1645v2PppBFIfInPriorityQueuesH2PerformanceEntry 16777216}

pr1645v2PppBFIfInPriorityQueuesH2PerformanceTotPkts OBJECT-TYPE
   SYNTAX      Counter64
   MAX-ACCESS  read-only
   STATUS      current
   DESCRIPTION
      "Path: pppBundle.performance.ifInPriorityQueues.h2Performance.totalPkts

       64 bit unsigned wrappable counter."
   ::= {pr1645v2PppBFIfInPriorityQueuesH2PerformanceEntry 234881024}

pr1645v2PppBFIfInPriorityQueuesH2PerformanceDirTxPkts OBJECT-TYPE
   SYNTAX      Counter64
   MAX-ACCESS  read-only
   STATUS      current
   DESCRIPTION
      "Path: pppBundle.performance.ifInPriorityQueues.h2Performance.directTxPkts

       64 bit unsigned wrappable counter."
   ::= {pr1645v2PppBFIfInPriorityQueuesH2PerformanceEntry 33554432}

pr1645v2PppBFIfInPriorityQueuesH2PerformanceQdPkts OBJECT-TYPE
   SYNTAX      Counter64
   MAX-ACCESS  read-only
   STATUS      current
   DESCRIPTION
      "Path: pppBundle.performance.ifInPriorityQueues.h2Performance.queuedPkts

       64 bit unsigned wrappable counter."
   ::= {pr1645v2PppBFIfInPriorityQueuesH2PerformanceEntry 50331648}

pr1645v2PppBFIfInPriorityQueuesH2PerformanceDropPkts OBJECT-TYPE
   SYNTAX      Counter64
   MAX-ACCESS  read-only
   STATUS      current
   DESCRIPTION
      "Path: pppBundle.performance.ifInPriorityQueues.h2Performance.droppedPkts

       64 bit unsigned wrappable counter."
   ::= {pr1645v2PppBFIfInPriorityQueuesH2PerformanceEntry 67108864}

pr1645v2PppBFIfInPriorityQueuesH2PerformanceRDropPkts OBJECT-TYPE
   SYNTAX      Counter64
   MAX-ACCESS  read-only
   STATUS      current
   DESCRIPTION
      "Path: pppBundle.performance.ifInPriorityQueues.h2Performance.redDroppedPkts

       64 bit unsigned wrappable counter."
   ::= {pr1645v2PppBFIfInPriorityQueuesH2PerformanceEntry 201326592}

pr1645v2PppBFIfInPriorityQueuesH2PerformanceCirTxPkts OBJECT-TYPE
   SYNTAX      Counter64
   MAX-ACCESS  read-only
   STATUS      current
   DESCRIPTION
      "Path: pppBundle.performance.ifInPriorityQueues.h2Performance.cirTxPkts

       64 bit unsigned wrappable counter."
   ::= {pr1645v2PppBFIfInPriorityQueuesH2PerformanceEntry 83886080}

pr1645v2PppBFIfInPriorityQueuesH2PerformanceEirTxPkts OBJECT-TYPE
   SYNTAX      Counter64
   MAX-ACCESS  read-only
   STATUS      current
   DESCRIPTION
      "Path: pppBundle.performance.ifInPriorityQueues.h2Performance.eirTxPkts

       64 bit unsigned wrappable counter."
   ::= {pr1645v2PppBFIfInPriorityQueuesH2PerformanceEntry 100663296}

pr1645v2PppBFIfInPriorityQueuesH2PerformanceViolTxPkts OBJECT-TYPE
   SYNTAX      Counter64
   MAX-ACCESS  read-only
   STATUS      current
   DESCRIPTION
      "Path: pppBundle.performance.ifInPriorityQueues.h2Performance.violateTxPkts

       64 bit unsigned wrappable counter."
   ::= {pr1645v2PppBFIfInPriorityQueuesH2PerformanceEntry 301989888}

pr1645v2PppBFIfInPriorityQueuesH2PerformanceTotOcts OBJECT-TYPE
   SYNTAX      Counter64
   MAX-ACCESS  read-only
   STATUS      current
   DESCRIPTION
      "Path: pppBundle.performance.ifInPriorityQueues.h2Performance.totalOctets

       64 bit unsigned wrappable counter."
   ::= {pr1645v2PppBFIfInPriorityQueuesH2PerformanceEntry 251658240}

pr1645v2PppBFIfInPriorityQueuesH2PerformanceDirTxOcts OBJECT-TYPE
   SYNTAX      Counter64
   MAX-ACCESS  read-only
   STATUS      current
   DESCRIPTION
      "Path: pppBundle.performance.ifInPriorityQueues.h2Performance.directTxOctets

       64 bit unsigned wrappable counter."
   ::= {pr1645v2PppBFIfInPriorityQueuesH2PerformanceEntry 117440512}

pr1645v2PppBFIfInPriorityQueuesH2PerformanceQdOcts OBJECT-TYPE
   SYNTAX      Counter64
   MAX-ACCESS  read-only
   STATUS      current
   DESCRIPTION
      "Path: pppBundle.performance.ifInPriorityQueues.h2Performance.queuedOctets

       64 bit unsigned wrappable counter."
   ::= {pr1645v2PppBFIfInPriorityQueuesH2PerformanceEntry 134217728}

pr1645v2PppBFIfInPriorityQueuesH2PerformanceDropOcts OBJECT-TYPE
   SYNTAX      Counter64
   MAX-ACCESS  read-only
   STATUS      current
   DESCRIPTION
      "Path: pppBundle.performance.ifInPriorityQueues.h2Performance.droppedOctets

       64 bit unsigned wrappable counter."
   ::= {pr1645v2PppBFIfInPriorityQueuesH2PerformanceEntry 150994944}

pr1645v2PppBFIfInPriorityQueuesH2PerformanceRDropOcts OBJECT-TYPE
   SYNTAX      Counter64
   MAX-ACCESS  read-only
   STATUS      current
   DESCRIPTION
      "Path: pppBundle.performance.ifInPriorityQueues.h2Performance.redDroppedOctets

       64 bit unsigned wrappable counter."
   ::= {pr1645v2PppBFIfInPriorityQueuesH2PerformanceEntry 218103808}

pr1645v2PppBFIfInPriorityQueuesH2PerformanceCirTxOcts OBJECT-TYPE
   SYNTAX      Counter64
   MAX-ACCESS  read-only
   STATUS      current
   DESCRIPTION
      "Path: pppBundle.performance.ifInPriorityQueues.h2Performance.cirTxOctets

       64 bit unsigned wrappable counter."
   ::= {pr1645v2PppBFIfInPriorityQueuesH2PerformanceEntry 167772160}

pr1645v2PppBFIfInPriorityQueuesH2PerformanceEirTxOcts OBJECT-TYPE
   SYNTAX      Counter64
   MAX-ACCESS  read-only
   STATUS      current
   DESCRIPTION
      "Path: pppBundle.performance.ifInPriorityQueues.h2Performance.eirTxOctets

       64 bit unsigned wrappable counter."
   ::= {pr1645v2PppBFIfInPriorityQueuesH2PerformanceEntry 184549376}

pr1645v2PppBFIfInPriorityQueuesH2PerformanceViolTxOcts OBJECT-TYPE
   SYNTAX      Counter64
   MAX-ACCESS  read-only
   STATUS      current
   DESCRIPTION
      "Path: pppBundle.performance.ifInPriorityQueues.h2Performance.violateTxOctets

       64 bit unsigned wrappable counter."
   ::= {pr1645v2PppBFIfInPriorityQueuesH2PerformanceEntry 318767104}

pr1645v2PppBFIfInPriorityQueuesH2PerformanceBandwidth OBJECT-TYPE
   SYNTAX      Integer32
   MAX-ACCESS  read-only
   STATUS      current
   DESCRIPTION
      "Path: pppBundle.performance.ifInPriorityQueues.h2Performance.bandwidth

       unit name = bps
       formula = 8 * ; 8 /"
   ::= {pr1645v2PppBFIfInPriorityQueuesH2PerformanceEntry 268435456}

pr1645v2PppBFIfInPriorityQueuesH24Performance OBJECT-TYPE
   SYNTAX      SEQUENCE OF Pr1645v2PppBFIfInPriorityQueuesH24PerformanceEntry
   MAX-ACCESS  not-accessible
   STATUS      current
   DESCRIPTION
      ""
   ::= {pr1645v2PppBFIfInPriorityQueues 100663296}

pr1645v2PppBFIfInPriorityQueuesH24PerformanceEntry OBJECT-TYPE
   SYNTAX      Pr1645v2PppBFIfInPriorityQueuesH24PerformanceEntry
   MAX-ACCESS  not-accessible
   STATUS      current
   DESCRIPTION
      ""
   INDEX      { pr1645v2PppBFIfInPriorityQueuesH24PerformanceGlobalIx,
                pr1645v2PppBFIfInPriorityQueuesTableIx,
                pr1645v2PppBFIfInPriorityQueuesH24PerformanceTableIx }
   ::= {pr1645v2PppBFIfInPriorityQueuesH24Performance 1}

Pr1645v2PppBFIfInPriorityQueuesH24PerformanceEntry ::=
   SEQUENCE
      {
      pr1645v2PppBFIfInPriorityQueuesH24PerformanceGlobalIx
         GlobalIndex,
      pr1645v2PppBFIfInPriorityQueuesH24PerformanceTableIx
         TableIndex,
      pr1645v2PppBFIfInPriorityQueuesH24PerformanceSysUpTime
         TimeTicks,
      pr1645v2PppBFIfInPriorityQueuesH24PerformanceTotPkts
         Counter64,
      pr1645v2PppBFIfInPriorityQueuesH24PerformanceDirTxPkts
         Counter64,
      pr1645v2PppBFIfInPriorityQueuesH24PerformanceQdPkts
         Counter64,
      pr1645v2PppBFIfInPriorityQueuesH24PerformanceDropPkts
         Counter64,
      pr1645v2PppBFIfInPriorityQueuesH24PerformanceRDropPkts
         Counter64,
      pr1645v2PppBFIfInPriorityQueuesH24PerformanceCirTxPkts
         Counter64,
      pr1645v2PppBFIfInPriorityQueuesH24PerformanceEirTxPkts
         Counter64,
      pr1645v2PppBFIfInPriorityQueuesH24PerformanceViolTxPkts
         Counter64,
      pr1645v2PppBFIfInPriorityQueuesH24PerformanceTotOcts
         Counter64,
      pr1645v2PppBFIfInPriorityQueuesH24PerformanceDirTxOcts
         Counter64,
      pr1645v2PppBFIfInPriorityQueuesH24PerformanceQdOcts
         Counter64,
      pr1645v2PppBFIfInPriorityQueuesH24PerformanceDropOcts
         Counter64,
      pr1645v2PppBFIfInPriorityQueuesH24PerformanceRDropOcts
         Counter64,
      pr1645v2PppBFIfInPriorityQueuesH24PerformanceCirTxOcts
         Counter64,
      pr1645v2PppBFIfInPriorityQueuesH24PerformanceEirTxOcts
         Counter64,
      pr1645v2PppBFIfInPriorityQueuesH24PerformanceViolTxOcts
         Counter64,
      pr1645v2PppBFIfInPriorityQueuesH24PerformanceBandwidth
         Integer32
      }

pr1645v2PppBFIfInPriorityQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2PppBFIfInPriorityQueuesH24PerformanceEntry 10}

pr1645v2PppBFIfInPriorityQueuesH24PerformanceTableIx OBJECT-TYPE
   SYNTAX      TableIndex
   MAX-ACCESS  not-accessible
   STATUS      current
   DESCRIPTION
      ""
   ::= {pr1645v2PppBFIfInPriorityQueuesH24PerformanceEntry 11}

pr1645v2PppBFIfInPriorityQueuesH24PerformanceSysUpTime OBJECT-TYPE
   SYNTAX      TimeTicks
   MAX-ACCESS  read-only
   STATUS      current
   DESCRIPTION
      "Path: pppBundle.performance.ifInPriorityQueues.h24Performance.sysUpTime

       Time in centi-second."
   ::= {pr1645v2PppBFIfInPriorityQueuesH24PerformanceEntry 16777216}

pr1645v2PppBFIfInPriorityQueuesH24PerformanceTotPkts OBJECT-TYPE
   SYNTAX      Counter64
   MAX-ACCESS  read-only
   STATUS      current
   DESCRIPTION
      "Path: pppBundle.performance.ifInPriorityQueues.h24Performance.totalPkts

       64 bit unsigned wrappable counter."
   ::= {pr1645v2PppBFIfInPriorityQueuesH24PerformanceEntry 234881024}

pr1645v2PppBFIfInPriorityQueuesH24PerformanceDirTxPkts OBJECT-TYPE
   SYNTAX      Counter64
   MAX-ACCESS  read-only
   STATUS      current
   DESCRIPTION
      "Path: pppBundle.performance.ifInPriorityQueues.h24Performance.directTxPkts

       64 bit unsigned wrappable counter."
   ::= {pr1645v2PppBFIfInPriorityQueuesH24PerformanceEntry 33554432}

pr1645v2PppBFIfInPriorityQueuesH24PerformanceQdPkts OBJECT-TYPE
   SYNTAX      Counter64
   MAX-ACCESS  read-only
   STATUS      current
   DESCRIPTION
      "Path: pppBundle.performance.ifInPriorityQueues.h24Performance.queuedPkts

       64 bit unsigned wrappable counter."
   ::= {pr1645v2PppBFIfInPriorityQueuesH24PerformanceEntry 50331648}

pr1645v2PppBFIfInPriorityQueuesH24PerformanceDropPkts OBJECT-TYPE
   SYNTAX      Counter64
   MAX-ACCESS  read-only
   STATUS      current
   DESCRIPTION
      "Path: pppBundle.performance.ifInPriorityQueues.h24Performance.droppedPkts

       64 bit unsigned wrappable counter."
   ::= {pr1645v2PppBFIfInPriorityQueuesH24PerformanceEntry 67108864}

pr1645v2PppBFIfInPriorityQueuesH24PerformanceRDropPkts OBJECT-TYPE
   SYNTAX      Counter64
   MAX-ACCESS  read-only
   STATUS      current
   DESCRIPTION
      "Path: pppBundle.performance.ifInPriorityQueues.h24Performance.redDroppedPkts

       64 bit unsigned wrappable counter."
   ::= {pr1645v2PppBFIfInPriorityQueuesH24PerformanceEntry 201326592}

pr1645v2PppBFIfInPriorityQueuesH24PerformanceCirTxPkts OBJECT-TYPE
   SYNTAX      Counter64
   MAX-ACCESS  read-only
   STATUS      current
   DESCRIPTION
      "Path: pppBundle.performance.ifInPriorityQueues.h24Performance.cirTxPkts

       64 bit unsigned wrappable counter."
   ::= {pr1645v2PppBFIfInPriorityQueuesH24PerformanceEntry 83886080}

pr1645v2PppBFIfInPriorityQueuesH24PerformanceEirTxPkts OBJECT-TYPE
   SYNTAX      Counter64
   MAX-ACCESS  read-only
   STATUS      current
   DESCRIPTION
      "Path: pppBundle.performance.ifInPriorityQueues.h24Performance.eirTxPkts

       64 bit unsigned wrappable counter."
   ::= {pr1645v2PppBFIfInPriorityQueuesH24PerformanceEntry 100663296}

pr1645v2PppBFIfInPriorityQueuesH24PerformanceViolTxPkts OBJECT-TYPE
   SYNTAX      Counter64
   MAX-ACCESS  read-only
   STATUS      current
   DESCRIPTION
      "Path: pppBundle.performance.ifInPriorityQueues.h24Performance.violateTxPkts

       64 bit unsigned wrappable counter."
   ::= {pr1645v2PppBFIfInPriorityQueuesH24PerformanceEntry 301989888}

pr1645v2PppBFIfInPriorityQueuesH24PerformanceTotOcts OBJECT-TYPE
   SYNTAX      Counter64
   MAX-ACCESS  read-only
   STATUS      current
   DESCRIPTION
      "Path: pppBundle.performance.ifInPriorityQueues.h24Performance.totalOctets

       64 bit unsigned wrappable counter."
   ::= {pr1645v2PppBFIfInPriorityQueuesH24PerformanceEntry 251658240}

pr1645v2PppBFIfInPriorityQueuesH24PerformanceDirTxOcts OBJECT-TYPE
   SYNTAX      Counter64
   MAX-ACCESS  read-only
   STATUS      current
   DESCRIPTION
      "Path: pppBundle.performance.ifInPriorityQueues.h24Performance.directTxOctets

       64 bit unsigned wrappable counter."
   ::= {pr1645v2PppBFIfInPriorityQueuesH24PerformanceEntry 117440512}

pr1645v2PppBFIfInPriorityQueuesH24PerformanceQdOcts OBJECT-TYPE
   SYNTAX      Counter64
   MAX-ACCESS  read-only
   STATUS      current
   DESCRIPTION
      "Path: pppBundle.performance.ifInPriorityQueues.h24Performance.queuedOctets

       64 bit unsigned wrappable counter."
   ::= {pr1645v2PppBFIfInPriorityQueuesH24PerformanceEntry 134217728}

pr1645v2PppBFIfInPriorityQueuesH24PerformanceDropOcts OBJECT-TYPE
   SYNTAX      Counter64
   MAX-ACCESS  read-only
   STATUS      current
   DESCRIPTION
      "Path: pppBundle.performance.ifInPriorityQueues.h24Performance.droppedOctets

       64 bit unsigned wrappable counter."
   ::= {pr1645v2PppBFIfInPriorityQueuesH24PerformanceEntry 150994944}

pr1645v2PppBFIfInPriorityQueuesH24PerformanceRDropOcts OBJECT-TYPE
   SYNTAX      Counter64
   MAX-ACCESS  read-only
   STATUS      current
   DESCRIPTION
      "Path: pppBundle.performance.ifInPriorityQueues.h24Performance.redDroppedOctets

       64 bit unsigned wrappable counter."
   ::= {pr1645v2PppBFIfInPriorityQueuesH24PerformanceEntry 218103808}

pr1645v2PppBFIfInPriorityQueuesH24PerformanceCirTxOcts OBJECT-TYPE
   SYNTAX      Counter64
   MAX-ACCESS  read-only
   STATUS      current
   DESCRIPTION
      "Path: pppBundle.performance.ifInPriorityQueues.h24Performance.cirTxOctets

       64 bit unsigned wrappable counter."
   ::= {pr1645v2PppBFIfInPriorityQueuesH24PerformanceEntry 167772160}

pr1645v2PppBFIfInPriorityQueuesH24PerformanceEirTxOcts OBJECT-TYPE
   SYNTAX      Counter64
   MAX-ACCESS  read-only
   STATUS      current
   DESCRIPTION
      "Path: pppBundle.performance.ifInPriorityQueues.h24Performance.eirTxOctets

       64 bit unsigned wrappable counter."
   ::= {pr1645v2PppBFIfInPriorityQueuesH24PerformanceEntry 184549376}

pr1645v2PppBFIfInPriorityQueuesH24PerformanceViolTxOcts OBJECT-TYPE
   SYNTAX      Counter64
   MAX-ACCESS  read-only
   STATUS      current
   DESCRIPTION
      "Path: pppBundle.performance.ifInPriorityQueues.h24Performance.violateTxOctets

       64 bit unsigned wrappable counter."
   ::= {pr1645v2PppBFIfInPriorityQueuesH24PerformanceEntry 318767104}

pr1645v2PppBFIfInPriorityQueuesH24PerformanceBandwidth OBJECT-TYPE
   SYNTAX      Integer32
   MAX-ACCESS  read-only
   STATUS      current
   DESCRIPTION
      "Path: pppBundle.performance.ifInPriorityQueues.h24Performance.bandwidth

       unit name = bps
       formula = 8 * ; 8 /"
   ::= {pr1645v2PppBFIfInPriorityQueuesH24PerformanceEntry 268435456}

pr1645v2PppBFIfInPriorityQueuesD7Performance OBJECT-TYPE
   SYNTAX      SEQUENCE OF Pr1645v2PppBFIfInPriorityQueuesD7PerformanceEntry
   MAX-ACCESS  not-accessible
   STATUS      current
   DESCRIPTION
      ""
   ::= {pr1645v2PppBFIfInPriorityQueues 117440512}

pr1645v2PppBFIfInPriorityQueuesD7PerformanceEntry OBJECT-TYPE
   SYNTAX      Pr1645v2PppBFIfInPriorityQueuesD7PerformanceEntry
   MAX-ACCESS  not-accessible
   STATUS      current
   DESCRIPTION
      ""
   INDEX      { pr1645v2PppBFIfInPriorityQueuesD7PerformanceGlobalIx,
                pr1645v2PppBFIfInPriorityQueuesTableIx,
                pr1645v2PppBFIfInPriorityQueuesD7PerformanceTableIx }
   ::= {pr1645v2PppBFIfInPriorityQueuesD7Performance 1}

Pr1645v2PppBFIfInPriorityQueuesD7PerformanceEntry ::=
   SEQUENCE
      {
      pr1645v2PppBFIfInPriorityQueuesD7PerformanceGlobalIx
         GlobalIndex,
      pr1645v2PppBFIfInPriorityQueuesD7PerformanceTableIx
         TableIndex,
      pr1645v2PppBFIfInPriorityQueuesD7PerformanceSysUpTime
         TimeTicks,
      pr1645v2PppBFIfInPriorityQueuesD7PerformanceTotPkts
         Counter64,
      pr1645v2PppBFIfInPriorityQueuesD7PerformanceDirTxPkts
         Counter64,
      pr1645v2PppBFIfInPriorityQueuesD7PerformanceQdPkts
         Counter64,
      pr1645v2PppBFIfInPriorityQueuesD7PerformanceDropPkts
         Counter64,
      pr1645v2PppBFIfInPriorityQueuesD7PerformanceRDropPkts
         Counter64,
      pr1645v2PppBFIfInPriorityQueuesD7PerformanceCirTxPkts
         Counter64,
      pr1645v2PppBFIfInPriorityQueuesD7PerformanceEirTxPkts
         Counter64,
      pr1645v2PppBFIfInPriorityQueuesD7PerformanceViolTxPkts
         Counter64,
      pr1645v2PppBFIfInPriorityQueuesD7PerformanceTotOcts
         Counter64,
      pr1645v2PppBFIfInPriorityQueuesD7PerformanceDirTxOcts
         Counter64,
      pr1645v2PppBFIfInPriorityQueuesD7PerformanceQdOcts
         Counter64,
      pr1645v2PppBFIfInPriorityQueuesD7PerformanceDropOcts
         Counter64,
      pr1645v2PppBFIfInPriorityQueuesD7PerformanceRDropOcts
         Counter64,
      pr1645v2PppBFIfInPriorityQueuesD7PerformanceCirTxOcts
         Counter64,
      pr1645v2PppBFIfInPriorityQueuesD7PerformanceEirTxOcts
         Counter64,
      pr1645v2PppBFIfInPriorityQueuesD7PerformanceViolTxOcts
         Counter64,
      pr1645v2PppBFIfInPriorityQueuesD7PerformanceBandwidth
         Integer32
      }

pr1645v2PppBFIfInPriorityQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2PppBFIfInPriorityQueuesD7PerformanceEntry 10}

pr1645v2PppBFIfInPriorityQueuesD7PerformanceTableIx OBJECT-TYPE
   SYNTAX      TableIndex
   MAX-ACCESS  not-accessible
   STATUS      current
   DESCRIPTION
      ""
   ::= {pr1645v2PppBFIfInPriorityQueuesD7PerformanceEntry 11}

pr1645v2PppBFIfInPriorityQueuesD7PerformanceSysUpTime OBJECT-TYPE
   SYNTAX      TimeTicks
   MAX-ACCESS  read-only
   STATUS      current
   DESCRIPTION
      "Path: pppBundle.performance.ifInPriorityQueues.d7Performance.sysUpTime

       Time in centi-second."
   ::= {pr1645v2PppBFIfInPriorityQueuesD7PerformanceEntry 16777216}

pr1645v2PppBFIfInPriorityQueuesD7PerformanceTotPkts OBJECT-TYPE
   SYNTAX      Counter64
   MAX-ACCESS  read-only
   STATUS      current
   DESCRIPTION
      "Path: pppBundle.performance.ifInPriorityQueues.d7Performance.totalPkts

       64 bit unsigned wrappable counter."
   ::= {pr1645v2PppBFIfInPriorityQueuesD7PerformanceEntry 234881024}

pr1645v2PppBFIfInPriorityQueuesD7PerformanceDirTxPkts OBJECT-TYPE
   SYNTAX      Counter64
   MAX-ACCESS  read-only
   STATUS      current
   DESCRIPTION
      "Path: pppBundle.performance.ifInPriorityQueues.d7Performance.directTxPkts

       64 bit unsigned wrappable counter."
   ::= {pr1645v2PppBFIfInPriorityQueuesD7PerformanceEntry 33554432}

pr1645v2PppBFIfInPriorityQueuesD7PerformanceQdPkts OBJECT-TYPE
   SYNTAX      Counter64
   MAX-ACCESS  read-only
   STATUS      current
   DESCRIPTION
      "Path: pppBundle.performance.ifInPriorityQueues.d7Performance.queuedPkts

       64 bit unsigned wrappable counter."
   ::= {pr1645v2PppBFIfInPriorityQueuesD7PerformanceEntry 50331648}

pr1645v2PppBFIfInPriorityQueuesD7PerformanceDropPkts OBJECT-TYPE
   SYNTAX      Counter64
   MAX-ACCESS  read-only
   STATUS      current
   DESCRIPTION
      "Path: pppBundle.performance.ifInPriorityQueues.d7Performance.droppedPkts

       64 bit unsigned wrappable counter."
   ::= {pr1645v2PppBFIfInPriorityQueuesD7PerformanceEntry 67108864}

pr1645v2PppBFIfInPriorityQueuesD7PerformanceRDropPkts OBJECT-TYPE
   SYNTAX      Counter64
   MAX-ACCESS  read-only
   STATUS      current
   DESCRIPTION
      "Path: pppBundle.performance.ifInPriorityQueues.d7Performance.redDroppedPkts

       64 bit unsigned wrappable counter."
   ::= {pr1645v2PppBFIfInPriorityQueuesD7PerformanceEntry 201326592}

pr1645v2PppBFIfInPriorityQueuesD7PerformanceCirTxPkts OBJECT-TYPE
   SYNTAX      Counter64
   MAX-ACCESS  read-only
   STATUS      current
   DESCRIPTION
      "Path: pppBundle.performance.ifInPriorityQueues.d7Performance.cirTxPkts

       64 bit unsigned wrappable counter."
   ::= {pr1645v2PppBFIfInPriorityQueuesD7PerformanceEntry 83886080}

pr1645v2PppBFIfInPriorityQueuesD7PerformanceEirTxPkts OBJECT-TYPE
   SYNTAX      Counter64
   MAX-ACCESS  read-only
   STATUS      current
   DESCRIPTION
      "Path: pppBundle.performance.ifInPriorityQueues.d7Performance.eirTxPkts

       64 bit unsigned wrappable counter."
   ::= {pr1645v2PppBFIfInPriorityQueuesD7PerformanceEntry 100663296}

pr1645v2PppBFIfInPriorityQueuesD7PerformanceViolTxPkts OBJECT-TYPE
   SYNTAX      Counter64
   MAX-ACCESS  read-only
   STATUS      current
   DESCRIPTION
      "Path: pppBundle.performance.ifInPriorityQueues.d7Performance.violateTxPkts

       64 bit unsigned wrappable counter."
   ::= {pr1645v2PppBFIfInPriorityQueuesD7PerformanceEntry 301989888}

pr1645v2PppBFIfInPriorityQueuesD7PerformanceTotOcts OBJECT-TYPE
   SYNTAX      Counter64
   MAX-ACCESS  read-only
   STATUS      current
   DESCRIPTION
      "Path: pppBundle.performance.ifInPriorityQueues.d7Performance.totalOctets

       64 bit unsigned wrappable counter."
   ::= {pr1645v2PppBFIfInPriorityQueuesD7PerformanceEntry 251658240}

pr1645v2PppBFIfInPriorityQueuesD7PerformanceDirTxOcts OBJECT-TYPE
   SYNTAX      Counter64
   MAX-ACCESS  read-only
   STATUS      current
   DESCRIPTION
      "Path: pppBundle.performance.ifInPriorityQueues.d7Performance.directTxOctets

       64 bit unsigned wrappable counter."
   ::= {pr1645v2PppBFIfInPriorityQueuesD7PerformanceEntry 117440512}

pr1645v2PppBFIfInPriorityQueuesD7PerformanceQdOcts OBJECT-TYPE
   SYNTAX      Counter64
   MAX-ACCESS  read-only
   STATUS      current
   DESCRIPTION
      "Path: pppBundle.performance.ifInPriorityQueues.d7Performance.queuedOctets

       64 bit unsigned wrappable counter."
   ::= {pr1645v2PppBFIfInPriorityQueuesD7PerformanceEntry 134217728}

pr1645v2PppBFIfInPriorityQueuesD7PerformanceDropOcts OBJECT-TYPE
   SYNTAX      Counter64
   MAX-ACCESS  read-only
   STATUS      current
   DESCRIPTION
      "Path: pppBundle.performance.ifInPriorityQueues.d7Performance.droppedOctets

       64 bit unsigned wrappable counter."
   ::= {pr1645v2PppBFIfInPriorityQueuesD7PerformanceEntry 150994944}

pr1645v2PppBFIfInPriorityQueuesD7PerformanceRDropOcts OBJECT-TYPE
   SYNTAX      Counter64
   MAX-ACCESS  read-only
   STATUS      current
   DESCRIPTION
      "Path: pppBundle.performance.ifInPriorityQueues.d7Performance.redDroppedOctets

       64 bit unsigned wrappable counter."
   ::= {pr1645v2PppBFIfInPriorityQueuesD7PerformanceEntry 218103808}

pr1645v2PppBFIfInPriorityQueuesD7PerformanceCirTxOcts OBJECT-TYPE
   SYNTAX      Counter64
   MAX-ACCESS  read-only
   STATUS      current
   DESCRIPTION
      "Path: pppBundle.performance.ifInPriorityQueues.d7Performance.cirTxOctets

       64 bit unsigned wrappable counter."
   ::= {pr1645v2PppBFIfInPriorityQueuesD7PerformanceEntry 167772160}

pr1645v2PppBFIfInPriorityQueuesD7PerformanceEirTxOcts OBJECT-TYPE
   SYNTAX      Counter64
   MAX-ACCESS  read-only
   STATUS      current
   DESCRIPTION
      "Path: pppBundle.performance.ifInPriorityQueues.d7Performance.eirTxOctets

       64 bit unsigned wrappable counter."
   ::= {pr1645v2PppBFIfInPriorityQueuesD7PerformanceEntry 184549376}

pr1645v2PppBFIfInPriorityQueuesD7PerformanceViolTxOcts OBJECT-TYPE
   SYNTAX      Counter64
   MAX-ACCESS  read-only
   STATUS      current
   DESCRIPTION
      "Path: pppBundle.performance.ifInPriorityQueues.d7Performance.violateTxOctets

       64 bit unsigned wrappable counter."
   ::= {pr1645v2PppBFIfInPriorityQueuesD7PerformanceEntry 318767104}

pr1645v2PppBFIfInPriorityQueuesD7PerformanceBandwidth OBJECT-TYPE
   SYNTAX      Integer32
   MAX-ACCESS  read-only
   STATUS      current
   DESCRIPTION
      "Path: pppBundle.performance.ifInPriorityQueues.d7Performance.bandwidth

       unit name = bps
       formula = 8 * ; 8 /"
   ::= {pr1645v2PppBFIfInPriorityQueuesD7PerformanceEntry 268435456}


pr1645v2PppBFInBandwidth OBJECT IDENTIFIER ::= {pr1645v2PppBF 181}

pr1645v2PppBFInBandwidthSSCTable OBJECT-TYPE
   SYNTAX      SEQUENCE OF Pr1645v2PppBFInBandwidthEntry
   MAX-ACCESS  not-accessible
   STATUS      current
   DESCRIPTION
      "bandwidth"
   ::= {pr1645v2PppBFInBandwidth 1}

pr1645v2PppBFInBandwidthEntry OBJECT-TYPE
   SYNTAX      Pr1645v2PppBFInBandwidthEntry
   MAX-ACCESS  not-accessible
   STATUS      current
   DESCRIPTION
      ""
   INDEX      { pr1645v2PppBFInBandwidthGlobalIx }
   ::= {pr1645v2PppBFInBandwidthSSCTable 1}

Pr1645v2PppBFInBandwidthEntry ::=
   SEQUENCE
      {
      pr1645v2PppBFInBandwidthGlobalIx
         GlobalIndex,
      pr1645v2PppBFInBandwidth15sec
         Integer32,
      pr1645v2PppBFInBandwidth30sec
         Integer32,
      pr1645v2PppBFInBandwidth1min
         Integer32,
      pr1645v2PppBFInBandwidth2min
         Integer32,
      pr1645v2PppBFInBandwidth5min
         Integer32
      }

pr1645v2PppBFInBandwidthGlobalIx OBJECT-TYPE
   SYNTAX      GlobalIndex
   MAX-ACCESS  not-accessible
   STATUS      current
   DESCRIPTION
      "The value of the tlsCntTreeGlobalIndex of the MANAGED OBJECT."
   ::= {pr1645v2PppBFInBandwidthEntry 10}

pr1645v2PppBFInBandwidth15sec OBJECT-TYPE
   SYNTAX      Integer32
   MAX-ACCESS  read-only
   STATUS      current
   DESCRIPTION
      "Path: pppBundle.performance.ifInBandwidth.15sec

       unit name = bps
       formula = 8 * ; 8 /"
   ::= {pr1645v2PppBFInBandwidthEntry 83886080}

pr1645v2PppBFInBandwidth30sec OBJECT-TYPE
   SYNTAX      Integer32
   MAX-ACCESS  read-only
   STATUS      current
   DESCRIPTION
      "Path: pppBundle.performance.ifInBandwidth.30sec

       unit name = bps
       formula = 8 * ; 8 /"
   ::= {pr1645v2PppBFInBandwidthEntry 167772160}

pr1645v2PppBFInBandwidth1min OBJECT-TYPE
   SYNTAX      Integer32
   MAX-ACCESS  read-only
   STATUS      current
   DESCRIPTION
      "Path: pppBundle.performance.ifInBandwidth.1min

       unit name = bps
       formula = 8 * ; 8 /"
   ::= {pr1645v2PppBFInBandwidthEntry 335544320}

pr1645v2PppBFInBandwidth2min OBJECT-TYPE
   SYNTAX      Integer32
   MAX-ACCESS  read-only
   STATUS      current
   DESCRIPTION
      "Path: pppBundle.performance.ifInBandwidth.2min

       unit name = bps
       formula = 8 * ; 8 /"
   ::= {pr1645v2PppBFInBandwidthEntry 671088640}

pr1645v2PppBFInBandwidth5min OBJECT-TYPE
   SYNTAX      Integer32
   MAX-ACCESS  read-only
   STATUS      current
   DESCRIPTION
      "Path: pppBundle.performance.ifInBandwidth.5min

       unit name = bps
       formula = 8 * ; 8 /"
   ::= {pr1645v2PppBFInBandwidthEntry 1677721600}


pr1645v2PppBFOutOctets OBJECT IDENTIFIER ::= {pr1645v2PppBF 115}

pr1645v2PppBFOutOctetsTable OBJECT-TYPE
   SYNTAX      SEQUENCE OF Pr1645v2PppBFOutOctetsEntry
   MAX-ACCESS  not-accessible
   STATUS      current
   DESCRIPTION
      "ifOutOctets"
   ::= {pr1645v2PppBFOutOctets 1}

pr1645v2PppBFOutOctetsEntry OBJECT-TYPE
   SYNTAX      Pr1645v2PppBFOutOctetsEntry
   MAX-ACCESS  not-accessible
   STATUS      current
   DESCRIPTION
      ""
   INDEX      { pr1645v2PppBFOutOctetsGlobalIx }
   ::= {pr1645v2PppBFOutOctetsTable 1}

Pr1645v2PppBFOutOctetsEntry ::=
   SEQUENCE
      {
      pr1645v2PppBFOutOctetsGlobalIx
         GlobalIndex,
      pr1645v2PppBFOutOctetsValue
         Counter64
      }

pr1645v2PppBFOutOctetsGlobalIx OBJECT-TYPE
   SYNTAX      GlobalIndex
   MAX-ACCESS  not-accessible
   STATUS      current
   DESCRIPTION
      "The value of the tlsCntTreeGlobalIndex of the MANAGED OBJECT."
   ::= {pr1645v2PppBFOutOctetsEntry 10}

pr1645v2PppBFOutOctetsValue OBJECT-TYPE
   SYNTAX      Counter64
   MAX-ACCESS  read-only
   STATUS      current
   DESCRIPTION
      "Path: pppBundle.performance.ifOutOctets

       64 bit unsigned wrappable counter."
   ::= {pr1645v2PppBFOutOctetsEntry 2147483648}


pr1645v2PppBFOutUcastPkts OBJECT IDENTIFIER ::= {pr1645v2PppBF 116}

pr1645v2PppBFOutUcastPktsTable OBJECT-TYPE
   SYNTAX      SEQUENCE OF Pr1645v2PppBFOutUcastPktsEntry
   MAX-ACCESS  not-accessible
   STATUS      current
   DESCRIPTION
      "ifOutUcastPkts"
   ::= {pr1645v2PppBFOutUcastPkts 1}

pr1645v2PppBFOutUcastPktsEntry OBJECT-TYPE
   SYNTAX      Pr1645v2PppBFOutUcastPktsEntry
   MAX-ACCESS  not-accessible
   STATUS      current
   DESCRIPTION
      ""
   INDEX      { pr1645v2PppBFOutUcastPktsGlobalIx }
   ::= {pr1645v2PppBFOutUcastPktsTable 1}

Pr1645v2PppBFOutUcastPktsEntry ::=
   SEQUENCE
      {
      pr1645v2PppBFOutUcastPktsGlobalIx
         GlobalIndex,
      pr1645v2PppBFOutUcastPktsValue
         Counter64
      }

pr1645v2PppBFOutUcastPktsGlobalIx OBJECT-TYPE
   SYNTAX      GlobalIndex
   MAX-ACCESS  not-accessible
   STATUS      current
   DESCRIPTION
      "The value of the tlsCntTreeGlobalIndex of the MANAGED OBJECT."
   ::= {pr1645v2PppBFOutUcastPktsEntry 10}

pr1645v2PppBFOutUcastPktsValue OBJECT-TYPE
   SYNTAX      Counter64
   MAX-ACCESS  read-only
   STATUS      current
   DESCRIPTION
      "Path: pppBundle.performance.ifOutUcastPkts

       64 bit unsigned wrappable counter."
   ::= {pr1645v2PppBFOutUcastPktsEntry 2147483648}


pr1645v2PppBFOutNUcastPkts OBJECT IDENTIFIER ::= {pr1645v2PppBF 117}

pr1645v2PppBFOutNUcastPktsTable OBJECT-TYPE
   SYNTAX      SEQUENCE OF Pr1645v2PppBFOutNUcastPktsEntry
   MAX-ACCESS  not-accessible
   STATUS      current
   DESCRIPTION
      "ifOutNUcastPkts"
   ::= {pr1645v2PppBFOutNUcastPkts 1}

pr1645v2PppBFOutNUcastPktsEntry OBJECT-TYPE
   SYNTAX      Pr1645v2PppBFOutNUcastPktsEntry
   MAX-ACCESS  not-accessible
   STATUS      current
   DESCRIPTION
      ""
   INDEX      { pr1645v2PppBFOutNUcastPktsGlobalIx }
   ::= {pr1645v2PppBFOutNUcastPktsTable 1}

Pr1645v2PppBFOutNUcastPktsEntry ::=
   SEQUENCE
      {
      pr1645v2PppBFOutNUcastPktsGlobalIx
         GlobalIndex,
      pr1645v2PppBFOutNUcastPktsValue
         Counter64
      }

pr1645v2PppBFOutNUcastPktsGlobalIx OBJECT-TYPE
   SYNTAX      GlobalIndex
   MAX-ACCESS  not-accessible
   STATUS      current
   DESCRIPTION
      "The value of the tlsCntTreeGlobalIndex of the MANAGED OBJECT."
   ::= {pr1645v2PppBFOutNUcastPktsEntry 10}

pr1645v2PppBFOutNUcastPktsValue OBJECT-TYPE
   SYNTAX      Counter64
   MAX-ACCESS  read-only
   STATUS      current
   DESCRIPTION
      "Path: pppBundle.performance.ifOutNUcastPkts

       64 bit unsigned wrappable counter."
   ::= {pr1645v2PppBFOutNUcastPktsEntry 2147483648}


pr1645v2PppBFOutBcastPkts OBJECT IDENTIFIER ::= {pr1645v2PppBF 217}

pr1645v2PppBFOutBcastPktsTable OBJECT-TYPE
   SYNTAX      SEQUENCE OF Pr1645v2PppBFOutBcastPktsEntry
   MAX-ACCESS  not-accessible
   STATUS      current
   DESCRIPTION
      "ifOutBcastPkts"
   ::= {pr1645v2PppBFOutBcastPkts 1}

pr1645v2PppBFOutBcastPktsEntry OBJECT-TYPE
   SYNTAX      Pr1645v2PppBFOutBcastPktsEntry
   MAX-ACCESS  not-accessible
   STATUS      current
   DESCRIPTION
      ""
   INDEX      { pr1645v2PppBFOutBcastPktsGlobalIx }
   ::= {pr1645v2PppBFOutBcastPktsTable 1}

Pr1645v2PppBFOutBcastPktsEntry ::=
   SEQUENCE
      {
      pr1645v2PppBFOutBcastPktsGlobalIx
         GlobalIndex,
      pr1645v2PppBFOutBcastPktsValue
         Counter64
      }

pr1645v2PppBFOutBcastPktsGlobalIx OBJECT-TYPE
   SYNTAX      GlobalIndex
   MAX-ACCESS  not-accessible
   STATUS      current
   DESCRIPTION
      "The value of the tlsCntTreeGlobalIndex of the MANAGED OBJECT."
   ::= {pr1645v2PppBFOutBcastPktsEntry 10}

pr1645v2PppBFOutBcastPktsValue OBJECT-TYPE
   SYNTAX      Counter64
   MAX-ACCESS  read-only
   STATUS      current
   DESCRIPTION
      "Path: pppBundle.performance.ifOutBcastPkts

       64 bit unsigned wrappable counter."
   ::= {pr1645v2PppBFOutBcastPktsEntry 2147483648}


pr1645v2PppBFOutMcastPkts OBJECT IDENTIFIER ::= {pr1645v2PppBF 227}

pr1645v2PppBFOutMcastPktsTable OBJECT-TYPE
   SYNTAX      SEQUENCE OF Pr1645v2PppBFOutMcastPktsEntry
   MAX-ACCESS  not-accessible
   STATUS      current
   DESCRIPTION
      "ifOutMcastPkts"
   ::= {pr1645v2PppBFOutMcastPkts 1}

pr1645v2PppBFOutMcastPktsEntry OBJECT-TYPE
   SYNTAX      Pr1645v2PppBFOutMcastPktsEntry
   MAX-ACCESS  not-accessible
   STATUS      current
   DESCRIPTION
      ""
   INDEX      { pr1645v2PppBFOutMcastPktsGlobalIx }
   ::= {pr1645v2PppBFOutMcastPktsTable 1}

Pr1645v2PppBFOutMcastPktsEntry ::=
   SEQUENCE
      {
      pr1645v2PppBFOutMcastPktsGlobalIx
         GlobalIndex,
      pr1645v2PppBFOutMcastPktsValue
         Counter64
      }

pr1645v2PppBFOutMcastPktsGlobalIx OBJECT-TYPE
   SYNTAX      GlobalIndex
   MAX-ACCESS  not-accessible
   STATUS      current
   DESCRIPTION
      "The value of the tlsCntTreeGlobalIndex of the MANAGED OBJECT."
   ::= {pr1645v2PppBFOutMcastPktsEntry 10}

pr1645v2PppBFOutMcastPktsValue OBJECT-TYPE
   SYNTAX      Counter64
   MAX-ACCESS  read-only
   STATUS      current
   DESCRIPTION
      "Path: pppBundle.performance.ifOutMcastPkts

       64 bit unsigned wrappable counter."
   ::= {pr1645v2PppBFOutMcastPktsEntry 2147483648}


pr1645v2PppBFOutDiscards OBJECT IDENTIFIER ::= {pr1645v2PppBF 118}

pr1645v2PppBFOutDiscardsTable OBJECT-TYPE
   SYNTAX      SEQUENCE OF Pr1645v2PppBFOutDiscardsEntry
   MAX-ACCESS  not-accessible
   STATUS      current
   DESCRIPTION
      "ifOutDiscards"
   ::= {pr1645v2PppBFOutDiscards 1}

pr1645v2PppBFOutDiscardsEntry OBJECT-TYPE
   SYNTAX      Pr1645v2PppBFOutDiscardsEntry
   MAX-ACCESS  not-accessible
   STATUS      current
   DESCRIPTION
      ""
   INDEX      { pr1645v2PppBFOutDiscardsGlobalIx }
   ::= {pr1645v2PppBFOutDiscardsTable 1}

Pr1645v2PppBFOutDiscardsEntry ::=
   SEQUENCE
      {
      pr1645v2PppBFOutDiscardsGlobalIx
         GlobalIndex,
      pr1645v2PppBFOutDiscardsValue
         Counter64
      }

pr1645v2PppBFOutDiscardsGlobalIx OBJECT-TYPE
   SYNTAX      GlobalIndex
   MAX-ACCESS  not-accessible
   STATUS      current
   DESCRIPTION
      "The value of the tlsCntTreeGlobalIndex of the MANAGED OBJECT."
   ::= {pr1645v2PppBFOutDiscardsEntry 10}

pr1645v2PppBFOutDiscardsValue OBJECT-TYPE
   SYNTAX      Counter64
   MAX-ACCESS  read-only
   STATUS      current
   DESCRIPTION
      "Path: pppBundle.performance.ifOutDiscards

       64 bit unsigned wrappable counter."
   ::= {pr1645v2PppBFOutDiscardsEntry 2147483648}


pr1645v2PppBFOutErrors OBJECT IDENTIFIER ::= {pr1645v2PppBF 119}

pr1645v2PppBFOutErrorsTable OBJECT-TYPE
   SYNTAX      SEQUENCE OF Pr1645v2PppBFOutErrorsEntry
   MAX-ACCESS  not-accessible
   STATUS      current
   DESCRIPTION
      "ifOutErrors"
   ::= {pr1645v2PppBFOutErrors 1}

pr1645v2PppBFOutErrorsEntry OBJECT-TYPE
   SYNTAX      Pr1645v2PppBFOutErrorsEntry
   MAX-ACCESS  not-accessible
   STATUS      current
   DESCRIPTION
      ""
   INDEX      { pr1645v2PppBFOutErrorsGlobalIx }
   ::= {pr1645v2PppBFOutErrorsTable 1}

Pr1645v2PppBFOutErrorsEntry ::=
   SEQUENCE
      {
      pr1645v2PppBFOutErrorsGlobalIx
         GlobalIndex,
      pr1645v2PppBFOutErrorsValue
         Counter64
      }

pr1645v2PppBFOutErrorsGlobalIx OBJECT-TYPE
   SYNTAX      GlobalIndex
   MAX-ACCESS  not-accessible
   STATUS      current
   DESCRIPTION
      "The value of the tlsCntTreeGlobalIndex of the MANAGED OBJECT."
   ::= {pr1645v2PppBFOutErrorsEntry 10}

pr1645v2PppBFOutErrorsValue OBJECT-TYPE
   SYNTAX      Counter64
   MAX-ACCESS  read-only
   STATUS      current
   DESCRIPTION
      "Path: pppBundle.performance.ifOutErrors

       64 bit unsigned wrappable counter."
   ::= {pr1645v2PppBFOutErrorsEntry 2147483648}


pr1645v2PppBFOutQLen OBJECT IDENTIFIER ::= {pr1645v2PppBF 120}

pr1645v2PppBFOutQLenTable OBJECT-TYPE
   SYNTAX      SEQUENCE OF Pr1645v2PppBFOutQLenEntry
   MAX-ACCESS  not-accessible
   STATUS      current
   DESCRIPTION
      "ifOutQLen"
   ::= {pr1645v2PppBFOutQLen 1}

pr1645v2PppBFOutQLenEntry OBJECT-TYPE
   SYNTAX      Pr1645v2PppBFOutQLenEntry
   MAX-ACCESS  not-accessible
   STATUS      current
   DESCRIPTION
      ""
   INDEX      { pr1645v2PppBFOutQLenGlobalIx }
   ::= {pr1645v2PppBFOutQLenTable 1}

Pr1645v2PppBFOutQLenEntry ::=
   SEQUENCE
      {
      pr1645v2PppBFOutQLenGlobalIx
         GlobalIndex,
      pr1645v2PppBFOutQLenValue
         Gauge32
      }

pr1645v2PppBFOutQLenGlobalIx OBJECT-TYPE
   SYNTAX      GlobalIndex
   MAX-ACCESS  not-accessible
   STATUS      current
   DESCRIPTION
      "The value of the tlsCntTreeGlobalIndex of the MANAGED OBJECT."
   ::= {pr1645v2PppBFOutQLenEntry 10}

pr1645v2PppBFOutQLenValue OBJECT-TYPE
   SYNTAX      Gauge32
   MAX-ACCESS  read-only
   STATUS      current
   DESCRIPTION
      "Path: pppBundle.performance.ifOutQLen

       32 bit unsigned gauge value."
   ::= {pr1645v2PppBFOutQLenEntry 2147483648}


pr1645v2PppBFOutDropEx OBJECT IDENTIFIER ::= {pr1645v2PppBF 127}

pr1645v2PppBFOutDropExTable OBJECT-TYPE
   SYNTAX      SEQUENCE OF Pr1645v2PppBFOutDropExEntry
   MAX-ACCESS  not-accessible
   STATUS      current
   DESCRIPTION
      "ifOutDiscards"
   ::= {pr1645v2PppBFOutDropEx 1}

pr1645v2PppBFOutDropExEntry OBJECT-TYPE
   SYNTAX      Pr1645v2PppBFOutDropExEntry
   MAX-ACCESS  not-accessible
   STATUS      current
   DESCRIPTION
      ""
   INDEX      { pr1645v2PppBFOutDropExGlobalIx }
   ::= {pr1645v2PppBFOutDropExTable 1}

Pr1645v2PppBFOutDropExEntry ::=
   SEQUENCE
      {
      pr1645v2PppBFOutDropExGlobalIx
         GlobalIndex,
      pr1645v2PppBFOutDropExValue
         Counter64
      }

pr1645v2PppBFOutDropExGlobalIx OBJECT-TYPE
   SYNTAX      GlobalIndex
   MAX-ACCESS  not-accessible
   STATUS      current
   DESCRIPTION
      "The value of the tlsCntTreeGlobalIndex of the MANAGED OBJECT."
   ::= {pr1645v2PppBFOutDropExEntry 10}

pr1645v2PppBFOutDropExValue OBJECT-TYPE
   SYNTAX      Counter64
   MAX-ACCESS  read-only
   STATUS      current
   DESCRIPTION
      "Path: pppBundle.performance.ifOutDropLevelExceeded

       64 bit unsigned wrappable counter."
   ::= {pr1645v2PppBFOutDropExEntry 2147483648}


pr1645v2PppBFOutDropNoArp OBJECT IDENTIFIER ::= {pr1645v2PppBF 134}

pr1645v2PppBFOutDropNoArpTable OBJECT-TYPE
   SYNTAX      SEQUENCE OF Pr1645v2PppBFOutDropNoArpEntry
   MAX-ACCESS  not-accessible
   STATUS      current
   DESCRIPTION
      "ifOutDiscards"
   ::= {pr1645v2PppBFOutDropNoArp 1}

pr1645v2PppBFOutDropNoArpEntry OBJECT-TYPE
   SYNTAX      Pr1645v2PppBFOutDropNoArpEntry
   MAX-ACCESS  not-accessible
   STATUS      current
   DESCRIPTION
      ""
   INDEX      { pr1645v2PppBFOutDropNoArpGlobalIx }
   ::= {pr1645v2PppBFOutDropNoArpTable 1}

Pr1645v2PppBFOutDropNoArpEntry ::=
   SEQUENCE
      {
      pr1645v2PppBFOutDropNoArpGlobalIx
         GlobalIndex,
      pr1645v2PppBFOutDropNoArpValue
         Counter64
      }

pr1645v2PppBFOutDropNoArpGlobalIx OBJECT-TYPE
   SYNTAX      GlobalIndex
   MAX-ACCESS  not-accessible
   STATUS      current
   DESCRIPTION
      "The value of the tlsCntTreeGlobalIndex of the MANAGED OBJECT."
   ::= {pr1645v2PppBFOutDropNoArpEntry 10}

pr1645v2PppBFOutDropNoArpValue OBJECT-TYPE
   SYNTAX      Counter64
   MAX-ACCESS  read-only
   STATUS      current
   DESCRIPTION
      "Path: pppBundle.performance.ifOutDiscardsNoArp

       64 bit unsigned wrappable counter."
   ::= {pr1645v2PppBFOutDropNoArpEntry 2147483648}


pr1645v2PppBFOutDropFilter OBJECT IDENTIFIER ::= {pr1645v2PppBF 138}

pr1645v2PppBFOutDropFilterTable OBJECT-TYPE
   SYNTAX      SEQUENCE OF Pr1645v2PppBFOutDropFilterEntry
   MAX-ACCESS  not-accessible
   STATUS      current
   DESCRIPTION
      "ifOutDiscards"
   ::= {pr1645v2PppBFOutDropFilter 1}

pr1645v2PppBFOutDropFilterEntry OBJECT-TYPE
   SYNTAX      Pr1645v2PppBFOutDropFilterEntry
   MAX-ACCESS  not-accessible
   STATUS      current
   DESCRIPTION
      ""
   INDEX      { pr1645v2PppBFOutDropFilterGlobalIx }
   ::= {pr1645v2PppBFOutDropFilterTable 1}

Pr1645v2PppBFOutDropFilterEntry ::=
   SEQUENCE
      {
      pr1645v2PppBFOutDropFilterGlobalIx
         GlobalIndex,
      pr1645v2PppBFOutDropFilterValue
         Counter64
      }

pr1645v2PppBFOutDropFilterGlobalIx OBJECT-TYPE
   SYNTAX      GlobalIndex
   MAX-ACCESS  not-accessible
   STATUS      current
   DESCRIPTION
      "The value of the tlsCntTreeGlobalIndex of the MANAGED OBJECT."
   ::= {pr1645v2PppBFOutDropFilterEntry 10}

pr1645v2PppBFOutDropFilterValue OBJECT-TYPE
   SYNTAX      Counter64
   MAX-ACCESS  read-only
   STATUS      current
   DESCRIPTION
      "Path: pppBundle.performance.ifOutDiscardsFilter

       64 bit unsigned wrappable counter."
   ::= {pr1645v2PppBFOutDropFilterEntry 2147483648}


pr1645v2PppBFIfOutPriorityQueues OBJECT IDENTIFIER ::= {pr1645v2PppBF 129}

pr1645v2PppBFIfOutPriorityQueuesSSCTable OBJECT-TYPE
   SYNTAX      SEQUENCE OF Pr1645v2PppBFIfOutPriorityQueuesEntry
   MAX-ACCESS  not-accessible
   STATUS      current
   DESCRIPTION
      "Queue Lengths"
   ::= {pr1645v2PppBFIfOutPriorityQueues 1}

pr1645v2PppBFIfOutPriorityQueuesEntry OBJECT-TYPE
   SYNTAX      Pr1645v2PppBFIfOutPriorityQueuesEntry
   MAX-ACCESS  not-accessible
   STATUS      current
   DESCRIPTION
      ""
   INDEX      { pr1645v2PppBFIfOutPriorityQueuesGlobalIx,
                pr1645v2PppBFIfOutPriorityQueuesTableIx }
   ::= {pr1645v2PppBFIfOutPriorityQueuesSSCTable 1}

Pr1645v2PppBFIfOutPriorityQueuesEntry ::=
   SEQUENCE
      {
      pr1645v2PppBFIfOutPriorityQueuesGlobalIx
         GlobalIndex,
      pr1645v2PppBFIfOutPriorityQueuesTableIx
         TableIndex,
      pr1645v2PppBFIfOutPriorityQueuesName
         INTEGER,
      pr1645v2PppBFIfOutPriorityQueuesLength
         Integer32,
      pr1645v2PppBFIfOutPriorityQueuesOctetLength
         Integer32,
      pr1645v2PppBFIfOutPriorityQueuesRedLength
         Integer32,
      pr1645v2PppBFIfOutPriorityQueuesPacketsTotal
         Counter64,
      pr1645v2PppBFIfOutPriorityQueuesPacketsDirectTx
         Counter64,
      pr1645v2PppBFIfOutPriorityQueuesPacketsQueued
         Counter64,
      pr1645v2PppBFIfOutPriorityQueuesPacketsDropped
         Counter64,
      pr1645v2PppBFIfOutPriorityQueuesPacketsRedDropped
         Counter64,
      pr1645v2PppBFIfOutPriorityQueuesPacketsCirTx
         Counter64,
      pr1645v2PppBFIfOutPriorityQueuesPacketsEirTx
         Counter64,
      pr1645v2PppBFIfOutPriorityQueuesPacketsViolateTx
         Counter64,
      pr1645v2PppBFIfOutPriorityQueuesOctetsTotal
         Counter64,
      pr1645v2PppBFIfOutPriorityQueuesOctetsDirectTx
         Counter64,
      pr1645v2PppBFIfOutPriorityQueuesOctetsQueued
         Counter64,
      pr1645v2PppBFIfOutPriorityQueuesOctetsDropped
         Counter64,
      pr1645v2PppBFIfOutPriorityQueuesOctetsRedDropped
         Counter64,
      pr1645v2PppBFIfOutPriorityQueuesOctetsCirTx
         Counter64,
      pr1645v2PppBFIfOutPriorityQueuesOctetsEirTx
         Counter64,
      pr1645v2PppBFIfOutPriorityQueuesOctetsViolateTx
         Counter64,
      pr1645v2PppBFIfOutPriorityQueuesOctetsBandwidth15sec
         Integer32,
      pr1645v2PppBFIfOutPriorityQueuesOctetsBandwidth30sec
         Integer32,
      pr1645v2PppBFIfOutPriorityQueuesOctetsBandwidth1min
         Integer32,
      pr1645v2PppBFIfOutPriorityQueuesOctetsBandwidth2min
         Integer32,
      pr1645v2PppBFIfOutPriorityQueuesOctetsBandwidth5min
         Integer32
      }

pr1645v2PppBFIfOutPriorityQueuesGlobalIx OBJECT-TYPE
   SYNTAX      GlobalIndex
   MAX-ACCESS  not-accessible
   STATUS      current
   DESCRIPTION
      "The value of the tlsCntTreeGlobalIndex of the MANAGED OBJECT."
   ::= {pr1645v2PppBFIfOutPriorityQueuesEntry 10}

pr1645v2PppBFIfOutPriorityQueuesTableIx OBJECT-TYPE
   SYNTAX      TableIndex
   MAX-ACCESS  not-accessible
   STATUS      current
   DESCRIPTION
      ""
   ::= {pr1645v2PppBFIfOutPriorityQueuesEntry 11}

pr1645v2PppBFIfOutPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: pppBundle.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2PppBFIfOutPriorityQueuesEntry 16777216}

pr1645v2PppBFIfOutPriorityQueuesLength OBJECT-TYPE
   SYNTAX      Integer32
   MAX-ACCESS  read-only
   STATUS      current
   DESCRIPTION
      "Path: pppBundle.performance.ifOutPriorityQueues.length"
   ::= {pr1645v2PppBFIfOutPriorityQueuesEntry 33554432}

pr1645v2PppBFIfOutPriorityQueuesOctetLength OBJECT-TYPE
   SYNTAX      Integer32
   MAX-ACCESS  read-only
   STATUS      current
   DESCRIPTION
      "Path: pppBundle.performance.ifOutPriorityQueues.octetLength"
   ::= {pr1645v2PppBFIfOutPriorityQueuesEntry 150994944}

pr1645v2PppBFIfOutPriorityQueuesRedLength OBJECT-TYPE
   SYNTAX      Integer32
   MAX-ACCESS  read-only
   STATUS      current
   DESCRIPTION
      "Path: pppBundle.performance.ifOutPriorityQueues.redLength"
   ::= {pr1645v2PppBFIfOutPriorityQueuesEntry 134217728}

pr1645v2PppBFIfOutPriorityQueuesPacketsTotal OBJECT-TYPE
   SYNTAX      Counter64
   MAX-ACCESS  read-only
   STATUS      current
   DESCRIPTION
      "Path: pppBundle.performance.ifOutPriorityQueues.packets.total

       64 bit unsigned wrappable counter."
   ::= {pr1645v2PppBFIfOutPriorityQueuesEntry 50790400}

pr1645v2PppBFIfOutPriorityQueuesPacketsDirectTx OBJECT-TYPE
   SYNTAX      Counter64
   MAX-ACCESS  read-only
   STATUS      current
   DESCRIPTION
      "Path: pppBundle.performance.ifOutPriorityQueues.packets.directTx

       64 bit unsigned wrappable counter."
   ::= {pr1645v2PppBFIfOutPriorityQueuesEntry 50397184}

pr1645v2PppBFIfOutPriorityQueuesPacketsQueued OBJECT-TYPE
   SYNTAX      Counter64
   MAX-ACCESS  read-only
   STATUS      current
   DESCRIPTION
      "Path: pppBundle.performance.ifOutPriorityQueues.packets.queued

       64 bit unsigned wrappable counter."
   ::= {pr1645v2PppBFIfOutPriorityQueuesEntry 50462720}

pr1645v2PppBFIfOutPriorityQueuesPacketsDropped OBJECT-TYPE
   SYNTAX      Counter64
   MAX-ACCESS  read-only
   STATUS      current
   DESCRIPTION
      "Path: pppBundle.performance.ifOutPriorityQueues.packets.dropped

       64 bit unsigned wrappable counter."
   ::= {pr1645v2PppBFIfOutPriorityQueuesEntry 50528256}

pr1645v2PppBFIfOutPriorityQueuesPacketsRedDropped OBJECT-TYPE
   SYNTAX      Counter64
   MAX-ACCESS  read-only
   STATUS      current
   DESCRIPTION
      "Path: pppBundle.performance.ifOutPriorityQueues.packets.redDropped

       64 bit unsigned wrappable counter."
   ::= {pr1645v2PppBFIfOutPriorityQueuesEntry 50724864}

pr1645v2PppBFIfOutPriorityQueuesPacketsCirTx OBJECT-TYPE
   SYNTAX      Counter64
   MAX-ACCESS  read-only
   STATUS      current
   DESCRIPTION
      "Path: pppBundle.performance.ifOutPriorityQueues.packets.cirTx

       64 bit unsigned wrappable counter."
   ::= {pr1645v2PppBFIfOutPriorityQueuesEntry 50593792}

pr1645v2PppBFIfOutPriorityQueuesPacketsEirTx OBJECT-TYPE
   SYNTAX      Counter64
   MAX-ACCESS  read-only
   STATUS      current
   DESCRIPTION
      "Path: pppBundle.performance.ifOutPriorityQueues.packets.eirTx

       64 bit unsigned wrappable counter."
   ::= {pr1645v2PppBFIfOutPriorityQueuesEntry 50659328}

pr1645v2PppBFIfOutPriorityQueuesPacketsViolateTx OBJECT-TYPE
   SYNTAX      Counter64
   MAX-ACCESS  read-only
   STATUS      current
   DESCRIPTION
      "Path: pppBundle.performance.ifOutPriorityQueues.packets.violateTx

       64 bit unsigned wrappable counter."
   ::= {pr1645v2PppBFIfOutPriorityQueuesEntry 50855936}

pr1645v2PppBFIfOutPriorityQueuesOctetsTotal OBJECT-TYPE
   SYNTAX      Counter64
   MAX-ACCESS  read-only
   STATUS      current
   DESCRIPTION
      "Path: pppBundle.performance.ifOutPriorityQueues.octets.total

       64 bit unsigned wrappable counter."
   ::= {pr1645v2PppBFIfOutPriorityQueuesEntry 67567616}

pr1645v2PppBFIfOutPriorityQueuesOctetsDirectTx OBJECT-TYPE
   SYNTAX      Counter64
   MAX-ACCESS  read-only
   STATUS      current
   DESCRIPTION
      "Path: pppBundle.performance.ifOutPriorityQueues.octets.directTx

       64 bit unsigned wrappable counter."
   ::= {pr1645v2PppBFIfOutPriorityQueuesEntry 67174400}

pr1645v2PppBFIfOutPriorityQueuesOctetsQueued OBJECT-TYPE
   SYNTAX      Counter64
   MAX-ACCESS  read-only
   STATUS      current
   DESCRIPTION
      "Path: pppBundle.performance.ifOutPriorityQueues.octets.queued

       64 bit unsigned wrappable counter."
   ::= {pr1645v2PppBFIfOutPriorityQueuesEntry 67239936}

pr1645v2PppBFIfOutPriorityQueuesOctetsDropped OBJECT-TYPE
   SYNTAX      Counter64
   MAX-ACCESS  read-only
   STATUS      current
   DESCRIPTION
      "Path: pppBundle.performance.ifOutPriorityQueues.octets.dropped

       64 bit unsigned wrappable counter."
   ::= {pr1645v2PppBFIfOutPriorityQueuesEntry 67305472}

pr1645v2PppBFIfOutPriorityQueuesOctetsRedDropped OBJECT-TYPE
   SYNTAX      Counter64
   MAX-ACCESS  read-only
   STATUS      current
   DESCRIPTION
      "Path: pppBundle.performance.ifOutPriorityQueues.octets.redDropped

       64 bit unsigned wrappable counter."
   ::= {pr1645v2PppBFIfOutPriorityQueuesEntry 67502080}

pr1645v2PppBFIfOutPriorityQueuesOctetsCirTx OBJECT-TYPE
   SYNTAX      Counter64
   MAX-ACCESS  read-only
   STATUS      current
   DESCRIPTION
      "Path: pppBundle.performance.ifOutPriorityQueues.octets.cirTx

       64 bit unsigned wrappable counter."
   ::= {pr1645v2PppBFIfOutPriorityQueuesEntry 67371008}

pr1645v2PppBFIfOutPriorityQueuesOctetsEirTx OBJECT-TYPE
   SYNTAX      Counter64
   MAX-ACCESS  read-only
   STATUS      current
   DESCRIPTION
      "Path: pppBundle.performance.ifOutPriorityQueues.octets.eirTx

       64 bit unsigned wrappable counter."
   ::= {pr1645v2PppBFIfOutPriorityQueuesEntry 67436544}

pr1645v2PppBFIfOutPriorityQueuesOctetsViolateTx OBJECT-TYPE
   SYNTAX      Counter64
   MAX-ACCESS  read-only
   STATUS      current
   DESCRIPTION
      "Path: pppBundle.performance.ifOutPriorityQueues.octets.violateTx

       64 bit unsigned wrappable counter."
   ::= {pr1645v2PppBFIfOutPriorityQueuesEntry 67633152}

pr1645v2PppBFIfOutPriorityQueuesOctetsBandwidth15sec OBJECT-TYPE
   SYNTAX      Integer32
   MAX-ACCESS  read-only
   STATUS      current
   DESCRIPTION
      "Path: pppBundle.performance.ifOutPriorityQueues.octets.bandwidth.15sec

       unit name = bps
       formula = 8 * ; 8 /"
   ::= {pr1645v2PppBFIfOutPriorityQueuesEntry 70386944}

pr1645v2PppBFIfOutPriorityQueuesOctetsBandwidth30sec OBJECT-TYPE
   SYNTAX      Integer32
   MAX-ACCESS  read-only
   STATUS      current
   DESCRIPTION
      "Path: pppBundle.performance.ifOutPriorityQueues.octets.bandwidth.30sec

       unit name = bps
       formula = 8 * ; 8 /"
   ::= {pr1645v2PppBFIfOutPriorityQueuesEntry 70388224}

pr1645v2PppBFIfOutPriorityQueuesOctetsBandwidth1min OBJECT-TYPE
   SYNTAX      Integer32
   MAX-ACCESS  read-only
   STATUS      current
   DESCRIPTION
      "Path: pppBundle.performance.ifOutPriorityQueues.octets.bandwidth.1min

       unit name = bps
       formula = 8 * ; 8 /"
   ::= {pr1645v2PppBFIfOutPriorityQueuesEntry 70390784}

pr1645v2PppBFIfOutPriorityQueuesOctetsBandwidth2min OBJECT-TYPE
   SYNTAX      Integer32
   MAX-ACCESS  read-only
   STATUS      current
   DESCRIPTION
      "Path: pppBundle.performance.ifOutPriorityQueues.octets.bandwidth.2min

       unit name = bps
       formula = 8 * ; 8 /"
   ::= {pr1645v2PppBFIfOutPriorityQueuesEntry 70395904}

pr1645v2PppBFIfOutPriorityQueuesOctetsBandwidth5min OBJECT-TYPE
   SYNTAX      Integer32
   MAX-ACCESS  read-only
   STATUS      current
   DESCRIPTION
      "Path: pppBundle.performance.ifOutPriorityQueues.octets.bandwidth.5min

       unit name = bps
       formula = 8 * ; 8 /"
   ::= {pr1645v2PppBFIfOutPriorityQueuesEntry 70411264}

pr1645v2PppBFIfOutPriorityQueuesH2Performance OBJECT-TYPE
   SYNTAX      SEQUENCE OF Pr1645v2PppBFIfOutPriorityQueuesH2PerformanceEntry
   MAX-ACCESS  not-accessible
   STATUS      current
   DESCRIPTION
      ""
   ::= {pr1645v2PppBFIfOutPriorityQueues 83886080}

pr1645v2PppBFIfOutPriorityQueuesH2PerformanceEntry OBJECT-TYPE
   SYNTAX      Pr1645v2PppBFIfOutPriorityQueuesH2PerformanceEntry
   MAX-ACCESS  not-accessible
   STATUS      current
   DESCRIPTION
      ""
   INDEX      { pr1645v2PppBFIfOutPriorityQueuesH2PerformanceGlobalIx,
                pr1645v2PppBFIfOutPriorityQueuesTableIx,
                pr1645v2PppBFIfOutPriorityQueuesH2PerformanceTableIx }
   ::= {pr1645v2PppBFIfOutPriorityQueuesH2Performance 1}

Pr1645v2PppBFIfOutPriorityQueuesH2PerformanceEntry ::=
   SEQUENCE
      {
      pr1645v2PppBFIfOutPriorityQueuesH2PerformanceGlobalIx
         GlobalIndex,
      pr1645v2PppBFIfOutPriorityQueuesH2PerformanceTableIx
         TableIndex,
      pr1645v2PppBFIfOutPriorityQueuesH2PerformanceSysUpTime
         TimeTicks,
      pr1645v2PppBFIfOutPriorityQueuesH2PerformanceTotPkts
         Counter64,
      pr1645v2PppBFIfOutPriorityQueuesH2PerformanceDirTxPkts
         Counter64,
      pr1645v2PppBFIfOutPriorityQueuesH2PerformanceQdPkts
         Counter64,
      pr1645v2PppBFIfOutPriorityQueuesH2PerformanceDropPkts
         Counter64,
      pr1645v2PppBFIfOutPriorityQueuesH2PerformanceRDropPkts
         Counter64,
      pr1645v2PppBFIfOutPriorityQueuesH2PerformanceCirTxPkts
         Counter64,
      pr1645v2PppBFIfOutPriorityQueuesH2PerformanceEirTxPkts
         Counter64,
      pr1645v2PppBFIfOutPriorityQueuesH2PerformanceViolTxPkts
         Counter64,
      pr1645v2PppBFIfOutPriorityQueuesH2PerformanceTotOcts
         Counter64,
      pr1645v2PppBFIfOutPriorityQueuesH2PerformanceDirTxOcts
         Counter64,
      pr1645v2PppBFIfOutPriorityQueuesH2PerformanceQdOcts
         Counter64,
      pr1645v2PppBFIfOutPriorityQueuesH2PerformanceDropOcts
         Counter64,
      pr1645v2PppBFIfOutPriorityQueuesH2PerformanceRDropOcts
         Counter64,
      pr1645v2PppBFIfOutPriorityQueuesH2PerformanceCirTxOcts
         Counter64,
      pr1645v2PppBFIfOutPriorityQueuesH2PerformanceEirTxOcts
         Counter64,
      pr1645v2PppBFIfOutPriorityQueuesH2PerformanceViolTxOcts
         Counter64,
      pr1645v2PppBFIfOutPriorityQueuesH2PerformanceBandwidth
         Integer32
      }

pr1645v2PppBFIfOutPriorityQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2PppBFIfOutPriorityQueuesH2PerformanceEntry 10}

pr1645v2PppBFIfOutPriorityQueuesH2PerformanceTableIx OBJECT-TYPE
   SYNTAX      TableIndex
   MAX-ACCESS  not-accessible
   STATUS      current
   DESCRIPTION
      ""
   ::= {pr1645v2PppBFIfOutPriorityQueuesH2PerformanceEntry 11}

pr1645v2PppBFIfOutPriorityQueuesH2PerformanceSysUpTime OBJECT-TYPE
   SYNTAX      TimeTicks
   MAX-ACCESS  read-only
   STATUS      current
   DESCRIPTION
      "Path: pppBundle.performance.ifOutPriorityQueues.h2Performance.sysUpTime

       Time in centi-second."
   ::= {pr1645v2PppBFIfOutPriorityQueuesH2PerformanceEntry 16777216}

pr1645v2PppBFIfOutPriorityQueuesH2PerformanceTotPkts OBJECT-TYPE
   SYNTAX      Counter64
   MAX-ACCESS  read-only
   STATUS      current
   DESCRIPTION
      "Path: pppBundle.performance.ifOutPriorityQueues.h2Performance.totalPkts

       64 bit unsigned wrappable counter."
   ::= {pr1645v2PppBFIfOutPriorityQueuesH2PerformanceEntry 234881024}

pr1645v2PppBFIfOutPriorityQueuesH2PerformanceDirTxPkts OBJECT-TYPE
   SYNTAX      Counter64
   MAX-ACCESS  read-only
   STATUS      current
   DESCRIPTION
      "Path: pppBundle.performance.ifOutPriorityQueues.h2Performance.directTxPkts

       64 bit unsigned wrappable counter."
   ::= {pr1645v2PppBFIfOutPriorityQueuesH2PerformanceEntry 33554432}

pr1645v2PppBFIfOutPriorityQueuesH2PerformanceQdPkts OBJECT-TYPE
   SYNTAX      Counter64
   MAX-ACCESS  read-only
   STATUS      current
   DESCRIPTION
      "Path: pppBundle.performance.ifOutPriorityQueues.h2Performance.queuedPkts

       64 bit unsigned wrappable counter."
   ::= {pr1645v2PppBFIfOutPriorityQueuesH2PerformanceEntry 50331648}

pr1645v2PppBFIfOutPriorityQueuesH2PerformanceDropPkts OBJECT-TYPE
   SYNTAX      Counter64
   MAX-ACCESS  read-only
   STATUS      current
   DESCRIPTION
      "Path: pppBundle.performance.ifOutPriorityQueues.h2Performance.droppedPkts

       64 bit unsigned wrappable counter."
   ::= {pr1645v2PppBFIfOutPriorityQueuesH2PerformanceEntry 67108864}

pr1645v2PppBFIfOutPriorityQueuesH2PerformanceRDropPkts OBJECT-TYPE
   SYNTAX      Counter64
   MAX-ACCESS  read-only
   STATUS      current
   DESCRIPTION
      "Path: pppBundle.performance.ifOutPriorityQueues.h2Performance.redDroppedPkts

       64 bit unsigned wrappable counter."
   ::= {pr1645v2PppBFIfOutPriorityQueuesH2PerformanceEntry 201326592}

pr1645v2PppBFIfOutPriorityQueuesH2PerformanceCirTxPkts OBJECT-TYPE
   SYNTAX      Counter64
   MAX-ACCESS  read-only
   STATUS      current
   DESCRIPTION
      "Path: pppBundle.performance.ifOutPriorityQueues.h2Performance.cirTxPkts

       64 bit unsigned wrappable counter."
   ::= {pr1645v2PppBFIfOutPriorityQueuesH2PerformanceEntry 83886080}

pr1645v2PppBFIfOutPriorityQueuesH2PerformanceEirTxPkts OBJECT-TYPE
   SYNTAX      Counter64
   MAX-ACCESS  read-only
   STATUS      current
   DESCRIPTION
      "Path: pppBundle.performance.ifOutPriorityQueues.h2Performance.eirTxPkts

       64 bit unsigned wrappable counter."
   ::= {pr1645v2PppBFIfOutPriorityQueuesH2PerformanceEntry 100663296}

pr1645v2PppBFIfOutPriorityQueuesH2PerformanceViolTxPkts OBJECT-TYPE
   SYNTAX      Counter64
   MAX-ACCESS  read-only
   STATUS      current
   DESCRIPTION
      "Path: pppBundle.performance.ifOutPriorityQueues.h2Performance.violateTxPkts

       64 bit unsigned wrappable counter."
   ::= {pr1645v2PppBFIfOutPriorityQueuesH2PerformanceEntry 301989888}

pr1645v2PppBFIfOutPriorityQueuesH2PerformanceTotOcts OBJECT-TYPE
   SYNTAX      Counter64
   MAX-ACCESS  read-only
   STATUS      current
   DESCRIPTION
      "Path: pppBundle.performance.ifOutPriorityQueues.h2Performance.totalOctets

       64 bit unsigned wrappable counter."
   ::= {pr1645v2PppBFIfOutPriorityQueuesH2PerformanceEntry 251658240}

pr1645v2PppBFIfOutPriorityQueuesH2PerformanceDirTxOcts OBJECT-TYPE
   SYNTAX      Counter64
   MAX-ACCESS  read-only
   STATUS      current
   DESCRIPTION
      "Path: pppBundle.performance.ifOutPriorityQueues.h2Performance.directTxOctets

       64 bit unsigned wrappable counter."
   ::= {pr1645v2PppBFIfOutPriorityQueuesH2PerformanceEntry 117440512}

pr1645v2PppBFIfOutPriorityQueuesH2PerformanceQdOcts OBJECT-TYPE
   SYNTAX      Counter64
   MAX-ACCESS  read-only
   STATUS      current
   DESCRIPTION
      "Path: pppBundle.performance.ifOutPriorityQueues.h2Performance.queuedOctets

       64 bit unsigned wrappable counter."
   ::= {pr1645v2PppBFIfOutPriorityQueuesH2PerformanceEntry 134217728}

pr1645v2PppBFIfOutPriorityQueuesH2PerformanceDropOcts OBJECT-TYPE
   SYNTAX      Counter64
   MAX-ACCESS  read-only
   STATUS      current
   DESCRIPTION
      "Path: pppBundle.performance.ifOutPriorityQueues.h2Performance.droppedOctets

       64 bit unsigned wrappable counter."
   ::= {pr1645v2PppBFIfOutPriorityQueuesH2PerformanceEntry 150994944}

pr1645v2PppBFIfOutPriorityQueuesH2PerformanceRDropOcts OBJECT-TYPE
   SYNTAX      Counter64
   MAX-ACCESS  read-only
   STATUS      current
   DESCRIPTION
      "Path: pppBundle.performance.ifOutPriorityQueues.h2Performance.redDroppedOctets

       64 bit unsigned wrappable counter."
   ::= {pr1645v2PppBFIfOutPriorityQueuesH2PerformanceEntry 218103808}

pr1645v2PppBFIfOutPriorityQueuesH2PerformanceCirTxOcts OBJECT-TYPE
   SYNTAX      Counter64
   MAX-ACCESS  read-only
   STATUS      current
   DESCRIPTION
      "Path: pppBundle.performance.ifOutPriorityQueues.h2Performance.cirTxOctets

       64 bit unsigned wrappable counter."
   ::= {pr1645v2PppBFIfOutPriorityQueuesH2PerformanceEntry 167772160}

pr1645v2PppBFIfOutPriorityQueuesH2PerformanceEirTxOcts OBJECT-TYPE
   SYNTAX      Counter64
   MAX-ACCESS  read-only
   STATUS      current
   DESCRIPTION
      "Path: pppBundle.performance.ifOutPriorityQueues.h2Performance.eirTxOctets

       64 bit unsigned wrappable counter."
   ::= {pr1645v2PppBFIfOutPriorityQueuesH2PerformanceEntry 184549376}

pr1645v2PppBFIfOutPriorityQueuesH2PerformanceViolTxOcts OBJECT-TYPE
   SYNTAX      Counter64
   MAX-ACCESS  read-only
   STATUS      current
   DESCRIPTION
      "Path: pppBundle.performance.ifOutPriorityQueues.h2Performance.violateTxOctets

       64 bit unsigned wrappable counter."
   ::= {pr1645v2PppBFIfOutPriorityQueuesH2PerformanceEntry 318767104}

pr1645v2PppBFIfOutPriorityQueuesH2PerformanceBandwidth OBJECT-TYPE
   SYNTAX      Integer32
   MAX-ACCESS  read-only
   STATUS      current
   DESCRIPTION
      "Path: pppBundle.performance.ifOutPriorityQueues.h2Performance.bandwidth

       unit name = bps
       formula = 8 * ; 8 /"
   ::= {pr1645v2PppBFIfOutPriorityQueuesH2PerformanceEntry 268435456}

pr1645v2PppBFIfOutPriorityQueuesH24Performance OBJECT-TYPE
   SYNTAX      SEQUENCE OF Pr1645v2PppBFIfOutPriorityQueuesH24PerformanceEntry
   MAX-ACCESS  not-accessible
   STATUS      current
   DESCRIPTION
      ""
   ::= {pr1645v2PppBFIfOutPriorityQueues 100663296}

pr1645v2PppBFIfOutPriorityQueuesH24PerformanceEntry OBJECT-TYPE
   SYNTAX      Pr1645v2PppBFIfOutPriorityQueuesH24PerformanceEntry
   MAX-ACCESS  not-accessible
   STATUS      current
   DESCRIPTION
      ""
   INDEX      { pr1645v2PppBFIfOutPriorityQueuesH24PerformanceGlobalIx,
                pr1645v2PppBFIfOutPriorityQueuesTableIx,
                pr1645v2PppBFIfOutPriorityQueuesH24PerformanceTableIx }
   ::= {pr1645v2PppBFIfOutPriorityQueuesH24Performance 1}

Pr1645v2PppBFIfOutPriorityQueuesH24PerformanceEntry ::=
   SEQUENCE
      {
      pr1645v2PppBFIfOutPriorityQueuesH24PerformanceGlobalIx
         GlobalIndex,
      pr1645v2PppBFIfOutPriorityQueuesH24PerformanceTableIx
         TableIndex,
      pr1645v2PppBFIfOutPriorityQueuesH24PerformanceSysUpTime
         TimeTicks,
      pr1645v2PppBFIfOutPriorityQueuesH24PerformanceTotPkts
         Counter64,
      pr1645v2PppBFIfOutPriorityQueuesH24PerformanceDirTxPkts
         Counter64,
      pr1645v2PppBFIfOutPriorityQueuesH24PerformanceQdPkts
         Counter64,
      pr1645v2PppBFIfOutPriorityQueuesH24PerformanceDropPkts
         Counter64,
      pr1645v2PppBFIfOutPriorityQueuesH24PerformanceRDropPkts
         Counter64,
      pr1645v2PppBFIfOutPriorityQueuesH24PerformanceCirTxPkts
         Counter64,
      pr1645v2PppBFIfOutPriorityQueuesH24PerformanceEirTxPkts
         Counter64,
      pr1645v2PppBFIfOutPriorityQueuesH24PerformanceViolTxPkts
         Counter64,
      pr1645v2PppBFIfOutPriorityQueuesH24PerformanceTotOcts
         Counter64,
      pr1645v2PppBFIfOutPriorityQueuesH24PerformanceDirTxOcts
         Counter64,
      pr1645v2PppBFIfOutPriorityQueuesH24PerformanceQdOcts
         Counter64,
      pr1645v2PppBFIfOutPriorityQueuesH24PerformanceDropOcts
         Counter64,
      pr1645v2PppBFIfOutPriorityQueuesH24PerformanceRDropOcts
         Counter64,
      pr1645v2PppBFIfOutPriorityQueuesH24PerformanceCirTxOcts
         Counter64,
      pr1645v2PppBFIfOutPriorityQueuesH24PerformanceEirTxOcts
         Counter64,
      pr1645v2PppBFIfOutPriorityQueuesH24PerformanceViolTxOcts
         Counter64,
      pr1645v2PppBFIfOutPriorityQueuesH24PerformanceBandwidth
         Integer32
      }

pr1645v2PppBFIfOutPriorityQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2PppBFIfOutPriorityQueuesH24PerformanceEntry 10}

pr1645v2PppBFIfOutPriorityQueuesH24PerformanceTableIx OBJECT-TYPE
   SYNTAX      TableIndex
   MAX-ACCESS  not-accessible
   STATUS      current
   DESCRIPTION
      ""
   ::= {pr1645v2PppBFIfOutPriorityQueuesH24PerformanceEntry 11}

pr1645v2PppBFIfOutPriorityQueuesH24PerformanceSysUpTime OBJECT-TYPE
   SYNTAX      TimeTicks
   MAX-ACCESS  read-only
   STATUS      current
   DESCRIPTION
      "Path: pppBundle.performance.ifOutPriorityQueues.h24Performance.sysUpTime

       Time in centi-second."
   ::= {pr1645v2PppBFIfOutPriorityQueuesH24PerformanceEntry 16777216}

pr1645v2PppBFIfOutPriorityQueuesH24PerformanceTotPkts OBJECT-TYPE
   SYNTAX      Counter64
   MAX-ACCESS  read-only
   STATUS      current
   DESCRIPTION
      "Path: pppBundle.performance.ifOutPriorityQueues.h24Performance.totalPkts

       64 bit unsigned wrappable counter."
   ::= {pr1645v2PppBFIfOutPriorityQueuesH24PerformanceEntry 234881024}

pr1645v2PppBFIfOutPriorityQueuesH24PerformanceDirTxPkts OBJECT-TYPE
   SYNTAX      Counter64
   MAX-ACCESS  read-only
   STATUS      current
   DESCRIPTION
      "Path: pppBundle.performance.ifOutPriorityQueues.h24Performance.directTxPkts

       64 bit unsigned wrappable counter."
   ::= {pr1645v2PppBFIfOutPriorityQueuesH24PerformanceEntry 33554432}

pr1645v2PppBFIfOutPriorityQueuesH24PerformanceQdPkts OBJECT-TYPE
   SYNTAX      Counter64
   MAX-ACCESS  read-only
   STATUS      current
   DESCRIPTION
      "Path: pppBundle.performance.ifOutPriorityQueues.h24Performance.queuedPkts

       64 bit unsigned wrappable counter."
   ::= {pr1645v2PppBFIfOutPriorityQueuesH24PerformanceEntry 50331648}

pr1645v2PppBFIfOutPriorityQueuesH24PerformanceDropPkts OBJECT-TYPE
   SYNTAX      Counter64
   MAX-ACCESS  read-only
   STATUS      current
   DESCRIPTION
      "Path: pppBundle.performance.ifOutPriorityQueues.h24Performance.droppedPkts

       64 bit unsigned wrappable counter."
   ::= {pr1645v2PppBFIfOutPriorityQueuesH24PerformanceEntry 67108864}

pr1645v2PppBFIfOutPriorityQueuesH24PerformanceRDropPkts OBJECT-TYPE
   SYNTAX      Counter64
   MAX-ACCESS  read-only
   STATUS      current
   DESCRIPTION
      "Path: pppBundle.performance.ifOutPriorityQueues.h24Performance.redDroppedPkts

       64 bit unsigned wrappable counter."
   ::= {pr1645v2PppBFIfOutPriorityQueuesH24PerformanceEntry 201326592}

pr1645v2PppBFIfOutPriorityQueuesH24PerformanceCirTxPkts OBJECT-TYPE
   SYNTAX      Counter64
   MAX-ACCESS  read-only
   STATUS      current
   DESCRIPTION
      "Path: pppBundle.performance.ifOutPriorityQueues.h24Performance.cirTxPkts

       64 bit unsigned wrappable counter."
   ::= {pr1645v2PppBFIfOutPriorityQueuesH24PerformanceEntry 83886080}

pr1645v2PppBFIfOutPriorityQueuesH24PerformanceEirTxPkts OBJECT-TYPE
   SYNTAX      Counter64
   MAX-ACCESS  read-only
   STATUS      current
   DESCRIPTION
      "Path: pppBundle.performance.ifOutPriorityQueues.h24Performance.eirTxPkts

       64 bit unsigned wrappable counter."
   ::= {pr1645v2PppBFIfOutPriorityQueuesH24PerformanceEntry 100663296}

pr1645v2PppBFIfOutPriorityQueuesH24PerformanceViolTxPkts OBJECT-TYPE
   SYNTAX      Counter64
   MAX-ACCESS  read-only
   STATUS      current
   DESCRIPTION
      "Path: pppBundle.performance.ifOutPriorityQueues.h24Performance.violateTxPkts

       64 bit unsigned wrappable counter."
   ::= {pr1645v2PppBFIfOutPriorityQueuesH24PerformanceEntry 301989888}

pr1645v2PppBFIfOutPriorityQueuesH24PerformanceTotOcts OBJECT-TYPE
   SYNTAX      Counter64
   MAX-ACCESS  read-only
   STATUS      current
   DESCRIPTION
      "Path: pppBundle.performance.ifOutPriorityQueues.h24Performance.totalOctets

       64 bit unsigned wrappable counter."
   ::= {pr1645v2PppBFIfOutPriorityQueuesH24PerformanceEntry 251658240}

pr1645v2PppBFIfOutPriorityQueuesH24PerformanceDirTxOcts OBJECT-TYPE
   SYNTAX      Counter64
   MAX-ACCESS  read-only
   STATUS      current
   DESCRIPTION
      "Path: pppBundle.performance.ifOutPriorityQueues.h24Performance.directTxOctets

       64 bit unsigned wrappable counter."
   ::= {pr1645v2PppBFIfOutPriorityQueuesH24PerformanceEntry 117440512}

pr1645v2PppBFIfOutPriorityQueuesH24PerformanceQdOcts OBJECT-TYPE
   SYNTAX      Counter64
   MAX-ACCESS  read-only
   STATUS      current
   DESCRIPTION
      "Path: pppBundle.performance.ifOutPriorityQueues.h24Performance.queuedOctets

       64 bit unsigned wrappable counter."
   ::= {pr1645v2PppBFIfOutPriorityQueuesH24PerformanceEntry 134217728}

pr1645v2PppBFIfOutPriorityQueuesH24PerformanceDropOcts OBJECT-TYPE
   SYNTAX      Counter64
   MAX-ACCESS  read-only
   STATUS      current
   DESCRIPTION
      "Path: pppBundle.performance.ifOutPriorityQueues.h24Performance.droppedOctets

       64 bit unsigned wrappable counter."
   ::= {pr1645v2PppBFIfOutPriorityQueuesH24PerformanceEntry 150994944}

pr1645v2PppBFIfOutPriorityQueuesH24PerformanceRDropOcts OBJECT-TYPE
   SYNTAX      Counter64
   MAX-ACCESS  read-only
   STATUS      current
   DESCRIPTION
      "Path: pppBundle.performance.ifOutPriorityQueues.h24Performance.redDroppedOctets

       64 bit unsigned wrappable counter."
   ::= {pr1645v2PppBFIfOutPriorityQueuesH24PerformanceEntry 218103808}

pr1645v2PppBFIfOutPriorityQueuesH24PerformanceCirTxOcts OBJECT-TYPE
   SYNTAX      Counter64
   MAX-ACCESS  read-only
   STATUS      current
   DESCRIPTION
      "Path: pppBundle.performance.ifOutPriorityQueues.h24Performance.cirTxOctets

       64 bit unsigned wrappable counter."
   ::= {pr1645v2PppBFIfOutPriorityQueuesH24PerformanceEntry 167772160}

pr1645v2PppBFIfOutPriorityQueuesH24PerformanceEirTxOcts OBJECT-TYPE
   SYNTAX      Counter64
   MAX-ACCESS  read-only
   STATUS      current
   DESCRIPTION
      "Path: pppBundle.performance.ifOutPriorityQueues.h24Performance.eirTxOctets

       64 bit unsigned wrappable counter."
   ::= {pr1645v2PppBFIfOutPriorityQueuesH24PerformanceEntry 184549376}

pr1645v2PppBFIfOutPriorityQueuesH24PerformanceViolTxOcts OBJECT-TYPE
   SYNTAX      Counter64
   MAX-ACCESS  read-only
   STATUS      current
   DESCRIPTION
      "Path: pppBundle.performance.ifOutPriorityQueues.h24Performance.violateTxOctets

       64 bit unsigned wrappable counter."
   ::= {pr1645v2PppBFIfOutPriorityQueuesH24PerformanceEntry 318767104}

pr1645v2PppBFIfOutPriorityQueuesH24PerformanceBandwidth OBJECT-TYPE
   SYNTAX      Integer32
   MAX-ACCESS  read-only
   STATUS      current
   DESCRIPTION
      "Path: pppBundle.performance.ifOutPriorityQueues.h24Performance.bandwidth

       unit name = bps
       formula = 8 * ; 8 /"
   ::= {pr1645v2PppBFIfOutPriorityQueuesH24PerformanceEntry 268435456}

pr1645v2PppBFIfOutPriorityQueuesD7Performance OBJECT-TYPE
   SYNTAX      SEQUENCE OF Pr1645v2PppBFIfOutPriorityQueuesD7PerformanceEntry
   MAX-ACCESS  not-accessible
   STATUS      current
   DESCRIPTION
      ""
   ::= {pr1645v2PppBFIfOutPriorityQueues 117440512}

pr1645v2PppBFIfOutPriorityQueuesD7PerformanceEntry OBJECT-TYPE
   SYNTAX      Pr1645v2PppBFIfOutPriorityQueuesD7PerformanceEntry
   MAX-ACCESS  not-accessible
   STATUS      current
   DESCRIPTION
      ""
   INDEX      { pr1645v2PppBFIfOutPriorityQueuesD7PerformanceGlobalIx,
                pr1645v2PppBFIfOutPriorityQueuesTableIx,
                pr1645v2PppBFIfOutPriorityQueuesD7PerformanceTableIx }
   ::= {pr1645v2PppBFIfOutPriorityQueuesD7Performance 1}

Pr1645v2PppBFIfOutPriorityQueuesD7PerformanceEntry ::=
   SEQUENCE
      {
      pr1645v2PppBFIfOutPriorityQueuesD7PerformanceGlobalIx
         GlobalIndex,
      pr1645v2PppBFIfOutPriorityQueuesD7PerformanceTableIx
         TableIndex,
      pr1645v2PppBFIfOutPriorityQueuesD7PerformanceSysUpTime
         TimeTicks,
      pr1645v2PppBFIfOutPriorityQueuesD7PerformanceTotPkts
         Counter64,
      pr1645v2PppBFIfOutPriorityQueuesD7PerformanceDirTxPkts
         Counter64,
      pr1645v2PppBFIfOutPriorityQueuesD7PerformanceQdPkts
         Counter64,
      pr1645v2PppBFIfOutPriorityQueuesD7PerformanceDropPkts
         Counter64,
      pr1645v2PppBFIfOutPriorityQueuesD7PerformanceRDropPkts
         Counter64,
      pr1645v2PppBFIfOutPriorityQueuesD7PerformanceCirTxPkts
         Counter64,
      pr1645v2PppBFIfOutPriorityQueuesD7PerformanceEirTxPkts
         Counter64,
      pr1645v2PppBFIfOutPriorityQueuesD7PerformanceViolTxPkts
         Counter64,
      pr1645v2PppBFIfOutPriorityQueuesD7PerformanceTotOcts
         Counter64,
      pr1645v2PppBFIfOutPriorityQueuesD7PerformanceDirTxOcts
         Counter64,
      pr1645v2PppBFIfOutPriorityQueuesD7PerformanceQdOcts
         Counter64,
      pr1645v2PppBFIfOutPriorityQueuesD7PerformanceDropOcts
         Counter64,
      pr1645v2PppBFIfOutPriorityQueuesD7PerformanceRDropOcts
         Counter64,
      pr1645v2PppBFIfOutPriorityQueuesD7PerformanceCirTxOcts
         Counter64,
      pr1645v2PppBFIfOutPriorityQueuesD7PerformanceEirTxOcts
         Counter64,
      pr1645v2PppBFIfOutPriorityQueuesD7PerformanceViolTxOcts
         Counter64,
      pr1645v2PppBFIfOutPriorityQueuesD7PerformanceBandwidth
         Integer32
      }

pr1645v2PppBFIfOutPriorityQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2PppBFIfOutPriorityQueuesD7PerformanceEntry 10}

pr1645v2PppBFIfOutPriorityQueuesD7PerformanceTableIx OBJECT-TYPE
   SYNTAX      TableIndex
   MAX-ACCESS  not-accessible
   STATUS      current
   DESCRIPTION
      ""
   ::= {pr1645v2PppBFIfOutPriorityQueuesD7PerformanceEntry 11}

pr1645v2PppBFIfOutPriorityQueuesD7PerformanceSysUpTime OBJECT-TYPE
   SYNTAX      TimeTicks
   MAX-ACCESS  read-only
   STATUS      current
   DESCRIPTION
      "Path: pppBundle.performance.ifOutPriorityQueues.d7Performance.sysUpTime

       Time in centi-second."
   ::= {pr1645v2PppBFIfOutPriorityQueuesD7PerformanceEntry 16777216}

pr1645v2PppBFIfOutPriorityQueuesD7PerformanceTotPkts OBJECT-TYPE
   SYNTAX      Counter64
   MAX-ACCESS  read-only
   STATUS      current
   DESCRIPTION
      "Path: pppBundle.performance.ifOutPriorityQueues.d7Performance.totalPkts

       64 bit unsigned wrappable counter."
   ::= {pr1645v2PppBFIfOutPriorityQueuesD7PerformanceEntry 234881024}

pr1645v2PppBFIfOutPriorityQueuesD7PerformanceDirTxPkts OBJECT-TYPE
   SYNTAX      Counter64
   MAX-ACCESS  read-only
   STATUS      current
   DESCRIPTION
      "Path: pppBundle.performance.ifOutPriorityQueues.d7Performance.directTxPkts

       64 bit unsigned wrappable counter."
   ::= {pr1645v2PppBFIfOutPriorityQueuesD7PerformanceEntry 33554432}

pr1645v2PppBFIfOutPriorityQueuesD7PerformanceQdPkts OBJECT-TYPE
   SYNTAX      Counter64
   MAX-ACCESS  read-only
   STATUS      current
   DESCRIPTION
      "Path: pppBundle.performance.ifOutPriorityQueues.d7Performance.queuedPkts

       64 bit unsigned wrappable counter."
   ::= {pr1645v2PppBFIfOutPriorityQueuesD7PerformanceEntry 50331648}

pr1645v2PppBFIfOutPriorityQueuesD7PerformanceDropPkts OBJECT-TYPE
   SYNTAX      Counter64
   MAX-ACCESS  read-only
   STATUS      current
   DESCRIPTION
      "Path: pppBundle.performance.ifOutPriorityQueues.d7Performance.droppedPkts

       64 bit unsigned wrappable counter."
   ::= {pr1645v2PppBFIfOutPriorityQueuesD7PerformanceEntry 67108864}

pr1645v2PppBFIfOutPriorityQueuesD7PerformanceRDropPkts OBJECT-TYPE
   SYNTAX      Counter64
   MAX-ACCESS  read-only
   STATUS      current
   DESCRIPTION
      "Path: pppBundle.performance.ifOutPriorityQueues.d7Performance.redDroppedPkts

       64 bit unsigned wrappable counter."
   ::= {pr1645v2PppBFIfOutPriorityQueuesD7PerformanceEntry 201326592}

pr1645v2PppBFIfOutPriorityQueuesD7PerformanceCirTxPkts OBJECT-TYPE
   SYNTAX      Counter64
   MAX-ACCESS  read-only
   STATUS      current
   DESCRIPTION
      "Path: pppBundle.performance.ifOutPriorityQueues.d7Performance.cirTxPkts

       64 bit unsigned wrappable counter."
   ::= {pr1645v2PppBFIfOutPriorityQueuesD7PerformanceEntry 83886080}

pr1645v2PppBFIfOutPriorityQueuesD7PerformanceEirTxPkts OBJECT-TYPE
   SYNTAX      Counter64
   MAX-ACCESS  read-only
   STATUS      current
   DESCRIPTION
      "Path: pppBundle.performance.ifOutPriorityQueues.d7Performance.eirTxPkts

       64 bit unsigned wrappable counter."
   ::= {pr1645v2PppBFIfOutPriorityQueuesD7PerformanceEntry 100663296}

pr1645v2PppBFIfOutPriorityQueuesD7PerformanceViolTxPkts OBJECT-TYPE
   SYNTAX      Counter64
   MAX-ACCESS  read-only
   STATUS      current
   DESCRIPTION
      "Path: pppBundle.performance.ifOutPriorityQueues.d7Performance.violateTxPkts

       64 bit unsigned wrappable counter."
   ::= {pr1645v2PppBFIfOutPriorityQueuesD7PerformanceEntry 301989888}

pr1645v2PppBFIfOutPriorityQueuesD7PerformanceTotOcts OBJECT-TYPE
   SYNTAX      Counter64
   MAX-ACCESS  read-only
   STATUS      current
   DESCRIPTION
      "Path: pppBundle.performance.ifOutPriorityQueues.d7Performance.totalOctets

       64 bit unsigned wrappable counter."
   ::= {pr1645v2PppBFIfOutPriorityQueuesD7PerformanceEntry 251658240}

pr1645v2PppBFIfOutPriorityQueuesD7PerformanceDirTxOcts OBJECT-TYPE
   SYNTAX      Counter64
   MAX-ACCESS  read-only
   STATUS      current
   DESCRIPTION
      "Path: pppBundle.performance.ifOutPriorityQueues.d7Performance.directTxOctets

       64 bit unsigned wrappable counter."
   ::= {pr1645v2PppBFIfOutPriorityQueuesD7PerformanceEntry 117440512}

pr1645v2PppBFIfOutPriorityQueuesD7PerformanceQdOcts OBJECT-TYPE
   SYNTAX      Counter64
   MAX-ACCESS  read-only
   STATUS      current
   DESCRIPTION
      "Path: pppBundle.performance.ifOutPriorityQueues.d7Performance.queuedOctets

       64 bit unsigned wrappable counter."
   ::= {pr1645v2PppBFIfOutPriorityQueuesD7PerformanceEntry 134217728}

pr1645v2PppBFIfOutPriorityQueuesD7PerformanceDropOcts OBJECT-TYPE
   SYNTAX      Counter64
   MAX-ACCESS  read-only
   STATUS      current
   DESCRIPTION
      "Path: pppBundle.performance.ifOutPriorityQueues.d7Performance.droppedOctets

       64 bit unsigned wrappable counter."
   ::= {pr1645v2PppBFIfOutPriorityQueuesD7PerformanceEntry 150994944}

pr1645v2PppBFIfOutPriorityQueuesD7PerformanceRDropOcts OBJECT-TYPE
   SYNTAX      Counter64
   MAX-ACCESS  read-only
   STATUS      current
   DESCRIPTION
      "Path: pppBundle.performance.ifOutPriorityQueues.d7Performance.redDroppedOctets

       64 bit unsigned wrappable counter."
   ::= {pr1645v2PppBFIfOutPriorityQueuesD7PerformanceEntry 218103808}

pr1645v2PppBFIfOutPriorityQueuesD7PerformanceCirTxOcts OBJECT-TYPE
   SYNTAX      Counter64
   MAX-ACCESS  read-only
   STATUS      current
   DESCRIPTION
      "Path: pppBundle.performance.ifOutPriorityQueues.d7Performance.cirTxOctets

       64 bit unsigned wrappable counter."
   ::= {pr1645v2PppBFIfOutPriorityQueuesD7PerformanceEntry 167772160}

pr1645v2PppBFIfOutPriorityQueuesD7PerformanceEirTxOcts OBJECT-TYPE
   SYNTAX      Counter64
   MAX-ACCESS  read-only
   STATUS      current
   DESCRIPTION
      "Path: pppBundle.performance.ifOutPriorityQueues.d7Performance.eirTxOctets

       64 bit unsigned wrappable counter."
   ::= {pr1645v2PppBFIfOutPriorityQueuesD7PerformanceEntry 184549376}

pr1645v2PppBFIfOutPriorityQueuesD7PerformanceViolTxOcts OBJECT-TYPE
   SYNTAX      Counter64
   MAX-ACCESS  read-only
   STATUS      current
   DESCRIPTION
      "Path: pppBundle.performance.ifOutPriorityQueues.d7Performance.violateTxOctets

       64 bit unsigned wrappable counter."
   ::= {pr1645v2PppBFIfOutPriorityQueuesD7PerformanceEntry 318767104}

pr1645v2PppBFIfOutPriorityQueuesD7PerformanceBandwidth OBJECT-TYPE
   SYNTAX      Integer32
   MAX-ACCESS  read-only
   STATUS      current
   DESCRIPTION
      "Path: pppBundle.performance.ifOutPriorityQueues.d7Performance.bandwidth

       unit name = bps
       formula = 8 * ; 8 /"
   ::= {pr1645v2PppBFIfOutPriorityQueuesD7PerformanceEntry 268435456}


pr1645v2PppBFOutBandwidth OBJECT IDENTIFIER ::= {pr1645v2PppBF 182}

pr1645v2PppBFOutBandwidthSSCTable OBJECT-TYPE
   SYNTAX      SEQUENCE OF Pr1645v2PppBFOutBandwidthEntry
   MAX-ACCESS  not-accessible
   STATUS      current
   DESCRIPTION
      "bandwidth"
   ::= {pr1645v2PppBFOutBandwidth 1}

pr1645v2PppBFOutBandwidthEntry OBJECT-TYPE
   SYNTAX      Pr1645v2PppBFOutBandwidthEntry
   MAX-ACCESS  not-accessible
   STATUS      current
   DESCRIPTION
      ""
   INDEX      { pr1645v2PppBFOutBandwidthGlobalIx }
   ::= {pr1645v2PppBFOutBandwidthSSCTable 1}

Pr1645v2PppBFOutBandwidthEntry ::=
   SEQUENCE
      {
      pr1645v2PppBFOutBandwidthGlobalIx
         GlobalIndex,
      pr1645v2PppBFOutBandwidth15sec
         Integer32,
      pr1645v2PppBFOutBandwidth30sec
         Integer32,
      pr1645v2PppBFOutBandwidth1min
         Integer32,
      pr1645v2PppBFOutBandwidth2min
         Integer32,
      pr1645v2PppBFOutBandwidth5min
         Integer32
      }

pr1645v2PppBFOutBandwidthGlobalIx OBJECT-TYPE
   SYNTAX      GlobalIndex
   MAX-ACCESS  not-accessible
   STATUS      current
   DESCRIPTION
      "The value of the tlsCntTreeGlobalIndex of the MANAGED OBJECT."
   ::= {pr1645v2PppBFOutBandwidthEntry 10}

pr1645v2PppBFOutBandwidth15sec OBJECT-TYPE
   SYNTAX      Integer32
   MAX-ACCESS  read-only
   STATUS      current
   DESCRIPTION
      "Path: pppBundle.performance.ifOutBandwidth.15sec

       unit name = bps
       formula = 8 * ; 8 /"
   ::= {pr1645v2PppBFOutBandwidthEntry 83886080}

pr1645v2PppBFOutBandwidth30sec OBJECT-TYPE
   SYNTAX      Integer32
   MAX-ACCESS  read-only
   STATUS      current
   DESCRIPTION
      "Path: pppBundle.performance.ifOutBandwidth.30sec

       unit name = bps
       formula = 8 * ; 8 /"
   ::= {pr1645v2PppBFOutBandwidthEntry 167772160}

pr1645v2PppBFOutBandwidth1min OBJECT-TYPE
   SYNTAX      Integer32
   MAX-ACCESS  read-only
   STATUS      current
   DESCRIPTION
      "Path: pppBundle.performance.ifOutBandwidth.1min

       unit name = bps
       formula = 8 * ; 8 /"
   ::= {pr1645v2PppBFOutBandwidthEntry 335544320}

pr1645v2PppBFOutBandwidth2min OBJECT-TYPE
   SYNTAX      Integer32
   MAX-ACCESS  read-only
   STATUS      current
   DESCRIPTION
      "Path: pppBundle.performance.ifOutBandwidth.2min

       unit name = bps
       formula = 8 * ; 8 /"
   ::= {pr1645v2PppBFOutBandwidthEntry 671088640}

pr1645v2PppBFOutBandwidth5min OBJECT-TYPE
   SYNTAX      Integer32
   MAX-ACCESS  read-only
   STATUS      current
   DESCRIPTION
      "Path: pppBundle.performance.ifOutBandwidth.5min

       unit name = bps
       formula = 8 * ; 8 /"
   ::= {pr1645v2PppBFOutBandwidthEntry 1677721600}


pr1645v2PppBFInP OBJECT IDENTIFIER ::= {pr1645v2PppBF 307}

pr1645v2PppBFInPSSCTable OBJECT-TYPE
   SYNTAX      SEQUENCE OF Pr1645v2PppBFInPEntry
   MAX-ACCESS  not-accessible
   STATUS      current
   DESCRIPTION
      "h2IfInPerformance"
   ::= {pr1645v2PppBFInP 1}

pr1645v2PppBFInPEntry OBJECT-TYPE
   SYNTAX      Pr1645v2PppBFInPEntry
   MAX-ACCESS  not-accessible
   STATUS      current
   DESCRIPTION
      ""
   INDEX      { pr1645v2PppBFInPGlobalIx,
                pr1645v2PppBFInPTableIx }
   ::= {pr1645v2PppBFInPSSCTable 1}

Pr1645v2PppBFInPEntry ::=
   SEQUENCE
      {
      pr1645v2PppBFInPGlobalIx
         GlobalIndex,
      pr1645v2PppBFInPTableIx
         TableIndex,
      pr1645v2PppBFInPSysUpTime
         TimeTicks,
      pr1645v2PppBFInPIfUpTime
         TimeTicks,
      pr1645v2PppBFInPIfStatChanges
         Counter32,
      pr1645v2PppBFInPIfInOctets
         Counter64,
      pr1645v2PppBFInPIfInUCPkts
         Counter64,
      pr1645v2PppBFInPIfInNUCPkts
         Counter64,
      pr1645v2PppBFInPIfInBCPkts
         Counter64,
      pr1645v2PppBFInPIfInMCPkts
         Counter64,
      pr1645v2PppBFInPIfInDiscards
         Counter64,
      pr1645v2PppBFInPIfInErrors
         Counter64,
      pr1645v2PppBFInPIfInUnkwn
         Counter64,
      pr1645v2PppBFInPInDropEx
         Counter64,
      pr1645v2PppBFInPInDropNoMac
         Counter64,
      pr1645v2PppBFInPInDropNUCast
         Counter64,
      pr1645v2PppBFInPInDropFilter
         Counter64,
      pr1645v2PppBFInPIfInBandwidth
         Integer32,
      pr1645v2PppBFInPIfOutOctets
         Counter64,
      pr1645v2PppBFInPIfOutUCPkts
         Counter64,
      pr1645v2PppBFInPIfOutNUCPkts
         Counter64,
      pr1645v2PppBFInPIfOutBCPkts
         Counter64,
      pr1645v2PppBFInPIfOutMCPkts
         Counter64,
      pr1645v2PppBFInPIfOutDiscards
         Counter64,
      pr1645v2PppBFInPIfOutErrors
         Counter64,
      pr1645v2PppBFInPOutDropEx
         Counter64,
      pr1645v2PppBFInPOutDropNoArp
         Counter64,
      pr1645v2PppBFInPOutDropFilter
         Counter64,
      pr1645v2PppBFInPIfOutBandwidth
         Integer32,
      pr1645v2PppBFInPIfErrSec
         Counter32
      }

pr1645v2PppBFInPGlobalIx OBJECT-TYPE
   SYNTAX      GlobalIndex
   MAX-ACCESS  not-accessible
   STATUS      current
   DESCRIPTION
      "The value of the tlsCntTreeGlobalIndex of the MANAGED OBJECT."
   ::= {pr1645v2PppBFInPEntry 10}

pr1645v2PppBFInPTableIx OBJECT-TYPE
   SYNTAX      TableIndex
   MAX-ACCESS  not-accessible
   STATUS      current
   DESCRIPTION
      ""
   ::= {pr1645v2PppBFInPEntry 11}

pr1645v2PppBFInPSysUpTime OBJECT-TYPE
   SYNTAX      TimeTicks
   MAX-ACCESS  read-only
   STATUS      current
   DESCRIPTION
      "Path: pppBundle.performance.h2Performance.sysUpTime

       Time in centi-second."
   ::= {pr1645v2PppBFInPEntry 16777216}

pr1645v2PppBFInPIfUpTime OBJECT-TYPE
   SYNTAX      TimeTicks
   MAX-ACCESS  read-only
   STATUS      current
   DESCRIPTION
      "Path: pppBundle.performance.h2Performance.ifUpTime

       Time in centi-second."
   ::= {pr1645v2PppBFInPEntry 33554432}

pr1645v2PppBFInPIfStatChanges OBJECT-TYPE
   SYNTAX      Counter32
   MAX-ACCESS  read-only
   STATUS      current
   DESCRIPTION
      "Path: pppBundle.performance.h2Performance.ifStatusChanges

       32 bit unsigned wrappable counter."
   ::= {pr1645v2PppBFInPEntry 50331648}

pr1645v2PppBFInPIfInOctets OBJECT-TYPE
   SYNTAX      Counter64
   MAX-ACCESS  read-only
   STATUS      current
   DESCRIPTION
      "Path: pppBundle.performance.h2Performance.ifInOctets

       64 bit unsigned wrappable counter."
   ::= {pr1645v2PppBFInPEntry 67108864}

pr1645v2PppBFInPIfInUCPkts OBJECT-TYPE
   SYNTAX      Counter64
   MAX-ACCESS  read-only
   STATUS      current
   DESCRIPTION
      "Path: pppBundle.performance.h2Performance.ifInUcastPkts

       64 bit unsigned wrappable counter."
   ::= {pr1645v2PppBFInPEntry 83886080}

pr1645v2PppBFInPIfInNUCPkts OBJECT-TYPE
   SYNTAX      Counter64
   MAX-ACCESS  read-only
   STATUS      current
   DESCRIPTION
      "Path: pppBundle.performance.h2Performance.ifInNUcastPkts

       64 bit unsigned wrappable counter."
   ::= {pr1645v2PppBFInPEntry 100663296}

pr1645v2PppBFInPIfInBCPkts OBJECT-TYPE
   SYNTAX      Counter64
   MAX-ACCESS  read-only
   STATUS      current
   DESCRIPTION
      "Path: pppBundle.performance.h2Performance.ifInBcastPkts

       64 bit unsigned wrappable counter."
   ::= {pr1645v2PppBFInPEntry 419430400}

pr1645v2PppBFInPIfInMCPkts OBJECT-TYPE
   SYNTAX      Counter64
   MAX-ACCESS  read-only
   STATUS      current
   DESCRIPTION
      "Path: pppBundle.performance.h2Performance.ifInMcastPkts

       64 bit unsigned wrappable counter."
   ::= {pr1645v2PppBFInPEntry 436207616}

pr1645v2PppBFInPIfInDiscards OBJECT-TYPE
   SYNTAX      Counter64
   MAX-ACCESS  read-only
   STATUS      current
   DESCRIPTION
      "Path: pppBundle.performance.h2Performance.ifInDiscards

       64 bit unsigned wrappable counter."
   ::= {pr1645v2PppBFInPEntry 117440512}

pr1645v2PppBFInPIfInErrors OBJECT-TYPE
   SYNTAX      Counter64
   MAX-ACCESS  read-only
   STATUS      current
   DESCRIPTION
      "Path: pppBundle.performance.h2Performance.ifInErrors

       64 bit unsigned wrappable counter."
   ::= {pr1645v2PppBFInPEntry 134217728}

pr1645v2PppBFInPIfInUnkwn OBJECT-TYPE
   SYNTAX      Counter64
   MAX-ACCESS  read-only
   STATUS      current
   DESCRIPTION
      "Path: pppBundle.performance.h2Performance.ifInUnknownProtos

       64 bit unsigned wrappable counter."
   ::= {pr1645v2PppBFInPEntry 150994944}

pr1645v2PppBFInPInDropEx OBJECT-TYPE
   SYNTAX      Counter64
   MAX-ACCESS  read-only
   STATUS      current
   DESCRIPTION
      "Path: pppBundle.performance.h2Performance.ifInDropLevelExceeded

       64 bit unsigned wrappable counter."
   ::= {pr1645v2PppBFInPEntry 335544320}

pr1645v2PppBFInPInDropNoMac OBJECT-TYPE
   SYNTAX      Counter64
   MAX-ACCESS  read-only
   STATUS      current
   DESCRIPTION
      "Path: pppBundle.performance.h2Performance.fInDiscardsNoMacFit

       64 bit unsigned wrappable counter."
   ::= {pr1645v2PppBFInPEntry 301989888}

pr1645v2PppBFInPInDropNUCast OBJECT-TYPE
   SYNTAX      Counter64
   MAX-ACCESS  read-only
   STATUS      current
   DESCRIPTION
      "Path: pppBundle.performance.h2Performance.fInDiscardsNUCast

       64 bit unsigned wrappable counter."
   ::= {pr1645v2PppBFInPEntry 318767104}

pr1645v2PppBFInPInDropFilter OBJECT-TYPE
   SYNTAX      Counter64
   MAX-ACCESS  read-only
   STATUS      current
   DESCRIPTION
      "Path: pppBundle.performance.h2Performance.fInDiscardsFilter

       64 bit unsigned wrappable counter."
   ::= {pr1645v2PppBFInPEntry 385875968}

pr1645v2PppBFInPIfInBandwidth OBJECT-TYPE
   SYNTAX      Integer32
   MAX-ACCESS  read-only
   STATUS      current
   DESCRIPTION
      "Path: pppBundle.performance.h2Performance.ifInBandwidth

       unit name = bps
       formula = 8 * ; 8 /"
   ::= {pr1645v2PppBFInPEntry 268435456}

pr1645v2PppBFInPIfOutOctets OBJECT-TYPE
   SYNTAX      Counter64
   MAX-ACCESS  read-only
   STATUS      current
   DESCRIPTION
      "Path: pppBundle.performance.h2Performance.ifOutOctets

       64 bit unsigned wrappable counter."
   ::= {pr1645v2PppBFInPEntry 167772160}

pr1645v2PppBFInPIfOutUCPkts OBJECT-TYPE
   SYNTAX      Counter64
   MAX-ACCESS  read-only
   STATUS      current
   DESCRIPTION
      "Path: pppBundle.performance.h2Performance.ifOutUcastPkts

       64 bit unsigned wrappable counter."
   ::= {pr1645v2PppBFInPEntry 184549376}

pr1645v2PppBFInPIfOutNUCPkts OBJECT-TYPE
   SYNTAX      Counter64
   MAX-ACCESS  read-only
   STATUS      current
   DESCRIPTION
      "Path: pppBundle.performance.h2Performance.ifOutNUcastPkts

       64 bit unsigned wrappable counter."
   ::= {pr1645v2PppBFInPEntry 201326592}

pr1645v2PppBFInPIfOutBCPkts OBJECT-TYPE
   SYNTAX      Counter64
   MAX-ACCESS  read-only
   STATUS      current
   DESCRIPTION
      "Path: pppBundle.performance.h2Performance.ifOutBcastPkts

       64 bit unsigned wrappable counter."
   ::= {pr1645v2PppBFInPEntry 452984832}

pr1645v2PppBFInPIfOutMCPkts OBJECT-TYPE
   SYNTAX      Counter64
   MAX-ACCESS  read-only
   STATUS      current
   DESCRIPTION
      "Path: pppBundle.performance.h2Performance.ifOutMcastPkts

       64 bit unsigned wrappable counter."
   ::= {pr1645v2PppBFInPEntry 469762048}

pr1645v2PppBFInPIfOutDiscards OBJECT-TYPE
   SYNTAX      Counter64
   MAX-ACCESS  read-only
   STATUS      current
   DESCRIPTION
      "Path: pppBundle.performance.h2Performance.ifOutDiscards

       64 bit unsigned wrappable counter."
   ::= {pr1645v2PppBFInPEntry 218103808}

pr1645v2PppBFInPIfOutErrors OBJECT-TYPE
   SYNTAX      Counter64
   MAX-ACCESS  read-only
   STATUS      current
   DESCRIPTION
      "Path: pppBundle.performance.h2Performance.ifOutErrors

       64 bit unsigned wrappable counter."
   ::= {pr1645v2PppBFInPEntry 234881024}

pr1645v2PppBFInPOutDropEx OBJECT-TYPE
   SYNTAX      Counter64
   MAX-ACCESS  read-only
   STATUS      current
   DESCRIPTION
      "Path: pppBundle.performance.h2Performance.ifOutDropLevelExceeded

       64 bit unsigned wrappable counter."
   ::= {pr1645v2PppBFInPEntry 352321536}

pr1645v2PppBFInPOutDropNoArp OBJECT-TYPE
   SYNTAX      Counter64
   MAX-ACCESS  read-only
   STATUS      current
   DESCRIPTION
      "Path: pppBundle.performance.h2Performance.ifOutDiscardsNoArp

       64 bit unsigned wrappable counter."
   ::= {pr1645v2PppBFInPEntry 369098752}

pr1645v2PppBFInPOutDropFilter OBJECT-TYPE
   SYNTAX      Counter64
   MAX-ACCESS  read-only
   STATUS      current
   DESCRIPTION
      "Path: pppBundle.performance.h2Performance.ifOutDiscardsFilter

       64 bit unsigned wrappable counter."
   ::= {pr1645v2PppBFInPEntry 402653184}

pr1645v2PppBFInPIfOutBandwidth OBJECT-TYPE
   SYNTAX      Integer32
   MAX-ACCESS  read-only
   STATUS      current
   DESCRIPTION
      "Path: pppBundle.performance.h2Performance.ifOutBandwidth

       unit name = bps
       formula = 8 * ; 8 /"
   ::= {pr1645v2PppBFInPEntry 285212672}

pr1645v2PppBFInPIfErrSec OBJECT-TYPE
   SYNTAX      Counter32
   MAX-ACCESS  read-only
   STATUS      current
   DESCRIPTION
      "Path: pppBundle.performance.h2Performance.ifErrSec

       32 bit unsigned wrappable counter."
   ::= {pr1645v2PppBFInPEntry 251658240}


pr1645v2PppBFH24InP OBJECT IDENTIFIER ::= {pr1645v2PppBF 308}

pr1645v2PppBFH24InPSSCTable OBJECT-TYPE
   SYNTAX      SEQUENCE OF Pr1645v2PppBFH24InPEntry
   MAX-ACCESS  not-accessible
   STATUS      current
   DESCRIPTION
      "h24IfInPerformance"
   ::= {pr1645v2PppBFH24InP 1}

pr1645v2PppBFH24InPEntry OBJECT-TYPE
   SYNTAX      Pr1645v2PppBFH24InPEntry
   MAX-ACCESS  not-accessible
   STATUS      current
   DESCRIPTION
      ""
   INDEX      { pr1645v2PppBFH24InPGlobalIx,
                pr1645v2PppBFH24InPTableIx }
   ::= {pr1645v2PppBFH24InPSSCTable 1}

Pr1645v2PppBFH24InPEntry ::=
   SEQUENCE
      {
      pr1645v2PppBFH24InPGlobalIx
         GlobalIndex,
      pr1645v2PppBFH24InPTableIx
         TableIndex,
      pr1645v2PppBFH24InPSysUpTime
         TimeTicks,
      pr1645v2PppBFH24InPIfUpTime
         TimeTicks,
      pr1645v2PppBFH24InPIfStatChanges
         Counter32,
      pr1645v2PppBFH24InPIfInOctets
         Counter64,
      pr1645v2PppBFH24InPIfInUCPkts
         Counter64,
      pr1645v2PppBFH24InPIfInNUCPkts
         Counter64,
      pr1645v2PppBFH24InPIfInBCPkts
         Counter64,
      pr1645v2PppBFH24InPIfInMCPkts
         Counter64,
      pr1645v2PppBFH24InPIfInDiscards
         Counter64,
      pr1645v2PppBFH24InPIfInErrors
         Counter64,
      pr1645v2PppBFH24InPIfInUnkwn
         Counter64,
      pr1645v2PppBFH24InPInDropEx
         Counter64,
      pr1645v2PppBFH24InPInDropNoMac
         Counter64,
      pr1645v2PppBFH24InPInDropNUCast
         Counter64,
      pr1645v2PppBFH24InPInDropFilter
         Counter64,
      pr1645v2PppBFH24InPIfInBandwidth
         Integer32,
      pr1645v2PppBFH24InPIfOutOctets
         Counter64,
      pr1645v2PppBFH24InPIfOutUCPkts
         Counter64,
      pr1645v2PppBFH24InPIfOutNUCPkts
         Counter64,
      pr1645v2PppBFH24InPIfOutBCPkts
         Counter64,
      pr1645v2PppBFH24InPIfOutMCPkts
         Counter64,
      pr1645v2PppBFH24InPIfOutDiscards
         Counter64,
      pr1645v2PppBFH24InPIfOutErrors
         Counter64,
      pr1645v2PppBFH24InPOutDropEx
         Counter64,
      pr1645v2PppBFH24InPOutDropNoArp
         Counter64,
      pr1645v2PppBFH24InPOutDropFilter
         Counter64,
      pr1645v2PppBFH24InPIfOutBandwidth
         Integer32,
      pr1645v2PppBFH24InPIfErrSec
         Counter32
      }

pr1645v2PppBFH24InPGlobalIx OBJECT-TYPE
   SYNTAX      GlobalIndex
   MAX-ACCESS  not-accessible
   STATUS      current
   DESCRIPTION
      "The value of the tlsCntTreeGlobalIndex of the MANAGED OBJECT."
   ::= {pr1645v2PppBFH24InPEntry 10}

pr1645v2PppBFH24InPTableIx OBJECT-TYPE
   SYNTAX      TableIndex
   MAX-ACCESS  not-accessible
   STATUS      current
   DESCRIPTION
      ""
   ::= {pr1645v2PppBFH24InPEntry 11}

pr1645v2PppBFH24InPSysUpTime OBJECT-TYPE
   SYNTAX      TimeTicks
   MAX-ACCESS  read-only
   STATUS      current
   DESCRIPTION
      "Path: pppBundle.performance.h24Performance.sysUpTime

       Time in centi-second."
   ::= {pr1645v2PppBFH24InPEntry 16777216}

pr1645v2PppBFH24InPIfUpTime OBJECT-TYPE
   SYNTAX      TimeTicks
   MAX-ACCESS  read-only
   STATUS      current
   DESCRIPTION
      "Path: pppBundle.performance.h24Performance.ifUpTime

       Time in centi-second."
   ::= {pr1645v2PppBFH24InPEntry 33554432}

pr1645v2PppBFH24InPIfStatChanges OBJECT-TYPE
   SYNTAX      Counter32
   MAX-ACCESS  read-only
   STATUS      current
   DESCRIPTION
      "Path: pppBundle.performance.h24Performance.ifStatusChanges

       32 bit unsigned wrappable counter."
   ::= {pr1645v2PppBFH24InPEntry 50331648}

pr1645v2PppBFH24InPIfInOctets OBJECT-TYPE
   SYNTAX      Counter64
   MAX-ACCESS  read-only
   STATUS      current
   DESCRIPTION
      "Path: pppBundle.performance.h24Performance.ifInOctets

       64 bit unsigned wrappable counter."
   ::= {pr1645v2PppBFH24InPEntry 67108864}

pr1645v2PppBFH24InPIfInUCPkts OBJECT-TYPE
   SYNTAX      Counter64
   MAX-ACCESS  read-only
   STATUS      current
   DESCRIPTION
      "Path: pppBundle.performance.h24Performance.ifInUcastPkts

       64 bit unsigned wrappable counter."
   ::= {pr1645v2PppBFH24InPEntry 83886080}

pr1645v2PppBFH24InPIfInNUCPkts OBJECT-TYPE
   SYNTAX      Counter64
   MAX-ACCESS  read-only
   STATUS      current
   DESCRIPTION
      "Path: pppBundle.performance.h24Performance.ifInNUcastPkts

       64 bit unsigned wrappable counter."
   ::= {pr1645v2PppBFH24InPEntry 100663296}

pr1645v2PppBFH24InPIfInBCPkts OBJECT-TYPE
   SYNTAX      Counter64
   MAX-ACCESS  read-only
   STATUS      current
   DESCRIPTION
      "Path: pppBundle.performance.h24Performance.ifInBcastPkts

       64 bit unsigned wrappable counter."
   ::= {pr1645v2PppBFH24InPEntry 419430400}

pr1645v2PppBFH24InPIfInMCPkts OBJECT-TYPE
   SYNTAX      Counter64
   MAX-ACCESS  read-only
   STATUS      current
   DESCRIPTION
      "Path: pppBundle.performance.h24Performance.ifInMcastPkts

       64 bit unsigned wrappable counter."
   ::= {pr1645v2PppBFH24InPEntry 436207616}

pr1645v2PppBFH24InPIfInDiscards OBJECT-TYPE
   SYNTAX      Counter64
   MAX-ACCESS  read-only
   STATUS      current
   DESCRIPTION
      "Path: pppBundle.performance.h24Performance.ifInDiscards

       64 bit unsigned wrappable counter."
   ::= {pr1645v2PppBFH24InPEntry 117440512}

pr1645v2PppBFH24InPIfInErrors OBJECT-TYPE
   SYNTAX      Counter64
   MAX-ACCESS  read-only
   STATUS      current
   DESCRIPTION
      "Path: pppBundle.performance.h24Performance.ifInErrors

       64 bit unsigned wrappable counter."
   ::= {pr1645v2PppBFH24InPEntry 134217728}

pr1645v2PppBFH24InPIfInUnkwn OBJECT-TYPE
   SYNTAX      Counter64
   MAX-ACCESS  read-only
   STATUS      current
   DESCRIPTION
      "Path: pppBundle.performance.h24Performance.ifInUnknownProtos

       64 bit unsigned wrappable counter."
   ::= {pr1645v2PppBFH24InPEntry 150994944}

pr1645v2PppBFH24InPInDropEx OBJECT-TYPE
   SYNTAX      Counter64
   MAX-ACCESS  read-only
   STATUS      current
   DESCRIPTION
      "Path: pppBundle.performance.h24Performance.ifInDropLevelExceeded

       64 bit unsigned wrappable counter."
   ::= {pr1645v2PppBFH24InPEntry 335544320}

pr1645v2PppBFH24InPInDropNoMac OBJECT-TYPE
   SYNTAX      Counter64
   MAX-ACCESS  read-only
   STATUS      current
   DESCRIPTION
      "Path: pppBundle.performance.h24Performance.fInDiscardsNoMacFit

       64 bit unsigned wrappable counter."
   ::= {pr1645v2PppBFH24InPEntry 301989888}

pr1645v2PppBFH24InPInDropNUCast OBJECT-TYPE
   SYNTAX      Counter64
   MAX-ACCESS  read-only
   STATUS      current
   DESCRIPTION
      "Path: pppBundle.performance.h24Performance.fInDiscardsNUCast

       64 bit unsigned wrappable counter."
   ::= {pr1645v2PppBFH24InPEntry 318767104}

pr1645v2PppBFH24InPInDropFilter OBJECT-TYPE
   SYNTAX      Counter64
   MAX-ACCESS  read-only
   STATUS      current
   DESCRIPTION
      "Path: pppBundle.performance.h24Performance.fInDiscardsFilter

       64 bit unsigned wrappable counter."
   ::= {pr1645v2PppBFH24InPEntry 385875968}

pr1645v2PppBFH24InPIfInBandwidth OBJECT-TYPE
   SYNTAX      Integer32
   MAX-ACCESS  read-only
   STATUS      current
   DESCRIPTION
      "Path: pppBundle.performance.h24Performance.ifInBandwidth

       unit name = bps
       formula = 8 * ; 8 /"
   ::= {pr1645v2PppBFH24InPEntry 268435456}

pr1645v2PppBFH24InPIfOutOctets OBJECT-TYPE
   SYNTAX      Counter64
   MAX-ACCESS  read-only
   STATUS      current
   DESCRIPTION
      "Path: pppBundle.performance.h24Performance.ifOutOctets

       64 bit unsigned wrappable counter."
   ::= {pr1645v2PppBFH24InPEntry 167772160}

pr1645v2PppBFH24InPIfOutUCPkts OBJECT-TYPE
   SYNTAX      Counter64
   MAX-ACCESS  read-only
   STATUS      current
   DESCRIPTION
      "Path: pppBundle.performance.h24Performance.ifOutUcastPkts

       64 bit unsigned wrappable counter."
   ::= {pr1645v2PppBFH24InPEntry 184549376}

pr1645v2PppBFH24InPIfOutNUCPkts OBJECT-TYPE
   SYNTAX      Counter64
   MAX-ACCESS  read-only
   STATUS      current
   DESCRIPTION
      "Path: pppBundle.performance.h24Performance.ifOutNUcastPkts

       64 bit unsigned wrappable counter."
   ::= {pr1645v2PppBFH24InPEntry 201326592}

pr1645v2PppBFH24InPIfOutBCPkts OBJECT-TYPE
   SYNTAX      Counter64
   MAX-ACCESS  read-only
   STATUS      current
   DESCRIPTION
      "Path: pppBundle.performance.h24Performance.ifOutBcastPkts

       64 bit unsigned wrappable counter."
   ::= {pr1645v2PppBFH24InPEntry 452984832}

pr1645v2PppBFH24InPIfOutMCPkts OBJECT-TYPE
   SYNTAX      Counter64
   MAX-ACCESS  read-only
   STATUS      current
   DESCRIPTION
      "Path: pppBundle.performance.h24Performance.ifOutMcastPkts

       64 bit unsigned wrappable counter."
   ::= {pr1645v2PppBFH24InPEntry 469762048}

pr1645v2PppBFH24InPIfOutDiscards OBJECT-TYPE
   SYNTAX      Counter64
   MAX-ACCESS  read-only
   STATUS      current
   DESCRIPTION
      "Path: pppBundle.performance.h24Performance.ifOutDiscards

       64 bit unsigned wrappable counter."
   ::= {pr1645v2PppBFH24InPEntry 218103808}

pr1645v2PppBFH24InPIfOutErrors OBJECT-TYPE
   SYNTAX      Counter64
   MAX-ACCESS  read-only
   STATUS      current
   DESCRIPTION
      "Path: pppBundle.performance.h24Performance.ifOutErrors

       64 bit unsigned wrappable counter."
   ::= {pr1645v2PppBFH24InPEntry 234881024}

pr1645v2PppBFH24InPOutDropEx OBJECT-TYPE
   SYNTAX      Counter64
   MAX-ACCESS  read-only
   STATUS      current
   DESCRIPTION
      "Path: pppBundle.performance.h24Performance.ifOutDropLevelExceeded

       64 bit unsigned wrappable counter."
   ::= {pr1645v2PppBFH24InPEntry 352321536}

pr1645v2PppBFH24InPOutDropNoArp OBJECT-TYPE
   SYNTAX      Counter64
   MAX-ACCESS  read-only
   STATUS      current
   DESCRIPTION
      "Path: pppBundle.performance.h24Performance.ifOutDiscardsNoArp

       64 bit unsigned wrappable counter."
   ::= {pr1645v2PppBFH24InPEntry 369098752}

pr1645v2PppBFH24InPOutDropFilter OBJECT-TYPE
   SYNTAX      Counter64
   MAX-ACCESS  read-only
   STATUS      current
   DESCRIPTION
      "Path: pppBundle.performance.h24Performance.ifOutDiscardsFilter

       64 bit unsigned wrappable counter."
   ::= {pr1645v2PppBFH24InPEntry 402653184}

pr1645v2PppBFH24InPIfOutBandwidth OBJECT-TYPE
   SYNTAX      Integer32
   MAX-ACCESS  read-only
   STATUS      current
   DESCRIPTION
      "Path: pppBundle.performance.h24Performance.ifOutBandwidth

       unit name = bps
       formula = 8 * ; 8 /"
   ::= {pr1645v2PppBFH24InPEntry 285212672}

pr1645v2PppBFH24InPIfErrSec OBJECT-TYPE
   SYNTAX      Counter32
   MAX-ACCESS  read-only
   STATUS      current
   DESCRIPTION
      "Path: pppBundle.performance.h24Performance.ifErrSec

       32 bit unsigned wrappable counter."
   ::= {pr1645v2PppBFH24InPEntry 251658240}


pr1645v2PppBFD7InP OBJECT IDENTIFIER ::= {pr1645v2PppBF 309}

pr1645v2PppBFD7InPSSCTable OBJECT-TYPE
   SYNTAX      SEQUENCE OF Pr1645v2PppBFD7InPEntry
   MAX-ACCESS  not-accessible
   STATUS      current
   DESCRIPTION
      "d7IfInPerformance"
   ::= {pr1645v2PppBFD7InP 1}

pr1645v2PppBFD7InPEntry OBJECT-TYPE
   SYNTAX      Pr1645v2PppBFD7InPEntry
   MAX-ACCESS  not-accessible
   STATUS      current
   DESCRIPTION
      ""
   INDEX      { pr1645v2PppBFD7InPGlobalIx,
                pr1645v2PppBFD7InPTableIx }
   ::= {pr1645v2PppBFD7InPSSCTable 1}

Pr1645v2PppBFD7InPEntry ::=
   SEQUENCE
      {
      pr1645v2PppBFD7InPGlobalIx
         GlobalIndex,
      pr1645v2PppBFD7InPTableIx
         TableIndex,
      pr1645v2PppBFD7InPSysUpTime
         TimeTicks,
      pr1645v2PppBFD7InPIfUpTime
         TimeTicks,
      pr1645v2PppBFD7InPIfStatChanges
         Counter32,
      pr1645v2PppBFD7InPIfInOctets
         Counter64,
      pr1645v2PppBFD7InPIfInUCPkts
         Counter64,
      pr1645v2PppBFD7InPIfInNUCPkts
         Counter64,
      pr1645v2PppBFD7InPIfInBCPkts
         Counter64,
      pr1645v2PppBFD7InPIfInMCPkts
         Counter64,
      pr1645v2PppBFD7InPIfInDiscards
         Counter64,
      pr1645v2PppBFD7InPIfInErrors
         Counter64,
      pr1645v2PppBFD7InPIfInUnkwn
         Counter64,
      pr1645v2PppBFD7InPInDropEx
         Counter64,
      pr1645v2PppBFD7InPInDropNoMac
         Counter64,
      pr1645v2PppBFD7InPInDropNUCast
         Counter64,
      pr1645v2PppBFD7InPInDropFilter
         Counter64,
      pr1645v2PppBFD7InPIfInBandwidth
         Integer32,
      pr1645v2PppBFD7InPIfOutOctets
         Counter64,
      pr1645v2PppBFD7InPIfOutUCPkts
         Counter64,
      pr1645v2PppBFD7InPIfOutNUCPkts
         Counter64,
      pr1645v2PppBFD7InPIfOutBCPkts
         Counter64,
      pr1645v2PppBFD7InPIfOutMCPkts
         Counter64,
      pr1645v2PppBFD7InPIfOutDiscards
         Counter64,
      pr1645v2PppBFD7InPIfOutErrors
         Counter64,
      pr1645v2PppBFD7InPOutDropEx
         Counter64,
      pr1645v2PppBFD7InPOutDropNoArp
         Counter64,
      pr1645v2PppBFD7InPOutDropFilter
         Counter64,
      pr1645v2PppBFD7InPIfOutBandwidth
         Integer32,
      pr1645v2PppBFD7InPIfErrSec
         Counter32
      }

pr1645v2PppBFD7InPGlobalIx OBJECT-TYPE
   SYNTAX      GlobalIndex
   MAX-ACCESS  not-accessible
   STATUS      current
   DESCRIPTION
      "The value of the tlsCntTreeGlobalIndex of the MANAGED OBJECT."
   ::= {pr1645v2PppBFD7InPEntry 10}

pr1645v2PppBFD7InPTableIx OBJECT-TYPE
   SYNTAX      TableIndex
   MAX-ACCESS  not-accessible
   STATUS      current
   DESCRIPTION
      ""
   ::= {pr1645v2PppBFD7InPEntry 11}

pr1645v2PppBFD7InPSysUpTime OBJECT-TYPE
   SYNTAX      TimeTicks
   MAX-ACCESS  read-only
   STATUS      current
   DESCRIPTION
      "Path: pppBundle.performance.d7Performance.sysUpTime

       Time in centi-second."
   ::= {pr1645v2PppBFD7InPEntry 16777216}

pr1645v2PppBFD7InPIfUpTime OBJECT-TYPE
   SYNTAX      TimeTicks
   MAX-ACCESS  read-only
   STATUS      current
   DESCRIPTION
      "Path: pppBundle.performance.d7Performance.ifUpTime

       Time in centi-second."
   ::= {pr1645v2PppBFD7InPEntry 33554432}

pr1645v2PppBFD7InPIfStatChanges OBJECT-TYPE
   SYNTAX      Counter32
   MAX-ACCESS  read-only
   STATUS      current
   DESCRIPTION
      "Path: pppBundle.performance.d7Performance.ifStatusChanges

       32 bit unsigned wrappable counter."
   ::= {pr1645v2PppBFD7InPEntry 50331648}

pr1645v2PppBFD7InPIfInOctets OBJECT-TYPE
   SYNTAX      Counter64
   MAX-ACCESS  read-only
   STATUS      current
   DESCRIPTION
      "Path: pppBundle.performance.d7Performance.ifInOctets

       64 bit unsigned wrappable counter."
   ::= {pr1645v2PppBFD7InPEntry 67108864}

pr1645v2PppBFD7InPIfInUCPkts OBJECT-TYPE
   SYNTAX      Counter64
   MAX-ACCESS  read-only
   STATUS      current
   DESCRIPTION
      "Path: pppBundle.performance.d7Performance.ifInUcastPkts

       64 bit unsigned wrappable counter."
   ::= {pr1645v2PppBFD7InPEntry 83886080}

pr1645v2PppBFD7InPIfInNUCPkts OBJECT-TYPE
   SYNTAX      Counter64
   MAX-ACCESS  read-only
   STATUS      current
   DESCRIPTION
      "Path: pppBundle.performance.d7Performance.ifInNUcastPkts

       64 bit unsigned wrappable counter."
   ::= {pr1645v2PppBFD7InPEntry 100663296}

pr1645v2PppBFD7InPIfInBCPkts OBJECT-TYPE
   SYNTAX      Counter64
   MAX-ACCESS  read-only
   STATUS      current
   DESCRIPTION
      "Path: pppBundle.performance.d7Performance.ifInBcastPkts

       64 bit unsigned wrappable counter."
   ::= {pr1645v2PppBFD7InPEntry 419430400}

pr1645v2PppBFD7InPIfInMCPkts OBJECT-TYPE
   SYNTAX      Counter64
   MAX-ACCESS  read-only
   STATUS      current
   DESCRIPTION
      "Path: pppBundle.performance.d7Performance.ifInMcastPkts

       64 bit unsigned wrappable counter."
   ::= {pr1645v2PppBFD7InPEntry 436207616}

pr1645v2PppBFD7InPIfInDiscards OBJECT-TYPE
   SYNTAX      Counter64
   MAX-ACCESS  read-only
   STATUS      current
   DESCRIPTION
      "Path: pppBundle.performance.d7Performance.ifInDiscards

       64 bit unsigned wrappable counter."
   ::= {pr1645v2PppBFD7InPEntry 117440512}

pr1645v2PppBFD7InPIfInErrors OBJECT-TYPE
   SYNTAX      Counter64
   MAX-ACCESS  read-only
   STATUS      current
   DESCRIPTION
      "Path: pppBundle.performance.d7Performance.ifInErrors

       64 bit unsigned wrappable counter."
   ::= {pr1645v2PppBFD7InPEntry 134217728}

pr1645v2PppBFD7InPIfInUnkwn OBJECT-TYPE
   SYNTAX      Counter64
   MAX-ACCESS  read-only
   STATUS      current
   DESCRIPTION
      "Path: pppBundle.performance.d7Performance.ifInUnknownProtos

       64 bit unsigned wrappable counter."
   ::= {pr1645v2PppBFD7InPEntry 150994944}

pr1645v2PppBFD7InPInDropEx OBJECT-TYPE
   SYNTAX      Counter64
   MAX-ACCESS  read-only
   STATUS      current
   DESCRIPTION
      "Path: pppBundle.performance.d7Performance.ifInDropLevelExceeded

       64 bit unsigned wrappable counter."
   ::= {pr1645v2PppBFD7InPEntry 335544320}

pr1645v2PppBFD7InPInDropNoMac OBJECT-TYPE
   SYNTAX      Counter64
   MAX-ACCESS  read-only
   STATUS      current
   DESCRIPTION
      "Path: pppBundle.performance.d7Performance.fInDiscardsNoMacFit

       64 bit unsigned wrappable counter."
   ::= {pr1645v2PppBFD7InPEntry 301989888}

pr1645v2PppBFD7InPInDropNUCast OBJECT-TYPE
   SYNTAX      Counter64
   MAX-ACCESS  read-only
   STATUS      current
   DESCRIPTION
      "Path: pppBundle.performance.d7Performance.fInDiscardsNUCast

       64 bit unsigned wrappable counter."
   ::= {pr1645v2PppBFD7InPEntry 318767104}

pr1645v2PppBFD7InPInDropFilter OBJECT-TYPE
   SYNTAX      Counter64
   MAX-ACCESS  read-only
   STATUS      current
   DESCRIPTION
      "Path: pppBundle.performance.d7Performance.fInDiscardsFilter

       64 bit unsigned wrappable counter."
   ::= {pr1645v2PppBFD7InPEntry 385875968}

pr1645v2PppBFD7InPIfInBandwidth OBJECT-TYPE
   SYNTAX      Integer32
   MAX-ACCESS  read-only
   STATUS      current
   DESCRIPTION
      "Path: pppBundle.performance.d7Performance.ifInBandwidth

       unit name = bps
       formula = 8 * ; 8 /"
   ::= {pr1645v2PppBFD7InPEntry 268435456}

pr1645v2PppBFD7InPIfOutOctets OBJECT-TYPE
   SYNTAX      Counter64
   MAX-ACCESS  read-only
   STATUS      current
   DESCRIPTION
      "Path: pppBundle.performance.d7Performance.ifOutOctets

       64 bit unsigned wrappable counter."
   ::= {pr1645v2PppBFD7InPEntry 167772160}

pr1645v2PppBFD7InPIfOutUCPkts OBJECT-TYPE
   SYNTAX      Counter64
   MAX-ACCESS  read-only
   STATUS      current
   DESCRIPTION
      "Path: pppBundle.performance.d7Performance.ifOutUcastPkts

       64 bit unsigned wrappable counter."
   ::= {pr1645v2PppBFD7InPEntry 184549376}

pr1645v2PppBFD7InPIfOutNUCPkts OBJECT-TYPE
   SYNTAX      Counter64
   MAX-ACCESS  read-only
   STATUS      current
   DESCRIPTION
      "Path: pppBundle.performance.d7Performance.ifOutNUcastPkts

       64 bit unsigned wrappable counter."
   ::= {pr1645v2PppBFD7InPEntry 201326592}

pr1645v2PppBFD7InPIfOutBCPkts OBJECT-TYPE
   SYNTAX      Counter64
   MAX-ACCESS  read-only
   STATUS      current
   DESCRIPTION
      "Path: pppBundle.performance.d7Performance.ifOutBcastPkts

       64 bit unsigned wrappable counter."
   ::= {pr1645v2PppBFD7InPEntry 452984832}

pr1645v2PppBFD7InPIfOutMCPkts OBJECT-TYPE
   SYNTAX      Counter64
   MAX-ACCESS  read-only
   STATUS      current
   DESCRIPTION
      "Path: pppBundle.performance.d7Performance.ifOutMcastPkts

       64 bit unsigned wrappable counter."
   ::= {pr1645v2PppBFD7InPEntry 469762048}

pr1645v2PppBFD7InPIfOutDiscards OBJECT-TYPE
   SYNTAX      Counter64
   MAX-ACCESS  read-only
   STATUS      current
   DESCRIPTION
      "Path: pppBundle.performance.d7Performance.ifOutDiscards

       64 bit unsigned wrappable counter."
   ::= {pr1645v2PppBFD7InPEntry 218103808}

pr1645v2PppBFD7InPIfOutErrors OBJECT-TYPE
   SYNTAX      Counter64
   MAX-ACCESS  read-only
   STATUS      current
   DESCRIPTION
      "Path: pppBundle.performance.d7Performance.ifOutErrors

       64 bit unsigned wrappable counter."
   ::= {pr1645v2PppBFD7InPEntry 234881024}

pr1645v2PppBFD7InPOutDropEx OBJECT-TYPE
   SYNTAX      Counter64
   MAX-ACCESS  read-only
   STATUS      current
   DESCRIPTION
      "Path: pppBundle.performance.d7Performance.ifOutDropLevelExceeded

       64 bit unsigned wrappable counter."
   ::= {pr1645v2PppBFD7InPEntry 352321536}

pr1645v2PppBFD7InPOutDropNoArp OBJECT-TYPE
   SYNTAX      Counter64
   MAX-ACCESS  read-only
   STATUS      current
   DESCRIPTION
      "Path: pppBundle.performance.d7Performance.ifOutDiscardsNoArp

       64 bit unsigned wrappable counter."
   ::= {pr1645v2PppBFD7InPEntry 369098752}

pr1645v2PppBFD7InPOutDropFilter OBJECT-TYPE
   SYNTAX      Counter64
   MAX-ACCESS  read-only
   STATUS      current
   DESCRIPTION
      "Path: pppBundle.performance.d7Performance.ifOutDiscardsFilter

       64 bit unsigned wrappable counter."
   ::= {pr1645v2PppBFD7InPEntry 402653184}

pr1645v2PppBFD7InPIfOutBandwidth OBJECT-TYPE
   SYNTAX      Integer32
   MAX-ACCESS  read-only
   STATUS      current
   DESCRIPTION
      "Path: pppBundle.performance.d7Performance.ifOutBandwidth

       unit name = bps
       formula = 8 * ; 8 /"
   ::= {pr1645v2PppBFD7InPEntry 285212672}

pr1645v2PppBFD7InPIfErrSec OBJECT-TYPE
   SYNTAX      Counter32
   MAX-ACCESS  read-only
   STATUS      current
   DESCRIPTION
      "Path: pppBundle.performance.d7Performance.ifErrSec

       32 bit unsigned wrappable counter."
   ::= {pr1645v2PppBFD7InPEntry 251658240}


pr1645v2PppBFPerf OBJECT IDENTIFIER ::= {pr1645v2PppBF 29}

pr1645v2PppBFPerfSSCTable OBJECT-TYPE
   SYNTAX      SEQUENCE OF Pr1645v2PppBFPerfEntry
   MAX-ACCESS  not-accessible
   STATUS      current
   DESCRIPTION
      ""
   ::= {pr1645v2PppBFPerf 1}

pr1645v2PppBFPerfEntry OBJECT-TYPE
   SYNTAX      Pr1645v2PppBFPerfEntry
   MAX-ACCESS  not-accessible
   STATUS      current
   DESCRIPTION
      ""
   INDEX      { pr1645v2PppBFPerfGlobalIx,
                pr1645v2PppBFPerfTableIx }
   ::= {pr1645v2PppBFPerfSSCTable 1}

Pr1645v2PppBFPerfEntry ::=
   SEQUENCE
      {
      pr1645v2PppBFPerfGlobalIx
         GlobalIndex,
      pr1645v2PppBFPerfTableIx
         TableIndex,
      pr1645v2PppBFPerfName
         DisplayString,
      pr1645v2PppBFPerfMCInOctets
         Counter64,
      pr1645v2PppBFPerfMCInUcast
         Counter64,
      pr1645v2PppBFPerfMCInNUcastPkts
         Counter64,
      pr1645v2PppBFPerfMCInBcastPkts
         Counter64,
      pr1645v2PppBFPerfMCInMcastPkts
         Counter64,
      pr1645v2PppBFPerfMCInDiscards
         Counter64,
      pr1645v2PppBFPerfMCInErrors
         Counter64,
      pr1645v2PppBFPerfMCInUnknownProtos
         Counter64,
      pr1645v2PppBFPerfMCInDropEx
         Counter64,
      pr1645v2PppBFPerfMCInDropNoMac
         Counter64,
      pr1645v2PppBFPerfMCInDropNUCast
         Counter64,
      pr1645v2PppBFPerfMCInDropFilter
         Counter64,
      pr1645v2PppBFPerfMCInBandwidth15sec
         Integer32,
      pr1645v2PppBFPerfMCInBandwidth30sec
         Integer32,
      pr1645v2PppBFPerfMCInBandwidth1min
         Integer32,
      pr1645v2PppBFPerfMCInBandwidth2min
         Integer32,
      pr1645v2PppBFPerfMCInBandwidth5min
         Integer32,
      pr1645v2PppBFPerfMCOutOctets
         Counter64,
      pr1645v2PppBFPerfMCOutUcastPkts
         Counter64,
      pr1645v2PppBFPerfMCOutNUcastPkts
         Counter64,
      pr1645v2PppBFPerfMCOutBcastPkts
         Counter64,
      pr1645v2PppBFPerfMCOutMcastPkts
         Counter64,
      pr1645v2PppBFPerfMCOutDiscards
         Counter64,
      pr1645v2PppBFPerfMCOutErrors
         Counter64,
      pr1645v2PppBFPerfMCOutQLen
         Counter32,
      pr1645v2PppBFPerfMCOutDropEx
         Counter64,
      pr1645v2PppBFPerfMCOutDropNoArp
         Counter64,
      pr1645v2PppBFPerfMCOutDropFilter
         Counter64,
      pr1645v2PppBFPerfMCOutBandwidth15sec
         Integer32,
      pr1645v2PppBFPerfMCOutBandwidth30sec
         Integer32,
      pr1645v2PppBFPerfMCOutBandwidth1min
         Integer32,
      pr1645v2PppBFPerfMCOutBandwidth2min
         Integer32,
      pr1645v2PppBFPerfMCOutBandwidth5min
         Integer32
      }

pr1645v2PppBFPerfGlobalIx OBJECT-TYPE
   SYNTAX      GlobalIndex
   MAX-ACCESS  not-accessible
   STATUS      current
   DESCRIPTION
      "The value of the tlsCntTreeGlobalIndex of the MANAGED OBJECT."
   ::= {pr1645v2PppBFPerfEntry 10}

pr1645v2PppBFPerfTableIx OBJECT-TYPE
   SYNTAX      TableIndex
   MAX-ACCESS  not-accessible
   STATUS      current
   DESCRIPTION
      ""
   ::= {pr1645v2PppBFPerfEntry 11}

pr1645v2PppBFPerfName OBJECT-TYPE
   SYNTAX      DisplayString
   MAX-ACCESS  read-only
   STATUS      current
   DESCRIPTION
      "Path: pppBundle.performance.multiclassInterfaces.name"
   ::= {pr1645v2PppBFPerfEntry 16777216}

pr1645v2PppBFPerfMCInOctets OBJECT-TYPE
   SYNTAX      Counter64
   MAX-ACCESS  read-only
   STATUS      current
   DESCRIPTION
      "Path: pppBundle.performance.multiclassInterfaces.mibCounters.ifInOctets

       64 bit unsigned wrappable counter."
   ::= {pr1645v2PppBFPerfEntry 40697856}

pr1645v2PppBFPerfMCInUcast OBJECT-TYPE
   SYNTAX      Counter64
   MAX-ACCESS  read-only
   STATUS      current
   DESCRIPTION
      "Path: pppBundle.performance.multiclassInterfaces.mibCounters.ifInUcastPkts

       64 bit unsigned wrappable counter."
   ::= {pr1645v2PppBFPerfEntry 40763392}

pr1645v2PppBFPerfMCInNUcastPkts OBJECT-TYPE
   SYNTAX      Counter64
   MAX-ACCESS  read-only
   STATUS      current
   DESCRIPTION
      "Path: pppBundle.performance.multiclassInterfaces.mibCounters.ifInNUcastPkts

       64 bit unsigned wrappable counter."
   ::= {pr1645v2PppBFPerfEntry 40828928}

pr1645v2PppBFPerfMCInBcastPkts OBJECT-TYPE
   SYNTAX      Counter64
   MAX-ACCESS  read-only
   STATUS      current
   DESCRIPTION
      "Path: pppBundle.performance.multiclassInterfaces.mibCounters.ifInBcastPkts

       64 bit unsigned wrappable counter."
   ::= {pr1645v2PppBFPerfEntry 47382528}

pr1645v2PppBFPerfMCInMcastPkts OBJECT-TYPE
   SYNTAX      Counter64
   MAX-ACCESS  read-only
   STATUS      current
   DESCRIPTION
      "Path: pppBundle.performance.multiclassInterfaces.mibCounters.ifInMcastPkts

       64 bit unsigned wrappable counter."
   ::= {pr1645v2PppBFPerfEntry 48037888}

pr1645v2PppBFPerfMCInDiscards OBJECT-TYPE
   SYNTAX      Counter64
   MAX-ACCESS  read-only
   STATUS      current
   DESCRIPTION
      "Path: pppBundle.performance.multiclassInterfaces.mibCounters.ifInDiscards

       64 bit unsigned wrappable counter."
   ::= {pr1645v2PppBFPerfEntry 40894464}

pr1645v2PppBFPerfMCInErrors OBJECT-TYPE
   SYNTAX      Counter64
   MAX-ACCESS  read-only
   STATUS      current
   DESCRIPTION
      "Path: pppBundle.performance.multiclassInterfaces.mibCounters.ifInErrors

       64 bit unsigned wrappable counter."
   ::= {pr1645v2PppBFPerfEntry 40960000}

pr1645v2PppBFPerfMCInUnknownProtos OBJECT-TYPE
   SYNTAX      Counter64
   MAX-ACCESS  read-only
   STATUS      current
   DESCRIPTION
      "Path: pppBundle.performance.multiclassInterfaces.mibCounters.ifInUnknownProtos

       64 bit unsigned wrappable counter."
   ::= {pr1645v2PppBFPerfEntry 41025536}

pr1645v2PppBFPerfMCInDropEx OBJECT-TYPE
   SYNTAX      Counter64
   MAX-ACCESS  read-only
   STATUS      current
   DESCRIPTION
      "Path: pppBundle.performance.multiclassInterfaces.mibCounters.ifInDropLevelExceeded

       64 bit unsigned wrappable counter."
   ::= {pr1645v2PppBFPerfEntry 42074112}

pr1645v2PppBFPerfMCInDropNoMac OBJECT-TYPE
   SYNTAX      Counter64
   MAX-ACCESS  read-only
   STATUS      current
   DESCRIPTION
      "Path: pppBundle.performance.multiclassInterfaces.mibCounters.ifInDiscardsNoMacFit

       64 bit unsigned wrappable counter."
   ::= {pr1645v2PppBFPerfEntry 42270720}

pr1645v2PppBFPerfMCInDropNUCast OBJECT-TYPE
   SYNTAX      Counter64
   MAX-ACCESS  read-only
   STATUS      current
   DESCRIPTION
      "Path: pppBundle.performance.multiclassInterfaces.mibCounters.ifInDiscardsNUCast

       64 bit unsigned wrappable counter."
   ::= {pr1645v2PppBFPerfEntry 42467328}

pr1645v2PppBFPerfMCInDropFilter OBJECT-TYPE
   SYNTAX      Counter64
   MAX-ACCESS  read-only
   STATUS      current
   DESCRIPTION
      "Path: pppBundle.performance.multiclassInterfaces.mibCounters.ifInDiscardsFilter

       64 bit unsigned wrappable counter."
   ::= {pr1645v2PppBFPerfEntry 42532864}

pr1645v2PppBFPerfMCInBandwidth15sec OBJECT-TYPE
   SYNTAX      Integer32
   MAX-ACCESS  read-only
   STATUS      current
   DESCRIPTION
      "Path: pppBundle.performance.multiclassInterfaces.mibCounters.ifInBandwidth.15sec

       unit name = bps
       formula = 8 * ; 8 /"
   ::= {pr1645v2PppBFPerfEntry 45417728}

pr1645v2PppBFPerfMCInBandwidth30sec OBJECT-TYPE
   SYNTAX      Integer32
   MAX-ACCESS  read-only
   STATUS      current
   DESCRIPTION
      "Path: pppBundle.performance.multiclassInterfaces.mibCounters.ifInBandwidth.30sec

       unit name = bps
       formula = 8 * ; 8 /"
   ::= {pr1645v2PppBFPerfEntry 45419008}

pr1645v2PppBFPerfMCInBandwidth1min OBJECT-TYPE
   SYNTAX      Integer32
   MAX-ACCESS  read-only
   STATUS      current
   DESCRIPTION
      "Path: pppBundle.performance.multiclassInterfaces.mibCounters.ifInBandwidth.1min

       unit name = bps
       formula = 8 * ; 8 /"
   ::= {pr1645v2PppBFPerfEntry 45421568}

pr1645v2PppBFPerfMCInBandwidth2min OBJECT-TYPE
   SYNTAX      Integer32
   MAX-ACCESS  read-only
   STATUS      current
   DESCRIPTION
      "Path: pppBundle.performance.multiclassInterfaces.mibCounters.ifInBandwidth.2min

       unit name = bps
       formula = 8 * ; 8 /"
   ::= {pr1645v2PppBFPerfEntry 45426688}

pr1645v2PppBFPerfMCInBandwidth5min OBJECT-TYPE
   SYNTAX      Integer32
   MAX-ACCESS  read-only
   STATUS      current
   DESCRIPTION
      "Path: pppBundle.performance.multiclassInterfaces.mibCounters.ifInBandwidth.5min

       unit name = bps
       formula = 8 * ; 8 /"
   ::= {pr1645v2PppBFPerfEntry 45442048}

pr1645v2PppBFPerfMCOutOctets OBJECT-TYPE
   SYNTAX      Counter64
   MAX-ACCESS  read-only
   STATUS      current
   DESCRIPTION
      "Path: pppBundle.performance.multiclassInterfaces.mibCounters.ifOutOctets

       64 bit unsigned wrappable counter."
   ::= {pr1645v2PppBFPerfEntry 41091072}

pr1645v2PppBFPerfMCOutUcastPkts OBJECT-TYPE
   SYNTAX      Counter64
   MAX-ACCESS  read-only
   STATUS      current
   DESCRIPTION
      "Path: pppBundle.performance.multiclassInterfaces.mibCounters.ifOutUcastPkts

       64 bit unsigned wrappable counter."
   ::= {pr1645v2PppBFPerfEntry 41156608}

pr1645v2PppBFPerfMCOutNUcastPkts OBJECT-TYPE
   SYNTAX      Counter64
   MAX-ACCESS  read-only
   STATUS      current
   DESCRIPTION
      "Path: pppBundle.performance.multiclassInterfaces.mibCounters.ifOutNUcastPkts

       64 bit unsigned wrappable counter."
   ::= {pr1645v2PppBFPerfEntry 41222144}

pr1645v2PppBFPerfMCOutBcastPkts OBJECT-TYPE
   SYNTAX      Counter64
   MAX-ACCESS  read-only
   STATUS      current
   DESCRIPTION
      "Path: pppBundle.performance.multiclassInterfaces.mibCounters.ifOutBcastPkts

       64 bit unsigned wrappable counter."
   ::= {pr1645v2PppBFPerfEntry 47775744}

pr1645v2PppBFPerfMCOutMcastPkts OBJECT-TYPE
   SYNTAX      Counter64
   MAX-ACCESS  read-only
   STATUS      current
   DESCRIPTION
      "Path: pppBundle.performance.multiclassInterfaces.mibCounters.ifOutMcastPkts

       64 bit unsigned wrappable counter."
   ::= {pr1645v2PppBFPerfEntry 48431104}

pr1645v2PppBFPerfMCOutDiscards OBJECT-TYPE
   SYNTAX      Counter64
   MAX-ACCESS  read-only
   STATUS      current
   DESCRIPTION
      "Path: pppBundle.performance.multiclassInterfaces.mibCounters.ifOutDiscards

       64 bit unsigned wrappable counter."
   ::= {pr1645v2PppBFPerfEntry 41287680}

pr1645v2PppBFPerfMCOutErrors OBJECT-TYPE
   SYNTAX      Counter64
   MAX-ACCESS  read-only
   STATUS      current
   DESCRIPTION
      "Path: pppBundle.performance.multiclassInterfaces.mibCounters.ifOutErrors

       64 bit unsigned wrappable counter."
   ::= {pr1645v2PppBFPerfEntry 41353216}

pr1645v2PppBFPerfMCOutQLen OBJECT-TYPE
   SYNTAX      Counter32
   MAX-ACCESS  read-only
   STATUS      current
   DESCRIPTION
      "Path: pppBundle.performance.multiclassInterfaces.mibCounters.ifOutQLen

       32 bit unsigned wrappable counter."
   ::= {pr1645v2PppBFPerfEntry 41418752}

pr1645v2PppBFPerfMCOutDropEx OBJECT-TYPE
   SYNTAX      Counter64
   MAX-ACCESS  read-only
   STATUS      current
   DESCRIPTION
      "Path: pppBundle.performance.multiclassInterfaces.mibCounters.ifOutDropLevelExceeded

       64 bit unsigned wrappable counter."
   ::= {pr1645v2PppBFPerfEntry 41484288}

pr1645v2PppBFPerfMCOutDropNoArp OBJECT-TYPE
   SYNTAX      Counter64
   MAX-ACCESS  read-only
   STATUS      current
   DESCRIPTION
      "Path: pppBundle.performance.multiclassInterfaces.mibCounters.ifOutDiscardsNoArp

       64 bit unsigned wrappable counter."
   ::= {pr1645v2PppBFPerfEntry 42336256}

pr1645v2PppBFPerfMCOutDropFilter OBJECT-TYPE
   SYNTAX      Counter64
   MAX-ACCESS  read-only
   STATUS      current
   DESCRIPTION
      "Path: pppBundle.performance.multiclassInterfaces.mibCounters.ifOutDiscardsFilter

       64 bit unsigned wrappable counter."
   ::= {pr1645v2PppBFPerfEntry 42598400}

pr1645v2PppBFPerfMCOutBandwidth15sec OBJECT-TYPE
   SYNTAX      Integer32
   MAX-ACCESS  read-only
   STATUS      current
   DESCRIPTION
      "Path: pppBundle.performance.multiclassInterfaces.mibCounters.ifOutBandwidth.15sec

       unit name = bps
       formula = 8 * ; 8 /"
   ::= {pr1645v2PppBFPerfEntry 45483264}

pr1645v2PppBFPerfMCOutBandwidth30sec OBJECT-TYPE
   SYNTAX      Integer32
   MAX-ACCESS  read-only
   STATUS      current
   DESCRIPTION
      "Path: pppBundle.performance.multiclassInterfaces.mibCounters.ifOutBandwidth.30sec

       unit name = bps
       formula = 8 * ; 8 /"
   ::= {pr1645v2PppBFPerfEntry 45484544}

pr1645v2PppBFPerfMCOutBandwidth1min OBJECT-TYPE
   SYNTAX      Integer32
   MAX-ACCESS  read-only
   STATUS      current
   DESCRIPTION
      "Path: pppBundle.performance.multiclassInterfaces.mibCounters.ifOutBandwidth.1min

       unit name = bps
       formula = 8 * ; 8 /"
   ::= {pr1645v2PppBFPerfEntry 45487104}

pr1645v2PppBFPerfMCOutBandwidth2min OBJECT-TYPE
   SYNTAX      Integer32
   MAX-ACCESS  read-only
   STATUS      current
   DESCRIPTION
      "Path: pppBundle.performance.multiclassInterfaces.mibCounters.ifOutBandwidth.2min

       unit name = bps
       formula = 8 * ; 8 /"
   ::= {pr1645v2PppBFPerfEntry 45492224}

pr1645v2PppBFPerfMCOutBandwidth5min OBJECT-TYPE
   SYNTAX      Integer32
   MAX-ACCESS  read-only
   STATUS      current
   DESCRIPTION
      "Path: pppBundle.performance.multiclassInterfaces.mibCounters.ifOutBandwidth.5min

       unit name = bps
       formula = 8 * ; 8 /"
   ::= {pr1645v2PppBFPerfEntry 45507584}

pr1645v2PppBFPerfMCH2P OBJECT-TYPE
   SYNTAX      SEQUENCE OF Pr1645v2PppBFPerfMCH2PEntry
   MAX-ACCESS  not-accessible
   STATUS      current
   DESCRIPTION
      ""
   ::= {pr1645v2PppBFPerf 41549824}

pr1645v2PppBFPerfMCH2PEntry OBJECT-TYPE
   SYNTAX      Pr1645v2PppBFPerfMCH2PEntry
   MAX-ACCESS  not-accessible
   STATUS      current
   DESCRIPTION
      ""
   INDEX      { pr1645v2PppBFPerfMCH2PGlobalIx,
                pr1645v2PppBFPerfTableIx,
                pr1645v2PppBFPerfMCH2PTableIx }
   ::= {pr1645v2PppBFPerfMCH2P 1}

Pr1645v2PppBFPerfMCH2PEntry ::=
   SEQUENCE
      {
      pr1645v2PppBFPerfMCH2PGlobalIx
         GlobalIndex,
      pr1645v2PppBFPerfMCH2PTableIx
         TableIndex,
      pr1645v2PppBFPerfMCH2PSysUpTime
         TimeTicks,
      pr1645v2PppBFPerfMCH2PIfUpTime
         TimeTicks,
      pr1645v2PppBFPerfMCH2PIfStatChanges
         Counter32,
      pr1645v2PppBFPerfMCH2PIfInOctets
         Counter64,
      pr1645v2PppBFPerfMCH2PIfInUCPkts
         Counter64,
      pr1645v2PppBFPerfMCH2PIfInNUCPkts
         Counter64,
      pr1645v2PppBFPerfMCH2PIfInBCPkts
         Counter64,
      pr1645v2PppBFPerfMCH2PIfInMCPkts
         Counter64,
      pr1645v2PppBFPerfMCH2PIfInDiscards
         Counter64,
      pr1645v2PppBFPerfMCH2PIfInErrors
         Counter64,
      pr1645v2PppBFPerfMCH2PIfInUnkwn
         Counter64,
      pr1645v2PppBFPerfMCH2PInDropEx
         Counter64,
      pr1645v2PppBFPerfMCH2PInDropNoMac
         Counter64,
      pr1645v2PppBFPerfMCH2PInDropNUCast
         Counter64,
      pr1645v2PppBFPerfMCH2PInDropFilter
         Counter64,
      pr1645v2PppBFPerfMCH2PIfInBandwidth
         Integer32,
      pr1645v2PppBFPerfMCH2PIfOutOctets
         Counter64,
      pr1645v2PppBFPerfMCH2PIfOutUCPkts
         Counter64,
      pr1645v2PppBFPerfMCH2PIfOutNUCPkts
         Counter64,
      pr1645v2PppBFPerfMCH2PIfOutBCPkts
         Counter64,
      pr1645v2PppBFPerfMCH2PIfOutMCPkts
         Counter64,
      pr1645v2PppBFPerfMCH2PIfOutDiscards
         Counter64,
      pr1645v2PppBFPerfMCH2PIfOutErrors
         Counter64,
      pr1645v2PppBFPerfMCH2POutDropEx
         Counter64,
      pr1645v2PppBFPerfMCH2POutDropNoArp
         Counter64,
      pr1645v2PppBFPerfMCH2POutDropFilter
         Counter64,
      pr1645v2PppBFPerfMCH2PIfOutBandwidth
         Integer32,
      pr1645v2PppBFPerfMCH2PIfErrSec
         Counter32
      }

pr1645v2PppBFPerfMCH2PGlobalIx OBJECT-TYPE
   SYNTAX      GlobalIndex
   MAX-ACCESS  not-accessible
   STATUS      current
   DESCRIPTION
      "The value of the tlsCntTreeGlobalIndex of the MANAGED OBJECT."
   ::= {pr1645v2PppBFPerfMCH2PEntry 10}

pr1645v2PppBFPerfMCH2PTableIx OBJECT-TYPE
   SYNTAX      TableIndex
   MAX-ACCESS  not-accessible
   STATUS      current
   DESCRIPTION
      ""
   ::= {pr1645v2PppBFPerfMCH2PEntry 11}

pr1645v2PppBFPerfMCH2PSysUpTime OBJECT-TYPE
   SYNTAX      TimeTicks
   MAX-ACCESS  read-only
   STATUS      current
   DESCRIPTION
      "Path: pppBundle.performance.multiclassInterfaces.mibCounters.h2Performance.sysUpTime

       Time in centi-second."
   ::= {pr1645v2PppBFPerfMCH2PEntry 16777216}

pr1645v2PppBFPerfMCH2PIfUpTime OBJECT-TYPE
   SYNTAX      TimeTicks
   MAX-ACCESS  read-only
   STATUS      current
   DESCRIPTION
      "Path: pppBundle.performance.multiclassInterfaces.mibCounters.h2Performance.ifUpTime

       Time in centi-second."
   ::= {pr1645v2PppBFPerfMCH2PEntry 33554432}

pr1645v2PppBFPerfMCH2PIfStatChanges OBJECT-TYPE
   SYNTAX      Counter32
   MAX-ACCESS  read-only
   STATUS      current
   DESCRIPTION
      "Path: pppBundle.performance.multiclassInterfaces.mibCounters.h2Performance.ifStatusChanges

       32 bit unsigned wrappable counter."
   ::= {pr1645v2PppBFPerfMCH2PEntry 50331648}

pr1645v2PppBFPerfMCH2PIfInOctets OBJECT-TYPE
   SYNTAX      Counter64
   MAX-ACCESS  read-only
   STATUS      current
   DESCRIPTION
      "Path: pppBundle.performance.multiclassInterfaces.mibCounters.h2Performance.ifInOctets

       64 bit unsigned wrappable counter."
   ::= {pr1645v2PppBFPerfMCH2PEntry 67108864}

pr1645v2PppBFPerfMCH2PIfInUCPkts OBJECT-TYPE
   SYNTAX      Counter64
   MAX-ACCESS  read-only
   STATUS      current
   DESCRIPTION
      "Path: pppBundle.performance.multiclassInterfaces.mibCounters.h2Performance.ifInUcastPkts

       64 bit unsigned wrappable counter."
   ::= {pr1645v2PppBFPerfMCH2PEntry 83886080}

pr1645v2PppBFPerfMCH2PIfInNUCPkts OBJECT-TYPE
   SYNTAX      Counter64
   MAX-ACCESS  read-only
   STATUS      current
   DESCRIPTION
      "Path: pppBundle.performance.multiclassInterfaces.mibCounters.h2Performance.ifInNUcastPkts

       64 bit unsigned wrappable counter."
   ::= {pr1645v2PppBFPerfMCH2PEntry 100663296}

pr1645v2PppBFPerfMCH2PIfInBCPkts OBJECT-TYPE
   SYNTAX      Counter64
   MAX-ACCESS  read-only
   STATUS      current
   DESCRIPTION
      "Path: pppBundle.performance.multiclassInterfaces.mibCounters.h2Performance.ifInBcastPkts

       64 bit unsigned wrappable counter."
   ::= {pr1645v2PppBFPerfMCH2PEntry 419430400}

pr1645v2PppBFPerfMCH2PIfInMCPkts OBJECT-TYPE
   SYNTAX      Counter64
   MAX-ACCESS  read-only
   STATUS      current
   DESCRIPTION
      "Path: pppBundle.performance.multiclassInterfaces.mibCounters.h2Performance.ifInMcastPkts

       64 bit unsigned wrappable counter."
   ::= {pr1645v2PppBFPerfMCH2PEntry 436207616}

pr1645v2PppBFPerfMCH2PIfInDiscards OBJECT-TYPE
   SYNTAX      Counter64
   MAX-ACCESS  read-only
   STATUS      current
   DESCRIPTION
      "Path: pppBundle.performance.multiclassInterfaces.mibCounters.h2Performance.ifInDiscards

       64 bit unsigned wrappable counter."
   ::= {pr1645v2PppBFPerfMCH2PEntry 117440512}

pr1645v2PppBFPerfMCH2PIfInErrors OBJECT-TYPE
   SYNTAX      Counter64
   MAX-ACCESS  read-only
   STATUS      current
   DESCRIPTION
      "Path: pppBundle.performance.multiclassInterfaces.mibCounters.h2Performance.ifInErrors

       64 bit unsigned wrappable counter."
   ::= {pr1645v2PppBFPerfMCH2PEntry 134217728}

pr1645v2PppBFPerfMCH2PIfInUnkwn OBJECT-TYPE
   SYNTAX      Counter64
   MAX-ACCESS  read-only
   STATUS      current
   DESCRIPTION
      "Path: pppBundle.performance.multiclassInterfaces.mibCounters.h2Performance.ifInUnknownProtos

       64 bit unsigned wrappable counter."
   ::= {pr1645v2PppBFPerfMCH2PEntry 150994944}

pr1645v2PppBFPerfMCH2PInDropEx OBJECT-TYPE
   SYNTAX      Counter64
   MAX-ACCESS  read-only
   STATUS      current
   DESCRIPTION
      "Path: pppBundle.performance.multiclassInterfaces.mibCounters.h2Performance.ifInDropLevelExceeded

       64 bit unsigned wrappable counter."
   ::= {pr1645v2PppBFPerfMCH2PEntry 335544320}

pr1645v2PppBFPerfMCH2PInDropNoMac OBJECT-TYPE
   SYNTAX      Counter64
   MAX-ACCESS  read-only
   STATUS      current
   DESCRIPTION
      "Path: pppBundle.performance.multiclassInterfaces.mibCounters.h2Performance.fInDiscardsNoMacFit

       64 bit unsigned wrappable counter."
   ::= {pr1645v2PppBFPerfMCH2PEntry 301989888}

pr1645v2PppBFPerfMCH2PInDropNUCast OBJECT-TYPE
   SYNTAX      Counter64
   MAX-ACCESS  read-only
   STATUS      current
   DESCRIPTION
      "Path: pppBundle.performance.multiclassInterfaces.mibCounters.h2Performance.fInDiscardsNUCast

       64 bit unsigned wrappable counter."
   ::= {pr1645v2PppBFPerfMCH2PEntry 318767104}

pr1645v2PppBFPerfMCH2PInDropFilter OBJECT-TYPE
   SYNTAX      Counter64
   MAX-ACCESS  read-only
   STATUS      current
   DESCRIPTION
      "Path: pppBundle.performance.multiclassInterfaces.mibCounters.h2Performance.fInDiscardsFilter

       64 bit unsigned wrappable counter."
   ::= {pr1645v2PppBFPerfMCH2PEntry 385875968}

pr1645v2PppBFPerfMCH2PIfInBandwidth OBJECT-TYPE
   SYNTAX      Integer32
   MAX-ACCESS  read-only
   STATUS      current
   DESCRIPTION
      "Path: pppBundle.performance.multiclassInterfaces.mibCounters.h2Performance.ifInBandwidth

       unit name = bps
       formula = 8 * ; 8 /"
   ::= {pr1645v2PppBFPerfMCH2PEntry 268435456}

pr1645v2PppBFPerfMCH2PIfOutOctets OBJECT-TYPE
   SYNTAX      Counter64
   MAX-ACCESS  read-only
   STATUS      current
   DESCRIPTION
      "Path: pppBundle.performance.multiclassInterfaces.mibCounters.h2Performance.ifOutOctets

       64 bit unsigned wrappable counter."
   ::= {pr1645v2PppBFPerfMCH2PEntry 167772160}

pr1645v2PppBFPerfMCH2PIfOutUCPkts OBJECT-TYPE
   SYNTAX      Counter64
   MAX-ACCESS  read-only
   STATUS      current
   DESCRIPTION
      "Path: pppBundle.performance.multiclassInterfaces.mibCounters.h2Performance.ifOutUcastPkts

       64 bit unsigned wrappable counter."
   ::= {pr1645v2PppBFPerfMCH2PEntry 184549376}

pr1645v2PppBFPerfMCH2PIfOutNUCPkts OBJECT-TYPE
   SYNTAX      Counter64
   MAX-ACCESS  read-only
   STATUS      current
   DESCRIPTION
      "Path: pppBundle.performance.multiclassInterfaces.mibCounters.h2Performance.ifOutNUcastPkts

       64 bit unsigned wrappable counter."
   ::= {pr1645v2PppBFPerfMCH2PEntry 201326592}

pr1645v2PppBFPerfMCH2PIfOutBCPkts OBJECT-TYPE
   SYNTAX      Counter64
   MAX-ACCESS  read-only
   STATUS      current
   DESCRIPTION
      "Path: pppBundle.performance.multiclassInterfaces.mibCounters.h2Performance.ifOutBcastPkts

       64 bit unsigned wrappable counter."
   ::= {pr1645v2PppBFPerfMCH2PEntry 452984832}

pr1645v2PppBFPerfMCH2PIfOutMCPkts OBJECT-TYPE
   SYNTAX      Counter64
   MAX-ACCESS  read-only
   STATUS      current
   DESCRIPTION
      "Path: pppBundle.performance.multiclassInterfaces.mibCounters.h2Performance.ifOutMcastPkts

       64 bit unsigned wrappable counter."
   ::= {pr1645v2PppBFPerfMCH2PEntry 469762048}

pr1645v2PppBFPerfMCH2PIfOutDiscards OBJECT-TYPE
   SYNTAX      Counter64
   MAX-ACCESS  read-only
   STATUS      current
   DESCRIPTION
      "Path: pppBundle.performance.multiclassInterfaces.mibCounters.h2Performance.ifOutDiscards

       64 bit unsigned wrappable counter."
   ::= {pr1645v2PppBFPerfMCH2PEntry 218103808}

pr1645v2PppBFPerfMCH2PIfOutErrors OBJECT-TYPE
   SYNTAX      Counter64
   MAX-ACCESS  read-only
   STATUS      current
   DESCRIPTION
      "Path: pppBundle.performance.multiclassInterfaces.mibCounters.h2Performance.ifOutErrors

       64 bit unsigned wrappable counter."
   ::= {pr1645v2PppBFPerfMCH2PEntry 234881024}

pr1645v2PppBFPerfMCH2POutDropEx OBJECT-TYPE
   SYNTAX      Counter64
   MAX-ACCESS  read-only
   STATUS      current
   DESCRIPTION
      "Path: pppBundle.performance.multiclassInterfaces.mibCounters.h2Performance.ifOutDropLevelExceeded

       64 bit unsigned wrappable counter."
   ::= {pr1645v2PppBFPerfMCH2PEntry 352321536}

pr1645v2PppBFPerfMCH2POutDropNoArp OBJECT-TYPE
   SYNTAX      Counter64
   MAX-ACCESS  read-only
   STATUS      current
   DESCRIPTION
      "Path: pppBundle.performance.multiclassInterfaces.mibCounters.h2Performance.ifOutDiscardsNoArp

       64 bit unsigned wrappable counter."
   ::= {pr1645v2PppBFPerfMCH2PEntry 369098752}

pr1645v2PppBFPerfMCH2POutDropFilter OBJECT-TYPE
   SYNTAX      Counter64
   MAX-ACCESS  read-only
   STATUS      current
   DESCRIPTION
      "Path: pppBundle.performance.multiclassInterfaces.mibCounters.h2Performance.ifOutDiscardsFilter

       64 bit unsigned wrappable counter."
   ::= {pr1645v2PppBFPerfMCH2PEntry 402653184}

pr1645v2PppBFPerfMCH2PIfOutBandwidth OBJECT-TYPE
   SYNTAX      Integer32
   MAX-ACCESS  read-only
   STATUS      current
   DESCRIPTION
      "Path: pppBundle.performance.multiclassInterfaces.mibCounters.h2Performance.ifOutBandwidth

       unit name = bps
       formula = 8 * ; 8 /"
   ::= {pr1645v2PppBFPerfMCH2PEntry 285212672}

pr1645v2PppBFPerfMCH2PIfErrSec OBJECT-TYPE
   SYNTAX      Counter32
   MAX-ACCESS  read-only
   STATUS      current
   DESCRIPTION
      "Path: pppBundle.performance.multiclassInterfaces.mibCounters.h2Performance.ifErrSec

       32 bit unsigned wrappable counter."
   ::= {pr1645v2PppBFPerfMCH2PEntry 251658240}

pr1645v2PppBFPerfMCH24P OBJECT-TYPE
   SYNTAX      SEQUENCE OF Pr1645v2PppBFPerfMCH24PEntry
   MAX-ACCESS  not-accessible
   STATUS      current
   DESCRIPTION
      ""
   ::= {pr1645v2PppBFPerf 41615360}

pr1645v2PppBFPerfMCH24PEntry OBJECT-TYPE
   SYNTAX      Pr1645v2PppBFPerfMCH24PEntry
   MAX-ACCESS  not-accessible
   STATUS      current
   DESCRIPTION
      ""
   INDEX      { pr1645v2PppBFPerfMCH24PGlobalIx,
                pr1645v2PppBFPerfTableIx,
                pr1645v2PppBFPerfMCH24PTableIx }
   ::= {pr1645v2PppBFPerfMCH24P 1}

Pr1645v2PppBFPerfMCH24PEntry ::=
   SEQUENCE
      {
      pr1645v2PppBFPerfMCH24PGlobalIx
         GlobalIndex,
      pr1645v2PppBFPerfMCH24PTableIx
         TableIndex,
      pr1645v2PppBFPerfMCH24PSysUpTime
         TimeTicks,
      pr1645v2PppBFPerfMCH24PIfUpTime
         TimeTicks,
      pr1645v2PppBFPerfMCH24PIfStatChanges
         Counter32,
      pr1645v2PppBFPerfMCH24PIfInOctets
         Counter64,
      pr1645v2PppBFPerfMCH24PIfInUCPkts
         Counter64,
      pr1645v2PppBFPerfMCH24PIfInNUCPkts
         Counter64,
      pr1645v2PppBFPerfMCH24PIfInBCPkts
         Counter64,
      pr1645v2PppBFPerfMCH24PIfInMCPkts
         Counter64,
      pr1645v2PppBFPerfMCH24PIfInDiscards
         Counter64,
      pr1645v2PppBFPerfMCH24PIfInErrors
         Counter64,
      pr1645v2PppBFPerfMCH24PIfInUnkwn
         Counter64,
      pr1645v2PppBFPerfMCH24PInDropEx
         Counter64,
      pr1645v2PppBFPerfMCH24PInDropNoMac
         Counter64,
      pr1645v2PppBFPerfMCH24PInDropNUCast
         Counter64,
      pr1645v2PppBFPerfMCH24PInDropFilter
         Counter64,
      pr1645v2PppBFPerfMCH24PIfInBandwidth
         Integer32,
      pr1645v2PppBFPerfMCH24PIfOutOctets
         Counter64,
      pr1645v2PppBFPerfMCH24PIfOutUCPkts
         Counter64,
      pr1645v2PppBFPerfMCH24PIfOutNUCPkts
         Counter64,
      pr1645v2PppBFPerfMCH24PIfOutBCPkts
         Counter64,
      pr1645v2PppBFPerfMCH24PIfOutMCPkts
         Counter64,
      pr1645v2PppBFPerfMCH24PIfOutDiscards
         Counter64,
      pr1645v2PppBFPerfMCH24PIfOutErrors
         Counter64,
      pr1645v2PppBFPerfMCH24POutDropEx
         Counter64,
      pr1645v2PppBFPerfMCH24POutDropNoArp
         Counter64,
      pr1645v2PppBFPerfMCH24POutDropFilter
         Counter64,
      pr1645v2PppBFPerfMCH24PIfOutBandwidth
         Integer32,
      pr1645v2PppBFPerfMCH24PIfErrSec
         Counter32
      }

pr1645v2PppBFPerfMCH24PGlobalIx OBJECT-TYPE
   SYNTAX      GlobalIndex
   MAX-ACCESS  not-accessible
   STATUS      current
   DESCRIPTION
      "The value of the tlsCntTreeGlobalIndex of the MANAGED OBJECT."
   ::= {pr1645v2PppBFPerfMCH24PEntry 10}

pr1645v2PppBFPerfMCH24PTableIx OBJECT-TYPE
   SYNTAX      TableIndex
   MAX-ACCESS  not-accessible
   STATUS      current
   DESCRIPTION
      ""
   ::= {pr1645v2PppBFPerfMCH24PEntry 11}

pr1645v2PppBFPerfMCH24PSysUpTime OBJECT-TYPE
   SYNTAX      TimeTicks
   MAX-ACCESS  read-only
   STATUS      current
   DESCRIPTION
      "Path: pppBundle.performance.multiclassInterfaces.mibCounters.h24Performance.sysUpTime

       Time in centi-second."
   ::= {pr1645v2PppBFPerfMCH24PEntry 16777216}

pr1645v2PppBFPerfMCH24PIfUpTime OBJECT-TYPE
   SYNTAX      TimeTicks
   MAX-ACCESS  read-only
   STATUS      current
   DESCRIPTION
      "Path: pppBundle.performance.multiclassInterfaces.mibCounters.h24Performance.ifUpTime

       Time in centi-second."
   ::= {pr1645v2PppBFPerfMCH24PEntry 33554432}

pr1645v2PppBFPerfMCH24PIfStatChanges OBJECT-TYPE
   SYNTAX      Counter32
   MAX-ACCESS  read-only
   STATUS      current
   DESCRIPTION
      "Path: pppBundle.performance.multiclassInterfaces.mibCounters.h24Performance.ifStatusChanges

       32 bit unsigned wrappable counter."
   ::= {pr1645v2PppBFPerfMCH24PEntry 50331648}

pr1645v2PppBFPerfMCH24PIfInOctets OBJECT-TYPE
   SYNTAX      Counter64
   MAX-ACCESS  read-only
   STATUS      current
   DESCRIPTION
      "Path: pppBundle.performance.multiclassInterfaces.mibCounters.h24Performance.ifInOctets

       64 bit unsigned wrappable counter."
   ::= {pr1645v2PppBFPerfMCH24PEntry 67108864}

pr1645v2PppBFPerfMCH24PIfInUCPkts OBJECT-TYPE
   SYNTAX      Counter64
   MAX-ACCESS  read-only
   STATUS      current
   DESCRIPTION
      "Path: pppBundle.performance.multiclassInterfaces.mibCounters.h24Performance.ifInUcastPkts

       64 bit unsigned wrappable counter."
   ::= {pr1645v2PppBFPerfMCH24PEntry 83886080}

pr1645v2PppBFPerfMCH24PIfInNUCPkts OBJECT-TYPE
   SYNTAX      Counter64
   MAX-ACCESS  read-only
   STATUS      current
   DESCRIPTION
      "Path: pppBundle.performance.multiclassInterfaces.mibCounters.h24Performance.ifInNUcastPkts

       64 bit unsigned wrappable counter."
   ::= {pr1645v2PppBFPerfMCH24PEntry 100663296}

pr1645v2PppBFPerfMCH24PIfInBCPkts OBJECT-TYPE
   SYNTAX      Counter64
   MAX-ACCESS  read-only
   STATUS      current
   DESCRIPTION
      "Path: pppBundle.performance.multiclassInterfaces.mibCounters.h24Performance.ifInBcastPkts

       64 bit unsigned wrappable counter."
   ::= {pr1645v2PppBFPerfMCH24PEntry 419430400}

pr1645v2PppBFPerfMCH24PIfInMCPkts OBJECT-TYPE
   SYNTAX      Counter64
   MAX-ACCESS  read-only
   STATUS      current
   DESCRIPTION
      "Path: pppBundle.performance.multiclassInterfaces.mibCounters.h24Performance.ifInMcastPkts

       64 bit unsigned wrappable counter."
   ::= {pr1645v2PppBFPerfMCH24PEntry 436207616}

pr1645v2PppBFPerfMCH24PIfInDiscards OBJECT-TYPE
   SYNTAX      Counter64
   MAX-ACCESS  read-only
   STATUS      current
   DESCRIPTION
      "Path: pppBundle.performance.multiclassInterfaces.mibCounters.h24Performance.ifInDiscards

       64 bit unsigned wrappable counter."
   ::= {pr1645v2PppBFPerfMCH24PEntry 117440512}

pr1645v2PppBFPerfMCH24PIfInErrors OBJECT-TYPE
   SYNTAX      Counter64
   MAX-ACCESS  read-only
   STATUS      current
   DESCRIPTION
      "Path: pppBundle.performance.multiclassInterfaces.mibCounters.h24Performance.ifInErrors

       64 bit unsigned wrappable counter."
   ::= {pr1645v2PppBFPerfMCH24PEntry 134217728}

pr1645v2PppBFPerfMCH24PIfInUnkwn OBJECT-TYPE
   SYNTAX      Counter64
   MAX-ACCESS  read-only
   STATUS      current
   DESCRIPTION
      "Path: pppBundle.performance.multiclassInterfaces.mibCounters.h24Performance.ifInUnknownProtos

       64 bit unsigned wrappable counter."
   ::= {pr1645v2PppBFPerfMCH24PEntry 150994944}

pr1645v2PppBFPerfMCH24PInDropEx OBJECT-TYPE
   SYNTAX      Counter64
   MAX-ACCESS  read-only
   STATUS      current
   DESCRIPTION
      "Path: pppBundle.performance.multiclassInterfaces.mibCounters.h24Performance.ifInDropLevelExceeded

       64 bit unsigned wrappable counter."
   ::= {pr1645v2PppBFPerfMCH24PEntry 335544320}

pr1645v2PppBFPerfMCH24PInDropNoMac OBJECT-TYPE
   SYNTAX      Counter64
   MAX-ACCESS  read-only
   STATUS      current
   DESCRIPTION
      "Path: pppBundle.performance.multiclassInterfaces.mibCounters.h24Performance.fInDiscardsNoMacFit

       64 bit unsigned wrappable counter."
   ::= {pr1645v2PppBFPerfMCH24PEntry 301989888}

pr1645v2PppBFPerfMCH24PInDropNUCast OBJECT-TYPE
   SYNTAX      Counter64
   MAX-ACCESS  read-only
   STATUS      current
   DESCRIPTION
      "Path: pppBundle.performance.multiclassInterfaces.mibCounters.h24Performance.fInDiscardsNUCast

       64 bit unsigned wrappable counter."
   ::= {pr1645v2PppBFPerfMCH24PEntry 318767104}

pr1645v2PppBFPerfMCH24PInDropFilter OBJECT-TYPE
   SYNTAX      Counter64
   MAX-ACCESS  read-only
   STATUS      current
   DESCRIPTION
      "Path: pppBundle.performance.multiclassInterfaces.mibCounters.h24Performance.fInDiscardsFilter

       64 bit unsigned wrappable counter."
   ::= {pr1645v2PppBFPerfMCH24PEntry 385875968}

pr1645v2PppBFPerfMCH24PIfInBandwidth OBJECT-TYPE
   SYNTAX      Integer32
   MAX-ACCESS  read-only
   STATUS      current
   DESCRIPTION
      "Path: pppBundle.performance.multiclassInterfaces.mibCounters.h24Performance.ifInBandwidth

       unit name = bps
       formula = 8 * ; 8 /"
   ::= {pr1645v2PppBFPerfMCH24PEntry 268435456}

pr1645v2PppBFPerfMCH24PIfOutOctets OBJECT-TYPE
   SYNTAX      Counter64
   MAX-ACCESS  read-only
   STATUS      current
   DESCRIPTION
      "Path: pppBundle.performance.multiclassInterfaces.mibCounters.h24Performance.ifOutOctets

       64 bit unsigned wrappable counter."
   ::= {pr1645v2PppBFPerfMCH24PEntry 167772160}

pr1645v2PppBFPerfMCH24PIfOutUCPkts OBJECT-TYPE
   SYNTAX      Counter64
   MAX-ACCESS  read-only
   STATUS      current
   DESCRIPTION
      "Path: pppBundle.performance.multiclassInterfaces.mibCounters.h24Performance.ifOutUcastPkts

       64 bit unsigned wrappable counter."
   ::= {pr1645v2PppBFPerfMCH24PEntry 184549376}

pr1645v2PppBFPerfMCH24PIfOutNUCPkts OBJECT-TYPE
   SYNTAX      Counter64
   MAX-ACCESS  read-only
   STATUS      current
   DESCRIPTION
      "Path: pppBundle.performance.multiclassInterfaces.mibCounters.h24Performance.ifOutNUcastPkts

       64 bit unsigned wrappable counter."
   ::= {pr1645v2PppBFPerfMCH24PEntry 201326592}

pr1645v2PppBFPerfMCH24PIfOutBCPkts OBJECT-TYPE
   SYNTAX      Counter64
   MAX-ACCESS  read-only
   STATUS      current
   DESCRIPTION
      "Path: pppBundle.performance.multiclassInterfaces.mibCounters.h24Performance.ifOutBcastPkts

       64 bit unsigned wrappable counter."
   ::= {pr1645v2PppBFPerfMCH24PEntry 452984832}

pr1645v2PppBFPerfMCH24PIfOutMCPkts OBJECT-TYPE
   SYNTAX      Counter64
   MAX-ACCESS  read-only
   STATUS      current
   DESCRIPTION
      "Path: pppBundle.performance.multiclassInterfaces.mibCounters.h24Performance.ifOutMcastPkts

       64 bit unsigned wrappable counter."
   ::= {pr1645v2PppBFPerfMCH24PEntry 469762048}

pr1645v2PppBFPerfMCH24PIfOutDiscards OBJECT-TYPE
   SYNTAX      Counter64
   MAX-ACCESS  read-only
   STATUS      current
   DESCRIPTION
      "Path: pppBundle.performance.multiclassInterfaces.mibCounters.h24Performance.ifOutDiscards

       64 bit unsigned wrappable counter."
   ::= {pr1645v2PppBFPerfMCH24PEntry 218103808}

pr1645v2PppBFPerfMCH24PIfOutErrors OBJECT-TYPE
   SYNTAX      Counter64
   MAX-ACCESS  read-only
   STATUS      current
   DESCRIPTION
      "Path: pppBundle.performance.multiclassInterfaces.mibCounters.h24Performance.ifOutErrors

       64 bit unsigned wrappable counter."
   ::= {pr1645v2PppBFPerfMCH24PEntry 234881024}

pr1645v2PppBFPerfMCH24POutDropEx OBJECT-TYPE
   SYNTAX      Counter64
   MAX-ACCESS  read-only
   STATUS      current
   DESCRIPTION
      "Path: pppBundle.performance.multiclassInterfaces.mibCounters.h24Performance.ifOutDropLevelExceeded

       64 bit unsigned wrappable counter."
   ::= {pr1645v2PppBFPerfMCH24PEntry 352321536}

pr1645v2PppBFPerfMCH24POutDropNoArp OBJECT-TYPE
   SYNTAX      Counter64
   MAX-ACCESS  read-only
   STATUS      current
   DESCRIPTION
      "Path: pppBundle.performance.multiclassInterfaces.mibCounters.h24Performance.ifOutDiscardsNoArp

       64 bit unsigned wrappable counter."
   ::= {pr1645v2PppBFPerfMCH24PEntry 369098752}

pr1645v2PppBFPerfMCH24POutDropFilter OBJECT-TYPE
   SYNTAX      Counter64
   MAX-ACCESS  read-only
   STATUS      current
   DESCRIPTION
      "Path: pppBundle.performance.multiclassInterfaces.mibCounters.h24Performance.ifOutDiscardsFilter

       64 bit unsigned wrappable counter."
   ::= {pr1645v2PppBFPerfMCH24PEntry 402653184}

pr1645v2PppBFPerfMCH24PIfOutBandwidth OBJECT-TYPE
   SYNTAX      Integer32
   MAX-ACCESS  read-only
   STATUS      current
   DESCRIPTION
      "Path: pppBundle.performance.multiclassInterfaces.mibCounters.h24Performance.ifOutBandwidth

       unit name = bps
       formula = 8 * ; 8 /"
   ::= {pr1645v2PppBFPerfMCH24PEntry 285212672}

pr1645v2PppBFPerfMCH24PIfErrSec OBJECT-TYPE
   SYNTAX      Counter32
   MAX-ACCESS  read-only
   STATUS      current
   DESCRIPTION
      "Path: pppBundle.performance.multiclassInterfaces.mibCounters.h24Performance.ifErrSec

       32 bit unsigned wrappable counter."
   ::= {pr1645v2PppBFPerfMCH24PEntry 251658240}

pr1645v2PppBFPerfMCD7P OBJECT-TYPE
   SYNTAX      SEQUENCE OF Pr1645v2PppBFPerfMCD7PEntry
   MAX-ACCESS  not-accessible
   STATUS      current
   DESCRIPTION
      ""
   ::= {pr1645v2PppBFPerf 41680896}

pr1645v2PppBFPerfMCD7PEntry OBJECT-TYPE
   SYNTAX      Pr1645v2PppBFPerfMCD7PEntry
   MAX-ACCESS  not-accessible
   STATUS      current
   DESCRIPTION
      ""
   INDEX      { pr1645v2PppBFPerfMCD7PGlobalIx,
                pr1645v2PppBFPerfTableIx,
                pr1645v2PppBFPerfMCD7PTableIx }
   ::= {pr1645v2PppBFPerfMCD7P 1}

Pr1645v2PppBFPerfMCD7PEntry ::=
   SEQUENCE
      {
      pr1645v2PppBFPerfMCD7PGlobalIx
         GlobalIndex,
      pr1645v2PppBFPerfMCD7PTableIx
         TableIndex,
      pr1645v2PppBFPerfMCD7PSysUpTime
         TimeTicks,
      pr1645v2PppBFPerfMCD7PIfUpTime
         TimeTicks,
      pr1645v2PppBFPerfMCD7PIfStatChanges
         Counter32,
      pr1645v2PppBFPerfMCD7PIfInOctets
         Counter64,
      pr1645v2PppBFPerfMCD7PIfInUCPkts
         Counter64,
      pr1645v2PppBFPerfMCD7PIfInNUCPkts
         Counter64,
      pr1645v2PppBFPerfMCD7PIfInBCPkts
         Counter64,
      pr1645v2PppBFPerfMCD7PIfInMCPkts
         Counter64,
      pr1645v2PppBFPerfMCD7PIfInDiscards
         Counter64,
      pr1645v2PppBFPerfMCD7PIfInErrors
         Counter64,
      pr1645v2PppBFPerfMCD7PIfInUnkwn
         Counter64,
      pr1645v2PppBFPerfMCD7PInDropEx
         Counter64,
      pr1645v2PppBFPerfMCD7PInDropNoMac
         Counter64,
      pr1645v2PppBFPerfMCD7PInDropNUCast
         Counter64,
      pr1645v2PppBFPerfMCD7PInDropFilter
         Counter64,
      pr1645v2PppBFPerfMCD7PIfInBandwidth
         Integer32,
      pr1645v2PppBFPerfMCD7PIfOutOctets
         Counter64,
      pr1645v2PppBFPerfMCD7PIfOutUCPkts
         Counter64,
      pr1645v2PppBFPerfMCD7PIfOutNUCPkts
         Counter64,
      pr1645v2PppBFPerfMCD7PIfOutBCPkts
         Counter64,
      pr1645v2PppBFPerfMCD7PIfOutMCPkts
         Counter64,
      pr1645v2PppBFPerfMCD7PIfOutDiscards
         Counter64,
      pr1645v2PppBFPerfMCD7PIfOutErrors
         Counter64,
      pr1645v2PppBFPerfMCD7POutDropEx
         Counter64,
      pr1645v2PppBFPerfMCD7POutDropNoArp
         Counter64,
      pr1645v2PppBFPerfMCD7POutDropFilter
         Counter64,
      pr1645v2PppBFPerfMCD7PIfOutBandwidth
         Integer32,
      pr1645v2PppBFPerfMCD7PIfErrSec
         Counter32
      }

pr1645v2PppBFPerfMCD7PGlobalIx OBJECT-TYPE
   SYNTAX      GlobalIndex
   MAX-ACCESS  not-accessible
   STATUS      current
   DESCRIPTION
      "The value of the tlsCntTreeGlobalIndex of the MANAGED OBJECT."
   ::= {pr1645v2PppBFPerfMCD7PEntry 10}

pr1645v2PppBFPerfMCD7PTableIx OBJECT-TYPE
   SYNTAX      TableIndex
   MAX-ACCESS  not-accessible
   STATUS      current
   DESCRIPTION
      ""
   ::= {pr1645v2PppBFPerfMCD7PEntry 11}

pr1645v2PppBFPerfMCD7PSysUpTime OBJECT-TYPE
   SYNTAX      TimeTicks
   MAX-ACCESS  read-only
   STATUS      current
   DESCRIPTION
      "Path: pppBundle.performance.multiclassInterfaces.mibCounters.d7Performance.sysUpTime

       Time in centi-second."
   ::= {pr1645v2PppBFPerfMCD7PEntry 16777216}

pr1645v2PppBFPerfMCD7PIfUpTime OBJECT-TYPE
   SYNTAX      TimeTicks
   MAX-ACCESS  read-only
   STATUS      current
   DESCRIPTION
      "Path: pppBundle.performance.multiclassInterfaces.mibCounters.d7Performance.ifUpTime

       Time in centi-second."
   ::= {pr1645v2PppBFPerfMCD7PEntry 33554432}

pr1645v2PppBFPerfMCD7PIfStatChanges OBJECT-TYPE
   SYNTAX      Counter32
   MAX-ACCESS  read-only
   STATUS      current
   DESCRIPTION
      "Path: pppBundle.performance.multiclassInterfaces.mibCounters.d7Performance.ifStatusChanges

       32 bit unsigned wrappable counter."
   ::= {pr1645v2PppBFPerfMCD7PEntry 50331648}

pr1645v2PppBFPerfMCD7PIfInOctets OBJECT-TYPE
   SYNTAX      Counter64
   MAX-ACCESS  read-only
   STATUS      current
   DESCRIPTION
      "Path: pppBundle.performance.multiclassInterfaces.mibCounters.d7Performance.ifInOctets

       64 bit unsigned wrappable counter."
   ::= {pr1645v2PppBFPerfMCD7PEntry 67108864}

pr1645v2PppBFPerfMCD7PIfInUCPkts OBJECT-TYPE
   SYNTAX      Counter64
   MAX-ACCESS  read-only
   STATUS      current
   DESCRIPTION
      "Path: pppBundle.performance.multiclassInterfaces.mibCounters.d7Performance.ifInUcastPkts

       64 bit unsigned wrappable counter."
   ::= {pr1645v2PppBFPerfMCD7PEntry 83886080}

pr1645v2PppBFPerfMCD7PIfInNUCPkts OBJECT-TYPE
   SYNTAX      Counter64
   MAX-ACCESS  read-only
   STATUS      current
   DESCRIPTION
      "Path: pppBundle.performance.multiclassInterfaces.mibCounters.d7Performance.ifInNUcastPkts

       64 bit unsigned wrappable counter."
   ::= {pr1645v2PppBFPerfMCD7PEntry 100663296}

pr1645v2PppBFPerfMCD7PIfInBCPkts OBJECT-TYPE
   SYNTAX      Counter64
   MAX-ACCESS  read-only
   STATUS      current
   DESCRIPTION
      "Path: pppBundle.performance.multiclassInterfaces.mibCounters.d7Performance.ifInBcastPkts

       64 bit unsigned wrappable counter."
   ::= {pr1645v2PppBFPerfMCD7PEntry 419430400}

pr1645v2PppBFPerfMCD7PIfInMCPkts OBJECT-TYPE
   SYNTAX      Counter64
   MAX-ACCESS  read-only
   STATUS      current
   DESCRIPTION
      "Path: pppBundle.performance.multiclassInterfaces.mibCounters.d7Performance.ifInMcastPkts

       64 bit unsigned wrappable counter."
   ::= {pr1645v2PppBFPerfMCD7PEntry 436207616}

pr1645v2PppBFPerfMCD7PIfInDiscards OBJECT-TYPE
   SYNTAX      Counter64
   MAX-ACCESS  read-only
   STATUS      current
   DESCRIPTION
      "Path: pppBundle.performance.multiclassInterfaces.mibCounters.d7Performance.ifInDiscards

       64 bit unsigned wrappable counter."
   ::= {pr1645v2PppBFPerfMCD7PEntry 117440512}

pr1645v2PppBFPerfMCD7PIfInErrors OBJECT-TYPE
   SYNTAX      Counter64
   MAX-ACCESS  read-only
   STATUS      current
   DESCRIPTION
      "Path: pppBundle.performance.multiclassInterfaces.mibCounters.d7Performance.ifInErrors

       64 bit unsigned wrappable counter."
   ::= {pr1645v2PppBFPerfMCD7PEntry 134217728}

pr1645v2PppBFPerfMCD7PIfInUnkwn OBJECT-TYPE
   SYNTAX      Counter64
   MAX-ACCESS  read-only
   STATUS      current
   DESCRIPTION
      "Path: pppBundle.performance.multiclassInterfaces.mibCounters.d7Performance.ifInUnknownProtos

       64 bit unsigned wrappable counter."
   ::= {pr1645v2PppBFPerfMCD7PEntry 150994944}

pr1645v2PppBFPerfMCD7PInDropEx OBJECT-TYPE
   SYNTAX      Counter64
   MAX-ACCESS  read-only
   STATUS      current
   DESCRIPTION
      "Path: pppBundle.performance.multiclassInterfaces.mibCounters.d7Performance.ifInDropLevelExceeded

       64 bit unsigned wrappable counter."
   ::= {pr1645v2PppBFPerfMCD7PEntry 335544320}

pr1645v2PppBFPerfMCD7PInDropNoMac OBJECT-TYPE
   SYNTAX      Counter64
   MAX-ACCESS  read-only
   STATUS      current
   DESCRIPTION
      "Path: pppBundle.performance.multiclassInterfaces.mibCounters.d7Performance.fInDiscardsNoMacFit

       64 bit unsigned wrappable counter."
   ::= {pr1645v2PppBFPerfMCD7PEntry 301989888}

pr1645v2PppBFPerfMCD7PInDropNUCast OBJECT-TYPE
   SYNTAX      Counter64
   MAX-ACCESS  read-only
   STATUS      current
   DESCRIPTION
      "Path: pppBundle.performance.multiclassInterfaces.mibCounters.d7Performance.fInDiscardsNUCast

       64 bit unsigned wrappable counter."
   ::= {pr1645v2PppBFPerfMCD7PEntry 318767104}

pr1645v2PppBFPerfMCD7PInDropFilter OBJECT-TYPE
   SYNTAX      Counter64
   MAX-ACCESS  read-only
   STATUS      current
   DESCRIPTION
      "Path: pppBundle.performance.multiclassInterfaces.mibCounters.d7Performance.fInDiscardsFilter

       64 bit unsigned wrappable counter."
   ::= {pr1645v2PppBFPerfMCD7PEntry 385875968}

pr1645v2PppBFPerfMCD7PIfInBandwidth OBJECT-TYPE
   SYNTAX      Integer32
   MAX-ACCESS  read-only
   STATUS      current
   DESCRIPTION
      "Path: pppBundle.performance.multiclassInterfaces.mibCounters.d7Performance.ifInBandwidth

       unit name = bps
       formula = 8 * ; 8 /"
   ::= {pr1645v2PppBFPerfMCD7PEntry 268435456}

pr1645v2PppBFPerfMCD7PIfOutOctets OBJECT-TYPE
   SYNTAX      Counter64
   MAX-ACCESS  read-only
   STATUS      current
   DESCRIPTION
      "Path: pppBundle.performance.multiclassInterfaces.mibCounters.d7Performance.ifOutOctets

       64 bit unsigned wrappable counter."
   ::= {pr1645v2PppBFPerfMCD7PEntry 167772160}

pr1645v2PppBFPerfMCD7PIfOutUCPkts OBJECT-TYPE
   SYNTAX      Counter64
   MAX-ACCESS  read-only
   STATUS      current
   DESCRIPTION
      "Path: pppBundle.performance.multiclassInterfaces.mibCounters.d7Performance.ifOutUcastPkts

       64 bit unsigned wrappable counter."
   ::= {pr1645v2PppBFPerfMCD7PEntry 184549376}

pr1645v2PppBFPerfMCD7PIfOutNUCPkts OBJECT-TYPE
   SYNTAX      Counter64
   MAX-ACCESS  read-only
   STATUS      current
   DESCRIPTION
      "Path: pppBundle.performance.multiclassInterfaces.mibCounters.d7Performance.ifOutNUcastPkts

       64 bit unsigned wrappable counter."
   ::= {pr1645v2PppBFPerfMCD7PEntry 201326592}

pr1645v2PppBFPerfMCD7PIfOutBCPkts OBJECT-TYPE
   SYNTAX      Counter64
   MAX-ACCESS  read-only
   STATUS      current
   DESCRIPTION
      "Path: pppBundle.performance.multiclassInterfaces.mibCounters.d7Performance.ifOutBcastPkts

       64 bit unsigned wrappable counter."
   ::= {pr1645v2PppBFPerfMCD7PEntry 452984832}

pr1645v2PppBFPerfMCD7PIfOutMCPkts OBJECT-TYPE
   SYNTAX      Counter64
   MAX-ACCESS  read-only
   STATUS      current
   DESCRIPTION
      "Path: pppBundle.performance.multiclassInterfaces.mibCounters.d7Performance.ifOutMcastPkts

       64 bit unsigned wrappable counter."
   ::= {pr1645v2PppBFPerfMCD7PEntry 469762048}

pr1645v2PppBFPerfMCD7PIfOutDiscards OBJECT-TYPE
   SYNTAX      Counter64
   MAX-ACCESS  read-only
   STATUS      current
   DESCRIPTION
      "Path: pppBundle.performance.multiclassInterfaces.mibCounters.d7Performance.ifOutDiscards

       64 bit unsigned wrappable counter."
   ::= {pr1645v2PppBFPerfMCD7PEntry 218103808}

pr1645v2PppBFPerfMCD7PIfOutErrors OBJECT-TYPE
   SYNTAX      Counter64
   MAX-ACCESS  read-only
   STATUS      current
   DESCRIPTION
      "Path: pppBundle.performance.multiclassInterfaces.mibCounters.d7Performance.ifOutErrors

       64 bit unsigned wrappable counter."
   ::= {pr1645v2PppBFPerfMCD7PEntry 234881024}

pr1645v2PppBFPerfMCD7POutDropEx OBJECT-TYPE
   SYNTAX      Counter64
   MAX-ACCESS  read-only
   STATUS      current
   DESCRIPTION
      "Path: pppBundle.performance.multiclassInterfaces.mibCounters.d7Performance.ifOutDropLevelExceeded

       64 bit unsigned wrappable counter."
   ::= {pr1645v2PppBFPerfMCD7PEntry 352321536}

pr1645v2PppBFPerfMCD7POutDropNoArp OBJECT-TYPE
   SYNTAX      Counter64
   MAX-ACCESS  read-only
   STATUS      current
   DESCRIPTION
      "Path: pppBundle.performance.multiclassInterfaces.mibCounters.d7Performance.ifOutDiscardsNoArp

       64 bit unsigned wrappable counter."
   ::= {pr1645v2PppBFPerfMCD7PEntry 369098752}

pr1645v2PppBFPerfMCD7POutDropFilter OBJECT-TYPE
   SYNTAX      Counter64
   MAX-ACCESS  read-only
   STATUS      current
   DESCRIPTION
      "Path: pppBundle.performance.multiclassInterfaces.mibCounters.d7Performance.ifOutDiscardsFilter

       64 bit unsigned wrappable counter."
   ::= {pr1645v2PppBFPerfMCD7PEntry 402653184}

pr1645v2PppBFPerfMCD7PIfOutBandwidth OBJECT-TYPE
   SYNTAX      Integer32
   MAX-ACCESS  read-only
   STATUS      current
   DESCRIPTION
      "Path: pppBundle.performance.multiclassInterfaces.mibCounters.d7Performance.ifOutBandwidth

       unit name = bps
       formula = 8 * ; 8 /"
   ::= {pr1645v2PppBFPerfMCD7PEntry 285212672}

pr1645v2PppBFPerfMCD7PIfErrSec OBJECT-TYPE
   SYNTAX      Counter32
   MAX-ACCESS  read-only
   STATUS      current
   DESCRIPTION
      "Path: pppBundle.performance.multiclassInterfaces.mibCounters.d7Performance.ifErrSec

       32 bit unsigned wrappable counter."
   ::= {pr1645v2PppBFPerfMCD7PEntry 251658240}


pr1645v2PppBFFragCntr OBJECT IDENTIFIER ::= {pr1645v2PppBF 30}

pr1645v2PppBFFragCntrSSCTable OBJECT-TYPE
   SYNTAX      SEQUENCE OF Pr1645v2PppBFFragCntrEntry
   MAX-ACCESS  not-accessible
   STATUS      current
   DESCRIPTION
      ""
   ::= {pr1645v2PppBFFragCntr 1}

pr1645v2PppBFFragCntrEntry OBJECT-TYPE
   SYNTAX      Pr1645v2PppBFFragCntrEntry
   MAX-ACCESS  not-accessible
   STATUS      current
   DESCRIPTION
      ""
   INDEX      { pr1645v2PppBFFragCntrGlobalIx }
   ::= {pr1645v2PppBFFragCntrSSCTable 1}

Pr1645v2PppBFFragCntrEntry ::=
   SEQUENCE
      {
      pr1645v2PppBFFragCntrGlobalIx
         GlobalIndex,
      pr1645v2PppBFFragCntrBufferLimit
         Counter32,
      pr1645v2PppBFFragCntrFragQueued
         Counter32,
      pr1645v2PppBFFragCntrByteQueued
         Counter32,
      pr1645v2PppBFFragCntrFragQLenExceeded
         Counter32,
      pr1645v2PppBFFragCntrByteQLenExceeded
         Counter32,
      pr1645v2PppBFFragCntrFragReorder
         Counter32,
      pr1645v2PppBFFragCntrFragResync
         Counter32,
      pr1645v2PppBFFragCntrFragResync2
         Counter32,
      pr1645v2PppBFFragCntrFragResyncSent
         Counter32,
      pr1645v2PppBFFragCntrFragLost
         Counter32,
      pr1645v2PppBFFragCntrFragLate
         Counter32,
      pr1645v2PppBFFragCntrByteLate
         Counter32,
      pr1645v2PppBFFragCntrFragLostRcv
         Counter32,
      pr1645v2PppBFFragCntrFragDiscard
         Counter32,
      pr1645v2PppBFFragCntrByteDiscard
         Counter32,
      pr1645v2PppBFFragCntrCurrRangeLow
         Counter32,
      pr1645v2PppBFFragCntrCurrRangeHigh
         Counter32,
      pr1645v2PppBFFragCntrRxSeqNr
         Counter32,
      pr1645v2PppBFFragCntrTxSeqNr
         Counter32
      }

pr1645v2PppBFFragCntrGlobalIx OBJECT-TYPE
   SYNTAX      GlobalIndex
   MAX-ACCESS  not-accessible
   STATUS      current
   DESCRIPTION
      "The value of the tlsCntTreeGlobalIndex of the MANAGED OBJECT."
   ::= {pr1645v2PppBFFragCntrEntry 10}

pr1645v2PppBFFragCntrBufferLimit OBJECT-TYPE
   SYNTAX      Counter32
   MAX-ACCESS  read-only
   STATUS      current
   DESCRIPTION
      "Path: pppBundle.performance.fragmentCounters.bufferLimit

       32 bit unsigned wrappable counter."
   ::= {pr1645v2PppBFFragCntrEntry 16777216}

pr1645v2PppBFFragCntrFragQueued OBJECT-TYPE
   SYNTAX      Counter32
   MAX-ACCESS  read-only
   STATUS      current
   DESCRIPTION
      "Path: pppBundle.performance.fragmentCounters.fragQueued

       32 bit unsigned wrappable counter."
   ::= {pr1645v2PppBFFragCntrEntry 33554432}

pr1645v2PppBFFragCntrByteQueued OBJECT-TYPE
   SYNTAX      Counter32
   MAX-ACCESS  read-only
   STATUS      current
   DESCRIPTION
      "Path: pppBundle.performance.fragmentCounters.byteQueued

       32 bit unsigned wrappable counter."
   ::= {pr1645v2PppBFFragCntrEntry 50331648}

pr1645v2PppBFFragCntrFragQLenExceeded OBJECT-TYPE
   SYNTAX      Counter32
   MAX-ACCESS  read-only
   STATUS      current
   DESCRIPTION
      "Path: pppBundle.performance.fragmentCounters.fragQLenExceeded

       32 bit unsigned wrappable counter."
   ::= {pr1645v2PppBFFragCntrEntry 67108864}

pr1645v2PppBFFragCntrByteQLenExceeded OBJECT-TYPE
   SYNTAX      Counter32
   MAX-ACCESS  read-only
   STATUS      current
   DESCRIPTION
      "Path: pppBundle.performance.fragmentCounters.byteQLenExceeded

       32 bit unsigned wrappable counter."
   ::= {pr1645v2PppBFFragCntrEntry 83886080}

pr1645v2PppBFFragCntrFragReorder OBJECT-TYPE
   SYNTAX      Counter32
   MAX-ACCESS  read-only
   STATUS      current
   DESCRIPTION
      "Path: pppBundle.performance.fragmentCounters.fragReorder

       32 bit unsigned wrappable counter."
   ::= {pr1645v2PppBFFragCntrEntry 100663296}

pr1645v2PppBFFragCntrFragResync OBJECT-TYPE
   SYNTAX      Counter32
   MAX-ACCESS  read-only
   STATUS      current
   DESCRIPTION
      "Path: pppBundle.performance.fragmentCounters.fragResync

       32 bit unsigned wrappable counter."
   ::= {pr1645v2PppBFFragCntrEntry 117440512}

pr1645v2PppBFFragCntrFragResync2 OBJECT-TYPE
   SYNTAX      Counter32
   MAX-ACCESS  read-only
   STATUS      current
   DESCRIPTION
      "Path: pppBundle.performance.fragmentCounters.fragResync2

       32 bit unsigned wrappable counter."
   ::= {pr1645v2PppBFFragCntrEntry 134217728}

pr1645v2PppBFFragCntrFragResyncSent OBJECT-TYPE
   SYNTAX      Counter32
   MAX-ACCESS  read-only
   STATUS      current
   DESCRIPTION
      "Path: pppBundle.performance.fragmentCounters.fragResyncSent

       32 bit unsigned wrappable counter."
   ::= {pr1645v2PppBFFragCntrEntry 150994944}

pr1645v2PppBFFragCntrFragLost OBJECT-TYPE
   SYNTAX      Counter32
   MAX-ACCESS  read-only
   STATUS      current
   DESCRIPTION
      "Path: pppBundle.performance.fragmentCounters.fragLost

       32 bit unsigned wrappable counter."
   ::= {pr1645v2PppBFFragCntrEntry 167772160}

pr1645v2PppBFFragCntrFragLate OBJECT-TYPE
   SYNTAX      Counter32
   MAX-ACCESS  read-only
   STATUS      current
   DESCRIPTION
      "Path: pppBundle.performance.fragmentCounters.fragLate

       32 bit unsigned wrappable counter."
   ::= {pr1645v2PppBFFragCntrEntry 184549376}

pr1645v2PppBFFragCntrByteLate OBJECT-TYPE
   SYNTAX      Counter32
   MAX-ACCESS  read-only
   STATUS      current
   DESCRIPTION
      "Path: pppBundle.performance.fragmentCounters.byteLate

       32 bit unsigned wrappable counter."
   ::= {pr1645v2PppBFFragCntrEntry 201326592}

pr1645v2PppBFFragCntrFragLostRcv OBJECT-TYPE
   SYNTAX      Counter32
   MAX-ACCESS  read-only
   STATUS      current
   DESCRIPTION
      "Path: pppBundle.performance.fragmentCounters.fragLostRcv

       32 bit unsigned wrappable counter."
   ::= {pr1645v2PppBFFragCntrEntry 218103808}

pr1645v2PppBFFragCntrFragDiscard OBJECT-TYPE
   SYNTAX      Counter32
   MAX-ACCESS  read-only
   STATUS      current
   DESCRIPTION
      "Path: pppBundle.performance.fragmentCounters.fragDiscard

       32 bit unsigned wrappable counter."
   ::= {pr1645v2PppBFFragCntrEntry 234881024}

pr1645v2PppBFFragCntrByteDiscard OBJECT-TYPE
   SYNTAX      Counter32
   MAX-ACCESS  read-only
   STATUS      current
   DESCRIPTION
      "Path: pppBundle.performance.fragmentCounters.byteDiscard

       32 bit unsigned wrappable counter."
   ::= {pr1645v2PppBFFragCntrEntry 251658240}

pr1645v2PppBFFragCntrCurrRangeLow OBJECT-TYPE
   SYNTAX      Counter32
   MAX-ACCESS  read-only
   STATUS      current
   DESCRIPTION
      "Path: pppBundle.performance.fragmentCounters.currRangeLow

       32 bit unsigned wrappable counter."
   ::= {pr1645v2PppBFFragCntrEntry 268435456}

pr1645v2PppBFFragCntrCurrRangeHigh OBJECT-TYPE
   SYNTAX      Counter32
   MAX-ACCESS  read-only
   STATUS      current
   DESCRIPTION
      "Path: pppBundle.performance.fragmentCounters.currRangeHigh

       32 bit unsigned wrappable counter."
   ::= {pr1645v2PppBFFragCntrEntry 285212672}

pr1645v2PppBFFragCntrRxSeqNr OBJECT-TYPE
   SYNTAX      Counter32
   MAX-ACCESS  read-only
   STATUS      current
   DESCRIPTION
      "Path: pppBundle.performance.fragmentCounters.rxSeqNr

       32 bit unsigned wrappable counter."
   ::= {pr1645v2PppBFFragCntrEntry 301989888}

pr1645v2PppBFFragCntrTxSeqNr OBJECT-TYPE
   SYNTAX      Counter32
   MAX-ACCESS  read-only
   STATUS      current
   DESCRIPTION
      "Path: pppBundle.performance.fragmentCounters.txSeqNr

       32 bit unsigned wrappable counter."
   ::= {pr1645v2PppBFFragCntrEntry 318767104}



fr1645v2PppBF OBJECT IDENTIFIER ::= {r1645v2PppBF 13}


fr1645v2PppBFAlarm OBJECT IDENTIFIER ::= {fr1645v2PppBF 207}

fr1645v2PppBFAlarmSSCTable OBJECT-TYPE
   SYNTAX      SEQUENCE OF Fr1645v2PppBFAlarmEntry
   MAX-ACCESS  not-accessible
   STATUS      current
   DESCRIPTION
      "IfAlarmInfo"
   ::= {fr1645v2PppBFAlarm 1}

fr1645v2PppBFAlarmEntry OBJECT-TYPE
   SYNTAX      Fr1645v2PppBFAlarmEntry
   MAX-ACCESS  not-accessible
   STATUS      current
   DESCRIPTION
      ""
   INDEX      { fr1645v2PppBFAlarmGlobalIx }
   ::= {fr1645v2PppBFAlarmSSCTable 1}

Fr1645v2PppBFAlarmEntry ::=
   SEQUENCE
      {
      fr1645v2PppBFAlarmGlobalIx
         GlobalIndex,
      fr1645v2PppBFAlarmDiscriminator
         Integer32,
      fr1645v2PppBFAlarmCurrent
         Integer32,
      fr1645v2PppBFAlarmPrevious
         Integer32,
      fr1645v2PppBFAlarmMask
         Integer32,
      fr1645v2PppBFAlarmLevLinkDown
         Integer32
      }

fr1645v2PppBFAlarmGlobalIx OBJECT-TYPE
   SYNTAX      GlobalIndex
   MAX-ACCESS  not-accessible
   STATUS      current
   DESCRIPTION
      "The value of the tlsCntTreeGlobalIndex of the MANAGED OBJECT."
   ::= {fr1645v2PppBFAlarmEntry 10}

fr1645v2PppBFAlarmDiscriminator OBJECT-TYPE
   SYNTAX      Integer32
   MAX-ACCESS  read-only
   STATUS      current
   DESCRIPTION
      "Path: pppBundle.alarms.alarmInfo.discriminator"
   ::= {fr1645v2PppBFAlarmEntry 16777216}

fr1645v2PppBFAlarmCurrent OBJECT-TYPE
   SYNTAX      Integer32
   MAX-ACCESS  read-only
   STATUS      current
   DESCRIPTION
      "Path: pppBundle.alarms.alarmInfo.currentAlarms

       Bit meanings:
               bit 0 = linkDown"
   ::= {fr1645v2PppBFAlarmEntry 33554432}

fr1645v2PppBFAlarmPrevious OBJECT-TYPE
   SYNTAX      Integer32
   MAX-ACCESS  read-only
   STATUS      current
   DESCRIPTION
      "Path: pppBundle.alarms.alarmInfo.previousAlarms

       Bit meanings:
               bit 0 = linkDown"
   ::= {fr1645v2PppBFAlarmEntry 50331648}

fr1645v2PppBFAlarmMask OBJECT-TYPE
   SYNTAX      Integer32
   MAX-ACCESS  read-only
   STATUS      current
   DESCRIPTION
      "Path: pppBundle.alarms.alarmInfo.alarmMask

       Bit meanings:
               bit 0 = linkDown"
   ::= {fr1645v2PppBFAlarmEntry 67108864}

fr1645v2PppBFAlarmLevLinkDown OBJECT-TYPE
   SYNTAX      Integer32
   MAX-ACCESS  read-only
   STATUS      current
   DESCRIPTION
      "Path: pppBundle.alarms.alarmInfo.alarmLevel.linkDown"
   ::= {fr1645v2PppBFAlarmEntry 83951616}


fr1645v2PppBFAlarmE2 OBJECT IDENTIFIER ::= {fr1645v2PppBFAlarm 2}

fr1645v2PppBFAlarmE2Entry OBJECT IDENTIFIER ::= {fr1645v2PppBFAlarmE2 1}

fr1645v2PppBFAlarmE2LinkDown OBJECT IDENTIFIER ::= {fr1645v2PppBFAlarmE2Entry 10}

fr1645v2PppBFAlarmE2LinkDownPfx OBJECT IDENTIFIER ::= {fr1645v2PppBFAlarmE2LinkDown 0}

fr1645v2PppBFAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'pppBundleFw'
                (root='router1645') has changed from the ON to the OFF state."
   ::= {fr1645v2PppBFAlarmE2LinkDownPfx 1}

fr1645v2PppBFAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'pppBundleFw'
                (root='router1645') has changed from the OFF to the ON state."
   ::= {fr1645v2PppBFAlarmE2LinkDownPfx 2}



ar1645v2PppBF OBJECT IDENTIFIER ::= {r1645v2PppBF 16}


ar1645v2PppBFResetTxSeqNr OBJECT IDENTIFIER ::= {ar1645v2PppBF 504}

ar1645v2PppBFResetTxSeqNrTable OBJECT-TYPE
   SYNTAX      SEQUENCE OF Ar1645v2PppBFResetTxSeqNrEntry
   MAX-ACCESS  not-accessible
   STATUS      current
   DESCRIPTION
      "reset the bundle's tx sequence nr"
   ::= {ar1645v2PppBFResetTxSeqNr 1}

ar1645v2PppBFResetTxSeqNrEntry OBJECT-TYPE
   SYNTAX      Ar1645v2PppBFResetTxSeqNrEntry
   MAX-ACCESS  not-accessible
   STATUS      current
   DESCRIPTION
      ""
   INDEX      { ar1645v2PppBFResetTxSeqNrGlobalIx }
   ::= {ar1645v2PppBFResetTxSeqNrTable 1}

Ar1645v2PppBFResetTxSeqNrEntry ::=
   SEQUENCE
      {
      ar1645v2PppBFResetTxSeqNrGlobalIx
         GlobalIndex,
      ar1645v2PppBFResetTxSeqNrValue
         Integer32
      }

ar1645v2PppBFResetTxSeqNrGlobalIx OBJECT-TYPE
   SYNTAX      GlobalIndex
   MAX-ACCESS  not-accessible
   STATUS      current
   DESCRIPTION
      "The value of the tlsCntTreeGlobalIndex of the MANAGED OBJECT."
   ::= {ar1645v2PppBFResetTxSeqNrEntry 10}

ar1645v2PppBFResetTxSeqNrValue OBJECT-TYPE
   SYNTAX      Integer32
   MAX-ACCESS  read-write
   STATUS      current
   DESCRIPTION
      "Path: pppBundle.actions.resetTxSeqNr"
   ::= {ar1645v2PppBFResetTxSeqNrEntry 2147483648}


ar1645v2PppBFClearCounters OBJECT IDENTIFIER ::= {ar1645v2PppBF 263}

ar1645v2PppBFClearCountersTable OBJECT-TYPE
   SYNTAX      SEQUENCE OF Ar1645v2PppBFClearCountersEntry
   MAX-ACCESS  not-accessible
   STATUS      current
   DESCRIPTION
      "reset counters"
   ::= {ar1645v2PppBFClearCounters 1}

ar1645v2PppBFClearCountersEntry OBJECT-TYPE
   SYNTAX      Ar1645v2PppBFClearCountersEntry
   MAX-ACCESS  not-accessible
   STATUS      current
   DESCRIPTION
      ""
   INDEX      { ar1645v2PppBFClearCountersGlobalIx }
   ::= {ar1645v2PppBFClearCountersTable 1}

Ar1645v2PppBFClearCountersEntry ::=
   SEQUENCE
      {
      ar1645v2PppBFClearCountersGlobalIx
         GlobalIndex,
      ar1645v2PppBFClearCountersValue
         Integer32
      }

ar1645v2PppBFClearCountersGlobalIx OBJECT-TYPE
   SYNTAX      GlobalIndex
   MAX-ACCESS  not-accessible
   STATUS      current
   DESCRIPTION
      "The value of the tlsCntTreeGlobalIndex of the MANAGED OBJECT."
   ::= {ar1645v2PppBFClearCountersEntry 10}

ar1645v2PppBFClearCountersValue OBJECT-TYPE
   SYNTAX      Integer32
   MAX-ACCESS  read-write
   STATUS      current
   DESCRIPTION
      "Path: pppBundle.actions.clearCounters"
   ::= {ar1645v2PppBFClearCountersEntry 2147483648}



END
