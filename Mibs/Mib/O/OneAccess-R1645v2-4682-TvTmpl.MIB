OneAccess-R1645v2-4682-TvTmpl DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2TvTmpl OBJECT IDENTIFIER ::= {r1645Rootv2 4682}

r1645v2TvTmplMOProp OBJECT IDENTIFIER ::= {r1645v2TvTmpl 1}

r1645v2TvTmplMOPropEntry OBJECT IDENTIFIER ::= {r1645v2TvTmplMOProp 1}

r1645v2TvTmplMOPropPath OBJECT-TYPE
   SYNTAX      ContainmentPath
   MAX-ACCESS  read-only
   STATUS      current
   DESCRIPTION
      "Textual description of the containment tree from the instance of
       the root object down to the instance of the current object."
   ::= {r1645v2TvTmplMOPropEntry 3}

r1645v2TvTmplMOPropRev OBJECT-TYPE
   SYNTAX      ObjectRevision
   MAX-ACCESS  read-only
   STATUS      current
   DESCRIPTION
      "This value corresponds with the revision of the MANAGED OBJECT."
   ::= {r1645v2TvTmplMOPropEntry 4}



er1645v2TvTmpl OBJECT IDENTIFIER ::= {r1645v2TvTmpl 11}


er1645v2TvTmplName OBJECT-TYPE
   SYNTAX      DisplayString
   MAX-ACCESS  read-write
   STATUS      current
   DESCRIPTION
      "Path: tunnels.editConf.name
       Info: config interface name"
   ::= {er1645v2TvTmpl 7}


er1645v2TvTmplIcf OBJECT IDENTIFIER ::= {er1645v2TvTmpl 4}

er1645v2TvTmplIcfSSCTable OBJECT-TYPE
   SYNTAX      SEQUENCE OF Er1645v2TvTmplIcfEntry
   MAX-ACCESS  not-accessible
   STATUS      current
   DESCRIPTION
      ""
   ::= {er1645v2TvTmplIcf 1}

er1645v2TvTmplIcfEntry OBJECT-TYPE
   SYNTAX      Er1645v2TvTmplIcfEntry
   MAX-ACCESS  not-accessible
   STATUS      current
   DESCRIPTION
      ""
   INDEX      { er1645v2TvTmplIcfTableIx }
   ::= {er1645v2TvTmplIcfSSCTable 1}

Er1645v2TvTmplIcfEntry ::=
   SEQUENCE
      {
      er1645v2TvTmplIcfActions
         VariableLengthTableActions,
      er1645v2TvTmplIcfTableIx
         TableIndex,
      er1645v2TvTmplIcfName
         DisplayString,
      er1645v2TvTmplIcfRemark
         DisplayString,
      er1645v2TvTmplIcfAdminStatus
         INTEGER,
      er1645v2TvTmplIcfMode
         INTEGER,
      er1645v2TvTmplIcfPriorityPolicy
         DisplayString,
      er1645v2TvTmplIcfIpVrfRouter
         DisplayString,
      er1645v2TvTmplIcfIpAdr
         IpAddress,
      er1645v2TvTmplIcfIpNetm
         IpAddress,
      er1645v2TvTmplIcfIpSNetName
         INTEGER,
      er1645v2TvTmplIcfIpSNetCust
         DisplayString,
      er1645v2TvTmplIcfIpRem
         IpAddress,
      er1645v2TvTmplIcfIpUnnumbered
         DisplayString,
      er1645v2TvTmplIcfIpAcceptLocAddr
         INTEGER,
      er1645v2TvTmplIcfIpAcceptRemAddr
         INTEGER,
      er1645v2TvTmplIcfIpGwPref
         Integer32,
      er1645v2TvTmplIcfIpRsn
         INTEGER,
      er1645v2TvTmplIcfIpMtu
         Integer32,
      er1645v2TvTmplIcfIpMssAdjust
         INTEGER,
      er1645v2TvTmplIcfIpRipMetric
         Integer32,
      er1645v2TvTmplIcfIpRipMetricOut
         Integer32,
      er1645v2TvTmplIcfIpRipMode
         INTEGER,
      er1645v2TvTmplIcfIpRipTxVersion
         INTEGER,
      er1645v2TvTmplIcfIpRipRxVersion
         INTEGER,
      er1645v2TvTmplIcfIpRipSplitHorizon
         INTEGER,
      er1645v2TvTmplIcfIpRipAuth
         INTEGER,
      er1645v2TvTmplIcfIpRipFilter
         DisplayString,
      er1645v2TvTmplIcfIpRipFilterIn
         DisplayString,
      er1645v2TvTmplIcfIpRipSnapshot
         INTEGER,
      er1645v2TvTmplIcfIpRipClearNextHop
         INTEGER,
      er1645v2TvTmplIcfIpAccPol
         DisplayString,
      er1645v2TvTmplIcfIpAB
         DisplayString,
      er1645v2TvTmplIcfIpMA
         INTEGER,
      er1645v2TvTmplIcfIpMF
         Integer32,
      er1645v2TvTmplIcfIpDB
         INTEGER,
      er1645v2TvTmplIcfIpIR
         INTEGER,
      er1645v2TvTmplIcfIpIgmp
         INTEGER,
      er1645v2TvTmplIcfIpNN
         DisplayString,
      er1645v2TvTmplIcfIpPimMode
         INTEGER,
      er1645v2TvTmplIcfIpPimDrPriority
         Counter32,
      er1645v2TvTmplIcfIpPimHelloTime
         TimeTicks,
      er1645v2TvTmplIcfIpPimPropagationDelay
         TimeTicks,
      er1645v2TvTmplIcfIpPimOverrideInterval
         TimeTicks,
      er1645v2TvTmplIcfIpPimBsrBorder
         INTEGER,
      er1645v2TvTmplIcfIpPimTtlThreshold
         Integer32,
      er1645v2TvTmplIcfIpIMNetworkUnreachable
         INTEGER,
      er1645v2TvTmplIcfIpIMHostUnreachable
         INTEGER,
      er1645v2TvTmplIcfIpIMProtocolUnreachable
         INTEGER,
      er1645v2TvTmplIcfIpIMPortUnreachable
         INTEGER,
      er1645v2TvTmplIcfIpIMMtuExceeded
         INTEGER,
      er1645v2TvTmplIcfIpIMAdminProhibited
         INTEGER,
      er1645v2TvTmplIcfIpIMTtlExceeded
         INTEGER,
      er1645v2TvTmplIcfIpIMRedirect
         INTEGER,
      er1645v2TvTmplIcfBridgingAccList
         DisplayString,
      er1645v2TvTmplIcfBridgingInACL
         DisplayString,
      er1645v2TvTmplIcfBridgingTp
         DisplayString,
      er1645v2TvTmplIcfBridgingBrGrp
         DisplayString,
      er1645v2TvTmplIcfBridgingLimBC
         INTEGER,
      er1645v2TvTmplIcfBridgingPrivateMode
         INTEGER,
      er1645v2TvTmplIcfBridgingLearning
         INTEGER,
      er1645v2TvTmplIcfBridgingMaxCacheSize
         INTEGER,
      er1645v2TvTmplIcfBridgingRelearnDropOnRelearn
         INTEGER,
      er1645v2TvTmplIcfBridgingRelearnShutdownThreshold
         Integer32,
      er1645v2TvTmplIcfBridgingRelearnShutdownTime
         TimeTicks,
      er1645v2TvTmplIcfBridgingRelearnLoopDetection
         INTEGER,
      er1645v2TvTmplIcfBridgingRelearnLoopDetectionInterval
         TimeTicks,
      er1645v2TvTmplIcfBridgingVlanMemberShip
         INTEGER,
      er1645v2TvTmplIcfBridgingVlTUntaggedAction
         INTEGER,
      er1645v2TvTmplIcfBridgingVlTUntaggedTagInfoTpid
         INTEGER,
      er1645v2TvTmplIcfBridgingVlTUntaggedTagInfoVid
         Integer32,
      er1645v2TvTmplIcfBridgingVlTUnknownVlansAction
         INTEGER,
      er1645v2TvTmplIcfBridgingVlTUnknownVlansTagInfoTpid
         INTEGER,
      er1645v2TvTmplIcfBridgingVlTUnknownVlansTagInfoVid
         Integer32,
      er1645v2TvTmplIcfBridgingDot1adType
         INTEGER,
      er1645v2TvTmplIcfBridgingPriority
         Integer32,
      er1645v2TvTmplIcfBridgingPathCost
         Integer32,
      er1645v2TvTmplIcfBridgingInternalPathCost
         Integer32,
      er1645v2TvTmplIcfBridgingTCD
         INTEGER,
      er1645v2TvTmplIcfBridgingRestrictedRole
         INTEGER,
      er1645v2TvTmplIcfBridgingAdminEdge
         INTEGER,
      er1645v2TvTmplIcfBridgingOamMacDeviceMac
         DisplayString,
      er1645v2TvTmplIcfBridgingOamMacUserMac
         OCTET STRING,
      er1645v2TvTmplIcfBridgingOamMacBridgeMac
         DisplayString,
      er1645v2TvTmplIcfBridgingMgmtInline
         INTEGER,
      er1645v2TvTmplIcfBridgingL2ptMode
         INTEGER,
      er1645v2TvTmplIcfBridgingL2ptProtocols
         Integer32,
      er1645v2TvTmplIcfBridgingL2ptDestMac
         OCTET STRING,
      er1645v2TvTmplIcfBridgingL2ptCos
         INTEGER,
      er1645v2TvTmplIcfBridgingL2ptDropThrStp
         INTEGER,
      er1645v2TvTmplIcfBridgingL2ptDropThrLldp
         INTEGER,
      er1645v2TvTmplIcfBridgingL2ptDropThrOam
         INTEGER,
      er1645v2TvTmplIcfBridgingL2ptDropThrCdp
         INTEGER,
      er1645v2TvTmplIcfBridgingL2ptDropThrVtp
         INTEGER,
      er1645v2TvTmplIcfBridgingL2ptDropThrLacp
         INTEGER,
      er1645v2TvTmplIcfBridgingL2ptDropThrEfmOam
         INTEGER,
      er1645v2TvTmplIcfBridgingL2ptDropThrPvst
         INTEGER,
      er1645v2TvTmplIcfBridgingL2ptDropThrMmrp
         INTEGER,
      er1645v2TvTmplIcfBridgingL2ptDropThrMvrp
         INTEGER,
      er1645v2TvTmplIcfBridgingL2ptDropThrGvrp
         INTEGER,
      er1645v2TvTmplIcfBridgingL2ptDropThrGmrp
         INTEGER,
      er1645v2TvTmplIcfBridgingL2ptDropThrDtp
         INTEGER,
      er1645v2TvTmplIcfBridgingL2ptDropThrPagp
         INTEGER,
      er1645v2TvTmplIcfBridgingL2ptDropThrUdld
         INTEGER,
      er1645v2TvTmplIcfL2tpLocalIpAddress
         IpAddress,
      er1645v2TvTmplIcfL2tpRemoteIpAddress
         IpAddress,
      er1645v2TvTmplIcfL2tpRemoteDnsName
         DisplayString,
      er1645v2TvTmplIcfL2tpAuthen
         INTEGER,
      er1645v2TvTmplIcfL2tpPppNam
         DisplayString,
      er1645v2TvTmplIcfL2tpPppSec
         DisplayString,
      er1645v2TvTmplIcfL2tpEncMPppSec
         INTEGER,
      er1645v2TvTmplIcfL2tpEncPppSec
         DisplayString,
      er1645v2TvTmplIcfL2tpLnkMOperation
         INTEGER,
      er1645v2TvTmplIcfL2tpLnkMInterval
         TimeTicks,
      er1645v2TvTmplIcfL2tpLnkMRepTimeOut
         TimeTicks,
      er1645v2TvTmplIcfL2tpLnkMFailsPrmt
         Integer32,
      er1645v2TvTmplIcfL2tpType
         INTEGER,
      er1645v2TvTmplIcfL2tpDataseqnr
         INTEGER,
      er1645v2TvTmplIcfL2tpIpsecFdx
         DisplayString,
      er1645v2TvTmplIcfL2tpIpsecHdxIn
         DisplayString,
      er1645v2TvTmplIcfL2tpIpsecHdxOut
         DisplayString,
      er1645v2TvTmplIcfL2tpIpsecPsCfg
         DisplayString,
      er1645v2TvTmplIcfL2tpIpsecPsLIdIp
         IpAddress,
      er1645v2TvTmplIcfL2tpIpsecPsLIdHn
         DisplayString,
      er1645v2TvTmplIcfL2tpIpsecPsLIdUn
         DisplayString,
      er1645v2TvTmplIcfL2tpIpsecPsRIdIp
         IpAddress,
      er1645v2TvTmplIcfL2tpIpsecPsRIdHn
         DisplayString,
      er1645v2TvTmplIcfL2tpIpsecPsRIdUn
         DisplayString,
      er1645v2TvTmplIcfL2tpIpsecPsKey
         DisplayString,
      er1645v2TvTmplIcfL2tpIpsecPsEncMKey
         INTEGER,
      er1645v2TvTmplIcfL2tpIpsecPsEncKey
         DisplayString,
      er1645v2TvTmplIcfL2tpIpsecPsPIdProt
         INTEGER,
      er1645v2TvTmplIcfL2tpIpsecPsPIdLocAddr
         IpAddress,
      er1645v2TvTmplIcfL2tpIpsecPsPIdLocMask
         IpAddress,
      er1645v2TvTmplIcfL2tpIpsecPsPIdLocPort
         INTEGER,
      er1645v2TvTmplIcfL2tpIpsecPsPIdRemAddr
         IpAddress,
      er1645v2TvTmplIcfL2tpIpsecPsPIdRemMask
         IpAddress,
      er1645v2TvTmplIcfL2tpIpsecPsPIdRemPort
         INTEGER,
      er1645v2TvTmplIcfL2tpIpsecCeCfg
         DisplayString,
      er1645v2TvTmplIcfL2tpIpsecCeLIdIp
         IpAddress,
      er1645v2TvTmplIcfL2tpIpsecCeLIdHn
         DisplayString,
      er1645v2TvTmplIcfL2tpIpsecCeLIdUn
         DisplayString,
      er1645v2TvTmplIcfL2tpIpsecCeLIdDn
         DisplayString,
      er1645v2TvTmplIcfL2tpIpsecCeRIdIp
         IpAddress,
      er1645v2TvTmplIcfL2tpIpsecCeRIdHn
         DisplayString,
      er1645v2TvTmplIcfL2tpIpsecCeRIdUn
         DisplayString,
      er1645v2TvTmplIcfL2tpIpsecCeRIdDn
         DisplayString,
      er1645v2TvTmplIcfL2tpIpsecCePIdProt
         INTEGER,
      er1645v2TvTmplIcfL2tpIpsecCePIdLocAddr
         IpAddress,
      er1645v2TvTmplIcfL2tpIpsecCePIdLocMask
         IpAddress,
      er1645v2TvTmplIcfL2tpIpsecCePIdLocPort
         INTEGER,
      er1645v2TvTmplIcfL2tpIpsecCePIdRemAddr
         IpAddress,
      er1645v2TvTmplIcfL2tpIpsecCePIdRemMask
         IpAddress,
      er1645v2TvTmplIcfL2tpIpsecCePIdRemPort
         INTEGER,
      er1645v2TvTmplIcfL2tpKeepaliveTO
         Integer32,
      er1645v2TvTmplIcfL2tpNoTraffT0
         Integer32,
      er1645v2TvTmplIcfL2tpMode
         INTEGER,
      er1645v2TvTmplIcfL2tpAuth
         INTEGER,
      er1645v2TvTmplIcfL2tpSecret
         DisplayString,
      er1645v2TvTmplIcfL2tpTos
         INTEGER,
      er1645v2TvTmplIcfL2tpRetrans
         Integer32,
      er1645v2TvTmplIcfL2tpTransmitws
         Integer32,
      er1645v2TvTmplIcfL2tpRcsws
         Integer32,
      er1645v2TvTmplIcfL2tpUdpcheck
         INTEGER,
      er1645v2TvTmplIcfL2tpCalledNr
         DisplayString,
      er1645v2TvTmplIcfL2tpSpeed
         Integer32,
      er1645v2TvTmplIcfL2tpMtu
         Integer32,
      er1645v2TvTmplIcfL2tpHostName
         DisplayString,
      er1645v2TvTmplIcfBackupInterface
         DisplayString,
      er1645v2TvTmplIcfBackupTimeOut
         Integer32,
      er1645v2TvTmplIcfBackupAutoRetry
         INTEGER,
      er1645v2TvTmplIcfInbBwCir
         Integer32,
      er1645v2TvTmplIcfInbBwTc
         INTEGER,
      er1645v2TvTmplIcfInbBwCorrType
         INTEGER,
      er1645v2TvTmplIcfInbBwCorrPredefEncapsFrameRelay
         DisplayString,
      er1645v2TvTmplIcfInbBwCorrPredefEncapsPpp
         DisplayString,
      er1645v2TvTmplIcfInbBwCorrPredefEncapsAtmHl
         INTEGER,
      er1645v2TvTmplIcfInbBwCorrPredefEncapsAtmMp
         INTEGER,
      er1645v2TvTmplIcfInbBwCorrPredefEncapsHdlc
         DisplayString,
      er1645v2TvTmplIcfInbBwCorrPredefEncapsEfmFs
         Integer32,
      er1645v2TvTmplIcfInbBwCorrPredefEncapsEfmIb
         Integer32,
      er1645v2TvTmplIcfInbBwCorrPredefMode
         INTEGER,
      er1645v2TvTmplIcfInbBwCorrManualOverhead
         Integer32,
      er1645v2TvTmplIcfInbBwCorrManualFrameData
         Counter32,
      er1645v2TvTmplIcfInbBwCorrManualFrameHeader
         Counter32,
      er1645v2TvTmplIcfInbBwMaxFifoQLen
         Integer32,
      er1645v2TvTmplIcfInbBwPriorityPolicy
         DisplayString,
      er1645v2TvTmplIcfBandwidthMode
         INTEGER,
      er1645v2TvTmplIcfBandwidthCir
         Integer32,
      er1645v2TvTmplIcfBandwidthEir
         Integer32,
      er1645v2TvTmplIcfBandwidthUnit
         INTEGER,
      er1645v2TvTmplIcfBandwidthTc
         INTEGER,
      er1645v2TvTmplIcfBandwidthTcFactor
         INTEGER,
      er1645v2TvTmplIcfBandwidthCorrType
         INTEGER,
      er1645v2TvTmplIcfBandwidthCorrPredefEncapsFrameRelay
         DisplayString,
      er1645v2TvTmplIcfBandwidthCorrPredefEncapsPpp
         DisplayString,
      er1645v2TvTmplIcfBandwidthCorrPredefEncapsAtmHl
         INTEGER,
      er1645v2TvTmplIcfBandwidthCorrPredefEncapsAtmMp
         INTEGER,
      er1645v2TvTmplIcfBandwidthCorrPredefEncapsHdlc
         DisplayString,
      er1645v2TvTmplIcfBandwidthCorrPredefEncapsEfmFs
         Integer32,
      er1645v2TvTmplIcfBandwidthCorrPredefEncapsEfmIb
         Integer32,
      er1645v2TvTmplIcfBandwidthCorrPredefMode
         INTEGER,
      er1645v2TvTmplIcfBandwidthCorrManualOverhead
         Integer32,
      er1645v2TvTmplIcfBandwidthCorrManualFrameData
         Counter32,
      er1645v2TvTmplIcfBandwidthCorrManualFrameHeader
         Counter32,
      er1645v2TvTmplIcfBandwidthMaxFifoQLen
         Integer32,
      er1645v2TvTmplIcfBandwidthDeFlagCir
         INTEGER,
      er1645v2TvTmplIcfBandwidthDeFlagEir
         INTEGER,
      er1645v2TvTmplIcfBandwidthDeFlagViolate
         INTEGER,
      er1645v2TvTmplIcfBandwidthActCirActNone
         OCTET STRING,
      er1645v2TvTmplIcfBandwidthActCirActEthCos1
         INTEGER,
      er1645v2TvTmplIcfBandwidthActCirActEthDei1
         INTEGER,
      er1645v2TvTmplIcfBandwidthActCirActEthCos2
         INTEGER,
      er1645v2TvTmplIcfBandwidthActCirActEthDei2
         INTEGER,
      er1645v2TvTmplIcfBandwidthActCirActEthCos3
         INTEGER,
      er1645v2TvTmplIcfBandwidthActCirActEthDei3
         INTEGER,
      er1645v2TvTmplIcfBandwidthActCirActEthCos4
         INTEGER,
      er1645v2TvTmplIcfBandwidthActCirActEthDei4
         INTEGER,
      er1645v2TvTmplIcfBandwidthActCirActEthCos5
         INTEGER,
      er1645v2TvTmplIcfBandwidthActCirActEthDei5
         INTEGER,
      er1645v2TvTmplIcfBandwidthActCirActEthCos6
         INTEGER,
      er1645v2TvTmplIcfBandwidthActCirActEthDei6
         INTEGER,
      er1645v2TvTmplIcfBandwidthActCirActEthCos7
         INTEGER,
      er1645v2TvTmplIcfBandwidthActCirActEthDei7
         INTEGER,
      er1645v2TvTmplIcfBandwidthActCirActEthCos8
         INTEGER,
      er1645v2TvTmplIcfBandwidthActCirActEthDei8
         INTEGER,
      er1645v2TvTmplIcfBandwidthActCirActEthTos
         INTEGER,
      er1645v2TvTmplIcfBandwidthActCirActEthQueue
         INTEGER,
      er1645v2TvTmplIcfBandwidthActCirActEthDrpLev
         INTEGER,
      er1645v2TvTmplIcfBandwidthActCirActEthDeFlag
         INTEGER,
      er1645v2TvTmplIcfBandwidthActCirActIpTos
         INTEGER,
      er1645v2TvTmplIcfBandwidthActCirActIpQueue
         INTEGER,
      er1645v2TvTmplIcfBandwidthActCirActIpDrpLev
         INTEGER,
      er1645v2TvTmplIcfBandwidthActCirActIpDeFlag
         INTEGER,
      er1645v2TvTmplIcfBandwidthActEirActNone
         OCTET STRING,
      er1645v2TvTmplIcfBandwidthActEirActEthCos1
         INTEGER,
      er1645v2TvTmplIcfBandwidthActEirActEthDei1
         INTEGER,
      er1645v2TvTmplIcfBandwidthActEirActEthCos2
         INTEGER,
      er1645v2TvTmplIcfBandwidthActEirActEthDei2
         INTEGER,
      er1645v2TvTmplIcfBandwidthActEirActEthCos3
         INTEGER,
      er1645v2TvTmplIcfBandwidthActEirActEthDei3
         INTEGER,
      er1645v2TvTmplIcfBandwidthActEirActEthCos4
         INTEGER,
      er1645v2TvTmplIcfBandwidthActEirActEthDei4
         INTEGER,
      er1645v2TvTmplIcfBandwidthActEirActEthCos5
         INTEGER,
      er1645v2TvTmplIcfBandwidthActEirActEthDei5
         INTEGER,
      er1645v2TvTmplIcfBandwidthActEirActEthCos6
         INTEGER,
      er1645v2TvTmplIcfBandwidthActEirActEthDei6
         INTEGER,
      er1645v2TvTmplIcfBandwidthActEirActEthCos7
         INTEGER,
      er1645v2TvTmplIcfBandwidthActEirActEthDei7
         INTEGER,
      er1645v2TvTmplIcfBandwidthActEirActEthCos8
         INTEGER,
      er1645v2TvTmplIcfBandwidthActEirActEthDei8
         INTEGER,
      er1645v2TvTmplIcfBandwidthActEirActEthTos
         INTEGER,
      er1645v2TvTmplIcfBandwidthActEirActEthQueue
         INTEGER,
      er1645v2TvTmplIcfBandwidthActEirActEthDrpLev
         INTEGER,
      er1645v2TvTmplIcfBandwidthActEirActEthDeFlag
         INTEGER,
      er1645v2TvTmplIcfBandwidthActEirActIpTos
         INTEGER,
      er1645v2TvTmplIcfBandwidthActEirActIpQueue
         INTEGER,
      er1645v2TvTmplIcfBandwidthActEirActIpDrpLev
         INTEGER,
      er1645v2TvTmplIcfBandwidthActEirActIpDeFlag
         INTEGER,
      er1645v2TvTmplIcfBandwidthActViolActNone
         OCTET STRING,
      er1645v2TvTmplIcfBandwidthActViolActDrop
         OCTET STRING,
      er1645v2TvTmplIcfBandwidthActViolActEthCos1
         INTEGER,
      er1645v2TvTmplIcfBandwidthActViolActEthDei1
         INTEGER,
      er1645v2TvTmplIcfBandwidthActViolActEthCos2
         INTEGER,
      er1645v2TvTmplIcfBandwidthActViolActEthDei2
         INTEGER,
      er1645v2TvTmplIcfBandwidthActViolActEthCos3
         INTEGER,
      er1645v2TvTmplIcfBandwidthActViolActEthDei3
         INTEGER,
      er1645v2TvTmplIcfBandwidthActViolActEthCos4
         INTEGER,
      er1645v2TvTmplIcfBandwidthActViolActEthDei4
         INTEGER,
      er1645v2TvTmplIcfBandwidthActViolActEthCos5
         INTEGER,
      er1645v2TvTmplIcfBandwidthActViolActEthDei5
         INTEGER,
      er1645v2TvTmplIcfBandwidthActViolActEthCos6
         INTEGER,
      er1645v2TvTmplIcfBandwidthActViolActEthDei6
         INTEGER,
      er1645v2TvTmplIcfBandwidthActViolActEthCos7
         INTEGER,
      er1645v2TvTmplIcfBandwidthActViolActEthDei7
         INTEGER,
      er1645v2TvTmplIcfBandwidthActViolActEthCos8
         INTEGER,
      er1645v2TvTmplIcfBandwidthActViolActEthDei8
         INTEGER,
      er1645v2TvTmplIcfBandwidthActViolActEthTos
         INTEGER,
      er1645v2TvTmplIcfBandwidthActViolActEthQueue
         INTEGER,
      er1645v2TvTmplIcfBandwidthActViolActEthDrpLev
         INTEGER,
      er1645v2TvTmplIcfBandwidthActViolActEthDeFlag
         INTEGER,
      er1645v2TvTmplIcfBandwidthActViolActIpTos
         INTEGER,
      er1645v2TvTmplIcfBandwidthActViolActIpQueue
         INTEGER,
      er1645v2TvTmplIcfBandwidthActViolActIpDrpLev
         INTEGER,
      er1645v2TvTmplIcfBandwidthActViolActIpDeFlag
         INTEGER
      }

er1645v2TvTmplIcfActions OBJECT-TYPE
   SYNTAX      VariableLengthTableActions
   MAX-ACCESS  read-write
   STATUS      current
   DESCRIPTION
      "By way of this field, some manipulations
       on this table may be performed."
   ::= {er1645v2TvTmplIcfEntry 2}

er1645v2TvTmplIcfTableIx OBJECT-TYPE
   SYNTAX      TableIndex
   MAX-ACCESS  not-accessible
   STATUS      current
   DESCRIPTION
      ""
   ::= {er1645v2TvTmplIcfEntry 11}

er1645v2TvTmplIcfName OBJECT-TYPE
   SYNTAX      DisplayString
   MAX-ACCESS  read-write
   STATUS      current
   DESCRIPTION
      "Path: tunnels.editConf.ipsecL2tpTunnels.name"
   ::= {er1645v2TvTmplIcfEntry 16777216}

er1645v2TvTmplIcfRemark OBJECT-TYPE
   SYNTAX      DisplayString
   MAX-ACCESS  read-write
   STATUS      current
   DESCRIPTION
      "Path: tunnels.editConf.ipsecL2tpTunnels.remark"
   ::= {er1645v2TvTmplIcfEntry 1157627904}

er1645v2TvTmplIcfAdminStatus OBJECT-TYPE
   SYNTAX      INTEGER
               {
               up (1),
               down (2)
               }
   MAX-ACCESS  read-write
   STATUS      current
   DESCRIPTION
      "Path: tunnels.editConf.ipsecL2tpTunnels.adminStatus

       Possibilities:
               up   (1)
               down   (2)"
   ::= {er1645v2TvTmplIcfEntry 33554432}

er1645v2TvTmplIcfMode OBJECT-TYPE
   SYNTAX      INTEGER
               {
               routing (1),
               bridging (2),
               routingAndBridging (3)
               }
   MAX-ACCESS  read-write
   STATUS      current
   DESCRIPTION
      "Path: tunnels.editConf.ipsecL2tpTunnels.mode

       Possibilities:
               routing   (1)
               bridging   (2)
               routingAndBridging   (3)"
   ::= {er1645v2TvTmplIcfEntry 67108864}

er1645v2TvTmplIcfPriorityPolicy OBJECT-TYPE
   SYNTAX      DisplayString
   MAX-ACCESS  read-write
   STATUS      current
   DESCRIPTION
      "Path: tunnels.editConf.ipsecL2tpTunnels.priorityPolicy"
   ::= {er1645v2TvTmplIcfEntry 83886080}

er1645v2TvTmplIcfIpVrfRouter OBJECT-TYPE
   SYNTAX      DisplayString
   MAX-ACCESS  read-write
   STATUS      current
   DESCRIPTION
      "Path: tunnels.editConf.ipsecL2tpTunnels.ip.vrfRouter"
   ::= {er1645v2TvTmplIcfEntry 53215232}

er1645v2TvTmplIcfIpAdr OBJECT-TYPE
   SYNTAX      IpAddress
   MAX-ACCESS  read-write
   STATUS      current
   DESCRIPTION
      "Path: tunnels.editConf.ipsecL2tpTunnels.ip.address"
   ::= {er1645v2TvTmplIcfEntry 58261504}

er1645v2TvTmplIcfIpNetm OBJECT-TYPE
   SYNTAX      IpAddress
   MAX-ACCESS  read-write
   STATUS      current
   DESCRIPTION
      "Path: tunnels.editConf.ipsecL2tpTunnels.ip.netMask"
   ::= {er1645v2TvTmplIcfEntry 58392576}

er1645v2TvTmplIcfIpSNetName OBJECT-TYPE
   SYNTAX      INTEGER
               {
               slOPTg (0),
               corp (2),
               dmz (3),
               internet (1)
               }
   MAX-ACCESS  read-write
   STATUS      current
   DESCRIPTION
      "Path: tunnels.editConf.ipsecL2tpTunnels.ip.sNet.name

       Possibilities:
               <OPT>   (0)
               corp   (2)
               dmz   (3)
               internet   (1)"
   ::= {er1645v2TvTmplIcfEntry 53674240}

er1645v2TvTmplIcfIpSNetCust OBJECT-TYPE
   SYNTAX      DisplayString
   MAX-ACCESS  read-write
   STATUS      current
   DESCRIPTION
      "Path: tunnels.editConf.ipsecL2tpTunnels.ip.sNet.custom"
   ::= {er1645v2TvTmplIcfEntry 53674496}

er1645v2TvTmplIcfIpRem OBJECT-TYPE
   SYNTAX      IpAddress
   MAX-ACCESS  read-write
   STATUS      current
   DESCRIPTION
      "Path: tunnels.editConf.ipsecL2tpTunnels.ip.remote"
   ::= {er1645v2TvTmplIcfEntry 58458112}

er1645v2TvTmplIcfIpUnnumbered OBJECT-TYPE
   SYNTAX      DisplayString
   MAX-ACCESS  read-write
   STATUS      current
   DESCRIPTION
      "Path: tunnels.editConf.ipsecL2tpTunnels.ip.unnumbered"
   ::= {er1645v2TvTmplIcfEntry 52625408}

er1645v2TvTmplIcfIpAcceptLocAddr OBJECT-TYPE
   SYNTAX      INTEGER
               {
               disabled (0),
               enabled (1)
               }
   MAX-ACCESS  read-write
   STATUS      current
   DESCRIPTION
      "Path: tunnels.editConf.ipsecL2tpTunnels.ip.acceptLocAddr

       Possibilities:
               disabled   (0)
               enabled   (1)"
   ::= {er1645v2TvTmplIcfEntry 50593792}

er1645v2TvTmplIcfIpAcceptRemAddr OBJECT-TYPE
   SYNTAX      INTEGER
               {
               disabled (0),
               enabled (1)
               }
   MAX-ACCESS  read-write
   STATUS      current
   DESCRIPTION
      "Path: tunnels.editConf.ipsecL2tpTunnels.ip.acceptRemAddr

       Possibilities:
               disabled   (0)
               enabled   (1)"
   ::= {er1645v2TvTmplIcfEntry 50724864}

er1645v2TvTmplIcfIpGwPref OBJECT-TYPE
   SYNTAX      Integer32
   MAX-ACCESS  read-write
   STATUS      current
   DESCRIPTION
      "Path: tunnels.editConf.ipsecL2tpTunnels.ip.gatewayPreference"
   ::= {er1645v2TvTmplIcfEntry 52690944}

er1645v2TvTmplIcfIpRsn OBJECT-TYPE
   SYNTAX      INTEGER
               {
               disabled (0),
               enabled (1)
               }
   MAX-ACCESS  read-write
   STATUS      current
   DESCRIPTION
      "Path: tunnels.editConf.ipsecL2tpTunnels.ip.requestSubnet

       Possibilities:
               disabled   (0)
               enabled   (1)"
   ::= {er1645v2TvTmplIcfEntry 56688640}

er1645v2TvTmplIcfIpMtu OBJECT-TYPE
   SYNTAX      Integer32
   MAX-ACCESS  read-write
   STATUS      current
   DESCRIPTION
      "Path: tunnels.editConf.ipsecL2tpTunnels.ip.mtu"
   ::= {er1645v2TvTmplIcfEntry 52953088}

er1645v2TvTmplIcfIpMssAdjust OBJECT-TYPE
   SYNTAX      INTEGER
               {
               disabled (0),
               auto (65536)
               }
   MAX-ACCESS  read-write
   STATUS      current
   DESCRIPTION
      "Path: tunnels.editConf.ipsecL2tpTunnels.ip.mssAdjust

       Possibilities:
               disabled   (0)
               auto   (65536)"
   ::= {er1645v2TvTmplIcfEntry 53280768}

er1645v2TvTmplIcfIpRipMetric OBJECT-TYPE
   SYNTAX      Integer32
   MAX-ACCESS  read-write
   STATUS      current
   DESCRIPTION
      "Path: tunnels.editConf.ipsecL2tpTunnels.ip.rip.metric"
   ::= {er1645v2TvTmplIcfEntry 51712768}

er1645v2TvTmplIcfIpRipMetricOut OBJECT-TYPE
   SYNTAX      Integer32
   MAX-ACCESS  read-write
   STATUS      current
   DESCRIPTION
      "Path: tunnels.editConf.ipsecL2tpTunnels.ip.rip.metricOut"
   ::= {er1645v2TvTmplIcfEntry 51713024}

er1645v2TvTmplIcfIpRipMode OBJECT-TYPE
   SYNTAX      INTEGER
               {
               disabled (0),
               passive (1),
               active (2)
               }
   MAX-ACCESS  read-write
   STATUS      current
   DESCRIPTION
      "Path: tunnels.editConf.ipsecL2tpTunnels.ip.rip.mode

       Possibilities:
               disabled   (0)
               passive   (1)
               active   (2)"
   ::= {er1645v2TvTmplIcfEntry 51713280}

er1645v2TvTmplIcfIpRipTxVersion OBJECT-TYPE
   SYNTAX      INTEGER
               {
               rip1 (0),
               rip2 (1),
               rip1mcompatible (2)
               }
   MAX-ACCESS  read-write
   STATUS      current
   DESCRIPTION
      "Path: tunnels.editConf.ipsecL2tpTunnels.ip.rip.txVersion

       Possibilities:
               rip1   (0)
               rip2   (1)
               rip1-compatible   (2)"
   ::= {er1645v2TvTmplIcfEntry 51716864}

er1645v2TvTmplIcfIpRipRxVersion OBJECT-TYPE
   SYNTAX      INTEGER
               {
               rip1only (0),
               rip2only (1),
               rip12 (2)
               }
   MAX-ACCESS  read-write
   STATUS      current
   DESCRIPTION
      "Path: tunnels.editConf.ipsecL2tpTunnels.ip.rip.rxVersion

       Possibilities:
               rip1only   (0)
               rip2only   (1)
               rip1&2   (2)"
   ::= {er1645v2TvTmplIcfEntry 51717120}

er1645v2TvTmplIcfIpRipSplitHorizon OBJECT-TYPE
   SYNTAX      INTEGER
               {
               disabled (0),
               enabled (1),
               poisonedReverse (2)
               }
   MAX-ACCESS  read-write
   STATUS      current
   DESCRIPTION
      "Path: tunnels.editConf.ipsecL2tpTunnels.ip.rip.splitHorizon

       Possibilities:
               disabled   (0)
               enabled   (1)
               poisonedReverse   (2)"
   ::= {er1645v2TvTmplIcfEntry 51713792}

er1645v2TvTmplIcfIpRipAuth OBJECT-TYPE
   SYNTAX      INTEGER
               {
               disabled (0),
               texts (1),
               md5 (2)
               }
   MAX-ACCESS  read-write
   STATUS      current
   DESCRIPTION
      "Path: tunnels.editConf.ipsecL2tpTunnels.ip.rip.authentication

       Possibilities:
               disabled   (0)
               text    (1)
               md5   (2)"
   ::= {er1645v2TvTmplIcfEntry 51712512}

er1645v2TvTmplIcfIpRipFilter OBJECT-TYPE
   SYNTAX      DisplayString
   MAX-ACCESS  read-write
   STATUS      current
   DESCRIPTION
      "Path: tunnels.editConf.ipsecL2tpTunnels.ip.rip.filter"
   ::= {er1645v2TvTmplIcfEntry 51716096}

er1645v2TvTmplIcfIpRipFilterIn OBJECT-TYPE
   SYNTAX      DisplayString
   MAX-ACCESS  read-write
   STATUS      current
   DESCRIPTION
      "Path: tunnels.editConf.ipsecL2tpTunnels.ip.rip.filterIn"
   ::= {er1645v2TvTmplIcfEntry 51716352}

er1645v2TvTmplIcfIpRipSnapshot OBJECT-TYPE
   SYNTAX      INTEGER
               {
               disabled (0),
               enabled (1)
               }
   MAX-ACCESS  read-write
   STATUS      current
   DESCRIPTION
      "Path: tunnels.editConf.ipsecL2tpTunnels.ip.rip.snapshot

       Possibilities:
               disabled   (0)
               enabled   (1)"
   ::= {er1645v2TvTmplIcfEntry 51708160}

er1645v2TvTmplIcfIpRipClearNextHop OBJECT-TYPE
   SYNTAX      INTEGER
               {
               disabled (0),
               enabled (1)
               }
   MAX-ACCESS  read-write
   STATUS      current
   DESCRIPTION
      "Path: tunnels.editConf.ipsecL2tpTunnels.ip.rip.clearNextHop

       Possibilities:
               disabled   (0)
               enabled   (1)"
   ::= {er1645v2TvTmplIcfEntry 51708416}

er1645v2TvTmplIcfIpAccPol OBJECT-TYPE
   SYNTAX      DisplayString
   MAX-ACCESS  read-write
   STATUS      current
   DESCRIPTION
      "Path: tunnels.editConf.ipsecL2tpTunnels.ip.accessPolicy"
   ::= {er1645v2TvTmplIcfEntry 53084160}

er1645v2TvTmplIcfIpAB OBJECT-TYPE
   SYNTAX      DisplayString
   MAX-ACCESS  read-write
   STATUS      current
   DESCRIPTION
      "Path: tunnels.editConf.ipsecL2tpTunnels.ip.trafficPolicy"
   ::= {er1645v2TvTmplIcfEntry 51249152}

er1645v2TvTmplIcfIpMA OBJECT-TYPE
   SYNTAX      INTEGER
               {
               disabled (0),
               enabled (1)
               }
   MAX-ACCESS  read-write
   STATUS      current
   DESCRIPTION
      "Path: tunnels.editConf.ipsecL2tpTunnels.ip.mgmtAccess

       Possibilities:
               disabled   (0)
               enabled   (1)"
   ::= {er1645v2TvTmplIcfEntry 51380224}

er1645v2TvTmplIcfIpMF OBJECT-TYPE
   SYNTAX      Integer32
   MAX-ACCESS  read-write
   STATUS      current
   DESCRIPTION
      "Path: tunnels.editConf.ipsecL2tpTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TvTmplIcfEntry 51445760}

er1645v2TvTmplIcfIpDB OBJECT-TYPE
   SYNTAX      INTEGER
               {
               disabled (0),
               enabled (1)
               }
   MAX-ACCESS  read-write
   STATUS      current
   DESCRIPTION
      "Path: tunnels.editConf.ipsecL2tpTunnels.ip.directedBroadcasts

       Possibilities:
               disabled   (0)
               enabled   (1)"
   ::= {er1645v2TvTmplIcfEntry 51773440}

er1645v2TvTmplIcfIpIR OBJECT-TYPE
   SYNTAX      INTEGER
               {
               disabled (0),
               enabled (1)
               }
   MAX-ACCESS  read-write
   STATUS      current
   DESCRIPTION
      "Path: tunnels.editConf.ipsecL2tpTunnels.ip.icmpRedirects

       Possibilities:
               disabled   (0)
               enabled   (1)"
   ::= {er1645v2TvTmplIcfEntry 52035584}

er1645v2TvTmplIcfIpIgmp OBJECT-TYPE
   SYNTAX      INTEGER
               {
               disabled (0),
               proxy (1),
               router (2),
               v3Router (5)
               }
   MAX-ACCESS  read-write
   STATUS      current
   DESCRIPTION
      "Path: tunnels.editConf.ipsecL2tpTunnels.ip.igmp

       Possibilities:
               disabled   (0)
               proxy   (1)
               router   (2)
               v3Router   (5)"
   ::= {er1645v2TvTmplIcfEntry 52428800}

er1645v2TvTmplIcfIpNN OBJECT-TYPE
   SYNTAX      DisplayString
   MAX-ACCESS  read-write
   STATUS      current
   DESCRIPTION
      "Path: tunnels.editConf.ipsecL2tpTunnels.ip.nat"
   ::= {er1645v2TvTmplIcfEntry 52101120}

er1645v2TvTmplIcfIpPimMode OBJECT-TYPE
   SYNTAX      INTEGER
               {
               disabled (0),
               sparse (1),
               passive (2)
               }
   MAX-ACCESS  read-write
   STATUS      current
   DESCRIPTION
      "Path: tunnels.editConf.ipsecL2tpTunnels.ip.pim.mode

       Possibilities:
               disabled   (0)
               sparse   (1)
               passive   (2)"
   ::= {er1645v2TvTmplIcfEntry 53346560}

er1645v2TvTmplIcfIpPimDrPriority OBJECT-TYPE
   SYNTAX      Counter32
   MAX-ACCESS  read-write
   STATUS      current
   DESCRIPTION
      "Path: tunnels.editConf.ipsecL2tpTunnels.ip.pim.drPriority

       32 bit unsigned wrappable counter."
   ::= {er1645v2TvTmplIcfEntry 53346816}

er1645v2TvTmplIcfIpPimHelloTime OBJECT-TYPE
   SYNTAX      TimeTicks
   MAX-ACCESS  read-write
   STATUS      current
   DESCRIPTION
      "Path: tunnels.editConf.ipsecL2tpTunnels.ip.pim.helloTime

       Time in centi-second."
   ::= {er1645v2TvTmplIcfEntry 53347072}

er1645v2TvTmplIcfIpPimPropagationDelay OBJECT-TYPE
   SYNTAX      TimeTicks
   MAX-ACCESS  read-write
   STATUS      current
   DESCRIPTION
      "Path: tunnels.editConf.ipsecL2tpTunnels.ip.pim.propagationDelay

       Time in centi-second."
   ::= {er1645v2TvTmplIcfEntry 53347328}

er1645v2TvTmplIcfIpPimOverrideInterval OBJECT-TYPE
   SYNTAX      TimeTicks
   MAX-ACCESS  read-write
   STATUS      current
   DESCRIPTION
      "Path: tunnels.editConf.ipsecL2tpTunnels.ip.pim.overrideInterval

       Time in centi-second."
   ::= {er1645v2TvTmplIcfEntry 53347584}

er1645v2TvTmplIcfIpPimBsrBorder OBJECT-TYPE
   SYNTAX      INTEGER
               {
               disabled (0),
               enabled (1)
               }
   MAX-ACCESS  read-write
   STATUS      current
   DESCRIPTION
      "Path: tunnels.editConf.ipsecL2tpTunnels.ip.pim.bsrBorder

       Possibilities:
               disabled   (0)
               enabled   (1)"
   ::= {er1645v2TvTmplIcfEntry 53347840}

er1645v2TvTmplIcfIpPimTtlThreshold OBJECT-TYPE
   SYNTAX      Integer32
   MAX-ACCESS  read-write
   STATUS      current
   DESCRIPTION
      "Path: tunnels.editConf.ipsecL2tpTunnels.ip.pim.ttlThreshold"
   ::= {er1645v2TvTmplIcfEntry 53348096}

er1645v2TvTmplIcfIpIMNetworkUnreachable OBJECT-TYPE
   SYNTAX      INTEGER
               {
               disabled (0),
               enabled (1)
               }
   MAX-ACCESS  read-write
   STATUS      current
   DESCRIPTION
      "Path: tunnels.editConf.ipsecL2tpTunnels.ip.icmpMessages.networkUnreachable

       Possibilities:
               disabled   (0)
               enabled   (1)"
   ::= {er1645v2TvTmplIcfEntry 53412096}

er1645v2TvTmplIcfIpIMHostUnreachable OBJECT-TYPE
   SYNTAX      INTEGER
               {
               disabled (0),
               enabled (1)
               }
   MAX-ACCESS  read-write
   STATUS      current
   DESCRIPTION
      "Path: tunnels.editConf.ipsecL2tpTunnels.ip.icmpMessages.hostUnreachable

       Possibilities:
               disabled   (0)
               enabled   (1)"
   ::= {er1645v2TvTmplIcfEntry 53412352}

er1645v2TvTmplIcfIpIMProtocolUnreachable OBJECT-TYPE
   SYNTAX      INTEGER
               {
               disabled (0),
               enabled (1)
               }
   MAX-ACCESS  read-write
   STATUS      current
   DESCRIPTION
      "Path: tunnels.editConf.ipsecL2tpTunnels.ip.icmpMessages.protocolUnreachable

       Possibilities:
               disabled   (0)
               enabled   (1)"
   ::= {er1645v2TvTmplIcfEntry 53412608}

er1645v2TvTmplIcfIpIMPortUnreachable OBJECT-TYPE
   SYNTAX      INTEGER
               {
               disabled (0),
               enabled (1)
               }
   MAX-ACCESS  read-write
   STATUS      current
   DESCRIPTION
      "Path: tunnels.editConf.ipsecL2tpTunnels.ip.icmpMessages.portUnreachable

       Possibilities:
               disabled   (0)
               enabled   (1)"
   ::= {er1645v2TvTmplIcfEntry 53412864}

er1645v2TvTmplIcfIpIMMtuExceeded OBJECT-TYPE
   SYNTAX      INTEGER
               {
               disabled (0),
               enabled (1)
               }
   MAX-ACCESS  read-write
   STATUS      current
   DESCRIPTION
      "Path: tunnels.editConf.ipsecL2tpTunnels.ip.icmpMessages.mtuExceeded

       Possibilities:
               disabled   (0)
               enabled   (1)"
   ::= {er1645v2TvTmplIcfEntry 53413120}

er1645v2TvTmplIcfIpIMAdminProhibited OBJECT-TYPE
   SYNTAX      INTEGER
               {
               disabled (0),
               enabled (1)
               }
   MAX-ACCESS  read-write
   STATUS      current
   DESCRIPTION
      "Path: tunnels.editConf.ipsecL2tpTunnels.ip.icmpMessages.adminProhibited

       Possibilities:
               disabled   (0)
               enabled   (1)"
   ::= {er1645v2TvTmplIcfEntry 53413376}

er1645v2TvTmplIcfIpIMTtlExceeded OBJECT-TYPE
   SYNTAX      INTEGER
               {
               disabled (0),
               enabled (1)
               }
   MAX-ACCESS  read-write
   STATUS      current
   DESCRIPTION
      "Path: tunnels.editConf.ipsecL2tpTunnels.ip.icmpMessages.ttlExceeded

       Possibilities:
               disabled   (0)
               enabled   (1)"
   ::= {er1645v2TvTmplIcfEntry 53413632}

er1645v2TvTmplIcfIpIMRedirect OBJECT-TYPE
   SYNTAX      INTEGER
               {
               disabled (0),
               enabled (1)
               }
   MAX-ACCESS  read-write
   STATUS      current
   DESCRIPTION
      "Path: tunnels.editConf.ipsecL2tpTunnels.ip.icmpMessages.redirect

       Possibilities:
               disabled   (0)
               enabled   (1)"
   ::= {er1645v2TvTmplIcfEntry 53413888}

er1645v2TvTmplIcfBridgingAccList OBJECT-TYPE
   SYNTAX      DisplayString
   MAX-ACCESS  read-write
   STATUS      current
   DESCRIPTION
      "Path: tunnels.editConf.ipsecL2tpTunnels.bridging.accessList"
   ::= {er1645v2TvTmplIcfEntry 453246976}

er1645v2TvTmplIcfBridgingInACL OBJECT-TYPE
   SYNTAX      DisplayString
   MAX-ACCESS  read-write
   STATUS      current
   DESCRIPTION
      "Path: tunnels.editConf.ipsecL2tpTunnels.bridging.inAccessList"
   ::= {er1645v2TvTmplIcfEntry 456916992}

er1645v2TvTmplIcfBridgingTp OBJECT-TYPE
   SYNTAX      DisplayString
   MAX-ACCESS  read-write
   STATUS      current
   DESCRIPTION
      "Path: tunnels.editConf.ipsecL2tpTunnels.bridging.trafficPolicy"
   ::= {er1645v2TvTmplIcfEntry 454295552}

er1645v2TvTmplIcfBridgingBrGrp OBJECT-TYPE
   SYNTAX      DisplayString
   MAX-ACCESS  read-write
   STATUS      current
   DESCRIPTION
      "Path: tunnels.editConf.ipsecL2tpTunnels.bridging.bridgeGroup"
   ::= {er1645v2TvTmplIcfEntry 454819840}

er1645v2TvTmplIcfBridgingLimBC OBJECT-TYPE
   SYNTAX      INTEGER
               {
               disabled (0),
               enabled (1)
               }
   MAX-ACCESS  read-write
   STATUS      current
   DESCRIPTION
      "Path: tunnels.editConf.ipsecL2tpTunnels.bridging.limitBroadcasts

       Possibilities:
               disabled   (0)
               enabled   (1)"
   ::= {er1645v2TvTmplIcfEntry 455081984}

er1645v2TvTmplIcfBridgingPrivateMode OBJECT-TYPE
   SYNTAX      INTEGER
               {
               disabled (0),
               enabled (1)
               }
   MAX-ACCESS  read-write
   STATUS      current
   DESCRIPTION
      "Path: tunnels.editConf.ipsecL2tpTunnels.bridging.privateMode

       Possibilities:
               disabled   (0)
               enabled   (1)"
   ::= {er1645v2TvTmplIcfEntry 459538432}

er1645v2TvTmplIcfBridgingLearning OBJECT-TYPE
   SYNTAX      INTEGER
               {
               disabled (0),
               enabled (1)
               }
   MAX-ACCESS  read-write
   STATUS      current
   DESCRIPTION
      "Path: tunnels.editConf.ipsecL2tpTunnels.bridging.learning

       Possibilities:
               disabled   (0)
               enabled   (1)"
   ::= {er1645v2TvTmplIcfEntry 456130560}

er1645v2TvTmplIcfBridgingMaxCacheSize OBJECT-TYPE
   SYNTAX      INTEGER
               {
               unlimited (0)
               }
   MAX-ACCESS  read-write
   STATUS      current
   DESCRIPTION
      "Path: tunnels.editConf.ipsecL2tpTunnels.bridging.maxCacheSize

       Possibilities:
               unlimited   (0)"
   ::= {er1645v2TvTmplIcfEntry 456392704}

er1645v2TvTmplIcfBridgingRelearnDropOnRelearn OBJECT-TYPE
   SYNTAX      INTEGER
               {
               disabled (0),
               enabled (1)
               }
   MAX-ACCESS  read-write
   STATUS      current
   DESCRIPTION
      "Path: tunnels.editConf.ipsecL2tpTunnels.bridging.relearn.dropOnRelearn

       Possibilities:
               disabled   (0)
               enabled   (1)"
   ::= {er1645v2TvTmplIcfEntry 456655872}

er1645v2TvTmplIcfBridgingRelearnShutdownThreshold OBJECT-TYPE
   SYNTAX      Integer32
   MAX-ACCESS  read-write
   STATUS      current
   DESCRIPTION
      "Path: tunnels.editConf.ipsecL2tpTunnels.bridging.relearn.shutdownThreshold"
   ::= {er1645v2TvTmplIcfEntry 456656896}

er1645v2TvTmplIcfBridgingRelearnShutdownTime OBJECT-TYPE
   SYNTAX      TimeTicks
   MAX-ACCESS  read-write
   STATUS      current
   DESCRIPTION
      "Path: tunnels.editConf.ipsecL2tpTunnels.bridging.relearn.shutdownTime

       Time in centi-second."
   ::= {er1645v2TvTmplIcfEntry 456657920}

er1645v2TvTmplIcfBridgingRelearnLoopDetection OBJECT-TYPE
   SYNTAX      INTEGER
               {
               disabled (0),
               passive (1),
               active (2)
               }
   MAX-ACCESS  read-write
   STATUS      current
   DESCRIPTION
      "Path: tunnels.editConf.ipsecL2tpTunnels.bridging.relearn.loopDetection

       Possibilities:
               disabled   (0)
               passive   (1)
               active   (2)"
   ::= {er1645v2TvTmplIcfEntry 456658944}

er1645v2TvTmplIcfBridgingRelearnLoopDetectionInterval OBJECT-TYPE
   SYNTAX      TimeTicks
   MAX-ACCESS  read-write
   STATUS      current
   DESCRIPTION
      "Path: tunnels.editConf.ipsecL2tpTunnels.bridging.relearn.loopDetectionInterval

       Time in centi-second."
   ::= {er1645v2TvTmplIcfEntry 456659968}

er1645v2TvTmplIcfBridgingVlanMemberShip OBJECT-TYPE
   SYNTAX      INTEGER
               {
               all (0),
               none (1),
               grouped (2)
               }
   MAX-ACCESS  read-write
   STATUS      current
   DESCRIPTION
      "Path: tunnels.editConf.ipsecL2tpTunnels.bridging.vlanMemberShip

       Possibilities:
               all   (0)
               none   (1)
               grouped   (2)"
   ::= {er1645v2TvTmplIcfEntry 457965568}

er1645v2TvTmplIcfBridgingVlTUntaggedAction OBJECT-TYPE
   SYNTAX      INTEGER
               {
               discard (0),
               accept (1),
               tag (2)
               }
   MAX-ACCESS  read-write
   STATUS      current
   DESCRIPTION
      "Path: tunnels.editConf.ipsecL2tpTunnels.bridging.vlanTagging.untagged.action

       Possibilities:
               discard   (0)
               accept   (1)
               tag   (2)"
   ::= {er1645v2TvTmplIcfEntry 459055104}

er1645v2TvTmplIcfBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecL2tpTunnels.bridging.vlanTagging.untagged.tagInfo.tpid

       Possibilities:
               dot1Q   (33024)
               dot1ad   (34984)
               0x9100   (37120)
               0x9200   (37376)
               0x9300   (37632)"
   ::= {er1645v2TvTmplIcfEntry 459059712}

er1645v2TvTmplIcfBridgingVlTUntaggedTagInfoVid OBJECT-TYPE
   SYNTAX      Integer32
   MAX-ACCESS  read-write
   STATUS      current
   DESCRIPTION
      "Path: tunnels.editConf.ipsecL2tpTunnels.bridging.vlanTagging.untagged.tagInfo.vid"
   ::= {er1645v2TvTmplIcfEntry 459060224}

er1645v2TvTmplIcfBridgingVlTUnknownVlansAction OBJECT-TYPE
   SYNTAX      INTEGER
               {
               discard (0),
               accept (1),
               tag (2)
               }
   MAX-ACCESS  read-write
   STATUS      current
   DESCRIPTION
      "Path: tunnels.editConf.ipsecL2tpTunnels.bridging.vlanTagging.unknownVlans.action

       Possibilities:
               discard   (0)
               accept   (1)
               tag   (2)"
   ::= {er1645v2TvTmplIcfEntry 459120640}

er1645v2TvTmplIcfBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecL2tpTunnels.bridging.vlanTagging.unknownVlans.tagInfo.tpid

       Possibilities:
               dot1Q   (33024)
               dot1ad   (34984)
               0x9100   (37120)
               0x9200   (37376)
               0x9300   (37632)"
   ::= {er1645v2TvTmplIcfEntry 459125248}

er1645v2TvTmplIcfBridgingVlTUnknownVlansTagInfoVid OBJECT-TYPE
   SYNTAX      Integer32
   MAX-ACCESS  read-write
   STATUS      current
   DESCRIPTION
      "Path: tunnels.editConf.ipsecL2tpTunnels.bridging.vlanTagging.unknownVlans.tagInfo.vid"
   ::= {er1645v2TvTmplIcfEntry 459125760}

er1645v2TvTmplIcfBridgingDot1adType OBJECT-TYPE
   SYNTAX      INTEGER
               {
               slOPTg (0),
               cPort (4),
               sPort (1),
               nni (2)
               }
   MAX-ACCESS  read-write
   STATUS      current
   DESCRIPTION
      "Path: tunnels.editConf.ipsecL2tpTunnels.bridging.dot1ad.type

       Possibilities:
               <OPT>   (0)
               cPort   (4)
               sPort   (1)
               nni   (2)"
   ::= {er1645v2TvTmplIcfEntry 460850176}

er1645v2TvTmplIcfBridgingPriority OBJECT-TYPE
   SYNTAX      Integer32
   MAX-ACCESS  read-write
   STATUS      current
   DESCRIPTION
      "Path: tunnels.editConf.ipsecL2tpTunnels.bridging.priority"
   ::= {er1645v2TvTmplIcfEntry 453509120}

er1645v2TvTmplIcfBridgingPathCost OBJECT-TYPE
   SYNTAX      Integer32
   MAX-ACCESS  read-write
   STATUS      current
   DESCRIPTION
      "Path: tunnels.editConf.ipsecL2tpTunnels.bridging.pathCost"
   ::= {er1645v2TvTmplIcfEntry 453771264}

er1645v2TvTmplIcfBridgingInternalPathCost OBJECT-TYPE
   SYNTAX      Integer32
   MAX-ACCESS  read-write
   STATUS      current
   DESCRIPTION
      "Path: tunnels.editConf.ipsecL2tpTunnels.bridging.internalPathCost"
   ::= {er1645v2TvTmplIcfEntry 457703424}

er1645v2TvTmplIcfBridgingTCD OBJECT-TYPE
   SYNTAX      INTEGER
               {
               disabled (0),
               enabled (1)
               }
   MAX-ACCESS  read-write
   STATUS      current
   DESCRIPTION
      "Path: tunnels.editConf.ipsecL2tpTunnels.bridging.topologyChangeDetection

       Possibilities:
               disabled   (0)
               enabled   (1)"
   ::= {er1645v2TvTmplIcfEntry 454033408}

er1645v2TvTmplIcfBridgingRestrictedRole OBJECT-TYPE
   SYNTAX      INTEGER
               {
               disabled (0),
               enabled (1)
               }
   MAX-ACCESS  read-write
   STATUS      current
   DESCRIPTION
      "Path: tunnels.editConf.ipsecL2tpTunnels.bridging.restrictedRole

       Possibilities:
               disabled   (0)
               enabled   (1)"
   ::= {er1645v2TvTmplIcfEntry 458227712}

er1645v2TvTmplIcfBridgingAdminEdge OBJECT-TYPE
   SYNTAX      INTEGER
               {
               disabled (0),
               enabled (1)
               }
   MAX-ACCESS  read-write
   STATUS      current
   DESCRIPTION
      "Path: tunnels.editConf.ipsecL2tpTunnels.bridging.adminEdge

       Possibilities:
               disabled   (0)
               enabled   (1)"
   ::= {er1645v2TvTmplIcfEntry 457179136}

er1645v2TvTmplIcfBridgingOamMacDeviceMac OBJECT-TYPE
   SYNTAX      DisplayString
   MAX-ACCESS  read-write
   STATUS      current
   DESCRIPTION
      "Path: tunnels.editConf.ipsecL2tpTunnels.bridging.ethOam.macAddress.deviceMac"
   ::= {er1645v2TvTmplIcfEntry 458506496}

er1645v2TvTmplIcfBridgingOamMacUserMac OBJECT-TYPE
   SYNTAX      OCTET STRING
   MAX-ACCESS  read-write
   STATUS      current
   DESCRIPTION
      "Path: tunnels.editConf.ipsecL2tpTunnels.bridging.ethOam.macAddress.userMac

       MAC address."
   ::= {er1645v2TvTmplIcfEntry 458506368}

er1645v2TvTmplIcfBridgingOamMacBridgeMac OBJECT-TYPE
   SYNTAX      DisplayString
   MAX-ACCESS  read-write
   STATUS      current
   DESCRIPTION
      "Path: tunnels.editConf.ipsecL2tpTunnels.bridging.ethOam.macAddress.bridgeMac"
   ::= {er1645v2TvTmplIcfEntry 458506432}

er1645v2TvTmplIcfBridgingMgmtInline OBJECT-TYPE
   SYNTAX      INTEGER
               {
               disabled (0),
               enabled (1)
               }
   MAX-ACCESS  read-write
   STATUS      current
   DESCRIPTION
      "Path: tunnels.editConf.ipsecL2tpTunnels.bridging.mgmtInline

       Possibilities:
               disabled   (0)
               enabled   (1)"
   ::= {er1645v2TvTmplIcfEntry 458752000}

er1645v2TvTmplIcfBridgingL2ptMode OBJECT-TYPE
   SYNTAX      INTEGER
               {
               disabled (0),
               enabled (1)
               }
   MAX-ACCESS  read-write
   STATUS      current
   DESCRIPTION
      "Path: tunnels.editConf.ipsecL2tpTunnels.bridging.l2ProtTunnel.mode

       Possibilities:
               disabled   (0)
               enabled   (1)"
   ::= {er1645v2TvTmplIcfEntry 459292672}

er1645v2TvTmplIcfBridgingL2ptProtocols OBJECT-TYPE
   SYNTAX      Integer32
   MAX-ACCESS  read-write
   STATUS      current
   DESCRIPTION
      "Path: tunnels.editConf.ipsecL2tpTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TvTmplIcfEntry 459309056}

er1645v2TvTmplIcfBridgingL2ptDestMac OBJECT-TYPE
   SYNTAX      OCTET STRING
   MAX-ACCESS  read-write
   STATUS      current
   DESCRIPTION
      "Path: tunnels.editConf.ipsecL2tpTunnels.bridging.l2ProtTunnel.destinationMac

       MAC address."
   ::= {er1645v2TvTmplIcfEntry 459325440}

er1645v2TvTmplIcfBridgingL2ptCos OBJECT-TYPE
   SYNTAX      INTEGER
               {
               unchanged (255)
               }
   MAX-ACCESS  read-write
   STATUS      current
   DESCRIPTION
      "Path: tunnels.editConf.ipsecL2tpTunnels.bridging.l2ProtTunnel.cos

       Possibilities:
               unchanged   (255)"
   ::= {er1645v2TvTmplIcfEntry 459341824}

er1645v2TvTmplIcfBridgingL2ptDropThrStp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.stp

       unit name = packets/sec

       Possibilities:
               unlimited   (0)"
   ::= {er1645v2TvTmplIcfEntry 459358272}

er1645v2TvTmplIcfBridgingL2ptDropThrLldp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.lldp

       unit name = packets/sec

       Possibilities:
               unlimited   (0)"
   ::= {er1645v2TvTmplIcfEntry 459358336}

er1645v2TvTmplIcfBridgingL2ptDropThrOam OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.oam

       unit name = packets/sec

       Possibilities:
               unlimited   (0)"
   ::= {er1645v2TvTmplIcfEntry 459358400}

er1645v2TvTmplIcfBridgingL2ptDropThrCdp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.cdp

       unit name = packets/sec

       Possibilities:
               unlimited   (0)"
   ::= {er1645v2TvTmplIcfEntry 459358464}

er1645v2TvTmplIcfBridgingL2ptDropThrVtp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.vtp

       unit name = packets/sec

       Possibilities:
               unlimited   (0)"
   ::= {er1645v2TvTmplIcfEntry 459358528}

er1645v2TvTmplIcfBridgingL2ptDropThrLacp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.lacp

       unit name = packets/sec

       Possibilities:
               unlimited   (0)"
   ::= {er1645v2TvTmplIcfEntry 459358592}

er1645v2TvTmplIcfBridgingL2ptDropThrEfmOam OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.efmOam

       unit name = packets/sec

       Possibilities:
               unlimited   (0)"
   ::= {er1645v2TvTmplIcfEntry 459358656}

er1645v2TvTmplIcfBridgingL2ptDropThrPvst OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.pvst

       unit name = packets/sec

       Possibilities:
               unlimited   (0)"
   ::= {er1645v2TvTmplIcfEntry 459358720}

er1645v2TvTmplIcfBridgingL2ptDropThrMmrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.mmrp

       unit name = packets/sec

       Possibilities:
               unlimited   (0)"
   ::= {er1645v2TvTmplIcfEntry 459358784}

er1645v2TvTmplIcfBridgingL2ptDropThrMvrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.mvrp

       unit name = packets/sec

       Possibilities:
               unlimited   (0)"
   ::= {er1645v2TvTmplIcfEntry 459358848}

er1645v2TvTmplIcfBridgingL2ptDropThrGvrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.gvrp

       unit name = packets/sec

       Possibilities:
               unlimited   (0)"
   ::= {er1645v2TvTmplIcfEntry 459358912}

er1645v2TvTmplIcfBridgingL2ptDropThrGmrp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.gmrp

       unit name = packets/sec

       Possibilities:
               unlimited   (0)"
   ::= {er1645v2TvTmplIcfEntry 459358976}

er1645v2TvTmplIcfBridgingL2ptDropThrDtp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.dtp

       unit name = packets/sec

       Possibilities:
               unlimited   (0)"
   ::= {er1645v2TvTmplIcfEntry 459359040}

er1645v2TvTmplIcfBridgingL2ptDropThrPagp OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.pagp

       unit name = packets/sec

       Possibilities:
               unlimited   (0)"
   ::= {er1645v2TvTmplIcfEntry 459359104}

er1645v2TvTmplIcfBridgingL2ptDropThrUdld OBJECT-TYPE
   SYNTAX      INTEGER
               {
               unlimited (0)
               }
   UNITS       "packets/sec"
   MAX-ACCESS  read-write
   STATUS      current
   DESCRIPTION
      "Path: tunnels.editConf.ipsecL2tpTunnels.bridging.l2ProtTunnel.dropThresholds.udld

       unit name = packets/sec

       Possibilities:
               unlimited   (0)"
   ::= {er1645v2TvTmplIcfEntry 459359168}

er1645v2TvTmplIcfL2tpLocalIpAddress OBJECT-TYPE
   SYNTAX      IpAddress
   MAX-ACCESS  read-write
   STATUS      current
   DESCRIPTION
      "Path: tunnels.editConf.ipsecL2tpTunnels.l2tp.localIpAddress"
   ::= {er1645v2TvTmplIcfEntry 302120960}

er1645v2TvTmplIcfL2tpRemoteIpAddress OBJECT-TYPE
   SYNTAX      IpAddress
   MAX-ACCESS  read-write
   STATUS      current
   DESCRIPTION
      "Path: tunnels.editConf.ipsecL2tpTunnels.l2tp.remoteIpAddress"
   ::= {er1645v2TvTmplIcfEntry 302252032}

er1645v2TvTmplIcfL2tpRemoteDnsName OBJECT-TYPE
   SYNTAX      DisplayString
   MAX-ACCESS  read-write
   STATUS      current
   DESCRIPTION
      "Path: tunnels.editConf.ipsecL2tpTunnels.l2tp.remoteDnsName"
   ::= {er1645v2TvTmplIcfEntry 305790976}

er1645v2TvTmplIcfL2tpAuthen OBJECT-TYPE
   SYNTAX      INTEGER
               {
               disabled (0),
               chap (1),
               pap (2),
               chapOrPap (3),
               msChap (4),
               msChapV2 (5)
               }
   MAX-ACCESS  read-write
   STATUS      current
   DESCRIPTION
      "Path: tunnels.editConf.ipsecL2tpTunnels.l2tp.pppAuthentication

       Possibilities:
               disabled   (0)
               chap   (1)
               pap   (2)
               chapOrPap   (3)
               msChap   (4)
               msChapV2   (5)"
   ::= {er1645v2TvTmplIcfEntry 303693824}

er1645v2TvTmplIcfL2tpPppNam OBJECT-TYPE
   SYNTAX      DisplayString
   MAX-ACCESS  read-write
   STATUS      current
   DESCRIPTION
      "Path: tunnels.editConf.ipsecL2tpTunnels.l2tp.pppSessionName"
   ::= {er1645v2TvTmplIcfEntry 304611328}

er1645v2TvTmplIcfL2tpPppSec OBJECT-TYPE
   SYNTAX      DisplayString
   MAX-ACCESS  read-write
   STATUS      current
   DESCRIPTION
      "Path: tunnels.editConf.ipsecL2tpTunnels.l2tp.pppSessionSecret"
   ::= {er1645v2TvTmplIcfEntry 304742400}

er1645v2TvTmplIcfL2tpEncMPppSec OBJECT-TYPE
   SYNTAX      INTEGER
               {
               none (1),
               encrypt (2),
               encType1 (3),
               invalid (128)
               }
   MAX-ACCESS  read-write
   STATUS      current
   DESCRIPTION
      "Path: tunnels.editConf.ipsecL2tpTunnels.l2tp.encModePppSessionSecret

       Possibilities:
               none   (1)
               encrypt   (2)
               encType1   (3)
               invalid   (128)"
   ::= {er1645v2TvTmplIcfEntry 304873472}

er1645v2TvTmplIcfL2tpEncPppSec OBJECT-TYPE
   SYNTAX      DisplayString
   MAX-ACCESS  read-write
   STATUS      current
   DESCRIPTION
      "Path: tunnels.editConf.ipsecL2tpTunnels.l2tp.encPppSessionSecret"
   ::= {er1645v2TvTmplIcfEntry 305004544}

er1645v2TvTmplIcfL2tpLnkMOperation OBJECT-TYPE
   SYNTAX      INTEGER
               {
               disabled (0),
               enabled (1)
               }
   MAX-ACCESS  read-write
   STATUS      current
   DESCRIPTION
      "Path: tunnels.editConf.ipsecL2tpTunnels.l2tp.linkMonitoring.operation

       Possibilities:
               disabled   (0)
               enabled   (1)"
   ::= {er1645v2TvTmplIcfEntry 305922560}

er1645v2TvTmplIcfL2tpLnkMInterval OBJECT-TYPE
   SYNTAX      TimeTicks
   MAX-ACCESS  read-write
   STATUS      current
   DESCRIPTION
      "Path: tunnels.editConf.ipsecL2tpTunnels.l2tp.linkMonitoring.interval

       Time in centi-second."
   ::= {er1645v2TvTmplIcfEntry 305923072}

er1645v2TvTmplIcfL2tpLnkMRepTimeOut OBJECT-TYPE
   SYNTAX      TimeTicks
   MAX-ACCESS  read-write
   STATUS      current
   DESCRIPTION
      "Path: tunnels.editConf.ipsecL2tpTunnels.l2tp.linkMonitoring.replyTimeOut

       Time in centi-second."
   ::= {er1645v2TvTmplIcfEntry 305923584}

er1645v2TvTmplIcfL2tpLnkMFailsPrmt OBJECT-TYPE
   SYNTAX      Integer32
   MAX-ACCESS  read-write
   STATUS      current
   DESCRIPTION
      "Path: tunnels.editConf.ipsecL2tpTunnels.l2tp.linkMonitoring.failsPermitted"
   ::= {er1645v2TvTmplIcfEntry 305924096}

er1645v2TvTmplIcfL2tpType OBJECT-TYPE
   SYNTAX      INTEGER
               {
               outgoingDial (0),
               outgoingLeasedLine (1),
               incoming (2)
               }
   MAX-ACCESS  read-write
   STATUS      current
   DESCRIPTION
      "Path: tunnels.editConf.ipsecL2tpTunnels.l2tp.type

       Possibilities:
               outgoingDial   (0)
               outgoingLeasedLine   (1)
               incoming   (2)"
   ::= {er1645v2TvTmplIcfEntry 303824896}

er1645v2TvTmplIcfL2tpDataseqnr OBJECT-TYPE
   SYNTAX      INTEGER
               {
               off (0),
               on (1)
               }
   MAX-ACCESS  read-write
   STATUS      current
   DESCRIPTION
      "Path: tunnels.editConf.ipsecL2tpTunnels.l2tp.dataChannelSequenceNumbering

       Possibilities:
               off   (0)
               on   (1)"
   ::= {er1645v2TvTmplIcfEntry 302383104}

er1645v2TvTmplIcfL2tpIpsecFdx OBJECT-TYPE
   SYNTAX      DisplayString
   MAX-ACCESS  read-write
   STATUS      current
   DESCRIPTION
      "Path: tunnels.editConf.ipsecL2tpTunnels.l2tp.ipsec.fdxManualSA"
   ::= {er1645v2TvTmplIcfEntry 304103424}

er1645v2TvTmplIcfL2tpIpsecHdxIn OBJECT-TYPE
   SYNTAX      DisplayString
   MAX-ACCESS  read-write
   STATUS      current
   DESCRIPTION
      "Path: tunnels.editConf.ipsecL2tpTunnels.l2tp.ipsec.hdxManualSA.inbound"
   ::= {er1645v2TvTmplIcfEntry 304119872}

er1645v2TvTmplIcfL2tpIpsecHdxOut OBJECT-TYPE
   SYNTAX      DisplayString
   MAX-ACCESS  read-write
   STATUS      current
   DESCRIPTION
      "Path: tunnels.editConf.ipsecL2tpTunnels.l2tp.ipsec.hdxManualSA.outbound"
   ::= {er1645v2TvTmplIcfEntry 304119936}

er1645v2TvTmplIcfL2tpIpsecPsCfg OBJECT-TYPE
   SYNTAX      DisplayString
   MAX-ACCESS  read-write
   STATUS      current
   DESCRIPTION
      "Path: tunnels.editConf.ipsecL2tpTunnels.l2tp.ipsec.ikePresharedSA.ikeSA"
   ::= {er1645v2TvTmplIcfEntry 304138240}

er1645v2TvTmplIcfL2tpIpsecPsLIdIp OBJECT-TYPE
   SYNTAX      IpAddress
   MAX-ACCESS  read-write
   STATUS      current
   DESCRIPTION
      "Path: tunnels.editConf.ipsecL2tpTunnels.l2tp.ipsec.ikePresharedSA.localId.ipAddress"
   ::= {er1645v2TvTmplIcfEntry 304140296}

er1645v2TvTmplIcfL2tpIpsecPsLIdHn OBJECT-TYPE
   SYNTAX      DisplayString
   MAX-ACCESS  read-write
   STATUS      current
   DESCRIPTION
      "Path: tunnels.editConf.ipsecL2tpTunnels.l2tp.ipsec.ikePresharedSA.localId.hostName"
   ::= {er1645v2TvTmplIcfEntry 304140304}

er1645v2TvTmplIcfL2tpIpsecPsLIdUn OBJECT-TYPE
   SYNTAX      DisplayString
   MAX-ACCESS  read-write
   STATUS      current
   DESCRIPTION
      "Path: tunnels.editConf.ipsecL2tpTunnels.l2tp.ipsec.ikePresharedSA.localId.user"
   ::= {er1645v2TvTmplIcfEntry 304140312}

er1645v2TvTmplIcfL2tpIpsecPsRIdIp OBJECT-TYPE
   SYNTAX      IpAddress
   MAX-ACCESS  read-write
   STATUS      current
   DESCRIPTION
      "Path: tunnels.editConf.ipsecL2tpTunnels.l2tp.ipsec.ikePresharedSA.remoteId.ipAddress"
   ::= {er1645v2TvTmplIcfEntry 304142344}

er1645v2TvTmplIcfL2tpIpsecPsRIdHn OBJECT-TYPE
   SYNTAX      DisplayString
   MAX-ACCESS  read-write
   STATUS      current
   DESCRIPTION
      "Path: tunnels.editConf.ipsecL2tpTunnels.l2tp.ipsec.ikePresharedSA.remoteId.hostName"
   ::= {er1645v2TvTmplIcfEntry 304142352}

er1645v2TvTmplIcfL2tpIpsecPsRIdUn OBJECT-TYPE
   SYNTAX      DisplayString
   MAX-ACCESS  read-write
   STATUS      current
   DESCRIPTION
      "Path: tunnels.editConf.ipsecL2tpTunnels.l2tp.ipsec.ikePresharedSA.remoteId.user"
   ::= {er1645v2TvTmplIcfEntry 304142360}

er1645v2TvTmplIcfL2tpIpsecPsKey OBJECT-TYPE
   SYNTAX      DisplayString
   MAX-ACCESS  read-write
   STATUS      current
   DESCRIPTION
      "Path: tunnels.editConf.ipsecL2tpTunnels.l2tp.ipsec.ikePresharedSA.preSharedKey"
   ::= {er1645v2TvTmplIcfEntry 304144384}

er1645v2TvTmplIcfL2tpIpsecPsEncMKey OBJECT-TYPE
   SYNTAX      INTEGER
               {
               none (1),
               encrypt (2),
               encType1 (3),
               invalid (128)
               }
   MAX-ACCESS  read-write
   STATUS      current
   DESCRIPTION
      "Path: tunnels.editConf.ipsecL2tpTunnels.l2tp.ipsec.ikePresharedSA.encModePreSharedKey

       Possibilities:
               none   (1)
               encrypt   (2)
               encType1   (3)
               invalid   (128)"
   ::= {er1645v2TvTmplIcfEntry 304148480}

er1645v2TvTmplIcfL2tpIpsecPsEncKey OBJECT-TYPE
   SYNTAX      DisplayString
   MAX-ACCESS  read-write
   STATUS      current
   DESCRIPTION
      "Path: tunnels.editConf.ipsecL2tpTunnels.l2tp.ipsec.ikePresharedSA.encPreSharedKey"
   ::= {er1645v2TvTmplIcfEntry 304150528}

er1645v2TvTmplIcfL2tpIpsecPsPIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecL2tpTunnels.l2tp.ipsec.ikePresharedSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TvTmplIcfEntry 304146560}

er1645v2TvTmplIcfL2tpIpsecPsPIdLocAddr OBJECT-TYPE
   SYNTAX      IpAddress
   MAX-ACCESS  read-write
   STATUS      current
   DESCRIPTION
      "Path: tunnels.editConf.ipsecL2tpTunnels.l2tp.ipsec.ikePresharedSA.proxyId.localIpAddress"
   ::= {er1645v2TvTmplIcfEntry 304146688}

er1645v2TvTmplIcfL2tpIpsecPsPIdLocMask OBJECT-TYPE
   SYNTAX      IpAddress
   MAX-ACCESS  read-write
   STATUS      current
   DESCRIPTION
      "Path: tunnels.editConf.ipsecL2tpTunnels.l2tp.ipsec.ikePresharedSA.proxyId.localIpMask"
   ::= {er1645v2TvTmplIcfEntry 304146816}

er1645v2TvTmplIcfL2tpIpsecPsPIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikePresharedSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIcfEntry 304146944}

er1645v2TvTmplIcfL2tpIpsecPsPIdRemAddr OBJECT-TYPE
   SYNTAX      IpAddress
   MAX-ACCESS  read-write
   STATUS      current
   DESCRIPTION
      "Path: tunnels.editConf.ipsecL2tpTunnels.l2tp.ipsec.ikePresharedSA.proxyId.remoteIpAddress"
   ::= {er1645v2TvTmplIcfEntry 304147072}

er1645v2TvTmplIcfL2tpIpsecPsPIdRemMask OBJECT-TYPE
   SYNTAX      IpAddress
   MAX-ACCESS  read-write
   STATUS      current
   DESCRIPTION
      "Path: tunnels.editConf.ipsecL2tpTunnels.l2tp.ipsec.ikePresharedSA.proxyId.remoteIpMask"
   ::= {er1645v2TvTmplIcfEntry 304147200}

er1645v2TvTmplIcfL2tpIpsecPsPIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikePresharedSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIcfEntry 304147328}

er1645v2TvTmplIcfL2tpIpsecCeCfg OBJECT-TYPE
   SYNTAX      DisplayString
   MAX-ACCESS  read-write
   STATUS      current
   DESCRIPTION
      "Path: tunnels.editConf.ipsecL2tpTunnels.l2tp.ipsec.ikeCertificateSA.ikeSA"
   ::= {er1645v2TvTmplIcfEntry 304154624}

er1645v2TvTmplIcfL2tpIpsecCeLIdIp OBJECT-TYPE
   SYNTAX      IpAddress
   MAX-ACCESS  read-write
   STATUS      current
   DESCRIPTION
      "Path: tunnels.editConf.ipsecL2tpTunnels.l2tp.ipsec.ikeCertificateSA.localId.ipAddress"
   ::= {er1645v2TvTmplIcfEntry 304156680}

er1645v2TvTmplIcfL2tpIpsecCeLIdHn OBJECT-TYPE
   SYNTAX      DisplayString
   MAX-ACCESS  read-write
   STATUS      current
   DESCRIPTION
      "Path: tunnels.editConf.ipsecL2tpTunnels.l2tp.ipsec.ikeCertificateSA.localId.hostName"
   ::= {er1645v2TvTmplIcfEntry 304156688}

er1645v2TvTmplIcfL2tpIpsecCeLIdUn OBJECT-TYPE
   SYNTAX      DisplayString
   MAX-ACCESS  read-write
   STATUS      current
   DESCRIPTION
      "Path: tunnels.editConf.ipsecL2tpTunnels.l2tp.ipsec.ikeCertificateSA.localId.user"
   ::= {er1645v2TvTmplIcfEntry 304156696}

er1645v2TvTmplIcfL2tpIpsecCeLIdDn OBJECT-TYPE
   SYNTAX      DisplayString
   MAX-ACCESS  read-write
   STATUS      current
   DESCRIPTION
      "Path: tunnels.editConf.ipsecL2tpTunnels.l2tp.ipsec.ikeCertificateSA.localId.derAsn1Dn"
   ::= {er1645v2TvTmplIcfEntry 304156704}

er1645v2TvTmplIcfL2tpIpsecCeRIdIp OBJECT-TYPE
   SYNTAX      IpAddress
   MAX-ACCESS  read-write
   STATUS      current
   DESCRIPTION
      "Path: tunnels.editConf.ipsecL2tpTunnels.l2tp.ipsec.ikeCertificateSA.remoteId.ipAddress"
   ::= {er1645v2TvTmplIcfEntry 304158728}

er1645v2TvTmplIcfL2tpIpsecCeRIdHn OBJECT-TYPE
   SYNTAX      DisplayString
   MAX-ACCESS  read-write
   STATUS      current
   DESCRIPTION
      "Path: tunnels.editConf.ipsecL2tpTunnels.l2tp.ipsec.ikeCertificateSA.remoteId.hostName"
   ::= {er1645v2TvTmplIcfEntry 304158736}

er1645v2TvTmplIcfL2tpIpsecCeRIdUn OBJECT-TYPE
   SYNTAX      DisplayString
   MAX-ACCESS  read-write
   STATUS      current
   DESCRIPTION
      "Path: tunnels.editConf.ipsecL2tpTunnels.l2tp.ipsec.ikeCertificateSA.remoteId.user"
   ::= {er1645v2TvTmplIcfEntry 304158744}

er1645v2TvTmplIcfL2tpIpsecCeRIdDn OBJECT-TYPE
   SYNTAX      DisplayString
   MAX-ACCESS  read-write
   STATUS      current
   DESCRIPTION
      "Path: tunnels.editConf.ipsecL2tpTunnels.l2tp.ipsec.ikeCertificateSA.remoteId.derAsn1Dn"
   ::= {er1645v2TvTmplIcfEntry 304158752}

er1645v2TvTmplIcfL2tpIpsecCePIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecL2tpTunnels.l2tp.ipsec.ikeCertificateSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TvTmplIcfEntry 304162944}

er1645v2TvTmplIcfL2tpIpsecCePIdLocAddr OBJECT-TYPE
   SYNTAX      IpAddress
   MAX-ACCESS  read-write
   STATUS      current
   DESCRIPTION
      "Path: tunnels.editConf.ipsecL2tpTunnels.l2tp.ipsec.ikeCertificateSA.proxyId.localIpAddress"
   ::= {er1645v2TvTmplIcfEntry 304163072}

er1645v2TvTmplIcfL2tpIpsecCePIdLocMask OBJECT-TYPE
   SYNTAX      IpAddress
   MAX-ACCESS  read-write
   STATUS      current
   DESCRIPTION
      "Path: tunnels.editConf.ipsecL2tpTunnels.l2tp.ipsec.ikeCertificateSA.proxyId.localIpMask"
   ::= {er1645v2TvTmplIcfEntry 304163200}

er1645v2TvTmplIcfL2tpIpsecCePIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikeCertificateSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIcfEntry 304163328}

er1645v2TvTmplIcfL2tpIpsecCePIdRemAddr OBJECT-TYPE
   SYNTAX      IpAddress
   MAX-ACCESS  read-write
   STATUS      current
   DESCRIPTION
      "Path: tunnels.editConf.ipsecL2tpTunnels.l2tp.ipsec.ikeCertificateSA.proxyId.remoteIpAddress"
   ::= {er1645v2TvTmplIcfEntry 304163456}

er1645v2TvTmplIcfL2tpIpsecCePIdRemMask OBJECT-TYPE
   SYNTAX      IpAddress
   MAX-ACCESS  read-write
   STATUS      current
   DESCRIPTION
      "Path: tunnels.editConf.ipsecL2tpTunnels.l2tp.ipsec.ikeCertificateSA.proxyId.remoteIpMask"
   ::= {er1645v2TvTmplIcfEntry 304163584}

er1645v2TvTmplIcfL2tpIpsecCePIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecL2tpTunnels.l2tp.ipsec.ikeCertificateSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIcfEntry 304163712}

er1645v2TvTmplIcfL2tpKeepaliveTO OBJECT-TYPE
   SYNTAX      Integer32
   MAX-ACCESS  read-write
   STATUS      current
   DESCRIPTION
      "Path: tunnels.editConf.ipsecL2tpTunnels.l2tp.keepAliveTimeOut"
   ::= {er1645v2TvTmplIcfEntry 302514176}

er1645v2TvTmplIcfL2tpNoTraffT0 OBJECT-TYPE
   SYNTAX      Integer32
   MAX-ACCESS  read-write
   STATUS      current
   DESCRIPTION
      "Path: tunnels.editConf.ipsecL2tpTunnels.l2tp.noTrafficTimeOut"
   ::= {er1645v2TvTmplIcfEntry 304218112}

er1645v2TvTmplIcfL2tpMode OBJECT-TYPE
   SYNTAX      INTEGER
               {
               lac (1),
               lns (2),
               auto (3)
               }
   MAX-ACCESS  read-write
   STATUS      current
   DESCRIPTION
      "Path: tunnels.editConf.ipsecL2tpTunnels.l2tp.l2tpMode

       Possibilities:
               lac   (1)
               lns   (2)
               auto   (3)"
   ::= {er1645v2TvTmplIcfEntry 302645248}

er1645v2TvTmplIcfL2tpAuth OBJECT-TYPE
   SYNTAX      INTEGER
               {
               off (0),
               on (1)
               }
   MAX-ACCESS  read-write
   STATUS      current
   DESCRIPTION
      "Path: tunnels.editConf.ipsecL2tpTunnels.l2tp.tunnelAuthentication

       Possibilities:
               off   (0)
               on   (1)"
   ::= {er1645v2TvTmplIcfEntry 302776320}

er1645v2TvTmplIcfL2tpSecret OBJECT-TYPE
   SYNTAX      DisplayString
   MAX-ACCESS  read-write
   STATUS      current
   DESCRIPTION
      "Path: tunnels.editConf.ipsecL2tpTunnels.l2tp.tunnelSecret"
   ::= {er1645v2TvTmplIcfEntry 302907392}

er1645v2TvTmplIcfL2tpTos OBJECT-TYPE
   SYNTAX      INTEGER
               {
               off (0),
               on (1)
               }
   MAX-ACCESS  read-write
   STATUS      current
   DESCRIPTION
      "Path: tunnels.editConf.ipsecL2tpTunnels.l2tp.copyTos

       Possibilities:
               off   (0)
               on   (1)"
   ::= {er1645v2TvTmplIcfEntry 303955968}

er1645v2TvTmplIcfL2tpRetrans OBJECT-TYPE
   SYNTAX      Integer32
   MAX-ACCESS  read-write
   STATUS      current
   DESCRIPTION
      "Path: tunnels.editConf.ipsecL2tpTunnels.l2tp.maxNrOfRetransmissions"
   ::= {er1645v2TvTmplIcfEntry 303038464}

er1645v2TvTmplIcfL2tpTransmitws OBJECT-TYPE
   SYNTAX      Integer32
   MAX-ACCESS  read-write
   STATUS      current
   DESCRIPTION
      "Path: tunnels.editConf.ipsecL2tpTunnels.l2tp.transmitWindowSize"
   ::= {er1645v2TvTmplIcfEntry 303169536}

er1645v2TvTmplIcfL2tpRcsws OBJECT-TYPE
   SYNTAX      Integer32
   MAX-ACCESS  read-write
   STATUS      current
   DESCRIPTION
      "Path: tunnels.editConf.ipsecL2tpTunnels.l2tp.receiveWindowSize"
   ::= {er1645v2TvTmplIcfEntry 303300608}

er1645v2TvTmplIcfL2tpUdpcheck OBJECT-TYPE
   SYNTAX      INTEGER
               {
               off (0),
               on (1)
               }
   MAX-ACCESS  read-write
   STATUS      current
   DESCRIPTION
      "Path: tunnels.editConf.ipsecL2tpTunnels.l2tp.udpChecksum

       Possibilities:
               off   (0)
               on   (1)"
   ::= {er1645v2TvTmplIcfEntry 303431680}

er1645v2TvTmplIcfL2tpCalledNr OBJECT-TYPE
   SYNTAX      DisplayString
   MAX-ACCESS  read-write
   STATUS      current
   DESCRIPTION
      "Path: tunnels.editConf.ipsecL2tpTunnels.l2tp.calledNr"
   ::= {er1645v2TvTmplIcfEntry 303562752}

er1645v2TvTmplIcfL2tpSpeed OBJECT-TYPE
   SYNTAX      Integer32
   MAX-ACCESS  read-write
   STATUS      current
   DESCRIPTION
      "Path: tunnels.editConf.ipsecL2tpTunnels.l2tp.speed"
   ::= {er1645v2TvTmplIcfEntry 315621376}

er1645v2TvTmplIcfL2tpMtu OBJECT-TYPE
   SYNTAX      Integer32
   MAX-ACCESS  read-write
   STATUS      current
   DESCRIPTION
      "Path: tunnels.editConf.ipsecL2tpTunnels.l2tp.mtu"
   ::= {er1645v2TvTmplIcfEntry 304349184}

er1645v2TvTmplIcfL2tpHostName OBJECT-TYPE
   SYNTAX      DisplayString
   MAX-ACCESS  read-write
   STATUS      current
   DESCRIPTION
      "Path: tunnels.editConf.ipsecL2tpTunnels.l2tp.hostName"
   ::= {er1645v2TvTmplIcfEntry 304480256}

er1645v2TvTmplIcfBackupInterface OBJECT-TYPE
   SYNTAX      DisplayString
   MAX-ACCESS  read-write
   STATUS      current
   DESCRIPTION
      "Path: tunnels.editConf.ipsecL2tpTunnels.backup.interface"
   ::= {er1645v2TvTmplIcfEntry 536936448}

er1645v2TvTmplIcfBackupTimeOut OBJECT-TYPE
   SYNTAX      Integer32
   MAX-ACCESS  read-write
   STATUS      current
   DESCRIPTION
      "Path: tunnels.editConf.ipsecL2tpTunnels.backup.timeOut"
   ::= {er1645v2TvTmplIcfEntry 537067520}

er1645v2TvTmplIcfBackupAutoRetry OBJECT-TYPE
   SYNTAX      INTEGER
               {
               no (0),
               yes (1)
               }
   MAX-ACCESS  read-write
   STATUS      current
   DESCRIPTION
      "Path: tunnels.editConf.ipsecL2tpTunnels.backup.autoRetry

       Possibilities:
               no   (0)
               yes   (1)"
   ::= {er1645v2TvTmplIcfEntry 537133056}

er1645v2TvTmplIcfInbBwCir OBJECT-TYPE
   SYNTAX      Integer32
   MAX-ACCESS  read-write
   STATUS      current
   DESCRIPTION
      "Path: tunnels.editConf.ipsecL2tpTunnels.inboundBandwidth.cir"
   ::= {er1645v2TvTmplIcfEntry 117506048}

er1645v2TvTmplIcfInbBwTc OBJECT-TYPE
   SYNTAX      INTEGER
               {
               auto (0)
               }
   MAX-ACCESS  read-write
   STATUS      current
   DESCRIPTION
      "Path: tunnels.editConf.ipsecL2tpTunnels.inboundBandwidth.tc

       Possibilities:
               auto   (0)"
   ::= {er1645v2TvTmplIcfEntry 117833728}

er1645v2TvTmplIcfInbBwCorrType OBJECT-TYPE
   SYNTAX      INTEGER
               {
               noCorrection (0),
               predefined (1),
               manual (2)
               }
   MAX-ACCESS  read-write
   STATUS      current
   DESCRIPTION
      "Path: tunnels.editConf.ipsecL2tpTunnels.inboundBandwidth.correction.type

       Possibilities:
               noCorrection   (0)
               predefined   (1)
               manual   (2)"
   ::= {er1645v2TvTmplIcfEntry 117579776}

er1645v2TvTmplIcfInbBwCorrPredefEncapsFrameRelay OBJECT-TYPE
   SYNTAX      DisplayString
   MAX-ACCESS  read-write
   STATUS      current
   DESCRIPTION
      "Path: tunnels.editConf.ipsecL2tpTunnels.inboundBandwidth.correction.predefined.encapsulation.frameRelay"
   ::= {er1645v2TvTmplIcfEntry 117589056}

er1645v2TvTmplIcfInbBwCorrPredefEncapsPpp OBJECT-TYPE
   SYNTAX      DisplayString
   MAX-ACCESS  read-write
   STATUS      current
   DESCRIPTION
      "Path: tunnels.editConf.ipsecL2tpTunnels.inboundBandwidth.correction.predefined.encapsulation.ppp"
   ::= {er1645v2TvTmplIcfEntry 117589120}

er1645v2TvTmplIcfInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecL2tpTunnels.inboundBandwidth.correction.predefined.encapsulation.atm.higherLayer

       Possibilities:
               rfc2684   (0)
               ppp   (1)
               pppOverEthernet   (2)"
   ::= {er1645v2TvTmplIcfEntry 117589192}

er1645v2TvTmplIcfInbBwCorrPredefEncapsAtmMp OBJECT-TYPE
   SYNTAX      INTEGER
               {
               llcEncapsulation (0),
               vcMultiplexing (1)
               }
   MAX-ACCESS  read-write
   STATUS      current
   DESCRIPTION
      "Path: tunnels.editConf.ipsecL2tpTunnels.inboundBandwidth.correction.predefined.encapsulation.atm.multiProtocol

       Possibilities:
               llcEncapsulation   (0)
               vcMultiplexing   (1)"
   ::= {er1645v2TvTmplIcfEntry 117589200}

er1645v2TvTmplIcfInbBwCorrPredefEncapsHdlc OBJECT-TYPE
   SYNTAX      DisplayString
   MAX-ACCESS  read-write
   STATUS      current
   DESCRIPTION
      "Path: tunnels.editConf.ipsecL2tpTunnels.inboundBandwidth.correction.predefined.encapsulation.hdlc"
   ::= {er1645v2TvTmplIcfEntry 117589248}

er1645v2TvTmplIcfInbBwCorrPredefEncapsEfmFs OBJECT-TYPE
   SYNTAX      Integer32
   MAX-ACCESS  read-write
   STATUS      current
   DESCRIPTION
      "Path: tunnels.editConf.ipsecL2tpTunnels.inboundBandwidth.correction.predefined.encapsulation.efm.fragmentSize"
   ::= {er1645v2TvTmplIcfEntry 117589320}

er1645v2TvTmplIcfInbBwCorrPredefEncapsEfmIb OBJECT-TYPE
   SYNTAX      Integer32
   MAX-ACCESS  read-write
   STATUS      current
   DESCRIPTION
      "Path: tunnels.editConf.ipsecL2tpTunnels.inboundBandwidth.correction.predefined.encapsulation.efm.idleBytes"
   ::= {er1645v2TvTmplIcfEntry 117589328}

er1645v2TvTmplIcfInbBwCorrPredefMode OBJECT-TYPE
   SYNTAX      INTEGER
               {
               routing (0),
               bridging (1)
               }
   MAX-ACCESS  read-write
   STATUS      current
   DESCRIPTION
      "Path: tunnels.editConf.ipsecL2tpTunnels.inboundBandwidth.correction.predefined.mode

       Possibilities:
               routing   (0)
               bridging   (1)"
   ::= {er1645v2TvTmplIcfEntry 117590016}

er1645v2TvTmplIcfInbBwCorrManualOverhead OBJECT-TYPE
   SYNTAX      Integer32
   MAX-ACCESS  read-write
   STATUS      current
   DESCRIPTION
      "Path: tunnels.editConf.ipsecL2tpTunnels.inboundBandwidth.correction.manual.overhead"
   ::= {er1645v2TvTmplIcfEntry 117596192}

er1645v2TvTmplIcfInbBwCorrManualFrameData OBJECT-TYPE
   SYNTAX      Counter32
   MAX-ACCESS  read-write
   STATUS      current
   DESCRIPTION
      "Path: tunnels.editConf.ipsecL2tpTunnels.inboundBandwidth.correction.manual.frameData

       32 bit unsigned wrappable counter."
   ::= {er1645v2TvTmplIcfEntry 117596224}

er1645v2TvTmplIcfInbBwCorrManualFrameHeader OBJECT-TYPE
   SYNTAX      Counter32
   MAX-ACCESS  read-write
   STATUS      current
   DESCRIPTION
      "Path: tunnels.editConf.ipsecL2tpTunnels.inboundBandwidth.correction.manual.frameHeader

       32 bit unsigned wrappable counter."
   ::= {er1645v2TvTmplIcfEntry 117596256}

er1645v2TvTmplIcfInbBwMaxFifoQLen OBJECT-TYPE
   SYNTAX      Integer32
   MAX-ACCESS  read-write
   STATUS      current
   DESCRIPTION
      "Path: tunnels.editConf.ipsecL2tpTunnels.inboundBandwidth.maxFifoQLen"
   ::= {er1645v2TvTmplIcfEntry 117637120}

er1645v2TvTmplIcfInbBwPriorityPolicy OBJECT-TYPE
   SYNTAX      DisplayString
   MAX-ACCESS  read-write
   STATUS      current
   DESCRIPTION
      "Path: tunnels.editConf.ipsecL2tpTunnels.inboundBandwidth.priorityPolicy"
   ::= {er1645v2TvTmplIcfEntry 117702656}

er1645v2TvTmplIcfBandwidthMode OBJECT-TYPE
   SYNTAX      INTEGER
               {
               reshaping (1),
               policing (2),
               policingReshape (3)
               }
   MAX-ACCESS  read-write
   STATUS      current
   DESCRIPTION
      "Path: tunnels.editConf.ipsecL2tpTunnels.bandwidth.mode

       Possibilities:
               reshaping   (1)
               policing   (2)
               policingReshape   (3)"
   ::= {er1645v2TvTmplIcfEntry 148897792}

er1645v2TvTmplIcfBandwidthCir OBJECT-TYPE
   SYNTAX      Integer32
   MAX-ACCESS  read-write
   STATUS      current
   DESCRIPTION
      "Path: tunnels.editConf.ipsecL2tpTunnels.bandwidth.cir"
   ::= {er1645v2TvTmplIcfEntry 135266304}

er1645v2TvTmplIcfBandwidthEir OBJECT-TYPE
   SYNTAX      Integer32
   MAX-ACCESS  read-write
   STATUS      current
   DESCRIPTION
      "Path: tunnels.editConf.ipsecL2tpTunnels.bandwidth.eir"
   ::= {er1645v2TvTmplIcfEntry 141557760}

er1645v2TvTmplIcfBandwidthUnit OBJECT-TYPE
   SYNTAX      INTEGER
               {
               bitssec (1),
               percent (2)
               }
   MAX-ACCESS  read-write
   STATUS      current
   DESCRIPTION
      "Path: tunnels.editConf.ipsecL2tpTunnels.bandwidth.unit

       Possibilities:
               bits/sec   (1)
               percent   (2)"
   ::= {er1645v2TvTmplIcfEntry 139460608}

er1645v2TvTmplIcfBandwidthTc OBJECT-TYPE
   SYNTAX      INTEGER
               {
               auto (0)
               }
   MAX-ACCESS  read-write
   STATUS      current
   DESCRIPTION
      "Path: tunnels.editConf.ipsecL2tpTunnels.bandwidth.tc

       Possibilities:
               auto   (0)"
   ::= {er1645v2TvTmplIcfEntry 140509184}

er1645v2TvTmplIcfBandwidthTcFactor OBJECT-TYPE
   SYNTAX      INTEGER
               {
               ms (10),
               s100us (1)
               }
   MAX-ACCESS  read-write
   STATUS      current
   DESCRIPTION
      "Path: tunnels.editConf.ipsecL2tpTunnels.bandwidth.tcFactor

       Possibilities:
               ms   (10)
               *100us   (1)"
   ::= {er1645v2TvTmplIcfEntry 142606336}

er1645v2TvTmplIcfBandwidthCorrType OBJECT-TYPE
   SYNTAX      INTEGER
               {
               noCorrection (0),
               predefined (1),
               manual (2)
               }
   MAX-ACCESS  read-write
   STATUS      current
   DESCRIPTION
      "Path: tunnels.editConf.ipsecL2tpTunnels.bandwidth.correction.type

       Possibilities:
               noCorrection   (0)
               predefined   (1)
               manual   (2)"
   ::= {er1645v2TvTmplIcfEntry 136445952}

er1645v2TvTmplIcfBandwidthCorrPredefEncapsFrameRelay OBJECT-TYPE
   SYNTAX      DisplayString
   MAX-ACCESS  read-write
   STATUS      current
   DESCRIPTION
      "Path: tunnels.editConf.ipsecL2tpTunnels.bandwidth.correction.predefined.encapsulation.frameRelay"
   ::= {er1645v2TvTmplIcfEntry 136594432}

er1645v2TvTmplIcfBandwidthCorrPredefEncapsPpp OBJECT-TYPE
   SYNTAX      DisplayString
   MAX-ACCESS  read-write
   STATUS      current
   DESCRIPTION
      "Path: tunnels.editConf.ipsecL2tpTunnels.bandwidth.correction.predefined.encapsulation.ppp"
   ::= {er1645v2TvTmplIcfEntry 136595456}

er1645v2TvTmplIcfBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecL2tpTunnels.bandwidth.correction.predefined.encapsulation.atm.higherLayer

       Possibilities:
               rfc2684   (0)
               ppp   (1)
               pppOverEthernet   (2)"
   ::= {er1645v2TvTmplIcfEntry 136596608}

er1645v2TvTmplIcfBandwidthCorrPredefEncapsAtmMp OBJECT-TYPE
   SYNTAX      INTEGER
               {
               llcEncapsulation (0),
               vcMultiplexing (1)
               }
   MAX-ACCESS  read-write
   STATUS      current
   DESCRIPTION
      "Path: tunnels.editConf.ipsecL2tpTunnels.bandwidth.correction.predefined.encapsulation.atm.multiProtocol

       Possibilities:
               llcEncapsulation   (0)
               vcMultiplexing   (1)"
   ::= {er1645v2TvTmplIcfEntry 136596736}

er1645v2TvTmplIcfBandwidthCorrPredefEncapsHdlc OBJECT-TYPE
   SYNTAX      DisplayString
   MAX-ACCESS  read-write
   STATUS      current
   DESCRIPTION
      "Path: tunnels.editConf.ipsecL2tpTunnels.bandwidth.correction.predefined.encapsulation.hdlc"
   ::= {er1645v2TvTmplIcfEntry 136597504}

er1645v2TvTmplIcfBandwidthCorrPredefEncapsEfmFs OBJECT-TYPE
   SYNTAX      Integer32
   MAX-ACCESS  read-write
   STATUS      current
   DESCRIPTION
      "Path: tunnels.editConf.ipsecL2tpTunnels.bandwidth.correction.predefined.encapsulation.efm.fragmentSize"
   ::= {er1645v2TvTmplIcfEntry 136598656}

er1645v2TvTmplIcfBandwidthCorrPredefEncapsEfmIb OBJECT-TYPE
   SYNTAX      Integer32
   MAX-ACCESS  read-write
   STATUS      current
   DESCRIPTION
      "Path: tunnels.editConf.ipsecL2tpTunnels.bandwidth.correction.predefined.encapsulation.efm.idleBytes"
   ::= {er1645v2TvTmplIcfEntry 136598784}

er1645v2TvTmplIcfBandwidthCorrPredefMode OBJECT-TYPE
   SYNTAX      INTEGER
               {
               routing (0),
               bridging (1)
               }
   MAX-ACCESS  read-write
   STATUS      current
   DESCRIPTION
      "Path: tunnels.editConf.ipsecL2tpTunnels.bandwidth.correction.predefined.mode

       Possibilities:
               routing   (0)
               bridging   (1)"
   ::= {er1645v2TvTmplIcfEntry 136609792}

er1645v2TvTmplIcfBandwidthCorrManualOverhead OBJECT-TYPE
   SYNTAX      Integer32
   MAX-ACCESS  read-write
   STATUS      current
   DESCRIPTION
      "Path: tunnels.editConf.ipsecL2tpTunnels.bandwidth.correction.manual.overhead"
   ::= {er1645v2TvTmplIcfEntry 136708608}

er1645v2TvTmplIcfBandwidthCorrManualFrameData OBJECT-TYPE
   SYNTAX      Counter32
   MAX-ACCESS  read-write
   STATUS      current
   DESCRIPTION
      "Path: tunnels.editConf.ipsecL2tpTunnels.bandwidth.correction.manual.frameData

       32 bit unsigned wrappable counter."
   ::= {er1645v2TvTmplIcfEntry 136709120}

er1645v2TvTmplIcfBandwidthCorrManualFrameHeader OBJECT-TYPE
   SYNTAX      Counter32
   MAX-ACCESS  read-write
   STATUS      current
   DESCRIPTION
      "Path: tunnels.editConf.ipsecL2tpTunnels.bandwidth.correction.manual.frameHeader

       32 bit unsigned wrappable counter."
   ::= {er1645v2TvTmplIcfEntry 136709632}

er1645v2TvTmplIcfBandwidthMaxFifoQLen OBJECT-TYPE
   SYNTAX      Integer32
   MAX-ACCESS  read-write
   STATUS      current
   DESCRIPTION
      "Path: tunnels.editConf.ipsecL2tpTunnels.bandwidth.maxFifoQLen"
   ::= {er1645v2TvTmplIcfEntry 137363456}

er1645v2TvTmplIcfBandwidthDeFlagCir OBJECT-TYPE
   SYNTAX      INTEGER
               {
               allowed (1),
               notAllowed (2)
               }
   MAX-ACCESS  read-write
   STATUS      current
   DESCRIPTION
      "Path: tunnels.editConf.ipsecL2tpTunnels.bandwidth.deFlag.cir

       Possibilities:
               allowed   (1)
               notAllowed   (2)"
   ::= {er1645v2TvTmplIcfEntry 147853312}

er1645v2TvTmplIcfBandwidthDeFlagEir OBJECT-TYPE
   SYNTAX      INTEGER
               {
               allowed (1),
               notAllowed (2)
               }
   MAX-ACCESS  read-write
   STATUS      current
   DESCRIPTION
      "Path: tunnels.editConf.ipsecL2tpTunnels.bandwidth.deFlag.eir

       Possibilities:
               allowed   (1)
               notAllowed   (2)"
   ::= {er1645v2TvTmplIcfEntry 147857408}

er1645v2TvTmplIcfBandwidthDeFlagViolate OBJECT-TYPE
   SYNTAX      INTEGER
               {
               allowed (1),
               notAllowed (2)
               }
   MAX-ACCESS  read-write
   STATUS      current
   DESCRIPTION
      "Path: tunnels.editConf.ipsecL2tpTunnels.bandwidth.deFlag.violate

       Possibilities:
               allowed   (1)
               notAllowed   (2)"
   ::= {er1645v2TvTmplIcfEntry 147861504}

er1645v2TvTmplIcfBandwidthActCirActNone OBJECT-TYPE
   SYNTAX      OCTET STRING
   MAX-ACCESS  read-write
   STATUS      current
   DESCRIPTION
      "Path: tunnels.editConf.ipsecL2tpTunnels.bandwidth.action.cirAction.none"
   ::= {er1645v2TvTmplIcfEntry 150085632}

er1645v2TvTmplIcfBandwidthActCirActEthCos1 OBJECT-TYPE
   SYNTAX      INTEGER
               {
               unchanged (256)
               }
   MAX-ACCESS  read-write
   STATUS      current
   DESCRIPTION
      "Path: tunnels.editConf.ipsecL2tpTunnels.bandwidth.action.cirAction.ethernet.cosDepth1

       Possibilities:
               unchanged   (256)"
   ::= {er1645v2TvTmplIcfEntry 150094080}

er1645v2TvTmplIcfBandwidthActCirActEthDei1 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth1

       Possibilities:
               unchanged   (255)
               clear   (0)
               set   (1)"
   ::= {er1645v2TvTmplIcfEntry 150099200}

er1645v2TvTmplIcfBandwidthActCirActEthCos2 OBJECT-TYPE
   SYNTAX      INTEGER
               {
               unchanged (256)
               }
   MAX-ACCESS  read-write
   STATUS      current
   DESCRIPTION
      "Path: tunnels.editConf.ipsecL2tpTunnels.bandwidth.action.cirAction.ethernet.cosDepth2

       Possibilities:
               unchanged   (256)"
   ::= {er1645v2TvTmplIcfEntry 150094336}

er1645v2TvTmplIcfBandwidthActCirActEthDei2 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth2

       Possibilities:
               unchanged   (255)
               clear   (0)
               set   (1)"
   ::= {er1645v2TvTmplIcfEntry 150099456}

er1645v2TvTmplIcfBandwidthActCirActEthCos3 OBJECT-TYPE
   SYNTAX      INTEGER
               {
               unchanged (256)
               }
   MAX-ACCESS  read-write
   STATUS      current
   DESCRIPTION
      "Path: tunnels.editConf.ipsecL2tpTunnels.bandwidth.action.cirAction.ethernet.cosDepth3

       Possibilities:
               unchanged   (256)"
   ::= {er1645v2TvTmplIcfEntry 150094592}

er1645v2TvTmplIcfBandwidthActCirActEthDei3 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth3

       Possibilities:
               unchanged   (255)
               clear   (0)
               set   (1)"
   ::= {er1645v2TvTmplIcfEntry 150099712}

er1645v2TvTmplIcfBandwidthActCirActEthCos4 OBJECT-TYPE
   SYNTAX      INTEGER
               {
               unchanged (256)
               }
   MAX-ACCESS  read-write
   STATUS      current
   DESCRIPTION
      "Path: tunnels.editConf.ipsecL2tpTunnels.bandwidth.action.cirAction.ethernet.cosDepth4

       Possibilities:
               unchanged   (256)"
   ::= {er1645v2TvTmplIcfEntry 150094848}

er1645v2TvTmplIcfBandwidthActCirActEthDei4 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth4

       Possibilities:
               unchanged   (255)
               clear   (0)
               set   (1)"
   ::= {er1645v2TvTmplIcfEntry 150099968}

er1645v2TvTmplIcfBandwidthActCirActEthCos5 OBJECT-TYPE
   SYNTAX      INTEGER
               {
               unchanged (256)
               }
   MAX-ACCESS  read-write
   STATUS      current
   DESCRIPTION
      "Path: tunnels.editConf.ipsecL2tpTunnels.bandwidth.action.cirAction.ethernet.cosDepth5

       Possibilities:
               unchanged   (256)"
   ::= {er1645v2TvTmplIcfEntry 150095104}

er1645v2TvTmplIcfBandwidthActCirActEthDei5 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth5

       Possibilities:
               unchanged   (255)
               clear   (0)
               set   (1)"
   ::= {er1645v2TvTmplIcfEntry 150100224}

er1645v2TvTmplIcfBandwidthActCirActEthCos6 OBJECT-TYPE
   SYNTAX      INTEGER
               {
               unchanged (256)
               }
   MAX-ACCESS  read-write
   STATUS      current
   DESCRIPTION
      "Path: tunnels.editConf.ipsecL2tpTunnels.bandwidth.action.cirAction.ethernet.cosDepth6

       Possibilities:
               unchanged   (256)"
   ::= {er1645v2TvTmplIcfEntry 150095360}

er1645v2TvTmplIcfBandwidthActCirActEthDei6 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth6

       Possibilities:
               unchanged   (255)
               clear   (0)
               set   (1)"
   ::= {er1645v2TvTmplIcfEntry 150100480}

er1645v2TvTmplIcfBandwidthActCirActEthCos7 OBJECT-TYPE
   SYNTAX      INTEGER
               {
               unchanged (256)
               }
   MAX-ACCESS  read-write
   STATUS      current
   DESCRIPTION
      "Path: tunnels.editConf.ipsecL2tpTunnels.bandwidth.action.cirAction.ethernet.cosDepth7

       Possibilities:
               unchanged   (256)"
   ::= {er1645v2TvTmplIcfEntry 150095616}

er1645v2TvTmplIcfBandwidthActCirActEthDei7 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth7

       Possibilities:
               unchanged   (255)
               clear   (0)
               set   (1)"
   ::= {er1645v2TvTmplIcfEntry 150100736}

er1645v2TvTmplIcfBandwidthActCirActEthCos8 OBJECT-TYPE
   SYNTAX      INTEGER
               {
               unchanged (256)
               }
   MAX-ACCESS  read-write
   STATUS      current
   DESCRIPTION
      "Path: tunnels.editConf.ipsecL2tpTunnels.bandwidth.action.cirAction.ethernet.cosDepth8

       Possibilities:
               unchanged   (256)"
   ::= {er1645v2TvTmplIcfEntry 150095872}

er1645v2TvTmplIcfBandwidthActCirActEthDei8 OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deiDepth8

       Possibilities:
               unchanged   (255)
               clear   (0)
               set   (1)"
   ::= {er1645v2TvTmplIcfEntry 150100992}

er1645v2TvTmplIcfBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplIcfEntry 150096128}

er1645v2TvTmplIcfBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplIcfEntry 150096384}

er1645v2TvTmplIcfBandwidthActCirActEthDrpLev OBJECT-TYPE
   SYNTAX      INTEGER
               {
               unchanged (0)
               }
   MAX-ACCESS  read-write
   STATUS      current
   DESCRIPTION
      "Path: tunnels.editConf.ipsecL2tpTunnels.bandwidth.action.cirAction.ethernet.dropLevel

       Possibilities:
               unchanged   (0)"
   ::= {er1645v2TvTmplIcfEntry 150096640}

er1645v2TvTmplIcfBandwidthActCirActEthDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ethernet.deFlag

       Possibilities:
               unchanged   (255)
               clear   (0)
               set   (1)"
   ::= {er1645v2TvTmplIcfEntry 150097408}

er1645v2TvTmplIcfBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplIcfEntry 150120704}

er1645v2TvTmplIcfBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplIcfEntry 150120960}

er1645v2TvTmplIcfBandwidthActCirActIpDrpLev OBJECT-TYPE
   SYNTAX      INTEGER
               {
               unchanged (0)
               }
   MAX-ACCESS  read-write
   STATUS      current
   DESCRIPTION
      "Path: tunnels.editConf.ipsecL2tpTunnels.bandwidth.action.cirAction.ip.dropLevel

       Possibilities:
               unchanged   (0)"
   ::= {er1645v2TvTmplIcfEntry 150121216}

er1645v2TvTmplIcfBandwidthActCirActIpDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.cirAction.ip.deFlag

       Possibilities:
               unchanged   (255)
               clear   (0)
               set   (1)"
   ::= {er1645v2TvTmplIcfEntry 150121984}

er1645v2TvTmplIcfBandwidthActEirActNone OBJECT-TYPE
   SYNTAX      OCTET STRING
   MAX-ACCESS  read-write
   STATUS      current
   DESCRIPTION
      "Path: tunnels.editConf.ipsecL2tpTunnels.bandwidth.action.eirAction.none"
   ::= {er1645v2TvTmplIcfEntry 150216704}

er1645v2TvTmplIcfBandwidthActEirActEthCos1 OBJECT-TYPE
   SYNTAX      INTEGER
               {
               unchanged (256)
               }
   MAX-ACCESS  read-write
   STATUS      current
   DESCRIPTION
      "Path: tunnels.editConf.ipsecL2tpTunnels.bandwidth.action.eirAction.ethernet.cosDepth1

       Possibilities:
               unchanged   (256)"
   ::= {er1645v2TvTmplIcfEntry 150225152}

er1645v2TvTmplIcfBandwidthActEirActEthDei1 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth1

       Possibilities:
               unchanged   (255)
               clear   (0)
               set   (1)"
   ::= {er1645v2TvTmplIcfEntry 150230272}

er1645v2TvTmplIcfBandwidthActEirActEthCos2 OBJECT-TYPE
   SYNTAX      INTEGER
               {
               unchanged (256)
               }
   MAX-ACCESS  read-write
   STATUS      current
   DESCRIPTION
      "Path: tunnels.editConf.ipsecL2tpTunnels.bandwidth.action.eirAction.ethernet.cosDepth2

       Possibilities:
               unchanged   (256)"
   ::= {er1645v2TvTmplIcfEntry 150225408}

er1645v2TvTmplIcfBandwidthActEirActEthDei2 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth2

       Possibilities:
               unchanged   (255)
               clear   (0)
               set   (1)"
   ::= {er1645v2TvTmplIcfEntry 150230528}

er1645v2TvTmplIcfBandwidthActEirActEthCos3 OBJECT-TYPE
   SYNTAX      INTEGER
               {
               unchanged (256)
               }
   MAX-ACCESS  read-write
   STATUS      current
   DESCRIPTION
      "Path: tunnels.editConf.ipsecL2tpTunnels.bandwidth.action.eirAction.ethernet.cosDepth3

       Possibilities:
               unchanged   (256)"
   ::= {er1645v2TvTmplIcfEntry 150225664}

er1645v2TvTmplIcfBandwidthActEirActEthDei3 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth3

       Possibilities:
               unchanged   (255)
               clear   (0)
               set   (1)"
   ::= {er1645v2TvTmplIcfEntry 150230784}

er1645v2TvTmplIcfBandwidthActEirActEthCos4 OBJECT-TYPE
   SYNTAX      INTEGER
               {
               unchanged (256)
               }
   MAX-ACCESS  read-write
   STATUS      current
   DESCRIPTION
      "Path: tunnels.editConf.ipsecL2tpTunnels.bandwidth.action.eirAction.ethernet.cosDepth4

       Possibilities:
               unchanged   (256)"
   ::= {er1645v2TvTmplIcfEntry 150225920}

er1645v2TvTmplIcfBandwidthActEirActEthDei4 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth4

       Possibilities:
               unchanged   (255)
               clear   (0)
               set   (1)"
   ::= {er1645v2TvTmplIcfEntry 150231040}

er1645v2TvTmplIcfBandwidthActEirActEthCos5 OBJECT-TYPE
   SYNTAX      INTEGER
               {
               unchanged (256)
               }
   MAX-ACCESS  read-write
   STATUS      current
   DESCRIPTION
      "Path: tunnels.editConf.ipsecL2tpTunnels.bandwidth.action.eirAction.ethernet.cosDepth5

       Possibilities:
               unchanged   (256)"
   ::= {er1645v2TvTmplIcfEntry 150226176}

er1645v2TvTmplIcfBandwidthActEirActEthDei5 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth5

       Possibilities:
               unchanged   (255)
               clear   (0)
               set   (1)"
   ::= {er1645v2TvTmplIcfEntry 150231296}

er1645v2TvTmplIcfBandwidthActEirActEthCos6 OBJECT-TYPE
   SYNTAX      INTEGER
               {
               unchanged (256)
               }
   MAX-ACCESS  read-write
   STATUS      current
   DESCRIPTION
      "Path: tunnels.editConf.ipsecL2tpTunnels.bandwidth.action.eirAction.ethernet.cosDepth6

       Possibilities:
               unchanged   (256)"
   ::= {er1645v2TvTmplIcfEntry 150226432}

er1645v2TvTmplIcfBandwidthActEirActEthDei6 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth6

       Possibilities:
               unchanged   (255)
               clear   (0)
               set   (1)"
   ::= {er1645v2TvTmplIcfEntry 150231552}

er1645v2TvTmplIcfBandwidthActEirActEthCos7 OBJECT-TYPE
   SYNTAX      INTEGER
               {
               unchanged (256)
               }
   MAX-ACCESS  read-write
   STATUS      current
   DESCRIPTION
      "Path: tunnels.editConf.ipsecL2tpTunnels.bandwidth.action.eirAction.ethernet.cosDepth7

       Possibilities:
               unchanged   (256)"
   ::= {er1645v2TvTmplIcfEntry 150226688}

er1645v2TvTmplIcfBandwidthActEirActEthDei7 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth7

       Possibilities:
               unchanged   (255)
               clear   (0)
               set   (1)"
   ::= {er1645v2TvTmplIcfEntry 150231808}

er1645v2TvTmplIcfBandwidthActEirActEthCos8 OBJECT-TYPE
   SYNTAX      INTEGER
               {
               unchanged (256)
               }
   MAX-ACCESS  read-write
   STATUS      current
   DESCRIPTION
      "Path: tunnels.editConf.ipsecL2tpTunnels.bandwidth.action.eirAction.ethernet.cosDepth8

       Possibilities:
               unchanged   (256)"
   ::= {er1645v2TvTmplIcfEntry 150226944}

er1645v2TvTmplIcfBandwidthActEirActEthDei8 OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deiDepth8

       Possibilities:
               unchanged   (255)
               clear   (0)
               set   (1)"
   ::= {er1645v2TvTmplIcfEntry 150232064}

er1645v2TvTmplIcfBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplIcfEntry 150227200}

er1645v2TvTmplIcfBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplIcfEntry 150227456}

er1645v2TvTmplIcfBandwidthActEirActEthDrpLev OBJECT-TYPE
   SYNTAX      INTEGER
               {
               unchanged (0)
               }
   MAX-ACCESS  read-write
   STATUS      current
   DESCRIPTION
      "Path: tunnels.editConf.ipsecL2tpTunnels.bandwidth.action.eirAction.ethernet.dropLevel

       Possibilities:
               unchanged   (0)"
   ::= {er1645v2TvTmplIcfEntry 150227712}

er1645v2TvTmplIcfBandwidthActEirActEthDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ethernet.deFlag

       Possibilities:
               unchanged   (255)
               clear   (0)
               set   (1)"
   ::= {er1645v2TvTmplIcfEntry 150228480}

er1645v2TvTmplIcfBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplIcfEntry 150251776}

er1645v2TvTmplIcfBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplIcfEntry 150252032}

er1645v2TvTmplIcfBandwidthActEirActIpDrpLev OBJECT-TYPE
   SYNTAX      INTEGER
               {
               unchanged (0)
               }
   MAX-ACCESS  read-write
   STATUS      current
   DESCRIPTION
      "Path: tunnels.editConf.ipsecL2tpTunnels.bandwidth.action.eirAction.ip.dropLevel

       Possibilities:
               unchanged   (0)"
   ::= {er1645v2TvTmplIcfEntry 150252288}

er1645v2TvTmplIcfBandwidthActEirActIpDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.eirAction.ip.deFlag

       Possibilities:
               unchanged   (255)
               clear   (0)
               set   (1)"
   ::= {er1645v2TvTmplIcfEntry 150253056}

er1645v2TvTmplIcfBandwidthActViolActNone OBJECT-TYPE
   SYNTAX      OCTET STRING
   MAX-ACCESS  read-write
   STATUS      current
   DESCRIPTION
      "Path: tunnels.editConf.ipsecL2tpTunnels.bandwidth.action.violateAction.none"
   ::= {er1645v2TvTmplIcfEntry 150347776}

er1645v2TvTmplIcfBandwidthActViolActDrop OBJECT-TYPE
   SYNTAX      OCTET STRING
   MAX-ACCESS  read-write
   STATUS      current
   DESCRIPTION
      "Path: tunnels.editConf.ipsecL2tpTunnels.bandwidth.action.violateAction.drop"
   ::= {er1645v2TvTmplIcfEntry 150364160}

er1645v2TvTmplIcfBandwidthActViolActEthCos1 OBJECT-TYPE
   SYNTAX      INTEGER
               {
               unchanged (256)
               }
   MAX-ACCESS  read-write
   STATUS      current
   DESCRIPTION
      "Path: tunnels.editConf.ipsecL2tpTunnels.bandwidth.action.violateAction.ethernet.cosDepth1

       Possibilities:
               unchanged   (256)"
   ::= {er1645v2TvTmplIcfEntry 150356224}

er1645v2TvTmplIcfBandwidthActViolActEthDei1 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth1

       Possibilities:
               unchanged   (255)
               clear   (0)
               set   (1)"
   ::= {er1645v2TvTmplIcfEntry 150361344}

er1645v2TvTmplIcfBandwidthActViolActEthCos2 OBJECT-TYPE
   SYNTAX      INTEGER
               {
               unchanged (256)
               }
   MAX-ACCESS  read-write
   STATUS      current
   DESCRIPTION
      "Path: tunnels.editConf.ipsecL2tpTunnels.bandwidth.action.violateAction.ethernet.cosDepth2

       Possibilities:
               unchanged   (256)"
   ::= {er1645v2TvTmplIcfEntry 150356480}

er1645v2TvTmplIcfBandwidthActViolActEthDei2 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth2

       Possibilities:
               unchanged   (255)
               clear   (0)
               set   (1)"
   ::= {er1645v2TvTmplIcfEntry 150361600}

er1645v2TvTmplIcfBandwidthActViolActEthCos3 OBJECT-TYPE
   SYNTAX      INTEGER
               {
               unchanged (256)
               }
   MAX-ACCESS  read-write
   STATUS      current
   DESCRIPTION
      "Path: tunnels.editConf.ipsecL2tpTunnels.bandwidth.action.violateAction.ethernet.cosDepth3

       Possibilities:
               unchanged   (256)"
   ::= {er1645v2TvTmplIcfEntry 150356736}

er1645v2TvTmplIcfBandwidthActViolActEthDei3 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth3

       Possibilities:
               unchanged   (255)
               clear   (0)
               set   (1)"
   ::= {er1645v2TvTmplIcfEntry 150361856}

er1645v2TvTmplIcfBandwidthActViolActEthCos4 OBJECT-TYPE
   SYNTAX      INTEGER
               {
               unchanged (256)
               }
   MAX-ACCESS  read-write
   STATUS      current
   DESCRIPTION
      "Path: tunnels.editConf.ipsecL2tpTunnels.bandwidth.action.violateAction.ethernet.cosDepth4

       Possibilities:
               unchanged   (256)"
   ::= {er1645v2TvTmplIcfEntry 150356992}

er1645v2TvTmplIcfBandwidthActViolActEthDei4 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth4

       Possibilities:
               unchanged   (255)
               clear   (0)
               set   (1)"
   ::= {er1645v2TvTmplIcfEntry 150362112}

er1645v2TvTmplIcfBandwidthActViolActEthCos5 OBJECT-TYPE
   SYNTAX      INTEGER
               {
               unchanged (256)
               }
   MAX-ACCESS  read-write
   STATUS      current
   DESCRIPTION
      "Path: tunnels.editConf.ipsecL2tpTunnels.bandwidth.action.violateAction.ethernet.cosDepth5

       Possibilities:
               unchanged   (256)"
   ::= {er1645v2TvTmplIcfEntry 150357248}

er1645v2TvTmplIcfBandwidthActViolActEthDei5 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth5

       Possibilities:
               unchanged   (255)
               clear   (0)
               set   (1)"
   ::= {er1645v2TvTmplIcfEntry 150362368}

er1645v2TvTmplIcfBandwidthActViolActEthCos6 OBJECT-TYPE
   SYNTAX      INTEGER
               {
               unchanged (256)
               }
   MAX-ACCESS  read-write
   STATUS      current
   DESCRIPTION
      "Path: tunnels.editConf.ipsecL2tpTunnels.bandwidth.action.violateAction.ethernet.cosDepth6

       Possibilities:
               unchanged   (256)"
   ::= {er1645v2TvTmplIcfEntry 150357504}

er1645v2TvTmplIcfBandwidthActViolActEthDei6 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth6

       Possibilities:
               unchanged   (255)
               clear   (0)
               set   (1)"
   ::= {er1645v2TvTmplIcfEntry 150362624}

er1645v2TvTmplIcfBandwidthActViolActEthCos7 OBJECT-TYPE
   SYNTAX      INTEGER
               {
               unchanged (256)
               }
   MAX-ACCESS  read-write
   STATUS      current
   DESCRIPTION
      "Path: tunnels.editConf.ipsecL2tpTunnels.bandwidth.action.violateAction.ethernet.cosDepth7

       Possibilities:
               unchanged   (256)"
   ::= {er1645v2TvTmplIcfEntry 150357760}

er1645v2TvTmplIcfBandwidthActViolActEthDei7 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth7

       Possibilities:
               unchanged   (255)
               clear   (0)
               set   (1)"
   ::= {er1645v2TvTmplIcfEntry 150362880}

er1645v2TvTmplIcfBandwidthActViolActEthCos8 OBJECT-TYPE
   SYNTAX      INTEGER
               {
               unchanged (256)
               }
   MAX-ACCESS  read-write
   STATUS      current
   DESCRIPTION
      "Path: tunnels.editConf.ipsecL2tpTunnels.bandwidth.action.violateAction.ethernet.cosDepth8

       Possibilities:
               unchanged   (256)"
   ::= {er1645v2TvTmplIcfEntry 150358016}

er1645v2TvTmplIcfBandwidthActViolActEthDei8 OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deiDepth8

       Possibilities:
               unchanged   (255)
               clear   (0)
               set   (1)"
   ::= {er1645v2TvTmplIcfEntry 150363136}

er1645v2TvTmplIcfBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplIcfEntry 150358272}

er1645v2TvTmplIcfBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplIcfEntry 150358528}

er1645v2TvTmplIcfBandwidthActViolActEthDrpLev OBJECT-TYPE
   SYNTAX      INTEGER
               {
               unchanged (0)
               }
   MAX-ACCESS  read-write
   STATUS      current
   DESCRIPTION
      "Path: tunnels.editConf.ipsecL2tpTunnels.bandwidth.action.violateAction.ethernet.dropLevel

       Possibilities:
               unchanged   (0)"
   ::= {er1645v2TvTmplIcfEntry 150358784}

er1645v2TvTmplIcfBandwidthActViolActEthDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ethernet.deFlag

       Possibilities:
               unchanged   (255)
               clear   (0)
               set   (1)"
   ::= {er1645v2TvTmplIcfEntry 150359552}

er1645v2TvTmplIcfBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecL2tpTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplIcfEntry 150382848}

er1645v2TvTmplIcfBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecL2tpTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplIcfEntry 150383104}

er1645v2TvTmplIcfBandwidthActViolActIpDrpLev OBJECT-TYPE
   SYNTAX      INTEGER
               {
               unchanged (0)
               }
   MAX-ACCESS  read-write
   STATUS      current
   DESCRIPTION
      "Path: tunnels.editConf.ipsecL2tpTunnels.bandwidth.action.violateAction.ip.dropLevel

       Possibilities:
               unchanged   (0)"
   ::= {er1645v2TvTmplIcfEntry 150383360}

er1645v2TvTmplIcfBandwidthActViolActIpDeFlag OBJECT-TYPE
   SYNTAX      INTEGER
               {
               unchanged (255),
               clear (0),
               set (1)
               }
   MAX-ACCESS  read-write
   STATUS      current
   DESCRIPTION
      "Path: tunnels.editConf.ipsecL2tpTunnels.bandwidth.action.violateAction.ip.deFlag

       Possibilities:
               unchanged   (255)
               clear   (0)
               set   (1)"
   ::= {er1645v2TvTmplIcfEntry 150384128}

er1645v2TvTmplIcfBridgingVlTVlans OBJECT-TYPE
   SYNTAX      SEQUENCE OF Er1645v2TvTmplIcfBridgingVlTVlansEntry
   MAX-ACCESS  not-accessible
   STATUS      current
   DESCRIPTION
      ""
   ::= {er1645v2TvTmplIcf 459079680}

er1645v2TvTmplIcfBridgingVlTVlansEntry OBJECT-TYPE
   SYNTAX      Er1645v2TvTmplIcfBridgingVlTVlansEntry
   MAX-ACCESS  not-accessible
   STATUS      current
   DESCRIPTION
      ""
   INDEX      { er1645v2TvTmplIcfTableIx,
                er1645v2TvTmplIcfBridgingVlTVlansTableIx }
   ::= {er1645v2TvTmplIcfBridgingVlTVlans 1}

Er1645v2TvTmplIcfBridgingVlTVlansEntry ::=
   SEQUENCE
      {
      er1645v2TvTmplIcfBridgingVlTVlansActions
         VariableLengthTableActions,
      er1645v2TvTmplIcfBridgingVlTVlansTableIx
         TableIndex,
      er1645v2TvTmplIcfBridgingVlTVlansVid
         Integer32,
      er1645v2TvTmplIcfBridgingVlTVlansEndVid
         Integer32,
      er1645v2TvTmplIcfBridgingVlTVlansAction
         INTEGER,
      er1645v2TvTmplIcfBridgingVlTVlansTagInfoTpid
         INTEGER,
      er1645v2TvTmplIcfBridgingVlTVlansTagInfoVid
         Integer32
      }

er1645v2TvTmplIcfBridgingVlTVlansActions OBJECT-TYPE
   SYNTAX      VariableLengthTableActions
   MAX-ACCESS  read-write
   STATUS      current
   DESCRIPTION
      "By way of this field, some manipulations
       on this table may be performed."
   ::= {er1645v2TvTmplIcfBridgingVlTVlansEntry 2}

er1645v2TvTmplIcfBridgingVlTVlansTableIx OBJECT-TYPE
   SYNTAX      TableIndex
   MAX-ACCESS  not-accessible
   STATUS      current
   DESCRIPTION
      ""
   ::= {er1645v2TvTmplIcfBridgingVlTVlansEntry 11}

er1645v2TvTmplIcfBridgingVlTVlansVid OBJECT-TYPE
   SYNTAX      Integer32
   MAX-ACCESS  read-write
   STATUS      current
   DESCRIPTION
      "Path: tunnels.editConf.ipsecL2tpTunnels.bridging.vlanTagging.vlans.vid"
   ::= {er1645v2TvTmplIcfBridgingVlTVlansEntry 536870912}

er1645v2TvTmplIcfBridgingVlTVlansEndVid OBJECT-TYPE
   SYNTAX      Integer32
   MAX-ACCESS  read-write
   STATUS      current
   DESCRIPTION
      "Path: tunnels.editConf.ipsecL2tpTunnels.bridging.vlanTagging.vlans.endVid"
   ::= {er1645v2TvTmplIcfBridgingVlTVlansEntry 2147483648}

er1645v2TvTmplIcfBridgingVlTVlansAction OBJECT-TYPE
   SYNTAX      INTEGER
               {
               discard (0),
               accept (1),
               tag (2)
               }
   MAX-ACCESS  read-write
   STATUS      current
   DESCRIPTION
      "Path: tunnels.editConf.ipsecL2tpTunnels.bridging.vlanTagging.vlans.action

       Possibilities:
               discard   (0)
               accept   (1)
               tag   (2)"
   ::= {er1645v2TvTmplIcfBridgingVlTVlansEntry 1073741824}

er1645v2TvTmplIcfBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecL2tpTunnels.bridging.vlanTagging.vlans.tagInfo.tpid

       Possibilities:
               dot1Q   (33024)
               dot1ad   (34984)
               0x9100   (37120)
               0x9200   (37376)
               0x9300   (37632)"
   ::= {er1645v2TvTmplIcfBridgingVlTVlansEntry 1677721600}

er1645v2TvTmplIcfBridgingVlTVlansTagInfoVid OBJECT-TYPE
   SYNTAX      Integer32
   MAX-ACCESS  read-write
   STATUS      current
   DESCRIPTION
      "Path: tunnels.editConf.ipsecL2tpTunnels.bridging.vlanTagging.vlans.tagInfo.vid"
   ::= {er1645v2TvTmplIcfBridgingVlTVlansEntry 1744830464}


er1645v2TvTmplCiGre OBJECT IDENTIFIER ::= {er1645v2TvTmpl 24}

er1645v2TvTmplCiGreSSCTable OBJECT-TYPE
   SYNTAX      SEQUENCE OF Er1645v2TvTmplCiGreEntry
   MAX-ACCESS  not-accessible
   STATUS      current
   DESCRIPTION
      ""
   ::= {er1645v2TvTmplCiGre 1}

er1645v2TvTmplCiGreEntry OBJECT-TYPE
   SYNTAX      Er1645v2TvTmplCiGreEntry
   MAX-ACCESS  not-accessible
   STATUS      current
   DESCRIPTION
      ""
   INDEX      { er1645v2TvTmplCiGreTableIx }
   ::= {er1645v2TvTmplCiGreSSCTable 1}

Er1645v2TvTmplCiGreEntry ::=
   SEQUENCE
      {
      er1645v2TvTmplCiGreActions
         VariableLengthTableActions,
      er1645v2TvTmplCiGreTableIx
         TableIndex,
      er1645v2TvTmplCiGreName
         DisplayString,
      er1645v2TvTmplCiGreRemark
         DisplayString,
      er1645v2TvTmplCiGreAdminStatus
         INTEGER,
      er1645v2TvTmplCiGreMode
         INTEGER,
      er1645v2TvTmplCiGrePriorityPolicy
         DisplayString,
      er1645v2TvTmplCiGreIpVrfRouter
         DisplayString,
      er1645v2TvTmplCiGreIpAdr
         IpAddress,
      er1645v2TvTmplCiGreIpNetm
         IpAddress,
      er1645v2TvTmplCiGreIpSNetName
         INTEGER,
      er1645v2TvTmplCiGreIpSNetCust
         DisplayString,
      er1645v2TvTmplCiGreIpRem
         IpAddress,
      er1645v2TvTmplCiGreIpGwPref
         Integer32,
      er1645v2TvTmplCiGreIpMtu
         Integer32,
      er1645v2TvTmplCiGreIpMssAdjust
         INTEGER,
      er1645v2TvTmplCiGreIpRipMetric
         Integer32,
      er1645v2TvTmplCiGreIpRipMetricOut
         Integer32,
      er1645v2TvTmplCiGreIpRipMode
         INTEGER,
      er1645v2TvTmplCiGreIpRipTxVersion
         INTEGER,
      er1645v2TvTmplCiGreIpRipRxVersion
         INTEGER,
      er1645v2TvTmplCiGreIpRipSplitHorizon
         INTEGER,
      er1645v2TvTmplCiGreIpRipAuth
         INTEGER,
      er1645v2TvTmplCiGreIpRipFilter
         DisplayString,
      er1645v2TvTmplCiGreIpRipFilterIn
         DisplayString,
      er1645v2TvTmplCiGreIpRipSnapshot
         INTEGER,
      er1645v2TvTmplCiGreIpRipClearNextHop
         INTEGER,
      er1645v2TvTmplCiGreIpAccPol
         DisplayString,
      er1645v2TvTmplCiGreIpAB
         DisplayString,
      er1645v2TvTmplCiGreIpMA
         INTEGER,
      er1645v2TvTmplCiGreIpMF
         Integer32,
      er1645v2TvTmplCiGreIpDB
         INTEGER,
      er1645v2TvTmplCiGreIpIR
         INTEGER,
      er1645v2TvTmplCiGreIpIgmp
         INTEGER,
      er1645v2TvTmplCiGreIpNN
         DisplayString,
      er1645v2TvTmplCiGreIpPimMode
         INTEGER,
      er1645v2TvTmplCiGreIpPimDrPriority
         Counter32,
      er1645v2TvTmplCiGreIpPimHelloTime
         TimeTicks,
      er1645v2TvTmplCiGreIpPimPropagationDelay
         TimeTicks,
      er1645v2TvTmplCiGreIpPimOverrideInterval
         TimeTicks,
      er1645v2TvTmplCiGreIpPimBsrBorder
         INTEGER,
      er1645v2TvTmplCiGreIpPimTtlThreshold
         Integer32,
      er1645v2TvTmplCiGreIpIMNetworkUnreachable
         INTEGER,
      er1645v2TvTmplCiGreIpIMHostUnreachable
         INTEGER,
      er1645v2TvTmplCiGreIpIMProtocolUnreachable
         INTEGER,
      er1645v2TvTmplCiGreIpIMPortUnreachable
         INTEGER,
      er1645v2TvTmplCiGreIpIMMtuExceeded
         INTEGER,
      er1645v2TvTmplCiGreIpIMAdminProhibited
         INTEGER,
      er1645v2TvTmplCiGreIpIMTtlExceeded
         INTEGER,
      er1645v2TvTmplCiGreIpIMRedirect
         INTEGER,
      er1645v2TvTmplCiGreBrAccList
         DisplayString,
      er1645v2TvTmplCiGreBrInACL
         DisplayString,
      er1645v2TvTmplCiGreBrTp
         DisplayString,
      er1645v2TvTmplCiGreBrBrGrp
         DisplayString,
      er1645v2TvTmplCiGreBrLimBC
         INTEGER,
      er1645v2TvTmplCiGreBrPrivateMode
         INTEGER,
      er1645v2TvTmplCiGreBrLearning
         INTEGER,
      er1645v2TvTmplCiGreBrMaxCacheSize
         INTEGER,
      er1645v2TvTmplCiGreBrRelearnDropOnRelearn
         INTEGER,
      er1645v2TvTmplCiGreBrRelearnShutdownThreshold
         Integer32,
      er1645v2TvTmplCiGreBrRelearnShutdownTime
         TimeTicks,
      er1645v2TvTmplCiGreBrRelearnLoopDetection
         INTEGER,
      er1645v2TvTmplCiGreBrRelearnLoopDetectionInterval
         TimeTicks,
      er1645v2TvTmplCiGreBrVlanMemberShip
         INTEGER,
      er1645v2TvTmplCiGreBrVlTUntaggedAction
         INTEGER,
      er1645v2TvTmplCiGreBrVlTUntaggedTagInfoTpid
         INTEGER,
      er1645v2TvTmplCiGreBrVlTUntaggedTagInfoVid
         Integer32,
      er1645v2TvTmplCiGreBrVlTUnknownVlansAction
         INTEGER,
      er1645v2TvTmplCiGreBrVlTUnknownVlansTagInfoTpid
         INTEGER,
      er1645v2TvTmplCiGreBrVlTUnknownVlansTagInfoVid
         Integer32,
      er1645v2TvTmplCiGreBrDot1adType
         INTEGER,
      er1645v2TvTmplCiGreBrPriority
         Integer32,
      er1645v2TvTmplCiGreBrPathCost
         Integer32,
      er1645v2TvTmplCiGreBrInternalPathCost
         Integer32,
      er1645v2TvTmplCiGreBrTCD
         INTEGER,
      er1645v2TvTmplCiGreBrRestrictedRole
         INTEGER,
      er1645v2TvTmplCiGreBrAdminEdge
         INTEGER,
      er1645v2TvTmplCiGreBrOamMacDeviceMac
         DisplayString,
      er1645v2TvTmplCiGreBrOamMacUserMac
         OCTET STRING,
      er1645v2TvTmplCiGreBrOamMacBridgeMac
         DisplayString,
      er1645v2TvTmplCiGreBrMgmtInline
         INTEGER,
      er1645v2TvTmplCiGreBrL2ptMode
         INTEGER,
      er1645v2TvTmplCiGreBrL2ptProtocols
         Integer32,
      er1645v2TvTmplCiGreBrL2ptDestMac
         OCTET STRING,
      er1645v2TvTmplCiGreBrL2ptCos
         INTEGER,
      er1645v2TvTmplCiGreBrL2ptDropThrStp
         INTEGER,
      er1645v2TvTmplCiGreBrL2ptDropThrLldp
         INTEGER,
      er1645v2TvTmplCiGreBrL2ptDropThrOam
         INTEGER,
      er1645v2TvTmplCiGreBrL2ptDropThrCdp
         INTEGER,
      er1645v2TvTmplCiGreBrL2ptDropThrVtp
         INTEGER,
      er1645v2TvTmplCiGreBrL2ptDropThrLacp
         INTEGER,
      er1645v2TvTmplCiGreBrL2ptDropThrEfmOam
         INTEGER,
      er1645v2TvTmplCiGreBrL2ptDropThrPvst
         INTEGER,
      er1645v2TvTmplCiGreBrL2ptDropThrMmrp
         INTEGER,
      er1645v2TvTmplCiGreBrL2ptDropThrMvrp
         INTEGER,
      er1645v2TvTmplCiGreBrL2ptDropThrGvrp
         INTEGER,
      er1645v2TvTmplCiGreBrL2ptDropThrGmrp
         INTEGER,
      er1645v2TvTmplCiGreBrL2ptDropThrDtp
         INTEGER,
      er1645v2TvTmplCiGreBrL2ptDropThrPagp
         INTEGER,
      er1645v2TvTmplCiGreBrL2ptDropThrUdld
         INTEGER,
      er1645v2TvTmplCiGreVirtEthernetVirtualEthernet
         DisplayString,
      er1645v2TvTmplCiGreGreLocalIpAddress
         IpAddress,
      er1645v2TvTmplCiGreGreLocalInterface
         DisplayString,
      er1645v2TvTmplCiGreGreRemoteIpAddress
         IpAddress,
      er1645v2TvTmplCiGreGreRemoteDnsName
         DisplayString,
      er1645v2TvTmplCiGreGreIpsFdx
         DisplayString,
      er1645v2TvTmplCiGreGreIpsHdxIn
         DisplayString,
      er1645v2TvTmplCiGreGreIpsHdxOut
         DisplayString,
      er1645v2TvTmplCiGreGreIpsPsCfg
         DisplayString,
      er1645v2TvTmplCiGreGreIpsPsLIdIp
         IpAddress,
      er1645v2TvTmplCiGreGreIpsPsLIdHn
         DisplayString,
      er1645v2TvTmplCiGreGreIpsPsLIdUn
         DisplayString,
      er1645v2TvTmplCiGreGreIpsPsRIdIp
         IpAddress,
      er1645v2TvTmplCiGreGreIpsPsRIdHn
         DisplayString,
      er1645v2TvTmplCiGreGreIpsPsRIdUn
         DisplayString,
      er1645v2TvTmplCiGreGreIpsPsKey
         DisplayString,
      er1645v2TvTmplCiGreGreIpsPsEncMKey
         INTEGER,
      er1645v2TvTmplCiGreGreIpsPsEncKey
         DisplayString,
      er1645v2TvTmplCiGreGreIpsPsPIdProt
         INTEGER,
      er1645v2TvTmplCiGreGreIpsPsPIdLocAddr
         IpAddress,
      er1645v2TvTmplCiGreGreIpsPsPIdLocMask
         IpAddress,
      er1645v2TvTmplCiGreGreIpsPsPIdLocPort
         INTEGER,
      er1645v2TvTmplCiGreGreIpsPsPIdRemAddr
         IpAddress,
      er1645v2TvTmplCiGreGreIpsPsPIdRemMask
         IpAddress,
      er1645v2TvTmplCiGreGreIpsPsPIdRemPort
         INTEGER,
      er1645v2TvTmplCiGreGreIpsCeCfg
         DisplayString,
      er1645v2TvTmplCiGreGreIpsCeLIdIp
         IpAddress,
      er1645v2TvTmplCiGreGreIpsCeLIdHn
         DisplayString,
      er1645v2TvTmplCiGreGreIpsCeLIdUn
         DisplayString,
      er1645v2TvTmplCiGreGreIpsCeLIdDn
         DisplayString,
      er1645v2TvTmplCiGreGreIpsCeRIdIp
         IpAddress,
      er1645v2TvTmplCiGreGreIpsCeRIdHn
         DisplayString,
      er1645v2TvTmplCiGreGreIpsCeRIdUn
         DisplayString,
      er1645v2TvTmplCiGreGreIpsCeRIdDn
         DisplayString,
      er1645v2TvTmplCiGreGreIpsCePIdProt
         INTEGER,
      er1645v2TvTmplCiGreGreIpsCePIdLocAddr
         IpAddress,
      er1645v2TvTmplCiGreGreIpsCePIdLocMask
         IpAddress,
      er1645v2TvTmplCiGreGreIpsCePIdLocPort
         INTEGER,
      er1645v2TvTmplCiGreGreIpsCePIdRemAddr
         IpAddress,
      er1645v2TvTmplCiGreGreIpsCePIdRemMask
         IpAddress,
      er1645v2TvTmplCiGreGreIpsCePIdRemPort
         INTEGER,
      er1645v2TvTmplCiGreGreKpAlMode
         INTEGER,
      er1645v2TvTmplCiGreGreKpAlInterval
         TimeTicks,
      er1645v2TvTmplCiGreGreKpAlRepTimeOut
         TimeTicks,
      er1645v2TvTmplCiGreGreKpAlFailsPrmt
         Integer32,
      er1645v2TvTmplCiGreGreNoTraffTO
         TimeTicks,
      er1645v2TvTmplCiGreGreNoTraffDi
         INTEGER,
      er1645v2TvTmplCiGreGreType
         INTEGER,
      er1645v2TvTmplCiGreGreRRoutDefRt
         INTEGER,
      er1645v2TvTmplCiGreGreTos
         INTEGER,
      er1645v2TvTmplCiGreGreQueueTosMapQueue1
         INTEGER,
      er1645v2TvTmplCiGreGreQueueTosMapQueue2
         INTEGER,
      er1645v2TvTmplCiGreGreQueueTosMapQueue3
         INTEGER,
      er1645v2TvTmplCiGreGreQueueTosMapQueue4
         INTEGER,
      er1645v2TvTmplCiGreGreQueueTosMapQueue5
         INTEGER,
      er1645v2TvTmplCiGreGreQueueTosMapLowDelayQueue
         INTEGER,
      er1645v2TvTmplCiGreGreQueueTosMapLowDelay2Queue
         INTEGER,
      er1645v2TvTmplCiGreGreQueueTosMapSystemQueue
         INTEGER,
      er1645v2TvTmplCiGreGreDf
         INTEGER,
      er1645v2TvTmplCiGreGreTtl
         INTEGER,
      er1645v2TvTmplCiGreGreMtu
         Integer32,
      er1645v2TvTmplCiGreMplsMode
         INTEGER,
      er1645v2TvTmplCiGreMplsInLabel
         Integer32,
      er1645v2TvTmplCiGreMplsOutLabel
         Integer32,
      er1645v2TvTmplCiGreMplsTrafficClassMode
         INTEGER,
      er1645v2TvTmplCiGreMplsTrafficClassFixed
         Integer32,
      er1645v2TvTmplCiGreMplsTrafficClassQosP0
         Integer32,
      er1645v2TvTmplCiGreMplsTrafficClassQosP1
         Integer32,
      er1645v2TvTmplCiGreMplsTrafficClassQosP2
         Integer32,
      er1645v2TvTmplCiGreMplsTrafficClassQosP3
         Integer32,
      er1645v2TvTmplCiGreMplsTrafficClassQosP4
         Integer32,
      er1645v2TvTmplCiGreMplsTrafficClassQosP5
         Integer32,
      er1645v2TvTmplCiGreMplsTrafficClassQosP6
         Integer32,
      er1645v2TvTmplCiGreMplsTrafficClassQosP7
         Integer32,
      er1645v2TvTmplCiGreMplsTtl
         INTEGER,
      er1645v2TvTmplCiGreInbBwCir
         Integer32,
      er1645v2TvTmplCiGreInbBwTc
         INTEGER,
      er1645v2TvTmplCiGreInbBwCorrType
         INTEGER,
      er1645v2TvTmplCiGreInbBwCorrPredefEncapsFrameRelay
         DisplayString,
      er1645v2TvTmplCiGreInbBwCorrPredefEncapsPpp
         DisplayString,
      er1645v2TvTmplCiGreInbBwCorrPredefEncapsAtmHl
         INTEGER,
      er1645v2TvTmplCiGreInbBwCorrPredefEncapsAtmMp
         INTEGER,
      er1645v2TvTmplCiGreInbBwCorrPredefEncapsHdlc
         DisplayString,
      er1645v2TvTmplCiGreInbBwCorrPredefEncapsEfmFs
         Integer32,
      er1645v2TvTmplCiGreInbBwCorrPredefEncapsEfmIb
         Integer32,
      er1645v2TvTmplCiGreInbBwCorrPredefMode
         INTEGER,
      er1645v2TvTmplCiGreInbBwCorrManualOverhead
         Integer32,
      er1645v2TvTmplCiGreInbBwCorrManualFrameData
         Counter32,
      er1645v2TvTmplCiGreInbBwCorrManualFrameHeader
         Counter32,
      er1645v2TvTmplCiGreInbBwMaxFifoQLen
         Integer32,
      er1645v2TvTmplCiGreInbBwPriorityPolicy
         DisplayString,
      er1645v2TvTmplCiGreBandwidthMode
         INTEGER,
      er1645v2TvTmplCiGreBandwidthCir
         Integer32,
      er1645v2TvTmplCiGreBandwidthEir
         Integer32,
      er1645v2TvTmplCiGreBandwidthUnit
         INTEGER,
      er1645v2TvTmplCiGreBandwidthTc
         INTEGER,
      er1645v2TvTmplCiGreBandwidthTcFactor
         INTEGER,
      er1645v2TvTmplCiGreBandwidthCorrType
         INTEGER,
      er1645v2TvTmplCiGreBandwidthCorrPredefEncapsFrameRelay
         DisplayString,
      er1645v2TvTmplCiGreBandwidthCorrPredefEncapsPpp
         DisplayString,
      er1645v2TvTmplCiGreBandwidthCorrPredefEncapsAtmHl
         INTEGER,
      er1645v2TvTmplCiGreBandwidthCorrPredefEncapsAtmMp
         INTEGER,
      er1645v2TvTmplCiGreBandwidthCorrPredefEncapsHdlc
         DisplayString,
      er1645v2TvTmplCiGreBandwidthCorrPredefEncapsEfmFs
         Integer32,
      er1645v2TvTmplCiGreBandwidthCorrPredefEncapsEfmIb
         Integer32,
      er1645v2TvTmplCiGreBandwidthCorrPredefMode
         INTEGER,
      er1645v2TvTmplCiGreBandwidthCorrManualOverhead
         Integer32,
      er1645v2TvTmplCiGreBandwidthCorrManualFrameData
         Counter32,
      er1645v2TvTmplCiGreBandwidthCorrManualFrameHeader
         Counter32,
      er1645v2TvTmplCiGreBandwidthMaxFifoQLen
         Integer32,
      er1645v2TvTmplCiGreBandwidthDeFlagCir
         INTEGER,
      er1645v2TvTmplCiGreBandwidthDeFlagEir
         INTEGER,
      er1645v2TvTmplCiGreBandwidthDeFlagViolate
         INTEGER,
      er1645v2TvTmplCiGreBandwidthActCirActNone
         OCTET STRING,
      er1645v2TvTmplCiGreBandwidthActCirActEthCos1
         INTEGER,
      er1645v2TvTmplCiGreBandwidthActCirActEthDei1
         INTEGER,
      er1645v2TvTmplCiGreBandwidthActCirActEthCos2
         INTEGER,
      er1645v2TvTmplCiGreBandwidthActCirActEthDei2
         INTEGER,
      er1645v2TvTmplCiGreBandwidthActCirActEthCos3
         INTEGER,
      er1645v2TvTmplCiGreBandwidthActCirActEthDei3
         INTEGER,
      er1645v2TvTmplCiGreBandwidthActCirActEthCos4
         INTEGER,
      er1645v2TvTmplCiGreBandwidthActCirActEthDei4
         INTEGER,
      er1645v2TvTmplCiGreBandwidthActCirActEthCos5
         INTEGER,
      er1645v2TvTmplCiGreBandwidthActCirActEthDei5
         INTEGER,
      er1645v2TvTmplCiGreBandwidthActCirActEthCos6
         INTEGER,
      er1645v2TvTmplCiGreBandwidthActCirActEthDei6
         INTEGER,
      er1645v2TvTmplCiGreBandwidthActCirActEthCos7
         INTEGER,
      er1645v2TvTmplCiGreBandwidthActCirActEthDei7
         INTEGER,
      er1645v2TvTmplCiGreBandwidthActCirActEthCos8
         INTEGER,
      er1645v2TvTmplCiGreBandwidthActCirActEthDei8
         INTEGER,
      er1645v2TvTmplCiGreBandwidthActCirActEthTos
         INTEGER,
      er1645v2TvTmplCiGreBandwidthActCirActEthQueue
         INTEGER,
      er1645v2TvTmplCiGreBandwidthActCirActEthDrpLev
         INTEGER,
      er1645v2TvTmplCiGreBandwidthActCirActEthDeFlag
         INTEGER,
      er1645v2TvTmplCiGreBandwidthActCirActIpTos
         INTEGER,
      er1645v2TvTmplCiGreBandwidthActCirActIpQueue
         INTEGER,
      er1645v2TvTmplCiGreBandwidthActCirActIpDrpLev
         INTEGER,
      er1645v2TvTmplCiGreBandwidthActCirActIpDeFlag
         INTEGER,
      er1645v2TvTmplCiGreBandwidthActEirActNone
         OCTET STRING,
      er1645v2TvTmplCiGreBandwidthActEirActEthCos1
         INTEGER,
      er1645v2TvTmplCiGreBandwidthActEirActEthDei1
         INTEGER,
      er1645v2TvTmplCiGreBandwidthActEirActEthCos2
         INTEGER,
      er1645v2TvTmplCiGreBandwidthActEirActEthDei2
         INTEGER,
      er1645v2TvTmplCiGreBandwidthActEirActEthCos3
         INTEGER,
      er1645v2TvTmplCiGreBandwidthActEirActEthDei3
         INTEGER,
      er1645v2TvTmplCiGreBandwidthActEirActEthCos4
         INTEGER,
      er1645v2TvTmplCiGreBandwidthActEirActEthDei4
         INTEGER,
      er1645v2TvTmplCiGreBandwidthActEirActEthCos5
         INTEGER,
      er1645v2TvTmplCiGreBandwidthActEirActEthDei5
         INTEGER,
      er1645v2TvTmplCiGreBandwidthActEirActEthCos6
         INTEGER,
      er1645v2TvTmplCiGreBandwidthActEirActEthDei6
         INTEGER,
      er1645v2TvTmplCiGreBandwidthActEirActEthCos7
         INTEGER,
      er1645v2TvTmplCiGreBandwidthActEirActEthDei7
         INTEGER,
      er1645v2TvTmplCiGreBandwidthActEirActEthCos8
         INTEGER,
      er1645v2TvTmplCiGreBandwidthActEirActEthDei8
         INTEGER,
      er1645v2TvTmplCiGreBandwidthActEirActEthTos
         INTEGER,
      er1645v2TvTmplCiGreBandwidthActEirActEthQueue
         INTEGER,
      er1645v2TvTmplCiGreBandwidthActEirActEthDrpLev
         INTEGER,
      er1645v2TvTmplCiGreBandwidthActEirActEthDeFlag
         INTEGER,
      er1645v2TvTmplCiGreBandwidthActEirActIpTos
         INTEGER,
      er1645v2TvTmplCiGreBandwidthActEirActIpQueue
         INTEGER,
      er1645v2TvTmplCiGreBandwidthActEirActIpDrpLev
         INTEGER,
      er1645v2TvTmplCiGreBandwidthActEirActIpDeFlag
         INTEGER,
      er1645v2TvTmplCiGreBandwidthActViolActNone
         OCTET STRING,
      er1645v2TvTmplCiGreBandwidthActViolActDrop
         OCTET STRING,
      er1645v2TvTmplCiGreBandwidthActViolActEthCos1
         INTEGER,
      er1645v2TvTmplCiGreBandwidthActViolActEthDei1
         INTEGER,
      er1645v2TvTmplCiGreBandwidthActViolActEthCos2
         INTEGER,
      er1645v2TvTmplCiGreBandwidthActViolActEthDei2
         INTEGER,
      er1645v2TvTmplCiGreBandwidthActViolActEthCos3
         INTEGER,
      er1645v2TvTmplCiGreBandwidthActViolActEthDei3
         INTEGER,
      er1645v2TvTmplCiGreBandwidthActViolActEthCos4
         INTEGER,
      er1645v2TvTmplCiGreBandwidthActViolActEthDei4
         INTEGER,
      er1645v2TvTmplCiGreBandwidthActViolActEthCos5
         INTEGER,
      er1645v2TvTmplCiGreBandwidthActViolActEthDei5
         INTEGER,
      er1645v2TvTmplCiGreBandwidthActViolActEthCos6
         INTEGER,
      er1645v2TvTmplCiGreBandwidthActViolActEthDei6
         INTEGER,
      er1645v2TvTmplCiGreBandwidthActViolActEthCos7
         INTEGER,
      er1645v2TvTmplCiGreBandwidthActViolActEthDei7
         INTEGER,
      er1645v2TvTmplCiGreBandwidthActViolActEthCos8
         INTEGER,
      er1645v2TvTmplCiGreBandwidthActViolActEthDei8
         INTEGER,
      er1645v2TvTmplCiGreBandwidthActViolActEthTos
         INTEGER,
      er1645v2TvTmplCiGreBandwidthActViolActEthQueue
         INTEGER,
      er1645v2TvTmplCiGreBandwidthActViolActEthDrpLev
         INTEGER,
      er1645v2TvTmplCiGreBandwidthActViolActEthDeFlag
         INTEGER,
      er1645v2TvTmplCiGreBandwidthActViolActIpTos
         INTEGER,
      er1645v2TvTmplCiGreBandwidthActViolActIpQueue
         INTEGER,
      er1645v2TvTmplCiGreBandwidthActViolActIpDrpLev
         INTEGER,
      er1645v2TvTmplCiGreBandwidthActViolActIpDeFlag
         INTEGER
      }

er1645v2TvTmplCiGreActions OBJECT-TYPE
   SYNTAX      VariableLengthTableActions
   MAX-ACCESS  read-write
   STATUS      current
   DESCRIPTION
      "By way of this field, some manipulations
       on this table may be performed."
   ::= {er1645v2TvTmplCiGreEntry 2}

er1645v2TvTmplCiGreTableIx OBJECT-TYPE
   SYNTAX      TableIndex
   MAX-ACCESS  not-accessible
   STATUS      current
   DESCRIPTION
      ""
   ::= {er1645v2TvTmplCiGreEntry 11}

er1645v2TvTmplCiGreName OBJECT-TYPE
   SYNTAX      DisplayString
   MAX-ACCESS  read-write
   STATUS      current
   DESCRIPTION
      "Path: tunnels.editConf.ipsecGreTunnels.name"
   ::= {er1645v2TvTmplCiGreEntry 16777216}

er1645v2TvTmplCiGreRemark OBJECT-TYPE
   SYNTAX      DisplayString
   MAX-ACCESS  read-write
   STATUS      current
   DESCRIPTION
      "Path: tunnels.editConf.ipsecGreTunnels.remark"
   ::= {er1645v2TvTmplCiGreEntry 1157627904}

er1645v2TvTmplCiGreAdminStatus OBJECT-TYPE
   SYNTAX      INTEGER
               {
               up (1),
               down (2)
               }
   MAX-ACCESS  read-write
   STATUS      current
   DESCRIPTION
      "Path: tunnels.editConf.ipsecGreTunnels.adminStatus

       Possibilities:
               up   (1)
               down   (2)"
   ::= {er1645v2TvTmplCiGreEntry 33554432}

er1645v2TvTmplCiGreMode OBJECT-TYPE
   SYNTAX      INTEGER
               {
               routing (1),
               bridging (2),
               multilink (8),
               virtEthernet (32)
               }
   MAX-ACCESS  read-write
   STATUS      current
   DESCRIPTION
      "Path: tunnels.editConf.ipsecGreTunnels.mode

       Possibilities:
               routing   (1)
               bridging   (2)
               multilink   (8)
               virtEthernet   (32)"
   ::= {er1645v2TvTmplCiGreEntry 67108864}

er1645v2TvTmplCiGrePriorityPolicy OBJECT-TYPE
   SYNTAX      DisplayString
   MAX-ACCESS  read-write
   STATUS      current
   DESCRIPTION
      "Path: tunnels.editConf.ipsecGreTunnels.priorityPolicy"
   ::= {er1645v2TvTmplCiGreEntry 83886080}

er1645v2TvTmplCiGreIpVrfRouter OBJECT-TYPE
   SYNTAX      DisplayString
   MAX-ACCESS  read-write
   STATUS      current
   DESCRIPTION
      "Path: tunnels.editConf.ipsecGreTunnels.ip.vrfRouter"
   ::= {er1645v2TvTmplCiGreEntry 53215232}

er1645v2TvTmplCiGreIpAdr OBJECT-TYPE
   SYNTAX      IpAddress
   MAX-ACCESS  read-write
   STATUS      current
   DESCRIPTION
      "Path: tunnels.editConf.ipsecGreTunnels.ip.address"
   ::= {er1645v2TvTmplCiGreEntry 58261504}

er1645v2TvTmplCiGreIpNetm OBJECT-TYPE
   SYNTAX      IpAddress
   MAX-ACCESS  read-write
   STATUS      current
   DESCRIPTION
      "Path: tunnels.editConf.ipsecGreTunnels.ip.netMask"
   ::= {er1645v2TvTmplCiGreEntry 58392576}

er1645v2TvTmplCiGreIpSNetName OBJECT-TYPE
   SYNTAX      INTEGER
               {
               slOPTg (0),
               corp (2),
               dmz (3),
               internet (1)
               }
   MAX-ACCESS  read-write
   STATUS      current
   DESCRIPTION
      "Path: tunnels.editConf.ipsecGreTunnels.ip.sNet.name

       Possibilities:
               <OPT>   (0)
               corp   (2)
               dmz   (3)
               internet   (1)"
   ::= {er1645v2TvTmplCiGreEntry 53674240}

er1645v2TvTmplCiGreIpSNetCust OBJECT-TYPE
   SYNTAX      DisplayString
   MAX-ACCESS  read-write
   STATUS      current
   DESCRIPTION
      "Path: tunnels.editConf.ipsecGreTunnels.ip.sNet.custom"
   ::= {er1645v2TvTmplCiGreEntry 53674496}

er1645v2TvTmplCiGreIpRem OBJECT-TYPE
   SYNTAX      IpAddress
   MAX-ACCESS  read-write
   STATUS      current
   DESCRIPTION
      "Path: tunnels.editConf.ipsecGreTunnels.ip.remote"
   ::= {er1645v2TvTmplCiGreEntry 58458112}

er1645v2TvTmplCiGreIpGwPref OBJECT-TYPE
   SYNTAX      Integer32
   MAX-ACCESS  read-write
   STATUS      current
   DESCRIPTION
      "Path: tunnels.editConf.ipsecGreTunnels.ip.gatewayPreference"
   ::= {er1645v2TvTmplCiGreEntry 52690944}

er1645v2TvTmplCiGreIpMtu OBJECT-TYPE
   SYNTAX      Integer32
   MAX-ACCESS  read-write
   STATUS      current
   DESCRIPTION
      "Path: tunnels.editConf.ipsecGreTunnels.ip.mtu"
   ::= {er1645v2TvTmplCiGreEntry 52953088}

er1645v2TvTmplCiGreIpMssAdjust OBJECT-TYPE
   SYNTAX      INTEGER
               {
               disabled (0),
               auto (65536)
               }
   MAX-ACCESS  read-write
   STATUS      current
   DESCRIPTION
      "Path: tunnels.editConf.ipsecGreTunnels.ip.mssAdjust

       Possibilities:
               disabled   (0)
               auto   (65536)"
   ::= {er1645v2TvTmplCiGreEntry 53280768}

er1645v2TvTmplCiGreIpRipMetric OBJECT-TYPE
   SYNTAX      Integer32
   MAX-ACCESS  read-write
   STATUS      current
   DESCRIPTION
      "Path: tunnels.editConf.ipsecGreTunnels.ip.rip.metric"
   ::= {er1645v2TvTmplCiGreEntry 51712768}

er1645v2TvTmplCiGreIpRipMetricOut OBJECT-TYPE
   SYNTAX      Integer32
   MAX-ACCESS  read-write
   STATUS      current
   DESCRIPTION
      "Path: tunnels.editConf.ipsecGreTunnels.ip.rip.metricOut"
   ::= {er1645v2TvTmplCiGreEntry 51713024}

er1645v2TvTmplCiGreIpRipMode OBJECT-TYPE
   SYNTAX      INTEGER
               {
               disabled (0),
               passive (1),
               active (2)
               }
   MAX-ACCESS  read-write
   STATUS      current
   DESCRIPTION
      "Path: tunnels.editConf.ipsecGreTunnels.ip.rip.mode

       Possibilities:
               disabled   (0)
               passive   (1)
               active   (2)"
   ::= {er1645v2TvTmplCiGreEntry 51713280}

er1645v2TvTmplCiGreIpRipTxVersion OBJECT-TYPE
   SYNTAX      INTEGER
               {
               rip1 (0),
               rip2 (1),
               rip1mcompatible (2)
               }
   MAX-ACCESS  read-write
   STATUS      current
   DESCRIPTION
      "Path: tunnels.editConf.ipsecGreTunnels.ip.rip.txVersion

       Possibilities:
               rip1   (0)
               rip2   (1)
               rip1-compatible   (2)"
   ::= {er1645v2TvTmplCiGreEntry 51716864}

er1645v2TvTmplCiGreIpRipRxVersion OBJECT-TYPE
   SYNTAX      INTEGER
               {
               rip1only (0),
               rip2only (1),
               rip12 (2)
               }
   MAX-ACCESS  read-write
   STATUS      current
   DESCRIPTION
      "Path: tunnels.editConf.ipsecGreTunnels.ip.rip.rxVersion

       Possibilities:
               rip1only   (0)
               rip2only   (1)
               rip1&2   (2)"
   ::= {er1645v2TvTmplCiGreEntry 51717120}

er1645v2TvTmplCiGreIpRipSplitHorizon OBJECT-TYPE
   SYNTAX      INTEGER
               {
               disabled (0),
               enabled (1),
               poisonedReverse (2)
               }
   MAX-ACCESS  read-write
   STATUS      current
   DESCRIPTION
      "Path: tunnels.editConf.ipsecGreTunnels.ip.rip.splitHorizon

       Possibilities:
               disabled   (0)
               enabled   (1)
               poisonedReverse   (2)"
   ::= {er1645v2TvTmplCiGreEntry 51713792}

er1645v2TvTmplCiGreIpRipAuth OBJECT-TYPE
   SYNTAX      INTEGER
               {
               disabled (0),
               texts (1),
               md5 (2)
               }
   MAX-ACCESS  read-write
   STATUS      current
   DESCRIPTION
      "Path: tunnels.editConf.ipsecGreTunnels.ip.rip.authentication

       Possibilities:
               disabled   (0)
               text    (1)
               md5   (2)"
   ::= {er1645v2TvTmplCiGreEntry 51712512}

er1645v2TvTmplCiGreIpRipFilter OBJECT-TYPE
   SYNTAX      DisplayString
   MAX-ACCESS  read-write
   STATUS      current
   DESCRIPTION
      "Path: tunnels.editConf.ipsecGreTunnels.ip.rip.filter"
   ::= {er1645v2TvTmplCiGreEntry 51716096}

er1645v2TvTmplCiGreIpRipFilterIn OBJECT-TYPE
   SYNTAX      DisplayString
   MAX-ACCESS  read-write
   STATUS      current
   DESCRIPTION
      "Path: tunnels.editConf.ipsecGreTunnels.ip.rip.filterIn"
   ::= {er1645v2TvTmplCiGreEntry 51716352}

er1645v2TvTmplCiGreIpRipSnapshot OBJECT-TYPE
   SYNTAX      INTEGER
               {
               disabled (0),
               enabled (1)
               }
   MAX-ACCESS  read-write
   STATUS      current
   DESCRIPTION
      "Path: tunnels.editConf.ipsecGreTunnels.ip.rip.snapshot

       Possibilities:
               disabled   (0)
               enabled   (1)"
   ::= {er1645v2TvTmplCiGreEntry 51708160}

er1645v2TvTmplCiGreIpRipClearNextHop OBJECT-TYPE
   SYNTAX      INTEGER
               {
               disabled (0),
               enabled (1)
               }
   MAX-ACCESS  read-write
   STATUS      current
   DESCRIPTION
      "Path: tunnels.editConf.ipsecGreTunnels.ip.rip.clearNextHop

       Possibilities:
               disabled   (0)
               enabled   (1)"
   ::= {er1645v2TvTmplCiGreEntry 51708416}

er1645v2TvTmplCiGreIpAccPol OBJECT-TYPE
   SYNTAX      DisplayString
   MAX-ACCESS  read-write
   STATUS      current
   DESCRIPTION
      "Path: tunnels.editConf.ipsecGreTunnels.ip.accessPolicy"
   ::= {er1645v2TvTmplCiGreEntry 53084160}

er1645v2TvTmplCiGreIpAB OBJECT-TYPE
   SYNTAX      DisplayString
   MAX-ACCESS  read-write
   STATUS      current
   DESCRIPTION
      "Path: tunnels.editConf.ipsecGreTunnels.ip.trafficPolicy"
   ::= {er1645v2TvTmplCiGreEntry 51249152}

er1645v2TvTmplCiGreIpMA OBJECT-TYPE
   SYNTAX      INTEGER
               {
               disabled (0),
               enabled (1)
               }
   MAX-ACCESS  read-write
   STATUS      current
   DESCRIPTION
      "Path: tunnels.editConf.ipsecGreTunnels.ip.mgmtAccess

       Possibilities:
               disabled   (0)
               enabled   (1)"
   ::= {er1645v2TvTmplCiGreEntry 51380224}

er1645v2TvTmplCiGreIpMF OBJECT-TYPE
   SYNTAX      Integer32
   MAX-ACCESS  read-write
   STATUS      current
   DESCRIPTION
      "Path: tunnels.editConf.ipsecGreTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TvTmplCiGreEntry 51445760}

er1645v2TvTmplCiGreIpDB OBJECT-TYPE
   SYNTAX      INTEGER
               {
               disabled (0),
               enabled (1)
               }
   MAX-ACCESS  read-write
   STATUS      current
   DESCRIPTION
      "Path: tunnels.editConf.ipsecGreTunnels.ip.directedBroadcasts

       Possibilities:
               disabled   (0)
               enabled   (1)"
   ::= {er1645v2TvTmplCiGreEntry 51773440}

er1645v2TvTmplCiGreIpIR OBJECT-TYPE
   SYNTAX      INTEGER
               {
               disabled (0),
               enabled (1)
               }
   MAX-ACCESS  read-write
   STATUS      current
   DESCRIPTION
      "Path: tunnels.editConf.ipsecGreTunnels.ip.icmpRedirects

       Possibilities:
               disabled   (0)
               enabled   (1)"
   ::= {er1645v2TvTmplCiGreEntry 52035584}

er1645v2TvTmplCiGreIpIgmp OBJECT-TYPE
   SYNTAX      INTEGER
               {
               disabled (0),
               proxy (1),
               router (2),
               v3Router (5)
               }
   MAX-ACCESS  read-write
   STATUS      current
   DESCRIPTION
      "Path: tunnels.editConf.ipsecGreTunnels.ip.igmp

       Possibilities:
               disabled   (0)
               proxy   (1)
               router   (2)
               v3Router   (5)"
   ::= {er1645v2TvTmplCiGreEntry 52428800}

er1645v2TvTmplCiGreIpNN OBJECT-TYPE
   SYNTAX      DisplayString
   MAX-ACCESS  read-write
   STATUS      current
   DESCRIPTION
      "Path: tunnels.editConf.ipsecGreTunnels.ip.nat"
   ::= {er1645v2TvTmplCiGreEntry 52101120}

er1645v2TvTmplCiGreIpPimMode OBJECT-TYPE
   SYNTAX      INTEGER
               {
               disabled (0),
               sparse (1),
               passive (2)
               }
   MAX-ACCESS  read-write
   STATUS      current
   DESCRIPTION
      "Path: tunnels.editConf.ipsecGreTunnels.ip.pim.mode

       Possibilities:
               disabled   (0)
               sparse   (1)
               passive   (2)"
   ::= {er1645v2TvTmplCiGreEntry 53346560}

er1645v2TvTmplCiGreIpPimDrPriority OBJECT-TYPE
   SYNTAX      Counter32
   MAX-ACCESS  read-write
   STATUS      current
   DESCRIPTION
      "Path: tunnels.editConf.ipsecGreTunnels.ip.pim.drPriority

       32 bit unsigned wrappable counter."
   ::= {er1645v2TvTmplCiGreEntry 53346816}

er1645v2TvTmplCiGreIpPimHelloTime OBJECT-TYPE
   SYNTAX      TimeTicks
   MAX-ACCESS  read-write
   STATUS      current
   DESCRIPTION
      "Path: tunnels.editConf.ipsecGreTunnels.ip.pim.helloTime

       Time in centi-second."
   ::= {er1645v2TvTmplCiGreEntry 53347072}

er1645v2TvTmplCiGreIpPimPropagationDelay OBJECT-TYPE
   SYNTAX      TimeTicks
   MAX-ACCESS  read-write
   STATUS      current
   DESCRIPTION
      "Path: tunnels.editConf.ipsecGreTunnels.ip.pim.propagationDelay

       Time in centi-second."
   ::= {er1645v2TvTmplCiGreEntry 53347328}

er1645v2TvTmplCiGreIpPimOverrideInterval OBJECT-TYPE
   SYNTAX      TimeTicks
   MAX-ACCESS  read-write
   STATUS      current
   DESCRIPTION
      "Path: tunnels.editConf.ipsecGreTunnels.ip.pim.overrideInterval

       Time in centi-second."
   ::= {er1645v2TvTmplCiGreEntry 53347584}

er1645v2TvTmplCiGreIpPimBsrBorder OBJECT-TYPE
   SYNTAX      INTEGER
               {
               disabled (0),
               enabled (1)
               }
   MAX-ACCESS  read-write
   STATUS      current
   DESCRIPTION
      "Path: tunnels.editConf.ipsecGreTunnels.ip.pim.bsrBorder

       Possibilities:
               disabled   (0)
               enabled   (1)"
   ::= {er1645v2TvTmplCiGreEntry 53347840}

er1645v2TvTmplCiGreIpPimTtlThreshold OBJECT-TYPE
   SYNTAX      Integer32
   MAX-ACCESS  read-write
   STATUS      current
   DESCRIPTION
      "Path: tunnels.editConf.ipsecGreTunnels.ip.pim.ttlThreshold"
   ::= {er1645v2TvTmplCiGreEntry 53348096}

er1645v2TvTmplCiGreIpIMNetworkUnreachable OBJECT-TYPE
   SYNTAX      INTEGER
               {
               disabled (0),
               enabled (1)
               }
   MAX-ACCESS  read-write
   STATUS      current
   DESCRIPTION
      "Path: tunnels.editConf.ipsecGreTunnels.ip.icmpMessages.networkUnreachable

       Possibilities:
               disabled   (0)
               enabled   (1)"
   ::= {er1645v2TvTmplCiGreEntry 53412096}

er1645v2TvTmplCiGreIpIMHostUnreachable OBJECT-TYPE
   SYNTAX      INTEGER
               {
               disabled (0),
               enabled (1)
               }
   MAX-ACCESS  read-write
   STATUS      current
   DESCRIPTION
      "Path: tunnels.editConf.ipsecGreTunnels.ip.icmpMessages.hostUnreachable

       Possibilities:
               disabled   (0)
               enabled   (1)"
   ::= {er1645v2TvTmplCiGreEntry 53412352}

er1645v2TvTmplCiGreIpIMProtocolUnreachable OBJECT-TYPE
   SYNTAX      INTEGER
               {
               disabled (0),
               enabled (1)
               }
   MAX-ACCESS  read-write
   STATUS      current
   DESCRIPTION
      "Path: tunnels.editConf.ipsecGreTunnels.ip.icmpMessages.protocolUnreachable

       Possibilities:
               disabled   (0)
               enabled   (1)"
   ::= {er1645v2TvTmplCiGreEntry 53412608}

er1645v2TvTmplCiGreIpIMPortUnreachable OBJECT-TYPE
   SYNTAX      INTEGER
               {
               disabled (0),
               enabled (1)
               }
   MAX-ACCESS  read-write
   STATUS      current
   DESCRIPTION
      "Path: tunnels.editConf.ipsecGreTunnels.ip.icmpMessages.portUnreachable

       Possibilities:
               disabled   (0)
               enabled   (1)"
   ::= {er1645v2TvTmplCiGreEntry 53412864}

er1645v2TvTmplCiGreIpIMMtuExceeded OBJECT-TYPE
   SYNTAX      INTEGER
               {
               disabled (0),
               enabled (1)
               }
   MAX-ACCESS  read-write
   STATUS      current
   DESCRIPTION
      "Path: tunnels.editConf.ipsecGreTunnels.ip.icmpMessages.mtuExceeded

       Possibilities:
               disabled   (0)
               enabled   (1)"
   ::= {er1645v2TvTmplCiGreEntry 53413120}

er1645v2TvTmplCiGreIpIMAdminProhibited OBJECT-TYPE
   SYNTAX      INTEGER
               {
               disabled (0),
               enabled (1)
               }
   MAX-ACCESS  read-write
   STATUS      current
   DESCRIPTION
      "Path: tunnels.editConf.ipsecGreTunnels.ip.icmpMessages.adminProhibited

       Possibilities:
               disabled   (0)
               enabled   (1)"
   ::= {er1645v2TvTmplCiGreEntry 53413376}

er1645v2TvTmplCiGreIpIMTtlExceeded OBJECT-TYPE
   SYNTAX      INTEGER
               {
               disabled (0),
               enabled (1)
               }
   MAX-ACCESS  read-write
   STATUS      current
   DESCRIPTION
      "Path: tunnels.editConf.ipsecGreTunnels.ip.icmpMessages.ttlExceeded

       Possibilities:
               disabled   (0)
               enabled   (1)"
   ::= {er1645v2TvTmplCiGreEntry 53413632}

er1645v2TvTmplCiGreIpIMRedirect OBJECT-TYPE
   SYNTAX      INTEGER
               {
               disabled (0),
               enabled (1)
               }
   MAX-ACCESS  read-write
   STATUS      current
   DESCRIPTION
      "Path: tunnels.editConf.ipsecGreTunnels.ip.icmpMessages.redirect

       Possibilities:
               disabled   (0)
               enabled   (1)"
   ::= {er1645v2TvTmplCiGreEntry 53413888}

er1645v2TvTmplCiGreBrAccList OBJECT-TYPE
   SYNTAX      DisplayString
   MAX-ACCESS  read-write
   STATUS      current
   DESCRIPTION
      "Path: tunnels.editConf.ipsecGreTunnels.bridging.accessList"
   ::= {er1645v2TvTmplCiGreEntry 453246976}

er1645v2TvTmplCiGreBrInACL OBJECT-TYPE
   SYNTAX      DisplayString
   MAX-ACCESS  read-write
   STATUS      current
   DESCRIPTION
      "Path: tunnels.editConf.ipsecGreTunnels.bridging.inAccessList"
   ::= {er1645v2TvTmplCiGreEntry 456916992}

er1645v2TvTmplCiGreBrTp OBJECT-TYPE
   SYNTAX      DisplayString
   MAX-ACCESS  read-write
   STATUS      current
   DESCRIPTION
      "Path: tunnels.editConf.ipsecGreTunnels.bridging.trafficPolicy"
   ::= {er1645v2TvTmplCiGreEntry 454295552}

er1645v2TvTmplCiGreBrBrGrp OBJECT-TYPE
   SYNTAX      DisplayString
   MAX-ACCESS  read-write
   STATUS      current
   DESCRIPTION
      "Path: tunnels.editConf.ipsecGreTunnels.bridging.bridgeGroup"
   ::= {er1645v2TvTmplCiGreEntry 454819840}

er1645v2TvTmplCiGreBrLimBC OBJECT-TYPE
   SYNTAX      INTEGER
               {
               disabled (0),
               enabled (1)
               }
   MAX-ACCESS  read-write
   STATUS      current
   DESCRIPTION
      "Path: tunnels.editConf.ipsecGreTunnels.bridging.limitBroadcasts

       Possibilities:
               disabled   (0)
               enabled   (1)"
   ::= {er1645v2TvTmplCiGreEntry 455081984}

er1645v2TvTmplCiGreBrPrivateMode OBJECT-TYPE
   SYNTAX      INTEGER
               {
               disabled (0),
               enabled (1)
               }
   MAX-ACCESS  read-write
   STATUS      current
   DESCRIPTION
      "Path: tunnels.editConf.ipsecGreTunnels.bridging.privateMode

       Possibilities:
               disabled   (0)
               enabled   (1)"
   ::= {er1645v2TvTmplCiGreEntry 459538432}

er1645v2TvTmplCiGreBrLearning OBJECT-TYPE
   SYNTAX      INTEGER
               {
               disabled (0),
               enabled (1)
               }
   MAX-ACCESS  read-write
   STATUS      current
   DESCRIPTION
      "Path: tunnels.editConf.ipsecGreTunnels.bridging.learning

       Possibilities:
               disabled   (0)
               enabled   (1)"
   ::= {er1645v2TvTmplCiGreEntry 456130560}

er1645v2TvTmplCiGreBrMaxCacheSize OBJECT-TYPE
   SYNTAX      INTEGER
               {
               unlimited (0)
               }
   MAX-ACCESS  read-write
   STATUS      current
   DESCRIPTION
      "Path: tunnels.editConf.ipsecGreTunnels.bridging.maxCacheSize

       Possibilities:
               unlimited   (0)"
   ::= {er1645v2TvTmplCiGreEntry 456392704}

er1645v2TvTmplCiGreBrRelearnDropOnRelearn OBJECT-TYPE
   SYNTAX      INTEGER
               {
               disabled (0),
               enabled (1)
               }
   MAX-ACCESS  read-write
   STATUS      current
   DESCRIPTION
      "Path: tunnels.editConf.ipsecGreTunnels.bridging.relearn.dropOnRelearn

       Possibilities:
               disabled   (0)
               enabled   (1)"
   ::= {er1645v2TvTmplCiGreEntry 456655872}

er1645v2TvTmplCiGreBrRelearnShutdownThreshold OBJECT-TYPE
   SYNTAX      Integer32
   MAX-ACCESS  read-write
   STATUS      current
   DESCRIPTION
      "Path: tunnels.editConf.ipsecGreTunnels.bridging.relearn.shutdownThreshold"
   ::= {er1645v2TvTmplCiGreEntry 456656896}

er1645v2TvTmplCiGreBrRelearnShutdownTime OBJECT-TYPE
   SYNTAX      TimeTicks
   MAX-ACCESS  read-write
   STATUS      current
   DESCRIPTION
      "Path: tunnels.editConf.ipsecGreTunnels.bridging.relearn.shutdownTime

       Time in centi-second."
   ::= {er1645v2TvTmplCiGreEntry 456657920}

er1645v2TvTmplCiGreBrRelearnLoopDetection OBJECT-TYPE
   SYNTAX      INTEGER
               {
               disabled (0),
               passive (1),
               active (2)
               }
   MAX-ACCESS  read-write
   STATUS      current
   DESCRIPTION
      "Path: tunnels.editConf.ipsecGreTunnels.bridging.relearn.loopDetection

       Possibilities:
               disabled   (0)
               passive   (1)
               active   (2)"
   ::= {er1645v2TvTmplCiGreEntry 456658944}

er1645v2TvTmplCiGreBrRelearnLoopDetectionInterval OBJECT-TYPE
   SYNTAX      TimeTicks
   MAX-ACCESS  read-write
   STATUS      current
   DESCRIPTION
      "Path: tunnels.editConf.ipsecGreTunnels.bridging.relearn.loopDetectionInterval

       Time in centi-second."
   ::= {er1645v2TvTmplCiGreEntry 456659968}

er1645v2TvTmplCiGreBrVlanMemberShip OBJECT-TYPE
   SYNTAX      INTEGER
               {
               all (0),
               none (1),
               grouped (2)
               }
   MAX-ACCESS  read-write
   STATUS      current
   DESCRIPTION
      "Path: tunnels.editConf.ipsecGreTunnels.bridging.vlanMemberShip

       Possibilities:
               all   (0)
               none   (1)
               grouped   (2)"
   ::= {er1645v2TvTmplCiGreEntry 457965568}

er1645v2TvTmplCiGreBrVlTUntaggedAction OBJECT-TYPE
   SYNTAX      INTEGER
               {
               discard (0),
               accept (1),
               tag (2)
               }
   MAX-ACCESS  read-write
   STATUS      current
   DESCRIPTION
      "Path: tunnels.editConf.ipsecGreTunnels.bridging.vlanTagging.untagged.action

       Possibilities:
               discard   (0)
               accept   (1)
               tag   (2)"
   ::= {er1645v2TvTmplCiGreEntry 459055104}

er1645v2TvTmplCiGreBrVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecGreTunnels.bridging.vlanTagging.untagged.tagInfo.tpid

       Possibilities:
               dot1Q   (33024)
               dot1ad   (34984)
               0x9100   (37120)
               0x9200   (37376)
               0x9300   (37632)"
   ::= {er1645v2TvTmplCiGreEntry 459059712}

er1645v2TvTmplCiGreBrVlTUntaggedTagInfoVid OBJECT-TYPE
   SYNTAX      Integer32
   MAX-ACCESS  read-write
   STATUS      current
   DESCRIPTION
      "Path: tunnels.editConf.ipsecGreTunnels.bridging.vlanTagging.untagged.tagInfo.vid"
   ::= {er1645v2TvTmplCiGreEntry 459060224}

er1645v2TvTmplCiGreBrVlTUnknownVlansAction OBJECT-TYPE
   SYNTAX      INTEGER
               {
               discard (0),
               accept (1),
               tag (2)
               }
   MAX-ACCESS  read-write
   STATUS      current
   DESCRIPTION
      "Path: tunnels.editConf.ipsecGreTunnels.bridging.vlanTagging.unknownVlans.action

       Possibilities:
               discard   (0)
               accept   (1)
               tag   (2)"
   ::= {er1645v2TvTmplCiGreEntry 459120640}

er1645v2TvTmplCiGreBrVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecGreTunnels.bridging.vlanTagging.unknownVlans.tagInfo.tpid

       Possibilities:
               dot1Q   (33024)
               dot1ad   (34984)
               0x9100   (37120)
               0x9200   (37376)
               0x9300   (37632)"
   ::= {er1645v2TvTmplCiGreEntry 459125248}

er1645v2TvTmplCiGreBrVlTUnknownVlansTagInfoVid OBJECT-TYPE
   SYNTAX      Integer32
   MAX-ACCESS  read-write
   STATUS      current
   DESCRIPTION
      "Path: tunnels.editConf.ipsecGreTunnels.bridging.vlanTagging.unknownVlans.tagInfo.vid"
   ::= {er1645v2TvTmplCiGreEntry 459125760}

er1645v2TvTmplCiGreBrDot1adType OBJECT-TYPE
   SYNTAX      INTEGER
               {
               slOPTg (0),
               cPort (4),
               sPort (1),
               nni (2)
               }
   MAX-ACCESS  read-write
   STATUS      current
   DESCRIPTION
      "Path: tunnels.editConf.ipsecGreTunnels.bridging.dot1ad.type

       Possibilities:
               <OPT>   (0)
               cPort   (4)
               sPort   (1)
               nni   (2)"
   ::= {er1645v2TvTmplCiGreEntry 460850176}

er1645v2TvTmplCiGreBrPriority OBJECT-TYPE
   SYNTAX      Integer32
   MAX-ACCESS  read-write
   STATUS      current
   DESCRIPTION
      "Path: tunnels.editConf.ipsecGreTunnels.bridging.priority"
   ::= {er1645v2TvTmplCiGreEntry 453509120}

er1645v2TvTmplCiGreBrPathCost OBJECT-TYPE
   SYNTAX      Integer32
   MAX-ACCESS  read-write
   STATUS      current
   DESCRIPTION
      "Path: tunnels.editConf.ipsecGreTunnels.bridging.pathCost"
   ::= {er1645v2TvTmplCiGreEntry 453771264}

er1645v2TvTmplCiGreBrInternalPathCost OBJECT-TYPE
   SYNTAX      Integer32
   MAX-ACCESS  read-write
   STATUS      current
   DESCRIPTION
      "Path: tunnels.editConf.ipsecGreTunnels.bridging.internalPathCost"
   ::= {er1645v2TvTmplCiGreEntry 457703424}

er1645v2TvTmplCiGreBrTCD OBJECT-TYPE
   SYNTAX      INTEGER
               {
               disabled (0),
               enabled (1)
               }
   MAX-ACCESS  read-write
   STATUS      current
   DESCRIPTION
      "Path: tunnels.editConf.ipsecGreTunnels.bridging.topologyChangeDetection

       Possibilities:
               disabled   (0)
               enabled   (1)"
   ::= {er1645v2TvTmplCiGreEntry 454033408}

er1645v2TvTmplCiGreBrRestrictedRole OBJECT-TYPE
   SYNTAX      INTEGER
               {
               disabled (0),
               enabled (1)
               }
   MAX-ACCESS  read-write
   STATUS      current
   DESCRIPTION
      "Path: tunnels.editConf.ipsecGreTunnels.bridging.restrictedRole

       Possibilities:
               disabled   (0)
               enabled   (1)"
   ::= {er1645v2TvTmplCiGreEntry 458227712}

er1645v2TvTmplCiGreBrAdminEdge OBJECT-TYPE
   SYNTAX      INTEGER
               {
               disabled (0),
               enabled (1)
               }
   MAX-ACCESS  read-write
   STATUS      current
   DESCRIPTION
      "Path: tunnels.editConf.ipsecGreTunnels.bridging.adminEdge

       Possibilities:
               disabled   (0)
               enabled   (1)"
   ::= {er1645v2TvTmplCiGreEntry 457179136}

er1645v2TvTmplCiGreBrOamMacDeviceMac OBJECT-TYPE
   SYNTAX      DisplayString
   MAX-ACCESS  read-write
   STATUS      current
   DESCRIPTION
      "Path: tunnels.editConf.ipsecGreTunnels.bridging.ethOam.macAddress.deviceMac"
   ::= {er1645v2TvTmplCiGreEntry 458506496}

er1645v2TvTmplCiGreBrOamMacUserMac OBJECT-TYPE
   SYNTAX      OCTET STRING
   MAX-ACCESS  read-write
   STATUS      current
   DESCRIPTION
      "Path: tunnels.editConf.ipsecGreTunnels.bridging.ethOam.macAddress.userMac

       MAC address."
   ::= {er1645v2TvTmplCiGreEntry 458506368}

er1645v2TvTmplCiGreBrOamMacBridgeMac OBJECT-TYPE
   SYNTAX      DisplayString
   MAX-ACCESS  read-write
   STATUS      current
   DESCRIPTION
      "Path: tunnels.editConf.ipsecGreTunnels.bridging.ethOam.macAddress.bridgeMac"
   ::= {er1645v2TvTmplCiGreEntry 458506432}

er1645v2TvTmplCiGreBrMgmtInline OBJECT-TYPE
   SYNTAX      INTEGER
               {
               disabled (0),
               enabled (1)
               }
   MAX-ACCESS  read-write
   STATUS      current
   DESCRIPTION
      "Path: tunnels.editConf.ipsecGreTunnels.bridging.mgmtInline

       Possibilities:
               disabled   (0)
               enabled   (1)"
   ::= {er1645v2TvTmplCiGreEntry 458752000}

er1645v2TvTmplCiGreBrL2ptMode OBJECT-TYPE
   SYNTAX      INTEGER
               {
               disabled (0),
               enabled (1)
               }
   MAX-ACCESS  read-write
   STATUS      current
   DESCRIPTION
      "Path: tunnels.editConf.ipsecGreTunnels.bridging.l2ProtTunnel.mode

       Possibilities:
               disabled   (0)
               enabled   (1)"
   ::= {er1645v2TvTmplCiGreEntry 459292672}

er1645v2TvTmplCiGreBrL2ptProtocols OBJECT-TYPE
   SYNTAX      Integer32
   MAX-ACCESS  read-write
   STATUS      current
   DESCRIPTION
      "Path: tunnels.editConf.ipsecGreTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TvTmplCiGreEntry 459309056}

er1645v2TvTmplCiGreBrL2ptDestMac OBJECT-TYPE
   SYNTAX      OCTET STRING
   MAX-ACCESS  read-write
   STATUS      current
   DESCRIPTION
      "Path: tunnels.editConf.ipsecGreTunnels.bridging.l2ProtTunnel.destinationMac

       MAC address."
   ::= {er1645v2TvTmplCiGreEntry 459325440}

er1645v2TvTmplCiGreBrL2ptCos OBJECT-TYPE
   SYNTAX      INTEGER
               {
               unchanged (255)
               }
   MAX-ACCESS  read-write
   STATUS      current
   DESCRIPTION
      "Path: tunnels.editConf.ipsecGreTunnels.bridging.l2ProtTunnel.cos

       Possibilities:
               unchanged   (255)"
   ::= {er1645v2TvTmplCiGreEntry 459341824}

er1645v2TvTmplCiGreBrL2ptDropThrStp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.stp

       unit name = packets/sec

       Possibilities:
               unlimited   (0)"
   ::= {er1645v2TvTmplCiGreEntry 459358272}

er1645v2TvTmplCiGreBrL2ptDropThrLldp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.lldp

       unit name = packets/sec

       Possibilities:
               unlimited   (0)"
   ::= {er1645v2TvTmplCiGreEntry 459358336}

er1645v2TvTmplCiGreBrL2ptDropThrOam OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.oam

       unit name = packets/sec

       Possibilities:
               unlimited   (0)"
   ::= {er1645v2TvTmplCiGreEntry 459358400}

er1645v2TvTmplCiGreBrL2ptDropThrCdp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.cdp

       unit name = packets/sec

       Possibilities:
               unlimited   (0)"
   ::= {er1645v2TvTmplCiGreEntry 459358464}

er1645v2TvTmplCiGreBrL2ptDropThrVtp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.vtp

       unit name = packets/sec

       Possibilities:
               unlimited   (0)"
   ::= {er1645v2TvTmplCiGreEntry 459358528}

er1645v2TvTmplCiGreBrL2ptDropThrLacp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.lacp

       unit name = packets/sec

       Possibilities:
               unlimited   (0)"
   ::= {er1645v2TvTmplCiGreEntry 459358592}

er1645v2TvTmplCiGreBrL2ptDropThrEfmOam OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.efmOam

       unit name = packets/sec

       Possibilities:
               unlimited   (0)"
   ::= {er1645v2TvTmplCiGreEntry 459358656}

er1645v2TvTmplCiGreBrL2ptDropThrPvst OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.pvst

       unit name = packets/sec

       Possibilities:
               unlimited   (0)"
   ::= {er1645v2TvTmplCiGreEntry 459358720}

er1645v2TvTmplCiGreBrL2ptDropThrMmrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.mmrp

       unit name = packets/sec

       Possibilities:
               unlimited   (0)"
   ::= {er1645v2TvTmplCiGreEntry 459358784}

er1645v2TvTmplCiGreBrL2ptDropThrMvrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.mvrp

       unit name = packets/sec

       Possibilities:
               unlimited   (0)"
   ::= {er1645v2TvTmplCiGreEntry 459358848}

er1645v2TvTmplCiGreBrL2ptDropThrGvrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.gvrp

       unit name = packets/sec

       Possibilities:
               unlimited   (0)"
   ::= {er1645v2TvTmplCiGreEntry 459358912}

er1645v2TvTmplCiGreBrL2ptDropThrGmrp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.gmrp

       unit name = packets/sec

       Possibilities:
               unlimited   (0)"
   ::= {er1645v2TvTmplCiGreEntry 459358976}

er1645v2TvTmplCiGreBrL2ptDropThrDtp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.dtp

       unit name = packets/sec

       Possibilities:
               unlimited   (0)"
   ::= {er1645v2TvTmplCiGreEntry 459359040}

er1645v2TvTmplCiGreBrL2ptDropThrPagp OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.pagp

       unit name = packets/sec

       Possibilities:
               unlimited   (0)"
   ::= {er1645v2TvTmplCiGreEntry 459359104}

er1645v2TvTmplCiGreBrL2ptDropThrUdld OBJECT-TYPE
   SYNTAX      INTEGER
               {
               unlimited (0)
               }
   UNITS       "packets/sec"
   MAX-ACCESS  read-write
   STATUS      current
   DESCRIPTION
      "Path: tunnels.editConf.ipsecGreTunnels.bridging.l2ProtTunnel.dropThresholds.udld

       unit name = packets/sec

       Possibilities:
               unlimited   (0)"
   ::= {er1645v2TvTmplCiGreEntry 459359168}

er1645v2TvTmplCiGreVirtEthernetVirtualEthernet OBJECT-TYPE
   SYNTAX      DisplayString
   MAX-ACCESS  read-write
   STATUS      current
   DESCRIPTION
      "Path: tunnels.editConf.ipsecGreTunnels.virtEthernet.virtualEthernet"
   ::= {er1645v2TvTmplCiGreEntry 151060480}

er1645v2TvTmplCiGreGreLocalIpAddress OBJECT-TYPE
   SYNTAX      IpAddress
   MAX-ACCESS  read-write
   STATUS      current
   DESCRIPTION
      "Path: tunnels.editConf.ipsecGreTunnels.gre.localIpAddress"
   ::= {er1645v2TvTmplCiGreEntry 587268096}

er1645v2TvTmplCiGreGreLocalInterface OBJECT-TYPE
   SYNTAX      DisplayString
   MAX-ACCESS  read-write
   STATUS      current
   DESCRIPTION
      "Path: tunnels.editConf.ipsecGreTunnels.gre.localInterface"
   ::= {er1645v2TvTmplCiGreEntry 588251136}

er1645v2TvTmplCiGreGreRemoteIpAddress OBJECT-TYPE
   SYNTAX      IpAddress
   MAX-ACCESS  read-write
   STATUS      current
   DESCRIPTION
      "Path: tunnels.editConf.ipsecGreTunnels.gre.remoteIpAddress"
   ::= {er1645v2TvTmplCiGreEntry 587333632}

er1645v2TvTmplCiGreGreRemoteDnsName OBJECT-TYPE
   SYNTAX      DisplayString
   MAX-ACCESS  read-write
   STATUS      current
   DESCRIPTION
      "Path: tunnels.editConf.ipsecGreTunnels.gre.remoteDnsName"
   ::= {er1645v2TvTmplCiGreEntry 587399168}

er1645v2TvTmplCiGreGreIpsFdx OBJECT-TYPE
   SYNTAX      DisplayString
   MAX-ACCESS  read-write
   STATUS      current
   DESCRIPTION
      "Path: tunnels.editConf.ipsecGreTunnels.gre.ipsec.fdxManualSA"
   ::= {er1645v2TvTmplCiGreEntry 587472896}

er1645v2TvTmplCiGreGreIpsHdxIn OBJECT-TYPE
   SYNTAX      DisplayString
   MAX-ACCESS  read-write
   STATUS      current
   DESCRIPTION
      "Path: tunnels.editConf.ipsecGreTunnels.gre.ipsec.hdxManualSA.inbound"
   ::= {er1645v2TvTmplCiGreEntry 587481120}

er1645v2TvTmplCiGreGreIpsHdxOut OBJECT-TYPE
   SYNTAX      DisplayString
   MAX-ACCESS  read-write
   STATUS      current
   DESCRIPTION
      "Path: tunnels.editConf.ipsecGreTunnels.gre.ipsec.hdxManualSA.outbound"
   ::= {er1645v2TvTmplCiGreEntry 587481152}

er1645v2TvTmplCiGreGreIpsPsCfg OBJECT-TYPE
   SYNTAX      DisplayString
   MAX-ACCESS  read-write
   STATUS      current
   DESCRIPTION
      "Path: tunnels.editConf.ipsecGreTunnels.gre.ipsec.ikePresharedSA.ikeSA"
   ::= {er1645v2TvTmplCiGreEntry 587489792}

er1645v2TvTmplCiGreGreIpsPsLIdIp OBJECT-TYPE
   SYNTAX      IpAddress
   MAX-ACCESS  read-write
   STATUS      current
   DESCRIPTION
      "Path: tunnels.editConf.ipsecGreTunnels.gre.ipsec.ikePresharedSA.localId.ipAddress"
   ::= {er1645v2TvTmplCiGreEntry 587490306}

er1645v2TvTmplCiGreGreIpsPsLIdHn OBJECT-TYPE
   SYNTAX      DisplayString
   MAX-ACCESS  read-write
   STATUS      current
   DESCRIPTION
      "Path: tunnels.editConf.ipsecGreTunnels.gre.ipsec.ikePresharedSA.localId.hostName"
   ::= {er1645v2TvTmplCiGreEntry 587490308}

er1645v2TvTmplCiGreGreIpsPsLIdUn OBJECT-TYPE
   SYNTAX      DisplayString
   MAX-ACCESS  read-write
   STATUS      current
   DESCRIPTION
      "Path: tunnels.editConf.ipsecGreTunnels.gre.ipsec.ikePresharedSA.localId.user"
   ::= {er1645v2TvTmplCiGreEntry 587490310}

er1645v2TvTmplCiGreGreIpsPsRIdIp OBJECT-TYPE
   SYNTAX      IpAddress
   MAX-ACCESS  read-write
   STATUS      current
   DESCRIPTION
      "Path: tunnels.editConf.ipsecGreTunnels.gre.ipsec.ikePresharedSA.remoteId.ipAddress"
   ::= {er1645v2TvTmplCiGreEntry 587490818}

er1645v2TvTmplCiGreGreIpsPsRIdHn OBJECT-TYPE
   SYNTAX      DisplayString
   MAX-ACCESS  read-write
   STATUS      current
   DESCRIPTION
      "Path: tunnels.editConf.ipsecGreTunnels.gre.ipsec.ikePresharedSA.remoteId.hostName"
   ::= {er1645v2TvTmplCiGreEntry 587490820}

er1645v2TvTmplCiGreGreIpsPsRIdUn OBJECT-TYPE
   SYNTAX      DisplayString
   MAX-ACCESS  read-write
   STATUS      current
   DESCRIPTION
      "Path: tunnels.editConf.ipsecGreTunnels.gre.ipsec.ikePresharedSA.remoteId.user"
   ::= {er1645v2TvTmplCiGreEntry 587490822}

er1645v2TvTmplCiGreGreIpsPsKey OBJECT-TYPE
   SYNTAX      DisplayString
   MAX-ACCESS  read-write
   STATUS      current
   DESCRIPTION
      "Path: tunnels.editConf.ipsecGreTunnels.gre.ipsec.ikePresharedSA.preSharedKey"
   ::= {er1645v2TvTmplCiGreEntry 587491328}

er1645v2TvTmplCiGreGreIpsPsEncMKey OBJECT-TYPE
   SYNTAX      INTEGER
               {
               none (1),
               encrypt (2),
               encType1 (3),
               invalid (128)
               }
   MAX-ACCESS  read-write
   STATUS      current
   DESCRIPTION
      "Path: tunnels.editConf.ipsecGreTunnels.gre.ipsec.ikePresharedSA.encModePreSharedKey

       Possibilities:
               none   (1)
               encrypt   (2)
               encType1   (3)
               invalid   (128)"
   ::= {er1645v2TvTmplCiGreEntry 587492352}

er1645v2TvTmplCiGreGreIpsPsEncKey OBJECT-TYPE
   SYNTAX      DisplayString
   MAX-ACCESS  read-write
   STATUS      current
   DESCRIPTION
      "Path: tunnels.editConf.ipsecGreTunnels.gre.ipsec.ikePresharedSA.encPreSharedKey"
   ::= {er1645v2TvTmplCiGreEntry 587492864}

er1645v2TvTmplCiGreGreIpsPsPIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecGreTunnels.gre.ipsec.ikePresharedSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TvTmplCiGreEntry 587491872}

er1645v2TvTmplCiGreGreIpsPsPIdLocAddr OBJECT-TYPE
   SYNTAX      IpAddress
   MAX-ACCESS  read-write
   STATUS      current
   DESCRIPTION
      "Path: tunnels.editConf.ipsecGreTunnels.gre.ipsec.ikePresharedSA.proxyId.localIpAddress"
   ::= {er1645v2TvTmplCiGreEntry 587491904}

er1645v2TvTmplCiGreGreIpsPsPIdLocMask OBJECT-TYPE
   SYNTAX      IpAddress
   MAX-ACCESS  read-write
   STATUS      current
   DESCRIPTION
      "Path: tunnels.editConf.ipsecGreTunnels.gre.ipsec.ikePresharedSA.proxyId.localIpMask"
   ::= {er1645v2TvTmplCiGreEntry 587491936}

er1645v2TvTmplCiGreGreIpsPsPIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikePresharedSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplCiGreEntry 587491968}

er1645v2TvTmplCiGreGreIpsPsPIdRemAddr OBJECT-TYPE
   SYNTAX      IpAddress
   MAX-ACCESS  read-write
   STATUS      current
   DESCRIPTION
      "Path: tunnels.editConf.ipsecGreTunnels.gre.ipsec.ikePresharedSA.proxyId.remoteIpAddress"
   ::= {er1645v2TvTmplCiGreEntry 587492000}

er1645v2TvTmplCiGreGreIpsPsPIdRemMask OBJECT-TYPE
   SYNTAX      IpAddress
   MAX-ACCESS  read-write
   STATUS      current
   DESCRIPTION
      "Path: tunnels.editConf.ipsecGreTunnels.gre.ipsec.ikePresharedSA.proxyId.remoteIpMask"
   ::= {er1645v2TvTmplCiGreEntry 587492032}

er1645v2TvTmplCiGreGreIpsPsPIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikePresharedSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplCiGreEntry 587492064}

er1645v2TvTmplCiGreGreIpsCeCfg OBJECT-TYPE
   SYNTAX      DisplayString
   MAX-ACCESS  read-write
   STATUS      current
   DESCRIPTION
      "Path: tunnels.editConf.ipsecGreTunnels.gre.ipsec.ikeCertificateSA.ikeSA"
   ::= {er1645v2TvTmplCiGreEntry 587497984}

er1645v2TvTmplCiGreGreIpsCeLIdIp OBJECT-TYPE
   SYNTAX      IpAddress
   MAX-ACCESS  read-write
   STATUS      current
   DESCRIPTION
      "Path: tunnels.editConf.ipsecGreTunnels.gre.ipsec.ikeCertificateSA.localId.ipAddress"
   ::= {er1645v2TvTmplCiGreEntry 587498498}

er1645v2TvTmplCiGreGreIpsCeLIdHn OBJECT-TYPE
   SYNTAX      DisplayString
   MAX-ACCESS  read-write
   STATUS      current
   DESCRIPTION
      "Path: tunnels.editConf.ipsecGreTunnels.gre.ipsec.ikeCertificateSA.localId.hostName"
   ::= {er1645v2TvTmplCiGreEntry 587498500}

er1645v2TvTmplCiGreGreIpsCeLIdUn OBJECT-TYPE
   SYNTAX      DisplayString
   MAX-ACCESS  read-write
   STATUS      current
   DESCRIPTION
      "Path: tunnels.editConf.ipsecGreTunnels.gre.ipsec.ikeCertificateSA.localId.user"
   ::= {er1645v2TvTmplCiGreEntry 587498502}

er1645v2TvTmplCiGreGreIpsCeLIdDn OBJECT-TYPE
   SYNTAX      DisplayString
   MAX-ACCESS  read-write
   STATUS      current
   DESCRIPTION
      "Path: tunnels.editConf.ipsecGreTunnels.gre.ipsec.ikeCertificateSA.localId.derAsn1Dn"
   ::= {er1645v2TvTmplCiGreEntry 587498504}

er1645v2TvTmplCiGreGreIpsCeRIdIp OBJECT-TYPE
   SYNTAX      IpAddress
   MAX-ACCESS  read-write
   STATUS      current
   DESCRIPTION
      "Path: tunnels.editConf.ipsecGreTunnels.gre.ipsec.ikeCertificateSA.remoteId.ipAddress"
   ::= {er1645v2TvTmplCiGreEntry 587499010}

er1645v2TvTmplCiGreGreIpsCeRIdHn OBJECT-TYPE
   SYNTAX      DisplayString
   MAX-ACCESS  read-write
   STATUS      current
   DESCRIPTION
      "Path: tunnels.editConf.ipsecGreTunnels.gre.ipsec.ikeCertificateSA.remoteId.hostName"
   ::= {er1645v2TvTmplCiGreEntry 587499012}

er1645v2TvTmplCiGreGreIpsCeRIdUn OBJECT-TYPE
   SYNTAX      DisplayString
   MAX-ACCESS  read-write
   STATUS      current
   DESCRIPTION
      "Path: tunnels.editConf.ipsecGreTunnels.gre.ipsec.ikeCertificateSA.remoteId.user"
   ::= {er1645v2TvTmplCiGreEntry 587499014}

er1645v2TvTmplCiGreGreIpsCeRIdDn OBJECT-TYPE
   SYNTAX      DisplayString
   MAX-ACCESS  read-write
   STATUS      current
   DESCRIPTION
      "Path: tunnels.editConf.ipsecGreTunnels.gre.ipsec.ikeCertificateSA.remoteId.derAsn1Dn"
   ::= {er1645v2TvTmplCiGreEntry 587499016}

er1645v2TvTmplCiGreGreIpsCePIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecGreTunnels.gre.ipsec.ikeCertificateSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TvTmplCiGreEntry 587500064}

er1645v2TvTmplCiGreGreIpsCePIdLocAddr OBJECT-TYPE
   SYNTAX      IpAddress
   MAX-ACCESS  read-write
   STATUS      current
   DESCRIPTION
      "Path: tunnels.editConf.ipsecGreTunnels.gre.ipsec.ikeCertificateSA.proxyId.localIpAddress"
   ::= {er1645v2TvTmplCiGreEntry 587500096}

er1645v2TvTmplCiGreGreIpsCePIdLocMask OBJECT-TYPE
   SYNTAX      IpAddress
   MAX-ACCESS  read-write
   STATUS      current
   DESCRIPTION
      "Path: tunnels.editConf.ipsecGreTunnels.gre.ipsec.ikeCertificateSA.proxyId.localIpMask"
   ::= {er1645v2TvTmplCiGreEntry 587500128}

er1645v2TvTmplCiGreGreIpsCePIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikeCertificateSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplCiGreEntry 587500160}

er1645v2TvTmplCiGreGreIpsCePIdRemAddr OBJECT-TYPE
   SYNTAX      IpAddress
   MAX-ACCESS  read-write
   STATUS      current
   DESCRIPTION
      "Path: tunnels.editConf.ipsecGreTunnels.gre.ipsec.ikeCertificateSA.proxyId.remoteIpAddress"
   ::= {er1645v2TvTmplCiGreEntry 587500192}

er1645v2TvTmplCiGreGreIpsCePIdRemMask OBJECT-TYPE
   SYNTAX      IpAddress
   MAX-ACCESS  read-write
   STATUS      current
   DESCRIPTION
      "Path: tunnels.editConf.ipsecGreTunnels.gre.ipsec.ikeCertificateSA.proxyId.remoteIpMask"
   ::= {er1645v2TvTmplCiGreEntry 587500224}

er1645v2TvTmplCiGreGreIpsCePIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecGreTunnels.gre.ipsec.ikeCertificateSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplCiGreEntry 587500256}

er1645v2TvTmplCiGreGreKpAlMode OBJECT-TYPE
   SYNTAX      INTEGER
               {
               disabled (0),
               enabled (1)
               }
   MAX-ACCESS  read-write
   STATUS      current
   DESCRIPTION
      "Path: tunnels.editConf.ipsecGreTunnels.gre.keepAlive.mode

       Possibilities:
               disabled   (0)
               enabled   (1)"
   ::= {er1645v2TvTmplCiGreEntry 587727104}

er1645v2TvTmplCiGreGreKpAlInterval OBJECT-TYPE
   SYNTAX      TimeTicks
   MAX-ACCESS  read-write
   STATUS      current
   DESCRIPTION
      "Path: tunnels.editConf.ipsecGreTunnels.gre.keepAlive.interval

       Time in centi-second."
   ::= {er1645v2TvTmplCiGreEntry 587727360}

er1645v2TvTmplCiGreGreKpAlRepTimeOut OBJECT-TYPE
   SYNTAX      TimeTicks
   MAX-ACCESS  read-write
   STATUS      current
   DESCRIPTION
      "Path: tunnels.editConf.ipsecGreTunnels.gre.keepAlive.replyTimeOut

       Time in centi-second."
   ::= {er1645v2TvTmplCiGreEntry 587727616}

er1645v2TvTmplCiGreGreKpAlFailsPrmt OBJECT-TYPE
   SYNTAX      Integer32
   MAX-ACCESS  read-write
   STATUS      current
   DESCRIPTION
      "Path: tunnels.editConf.ipsecGreTunnels.gre.keepAlive.failsPermitted"
   ::= {er1645v2TvTmplCiGreEntry 587727872}

er1645v2TvTmplCiGreGreNoTraffTO OBJECT-TYPE
   SYNTAX      TimeTicks
   MAX-ACCESS  read-write
   STATUS      current
   DESCRIPTION
      "Path: tunnels.editConf.ipsecGreTunnels.gre.noTrafficTimeOut

       Time in centi-second."
   ::= {er1645v2TvTmplCiGreEntry 587792384}

er1645v2TvTmplCiGreGreNoTraffDi OBJECT-TYPE
   SYNTAX      INTEGER
               {
               inbound (1),
               outbound (2),
               both (3)
               }
   MAX-ACCESS  read-write
   STATUS      current
   DESCRIPTION
      "Path: tunnels.editConf.ipsecGreTunnels.gre.noTrafficDirection

       Possibilities:
               inbound   (1)
               outbound   (2)
               both   (3)"
   ::= {er1645v2TvTmplCiGreEntry 588185600}

er1645v2TvTmplCiGreGreType OBJECT-TYPE
   SYNTAX      INTEGER
               {
               outgoingDial (1),
               outgoingLeasedLine (2),
               incoming (0)
               }
   MAX-ACCESS  read-write
   STATUS      current
   DESCRIPTION
      "Path: tunnels.editConf.ipsecGreTunnels.gre.type

       Possibilities:
               outgoingDial   (1)
               outgoingLeasedLine   (2)
               incoming   (0)"
   ::= {er1645v2TvTmplCiGreEntry 587857920}

er1645v2TvTmplCiGreGreRRoutDefRt OBJECT-TYPE
   SYNTAX      INTEGER
               {
               disabled (0),
               enabled (1)
               }
   MAX-ACCESS  read-write
   STATUS      current
   DESCRIPTION
      "Path: tunnels.editConf.ipsecGreTunnels.gre.remoteRoute.useDefaultRoute

       Possibilities:
               disabled   (0)
               enabled   (1)"
   ::= {er1645v2TvTmplCiGreEntry 587923712}

er1645v2TvTmplCiGreGreTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256),
               queueTosMap (257)
               }
   MAX-ACCESS  read-write
   STATUS      current
   DESCRIPTION
      "Path: tunnels.editConf.ipsecGreTunnels.gre.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)
               queueTosMap   (257)"
   ::= {er1645v2TvTmplCiGreEntry 587988992}

er1645v2TvTmplCiGreGreQueueTosMapQueue1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589168896}

er1645v2TvTmplCiGreGreQueueTosMapQueue2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589169152}

er1645v2TvTmplCiGreGreQueueTosMapQueue3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589169408}

er1645v2TvTmplCiGreGreQueueTosMapQueue4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589169664}

er1645v2TvTmplCiGreGreQueueTosMapQueue5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.queue5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589169920}

er1645v2TvTmplCiGreGreQueueTosMapLowDelayQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.lowDelayQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589170176}

er1645v2TvTmplCiGreGreQueueTosMapLowDelay2Queue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.lowDelay2Queue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589170432}

er1645v2TvTmplCiGreGreQueueTosMapSystemQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecGreTunnels.gre.queueTosMap.systemQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCiGreEntry 589170688}

er1645v2TvTmplCiGreGreDf OBJECT-TYPE
   SYNTAX      INTEGER
               {
               clear (0),
               set (1),
               copy (2)
               }
   MAX-ACCESS  read-write
   STATUS      current
   DESCRIPTION
      "Path: tunnels.editConf.ipsecGreTunnels.gre.dontFragmentBit

       Possibilities:
               clear   (0)
               set   (1)
               copy   (2)"
   ::= {er1645v2TvTmplCiGreEntry 588054528}

er1645v2TvTmplCiGreGreTtl OBJECT-TYPE
   SYNTAX      INTEGER
               {
               copy (256)
               }
   MAX-ACCESS  read-write
   STATUS      current
   DESCRIPTION
      "Path: tunnels.editConf.ipsecGreTunnels.gre.ttl

       Possibilities:
               copy   (256)"
   ::= {er1645v2TvTmplCiGreEntry 588120064}

er1645v2TvTmplCiGreGreMtu OBJECT-TYPE
   SYNTAX      Integer32
   MAX-ACCESS  read-write
   STATUS      current
   DESCRIPTION
      "Path: tunnels.editConf.ipsecGreTunnels.gre.mtu"
   ::= {er1645v2TvTmplCiGreEntry 588382208}

er1645v2TvTmplCiGreMplsMode OBJECT-TYPE
   SYNTAX      INTEGER
               {
               disabled (0),
               enabled (1)
               }
   MAX-ACCESS  read-write
   STATUS      current
   DESCRIPTION
      "Path: tunnels.editConf.ipsecGreTunnels.mpls.mode

       Possibilities:
               disabled   (0)
               enabled   (1)"
   ::= {er1645v2TvTmplCiGreEntry 167837696}

er1645v2TvTmplCiGreMplsInLabel OBJECT-TYPE
   SYNTAX      Integer32
   MAX-ACCESS  read-write
   STATUS      current
   DESCRIPTION
      "Path: tunnels.editConf.ipsecGreTunnels.mpls.inLabel"
   ::= {er1645v2TvTmplCiGreEntry 167903232}

er1645v2TvTmplCiGreMplsOutLabel OBJECT-TYPE
   SYNTAX      Integer32
   MAX-ACCESS  read-write
   STATUS      current
   DESCRIPTION
      "Path: tunnels.editConf.ipsecGreTunnels.mpls.outLabel"
   ::= {er1645v2TvTmplCiGreEntry 168099840}

er1645v2TvTmplCiGreMplsTrafficClassMode OBJECT-TYPE
   SYNTAX      INTEGER
               {
               fixed (0),
               qos (1)
               }
   MAX-ACCESS  read-write
   STATUS      current
   DESCRIPTION
      "Path: tunnels.editConf.ipsecGreTunnels.mpls.trafficClass.mode

       Possibilities:
               fixed   (0)
               qos   (1)"
   ::= {er1645v2TvTmplCiGreEntry 167969024}

er1645v2TvTmplCiGreMplsTrafficClassFixed OBJECT-TYPE
   SYNTAX      Integer32
   MAX-ACCESS  read-write
   STATUS      current
   DESCRIPTION
      "Path: tunnels.editConf.ipsecGreTunnels.mpls.trafficClass.fixed"
   ::= {er1645v2TvTmplCiGreEntry 167969280}

er1645v2TvTmplCiGreMplsTrafficClassQosP0 OBJECT-TYPE
   SYNTAX      Integer32
   MAX-ACCESS  read-write
   STATUS      current
   DESCRIPTION
      "Path: tunnels.editConf.ipsecGreTunnels.mpls.trafficClass.qos.p0"
   ::= {er1645v2TvTmplCiGreEntry 167969537}

er1645v2TvTmplCiGreMplsTrafficClassQosP1 OBJECT-TYPE
   SYNTAX      Integer32
   MAX-ACCESS  read-write
   STATUS      current
   DESCRIPTION
      "Path: tunnels.editConf.ipsecGreTunnels.mpls.trafficClass.qos.p1"
   ::= {er1645v2TvTmplCiGreEntry 167969538}

er1645v2TvTmplCiGreMplsTrafficClassQosP2 OBJECT-TYPE
   SYNTAX      Integer32
   MAX-ACCESS  read-write
   STATUS      current
   DESCRIPTION
      "Path: tunnels.editConf.ipsecGreTunnels.mpls.trafficClass.qos.p2"
   ::= {er1645v2TvTmplCiGreEntry 167969539}

er1645v2TvTmplCiGreMplsTrafficClassQosP3 OBJECT-TYPE
   SYNTAX      Integer32
   MAX-ACCESS  read-write
   STATUS      current
   DESCRIPTION
      "Path: tunnels.editConf.ipsecGreTunnels.mpls.trafficClass.qos.p3"
   ::= {er1645v2TvTmplCiGreEntry 167969540}

er1645v2TvTmplCiGreMplsTrafficClassQosP4 OBJECT-TYPE
   SYNTAX      Integer32
   MAX-ACCESS  read-write
   STATUS      current
   DESCRIPTION
      "Path: tunnels.editConf.ipsecGreTunnels.mpls.trafficClass.qos.p4"
   ::= {er1645v2TvTmplCiGreEntry 167969541}

er1645v2TvTmplCiGreMplsTrafficClassQosP5 OBJECT-TYPE
   SYNTAX      Integer32
   MAX-ACCESS  read-write
   STATUS      current
   DESCRIPTION
      "Path: tunnels.editConf.ipsecGreTunnels.mpls.trafficClass.qos.p5"
   ::= {er1645v2TvTmplCiGreEntry 167969542}

er1645v2TvTmplCiGreMplsTrafficClassQosP6 OBJECT-TYPE
   SYNTAX      Integer32
   MAX-ACCESS  read-write
   STATUS      current
   DESCRIPTION
      "Path: tunnels.editConf.ipsecGreTunnels.mpls.trafficClass.qos.p6"
   ::= {er1645v2TvTmplCiGreEntry 167969543}

er1645v2TvTmplCiGreMplsTrafficClassQosP7 OBJECT-TYPE
   SYNTAX      Integer32
   MAX-ACCESS  read-write
   STATUS      current
   DESCRIPTION
      "Path: tunnels.editConf.ipsecGreTunnels.mpls.trafficClass.qos.p7"
   ::= {er1645v2TvTmplCiGreEntry 167969544}

er1645v2TvTmplCiGreMplsTtl OBJECT-TYPE
   SYNTAX      INTEGER
               {
               copy (256)
               }
   MAX-ACCESS  read-write
   STATUS      current
   DESCRIPTION
      "Path: tunnels.editConf.ipsecGreTunnels.mpls.ttl

       Possibilities:
               copy   (256)"
   ::= {er1645v2TvTmplCiGreEntry 168034304}

er1645v2TvTmplCiGreInbBwCir OBJECT-TYPE
   SYNTAX      Integer32
   MAX-ACCESS  read-write
   STATUS      current
   DESCRIPTION
      "Path: tunnels.editConf.ipsecGreTunnels.inboundBandwidth.cir"
   ::= {er1645v2TvTmplCiGreEntry 117506048}

er1645v2TvTmplCiGreInbBwTc OBJECT-TYPE
   SYNTAX      INTEGER
               {
               auto (0)
               }
   MAX-ACCESS  read-write
   STATUS      current
   DESCRIPTION
      "Path: tunnels.editConf.ipsecGreTunnels.inboundBandwidth.tc

       Possibilities:
               auto   (0)"
   ::= {er1645v2TvTmplCiGreEntry 117833728}

er1645v2TvTmplCiGreInbBwCorrType OBJECT-TYPE
   SYNTAX      INTEGER
               {
               noCorrection (0),
               predefined (1),
               manual (2)
               }
   MAX-ACCESS  read-write
   STATUS      current
   DESCRIPTION
      "Path: tunnels.editConf.ipsecGreTunnels.inboundBandwidth.correction.type

       Possibilities:
               noCorrection   (0)
               predefined   (1)
               manual   (2)"
   ::= {er1645v2TvTmplCiGreEntry 117579776}

er1645v2TvTmplCiGreInbBwCorrPredefEncapsFrameRelay OBJECT-TYPE
   SYNTAX      DisplayString
   MAX-ACCESS  read-write
   STATUS      current
   DESCRIPTION
      "Path: tunnels.editConf.ipsecGreTunnels.inboundBandwidth.correction.predefined.encapsulation.frameRelay"
   ::= {er1645v2TvTmplCiGreEntry 117589056}

er1645v2TvTmplCiGreInbBwCorrPredefEncapsPpp OBJECT-TYPE
   SYNTAX      DisplayString
   MAX-ACCESS  read-write
   STATUS      current
   DESCRIPTION
      "Path: tunnels.editConf.ipsecGreTunnels.inboundBandwidth.correction.predefined.encapsulation.ppp"
   ::= {er1645v2TvTmplCiGreEntry 117589120}

er1645v2TvTmplCiGreInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecGreTunnels.inboundBandwidth.correction.predefined.encapsulation.atm.higherLayer

       Possibilities:
               rfc2684   (0)
               ppp   (1)
               pppOverEthernet   (2)"
   ::= {er1645v2TvTmplCiGreEntry 117589192}

er1645v2TvTmplCiGreInbBwCorrPredefEncapsAtmMp OBJECT-TYPE
   SYNTAX      INTEGER
               {
               llcEncapsulation (0),
               vcMultiplexing (1)
               }
   MAX-ACCESS  read-write
   STATUS      current
   DESCRIPTION
      "Path: tunnels.editConf.ipsecGreTunnels.inboundBandwidth.correction.predefined.encapsulation.atm.multiProtocol

       Possibilities:
               llcEncapsulation   (0)
               vcMultiplexing   (1)"
   ::= {er1645v2TvTmplCiGreEntry 117589200}

er1645v2TvTmplCiGreInbBwCorrPredefEncapsHdlc OBJECT-TYPE
   SYNTAX      DisplayString
   MAX-ACCESS  read-write
   STATUS      current
   DESCRIPTION
      "Path: tunnels.editConf.ipsecGreTunnels.inboundBandwidth.correction.predefined.encapsulation.hdlc"
   ::= {er1645v2TvTmplCiGreEntry 117589248}

er1645v2TvTmplCiGreInbBwCorrPredefEncapsEfmFs OBJECT-TYPE
   SYNTAX      Integer32
   MAX-ACCESS  read-write
   STATUS      current
   DESCRIPTION
      "Path: tunnels.editConf.ipsecGreTunnels.inboundBandwidth.correction.predefined.encapsulation.efm.fragmentSize"
   ::= {er1645v2TvTmplCiGreEntry 117589320}

er1645v2TvTmplCiGreInbBwCorrPredefEncapsEfmIb OBJECT-TYPE
   SYNTAX      Integer32
   MAX-ACCESS  read-write
   STATUS      current
   DESCRIPTION
      "Path: tunnels.editConf.ipsecGreTunnels.inboundBandwidth.correction.predefined.encapsulation.efm.idleBytes"
   ::= {er1645v2TvTmplCiGreEntry 117589328}

er1645v2TvTmplCiGreInbBwCorrPredefMode OBJECT-TYPE
   SYNTAX      INTEGER
               {
               routing (0),
               bridging (1)
               }
   MAX-ACCESS  read-write
   STATUS      current
   DESCRIPTION
      "Path: tunnels.editConf.ipsecGreTunnels.inboundBandwidth.correction.predefined.mode

       Possibilities:
               routing   (0)
               bridging   (1)"
   ::= {er1645v2TvTmplCiGreEntry 117590016}

er1645v2TvTmplCiGreInbBwCorrManualOverhead OBJECT-TYPE
   SYNTAX      Integer32
   MAX-ACCESS  read-write
   STATUS      current
   DESCRIPTION
      "Path: tunnels.editConf.ipsecGreTunnels.inboundBandwidth.correction.manual.overhead"
   ::= {er1645v2TvTmplCiGreEntry 117596192}

er1645v2TvTmplCiGreInbBwCorrManualFrameData OBJECT-TYPE
   SYNTAX      Counter32
   MAX-ACCESS  read-write
   STATUS      current
   DESCRIPTION
      "Path: tunnels.editConf.ipsecGreTunnels.inboundBandwidth.correction.manual.frameData

       32 bit unsigned wrappable counter."
   ::= {er1645v2TvTmplCiGreEntry 117596224}

er1645v2TvTmplCiGreInbBwCorrManualFrameHeader OBJECT-TYPE
   SYNTAX      Counter32
   MAX-ACCESS  read-write
   STATUS      current
   DESCRIPTION
      "Path: tunnels.editConf.ipsecGreTunnels.inboundBandwidth.correction.manual.frameHeader

       32 bit unsigned wrappable counter."
   ::= {er1645v2TvTmplCiGreEntry 117596256}

er1645v2TvTmplCiGreInbBwMaxFifoQLen OBJECT-TYPE
   SYNTAX      Integer32
   MAX-ACCESS  read-write
   STATUS      current
   DESCRIPTION
      "Path: tunnels.editConf.ipsecGreTunnels.inboundBandwidth.maxFifoQLen"
   ::= {er1645v2TvTmplCiGreEntry 117637120}

er1645v2TvTmplCiGreInbBwPriorityPolicy OBJECT-TYPE
   SYNTAX      DisplayString
   MAX-ACCESS  read-write
   STATUS      current
   DESCRIPTION
      "Path: tunnels.editConf.ipsecGreTunnels.inboundBandwidth.priorityPolicy"
   ::= {er1645v2TvTmplCiGreEntry 117702656}

er1645v2TvTmplCiGreBandwidthMode OBJECT-TYPE
   SYNTAX      INTEGER
               {
               reshaping (1),
               policing (2),
               policingReshape (3)
               }
   MAX-ACCESS  read-write
   STATUS      current
   DESCRIPTION
      "Path: tunnels.editConf.ipsecGreTunnels.bandwidth.mode

       Possibilities:
               reshaping   (1)
               policing   (2)
               policingReshape   (3)"
   ::= {er1645v2TvTmplCiGreEntry 148897792}

er1645v2TvTmplCiGreBandwidthCir OBJECT-TYPE
   SYNTAX      Integer32
   MAX-ACCESS  read-write
   STATUS      current
   DESCRIPTION
      "Path: tunnels.editConf.ipsecGreTunnels.bandwidth.cir"
   ::= {er1645v2TvTmplCiGreEntry 135266304}

er1645v2TvTmplCiGreBandwidthEir OBJECT-TYPE
   SYNTAX      Integer32
   MAX-ACCESS  read-write
   STATUS      current
   DESCRIPTION
      "Path: tunnels.editConf.ipsecGreTunnels.bandwidth.eir"
   ::= {er1645v2TvTmplCiGreEntry 141557760}

er1645v2TvTmplCiGreBandwidthUnit OBJECT-TYPE
   SYNTAX      INTEGER
               {
               bitssec (1),
               percent (2)
               }
   MAX-ACCESS  read-write
   STATUS      current
   DESCRIPTION
      "Path: tunnels.editConf.ipsecGreTunnels.bandwidth.unit

       Possibilities:
               bits/sec   (1)
               percent   (2)"
   ::= {er1645v2TvTmplCiGreEntry 139460608}

er1645v2TvTmplCiGreBandwidthTc OBJECT-TYPE
   SYNTAX      INTEGER
               {
               auto (0)
               }
   MAX-ACCESS  read-write
   STATUS      current
   DESCRIPTION
      "Path: tunnels.editConf.ipsecGreTunnels.bandwidth.tc

       Possibilities:
               auto   (0)"
   ::= {er1645v2TvTmplCiGreEntry 140509184}

er1645v2TvTmplCiGreBandwidthTcFactor OBJECT-TYPE
   SYNTAX      INTEGER
               {
               ms (10),
               s100us (1)
               }
   MAX-ACCESS  read-write
   STATUS      current
   DESCRIPTION
      "Path: tunnels.editConf.ipsecGreTunnels.bandwidth.tcFactor

       Possibilities:
               ms   (10)
               *100us   (1)"
   ::= {er1645v2TvTmplCiGreEntry 142606336}

er1645v2TvTmplCiGreBandwidthCorrType OBJECT-TYPE
   SYNTAX      INTEGER
               {
               noCorrection (0),
               predefined (1),
               manual (2)
               }
   MAX-ACCESS  read-write
   STATUS      current
   DESCRIPTION
      "Path: tunnels.editConf.ipsecGreTunnels.bandwidth.correction.type

       Possibilities:
               noCorrection   (0)
               predefined   (1)
               manual   (2)"
   ::= {er1645v2TvTmplCiGreEntry 136445952}

er1645v2TvTmplCiGreBandwidthCorrPredefEncapsFrameRelay OBJECT-TYPE
   SYNTAX      DisplayString
   MAX-ACCESS  read-write
   STATUS      current
   DESCRIPTION
      "Path: tunnels.editConf.ipsecGreTunnels.bandwidth.correction.predefined.encapsulation.frameRelay"
   ::= {er1645v2TvTmplCiGreEntry 136594432}

er1645v2TvTmplCiGreBandwidthCorrPredefEncapsPpp OBJECT-TYPE
   SYNTAX      DisplayString
   MAX-ACCESS  read-write
   STATUS      current
   DESCRIPTION
      "Path: tunnels.editConf.ipsecGreTunnels.bandwidth.correction.predefined.encapsulation.ppp"
   ::= {er1645v2TvTmplCiGreEntry 136595456}

er1645v2TvTmplCiGreBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipsecGreTunnels.bandwidth.correction.predefined.encapsulation.atm.higherLayer

       Possibilities:
               rfc2684   (0)
               ppp   (1)
               pppOverEthernet   (2)"
   ::= {er1645v2TvTmplCiGreEntry 136596608}

er1645v2TvTmplCiGreBandwidthCorrPredefEncapsAtmMp OBJECT-TYPE
   SYNTAX      INTEGER
               {
               llcEncapsulation (0),
               vcMultiplexing (1)
               }
   MAX-ACCESS  read-write
   STATUS      current
   DESCRIPTION
      "Path: tunnels.editConf.ipsecGreTunnels.bandwidth.correction.predefined.encapsulation.atm.multiProtocol

       Possibilities:
               llcEncapsulation   (0)
               vcMultiplexing   (1)"
   ::= {er1645v2TvTmplCiGreEntry 136596736}

er1645v2TvTmplCiGreBandwidthCorrPredefEncapsHdlc OBJECT-TYPE
   SYNTAX      DisplayString
   MAX-ACCESS  read-write
   STATUS      current
   DESCRIPTION
      "Path: tunnels.editConf.ipsecGreTunnels.bandwidth.correction.predefined.encapsulation.hdlc"
   ::= {er1645v2TvTmplCiGreEntry 136597504}

er1645v2TvTmplCiGreBandwidthCorrPredefEncapsEfmFs OBJECT-TYPE
   SYNTAX      Integer32
   MAX-ACCESS  read-write
   STATUS      current
   DESCRIPTION
      "Path: tunnels.editConf.ipsecGreTunnels.bandwidth.correction.predefined.encapsulation.efm.fragmentSize"
   ::= {er1645v2TvTmplCiGreEntry 136598656}

er1645v2TvTmplCiGreBandwidthCorrPredefEncapsEfmIb OBJECT-TYPE
   SYNTAX      Integer32
   MAX-ACCESS  read-write
   STATUS      current
   DESCRIPTION
      "Path: tunnels.editConf.ipsecGreTunnels.bandwidth.correction.predefined.encapsulation.efm.idleBytes"
   ::= {er1645v2TvTmplCiGreEntry 136598784}

er1645v2TvTmplCiGreBandwidthCorrPredefMode OBJECT-TYPE
   SYNTAX      INTEGER
               {
               routing (0),
               bridging (1)
               }
   MAX-ACCESS  read-write
   STATUS      current
   DESCRIPTION
      "Path: tunnels.editConf.ipsecGreTunnels.bandwidth.correction.predefined.mode

       Possibilities:
               routing   (0)
               bridging   (1)"
   ::= {er1645v2TvTmplCiGreEntry 136609792}

er1645v2TvTmplCiGreBandwidthCorrManualOverhead OBJECT-TYPE
   SYNTAX      Integer32
   MAX-ACCESS  read-write
   STATUS      current
   DESCRIPTION
      "Path: tunnels.editConf.ipsecGreTunnels.bandwidth.correction.manual.overhead"
   ::= {er1645v2TvTmplCiGreEntry 136708608}

er1645v2TvTmplCiGreBandwidthCorrManualFrameData OBJECT-TYPE
   SYNTAX      Counter32
   MAX-ACCESS  read-write
   STATUS      current
   DESCRIPTION
      "Path: tunnels.editConf.ipsecGreTunnels.bandwidth.correction.manual.frameData

       32 bit unsigned wrappable counter."
   ::= {er1645v2TvTmplCiGreEntry 136709120}

er1645v2TvTmplCiGreBandwidthCorrManualFrameHeader OBJECT-TYPE
   SYNTAX      Counter32
   MAX-ACCESS  read-write
   STATUS      current
   DESCRIPTION
      "Path: tunnels.editConf.ipsecGreTunnels.bandwidth.correction.manual.frameHeader

       32 bit unsigned wrappable counter."
   ::= {er1645v2TvTmplCiGreEntry 136709632}

er1645v2TvTmplCiGreBandwidthMaxFifoQLen OBJECT-TYPE
   SYNTAX      Integer32
   MAX-ACCESS  read-write
   STATUS      current
   DESCRIPTION
      "Path: tunnels.editConf.ipsecGreTunnels.bandwidth.maxFifoQLen"
   ::= {er1645v2TvTmplCiGreEntry 137363456}

er1645v2TvTmplCiGreBandwidthDeFlagCir OBJECT-TYPE
   SYNTAX      INTEGER
               {
               allowed (1),
               notAllowed (2)
               }
   MAX-ACCESS  read-write
   STATUS      current
   DESCRIPTION
      "Path: tunnels.editConf.ipsecGreTunnels.bandwidth.deFlag.cir

       Possibilities:
               allowed   (1)
               notAllowed   (2)"
   ::= {er1645v2TvTmplCiGreEntry 147853312}

er1645v2TvTmplCiGreBandwidthDeFlagEir OBJECT-TYPE
   SYNTAX      INTEGER
               {
               allowed (1),
               notAllowed (2)
               }
   MAX-ACCESS  read-write
   STATUS      current
   DESCRIPTION
      "Path: tunnels.editConf.ipsecGreTunnels.bandwidth.deFlag.eir

       Possibilities:
               allowed   (1)
               notAllowed   (2)"
   ::= {er1645v2TvTmplCiGreEntry 147857408}

er1645v2TvTmplCiGreBandwidthDeFlagViolate OBJECT-TYPE
   SYNTAX      INTEGER
               {
               allowed (1),
               notAllowed (2)
               }
   MAX-ACCESS  read-write
   STATUS      current
   DESCRIPTION
      "Path: tunnels.editConf.ipsecGreTunnels.bandwidth.deFlag.violate

       Possibilities:
               allowed   (1)
               notAllowed   (2)"
   ::= {er1645v2TvTmplCiGreEntry 147861504}

er1645v2TvTmplCiGreBandwidthActCirActNone OBJECT-TYPE
   SYNTAX      OCTET STRING
   MAX-ACCESS  read-write
   STATUS      current
   DESCRIPTION
      "Path: tunnels.editConf.ipsecGreTunnels.bandwidth.action.cirAction.none"
   ::= {er1645v2TvTmplCiGreEntry 150085632}

er1645v2TvTmplCiGreBandwidthActCirActEthCos1 OBJECT-TYPE
   SYNTAX      INTEGER
               {
               unchanged (256)
               }
   MAX-ACCESS  read-write
   STATUS      current
   DESCRIPTION
      "Path: tunnels.editConf.ipsecGreTunnels.bandwidth.action.cirAction.ethernet.cosDepth1

       Possibilities:
               unchanged   (256)"
   ::= {er1645v2TvTmplCiGreEntry 150094080}

er1645v2TvTmplCiGreBandwidthActCirActEthDei1 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth1

       Possibilities:
               unchanged   (255)
               clear   (0)
               set   (1)"
   ::= {er1645v2TvTmplCiGreEntry 150099200}

er1645v2TvTmplCiGreBandwidthActCirActEthCos2 OBJECT-TYPE
   SYNTAX      INTEGER
               {
               unchanged (256)
               }
   MAX-ACCESS  read-write
   STATUS      current
   DESCRIPTION
      "Path: tunnels.editConf.ipsecGreTunnels.bandwidth.action.cirAction.ethernet.cosDepth2

       Possibilities:
               unchanged   (256)"
   ::= {er1645v2TvTmplCiGreEntry 150094336}

er1645v2TvTmplCiGreBandwidthActCirActEthDei2 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth2

       Possibilities:
               unchanged   (255)
               clear   (0)
               set   (1)"
   ::= {er1645v2TvTmplCiGreEntry 150099456}

er1645v2TvTmplCiGreBandwidthActCirActEthCos3 OBJECT-TYPE
   SYNTAX      INTEGER
               {
               unchanged (256)
               }
   MAX-ACCESS  read-write
   STATUS      current
   DESCRIPTION
      "Path: tunnels.editConf.ipsecGreTunnels.bandwidth.action.cirAction.ethernet.cosDepth3

       Possibilities:
               unchanged   (256)"
   ::= {er1645v2TvTmplCiGreEntry 150094592}

er1645v2TvTmplCiGreBandwidthActCirActEthDei3 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth3

       Possibilities:
               unchanged   (255)
               clear   (0)
               set   (1)"
   ::= {er1645v2TvTmplCiGreEntry 150099712}

er1645v2TvTmplCiGreBandwidthActCirActEthCos4 OBJECT-TYPE
   SYNTAX      INTEGER
               {
               unchanged (256)
               }
   MAX-ACCESS  read-write
   STATUS      current
   DESCRIPTION
      "Path: tunnels.editConf.ipsecGreTunnels.bandwidth.action.cirAction.ethernet.cosDepth4

       Possibilities:
               unchanged   (256)"
   ::= {er1645v2TvTmplCiGreEntry 150094848}

er1645v2TvTmplCiGreBandwidthActCirActEthDei4 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth4

       Possibilities:
               unchanged   (255)
               clear   (0)
               set   (1)"
   ::= {er1645v2TvTmplCiGreEntry 150099968}

er1645v2TvTmplCiGreBandwidthActCirActEthCos5 OBJECT-TYPE
   SYNTAX      INTEGER
               {
               unchanged (256)
               }
   MAX-ACCESS  read-write
   STATUS      current
   DESCRIPTION
      "Path: tunnels.editConf.ipsecGreTunnels.bandwidth.action.cirAction.ethernet.cosDepth5

       Possibilities:
               unchanged   (256)"
   ::= {er1645v2TvTmplCiGreEntry 150095104}

er1645v2TvTmplCiGreBandwidthActCirActEthDei5 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth5

       Possibilities:
               unchanged   (255)
               clear   (0)
               set   (1)"
   ::= {er1645v2TvTmplCiGreEntry 150100224}

er1645v2TvTmplCiGreBandwidthActCirActEthCos6 OBJECT-TYPE
   SYNTAX      INTEGER
               {
               unchanged (256)
               }
   MAX-ACCESS  read-write
   STATUS      current
   DESCRIPTION
      "Path: tunnels.editConf.ipsecGreTunnels.bandwidth.action.cirAction.ethernet.cosDepth6

       Possibilities:
               unchanged   (256)"
   ::= {er1645v2TvTmplCiGreEntry 150095360}

er1645v2TvTmplCiGreBandwidthActCirActEthDei6 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth6

       Possibilities:
               unchanged   (255)
               clear   (0)
               set   (1)"
   ::= {er1645v2TvTmplCiGreEntry 150100480}

er1645v2TvTmplCiGreBandwidthActCirActEthCos7 OBJECT-TYPE
   SYNTAX      INTEGER
               {
               unchanged (256)
               }
   MAX-ACCESS  read-write
   STATUS      current
   DESCRIPTION
      "Path: tunnels.editConf.ipsecGreTunnels.bandwidth.action.cirAction.ethernet.cosDepth7

       Possibilities:
               unchanged   (256)"
   ::= {er1645v2TvTmplCiGreEntry 150095616}

er1645v2TvTmplCiGreBandwidthActCirActEthDei7 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth7

       Possibilities:
               unchanged   (255)
               clear   (0)
               set   (1)"
   ::= {er1645v2TvTmplCiGreEntry 150100736}

er1645v2TvTmplCiGreBandwidthActCirActEthCos8 OBJECT-TYPE
   SYNTAX      INTEGER
               {
               unchanged (256)
               }
   MAX-ACCESS  read-write
   STATUS      current
   DESCRIPTION
      "Path: tunnels.editConf.ipsecGreTunnels.bandwidth.action.cirAction.ethernet.cosDepth8

       Possibilities:
               unchanged   (256)"
   ::= {er1645v2TvTmplCiGreEntry 150095872}

er1645v2TvTmplCiGreBandwidthActCirActEthDei8 OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deiDepth8

       Possibilities:
               unchanged   (255)
               clear   (0)
               set   (1)"
   ::= {er1645v2TvTmplCiGreEntry 150100992}

er1645v2TvTmplCiGreBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCiGreEntry 150096128}

er1645v2TvTmplCiGreBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCiGreEntry 150096384}

er1645v2TvTmplCiGreBandwidthActCirActEthDrpLev OBJECT-TYPE
   SYNTAX      INTEGER
               {
               unchanged (0)
               }
   MAX-ACCESS  read-write
   STATUS      current
   DESCRIPTION
      "Path: tunnels.editConf.ipsecGreTunnels.bandwidth.action.cirAction.ethernet.dropLevel

       Possibilities:
               unchanged   (0)"
   ::= {er1645v2TvTmplCiGreEntry 150096640}

er1645v2TvTmplCiGreBandwidthActCirActEthDeFlag OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ethernet.deFlag

       Possibilities:
               unchanged   (255)
               clear   (0)
               set   (1)"
   ::= {er1645v2TvTmplCiGreEntry 150097408}

er1645v2TvTmplCiGreBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCiGreEntry 150120704}

er1645v2TvTmplCiGreBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCiGreEntry 150120960}

er1645v2TvTmplCiGreBandwidthActCirActIpDrpLev OBJECT-TYPE
   SYNTAX      INTEGER
               {
               unchanged (0)
               }
   MAX-ACCESS  read-write
   STATUS      current
   DESCRIPTION
      "Path: tunnels.editConf.ipsecGreTunnels.bandwidth.action.cirAction.ip.dropLevel

       Possibilities:
               unchanged   (0)"
   ::= {er1645v2TvTmplCiGreEntry 150121216}

er1645v2TvTmplCiGreBandwidthActCirActIpDeFlag OBJECT-TYPE
   SYNTAX      INTEGER
               {
               unchanged (255),
               clear (0),
               set (1)
               }
   MAX-ACCESS  read-write
   STATUS      current
   DESCRIPTION
      "Path: tunnels.editConf.ipsecGreTunnels.bandwidth.action.cirAction.ip.deFlag

       Possibilities:
               unchanged   (255)
               clear   (0)
               set   (1)"
   ::= {er1645v2TvTmplCiGreEntry 150121984}

er1645v2TvTmplCiGreBandwidthActEirActNone OBJECT-TYPE
   SYNTAX      OCTET STRING
   MAX-ACCESS  read-write
   STATUS      current
   DESCRIPTION
      "Path: tunnels.editConf.ipsecGreTunnels.bandwidth.action.eirAction.none"
   ::= {er1645v2TvTmplCiGreEntry 150216704}

er1645v2TvTmplCiGreBandwidthActEirActEthCos1 OBJECT-TYPE
   SYNTAX      INTEGER
               {
               unchanged (256)
               }
   MAX-ACCESS  read-write
   STATUS      current
   DESCRIPTION
      "Path: tunnels.editConf.ipsecGreTunnels.bandwidth.action.eirAction.ethernet.cosDepth1

       Possibilities:
               unchanged   (256)"
   ::= {er1645v2TvTmplCiGreEntry 150225152}

er1645v2TvTmplCiGreBandwidthActEirActEthDei1 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth1

       Possibilities:
               unchanged   (255)
               clear   (0)
               set   (1)"
   ::= {er1645v2TvTmplCiGreEntry 150230272}

er1645v2TvTmplCiGreBandwidthActEirActEthCos2 OBJECT-TYPE
   SYNTAX      INTEGER
               {
               unchanged (256)
               }
   MAX-ACCESS  read-write
   STATUS      current
   DESCRIPTION
      "Path: tunnels.editConf.ipsecGreTunnels.bandwidth.action.eirAction.ethernet.cosDepth2

       Possibilities:
               unchanged   (256)"
   ::= {er1645v2TvTmplCiGreEntry 150225408}

er1645v2TvTmplCiGreBandwidthActEirActEthDei2 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth2

       Possibilities:
               unchanged   (255)
               clear   (0)
               set   (1)"
   ::= {er1645v2TvTmplCiGreEntry 150230528}

er1645v2TvTmplCiGreBandwidthActEirActEthCos3 OBJECT-TYPE
   SYNTAX      INTEGER
               {
               unchanged (256)
               }
   MAX-ACCESS  read-write
   STATUS      current
   DESCRIPTION
      "Path: tunnels.editConf.ipsecGreTunnels.bandwidth.action.eirAction.ethernet.cosDepth3

       Possibilities:
               unchanged   (256)"
   ::= {er1645v2TvTmplCiGreEntry 150225664}

er1645v2TvTmplCiGreBandwidthActEirActEthDei3 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth3

       Possibilities:
               unchanged   (255)
               clear   (0)
               set   (1)"
   ::= {er1645v2TvTmplCiGreEntry 150230784}

er1645v2TvTmplCiGreBandwidthActEirActEthCos4 OBJECT-TYPE
   SYNTAX      INTEGER
               {
               unchanged (256)
               }
   MAX-ACCESS  read-write
   STATUS      current
   DESCRIPTION
      "Path: tunnels.editConf.ipsecGreTunnels.bandwidth.action.eirAction.ethernet.cosDepth4

       Possibilities:
               unchanged   (256)"
   ::= {er1645v2TvTmplCiGreEntry 150225920}

er1645v2TvTmplCiGreBandwidthActEirActEthDei4 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth4

       Possibilities:
               unchanged   (255)
               clear   (0)
               set   (1)"
   ::= {er1645v2TvTmplCiGreEntry 150231040}

er1645v2TvTmplCiGreBandwidthActEirActEthCos5 OBJECT-TYPE
   SYNTAX      INTEGER
               {
               unchanged (256)
               }
   MAX-ACCESS  read-write
   STATUS      current
   DESCRIPTION
      "Path: tunnels.editConf.ipsecGreTunnels.bandwidth.action.eirAction.ethernet.cosDepth5

       Possibilities:
               unchanged   (256)"
   ::= {er1645v2TvTmplCiGreEntry 150226176}

er1645v2TvTmplCiGreBandwidthActEirActEthDei5 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth5

       Possibilities:
               unchanged   (255)
               clear   (0)
               set   (1)"
   ::= {er1645v2TvTmplCiGreEntry 150231296}

er1645v2TvTmplCiGreBandwidthActEirActEthCos6 OBJECT-TYPE
   SYNTAX      INTEGER
               {
               unchanged (256)
               }
   MAX-ACCESS  read-write
   STATUS      current
   DESCRIPTION
      "Path: tunnels.editConf.ipsecGreTunnels.bandwidth.action.eirAction.ethernet.cosDepth6

       Possibilities:
               unchanged   (256)"
   ::= {er1645v2TvTmplCiGreEntry 150226432}

er1645v2TvTmplCiGreBandwidthActEirActEthDei6 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth6

       Possibilities:
               unchanged   (255)
               clear   (0)
               set   (1)"
   ::= {er1645v2TvTmplCiGreEntry 150231552}

er1645v2TvTmplCiGreBandwidthActEirActEthCos7 OBJECT-TYPE
   SYNTAX      INTEGER
               {
               unchanged (256)
               }
   MAX-ACCESS  read-write
   STATUS      current
   DESCRIPTION
      "Path: tunnels.editConf.ipsecGreTunnels.bandwidth.action.eirAction.ethernet.cosDepth7

       Possibilities:
               unchanged   (256)"
   ::= {er1645v2TvTmplCiGreEntry 150226688}

er1645v2TvTmplCiGreBandwidthActEirActEthDei7 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth7

       Possibilities:
               unchanged   (255)
               clear   (0)
               set   (1)"
   ::= {er1645v2TvTmplCiGreEntry 150231808}

er1645v2TvTmplCiGreBandwidthActEirActEthCos8 OBJECT-TYPE
   SYNTAX      INTEGER
               {
               unchanged (256)
               }
   MAX-ACCESS  read-write
   STATUS      current
   DESCRIPTION
      "Path: tunnels.editConf.ipsecGreTunnels.bandwidth.action.eirAction.ethernet.cosDepth8

       Possibilities:
               unchanged   (256)"
   ::= {er1645v2TvTmplCiGreEntry 150226944}

er1645v2TvTmplCiGreBandwidthActEirActEthDei8 OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deiDepth8

       Possibilities:
               unchanged   (255)
               clear   (0)
               set   (1)"
   ::= {er1645v2TvTmplCiGreEntry 150232064}

er1645v2TvTmplCiGreBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCiGreEntry 150227200}

er1645v2TvTmplCiGreBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCiGreEntry 150227456}

er1645v2TvTmplCiGreBandwidthActEirActEthDrpLev OBJECT-TYPE
   SYNTAX      INTEGER
               {
               unchanged (0)
               }
   MAX-ACCESS  read-write
   STATUS      current
   DESCRIPTION
      "Path: tunnels.editConf.ipsecGreTunnels.bandwidth.action.eirAction.ethernet.dropLevel

       Possibilities:
               unchanged   (0)"
   ::= {er1645v2TvTmplCiGreEntry 150227712}

er1645v2TvTmplCiGreBandwidthActEirActEthDeFlag OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ethernet.deFlag

       Possibilities:
               unchanged   (255)
               clear   (0)
               set   (1)"
   ::= {er1645v2TvTmplCiGreEntry 150228480}

er1645v2TvTmplCiGreBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCiGreEntry 150251776}

er1645v2TvTmplCiGreBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCiGreEntry 150252032}

er1645v2TvTmplCiGreBandwidthActEirActIpDrpLev OBJECT-TYPE
   SYNTAX      INTEGER
               {
               unchanged (0)
               }
   MAX-ACCESS  read-write
   STATUS      current
   DESCRIPTION
      "Path: tunnels.editConf.ipsecGreTunnels.bandwidth.action.eirAction.ip.dropLevel

       Possibilities:
               unchanged   (0)"
   ::= {er1645v2TvTmplCiGreEntry 150252288}

er1645v2TvTmplCiGreBandwidthActEirActIpDeFlag OBJECT-TYPE
   SYNTAX      INTEGER
               {
               unchanged (255),
               clear (0),
               set (1)
               }
   MAX-ACCESS  read-write
   STATUS      current
   DESCRIPTION
      "Path: tunnels.editConf.ipsecGreTunnels.bandwidth.action.eirAction.ip.deFlag

       Possibilities:
               unchanged   (255)
               clear   (0)
               set   (1)"
   ::= {er1645v2TvTmplCiGreEntry 150253056}

er1645v2TvTmplCiGreBandwidthActViolActNone OBJECT-TYPE
   SYNTAX      OCTET STRING
   MAX-ACCESS  read-write
   STATUS      current
   DESCRIPTION
      "Path: tunnels.editConf.ipsecGreTunnels.bandwidth.action.violateAction.none"
   ::= {er1645v2TvTmplCiGreEntry 150347776}

er1645v2TvTmplCiGreBandwidthActViolActDrop OBJECT-TYPE
   SYNTAX      OCTET STRING
   MAX-ACCESS  read-write
   STATUS      current
   DESCRIPTION
      "Path: tunnels.editConf.ipsecGreTunnels.bandwidth.action.violateAction.drop"
   ::= {er1645v2TvTmplCiGreEntry 150364160}

er1645v2TvTmplCiGreBandwidthActViolActEthCos1 OBJECT-TYPE
   SYNTAX      INTEGER
               {
               unchanged (256)
               }
   MAX-ACCESS  read-write
   STATUS      current
   DESCRIPTION
      "Path: tunnels.editConf.ipsecGreTunnels.bandwidth.action.violateAction.ethernet.cosDepth1

       Possibilities:
               unchanged   (256)"
   ::= {er1645v2TvTmplCiGreEntry 150356224}

er1645v2TvTmplCiGreBandwidthActViolActEthDei1 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth1

       Possibilities:
               unchanged   (255)
               clear   (0)
               set   (1)"
   ::= {er1645v2TvTmplCiGreEntry 150361344}

er1645v2TvTmplCiGreBandwidthActViolActEthCos2 OBJECT-TYPE
   SYNTAX      INTEGER
               {
               unchanged (256)
               }
   MAX-ACCESS  read-write
   STATUS      current
   DESCRIPTION
      "Path: tunnels.editConf.ipsecGreTunnels.bandwidth.action.violateAction.ethernet.cosDepth2

       Possibilities:
               unchanged   (256)"
   ::= {er1645v2TvTmplCiGreEntry 150356480}

er1645v2TvTmplCiGreBandwidthActViolActEthDei2 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth2

       Possibilities:
               unchanged   (255)
               clear   (0)
               set   (1)"
   ::= {er1645v2TvTmplCiGreEntry 150361600}

er1645v2TvTmplCiGreBandwidthActViolActEthCos3 OBJECT-TYPE
   SYNTAX      INTEGER
               {
               unchanged (256)
               }
   MAX-ACCESS  read-write
   STATUS      current
   DESCRIPTION
      "Path: tunnels.editConf.ipsecGreTunnels.bandwidth.action.violateAction.ethernet.cosDepth3

       Possibilities:
               unchanged   (256)"
   ::= {er1645v2TvTmplCiGreEntry 150356736}

er1645v2TvTmplCiGreBandwidthActViolActEthDei3 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth3

       Possibilities:
               unchanged   (255)
               clear   (0)
               set   (1)"
   ::= {er1645v2TvTmplCiGreEntry 150361856}

er1645v2TvTmplCiGreBandwidthActViolActEthCos4 OBJECT-TYPE
   SYNTAX      INTEGER
               {
               unchanged (256)
               }
   MAX-ACCESS  read-write
   STATUS      current
   DESCRIPTION
      "Path: tunnels.editConf.ipsecGreTunnels.bandwidth.action.violateAction.ethernet.cosDepth4

       Possibilities:
               unchanged   (256)"
   ::= {er1645v2TvTmplCiGreEntry 150356992}

er1645v2TvTmplCiGreBandwidthActViolActEthDei4 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth4

       Possibilities:
               unchanged   (255)
               clear   (0)
               set   (1)"
   ::= {er1645v2TvTmplCiGreEntry 150362112}

er1645v2TvTmplCiGreBandwidthActViolActEthCos5 OBJECT-TYPE
   SYNTAX      INTEGER
               {
               unchanged (256)
               }
   MAX-ACCESS  read-write
   STATUS      current
   DESCRIPTION
      "Path: tunnels.editConf.ipsecGreTunnels.bandwidth.action.violateAction.ethernet.cosDepth5

       Possibilities:
               unchanged   (256)"
   ::= {er1645v2TvTmplCiGreEntry 150357248}

er1645v2TvTmplCiGreBandwidthActViolActEthDei5 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth5

       Possibilities:
               unchanged   (255)
               clear   (0)
               set   (1)"
   ::= {er1645v2TvTmplCiGreEntry 150362368}

er1645v2TvTmplCiGreBandwidthActViolActEthCos6 OBJECT-TYPE
   SYNTAX      INTEGER
               {
               unchanged (256)
               }
   MAX-ACCESS  read-write
   STATUS      current
   DESCRIPTION
      "Path: tunnels.editConf.ipsecGreTunnels.bandwidth.action.violateAction.ethernet.cosDepth6

       Possibilities:
               unchanged   (256)"
   ::= {er1645v2TvTmplCiGreEntry 150357504}

er1645v2TvTmplCiGreBandwidthActViolActEthDei6 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth6

       Possibilities:
               unchanged   (255)
               clear   (0)
               set   (1)"
   ::= {er1645v2TvTmplCiGreEntry 150362624}

er1645v2TvTmplCiGreBandwidthActViolActEthCos7 OBJECT-TYPE
   SYNTAX      INTEGER
               {
               unchanged (256)
               }
   MAX-ACCESS  read-write
   STATUS      current
   DESCRIPTION
      "Path: tunnels.editConf.ipsecGreTunnels.bandwidth.action.violateAction.ethernet.cosDepth7

       Possibilities:
               unchanged   (256)"
   ::= {er1645v2TvTmplCiGreEntry 150357760}

er1645v2TvTmplCiGreBandwidthActViolActEthDei7 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth7

       Possibilities:
               unchanged   (255)
               clear   (0)
               set   (1)"
   ::= {er1645v2TvTmplCiGreEntry 150362880}

er1645v2TvTmplCiGreBandwidthActViolActEthCos8 OBJECT-TYPE
   SYNTAX      INTEGER
               {
               unchanged (256)
               }
   MAX-ACCESS  read-write
   STATUS      current
   DESCRIPTION
      "Path: tunnels.editConf.ipsecGreTunnels.bandwidth.action.violateAction.ethernet.cosDepth8

       Possibilities:
               unchanged   (256)"
   ::= {er1645v2TvTmplCiGreEntry 150358016}

er1645v2TvTmplCiGreBandwidthActViolActEthDei8 OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deiDepth8

       Possibilities:
               unchanged   (255)
               clear   (0)
               set   (1)"
   ::= {er1645v2TvTmplCiGreEntry 150363136}

er1645v2TvTmplCiGreBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCiGreEntry 150358272}

er1645v2TvTmplCiGreBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCiGreEntry 150358528}

er1645v2TvTmplCiGreBandwidthActViolActEthDrpLev OBJECT-TYPE
   SYNTAX      INTEGER
               {
               unchanged (0)
               }
   MAX-ACCESS  read-write
   STATUS      current
   DESCRIPTION
      "Path: tunnels.editConf.ipsecGreTunnels.bandwidth.action.violateAction.ethernet.dropLevel

       Possibilities:
               unchanged   (0)"
   ::= {er1645v2TvTmplCiGreEntry 150358784}

er1645v2TvTmplCiGreBandwidthActViolActEthDeFlag OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ethernet.deFlag

       Possibilities:
               unchanged   (255)
               clear   (0)
               set   (1)"
   ::= {er1645v2TvTmplCiGreEntry 150359552}

er1645v2TvTmplCiGreBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.ipsecGreTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCiGreEntry 150382848}

er1645v2TvTmplCiGreBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.ipsecGreTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCiGreEntry 150383104}

er1645v2TvTmplCiGreBandwidthActViolActIpDrpLev OBJECT-TYPE
   SYNTAX      INTEGER
               {
               unchanged (0)
               }
   MAX-ACCESS  read-write
   STATUS      current
   DESCRIPTION
      "Path: tunnels.editConf.ipsecGreTunnels.bandwidth.action.violateAction.ip.dropLevel

       Possibilities:
               unchanged   (0)"
   ::= {er1645v2TvTmplCiGreEntry 150383360}

er1645v2TvTmplCiGreBandwidthActViolActIpDeFlag OBJECT-TYPE
   SYNTAX      INTEGER
               {
               unchanged (255),
               clear (0),
               set (1)
               }
   MAX-ACCESS  read-write
   STATUS      current
   DESCRIPTION
      "Path: tunnels.editConf.ipsecGreTunnels.bandwidth.action.violateAction.ip.deFlag

       Possibilities:
               unchanged   (255)
               clear   (0)
               set   (1)"
   ::= {er1645v2TvTmplCiGreEntry 150384128}

er1645v2TvTmplCiGreBrVlTVlans OBJECT-TYPE
   SYNTAX      SEQUENCE OF Er1645v2TvTmplCiGreBrVlTVlansEntry
   MAX-ACCESS  not-accessible
   STATUS      current
   DESCRIPTION
      ""
   ::= {er1645v2TvTmplCiGre 459079680}

er1645v2TvTmplCiGreBrVlTVlansEntry OBJECT-TYPE
   SYNTAX      Er1645v2TvTmplCiGreBrVlTVlansEntry
   MAX-ACCESS  not-accessible
   STATUS      current
   DESCRIPTION
      ""
   INDEX      { er1645v2TvTmplCiGreTableIx,
                er1645v2TvTmplCiGreBrVlTVlansTableIx }
   ::= {er1645v2TvTmplCiGreBrVlTVlans 1}

Er1645v2TvTmplCiGreBrVlTVlansEntry ::=
   SEQUENCE
      {
      er1645v2TvTmplCiGreBrVlTVlansActions
         VariableLengthTableActions,
      er1645v2TvTmplCiGreBrVlTVlansTableIx
         TableIndex,
      er1645v2TvTmplCiGreBrVlTVlansVid
         Integer32,
      er1645v2TvTmplCiGreBrVlTVlansEndVid
         Integer32,
      er1645v2TvTmplCiGreBrVlTVlansAction
         INTEGER,
      er1645v2TvTmplCiGreBrVlTVlansTagInfoTpid
         INTEGER,
      er1645v2TvTmplCiGreBrVlTVlansTagInfoVid
         Integer32
      }

er1645v2TvTmplCiGreBrVlTVlansActions OBJECT-TYPE
   SYNTAX      VariableLengthTableActions
   MAX-ACCESS  read-write
   STATUS      current
   DESCRIPTION
      "By way of this field, some manipulations
       on this table may be performed."
   ::= {er1645v2TvTmplCiGreBrVlTVlansEntry 2}

er1645v2TvTmplCiGreBrVlTVlansTableIx OBJECT-TYPE
   SYNTAX      TableIndex
   MAX-ACCESS  not-accessible
   STATUS      current
   DESCRIPTION
      ""
   ::= {er1645v2TvTmplCiGreBrVlTVlansEntry 11}

er1645v2TvTmplCiGreBrVlTVlansVid OBJECT-TYPE
   SYNTAX      Integer32
   MAX-ACCESS  read-write
   STATUS      current
   DESCRIPTION
      "Path: tunnels.editConf.ipsecGreTunnels.bridging.vlanTagging.vlans.vid"
   ::= {er1645v2TvTmplCiGreBrVlTVlansEntry 536870912}

er1645v2TvTmplCiGreBrVlTVlansEndVid OBJECT-TYPE
   SYNTAX      Integer32
   MAX-ACCESS  read-write
   STATUS      current
   DESCRIPTION
      "Path: tunnels.editConf.ipsecGreTunnels.bridging.vlanTagging.vlans.endVid"
   ::= {er1645v2TvTmplCiGreBrVlTVlansEntry 2147483648}

er1645v2TvTmplCiGreBrVlTVlansAction OBJECT-TYPE
   SYNTAX      INTEGER
               {
               discard (0),
               accept (1),
               tag (2)
               }
   MAX-ACCESS  read-write
   STATUS      current
   DESCRIPTION
      "Path: tunnels.editConf.ipsecGreTunnels.bridging.vlanTagging.vlans.action

       Possibilities:
               discard   (0)
               accept   (1)
               tag   (2)"
   ::= {er1645v2TvTmplCiGreBrVlTVlansEntry 1073741824}

er1645v2TvTmplCiGreBrVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.ipsecGreTunnels.bridging.vlanTagging.vlans.tagInfo.tpid

       Possibilities:
               dot1Q   (33024)
               dot1ad   (34984)
               0x9100   (37120)
               0x9200   (37376)
               0x9300   (37632)"
   ::= {er1645v2TvTmplCiGreBrVlTVlansEntry 1677721600}

er1645v2TvTmplCiGreBrVlTVlansTagInfoVid OBJECT-TYPE
   SYNTAX      Integer32
   MAX-ACCESS  read-write
   STATUS      current
   DESCRIPTION
      "Path: tunnels.editConf.ipsecGreTunnels.bridging.vlanTagging.vlans.tagInfo.vid"
   ::= {er1645v2TvTmplCiGreBrVlTVlansEntry 1744830464}


er1645v2TvTmplIpsTun OBJECT IDENTIFIER ::= {er1645v2TvTmpl 10}

er1645v2TvTmplIpsTunSSCTable OBJECT-TYPE
   SYNTAX      SEQUENCE OF Er1645v2TvTmplIpsTunEntry
   MAX-ACCESS  not-accessible
   STATUS      current
   DESCRIPTION
      ""
   ::= {er1645v2TvTmplIpsTun 1}

er1645v2TvTmplIpsTunEntry OBJECT-TYPE
   SYNTAX      Er1645v2TvTmplIpsTunEntry
   MAX-ACCESS  not-accessible
   STATUS      current
   DESCRIPTION
      ""
   INDEX      { er1645v2TvTmplIpsTunTableIx }
   ::= {er1645v2TvTmplIpsTunSSCTable 1}

Er1645v2TvTmplIpsTunEntry ::=
   SEQUENCE
      {
      er1645v2TvTmplIpsTunActions
         VariableLengthTableActions,
      er1645v2TvTmplIpsTunTableIx
         TableIndex,
      er1645v2TvTmplIpsTunName
         DisplayString,
      er1645v2TvTmplIpsTunRemark
         DisplayString,
      er1645v2TvTmplIpsTunAdminStatus
         INTEGER,
      er1645v2TvTmplIpsTunLocalIpAddress
         IpAddress,
      er1645v2TvTmplIpsTunLocalInterface
         DisplayString,
      er1645v2TvTmplIpsTunRemoteIpAddress
         IpAddress,
      er1645v2TvTmplIpsTunRemoteDnsName
         DisplayString,
      er1645v2TvTmplIpsTunIpsecFdx
         DisplayString,
      er1645v2TvTmplIpsTunIpsecHdxIn
         DisplayString,
      er1645v2TvTmplIpsTunIpsecHdxOut
         DisplayString,
      er1645v2TvTmplIpsTunIpsecPsCfg
         DisplayString,
      er1645v2TvTmplIpsTunIpsecPsLIdIp
         IpAddress,
      er1645v2TvTmplIpsTunIpsecPsLIdHn
         DisplayString,
      er1645v2TvTmplIpsTunIpsecPsLIdUn
         DisplayString,
      er1645v2TvTmplIpsTunIpsecPsRIdIp
         IpAddress,
      er1645v2TvTmplIpsTunIpsecPsRIdHn
         DisplayString,
      er1645v2TvTmplIpsTunIpsecPsRIdUn
         DisplayString,
      er1645v2TvTmplIpsTunIpsecPsKey
         DisplayString,
      er1645v2TvTmplIpsTunIpsecPsEncMKey
         INTEGER,
      er1645v2TvTmplIpsTunIpsecPsEncKey
         DisplayString,
      er1645v2TvTmplIpsTunIpsecPsPIdProt
         INTEGER,
      er1645v2TvTmplIpsTunIpsecPsPIdLocAddr
         IpAddress,
      er1645v2TvTmplIpsTunIpsecPsPIdLocMask
         IpAddress,
      er1645v2TvTmplIpsTunIpsecPsPIdLocPort
         INTEGER,
      er1645v2TvTmplIpsTunIpsecPsPIdRemAddr
         IpAddress,
      er1645v2TvTmplIpsTunIpsecPsPIdRemMask
         IpAddress,
      er1645v2TvTmplIpsTunIpsecPsPIdRemPort
         INTEGER,
      er1645v2TvTmplIpsTunIpsecCeCfg
         DisplayString,
      er1645v2TvTmplIpsTunIpsecCeLIdIp
         IpAddress,
      er1645v2TvTmplIpsTunIpsecCeLIdHn
         DisplayString,
      er1645v2TvTmplIpsTunIpsecCeLIdUn
         DisplayString,
      er1645v2TvTmplIpsTunIpsecCeLIdDn
         DisplayString,
      er1645v2TvTmplIpsTunIpsecCeRIdIp
         IpAddress,
      er1645v2TvTmplIpsTunIpsecCeRIdHn
         DisplayString,
      er1645v2TvTmplIpsTunIpsecCeRIdUn
         DisplayString,
      er1645v2TvTmplIpsTunIpsecCeRIdDn
         DisplayString,
      er1645v2TvTmplIpsTunIpsecCePIdProt
         INTEGER,
      er1645v2TvTmplIpsTunIpsecCePIdLocAddr
         IpAddress,
      er1645v2TvTmplIpsTunIpsecCePIdLocMask
         IpAddress,
      er1645v2TvTmplIpsTunIpsecCePIdLocPort
         INTEGER,
      er1645v2TvTmplIpsTunIpsecCePIdRemAddr
         IpAddress,
      er1645v2TvTmplIpsTunIpsecCePIdRemMask
         IpAddress,
      er1645v2TvTmplIpsTunIpsecCePIdRemPort
         INTEGER,
      er1645v2TvTmplIpsTunType
         INTEGER,
      er1645v2TvTmplIpsTunNoTraffTO
         TimeTicks,
      er1645v2TvTmplIpsTunNoTraffDi
         INTEGER,
      er1645v2TvTmplIpsTunRemRouteDefRt
         INTEGER,
      er1645v2TvTmplIpsTunTos
         INTEGER,
      er1645v2TvTmplIpsTunQueueTosMapQueue1
         INTEGER,
      er1645v2TvTmplIpsTunQueueTosMapQueue2
         INTEGER,
      er1645v2TvTmplIpsTunQueueTosMapQueue3
         INTEGER,
      er1645v2TvTmplIpsTunQueueTosMapQueue4
         INTEGER,
      er1645v2TvTmplIpsTunQueueTosMapQueue5
         INTEGER,
      er1645v2TvTmplIpsTunQueueTosMapLowDelayQueue
         INTEGER,
      er1645v2TvTmplIpsTunQueueTosMapLowDelay2Queue
         INTEGER,
      er1645v2TvTmplIpsTunQueueTosMapSystemQueue
         INTEGER,
      er1645v2TvTmplIpsTunDf
         INTEGER,
      er1645v2TvTmplIpsTunMtu
         Integer32
      }

er1645v2TvTmplIpsTunActions OBJECT-TYPE
   SYNTAX      VariableLengthTableActions
   MAX-ACCESS  read-write
   STATUS      current
   DESCRIPTION
      "By way of this field, some manipulations
       on this table may be performed."
   ::= {er1645v2TvTmplIpsTunEntry 2}

er1645v2TvTmplIpsTunTableIx OBJECT-TYPE
   SYNTAX      TableIndex
   MAX-ACCESS  not-accessible
   STATUS      current
   DESCRIPTION
      ""
   ::= {er1645v2TvTmplIpsTunEntry 11}

er1645v2TvTmplIpsTunName OBJECT-TYPE
   SYNTAX      DisplayString
   MAX-ACCESS  read-write
   STATUS      current
   DESCRIPTION
      "Path: tunnels.editConf.ipsecTunnels.name"
   ::= {er1645v2TvTmplIpsTunEntry 16777216}

er1645v2TvTmplIpsTunRemark OBJECT-TYPE
   SYNTAX      DisplayString
   MAX-ACCESS  read-write
   STATUS      current
   DESCRIPTION
      "Path: tunnels.editConf.ipsecTunnels.remark"
   ::= {er1645v2TvTmplIpsTunEntry 1157627904}

er1645v2TvTmplIpsTunAdminStatus OBJECT-TYPE
   SYNTAX      INTEGER
               {
               up (1),
               down (2)
               }
   MAX-ACCESS  read-write
   STATUS      current
   DESCRIPTION
      "Path: tunnels.editConf.ipsecTunnels.adminStatus

       Possibilities:
               up   (1)
               down   (2)"
   ::= {er1645v2TvTmplIpsTunEntry 218103808}

er1645v2TvTmplIpsTunLocalIpAddress OBJECT-TYPE
   SYNTAX      IpAddress
   MAX-ACCESS  read-write
   STATUS      current
   DESCRIPTION
      "Path: tunnels.editConf.ipsecTunnels.localIpAddress"
   ::= {er1645v2TvTmplIpsTunEntry 33554432}

er1645v2TvTmplIpsTunLocalInterface OBJECT-TYPE
   SYNTAX      DisplayString
   MAX-ACCESS  read-write
   STATUS      current
   DESCRIPTION
      "Path: tunnels.editConf.ipsecTunnels.localInterface"
   ::= {er1645v2TvTmplIpsTunEntry 201326592}

er1645v2TvTmplIpsTunRemoteIpAddress OBJECT-TYPE
   SYNTAX      IpAddress
   MAX-ACCESS  read-write
   STATUS      current
   DESCRIPTION
      "Path: tunnels.editConf.ipsecTunnels.remoteIpAddress"
   ::= {er1645v2TvTmplIpsTunEntry 50331648}

er1645v2TvTmplIpsTunRemoteDnsName OBJECT-TYPE
   SYNTAX      DisplayString
   MAX-ACCESS  read-write
   STATUS      current
   DESCRIPTION
      "Path: tunnels.editConf.ipsecTunnels.remoteDnsName"
   ::= {er1645v2TvTmplIpsTunEntry 67108864}

er1645v2TvTmplIpsTunIpsecFdx OBJECT-TYPE
   SYNTAX      DisplayString
   MAX-ACCESS  read-write
   STATUS      current
   DESCRIPTION
      "Path: tunnels.editConf.ipsecTunnels.ipsec.fdxManualSA"
   ::= {er1645v2TvTmplIpsTunEntry 85983232}

er1645v2TvTmplIpsTunIpsecHdxIn OBJECT-TYPE
   SYNTAX      DisplayString
   MAX-ACCESS  read-write
   STATUS      current
   DESCRIPTION
      "Path: tunnels.editConf.ipsecTunnels.ipsec.hdxManualSA.inbound"
   ::= {er1645v2TvTmplIpsTunEntry 88088576}

er1645v2TvTmplIpsTunIpsecHdxOut OBJECT-TYPE
   SYNTAX      DisplayString
   MAX-ACCESS  read-write
   STATUS      current
   DESCRIPTION
      "Path: tunnels.editConf.ipsecTunnels.ipsec.hdxManualSA.outbound"
   ::= {er1645v2TvTmplIpsTunEntry 88096768}

er1645v2TvTmplIpsTunIpsecPsCfg OBJECT-TYPE
   SYNTAX      DisplayString
   MAX-ACCESS  read-write
   STATUS      current
   DESCRIPTION
      "Path: tunnels.editConf.ipsecTunnels.ipsec.ikePresharedSA.ikeSA"
   ::= {er1645v2TvTmplIpsTunEntry 90439680}

er1645v2TvTmplIpsTunIpsecPsLIdIp OBJECT-TYPE
   SYNTAX      IpAddress
   MAX-ACCESS  read-write
   STATUS      current
   DESCRIPTION
      "Path: tunnels.editConf.ipsecTunnels.ipsec.ikePresharedSA.localId.ipAddress"
   ::= {er1645v2TvTmplIpsTunEntry 90702848}

er1645v2TvTmplIpsTunIpsecPsLIdHn OBJECT-TYPE
   SYNTAX      DisplayString
   MAX-ACCESS  read-write
   STATUS      current
   DESCRIPTION
      "Path: tunnels.editConf.ipsecTunnels.ipsec.ikePresharedSA.localId.hostName"
   ::= {er1645v2TvTmplIpsTunEntry 90703872}

er1645v2TvTmplIpsTunIpsecPsLIdUn OBJECT-TYPE
   SYNTAX      DisplayString
   MAX-ACCESS  read-write
   STATUS      current
   DESCRIPTION
      "Path: tunnels.editConf.ipsecTunnels.ipsec.ikePresharedSA.localId.user"
   ::= {er1645v2TvTmplIpsTunEntry 90704896}

er1645v2TvTmplIpsTunIpsecPsRIdIp OBJECT-TYPE
   SYNTAX      IpAddress
   MAX-ACCESS  read-write
   STATUS      current
   DESCRIPTION
      "Path: tunnels.editConf.ipsecTunnels.ipsec.ikePresharedSA.remoteId.ipAddress"
   ::= {er1645v2TvTmplIpsTunEntry 90964992}

er1645v2TvTmplIpsTunIpsecPsRIdHn OBJECT-TYPE
   SYNTAX      DisplayString
   MAX-ACCESS  read-write
   STATUS      current
   DESCRIPTION
      "Path: tunnels.editConf.ipsecTunnels.ipsec.ikePresharedSA.remoteId.hostName"
   ::= {er1645v2TvTmplIpsTunEntry 90966016}

er1645v2TvTmplIpsTunIpsecPsRIdUn OBJECT-TYPE
   SYNTAX      DisplayString
   MAX-ACCESS  read-write
   STATUS      current
   DESCRIPTION
      "Path: tunnels.editConf.ipsecTunnels.ipsec.ikePresharedSA.remoteId.user"
   ::= {er1645v2TvTmplIpsTunEntry 90967040}

er1645v2TvTmplIpsTunIpsecPsKey OBJECT-TYPE
   SYNTAX      DisplayString
   MAX-ACCESS  read-write
   STATUS      current
   DESCRIPTION
      "Path: tunnels.editConf.ipsecTunnels.ipsec.ikePresharedSA.preSharedKey"
   ::= {er1645v2TvTmplIpsTunEntry 91226112}

er1645v2TvTmplIpsTunIpsecPsEncMKey OBJECT-TYPE
   SYNTAX      INTEGER
               {
               none (1),
               encrypt (2),
               encType1 (3),
               invalid (128)
               }
   MAX-ACCESS  read-write
   STATUS      current
   DESCRIPTION
      "Path: tunnels.editConf.ipsecTunnels.ipsec.ikePresharedSA.encModePreSharedKey

       Possibilities:
               none   (1)
               encrypt   (2)
               encType1   (3)
               invalid   (128)"
   ::= {er1645v2TvTmplIpsTunEntry 91750400}

er1645v2TvTmplIpsTunIpsecPsEncKey OBJECT-TYPE
   SYNTAX      DisplayString
   MAX-ACCESS  read-write
   STATUS      current
   DESCRIPTION
      "Path: tunnels.editConf.ipsecTunnels.ipsec.ikePresharedSA.encPreSharedKey"
   ::= {er1645v2TvTmplIpsTunEntry 92012544}

er1645v2TvTmplIpsTunIpsecPsPIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecTunnels.ipsec.ikePresharedSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TvTmplIpsTunEntry 91504640}

er1645v2TvTmplIpsTunIpsecPsPIdLocAddr OBJECT-TYPE
   SYNTAX      IpAddress
   MAX-ACCESS  read-write
   STATUS      current
   DESCRIPTION
      "Path: tunnels.editConf.ipsecTunnels.ipsec.ikePresharedSA.proxyId.localIpAddress"
   ::= {er1645v2TvTmplIpsTunEntry 91521024}

er1645v2TvTmplIpsTunIpsecPsPIdLocMask OBJECT-TYPE
   SYNTAX      IpAddress
   MAX-ACCESS  read-write
   STATUS      current
   DESCRIPTION
      "Path: tunnels.editConf.ipsecTunnels.ipsec.ikePresharedSA.proxyId.localIpMask"
   ::= {er1645v2TvTmplIpsTunEntry 91537408}

er1645v2TvTmplIpsTunIpsecPsPIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikePresharedSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIpsTunEntry 91553792}

er1645v2TvTmplIpsTunIpsecPsPIdRemAddr OBJECT-TYPE
   SYNTAX      IpAddress
   MAX-ACCESS  read-write
   STATUS      current
   DESCRIPTION
      "Path: tunnels.editConf.ipsecTunnels.ipsec.ikePresharedSA.proxyId.remoteIpAddress"
   ::= {er1645v2TvTmplIpsTunEntry 91570176}

er1645v2TvTmplIpsTunIpsecPsPIdRemMask OBJECT-TYPE
   SYNTAX      IpAddress
   MAX-ACCESS  read-write
   STATUS      current
   DESCRIPTION
      "Path: tunnels.editConf.ipsecTunnels.ipsec.ikePresharedSA.proxyId.remoteIpMask"
   ::= {er1645v2TvTmplIpsTunEntry 91586560}

er1645v2TvTmplIpsTunIpsecPsPIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikePresharedSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIpsTunEntry 91602944}

er1645v2TvTmplIpsTunIpsecCeCfg OBJECT-TYPE
   SYNTAX      DisplayString
   MAX-ACCESS  read-write
   STATUS      current
   DESCRIPTION
      "Path: tunnels.editConf.ipsecTunnels.ipsec.ikeCertificateSA.ikeSA"
   ::= {er1645v2TvTmplIpsTunEntry 92282880}

er1645v2TvTmplIpsTunIpsecCeLIdIp OBJECT-TYPE
   SYNTAX      IpAddress
   MAX-ACCESS  read-write
   STATUS      current
   DESCRIPTION
      "Path: tunnels.editConf.ipsecTunnels.ipsec.ikeCertificateSA.localId.ipAddress"
   ::= {er1645v2TvTmplIpsTunEntry 92291104}

er1645v2TvTmplIpsTunIpsecCeLIdHn OBJECT-TYPE
   SYNTAX      DisplayString
   MAX-ACCESS  read-write
   STATUS      current
   DESCRIPTION
      "Path: tunnels.editConf.ipsecTunnels.ipsec.ikeCertificateSA.localId.hostName"
   ::= {er1645v2TvTmplIpsTunEntry 92291136}

er1645v2TvTmplIpsTunIpsecCeLIdUn OBJECT-TYPE
   SYNTAX      DisplayString
   MAX-ACCESS  read-write
   STATUS      current
   DESCRIPTION
      "Path: tunnels.editConf.ipsecTunnels.ipsec.ikeCertificateSA.localId.user"
   ::= {er1645v2TvTmplIpsTunEntry 92291168}

er1645v2TvTmplIpsTunIpsecCeLIdDn OBJECT-TYPE
   SYNTAX      DisplayString
   MAX-ACCESS  read-write
   STATUS      current
   DESCRIPTION
      "Path: tunnels.editConf.ipsecTunnels.ipsec.ikeCertificateSA.localId.derAsn1Dn"
   ::= {er1645v2TvTmplIpsTunEntry 92291200}

er1645v2TvTmplIpsTunIpsecCeRIdIp OBJECT-TYPE
   SYNTAX      IpAddress
   MAX-ACCESS  read-write
   STATUS      current
   DESCRIPTION
      "Path: tunnels.editConf.ipsecTunnels.ipsec.ikeCertificateSA.remoteId.ipAddress"
   ::= {er1645v2TvTmplIpsTunEntry 92299296}

er1645v2TvTmplIpsTunIpsecCeRIdHn OBJECT-TYPE
   SYNTAX      DisplayString
   MAX-ACCESS  read-write
   STATUS      current
   DESCRIPTION
      "Path: tunnels.editConf.ipsecTunnels.ipsec.ikeCertificateSA.remoteId.hostName"
   ::= {er1645v2TvTmplIpsTunEntry 92299328}

er1645v2TvTmplIpsTunIpsecCeRIdUn OBJECT-TYPE
   SYNTAX      DisplayString
   MAX-ACCESS  read-write
   STATUS      current
   DESCRIPTION
      "Path: tunnels.editConf.ipsecTunnels.ipsec.ikeCertificateSA.remoteId.user"
   ::= {er1645v2TvTmplIpsTunEntry 92299360}

er1645v2TvTmplIpsTunIpsecCeRIdDn OBJECT-TYPE
   SYNTAX      DisplayString
   MAX-ACCESS  read-write
   STATUS      current
   DESCRIPTION
      "Path: tunnels.editConf.ipsecTunnels.ipsec.ikeCertificateSA.remoteId.derAsn1Dn"
   ::= {er1645v2TvTmplIpsTunEntry 92299392}

er1645v2TvTmplIpsTunIpsecCePIdProt OBJECT-TYPE
   SYNTAX      INTEGER
               {
               any (0),
               aH (51),
               eGP (8),
               eSP (50),
               gRE (47),
               iCMP (1),
               iGP (9),
               iGMP (2),
               iGRP (88),
               iPinIP (4),
               oSPF (89),
               uDP (17),
               rSVP (46),
               tCP (6),
               tCPestablished (255)
               }
   MAX-ACCESS  read-write
   STATUS      current
   DESCRIPTION
      "Path: tunnels.editConf.ipsecTunnels.ipsec.ikeCertificateSA.proxyId.ipProtocol

       Possibilities:
               any   (0)
               AH   (51)
               EGP   (8)
               ESP   (50)
               GRE   (47)
               ICMP   (1)
               IGP   (9)
               IGMP   (2)
               IGRP   (88)
               IPinIP   (4)
               OSPF   (89)
               UDP   (17)
               RSVP   (46)
               TCP   (6)
               TCPestablished   (255)"
   ::= {er1645v2TvTmplIpsTunEntry 92316160}

er1645v2TvTmplIpsTunIpsecCePIdLocAddr OBJECT-TYPE
   SYNTAX      IpAddress
   MAX-ACCESS  read-write
   STATUS      current
   DESCRIPTION
      "Path: tunnels.editConf.ipsecTunnels.ipsec.ikeCertificateSA.proxyId.localIpAddress"
   ::= {er1645v2TvTmplIpsTunEntry 92316672}

er1645v2TvTmplIpsTunIpsecCePIdLocMask OBJECT-TYPE
   SYNTAX      IpAddress
   MAX-ACCESS  read-write
   STATUS      current
   DESCRIPTION
      "Path: tunnels.editConf.ipsecTunnels.ipsec.ikeCertificateSA.proxyId.localIpMask"
   ::= {er1645v2TvTmplIpsTunEntry 92317184}

er1645v2TvTmplIpsTunIpsecCePIdLocPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikeCertificateSA.proxyId.localIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIpsTunEntry 92317696}

er1645v2TvTmplIpsTunIpsecCePIdRemAddr OBJECT-TYPE
   SYNTAX      IpAddress
   MAX-ACCESS  read-write
   STATUS      current
   DESCRIPTION
      "Path: tunnels.editConf.ipsecTunnels.ipsec.ikeCertificateSA.proxyId.remoteIpAddress"
   ::= {er1645v2TvTmplIpsTunEntry 92318208}

er1645v2TvTmplIpsTunIpsecCePIdRemMask OBJECT-TYPE
   SYNTAX      IpAddress
   MAX-ACCESS  read-write
   STATUS      current
   DESCRIPTION
      "Path: tunnels.editConf.ipsecTunnels.ipsec.ikeCertificateSA.proxyId.remoteIpMask"
   ::= {er1645v2TvTmplIpsTunEntry 92318720}

er1645v2TvTmplIpsTunIpsecCePIdRemPort OBJECT-TYPE
   SYNTAX      INTEGER
               {
               any (0),
               bgp (179),
               bootpmdhcpmc (68),
               bootpmdhcpms (67),
               cpudpencap (2746),
               discard (9),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-write
   STATUS      current
   DESCRIPTION
      "Path: tunnels.editConf.ipsecTunnels.ipsec.ikeCertificateSA.proxyId.remoteIpPort

       Possibilities:
               any   (0)
               bgp   (179)
               bootp-dhcp-c   (68)
               bootp-dhcp-s   (67)
               cpudpencap   (2746)
               discard   (9)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {er1645v2TvTmplIpsTunEntry 92319232}

er1645v2TvTmplIpsTunType OBJECT-TYPE
   SYNTAX      INTEGER
               {
               outgoingDial (1),
               outgoingLeasedLine (2),
               incoming (0)
               }
   MAX-ACCESS  read-write
   STATUS      current
   DESCRIPTION
      "Path: tunnels.editConf.ipsecTunnels.type

       Possibilities:
               outgoingDial   (1)
               outgoingLeasedLine   (2)
               incoming   (0)"
   ::= {er1645v2TvTmplIpsTunEntry 134217728}

er1645v2TvTmplIpsTunNoTraffTO OBJECT-TYPE
   SYNTAX      TimeTicks
   MAX-ACCESS  read-write
   STATUS      current
   DESCRIPTION
      "Path: tunnels.editConf.ipsecTunnels.noTrafficTimeOut

       Time in centi-second."
   ::= {er1645v2TvTmplIpsTunEntry 150994944}

er1645v2TvTmplIpsTunNoTraffDi OBJECT-TYPE
   SYNTAX      INTEGER
               {
               inbound (1),
               outbound (2),
               both (3)
               }
   MAX-ACCESS  read-write
   STATUS      current
   DESCRIPTION
      "Path: tunnels.editConf.ipsecTunnels.noTrafficDirection

       Possibilities:
               inbound   (1)
               outbound   (2)
               both   (3)"
   ::= {er1645v2TvTmplIpsTunEntry 184549376}

er1645v2TvTmplIpsTunRemRouteDefRt OBJECT-TYPE
   SYNTAX      INTEGER
               {
               disabled (0),
               enabled (1)
               }
   MAX-ACCESS  read-write
   STATUS      current
   DESCRIPTION
      "Path: tunnels.editConf.ipsecTunnels.remoteRoute.useDefaultRoute

       Possibilities:
               disabled   (0)
               enabled   (1)"
   ::= {er1645v2TvTmplIpsTunEntry 167837696}

er1645v2TvTmplIpsTunTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256),
               queueTosMap (257)
               }
   MAX-ACCESS  read-write
   STATUS      current
   DESCRIPTION
      "Path: tunnels.editConf.ipsecTunnels.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)
               queueTosMap   (257)"
   ::= {er1645v2TvTmplIpsTunEntry 100663296}

er1645v2TvTmplIpsTunQueueTosMapQueue1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503382016}

er1645v2TvTmplIpsTunQueueTosMapQueue2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503447552}

er1645v2TvTmplIpsTunQueueTosMapQueue3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503513088}

er1645v2TvTmplIpsTunQueueTosMapQueue4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503578624}

er1645v2TvTmplIpsTunQueueTosMapQueue5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.queue5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503644160}

er1645v2TvTmplIpsTunQueueTosMapLowDelayQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.lowDelayQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503709696}

er1645v2TvTmplIpsTunQueueTosMapLowDelay2Queue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.lowDelay2Queue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503775232}

er1645v2TvTmplIpsTunQueueTosMapSystemQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.ipsecTunnels.queueTosMap.systemQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplIpsTunEntry 503840768}

er1645v2TvTmplIpsTunDf OBJECT-TYPE
   SYNTAX      INTEGER
               {
               clear (0),
               set (1),
               copy (2)
               }
   MAX-ACCESS  read-write
   STATUS      current
   DESCRIPTION
      "Path: tunnels.editConf.ipsecTunnels.dontFragmentBit

       Possibilities:
               clear   (0)
               set   (1)
               copy   (2)"
   ::= {er1645v2TvTmplIpsTunEntry 117440512}

er1645v2TvTmplIpsTunMtu OBJECT-TYPE
   SYNTAX      Integer32
   MAX-ACCESS  read-write
   STATUS      current
   DESCRIPTION
      "Path: tunnels.editConf.ipsecTunnels.mtu"
   ::= {er1645v2TvTmplIpsTunEntry 301989888}


er1645v2TvTmplCfg OBJECT IDENTIFIER ::= {er1645v2TvTmpl 1}

er1645v2TvTmplCfgSSCTable OBJECT-TYPE
   SYNTAX      SEQUENCE OF Er1645v2TvTmplCfgEntry
   MAX-ACCESS  not-accessible
   STATUS      current
   DESCRIPTION
      ""
   ::= {er1645v2TvTmplCfg 1}

er1645v2TvTmplCfgEntry OBJECT-TYPE
   SYNTAX      Er1645v2TvTmplCfgEntry
   MAX-ACCESS  not-accessible
   STATUS      current
   DESCRIPTION
      ""
   INDEX      { er1645v2TvTmplCfgTableIx }
   ::= {er1645v2TvTmplCfgSSCTable 1}

Er1645v2TvTmplCfgEntry ::=
   SEQUENCE
      {
      er1645v2TvTmplCfgActions
         VariableLengthTableActions,
      er1645v2TvTmplCfgTableIx
         TableIndex,
      er1645v2TvTmplCfgName
         DisplayString,
      er1645v2TvTmplCfgRemark
         DisplayString,
      er1645v2TvTmplCfgAdminStatus
         INTEGER,
      er1645v2TvTmplCfgMode
         INTEGER,
      er1645v2TvTmplCfgPriorityPolicy
         DisplayString,
      er1645v2TvTmplCfgIpVrfRouter
         DisplayString,
      er1645v2TvTmplCfgIpAdr
         IpAddress,
      er1645v2TvTmplCfgIpNetm
         IpAddress,
      er1645v2TvTmplCfgIpSNetName
         INTEGER,
      er1645v2TvTmplCfgIpSNetCust
         DisplayString,
      er1645v2TvTmplCfgIpRem
         IpAddress,
      er1645v2TvTmplCfgIpUnnumbered
         DisplayString,
      er1645v2TvTmplCfgIpAcceptLocAddr
         INTEGER,
      er1645v2TvTmplCfgIpAcceptRemAddr
         INTEGER,
      er1645v2TvTmplCfgIpGwPref
         Integer32,
      er1645v2TvTmplCfgIpRsn
         INTEGER,
      er1645v2TvTmplCfgIpMtu
         Integer32,
      er1645v2TvTmplCfgIpMssAdjust
         INTEGER,
      er1645v2TvTmplCfgIpRipMetric
         Integer32,
      er1645v2TvTmplCfgIpRipMetricOut
         Integer32,
      er1645v2TvTmplCfgIpRipMode
         INTEGER,
      er1645v2TvTmplCfgIpRipTxVersion
         INTEGER,
      er1645v2TvTmplCfgIpRipRxVersion
         INTEGER,
      er1645v2TvTmplCfgIpRipSplitHorizon
         INTEGER,
      er1645v2TvTmplCfgIpRipAuth
         INTEGER,
      er1645v2TvTmplCfgIpRipFilter
         DisplayString,
      er1645v2TvTmplCfgIpRipFilterIn
         DisplayString,
      er1645v2TvTmplCfgIpRipSnapshot
         INTEGER,
      er1645v2TvTmplCfgIpRipClearNextHop
         INTEGER,
      er1645v2TvTmplCfgIpAccPol
         DisplayString,
      er1645v2TvTmplCfgIpAB
         DisplayString,
      er1645v2TvTmplCfgIpMA
         INTEGER,
      er1645v2TvTmplCfgIpMF
         Integer32,
      er1645v2TvTmplCfgIpDB
         INTEGER,
      er1645v2TvTmplCfgIpIR
         INTEGER,
      er1645v2TvTmplCfgIpIgmp
         INTEGER,
      er1645v2TvTmplCfgIpNN
         DisplayString,
      er1645v2TvTmplCfgIpPimMode
         INTEGER,
      er1645v2TvTmplCfgIpPimDrPriority
         Counter32,
      er1645v2TvTmplCfgIpPimHelloTime
         TimeTicks,
      er1645v2TvTmplCfgIpPimPropagationDelay
         TimeTicks,
      er1645v2TvTmplCfgIpPimOverrideInterval
         TimeTicks,
      er1645v2TvTmplCfgIpPimBsrBorder
         INTEGER,
      er1645v2TvTmplCfgIpPimTtlThreshold
         Integer32,
      er1645v2TvTmplCfgIpIMNetworkUnreachable
         INTEGER,
      er1645v2TvTmplCfgIpIMHostUnreachable
         INTEGER,
      er1645v2TvTmplCfgIpIMProtocolUnreachable
         INTEGER,
      er1645v2TvTmplCfgIpIMPortUnreachable
         INTEGER,
      er1645v2TvTmplCfgIpIMMtuExceeded
         INTEGER,
      er1645v2TvTmplCfgIpIMAdminProhibited
         INTEGER,
      er1645v2TvTmplCfgIpIMTtlExceeded
         INTEGER,
      er1645v2TvTmplCfgIpIMRedirect
         INTEGER,
      er1645v2TvTmplCfgBridgingAccList
         DisplayString,
      er1645v2TvTmplCfgBridgingInACL
         DisplayString,
      er1645v2TvTmplCfgBridgingTp
         DisplayString,
      er1645v2TvTmplCfgBridgingBrGrp
         DisplayString,
      er1645v2TvTmplCfgBridgingLimBC
         INTEGER,
      er1645v2TvTmplCfgBridgingPrivateMode
         INTEGER,
      er1645v2TvTmplCfgBridgingLearning
         INTEGER,
      er1645v2TvTmplCfgBridgingMaxCacheSize
         INTEGER,
      er1645v2TvTmplCfgBridgingRelearnDropOnRelearn
         INTEGER,
      er1645v2TvTmplCfgBridgingRelearnShutdownThreshold
         Integer32,
      er1645v2TvTmplCfgBridgingRelearnShutdownTime
         TimeTicks,
      er1645v2TvTmplCfgBridgingRelearnLoopDetection
         INTEGER,
      er1645v2TvTmplCfgBridgingRelearnLoopDetectionInterval
         TimeTicks,
      er1645v2TvTmplCfgBridgingVlanMemberShip
         INTEGER,
      er1645v2TvTmplCfgBridgingVlTUntaggedAction
         INTEGER,
      er1645v2TvTmplCfgBridgingVlTUntaggedTagInfoTpid
         INTEGER,
      er1645v2TvTmplCfgBridgingVlTUntaggedTagInfoVid
         Integer32,
      er1645v2TvTmplCfgBridgingVlTUnknownVlansAction
         INTEGER,
      er1645v2TvTmplCfgBridgingVlTUnknownVlansTagInfoTpid
         INTEGER,
      er1645v2TvTmplCfgBridgingVlTUnknownVlansTagInfoVid
         Integer32,
      er1645v2TvTmplCfgBridgingDot1adType
         INTEGER,
      er1645v2TvTmplCfgBridgingPriority
         Integer32,
      er1645v2TvTmplCfgBridgingPathCost
         Integer32,
      er1645v2TvTmplCfgBridgingInternalPathCost
         Integer32,
      er1645v2TvTmplCfgBridgingTCD
         INTEGER,
      er1645v2TvTmplCfgBridgingRestrictedRole
         INTEGER,
      er1645v2TvTmplCfgBridgingAdminEdge
         INTEGER,
      er1645v2TvTmplCfgBridgingOamMacDeviceMac
         DisplayString,
      er1645v2TvTmplCfgBridgingOamMacUserMac
         OCTET STRING,
      er1645v2TvTmplCfgBridgingOamMacBridgeMac
         DisplayString,
      er1645v2TvTmplCfgBridgingMgmtInline
         INTEGER,
      er1645v2TvTmplCfgBridgingL2ptMode
         INTEGER,
      er1645v2TvTmplCfgBridgingL2ptProtocols
         Integer32,
      er1645v2TvTmplCfgBridgingL2ptDestMac
         OCTET STRING,
      er1645v2TvTmplCfgBridgingL2ptCos
         INTEGER,
      er1645v2TvTmplCfgBridgingL2ptDropThrStp
         INTEGER,
      er1645v2TvTmplCfgBridgingL2ptDropThrLldp
         INTEGER,
      er1645v2TvTmplCfgBridgingL2ptDropThrOam
         INTEGER,
      er1645v2TvTmplCfgBridgingL2ptDropThrCdp
         INTEGER,
      er1645v2TvTmplCfgBridgingL2ptDropThrVtp
         INTEGER,
      er1645v2TvTmplCfgBridgingL2ptDropThrLacp
         INTEGER,
      er1645v2TvTmplCfgBridgingL2ptDropThrEfmOam
         INTEGER,
      er1645v2TvTmplCfgBridgingL2ptDropThrPvst
         INTEGER,
      er1645v2TvTmplCfgBridgingL2ptDropThrMmrp
         INTEGER,
      er1645v2TvTmplCfgBridgingL2ptDropThrMvrp
         INTEGER,
      er1645v2TvTmplCfgBridgingL2ptDropThrGvrp
         INTEGER,
      er1645v2TvTmplCfgBridgingL2ptDropThrGmrp
         INTEGER,
      er1645v2TvTmplCfgBridgingL2ptDropThrDtp
         INTEGER,
      er1645v2TvTmplCfgBridgingL2ptDropThrPagp
         INTEGER,
      er1645v2TvTmplCfgBridgingL2ptDropThrUdld
         INTEGER,
      er1645v2TvTmplCfgVirtEthernetVirtualEthernet
         DisplayString,
      er1645v2TvTmplCfgEncapsulation
         INTEGER,
      er1645v2TvTmplCfgL2tpVrfRouter
         DisplayString,
      er1645v2TvTmplCfgL2tpLocalIpAddress
         IpAddress,
      er1645v2TvTmplCfgL2tpLocalInterface
         DisplayString,
      er1645v2TvTmplCfgL2tpRemoteIpAddress
         IpAddress,
      er1645v2TvTmplCfgL2tpRemoteDnsName
         DisplayString,
      er1645v2TvTmplCfgL2tpAuthen
         INTEGER,
      er1645v2TvTmplCfgL2tpPppNam
         DisplayString,
      er1645v2TvTmplCfgL2tpPppSec
         DisplayString,
      er1645v2TvTmplCfgL2tpEncMPppSec
         INTEGER,
      er1645v2TvTmplCfgL2tpEncPppSec
         DisplayString,
      er1645v2TvTmplCfgL2tpLnkMOperation
         INTEGER,
      er1645v2TvTmplCfgL2tpLnkMInterval
         TimeTicks,
      er1645v2TvTmplCfgL2tpLnkMRepTimeOut
         TimeTicks,
      er1645v2TvTmplCfgL2tpLnkMFailsPrmt
         Integer32,
      er1645v2TvTmplCfgL2tpType
         INTEGER,
      er1645v2TvTmplCfgL2tpDataseqnr
         INTEGER,
      er1645v2TvTmplCfgL2tpKeepaliveTO
         Integer32,
      er1645v2TvTmplCfgL2tpNoTraffT0
         Integer32,
      er1645v2TvTmplCfgL2tpMode
         INTEGER,
      er1645v2TvTmplCfgL2tpAuth
         INTEGER,
      er1645v2TvTmplCfgL2tpSecret
         DisplayString,
      er1645v2TvTmplCfgL2tpTos
         INTEGER,
      er1645v2TvTmplCfgL2tpRetrans
         Integer32,
      er1645v2TvTmplCfgL2tpTransmitws
         Integer32,
      er1645v2TvTmplCfgL2tpRcsws
         Integer32,
      er1645v2TvTmplCfgL2tpUdpcheck
         INTEGER,
      er1645v2TvTmplCfgL2tpCalledNr
         DisplayString,
      er1645v2TvTmplCfgL2tpSpeed
         Integer32,
      er1645v2TvTmplCfgL2tpMtu
         Integer32,
      er1645v2TvTmplCfgL2tpHostName
         DisplayString,
      er1645v2TvTmplCfgL2tpV3VrfRouter
         DisplayString,
      er1645v2TvTmplCfgL2tpV3LocalIpAddress
         IpAddress,
      er1645v2TvTmplCfgL2tpV3LocalInterface
         DisplayString,
      er1645v2TvTmplCfgL2tpV3RemoteIpAddress
         IpAddress,
      er1645v2TvTmplCfgL2tpV3RemoteDnsName
         DisplayString,
      er1645v2TvTmplCfgL2tpV3Type
         INTEGER,
      er1645v2TvTmplCfgL2tpV3KeepaliveTO
         Integer32,
      er1645v2TvTmplCfgL2tpV3NoTraffT0
         Integer32,
      er1645v2TvTmplCfgL2tpV3Mode
         INTEGER,
      er1645v2TvTmplCfgL2tpV3Auth
         INTEGER,
      er1645v2TvTmplCfgL2tpV3Secret
         DisplayString,
      er1645v2TvTmplCfgL2tpV3Tos
         INTEGER,
      er1645v2TvTmplCfgL2tpV3Retrans
         Integer32,
      er1645v2TvTmplCfgL2tpV3Transmitws
         Integer32,
      er1645v2TvTmplCfgL2tpV3Rcsws
         Integer32,
      er1645v2TvTmplCfgL2tpV3Udpcheck
         INTEGER,
      er1645v2TvTmplCfgL2tpV3CalledNr
         DisplayString,
      er1645v2TvTmplCfgL2tpV3Speed
         Integer32,
      er1645v2TvTmplCfgL2tpV3Mtu
         Integer32,
      er1645v2TvTmplCfgL2tpV3HostName
         DisplayString,
      er1645v2TvTmplCfgL2tpV3Hidden
         INTEGER,
      er1645v2TvTmplCfgL2tpV3RemoteEndId
         DisplayString,
      er1645v2TvTmplCfgL2tpV3RouterId
         IpAddress,
      er1645v2TvTmplCfgL2tpV3PseudowireType
         INTEGER,
      er1645v2TvTmplCfgL2tpV3Cookie
         INTEGER,
      er1645v2TvTmplCfgL2tpV3Compatibility
         INTEGER,
      er1645v2TvTmplCfgL2tpV3ManualVrfRouter
         DisplayString,
      er1645v2TvTmplCfgL2tpV3ManualLocalIpAddress
         IpAddress,
      er1645v2TvTmplCfgL2tpV3ManualRemoteIpAddress
         IpAddress,
      er1645v2TvTmplCfgL2tpV3ManualTos
         INTEGER,
      er1645v2TvTmplCfgL2tpV3ManualUdpcheck
         INTEGER,
      er1645v2TvTmplCfgL2tpV3ManualMtu
         Integer32,
      er1645v2TvTmplCfgL2tpV3ManualLocalSessionId
         Gauge32,
      er1645v2TvTmplCfgL2tpV3ManualRemoteSessionId
         Gauge32,
      er1645v2TvTmplCfgL2tpV3ManualLcookieOff
         DisplayString,
      er1645v2TvTmplCfgL2tpV3ManualLcookie4Bytes
         Gauge32,
      er1645v2TvTmplCfgL2tpV3ManualLcookie8BytesHigh
         Gauge32,
      er1645v2TvTmplCfgL2tpV3ManualLcookie8BytesLow
         Gauge32,
      er1645v2TvTmplCfgL2tpV3ManualRcookieOff
         DisplayString,
      er1645v2TvTmplCfgL2tpV3ManualRcookie4Bytes
         Gauge32,
      er1645v2TvTmplCfgL2tpV3ManualRcookie8BytesHigh
         Gauge32,
      er1645v2TvTmplCfgL2tpV3ManualRcookie8BytesLow
         Gauge32,
      er1645v2TvTmplCfgL2tpV3ManualLocalDataSeq
         INTEGER,
      er1645v2TvTmplCfgL2tpV3ManualRemoteDataSeq
         INTEGER,
      er1645v2TvTmplCfgBackupInterface
         DisplayString,
      er1645v2TvTmplCfgBackupTimeOut
         Integer32,
      er1645v2TvTmplCfgBackupAutoRetry
         INTEGER,
      er1645v2TvTmplCfgInbBwCir
         Integer32,
      er1645v2TvTmplCfgInbBwTc
         INTEGER,
      er1645v2TvTmplCfgInbBwCorrType
         INTEGER,
      er1645v2TvTmplCfgInbBwCorrPredefEncapsFrameRelay
         DisplayString,
      er1645v2TvTmplCfgInbBwCorrPredefEncapsPpp
         DisplayString,
      er1645v2TvTmplCfgInbBwCorrPredefEncapsAtmHl
         INTEGER,
      er1645v2TvTmplCfgInbBwCorrPredefEncapsAtmMp
         INTEGER,
      er1645v2TvTmplCfgInbBwCorrPredefEncapsHdlc
         DisplayString,
      er1645v2TvTmplCfgInbBwCorrPredefEncapsEfmFs
         Integer32,
      er1645v2TvTmplCfgInbBwCorrPredefEncapsEfmIb
         Integer32,
      er1645v2TvTmplCfgInbBwCorrPredefMode
         INTEGER,
      er1645v2TvTmplCfgInbBwCorrManualOverhead
         Integer32,
      er1645v2TvTmplCfgInbBwCorrManualFrameData
         Counter32,
      er1645v2TvTmplCfgInbBwCorrManualFrameHeader
         Counter32,
      er1645v2TvTmplCfgInbBwMaxFifoQLen
         Integer32,
      er1645v2TvTmplCfgInbBwPriorityPolicy
         DisplayString,
      er1645v2TvTmplCfgBandwidthMode
         INTEGER,
      er1645v2TvTmplCfgBandwidthCir
         Integer32,
      er1645v2TvTmplCfgBandwidthEir
         Integer32,
      er1645v2TvTmplCfgBandwidthUnit
         INTEGER,
      er1645v2TvTmplCfgBandwidthTc
         INTEGER,
      er1645v2TvTmplCfgBandwidthTcFactor
         INTEGER,
      er1645v2TvTmplCfgBandwidthCorrType
         INTEGER,
      er1645v2TvTmplCfgBandwidthCorrPredefEncapsFrameRelay
         DisplayString,
      er1645v2TvTmplCfgBandwidthCorrPredefEncapsPpp
         DisplayString,
      er1645v2TvTmplCfgBandwidthCorrPredefEncapsAtmHl
         INTEGER,
      er1645v2TvTmplCfgBandwidthCorrPredefEncapsAtmMp
         INTEGER,
      er1645v2TvTmplCfgBandwidthCorrPredefEncapsHdlc
         DisplayString,
      er1645v2TvTmplCfgBandwidthCorrPredefEncapsEfmFs
         Integer32,
      er1645v2TvTmplCfgBandwidthCorrPredefEncapsEfmIb
         Integer32,
      er1645v2TvTmplCfgBandwidthCorrPredefMode
         INTEGER,
      er1645v2TvTmplCfgBandwidthCorrManualOverhead
         Integer32,
      er1645v2TvTmplCfgBandwidthCorrManualFrameData
         Counter32,
      er1645v2TvTmplCfgBandwidthCorrManualFrameHeader
         Counter32,
      er1645v2TvTmplCfgBandwidthMaxFifoQLen
         Integer32,
      er1645v2TvTmplCfgBandwidthDeFlagCir
         INTEGER,
      er1645v2TvTmplCfgBandwidthDeFlagEir
         INTEGER,
      er1645v2TvTmplCfgBandwidthDeFlagViolate
         INTEGER,
      er1645v2TvTmplCfgBandwidthActCirActNone
         OCTET STRING,
      er1645v2TvTmplCfgBandwidthActCirActEthCos1
         INTEGER,
      er1645v2TvTmplCfgBandwidthActCirActEthDei1
         INTEGER,
      er1645v2TvTmplCfgBandwidthActCirActEthCos2
         INTEGER,
      er1645v2TvTmplCfgBandwidthActCirActEthDei2
         INTEGER,
      er1645v2TvTmplCfgBandwidthActCirActEthCos3
         INTEGER,
      er1645v2TvTmplCfgBandwidthActCirActEthDei3
         INTEGER,
      er1645v2TvTmplCfgBandwidthActCirActEthCos4
         INTEGER,
      er1645v2TvTmplCfgBandwidthActCirActEthDei4
         INTEGER,
      er1645v2TvTmplCfgBandwidthActCirActEthCos5
         INTEGER,
      er1645v2TvTmplCfgBandwidthActCirActEthDei5
         INTEGER,
      er1645v2TvTmplCfgBandwidthActCirActEthCos6
         INTEGER,
      er1645v2TvTmplCfgBandwidthActCirActEthDei6
         INTEGER,
      er1645v2TvTmplCfgBandwidthActCirActEthCos7
         INTEGER,
      er1645v2TvTmplCfgBandwidthActCirActEthDei7
         INTEGER,
      er1645v2TvTmplCfgBandwidthActCirActEthCos8
         INTEGER,
      er1645v2TvTmplCfgBandwidthActCirActEthDei8
         INTEGER,
      er1645v2TvTmplCfgBandwidthActCirActEthTos
         INTEGER,
      er1645v2TvTmplCfgBandwidthActCirActEthQueue
         INTEGER,
      er1645v2TvTmplCfgBandwidthActCirActEthDrpLev
         INTEGER,
      er1645v2TvTmplCfgBandwidthActCirActEthDeFlag
         INTEGER,
      er1645v2TvTmplCfgBandwidthActCirActIpTos
         INTEGER,
      er1645v2TvTmplCfgBandwidthActCirActIpQueue
         INTEGER,
      er1645v2TvTmplCfgBandwidthActCirActIpDrpLev
         INTEGER,
      er1645v2TvTmplCfgBandwidthActCirActIpDeFlag
         INTEGER,
      er1645v2TvTmplCfgBandwidthActEirActNone
         OCTET STRING,
      er1645v2TvTmplCfgBandwidthActEirActEthCos1
         INTEGER,
      er1645v2TvTmplCfgBandwidthActEirActEthDei1
         INTEGER,
      er1645v2TvTmplCfgBandwidthActEirActEthCos2
         INTEGER,
      er1645v2TvTmplCfgBandwidthActEirActEthDei2
         INTEGER,
      er1645v2TvTmplCfgBandwidthActEirActEthCos3
         INTEGER,
      er1645v2TvTmplCfgBandwidthActEirActEthDei3
         INTEGER,
      er1645v2TvTmplCfgBandwidthActEirActEthCos4
         INTEGER,
      er1645v2TvTmplCfgBandwidthActEirActEthDei4
         INTEGER,
      er1645v2TvTmplCfgBandwidthActEirActEthCos5
         INTEGER,
      er1645v2TvTmplCfgBandwidthActEirActEthDei5
         INTEGER,
      er1645v2TvTmplCfgBandwidthActEirActEthCos6
         INTEGER,
      er1645v2TvTmplCfgBandwidthActEirActEthDei6
         INTEGER,
      er1645v2TvTmplCfgBandwidthActEirActEthCos7
         INTEGER,
      er1645v2TvTmplCfgBandwidthActEirActEthDei7
         INTEGER,
      er1645v2TvTmplCfgBandwidthActEirActEthCos8
         INTEGER,
      er1645v2TvTmplCfgBandwidthActEirActEthDei8
         INTEGER,
      er1645v2TvTmplCfgBandwidthActEirActEthTos
         INTEGER,
      er1645v2TvTmplCfgBandwidthActEirActEthQueue
         INTEGER,
      er1645v2TvTmplCfgBandwidthActEirActEthDrpLev
         INTEGER,
      er1645v2TvTmplCfgBandwidthActEirActEthDeFlag
         INTEGER,
      er1645v2TvTmplCfgBandwidthActEirActIpTos
         INTEGER,
      er1645v2TvTmplCfgBandwidthActEirActIpQueue
         INTEGER,
      er1645v2TvTmplCfgBandwidthActEirActIpDrpLev
         INTEGER,
      er1645v2TvTmplCfgBandwidthActEirActIpDeFlag
         INTEGER,
      er1645v2TvTmplCfgBandwidthActViolActNone
         OCTET STRING,
      er1645v2TvTmplCfgBandwidthActViolActDrop
         OCTET STRING,
      er1645v2TvTmplCfgBandwidthActViolActEthCos1
         INTEGER,
      er1645v2TvTmplCfgBandwidthActViolActEthDei1
         INTEGER,
      er1645v2TvTmplCfgBandwidthActViolActEthCos2
         INTEGER,
      er1645v2TvTmplCfgBandwidthActViolActEthDei2
         INTEGER,
      er1645v2TvTmplCfgBandwidthActViolActEthCos3
         INTEGER,
      er1645v2TvTmplCfgBandwidthActViolActEthDei3
         INTEGER,
      er1645v2TvTmplCfgBandwidthActViolActEthCos4
         INTEGER,
      er1645v2TvTmplCfgBandwidthActViolActEthDei4
         INTEGER,
      er1645v2TvTmplCfgBandwidthActViolActEthCos5
         INTEGER,
      er1645v2TvTmplCfgBandwidthActViolActEthDei5
         INTEGER,
      er1645v2TvTmplCfgBandwidthActViolActEthCos6
         INTEGER,
      er1645v2TvTmplCfgBandwidthActViolActEthDei6
         INTEGER,
      er1645v2TvTmplCfgBandwidthActViolActEthCos7
         INTEGER,
      er1645v2TvTmplCfgBandwidthActViolActEthDei7
         INTEGER,
      er1645v2TvTmplCfgBandwidthActViolActEthCos8
         INTEGER,
      er1645v2TvTmplCfgBandwidthActViolActEthDei8
         INTEGER,
      er1645v2TvTmplCfgBandwidthActViolActEthTos
         INTEGER,
      er1645v2TvTmplCfgBandwidthActViolActEthQueue
         INTEGER,
      er1645v2TvTmplCfgBandwidthActViolActEthDrpLev
         INTEGER,
      er1645v2TvTmplCfgBandwidthActViolActEthDeFlag
         INTEGER,
      er1645v2TvTmplCfgBandwidthActViolActIpTos
         INTEGER,
      er1645v2TvTmplCfgBandwidthActViolActIpQueue
         INTEGER,
      er1645v2TvTmplCfgBandwidthActViolActIpDrpLev
         INTEGER,
      er1645v2TvTmplCfgBandwidthActViolActIpDeFlag
         INTEGER
      }

er1645v2TvTmplCfgActions OBJECT-TYPE
   SYNTAX      VariableLengthTableActions
   MAX-ACCESS  read-write
   STATUS      current
   DESCRIPTION
      "By way of this field, some manipulations
       on this table may be performed."
   ::= {er1645v2TvTmplCfgEntry 2}

er1645v2TvTmplCfgTableIx OBJECT-TYPE
   SYNTAX      TableIndex
   MAX-ACCESS  not-accessible
   STATUS      current
   DESCRIPTION
      ""
   ::= {er1645v2TvTmplCfgEntry 11}

er1645v2TvTmplCfgName OBJECT-TYPE
   SYNTAX      DisplayString
   MAX-ACCESS  read-write
   STATUS      current
   DESCRIPTION
      "Path: tunnels.editConf.l2tpTunnels.name"
   ::= {er1645v2TvTmplCfgEntry 16777216}

er1645v2TvTmplCfgRemark OBJECT-TYPE
   SYNTAX      DisplayString
   MAX-ACCESS  read-write
   STATUS      current
   DESCRIPTION
      "Path: tunnels.editConf.l2tpTunnels.remark"
   ::= {er1645v2TvTmplCfgEntry 1157627904}

er1645v2TvTmplCfgAdminStatus OBJECT-TYPE
   SYNTAX      INTEGER
               {
               up (1),
               down (2)
               }
   MAX-ACCESS  read-write
   STATUS      current
   DESCRIPTION
      "Path: tunnels.editConf.l2tpTunnels.adminStatus

       Possibilities:
               up   (1)
               down   (2)"
   ::= {er1645v2TvTmplCfgEntry 33554432}

er1645v2TvTmplCfgMode OBJECT-TYPE
   SYNTAX      INTEGER
               {
               routing (1),
               bridging (2),
               routingAndBridging (3),
               multiLink (8),
               virtEthernet (32)
               }
   MAX-ACCESS  read-write
   STATUS      current
   DESCRIPTION
      "Path: tunnels.editConf.l2tpTunnels.mode

       Possibilities:
               routing   (1)
               bridging   (2)
               routingAndBridging   (3)
               multiLink   (8)
               virtEthernet   (32)"
   ::= {er1645v2TvTmplCfgEntry 67108864}

er1645v2TvTmplCfgPriorityPolicy OBJECT-TYPE
   SYNTAX      DisplayString
   MAX-ACCESS  read-write
   STATUS      current
   DESCRIPTION
      "Path: tunnels.editConf.l2tpTunnels.priorityPolicy"
   ::= {er1645v2TvTmplCfgEntry 83886080}

er1645v2TvTmplCfgIpVrfRouter OBJECT-TYPE
   SYNTAX      DisplayString
   MAX-ACCESS  read-write
   STATUS      current
   DESCRIPTION
      "Path: tunnels.editConf.l2tpTunnels.ip.vrfRouter"
   ::= {er1645v2TvTmplCfgEntry 53215232}

er1645v2TvTmplCfgIpAdr OBJECT-TYPE
   SYNTAX      IpAddress
   MAX-ACCESS  read-write
   STATUS      current
   DESCRIPTION
      "Path: tunnels.editConf.l2tpTunnels.ip.address"
   ::= {er1645v2TvTmplCfgEntry 58261504}

er1645v2TvTmplCfgIpNetm OBJECT-TYPE
   SYNTAX      IpAddress
   MAX-ACCESS  read-write
   STATUS      current
   DESCRIPTION
      "Path: tunnels.editConf.l2tpTunnels.ip.netMask"
   ::= {er1645v2TvTmplCfgEntry 58392576}

er1645v2TvTmplCfgIpSNetName OBJECT-TYPE
   SYNTAX      INTEGER
               {
               slOPTg (0),
               corp (2),
               dmz (3),
               internet (1)
               }
   MAX-ACCESS  read-write
   STATUS      current
   DESCRIPTION
      "Path: tunnels.editConf.l2tpTunnels.ip.sNet.name

       Possibilities:
               <OPT>   (0)
               corp   (2)
               dmz   (3)
               internet   (1)"
   ::= {er1645v2TvTmplCfgEntry 53674240}

er1645v2TvTmplCfgIpSNetCust OBJECT-TYPE
   SYNTAX      DisplayString
   MAX-ACCESS  read-write
   STATUS      current
   DESCRIPTION
      "Path: tunnels.editConf.l2tpTunnels.ip.sNet.custom"
   ::= {er1645v2TvTmplCfgEntry 53674496}

er1645v2TvTmplCfgIpRem OBJECT-TYPE
   SYNTAX      IpAddress
   MAX-ACCESS  read-write
   STATUS      current
   DESCRIPTION
      "Path: tunnels.editConf.l2tpTunnels.ip.remote"
   ::= {er1645v2TvTmplCfgEntry 58458112}

er1645v2TvTmplCfgIpUnnumbered OBJECT-TYPE
   SYNTAX      DisplayString
   MAX-ACCESS  read-write
   STATUS      current
   DESCRIPTION
      "Path: tunnels.editConf.l2tpTunnels.ip.unnumbered"
   ::= {er1645v2TvTmplCfgEntry 52625408}

er1645v2TvTmplCfgIpAcceptLocAddr OBJECT-TYPE
   SYNTAX      INTEGER
               {
               disabled (0),
               enabled (1)
               }
   MAX-ACCESS  read-write
   STATUS      current
   DESCRIPTION
      "Path: tunnels.editConf.l2tpTunnels.ip.acceptLocAddr

       Possibilities:
               disabled   (0)
               enabled   (1)"
   ::= {er1645v2TvTmplCfgEntry 50593792}

er1645v2TvTmplCfgIpAcceptRemAddr OBJECT-TYPE
   SYNTAX      INTEGER
               {
               disabled (0),
               enabled (1)
               }
   MAX-ACCESS  read-write
   STATUS      current
   DESCRIPTION
      "Path: tunnels.editConf.l2tpTunnels.ip.acceptRemAddr

       Possibilities:
               disabled   (0)
               enabled   (1)"
   ::= {er1645v2TvTmplCfgEntry 50724864}

er1645v2TvTmplCfgIpGwPref OBJECT-TYPE
   SYNTAX      Integer32
   MAX-ACCESS  read-write
   STATUS      current
   DESCRIPTION
      "Path: tunnels.editConf.l2tpTunnels.ip.gatewayPreference"
   ::= {er1645v2TvTmplCfgEntry 52690944}

er1645v2TvTmplCfgIpRsn OBJECT-TYPE
   SYNTAX      INTEGER
               {
               disabled (0),
               enabled (1)
               }
   MAX-ACCESS  read-write
   STATUS      current
   DESCRIPTION
      "Path: tunnels.editConf.l2tpTunnels.ip.requestSubnet

       Possibilities:
               disabled   (0)
               enabled   (1)"
   ::= {er1645v2TvTmplCfgEntry 56688640}

er1645v2TvTmplCfgIpMtu OBJECT-TYPE
   SYNTAX      Integer32
   MAX-ACCESS  read-write
   STATUS      current
   DESCRIPTION
      "Path: tunnels.editConf.l2tpTunnels.ip.mtu"
   ::= {er1645v2TvTmplCfgEntry 52953088}

er1645v2TvTmplCfgIpMssAdjust OBJECT-TYPE
   SYNTAX      INTEGER
               {
               disabled (0),
               auto (65536)
               }
   MAX-ACCESS  read-write
   STATUS      current
   DESCRIPTION
      "Path: tunnels.editConf.l2tpTunnels.ip.mssAdjust

       Possibilities:
               disabled   (0)
               auto   (65536)"
   ::= {er1645v2TvTmplCfgEntry 53280768}

er1645v2TvTmplCfgIpRipMetric OBJECT-TYPE
   SYNTAX      Integer32
   MAX-ACCESS  read-write
   STATUS      current
   DESCRIPTION
      "Path: tunnels.editConf.l2tpTunnels.ip.rip.metric"
   ::= {er1645v2TvTmplCfgEntry 51712768}

er1645v2TvTmplCfgIpRipMetricOut OBJECT-TYPE
   SYNTAX      Integer32
   MAX-ACCESS  read-write
   STATUS      current
   DESCRIPTION
      "Path: tunnels.editConf.l2tpTunnels.ip.rip.metricOut"
   ::= {er1645v2TvTmplCfgEntry 51713024}

er1645v2TvTmplCfgIpRipMode OBJECT-TYPE
   SYNTAX      INTEGER
               {
               disabled (0),
               passive (1),
               active (2)
               }
   MAX-ACCESS  read-write
   STATUS      current
   DESCRIPTION
      "Path: tunnels.editConf.l2tpTunnels.ip.rip.mode

       Possibilities:
               disabled   (0)
               passive   (1)
               active   (2)"
   ::= {er1645v2TvTmplCfgEntry 51713280}

er1645v2TvTmplCfgIpRipTxVersion OBJECT-TYPE
   SYNTAX      INTEGER
               {
               rip1 (0),
               rip2 (1),
               rip1mcompatible (2)
               }
   MAX-ACCESS  read-write
   STATUS      current
   DESCRIPTION
      "Path: tunnels.editConf.l2tpTunnels.ip.rip.txVersion

       Possibilities:
               rip1   (0)
               rip2   (1)
               rip1-compatible   (2)"
   ::= {er1645v2TvTmplCfgEntry 51716864}

er1645v2TvTmplCfgIpRipRxVersion OBJECT-TYPE
   SYNTAX      INTEGER
               {
               rip1only (0),
               rip2only (1),
               rip12 (2)
               }
   MAX-ACCESS  read-write
   STATUS      current
   DESCRIPTION
      "Path: tunnels.editConf.l2tpTunnels.ip.rip.rxVersion

       Possibilities:
               rip1only   (0)
               rip2only   (1)
               rip1&2   (2)"
   ::= {er1645v2TvTmplCfgEntry 51717120}

er1645v2TvTmplCfgIpRipSplitHorizon OBJECT-TYPE
   SYNTAX      INTEGER
               {
               disabled (0),
               enabled (1),
               poisonedReverse (2)
               }
   MAX-ACCESS  read-write
   STATUS      current
   DESCRIPTION
      "Path: tunnels.editConf.l2tpTunnels.ip.rip.splitHorizon

       Possibilities:
               disabled   (0)
               enabled   (1)
               poisonedReverse   (2)"
   ::= {er1645v2TvTmplCfgEntry 51713792}

er1645v2TvTmplCfgIpRipAuth OBJECT-TYPE
   SYNTAX      INTEGER
               {
               disabled (0),
               texts (1),
               md5 (2)
               }
   MAX-ACCESS  read-write
   STATUS      current
   DESCRIPTION
      "Path: tunnels.editConf.l2tpTunnels.ip.rip.authentication

       Possibilities:
               disabled   (0)
               text    (1)
               md5   (2)"
   ::= {er1645v2TvTmplCfgEntry 51712512}

er1645v2TvTmplCfgIpRipFilter OBJECT-TYPE
   SYNTAX      DisplayString
   MAX-ACCESS  read-write
   STATUS      current
   DESCRIPTION
      "Path: tunnels.editConf.l2tpTunnels.ip.rip.filter"
   ::= {er1645v2TvTmplCfgEntry 51716096}

er1645v2TvTmplCfgIpRipFilterIn OBJECT-TYPE
   SYNTAX      DisplayString
   MAX-ACCESS  read-write
   STATUS      current
   DESCRIPTION
      "Path: tunnels.editConf.l2tpTunnels.ip.rip.filterIn"
   ::= {er1645v2TvTmplCfgEntry 51716352}

er1645v2TvTmplCfgIpRipSnapshot OBJECT-TYPE
   SYNTAX      INTEGER
               {
               disabled (0),
               enabled (1)
               }
   MAX-ACCESS  read-write
   STATUS      current
   DESCRIPTION
      "Path: tunnels.editConf.l2tpTunnels.ip.rip.snapshot

       Possibilities:
               disabled   (0)
               enabled   (1)"
   ::= {er1645v2TvTmplCfgEntry 51708160}

er1645v2TvTmplCfgIpRipClearNextHop OBJECT-TYPE
   SYNTAX      INTEGER
               {
               disabled (0),
               enabled (1)
               }
   MAX-ACCESS  read-write
   STATUS      current
   DESCRIPTION
      "Path: tunnels.editConf.l2tpTunnels.ip.rip.clearNextHop

       Possibilities:
               disabled   (0)
               enabled   (1)"
   ::= {er1645v2TvTmplCfgEntry 51708416}

er1645v2TvTmplCfgIpAccPol OBJECT-TYPE
   SYNTAX      DisplayString
   MAX-ACCESS  read-write
   STATUS      current
   DESCRIPTION
      "Path: tunnels.editConf.l2tpTunnels.ip.accessPolicy"
   ::= {er1645v2TvTmplCfgEntry 53084160}

er1645v2TvTmplCfgIpAB OBJECT-TYPE
   SYNTAX      DisplayString
   MAX-ACCESS  read-write
   STATUS      current
   DESCRIPTION
      "Path: tunnels.editConf.l2tpTunnels.ip.trafficPolicy"
   ::= {er1645v2TvTmplCfgEntry 51249152}

er1645v2TvTmplCfgIpMA OBJECT-TYPE
   SYNTAX      INTEGER
               {
               disabled (0),
               enabled (1)
               }
   MAX-ACCESS  read-write
   STATUS      current
   DESCRIPTION
      "Path: tunnels.editConf.l2tpTunnels.ip.mgmtAccess

       Possibilities:
               disabled   (0)
               enabled   (1)"
   ::= {er1645v2TvTmplCfgEntry 51380224}

er1645v2TvTmplCfgIpMF OBJECT-TYPE
   SYNTAX      Integer32
   MAX-ACCESS  read-write
   STATUS      current
   DESCRIPTION
      "Path: tunnels.editConf.l2tpTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TvTmplCfgEntry 51445760}

er1645v2TvTmplCfgIpDB OBJECT-TYPE
   SYNTAX      INTEGER
               {
               disabled (0),
               enabled (1)
               }
   MAX-ACCESS  read-write
   STATUS      current
   DESCRIPTION
      "Path: tunnels.editConf.l2tpTunnels.ip.directedBroadcasts

       Possibilities:
               disabled   (0)
               enabled   (1)"
   ::= {er1645v2TvTmplCfgEntry 51773440}

er1645v2TvTmplCfgIpIR OBJECT-TYPE
   SYNTAX      INTEGER
               {
               disabled (0),
               enabled (1)
               }
   MAX-ACCESS  read-write
   STATUS      current
   DESCRIPTION
      "Path: tunnels.editConf.l2tpTunnels.ip.icmpRedirects

       Possibilities:
               disabled   (0)
               enabled   (1)"
   ::= {er1645v2TvTmplCfgEntry 52035584}

er1645v2TvTmplCfgIpIgmp OBJECT-TYPE
   SYNTAX      INTEGER
               {
               disabled (0),
               proxy (1),
               router (2),
               v3Router (5)
               }
   MAX-ACCESS  read-write
   STATUS      current
   DESCRIPTION
      "Path: tunnels.editConf.l2tpTunnels.ip.igmp

       Possibilities:
               disabled   (0)
               proxy   (1)
               router   (2)
               v3Router   (5)"
   ::= {er1645v2TvTmplCfgEntry 52428800}

er1645v2TvTmplCfgIpNN OBJECT-TYPE
   SYNTAX      DisplayString
   MAX-ACCESS  read-write
   STATUS      current
   DESCRIPTION
      "Path: tunnels.editConf.l2tpTunnels.ip.nat"
   ::= {er1645v2TvTmplCfgEntry 52101120}

er1645v2TvTmplCfgIpPimMode OBJECT-TYPE
   SYNTAX      INTEGER
               {
               disabled (0),
               sparse (1),
               passive (2)
               }
   MAX-ACCESS  read-write
   STATUS      current
   DESCRIPTION
      "Path: tunnels.editConf.l2tpTunnels.ip.pim.mode

       Possibilities:
               disabled   (0)
               sparse   (1)
               passive   (2)"
   ::= {er1645v2TvTmplCfgEntry 53346560}

er1645v2TvTmplCfgIpPimDrPriority OBJECT-TYPE
   SYNTAX      Counter32
   MAX-ACCESS  read-write
   STATUS      current
   DESCRIPTION
      "Path: tunnels.editConf.l2tpTunnels.ip.pim.drPriority

       32 bit unsigned wrappable counter."
   ::= {er1645v2TvTmplCfgEntry 53346816}

er1645v2TvTmplCfgIpPimHelloTime OBJECT-TYPE
   SYNTAX      TimeTicks
   MAX-ACCESS  read-write
   STATUS      current
   DESCRIPTION
      "Path: tunnels.editConf.l2tpTunnels.ip.pim.helloTime

       Time in centi-second."
   ::= {er1645v2TvTmplCfgEntry 53347072}

er1645v2TvTmplCfgIpPimPropagationDelay OBJECT-TYPE
   SYNTAX      TimeTicks
   MAX-ACCESS  read-write
   STATUS      current
   DESCRIPTION
      "Path: tunnels.editConf.l2tpTunnels.ip.pim.propagationDelay

       Time in centi-second."
   ::= {er1645v2TvTmplCfgEntry 53347328}

er1645v2TvTmplCfgIpPimOverrideInterval OBJECT-TYPE
   SYNTAX      TimeTicks
   MAX-ACCESS  read-write
   STATUS      current
   DESCRIPTION
      "Path: tunnels.editConf.l2tpTunnels.ip.pim.overrideInterval

       Time in centi-second."
   ::= {er1645v2TvTmplCfgEntry 53347584}

er1645v2TvTmplCfgIpPimBsrBorder OBJECT-TYPE
   SYNTAX      INTEGER
               {
               disabled (0),
               enabled (1)
               }
   MAX-ACCESS  read-write
   STATUS      current
   DESCRIPTION
      "Path: tunnels.editConf.l2tpTunnels.ip.pim.bsrBorder

       Possibilities:
               disabled   (0)
               enabled   (1)"
   ::= {er1645v2TvTmplCfgEntry 53347840}

er1645v2TvTmplCfgIpPimTtlThreshold OBJECT-TYPE
   SYNTAX      Integer32
   MAX-ACCESS  read-write
   STATUS      current
   DESCRIPTION
      "Path: tunnels.editConf.l2tpTunnels.ip.pim.ttlThreshold"
   ::= {er1645v2TvTmplCfgEntry 53348096}

er1645v2TvTmplCfgIpIMNetworkUnreachable OBJECT-TYPE
   SYNTAX      INTEGER
               {
               disabled (0),
               enabled (1)
               }
   MAX-ACCESS  read-write
   STATUS      current
   DESCRIPTION
      "Path: tunnels.editConf.l2tpTunnels.ip.icmpMessages.networkUnreachable

       Possibilities:
               disabled   (0)
               enabled   (1)"
   ::= {er1645v2TvTmplCfgEntry 53412096}

er1645v2TvTmplCfgIpIMHostUnreachable OBJECT-TYPE
   SYNTAX      INTEGER
               {
               disabled (0),
               enabled (1)
               }
   MAX-ACCESS  read-write
   STATUS      current
   DESCRIPTION
      "Path: tunnels.editConf.l2tpTunnels.ip.icmpMessages.hostUnreachable

       Possibilities:
               disabled   (0)
               enabled   (1)"
   ::= {er1645v2TvTmplCfgEntry 53412352}

er1645v2TvTmplCfgIpIMProtocolUnreachable OBJECT-TYPE
   SYNTAX      INTEGER
               {
               disabled (0),
               enabled (1)
               }
   MAX-ACCESS  read-write
   STATUS      current
   DESCRIPTION
      "Path: tunnels.editConf.l2tpTunnels.ip.icmpMessages.protocolUnreachable

       Possibilities:
               disabled   (0)
               enabled   (1)"
   ::= {er1645v2TvTmplCfgEntry 53412608}

er1645v2TvTmplCfgIpIMPortUnreachable OBJECT-TYPE
   SYNTAX      INTEGER
               {
               disabled (0),
               enabled (1)
               }
   MAX-ACCESS  read-write
   STATUS      current
   DESCRIPTION
      "Path: tunnels.editConf.l2tpTunnels.ip.icmpMessages.portUnreachable

       Possibilities:
               disabled   (0)
               enabled   (1)"
   ::= {er1645v2TvTmplCfgEntry 53412864}

er1645v2TvTmplCfgIpIMMtuExceeded OBJECT-TYPE
   SYNTAX      INTEGER
               {
               disabled (0),
               enabled (1)
               }
   MAX-ACCESS  read-write
   STATUS      current
   DESCRIPTION
      "Path: tunnels.editConf.l2tpTunnels.ip.icmpMessages.mtuExceeded

       Possibilities:
               disabled   (0)
               enabled   (1)"
   ::= {er1645v2TvTmplCfgEntry 53413120}

er1645v2TvTmplCfgIpIMAdminProhibited OBJECT-TYPE
   SYNTAX      INTEGER
               {
               disabled (0),
               enabled (1)
               }
   MAX-ACCESS  read-write
   STATUS      current
   DESCRIPTION
      "Path: tunnels.editConf.l2tpTunnels.ip.icmpMessages.adminProhibited

       Possibilities:
               disabled   (0)
               enabled   (1)"
   ::= {er1645v2TvTmplCfgEntry 53413376}

er1645v2TvTmplCfgIpIMTtlExceeded OBJECT-TYPE
   SYNTAX      INTEGER
               {
               disabled (0),
               enabled (1)
               }
   MAX-ACCESS  read-write
   STATUS      current
   DESCRIPTION
      "Path: tunnels.editConf.l2tpTunnels.ip.icmpMessages.ttlExceeded

       Possibilities:
               disabled   (0)
               enabled   (1)"
   ::= {er1645v2TvTmplCfgEntry 53413632}

er1645v2TvTmplCfgIpIMRedirect OBJECT-TYPE
   SYNTAX      INTEGER
               {
               disabled (0),
               enabled (1)
               }
   MAX-ACCESS  read-write
   STATUS      current
   DESCRIPTION
      "Path: tunnels.editConf.l2tpTunnels.ip.icmpMessages.redirect

       Possibilities:
               disabled   (0)
               enabled   (1)"
   ::= {er1645v2TvTmplCfgEntry 53413888}

er1645v2TvTmplCfgBridgingAccList OBJECT-TYPE
   SYNTAX      DisplayString
   MAX-ACCESS  read-write
   STATUS      current
   DESCRIPTION
      "Path: tunnels.editConf.l2tpTunnels.bridging.accessList"
   ::= {er1645v2TvTmplCfgEntry 453246976}

er1645v2TvTmplCfgBridgingInACL OBJECT-TYPE
   SYNTAX      DisplayString
   MAX-ACCESS  read-write
   STATUS      current
   DESCRIPTION
      "Path: tunnels.editConf.l2tpTunnels.bridging.inAccessList"
   ::= {er1645v2TvTmplCfgEntry 456916992}

er1645v2TvTmplCfgBridgingTp OBJECT-TYPE
   SYNTAX      DisplayString
   MAX-ACCESS  read-write
   STATUS      current
   DESCRIPTION
      "Path: tunnels.editConf.l2tpTunnels.bridging.trafficPolicy"
   ::= {er1645v2TvTmplCfgEntry 454295552}

er1645v2TvTmplCfgBridgingBrGrp OBJECT-TYPE
   SYNTAX      DisplayString
   MAX-ACCESS  read-write
   STATUS      current
   DESCRIPTION
      "Path: tunnels.editConf.l2tpTunnels.bridging.bridgeGroup"
   ::= {er1645v2TvTmplCfgEntry 454819840}

er1645v2TvTmplCfgBridgingLimBC OBJECT-TYPE
   SYNTAX      INTEGER
               {
               disabled (0),
               enabled (1)
               }
   MAX-ACCESS  read-write
   STATUS      current
   DESCRIPTION
      "Path: tunnels.editConf.l2tpTunnels.bridging.limitBroadcasts

       Possibilities:
               disabled   (0)
               enabled   (1)"
   ::= {er1645v2TvTmplCfgEntry 455081984}

er1645v2TvTmplCfgBridgingPrivateMode OBJECT-TYPE
   SYNTAX      INTEGER
               {
               disabled (0),
               enabled (1)
               }
   MAX-ACCESS  read-write
   STATUS      current
   DESCRIPTION
      "Path: tunnels.editConf.l2tpTunnels.bridging.privateMode

       Possibilities:
               disabled   (0)
               enabled   (1)"
   ::= {er1645v2TvTmplCfgEntry 459538432}

er1645v2TvTmplCfgBridgingLearning OBJECT-TYPE
   SYNTAX      INTEGER
               {
               disabled (0),
               enabled (1)
               }
   MAX-ACCESS  read-write
   STATUS      current
   DESCRIPTION
      "Path: tunnels.editConf.l2tpTunnels.bridging.learning

       Possibilities:
               disabled   (0)
               enabled   (1)"
   ::= {er1645v2TvTmplCfgEntry 456130560}

er1645v2TvTmplCfgBridgingMaxCacheSize OBJECT-TYPE
   SYNTAX      INTEGER
               {
               unlimited (0)
               }
   MAX-ACCESS  read-write
   STATUS      current
   DESCRIPTION
      "Path: tunnels.editConf.l2tpTunnels.bridging.maxCacheSize

       Possibilities:
               unlimited   (0)"
   ::= {er1645v2TvTmplCfgEntry 456392704}

er1645v2TvTmplCfgBridgingRelearnDropOnRelearn OBJECT-TYPE
   SYNTAX      INTEGER
               {
               disabled (0),
               enabled (1)
               }
   MAX-ACCESS  read-write
   STATUS      current
   DESCRIPTION
      "Path: tunnels.editConf.l2tpTunnels.bridging.relearn.dropOnRelearn

       Possibilities:
               disabled   (0)
               enabled   (1)"
   ::= {er1645v2TvTmplCfgEntry 456655872}

er1645v2TvTmplCfgBridgingRelearnShutdownThreshold OBJECT-TYPE
   SYNTAX      Integer32
   MAX-ACCESS  read-write
   STATUS      current
   DESCRIPTION
      "Path: tunnels.editConf.l2tpTunnels.bridging.relearn.shutdownThreshold"
   ::= {er1645v2TvTmplCfgEntry 456656896}

er1645v2TvTmplCfgBridgingRelearnShutdownTime OBJECT-TYPE
   SYNTAX      TimeTicks
   MAX-ACCESS  read-write
   STATUS      current
   DESCRIPTION
      "Path: tunnels.editConf.l2tpTunnels.bridging.relearn.shutdownTime

       Time in centi-second."
   ::= {er1645v2TvTmplCfgEntry 456657920}

er1645v2TvTmplCfgBridgingRelearnLoopDetection OBJECT-TYPE
   SYNTAX      INTEGER
               {
               disabled (0),
               passive (1),
               active (2)
               }
   MAX-ACCESS  read-write
   STATUS      current
   DESCRIPTION
      "Path: tunnels.editConf.l2tpTunnels.bridging.relearn.loopDetection

       Possibilities:
               disabled   (0)
               passive   (1)
               active   (2)"
   ::= {er1645v2TvTmplCfgEntry 456658944}

er1645v2TvTmplCfgBridgingRelearnLoopDetectionInterval OBJECT-TYPE
   SYNTAX      TimeTicks
   MAX-ACCESS  read-write
   STATUS      current
   DESCRIPTION
      "Path: tunnels.editConf.l2tpTunnels.bridging.relearn.loopDetectionInterval

       Time in centi-second."
   ::= {er1645v2TvTmplCfgEntry 456659968}

er1645v2TvTmplCfgBridgingVlanMemberShip OBJECT-TYPE
   SYNTAX      INTEGER
               {
               all (0),
               none (1),
               grouped (2)
               }
   MAX-ACCESS  read-write
   STATUS      current
   DESCRIPTION
      "Path: tunnels.editConf.l2tpTunnels.bridging.vlanMemberShip

       Possibilities:
               all   (0)
               none   (1)
               grouped   (2)"
   ::= {er1645v2TvTmplCfgEntry 457965568}

er1645v2TvTmplCfgBridgingVlTUntaggedAction OBJECT-TYPE
   SYNTAX      INTEGER
               {
               discard (0),
               accept (1),
               tag (2)
               }
   MAX-ACCESS  read-write
   STATUS      current
   DESCRIPTION
      "Path: tunnels.editConf.l2tpTunnels.bridging.vlanTagging.untagged.action

       Possibilities:
               discard   (0)
               accept   (1)
               tag   (2)"
   ::= {er1645v2TvTmplCfgEntry 459055104}

er1645v2TvTmplCfgBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.l2tpTunnels.bridging.vlanTagging.untagged.tagInfo.tpid

       Possibilities:
               dot1Q   (33024)
               dot1ad   (34984)
               0x9100   (37120)
               0x9200   (37376)
               0x9300   (37632)"
   ::= {er1645v2TvTmplCfgEntry 459059712}

er1645v2TvTmplCfgBridgingVlTUntaggedTagInfoVid OBJECT-TYPE
   SYNTAX      Integer32
   MAX-ACCESS  read-write
   STATUS      current
   DESCRIPTION
      "Path: tunnels.editConf.l2tpTunnels.bridging.vlanTagging.untagged.tagInfo.vid"
   ::= {er1645v2TvTmplCfgEntry 459060224}

er1645v2TvTmplCfgBridgingVlTUnknownVlansAction OBJECT-TYPE
   SYNTAX      INTEGER
               {
               discard (0),
               accept (1),
               tag (2)
               }
   MAX-ACCESS  read-write
   STATUS      current
   DESCRIPTION
      "Path: tunnels.editConf.l2tpTunnels.bridging.vlanTagging.unknownVlans.action

       Possibilities:
               discard   (0)
               accept   (1)
               tag   (2)"
   ::= {er1645v2TvTmplCfgEntry 459120640}

er1645v2TvTmplCfgBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.l2tpTunnels.bridging.vlanTagging.unknownVlans.tagInfo.tpid

       Possibilities:
               dot1Q   (33024)
               dot1ad   (34984)
               0x9100   (37120)
               0x9200   (37376)
               0x9300   (37632)"
   ::= {er1645v2TvTmplCfgEntry 459125248}

er1645v2TvTmplCfgBridgingVlTUnknownVlansTagInfoVid OBJECT-TYPE
   SYNTAX      Integer32
   MAX-ACCESS  read-write
   STATUS      current
   DESCRIPTION
      "Path: tunnels.editConf.l2tpTunnels.bridging.vlanTagging.unknownVlans.tagInfo.vid"
   ::= {er1645v2TvTmplCfgEntry 459125760}

er1645v2TvTmplCfgBridgingDot1adType OBJECT-TYPE
   SYNTAX      INTEGER
               {
               slOPTg (0),
               cPort (4),
               sPort (1),
               nni (2)
               }
   MAX-ACCESS  read-write
   STATUS      current
   DESCRIPTION
      "Path: tunnels.editConf.l2tpTunnels.bridging.dot1ad.type

       Possibilities:
               <OPT>   (0)
               cPort   (4)
               sPort   (1)
               nni   (2)"
   ::= {er1645v2TvTmplCfgEntry 460850176}

er1645v2TvTmplCfgBridgingPriority OBJECT-TYPE
   SYNTAX      Integer32
   MAX-ACCESS  read-write
   STATUS      current
   DESCRIPTION
      "Path: tunnels.editConf.l2tpTunnels.bridging.priority"
   ::= {er1645v2TvTmplCfgEntry 453509120}

er1645v2TvTmplCfgBridgingPathCost OBJECT-TYPE
   SYNTAX      Integer32
   MAX-ACCESS  read-write
   STATUS      current
   DESCRIPTION
      "Path: tunnels.editConf.l2tpTunnels.bridging.pathCost"
   ::= {er1645v2TvTmplCfgEntry 453771264}

er1645v2TvTmplCfgBridgingInternalPathCost OBJECT-TYPE
   SYNTAX      Integer32
   MAX-ACCESS  read-write
   STATUS      current
   DESCRIPTION
      "Path: tunnels.editConf.l2tpTunnels.bridging.internalPathCost"
   ::= {er1645v2TvTmplCfgEntry 457703424}

er1645v2TvTmplCfgBridgingTCD OBJECT-TYPE
   SYNTAX      INTEGER
               {
               disabled (0),
               enabled (1)
               }
   MAX-ACCESS  read-write
   STATUS      current
   DESCRIPTION
      "Path: tunnels.editConf.l2tpTunnels.bridging.topologyChangeDetection

       Possibilities:
               disabled   (0)
               enabled   (1)"
   ::= {er1645v2TvTmplCfgEntry 454033408}

er1645v2TvTmplCfgBridgingRestrictedRole OBJECT-TYPE
   SYNTAX      INTEGER
               {
               disabled (0),
               enabled (1)
               }
   MAX-ACCESS  read-write
   STATUS      current
   DESCRIPTION
      "Path: tunnels.editConf.l2tpTunnels.bridging.restrictedRole

       Possibilities:
               disabled   (0)
               enabled   (1)"
   ::= {er1645v2TvTmplCfgEntry 458227712}

er1645v2TvTmplCfgBridgingAdminEdge OBJECT-TYPE
   SYNTAX      INTEGER
               {
               disabled (0),
               enabled (1)
               }
   MAX-ACCESS  read-write
   STATUS      current
   DESCRIPTION
      "Path: tunnels.editConf.l2tpTunnels.bridging.adminEdge

       Possibilities:
               disabled   (0)
               enabled   (1)"
   ::= {er1645v2TvTmplCfgEntry 457179136}

er1645v2TvTmplCfgBridgingOamMacDeviceMac OBJECT-TYPE
   SYNTAX      DisplayString
   MAX-ACCESS  read-write
   STATUS      current
   DESCRIPTION
      "Path: tunnels.editConf.l2tpTunnels.bridging.ethOam.macAddress.deviceMac"
   ::= {er1645v2TvTmplCfgEntry 458506496}

er1645v2TvTmplCfgBridgingOamMacUserMac OBJECT-TYPE
   SYNTAX      OCTET STRING
   MAX-ACCESS  read-write
   STATUS      current
   DESCRIPTION
      "Path: tunnels.editConf.l2tpTunnels.bridging.ethOam.macAddress.userMac

       MAC address."
   ::= {er1645v2TvTmplCfgEntry 458506368}

er1645v2TvTmplCfgBridgingOamMacBridgeMac OBJECT-TYPE
   SYNTAX      DisplayString
   MAX-ACCESS  read-write
   STATUS      current
   DESCRIPTION
      "Path: tunnels.editConf.l2tpTunnels.bridging.ethOam.macAddress.bridgeMac"
   ::= {er1645v2TvTmplCfgEntry 458506432}

er1645v2TvTmplCfgBridgingMgmtInline OBJECT-TYPE
   SYNTAX      INTEGER
               {
               disabled (0),
               enabled (1)
               }
   MAX-ACCESS  read-write
   STATUS      current
   DESCRIPTION
      "Path: tunnels.editConf.l2tpTunnels.bridging.mgmtInline

       Possibilities:
               disabled   (0)
               enabled   (1)"
   ::= {er1645v2TvTmplCfgEntry 458752000}

er1645v2TvTmplCfgBridgingL2ptMode OBJECT-TYPE
   SYNTAX      INTEGER
               {
               disabled (0),
               enabled (1)
               }
   MAX-ACCESS  read-write
   STATUS      current
   DESCRIPTION
      "Path: tunnels.editConf.l2tpTunnels.bridging.l2ProtTunnel.mode

       Possibilities:
               disabled   (0)
               enabled   (1)"
   ::= {er1645v2TvTmplCfgEntry 459292672}

er1645v2TvTmplCfgBridgingL2ptProtocols OBJECT-TYPE
   SYNTAX      Integer32
   MAX-ACCESS  read-write
   STATUS      current
   DESCRIPTION
      "Path: tunnels.editConf.l2tpTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TvTmplCfgEntry 459309056}

er1645v2TvTmplCfgBridgingL2ptDestMac OBJECT-TYPE
   SYNTAX      OCTET STRING
   MAX-ACCESS  read-write
   STATUS      current
   DESCRIPTION
      "Path: tunnels.editConf.l2tpTunnels.bridging.l2ProtTunnel.destinationMac

       MAC address."
   ::= {er1645v2TvTmplCfgEntry 459325440}

er1645v2TvTmplCfgBridgingL2ptCos OBJECT-TYPE
   SYNTAX      INTEGER
               {
               unchanged (255)
               }
   MAX-ACCESS  read-write
   STATUS      current
   DESCRIPTION
      "Path: tunnels.editConf.l2tpTunnels.bridging.l2ProtTunnel.cos

       Possibilities:
               unchanged   (255)"
   ::= {er1645v2TvTmplCfgEntry 459341824}

er1645v2TvTmplCfgBridgingL2ptDropThrStp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.stp

       unit name = packets/sec

       Possibilities:
               unlimited   (0)"
   ::= {er1645v2TvTmplCfgEntry 459358272}

er1645v2TvTmplCfgBridgingL2ptDropThrLldp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.lldp

       unit name = packets/sec

       Possibilities:
               unlimited   (0)"
   ::= {er1645v2TvTmplCfgEntry 459358336}

er1645v2TvTmplCfgBridgingL2ptDropThrOam OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.oam

       unit name = packets/sec

       Possibilities:
               unlimited   (0)"
   ::= {er1645v2TvTmplCfgEntry 459358400}

er1645v2TvTmplCfgBridgingL2ptDropThrCdp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.cdp

       unit name = packets/sec

       Possibilities:
               unlimited   (0)"
   ::= {er1645v2TvTmplCfgEntry 459358464}

er1645v2TvTmplCfgBridgingL2ptDropThrVtp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.vtp

       unit name = packets/sec

       Possibilities:
               unlimited   (0)"
   ::= {er1645v2TvTmplCfgEntry 459358528}

er1645v2TvTmplCfgBridgingL2ptDropThrLacp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.lacp

       unit name = packets/sec

       Possibilities:
               unlimited   (0)"
   ::= {er1645v2TvTmplCfgEntry 459358592}

er1645v2TvTmplCfgBridgingL2ptDropThrEfmOam OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.efmOam

       unit name = packets/sec

       Possibilities:
               unlimited   (0)"
   ::= {er1645v2TvTmplCfgEntry 459358656}

er1645v2TvTmplCfgBridgingL2ptDropThrPvst OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.pvst

       unit name = packets/sec

       Possibilities:
               unlimited   (0)"
   ::= {er1645v2TvTmplCfgEntry 459358720}

er1645v2TvTmplCfgBridgingL2ptDropThrMmrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.mmrp

       unit name = packets/sec

       Possibilities:
               unlimited   (0)"
   ::= {er1645v2TvTmplCfgEntry 459358784}

er1645v2TvTmplCfgBridgingL2ptDropThrMvrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.mvrp

       unit name = packets/sec

       Possibilities:
               unlimited   (0)"
   ::= {er1645v2TvTmplCfgEntry 459358848}

er1645v2TvTmplCfgBridgingL2ptDropThrGvrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.gvrp

       unit name = packets/sec

       Possibilities:
               unlimited   (0)"
   ::= {er1645v2TvTmplCfgEntry 459358912}

er1645v2TvTmplCfgBridgingL2ptDropThrGmrp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.gmrp

       unit name = packets/sec

       Possibilities:
               unlimited   (0)"
   ::= {er1645v2TvTmplCfgEntry 459358976}

er1645v2TvTmplCfgBridgingL2ptDropThrDtp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.dtp

       unit name = packets/sec

       Possibilities:
               unlimited   (0)"
   ::= {er1645v2TvTmplCfgEntry 459359040}

er1645v2TvTmplCfgBridgingL2ptDropThrPagp OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.pagp

       unit name = packets/sec

       Possibilities:
               unlimited   (0)"
   ::= {er1645v2TvTmplCfgEntry 459359104}

er1645v2TvTmplCfgBridgingL2ptDropThrUdld OBJECT-TYPE
   SYNTAX      INTEGER
               {
               unlimited (0)
               }
   UNITS       "packets/sec"
   MAX-ACCESS  read-write
   STATUS      current
   DESCRIPTION
      "Path: tunnels.editConf.l2tpTunnels.bridging.l2ProtTunnel.dropThresholds.udld

       unit name = packets/sec

       Possibilities:
               unlimited   (0)"
   ::= {er1645v2TvTmplCfgEntry 459359168}

er1645v2TvTmplCfgVirtEthernetVirtualEthernet OBJECT-TYPE
   SYNTAX      DisplayString
   MAX-ACCESS  read-write
   STATUS      current
   DESCRIPTION
      "Path: tunnels.editConf.l2tpTunnels.virtEthernet.virtualEthernet"
   ::= {er1645v2TvTmplCfgEntry 151060480}

er1645v2TvTmplCfgEncapsulation OBJECT-TYPE
   SYNTAX      INTEGER
               {
               l2tp (1),
               l2tpV3 (2),
               l2tpV3Udp (3),
               l2tpV3Manual (18),
               l2tpV3ManualUdp (19)
               }
   MAX-ACCESS  read-write
   STATUS      current
   DESCRIPTION
      "Path: tunnels.editConf.l2tpTunnels.encapsulation

       Possibilities:
               l2tp   (1)
               l2tpV3   (2)
               l2tpV3Udp   (3)
               l2tpV3Manual   (18)
               l2tpV3ManualUdp   (19)"
   ::= {er1645v2TvTmplCfgEntry 587202560}

er1645v2TvTmplCfgL2tpVrfRouter OBJECT-TYPE
   SYNTAX      DisplayString
   MAX-ACCESS  read-write
   STATUS      current
   DESCRIPTION
      "Path: tunnels.editConf.l2tpTunnels.l2tp.vrfRouter"
   ::= {er1645v2TvTmplCfgEntry 307757056}

er1645v2TvTmplCfgL2tpLocalIpAddress OBJECT-TYPE
   SYNTAX      IpAddress
   MAX-ACCESS  read-write
   STATUS      current
   DESCRIPTION
      "Path: tunnels.editConf.l2tpTunnels.l2tp.localIpAddress"
   ::= {er1645v2TvTmplCfgEntry 302120960}

er1645v2TvTmplCfgL2tpLocalInterface OBJECT-TYPE
   SYNTAX      DisplayString
   MAX-ACCESS  read-write
   STATUS      current
   DESCRIPTION
      "Path: tunnels.editConf.l2tpTunnels.l2tp.localInterface"
   ::= {er1645v2TvTmplCfgEntry 305135616}

er1645v2TvTmplCfgL2tpRemoteIpAddress OBJECT-TYPE
   SYNTAX      IpAddress
   MAX-ACCESS  read-write
   STATUS      current
   DESCRIPTION
      "Path: tunnels.editConf.l2tpTunnels.l2tp.remoteIpAddress"
   ::= {er1645v2TvTmplCfgEntry 302252032}

er1645v2TvTmplCfgL2tpRemoteDnsName OBJECT-TYPE
   SYNTAX      DisplayString
   MAX-ACCESS  read-write
   STATUS      current
   DESCRIPTION
      "Path: tunnels.editConf.l2tpTunnels.l2tp.remoteDnsName"
   ::= {er1645v2TvTmplCfgEntry 305790976}

er1645v2TvTmplCfgL2tpAuthen OBJECT-TYPE
   SYNTAX      INTEGER
               {
               disabled (0),
               chap (1),
               pap (2),
               chapOrPap (3),
               msChap (4),
               msChapV2 (5)
               }
   MAX-ACCESS  read-write
   STATUS      current
   DESCRIPTION
      "Path: tunnels.editConf.l2tpTunnels.l2tp.pppAuthentication

       Possibilities:
               disabled   (0)
               chap   (1)
               pap   (2)
               chapOrPap   (3)
               msChap   (4)
               msChapV2   (5)"
   ::= {er1645v2TvTmplCfgEntry 303693824}

er1645v2TvTmplCfgL2tpPppNam OBJECT-TYPE
   SYNTAX      DisplayString
   MAX-ACCESS  read-write
   STATUS      current
   DESCRIPTION
      "Path: tunnels.editConf.l2tpTunnels.l2tp.pppSessionName"
   ::= {er1645v2TvTmplCfgEntry 304611328}

er1645v2TvTmplCfgL2tpPppSec OBJECT-TYPE
   SYNTAX      DisplayString
   MAX-ACCESS  read-write
   STATUS      current
   DESCRIPTION
      "Path: tunnels.editConf.l2tpTunnels.l2tp.pppSessionSecret"
   ::= {er1645v2TvTmplCfgEntry 304742400}

er1645v2TvTmplCfgL2tpEncMPppSec OBJECT-TYPE
   SYNTAX      INTEGER
               {
               none (1),
               encrypt (2),
               encType1 (3),
               invalid (128)
               }
   MAX-ACCESS  read-write
   STATUS      current
   DESCRIPTION
      "Path: tunnels.editConf.l2tpTunnels.l2tp.encModePppSessionSecret

       Possibilities:
               none   (1)
               encrypt   (2)
               encType1   (3)
               invalid   (128)"
   ::= {er1645v2TvTmplCfgEntry 304873472}

er1645v2TvTmplCfgL2tpEncPppSec OBJECT-TYPE
   SYNTAX      DisplayString
   MAX-ACCESS  read-write
   STATUS      current
   DESCRIPTION
      "Path: tunnels.editConf.l2tpTunnels.l2tp.encPppSessionSecret"
   ::= {er1645v2TvTmplCfgEntry 305004544}

er1645v2TvTmplCfgL2tpLnkMOperation OBJECT-TYPE
   SYNTAX      INTEGER
               {
               disabled (0),
               enabled (1)
               }
   MAX-ACCESS  read-write
   STATUS      current
   DESCRIPTION
      "Path: tunnels.editConf.l2tpTunnels.l2tp.linkMonitoring.operation

       Possibilities:
               disabled   (0)
               enabled   (1)"
   ::= {er1645v2TvTmplCfgEntry 305922560}

er1645v2TvTmplCfgL2tpLnkMInterval OBJECT-TYPE
   SYNTAX      TimeTicks
   MAX-ACCESS  read-write
   STATUS      current
   DESCRIPTION
      "Path: tunnels.editConf.l2tpTunnels.l2tp.linkMonitoring.interval

       Time in centi-second."
   ::= {er1645v2TvTmplCfgEntry 305923072}

er1645v2TvTmplCfgL2tpLnkMRepTimeOut OBJECT-TYPE
   SYNTAX      TimeTicks
   MAX-ACCESS  read-write
   STATUS      current
   DESCRIPTION
      "Path: tunnels.editConf.l2tpTunnels.l2tp.linkMonitoring.replyTimeOut

       Time in centi-second."
   ::= {er1645v2TvTmplCfgEntry 305923584}

er1645v2TvTmplCfgL2tpLnkMFailsPrmt OBJECT-TYPE
   SYNTAX      Integer32
   MAX-ACCESS  read-write
   STATUS      current
   DESCRIPTION
      "Path: tunnels.editConf.l2tpTunnels.l2tp.linkMonitoring.failsPermitted"
   ::= {er1645v2TvTmplCfgEntry 305924096}

er1645v2TvTmplCfgL2tpType OBJECT-TYPE
   SYNTAX      INTEGER
               {
               outgoingDial (0),
               outgoingLeasedLine (1),
               incoming (2)
               }
   MAX-ACCESS  read-write
   STATUS      current
   DESCRIPTION
      "Path: tunnels.editConf.l2tpTunnels.l2tp.type

       Possibilities:
               outgoingDial   (0)
               outgoingLeasedLine   (1)
               incoming   (2)"
   ::= {er1645v2TvTmplCfgEntry 303824896}

er1645v2TvTmplCfgL2tpDataseqnr OBJECT-TYPE
   SYNTAX      INTEGER
               {
               off (0),
               on (1)
               }
   MAX-ACCESS  read-write
   STATUS      current
   DESCRIPTION
      "Path: tunnels.editConf.l2tpTunnels.l2tp.dataChannelSequenceNumbering

       Possibilities:
               off   (0)
               on   (1)"
   ::= {er1645v2TvTmplCfgEntry 302383104}

er1645v2TvTmplCfgL2tpKeepaliveTO OBJECT-TYPE
   SYNTAX      Integer32
   MAX-ACCESS  read-write
   STATUS      current
   DESCRIPTION
      "Path: tunnels.editConf.l2tpTunnels.l2tp.keepAliveTimeOut"
   ::= {er1645v2TvTmplCfgEntry 302514176}

er1645v2TvTmplCfgL2tpNoTraffT0 OBJECT-TYPE
   SYNTAX      Integer32
   MAX-ACCESS  read-write
   STATUS      current
   DESCRIPTION
      "Path: tunnels.editConf.l2tpTunnels.l2tp.noTrafficTimeOut"
   ::= {er1645v2TvTmplCfgEntry 304218112}

er1645v2TvTmplCfgL2tpMode OBJECT-TYPE
   SYNTAX      INTEGER
               {
               lac (1),
               lns (2),
               auto (3)
               }
   MAX-ACCESS  read-write
   STATUS      current
   DESCRIPTION
      "Path: tunnels.editConf.l2tpTunnels.l2tp.l2tpMode

       Possibilities:
               lac   (1)
               lns   (2)
               auto   (3)"
   ::= {er1645v2TvTmplCfgEntry 302645248}

er1645v2TvTmplCfgL2tpAuth OBJECT-TYPE
   SYNTAX      INTEGER
               {
               off (0),
               on (1)
               }
   MAX-ACCESS  read-write
   STATUS      current
   DESCRIPTION
      "Path: tunnels.editConf.l2tpTunnels.l2tp.tunnelAuthentication

       Possibilities:
               off   (0)
               on   (1)"
   ::= {er1645v2TvTmplCfgEntry 302776320}

er1645v2TvTmplCfgL2tpSecret OBJECT-TYPE
   SYNTAX      DisplayString
   MAX-ACCESS  read-write
   STATUS      current
   DESCRIPTION
      "Path: tunnels.editConf.l2tpTunnels.l2tp.tunnelSecret"
   ::= {er1645v2TvTmplCfgEntry 302907392}

er1645v2TvTmplCfgL2tpTos OBJECT-TYPE
   SYNTAX      INTEGER
               {
               off (0),
               on (1)
               }
   MAX-ACCESS  read-write
   STATUS      current
   DESCRIPTION
      "Path: tunnels.editConf.l2tpTunnels.l2tp.copyTos

       Possibilities:
               off   (0)
               on   (1)"
   ::= {er1645v2TvTmplCfgEntry 303955968}

er1645v2TvTmplCfgL2tpRetrans OBJECT-TYPE
   SYNTAX      Integer32
   MAX-ACCESS  read-write
   STATUS      current
   DESCRIPTION
      "Path: tunnels.editConf.l2tpTunnels.l2tp.maxNrOfRetransmissions"
   ::= {er1645v2TvTmplCfgEntry 303038464}

er1645v2TvTmplCfgL2tpTransmitws OBJECT-TYPE
   SYNTAX      Integer32
   MAX-ACCESS  read-write
   STATUS      current
   DESCRIPTION
      "Path: tunnels.editConf.l2tpTunnels.l2tp.transmitWindowSize"
   ::= {er1645v2TvTmplCfgEntry 303169536}

er1645v2TvTmplCfgL2tpRcsws OBJECT-TYPE
   SYNTAX      Integer32
   MAX-ACCESS  read-write
   STATUS      current
   DESCRIPTION
      "Path: tunnels.editConf.l2tpTunnels.l2tp.receiveWindowSize"
   ::= {er1645v2TvTmplCfgEntry 303300608}

er1645v2TvTmplCfgL2tpUdpcheck OBJECT-TYPE
   SYNTAX      INTEGER
               {
               off (0),
               on (1)
               }
   MAX-ACCESS  read-write
   STATUS      current
   DESCRIPTION
      "Path: tunnels.editConf.l2tpTunnels.l2tp.udpChecksum

       Possibilities:
               off   (0)
               on   (1)"
   ::= {er1645v2TvTmplCfgEntry 303431680}

er1645v2TvTmplCfgL2tpCalledNr OBJECT-TYPE
   SYNTAX      DisplayString
   MAX-ACCESS  read-write
   STATUS      current
   DESCRIPTION
      "Path: tunnels.editConf.l2tpTunnels.l2tp.calledNr"
   ::= {er1645v2TvTmplCfgEntry 303562752}

er1645v2TvTmplCfgL2tpSpeed OBJECT-TYPE
   SYNTAX      Integer32
   MAX-ACCESS  read-write
   STATUS      current
   DESCRIPTION
      "Path: tunnels.editConf.l2tpTunnels.l2tp.speed"
   ::= {er1645v2TvTmplCfgEntry 315621376}

er1645v2TvTmplCfgL2tpMtu OBJECT-TYPE
   SYNTAX      Integer32
   MAX-ACCESS  read-write
   STATUS      current
   DESCRIPTION
      "Path: tunnels.editConf.l2tpTunnels.l2tp.mtu"
   ::= {er1645v2TvTmplCfgEntry 304349184}

er1645v2TvTmplCfgL2tpHostName OBJECT-TYPE
   SYNTAX      DisplayString
   MAX-ACCESS  read-write
   STATUS      current
   DESCRIPTION
      "Path: tunnels.editConf.l2tpTunnels.l2tp.hostName"
   ::= {er1645v2TvTmplCfgEntry 304480256}

er1645v2TvTmplCfgL2tpV3VrfRouter OBJECT-TYPE
   SYNTAX      DisplayString
   MAX-ACCESS  read-write
   STATUS      current
   DESCRIPTION
      "Path: tunnels.editConf.l2tpTunnels.l2tpV3.vrfRouter"
   ::= {er1645v2TvTmplCfgEntry 324534272}

er1645v2TvTmplCfgL2tpV3LocalIpAddress OBJECT-TYPE
   SYNTAX      IpAddress
   MAX-ACCESS  read-write
   STATUS      current
   DESCRIPTION
      "Path: tunnels.editConf.l2tpTunnels.l2tpV3.localIpAddress"
   ::= {er1645v2TvTmplCfgEntry 318898176}

er1645v2TvTmplCfgL2tpV3LocalInterface OBJECT-TYPE
   SYNTAX      DisplayString
   MAX-ACCESS  read-write
   STATUS      current
   DESCRIPTION
      "Path: tunnels.editConf.l2tpTunnels.l2tpV3.localInterface"
   ::= {er1645v2TvTmplCfgEntry 321912832}

er1645v2TvTmplCfgL2tpV3RemoteIpAddress OBJECT-TYPE
   SYNTAX      IpAddress
   MAX-ACCESS  read-write
   STATUS      current
   DESCRIPTION
      "Path: tunnels.editConf.l2tpTunnels.l2tpV3.remoteIpAddress"
   ::= {er1645v2TvTmplCfgEntry 319029248}

er1645v2TvTmplCfgL2tpV3RemoteDnsName OBJECT-TYPE
   SYNTAX      DisplayString
   MAX-ACCESS  read-write
   STATUS      current
   DESCRIPTION
      "Path: tunnels.editConf.l2tpTunnels.l2tpV3.remoteDnsName"
   ::= {er1645v2TvTmplCfgEntry 322568192}

er1645v2TvTmplCfgL2tpV3Type OBJECT-TYPE
   SYNTAX      INTEGER
               {
               outgoingDial (0),
               outgoingLeasedLine (1),
               incoming (2)
               }
   MAX-ACCESS  read-write
   STATUS      current
   DESCRIPTION
      "Path: tunnels.editConf.l2tpTunnels.l2tpV3.type

       Possibilities:
               outgoingDial   (0)
               outgoingLeasedLine   (1)
               incoming   (2)"
   ::= {er1645v2TvTmplCfgEntry 320602112}

er1645v2TvTmplCfgL2tpV3KeepaliveTO OBJECT-TYPE
   SYNTAX      Integer32
   MAX-ACCESS  read-write
   STATUS      current
   DESCRIPTION
      "Path: tunnels.editConf.l2tpTunnels.l2tpV3.keepAliveTimeOut"
   ::= {er1645v2TvTmplCfgEntry 319291392}

er1645v2TvTmplCfgL2tpV3NoTraffT0 OBJECT-TYPE
   SYNTAX      Integer32
   MAX-ACCESS  read-write
   STATUS      current
   DESCRIPTION
      "Path: tunnels.editConf.l2tpTunnels.l2tpV3.noTrafficTimeOut"
   ::= {er1645v2TvTmplCfgEntry 320995328}

er1645v2TvTmplCfgL2tpV3Mode OBJECT-TYPE
   SYNTAX      INTEGER
               {
               lac (1),
               lns (2),
               auto (3)
               }
   MAX-ACCESS  read-write
   STATUS      current
   DESCRIPTION
      "Path: tunnels.editConf.l2tpTunnels.l2tpV3.l2tpMode

       Possibilities:
               lac   (1)
               lns   (2)
               auto   (3)"
   ::= {er1645v2TvTmplCfgEntry 319422464}

er1645v2TvTmplCfgL2tpV3Auth OBJECT-TYPE
   SYNTAX      INTEGER
               {
               off (0),
               on (1)
               }
   MAX-ACCESS  read-write
   STATUS      current
   DESCRIPTION
      "Path: tunnels.editConf.l2tpTunnels.l2tpV3.tunnelAuthentication

       Possibilities:
               off   (0)
               on   (1)"
   ::= {er1645v2TvTmplCfgEntry 319553536}

er1645v2TvTmplCfgL2tpV3Secret OBJECT-TYPE
   SYNTAX      DisplayString
   MAX-ACCESS  read-write
   STATUS      current
   DESCRIPTION
      "Path: tunnels.editConf.l2tpTunnels.l2tpV3.tunnelSecret"
   ::= {er1645v2TvTmplCfgEntry 319684608}

er1645v2TvTmplCfgL2tpV3Tos OBJECT-TYPE
   SYNTAX      INTEGER
               {
               off (0),
               on (1)
               }
   MAX-ACCESS  read-write
   STATUS      current
   DESCRIPTION
      "Path: tunnels.editConf.l2tpTunnels.l2tpV3.copyTos

       Possibilities:
               off   (0)
               on   (1)"
   ::= {er1645v2TvTmplCfgEntry 320733184}

er1645v2TvTmplCfgL2tpV3Retrans OBJECT-TYPE
   SYNTAX      Integer32
   MAX-ACCESS  read-write
   STATUS      current
   DESCRIPTION
      "Path: tunnels.editConf.l2tpTunnels.l2tpV3.maxNrOfRetransmissions"
   ::= {er1645v2TvTmplCfgEntry 319815680}

er1645v2TvTmplCfgL2tpV3Transmitws OBJECT-TYPE
   SYNTAX      Integer32
   MAX-ACCESS  read-write
   STATUS      current
   DESCRIPTION
      "Path: tunnels.editConf.l2tpTunnels.l2tpV3.transmitWindowSize"
   ::= {er1645v2TvTmplCfgEntry 319946752}

er1645v2TvTmplCfgL2tpV3Rcsws OBJECT-TYPE
   SYNTAX      Integer32
   MAX-ACCESS  read-write
   STATUS      current
   DESCRIPTION
      "Path: tunnels.editConf.l2tpTunnels.l2tpV3.receiveWindowSize"
   ::= {er1645v2TvTmplCfgEntry 320077824}

er1645v2TvTmplCfgL2tpV3Udpcheck OBJECT-TYPE
   SYNTAX      INTEGER
               {
               off (0),
               on (1)
               }
   MAX-ACCESS  read-write
   STATUS      current
   DESCRIPTION
      "Path: tunnels.editConf.l2tpTunnels.l2tpV3.udpChecksum

       Possibilities:
               off   (0)
               on   (1)"
   ::= {er1645v2TvTmplCfgEntry 320208896}

er1645v2TvTmplCfgL2tpV3CalledNr OBJECT-TYPE
   SYNTAX      DisplayString
   MAX-ACCESS  read-write
   STATUS      current
   DESCRIPTION
      "Path: tunnels.editConf.l2tpTunnels.l2tpV3.calledNr"
   ::= {er1645v2TvTmplCfgEntry 320339968}

er1645v2TvTmplCfgL2tpV3Speed OBJECT-TYPE
   SYNTAX      Integer32
   MAX-ACCESS  read-write
   STATUS      current
   DESCRIPTION
      "Path: tunnels.editConf.l2tpTunnels.l2tpV3.speed"
   ::= {er1645v2TvTmplCfgEntry 332398592}

er1645v2TvTmplCfgL2tpV3Mtu OBJECT-TYPE
   SYNTAX      Integer32
   MAX-ACCESS  read-write
   STATUS      current
   DESCRIPTION
      "Path: tunnels.editConf.l2tpTunnels.l2tpV3.mtu"
   ::= {er1645v2TvTmplCfgEntry 321126400}

er1645v2TvTmplCfgL2tpV3HostName OBJECT-TYPE
   SYNTAX      DisplayString
   MAX-ACCESS  read-write
   STATUS      current
   DESCRIPTION
      "Path: tunnels.editConf.l2tpTunnels.l2tpV3.hostName"
   ::= {er1645v2TvTmplCfgEntry 321257472}

er1645v2TvTmplCfgL2tpV3Hidden OBJECT-TYPE
   SYNTAX      INTEGER
               {
               off (0),
               on (1)
               }
   MAX-ACCESS  read-write
   STATUS      current
   DESCRIPTION
      "Path: tunnels.editConf.l2tpTunnels.l2tpV3.hidden

       Possibilities:
               off   (0)
               on   (1)"
   ::= {er1645v2TvTmplCfgEntry 322830336}

er1645v2TvTmplCfgL2tpV3RemoteEndId OBJECT-TYPE
   SYNTAX      DisplayString
   MAX-ACCESS  read-write
   STATUS      current
   DESCRIPTION
      "Path: tunnels.editConf.l2tpTunnels.l2tpV3.remoteEndId"
   ::= {er1645v2TvTmplCfgEntry 324009984}

er1645v2TvTmplCfgL2tpV3RouterId OBJECT-TYPE
   SYNTAX      IpAddress
   MAX-ACCESS  read-write
   STATUS      current
   DESCRIPTION
      "Path: tunnels.editConf.l2tpTunnels.l2tpV3.routerId"
   ::= {er1645v2TvTmplCfgEntry 324141056}

er1645v2TvTmplCfgL2tpV3PseudowireType OBJECT-TYPE
   SYNTAX      INTEGER
               {
               ethernet (5),
               ethernetVlan (4),
               ipTransport (11)
               }
   MAX-ACCESS  read-write
   STATUS      current
   DESCRIPTION
      "Path: tunnels.editConf.l2tpTunnels.l2tpV3.pseudowireType

       Possibilities:
               ethernet   (5)
               ethernetVlan   (4)
               ipTransport   (11)"
   ::= {er1645v2TvTmplCfgEntry 324272128}

er1645v2TvTmplCfgL2tpV3Cookie OBJECT-TYPE
   SYNTAX      INTEGER
               {
               off (0),
               s4sbytes (4),
               s8sbytes (8)
               }
   MAX-ACCESS  read-write
   STATUS      current
   DESCRIPTION
      "Path: tunnels.editConf.l2tpTunnels.l2tpV3.cookie

       Possibilities:
               off   (0)
               4 bytes   (4)
               8 bytes   (8)"
   ::= {er1645v2TvTmplCfgEntry 324665344}

er1645v2TvTmplCfgL2tpV3Compatibility OBJECT-TYPE
   SYNTAX      INTEGER
               {
               off (0),
               cisco (1)
               }
   MAX-ACCESS  read-write
   STATUS      current
   DESCRIPTION
      "Path: tunnels.editConf.l2tpTunnels.l2tpV3.compatibility

       Possibilities:
               off   (0)
               cisco   (1)"
   ::= {er1645v2TvTmplCfgEntry 324403200}

er1645v2TvTmplCfgL2tpV3ManualVrfRouter OBJECT-TYPE
   SYNTAX      DisplayString
   MAX-ACCESS  read-write
   STATUS      current
   DESCRIPTION
      "Path: tunnels.editConf.l2tpTunnels.l2tpV3Manual.vrfRouter"
   ::= {er1645v2TvTmplCfgEntry 341311488}

er1645v2TvTmplCfgL2tpV3ManualLocalIpAddress OBJECT-TYPE
   SYNTAX      IpAddress
   MAX-ACCESS  read-write
   STATUS      current
   DESCRIPTION
      "Path: tunnels.editConf.l2tpTunnels.l2tpV3Manual.localIpAddress"
   ::= {er1645v2TvTmplCfgEntry 335675392}

er1645v2TvTmplCfgL2tpV3ManualRemoteIpAddress OBJECT-TYPE
   SYNTAX      IpAddress
   MAX-ACCESS  read-write
   STATUS      current
   DESCRIPTION
      "Path: tunnels.editConf.l2tpTunnels.l2tpV3Manual.remoteIpAddress"
   ::= {er1645v2TvTmplCfgEntry 335806464}

er1645v2TvTmplCfgL2tpV3ManualTos OBJECT-TYPE
   SYNTAX      INTEGER
               {
               off (0),
               on (1)
               }
   MAX-ACCESS  read-write
   STATUS      current
   DESCRIPTION
      "Path: tunnels.editConf.l2tpTunnels.l2tpV3Manual.copyTos

       Possibilities:
               off   (0)
               on   (1)"
   ::= {er1645v2TvTmplCfgEntry 337510400}

er1645v2TvTmplCfgL2tpV3ManualUdpcheck OBJECT-TYPE
   SYNTAX      INTEGER
               {
               off (0),
               on (1)
               }
   MAX-ACCESS  read-write
   STATUS      current
   DESCRIPTION
      "Path: tunnels.editConf.l2tpTunnels.l2tpV3Manual.udpChecksum

       Possibilities:
               off   (0)
               on   (1)"
   ::= {er1645v2TvTmplCfgEntry 336986112}

er1645v2TvTmplCfgL2tpV3ManualMtu OBJECT-TYPE
   SYNTAX      Integer32
   MAX-ACCESS  read-write
   STATUS      current
   DESCRIPTION
      "Path: tunnels.editConf.l2tpTunnels.l2tpV3Manual.mtu"
   ::= {er1645v2TvTmplCfgEntry 337903616}

er1645v2TvTmplCfgL2tpV3ManualLocalSessionId OBJECT-TYPE
   SYNTAX      Gauge32
   MAX-ACCESS  read-write
   STATUS      current
   DESCRIPTION
      "Path: tunnels.editConf.l2tpTunnels.l2tpV3Manual.localSessionId

       32 bit unsigned gauge value."
   ::= {er1645v2TvTmplCfgEntry 343408640}

er1645v2TvTmplCfgL2tpV3ManualRemoteSessionId OBJECT-TYPE
   SYNTAX      Gauge32
   MAX-ACCESS  read-write
   STATUS      current
   DESCRIPTION
      "Path: tunnels.editConf.l2tpTunnels.l2tpV3Manual.remoteSessionId

       32 bit unsigned gauge value."
   ::= {er1645v2TvTmplCfgEntry 343539712}

er1645v2TvTmplCfgL2tpV3ManualLcookieOff OBJECT-TYPE
   SYNTAX      DisplayString
   MAX-ACCESS  read-write
   STATUS      current
   DESCRIPTION
      "Path: tunnels.editConf.l2tpTunnels.l2tpV3Manual.localCookie.off"
   ::= {er1645v2TvTmplCfgEntry 343687168}

er1645v2TvTmplCfgL2tpV3ManualLcookie4Bytes OBJECT-TYPE
   SYNTAX      Gauge32
   MAX-ACCESS  read-write
   STATUS      current
   DESCRIPTION
      "Path: tunnels.editConf.l2tpTunnels.l2tpV3Manual.localCookie.4Bytes

       32 bit unsigned gauge value."
   ::= {er1645v2TvTmplCfgEntry 343703552}

er1645v2TvTmplCfgL2tpV3ManualLcookie8BytesHigh OBJECT-TYPE
   SYNTAX      Gauge32
   MAX-ACCESS  read-write
   STATUS      current
   DESCRIPTION
      "Path: tunnels.editConf.l2tpTunnels.l2tpV3Manual.localCookie.8Bytes.high

       32 bit unsigned gauge value."
   ::= {er1645v2TvTmplCfgEntry 343721984}

er1645v2TvTmplCfgL2tpV3ManualLcookie8BytesLow OBJECT-TYPE
   SYNTAX      Gauge32
   MAX-ACCESS  read-write
   STATUS      current
   DESCRIPTION
      "Path: tunnels.editConf.l2tpTunnels.l2tpV3Manual.localCookie.8Bytes.low

       32 bit unsigned gauge value."
   ::= {er1645v2TvTmplCfgEntry 343724032}

er1645v2TvTmplCfgL2tpV3ManualRcookieOff OBJECT-TYPE
   SYNTAX      DisplayString
   MAX-ACCESS  read-write
   STATUS      current
   DESCRIPTION
      "Path: tunnels.editConf.l2tpTunnels.l2tpV3Manual.remoteCookie.off"
   ::= {er1645v2TvTmplCfgEntry 343818240}

er1645v2TvTmplCfgL2tpV3ManualRcookie4Bytes OBJECT-TYPE
   SYNTAX      Gauge32
   MAX-ACCESS  read-write
   STATUS      current
   DESCRIPTION
      "Path: tunnels.editConf.l2tpTunnels.l2tpV3Manual.remoteCookie.4Bytes

       32 bit unsigned gauge value."
   ::= {er1645v2TvTmplCfgEntry 343834624}

er1645v2TvTmplCfgL2tpV3ManualRcookie8BytesHigh OBJECT-TYPE
   SYNTAX      Gauge32
   MAX-ACCESS  read-write
   STATUS      current
   DESCRIPTION
      "Path: tunnels.editConf.l2tpTunnels.l2tpV3Manual.remoteCookie.8Bytes.high

       32 bit unsigned gauge value."
   ::= {er1645v2TvTmplCfgEntry 343853056}

er1645v2TvTmplCfgL2tpV3ManualRcookie8BytesLow OBJECT-TYPE
   SYNTAX      Gauge32
   MAX-ACCESS  read-write
   STATUS      current
   DESCRIPTION
      "Path: tunnels.editConf.l2tpTunnels.l2tpV3Manual.remoteCookie.8Bytes.low

       32 bit unsigned gauge value."
   ::= {er1645v2TvTmplCfgEntry 343855104}

er1645v2TvTmplCfgL2tpV3ManualLocalDataSeq OBJECT-TYPE
   SYNTAX      INTEGER
               {
               off (16),
               on (2)
               }
   MAX-ACCESS  read-write
   STATUS      current
   DESCRIPTION
      "Path: tunnels.editConf.l2tpTunnels.l2tpV3Manual.localDataSeq

       Possibilities:
               off   (16)
               on   (2)"
   ::= {er1645v2TvTmplCfgEntry 343932928}

er1645v2TvTmplCfgL2tpV3ManualRemoteDataSeq OBJECT-TYPE
   SYNTAX      INTEGER
               {
               off (16),
               on (2)
               }
   MAX-ACCESS  read-write
   STATUS      current
   DESCRIPTION
      "Path: tunnels.editConf.l2tpTunnels.l2tpV3Manual.remoteDataSeq

       Possibilities:
               off   (16)
               on   (2)"
   ::= {er1645v2TvTmplCfgEntry 344064000}

er1645v2TvTmplCfgBackupInterface OBJECT-TYPE
   SYNTAX      DisplayString
   MAX-ACCESS  read-write
   STATUS      current
   DESCRIPTION
      "Path: tunnels.editConf.l2tpTunnels.backup.interface"
   ::= {er1645v2TvTmplCfgEntry 536936448}

er1645v2TvTmplCfgBackupTimeOut OBJECT-TYPE
   SYNTAX      Integer32
   MAX-ACCESS  read-write
   STATUS      current
   DESCRIPTION
      "Path: tunnels.editConf.l2tpTunnels.backup.timeOut"
   ::= {er1645v2TvTmplCfgEntry 537067520}

er1645v2TvTmplCfgBackupAutoRetry OBJECT-TYPE
   SYNTAX      INTEGER
               {
               no (0),
               yes (1)
               }
   MAX-ACCESS  read-write
   STATUS      current
   DESCRIPTION
      "Path: tunnels.editConf.l2tpTunnels.backup.autoRetry

       Possibilities:
               no   (0)
               yes   (1)"
   ::= {er1645v2TvTmplCfgEntry 537133056}

er1645v2TvTmplCfgInbBwCir OBJECT-TYPE
   SYNTAX      Integer32
   MAX-ACCESS  read-write
   STATUS      current
   DESCRIPTION
      "Path: tunnels.editConf.l2tpTunnels.inboundBandwidth.cir"
   ::= {er1645v2TvTmplCfgEntry 117506048}

er1645v2TvTmplCfgInbBwTc OBJECT-TYPE
   SYNTAX      INTEGER
               {
               auto (0)
               }
   MAX-ACCESS  read-write
   STATUS      current
   DESCRIPTION
      "Path: tunnels.editConf.l2tpTunnels.inboundBandwidth.tc

       Possibilities:
               auto   (0)"
   ::= {er1645v2TvTmplCfgEntry 117833728}

er1645v2TvTmplCfgInbBwCorrType OBJECT-TYPE
   SYNTAX      INTEGER
               {
               noCorrection (0),
               predefined (1),
               manual (2)
               }
   MAX-ACCESS  read-write
   STATUS      current
   DESCRIPTION
      "Path: tunnels.editConf.l2tpTunnels.inboundBandwidth.correction.type

       Possibilities:
               noCorrection   (0)
               predefined   (1)
               manual   (2)"
   ::= {er1645v2TvTmplCfgEntry 117579776}

er1645v2TvTmplCfgInbBwCorrPredefEncapsFrameRelay OBJECT-TYPE
   SYNTAX      DisplayString
   MAX-ACCESS  read-write
   STATUS      current
   DESCRIPTION
      "Path: tunnels.editConf.l2tpTunnels.inboundBandwidth.correction.predefined.encapsulation.frameRelay"
   ::= {er1645v2TvTmplCfgEntry 117589056}

er1645v2TvTmplCfgInbBwCorrPredefEncapsPpp OBJECT-TYPE
   SYNTAX      DisplayString
   MAX-ACCESS  read-write
   STATUS      current
   DESCRIPTION
      "Path: tunnels.editConf.l2tpTunnels.inboundBandwidth.correction.predefined.encapsulation.ppp"
   ::= {er1645v2TvTmplCfgEntry 117589120}

er1645v2TvTmplCfgInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.l2tpTunnels.inboundBandwidth.correction.predefined.encapsulation.atm.higherLayer

       Possibilities:
               rfc2684   (0)
               ppp   (1)
               pppOverEthernet   (2)"
   ::= {er1645v2TvTmplCfgEntry 117589192}

er1645v2TvTmplCfgInbBwCorrPredefEncapsAtmMp OBJECT-TYPE
   SYNTAX      INTEGER
               {
               llcEncapsulation (0),
               vcMultiplexing (1)
               }
   MAX-ACCESS  read-write
   STATUS      current
   DESCRIPTION
      "Path: tunnels.editConf.l2tpTunnels.inboundBandwidth.correction.predefined.encapsulation.atm.multiProtocol

       Possibilities:
               llcEncapsulation   (0)
               vcMultiplexing   (1)"
   ::= {er1645v2TvTmplCfgEntry 117589200}

er1645v2TvTmplCfgInbBwCorrPredefEncapsHdlc OBJECT-TYPE
   SYNTAX      DisplayString
   MAX-ACCESS  read-write
   STATUS      current
   DESCRIPTION
      "Path: tunnels.editConf.l2tpTunnels.inboundBandwidth.correction.predefined.encapsulation.hdlc"
   ::= {er1645v2TvTmplCfgEntry 117589248}

er1645v2TvTmplCfgInbBwCorrPredefEncapsEfmFs OBJECT-TYPE
   SYNTAX      Integer32
   MAX-ACCESS  read-write
   STATUS      current
   DESCRIPTION
      "Path: tunnels.editConf.l2tpTunnels.inboundBandwidth.correction.predefined.encapsulation.efm.fragmentSize"
   ::= {er1645v2TvTmplCfgEntry 117589320}

er1645v2TvTmplCfgInbBwCorrPredefEncapsEfmIb OBJECT-TYPE
   SYNTAX      Integer32
   MAX-ACCESS  read-write
   STATUS      current
   DESCRIPTION
      "Path: tunnels.editConf.l2tpTunnels.inboundBandwidth.correction.predefined.encapsulation.efm.idleBytes"
   ::= {er1645v2TvTmplCfgEntry 117589328}

er1645v2TvTmplCfgInbBwCorrPredefMode OBJECT-TYPE
   SYNTAX      INTEGER
               {
               routing (0),
               bridging (1)
               }
   MAX-ACCESS  read-write
   STATUS      current
   DESCRIPTION
      "Path: tunnels.editConf.l2tpTunnels.inboundBandwidth.correction.predefined.mode

       Possibilities:
               routing   (0)
               bridging   (1)"
   ::= {er1645v2TvTmplCfgEntry 117590016}

er1645v2TvTmplCfgInbBwCorrManualOverhead OBJECT-TYPE
   SYNTAX      Integer32
   MAX-ACCESS  read-write
   STATUS      current
   DESCRIPTION
      "Path: tunnels.editConf.l2tpTunnels.inboundBandwidth.correction.manual.overhead"
   ::= {er1645v2TvTmplCfgEntry 117596192}

er1645v2TvTmplCfgInbBwCorrManualFrameData OBJECT-TYPE
   SYNTAX      Counter32
   MAX-ACCESS  read-write
   STATUS      current
   DESCRIPTION
      "Path: tunnels.editConf.l2tpTunnels.inboundBandwidth.correction.manual.frameData

       32 bit unsigned wrappable counter."
   ::= {er1645v2TvTmplCfgEntry 117596224}

er1645v2TvTmplCfgInbBwCorrManualFrameHeader OBJECT-TYPE
   SYNTAX      Counter32
   MAX-ACCESS  read-write
   STATUS      current
   DESCRIPTION
      "Path: tunnels.editConf.l2tpTunnels.inboundBandwidth.correction.manual.frameHeader

       32 bit unsigned wrappable counter."
   ::= {er1645v2TvTmplCfgEntry 117596256}

er1645v2TvTmplCfgInbBwMaxFifoQLen OBJECT-TYPE
   SYNTAX      Integer32
   MAX-ACCESS  read-write
   STATUS      current
   DESCRIPTION
      "Path: tunnels.editConf.l2tpTunnels.inboundBandwidth.maxFifoQLen"
   ::= {er1645v2TvTmplCfgEntry 117637120}

er1645v2TvTmplCfgInbBwPriorityPolicy OBJECT-TYPE
   SYNTAX      DisplayString
   MAX-ACCESS  read-write
   STATUS      current
   DESCRIPTION
      "Path: tunnels.editConf.l2tpTunnels.inboundBandwidth.priorityPolicy"
   ::= {er1645v2TvTmplCfgEntry 117702656}

er1645v2TvTmplCfgBandwidthMode OBJECT-TYPE
   SYNTAX      INTEGER
               {
               reshaping (1),
               policing (2),
               policingReshape (3)
               }
   MAX-ACCESS  read-write
   STATUS      current
   DESCRIPTION
      "Path: tunnels.editConf.l2tpTunnels.bandwidth.mode

       Possibilities:
               reshaping   (1)
               policing   (2)
               policingReshape   (3)"
   ::= {er1645v2TvTmplCfgEntry 148897792}

er1645v2TvTmplCfgBandwidthCir OBJECT-TYPE
   SYNTAX      Integer32
   MAX-ACCESS  read-write
   STATUS      current
   DESCRIPTION
      "Path: tunnels.editConf.l2tpTunnels.bandwidth.cir"
   ::= {er1645v2TvTmplCfgEntry 135266304}

er1645v2TvTmplCfgBandwidthEir OBJECT-TYPE
   SYNTAX      Integer32
   MAX-ACCESS  read-write
   STATUS      current
   DESCRIPTION
      "Path: tunnels.editConf.l2tpTunnels.bandwidth.eir"
   ::= {er1645v2TvTmplCfgEntry 141557760}

er1645v2TvTmplCfgBandwidthUnit OBJECT-TYPE
   SYNTAX      INTEGER
               {
               bitssec (1),
               percent (2)
               }
   MAX-ACCESS  read-write
   STATUS      current
   DESCRIPTION
      "Path: tunnels.editConf.l2tpTunnels.bandwidth.unit

       Possibilities:
               bits/sec   (1)
               percent   (2)"
   ::= {er1645v2TvTmplCfgEntry 139460608}

er1645v2TvTmplCfgBandwidthTc OBJECT-TYPE
   SYNTAX      INTEGER
               {
               auto (0)
               }
   MAX-ACCESS  read-write
   STATUS      current
   DESCRIPTION
      "Path: tunnels.editConf.l2tpTunnels.bandwidth.tc

       Possibilities:
               auto   (0)"
   ::= {er1645v2TvTmplCfgEntry 140509184}

er1645v2TvTmplCfgBandwidthTcFactor OBJECT-TYPE
   SYNTAX      INTEGER
               {
               ms (10),
               s100us (1)
               }
   MAX-ACCESS  read-write
   STATUS      current
   DESCRIPTION
      "Path: tunnels.editConf.l2tpTunnels.bandwidth.tcFactor

       Possibilities:
               ms   (10)
               *100us   (1)"
   ::= {er1645v2TvTmplCfgEntry 142606336}

er1645v2TvTmplCfgBandwidthCorrType OBJECT-TYPE
   SYNTAX      INTEGER
               {
               noCorrection (0),
               predefined (1),
               manual (2)
               }
   MAX-ACCESS  read-write
   STATUS      current
   DESCRIPTION
      "Path: tunnels.editConf.l2tpTunnels.bandwidth.correction.type

       Possibilities:
               noCorrection   (0)
               predefined   (1)
               manual   (2)"
   ::= {er1645v2TvTmplCfgEntry 136445952}

er1645v2TvTmplCfgBandwidthCorrPredefEncapsFrameRelay OBJECT-TYPE
   SYNTAX      DisplayString
   MAX-ACCESS  read-write
   STATUS      current
   DESCRIPTION
      "Path: tunnels.editConf.l2tpTunnels.bandwidth.correction.predefined.encapsulation.frameRelay"
   ::= {er1645v2TvTmplCfgEntry 136594432}

er1645v2TvTmplCfgBandwidthCorrPredefEncapsPpp OBJECT-TYPE
   SYNTAX      DisplayString
   MAX-ACCESS  read-write
   STATUS      current
   DESCRIPTION
      "Path: tunnels.editConf.l2tpTunnels.bandwidth.correction.predefined.encapsulation.ppp"
   ::= {er1645v2TvTmplCfgEntry 136595456}

er1645v2TvTmplCfgBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.l2tpTunnels.bandwidth.correction.predefined.encapsulation.atm.higherLayer

       Possibilities:
               rfc2684   (0)
               ppp   (1)
               pppOverEthernet   (2)"
   ::= {er1645v2TvTmplCfgEntry 136596608}

er1645v2TvTmplCfgBandwidthCorrPredefEncapsAtmMp OBJECT-TYPE
   SYNTAX      INTEGER
               {
               llcEncapsulation (0),
               vcMultiplexing (1)
               }
   MAX-ACCESS  read-write
   STATUS      current
   DESCRIPTION
      "Path: tunnels.editConf.l2tpTunnels.bandwidth.correction.predefined.encapsulation.atm.multiProtocol

       Possibilities:
               llcEncapsulation   (0)
               vcMultiplexing   (1)"
   ::= {er1645v2TvTmplCfgEntry 136596736}

er1645v2TvTmplCfgBandwidthCorrPredefEncapsHdlc OBJECT-TYPE
   SYNTAX      DisplayString
   MAX-ACCESS  read-write
   STATUS      current
   DESCRIPTION
      "Path: tunnels.editConf.l2tpTunnels.bandwidth.correction.predefined.encapsulation.hdlc"
   ::= {er1645v2TvTmplCfgEntry 136597504}

er1645v2TvTmplCfgBandwidthCorrPredefEncapsEfmFs OBJECT-TYPE
   SYNTAX      Integer32
   MAX-ACCESS  read-write
   STATUS      current
   DESCRIPTION
      "Path: tunnels.editConf.l2tpTunnels.bandwidth.correction.predefined.encapsulation.efm.fragmentSize"
   ::= {er1645v2TvTmplCfgEntry 136598656}

er1645v2TvTmplCfgBandwidthCorrPredefEncapsEfmIb OBJECT-TYPE
   SYNTAX      Integer32
   MAX-ACCESS  read-write
   STATUS      current
   DESCRIPTION
      "Path: tunnels.editConf.l2tpTunnels.bandwidth.correction.predefined.encapsulation.efm.idleBytes"
   ::= {er1645v2TvTmplCfgEntry 136598784}

er1645v2TvTmplCfgBandwidthCorrPredefMode OBJECT-TYPE
   SYNTAX      INTEGER
               {
               routing (0),
               bridging (1)
               }
   MAX-ACCESS  read-write
   STATUS      current
   DESCRIPTION
      "Path: tunnels.editConf.l2tpTunnels.bandwidth.correction.predefined.mode

       Possibilities:
               routing   (0)
               bridging   (1)"
   ::= {er1645v2TvTmplCfgEntry 136609792}

er1645v2TvTmplCfgBandwidthCorrManualOverhead OBJECT-TYPE
   SYNTAX      Integer32
   MAX-ACCESS  read-write
   STATUS      current
   DESCRIPTION
      "Path: tunnels.editConf.l2tpTunnels.bandwidth.correction.manual.overhead"
   ::= {er1645v2TvTmplCfgEntry 136708608}

er1645v2TvTmplCfgBandwidthCorrManualFrameData OBJECT-TYPE
   SYNTAX      Counter32
   MAX-ACCESS  read-write
   STATUS      current
   DESCRIPTION
      "Path: tunnels.editConf.l2tpTunnels.bandwidth.correction.manual.frameData

       32 bit unsigned wrappable counter."
   ::= {er1645v2TvTmplCfgEntry 136709120}

er1645v2TvTmplCfgBandwidthCorrManualFrameHeader OBJECT-TYPE
   SYNTAX      Counter32
   MAX-ACCESS  read-write
   STATUS      current
   DESCRIPTION
      "Path: tunnels.editConf.l2tpTunnels.bandwidth.correction.manual.frameHeader

       32 bit unsigned wrappable counter."
   ::= {er1645v2TvTmplCfgEntry 136709632}

er1645v2TvTmplCfgBandwidthMaxFifoQLen OBJECT-TYPE
   SYNTAX      Integer32
   MAX-ACCESS  read-write
   STATUS      current
   DESCRIPTION
      "Path: tunnels.editConf.l2tpTunnels.bandwidth.maxFifoQLen"
   ::= {er1645v2TvTmplCfgEntry 137363456}

er1645v2TvTmplCfgBandwidthDeFlagCir OBJECT-TYPE
   SYNTAX      INTEGER
               {
               allowed (1),
               notAllowed (2)
               }
   MAX-ACCESS  read-write
   STATUS      current
   DESCRIPTION
      "Path: tunnels.editConf.l2tpTunnels.bandwidth.deFlag.cir

       Possibilities:
               allowed   (1)
               notAllowed   (2)"
   ::= {er1645v2TvTmplCfgEntry 147853312}

er1645v2TvTmplCfgBandwidthDeFlagEir OBJECT-TYPE
   SYNTAX      INTEGER
               {
               allowed (1),
               notAllowed (2)
               }
   MAX-ACCESS  read-write
   STATUS      current
   DESCRIPTION
      "Path: tunnels.editConf.l2tpTunnels.bandwidth.deFlag.eir

       Possibilities:
               allowed   (1)
               notAllowed   (2)"
   ::= {er1645v2TvTmplCfgEntry 147857408}

er1645v2TvTmplCfgBandwidthDeFlagViolate OBJECT-TYPE
   SYNTAX      INTEGER
               {
               allowed (1),
               notAllowed (2)
               }
   MAX-ACCESS  read-write
   STATUS      current
   DESCRIPTION
      "Path: tunnels.editConf.l2tpTunnels.bandwidth.deFlag.violate

       Possibilities:
               allowed   (1)
               notAllowed   (2)"
   ::= {er1645v2TvTmplCfgEntry 147861504}

er1645v2TvTmplCfgBandwidthActCirActNone OBJECT-TYPE
   SYNTAX      OCTET STRING
   MAX-ACCESS  read-write
   STATUS      current
   DESCRIPTION
      "Path: tunnels.editConf.l2tpTunnels.bandwidth.action.cirAction.none"
   ::= {er1645v2TvTmplCfgEntry 150085632}

er1645v2TvTmplCfgBandwidthActCirActEthCos1 OBJECT-TYPE
   SYNTAX      INTEGER
               {
               unchanged (256)
               }
   MAX-ACCESS  read-write
   STATUS      current
   DESCRIPTION
      "Path: tunnels.editConf.l2tpTunnels.bandwidth.action.cirAction.ethernet.cosDepth1

       Possibilities:
               unchanged   (256)"
   ::= {er1645v2TvTmplCfgEntry 150094080}

er1645v2TvTmplCfgBandwidthActCirActEthDei1 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth1

       Possibilities:
               unchanged   (255)
               clear   (0)
               set   (1)"
   ::= {er1645v2TvTmplCfgEntry 150099200}

er1645v2TvTmplCfgBandwidthActCirActEthCos2 OBJECT-TYPE
   SYNTAX      INTEGER
               {
               unchanged (256)
               }
   MAX-ACCESS  read-write
   STATUS      current
   DESCRIPTION
      "Path: tunnels.editConf.l2tpTunnels.bandwidth.action.cirAction.ethernet.cosDepth2

       Possibilities:
               unchanged   (256)"
   ::= {er1645v2TvTmplCfgEntry 150094336}

er1645v2TvTmplCfgBandwidthActCirActEthDei2 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth2

       Possibilities:
               unchanged   (255)
               clear   (0)
               set   (1)"
   ::= {er1645v2TvTmplCfgEntry 150099456}

er1645v2TvTmplCfgBandwidthActCirActEthCos3 OBJECT-TYPE
   SYNTAX      INTEGER
               {
               unchanged (256)
               }
   MAX-ACCESS  read-write
   STATUS      current
   DESCRIPTION
      "Path: tunnels.editConf.l2tpTunnels.bandwidth.action.cirAction.ethernet.cosDepth3

       Possibilities:
               unchanged   (256)"
   ::= {er1645v2TvTmplCfgEntry 150094592}

er1645v2TvTmplCfgBandwidthActCirActEthDei3 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth3

       Possibilities:
               unchanged   (255)
               clear   (0)
               set   (1)"
   ::= {er1645v2TvTmplCfgEntry 150099712}

er1645v2TvTmplCfgBandwidthActCirActEthCos4 OBJECT-TYPE
   SYNTAX      INTEGER
               {
               unchanged (256)
               }
   MAX-ACCESS  read-write
   STATUS      current
   DESCRIPTION
      "Path: tunnels.editConf.l2tpTunnels.bandwidth.action.cirAction.ethernet.cosDepth4

       Possibilities:
               unchanged   (256)"
   ::= {er1645v2TvTmplCfgEntry 150094848}

er1645v2TvTmplCfgBandwidthActCirActEthDei4 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth4

       Possibilities:
               unchanged   (255)
               clear   (0)
               set   (1)"
   ::= {er1645v2TvTmplCfgEntry 150099968}

er1645v2TvTmplCfgBandwidthActCirActEthCos5 OBJECT-TYPE
   SYNTAX      INTEGER
               {
               unchanged (256)
               }
   MAX-ACCESS  read-write
   STATUS      current
   DESCRIPTION
      "Path: tunnels.editConf.l2tpTunnels.bandwidth.action.cirAction.ethernet.cosDepth5

       Possibilities:
               unchanged   (256)"
   ::= {er1645v2TvTmplCfgEntry 150095104}

er1645v2TvTmplCfgBandwidthActCirActEthDei5 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth5

       Possibilities:
               unchanged   (255)
               clear   (0)
               set   (1)"
   ::= {er1645v2TvTmplCfgEntry 150100224}

er1645v2TvTmplCfgBandwidthActCirActEthCos6 OBJECT-TYPE
   SYNTAX      INTEGER
               {
               unchanged (256)
               }
   MAX-ACCESS  read-write
   STATUS      current
   DESCRIPTION
      "Path: tunnels.editConf.l2tpTunnels.bandwidth.action.cirAction.ethernet.cosDepth6

       Possibilities:
               unchanged   (256)"
   ::= {er1645v2TvTmplCfgEntry 150095360}

er1645v2TvTmplCfgBandwidthActCirActEthDei6 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth6

       Possibilities:
               unchanged   (255)
               clear   (0)
               set   (1)"
   ::= {er1645v2TvTmplCfgEntry 150100480}

er1645v2TvTmplCfgBandwidthActCirActEthCos7 OBJECT-TYPE
   SYNTAX      INTEGER
               {
               unchanged (256)
               }
   MAX-ACCESS  read-write
   STATUS      current
   DESCRIPTION
      "Path: tunnels.editConf.l2tpTunnels.bandwidth.action.cirAction.ethernet.cosDepth7

       Possibilities:
               unchanged   (256)"
   ::= {er1645v2TvTmplCfgEntry 150095616}

er1645v2TvTmplCfgBandwidthActCirActEthDei7 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth7

       Possibilities:
               unchanged   (255)
               clear   (0)
               set   (1)"
   ::= {er1645v2TvTmplCfgEntry 150100736}

er1645v2TvTmplCfgBandwidthActCirActEthCos8 OBJECT-TYPE
   SYNTAX      INTEGER
               {
               unchanged (256)
               }
   MAX-ACCESS  read-write
   STATUS      current
   DESCRIPTION
      "Path: tunnels.editConf.l2tpTunnels.bandwidth.action.cirAction.ethernet.cosDepth8

       Possibilities:
               unchanged   (256)"
   ::= {er1645v2TvTmplCfgEntry 150095872}

er1645v2TvTmplCfgBandwidthActCirActEthDei8 OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deiDepth8

       Possibilities:
               unchanged   (255)
               clear   (0)
               set   (1)"
   ::= {er1645v2TvTmplCfgEntry 150100992}

er1645v2TvTmplCfgBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCfgEntry 150096128}

er1645v2TvTmplCfgBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCfgEntry 150096384}

er1645v2TvTmplCfgBandwidthActCirActEthDrpLev OBJECT-TYPE
   SYNTAX      INTEGER
               {
               unchanged (0)
               }
   MAX-ACCESS  read-write
   STATUS      current
   DESCRIPTION
      "Path: tunnels.editConf.l2tpTunnels.bandwidth.action.cirAction.ethernet.dropLevel

       Possibilities:
               unchanged   (0)"
   ::= {er1645v2TvTmplCfgEntry 150096640}

er1645v2TvTmplCfgBandwidthActCirActEthDeFlag OBJECT-TYPE
   SYNTAX      INTEGER
               {
               unchanged (255),
               clear (0),
               set (1)
               }
   MAX-ACCESS  read-write
   STATUS      current
   DESCRIPTION
      "Path: tunnels.editConf.l2tpTunnels.bandwidth.action.cirAction.ethernet.deFlag

       Possibilities:
               unchanged   (255)
               clear   (0)
               set   (1)"
   ::= {er1645v2TvTmplCfgEntry 150097408}

er1645v2TvTmplCfgBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCfgEntry 150120704}

er1645v2TvTmplCfgBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCfgEntry 150120960}

er1645v2TvTmplCfgBandwidthActCirActIpDrpLev OBJECT-TYPE
   SYNTAX      INTEGER
               {
               unchanged (0)
               }
   MAX-ACCESS  read-write
   STATUS      current
   DESCRIPTION
      "Path: tunnels.editConf.l2tpTunnels.bandwidth.action.cirAction.ip.dropLevel

       Possibilities:
               unchanged   (0)"
   ::= {er1645v2TvTmplCfgEntry 150121216}

er1645v2TvTmplCfgBandwidthActCirActIpDeFlag OBJECT-TYPE
   SYNTAX      INTEGER
               {
               unchanged (255),
               clear (0),
               set (1)
               }
   MAX-ACCESS  read-write
   STATUS      current
   DESCRIPTION
      "Path: tunnels.editConf.l2tpTunnels.bandwidth.action.cirAction.ip.deFlag

       Possibilities:
               unchanged   (255)
               clear   (0)
               set   (1)"
   ::= {er1645v2TvTmplCfgEntry 150121984}

er1645v2TvTmplCfgBandwidthActEirActNone OBJECT-TYPE
   SYNTAX      OCTET STRING
   MAX-ACCESS  read-write
   STATUS      current
   DESCRIPTION
      "Path: tunnels.editConf.l2tpTunnels.bandwidth.action.eirAction.none"
   ::= {er1645v2TvTmplCfgEntry 150216704}

er1645v2TvTmplCfgBandwidthActEirActEthCos1 OBJECT-TYPE
   SYNTAX      INTEGER
               {
               unchanged (256)
               }
   MAX-ACCESS  read-write
   STATUS      current
   DESCRIPTION
      "Path: tunnels.editConf.l2tpTunnels.bandwidth.action.eirAction.ethernet.cosDepth1

       Possibilities:
               unchanged   (256)"
   ::= {er1645v2TvTmplCfgEntry 150225152}

er1645v2TvTmplCfgBandwidthActEirActEthDei1 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth1

       Possibilities:
               unchanged   (255)
               clear   (0)
               set   (1)"
   ::= {er1645v2TvTmplCfgEntry 150230272}

er1645v2TvTmplCfgBandwidthActEirActEthCos2 OBJECT-TYPE
   SYNTAX      INTEGER
               {
               unchanged (256)
               }
   MAX-ACCESS  read-write
   STATUS      current
   DESCRIPTION
      "Path: tunnels.editConf.l2tpTunnels.bandwidth.action.eirAction.ethernet.cosDepth2

       Possibilities:
               unchanged   (256)"
   ::= {er1645v2TvTmplCfgEntry 150225408}

er1645v2TvTmplCfgBandwidthActEirActEthDei2 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth2

       Possibilities:
               unchanged   (255)
               clear   (0)
               set   (1)"
   ::= {er1645v2TvTmplCfgEntry 150230528}

er1645v2TvTmplCfgBandwidthActEirActEthCos3 OBJECT-TYPE
   SYNTAX      INTEGER
               {
               unchanged (256)
               }
   MAX-ACCESS  read-write
   STATUS      current
   DESCRIPTION
      "Path: tunnels.editConf.l2tpTunnels.bandwidth.action.eirAction.ethernet.cosDepth3

       Possibilities:
               unchanged   (256)"
   ::= {er1645v2TvTmplCfgEntry 150225664}

er1645v2TvTmplCfgBandwidthActEirActEthDei3 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth3

       Possibilities:
               unchanged   (255)
               clear   (0)
               set   (1)"
   ::= {er1645v2TvTmplCfgEntry 150230784}

er1645v2TvTmplCfgBandwidthActEirActEthCos4 OBJECT-TYPE
   SYNTAX      INTEGER
               {
               unchanged (256)
               }
   MAX-ACCESS  read-write
   STATUS      current
   DESCRIPTION
      "Path: tunnels.editConf.l2tpTunnels.bandwidth.action.eirAction.ethernet.cosDepth4

       Possibilities:
               unchanged   (256)"
   ::= {er1645v2TvTmplCfgEntry 150225920}

er1645v2TvTmplCfgBandwidthActEirActEthDei4 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth4

       Possibilities:
               unchanged   (255)
               clear   (0)
               set   (1)"
   ::= {er1645v2TvTmplCfgEntry 150231040}

er1645v2TvTmplCfgBandwidthActEirActEthCos5 OBJECT-TYPE
   SYNTAX      INTEGER
               {
               unchanged (256)
               }
   MAX-ACCESS  read-write
   STATUS      current
   DESCRIPTION
      "Path: tunnels.editConf.l2tpTunnels.bandwidth.action.eirAction.ethernet.cosDepth5

       Possibilities:
               unchanged   (256)"
   ::= {er1645v2TvTmplCfgEntry 150226176}

er1645v2TvTmplCfgBandwidthActEirActEthDei5 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth5

       Possibilities:
               unchanged   (255)
               clear   (0)
               set   (1)"
   ::= {er1645v2TvTmplCfgEntry 150231296}

er1645v2TvTmplCfgBandwidthActEirActEthCos6 OBJECT-TYPE
   SYNTAX      INTEGER
               {
               unchanged (256)
               }
   MAX-ACCESS  read-write
   STATUS      current
   DESCRIPTION
      "Path: tunnels.editConf.l2tpTunnels.bandwidth.action.eirAction.ethernet.cosDepth6

       Possibilities:
               unchanged   (256)"
   ::= {er1645v2TvTmplCfgEntry 150226432}

er1645v2TvTmplCfgBandwidthActEirActEthDei6 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth6

       Possibilities:
               unchanged   (255)
               clear   (0)
               set   (1)"
   ::= {er1645v2TvTmplCfgEntry 150231552}

er1645v2TvTmplCfgBandwidthActEirActEthCos7 OBJECT-TYPE
   SYNTAX      INTEGER
               {
               unchanged (256)
               }
   MAX-ACCESS  read-write
   STATUS      current
   DESCRIPTION
      "Path: tunnels.editConf.l2tpTunnels.bandwidth.action.eirAction.ethernet.cosDepth7

       Possibilities:
               unchanged   (256)"
   ::= {er1645v2TvTmplCfgEntry 150226688}

er1645v2TvTmplCfgBandwidthActEirActEthDei7 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth7

       Possibilities:
               unchanged   (255)
               clear   (0)
               set   (1)"
   ::= {er1645v2TvTmplCfgEntry 150231808}

er1645v2TvTmplCfgBandwidthActEirActEthCos8 OBJECT-TYPE
   SYNTAX      INTEGER
               {
               unchanged (256)
               }
   MAX-ACCESS  read-write
   STATUS      current
   DESCRIPTION
      "Path: tunnels.editConf.l2tpTunnels.bandwidth.action.eirAction.ethernet.cosDepth8

       Possibilities:
               unchanged   (256)"
   ::= {er1645v2TvTmplCfgEntry 150226944}

er1645v2TvTmplCfgBandwidthActEirActEthDei8 OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deiDepth8

       Possibilities:
               unchanged   (255)
               clear   (0)
               set   (1)"
   ::= {er1645v2TvTmplCfgEntry 150232064}

er1645v2TvTmplCfgBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCfgEntry 150227200}

er1645v2TvTmplCfgBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCfgEntry 150227456}

er1645v2TvTmplCfgBandwidthActEirActEthDrpLev OBJECT-TYPE
   SYNTAX      INTEGER
               {
               unchanged (0)
               }
   MAX-ACCESS  read-write
   STATUS      current
   DESCRIPTION
      "Path: tunnels.editConf.l2tpTunnels.bandwidth.action.eirAction.ethernet.dropLevel

       Possibilities:
               unchanged   (0)"
   ::= {er1645v2TvTmplCfgEntry 150227712}

er1645v2TvTmplCfgBandwidthActEirActEthDeFlag OBJECT-TYPE
   SYNTAX      INTEGER
               {
               unchanged (255),
               clear (0),
               set (1)
               }
   MAX-ACCESS  read-write
   STATUS      current
   DESCRIPTION
      "Path: tunnels.editConf.l2tpTunnels.bandwidth.action.eirAction.ethernet.deFlag

       Possibilities:
               unchanged   (255)
               clear   (0)
               set   (1)"
   ::= {er1645v2TvTmplCfgEntry 150228480}

er1645v2TvTmplCfgBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCfgEntry 150251776}

er1645v2TvTmplCfgBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCfgEntry 150252032}

er1645v2TvTmplCfgBandwidthActEirActIpDrpLev OBJECT-TYPE
   SYNTAX      INTEGER
               {
               unchanged (0)
               }
   MAX-ACCESS  read-write
   STATUS      current
   DESCRIPTION
      "Path: tunnels.editConf.l2tpTunnels.bandwidth.action.eirAction.ip.dropLevel

       Possibilities:
               unchanged   (0)"
   ::= {er1645v2TvTmplCfgEntry 150252288}

er1645v2TvTmplCfgBandwidthActEirActIpDeFlag OBJECT-TYPE
   SYNTAX      INTEGER
               {
               unchanged (255),
               clear (0),
               set (1)
               }
   MAX-ACCESS  read-write
   STATUS      current
   DESCRIPTION
      "Path: tunnels.editConf.l2tpTunnels.bandwidth.action.eirAction.ip.deFlag

       Possibilities:
               unchanged   (255)
               clear   (0)
               set   (1)"
   ::= {er1645v2TvTmplCfgEntry 150253056}

er1645v2TvTmplCfgBandwidthActViolActNone OBJECT-TYPE
   SYNTAX      OCTET STRING
   MAX-ACCESS  read-write
   STATUS      current
   DESCRIPTION
      "Path: tunnels.editConf.l2tpTunnels.bandwidth.action.violateAction.none"
   ::= {er1645v2TvTmplCfgEntry 150347776}

er1645v2TvTmplCfgBandwidthActViolActDrop OBJECT-TYPE
   SYNTAX      OCTET STRING
   MAX-ACCESS  read-write
   STATUS      current
   DESCRIPTION
      "Path: tunnels.editConf.l2tpTunnels.bandwidth.action.violateAction.drop"
   ::= {er1645v2TvTmplCfgEntry 150364160}

er1645v2TvTmplCfgBandwidthActViolActEthCos1 OBJECT-TYPE
   SYNTAX      INTEGER
               {
               unchanged (256)
               }
   MAX-ACCESS  read-write
   STATUS      current
   DESCRIPTION
      "Path: tunnels.editConf.l2tpTunnels.bandwidth.action.violateAction.ethernet.cosDepth1

       Possibilities:
               unchanged   (256)"
   ::= {er1645v2TvTmplCfgEntry 150356224}

er1645v2TvTmplCfgBandwidthActViolActEthDei1 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth1

       Possibilities:
               unchanged   (255)
               clear   (0)
               set   (1)"
   ::= {er1645v2TvTmplCfgEntry 150361344}

er1645v2TvTmplCfgBandwidthActViolActEthCos2 OBJECT-TYPE
   SYNTAX      INTEGER
               {
               unchanged (256)
               }
   MAX-ACCESS  read-write
   STATUS      current
   DESCRIPTION
      "Path: tunnels.editConf.l2tpTunnels.bandwidth.action.violateAction.ethernet.cosDepth2

       Possibilities:
               unchanged   (256)"
   ::= {er1645v2TvTmplCfgEntry 150356480}

er1645v2TvTmplCfgBandwidthActViolActEthDei2 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth2

       Possibilities:
               unchanged   (255)
               clear   (0)
               set   (1)"
   ::= {er1645v2TvTmplCfgEntry 150361600}

er1645v2TvTmplCfgBandwidthActViolActEthCos3 OBJECT-TYPE
   SYNTAX      INTEGER
               {
               unchanged (256)
               }
   MAX-ACCESS  read-write
   STATUS      current
   DESCRIPTION
      "Path: tunnels.editConf.l2tpTunnels.bandwidth.action.violateAction.ethernet.cosDepth3

       Possibilities:
               unchanged   (256)"
   ::= {er1645v2TvTmplCfgEntry 150356736}

er1645v2TvTmplCfgBandwidthActViolActEthDei3 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth3

       Possibilities:
               unchanged   (255)
               clear   (0)
               set   (1)"
   ::= {er1645v2TvTmplCfgEntry 150361856}

er1645v2TvTmplCfgBandwidthActViolActEthCos4 OBJECT-TYPE
   SYNTAX      INTEGER
               {
               unchanged (256)
               }
   MAX-ACCESS  read-write
   STATUS      current
   DESCRIPTION
      "Path: tunnels.editConf.l2tpTunnels.bandwidth.action.violateAction.ethernet.cosDepth4

       Possibilities:
               unchanged   (256)"
   ::= {er1645v2TvTmplCfgEntry 150356992}

er1645v2TvTmplCfgBandwidthActViolActEthDei4 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth4

       Possibilities:
               unchanged   (255)
               clear   (0)
               set   (1)"
   ::= {er1645v2TvTmplCfgEntry 150362112}

er1645v2TvTmplCfgBandwidthActViolActEthCos5 OBJECT-TYPE
   SYNTAX      INTEGER
               {
               unchanged (256)
               }
   MAX-ACCESS  read-write
   STATUS      current
   DESCRIPTION
      "Path: tunnels.editConf.l2tpTunnels.bandwidth.action.violateAction.ethernet.cosDepth5

       Possibilities:
               unchanged   (256)"
   ::= {er1645v2TvTmplCfgEntry 150357248}

er1645v2TvTmplCfgBandwidthActViolActEthDei5 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth5

       Possibilities:
               unchanged   (255)
               clear   (0)
               set   (1)"
   ::= {er1645v2TvTmplCfgEntry 150362368}

er1645v2TvTmplCfgBandwidthActViolActEthCos6 OBJECT-TYPE
   SYNTAX      INTEGER
               {
               unchanged (256)
               }
   MAX-ACCESS  read-write
   STATUS      current
   DESCRIPTION
      "Path: tunnels.editConf.l2tpTunnels.bandwidth.action.violateAction.ethernet.cosDepth6

       Possibilities:
               unchanged   (256)"
   ::= {er1645v2TvTmplCfgEntry 150357504}

er1645v2TvTmplCfgBandwidthActViolActEthDei6 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth6

       Possibilities:
               unchanged   (255)
               clear   (0)
               set   (1)"
   ::= {er1645v2TvTmplCfgEntry 150362624}

er1645v2TvTmplCfgBandwidthActViolActEthCos7 OBJECT-TYPE
   SYNTAX      INTEGER
               {
               unchanged (256)
               }
   MAX-ACCESS  read-write
   STATUS      current
   DESCRIPTION
      "Path: tunnels.editConf.l2tpTunnels.bandwidth.action.violateAction.ethernet.cosDepth7

       Possibilities:
               unchanged   (256)"
   ::= {er1645v2TvTmplCfgEntry 150357760}

er1645v2TvTmplCfgBandwidthActViolActEthDei7 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth7

       Possibilities:
               unchanged   (255)
               clear   (0)
               set   (1)"
   ::= {er1645v2TvTmplCfgEntry 150362880}

er1645v2TvTmplCfgBandwidthActViolActEthCos8 OBJECT-TYPE
   SYNTAX      INTEGER
               {
               unchanged (256)
               }
   MAX-ACCESS  read-write
   STATUS      current
   DESCRIPTION
      "Path: tunnels.editConf.l2tpTunnels.bandwidth.action.violateAction.ethernet.cosDepth8

       Possibilities:
               unchanged   (256)"
   ::= {er1645v2TvTmplCfgEntry 150358016}

er1645v2TvTmplCfgBandwidthActViolActEthDei8 OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deiDepth8

       Possibilities:
               unchanged   (255)
               clear   (0)
               set   (1)"
   ::= {er1645v2TvTmplCfgEntry 150363136}

er1645v2TvTmplCfgBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCfgEntry 150358272}

er1645v2TvTmplCfgBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCfgEntry 150358528}

er1645v2TvTmplCfgBandwidthActViolActEthDrpLev OBJECT-TYPE
   SYNTAX      INTEGER
               {
               unchanged (0)
               }
   MAX-ACCESS  read-write
   STATUS      current
   DESCRIPTION
      "Path: tunnels.editConf.l2tpTunnels.bandwidth.action.violateAction.ethernet.dropLevel

       Possibilities:
               unchanged   (0)"
   ::= {er1645v2TvTmplCfgEntry 150358784}

er1645v2TvTmplCfgBandwidthActViolActEthDeFlag OBJECT-TYPE
   SYNTAX      INTEGER
               {
               unchanged (255),
               clear (0),
               set (1)
               }
   MAX-ACCESS  read-write
   STATUS      current
   DESCRIPTION
      "Path: tunnels.editConf.l2tpTunnels.bandwidth.action.violateAction.ethernet.deFlag

       Possibilities:
               unchanged   (255)
               clear   (0)
               set   (1)"
   ::= {er1645v2TvTmplCfgEntry 150359552}

er1645v2TvTmplCfgBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.l2tpTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCfgEntry 150382848}

er1645v2TvTmplCfgBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.l2tpTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCfgEntry 150383104}

er1645v2TvTmplCfgBandwidthActViolActIpDrpLev OBJECT-TYPE
   SYNTAX      INTEGER
               {
               unchanged (0)
               }
   MAX-ACCESS  read-write
   STATUS      current
   DESCRIPTION
      "Path: tunnels.editConf.l2tpTunnels.bandwidth.action.violateAction.ip.dropLevel

       Possibilities:
               unchanged   (0)"
   ::= {er1645v2TvTmplCfgEntry 150383360}

er1645v2TvTmplCfgBandwidthActViolActIpDeFlag OBJECT-TYPE
   SYNTAX      INTEGER
               {
               unchanged (255),
               clear (0),
               set (1)
               }
   MAX-ACCESS  read-write
   STATUS      current
   DESCRIPTION
      "Path: tunnels.editConf.l2tpTunnels.bandwidth.action.violateAction.ip.deFlag

       Possibilities:
               unchanged   (255)
               clear   (0)
               set   (1)"
   ::= {er1645v2TvTmplCfgEntry 150384128}

er1645v2TvTmplCfgBridgingVlTVlans OBJECT-TYPE
   SYNTAX      SEQUENCE OF Er1645v2TvTmplCfgBridgingVlTVlansEntry
   MAX-ACCESS  not-accessible
   STATUS      current
   DESCRIPTION
      ""
   ::= {er1645v2TvTmplCfg 459079680}

er1645v2TvTmplCfgBridgingVlTVlansEntry OBJECT-TYPE
   SYNTAX      Er1645v2TvTmplCfgBridgingVlTVlansEntry
   MAX-ACCESS  not-accessible
   STATUS      current
   DESCRIPTION
      ""
   INDEX      { er1645v2TvTmplCfgTableIx,
                er1645v2TvTmplCfgBridgingVlTVlansTableIx }
   ::= {er1645v2TvTmplCfgBridgingVlTVlans 1}

Er1645v2TvTmplCfgBridgingVlTVlansEntry ::=
   SEQUENCE
      {
      er1645v2TvTmplCfgBridgingVlTVlansActions
         VariableLengthTableActions,
      er1645v2TvTmplCfgBridgingVlTVlansTableIx
         TableIndex,
      er1645v2TvTmplCfgBridgingVlTVlansVid
         Integer32,
      er1645v2TvTmplCfgBridgingVlTVlansEndVid
         Integer32,
      er1645v2TvTmplCfgBridgingVlTVlansAction
         INTEGER,
      er1645v2TvTmplCfgBridgingVlTVlansTagInfoTpid
         INTEGER,
      er1645v2TvTmplCfgBridgingVlTVlansTagInfoVid
         Integer32
      }

er1645v2TvTmplCfgBridgingVlTVlansActions OBJECT-TYPE
   SYNTAX      VariableLengthTableActions
   MAX-ACCESS  read-write
   STATUS      current
   DESCRIPTION
      "By way of this field, some manipulations
       on this table may be performed."
   ::= {er1645v2TvTmplCfgBridgingVlTVlansEntry 2}

er1645v2TvTmplCfgBridgingVlTVlansTableIx OBJECT-TYPE
   SYNTAX      TableIndex
   MAX-ACCESS  not-accessible
   STATUS      current
   DESCRIPTION
      ""
   ::= {er1645v2TvTmplCfgBridgingVlTVlansEntry 11}

er1645v2TvTmplCfgBridgingVlTVlansVid OBJECT-TYPE
   SYNTAX      Integer32
   MAX-ACCESS  read-write
   STATUS      current
   DESCRIPTION
      "Path: tunnels.editConf.l2tpTunnels.bridging.vlanTagging.vlans.vid"
   ::= {er1645v2TvTmplCfgBridgingVlTVlansEntry 536870912}

er1645v2TvTmplCfgBridgingVlTVlansEndVid OBJECT-TYPE
   SYNTAX      Integer32
   MAX-ACCESS  read-write
   STATUS      current
   DESCRIPTION
      "Path: tunnels.editConf.l2tpTunnels.bridging.vlanTagging.vlans.endVid"
   ::= {er1645v2TvTmplCfgBridgingVlTVlansEntry 2147483648}

er1645v2TvTmplCfgBridgingVlTVlansAction OBJECT-TYPE
   SYNTAX      INTEGER
               {
               discard (0),
               accept (1),
               tag (2)
               }
   MAX-ACCESS  read-write
   STATUS      current
   DESCRIPTION
      "Path: tunnels.editConf.l2tpTunnels.bridging.vlanTagging.vlans.action

       Possibilities:
               discard   (0)
               accept   (1)
               tag   (2)"
   ::= {er1645v2TvTmplCfgBridgingVlTVlansEntry 1073741824}

er1645v2TvTmplCfgBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.l2tpTunnels.bridging.vlanTagging.vlans.tagInfo.tpid

       Possibilities:
               dot1Q   (33024)
               dot1ad   (34984)
               0x9100   (37120)
               0x9200   (37376)
               0x9300   (37632)"
   ::= {er1645v2TvTmplCfgBridgingVlTVlansEntry 1677721600}

er1645v2TvTmplCfgBridgingVlTVlansTagInfoVid OBJECT-TYPE
   SYNTAX      Integer32
   MAX-ACCESS  read-write
   STATUS      current
   DESCRIPTION
      "Path: tunnels.editConf.l2tpTunnels.bridging.vlanTagging.vlans.tagInfo.vid"
   ::= {er1645v2TvTmplCfgBridgingVlTVlansEntry 1744830464}


er1645v2TvTmplCGre OBJECT IDENTIFIER ::= {er1645v2TvTmpl 21}

er1645v2TvTmplCGreSSCTable OBJECT-TYPE
   SYNTAX      SEQUENCE OF Er1645v2TvTmplCGreEntry
   MAX-ACCESS  not-accessible
   STATUS      current
   DESCRIPTION
      ""
   ::= {er1645v2TvTmplCGre 1}

er1645v2TvTmplCGreEntry OBJECT-TYPE
   SYNTAX      Er1645v2TvTmplCGreEntry
   MAX-ACCESS  not-accessible
   STATUS      current
   DESCRIPTION
      ""
   INDEX      { er1645v2TvTmplCGreTableIx }
   ::= {er1645v2TvTmplCGreSSCTable 1}

Er1645v2TvTmplCGreEntry ::=
   SEQUENCE
      {
      er1645v2TvTmplCGreActions
         VariableLengthTableActions,
      er1645v2TvTmplCGreTableIx
         TableIndex,
      er1645v2TvTmplCGreName
         DisplayString,
      er1645v2TvTmplCGreRemark
         DisplayString,
      er1645v2TvTmplCGreAdminStatus
         INTEGER,
      er1645v2TvTmplCGreMode
         INTEGER,
      er1645v2TvTmplCGrePriorityPolicy
         DisplayString,
      er1645v2TvTmplCGreIpVrfRouter
         DisplayString,
      er1645v2TvTmplCGreIpAdr
         IpAddress,
      er1645v2TvTmplCGreIpNetm
         IpAddress,
      er1645v2TvTmplCGreIpSNetName
         INTEGER,
      er1645v2TvTmplCGreIpSNetCust
         DisplayString,
      er1645v2TvTmplCGreIpRem
         IpAddress,
      er1645v2TvTmplCGreIpGwPref
         Integer32,
      er1645v2TvTmplCGreIpMtu
         Integer32,
      er1645v2TvTmplCGreIpMssAdjust
         INTEGER,
      er1645v2TvTmplCGreIpRipMetric
         Integer32,
      er1645v2TvTmplCGreIpRipMetricOut
         Integer32,
      er1645v2TvTmplCGreIpRipMode
         INTEGER,
      er1645v2TvTmplCGreIpRipTxVersion
         INTEGER,
      er1645v2TvTmplCGreIpRipRxVersion
         INTEGER,
      er1645v2TvTmplCGreIpRipSplitHorizon
         INTEGER,
      er1645v2TvTmplCGreIpRipAuth
         INTEGER,
      er1645v2TvTmplCGreIpRipFilter
         DisplayString,
      er1645v2TvTmplCGreIpRipFilterIn
         DisplayString,
      er1645v2TvTmplCGreIpRipSnapshot
         INTEGER,
      er1645v2TvTmplCGreIpRipClearNextHop
         INTEGER,
      er1645v2TvTmplCGreIpAccPol
         DisplayString,
      er1645v2TvTmplCGreIpAB
         DisplayString,
      er1645v2TvTmplCGreIpMA
         INTEGER,
      er1645v2TvTmplCGreIpMF
         Integer32,
      er1645v2TvTmplCGreIpDB
         INTEGER,
      er1645v2TvTmplCGreIpIR
         INTEGER,
      er1645v2TvTmplCGreIpIgmp
         INTEGER,
      er1645v2TvTmplCGreIpNN
         DisplayString,
      er1645v2TvTmplCGreIpPimMode
         INTEGER,
      er1645v2TvTmplCGreIpPimDrPriority
         Counter32,
      er1645v2TvTmplCGreIpPimHelloTime
         TimeTicks,
      er1645v2TvTmplCGreIpPimPropagationDelay
         TimeTicks,
      er1645v2TvTmplCGreIpPimOverrideInterval
         TimeTicks,
      er1645v2TvTmplCGreIpPimBsrBorder
         INTEGER,
      er1645v2TvTmplCGreIpPimTtlThreshold
         Integer32,
      er1645v2TvTmplCGreIpIMNetworkUnreachable
         INTEGER,
      er1645v2TvTmplCGreIpIMHostUnreachable
         INTEGER,
      er1645v2TvTmplCGreIpIMProtocolUnreachable
         INTEGER,
      er1645v2TvTmplCGreIpIMPortUnreachable
         INTEGER,
      er1645v2TvTmplCGreIpIMMtuExceeded
         INTEGER,
      er1645v2TvTmplCGreIpIMAdminProhibited
         INTEGER,
      er1645v2TvTmplCGreIpIMTtlExceeded
         INTEGER,
      er1645v2TvTmplCGreIpIMRedirect
         INTEGER,
      er1645v2TvTmplCGreBrAccList
         DisplayString,
      er1645v2TvTmplCGreBrInACL
         DisplayString,
      er1645v2TvTmplCGreBrTp
         DisplayString,
      er1645v2TvTmplCGreBrBrGrp
         DisplayString,
      er1645v2TvTmplCGreBrLimBC
         INTEGER,
      er1645v2TvTmplCGreBrPrivateMode
         INTEGER,
      er1645v2TvTmplCGreBrLearning
         INTEGER,
      er1645v2TvTmplCGreBrMaxCacheSize
         INTEGER,
      er1645v2TvTmplCGreBrRelearnDropOnRelearn
         INTEGER,
      er1645v2TvTmplCGreBrRelearnShutdownThreshold
         Integer32,
      er1645v2TvTmplCGreBrRelearnShutdownTime
         TimeTicks,
      er1645v2TvTmplCGreBrRelearnLoopDetection
         INTEGER,
      er1645v2TvTmplCGreBrRelearnLoopDetectionInterval
         TimeTicks,
      er1645v2TvTmplCGreBrVlanMemberShip
         INTEGER,
      er1645v2TvTmplCGreBrVlTUntaggedAction
         INTEGER,
      er1645v2TvTmplCGreBrVlTUntaggedTagInfoTpid
         INTEGER,
      er1645v2TvTmplCGreBrVlTUntaggedTagInfoVid
         Integer32,
      er1645v2TvTmplCGreBrVlTUnknownVlansAction
         INTEGER,
      er1645v2TvTmplCGreBrVlTUnknownVlansTagInfoTpid
         INTEGER,
      er1645v2TvTmplCGreBrVlTUnknownVlansTagInfoVid
         Integer32,
      er1645v2TvTmplCGreBrDot1adType
         INTEGER,
      er1645v2TvTmplCGreBrPriority
         Integer32,
      er1645v2TvTmplCGreBrPathCost
         Integer32,
      er1645v2TvTmplCGreBrInternalPathCost
         Integer32,
      er1645v2TvTmplCGreBrTCD
         INTEGER,
      er1645v2TvTmplCGreBrRestrictedRole
         INTEGER,
      er1645v2TvTmplCGreBrAdminEdge
         INTEGER,
      er1645v2TvTmplCGreBrOamMacDeviceMac
         DisplayString,
      er1645v2TvTmplCGreBrOamMacUserMac
         OCTET STRING,
      er1645v2TvTmplCGreBrOamMacBridgeMac
         DisplayString,
      er1645v2TvTmplCGreBrMgmtInline
         INTEGER,
      er1645v2TvTmplCGreBrL2ptMode
         INTEGER,
      er1645v2TvTmplCGreBrL2ptProtocols
         Integer32,
      er1645v2TvTmplCGreBrL2ptDestMac
         OCTET STRING,
      er1645v2TvTmplCGreBrL2ptCos
         INTEGER,
      er1645v2TvTmplCGreBrL2ptDropThrStp
         INTEGER,
      er1645v2TvTmplCGreBrL2ptDropThrLldp
         INTEGER,
      er1645v2TvTmplCGreBrL2ptDropThrOam
         INTEGER,
      er1645v2TvTmplCGreBrL2ptDropThrCdp
         INTEGER,
      er1645v2TvTmplCGreBrL2ptDropThrVtp
         INTEGER,
      er1645v2TvTmplCGreBrL2ptDropThrLacp
         INTEGER,
      er1645v2TvTmplCGreBrL2ptDropThrEfmOam
         INTEGER,
      er1645v2TvTmplCGreBrL2ptDropThrPvst
         INTEGER,
      er1645v2TvTmplCGreBrL2ptDropThrMmrp
         INTEGER,
      er1645v2TvTmplCGreBrL2ptDropThrMvrp
         INTEGER,
      er1645v2TvTmplCGreBrL2ptDropThrGvrp
         INTEGER,
      er1645v2TvTmplCGreBrL2ptDropThrGmrp
         INTEGER,
      er1645v2TvTmplCGreBrL2ptDropThrDtp
         INTEGER,
      er1645v2TvTmplCGreBrL2ptDropThrPagp
         INTEGER,
      er1645v2TvTmplCGreBrL2ptDropThrUdld
         INTEGER,
      er1645v2TvTmplCGreVirtEthernetVirtualEthernet
         DisplayString,
      er1645v2TvTmplCGreGreVrfRouter
         DisplayString,
      er1645v2TvTmplCGreGreLocalIpAddress
         IpAddress,
      er1645v2TvTmplCGreGreRemoteIpAddress
         IpAddress,
      er1645v2TvTmplCGreGreVrfRouterV6
         DisplayString,
      er1645v2TvTmplCGreGreLocalIpV6Address
         Ipv6Address,
      er1645v2TvTmplCGreGreRemoteIpV6Address
         Ipv6Address,
      er1645v2TvTmplCGreGreLocalInterface
         DisplayString,
      er1645v2TvTmplCGreGreRemoteDnsName
         DisplayString,
      er1645v2TvTmplCGreGreKey
         Integer32,
      er1645v2TvTmplCGreGreKpAlMode
         INTEGER,
      er1645v2TvTmplCGreGreKpAlInterval
         TimeTicks,
      er1645v2TvTmplCGreGreKpAlRepTimeOut
         TimeTicks,
      er1645v2TvTmplCGreGreKpAlFailsPrmt
         Integer32,
      er1645v2TvTmplCGreGreRRoutDefRt
         INTEGER,
      er1645v2TvTmplCGreGreTos
         INTEGER,
      er1645v2TvTmplCGreGreQueueTosMapQueue1
         INTEGER,
      er1645v2TvTmplCGreGreQueueTosMapQueue2
         INTEGER,
      er1645v2TvTmplCGreGreQueueTosMapQueue3
         INTEGER,
      er1645v2TvTmplCGreGreQueueTosMapQueue4
         INTEGER,
      er1645v2TvTmplCGreGreQueueTosMapQueue5
         INTEGER,
      er1645v2TvTmplCGreGreQueueTosMapLowDelayQueue
         INTEGER,
      er1645v2TvTmplCGreGreQueueTosMapLowDelay2Queue
         INTEGER,
      er1645v2TvTmplCGreGreQueueTosMapSystemQueue
         INTEGER,
      er1645v2TvTmplCGreGreDf
         INTEGER,
      er1645v2TvTmplCGreGreTtl
         INTEGER,
      er1645v2TvTmplCGreGreMtu
         Integer32,
      er1645v2TvTmplCGreMplsMode
         INTEGER,
      er1645v2TvTmplCGreMplsInLabel
         Integer32,
      er1645v2TvTmplCGreMplsOutLabel
         Integer32,
      er1645v2TvTmplCGreMplsTrafficClassMode
         INTEGER,
      er1645v2TvTmplCGreMplsTrafficClassFixed
         Integer32,
      er1645v2TvTmplCGreMplsTrafficClassQosP0
         Integer32,
      er1645v2TvTmplCGreMplsTrafficClassQosP1
         Integer32,
      er1645v2TvTmplCGreMplsTrafficClassQosP2
         Integer32,
      er1645v2TvTmplCGreMplsTrafficClassQosP3
         Integer32,
      er1645v2TvTmplCGreMplsTrafficClassQosP4
         Integer32,
      er1645v2TvTmplCGreMplsTrafficClassQosP5
         Integer32,
      er1645v2TvTmplCGreMplsTrafficClassQosP6
         Integer32,
      er1645v2TvTmplCGreMplsTrafficClassQosP7
         Integer32,
      er1645v2TvTmplCGreMplsTtl
         INTEGER,
      er1645v2TvTmplCGreInbBwCir
         Integer32,
      er1645v2TvTmplCGreInbBwTc
         INTEGER,
      er1645v2TvTmplCGreInbBwCorrType
         INTEGER,
      er1645v2TvTmplCGreInbBwCorrPredefEncapsFrameRelay
         DisplayString,
      er1645v2TvTmplCGreInbBwCorrPredefEncapsPpp
         DisplayString,
      er1645v2TvTmplCGreInbBwCorrPredefEncapsAtmHl
         INTEGER,
      er1645v2TvTmplCGreInbBwCorrPredefEncapsAtmMp
         INTEGER,
      er1645v2TvTmplCGreInbBwCorrPredefEncapsHdlc
         DisplayString,
      er1645v2TvTmplCGreInbBwCorrPredefEncapsEfmFs
         Integer32,
      er1645v2TvTmplCGreInbBwCorrPredefEncapsEfmIb
         Integer32,
      er1645v2TvTmplCGreInbBwCorrPredefMode
         INTEGER,
      er1645v2TvTmplCGreInbBwCorrManualOverhead
         Integer32,
      er1645v2TvTmplCGreInbBwCorrManualFrameData
         Counter32,
      er1645v2TvTmplCGreInbBwCorrManualFrameHeader
         Counter32,
      er1645v2TvTmplCGreInbBwMaxFifoQLen
         Integer32,
      er1645v2TvTmplCGreInbBwPriorityPolicy
         DisplayString,
      er1645v2TvTmplCGreBandwidthMode
         INTEGER,
      er1645v2TvTmplCGreBandwidthCir
         Integer32,
      er1645v2TvTmplCGreBandwidthEir
         Integer32,
      er1645v2TvTmplCGreBandwidthUnit
         INTEGER,
      er1645v2TvTmplCGreBandwidthTc
         INTEGER,
      er1645v2TvTmplCGreBandwidthTcFactor
         INTEGER,
      er1645v2TvTmplCGreBandwidthCorrType
         INTEGER,
      er1645v2TvTmplCGreBandwidthCorrPredefEncapsFrameRelay
         DisplayString,
      er1645v2TvTmplCGreBandwidthCorrPredefEncapsPpp
         DisplayString,
      er1645v2TvTmplCGreBandwidthCorrPredefEncapsAtmHl
         INTEGER,
      er1645v2TvTmplCGreBandwidthCorrPredefEncapsAtmMp
         INTEGER,
      er1645v2TvTmplCGreBandwidthCorrPredefEncapsHdlc
         DisplayString,
      er1645v2TvTmplCGreBandwidthCorrPredefEncapsEfmFs
         Integer32,
      er1645v2TvTmplCGreBandwidthCorrPredefEncapsEfmIb
         Integer32,
      er1645v2TvTmplCGreBandwidthCorrPredefMode
         INTEGER,
      er1645v2TvTmplCGreBandwidthCorrManualOverhead
         Integer32,
      er1645v2TvTmplCGreBandwidthCorrManualFrameData
         Counter32,
      er1645v2TvTmplCGreBandwidthCorrManualFrameHeader
         Counter32,
      er1645v2TvTmplCGreBandwidthMaxFifoQLen
         Integer32,
      er1645v2TvTmplCGreBandwidthDeFlagCir
         INTEGER,
      er1645v2TvTmplCGreBandwidthDeFlagEir
         INTEGER,
      er1645v2TvTmplCGreBandwidthDeFlagViolate
         INTEGER,
      er1645v2TvTmplCGreBandwidthActCirActNone
         OCTET STRING,
      er1645v2TvTmplCGreBandwidthActCirActEthCos1
         INTEGER,
      er1645v2TvTmplCGreBandwidthActCirActEthDei1
         INTEGER,
      er1645v2TvTmplCGreBandwidthActCirActEthCos2
         INTEGER,
      er1645v2TvTmplCGreBandwidthActCirActEthDei2
         INTEGER,
      er1645v2TvTmplCGreBandwidthActCirActEthCos3
         INTEGER,
      er1645v2TvTmplCGreBandwidthActCirActEthDei3
         INTEGER,
      er1645v2TvTmplCGreBandwidthActCirActEthCos4
         INTEGER,
      er1645v2TvTmplCGreBandwidthActCirActEthDei4
         INTEGER,
      er1645v2TvTmplCGreBandwidthActCirActEthCos5
         INTEGER,
      er1645v2TvTmplCGreBandwidthActCirActEthDei5
         INTEGER,
      er1645v2TvTmplCGreBandwidthActCirActEthCos6
         INTEGER,
      er1645v2TvTmplCGreBandwidthActCirActEthDei6
         INTEGER,
      er1645v2TvTmplCGreBandwidthActCirActEthCos7
         INTEGER,
      er1645v2TvTmplCGreBandwidthActCirActEthDei7
         INTEGER,
      er1645v2TvTmplCGreBandwidthActCirActEthCos8
         INTEGER,
      er1645v2TvTmplCGreBandwidthActCirActEthDei8
         INTEGER,
      er1645v2TvTmplCGreBandwidthActCirActEthTos
         INTEGER,
      er1645v2TvTmplCGreBandwidthActCirActEthQueue
         INTEGER,
      er1645v2TvTmplCGreBandwidthActCirActEthDrpLev
         INTEGER,
      er1645v2TvTmplCGreBandwidthActCirActEthDeFlag
         INTEGER,
      er1645v2TvTmplCGreBandwidthActCirActIpTos
         INTEGER,
      er1645v2TvTmplCGreBandwidthActCirActIpQueue
         INTEGER,
      er1645v2TvTmplCGreBandwidthActCirActIpDrpLev
         INTEGER,
      er1645v2TvTmplCGreBandwidthActCirActIpDeFlag
         INTEGER,
      er1645v2TvTmplCGreBandwidthActEirActNone
         OCTET STRING,
      er1645v2TvTmplCGreBandwidthActEirActEthCos1
         INTEGER,
      er1645v2TvTmplCGreBandwidthActEirActEthDei1
         INTEGER,
      er1645v2TvTmplCGreBandwidthActEirActEthCos2
         INTEGER,
      er1645v2TvTmplCGreBandwidthActEirActEthDei2
         INTEGER,
      er1645v2TvTmplCGreBandwidthActEirActEthCos3
         INTEGER,
      er1645v2TvTmplCGreBandwidthActEirActEthDei3
         INTEGER,
      er1645v2TvTmplCGreBandwidthActEirActEthCos4
         INTEGER,
      er1645v2TvTmplCGreBandwidthActEirActEthDei4
         INTEGER,
      er1645v2TvTmplCGreBandwidthActEirActEthCos5
         INTEGER,
      er1645v2TvTmplCGreBandwidthActEirActEthDei5
         INTEGER,
      er1645v2TvTmplCGreBandwidthActEirActEthCos6
         INTEGER,
      er1645v2TvTmplCGreBandwidthActEirActEthDei6
         INTEGER,
      er1645v2TvTmplCGreBandwidthActEirActEthCos7
         INTEGER,
      er1645v2TvTmplCGreBandwidthActEirActEthDei7
         INTEGER,
      er1645v2TvTmplCGreBandwidthActEirActEthCos8
         INTEGER,
      er1645v2TvTmplCGreBandwidthActEirActEthDei8
         INTEGER,
      er1645v2TvTmplCGreBandwidthActEirActEthTos
         INTEGER,
      er1645v2TvTmplCGreBandwidthActEirActEthQueue
         INTEGER,
      er1645v2TvTmplCGreBandwidthActEirActEthDrpLev
         INTEGER,
      er1645v2TvTmplCGreBandwidthActEirActEthDeFlag
         INTEGER,
      er1645v2TvTmplCGreBandwidthActEirActIpTos
         INTEGER,
      er1645v2TvTmplCGreBandwidthActEirActIpQueue
         INTEGER,
      er1645v2TvTmplCGreBandwidthActEirActIpDrpLev
         INTEGER,
      er1645v2TvTmplCGreBandwidthActEirActIpDeFlag
         INTEGER,
      er1645v2TvTmplCGreBandwidthActViolActNone
         OCTET STRING,
      er1645v2TvTmplCGreBandwidthActViolActDrop
         OCTET STRING,
      er1645v2TvTmplCGreBandwidthActViolActEthCos1
         INTEGER,
      er1645v2TvTmplCGreBandwidthActViolActEthDei1
         INTEGER,
      er1645v2TvTmplCGreBandwidthActViolActEthCos2
         INTEGER,
      er1645v2TvTmplCGreBandwidthActViolActEthDei2
         INTEGER,
      er1645v2TvTmplCGreBandwidthActViolActEthCos3
         INTEGER,
      er1645v2TvTmplCGreBandwidthActViolActEthDei3
         INTEGER,
      er1645v2TvTmplCGreBandwidthActViolActEthCos4
         INTEGER,
      er1645v2TvTmplCGreBandwidthActViolActEthDei4
         INTEGER,
      er1645v2TvTmplCGreBandwidthActViolActEthCos5
         INTEGER,
      er1645v2TvTmplCGreBandwidthActViolActEthDei5
         INTEGER,
      er1645v2TvTmplCGreBandwidthActViolActEthCos6
         INTEGER,
      er1645v2TvTmplCGreBandwidthActViolActEthDei6
         INTEGER,
      er1645v2TvTmplCGreBandwidthActViolActEthCos7
         INTEGER,
      er1645v2TvTmplCGreBandwidthActViolActEthDei7
         INTEGER,
      er1645v2TvTmplCGreBandwidthActViolActEthCos8
         INTEGER,
      er1645v2TvTmplCGreBandwidthActViolActEthDei8
         INTEGER,
      er1645v2TvTmplCGreBandwidthActViolActEthTos
         INTEGER,
      er1645v2TvTmplCGreBandwidthActViolActEthQueue
         INTEGER,
      er1645v2TvTmplCGreBandwidthActViolActEthDrpLev
         INTEGER,
      er1645v2TvTmplCGreBandwidthActViolActEthDeFlag
         INTEGER,
      er1645v2TvTmplCGreBandwidthActViolActIpTos
         INTEGER,
      er1645v2TvTmplCGreBandwidthActViolActIpQueue
         INTEGER,
      er1645v2TvTmplCGreBandwidthActViolActIpDrpLev
         INTEGER,
      er1645v2TvTmplCGreBandwidthActViolActIpDeFlag
         INTEGER
      }

er1645v2TvTmplCGreActions OBJECT-TYPE
   SYNTAX      VariableLengthTableActions
   MAX-ACCESS  read-write
   STATUS      current
   DESCRIPTION
      "By way of this field, some manipulations
       on this table may be performed."
   ::= {er1645v2TvTmplCGreEntry 2}

er1645v2TvTmplCGreTableIx OBJECT-TYPE
   SYNTAX      TableIndex
   MAX-ACCESS  not-accessible
   STATUS      current
   DESCRIPTION
      ""
   ::= {er1645v2TvTmplCGreEntry 11}

er1645v2TvTmplCGreName OBJECT-TYPE
   SYNTAX      DisplayString
   MAX-ACCESS  read-write
   STATUS      current
   DESCRIPTION
      "Path: tunnels.editConf.greTunnels.name"
   ::= {er1645v2TvTmplCGreEntry 16777216}

er1645v2TvTmplCGreRemark OBJECT-TYPE
   SYNTAX      DisplayString
   MAX-ACCESS  read-write
   STATUS      current
   DESCRIPTION
      "Path: tunnels.editConf.greTunnels.remark"
   ::= {er1645v2TvTmplCGreEntry 1157627904}

er1645v2TvTmplCGreAdminStatus OBJECT-TYPE
   SYNTAX      INTEGER
               {
               up (1),
               down (2)
               }
   MAX-ACCESS  read-write
   STATUS      current
   DESCRIPTION
      "Path: tunnels.editConf.greTunnels.adminStatus

       Possibilities:
               up   (1)
               down   (2)"
   ::= {er1645v2TvTmplCGreEntry 33554432}

er1645v2TvTmplCGreMode OBJECT-TYPE
   SYNTAX      INTEGER
               {
               routing (1),
               bridging (2),
               multilink (8),
               virtEthernet (32)
               }
   MAX-ACCESS  read-write
   STATUS      current
   DESCRIPTION
      "Path: tunnels.editConf.greTunnels.mode

       Possibilities:
               routing   (1)
               bridging   (2)
               multilink   (8)
               virtEthernet   (32)"
   ::= {er1645v2TvTmplCGreEntry 67108864}

er1645v2TvTmplCGrePriorityPolicy OBJECT-TYPE
   SYNTAX      DisplayString
   MAX-ACCESS  read-write
   STATUS      current
   DESCRIPTION
      "Path: tunnels.editConf.greTunnels.priorityPolicy"
   ::= {er1645v2TvTmplCGreEntry 83886080}

er1645v2TvTmplCGreIpVrfRouter OBJECT-TYPE
   SYNTAX      DisplayString
   MAX-ACCESS  read-write
   STATUS      current
   DESCRIPTION
      "Path: tunnels.editConf.greTunnels.ip.vrfRouter"
   ::= {er1645v2TvTmplCGreEntry 53215232}

er1645v2TvTmplCGreIpAdr OBJECT-TYPE
   SYNTAX      IpAddress
   MAX-ACCESS  read-write
   STATUS      current
   DESCRIPTION
      "Path: tunnels.editConf.greTunnels.ip.address"
   ::= {er1645v2TvTmplCGreEntry 58261504}

er1645v2TvTmplCGreIpNetm OBJECT-TYPE
   SYNTAX      IpAddress
   MAX-ACCESS  read-write
   STATUS      current
   DESCRIPTION
      "Path: tunnels.editConf.greTunnels.ip.netMask"
   ::= {er1645v2TvTmplCGreEntry 58392576}

er1645v2TvTmplCGreIpSNetName OBJECT-TYPE
   SYNTAX      INTEGER
               {
               slOPTg (0),
               corp (2),
               dmz (3),
               internet (1)
               }
   MAX-ACCESS  read-write
   STATUS      current
   DESCRIPTION
      "Path: tunnels.editConf.greTunnels.ip.sNet.name

       Possibilities:
               <OPT>   (0)
               corp   (2)
               dmz   (3)
               internet   (1)"
   ::= {er1645v2TvTmplCGreEntry 53674240}

er1645v2TvTmplCGreIpSNetCust OBJECT-TYPE
   SYNTAX      DisplayString
   MAX-ACCESS  read-write
   STATUS      current
   DESCRIPTION
      "Path: tunnels.editConf.greTunnels.ip.sNet.custom"
   ::= {er1645v2TvTmplCGreEntry 53674496}

er1645v2TvTmplCGreIpRem OBJECT-TYPE
   SYNTAX      IpAddress
   MAX-ACCESS  read-write
   STATUS      current
   DESCRIPTION
      "Path: tunnels.editConf.greTunnels.ip.remote"
   ::= {er1645v2TvTmplCGreEntry 58458112}

er1645v2TvTmplCGreIpGwPref OBJECT-TYPE
   SYNTAX      Integer32
   MAX-ACCESS  read-write
   STATUS      current
   DESCRIPTION
      "Path: tunnels.editConf.greTunnels.ip.gatewayPreference"
   ::= {er1645v2TvTmplCGreEntry 52690944}

er1645v2TvTmplCGreIpMtu OBJECT-TYPE
   SYNTAX      Integer32
   MAX-ACCESS  read-write
   STATUS      current
   DESCRIPTION
      "Path: tunnels.editConf.greTunnels.ip.mtu"
   ::= {er1645v2TvTmplCGreEntry 52953088}

er1645v2TvTmplCGreIpMssAdjust OBJECT-TYPE
   SYNTAX      INTEGER
               {
               disabled (0),
               auto (65536)
               }
   MAX-ACCESS  read-write
   STATUS      current
   DESCRIPTION
      "Path: tunnels.editConf.greTunnels.ip.mssAdjust

       Possibilities:
               disabled   (0)
               auto   (65536)"
   ::= {er1645v2TvTmplCGreEntry 53280768}

er1645v2TvTmplCGreIpRipMetric OBJECT-TYPE
   SYNTAX      Integer32
   MAX-ACCESS  read-write
   STATUS      current
   DESCRIPTION
      "Path: tunnels.editConf.greTunnels.ip.rip.metric"
   ::= {er1645v2TvTmplCGreEntry 51712768}

er1645v2TvTmplCGreIpRipMetricOut OBJECT-TYPE
   SYNTAX      Integer32
   MAX-ACCESS  read-write
   STATUS      current
   DESCRIPTION
      "Path: tunnels.editConf.greTunnels.ip.rip.metricOut"
   ::= {er1645v2TvTmplCGreEntry 51713024}

er1645v2TvTmplCGreIpRipMode OBJECT-TYPE
   SYNTAX      INTEGER
               {
               disabled (0),
               passive (1),
               active (2)
               }
   MAX-ACCESS  read-write
   STATUS      current
   DESCRIPTION
      "Path: tunnels.editConf.greTunnels.ip.rip.mode

       Possibilities:
               disabled   (0)
               passive   (1)
               active   (2)"
   ::= {er1645v2TvTmplCGreEntry 51713280}

er1645v2TvTmplCGreIpRipTxVersion OBJECT-TYPE
   SYNTAX      INTEGER
               {
               rip1 (0),
               rip2 (1),
               rip1mcompatible (2)
               }
   MAX-ACCESS  read-write
   STATUS      current
   DESCRIPTION
      "Path: tunnels.editConf.greTunnels.ip.rip.txVersion

       Possibilities:
               rip1   (0)
               rip2   (1)
               rip1-compatible   (2)"
   ::= {er1645v2TvTmplCGreEntry 51716864}

er1645v2TvTmplCGreIpRipRxVersion OBJECT-TYPE
   SYNTAX      INTEGER
               {
               rip1only (0),
               rip2only (1),
               rip12 (2)
               }
   MAX-ACCESS  read-write
   STATUS      current
   DESCRIPTION
      "Path: tunnels.editConf.greTunnels.ip.rip.rxVersion

       Possibilities:
               rip1only   (0)
               rip2only   (1)
               rip1&2   (2)"
   ::= {er1645v2TvTmplCGreEntry 51717120}

er1645v2TvTmplCGreIpRipSplitHorizon OBJECT-TYPE
   SYNTAX      INTEGER
               {
               disabled (0),
               enabled (1),
               poisonedReverse (2)
               }
   MAX-ACCESS  read-write
   STATUS      current
   DESCRIPTION
      "Path: tunnels.editConf.greTunnels.ip.rip.splitHorizon

       Possibilities:
               disabled   (0)
               enabled   (1)
               poisonedReverse   (2)"
   ::= {er1645v2TvTmplCGreEntry 51713792}

er1645v2TvTmplCGreIpRipAuth OBJECT-TYPE
   SYNTAX      INTEGER
               {
               disabled (0),
               texts (1),
               md5 (2)
               }
   MAX-ACCESS  read-write
   STATUS      current
   DESCRIPTION
      "Path: tunnels.editConf.greTunnels.ip.rip.authentication

       Possibilities:
               disabled   (0)
               text    (1)
               md5   (2)"
   ::= {er1645v2TvTmplCGreEntry 51712512}

er1645v2TvTmplCGreIpRipFilter OBJECT-TYPE
   SYNTAX      DisplayString
   MAX-ACCESS  read-write
   STATUS      current
   DESCRIPTION
      "Path: tunnels.editConf.greTunnels.ip.rip.filter"
   ::= {er1645v2TvTmplCGreEntry 51716096}

er1645v2TvTmplCGreIpRipFilterIn OBJECT-TYPE
   SYNTAX      DisplayString
   MAX-ACCESS  read-write
   STATUS      current
   DESCRIPTION
      "Path: tunnels.editConf.greTunnels.ip.rip.filterIn"
   ::= {er1645v2TvTmplCGreEntry 51716352}

er1645v2TvTmplCGreIpRipSnapshot OBJECT-TYPE
   SYNTAX      INTEGER
               {
               disabled (0),
               enabled (1)
               }
   MAX-ACCESS  read-write
   STATUS      current
   DESCRIPTION
      "Path: tunnels.editConf.greTunnels.ip.rip.snapshot

       Possibilities:
               disabled   (0)
               enabled   (1)"
   ::= {er1645v2TvTmplCGreEntry 51708160}

er1645v2TvTmplCGreIpRipClearNextHop OBJECT-TYPE
   SYNTAX      INTEGER
               {
               disabled (0),
               enabled (1)
               }
   MAX-ACCESS  read-write
   STATUS      current
   DESCRIPTION
      "Path: tunnels.editConf.greTunnels.ip.rip.clearNextHop

       Possibilities:
               disabled   (0)
               enabled   (1)"
   ::= {er1645v2TvTmplCGreEntry 51708416}

er1645v2TvTmplCGreIpAccPol OBJECT-TYPE
   SYNTAX      DisplayString
   MAX-ACCESS  read-write
   STATUS      current
   DESCRIPTION
      "Path: tunnels.editConf.greTunnels.ip.accessPolicy"
   ::= {er1645v2TvTmplCGreEntry 53084160}

er1645v2TvTmplCGreIpAB OBJECT-TYPE
   SYNTAX      DisplayString
   MAX-ACCESS  read-write
   STATUS      current
   DESCRIPTION
      "Path: tunnels.editConf.greTunnels.ip.trafficPolicy"
   ::= {er1645v2TvTmplCGreEntry 51249152}

er1645v2TvTmplCGreIpMA OBJECT-TYPE
   SYNTAX      INTEGER
               {
               disabled (0),
               enabled (1)
               }
   MAX-ACCESS  read-write
   STATUS      current
   DESCRIPTION
      "Path: tunnels.editConf.greTunnels.ip.mgmtAccess

       Possibilities:
               disabled   (0)
               enabled   (1)"
   ::= {er1645v2TvTmplCGreEntry 51380224}

er1645v2TvTmplCGreIpMF OBJECT-TYPE
   SYNTAX      Integer32
   MAX-ACCESS  read-write
   STATUS      current
   DESCRIPTION
      "Path: tunnels.editConf.greTunnels.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2TvTmplCGreEntry 51445760}

er1645v2TvTmplCGreIpDB OBJECT-TYPE
   SYNTAX      INTEGER
               {
               disabled (0),
               enabled (1)
               }
   MAX-ACCESS  read-write
   STATUS      current
   DESCRIPTION
      "Path: tunnels.editConf.greTunnels.ip.directedBroadcasts

       Possibilities:
               disabled   (0)
               enabled   (1)"
   ::= {er1645v2TvTmplCGreEntry 51773440}

er1645v2TvTmplCGreIpIR OBJECT-TYPE
   SYNTAX      INTEGER
               {
               disabled (0),
               enabled (1)
               }
   MAX-ACCESS  read-write
   STATUS      current
   DESCRIPTION
      "Path: tunnels.editConf.greTunnels.ip.icmpRedirects

       Possibilities:
               disabled   (0)
               enabled   (1)"
   ::= {er1645v2TvTmplCGreEntry 52035584}

er1645v2TvTmplCGreIpIgmp OBJECT-TYPE
   SYNTAX      INTEGER
               {
               disabled (0),
               proxy (1),
               router (2),
               v3Router (5)
               }
   MAX-ACCESS  read-write
   STATUS      current
   DESCRIPTION
      "Path: tunnels.editConf.greTunnels.ip.igmp

       Possibilities:
               disabled   (0)
               proxy   (1)
               router   (2)
               v3Router   (5)"
   ::= {er1645v2TvTmplCGreEntry 52428800}

er1645v2TvTmplCGreIpNN OBJECT-TYPE
   SYNTAX      DisplayString
   MAX-ACCESS  read-write
   STATUS      current
   DESCRIPTION
      "Path: tunnels.editConf.greTunnels.ip.nat"
   ::= {er1645v2TvTmplCGreEntry 52101120}

er1645v2TvTmplCGreIpPimMode OBJECT-TYPE
   SYNTAX      INTEGER
               {
               disabled (0),
               sparse (1),
               passive (2)
               }
   MAX-ACCESS  read-write
   STATUS      current
   DESCRIPTION
      "Path: tunnels.editConf.greTunnels.ip.pim.mode

       Possibilities:
               disabled   (0)
               sparse   (1)
               passive   (2)"
   ::= {er1645v2TvTmplCGreEntry 53346560}

er1645v2TvTmplCGreIpPimDrPriority OBJECT-TYPE
   SYNTAX      Counter32
   MAX-ACCESS  read-write
   STATUS      current
   DESCRIPTION
      "Path: tunnels.editConf.greTunnels.ip.pim.drPriority

       32 bit unsigned wrappable counter."
   ::= {er1645v2TvTmplCGreEntry 53346816}

er1645v2TvTmplCGreIpPimHelloTime OBJECT-TYPE
   SYNTAX      TimeTicks
   MAX-ACCESS  read-write
   STATUS      current
   DESCRIPTION
      "Path: tunnels.editConf.greTunnels.ip.pim.helloTime

       Time in centi-second."
   ::= {er1645v2TvTmplCGreEntry 53347072}

er1645v2TvTmplCGreIpPimPropagationDelay OBJECT-TYPE
   SYNTAX      TimeTicks
   MAX-ACCESS  read-write
   STATUS      current
   DESCRIPTION
      "Path: tunnels.editConf.greTunnels.ip.pim.propagationDelay

       Time in centi-second."
   ::= {er1645v2TvTmplCGreEntry 53347328}

er1645v2TvTmplCGreIpPimOverrideInterval OBJECT-TYPE
   SYNTAX      TimeTicks
   MAX-ACCESS  read-write
   STATUS      current
   DESCRIPTION
      "Path: tunnels.editConf.greTunnels.ip.pim.overrideInterval

       Time in centi-second."
   ::= {er1645v2TvTmplCGreEntry 53347584}

er1645v2TvTmplCGreIpPimBsrBorder OBJECT-TYPE
   SYNTAX      INTEGER
               {
               disabled (0),
               enabled (1)
               }
   MAX-ACCESS  read-write
   STATUS      current
   DESCRIPTION
      "Path: tunnels.editConf.greTunnels.ip.pim.bsrBorder

       Possibilities:
               disabled   (0)
               enabled   (1)"
   ::= {er1645v2TvTmplCGreEntry 53347840}

er1645v2TvTmplCGreIpPimTtlThreshold OBJECT-TYPE
   SYNTAX      Integer32
   MAX-ACCESS  read-write
   STATUS      current
   DESCRIPTION
      "Path: tunnels.editConf.greTunnels.ip.pim.ttlThreshold"
   ::= {er1645v2TvTmplCGreEntry 53348096}

er1645v2TvTmplCGreIpIMNetworkUnreachable OBJECT-TYPE
   SYNTAX      INTEGER
               {
               disabled (0),
               enabled (1)
               }
   MAX-ACCESS  read-write
   STATUS      current
   DESCRIPTION
      "Path: tunnels.editConf.greTunnels.ip.icmpMessages.networkUnreachable

       Possibilities:
               disabled   (0)
               enabled   (1)"
   ::= {er1645v2TvTmplCGreEntry 53412096}

er1645v2TvTmplCGreIpIMHostUnreachable OBJECT-TYPE
   SYNTAX      INTEGER
               {
               disabled (0),
               enabled (1)
               }
   MAX-ACCESS  read-write
   STATUS      current
   DESCRIPTION
      "Path: tunnels.editConf.greTunnels.ip.icmpMessages.hostUnreachable

       Possibilities:
               disabled   (0)
               enabled   (1)"
   ::= {er1645v2TvTmplCGreEntry 53412352}

er1645v2TvTmplCGreIpIMProtocolUnreachable OBJECT-TYPE
   SYNTAX      INTEGER
               {
               disabled (0),
               enabled (1)
               }
   MAX-ACCESS  read-write
   STATUS      current
   DESCRIPTION
      "Path: tunnels.editConf.greTunnels.ip.icmpMessages.protocolUnreachable

       Possibilities:
               disabled   (0)
               enabled   (1)"
   ::= {er1645v2TvTmplCGreEntry 53412608}

er1645v2TvTmplCGreIpIMPortUnreachable OBJECT-TYPE
   SYNTAX      INTEGER
               {
               disabled (0),
               enabled (1)
               }
   MAX-ACCESS  read-write
   STATUS      current
   DESCRIPTION
      "Path: tunnels.editConf.greTunnels.ip.icmpMessages.portUnreachable

       Possibilities:
               disabled   (0)
               enabled   (1)"
   ::= {er1645v2TvTmplCGreEntry 53412864}

er1645v2TvTmplCGreIpIMMtuExceeded OBJECT-TYPE
   SYNTAX      INTEGER
               {
               disabled (0),
               enabled (1)
               }
   MAX-ACCESS  read-write
   STATUS      current
   DESCRIPTION
      "Path: tunnels.editConf.greTunnels.ip.icmpMessages.mtuExceeded

       Possibilities:
               disabled   (0)
               enabled   (1)"
   ::= {er1645v2TvTmplCGreEntry 53413120}

er1645v2TvTmplCGreIpIMAdminProhibited OBJECT-TYPE
   SYNTAX      INTEGER
               {
               disabled (0),
               enabled (1)
               }
   MAX-ACCESS  read-write
   STATUS      current
   DESCRIPTION
      "Path: tunnels.editConf.greTunnels.ip.icmpMessages.adminProhibited

       Possibilities:
               disabled   (0)
               enabled   (1)"
   ::= {er1645v2TvTmplCGreEntry 53413376}

er1645v2TvTmplCGreIpIMTtlExceeded OBJECT-TYPE
   SYNTAX      INTEGER
               {
               disabled (0),
               enabled (1)
               }
   MAX-ACCESS  read-write
   STATUS      current
   DESCRIPTION
      "Path: tunnels.editConf.greTunnels.ip.icmpMessages.ttlExceeded

       Possibilities:
               disabled   (0)
               enabled   (1)"
   ::= {er1645v2TvTmplCGreEntry 53413632}

er1645v2TvTmplCGreIpIMRedirect OBJECT-TYPE
   SYNTAX      INTEGER
               {
               disabled (0),
               enabled (1)
               }
   MAX-ACCESS  read-write
   STATUS      current
   DESCRIPTION
      "Path: tunnels.editConf.greTunnels.ip.icmpMessages.redirect

       Possibilities:
               disabled   (0)
               enabled   (1)"
   ::= {er1645v2TvTmplCGreEntry 53413888}

er1645v2TvTmplCGreBrAccList OBJECT-TYPE
   SYNTAX      DisplayString
   MAX-ACCESS  read-write
   STATUS      current
   DESCRIPTION
      "Path: tunnels.editConf.greTunnels.bridging.accessList"
   ::= {er1645v2TvTmplCGreEntry 453246976}

er1645v2TvTmplCGreBrInACL OBJECT-TYPE
   SYNTAX      DisplayString
   MAX-ACCESS  read-write
   STATUS      current
   DESCRIPTION
      "Path: tunnels.editConf.greTunnels.bridging.inAccessList"
   ::= {er1645v2TvTmplCGreEntry 456916992}

er1645v2TvTmplCGreBrTp OBJECT-TYPE
   SYNTAX      DisplayString
   MAX-ACCESS  read-write
   STATUS      current
   DESCRIPTION
      "Path: tunnels.editConf.greTunnels.bridging.trafficPolicy"
   ::= {er1645v2TvTmplCGreEntry 454295552}

er1645v2TvTmplCGreBrBrGrp OBJECT-TYPE
   SYNTAX      DisplayString
   MAX-ACCESS  read-write
   STATUS      current
   DESCRIPTION
      "Path: tunnels.editConf.greTunnels.bridging.bridgeGroup"
   ::= {er1645v2TvTmplCGreEntry 454819840}

er1645v2TvTmplCGreBrLimBC OBJECT-TYPE
   SYNTAX      INTEGER
               {
               disabled (0),
               enabled (1)
               }
   MAX-ACCESS  read-write
   STATUS      current
   DESCRIPTION
      "Path: tunnels.editConf.greTunnels.bridging.limitBroadcasts

       Possibilities:
               disabled   (0)
               enabled   (1)"
   ::= {er1645v2TvTmplCGreEntry 455081984}

er1645v2TvTmplCGreBrPrivateMode OBJECT-TYPE
   SYNTAX      INTEGER
               {
               disabled (0),
               enabled (1)
               }
   MAX-ACCESS  read-write
   STATUS      current
   DESCRIPTION
      "Path: tunnels.editConf.greTunnels.bridging.privateMode

       Possibilities:
               disabled   (0)
               enabled   (1)"
   ::= {er1645v2TvTmplCGreEntry 459538432}

er1645v2TvTmplCGreBrLearning OBJECT-TYPE
   SYNTAX      INTEGER
               {
               disabled (0),
               enabled (1)
               }
   MAX-ACCESS  read-write
   STATUS      current
   DESCRIPTION
      "Path: tunnels.editConf.greTunnels.bridging.learning

       Possibilities:
               disabled   (0)
               enabled   (1)"
   ::= {er1645v2TvTmplCGreEntry 456130560}

er1645v2TvTmplCGreBrMaxCacheSize OBJECT-TYPE
   SYNTAX      INTEGER
               {
               unlimited (0)
               }
   MAX-ACCESS  read-write
   STATUS      current
   DESCRIPTION
      "Path: tunnels.editConf.greTunnels.bridging.maxCacheSize

       Possibilities:
               unlimited   (0)"
   ::= {er1645v2TvTmplCGreEntry 456392704}

er1645v2TvTmplCGreBrRelearnDropOnRelearn OBJECT-TYPE
   SYNTAX      INTEGER
               {
               disabled (0),
               enabled (1)
               }
   MAX-ACCESS  read-write
   STATUS      current
   DESCRIPTION
      "Path: tunnels.editConf.greTunnels.bridging.relearn.dropOnRelearn

       Possibilities:
               disabled   (0)
               enabled   (1)"
   ::= {er1645v2TvTmplCGreEntry 456655872}

er1645v2TvTmplCGreBrRelearnShutdownThreshold OBJECT-TYPE
   SYNTAX      Integer32
   MAX-ACCESS  read-write
   STATUS      current
   DESCRIPTION
      "Path: tunnels.editConf.greTunnels.bridging.relearn.shutdownThreshold"
   ::= {er1645v2TvTmplCGreEntry 456656896}

er1645v2TvTmplCGreBrRelearnShutdownTime OBJECT-TYPE
   SYNTAX      TimeTicks
   MAX-ACCESS  read-write
   STATUS      current
   DESCRIPTION
      "Path: tunnels.editConf.greTunnels.bridging.relearn.shutdownTime

       Time in centi-second."
   ::= {er1645v2TvTmplCGreEntry 456657920}

er1645v2TvTmplCGreBrRelearnLoopDetection OBJECT-TYPE
   SYNTAX      INTEGER
               {
               disabled (0),
               passive (1),
               active (2)
               }
   MAX-ACCESS  read-write
   STATUS      current
   DESCRIPTION
      "Path: tunnels.editConf.greTunnels.bridging.relearn.loopDetection

       Possibilities:
               disabled   (0)
               passive   (1)
               active   (2)"
   ::= {er1645v2TvTmplCGreEntry 456658944}

er1645v2TvTmplCGreBrRelearnLoopDetectionInterval OBJECT-TYPE
   SYNTAX      TimeTicks
   MAX-ACCESS  read-write
   STATUS      current
   DESCRIPTION
      "Path: tunnels.editConf.greTunnels.bridging.relearn.loopDetectionInterval

       Time in centi-second."
   ::= {er1645v2TvTmplCGreEntry 456659968}

er1645v2TvTmplCGreBrVlanMemberShip OBJECT-TYPE
   SYNTAX      INTEGER
               {
               all (0),
               none (1),
               grouped (2)
               }
   MAX-ACCESS  read-write
   STATUS      current
   DESCRIPTION
      "Path: tunnels.editConf.greTunnels.bridging.vlanMemberShip

       Possibilities:
               all   (0)
               none   (1)
               grouped   (2)"
   ::= {er1645v2TvTmplCGreEntry 457965568}

er1645v2TvTmplCGreBrVlTUntaggedAction OBJECT-TYPE
   SYNTAX      INTEGER
               {
               discard (0),
               accept (1),
               tag (2)
               }
   MAX-ACCESS  read-write
   STATUS      current
   DESCRIPTION
      "Path: tunnels.editConf.greTunnels.bridging.vlanTagging.untagged.action

       Possibilities:
               discard   (0)
               accept   (1)
               tag   (2)"
   ::= {er1645v2TvTmplCGreEntry 459055104}

er1645v2TvTmplCGreBrVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.greTunnels.bridging.vlanTagging.untagged.tagInfo.tpid

       Possibilities:
               dot1Q   (33024)
               dot1ad   (34984)
               0x9100   (37120)
               0x9200   (37376)
               0x9300   (37632)"
   ::= {er1645v2TvTmplCGreEntry 459059712}

er1645v2TvTmplCGreBrVlTUntaggedTagInfoVid OBJECT-TYPE
   SYNTAX      Integer32
   MAX-ACCESS  read-write
   STATUS      current
   DESCRIPTION
      "Path: tunnels.editConf.greTunnels.bridging.vlanTagging.untagged.tagInfo.vid"
   ::= {er1645v2TvTmplCGreEntry 459060224}

er1645v2TvTmplCGreBrVlTUnknownVlansAction OBJECT-TYPE
   SYNTAX      INTEGER
               {
               discard (0),
               accept (1),
               tag (2)
               }
   MAX-ACCESS  read-write
   STATUS      current
   DESCRIPTION
      "Path: tunnels.editConf.greTunnels.bridging.vlanTagging.unknownVlans.action

       Possibilities:
               discard   (0)
               accept   (1)
               tag   (2)"
   ::= {er1645v2TvTmplCGreEntry 459120640}

er1645v2TvTmplCGreBrVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.greTunnels.bridging.vlanTagging.unknownVlans.tagInfo.tpid

       Possibilities:
               dot1Q   (33024)
               dot1ad   (34984)
               0x9100   (37120)
               0x9200   (37376)
               0x9300   (37632)"
   ::= {er1645v2TvTmplCGreEntry 459125248}

er1645v2TvTmplCGreBrVlTUnknownVlansTagInfoVid OBJECT-TYPE
   SYNTAX      Integer32
   MAX-ACCESS  read-write
   STATUS      current
   DESCRIPTION
      "Path: tunnels.editConf.greTunnels.bridging.vlanTagging.unknownVlans.tagInfo.vid"
   ::= {er1645v2TvTmplCGreEntry 459125760}

er1645v2TvTmplCGreBrDot1adType OBJECT-TYPE
   SYNTAX      INTEGER
               {
               slOPTg (0),
               cPort (4),
               sPort (1),
               nni (2)
               }
   MAX-ACCESS  read-write
   STATUS      current
   DESCRIPTION
      "Path: tunnels.editConf.greTunnels.bridging.dot1ad.type

       Possibilities:
               <OPT>   (0)
               cPort   (4)
               sPort   (1)
               nni   (2)"
   ::= {er1645v2TvTmplCGreEntry 460850176}

er1645v2TvTmplCGreBrPriority OBJECT-TYPE
   SYNTAX      Integer32
   MAX-ACCESS  read-write
   STATUS      current
   DESCRIPTION
      "Path: tunnels.editConf.greTunnels.bridging.priority"
   ::= {er1645v2TvTmplCGreEntry 453509120}

er1645v2TvTmplCGreBrPathCost OBJECT-TYPE
   SYNTAX      Integer32
   MAX-ACCESS  read-write
   STATUS      current
   DESCRIPTION
      "Path: tunnels.editConf.greTunnels.bridging.pathCost"
   ::= {er1645v2TvTmplCGreEntry 453771264}

er1645v2TvTmplCGreBrInternalPathCost OBJECT-TYPE
   SYNTAX      Integer32
   MAX-ACCESS  read-write
   STATUS      current
   DESCRIPTION
      "Path: tunnels.editConf.greTunnels.bridging.internalPathCost"
   ::= {er1645v2TvTmplCGreEntry 457703424}

er1645v2TvTmplCGreBrTCD OBJECT-TYPE
   SYNTAX      INTEGER
               {
               disabled (0),
               enabled (1)
               }
   MAX-ACCESS  read-write
   STATUS      current
   DESCRIPTION
      "Path: tunnels.editConf.greTunnels.bridging.topologyChangeDetection

       Possibilities:
               disabled   (0)
               enabled   (1)"
   ::= {er1645v2TvTmplCGreEntry 454033408}

er1645v2TvTmplCGreBrRestrictedRole OBJECT-TYPE
   SYNTAX      INTEGER
               {
               disabled (0),
               enabled (1)
               }
   MAX-ACCESS  read-write
   STATUS      current
   DESCRIPTION
      "Path: tunnels.editConf.greTunnels.bridging.restrictedRole

       Possibilities:
               disabled   (0)
               enabled   (1)"
   ::= {er1645v2TvTmplCGreEntry 458227712}

er1645v2TvTmplCGreBrAdminEdge OBJECT-TYPE
   SYNTAX      INTEGER
               {
               disabled (0),
               enabled (1)
               }
   MAX-ACCESS  read-write
   STATUS      current
   DESCRIPTION
      "Path: tunnels.editConf.greTunnels.bridging.adminEdge

       Possibilities:
               disabled   (0)
               enabled   (1)"
   ::= {er1645v2TvTmplCGreEntry 457179136}

er1645v2TvTmplCGreBrOamMacDeviceMac OBJECT-TYPE
   SYNTAX      DisplayString
   MAX-ACCESS  read-write
   STATUS      current
   DESCRIPTION
      "Path: tunnels.editConf.greTunnels.bridging.ethOam.macAddress.deviceMac"
   ::= {er1645v2TvTmplCGreEntry 458506496}

er1645v2TvTmplCGreBrOamMacUserMac OBJECT-TYPE
   SYNTAX      OCTET STRING
   MAX-ACCESS  read-write
   STATUS      current
   DESCRIPTION
      "Path: tunnels.editConf.greTunnels.bridging.ethOam.macAddress.userMac

       MAC address."
   ::= {er1645v2TvTmplCGreEntry 458506368}

er1645v2TvTmplCGreBrOamMacBridgeMac OBJECT-TYPE
   SYNTAX      DisplayString
   MAX-ACCESS  read-write
   STATUS      current
   DESCRIPTION
      "Path: tunnels.editConf.greTunnels.bridging.ethOam.macAddress.bridgeMac"
   ::= {er1645v2TvTmplCGreEntry 458506432}

er1645v2TvTmplCGreBrMgmtInline OBJECT-TYPE
   SYNTAX      INTEGER
               {
               disabled (0),
               enabled (1)
               }
   MAX-ACCESS  read-write
   STATUS      current
   DESCRIPTION
      "Path: tunnels.editConf.greTunnels.bridging.mgmtInline

       Possibilities:
               disabled   (0)
               enabled   (1)"
   ::= {er1645v2TvTmplCGreEntry 458752000}

er1645v2TvTmplCGreBrL2ptMode OBJECT-TYPE
   SYNTAX      INTEGER
               {
               disabled (0),
               enabled (1)
               }
   MAX-ACCESS  read-write
   STATUS      current
   DESCRIPTION
      "Path: tunnels.editConf.greTunnels.bridging.l2ProtTunnel.mode

       Possibilities:
               disabled   (0)
               enabled   (1)"
   ::= {er1645v2TvTmplCGreEntry 459292672}

er1645v2TvTmplCGreBrL2ptProtocols OBJECT-TYPE
   SYNTAX      Integer32
   MAX-ACCESS  read-write
   STATUS      current
   DESCRIPTION
      "Path: tunnels.editConf.greTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TvTmplCGreEntry 459309056}

er1645v2TvTmplCGreBrL2ptDestMac OBJECT-TYPE
   SYNTAX      OCTET STRING
   MAX-ACCESS  read-write
   STATUS      current
   DESCRIPTION
      "Path: tunnels.editConf.greTunnels.bridging.l2ProtTunnel.destinationMac

       MAC address."
   ::= {er1645v2TvTmplCGreEntry 459325440}

er1645v2TvTmplCGreBrL2ptCos OBJECT-TYPE
   SYNTAX      INTEGER
               {
               unchanged (255)
               }
   MAX-ACCESS  read-write
   STATUS      current
   DESCRIPTION
      "Path: tunnels.editConf.greTunnels.bridging.l2ProtTunnel.cos

       Possibilities:
               unchanged   (255)"
   ::= {er1645v2TvTmplCGreEntry 459341824}

er1645v2TvTmplCGreBrL2ptDropThrStp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.stp

       unit name = packets/sec

       Possibilities:
               unlimited   (0)"
   ::= {er1645v2TvTmplCGreEntry 459358272}

er1645v2TvTmplCGreBrL2ptDropThrLldp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.lldp

       unit name = packets/sec

       Possibilities:
               unlimited   (0)"
   ::= {er1645v2TvTmplCGreEntry 459358336}

er1645v2TvTmplCGreBrL2ptDropThrOam OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.oam

       unit name = packets/sec

       Possibilities:
               unlimited   (0)"
   ::= {er1645v2TvTmplCGreEntry 459358400}

er1645v2TvTmplCGreBrL2ptDropThrCdp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.cdp

       unit name = packets/sec

       Possibilities:
               unlimited   (0)"
   ::= {er1645v2TvTmplCGreEntry 459358464}

er1645v2TvTmplCGreBrL2ptDropThrVtp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.vtp

       unit name = packets/sec

       Possibilities:
               unlimited   (0)"
   ::= {er1645v2TvTmplCGreEntry 459358528}

er1645v2TvTmplCGreBrL2ptDropThrLacp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.lacp

       unit name = packets/sec

       Possibilities:
               unlimited   (0)"
   ::= {er1645v2TvTmplCGreEntry 459358592}

er1645v2TvTmplCGreBrL2ptDropThrEfmOam OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.efmOam

       unit name = packets/sec

       Possibilities:
               unlimited   (0)"
   ::= {er1645v2TvTmplCGreEntry 459358656}

er1645v2TvTmplCGreBrL2ptDropThrPvst OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.pvst

       unit name = packets/sec

       Possibilities:
               unlimited   (0)"
   ::= {er1645v2TvTmplCGreEntry 459358720}

er1645v2TvTmplCGreBrL2ptDropThrMmrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.mmrp

       unit name = packets/sec

       Possibilities:
               unlimited   (0)"
   ::= {er1645v2TvTmplCGreEntry 459358784}

er1645v2TvTmplCGreBrL2ptDropThrMvrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.mvrp

       unit name = packets/sec

       Possibilities:
               unlimited   (0)"
   ::= {er1645v2TvTmplCGreEntry 459358848}

er1645v2TvTmplCGreBrL2ptDropThrGvrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.gvrp

       unit name = packets/sec

       Possibilities:
               unlimited   (0)"
   ::= {er1645v2TvTmplCGreEntry 459358912}

er1645v2TvTmplCGreBrL2ptDropThrGmrp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.gmrp

       unit name = packets/sec

       Possibilities:
               unlimited   (0)"
   ::= {er1645v2TvTmplCGreEntry 459358976}

er1645v2TvTmplCGreBrL2ptDropThrDtp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.dtp

       unit name = packets/sec

       Possibilities:
               unlimited   (0)"
   ::= {er1645v2TvTmplCGreEntry 459359040}

er1645v2TvTmplCGreBrL2ptDropThrPagp OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.pagp

       unit name = packets/sec

       Possibilities:
               unlimited   (0)"
   ::= {er1645v2TvTmplCGreEntry 459359104}

er1645v2TvTmplCGreBrL2ptDropThrUdld OBJECT-TYPE
   SYNTAX      INTEGER
               {
               unlimited (0)
               }
   UNITS       "packets/sec"
   MAX-ACCESS  read-write
   STATUS      current
   DESCRIPTION
      "Path: tunnels.editConf.greTunnels.bridging.l2ProtTunnel.dropThresholds.udld

       unit name = packets/sec

       Possibilities:
               unlimited   (0)"
   ::= {er1645v2TvTmplCGreEntry 459359168}

er1645v2TvTmplCGreVirtEthernetVirtualEthernet OBJECT-TYPE
   SYNTAX      DisplayString
   MAX-ACCESS  read-write
   STATUS      current
   DESCRIPTION
      "Path: tunnels.editConf.greTunnels.virtEthernet.virtualEthernet"
   ::= {er1645v2TvTmplCGreEntry 151060480}

er1645v2TvTmplCGreGreVrfRouter OBJECT-TYPE
   SYNTAX      DisplayString
   MAX-ACCESS  read-write
   STATUS      current
   DESCRIPTION
      "Path: tunnels.editConf.greTunnels.gre.vrfRouter"
   ::= {er1645v2TvTmplCGreEntry 590086144}

er1645v2TvTmplCGreGreLocalIpAddress OBJECT-TYPE
   SYNTAX      IpAddress
   MAX-ACCESS  read-write
   STATUS      current
   DESCRIPTION
      "Path: tunnels.editConf.greTunnels.gre.localIpAddress"
   ::= {er1645v2TvTmplCGreEntry 587268096}

er1645v2TvTmplCGreGreRemoteIpAddress OBJECT-TYPE
   SYNTAX      IpAddress
   MAX-ACCESS  read-write
   STATUS      current
   DESCRIPTION
      "Path: tunnels.editConf.greTunnels.gre.remoteIpAddress"
   ::= {er1645v2TvTmplCGreEntry 587333632}

er1645v2TvTmplCGreGreVrfRouterV6 OBJECT-TYPE
   SYNTAX      DisplayString
   MAX-ACCESS  read-write
   STATUS      current
   DESCRIPTION
      "Path: tunnels.editConf.greTunnels.gre.vrfRouterV6"
   ::= {er1645v2TvTmplCGreEntry 590348288}

er1645v2TvTmplCGreGreLocalIpV6Address OBJECT-TYPE
   SYNTAX      Ipv6Address
   MAX-ACCESS  read-write
   STATUS      current
   DESCRIPTION
      "Path: tunnels.editConf.greTunnels.gre.localIpV6Address

       ipv6 address"
   ::= {er1645v2TvTmplCGreEntry 590217216}

er1645v2TvTmplCGreGreRemoteIpV6Address OBJECT-TYPE
   SYNTAX      Ipv6Address
   MAX-ACCESS  read-write
   STATUS      current
   DESCRIPTION
      "Path: tunnels.editConf.greTunnels.gre.remoteIpV6Address

       ipv6 address"
   ::= {er1645v2TvTmplCGreEntry 590282752}

er1645v2TvTmplCGreGreLocalInterface OBJECT-TYPE
   SYNTAX      DisplayString
   MAX-ACCESS  read-write
   STATUS      current
   DESCRIPTION
      "Path: tunnels.editConf.greTunnels.gre.localInterface"
   ::= {er1645v2TvTmplCGreEntry 588251136}

er1645v2TvTmplCGreGreRemoteDnsName OBJECT-TYPE
   SYNTAX      DisplayString
   MAX-ACCESS  read-write
   STATUS      current
   DESCRIPTION
      "Path: tunnels.editConf.greTunnels.gre.remoteDnsName"
   ::= {er1645v2TvTmplCGreEntry 587399168}

er1645v2TvTmplCGreGreKey OBJECT-TYPE
   SYNTAX      Integer32
   MAX-ACCESS  read-write
   STATUS      current
   DESCRIPTION
      "Path: tunnels.editConf.greTunnels.gre.key"
   ::= {er1645v2TvTmplCGreEntry 587595776}

er1645v2TvTmplCGreGreKpAlMode OBJECT-TYPE
   SYNTAX      INTEGER
               {
               disabled (0),
               enabled (1)
               }
   MAX-ACCESS  read-write
   STATUS      current
   DESCRIPTION
      "Path: tunnels.editConf.greTunnels.gre.keepAlive.mode

       Possibilities:
               disabled   (0)
               enabled   (1)"
   ::= {er1645v2TvTmplCGreEntry 587727104}

er1645v2TvTmplCGreGreKpAlInterval OBJECT-TYPE
   SYNTAX      TimeTicks
   MAX-ACCESS  read-write
   STATUS      current
   DESCRIPTION
      "Path: tunnels.editConf.greTunnels.gre.keepAlive.interval

       Time in centi-second."
   ::= {er1645v2TvTmplCGreEntry 587727360}

er1645v2TvTmplCGreGreKpAlRepTimeOut OBJECT-TYPE
   SYNTAX      TimeTicks
   MAX-ACCESS  read-write
   STATUS      current
   DESCRIPTION
      "Path: tunnels.editConf.greTunnels.gre.keepAlive.replyTimeOut

       Time in centi-second."
   ::= {er1645v2TvTmplCGreEntry 587727616}

er1645v2TvTmplCGreGreKpAlFailsPrmt OBJECT-TYPE
   SYNTAX      Integer32
   MAX-ACCESS  read-write
   STATUS      current
   DESCRIPTION
      "Path: tunnels.editConf.greTunnels.gre.keepAlive.failsPermitted"
   ::= {er1645v2TvTmplCGreEntry 587727872}

er1645v2TvTmplCGreGreRRoutDefRt OBJECT-TYPE
   SYNTAX      INTEGER
               {
               disabled (0),
               enabled (1)
               }
   MAX-ACCESS  read-write
   STATUS      current
   DESCRIPTION
      "Path: tunnels.editConf.greTunnels.gre.remoteRoute.useDefaultRoute

       Possibilities:
               disabled   (0)
               enabled   (1)"
   ::= {er1645v2TvTmplCGreEntry 587923712}

er1645v2TvTmplCGreGreTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256),
               queueTosMap (257)
               }
   MAX-ACCESS  read-write
   STATUS      current
   DESCRIPTION
      "Path: tunnels.editConf.greTunnels.gre.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)
               queueTosMap   (257)"
   ::= {er1645v2TvTmplCGreEntry 587988992}

er1645v2TvTmplCGreGreQueueTosMapQueue1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589168896}

er1645v2TvTmplCGreGreQueueTosMapQueue2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589169152}

er1645v2TvTmplCGreGreQueueTosMapQueue3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589169408}

er1645v2TvTmplCGreGreQueueTosMapQueue4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589169664}

er1645v2TvTmplCGreGreQueueTosMapQueue5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.queue5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589169920}

er1645v2TvTmplCGreGreQueueTosMapLowDelayQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.lowDelayQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589170176}

er1645v2TvTmplCGreGreQueueTosMapLowDelay2Queue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.lowDelay2Queue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589170432}

er1645v2TvTmplCGreGreQueueTosMapSystemQueue OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: tunnels.editConf.greTunnels.gre.queueTosMap.systemQueue

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2TvTmplCGreEntry 589170688}

er1645v2TvTmplCGreGreDf OBJECT-TYPE
   SYNTAX      INTEGER
               {
               clear (0),
               set (1),
               copy (2)
               }
   MAX-ACCESS  read-write
   STATUS      current
   DESCRIPTION
      "Path: tunnels.editConf.greTunnels.gre.dontFragmentBit

       Possibilities:
               clear   (0)
               set   (1)
               copy   (2)"
   ::= {er1645v2TvTmplCGreEntry 588054528}

er1645v2TvTmplCGreGreTtl OBJECT-TYPE
   SYNTAX      INTEGER
               {
               copy (256)
               }
   MAX-ACCESS  read-write
   STATUS      current
   DESCRIPTION
      "Path: tunnels.editConf.greTunnels.gre.ttl

       Possibilities:
               copy   (256)"
   ::= {er1645v2TvTmplCGreEntry 588120064}

er1645v2TvTmplCGreGreMtu OBJECT-TYPE
   SYNTAX      Integer32
   MAX-ACCESS  read-write
   STATUS      current
   DESCRIPTION
      "Path: tunnels.editConf.greTunnels.gre.mtu"
   ::= {er1645v2TvTmplCGreEntry 588382208}

er1645v2TvTmplCGreMplsMode OBJECT-TYPE
   SYNTAX      INTEGER
               {
               disabled (0),
               enabled (1)
               }
   MAX-ACCESS  read-write
   STATUS      current
   DESCRIPTION
      "Path: tunnels.editConf.greTunnels.mpls.mode

       Possibilities:
               disabled   (0)
               enabled   (1)"
   ::= {er1645v2TvTmplCGreEntry 167837696}

er1645v2TvTmplCGreMplsInLabel OBJECT-TYPE
   SYNTAX      Integer32
   MAX-ACCESS  read-write
   STATUS      current
   DESCRIPTION
      "Path: tunnels.editConf.greTunnels.mpls.inLabel"
   ::= {er1645v2TvTmplCGreEntry 167903232}

er1645v2TvTmplCGreMplsOutLabel OBJECT-TYPE
   SYNTAX      Integer32
   MAX-ACCESS  read-write
   STATUS      current
   DESCRIPTION
      "Path: tunnels.editConf.greTunnels.mpls.outLabel"
   ::= {er1645v2TvTmplCGreEntry 168099840}

er1645v2TvTmplCGreMplsTrafficClassMode OBJECT-TYPE
   SYNTAX      INTEGER
               {
               fixed (0),
               qos (1)
               }
   MAX-ACCESS  read-write
   STATUS      current
   DESCRIPTION
      "Path: tunnels.editConf.greTunnels.mpls.trafficClass.mode

       Possibilities:
               fixed   (0)
               qos   (1)"
   ::= {er1645v2TvTmplCGreEntry 167969024}

er1645v2TvTmplCGreMplsTrafficClassFixed OBJECT-TYPE
   SYNTAX      Integer32
   MAX-ACCESS  read-write
   STATUS      current
   DESCRIPTION
      "Path: tunnels.editConf.greTunnels.mpls.trafficClass.fixed"
   ::= {er1645v2TvTmplCGreEntry 167969280}

er1645v2TvTmplCGreMplsTrafficClassQosP0 OBJECT-TYPE
   SYNTAX      Integer32
   MAX-ACCESS  read-write
   STATUS      current
   DESCRIPTION
      "Path: tunnels.editConf.greTunnels.mpls.trafficClass.qos.p0"
   ::= {er1645v2TvTmplCGreEntry 167969537}

er1645v2TvTmplCGreMplsTrafficClassQosP1 OBJECT-TYPE
   SYNTAX      Integer32
   MAX-ACCESS  read-write
   STATUS      current
   DESCRIPTION
      "Path: tunnels.editConf.greTunnels.mpls.trafficClass.qos.p1"
   ::= {er1645v2TvTmplCGreEntry 167969538}

er1645v2TvTmplCGreMplsTrafficClassQosP2 OBJECT-TYPE
   SYNTAX      Integer32
   MAX-ACCESS  read-write
   STATUS      current
   DESCRIPTION
      "Path: tunnels.editConf.greTunnels.mpls.trafficClass.qos.p2"
   ::= {er1645v2TvTmplCGreEntry 167969539}

er1645v2TvTmplCGreMplsTrafficClassQosP3 OBJECT-TYPE
   SYNTAX      Integer32
   MAX-ACCESS  read-write
   STATUS      current
   DESCRIPTION
      "Path: tunnels.editConf.greTunnels.mpls.trafficClass.qos.p3"
   ::= {er1645v2TvTmplCGreEntry 167969540}

er1645v2TvTmplCGreMplsTrafficClassQosP4 OBJECT-TYPE
   SYNTAX      Integer32
   MAX-ACCESS  read-write
   STATUS      current
   DESCRIPTION
      "Path: tunnels.editConf.greTunnels.mpls.trafficClass.qos.p4"
   ::= {er1645v2TvTmplCGreEntry 167969541}

er1645v2TvTmplCGreMplsTrafficClassQosP5 OBJECT-TYPE
   SYNTAX      Integer32
   MAX-ACCESS  read-write
   STATUS      current
   DESCRIPTION
      "Path: tunnels.editConf.greTunnels.mpls.trafficClass.qos.p5"
   ::= {er1645v2TvTmplCGreEntry 167969542}

er1645v2TvTmplCGreMplsTrafficClassQosP6 OBJECT-TYPE
   SYNTAX      Integer32
   MAX-ACCESS  read-write
   STATUS      current
   DESCRIPTION
      "Path: tunnels.editConf.greTunnels.mpls.trafficClass.qos.p6"
   ::= {er1645v2TvTmplCGreEntry 167969543}

er1645v2TvTmplCGreMplsTrafficClassQosP7 OBJECT-TYPE
   SYNTAX      Integer32
   MAX-ACCESS  read-write
   STATUS      current
   DESCRIPTION
      "Path: tunnels.editConf.greTunnels.mpls.trafficClass.qos.p7"
   ::= {er1645v2TvTmplCGreEntry 167969544}

er1645v2TvTmplCGreMplsTtl OBJECT-TYPE
   SYNTAX      INTEGER
               {
               copy (256)
               }
   MAX-ACCESS  read-write
   STATUS      current
   DESCRIPTION
      "Path: tunnels.editConf.greTunnels.mpls.ttl

       Possibilities:
               copy   (256)"
   ::= {er1645v2TvTmplCGreEntry 168034304}

er1645v2TvTmplCGreInbBwCir OBJECT-TYPE
   SYNTAX      Integer32
   MAX-ACCESS  read-write
   STATUS      current
   DESCRIPTION
      "Path: tunnels.editConf.greTunnels.inboundBandwidth.cir"
   ::= {er1645v2TvTmplCGreEntry 117506048}

er1645v2TvTmplCGreInbBwTc OBJECT-TYPE
   SYNTAX      INTEGER
               {
               auto (0)
               }
   MAX-ACCESS  read-write
   STATUS      current
   DESCRIPTION
      "Path: tunnels.editConf.greTunnels.inboundBandwidth.tc

       Possibilities:
               auto   (0)"
   ::= {er1645v2TvTmplCGreEntry 117833728}

er1645v2TvTmplCGreInbBwCorrType OBJECT-TYPE
   SYNTAX      INTEGER
               {
               noCorrection (0),
               predefined (1),
               manual (2)
               }
   MAX-ACCESS  read-write
   STATUS      current
   DESCRIPTION
      "Path: tunnels.editConf.greTunnels.inboundBandwidth.correction.type

       Possibilities:
               noCorrection   (0)
               predefined   (1)
               manual   (2)"
   ::= {er1645v2TvTmplCGreEntry 117579776}

er1645v2TvTmplCGreInbBwCorrPredefEncapsFrameRelay OBJECT-TYPE
   SYNTAX      DisplayString
   MAX-ACCESS  read-write
   STATUS      current
   DESCRIPTION
      "Path: tunnels.editConf.greTunnels.inboundBandwidth.correction.predefined.encapsulation.frameRelay"
   ::= {er1645v2TvTmplCGreEntry 117589056}

er1645v2TvTmplCGreInbBwCorrPredefEncapsPpp OBJECT-TYPE
   SYNTAX      DisplayString
   MAX-ACCESS  read-write
   STATUS      current
   DESCRIPTION
      "Path: tunnels.editConf.greTunnels.inboundBandwidth.correction.predefined.encapsulation.ppp"
   ::= {er1645v2TvTmplCGreEntry 117589120}

er1645v2TvTmplCGreInbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.greTunnels.inboundBandwidth.correction.predefined.encapsulation.atm.higherLayer

       Possibilities:
               rfc2684   (0)
               ppp   (1)
               pppOverEthernet   (2)"
   ::= {er1645v2TvTmplCGreEntry 117589192}

er1645v2TvTmplCGreInbBwCorrPredefEncapsAtmMp OBJECT-TYPE
   SYNTAX      INTEGER
               {
               llcEncapsulation (0),
               vcMultiplexing (1)
               }
   MAX-ACCESS  read-write
   STATUS      current
   DESCRIPTION
      "Path: tunnels.editConf.greTunnels.inboundBandwidth.correction.predefined.encapsulation.atm.multiProtocol

       Possibilities:
               llcEncapsulation   (0)
               vcMultiplexing   (1)"
   ::= {er1645v2TvTmplCGreEntry 117589200}

er1645v2TvTmplCGreInbBwCorrPredefEncapsHdlc OBJECT-TYPE
   SYNTAX      DisplayString
   MAX-ACCESS  read-write
   STATUS      current
   DESCRIPTION
      "Path: tunnels.editConf.greTunnels.inboundBandwidth.correction.predefined.encapsulation.hdlc"
   ::= {er1645v2TvTmplCGreEntry 117589248}

er1645v2TvTmplCGreInbBwCorrPredefEncapsEfmFs OBJECT-TYPE
   SYNTAX      Integer32
   MAX-ACCESS  read-write
   STATUS      current
   DESCRIPTION
      "Path: tunnels.editConf.greTunnels.inboundBandwidth.correction.predefined.encapsulation.efm.fragmentSize"
   ::= {er1645v2TvTmplCGreEntry 117589320}

er1645v2TvTmplCGreInbBwCorrPredefEncapsEfmIb OBJECT-TYPE
   SYNTAX      Integer32
   MAX-ACCESS  read-write
   STATUS      current
   DESCRIPTION
      "Path: tunnels.editConf.greTunnels.inboundBandwidth.correction.predefined.encapsulation.efm.idleBytes"
   ::= {er1645v2TvTmplCGreEntry 117589328}

er1645v2TvTmplCGreInbBwCorrPredefMode OBJECT-TYPE
   SYNTAX      INTEGER
               {
               routing (0),
               bridging (1)
               }
   MAX-ACCESS  read-write
   STATUS      current
   DESCRIPTION
      "Path: tunnels.editConf.greTunnels.inboundBandwidth.correction.predefined.mode

       Possibilities:
               routing   (0)
               bridging   (1)"
   ::= {er1645v2TvTmplCGreEntry 117590016}

er1645v2TvTmplCGreInbBwCorrManualOverhead OBJECT-TYPE
   SYNTAX      Integer32
   MAX-ACCESS  read-write
   STATUS      current
   DESCRIPTION
      "Path: tunnels.editConf.greTunnels.inboundBandwidth.correction.manual.overhead"
   ::= {er1645v2TvTmplCGreEntry 117596192}

er1645v2TvTmplCGreInbBwCorrManualFrameData OBJECT-TYPE
   SYNTAX      Counter32
   MAX-ACCESS  read-write
   STATUS      current
   DESCRIPTION
      "Path: tunnels.editConf.greTunnels.inboundBandwidth.correction.manual.frameData

       32 bit unsigned wrappable counter."
   ::= {er1645v2TvTmplCGreEntry 117596224}

er1645v2TvTmplCGreInbBwCorrManualFrameHeader OBJECT-TYPE
   SYNTAX      Counter32
   MAX-ACCESS  read-write
   STATUS      current
   DESCRIPTION
      "Path: tunnels.editConf.greTunnels.inboundBandwidth.correction.manual.frameHeader

       32 bit unsigned wrappable counter."
   ::= {er1645v2TvTmplCGreEntry 117596256}

er1645v2TvTmplCGreInbBwMaxFifoQLen OBJECT-TYPE
   SYNTAX      Integer32
   MAX-ACCESS  read-write
   STATUS      current
   DESCRIPTION
      "Path: tunnels.editConf.greTunnels.inboundBandwidth.maxFifoQLen"
   ::= {er1645v2TvTmplCGreEntry 117637120}

er1645v2TvTmplCGreInbBwPriorityPolicy OBJECT-TYPE
   SYNTAX      DisplayString
   MAX-ACCESS  read-write
   STATUS      current
   DESCRIPTION
      "Path: tunnels.editConf.greTunnels.inboundBandwidth.priorityPolicy"
   ::= {er1645v2TvTmplCGreEntry 117702656}

er1645v2TvTmplCGreBandwidthMode OBJECT-TYPE
   SYNTAX      INTEGER
               {
               reshaping (1),
               policing (2),
               policingReshape (3)
               }
   MAX-ACCESS  read-write
   STATUS      current
   DESCRIPTION
      "Path: tunnels.editConf.greTunnels.bandwidth.mode

       Possibilities:
               reshaping   (1)
               policing   (2)
               policingReshape   (3)"
   ::= {er1645v2TvTmplCGreEntry 148897792}

er1645v2TvTmplCGreBandwidthCir OBJECT-TYPE
   SYNTAX      Integer32
   MAX-ACCESS  read-write
   STATUS      current
   DESCRIPTION
      "Path: tunnels.editConf.greTunnels.bandwidth.cir"
   ::= {er1645v2TvTmplCGreEntry 135266304}

er1645v2TvTmplCGreBandwidthEir OBJECT-TYPE
   SYNTAX      Integer32
   MAX-ACCESS  read-write
   STATUS      current
   DESCRIPTION
      "Path: tunnels.editConf.greTunnels.bandwidth.eir"
   ::= {er1645v2TvTmplCGreEntry 141557760}

er1645v2TvTmplCGreBandwidthUnit OBJECT-TYPE
   SYNTAX      INTEGER
               {
               bitssec (1),
               percent (2)
               }
   MAX-ACCESS  read-write
   STATUS      current
   DESCRIPTION
      "Path: tunnels.editConf.greTunnels.bandwidth.unit

       Possibilities:
               bits/sec   (1)
               percent   (2)"
   ::= {er1645v2TvTmplCGreEntry 139460608}

er1645v2TvTmplCGreBandwidthTc OBJECT-TYPE
   SYNTAX      INTEGER
               {
               auto (0)
               }
   MAX-ACCESS  read-write
   STATUS      current
   DESCRIPTION
      "Path: tunnels.editConf.greTunnels.bandwidth.tc

       Possibilities:
               auto   (0)"
   ::= {er1645v2TvTmplCGreEntry 140509184}

er1645v2TvTmplCGreBandwidthTcFactor OBJECT-TYPE
   SYNTAX      INTEGER
               {
               ms (10),
               s100us (1)
               }
   MAX-ACCESS  read-write
   STATUS      current
   DESCRIPTION
      "Path: tunnels.editConf.greTunnels.bandwidth.tcFactor

       Possibilities:
               ms   (10)
               *100us   (1)"
   ::= {er1645v2TvTmplCGreEntry 142606336}

er1645v2TvTmplCGreBandwidthCorrType OBJECT-TYPE
   SYNTAX      INTEGER
               {
               noCorrection (0),
               predefined (1),
               manual (2)
               }
   MAX-ACCESS  read-write
   STATUS      current
   DESCRIPTION
      "Path: tunnels.editConf.greTunnels.bandwidth.correction.type

       Possibilities:
               noCorrection   (0)
               predefined   (1)
               manual   (2)"
   ::= {er1645v2TvTmplCGreEntry 136445952}

er1645v2TvTmplCGreBandwidthCorrPredefEncapsFrameRelay OBJECT-TYPE
   SYNTAX      DisplayString
   MAX-ACCESS  read-write
   STATUS      current
   DESCRIPTION
      "Path: tunnels.editConf.greTunnels.bandwidth.correction.predefined.encapsulation.frameRelay"
   ::= {er1645v2TvTmplCGreEntry 136594432}

er1645v2TvTmplCGreBandwidthCorrPredefEncapsPpp OBJECT-TYPE
   SYNTAX      DisplayString
   MAX-ACCESS  read-write
   STATUS      current
   DESCRIPTION
      "Path: tunnels.editConf.greTunnels.bandwidth.correction.predefined.encapsulation.ppp"
   ::= {er1645v2TvTmplCGreEntry 136595456}

er1645v2TvTmplCGreBandwidthCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.greTunnels.bandwidth.correction.predefined.encapsulation.atm.higherLayer

       Possibilities:
               rfc2684   (0)
               ppp   (1)
               pppOverEthernet   (2)"
   ::= {er1645v2TvTmplCGreEntry 136596608}

er1645v2TvTmplCGreBandwidthCorrPredefEncapsAtmMp OBJECT-TYPE
   SYNTAX      INTEGER
               {
               llcEncapsulation (0),
               vcMultiplexing (1)
               }
   MAX-ACCESS  read-write
   STATUS      current
   DESCRIPTION
      "Path: tunnels.editConf.greTunnels.bandwidth.correction.predefined.encapsulation.atm.multiProtocol

       Possibilities:
               llcEncapsulation   (0)
               vcMultiplexing   (1)"
   ::= {er1645v2TvTmplCGreEntry 136596736}

er1645v2TvTmplCGreBandwidthCorrPredefEncapsHdlc OBJECT-TYPE
   SYNTAX      DisplayString
   MAX-ACCESS  read-write
   STATUS      current
   DESCRIPTION
      "Path: tunnels.editConf.greTunnels.bandwidth.correction.predefined.encapsulation.hdlc"
   ::= {er1645v2TvTmplCGreEntry 136597504}

er1645v2TvTmplCGreBandwidthCorrPredefEncapsEfmFs OBJECT-TYPE
   SYNTAX      Integer32
   MAX-ACCESS  read-write
   STATUS      current
   DESCRIPTION
      "Path: tunnels.editConf.greTunnels.bandwidth.correction.predefined.encapsulation.efm.fragmentSize"
   ::= {er1645v2TvTmplCGreEntry 136598656}

er1645v2TvTmplCGreBandwidthCorrPredefEncapsEfmIb OBJECT-TYPE
   SYNTAX      Integer32
   MAX-ACCESS  read-write
   STATUS      current
   DESCRIPTION
      "Path: tunnels.editConf.greTunnels.bandwidth.correction.predefined.encapsulation.efm.idleBytes"
   ::= {er1645v2TvTmplCGreEntry 136598784}

er1645v2TvTmplCGreBandwidthCorrPredefMode OBJECT-TYPE
   SYNTAX      INTEGER
               {
               routing (0),
               bridging (1)
               }
   MAX-ACCESS  read-write
   STATUS      current
   DESCRIPTION
      "Path: tunnels.editConf.greTunnels.bandwidth.correction.predefined.mode

       Possibilities:
               routing   (0)
               bridging   (1)"
   ::= {er1645v2TvTmplCGreEntry 136609792}

er1645v2TvTmplCGreBandwidthCorrManualOverhead OBJECT-TYPE
   SYNTAX      Integer32
   MAX-ACCESS  read-write
   STATUS      current
   DESCRIPTION
      "Path: tunnels.editConf.greTunnels.bandwidth.correction.manual.overhead"
   ::= {er1645v2TvTmplCGreEntry 136708608}

er1645v2TvTmplCGreBandwidthCorrManualFrameData OBJECT-TYPE
   SYNTAX      Counter32
   MAX-ACCESS  read-write
   STATUS      current
   DESCRIPTION
      "Path: tunnels.editConf.greTunnels.bandwidth.correction.manual.frameData

       32 bit unsigned wrappable counter."
   ::= {er1645v2TvTmplCGreEntry 136709120}

er1645v2TvTmplCGreBandwidthCorrManualFrameHeader OBJECT-TYPE
   SYNTAX      Counter32
   MAX-ACCESS  read-write
   STATUS      current
   DESCRIPTION
      "Path: tunnels.editConf.greTunnels.bandwidth.correction.manual.frameHeader

       32 bit unsigned wrappable counter."
   ::= {er1645v2TvTmplCGreEntry 136709632}

er1645v2TvTmplCGreBandwidthMaxFifoQLen OBJECT-TYPE
   SYNTAX      Integer32
   MAX-ACCESS  read-write
   STATUS      current
   DESCRIPTION
      "Path: tunnels.editConf.greTunnels.bandwidth.maxFifoQLen"
   ::= {er1645v2TvTmplCGreEntry 137363456}

er1645v2TvTmplCGreBandwidthDeFlagCir OBJECT-TYPE
   SYNTAX      INTEGER
               {
               allowed (1),
               notAllowed (2)
               }
   MAX-ACCESS  read-write
   STATUS      current
   DESCRIPTION
      "Path: tunnels.editConf.greTunnels.bandwidth.deFlag.cir

       Possibilities:
               allowed   (1)
               notAllowed   (2)"
   ::= {er1645v2TvTmplCGreEntry 147853312}

er1645v2TvTmplCGreBandwidthDeFlagEir OBJECT-TYPE
   SYNTAX      INTEGER
               {
               allowed (1),
               notAllowed (2)
               }
   MAX-ACCESS  read-write
   STATUS      current
   DESCRIPTION
      "Path: tunnels.editConf.greTunnels.bandwidth.deFlag.eir

       Possibilities:
               allowed   (1)
               notAllowed   (2)"
   ::= {er1645v2TvTmplCGreEntry 147857408}

er1645v2TvTmplCGreBandwidthDeFlagViolate OBJECT-TYPE
   SYNTAX      INTEGER
               {
               allowed (1),
               notAllowed (2)
               }
   MAX-ACCESS  read-write
   STATUS      current
   DESCRIPTION
      "Path: tunnels.editConf.greTunnels.bandwidth.deFlag.violate

       Possibilities:
               allowed   (1)
               notAllowed   (2)"
   ::= {er1645v2TvTmplCGreEntry 147861504}

er1645v2TvTmplCGreBandwidthActCirActNone OBJECT-TYPE
   SYNTAX      OCTET STRING
   MAX-ACCESS  read-write
   STATUS      current
   DESCRIPTION
      "Path: tunnels.editConf.greTunnels.bandwidth.action.cirAction.none"
   ::= {er1645v2TvTmplCGreEntry 150085632}

er1645v2TvTmplCGreBandwidthActCirActEthCos1 OBJECT-TYPE
   SYNTAX      INTEGER
               {
               unchanged (256)
               }
   MAX-ACCESS  read-write
   STATUS      current
   DESCRIPTION
      "Path: tunnels.editConf.greTunnels.bandwidth.action.cirAction.ethernet.cosDepth1

       Possibilities:
               unchanged   (256)"
   ::= {er1645v2TvTmplCGreEntry 150094080}

er1645v2TvTmplCGreBandwidthActCirActEthDei1 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth1

       Possibilities:
               unchanged   (255)
               clear   (0)
               set   (1)"
   ::= {er1645v2TvTmplCGreEntry 150099200}

er1645v2TvTmplCGreBandwidthActCirActEthCos2 OBJECT-TYPE
   SYNTAX      INTEGER
               {
               unchanged (256)
               }
   MAX-ACCESS  read-write
   STATUS      current
   DESCRIPTION
      "Path: tunnels.editConf.greTunnels.bandwidth.action.cirAction.ethernet.cosDepth2

       Possibilities:
               unchanged   (256)"
   ::= {er1645v2TvTmplCGreEntry 150094336}

er1645v2TvTmplCGreBandwidthActCirActEthDei2 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth2

       Possibilities:
               unchanged   (255)
               clear   (0)
               set   (1)"
   ::= {er1645v2TvTmplCGreEntry 150099456}

er1645v2TvTmplCGreBandwidthActCirActEthCos3 OBJECT-TYPE
   SYNTAX      INTEGER
               {
               unchanged (256)
               }
   MAX-ACCESS  read-write
   STATUS      current
   DESCRIPTION
      "Path: tunnels.editConf.greTunnels.bandwidth.action.cirAction.ethernet.cosDepth3

       Possibilities:
               unchanged   (256)"
   ::= {er1645v2TvTmplCGreEntry 150094592}

er1645v2TvTmplCGreBandwidthActCirActEthDei3 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth3

       Possibilities:
               unchanged   (255)
               clear   (0)
               set   (1)"
   ::= {er1645v2TvTmplCGreEntry 150099712}

er1645v2TvTmplCGreBandwidthActCirActEthCos4 OBJECT-TYPE
   SYNTAX      INTEGER
               {
               unchanged (256)
               }
   MAX-ACCESS  read-write
   STATUS      current
   DESCRIPTION
      "Path: tunnels.editConf.greTunnels.bandwidth.action.cirAction.ethernet.cosDepth4

       Possibilities:
               unchanged   (256)"
   ::= {er1645v2TvTmplCGreEntry 150094848}

er1645v2TvTmplCGreBandwidthActCirActEthDei4 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth4

       Possibilities:
               unchanged   (255)
               clear   (0)
               set   (1)"
   ::= {er1645v2TvTmplCGreEntry 150099968}

er1645v2TvTmplCGreBandwidthActCirActEthCos5 OBJECT-TYPE
   SYNTAX      INTEGER
               {
               unchanged (256)
               }
   MAX-ACCESS  read-write
   STATUS      current
   DESCRIPTION
      "Path: tunnels.editConf.greTunnels.bandwidth.action.cirAction.ethernet.cosDepth5

       Possibilities:
               unchanged   (256)"
   ::= {er1645v2TvTmplCGreEntry 150095104}

er1645v2TvTmplCGreBandwidthActCirActEthDei5 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth5

       Possibilities:
               unchanged   (255)
               clear   (0)
               set   (1)"
   ::= {er1645v2TvTmplCGreEntry 150100224}

er1645v2TvTmplCGreBandwidthActCirActEthCos6 OBJECT-TYPE
   SYNTAX      INTEGER
               {
               unchanged (256)
               }
   MAX-ACCESS  read-write
   STATUS      current
   DESCRIPTION
      "Path: tunnels.editConf.greTunnels.bandwidth.action.cirAction.ethernet.cosDepth6

       Possibilities:
               unchanged   (256)"
   ::= {er1645v2TvTmplCGreEntry 150095360}

er1645v2TvTmplCGreBandwidthActCirActEthDei6 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth6

       Possibilities:
               unchanged   (255)
               clear   (0)
               set   (1)"
   ::= {er1645v2TvTmplCGreEntry 150100480}

er1645v2TvTmplCGreBandwidthActCirActEthCos7 OBJECT-TYPE
   SYNTAX      INTEGER
               {
               unchanged (256)
               }
   MAX-ACCESS  read-write
   STATUS      current
   DESCRIPTION
      "Path: tunnels.editConf.greTunnels.bandwidth.action.cirAction.ethernet.cosDepth7

       Possibilities:
               unchanged   (256)"
   ::= {er1645v2TvTmplCGreEntry 150095616}

er1645v2TvTmplCGreBandwidthActCirActEthDei7 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth7

       Possibilities:
               unchanged   (255)
               clear   (0)
               set   (1)"
   ::= {er1645v2TvTmplCGreEntry 150100736}

er1645v2TvTmplCGreBandwidthActCirActEthCos8 OBJECT-TYPE
   SYNTAX      INTEGER
               {
               unchanged (256)
               }
   MAX-ACCESS  read-write
   STATUS      current
   DESCRIPTION
      "Path: tunnels.editConf.greTunnels.bandwidth.action.cirAction.ethernet.cosDepth8

       Possibilities:
               unchanged   (256)"
   ::= {er1645v2TvTmplCGreEntry 150095872}

er1645v2TvTmplCGreBandwidthActCirActEthDei8 OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deiDepth8

       Possibilities:
               unchanged   (255)
               clear   (0)
               set   (1)"
   ::= {er1645v2TvTmplCGreEntry 150100992}

er1645v2TvTmplCGreBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCGreEntry 150096128}

er1645v2TvTmplCGreBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCGreEntry 150096384}

er1645v2TvTmplCGreBandwidthActCirActEthDrpLev OBJECT-TYPE
   SYNTAX      INTEGER
               {
               unchanged (0)
               }
   MAX-ACCESS  read-write
   STATUS      current
   DESCRIPTION
      "Path: tunnels.editConf.greTunnels.bandwidth.action.cirAction.ethernet.dropLevel

       Possibilities:
               unchanged   (0)"
   ::= {er1645v2TvTmplCGreEntry 150096640}

er1645v2TvTmplCGreBandwidthActCirActEthDeFlag OBJECT-TYPE
   SYNTAX      INTEGER
               {
               unchanged (255),
               clear (0),
               set (1)
               }
   MAX-ACCESS  read-write
   STATUS      current
   DESCRIPTION
      "Path: tunnels.editConf.greTunnels.bandwidth.action.cirAction.ethernet.deFlag

       Possibilities:
               unchanged   (255)
               clear   (0)
               set   (1)"
   ::= {er1645v2TvTmplCGreEntry 150097408}

er1645v2TvTmplCGreBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCGreEntry 150120704}

er1645v2TvTmplCGreBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCGreEntry 150120960}

er1645v2TvTmplCGreBandwidthActCirActIpDrpLev OBJECT-TYPE
   SYNTAX      INTEGER
               {
               unchanged (0)
               }
   MAX-ACCESS  read-write
   STATUS      current
   DESCRIPTION
      "Path: tunnels.editConf.greTunnels.bandwidth.action.cirAction.ip.dropLevel

       Possibilities:
               unchanged   (0)"
   ::= {er1645v2TvTmplCGreEntry 150121216}

er1645v2TvTmplCGreBandwidthActCirActIpDeFlag OBJECT-TYPE
   SYNTAX      INTEGER
               {
               unchanged (255),
               clear (0),
               set (1)
               }
   MAX-ACCESS  read-write
   STATUS      current
   DESCRIPTION
      "Path: tunnels.editConf.greTunnels.bandwidth.action.cirAction.ip.deFlag

       Possibilities:
               unchanged   (255)
               clear   (0)
               set   (1)"
   ::= {er1645v2TvTmplCGreEntry 150121984}

er1645v2TvTmplCGreBandwidthActEirActNone OBJECT-TYPE
   SYNTAX      OCTET STRING
   MAX-ACCESS  read-write
   STATUS      current
   DESCRIPTION
      "Path: tunnels.editConf.greTunnels.bandwidth.action.eirAction.none"
   ::= {er1645v2TvTmplCGreEntry 150216704}

er1645v2TvTmplCGreBandwidthActEirActEthCos1 OBJECT-TYPE
   SYNTAX      INTEGER
               {
               unchanged (256)
               }
   MAX-ACCESS  read-write
   STATUS      current
   DESCRIPTION
      "Path: tunnels.editConf.greTunnels.bandwidth.action.eirAction.ethernet.cosDepth1

       Possibilities:
               unchanged   (256)"
   ::= {er1645v2TvTmplCGreEntry 150225152}

er1645v2TvTmplCGreBandwidthActEirActEthDei1 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth1

       Possibilities:
               unchanged   (255)
               clear   (0)
               set   (1)"
   ::= {er1645v2TvTmplCGreEntry 150230272}

er1645v2TvTmplCGreBandwidthActEirActEthCos2 OBJECT-TYPE
   SYNTAX      INTEGER
               {
               unchanged (256)
               }
   MAX-ACCESS  read-write
   STATUS      current
   DESCRIPTION
      "Path: tunnels.editConf.greTunnels.bandwidth.action.eirAction.ethernet.cosDepth2

       Possibilities:
               unchanged   (256)"
   ::= {er1645v2TvTmplCGreEntry 150225408}

er1645v2TvTmplCGreBandwidthActEirActEthDei2 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth2

       Possibilities:
               unchanged   (255)
               clear   (0)
               set   (1)"
   ::= {er1645v2TvTmplCGreEntry 150230528}

er1645v2TvTmplCGreBandwidthActEirActEthCos3 OBJECT-TYPE
   SYNTAX      INTEGER
               {
               unchanged (256)
               }
   MAX-ACCESS  read-write
   STATUS      current
   DESCRIPTION
      "Path: tunnels.editConf.greTunnels.bandwidth.action.eirAction.ethernet.cosDepth3

       Possibilities:
               unchanged   (256)"
   ::= {er1645v2TvTmplCGreEntry 150225664}

er1645v2TvTmplCGreBandwidthActEirActEthDei3 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth3

       Possibilities:
               unchanged   (255)
               clear   (0)
               set   (1)"
   ::= {er1645v2TvTmplCGreEntry 150230784}

er1645v2TvTmplCGreBandwidthActEirActEthCos4 OBJECT-TYPE
   SYNTAX      INTEGER
               {
               unchanged (256)
               }
   MAX-ACCESS  read-write
   STATUS      current
   DESCRIPTION
      "Path: tunnels.editConf.greTunnels.bandwidth.action.eirAction.ethernet.cosDepth4

       Possibilities:
               unchanged   (256)"
   ::= {er1645v2TvTmplCGreEntry 150225920}

er1645v2TvTmplCGreBandwidthActEirActEthDei4 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth4

       Possibilities:
               unchanged   (255)
               clear   (0)
               set   (1)"
   ::= {er1645v2TvTmplCGreEntry 150231040}

er1645v2TvTmplCGreBandwidthActEirActEthCos5 OBJECT-TYPE
   SYNTAX      INTEGER
               {
               unchanged (256)
               }
   MAX-ACCESS  read-write
   STATUS      current
   DESCRIPTION
      "Path: tunnels.editConf.greTunnels.bandwidth.action.eirAction.ethernet.cosDepth5

       Possibilities:
               unchanged   (256)"
   ::= {er1645v2TvTmplCGreEntry 150226176}

er1645v2TvTmplCGreBandwidthActEirActEthDei5 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth5

       Possibilities:
               unchanged   (255)
               clear   (0)
               set   (1)"
   ::= {er1645v2TvTmplCGreEntry 150231296}

er1645v2TvTmplCGreBandwidthActEirActEthCos6 OBJECT-TYPE
   SYNTAX      INTEGER
               {
               unchanged (256)
               }
   MAX-ACCESS  read-write
   STATUS      current
   DESCRIPTION
      "Path: tunnels.editConf.greTunnels.bandwidth.action.eirAction.ethernet.cosDepth6

       Possibilities:
               unchanged   (256)"
   ::= {er1645v2TvTmplCGreEntry 150226432}

er1645v2TvTmplCGreBandwidthActEirActEthDei6 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth6

       Possibilities:
               unchanged   (255)
               clear   (0)
               set   (1)"
   ::= {er1645v2TvTmplCGreEntry 150231552}

er1645v2TvTmplCGreBandwidthActEirActEthCos7 OBJECT-TYPE
   SYNTAX      INTEGER
               {
               unchanged (256)
               }
   MAX-ACCESS  read-write
   STATUS      current
   DESCRIPTION
      "Path: tunnels.editConf.greTunnels.bandwidth.action.eirAction.ethernet.cosDepth7

       Possibilities:
               unchanged   (256)"
   ::= {er1645v2TvTmplCGreEntry 150226688}

er1645v2TvTmplCGreBandwidthActEirActEthDei7 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth7

       Possibilities:
               unchanged   (255)
               clear   (0)
               set   (1)"
   ::= {er1645v2TvTmplCGreEntry 150231808}

er1645v2TvTmplCGreBandwidthActEirActEthCos8 OBJECT-TYPE
   SYNTAX      INTEGER
               {
               unchanged (256)
               }
   MAX-ACCESS  read-write
   STATUS      current
   DESCRIPTION
      "Path: tunnels.editConf.greTunnels.bandwidth.action.eirAction.ethernet.cosDepth8

       Possibilities:
               unchanged   (256)"
   ::= {er1645v2TvTmplCGreEntry 150226944}

er1645v2TvTmplCGreBandwidthActEirActEthDei8 OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deiDepth8

       Possibilities:
               unchanged   (255)
               clear   (0)
               set   (1)"
   ::= {er1645v2TvTmplCGreEntry 150232064}

er1645v2TvTmplCGreBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCGreEntry 150227200}

er1645v2TvTmplCGreBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCGreEntry 150227456}

er1645v2TvTmplCGreBandwidthActEirActEthDrpLev OBJECT-TYPE
   SYNTAX      INTEGER
               {
               unchanged (0)
               }
   MAX-ACCESS  read-write
   STATUS      current
   DESCRIPTION
      "Path: tunnels.editConf.greTunnels.bandwidth.action.eirAction.ethernet.dropLevel

       Possibilities:
               unchanged   (0)"
   ::= {er1645v2TvTmplCGreEntry 150227712}

er1645v2TvTmplCGreBandwidthActEirActEthDeFlag OBJECT-TYPE
   SYNTAX      INTEGER
               {
               unchanged (255),
               clear (0),
               set (1)
               }
   MAX-ACCESS  read-write
   STATUS      current
   DESCRIPTION
      "Path: tunnels.editConf.greTunnels.bandwidth.action.eirAction.ethernet.deFlag

       Possibilities:
               unchanged   (255)
               clear   (0)
               set   (1)"
   ::= {er1645v2TvTmplCGreEntry 150228480}

er1645v2TvTmplCGreBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCGreEntry 150251776}

er1645v2TvTmplCGreBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCGreEntry 150252032}

er1645v2TvTmplCGreBandwidthActEirActIpDrpLev OBJECT-TYPE
   SYNTAX      INTEGER
               {
               unchanged (0)
               }
   MAX-ACCESS  read-write
   STATUS      current
   DESCRIPTION
      "Path: tunnels.editConf.greTunnels.bandwidth.action.eirAction.ip.dropLevel

       Possibilities:
               unchanged   (0)"
   ::= {er1645v2TvTmplCGreEntry 150252288}

er1645v2TvTmplCGreBandwidthActEirActIpDeFlag OBJECT-TYPE
   SYNTAX      INTEGER
               {
               unchanged (255),
               clear (0),
               set (1)
               }
   MAX-ACCESS  read-write
   STATUS      current
   DESCRIPTION
      "Path: tunnels.editConf.greTunnels.bandwidth.action.eirAction.ip.deFlag

       Possibilities:
               unchanged   (255)
               clear   (0)
               set   (1)"
   ::= {er1645v2TvTmplCGreEntry 150253056}

er1645v2TvTmplCGreBandwidthActViolActNone OBJECT-TYPE
   SYNTAX      OCTET STRING
   MAX-ACCESS  read-write
   STATUS      current
   DESCRIPTION
      "Path: tunnels.editConf.greTunnels.bandwidth.action.violateAction.none"
   ::= {er1645v2TvTmplCGreEntry 150347776}

er1645v2TvTmplCGreBandwidthActViolActDrop OBJECT-TYPE
   SYNTAX      OCTET STRING
   MAX-ACCESS  read-write
   STATUS      current
   DESCRIPTION
      "Path: tunnels.editConf.greTunnels.bandwidth.action.violateAction.drop"
   ::= {er1645v2TvTmplCGreEntry 150364160}

er1645v2TvTmplCGreBandwidthActViolActEthCos1 OBJECT-TYPE
   SYNTAX      INTEGER
               {
               unchanged (256)
               }
   MAX-ACCESS  read-write
   STATUS      current
   DESCRIPTION
      "Path: tunnels.editConf.greTunnels.bandwidth.action.violateAction.ethernet.cosDepth1

       Possibilities:
               unchanged   (256)"
   ::= {er1645v2TvTmplCGreEntry 150356224}

er1645v2TvTmplCGreBandwidthActViolActEthDei1 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth1

       Possibilities:
               unchanged   (255)
               clear   (0)
               set   (1)"
   ::= {er1645v2TvTmplCGreEntry 150361344}

er1645v2TvTmplCGreBandwidthActViolActEthCos2 OBJECT-TYPE
   SYNTAX      INTEGER
               {
               unchanged (256)
               }
   MAX-ACCESS  read-write
   STATUS      current
   DESCRIPTION
      "Path: tunnels.editConf.greTunnels.bandwidth.action.violateAction.ethernet.cosDepth2

       Possibilities:
               unchanged   (256)"
   ::= {er1645v2TvTmplCGreEntry 150356480}

er1645v2TvTmplCGreBandwidthActViolActEthDei2 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth2

       Possibilities:
               unchanged   (255)
               clear   (0)
               set   (1)"
   ::= {er1645v2TvTmplCGreEntry 150361600}

er1645v2TvTmplCGreBandwidthActViolActEthCos3 OBJECT-TYPE
   SYNTAX      INTEGER
               {
               unchanged (256)
               }
   MAX-ACCESS  read-write
   STATUS      current
   DESCRIPTION
      "Path: tunnels.editConf.greTunnels.bandwidth.action.violateAction.ethernet.cosDepth3

       Possibilities:
               unchanged   (256)"
   ::= {er1645v2TvTmplCGreEntry 150356736}

er1645v2TvTmplCGreBandwidthActViolActEthDei3 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth3

       Possibilities:
               unchanged   (255)
               clear   (0)
               set   (1)"
   ::= {er1645v2TvTmplCGreEntry 150361856}

er1645v2TvTmplCGreBandwidthActViolActEthCos4 OBJECT-TYPE
   SYNTAX      INTEGER
               {
               unchanged (256)
               }
   MAX-ACCESS  read-write
   STATUS      current
   DESCRIPTION
      "Path: tunnels.editConf.greTunnels.bandwidth.action.violateAction.ethernet.cosDepth4

       Possibilities:
               unchanged   (256)"
   ::= {er1645v2TvTmplCGreEntry 150356992}

er1645v2TvTmplCGreBandwidthActViolActEthDei4 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth4

       Possibilities:
               unchanged   (255)
               clear   (0)
               set   (1)"
   ::= {er1645v2TvTmplCGreEntry 150362112}

er1645v2TvTmplCGreBandwidthActViolActEthCos5 OBJECT-TYPE
   SYNTAX      INTEGER
               {
               unchanged (256)
               }
   MAX-ACCESS  read-write
   STATUS      current
   DESCRIPTION
      "Path: tunnels.editConf.greTunnels.bandwidth.action.violateAction.ethernet.cosDepth5

       Possibilities:
               unchanged   (256)"
   ::= {er1645v2TvTmplCGreEntry 150357248}

er1645v2TvTmplCGreBandwidthActViolActEthDei5 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth5

       Possibilities:
               unchanged   (255)
               clear   (0)
               set   (1)"
   ::= {er1645v2TvTmplCGreEntry 150362368}

er1645v2TvTmplCGreBandwidthActViolActEthCos6 OBJECT-TYPE
   SYNTAX      INTEGER
               {
               unchanged (256)
               }
   MAX-ACCESS  read-write
   STATUS      current
   DESCRIPTION
      "Path: tunnels.editConf.greTunnels.bandwidth.action.violateAction.ethernet.cosDepth6

       Possibilities:
               unchanged   (256)"
   ::= {er1645v2TvTmplCGreEntry 150357504}

er1645v2TvTmplCGreBandwidthActViolActEthDei6 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth6

       Possibilities:
               unchanged   (255)
               clear   (0)
               set   (1)"
   ::= {er1645v2TvTmplCGreEntry 150362624}

er1645v2TvTmplCGreBandwidthActViolActEthCos7 OBJECT-TYPE
   SYNTAX      INTEGER
               {
               unchanged (256)
               }
   MAX-ACCESS  read-write
   STATUS      current
   DESCRIPTION
      "Path: tunnels.editConf.greTunnels.bandwidth.action.violateAction.ethernet.cosDepth7

       Possibilities:
               unchanged   (256)"
   ::= {er1645v2TvTmplCGreEntry 150357760}

er1645v2TvTmplCGreBandwidthActViolActEthDei7 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth7

       Possibilities:
               unchanged   (255)
               clear   (0)
               set   (1)"
   ::= {er1645v2TvTmplCGreEntry 150362880}

er1645v2TvTmplCGreBandwidthActViolActEthCos8 OBJECT-TYPE
   SYNTAX      INTEGER
               {
               unchanged (256)
               }
   MAX-ACCESS  read-write
   STATUS      current
   DESCRIPTION
      "Path: tunnels.editConf.greTunnels.bandwidth.action.violateAction.ethernet.cosDepth8

       Possibilities:
               unchanged   (256)"
   ::= {er1645v2TvTmplCGreEntry 150358016}

er1645v2TvTmplCGreBandwidthActViolActEthDei8 OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deiDepth8

       Possibilities:
               unchanged   (255)
               clear   (0)
               set   (1)"
   ::= {er1645v2TvTmplCGreEntry 150363136}

er1645v2TvTmplCGreBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCGreEntry 150358272}

er1645v2TvTmplCGreBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCGreEntry 150358528}

er1645v2TvTmplCGreBandwidthActViolActEthDrpLev OBJECT-TYPE
   SYNTAX      INTEGER
               {
               unchanged (0)
               }
   MAX-ACCESS  read-write
   STATUS      current
   DESCRIPTION
      "Path: tunnels.editConf.greTunnels.bandwidth.action.violateAction.ethernet.dropLevel

       Possibilities:
               unchanged   (0)"
   ::= {er1645v2TvTmplCGreEntry 150358784}

er1645v2TvTmplCGreBandwidthActViolActEthDeFlag OBJECT-TYPE
   SYNTAX      INTEGER
               {
               unchanged (255),
               clear (0),
               set (1)
               }
   MAX-ACCESS  read-write
   STATUS      current
   DESCRIPTION
      "Path: tunnels.editConf.greTunnels.bandwidth.action.violateAction.ethernet.deFlag

       Possibilities:
               unchanged   (255)
               clear   (0)
               set   (1)"
   ::= {er1645v2TvTmplCGreEntry 150359552}

er1645v2TvTmplCGreBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: tunnels.editConf.greTunnels.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2TvTmplCGreEntry 150382848}

er1645v2TvTmplCGreBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: tunnels.editConf.greTunnels.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2TvTmplCGreEntry 150383104}

er1645v2TvTmplCGreBandwidthActViolActIpDrpLev OBJECT-TYPE
   SYNTAX      INTEGER
               {
               unchanged (0)
               }
   MAX-ACCESS  read-write
   STATUS      current
   DESCRIPTION
      "Path: tunnels.editConf.greTunnels.bandwidth.action.violateAction.ip.dropLevel

       Possibilities:
               unchanged   (0)"
   ::= {er1645v2TvTmplCGreEntry 150383360}

er1645v2TvTmplCGreBandwidthActViolActIpDeFlag OBJECT-TYPE
   SYNTAX      INTEGER
               {
               unchanged (255),
               clear (0),
               set (1)
               }
   MAX-ACCESS  read-write
   STATUS      current
   DESCRIPTION
      "Path: tunnels.editConf.greTunnels.bandwidth.action.violateAction.ip.deFlag

       Possibilities:
               unchanged   (255)
               clear   (0)
               set   (1)"
   ::= {er1645v2TvTmplCGreEntry 150384128}

er1645v2TvTmplCGreBrVlTVlans OBJECT-TYPE
   SYNTAX      SEQUENCE OF Er1645v2TvTmplCGreBrVlTVlansEntry
   MAX-ACCESS  not-accessible
   STATUS      current
   DESCRIPTION
      ""
   ::= {er1645v2TvTmplCGre 459079680}

er1645v2TvTmplCGreBrVlTVlansEntry OBJECT-TYPE
   SYNTAX      Er1645v2TvTmplCGreBrVlTVlansEntry
   MAX-ACCESS  not-accessible
   STATUS      current
   DESCRIPTION
      ""
   INDEX      { er1645v2TvTmplCGreTableIx,
                er1645v2TvTmplCGreBrVlTVlansTableIx }
   ::= {er1645v2TvTmplCGreBrVlTVlans 1}

Er1645v2TvTmplCGreBrVlTVlansEntry ::=
   SEQUENCE
      {
      er1645v2TvTmplCGreBrVlTVlansActions
         VariableLengthTableActions,
      er1645v2TvTmplCGreBrVlTVlansTableIx
         TableIndex,
      er1645v2TvTmplCGreBrVlTVlansVid
         Integer32,
      er1645v2TvTmplCGreBrVlTVlansEndVid
         Integer32,
      er1645v2TvTmplCGreBrVlTVlansAction
         INTEGER,
      er1645v2TvTmplCGreBrVlTVlansTagInfoTpid
         INTEGER,
      er1645v2TvTmplCGreBrVlTVlansTagInfoVid
         Integer32
      }

er1645v2TvTmplCGreBrVlTVlansActions OBJECT-TYPE
   SYNTAX      VariableLengthTableActions
   MAX-ACCESS  read-write
   STATUS      current
   DESCRIPTION
      "By way of this field, some manipulations
       on this table may be performed."
   ::= {er1645v2TvTmplCGreBrVlTVlansEntry 2}

er1645v2TvTmplCGreBrVlTVlansTableIx OBJECT-TYPE
   SYNTAX      TableIndex
   MAX-ACCESS  not-accessible
   STATUS      current
   DESCRIPTION
      ""
   ::= {er1645v2TvTmplCGreBrVlTVlansEntry 11}

er1645v2TvTmplCGreBrVlTVlansVid OBJECT-TYPE
   SYNTAX      Integer32
   MAX-ACCESS  read-write
   STATUS      current
   DESCRIPTION
      "Path: tunnels.editConf.greTunnels.bridging.vlanTagging.vlans.vid"
   ::= {er1645v2TvTmplCGreBrVlTVlansEntry 536870912}

er1645v2TvTmplCGreBrVlTVlansEndVid OBJECT-TYPE
   SYNTAX      Integer32
   MAX-ACCESS  read-write
   STATUS      current
   DESCRIPTION
      "Path: tunnels.editConf.greTunnels.bridging.vlanTagging.vlans.endVid"
   ::= {er1645v2TvTmplCGreBrVlTVlansEntry 2147483648}

er1645v2TvTmplCGreBrVlTVlansAction OBJECT-TYPE
   SYNTAX      INTEGER
               {
               discard (0),
               accept (1),
               tag (2)
               }
   MAX-ACCESS  read-write
   STATUS      current
   DESCRIPTION
      "Path: tunnels.editConf.greTunnels.bridging.vlanTagging.vlans.action

       Possibilities:
               discard   (0)
               accept   (1)
               tag   (2)"
   ::= {er1645v2TvTmplCGreBrVlTVlansEntry 1073741824}

er1645v2TvTmplCGreBrVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.greTunnels.bridging.vlanTagging.vlans.tagInfo.tpid

       Possibilities:
               dot1Q   (33024)
               dot1ad   (34984)
               0x9100   (37120)
               0x9200   (37376)
               0x9300   (37632)"
   ::= {er1645v2TvTmplCGreBrVlTVlansEntry 1677721600}

er1645v2TvTmplCGreBrVlTVlansTagInfoVid OBJECT-TYPE
   SYNTAX      Integer32
   MAX-ACCESS  read-write
   STATUS      current
   DESCRIPTION
      "Path: tunnels.editConf.greTunnels.bridging.vlanTagging.vlans.tagInfo.vid"
   ::= {er1645v2TvTmplCGreBrVlTVlansEntry 1744830464}


er1645v2TvTmplIpV6toV4 OBJECT IDENTIFIER ::= {er1645v2TvTmpl 40}

er1645v2TvTmplIpV6toV4SSCTable OBJECT-TYPE
   SYNTAX      SEQUENCE OF Er1645v2TvTmplIpV6toV4Entry
   MAX-ACCESS  not-accessible
   STATUS      current
   DESCRIPTION
      "V6V4 tunnel config"
   ::= {er1645v2TvTmplIpV6toV4 1}

er1645v2TvTmplIpV6toV4Entry OBJECT-TYPE
   SYNTAX      Er1645v2TvTmplIpV6toV4Entry
   MAX-ACCESS  not-accessible
   STATUS      current
   DESCRIPTION
      ""
   INDEX      { er1645v2TvTmplIpV6toV4TableIx }
   ::= {er1645v2TvTmplIpV6toV4SSCTable 1}

Er1645v2TvTmplIpV6toV4Entry ::=
   SEQUENCE
      {
      er1645v2TvTmplIpV6toV4Actions
         VariableLengthTableActions,
      er1645v2TvTmplIpV6toV4TableIx
         TableIndex,
      er1645v2TvTmplIpV6toV4Name
         DisplayString,
      er1645v2TvTmplIpV6toV4Remark
         DisplayString,
      er1645v2TvTmplIpV6toV4AdminStatus
         INTEGER,
      er1645v2TvTmplIpV6toV4PriorityPolicy
         DisplayString,
      er1645v2TvTmplIpV6toV4IpV6VrfRouter
         DisplayString,
      er1645v2TvTmplIpV6toV4IpV6AddrAutoConfigNrDupAddrDetects
         Integer32,
      er1645v2TvTmplIpV6toV4IpV6AddrAutoConfigAcceptRa
         INTEGER,
      er1645v2TvTmplIpV6toV4IpV6AddrAutoConfigAcceptRaRdnss
         INTEGER,
      er1645v2TvTmplIpV6toV4IpV6AddrAutoConfigAcceptRaDnssl
         INTEGER,
      er1645v2TvTmplIpV6toV4IpV6DefaultRoute
         INTEGER,
      er1645v2TvTmplIpV6toV4IpV6RaSend
         INTEGER,
      er1645v2TvTmplIpV6toV4IpV6RaMinInterval
         TimeTicks,
      er1645v2TvTmplIpV6toV4IpV6RaMaxInterval
         TimeTicks,
      er1645v2TvTmplIpV6toV4IpV6RaManagedFlag
         INTEGER,
      er1645v2TvTmplIpV6toV4IpV6RaOtherConfFlag
         INTEGER,
      er1645v2TvTmplIpV6toV4IpV6RaLinkMtu
         Integer32,
      er1645v2TvTmplIpV6toV4IpV6RaReachableTime
         TimeTicks,
      er1645v2TvTmplIpV6toV4IpV6RaRetransmitTime
         TimeTicks,
      er1645v2TvTmplIpV6toV4IpV6RaHopLimit
         Integer32,
      er1645v2TvTmplIpV6toV4IpV6RaDefaultLifeTime
         TimeTicks,
      er1645v2TvTmplIpV6toV4IpV6RaDnsOptionsRdnssLifeTime
         TimeTicks,
      er1645v2TvTmplIpV6toV4IpV6RaDnsOptionsRdnssImportServers
         INTEGER,
      er1645v2TvTmplIpV6toV4IpV6RaDnsOptionsDnsslLifeTime
         TimeTicks,
      er1645v2TvTmplIpV6toV4IpV6RaDnsOptionsDnsslImportDomains
         INTEGER,
      er1645v2TvTmplIpV6toV4IpV6RsSend
         INTEGER,
      er1645v2TvTmplIpV6toV4IpV6RsMaxRandomDelay
         TimeTicks,
      er1645v2TvTmplIpV6toV4IpV6RsInterval
         TimeTicks,
      er1645v2TvTmplIpV6toV4IpV6RsMaxSolicitations
         Integer32,
      er1645v2TvTmplIpV6toV4IpV6TrafficPolicyInbound
         DisplayString,
      er1645v2TvTmplIpV6toV4IpV6TrafficPolicyOutbound
         DisplayString,
      er1645v2TvTmplIpV6toV4IpV6FirewallZone
         DisplayString,
      er1645v2TvTmplIpV6toV4IpV6DhcpClientAddrAC
         INTEGER,
      er1645v2TvTmplIpV6toV4IpV6DhcpClientPrDelMode
         INTEGER,
      er1645v2TvTmplIpV6toV4IpV6DhcpClientPrDelPool
         DisplayString,
      er1645v2TvTmplIpV6toV4IpV6DhcpClientPrDelPdExclOpt
         INTEGER,
      er1645v2TvTmplIpV6toV4IpV6DhcpClientDnsServerPref
         Integer32,
      er1645v2TvTmplIpV6toV4IpV6DhcpClientRapidCommit
         INTEGER,
      er1645v2TvTmplIpV6toV4IpV6DhcpClientTimersSolTimeOut
         TimeTicks,
      er1645v2TvTmplIpV6toV4IpV6DhcpClientTimersSolMaxRt
         TimeTicks,
      er1645v2TvTmplIpV6toV4IpV6DhcpClientTimersInfoRefresh
         TimeTicks,
      er1645v2TvTmplIpV6toV4IpV6DhcpServerMode
         INTEGER,
      er1645v2TvTmplIpV6toV4IpV6DhcpServerPreference
         Integer32,
      er1645v2TvTmplIpV6toV4IpV6DhcpServerPool
         DisplayString,
      er1645v2TvTmplIpV6toV4IpV6DhcpServerRapidCommit
         INTEGER,
      er1645v2TvTmplIpV6toV4IpV6DhcpServerTimersInfoRefresh
         TimeTicks,
      er1645v2TvTmplIpV6toV4IpV6DhcpRelayMode
         INTEGER,
      er1645v2TvTmplIpV6toV4IpV6SendRedirect
         INTEGER,
      er1645v2TvTmplIpV6toV4IpV6LinkMtu
         Integer32,
      er1645v2TvTmplIpV6toV4IpV6InterfaceId
         OCTET STRING,
      er1645v2TvTmplIpV6toV4IpV6MF
         Integer32,
      er1645v2TvTmplIpV6toV4IpV6IcmpMessagesNoRoute
         INTEGER,
      er1645v2TvTmplIpV6toV4IpV6IcmpMessagesBeyondScope
         INTEGER,
      er1645v2TvTmplIpV6toV4IpV6IcmpMessagesAddressUnreachable
         INTEGER,
      er1645v2TvTmplIpV6toV4IpV6IcmpMessagesPortUnreachable
         INTEGER,
      er1645v2TvTmplIpV6toV4IpV6IcmpMessagesPacketTooBig
         INTEGER,
      er1645v2TvTmplIpV6toV4IpV6IcmpMessagesHopLimitExceeded
         INTEGER,
      er1645v2TvTmplIpV6toV4IpV6IcmpMessagesFragTimeExceeded
         INTEGER,
      er1645v2TvTmplIpV6toV4IpV6IcmpMessagesHeaderFieldErr
         INTEGER,
      er1645v2TvTmplIpV6toV4IpV6IcmpMessagesOptionUnrecognized
         INTEGER,
      er1645v2TvTmplIpV6toV4IpV6IcmpMessagesRedirect
         INTEGER,
      er1645v2TvTmplIpV6toV4Encaps6to4V6ToV4VrfRouter
         DisplayString,
      er1645v2TvTmplIpV6toV4Encaps6to4V6ToV4LocalAddress
         IpAddress,
      er1645v2TvTmplIpV6toV4Encaps6to4V6ToV4LocalInterface
         DisplayString,
      er1645v2TvTmplIpV6toV4Encaps6to4V6ToV4RelayAddress
         IpAddress,
      er1645v2TvTmplIpV6toV4Encaps6to4V6ToV4Tos
         Integer32,
      er1645v2TvTmplIpV6toV4Encaps6to4V6ToV4Ttl
         Integer32,
      er1645v2TvTmplIpV6toV4Encaps6to4V6RdVrfRouter
         DisplayString,
      er1645v2TvTmplIpV6toV4Encaps6to4V6RdLocalAddress
         IpAddress,
      er1645v2TvTmplIpV6toV4Encaps6to4V6RdLocalInterface
         DisplayString,
      er1645v2TvTmplIpV6toV4Encaps6to4V6RdBorderRelayAddress
         IpAddress,
      er1645v2TvTmplIpV6toV4Encaps6to4V6RdV6Prefix
         Ipv6Address,
      er1645v2TvTmplIpV6toV4Encaps6to4V6RdV6PrefixLen
         Integer32,
      er1645v2TvTmplIpV6toV4Encaps6to4V6RdV4CommonPrefixLen
         Integer32,
      er1645v2TvTmplIpV6toV4Encaps6to4V6RdV4CommonSuffixLen
         Integer32,
      er1645v2TvTmplIpV6toV4Encaps6to4V6RdTos
         Integer32,
      er1645v2TvTmplIpV6toV4Encaps6to4V6RdTtl
         Integer32,
      er1645v2TvTmplIpV6toV4Encaps6to4V6InV4VrfRouter
         DisplayString,
      er1645v2TvTmplIpV6toV4Encaps6to4V6InV4LocalAddress
         IpAddress,
      er1645v2TvTmplIpV6toV4Encaps6to4V6InV4LocalInterface
         DisplayString,
      er1645v2TvTmplIpV6toV4Encaps6to4V6InV4RemoteAddress
         IpAddress,
      er1645v2TvTmplIpV6toV4Encaps6to4V6InV4Tos
         INTEGER,
      er1645v2TvTmplIpV6toV4Encaps6to4V6InV4Ttl
         INTEGER,
      er1645v2TvTmplIpV6toV4Encaps6to4IsatapVrfRouter
         DisplayString,
      er1645v2TvTmplIpV6toV4Encaps6to4IsatapLocalAddress
         IpAddress,
      er1645v2TvTmplIpV6toV4Encaps6to4IsatapLocalInterface
         DisplayString,
      er1645v2TvTmplIpV6toV4Encaps6to4IsatapTos
         INTEGER,
      er1645v2TvTmplIpV6toV4Encaps6to4IsatapTtl
         INTEGER,
      er1645v2TvTmplIpV6toV4InbBwCir
         Integer32,
      er1645v2TvTmplIpV6toV4InbBwTc
         INTEGER,
      er1645v2TvTmplIpV6toV4InbBwCorrType
         INTEGER,
      er1645v2TvTmplIpV6toV4InbBwCorrPredefEncapsFrameRelay
         DisplayString,
      er1645v2TvTmplIpV6toV4InbBwCorrPredefEncapsPpp
         DisplayString,
      er1645v2TvTmplIpV6toV4InbBwCorrPredefEncapsAtmHl
         INTEGER,
      er1645v2TvTmplIpV6toV4InbBwCorrPredefEncapsAtmMp
         INTEGER,
      er1645v2TvTmplIpV6toV4InbBwCorrPredefEncapsHdlc
         DisplayString,
      er1645v2TvTmplIpV6toV4InbBwCorrPredefEncapsEfmFs
         Integer32,
      er1645v2TvTmplIpV6toV4InbBwCorrPredefEncapsEfmIb
         Integer32,
      er1645v2TvTmplIpV6toV4InbBwCorrPredefMode
         INTEGER,
      er1645v2TvTmplIpV6toV4InbBwCorrManualOverhead
         Integer32,
      er1645v2TvTmplIpV6toV4InbBwCorrManualFrameData
         Counter32,
      er1645v2TvTmplIpV6toV4InbBwCorrManualFrameHeader
         Counter32,
      er1645v2TvTmplIpV6toV4InbBwMaxFifoQLen
         Integer32,
      er1645v2TvTmplIpV6toV4InbBwPriorityPolicy
         DisplayString
      }

er1645v2TvTmplIpV6toV4Actions OBJECT-TYPE
   SYNTAX      VariableLengthTableActions
   MAX-ACCESS  read-write
   STATUS      current
   DESCRIPTION
      "By way of this field, some manipulations
       on this table may be performed."
   ::= {er1645v2TvTmplIpV6toV4Entry 2}

er1645v2TvTmplIpV6toV4TableIx OBJECT-TYPE
   SYNTAX      TableIndex
   MAX-ACCESS  not-accessible
   STATUS      current
   DESCRIPTION
      ""
   ::= {er1645v2TvTmplIpV6toV4Entry 11}

er1645v2TvTmplIpV6toV4Name OBJECT-TYPE
   SYNTAX      DisplayString
   MAX-ACCESS  read-write
   STATUS      current
   DESCRIPTION
      "Path: tunnels.editConf.ipV6toV4.name"
   ::= {er1645v2TvTmplIpV6toV4Entry 16777216}

er1645v2TvTmplIpV6toV4Remark OBJECT-TYPE
   SYNTAX      DisplayString
   MAX-ACCESS  read-write
   STATUS      current
   DESCRIPTION
      "Path: tunnels.editConf.ipV6toV4.remark"
   ::= {er1645v2TvTmplIpV6toV4Entry 1157627904}

er1645v2TvTmplIpV6toV4AdminStatus OBJECT-TYPE
   SYNTAX      INTEGER
               {
               up (1),
               down (2)
               }
   MAX-ACCESS  read-write
   STATUS      current
   DESCRIPTION
      "Path: tunnels.editConf.ipV6toV4.adminStatus

       Possibilities:
               up   (1)
               down   (2)"
   ::= {er1645v2TvTmplIpV6toV4Entry 33554432}

er1645v2TvTmplIpV6toV4PriorityPolicy OBJECT-TYPE
   SYNTAX      DisplayString
   MAX-ACCESS  read-write
   STATUS      current
   DESCRIPTION
      "Path: tunnels.editConf.ipV6toV4.priorityPolicy"
   ::= {er1645v2TvTmplIpV6toV4Entry 83886080}

er1645v2TvTmplIpV6toV4IpV6VrfRouter OBJECT-TYPE
   SYNTAX      DisplayString
   MAX-ACCESS  read-write
   STATUS      current
   DESCRIPTION
      "Path: tunnels.editConf.ipV6toV4.ipV6.vrfRouter"
   ::= {er1645v2TvTmplIpV6toV4Entry 134283264}

er1645v2TvTmplIpV6toV4IpV6AddrAutoConfigNrDupAddrDetects OBJECT-TYPE
   SYNTAX      Integer32
   MAX-ACCESS  read-write
   STATUS      current
   DESCRIPTION
      "Path: tunnels.editConf.ipV6toV4.ipV6.addrAutoConfig.nrDupAddrDetects"
   ::= {er1645v2TvTmplIpV6toV4Entry 134480128}

er1645v2TvTmplIpV6toV4IpV6AddrAutoConfigAcceptRa OBJECT-TYPE
   SYNTAX      INTEGER
               {
               disabled (0),
               enabled (1)
               }
   MAX-ACCESS  read-write
   STATUS      current
   DESCRIPTION
      "Path: tunnels.editConf.ipV6toV4.ipV6.addrAutoConfig.acceptRa

       Possibilities:
               disabled   (0)
               enabled   (1)"
   ::= {er1645v2TvTmplIpV6toV4Entry 134480384}

er1645v2TvTmplIpV6toV4IpV6AddrAutoConfigAcceptRaRdnss OBJECT-TYPE
   SYNTAX      INTEGER
               {
               disabled (0),
               enabled (1)
               }
   MAX-ACCESS  read-write
   STATUS      current
   DESCRIPTION
      "Path: tunnels.editConf.ipV6toV4.ipV6.addrAutoConfig.acceptRaRdnss

       Possibilities:
               disabled   (0)
               enabled   (1)"
   ::= {er1645v2TvTmplIpV6toV4Entry 134480640}

er1645v2TvTmplIpV6toV4IpV6AddrAutoConfigAcceptRaDnssl OBJECT-TYPE
   SYNTAX      INTEGER
               {
               disabled (0),
               enabled (1)
               }
   MAX-ACCESS  read-write
   STATUS      current
   DESCRIPTION
      "Path: tunnels.editConf.ipV6toV4.ipV6.addrAutoConfig.acceptRaDnssl

       Possibilities:
               disabled   (0)
               enabled   (1)"
   ::= {er1645v2TvTmplIpV6toV4Entry 134480896}

er1645v2TvTmplIpV6toV4IpV6DefaultRoute OBJECT-TYPE
   SYNTAX      INTEGER
               {
               disabled (0),
               enabled (1)
               }
   MAX-ACCESS  read-write
   STATUS      current
   DESCRIPTION
      "Path: tunnels.editConf.ipV6toV4.ipV6.defaultRoute

       Possibilities:
               disabled   (0)
               enabled   (1)"
   ::= {er1645v2TvTmplIpV6toV4Entry 134545408}

er1645v2TvTmplIpV6toV4IpV6RaSend OBJECT-TYPE
   SYNTAX      INTEGER
               {
               disabled (0),
               enabled (1)
               }
   MAX-ACCESS  read-write
   STATUS      current
   DESCRIPTION
      "Path: tunnels.editConf.ipV6toV4.ipV6.ra.send

       Possibilities:
               disabled   (0)
               enabled   (1)"
   ::= {er1645v2TvTmplIpV6toV4Entry 134611200}

er1645v2TvTmplIpV6toV4IpV6RaMinInterval OBJECT-TYPE
   SYNTAX      TimeTicks
   MAX-ACCESS  read-write
   STATUS      current
   DESCRIPTION
      "Path: tunnels.editConf.ipV6toV4.ipV6.ra.minInterval

       Time in centi-second."
   ::= {er1645v2TvTmplIpV6toV4Entry 134611456}

er1645v2TvTmplIpV6toV4IpV6RaMaxInterval OBJECT-TYPE
   SYNTAX      TimeTicks
   MAX-ACCESS  read-write
   STATUS      current
   DESCRIPTION
      "Path: tunnels.editConf.ipV6toV4.ipV6.ra.maxInterval

       Time in centi-second."
   ::= {er1645v2TvTmplIpV6toV4Entry 134611712}

er1645v2TvTmplIpV6toV4IpV6RaManagedFlag OBJECT-TYPE
   SYNTAX      INTEGER
               {
               disabled (0),
               enabled (1)
               }
   MAX-ACCESS  read-write
   STATUS      current
   DESCRIPTION
      "Path: tunnels.editConf.ipV6toV4.ipV6.ra.managedFlag

       Possibilities:
               disabled   (0)
               enabled   (1)"
   ::= {er1645v2TvTmplIpV6toV4Entry 134611968}

er1645v2TvTmplIpV6toV4IpV6RaOtherConfFlag OBJECT-TYPE
   SYNTAX      INTEGER
               {
               disabled (0),
               enabled (1)
               }
   MAX-ACCESS  read-write
   STATUS      current
   DESCRIPTION
      "Path: tunnels.editConf.ipV6toV4.ipV6.ra.otherConfFlag

       Possibilities:
               disabled   (0)
               enabled   (1)"
   ::= {er1645v2TvTmplIpV6toV4Entry 134612224}

er1645v2TvTmplIpV6toV4IpV6RaLinkMtu OBJECT-TYPE
   SYNTAX      Integer32
   MAX-ACCESS  read-write
   STATUS      current
   DESCRIPTION
      "Path: tunnels.editConf.ipV6toV4.ipV6.ra.linkMtu"
   ::= {er1645v2TvTmplIpV6toV4Entry 134612480}

er1645v2TvTmplIpV6toV4IpV6RaReachableTime OBJECT-TYPE
   SYNTAX      TimeTicks
   MAX-ACCESS  read-write
   STATUS      current
   DESCRIPTION
      "Path: tunnels.editConf.ipV6toV4.ipV6.ra.reachableTime

       Time in centi-second."
   ::= {er1645v2TvTmplIpV6toV4Entry 134612736}

er1645v2TvTmplIpV6toV4IpV6RaRetransmitTime OBJECT-TYPE
   SYNTAX      TimeTicks
   MAX-ACCESS  read-write
   STATUS      current
   DESCRIPTION
      "Path: tunnels.editConf.ipV6toV4.ipV6.ra.retransmitTime

       Time in centi-second."
   ::= {er1645v2TvTmplIpV6toV4Entry 134612992}

er1645v2TvTmplIpV6toV4IpV6RaHopLimit OBJECT-TYPE
   SYNTAX      Integer32
   MAX-ACCESS  read-write
   STATUS      current
   DESCRIPTION
      "Path: tunnels.editConf.ipV6toV4.ipV6.ra.hopLimit"
   ::= {er1645v2TvTmplIpV6toV4Entry 134613248}

er1645v2TvTmplIpV6toV4IpV6RaDefaultLifeTime OBJECT-TYPE
   SYNTAX      TimeTicks
   MAX-ACCESS  read-write
   STATUS      current
   DESCRIPTION
      "Path: tunnels.editConf.ipV6toV4.ipV6.ra.defaultLifeTime

       Time in centi-second."
   ::= {er1645v2TvTmplIpV6toV4Entry 134613504}

er1645v2TvTmplIpV6toV4IpV6RaDnsOptionsRdnssLifeTime OBJECT-TYPE
   SYNTAX      TimeTicks
   MAX-ACCESS  read-write
   STATUS      current
   DESCRIPTION
      "Path: tunnels.editConf.ipV6toV4.ipV6.ra.dnsOptions.rdnss.lifeTime

       Time in centi-second."
   ::= {er1645v2TvTmplIpV6toV4Entry 134613796}

er1645v2TvTmplIpV6toV4IpV6RaDnsOptionsRdnssImportServers OBJECT-TYPE
   SYNTAX      INTEGER
               {
               disabled (0),
               enabled (1)
               }
   MAX-ACCESS  read-write
   STATUS      current
   DESCRIPTION
      "Path: tunnels.editConf.ipV6toV4.ipV6.ra.dnsOptions.rdnss.importServers

       Possibilities:
               disabled   (0)
               enabled   (1)"
   ::= {er1645v2TvTmplIpV6toV4Entry 134613804}

er1645v2TvTmplIpV6toV4IpV6RaDnsOptionsDnsslLifeTime OBJECT-TYPE
   SYNTAX      TimeTicks
   MAX-ACCESS  read-write
   STATUS      current
   DESCRIPTION
      "Path: tunnels.editConf.ipV6toV4.ipV6.ra.dnsOptions.dnssl.lifeTime

       Time in centi-second."
   ::= {er1645v2TvTmplIpV6toV4Entry 134613828}

er1645v2TvTmplIpV6toV4IpV6RaDnsOptionsDnsslImportDomains OBJECT-TYPE
   SYNTAX      INTEGER
               {
               disabled (0),
               enabled (1)
               }
   MAX-ACCESS  read-write
   STATUS      current
   DESCRIPTION
      "Path: tunnels.editConf.ipV6toV4.ipV6.ra.dnsOptions.dnssl.importDomains

       Possibilities:
               disabled   (0)
               enabled   (1)"
   ::= {er1645v2TvTmplIpV6toV4Entry 134613836}

er1645v2TvTmplIpV6toV4IpV6RsSend OBJECT-TYPE
   SYNTAX      INTEGER
               {
               disabled (0),
               enabled (1)
               }
   MAX-ACCESS  read-write
   STATUS      current
   DESCRIPTION
      "Path: tunnels.editConf.ipV6toV4.ipV6.rs.send

       Possibilities:
               disabled   (0)
               enabled   (1)"
   ::= {er1645v2TvTmplIpV6toV4Entry 135528704}

er1645v2TvTmplIpV6toV4IpV6RsMaxRandomDelay OBJECT-TYPE
   SYNTAX      TimeTicks
   MAX-ACCESS  read-write
   STATUS      current
   DESCRIPTION
      "Path: tunnels.editConf.ipV6toV4.ipV6.rs.maxRandomDelay

       Time in centi-second."
   ::= {er1645v2TvTmplIpV6toV4Entry 135528960}

er1645v2TvTmplIpV6toV4IpV6RsInterval OBJECT-TYPE
   SYNTAX      TimeTicks
   MAX-ACCESS  read-write
   STATUS      current
   DESCRIPTION
      "Path: tunnels.editConf.ipV6toV4.ipV6.rs.interval

       Time in centi-second."
   ::= {er1645v2TvTmplIpV6toV4Entry 135529216}

er1645v2TvTmplIpV6toV4IpV6RsMaxSolicitations OBJECT-TYPE
   SYNTAX      Integer32
   MAX-ACCESS  read-write
   STATUS      current
   DESCRIPTION
      "Path: tunnels.editConf.ipV6toV4.ipV6.rs.maxSolicitations"
   ::= {er1645v2TvTmplIpV6toV4Entry 135529472}

er1645v2TvTmplIpV6toV4IpV6TrafficPolicyInbound OBJECT-TYPE
   SYNTAX      DisplayString
   MAX-ACCESS  read-write
   STATUS      current
   DESCRIPTION
      "Path: tunnels.editConf.ipV6toV4.ipV6.trafficPolicy.inbound"
   ::= {er1645v2TvTmplIpV6toV4Entry 134938880}

er1645v2TvTmplIpV6toV4IpV6TrafficPolicyOutbound OBJECT-TYPE
   SYNTAX      DisplayString
   MAX-ACCESS  read-write
   STATUS      current
   DESCRIPTION
      "Path: tunnels.editConf.ipV6toV4.ipV6.trafficPolicy.outbound"
   ::= {er1645v2TvTmplIpV6toV4Entry 134939136}

er1645v2TvTmplIpV6toV4IpV6FirewallZone OBJECT-TYPE
   SYNTAX      DisplayString
   MAX-ACCESS  read-write
   STATUS      current
   DESCRIPTION
      "Path: tunnels.editConf.ipV6toV4.ipV6.firewall.zone"
   ::= {er1645v2TvTmplIpV6toV4Entry 135004416}

er1645v2TvTmplIpV6toV4IpV6DhcpClientAddrAC OBJECT-TYPE
   SYNTAX      INTEGER
               {
               disabled (0),
               enabled (1)
               }
   MAX-ACCESS  read-write
   STATUS      current
   DESCRIPTION
      "Path: tunnels.editConf.ipV6toV4.ipV6.dhcp.client.addrAutoConfig

       Possibilities:
               disabled   (0)
               enabled   (1)"
   ::= {er1645v2TvTmplIpV6toV4Entry 134882304}

er1645v2TvTmplIpV6toV4IpV6DhcpClientPrDelMode OBJECT-TYPE
   SYNTAX      INTEGER
               {
               disabled (0),
               enabled (1)
               }
   MAX-ACCESS  read-write
   STATUS      current
   DESCRIPTION
      "Path: tunnels.editConf.ipV6toV4.ipV6.dhcp.client.pd.mode

       Possibilities:
               disabled   (0)
               enabled   (1)"
   ::= {er1645v2TvTmplIpV6toV4Entry 134883332}

er1645v2TvTmplIpV6toV4IpV6DhcpClientPrDelPool OBJECT-TYPE
   SYNTAX      DisplayString
   MAX-ACCESS  read-write
   STATUS      current
   DESCRIPTION
      "Path: tunnels.editConf.ipV6toV4.ipV6.dhcp.client.pd.pool"
   ::= {er1645v2TvTmplIpV6toV4Entry 134883336}

er1645v2TvTmplIpV6toV4IpV6DhcpClientPrDelPdExclOpt OBJECT-TYPE
   SYNTAX      INTEGER
               {
               disabled (0),
               enabled (1)
               }
   MAX-ACCESS  read-write
   STATUS      current
   DESCRIPTION
      "Path: tunnels.editConf.ipV6toV4.ipV6.dhcp.client.pd.pdExclOpt

       Possibilities:
               disabled   (0)
               enabled   (1)"
   ::= {er1645v2TvTmplIpV6toV4Entry 134883340}

er1645v2TvTmplIpV6toV4IpV6DhcpClientDnsServerPref OBJECT-TYPE
   SYNTAX      Integer32
   MAX-ACCESS  read-write
   STATUS      current
   DESCRIPTION
      "Path: tunnels.editConf.ipV6toV4.ipV6.dhcp.client.dns.serverPref"
   ::= {er1645v2TvTmplIpV6toV4Entry 134885380}

er1645v2TvTmplIpV6toV4IpV6DhcpClientRapidCommit OBJECT-TYPE
   SYNTAX      INTEGER
               {
               disabled (0),
               enabled (1)
               }
   MAX-ACCESS  read-write
   STATUS      current
   DESCRIPTION
      "Path: tunnels.editConf.ipV6toV4.ipV6.dhcp.client.rapidCommit

       Possibilities:
               disabled   (0)
               enabled   (1)"
   ::= {er1645v2TvTmplIpV6toV4Entry 134884352}

er1645v2TvTmplIpV6toV4IpV6DhcpClientTimersSolTimeOut OBJECT-TYPE
   SYNTAX      TimeTicks
   MAX-ACCESS  read-write
   STATUS      current
   DESCRIPTION
      "Path: tunnels.editConf.ipV6toV4.ipV6.dhcp.client.timers.solTimeOut

       Time in centi-second."
   ::= {er1645v2TvTmplIpV6toV4Entry 134886404}

er1645v2TvTmplIpV6toV4IpV6DhcpClientTimersSolMaxRt OBJECT-TYPE
   SYNTAX      TimeTicks
   MAX-ACCESS  read-write
   STATUS      current
   DESCRIPTION
      "Path: tunnels.editConf.ipV6toV4.ipV6.dhcp.client.timers.solMaxRt

       Time in centi-second."
   ::= {er1645v2TvTmplIpV6toV4Entry 134886408}

er1645v2TvTmplIpV6toV4IpV6DhcpClientTimersInfoRefresh OBJECT-TYPE
   SYNTAX      TimeTicks
   MAX-ACCESS  read-write
   STATUS      current
   DESCRIPTION
      "Path: tunnels.editConf.ipV6toV4.ipV6.dhcp.client.timers.infoRefresh

       Time in centi-second."
   ::= {er1645v2TvTmplIpV6toV4Entry 134886412}

er1645v2TvTmplIpV6toV4IpV6DhcpServerMode OBJECT-TYPE
   SYNTAX      INTEGER
               {
               disabled (0),
               enabled (1)
               }
   MAX-ACCESS  read-write
   STATUS      current
   DESCRIPTION
      "Path: tunnels.editConf.ipV6toV4.ipV6.dhcp.server.mode

       Possibilities:
               disabled   (0)
               enabled   (1)"
   ::= {er1645v2TvTmplIpV6toV4Entry 134890496}

er1645v2TvTmplIpV6toV4IpV6DhcpServerPreference OBJECT-TYPE
   SYNTAX      Integer32
   MAX-ACCESS  read-write
   STATUS      current
   DESCRIPTION
      "Path: tunnels.editConf.ipV6toV4.ipV6.dhcp.server.preference"
   ::= {er1645v2TvTmplIpV6toV4Entry 134891520}

er1645v2TvTmplIpV6toV4IpV6DhcpServerPool OBJECT-TYPE
   SYNTAX      DisplayString
   MAX-ACCESS  read-write
   STATUS      current
   DESCRIPTION
      "Path: tunnels.editConf.ipV6toV4.ipV6.dhcp.server.pool"
   ::= {er1645v2TvTmplIpV6toV4Entry 134892544}

er1645v2TvTmplIpV6toV4IpV6DhcpServerRapidCommit OBJECT-TYPE
   SYNTAX      INTEGER
               {
               disabled (0),
               enabled (1)
               }
   MAX-ACCESS  read-write
   STATUS      current
   DESCRIPTION
      "Path: tunnels.editConf.ipV6toV4.ipV6.dhcp.server.rapidCommit

       Possibilities:
               disabled   (0)
               enabled   (1)"
   ::= {er1645v2TvTmplIpV6toV4Entry 134893568}

er1645v2TvTmplIpV6toV4IpV6DhcpServerTimersInfoRefresh OBJECT-TYPE
   SYNTAX      TimeTicks
   MAX-ACCESS  read-write
   STATUS      current
   DESCRIPTION
      "Path: tunnels.editConf.ipV6toV4.ipV6.dhcp.server.timers.infoRefresh

       Time in centi-second."
   ::= {er1645v2TvTmplIpV6toV4Entry 134894596}

er1645v2TvTmplIpV6toV4IpV6DhcpRelayMode OBJECT-TYPE
   SYNTAX      INTEGER
               {
               disabled (0),
               enabled (1)
               }
   MAX-ACCESS  read-write
   STATUS      current
   DESCRIPTION
      "Path: tunnels.editConf.ipV6toV4.ipV6.dhcp.relay.mode

       Possibilities:
               disabled   (0)
               enabled   (1)"
   ::= {er1645v2TvTmplIpV6toV4Entry 134897696}

er1645v2TvTmplIpV6toV4IpV6SendRedirect OBJECT-TYPE
   SYNTAX      INTEGER
               {
               disabled (0),
               enabled (1)
               }
   MAX-ACCESS  read-write
   STATUS      current
   DESCRIPTION
      "Path: tunnels.editConf.ipV6toV4.ipV6.sendRedirect

       Possibilities:
               disabled   (0)
               enabled   (1)"
   ::= {er1645v2TvTmplIpV6toV4Entry 134676480}

er1645v2TvTmplIpV6toV4IpV6LinkMtu OBJECT-TYPE
   SYNTAX      Integer32
   MAX-ACCESS  read-write
   STATUS      current
   DESCRIPTION
      "Path: tunnels.editConf.ipV6toV4.ipV6.linkMtu"
   ::= {er1645v2TvTmplIpV6toV4Entry 134742016}

er1645v2TvTmplIpV6toV4IpV6InterfaceId OBJECT-TYPE
   SYNTAX      OCTET STRING
   MAX-ACCESS  read-write
   STATUS      current
   DESCRIPTION
      "Path: tunnels.editConf.ipV6toV4.ipV6.interfaceId"
   ::= {er1645v2TvTmplIpV6toV4Entry 134807552}

er1645v2TvTmplIpV6toV4IpV6MF OBJECT-TYPE
   SYNTAX      Integer32
   MAX-ACCESS  read-write
   STATUS      current
   DESCRIPTION
      "Path: tunnels.editConf.ipV6toV4.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2TvTmplIpV6toV4Entry 135331840}

er1645v2TvTmplIpV6toV4IpV6IcmpMessagesNoRoute OBJECT-TYPE
   SYNTAX      INTEGER
               {
               disabled (0),
               enabled (1)
               }
   MAX-ACCESS  read-write
   STATUS      current
   DESCRIPTION
      "Path: tunnels.editConf.ipV6toV4.ipV6.icmpMessages.noRoute

       Possibilities:
               disabled   (0)
               enabled   (1)"
   ::= {er1645v2TvTmplIpV6toV4Entry 135397632}

er1645v2TvTmplIpV6toV4IpV6IcmpMessagesBeyondScope OBJECT-TYPE
   SYNTAX      INTEGER
               {
               disabled (0),
               enabled (1)
               }
   MAX-ACCESS  read-write
   STATUS      current
   DESCRIPTION
      "Path: tunnels.editConf.ipV6toV4.ipV6.icmpMessages.beyondScope

       Possibilities:
               disabled   (0)
               enabled   (1)"
   ::= {er1645v2TvTmplIpV6toV4Entry 135398144}

er1645v2TvTmplIpV6toV4IpV6IcmpMessagesAddressUnreachable OBJECT-TYPE
   SYNTAX      INTEGER
               {
               disabled (0),
               enabled (1)
               }
   MAX-ACCESS  read-write
   STATUS      current
   DESCRIPTION
      "Path: tunnels.editConf.ipV6toV4.ipV6.icmpMessages.addressUnreachable

       Possibilities:
               disabled   (0)
               enabled   (1)"
   ::= {er1645v2TvTmplIpV6toV4Entry 135398400}

er1645v2TvTmplIpV6toV4IpV6IcmpMessagesPortUnreachable OBJECT-TYPE
   SYNTAX      INTEGER
               {
               disabled (0),
               enabled (1)
               }
   MAX-ACCESS  read-write
   STATUS      current
   DESCRIPTION
      "Path: tunnels.editConf.ipV6toV4.ipV6.icmpMessages.portUnreachable

       Possibilities:
               disabled   (0)
               enabled   (1)"
   ::= {er1645v2TvTmplIpV6toV4Entry 135398656}

er1645v2TvTmplIpV6toV4IpV6IcmpMessagesPacketTooBig OBJECT-TYPE
   SYNTAX      INTEGER
               {
               disabled (0),
               enabled (1)
               }
   MAX-ACCESS  read-write
   STATUS      current
   DESCRIPTION
      "Path: tunnels.editConf.ipV6toV4.ipV6.icmpMessages.packetTooBig

       Possibilities:
               disabled   (0)
               enabled   (1)"
   ::= {er1645v2TvTmplIpV6toV4Entry 135399936}

er1645v2TvTmplIpV6toV4IpV6IcmpMessagesHopLimitExceeded OBJECT-TYPE
   SYNTAX      INTEGER
               {
               disabled (0),
               enabled (1)
               }
   MAX-ACCESS  read-write
   STATUS      current
   DESCRIPTION
      "Path: tunnels.editConf.ipV6toV4.ipV6.icmpMessages.hopLimitExceeded

       Possibilities:
               disabled   (0)
               enabled   (1)"
   ::= {er1645v2TvTmplIpV6toV4Entry 135402496}

er1645v2TvTmplIpV6toV4IpV6IcmpMessagesFragTimeExceeded OBJECT-TYPE
   SYNTAX      INTEGER
               {
               disabled (0),
               enabled (1)
               }
   MAX-ACCESS  read-write
   STATUS      current
   DESCRIPTION
      "Path: tunnels.editConf.ipV6toV4.ipV6.icmpMessages.fragTimeExceeded

       Possibilities:
               disabled   (0)
               enabled   (1)"
   ::= {er1645v2TvTmplIpV6toV4Entry 135402752}

er1645v2TvTmplIpV6toV4IpV6IcmpMessagesHeaderFieldErr OBJECT-TYPE
   SYNTAX      INTEGER
               {
               disabled (0),
               enabled (1)
               }
   MAX-ACCESS  read-write
   STATUS      current
   DESCRIPTION
      "Path: tunnels.editConf.ipV6toV4.ipV6.icmpMessages.headerFieldErr

       Possibilities:
               disabled   (0)
               enabled   (1)"
   ::= {er1645v2TvTmplIpV6toV4Entry 135405056}

er1645v2TvTmplIpV6toV4IpV6IcmpMessagesOptionUnrecognized OBJECT-TYPE
   SYNTAX      INTEGER
               {
               disabled (0),
               enabled (1)
               }
   MAX-ACCESS  read-write
   STATUS      current
   DESCRIPTION
      "Path: tunnels.editConf.ipV6toV4.ipV6.icmpMessages.optionUnrecognized

       Possibilities:
               disabled   (0)
               enabled   (1)"
   ::= {er1645v2TvTmplIpV6toV4Entry 135405568}

er1645v2TvTmplIpV6toV4IpV6IcmpMessagesRedirect OBJECT-TYPE
   SYNTAX      INTEGER
               {
               disabled (0),
               enabled (1)
               }
   MAX-ACCESS  read-write
   STATUS      current
   DESCRIPTION
      "Path: tunnels.editConf.ipV6toV4.ipV6.icmpMessages.redirect

       Possibilities:
               disabled   (0)
               enabled   (1)"
   ::= {er1645v2TvTmplIpV6toV4Entry 135407616}

er1645v2TvTmplIpV6toV4Encaps6to4V6ToV4VrfRouter OBJECT-TYPE
   SYNTAX      DisplayString
   MAX-ACCESS  read-write
   STATUS      current
   DESCRIPTION
      "Path: tunnels.editConf.ipV6toV4.encaps6to4.v6ToV4.vrfRouter"
   ::= {er1645v2TvTmplIpV6toV4Entry 152371456}

er1645v2TvTmplIpV6toV4Encaps6to4V6ToV4LocalAddress OBJECT-TYPE
   SYNTAX      IpAddress
   MAX-ACCESS  read-write
   STATUS      current
   DESCRIPTION
      "Path: tunnels.editConf.ipV6toV4.encaps6to4.v6ToV4.localAddress"
   ::= {er1645v2TvTmplIpV6toV4Entry 152371712}

er1645v2TvTmplIpV6toV4Encaps6to4V6ToV4LocalInterface OBJECT-TYPE
   SYNTAX      DisplayString
   MAX-ACCESS  read-write
   STATUS      current
   DESCRIPTION
      "Path: tunnels.editConf.ipV6toV4.encaps6to4.v6ToV4.localInterface"
   ::= {er1645v2TvTmplIpV6toV4Entry 152371968}

er1645v2TvTmplIpV6toV4Encaps6to4V6ToV4RelayAddress OBJECT-TYPE
   SYNTAX      IpAddress
   MAX-ACCESS  read-write
   STATUS      current
   DESCRIPTION
      "Path: tunnels.editConf.ipV6toV4.encaps6to4.v6ToV4.relayAddress"
   ::= {er1645v2TvTmplIpV6toV4Entry 152372224}

er1645v2TvTmplIpV6toV4Encaps6to4V6ToV4Tos OBJECT-TYPE
   SYNTAX      Integer32
   MAX-ACCESS  read-write
   STATUS      current
   DESCRIPTION
      "Path: tunnels.editConf.ipV6toV4.encaps6to4.v6ToV4.tos"
   ::= {er1645v2TvTmplIpV6toV4Entry 152372480}

er1645v2TvTmplIpV6toV4Encaps6to4V6ToV4Ttl OBJECT-TYPE
   SYNTAX      Integer32
   MAX-ACCESS  read-write
   STATUS      current
   DESCRIPTION
      "Path: tunnels.editConf.ipV6toV4.encaps6to4.v6ToV4.ttl"
   ::= {er1645v2TvTmplIpV6toV4Entry 152372736}

er1645v2TvTmplIpV6toV4Encaps6to4V6RdVrfRouter OBJECT-TYPE
   SYNTAX      DisplayString
   MAX-ACCESS  read-write
   STATUS      current
   DESCRIPTION
      "Path: tunnels.editConf.ipV6toV4.encaps6to4.v6Rd.vrfRouter"
   ::= {er1645v2TvTmplIpV6toV4Entry 152436992}

er1645v2TvTmplIpV6toV4Encaps6to4V6RdLocalAddress OBJECT-TYPE
   SYNTAX      IpAddress
   MAX-ACCESS  read-write
   STATUS      current
   DESCRIPTION
      "Path: tunnels.editConf.ipV6toV4.encaps6to4.v6Rd.localAddress"
   ::= {er1645v2TvTmplIpV6toV4Entry 152437248}

er1645v2TvTmplIpV6toV4Encaps6to4V6RdLocalInterface OBJECT-TYPE
   SYNTAX      DisplayString
   MAX-ACCESS  read-write
   STATUS      current
   DESCRIPTION
      "Path: tunnels.editConf.ipV6toV4.encaps6to4.v6Rd.localInterface"
   ::= {er1645v2TvTmplIpV6toV4Entry 152437504}

er1645v2TvTmplIpV6toV4Encaps6to4V6RdBorderRelayAddress OBJECT-TYPE
   SYNTAX      IpAddress
   MAX-ACCESS  read-write
   STATUS      current
   DESCRIPTION
      "Path: tunnels.editConf.ipV6toV4.encaps6to4.v6Rd.borderRelayAddress"
   ::= {er1645v2TvTmplIpV6toV4Entry 152437760}

er1645v2TvTmplIpV6toV4Encaps6to4V6RdV6Prefix OBJECT-TYPE
   SYNTAX      Ipv6Address
   MAX-ACCESS  read-write
   STATUS      current
   DESCRIPTION
      "Path: tunnels.editConf.ipV6toV4.encaps6to4.v6Rd.v6Prefix

       ipv6 address"
   ::= {er1645v2TvTmplIpV6toV4Entry 152438528}

er1645v2TvTmplIpV6toV4Encaps6to4V6RdV6PrefixLen OBJECT-TYPE
   SYNTAX      Integer32
   MAX-ACCESS  read-write
   STATUS      current
   DESCRIPTION
      "Path: tunnels.editConf.ipV6toV4.encaps6to4.v6Rd.v6PrefixLen"
   ::= {er1645v2TvTmplIpV6toV4Entry 152438784}

er1645v2TvTmplIpV6toV4Encaps6to4V6RdV4CommonPrefixLen OBJECT-TYPE
   SYNTAX      Integer32
   MAX-ACCESS  read-write
   STATUS      current
   DESCRIPTION
      "Path: tunnels.editConf.ipV6toV4.encaps6to4.v6Rd.v4CommonPrefixLen"
   ::= {er1645v2TvTmplIpV6toV4Entry 152439040}

er1645v2TvTmplIpV6toV4Encaps6to4V6RdV4CommonSuffixLen OBJECT-TYPE
   SYNTAX      Integer32
   MAX-ACCESS  read-write
   STATUS      current
   DESCRIPTION
      "Path: tunnels.editConf.ipV6toV4.encaps6to4.v6Rd.v4CommonSuffixLen"
   ::= {er1645v2TvTmplIpV6toV4Entry 152439296}

er1645v2TvTmplIpV6toV4Encaps6to4V6RdTos OBJECT-TYPE
   SYNTAX      Integer32
   MAX-ACCESS  read-write
   STATUS      current
   DESCRIPTION
      "Path: tunnels.editConf.ipV6toV4.encaps6to4.v6Rd.tos"
   ::= {er1645v2TvTmplIpV6toV4Entry 152438016}

er1645v2TvTmplIpV6toV4Encaps6to4V6RdTtl OBJECT-TYPE
   SYNTAX      Integer32
   MAX-ACCESS  read-write
   STATUS      current
   DESCRIPTION
      "Path: tunnels.editConf.ipV6toV4.encaps6to4.v6Rd.ttl"
   ::= {er1645v2TvTmplIpV6toV4Entry 152438272}

er1645v2TvTmplIpV6toV4Encaps6to4V6InV4VrfRouter OBJECT-TYPE
   SYNTAX      DisplayString
   MAX-ACCESS  read-write
   STATUS      current
   DESCRIPTION
      "Path: tunnels.editConf.ipV6toV4.encaps6to4.v6InV4.vrfRouter"
   ::= {er1645v2TvTmplIpV6toV4Entry 152502528}

er1645v2TvTmplIpV6toV4Encaps6to4V6InV4LocalAddress OBJECT-TYPE
   SYNTAX      IpAddress
   MAX-ACCESS  read-write
   STATUS      current
   DESCRIPTION
      "Path: tunnels.editConf.ipV6toV4.encaps6to4.v6InV4.localAddress"
   ::= {er1645v2TvTmplIpV6toV4Entry 152502784}

er1645v2TvTmplIpV6toV4Encaps6to4V6InV4LocalInterface OBJECT-TYPE
   SYNTAX      DisplayString
   MAX-ACCESS  read-write
   STATUS      current
   DESCRIPTION
      "Path: tunnels.editConf.ipV6toV4.encaps6to4.v6InV4.localInterface"
   ::= {er1645v2TvTmplIpV6toV4Entry 152503040}

er1645v2TvTmplIpV6toV4Encaps6to4V6InV4RemoteAddress OBJECT-TYPE
   SYNTAX      IpAddress
   MAX-ACCESS  read-write
   STATUS      current
   DESCRIPTION
      "Path: tunnels.editConf.ipV6toV4.encaps6to4.v6InV4.remoteAddress"
   ::= {er1645v2TvTmplIpV6toV4Entry 152503296}

er1645v2TvTmplIpV6toV4Encaps6to4V6InV4Tos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256)
               }
   MAX-ACCESS  read-write
   STATUS      current
   DESCRIPTION
      "Path: tunnels.editConf.ipV6toV4.encaps6to4.v6InV4.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)"
   ::= {er1645v2TvTmplIpV6toV4Entry 152503552}

er1645v2TvTmplIpV6toV4Encaps6to4V6InV4Ttl OBJECT-TYPE
   SYNTAX      INTEGER
               {
               copy (256)
               }
   MAX-ACCESS  read-write
   STATUS      current
   DESCRIPTION
      "Path: tunnels.editConf.ipV6toV4.encaps6to4.v6InV4.ttl

       Possibilities:
               copy   (256)"
   ::= {er1645v2TvTmplIpV6toV4Entry 152503808}

er1645v2TvTmplIpV6toV4Encaps6to4IsatapVrfRouter OBJECT-TYPE
   SYNTAX      DisplayString
   MAX-ACCESS  read-write
   STATUS      current
   DESCRIPTION
      "Path: tunnels.editConf.ipV6toV4.encaps6to4.isatap.vrfRouter"
   ::= {er1645v2TvTmplIpV6toV4Entry 152568064}

er1645v2TvTmplIpV6toV4Encaps6to4IsatapLocalAddress OBJECT-TYPE
   SYNTAX      IpAddress
   MAX-ACCESS  read-write
   STATUS      current
   DESCRIPTION
      "Path: tunnels.editConf.ipV6toV4.encaps6to4.isatap.localAddress"
   ::= {er1645v2TvTmplIpV6toV4Entry 152568320}

er1645v2TvTmplIpV6toV4Encaps6to4IsatapLocalInterface OBJECT-TYPE
   SYNTAX      DisplayString
   MAX-ACCESS  read-write
   STATUS      current
   DESCRIPTION
      "Path: tunnels.editConf.ipV6toV4.encaps6to4.isatap.localInterface"
   ::= {er1645v2TvTmplIpV6toV4Entry 152568576}

er1645v2TvTmplIpV6toV4Encaps6to4IsatapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               copy (256)
               }
   MAX-ACCESS  read-write
   STATUS      current
   DESCRIPTION
      "Path: tunnels.editConf.ipV6toV4.encaps6to4.isatap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               copy   (256)"
   ::= {er1645v2TvTmplIpV6toV4Entry 152569088}

er1645v2TvTmplIpV6toV4Encaps6to4IsatapTtl OBJECT-TYPE
   SYNTAX      INTEGER
               {
               copy (256)
               }
   MAX-ACCESS  read-write
   STATUS      current
   DESCRIPTION
      "Path: tunnels.editConf.ipV6toV4.encaps6to4.isatap.ttl

       Possibilities:
               copy   (256)"
   ::= {er1645v2TvTmplIpV6toV4Entry 152569344}

er1645v2TvTmplIpV6toV4InbBwCir OBJECT-TYPE
   SYNTAX      Integer32
   MAX-ACCESS  read-write
   STATUS      current
   DESCRIPTION
      "Path: tunnels.editConf.ipV6toV4.inboundBandwidth.cir"
   ::= {er1645v2TvTmplIpV6toV4Entry 117506048}

er1645v2TvTmplIpV6toV4InbBwTc OBJECT-TYPE
   SYNTAX      INTEGER
               {
               auto (0)
               }
   MAX-ACCESS  read-write
   STATUS      current
   DESCRIPTION
      "Path: tunnels.editConf.ipV6toV4.inboundBandwidth.tc

       Possibilities:
               auto   (0)"
   ::= {er1645v2TvTmplIpV6toV4Entry 117833728}

er1645v2TvTmplIpV6toV4InbBwCorrType OBJECT-TYPE
   SYNTAX      INTEGER
               {
               noCorrection (0),
               predefined (1),
               manual (2)
               }
   MAX-ACCESS  read-write
   STATUS      current
   DESCRIPTION
      "Path: tunnels.editConf.ipV6toV4.inboundBandwidth.correction.type

       Possibilities:
               noCorrection   (0)
               predefined   (1)
               manual   (2)"
   ::= {er1645v2TvTmplIpV6toV4Entry 117579776}

er1645v2TvTmplIpV6toV4InbBwCorrPredefEncapsFrameRelay OBJECT-TYPE
   SYNTAX      DisplayString
   MAX-ACCESS  read-write
   STATUS      current
   DESCRIPTION
      "Path: tunnels.editConf.ipV6toV4.inboundBandwidth.correction.predefined.encapsulation.frameRelay"
   ::= {er1645v2TvTmplIpV6toV4Entry 117589056}

er1645v2TvTmplIpV6toV4InbBwCorrPredefEncapsPpp OBJECT-TYPE
   SYNTAX      DisplayString
   MAX-ACCESS  read-write
   STATUS      current
   DESCRIPTION
      "Path: tunnels.editConf.ipV6toV4.inboundBandwidth.correction.predefined.encapsulation.ppp"
   ::= {er1645v2TvTmplIpV6toV4Entry 117589120}

er1645v2TvTmplIpV6toV4InbBwCorrPredefEncapsAtmHl OBJECT-TYPE
   SYNTAX      INTEGER
               {
               rfc2684 (0),
               ppp (1),
               pppOverEthernet (2)
               }
   MAX-ACCESS  read-write
   STATUS      current
   DESCRIPTION
      "Path: tunnels.editConf.ipV6toV4.inboundBandwidth.correction.predefined.encapsulation.atm.higherLayer

       Possibilities:
               rfc2684   (0)
               ppp   (1)
               pppOverEthernet   (2)"
   ::= {er1645v2TvTmplIpV6toV4Entry 117589192}

er1645v2TvTmplIpV6toV4InbBwCorrPredefEncapsAtmMp OBJECT-TYPE
   SYNTAX      INTEGER
               {
               llcEncapsulation (0),
               vcMultiplexing (1)
               }
   MAX-ACCESS  read-write
   STATUS      current
   DESCRIPTION
      "Path: tunnels.editConf.ipV6toV4.inboundBandwidth.correction.predefined.encapsulation.atm.multiProtocol

       Possibilities:
               llcEncapsulation   (0)
               vcMultiplexing   (1)"
   ::= {er1645v2TvTmplIpV6toV4Entry 117589200}

er1645v2TvTmplIpV6toV4InbBwCorrPredefEncapsHdlc OBJECT-TYPE
   SYNTAX      DisplayString
   MAX-ACCESS  read-write
   STATUS      current
   DESCRIPTION
      "Path: tunnels.editConf.ipV6toV4.inboundBandwidth.correction.predefined.encapsulation.hdlc"
   ::= {er1645v2TvTmplIpV6toV4Entry 117589248}

er1645v2TvTmplIpV6toV4InbBwCorrPredefEncapsEfmFs OBJECT-TYPE
   SYNTAX      Integer32
   MAX-ACCESS  read-write
   STATUS      current
   DESCRIPTION
      "Path: tunnels.editConf.ipV6toV4.inboundBandwidth.correction.predefined.encapsulation.efm.fragmentSize"
   ::= {er1645v2TvTmplIpV6toV4Entry 117589320}

er1645v2TvTmplIpV6toV4InbBwCorrPredefEncapsEfmIb OBJECT-TYPE
   SYNTAX      Integer32
   MAX-ACCESS  read-write
   STATUS      current
   DESCRIPTION
      "Path: tunnels.editConf.ipV6toV4.inboundBandwidth.correction.predefined.encapsulation.efm.idleBytes"
   ::= {er1645v2TvTmplIpV6toV4Entry 117589328}

er1645v2TvTmplIpV6toV4InbBwCorrPredefMode OBJECT-TYPE
   SYNTAX      INTEGER
               {
               routing (0),
               bridging (1)
               }
   MAX-ACCESS  read-write
   STATUS      current
   DESCRIPTION
      "Path: tunnels.editConf.ipV6toV4.inboundBandwidth.correction.predefined.mode

       Possibilities:
               routing   (0)
               bridging   (1)"
   ::= {er1645v2TvTmplIpV6toV4Entry 117590016}

er1645v2TvTmplIpV6toV4InbBwCorrManualOverhead OBJECT-TYPE
   SYNTAX      Integer32
   MAX-ACCESS  read-write
   STATUS      current
   DESCRIPTION
      "Path: tunnels.editConf.ipV6toV4.inboundBandwidth.correction.manual.overhead"
   ::= {er1645v2TvTmplIpV6toV4Entry 117596192}

er1645v2TvTmplIpV6toV4InbBwCorrManualFrameData OBJECT-TYPE
   SYNTAX      Counter32
   MAX-ACCESS  read-write
   STATUS      current
   DESCRIPTION
      "Path: tunnels.editConf.ipV6toV4.inboundBandwidth.correction.manual.frameData

       32 bit unsigned wrappable counter."
   ::= {er1645v2TvTmplIpV6toV4Entry 117596224}

er1645v2TvTmplIpV6toV4InbBwCorrManualFrameHeader OBJECT-TYPE
   SYNTAX      Counter32
   MAX-ACCESS  read-write
   STATUS      current
   DESCRIPTION
      "Path: tunnels.editConf.ipV6toV4.inboundBandwidth.correction.manual.frameHeader

       32 bit unsigned wrappable counter."
   ::= {er1645v2TvTmplIpV6toV4Entry 117596256}

er1645v2TvTmplIpV6toV4InbBwMaxFifoQLen OBJECT-TYPE
   SYNTAX      Integer32
   MAX-ACCESS  read-write
   STATUS      current
   DESCRIPTION
      "Path: tunnels.editConf.ipV6toV4.inboundBandwidth.maxFifoQLen"
   ::= {er1645v2TvTmplIpV6toV4Entry 117637120}

er1645v2TvTmplIpV6toV4InbBwPriorityPolicy OBJECT-TYPE
   SYNTAX      DisplayString
   MAX-ACCESS  read-write
   STATUS      current
   DESCRIPTION
      "Path: tunnels.editConf.ipV6toV4.inboundBandwidth.priorityPolicy"
   ::= {er1645v2TvTmplIpV6toV4Entry 117702656}

er1645v2TvTmplIpV6toV4IpV6Addresses OBJECT-TYPE
   SYNTAX      SEQUENCE OF Er1645v2TvTmplIpV6toV4IpV6AddressesEntry
   MAX-ACCESS  not-accessible
   STATUS      current
   DESCRIPTION
      ""
   ::= {er1645v2TvTmplIpV6toV4 134414336}

er1645v2TvTmplIpV6toV4IpV6AddressesEntry OBJECT-TYPE
   SYNTAX      Er1645v2TvTmplIpV6toV4IpV6AddressesEntry
   MAX-ACCESS  not-accessible
   STATUS      current
   DESCRIPTION
      ""
   INDEX      { er1645v2TvTmplIpV6toV4TableIx,
                er1645v2TvTmplIpV6toV4IpV6AddressesTableIx }
   ::= {er1645v2TvTmplIpV6toV4IpV6Addresses 1}

Er1645v2TvTmplIpV6toV4IpV6AddressesEntry ::=
   SEQUENCE
      {
      er1645v2TvTmplIpV6toV4IpV6AddressesActions
         VariableLengthTableActions,
      er1645v2TvTmplIpV6toV4IpV6AddressesTableIx
         TableIndex,
      er1645v2TvTmplIpV6toV4IpV6AddressesType
         INTEGER,
      er1645v2TvTmplIpV6toV4IpV6AddressesAddress
         Ipv6Address,
      er1645v2TvTmplIpV6toV4IpV6AddressesPrefixLength
         Integer32,
      er1645v2TvTmplIpV6toV4IpV6AddressesGeneralPrefix
         DisplayString,
      er1645v2TvTmplIpV6toV4IpV6AddressesRaSend
         INTEGER,
      er1645v2TvTmplIpV6toV4IpV6AddressesRaOnLinkFlag
         INTEGER,
      er1645v2TvTmplIpV6toV4IpV6AddressesRaAutoFlag
         INTEGER,
      er1645v2TvTmplIpV6toV4IpV6AddressesRaValidLifeTime
         TimeTicks,
      er1645v2TvTmplIpV6toV4IpV6AddressesRaValidLTMode
         INTEGER,
      er1645v2TvTmplIpV6toV4IpV6AddressesRaPrefLifeTime
         TimeTicks,
      er1645v2TvTmplIpV6toV4IpV6AddressesRaPrefLTMode
         INTEGER
      }

er1645v2TvTmplIpV6toV4IpV6AddressesActions OBJECT-TYPE
   SYNTAX      VariableLengthTableActions
   MAX-ACCESS  read-write
   STATUS      current
   DESCRIPTION
      "By way of this field, some manipulations
       on this table may be performed."
   ::= {er1645v2TvTmplIpV6toV4IpV6AddressesEntry 2}

er1645v2TvTmplIpV6toV4IpV6AddressesTableIx OBJECT-TYPE
   SYNTAX      TableIndex
   MAX-ACCESS  not-accessible
   STATUS      current
   DESCRIPTION
      ""
   ::= {er1645v2TvTmplIpV6toV4IpV6AddressesEntry 11}

er1645v2TvTmplIpV6toV4IpV6AddressesType OBJECT-TYPE
   SYNTAX      INTEGER
               {
               unicast (0),
               eui64 (1),
               anycast (2),
               linkLocal (3),
               generalPrefix (4)
               }
   MAX-ACCESS  read-write
   STATUS      current
   DESCRIPTION
      "Path: tunnels.editConf.ipV6toV4.ipV6.addresses.type

       Possibilities:
               unicast   (0)
               eui64   (1)
               anycast   (2)
               linkLocal   (3)
               generalPrefix   (4)"
   ::= {er1645v2TvTmplIpV6toV4IpV6AddressesEntry 50331648}

er1645v2TvTmplIpV6toV4IpV6AddressesAddress OBJECT-TYPE
   SYNTAX      Ipv6Address
   MAX-ACCESS  read-write
   STATUS      current
   DESCRIPTION
      "Path: tunnels.editConf.ipV6toV4.ipV6.addresses.address

       ipv6 address"
   ::= {er1645v2TvTmplIpV6toV4IpV6AddressesEntry 16777216}

er1645v2TvTmplIpV6toV4IpV6AddressesPrefixLength OBJECT-TYPE
   SYNTAX      Integer32
   MAX-ACCESS  read-write
   STATUS      current
   DESCRIPTION
      "Path: tunnels.editConf.ipV6toV4.ipV6.addresses.prefixLength"
   ::= {er1645v2TvTmplIpV6toV4IpV6AddressesEntry 33554432}

er1645v2TvTmplIpV6toV4IpV6AddressesGeneralPrefix OBJECT-TYPE
   SYNTAX      DisplayString
   MAX-ACCESS  read-write
   STATUS      current
   DESCRIPTION
      "Path: tunnels.editConf.ipV6toV4.ipV6.addresses.generalPrefix"
   ::= {er1645v2TvTmplIpV6toV4IpV6AddressesEntry 83886080}

er1645v2TvTmplIpV6toV4IpV6AddressesRaSend OBJECT-TYPE
   SYNTAX      INTEGER
               {
               disabled (0),
               enabled (1)
               }
   MAX-ACCESS  read-write
   STATUS      current
   DESCRIPTION
      "Path: tunnels.editConf.ipV6toV4.ipV6.addresses.ra.send

       Possibilities:
               disabled   (0)
               enabled   (1)"
   ::= {er1645v2TvTmplIpV6toV4IpV6AddressesEntry 67174400}

er1645v2TvTmplIpV6toV4IpV6AddressesRaOnLinkFlag OBJECT-TYPE
   SYNTAX      INTEGER
               {
               disabled (0),
               enabled (1)
               }
   MAX-ACCESS  read-write
   STATUS      current
   DESCRIPTION
      "Path: tunnels.editConf.ipV6toV4.ipV6.addresses.ra.onLinkFlag

       Possibilities:
               disabled   (0)
               enabled   (1)"
   ::= {er1645v2TvTmplIpV6toV4IpV6AddressesEntry 67371008}

er1645v2TvTmplIpV6toV4IpV6AddressesRaAutoFlag OBJECT-TYPE
   SYNTAX      INTEGER
               {
               disabled (0),
               enabled (1)
               }
   MAX-ACCESS  read-write
   STATUS      current
   DESCRIPTION
      "Path: tunnels.editConf.ipV6toV4.ipV6.addresses.ra.autonomousFlag

       Possibilities:
               disabled   (0)
               enabled   (1)"
   ::= {er1645v2TvTmplIpV6toV4IpV6AddressesEntry 67567616}

er1645v2TvTmplIpV6toV4IpV6AddressesRaValidLifeTime OBJECT-TYPE
   SYNTAX      TimeTicks
   MAX-ACCESS  read-write
   STATUS      current
   DESCRIPTION
      "Path: tunnels.editConf.ipV6toV4.ipV6.addresses.ra.validLifeTime

       Time in centi-second."
   ::= {er1645v2TvTmplIpV6toV4IpV6AddressesEntry 67239936}

er1645v2TvTmplIpV6toV4IpV6AddressesRaValidLTMode OBJECT-TYPE
   SYNTAX      INTEGER
               {
               fixed (0),
               infinite (2)
               }
   MAX-ACCESS  read-write
   STATUS      current
   DESCRIPTION
      "Path: tunnels.editConf.ipV6toV4.ipV6.addresses.ra.validLifeTimeMode

       Possibilities:
               fixed   (0)
               infinite   (2)"
   ::= {er1645v2TvTmplIpV6toV4IpV6AddressesEntry 67305472}

er1645v2TvTmplIpV6toV4IpV6AddressesRaPrefLifeTime OBJECT-TYPE
   SYNTAX      TimeTicks
   MAX-ACCESS  read-write
   STATUS      current
   DESCRIPTION
      "Path: tunnels.editConf.ipV6toV4.ipV6.addresses.ra.prefLifeTime

       Time in centi-second."
   ::= {er1645v2TvTmplIpV6toV4IpV6AddressesEntry 67436544}

er1645v2TvTmplIpV6toV4IpV6AddressesRaPrefLTMode OBJECT-TYPE
   SYNTAX      INTEGER
               {
               fixed (0),
               infinite (2)
               }
   MAX-ACCESS  read-write
   STATUS      current
   DESCRIPTION
      "Path: tunnels.editConf.ipV6toV4.ipV6.addresses.ra.prefLifeTimeMode

       Possibilities:
               fixed   (0)
               infinite   (2)"
   ::= {er1645v2TvTmplIpV6toV4IpV6AddressesEntry 67502080}

er1645v2TvTmplIpV6toV4IpV6RaDnsOptionsRdnssServers OBJECT-TYPE
   SYNTAX      SEQUENCE OF Er1645v2TvTmplIpV6toV4IpV6RaDnsOptionsRdnssServersEntry
   MAX-ACCESS  not-accessible
   STATUS      current
   DESCRIPTION
      ""
   ::= {er1645v2TvTmplIpV6toV4 134613800}

er1645v2TvTmplIpV6toV4IpV6RaDnsOptionsRdnssServersEntry OBJECT-TYPE
   SYNTAX      Er1645v2TvTmplIpV6toV4IpV6RaDnsOptionsRdnssServersEntry
   MAX-ACCESS  not-accessible
   STATUS      current
   DESCRIPTION
      ""
   INDEX      { er1645v2TvTmplIpV6toV4TableIx,
                er1645v2TvTmplIpV6toV4IpV6RaDnsOptionsRdnssServersTableIx }
   ::= {er1645v2TvTmplIpV6toV4IpV6RaDnsOptionsRdnssServers 1}

Er1645v2TvTmplIpV6toV4IpV6RaDnsOptionsRdnssServersEntry ::=
   SEQUENCE
      {
      er1645v2TvTmplIpV6toV4IpV6RaDnsOptionsRdnssServersActions
         VariableLengthTableActions,
      er1645v2TvTmplIpV6toV4IpV6RaDnsOptionsRdnssServersTableIx
         TableIndex,
      er1645v2TvTmplIpV6toV4IpV6RaDnsOptionsRdnssServersAddress
         Ipv6Address
      }

er1645v2TvTmplIpV6toV4IpV6RaDnsOptionsRdnssServersActions OBJECT-TYPE
   SYNTAX      VariableLengthTableActions
   MAX-ACCESS  read-write
   STATUS      current
   DESCRIPTION
      "By way of this field, some manipulations
       on this table may be performed."
   ::= {er1645v2TvTmplIpV6toV4IpV6RaDnsOptionsRdnssServersEntry 2}

er1645v2TvTmplIpV6toV4IpV6RaDnsOptionsRdnssServersTableIx OBJECT-TYPE
   SYNTAX      TableIndex
   MAX-ACCESS  not-accessible
   STATUS      current
   DESCRIPTION
      ""
   ::= {er1645v2TvTmplIpV6toV4IpV6RaDnsOptionsRdnssServersEntry 11}

er1645v2TvTmplIpV6toV4IpV6RaDnsOptionsRdnssServersAddress OBJECT-TYPE
   SYNTAX      Ipv6Address
   MAX-ACCESS  read-write
   STATUS      current
   DESCRIPTION
      "Path: tunnels.editConf.ipV6toV4.ipV6.ra.dnsOptions.rdnss.servers.address

       ipv6 address"
   ::= {er1645v2TvTmplIpV6toV4IpV6RaDnsOptionsRdnssServersEntry 16777216}

er1645v2TvTmplIpV6toV4IpV6RaDnsOptionsDnsslDomains OBJECT-TYPE
   SYNTAX      SEQUENCE OF Er1645v2TvTmplIpV6toV4IpV6RaDnsOptionsDnsslDomainsEntry
   MAX-ACCESS  not-accessible
   STATUS      current
   DESCRIPTION
      ""
   ::= {er1645v2TvTmplIpV6toV4 134613832}

er1645v2TvTmplIpV6toV4IpV6RaDnsOptionsDnsslDomainsEntry OBJECT-TYPE
   SYNTAX      Er1645v2TvTmplIpV6toV4IpV6RaDnsOptionsDnsslDomainsEntry
   MAX-ACCESS  not-accessible
   STATUS      current
   DESCRIPTION
      ""
   INDEX      { er1645v2TvTmplIpV6toV4TableIx,
                er1645v2TvTmplIpV6toV4IpV6RaDnsOptionsDnsslDomainsTableIx }
   ::= {er1645v2TvTmplIpV6toV4IpV6RaDnsOptionsDnsslDomains 1}

Er1645v2TvTmplIpV6toV4IpV6RaDnsOptionsDnsslDomainsEntry ::=
   SEQUENCE
      {
      er1645v2TvTmplIpV6toV4IpV6RaDnsOptionsDnsslDomainsActions
         VariableLengthTableActions,
      er1645v2TvTmplIpV6toV4IpV6RaDnsOptionsDnsslDomainsTableIx
         TableIndex,
      er1645v2TvTmplIpV6toV4IpV6RaDnsOptionsDnsslDomainsName
         DisplayString
      }

er1645v2TvTmplIpV6toV4IpV6RaDnsOptionsDnsslDomainsActions OBJECT-TYPE
   SYNTAX      VariableLengthTableActions
   MAX-ACCESS  read-write
   STATUS      current
   DESCRIPTION
      "By way of this field, some manipulations
       on this table may be performed."
   ::= {er1645v2TvTmplIpV6toV4IpV6RaDnsOptionsDnsslDomainsEntry 2}

er1645v2TvTmplIpV6toV4IpV6RaDnsOptionsDnsslDomainsTableIx OBJECT-TYPE
   SYNTAX      TableIndex
   MAX-ACCESS  not-accessible
   STATUS      current
   DESCRIPTION
      ""
   ::= {er1645v2TvTmplIpV6toV4IpV6RaDnsOptionsDnsslDomainsEntry 11}

er1645v2TvTmplIpV6toV4IpV6RaDnsOptionsDnsslDomainsName OBJECT-TYPE
   SYNTAX      DisplayString
   MAX-ACCESS  read-write
   STATUS      current
   DESCRIPTION
      "Path: tunnels.editConf.ipV6toV4.ipV6.ra.dnsOptions.dnssl.domains.name"
   ::= {er1645v2TvTmplIpV6toV4IpV6RaDnsOptionsDnsslDomainsEntry 16777216}

er1645v2TvTmplIpV6toV4IpV6DhcpClientUserClassOpt OBJECT-TYPE
   SYNTAX      SEQUENCE OF Er1645v2TvTmplIpV6toV4IpV6DhcpClientUserClassOptEntry
   MAX-ACCESS  not-accessible
   STATUS      current
   DESCRIPTION
      ""
   ::= {er1645v2TvTmplIpV6toV4 134887424}

er1645v2TvTmplIpV6toV4IpV6DhcpClientUserClassOptEntry OBJECT-TYPE
   SYNTAX      Er1645v2TvTmplIpV6toV4IpV6DhcpClientUserClassOptEntry
   MAX-ACCESS  not-accessible
   STATUS      current
   DESCRIPTION
      ""
   INDEX      { er1645v2TvTmplIpV6toV4TableIx,
                er1645v2TvTmplIpV6toV4IpV6DhcpClientUserClassOptTableIx }
   ::= {er1645v2TvTmplIpV6toV4IpV6DhcpClientUserClassOpt 1}

Er1645v2TvTmplIpV6toV4IpV6DhcpClientUserClassOptEntry ::=
   SEQUENCE
      {
      er1645v2TvTmplIpV6toV4IpV6DhcpClientUserClassOptActions
         VariableLengthTableActions,
      er1645v2TvTmplIpV6toV4IpV6DhcpClientUserClassOptTableIx
         TableIndex,
      er1645v2TvTmplIpV6toV4IpV6DhcpClientUserClassOptValueAscii
         DisplayString,
      er1645v2TvTmplIpV6toV4IpV6DhcpClientUserClassOptValueDecimal
         Integer32,
      er1645v2TvTmplIpV6toV4IpV6DhcpClientUserClassOptValueHexData
         OCTET STRING
      }

er1645v2TvTmplIpV6toV4IpV6DhcpClientUserClassOptActions OBJECT-TYPE
   SYNTAX      VariableLengthTableActions
   MAX-ACCESS  read-write
   STATUS      current
   DESCRIPTION
      "By way of this field, some manipulations
       on this table may be performed."
   ::= {er1645v2TvTmplIpV6toV4IpV6DhcpClientUserClassOptEntry 2}

er1645v2TvTmplIpV6toV4IpV6DhcpClientUserClassOptTableIx OBJECT-TYPE
   SYNTAX      TableIndex
   MAX-ACCESS  not-accessible
   STATUS      current
   DESCRIPTION
      ""
   ::= {er1645v2TvTmplIpV6toV4IpV6DhcpClientUserClassOptEntry 11}

er1645v2TvTmplIpV6toV4IpV6DhcpClientUserClassOptValueAscii OBJECT-TYPE
   SYNTAX      DisplayString
   MAX-ACCESS  read-write
   STATUS      current
   DESCRIPTION
      "Path: tunnels.editConf.ipV6toV4.ipV6.dhcp.client.userClassOpt.value.ascii"
   ::= {er1645v2TvTmplIpV6toV4IpV6DhcpClientUserClassOptEntry 16842752}

er1645v2TvTmplIpV6toV4IpV6DhcpClientUserClassOptValueDecimal OBJECT-TYPE
   SYNTAX      Integer32
   MAX-ACCESS  read-write
   STATUS      current
   DESCRIPTION
      "Path: tunnels.editConf.ipV6toV4.ipV6.dhcp.client.userClassOpt.value.decimal"
   ::= {er1645v2TvTmplIpV6toV4IpV6DhcpClientUserClassOptEntry 16908288}

er1645v2TvTmplIpV6toV4IpV6DhcpClientUserClassOptValueHexData OBJECT-TYPE
   SYNTAX      OCTET STRING
   MAX-ACCESS  read-write
   STATUS      current
   DESCRIPTION
      "Path: tunnels.editConf.ipV6toV4.ipV6.dhcp.client.userClassOpt.value.hexData"
   ::= {er1645v2TvTmplIpV6toV4IpV6DhcpClientUserClassOptEntry 16973824}

er1645v2TvTmplIpV6toV4IpV6DhcpClientVendorCl OBJECT-TYPE
   SYNTAX      SEQUENCE OF Er1645v2TvTmplIpV6toV4IpV6DhcpClientVendorClEntry
   MAX-ACCESS  not-accessible
   STATUS      current
   DESCRIPTION
      ""
   ::= {er1645v2TvTmplIpV6toV4 134888448}

er1645v2TvTmplIpV6toV4IpV6DhcpClientVendorClEntry OBJECT-TYPE
   SYNTAX      Er1645v2TvTmplIpV6toV4IpV6DhcpClientVendorClEntry
   MAX-ACCESS  not-accessible
   STATUS      current
   DESCRIPTION
      ""
   INDEX      { er1645v2TvTmplIpV6toV4TableIx,
                er1645v2TvTmplIpV6toV4IpV6DhcpClientVendorClTableIx }
   ::= {er1645v2TvTmplIpV6toV4IpV6DhcpClientVendorCl 1}

Er1645v2TvTmplIpV6toV4IpV6DhcpClientVendorClEntry ::=
   SEQUENCE
      {
      er1645v2TvTmplIpV6toV4IpV6DhcpClientVendorClActions
         VariableLengthTableActions,
      er1645v2TvTmplIpV6toV4IpV6DhcpClientVendorClTableIx
         TableIndex,
      er1645v2TvTmplIpV6toV4IpV6DhcpClientVendorClValueAscii
         DisplayString,
      er1645v2TvTmplIpV6toV4IpV6DhcpClientVendorClValueDecimal
         Integer32,
      er1645v2TvTmplIpV6toV4IpV6DhcpClientVendorClValueHexData
         OCTET STRING
      }

er1645v2TvTmplIpV6toV4IpV6DhcpClientVendorClActions OBJECT-TYPE
   SYNTAX      VariableLengthTableActions
   MAX-ACCESS  read-write
   STATUS      current
   DESCRIPTION
      "By way of this field, some manipulations
       on this table may be performed."
   ::= {er1645v2TvTmplIpV6toV4IpV6DhcpClientVendorClEntry 2}

er1645v2TvTmplIpV6toV4IpV6DhcpClientVendorClTableIx OBJECT-TYPE
   SYNTAX      TableIndex
   MAX-ACCESS  not-accessible
   STATUS      current
   DESCRIPTION
      ""
   ::= {er1645v2TvTmplIpV6toV4IpV6DhcpClientVendorClEntry 11}

er1645v2TvTmplIpV6toV4IpV6DhcpClientVendorClValueAscii OBJECT-TYPE
   SYNTAX      DisplayString
   MAX-ACCESS  read-write
   STATUS      current
   DESCRIPTION
      "Path: tunnels.editConf.ipV6toV4.ipV6.dhcp.client.vendorClassOpt.value.ascii"
   ::= {er1645v2TvTmplIpV6toV4IpV6DhcpClientVendorClEntry 16842752}

er1645v2TvTmplIpV6toV4IpV6DhcpClientVendorClValueDecimal OBJECT-TYPE
   SYNTAX      Integer32
   MAX-ACCESS  read-write
   STATUS      current
   DESCRIPTION
      "Path: tunnels.editConf.ipV6toV4.ipV6.dhcp.client.vendorClassOpt.value.decimal"
   ::= {er1645v2TvTmplIpV6toV4IpV6DhcpClientVendorClEntry 16908288}

er1645v2TvTmplIpV6toV4IpV6DhcpClientVendorClValueHexData OBJECT-TYPE
   SYNTAX      OCTET STRING
   MAX-ACCESS  read-write
   STATUS      current
   DESCRIPTION
      "Path: tunnels.editConf.ipV6toV4.ipV6.dhcp.client.vendorClassOpt.value.hexData"
   ::= {er1645v2TvTmplIpV6toV4IpV6DhcpClientVendorClEntry 16973824}

er1645v2TvTmplIpV6toV4IpV6DhcpRelayDestinations OBJECT-TYPE
   SYNTAX      SEQUENCE OF Er1645v2TvTmplIpV6toV4IpV6DhcpRelayDestinationsEntry
   MAX-ACCESS  not-accessible
   STATUS      current
   DESCRIPTION
      ""
   ::= {er1645v2TvTmplIpV6toV4 134897728}

er1645v2TvTmplIpV6toV4IpV6DhcpRelayDestinationsEntry OBJECT-TYPE
   SYNTAX      Er1645v2TvTmplIpV6toV4IpV6DhcpRelayDestinationsEntry
   MAX-ACCESS  not-accessible
   STATUS      current
   DESCRIPTION
      ""
   INDEX      { er1645v2TvTmplIpV6toV4TableIx,
                er1645v2TvTmplIpV6toV4IpV6DhcpRelayDestinationsTableIx }
   ::= {er1645v2TvTmplIpV6toV4IpV6DhcpRelayDestinations 1}

Er1645v2TvTmplIpV6toV4IpV6DhcpRelayDestinationsEntry ::=
   SEQUENCE
      {
      er1645v2TvTmplIpV6toV4IpV6DhcpRelayDestinationsActions
         VariableLengthTableActions,
      er1645v2TvTmplIpV6toV4IpV6DhcpRelayDestinationsTableIx
         TableIndex,
      er1645v2TvTmplIpV6toV4IpV6DhcpRelayDestinationsAddress
         Ipv6Address,
      er1645v2TvTmplIpV6toV4IpV6DhcpRelayDestinationsInterface
         DisplayString
      }

er1645v2TvTmplIpV6toV4IpV6DhcpRelayDestinationsActions OBJECT-TYPE
   SYNTAX      VariableLengthTableActions
   MAX-ACCESS  read-write
   STATUS      current
   DESCRIPTION
      "By way of this field, some manipulations
       on this table may be performed."
   ::= {er1645v2TvTmplIpV6toV4IpV6DhcpRelayDestinationsEntry 2}

er1645v2TvTmplIpV6toV4IpV6DhcpRelayDestinationsTableIx OBJECT-TYPE
   SYNTAX      TableIndex
   MAX-ACCESS  not-accessible
   STATUS      current
   DESCRIPTION
      ""
   ::= {er1645v2TvTmplIpV6toV4IpV6DhcpRelayDestinationsEntry 11}

er1645v2TvTmplIpV6toV4IpV6DhcpRelayDestinationsAddress OBJECT-TYPE
   SYNTAX      Ipv6Address
   MAX-ACCESS  read-write
   STATUS      current
   DESCRIPTION
      "Path: tunnels.editConf.ipV6toV4.ipV6.dhcp.relay.destinations.address

       ipv6 address"
   ::= {er1645v2TvTmplIpV6toV4IpV6DhcpRelayDestinationsEntry 16777216}

er1645v2TvTmplIpV6toV4IpV6DhcpRelayDestinationsInterface OBJECT-TYPE
   SYNTAX      DisplayString
   MAX-ACCESS  read-write
   STATUS      current
   DESCRIPTION
      "Path: tunnels.editConf.ipV6toV4.ipV6.dhcp.relay.destinations.interface"
   ::= {er1645v2TvTmplIpV6toV4IpV6DhcpRelayDestinationsEntry 33554432}

er1645v2TvTmplIpV6toV4Encaps6to4IsatapRemAddr OBJECT-TYPE
   SYNTAX      SEQUENCE OF Er1645v2TvTmplIpV6toV4Encaps6to4IsatapRemAddrEntry
   MAX-ACCESS  not-accessible
   STATUS      current
   DESCRIPTION
      ""
   ::= {er1645v2TvTmplIpV6toV4 152570624}

er1645v2TvTmplIpV6toV4Encaps6to4IsatapRemAddrEntry OBJECT-TYPE
   SYNTAX      Er1645v2TvTmplIpV6toV4Encaps6to4IsatapRemAddrEntry
   MAX-ACCESS  not-accessible
   STATUS      current
   DESCRIPTION
      ""
   INDEX      { er1645v2TvTmplIpV6toV4TableIx,
                er1645v2TvTmplIpV6toV4Encaps6to4IsatapRemAddrTableIx }
   ::= {er1645v2TvTmplIpV6toV4Encaps6to4IsatapRemAddr 1}

Er1645v2TvTmplIpV6toV4Encaps6to4IsatapRemAddrEntry ::=
   SEQUENCE
      {
      er1645v2TvTmplIpV6toV4Encaps6to4IsatapRemAddrActions
         VariableLengthTableActions,
      er1645v2TvTmplIpV6toV4Encaps6to4IsatapRemAddrTableIx
         TableIndex,
      er1645v2TvTmplIpV6toV4Encaps6to4IsatapRemAddrAddress
         IpAddress
      }

er1645v2TvTmplIpV6toV4Encaps6to4IsatapRemAddrActions OBJECT-TYPE
   SYNTAX      VariableLengthTableActions
   MAX-ACCESS  read-write
   STATUS      current
   DESCRIPTION
      "By way of this field, some manipulations
       on this table may be performed."
   ::= {er1645v2TvTmplIpV6toV4Encaps6to4IsatapRemAddrEntry 2}

er1645v2TvTmplIpV6toV4Encaps6to4IsatapRemAddrTableIx OBJECT-TYPE
   SYNTAX      TableIndex
   MAX-ACCESS  not-accessible
   STATUS      current
   DESCRIPTION
      ""
   ::= {er1645v2TvTmplIpV6toV4Encaps6to4IsatapRemAddrEntry 11}

er1645v2TvTmplIpV6toV4Encaps6to4IsatapRemAddrAddress OBJECT-TYPE
   SYNTAX      IpAddress
   MAX-ACCESS  read-write
   STATUS      current
   DESCRIPTION
      "Path: tunnels.editConf.ipV6toV4.encaps6to4.isatap.remoteAddresses.address"
   ::= {er1645v2TvTmplIpV6toV4Encaps6to4IsatapRemAddrEntry 16777216}


er1645v2TvTmplVxT OBJECT IDENTIFIER ::= {er1645v2TvTmpl 43}

er1645v2TvTmplVxTSSCTable OBJECT-TYPE
   SYNTAX      SEQUENCE OF Er1645v2TvTmplVxTEntry
   MAX-ACCESS  not-accessible
   STATUS      current
   DESCRIPTION
      ""
   ::= {er1645v2TvTmplVxT 1}

er1645v2TvTmplVxTEntry OBJECT-TYPE
   SYNTAX      Er1645v2TvTmplVxTEntry
   MAX-ACCESS  not-accessible
   STATUS      current
   DESCRIPTION
      ""
   INDEX      { er1645v2TvTmplVxTTableIx }
   ::= {er1645v2TvTmplVxTSSCTable 1}

Er1645v2TvTmplVxTEntry ::=
   SEQUENCE
      {
      er1645v2TvTmplVxTActions
         VariableLengthTableActions,
      er1645v2TvTmplVxTTableIx
         TableIndex,
      er1645v2TvTmplVxTName
         DisplayString,
      er1645v2TvTmplVxTRemark
         DisplayString,
      er1645v2TvTmplVxTAdminStatus
         INTEGER,
      er1645v2TvTmplVxTMode
         INTEGER,
      er1645v2TvTmplVxTBridgingAccList
         DisplayString,
      er1645v2TvTmplVxTBridgingInACL
         DisplayString,
      er1645v2TvTmplVxTBridgingTp
         DisplayString,
      er1645v2TvTmplVxTBridgingBrGrp
         DisplayString,
      er1645v2TvTmplVxTBridgingLimBC
         INTEGER,
      er1645v2TvTmplVxTBridgingPrivateMode
         INTEGER,
      er1645v2TvTmplVxTBridgingLearning
         INTEGER,
      er1645v2TvTmplVxTBridgingMaxCacheSize
         INTEGER,
      er1645v2TvTmplVxTBridgingRelearnDropOnRelearn
         INTEGER,
      er1645v2TvTmplVxTBridgingRelearnShutdownThreshold
         Integer32,
      er1645v2TvTmplVxTBridgingRelearnShutdownTime
         TimeTicks,
      er1645v2TvTmplVxTBridgingRelearnLoopDetection
         INTEGER,
      er1645v2TvTmplVxTBridgingRelearnLoopDetectionInterval
         TimeTicks,
      er1645v2TvTmplVxTBridgingVlanMemberShip
         INTEGER,
      er1645v2TvTmplVxTBridgingVlTUntaggedAction
         INTEGER,
      er1645v2TvTmplVxTBridgingVlTUntaggedTagInfoTpid
         INTEGER,
      er1645v2TvTmplVxTBridgingVlTUntaggedTagInfoVid
         Integer32,
      er1645v2TvTmplVxTBridgingVlTUnknownVlansAction
         INTEGER,
      er1645v2TvTmplVxTBridgingVlTUnknownVlansTagInfoTpid
         INTEGER,
      er1645v2TvTmplVxTBridgingVlTUnknownVlansTagInfoVid
         Integer32,
      er1645v2TvTmplVxTBridgingDot1adType
         INTEGER,
      er1645v2TvTmplVxTBridgingPriority
         Integer32,
      er1645v2TvTmplVxTBridgingPathCost
         Integer32,
      er1645v2TvTmplVxTBridgingInternalPathCost
         Integer32,
      er1645v2TvTmplVxTBridgingTCD
         INTEGER,
      er1645v2TvTmplVxTBridgingRestrictedRole
         INTEGER,
      er1645v2TvTmplVxTBridgingAdminEdge
         INTEGER,
      er1645v2TvTmplVxTBridgingOamMacDeviceMac
         DisplayString,
      er1645v2TvTmplVxTBridgingOamMacUserMac
         OCTET STRING,
      er1645v2TvTmplVxTBridgingOamMacBridgeMac
         DisplayString,
      er1645v2TvTmplVxTBridgingMgmtInline
         INTEGER,
      er1645v2TvTmplVxTBridgingL2ptMode
         INTEGER,
      er1645v2TvTmplVxTBridgingL2ptProtocols
         Integer32,
      er1645v2TvTmplVxTBridgingL2ptDestMac
         OCTET STRING,
      er1645v2TvTmplVxTBridgingL2ptCos
         INTEGER,
      er1645v2TvTmplVxTBridgingL2ptDropThrStp
         INTEGER,
      er1645v2TvTmplVxTBridgingL2ptDropThrLldp
         INTEGER,
      er1645v2TvTmplVxTBridgingL2ptDropThrOam
         INTEGER,
      er1645v2TvTmplVxTBridgingL2ptDropThrCdp
         INTEGER,
      er1645v2TvTmplVxTBridgingL2ptDropThrVtp
         INTEGER,
      er1645v2TvTmplVxTBridgingL2ptDropThrLacp
         INTEGER,
      er1645v2TvTmplVxTBridgingL2ptDropThrEfmOam
         INTEGER,
      er1645v2TvTmplVxTBridgingL2ptDropThrPvst
         INTEGER,
      er1645v2TvTmplVxTBridgingL2ptDropThrMmrp
         INTEGER,
      er1645v2TvTmplVxTBridgingL2ptDropThrMvrp
         INTEGER,
      er1645v2TvTmplVxTBridgingL2ptDropThrGvrp
         INTEGER,
      er1645v2TvTmplVxTBridgingL2ptDropThrGmrp
         INTEGER,
      er1645v2TvTmplVxTBridgingL2ptDropThrDtp
         INTEGER,
      er1645v2TvTmplVxTBridgingL2ptDropThrPagp
         INTEGER,
      er1645v2TvTmplVxTBridgingL2ptDropThrUdld
         INTEGER,
      er1645v2TvTmplVxTVxLanVni
         Integer32,
      er1645v2TvTmplVxTVxLanRemoteMulticast
         IpAddress,
      er1645v2TvTmplVxTVxLanRemoteUnicast
         IpAddress,
      er1645v2TvTmplVxTVxLanLocalInterface
         DisplayString
      }

er1645v2TvTmplVxTActions OBJECT-TYPE
   SYNTAX      VariableLengthTableActions
   MAX-ACCESS  read-write
   STATUS      current
   DESCRIPTION
      "By way of this field, some manipulations
       on this table may be performed."
   ::= {er1645v2TvTmplVxTEntry 2}

er1645v2TvTmplVxTTableIx OBJECT-TYPE
   SYNTAX      TableIndex
   MAX-ACCESS  not-accessible
   STATUS      current
   DESCRIPTION
      ""
   ::= {er1645v2TvTmplVxTEntry 11}

er1645v2TvTmplVxTName OBJECT-TYPE
   SYNTAX      DisplayString
   MAX-ACCESS  read-write
   STATUS      current
   DESCRIPTION
      "Path: tunnels.editConf.vxLanTunnels.name"
   ::= {er1645v2TvTmplVxTEntry 16777216}

er1645v2TvTmplVxTRemark OBJECT-TYPE
   SYNTAX      DisplayString
   MAX-ACCESS  read-write
   STATUS      current
   DESCRIPTION
      "Path: tunnels.editConf.vxLanTunnels.remark"
   ::= {er1645v2TvTmplVxTEntry 1157627904}

er1645v2TvTmplVxTAdminStatus OBJECT-TYPE
   SYNTAX      INTEGER
               {
               up (1),
               down (2)
               }
   MAX-ACCESS  read-write
   STATUS      current
   DESCRIPTION
      "Path: tunnels.editConf.vxLanTunnels.adminStatus

       Possibilities:
               up   (1)
               down   (2)"
   ::= {er1645v2TvTmplVxTEntry 33554432}

er1645v2TvTmplVxTMode OBJECT-TYPE
   SYNTAX      INTEGER
               {
               bridging (2)
               }
   MAX-ACCESS  read-write
   STATUS      current
   DESCRIPTION
      "Path: tunnels.editConf.vxLanTunnels.mode

       Possibilities:
               bridging   (2)"
   ::= {er1645v2TvTmplVxTEntry 67108864}

er1645v2TvTmplVxTBridgingAccList OBJECT-TYPE
   SYNTAX      DisplayString
   MAX-ACCESS  read-write
   STATUS      current
   DESCRIPTION
      "Path: tunnels.editConf.vxLanTunnels.bridging.accessList"
   ::= {er1645v2TvTmplVxTEntry 453246976}

er1645v2TvTmplVxTBridgingInACL OBJECT-TYPE
   SYNTAX      DisplayString
   MAX-ACCESS  read-write
   STATUS      current
   DESCRIPTION
      "Path: tunnels.editConf.vxLanTunnels.bridging.inAccessList"
   ::= {er1645v2TvTmplVxTEntry 456916992}

er1645v2TvTmplVxTBridgingTp OBJECT-TYPE
   SYNTAX      DisplayString
   MAX-ACCESS  read-write
   STATUS      current
   DESCRIPTION
      "Path: tunnels.editConf.vxLanTunnels.bridging.trafficPolicy"
   ::= {er1645v2TvTmplVxTEntry 454295552}

er1645v2TvTmplVxTBridgingBrGrp OBJECT-TYPE
   SYNTAX      DisplayString
   MAX-ACCESS  read-write
   STATUS      current
   DESCRIPTION
      "Path: tunnels.editConf.vxLanTunnels.bridging.bridgeGroup"
   ::= {er1645v2TvTmplVxTEntry 454819840}

er1645v2TvTmplVxTBridgingLimBC OBJECT-TYPE
   SYNTAX      INTEGER
               {
               disabled (0),
               enabled (1)
               }
   MAX-ACCESS  read-write
   STATUS      current
   DESCRIPTION
      "Path: tunnels.editConf.vxLanTunnels.bridging.limitBroadcasts

       Possibilities:
               disabled   (0)
               enabled   (1)"
   ::= {er1645v2TvTmplVxTEntry 455081984}

er1645v2TvTmplVxTBridgingPrivateMode OBJECT-TYPE
   SYNTAX      INTEGER
               {
               disabled (0),
               enabled (1)
               }
   MAX-ACCESS  read-write
   STATUS      current
   DESCRIPTION
      "Path: tunnels.editConf.vxLanTunnels.bridging.privateMode

       Possibilities:
               disabled   (0)
               enabled   (1)"
   ::= {er1645v2TvTmplVxTEntry 459538432}

er1645v2TvTmplVxTBridgingLearning OBJECT-TYPE
   SYNTAX      INTEGER
               {
               disabled (0),
               enabled (1)
               }
   MAX-ACCESS  read-write
   STATUS      current
   DESCRIPTION
      "Path: tunnels.editConf.vxLanTunnels.bridging.learning

       Possibilities:
               disabled   (0)
               enabled   (1)"
   ::= {er1645v2TvTmplVxTEntry 456130560}

er1645v2TvTmplVxTBridgingMaxCacheSize OBJECT-TYPE
   SYNTAX      INTEGER
               {
               unlimited (0)
               }
   MAX-ACCESS  read-write
   STATUS      current
   DESCRIPTION
      "Path: tunnels.editConf.vxLanTunnels.bridging.maxCacheSize

       Possibilities:
               unlimited   (0)"
   ::= {er1645v2TvTmplVxTEntry 456392704}

er1645v2TvTmplVxTBridgingRelearnDropOnRelearn OBJECT-TYPE
   SYNTAX      INTEGER
               {
               disabled (0),
               enabled (1)
               }
   MAX-ACCESS  read-write
   STATUS      current
   DESCRIPTION
      "Path: tunnels.editConf.vxLanTunnels.bridging.relearn.dropOnRelearn

       Possibilities:
               disabled   (0)
               enabled   (1)"
   ::= {er1645v2TvTmplVxTEntry 456655872}

er1645v2TvTmplVxTBridgingRelearnShutdownThreshold OBJECT-TYPE
   SYNTAX      Integer32
   MAX-ACCESS  read-write
   STATUS      current
   DESCRIPTION
      "Path: tunnels.editConf.vxLanTunnels.bridging.relearn.shutdownThreshold"
   ::= {er1645v2TvTmplVxTEntry 456656896}

er1645v2TvTmplVxTBridgingRelearnShutdownTime OBJECT-TYPE
   SYNTAX      TimeTicks
   MAX-ACCESS  read-write
   STATUS      current
   DESCRIPTION
      "Path: tunnels.editConf.vxLanTunnels.bridging.relearn.shutdownTime

       Time in centi-second."
   ::= {er1645v2TvTmplVxTEntry 456657920}

er1645v2TvTmplVxTBridgingRelearnLoopDetection OBJECT-TYPE
   SYNTAX      INTEGER
               {
               disabled (0),
               passive (1),
               active (2)
               }
   MAX-ACCESS  read-write
   STATUS      current
   DESCRIPTION
      "Path: tunnels.editConf.vxLanTunnels.bridging.relearn.loopDetection

       Possibilities:
               disabled   (0)
               passive   (1)
               active   (2)"
   ::= {er1645v2TvTmplVxTEntry 456658944}

er1645v2TvTmplVxTBridgingRelearnLoopDetectionInterval OBJECT-TYPE
   SYNTAX      TimeTicks
   MAX-ACCESS  read-write
   STATUS      current
   DESCRIPTION
      "Path: tunnels.editConf.vxLanTunnels.bridging.relearn.loopDetectionInterval

       Time in centi-second."
   ::= {er1645v2TvTmplVxTEntry 456659968}

er1645v2TvTmplVxTBridgingVlanMemberShip OBJECT-TYPE
   SYNTAX      INTEGER
               {
               all (0),
               none (1),
               grouped (2)
               }
   MAX-ACCESS  read-write
   STATUS      current
   DESCRIPTION
      "Path: tunnels.editConf.vxLanTunnels.bridging.vlanMemberShip

       Possibilities:
               all   (0)
               none   (1)
               grouped   (2)"
   ::= {er1645v2TvTmplVxTEntry 457965568}

er1645v2TvTmplVxTBridgingVlTUntaggedAction OBJECT-TYPE
   SYNTAX      INTEGER
               {
               discard (0),
               accept (1),
               tag (2)
               }
   MAX-ACCESS  read-write
   STATUS      current
   DESCRIPTION
      "Path: tunnels.editConf.vxLanTunnels.bridging.vlanTagging.untagged.action

       Possibilities:
               discard   (0)
               accept   (1)
               tag   (2)"
   ::= {er1645v2TvTmplVxTEntry 459055104}

er1645v2TvTmplVxTBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.vxLanTunnels.bridging.vlanTagging.untagged.tagInfo.tpid

       Possibilities:
               dot1Q   (33024)
               dot1ad   (34984)
               0x9100   (37120)
               0x9200   (37376)
               0x9300   (37632)"
   ::= {er1645v2TvTmplVxTEntry 459059712}

er1645v2TvTmplVxTBridgingVlTUntaggedTagInfoVid OBJECT-TYPE
   SYNTAX      Integer32
   MAX-ACCESS  read-write
   STATUS      current
   DESCRIPTION
      "Path: tunnels.editConf.vxLanTunnels.bridging.vlanTagging.untagged.tagInfo.vid"
   ::= {er1645v2TvTmplVxTEntry 459060224}

er1645v2TvTmplVxTBridgingVlTUnknownVlansAction OBJECT-TYPE
   SYNTAX      INTEGER
               {
               discard (0),
               accept (1),
               tag (2)
               }
   MAX-ACCESS  read-write
   STATUS      current
   DESCRIPTION
      "Path: tunnels.editConf.vxLanTunnels.bridging.vlanTagging.unknownVlans.action

       Possibilities:
               discard   (0)
               accept   (1)
               tag   (2)"
   ::= {er1645v2TvTmplVxTEntry 459120640}

er1645v2TvTmplVxTBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.vxLanTunnels.bridging.vlanTagging.unknownVlans.tagInfo.tpid

       Possibilities:
               dot1Q   (33024)
               dot1ad   (34984)
               0x9100   (37120)
               0x9200   (37376)
               0x9300   (37632)"
   ::= {er1645v2TvTmplVxTEntry 459125248}

er1645v2TvTmplVxTBridgingVlTUnknownVlansTagInfoVid OBJECT-TYPE
   SYNTAX      Integer32
   MAX-ACCESS  read-write
   STATUS      current
   DESCRIPTION
      "Path: tunnels.editConf.vxLanTunnels.bridging.vlanTagging.unknownVlans.tagInfo.vid"
   ::= {er1645v2TvTmplVxTEntry 459125760}

er1645v2TvTmplVxTBridgingDot1adType OBJECT-TYPE
   SYNTAX      INTEGER
               {
               slOPTg (0),
               cPort (4),
               sPort (1),
               nni (2)
               }
   MAX-ACCESS  read-write
   STATUS      current
   DESCRIPTION
      "Path: tunnels.editConf.vxLanTunnels.bridging.dot1ad.type

       Possibilities:
               <OPT>   (0)
               cPort   (4)
               sPort   (1)
               nni   (2)"
   ::= {er1645v2TvTmplVxTEntry 460850176}

er1645v2TvTmplVxTBridgingPriority OBJECT-TYPE
   SYNTAX      Integer32
   MAX-ACCESS  read-write
   STATUS      current
   DESCRIPTION
      "Path: tunnels.editConf.vxLanTunnels.bridging.priority"
   ::= {er1645v2TvTmplVxTEntry 453509120}

er1645v2TvTmplVxTBridgingPathCost OBJECT-TYPE
   SYNTAX      Integer32
   MAX-ACCESS  read-write
   STATUS      current
   DESCRIPTION
      "Path: tunnels.editConf.vxLanTunnels.bridging.pathCost"
   ::= {er1645v2TvTmplVxTEntry 453771264}

er1645v2TvTmplVxTBridgingInternalPathCost OBJECT-TYPE
   SYNTAX      Integer32
   MAX-ACCESS  read-write
   STATUS      current
   DESCRIPTION
      "Path: tunnels.editConf.vxLanTunnels.bridging.internalPathCost"
   ::= {er1645v2TvTmplVxTEntry 457703424}

er1645v2TvTmplVxTBridgingTCD OBJECT-TYPE
   SYNTAX      INTEGER
               {
               disabled (0),
               enabled (1)
               }
   MAX-ACCESS  read-write
   STATUS      current
   DESCRIPTION
      "Path: tunnels.editConf.vxLanTunnels.bridging.topologyChangeDetection

       Possibilities:
               disabled   (0)
               enabled   (1)"
   ::= {er1645v2TvTmplVxTEntry 454033408}

er1645v2TvTmplVxTBridgingRestrictedRole OBJECT-TYPE
   SYNTAX      INTEGER
               {
               disabled (0),
               enabled (1)
               }
   MAX-ACCESS  read-write
   STATUS      current
   DESCRIPTION
      "Path: tunnels.editConf.vxLanTunnels.bridging.restrictedRole

       Possibilities:
               disabled   (0)
               enabled   (1)"
   ::= {er1645v2TvTmplVxTEntry 458227712}

er1645v2TvTmplVxTBridgingAdminEdge OBJECT-TYPE
   SYNTAX      INTEGER
               {
               disabled (0),
               enabled (1)
               }
   MAX-ACCESS  read-write
   STATUS      current
   DESCRIPTION
      "Path: tunnels.editConf.vxLanTunnels.bridging.adminEdge

       Possibilities:
               disabled   (0)
               enabled   (1)"
   ::= {er1645v2TvTmplVxTEntry 457179136}

er1645v2TvTmplVxTBridgingOamMacDeviceMac OBJECT-TYPE
   SYNTAX      DisplayString
   MAX-ACCESS  read-write
   STATUS      current
   DESCRIPTION
      "Path: tunnels.editConf.vxLanTunnels.bridging.ethOam.macAddress.deviceMac"
   ::= {er1645v2TvTmplVxTEntry 458506496}

er1645v2TvTmplVxTBridgingOamMacUserMac OBJECT-TYPE
   SYNTAX      OCTET STRING
   MAX-ACCESS  read-write
   STATUS      current
   DESCRIPTION
      "Path: tunnels.editConf.vxLanTunnels.bridging.ethOam.macAddress.userMac

       MAC address."
   ::= {er1645v2TvTmplVxTEntry 458506368}

er1645v2TvTmplVxTBridgingOamMacBridgeMac OBJECT-TYPE
   SYNTAX      DisplayString
   MAX-ACCESS  read-write
   STATUS      current
   DESCRIPTION
      "Path: tunnels.editConf.vxLanTunnels.bridging.ethOam.macAddress.bridgeMac"
   ::= {er1645v2TvTmplVxTEntry 458506432}

er1645v2TvTmplVxTBridgingMgmtInline OBJECT-TYPE
   SYNTAX      INTEGER
               {
               disabled (0),
               enabled (1)
               }
   MAX-ACCESS  read-write
   STATUS      current
   DESCRIPTION
      "Path: tunnels.editConf.vxLanTunnels.bridging.mgmtInline

       Possibilities:
               disabled   (0)
               enabled   (1)"
   ::= {er1645v2TvTmplVxTEntry 458752000}

er1645v2TvTmplVxTBridgingL2ptMode OBJECT-TYPE
   SYNTAX      INTEGER
               {
               disabled (0),
               enabled (1)
               }
   MAX-ACCESS  read-write
   STATUS      current
   DESCRIPTION
      "Path: tunnels.editConf.vxLanTunnels.bridging.l2ProtTunnel.mode

       Possibilities:
               disabled   (0)
               enabled   (1)"
   ::= {er1645v2TvTmplVxTEntry 459292672}

er1645v2TvTmplVxTBridgingL2ptProtocols OBJECT-TYPE
   SYNTAX      Integer32
   MAX-ACCESS  read-write
   STATUS      current
   DESCRIPTION
      "Path: tunnels.editConf.vxLanTunnels.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2TvTmplVxTEntry 459309056}

er1645v2TvTmplVxTBridgingL2ptDestMac OBJECT-TYPE
   SYNTAX      OCTET STRING
   MAX-ACCESS  read-write
   STATUS      current
   DESCRIPTION
      "Path: tunnels.editConf.vxLanTunnels.bridging.l2ProtTunnel.destinationMac

       MAC address."
   ::= {er1645v2TvTmplVxTEntry 459325440}

er1645v2TvTmplVxTBridgingL2ptCos OBJECT-TYPE
   SYNTAX      INTEGER
               {
               unchanged (255)
               }
   MAX-ACCESS  read-write
   STATUS      current
   DESCRIPTION
      "Path: tunnels.editConf.vxLanTunnels.bridging.l2ProtTunnel.cos

       Possibilities:
               unchanged   (255)"
   ::= {er1645v2TvTmplVxTEntry 459341824}

er1645v2TvTmplVxTBridgingL2ptDropThrStp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.stp

       unit name = packets/sec

       Possibilities:
               unlimited   (0)"
   ::= {er1645v2TvTmplVxTEntry 459358272}

er1645v2TvTmplVxTBridgingL2ptDropThrLldp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.lldp

       unit name = packets/sec

       Possibilities:
               unlimited   (0)"
   ::= {er1645v2TvTmplVxTEntry 459358336}

er1645v2TvTmplVxTBridgingL2ptDropThrOam OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.oam

       unit name = packets/sec

       Possibilities:
               unlimited   (0)"
   ::= {er1645v2TvTmplVxTEntry 459358400}

er1645v2TvTmplVxTBridgingL2ptDropThrCdp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.cdp

       unit name = packets/sec

       Possibilities:
               unlimited   (0)"
   ::= {er1645v2TvTmplVxTEntry 459358464}

er1645v2TvTmplVxTBridgingL2ptDropThrVtp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.vtp

       unit name = packets/sec

       Possibilities:
               unlimited   (0)"
   ::= {er1645v2TvTmplVxTEntry 459358528}

er1645v2TvTmplVxTBridgingL2ptDropThrLacp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.lacp

       unit name = packets/sec

       Possibilities:
               unlimited   (0)"
   ::= {er1645v2TvTmplVxTEntry 459358592}

er1645v2TvTmplVxTBridgingL2ptDropThrEfmOam OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.efmOam

       unit name = packets/sec

       Possibilities:
               unlimited   (0)"
   ::= {er1645v2TvTmplVxTEntry 459358656}

er1645v2TvTmplVxTBridgingL2ptDropThrPvst OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.pvst

       unit name = packets/sec

       Possibilities:
               unlimited   (0)"
   ::= {er1645v2TvTmplVxTEntry 459358720}

er1645v2TvTmplVxTBridgingL2ptDropThrMmrp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.mmrp

       unit name = packets/sec

       Possibilities:
               unlimited   (0)"
   ::= {er1645v2TvTmplVxTEntry 459358784}

er1645v2TvTmplVxTBridgingL2ptDropThrMvrp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.mvrp

       unit name = packets/sec

       Possibilities:
               unlimited   (0)"
   ::= {er1645v2TvTmplVxTEntry 459358848}

er1645v2TvTmplVxTBridgingL2ptDropThrGvrp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.gvrp

       unit name = packets/sec

       Possibilities:
               unlimited   (0)"
   ::= {er1645v2TvTmplVxTEntry 459358912}

er1645v2TvTmplVxTBridgingL2ptDropThrGmrp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.gmrp

       unit name = packets/sec

       Possibilities:
               unlimited   (0)"
   ::= {er1645v2TvTmplVxTEntry 459358976}

er1645v2TvTmplVxTBridgingL2ptDropThrDtp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.dtp

       unit name = packets/sec

       Possibilities:
               unlimited   (0)"
   ::= {er1645v2TvTmplVxTEntry 459359040}

er1645v2TvTmplVxTBridgingL2ptDropThrPagp OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.pagp

       unit name = packets/sec

       Possibilities:
               unlimited   (0)"
   ::= {er1645v2TvTmplVxTEntry 459359104}

er1645v2TvTmplVxTBridgingL2ptDropThrUdld OBJECT-TYPE
   SYNTAX      INTEGER
               {
               unlimited (0)
               }
   UNITS       "packets/sec"
   MAX-ACCESS  read-write
   STATUS      current
   DESCRIPTION
      "Path: tunnels.editConf.vxLanTunnels.bridging.l2ProtTunnel.dropThresholds.udld

       unit name = packets/sec

       Possibilities:
               unlimited   (0)"
   ::= {er1645v2TvTmplVxTEntry 459359168}

er1645v2TvTmplVxTVxLanVni OBJECT-TYPE
   SYNTAX      Integer32
   MAX-ACCESS  read-write
   STATUS      current
   DESCRIPTION
      "Path: tunnels.editConf.vxLanTunnels.vxLan.vni"
   ::= {er1645v2TvTmplVxTEntry 240517120}

er1645v2TvTmplVxTVxLanRemoteMulticast OBJECT-TYPE
   SYNTAX      IpAddress
   MAX-ACCESS  read-write
   STATUS      current
   DESCRIPTION
      "Path: tunnels.editConf.vxLanTunnels.vxLan.remote.multicast"
   ::= {er1645v2TvTmplVxTEntry 240582912}

er1645v2TvTmplVxTVxLanRemoteUnicast OBJECT-TYPE
   SYNTAX      IpAddress
   MAX-ACCESS  read-write
   STATUS      current
   DESCRIPTION
      "Path: tunnels.editConf.vxLanTunnels.vxLan.remote.unicast"
   ::= {er1645v2TvTmplVxTEntry 240583168}

er1645v2TvTmplVxTVxLanLocalInterface OBJECT-TYPE
   SYNTAX      DisplayString
   MAX-ACCESS  read-write
   STATUS      current
   DESCRIPTION
      "Path: tunnels.editConf.vxLanTunnels.vxLan.localInterface"
   ::= {er1645v2TvTmplVxTEntry 240648192}

er1645v2TvTmplVxTBridgingVlTVlans OBJECT-TYPE
   SYNTAX      SEQUENCE OF Er1645v2TvTmplVxTBridgingVlTVlansEntry
   MAX-ACCESS  not-accessible
   STATUS      current
   DESCRIPTION
      ""
   ::= {er1645v2TvTmplVxT 459079680}

er1645v2TvTmplVxTBridgingVlTVlansEntry OBJECT-TYPE
   SYNTAX      Er1645v2TvTmplVxTBridgingVlTVlansEntry
   MAX-ACCESS  not-accessible
   STATUS      current
   DESCRIPTION
      ""
   INDEX      { er1645v2TvTmplVxTTableIx,
                er1645v2TvTmplVxTBridgingVlTVlansTableIx }
   ::= {er1645v2TvTmplVxTBridgingVlTVlans 1}

Er1645v2TvTmplVxTBridgingVlTVlansEntry ::=
   SEQUENCE
      {
      er1645v2TvTmplVxTBridgingVlTVlansActions
         VariableLengthTableActions,
      er1645v2TvTmplVxTBridgingVlTVlansTableIx
         TableIndex,
      er1645v2TvTmplVxTBridgingVlTVlansVid
         Integer32,
      er1645v2TvTmplVxTBridgingVlTVlansEndVid
         Integer32,
      er1645v2TvTmplVxTBridgingVlTVlansAction
         INTEGER,
      er1645v2TvTmplVxTBridgingVlTVlansTagInfoTpid
         INTEGER,
      er1645v2TvTmplVxTBridgingVlTVlansTagInfoVid
         Integer32
      }

er1645v2TvTmplVxTBridgingVlTVlansActions OBJECT-TYPE
   SYNTAX      VariableLengthTableActions
   MAX-ACCESS  read-write
   STATUS      current
   DESCRIPTION
      "By way of this field, some manipulations
       on this table may be performed."
   ::= {er1645v2TvTmplVxTBridgingVlTVlansEntry 2}

er1645v2TvTmplVxTBridgingVlTVlansTableIx OBJECT-TYPE
   SYNTAX      TableIndex
   MAX-ACCESS  not-accessible
   STATUS      current
   DESCRIPTION
      ""
   ::= {er1645v2TvTmplVxTBridgingVlTVlansEntry 11}

er1645v2TvTmplVxTBridgingVlTVlansVid OBJECT-TYPE
   SYNTAX      Integer32
   MAX-ACCESS  read-write
   STATUS      current
   DESCRIPTION
      "Path: tunnels.editConf.vxLanTunnels.bridging.vlanTagging.vlans.vid"
   ::= {er1645v2TvTmplVxTBridgingVlTVlansEntry 536870912}

er1645v2TvTmplVxTBridgingVlTVlansEndVid OBJECT-TYPE
   SYNTAX      Integer32
   MAX-ACCESS  read-write
   STATUS      current
   DESCRIPTION
      "Path: tunnels.editConf.vxLanTunnels.bridging.vlanTagging.vlans.endVid"
   ::= {er1645v2TvTmplVxTBridgingVlTVlansEntry 2147483648}

er1645v2TvTmplVxTBridgingVlTVlansAction OBJECT-TYPE
   SYNTAX      INTEGER
               {
               discard (0),
               accept (1),
               tag (2)
               }
   MAX-ACCESS  read-write
   STATUS      current
   DESCRIPTION
      "Path: tunnels.editConf.vxLanTunnels.bridging.vlanTagging.vlans.action

       Possibilities:
               discard   (0)
               accept   (1)
               tag   (2)"
   ::= {er1645v2TvTmplVxTBridgingVlTVlansEntry 1073741824}

er1645v2TvTmplVxTBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: tunnels.editConf.vxLanTunnels.bridging.vlanTagging.vlans.tagInfo.tpid

       Possibilities:
               dot1Q   (33024)
               dot1ad   (34984)
               0x9100   (37120)
               0x9200   (37376)
               0x9300   (37632)"
   ::= {er1645v2TvTmplVxTBridgingVlTVlansEntry 1677721600}

er1645v2TvTmplVxTBridgingVlTVlansTagInfoVid OBJECT-TYPE
   SYNTAX      Integer32
   MAX-ACCESS  read-write
   STATUS      current
   DESCRIPTION
      "Path: tunnels.editConf.vxLanTunnels.bridging.vlanTagging.vlans.tagInfo.vid"
   ::= {er1645v2TvTmplVxTBridgingVlTVlansEntry 1744830464}


er1645v2TvTmplAlarmMask OBJECT-TYPE
   SYNTAX      Integer32
   MAX-ACCESS  read-write
   STATUS      current
   DESCRIPTION
      "Path: tunnels.editConf.alarmMask
       Info: tunnelAlarmMask

       Bit meanings:
               bit 1 = l2tpDown,
               bit 2 = ipsecL2tpDown,
               bit 3 = greDown,
               bit 4 = ipsecGreDown"
   ::= {er1645v2TvTmpl 50}


er1645v2TvTmplAlarmLev OBJECT IDENTIFIER ::= {er1645v2TvTmpl 51}

er1645v2TvTmplAlarmLevSSC OBJECT IDENTIFIER ::= {er1645v2TvTmplAlarmLev 1}

er1645v2TvTmplAlarmLevEntry OBJECT IDENTIFIER ::= {er1645v2TvTmplAlarmLevSSC 1}

er1645v2TvTmplAlarmLevL2tpDown OBJECT-TYPE
   SYNTAX      Integer32
   MAX-ACCESS  read-write
   STATUS      current
   DESCRIPTION
      "Path: tunnels.editConf.alarmLevel.l2tpDown"
   ::= {er1645v2TvTmplAlarmLevEntry 33554432}

er1645v2TvTmplAlarmLevIpsecL2tpDown OBJECT-TYPE
   SYNTAX      Integer32
   MAX-ACCESS  read-write
   STATUS      current
   DESCRIPTION
      "Path: tunnels.editConf.alarmLevel.ipsecL2tpDown"
   ::= {er1645v2TvTmplAlarmLevEntry 50331648}

er1645v2TvTmplAlarmLevGreDown OBJECT-TYPE
   SYNTAX      Integer32
   MAX-ACCESS  read-write
   STATUS      current
   DESCRIPTION
      "Path: tunnels.editConf.alarmLevel.greDown"
   ::= {er1645v2TvTmplAlarmLevEntry 67108864}

er1645v2TvTmplAlarmLevIpsecGreDown OBJECT-TYPE
   SYNTAX      Integer32
   MAX-ACCESS  read-write
   STATUS      current
   DESCRIPTION
      "Path: tunnels.editConf.alarmLevel.ipsecGreDown"
   ::= {er1645v2TvTmplAlarmLevEntry 83886080}



sr1645v2TvTmpl OBJECT IDENTIFIER ::= {r1645v2TvTmpl 14}


sr1645v2TvTmplDescr OBJECT-TYPE
   SYNTAX      DisplayString
   MAX-ACCESS  read-only
   STATUS      current
   DESCRIPTION
      "Path: tunnels.status.ifDescr
       Info: ifDescr"
   ::= {sr1645v2TvTmpl 101}


sr1645v2TvTmplType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: tunnels.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2TvTmpl 102}


sr1645v2TvTmplOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.ifOperStatus
       Info: ifOperStatus

       Possibilities:
               up   (1)
               down   (2)
               testing   (3)
               unknown   (4)
               dormant   (5)
               notPresent   (6)
               lowerLayerDown   (7)"
   ::= {sr1645v2TvTmpl 107}


sr1645v2TvTmplSnmpIndex OBJECT-TYPE
   SYNTAX      Integer32
   MAX-ACCESS  read-only
   STATUS      current
   DESCRIPTION
      "Path: tunnels.status.snmpIndex
       Info: SNMP index assigned to this object"
   ::= {sr1645v2TvTmpl 269}


sr1645v2TvTmplStati OBJECT IDENTIFIER ::= {sr1645v2TvTmpl 5}

sr1645v2TvTmplStatiSSCTable OBJECT-TYPE
   SYNTAX      SEQUENCE OF Sr1645v2TvTmplStatiEntry
   MAX-ACCESS  not-accessible
   STATUS      current
   DESCRIPTION
      ""
   ::= {sr1645v2TvTmplStati 1}

sr1645v2TvTmplStatiEntry OBJECT-TYPE
   SYNTAX      Sr1645v2TvTmplStatiEntry
   MAX-ACCESS  not-accessible
   STATUS      current
   DESCRIPTION
      ""
   INDEX      { sr1645v2TvTmplStatiTableIx }
   ::= {sr1645v2TvTmplStatiSSCTable 1}

Sr1645v2TvTmplStatiEntry ::=
   SEQUENCE
      {
      sr1645v2TvTmplStatiTableIx
         TableIndex,
      sr1645v2TvTmplStatiName
         DisplayString,
      sr1645v2TvTmplStatiMode
         INTEGER,
      sr1645v2TvTmplStatiIfOperStatus
         INTEGER,
      sr1645v2TvTmplStatiIfLastChange
         TimeTicks,
      sr1645v2TvTmplStatiIfLastChangeDate
         DisplayString,
      sr1645v2TvTmplStatiIpVrfRouter
         DisplayString,
      sr1645v2TvTmplStatiIpAddress
         IpAddress,
      sr1645v2TvTmplStatiIpNetMask
         IpAddress,
      sr1645v2TvTmplStatiIpRemote
         IpAddress,
      sr1645v2TvTmplStatiBridgingStatus
         INTEGER,
      sr1645v2TvTmplStatiBridgingSpanningTreePortRole
         INTEGER,
      sr1645v2TvTmplStatiBridgingSpanningTreePortId
         Integer32,
      sr1645v2TvTmplStatiBridgingSpanningTreePpCostExtPathCost
         Integer32,
      sr1645v2TvTmplStatiBridgingSpanningTreePpCostIntPathCost
         Integer32,
      sr1645v2TvTmplStatiBridgingSpanningTreeExtRpCost
         Integer32,
      sr1645v2TvTmplStatiBridgingSpanningTreeIntRpCost
         Integer32,
      sr1645v2TvTmplStatiBridgingSpanningTreeDesBrIdPriority
         Integer32,
      sr1645v2TvTmplStatiBridgingSpanningTreeDesBrIdMacAddress
         OCTET STRING,
      sr1645v2TvTmplStatiBridgingSpanningTreeDesPrtId
         Integer32,
      sr1645v2TvTmplStatiBridgingSpanningTreeDesInt
         INTEGER,
      sr1645v2TvTmplStatiBridgingSpanningTreeEdgeDetection
         INTEGER,
      sr1645v2TvTmplStatiL2tpLocalIpAddress
         IpAddress,
      sr1645v2TvTmplStatiL2tpRemAddr
         IpAddress,
      sr1645v2TvTmplStatiL2tpSendingSeqNr
         Integer32,
      sr1645v2TvTmplStatiL2tpReceivingSeqNr
         Integer32,
      sr1645v2TvTmplStatiL2tpL2tpType
         INTEGER,
      sr1645v2TvTmplStatiL2tpControlState
         INTEGER,
      sr1645v2TvTmplStatiL2tpCallState
         INTEGER,
      sr1645v2TvTmplStatiL2tpDeliveryState
         INTEGER,
      sr1645v2TvTmplStatiL2tpAuthenState
         INTEGER,
      sr1645v2TvTmplStatiL2tpIke
         INTEGER,
      sr1645v2TvTmplStatiPppLcpState
         INTEGER,
      sr1645v2TvTmplStatiPppIpcpState
         INTEGER,
      sr1645v2TvTmplStatiPppBcpState
         INTEGER,
      sr1645v2TvTmplStatiPppMyAutSt
         INTEGER,
      sr1645v2TvTmplStatiPppMyAutUsr
         DisplayString,
      sr1645v2TvTmplStatiPppHisAutSt
         INTEGER
      }

sr1645v2TvTmplStatiTableIx OBJECT-TYPE
   SYNTAX      TableIndex
   MAX-ACCESS  not-accessible
   STATUS      current
   DESCRIPTION
      ""
   ::= {sr1645v2TvTmplStatiEntry 11}

sr1645v2TvTmplStatiName OBJECT-TYPE
   SYNTAX      DisplayString
   MAX-ACCESS  read-only
   STATUS      current
   DESCRIPTION
      "Path: tunnels.status.ipsecL2tpTunnels.name"
   ::= {sr1645v2TvTmplStatiEntry 16777216}

sr1645v2TvTmplStatiMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.ipsecL2tpTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TvTmplStatiEntry 335544320}

sr1645v2TvTmplStatiIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.ipsecL2tpTunnels.ifOperStatus

       Possibilities:
               up   (1)
               down   (2)
               testing   (3)
               unknown   (4)
               dormant   (5)
               notPresent   (6)
               lowerLayerDown   (7)"
   ::= {sr1645v2TvTmplStatiEntry 1795162112}

sr1645v2TvTmplStatiIfLastChange OBJECT-TYPE
   SYNTAX      TimeTicks
   MAX-ACCESS  read-only
   STATUS      current
   DESCRIPTION
      "Path: tunnels.status.ipsecL2tpTunnels.ifLastChange

       Time in centi-second."
   ::= {sr1645v2TvTmplStatiEntry 1811939328}

sr1645v2TvTmplStatiIfLastChangeDate OBJECT-TYPE
   SYNTAX      DisplayString
   MAX-ACCESS  read-only
   STATUS      current
   DESCRIPTION
      "Path: tunnels.status.ipsecL2tpTunnels.ifLastChangeDate"
   ::= {sr1645v2TvTmplStatiEntry 3070230528}

sr1645v2TvTmplStatiIpVrfRouter OBJECT-TYPE
   SYNTAX      DisplayString
   MAX-ACCESS  read-only
   STATUS      current
   DESCRIPTION
      "Path: tunnels.status.ipsecL2tpTunnels.ip.vrfRouter"
   ::= {sr1645v2TvTmplStatiEntry 50397184}

sr1645v2TvTmplStatiIpAddress OBJECT-TYPE
   SYNTAX      IpAddress
   MAX-ACCESS  read-only
   STATUS      current
   DESCRIPTION
      "Path: tunnels.status.ipsecL2tpTunnels.ip.address"
   ::= {sr1645v2TvTmplStatiEntry 51380224}

sr1645v2TvTmplStatiIpNetMask OBJECT-TYPE
   SYNTAX      IpAddress
   MAX-ACCESS  read-only
   STATUS      current
   DESCRIPTION
      "Path: tunnels.status.ipsecL2tpTunnels.ip.netMask"
   ::= {sr1645v2TvTmplStatiEntry 51445760}

sr1645v2TvTmplStatiIpRemote OBJECT-TYPE
   SYNTAX      IpAddress
   MAX-ACCESS  read-only
   STATUS      current
   DESCRIPTION
      "Path: tunnels.status.ipsecL2tpTunnels.ip.remote"
   ::= {sr1645v2TvTmplStatiEntry 51511296}

sr1645v2TvTmplStatiBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.ipsecL2tpTunnels.bridging.status

       Possibilities:
               disabled   (0)
               discarding   (1)
               learning   (2)
               forwarding   (3)
               backupBlockedIntfDown   (256)
               backupBlockedIntfUp   (259)
               shutdown   (255)"
   ::= {sr1645v2TvTmplStatiEntry 453050368}

sr1645v2TvTmplStatiBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.ipsecL2tpTunnels.bridging.spanningTree.portRole

       Possibilities:
               none   (0)
               root   (1)
               designated   (2)
               alternate   (3)
               backup   (4)
               disabled   (5)
               master   (6)"
   ::= {sr1645v2TvTmplStatiEntry 453116160}

sr1645v2TvTmplStatiBridgingSpanningTreePortId OBJECT-TYPE
   SYNTAX      Integer32
   MAX-ACCESS  read-only
   STATUS      current
   DESCRIPTION
      "Path: tunnels.status.ipsecL2tpTunnels.bridging.spanningTree.portId"
   ::= {sr1645v2TvTmplStatiEntry 453116416}

sr1645v2TvTmplStatiBridgingSpanningTreePpCostExtPathCost OBJECT-TYPE
   SYNTAX      Integer32
   MAX-ACCESS  read-only
   STATUS      current
   DESCRIPTION
      "Path: tunnels.status.ipsecL2tpTunnels.bridging.spanningTree.portPathCosts.extPathCost"
   ::= {sr1645v2TvTmplStatiEntry 453116673}

sr1645v2TvTmplStatiBridgingSpanningTreePpCostIntPathCost OBJECT-TYPE
   SYNTAX      Integer32
   MAX-ACCESS  read-only
   STATUS      current
   DESCRIPTION
      "Path: tunnels.status.ipsecL2tpTunnels.bridging.spanningTree.portPathCosts.intPathCost"
   ::= {sr1645v2TvTmplStatiEntry 453116674}

sr1645v2TvTmplStatiBridgingSpanningTreeExtRpCost OBJECT-TYPE
   SYNTAX      Integer32
   MAX-ACCESS  read-only
   STATUS      current
   DESCRIPTION
      "Path: tunnels.status.ipsecL2tpTunnels.bridging.spanningTree.extRootPathCost"
   ::= {sr1645v2TvTmplStatiEntry 453116928}

sr1645v2TvTmplStatiBridgingSpanningTreeIntRpCost OBJECT-TYPE
   SYNTAX      Integer32
   MAX-ACCESS  read-only
   STATUS      current
   DESCRIPTION
      "Path: tunnels.status.ipsecL2tpTunnels.bridging.spanningTree.intRootPathCost"
   ::= {sr1645v2TvTmplStatiEntry 453117184}

sr1645v2TvTmplStatiBridgingSpanningTreeDesBrIdPriority OBJECT-TYPE
   SYNTAX      Integer32
   MAX-ACCESS  read-only
   STATUS      current
   DESCRIPTION
      "Path: tunnels.status.ipsecL2tpTunnels.bridging.spanningTree.designatedBridgeId.priority"
   ::= {sr1645v2TvTmplStatiEntry 453117441}

sr1645v2TvTmplStatiBridgingSpanningTreeDesBrIdMacAddress OBJECT-TYPE
   SYNTAX      OCTET STRING
   MAX-ACCESS  read-only
   STATUS      current
   DESCRIPTION
      "Path: tunnels.status.ipsecL2tpTunnels.bridging.spanningTree.designatedBridgeId.macAddress

       MAC address."
   ::= {sr1645v2TvTmplStatiEntry 453117442}

sr1645v2TvTmplStatiBridgingSpanningTreeDesPrtId OBJECT-TYPE
   SYNTAX      Integer32
   MAX-ACCESS  read-only
   STATUS      current
   DESCRIPTION
      "Path: tunnels.status.ipsecL2tpTunnels.bridging.spanningTree.designatedPortId"
   ::= {sr1645v2TvTmplStatiEntry 453117696}

sr1645v2TvTmplStatiBridgingSpanningTreeDesInt OBJECT-TYPE
   SYNTAX      INTEGER
               {
               no (0),
               yes (1)
               }
   MAX-ACCESS  read-only
   STATUS      current
   DESCRIPTION
      "Path: tunnels.status.ipsecL2tpTunnels.bridging.spanningTree.designatedOrInternal

       Possibilities:
               no   (0)
               yes   (1)"
   ::= {sr1645v2TvTmplStatiEntry 453117952}

sr1645v2TvTmplStatiBridgingSpanningTreeEdgeDetection OBJECT-TYPE
   SYNTAX      INTEGER
               {
               none (0),
               edge (1),
               notEdge (2)
               }
   MAX-ACCESS  read-only
   STATUS      current
   DESCRIPTION
      "Path: tunnels.status.ipsecL2tpTunnels.bridging.spanningTree.edgeDetection

       Possibilities:
               none   (0)
               edge   (1)
               notEdge   (2)"
   ::= {sr1645v2TvTmplStatiEntry 453118208}

sr1645v2TvTmplStatiL2tpLocalIpAddress OBJECT-TYPE
   SYNTAX      IpAddress
   MAX-ACCESS  read-only
   STATUS      current
   DESCRIPTION
      "Path: tunnels.status.ipsecL2tpTunnels.l2tp.localIpAddress"
   ::= {sr1645v2TvTmplStatiEntry 302579712}

sr1645v2TvTmplStatiL2tpRemAddr OBJECT-TYPE
   SYNTAX      IpAddress
   MAX-ACCESS  read-only
   STATUS      current
   DESCRIPTION
      "Path: tunnels.status.ipsecL2tpTunnels.l2tp.remoteIpAddress"
   ::= {sr1645v2TvTmplStatiEntry 302645248}

sr1645v2TvTmplStatiL2tpSendingSeqNr OBJECT-TYPE
   SYNTAX      Integer32
   MAX-ACCESS  read-only
   STATUS      current
   DESCRIPTION
      "Path: tunnels.status.ipsecL2tpTunnels.l2tp.sendingSeqNr"
   ::= {sr1645v2TvTmplStatiEntry 302055424}

sr1645v2TvTmplStatiL2tpReceivingSeqNr OBJECT-TYPE
   SYNTAX      Integer32
   MAX-ACCESS  read-only
   STATUS      current
   DESCRIPTION
      "Path: tunnels.status.ipsecL2tpTunnels.l2tp.receivingSeqNr"
   ::= {sr1645v2TvTmplStatiEntry 302120960}

sr1645v2TvTmplStatiL2tpL2tpType OBJECT-TYPE
   SYNTAX      INTEGER
               {
               lac (1),
               lns (2),
               auto (3)
               }
   MAX-ACCESS  read-only
   STATUS      current
   DESCRIPTION
      "Path: tunnels.status.ipsecL2tpTunnels.l2tp.l2tpType

       Possibilities:
               lac   (1)
               lns   (2)
               auto   (3)"
   ::= {sr1645v2TvTmplStatiEntry 302186496}

sr1645v2TvTmplStatiL2tpControlState OBJECT-TYPE
   SYNTAX      INTEGER
               {
               idle (1),
               waitCtlReply (2),
               waitCtlConn (3),
               established (4)
               }
   MAX-ACCESS  read-only
   STATUS      current
   DESCRIPTION
      "Path: tunnels.status.ipsecL2tpTunnels.l2tp.controlState

       Possibilities:
               idle   (1)
               waitCtlReply   (2)
               waitCtlConn   (3)
               established   (4)"
   ::= {sr1645v2TvTmplStatiEntry 302252032}

sr1645v2TvTmplStatiL2tpCallState OBJECT-TYPE
   SYNTAX      INTEGER
               {
               idle (1),
               waitTunnel (2),
               waitReply (3),
               waitConnect (4),
               established (5)
               }
   MAX-ACCESS  read-only
   STATUS      current
   DESCRIPTION
      "Path: tunnels.status.ipsecL2tpTunnels.l2tp.callState

       Possibilities:
               idle   (1)
               waitTunnel   (2)
               waitReply   (3)
               waitConnect   (4)
               established   (5)"
   ::= {sr1645v2TvTmplStatiEntry 302317568}

sr1645v2TvTmplStatiL2tpDeliveryState OBJECT-TYPE
   SYNTAX      INTEGER
               {
               idle (1),
               operating (2),
               done (3)
               }
   MAX-ACCESS  read-only
   STATUS      current
   DESCRIPTION
      "Path: tunnels.status.ipsecL2tpTunnels.l2tp.deliveryState

       Possibilities:
               idle   (1)
               operating   (2)
               done   (3)"
   ::= {sr1645v2TvTmplStatiEntry 302383104}

sr1645v2TvTmplStatiL2tpAuthenState OBJECT-TYPE
   SYNTAX      INTEGER
               {
               noAuthentication (0),
               authenFailure (1),
               authenSuccessful (2)
               }
   MAX-ACCESS  read-only
   STATUS      current
   DESCRIPTION
      "Path: tunnels.status.ipsecL2tpTunnels.l2tp.authenState

       Possibilities:
               noAuthentication   (0)
               authenFailure   (1)
               authenSuccessful   (2)"
   ::= {sr1645v2TvTmplStatiEntry 302448640}

sr1645v2TvTmplStatiL2tpIke OBJECT-TYPE
   SYNTAX      INTEGER
               {
               idle (0),
               down (1),
               setup (2),
               up (3),
               rollOver (4)
               }
   MAX-ACCESS  read-only
   STATUS      current
   DESCRIPTION
      "Path: tunnels.status.ipsecL2tpTunnels.l2tp.ike

       Possibilities:
               idle   (0)
               down   (1)
               setup   (2)
               up   (3)
               rollOver   (4)"
   ::= {sr1645v2TvTmplStatiEntry 302514176}

sr1645v2TvTmplStatiPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.ipsecL2tpTunnels.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TvTmplStatiEntry 184614912}

sr1645v2TvTmplStatiPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.ipsecL2tpTunnels.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TvTmplStatiEntry 184680448}

sr1645v2TvTmplStatiPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.ipsecL2tpTunnels.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TvTmplStatiEntry 184745984}

sr1645v2TvTmplStatiPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: tunnels.status.ipsecL2tpTunnels.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2TvTmplStatiEntry 185204736}

sr1645v2TvTmplStatiPppMyAutUsr OBJECT-TYPE
   SYNTAX      DisplayString
   MAX-ACCESS  read-only
   STATUS      current
   DESCRIPTION
      "Path: tunnels.status.ipsecL2tpTunnels.ppp.myAuthenUser"
   ::= {sr1645v2TvTmplStatiEntry 185335808}

sr1645v2TvTmplStatiPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: tunnels.status.ipsecL2tpTunnels.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2TvTmplStatiEntry 185270272}


sr1645v2TvTmplSiGre OBJECT IDENTIFIER ::= {sr1645v2TvTmpl 25}

sr1645v2TvTmplSiGreSSCTable OBJECT-TYPE
   SYNTAX      SEQUENCE OF Sr1645v2TvTmplSiGreEntry
   MAX-ACCESS  not-accessible
   STATUS      current
   DESCRIPTION
      ""
   ::= {sr1645v2TvTmplSiGre 1}

sr1645v2TvTmplSiGreEntry OBJECT-TYPE
   SYNTAX      Sr1645v2TvTmplSiGreEntry
   MAX-ACCESS  not-accessible
   STATUS      current
   DESCRIPTION
      ""
   INDEX      { sr1645v2TvTmplSiGreTableIx }
   ::= {sr1645v2TvTmplSiGreSSCTable 1}

Sr1645v2TvTmplSiGreEntry ::=
   SEQUENCE
      {
      sr1645v2TvTmplSiGreTableIx
         TableIndex,
      sr1645v2TvTmplSiGreName
         DisplayString,
      sr1645v2TvTmplSiGreMode
         INTEGER,
      sr1645v2TvTmplSiGreIfOperStatus
         INTEGER,
      sr1645v2TvTmplSiGreIfLastChange
         TimeTicks,
      sr1645v2TvTmplSiGreIfLastChangeDate
         DisplayString,
      sr1645v2TvTmplSiGreIpVrfRouter
         DisplayString,
      sr1645v2TvTmplSiGreIpAddress
         IpAddress,
      sr1645v2TvTmplSiGreIpNetMask
         IpAddress,
      sr1645v2TvTmplSiGreIpRemote
         IpAddress,
      sr1645v2TvTmplSiGreBrStatus
         INTEGER,
      sr1645v2TvTmplSiGreBrSpanningTreePortRole
         INTEGER,
      sr1645v2TvTmplSiGreBrSpanningTreePortId
         Integer32,
      sr1645v2TvTmplSiGreBrSpanningTreePpCostExtPathCost
         Integer32,
      sr1645v2TvTmplSiGreBrSpanningTreePpCostIntPathCost
         Integer32,
      sr1645v2TvTmplSiGreBrSpanningTreeExtRpCost
         Integer32,
      sr1645v2TvTmplSiGreBrSpanningTreeIntRpCost
         Integer32,
      sr1645v2TvTmplSiGreBrSpanningTreeDesBrIdPriority
         Integer32,
      sr1645v2TvTmplSiGreBrSpanningTreeDesBrIdMacAddress
         OCTET STRING,
      sr1645v2TvTmplSiGreBrSpanningTreeDesPrtId
         Integer32,
      sr1645v2TvTmplSiGreBrSpanningTreeDesInt
         INTEGER,
      sr1645v2TvTmplSiGreBrSpanningTreeEdgeDetection
         INTEGER,
      sr1645v2TvTmplSiGreGreLocalIpAddress
         IpAddress,
      sr1645v2TvTmplSiGreGreRemoteIpAddress
         IpAddress,
      sr1645v2TvTmplSiGreGreIke
         INTEGER,
      sr1645v2TvTmplSiGreGreState
         INTEGER,
      sr1645v2TvTmplSiGreGreKeepAliveFails
         Counter32,
      sr1645v2TvTmplSiGreGreMplsMode
         INTEGER,
      sr1645v2TvTmplSiGreGreMplsInLabel
         Integer32,
      sr1645v2TvTmplSiGreGreMplsOutLabel
         Integer32
      }

sr1645v2TvTmplSiGreTableIx OBJECT-TYPE
   SYNTAX      TableIndex
   MAX-ACCESS  not-accessible
   STATUS      current
   DESCRIPTION
      ""
   ::= {sr1645v2TvTmplSiGreEntry 11}

sr1645v2TvTmplSiGreName OBJECT-TYPE
   SYNTAX      DisplayString
   MAX-ACCESS  read-only
   STATUS      current
   DESCRIPTION
      "Path: tunnels.status.ipsecGreTunnels.name"
   ::= {sr1645v2TvTmplSiGreEntry 16777216}

sr1645v2TvTmplSiGreMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.ipsecGreTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TvTmplSiGreEntry 335544320}

sr1645v2TvTmplSiGreIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.ipsecGreTunnels.ifOperStatus

       Possibilities:
               up   (1)
               down   (2)
               testing   (3)
               unknown   (4)
               dormant   (5)
               notPresent   (6)
               lowerLayerDown   (7)"
   ::= {sr1645v2TvTmplSiGreEntry 1795162112}

sr1645v2TvTmplSiGreIfLastChange OBJECT-TYPE
   SYNTAX      TimeTicks
   MAX-ACCESS  read-only
   STATUS      current
   DESCRIPTION
      "Path: tunnels.status.ipsecGreTunnels.ifLastChange

       Time in centi-second."
   ::= {sr1645v2TvTmplSiGreEntry 1811939328}

sr1645v2TvTmplSiGreIfLastChangeDate OBJECT-TYPE
   SYNTAX      DisplayString
   MAX-ACCESS  read-only
   STATUS      current
   DESCRIPTION
      "Path: tunnels.status.ipsecGreTunnels.ifLastChangeDate"
   ::= {sr1645v2TvTmplSiGreEntry 3070230528}

sr1645v2TvTmplSiGreIpVrfRouter OBJECT-TYPE
   SYNTAX      DisplayString
   MAX-ACCESS  read-only
   STATUS      current
   DESCRIPTION
      "Path: tunnels.status.ipsecGreTunnels.ip.vrfRouter"
   ::= {sr1645v2TvTmplSiGreEntry 50397184}

sr1645v2TvTmplSiGreIpAddress OBJECT-TYPE
   SYNTAX      IpAddress
   MAX-ACCESS  read-only
   STATUS      current
   DESCRIPTION
      "Path: tunnels.status.ipsecGreTunnels.ip.address"
   ::= {sr1645v2TvTmplSiGreEntry 51380224}

sr1645v2TvTmplSiGreIpNetMask OBJECT-TYPE
   SYNTAX      IpAddress
   MAX-ACCESS  read-only
   STATUS      current
   DESCRIPTION
      "Path: tunnels.status.ipsecGreTunnels.ip.netMask"
   ::= {sr1645v2TvTmplSiGreEntry 51445760}

sr1645v2TvTmplSiGreIpRemote OBJECT-TYPE
   SYNTAX      IpAddress
   MAX-ACCESS  read-only
   STATUS      current
   DESCRIPTION
      "Path: tunnels.status.ipsecGreTunnels.ip.remote"
   ::= {sr1645v2TvTmplSiGreEntry 51511296}

sr1645v2TvTmplSiGreBrStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.ipsecGreTunnels.bridging.status

       Possibilities:
               disabled   (0)
               discarding   (1)
               learning   (2)
               forwarding   (3)
               backupBlockedIntfDown   (256)
               backupBlockedIntfUp   (259)
               shutdown   (255)"
   ::= {sr1645v2TvTmplSiGreEntry 453050368}

sr1645v2TvTmplSiGreBrSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.ipsecGreTunnels.bridging.spanningTree.portRole

       Possibilities:
               none   (0)
               root   (1)
               designated   (2)
               alternate   (3)
               backup   (4)
               disabled   (5)
               master   (6)"
   ::= {sr1645v2TvTmplSiGreEntry 453116160}

sr1645v2TvTmplSiGreBrSpanningTreePortId OBJECT-TYPE
   SYNTAX      Integer32
   MAX-ACCESS  read-only
   STATUS      current
   DESCRIPTION
      "Path: tunnels.status.ipsecGreTunnels.bridging.spanningTree.portId"
   ::= {sr1645v2TvTmplSiGreEntry 453116416}

sr1645v2TvTmplSiGreBrSpanningTreePpCostExtPathCost OBJECT-TYPE
   SYNTAX      Integer32
   MAX-ACCESS  read-only
   STATUS      current
   DESCRIPTION
      "Path: tunnels.status.ipsecGreTunnels.bridging.spanningTree.portPathCosts.extPathCost"
   ::= {sr1645v2TvTmplSiGreEntry 453116673}

sr1645v2TvTmplSiGreBrSpanningTreePpCostIntPathCost OBJECT-TYPE
   SYNTAX      Integer32
   MAX-ACCESS  read-only
   STATUS      current
   DESCRIPTION
      "Path: tunnels.status.ipsecGreTunnels.bridging.spanningTree.portPathCosts.intPathCost"
   ::= {sr1645v2TvTmplSiGreEntry 453116674}

sr1645v2TvTmplSiGreBrSpanningTreeExtRpCost OBJECT-TYPE
   SYNTAX      Integer32
   MAX-ACCESS  read-only
   STATUS      current
   DESCRIPTION
      "Path: tunnels.status.ipsecGreTunnels.bridging.spanningTree.extRootPathCost"
   ::= {sr1645v2TvTmplSiGreEntry 453116928}

sr1645v2TvTmplSiGreBrSpanningTreeIntRpCost OBJECT-TYPE
   SYNTAX      Integer32
   MAX-ACCESS  read-only
   STATUS      current
   DESCRIPTION
      "Path: tunnels.status.ipsecGreTunnels.bridging.spanningTree.intRootPathCost"
   ::= {sr1645v2TvTmplSiGreEntry 453117184}

sr1645v2TvTmplSiGreBrSpanningTreeDesBrIdPriority OBJECT-TYPE
   SYNTAX      Integer32
   MAX-ACCESS  read-only
   STATUS      current
   DESCRIPTION
      "Path: tunnels.status.ipsecGreTunnels.bridging.spanningTree.designatedBridgeId.priority"
   ::= {sr1645v2TvTmplSiGreEntry 453117441}

sr1645v2TvTmplSiGreBrSpanningTreeDesBrIdMacAddress OBJECT-TYPE
   SYNTAX      OCTET STRING
   MAX-ACCESS  read-only
   STATUS      current
   DESCRIPTION
      "Path: tunnels.status.ipsecGreTunnels.bridging.spanningTree.designatedBridgeId.macAddress

       MAC address."
   ::= {sr1645v2TvTmplSiGreEntry 453117442}

sr1645v2TvTmplSiGreBrSpanningTreeDesPrtId OBJECT-TYPE
   SYNTAX      Integer32
   MAX-ACCESS  read-only
   STATUS      current
   DESCRIPTION
      "Path: tunnels.status.ipsecGreTunnels.bridging.spanningTree.designatedPortId"
   ::= {sr1645v2TvTmplSiGreEntry 453117696}

sr1645v2TvTmplSiGreBrSpanningTreeDesInt OBJECT-TYPE
   SYNTAX      INTEGER
               {
               no (0),
               yes (1)
               }
   MAX-ACCESS  read-only
   STATUS      current
   DESCRIPTION
      "Path: tunnels.status.ipsecGreTunnels.bridging.spanningTree.designatedOrInternal

       Possibilities:
               no   (0)
               yes   (1)"
   ::= {sr1645v2TvTmplSiGreEntry 453117952}

sr1645v2TvTmplSiGreBrSpanningTreeEdgeDetection OBJECT-TYPE
   SYNTAX      INTEGER
               {
               none (0),
               edge (1),
               notEdge (2)
               }
   MAX-ACCESS  read-only
   STATUS      current
   DESCRIPTION
      "Path: tunnels.status.ipsecGreTunnels.bridging.spanningTree.edgeDetection

       Possibilities:
               none   (0)
               edge   (1)
               notEdge   (2)"
   ::= {sr1645v2TvTmplSiGreEntry 453118208}

sr1645v2TvTmplSiGreGreLocalIpAddress OBJECT-TYPE
   SYNTAX      IpAddress
   MAX-ACCESS  read-only
   STATUS      current
   DESCRIPTION
      "Path: tunnels.status.ipsecGreTunnels.gre.localIpAddress"
   ::= {sr1645v2TvTmplSiGreEntry 587268096}

sr1645v2TvTmplSiGreGreRemoteIpAddress OBJECT-TYPE
   SYNTAX      IpAddress
   MAX-ACCESS  read-only
   STATUS      current
   DESCRIPTION
      "Path: tunnels.status.ipsecGreTunnels.gre.remoteIpAddress"
   ::= {sr1645v2TvTmplSiGreEntry 587333632}

sr1645v2TvTmplSiGreGreIke OBJECT-TYPE
   SYNTAX      INTEGER
               {
               idle (0),
               down (1),
               setup (2),
               up (3),
               rollOver (4)
               }
   MAX-ACCESS  read-only
   STATUS      current
   DESCRIPTION
      "Path: tunnels.status.ipsecGreTunnels.gre.ike

       Possibilities:
               idle   (0)
               down   (1)
               setup   (2)
               up   (3)
               rollOver   (4)"
   ::= {sr1645v2TvTmplSiGreEntry 587399168}

sr1645v2TvTmplSiGreGreState OBJECT-TYPE
   SYNTAX      INTEGER
               {
               setup (0),
               resolvingRemote (1),
               resolvingLocal (2),
               waitDnsReply (3),
               initParked (4),
               open (5),
               activated (128),
               initActivate (129),
               spoofing (130),
               down (131),
               up (132),
               park (133)
               }
   MAX-ACCESS  read-only
   STATUS      current
   DESCRIPTION
      "Path: tunnels.status.ipsecGreTunnels.gre.state

       Possibilities:
               setup   (0)
               resolvingRemote   (1)
               resolvingLocal   (2)
               waitDnsReply   (3)
               initParked   (4)
               open   (5)
               activated   (128)
               initActivate   (129)
               spoofing   (130)
               down   (131)
               up   (132)
               park   (133)"
   ::= {sr1645v2TvTmplSiGreEntry 587464704}

sr1645v2TvTmplSiGreGreKeepAliveFails OBJECT-TYPE
   SYNTAX      Counter32
   MAX-ACCESS  read-only
   STATUS      current
   DESCRIPTION
      "Path: tunnels.status.ipsecGreTunnels.gre.keepAlive.fails

       32 bit unsigned wrappable counter."
   ::= {sr1645v2TvTmplSiGreEntry 587596032}

sr1645v2TvTmplSiGreGreMplsMode OBJECT-TYPE
   SYNTAX      INTEGER
               {
               disabled (0),
               enabled (1)
               }
   MAX-ACCESS  read-only
   STATUS      current
   DESCRIPTION
      "Path: tunnels.status.ipsecGreTunnels.gre.mpls.mode

       Possibilities:
               disabled   (0)
               enabled   (1)"
   ::= {sr1645v2TvTmplSiGreEntry 587530496}

sr1645v2TvTmplSiGreGreMplsInLabel OBJECT-TYPE
   SYNTAX      Integer32
   MAX-ACCESS  read-only
   STATUS      current
   DESCRIPTION
      "Path: tunnels.status.ipsecGreTunnels.gre.mpls.inLabel"
   ::= {sr1645v2TvTmplSiGreEntry 587530752}

sr1645v2TvTmplSiGreGreMplsOutLabel OBJECT-TYPE
   SYNTAX      Integer32
   MAX-ACCESS  read-only
   STATUS      current
   DESCRIPTION
      "Path: tunnels.status.ipsecGreTunnels.gre.mpls.outLabel"
   ::= {sr1645v2TvTmplSiGreEntry 587531008}


sr1645v2TvTmplIpsTun OBJECT IDENTIFIER ::= {sr1645v2TvTmpl 11}

sr1645v2TvTmplIpsTunSSCTable OBJECT-TYPE
   SYNTAX      SEQUENCE OF Sr1645v2TvTmplIpsTunEntry
   MAX-ACCESS  not-accessible
   STATUS      current
   DESCRIPTION
      ""
   ::= {sr1645v2TvTmplIpsTun 1}

sr1645v2TvTmplIpsTunEntry OBJECT-TYPE
   SYNTAX      Sr1645v2TvTmplIpsTunEntry
   MAX-ACCESS  not-accessible
   STATUS      current
   DESCRIPTION
      ""
   INDEX      { sr1645v2TvTmplIpsTunTableIx }
   ::= {sr1645v2TvTmplIpsTunSSCTable 1}

Sr1645v2TvTmplIpsTunEntry ::=
   SEQUENCE
      {
      sr1645v2TvTmplIpsTunTableIx
         TableIndex,
      sr1645v2TvTmplIpsTunName
         DisplayString,
      sr1645v2TvTmplIpsTunLocalIpAddress
         IpAddress,
      sr1645v2TvTmplIpsTunRemoteIpAddress
         IpAddress,
      sr1645v2TvTmplIpsTunOperStatus
         INTEGER,
      sr1645v2TvTmplIpsTunLastChange
         TimeTicks,
      sr1645v2TvTmplIpsTunLastChangeDate
         DisplayString,
      sr1645v2TvTmplIpsTunIke
         INTEGER
      }

sr1645v2TvTmplIpsTunTableIx OBJECT-TYPE
   SYNTAX      TableIndex
   MAX-ACCESS  not-accessible
   STATUS      current
   DESCRIPTION
      ""
   ::= {sr1645v2TvTmplIpsTunEntry 11}

sr1645v2TvTmplIpsTunName OBJECT-TYPE
   SYNTAX      DisplayString
   MAX-ACCESS  read-only
   STATUS      current
   DESCRIPTION
      "Path: tunnels.status.ipsecTunnels.name"
   ::= {sr1645v2TvTmplIpsTunEntry 16777216}

sr1645v2TvTmplIpsTunLocalIpAddress OBJECT-TYPE
   SYNTAX      IpAddress
   MAX-ACCESS  read-only
   STATUS      current
   DESCRIPTION
      "Path: tunnels.status.ipsecTunnels.localIpAddress"
   ::= {sr1645v2TvTmplIpsTunEntry 33554432}

sr1645v2TvTmplIpsTunRemoteIpAddress OBJECT-TYPE
   SYNTAX      IpAddress
   MAX-ACCESS  read-only
   STATUS      current
   DESCRIPTION
      "Path: tunnels.status.ipsecTunnels.remoteIpAddress"
   ::= {sr1645v2TvTmplIpsTunEntry 50331648}

sr1645v2TvTmplIpsTunOperStatus OBJECT-TYPE
   SYNTAX      INTEGER
               {
               down (0),
               up (1),
               resolvingRemote (2),
               resolvingLocal (3),
               setup (4),
               delete (5),
               new (6),
               waitDnsReply (7),
               spoofing (8),
               initSA (9),
               waitUp (10)
               }
   MAX-ACCESS  read-only
   STATUS      current
   DESCRIPTION
      "Path: tunnels.status.ipsecTunnels.operStatus

       Possibilities:
               down   (0)
               up   (1)
               resolvingRemote   (2)
               resolvingLocal   (3)
               setup   (4)
               delete   (5)
               new   (6)
               waitDnsReply   (7)
               spoofing   (8)
               initSA   (9)
               waitUp   (10)"
   ::= {sr1645v2TvTmplIpsTunEntry 83886080}

sr1645v2TvTmplIpsTunLastChange OBJECT-TYPE
   SYNTAX      TimeTicks
   MAX-ACCESS  read-only
   STATUS      current
   DESCRIPTION
      "Path: tunnels.status.ipsecTunnels.lastChange

       Time in centi-second."
   ::= {sr1645v2TvTmplIpsTunEntry 100663296}

sr1645v2TvTmplIpsTunLastChangeDate OBJECT-TYPE
   SYNTAX      DisplayString
   MAX-ACCESS  read-only
   STATUS      current
   DESCRIPTION
      "Path: tunnels.status.ipsecTunnels.lastChangeDate"
   ::= {sr1645v2TvTmplIpsTunEntry 117440512}

sr1645v2TvTmplIpsTunIke OBJECT-TYPE
   SYNTAX      INTEGER
               {
               idle (0),
               down (1),
               setup (2),
               up (3),
               rollOver (4)
               }
   MAX-ACCESS  read-only
   STATUS      current
   DESCRIPTION
      "Path: tunnels.status.ipsecTunnels.ike

       Possibilities:
               idle   (0)
               down   (1)
               setup   (2)
               up   (3)
               rollOver   (4)"
   ::= {sr1645v2TvTmplIpsTunEntry 67108864}


sr1645v2TvTmplStat OBJECT IDENTIFIER ::= {sr1645v2TvTmpl 2}

sr1645v2TvTmplStatSSCTable OBJECT-TYPE
   SYNTAX      SEQUENCE OF Sr1645v2TvTmplStatEntry
   MAX-ACCESS  not-accessible
   STATUS      current
   DESCRIPTION
      ""
   ::= {sr1645v2TvTmplStat 1}

sr1645v2TvTmplStatEntry OBJECT-TYPE
   SYNTAX      Sr1645v2TvTmplStatEntry
   MAX-ACCESS  not-accessible
   STATUS      current
   DESCRIPTION
      ""
   INDEX      { sr1645v2TvTmplStatTableIx }
   ::= {sr1645v2TvTmplStatSSCTable 1}

Sr1645v2TvTmplStatEntry ::=
   SEQUENCE
      {
      sr1645v2TvTmplStatTableIx
         TableIndex,
      sr1645v2TvTmplStatName
         DisplayString,
      sr1645v2TvTmplStatMode
         INTEGER,
      sr1645v2TvTmplStatIfOperStatus
         INTEGER,
      sr1645v2TvTmplStatIfLastChange
         TimeTicks,
      sr1645v2TvTmplStatIfLastChangeDate
         DisplayString,
      sr1645v2TvTmplStatIpVrfRouter
         DisplayString,
      sr1645v2TvTmplStatIpAddress
         IpAddress,
      sr1645v2TvTmplStatIpNetMask
         IpAddress,
      sr1645v2TvTmplStatIpRemote
         IpAddress,
      sr1645v2TvTmplStatBridgingStatus
         INTEGER,
      sr1645v2TvTmplStatBridgingSpanningTreePortRole
         INTEGER,
      sr1645v2TvTmplStatBridgingSpanningTreePortId
         Integer32,
      sr1645v2TvTmplStatBridgingSpanningTreePpCostExtPathCost
         Integer32,
      sr1645v2TvTmplStatBridgingSpanningTreePpCostIntPathCost
         Integer32,
      sr1645v2TvTmplStatBridgingSpanningTreeExtRpCost
         Integer32,
      sr1645v2TvTmplStatBridgingSpanningTreeIntRpCost
         Integer32,
      sr1645v2TvTmplStatBridgingSpanningTreeDesBrIdPriority
         Integer32,
      sr1645v2TvTmplStatBridgingSpanningTreeDesBrIdMacAddress
         OCTET STRING,
      sr1645v2TvTmplStatBridgingSpanningTreeDesPrtId
         Integer32,
      sr1645v2TvTmplStatBridgingSpanningTreeDesInt
         INTEGER,
      sr1645v2TvTmplStatBridgingSpanningTreeEdgeDetection
         INTEGER,
      sr1645v2TvTmplStatEncapsulation
         INTEGER,
      sr1645v2TvTmplStatL2tpVrfRouter
         DisplayString,
      sr1645v2TvTmplStatL2tpLocalIpAddress
         IpAddress,
      sr1645v2TvTmplStatL2tpRemAddr
         IpAddress,
      sr1645v2TvTmplStatL2tpSendingSeqNr
         Integer32,
      sr1645v2TvTmplStatL2tpReceivingSeqNr
         Integer32,
      sr1645v2TvTmplStatL2tpL2tpType
         INTEGER,
      sr1645v2TvTmplStatL2tpControlState
         INTEGER,
      sr1645v2TvTmplStatL2tpCallState
         INTEGER,
      sr1645v2TvTmplStatL2tpDeliveryState
         INTEGER,
      sr1645v2TvTmplStatL2tpAuthenState
         INTEGER,
      sr1645v2TvTmplStatL2tpLocalTunnelId
         Gauge32,
      sr1645v2TvTmplStatL2tpRemoteTunnelId
         Gauge32,
      sr1645v2TvTmplStatL2tpLocalSessionId
         Gauge32,
      sr1645v2TvTmplStatL2tpRemoteSessionId
         Gauge32,
      sr1645v2TvTmplStatL2tpV3VrfRouter
         DisplayString,
      sr1645v2TvTmplStatL2tpV3LocalIpAddress
         IpAddress,
      sr1645v2TvTmplStatL2tpV3RemAddr
         IpAddress,
      sr1645v2TvTmplStatL2tpV3SendingSeqNr
         Integer32,
      sr1645v2TvTmplStatL2tpV3ReceivingSeqNr
         Integer32,
      sr1645v2TvTmplStatL2tpV3L2tpType
         INTEGER,
      sr1645v2TvTmplStatL2tpV3ControlState
         INTEGER,
      sr1645v2TvTmplStatL2tpV3CallState
         INTEGER,
      sr1645v2TvTmplStatL2tpV3DeliveryState
         INTEGER,
      sr1645v2TvTmplStatL2tpV3LocalConnectionId
         Gauge32,
      sr1645v2TvTmplStatL2tpV3RemoteConnectionId
         Gauge32,
      sr1645v2TvTmplStatL2tpV3LocalSessionId
         Gauge32,
      sr1645v2TvTmplStatL2tpV3RemoteSessionId
         Gauge32,
      sr1645v2TvTmplStatL2tpV3LocalCookieLength
         Integer32,
      sr1645v2TvTmplStatL2tpV3RemoteCookieLength
         Integer32,
      sr1645v2TvTmplStatL2tpV3LocalDataSeq
         INTEGER,
      sr1645v2TvTmplStatL2tpV3RemoteDataSeq
         INTEGER,
      sr1645v2TvTmplStatL2tpV3ManualVrfRouter
         DisplayString,
      sr1645v2TvTmplStatL2tpV3ManualLocalIpAddress
         IpAddress,
      sr1645v2TvTmplStatL2tpV3ManualRemAddr
         IpAddress,
      sr1645v2TvTmplStatL2tpV3ManualLocalSessionId
         Gauge32,
      sr1645v2TvTmplStatL2tpV3ManualRemoteSessionId
         Gauge32,
      sr1645v2TvTmplStatL2tpV3ManualLocalCookieLength
         Integer32,
      sr1645v2TvTmplStatL2tpV3ManualRemoteCookieLength
         Integer32,
      sr1645v2TvTmplStatL2tpV3ManualLocalDataSeq
         INTEGER,
      sr1645v2TvTmplStatL2tpV3ManualRemoteDataSeq
         INTEGER,
      sr1645v2TvTmplStatPppLcpState
         INTEGER,
      sr1645v2TvTmplStatPppIpcpState
         INTEGER,
      sr1645v2TvTmplStatPppBcpState
         INTEGER,
      sr1645v2TvTmplStatPppMyAutSt
         INTEGER,
      sr1645v2TvTmplStatPppMyAutUsr
         DisplayString,
      sr1645v2TvTmplStatPppHisAutSt
         INTEGER
      }

sr1645v2TvTmplStatTableIx OBJECT-TYPE
   SYNTAX      TableIndex
   MAX-ACCESS  not-accessible
   STATUS      current
   DESCRIPTION
      ""
   ::= {sr1645v2TvTmplStatEntry 11}

sr1645v2TvTmplStatName OBJECT-TYPE
   SYNTAX      DisplayString
   MAX-ACCESS  read-only
   STATUS      current
   DESCRIPTION
      "Path: tunnels.status.l2tpTunnels.name"
   ::= {sr1645v2TvTmplStatEntry 16777216}

sr1645v2TvTmplStatMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.l2tpTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TvTmplStatEntry 335544320}

sr1645v2TvTmplStatIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.l2tpTunnels.ifOperStatus

       Possibilities:
               up   (1)
               down   (2)
               testing   (3)
               unknown   (4)
               dormant   (5)
               notPresent   (6)
               lowerLayerDown   (7)"
   ::= {sr1645v2TvTmplStatEntry 1795162112}

sr1645v2TvTmplStatIfLastChange OBJECT-TYPE
   SYNTAX      TimeTicks
   MAX-ACCESS  read-only
   STATUS      current
   DESCRIPTION
      "Path: tunnels.status.l2tpTunnels.ifLastChange

       Time in centi-second."
   ::= {sr1645v2TvTmplStatEntry 1811939328}

sr1645v2TvTmplStatIfLastChangeDate OBJECT-TYPE
   SYNTAX      DisplayString
   MAX-ACCESS  read-only
   STATUS      current
   DESCRIPTION
      "Path: tunnels.status.l2tpTunnels.ifLastChangeDate"
   ::= {sr1645v2TvTmplStatEntry 3070230528}

sr1645v2TvTmplStatIpVrfRouter OBJECT-TYPE
   SYNTAX      DisplayString
   MAX-ACCESS  read-only
   STATUS      current
   DESCRIPTION
      "Path: tunnels.status.l2tpTunnels.ip.vrfRouter"
   ::= {sr1645v2TvTmplStatEntry 50397184}

sr1645v2TvTmplStatIpAddress OBJECT-TYPE
   SYNTAX      IpAddress
   MAX-ACCESS  read-only
   STATUS      current
   DESCRIPTION
      "Path: tunnels.status.l2tpTunnels.ip.address"
   ::= {sr1645v2TvTmplStatEntry 51380224}

sr1645v2TvTmplStatIpNetMask OBJECT-TYPE
   SYNTAX      IpAddress
   MAX-ACCESS  read-only
   STATUS      current
   DESCRIPTION
      "Path: tunnels.status.l2tpTunnels.ip.netMask"
   ::= {sr1645v2TvTmplStatEntry 51445760}

sr1645v2TvTmplStatIpRemote OBJECT-TYPE
   SYNTAX      IpAddress
   MAX-ACCESS  read-only
   STATUS      current
   DESCRIPTION
      "Path: tunnels.status.l2tpTunnels.ip.remote"
   ::= {sr1645v2TvTmplStatEntry 51511296}

sr1645v2TvTmplStatBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.l2tpTunnels.bridging.status

       Possibilities:
               disabled   (0)
               discarding   (1)
               learning   (2)
               forwarding   (3)
               backupBlockedIntfDown   (256)
               backupBlockedIntfUp   (259)
               shutdown   (255)"
   ::= {sr1645v2TvTmplStatEntry 453050368}

sr1645v2TvTmplStatBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.l2tpTunnels.bridging.spanningTree.portRole

       Possibilities:
               none   (0)
               root   (1)
               designated   (2)
               alternate   (3)
               backup   (4)
               disabled   (5)
               master   (6)"
   ::= {sr1645v2TvTmplStatEntry 453116160}

sr1645v2TvTmplStatBridgingSpanningTreePortId OBJECT-TYPE
   SYNTAX      Integer32
   MAX-ACCESS  read-only
   STATUS      current
   DESCRIPTION
      "Path: tunnels.status.l2tpTunnels.bridging.spanningTree.portId"
   ::= {sr1645v2TvTmplStatEntry 453116416}

sr1645v2TvTmplStatBridgingSpanningTreePpCostExtPathCost OBJECT-TYPE
   SYNTAX      Integer32
   MAX-ACCESS  read-only
   STATUS      current
   DESCRIPTION
      "Path: tunnels.status.l2tpTunnels.bridging.spanningTree.portPathCosts.extPathCost"
   ::= {sr1645v2TvTmplStatEntry 453116673}

sr1645v2TvTmplStatBridgingSpanningTreePpCostIntPathCost OBJECT-TYPE
   SYNTAX      Integer32
   MAX-ACCESS  read-only
   STATUS      current
   DESCRIPTION
      "Path: tunnels.status.l2tpTunnels.bridging.spanningTree.portPathCosts.intPathCost"
   ::= {sr1645v2TvTmplStatEntry 453116674}

sr1645v2TvTmplStatBridgingSpanningTreeExtRpCost OBJECT-TYPE
   SYNTAX      Integer32
   MAX-ACCESS  read-only
   STATUS      current
   DESCRIPTION
      "Path: tunnels.status.l2tpTunnels.bridging.spanningTree.extRootPathCost"
   ::= {sr1645v2TvTmplStatEntry 453116928}

sr1645v2TvTmplStatBridgingSpanningTreeIntRpCost OBJECT-TYPE
   SYNTAX      Integer32
   MAX-ACCESS  read-only
   STATUS      current
   DESCRIPTION
      "Path: tunnels.status.l2tpTunnels.bridging.spanningTree.intRootPathCost"
   ::= {sr1645v2TvTmplStatEntry 453117184}

sr1645v2TvTmplStatBridgingSpanningTreeDesBrIdPriority OBJECT-TYPE
   SYNTAX      Integer32
   MAX-ACCESS  read-only
   STATUS      current
   DESCRIPTION
      "Path: tunnels.status.l2tpTunnels.bridging.spanningTree.designatedBridgeId.priority"
   ::= {sr1645v2TvTmplStatEntry 453117441}

sr1645v2TvTmplStatBridgingSpanningTreeDesBrIdMacAddress OBJECT-TYPE
   SYNTAX      OCTET STRING
   MAX-ACCESS  read-only
   STATUS      current
   DESCRIPTION
      "Path: tunnels.status.l2tpTunnels.bridging.spanningTree.designatedBridgeId.macAddress

       MAC address."
   ::= {sr1645v2TvTmplStatEntry 453117442}

sr1645v2TvTmplStatBridgingSpanningTreeDesPrtId OBJECT-TYPE
   SYNTAX      Integer32
   MAX-ACCESS  read-only
   STATUS      current
   DESCRIPTION
      "Path: tunnels.status.l2tpTunnels.bridging.spanningTree.designatedPortId"
   ::= {sr1645v2TvTmplStatEntry 453117696}

sr1645v2TvTmplStatBridgingSpanningTreeDesInt OBJECT-TYPE
   SYNTAX      INTEGER
               {
               no (0),
               yes (1)
               }
   MAX-ACCESS  read-only
   STATUS      current
   DESCRIPTION
      "Path: tunnels.status.l2tpTunnels.bridging.spanningTree.designatedOrInternal

       Possibilities:
               no   (0)
               yes   (1)"
   ::= {sr1645v2TvTmplStatEntry 453117952}

sr1645v2TvTmplStatBridgingSpanningTreeEdgeDetection OBJECT-TYPE
   SYNTAX      INTEGER
               {
               none (0),
               edge (1),
               notEdge (2)
               }
   MAX-ACCESS  read-only
   STATUS      current
   DESCRIPTION
      "Path: tunnels.status.l2tpTunnels.bridging.spanningTree.edgeDetection

       Possibilities:
               none   (0)
               edge   (1)
               notEdge   (2)"
   ::= {sr1645v2TvTmplStatEntry 453118208}

sr1645v2TvTmplStatEncapsulation OBJECT-TYPE
   SYNTAX      INTEGER
               {
               l2tp (1),
               l2tpV3 (2),
               l2tpV3Udp (3),
               l2tpV3Manual (18),
               l2tpV3ManualUdp (19)
               }
   MAX-ACCESS  read-only
   STATUS      current
   DESCRIPTION
      "Path: tunnels.status.l2tpTunnels.encapsulation

       Possibilities:
               l2tp   (1)
               l2tpV3   (2)
               l2tpV3Udp   (3)
               l2tpV3Manual   (18)
               l2tpV3ManualUdp   (19)"
   ::= {sr1645v2TvTmplStatEntry 369098752}

sr1645v2TvTmplStatL2tpVrfRouter OBJECT-TYPE
   SYNTAX      DisplayString
   MAX-ACCESS  read-only
   STATUS      current
   DESCRIPTION
      "Path: tunnels.status.l2tpTunnels.l2tp.vrfRouter"
   ::= {sr1645v2TvTmplStatEntry 302710784}

sr1645v2TvTmplStatL2tpLocalIpAddress OBJECT-TYPE
   SYNTAX      IpAddress
   MAX-ACCESS  read-only
   STATUS      current
   DESCRIPTION
      "Path: tunnels.status.l2tpTunnels.l2tp.localIpAddress"
   ::= {sr1645v2TvTmplStatEntry 302579712}

sr1645v2TvTmplStatL2tpRemAddr OBJECT-TYPE
   SYNTAX      IpAddress
   MAX-ACCESS  read-only
   STATUS      current
   DESCRIPTION
      "Path: tunnels.status.l2tpTunnels.l2tp.remoteIpAddress"
   ::= {sr1645v2TvTmplStatEntry 302645248}

sr1645v2TvTmplStatL2tpSendingSeqNr OBJECT-TYPE
   SYNTAX      Integer32
   MAX-ACCESS  read-only
   STATUS      current
   DESCRIPTION
      "Path: tunnels.status.l2tpTunnels.l2tp.sendingSeqNr"
   ::= {sr1645v2TvTmplStatEntry 302055424}

sr1645v2TvTmplStatL2tpReceivingSeqNr OBJECT-TYPE
   SYNTAX      Integer32
   MAX-ACCESS  read-only
   STATUS      current
   DESCRIPTION
      "Path: tunnels.status.l2tpTunnels.l2tp.receivingSeqNr"
   ::= {sr1645v2TvTmplStatEntry 302120960}

sr1645v2TvTmplStatL2tpL2tpType OBJECT-TYPE
   SYNTAX      INTEGER
               {
               lac (1),
               lns (2),
               auto (3)
               }
   MAX-ACCESS  read-only
   STATUS      current
   DESCRIPTION
      "Path: tunnels.status.l2tpTunnels.l2tp.l2tpType

       Possibilities:
               lac   (1)
               lns   (2)
               auto   (3)"
   ::= {sr1645v2TvTmplStatEntry 302186496}

sr1645v2TvTmplStatL2tpControlState OBJECT-TYPE
   SYNTAX      INTEGER
               {
               idle (1),
               waitCtlReply (2),
               waitCtlConn (3),
               established (4)
               }
   MAX-ACCESS  read-only
   STATUS      current
   DESCRIPTION
      "Path: tunnels.status.l2tpTunnels.l2tp.controlState

       Possibilities:
               idle   (1)
               waitCtlReply   (2)
               waitCtlConn   (3)
               established   (4)"
   ::= {sr1645v2TvTmplStatEntry 302252032}

sr1645v2TvTmplStatL2tpCallState OBJECT-TYPE
   SYNTAX      INTEGER
               {
               idle (1),
               waitTunnel (2),
               waitReply (3),
               waitConnect (4),
               established (5)
               }
   MAX-ACCESS  read-only
   STATUS      current
   DESCRIPTION
      "Path: tunnels.status.l2tpTunnels.l2tp.callState

       Possibilities:
               idle   (1)
               waitTunnel   (2)
               waitReply   (3)
               waitConnect   (4)
               established   (5)"
   ::= {sr1645v2TvTmplStatEntry 302317568}

sr1645v2TvTmplStatL2tpDeliveryState OBJECT-TYPE
   SYNTAX      INTEGER
               {
               idle (1),
               operating (2),
               done (3)
               }
   MAX-ACCESS  read-only
   STATUS      current
   DESCRIPTION
      "Path: tunnels.status.l2tpTunnels.l2tp.deliveryState

       Possibilities:
               idle   (1)
               operating   (2)
               done   (3)"
   ::= {sr1645v2TvTmplStatEntry 302383104}

sr1645v2TvTmplStatL2tpAuthenState OBJECT-TYPE
   SYNTAX      INTEGER
               {
               noAuthentication (0),
               authenFailure (1),
               authenSuccessful (2)
               }
   MAX-ACCESS  read-only
   STATUS      current
   DESCRIPTION
      "Path: tunnels.status.l2tpTunnels.l2tp.authenState

       Possibilities:
               noAuthentication   (0)
               authenFailure   (1)
               authenSuccessful   (2)"
   ::= {sr1645v2TvTmplStatEntry 302448640}

sr1645v2TvTmplStatL2tpLocalTunnelId OBJECT-TYPE
   SYNTAX      Gauge32
   MAX-ACCESS  read-only
   STATUS      current
   DESCRIPTION
      "Path: tunnels.status.l2tpTunnels.l2tp.localTunnelId

       32 bit unsigned gauge value."
   ::= {sr1645v2TvTmplStatEntry 302776320}

sr1645v2TvTmplStatL2tpRemoteTunnelId OBJECT-TYPE
   SYNTAX      Gauge32
   MAX-ACCESS  read-only
   STATUS      current
   DESCRIPTION
      "Path: tunnels.status.l2tpTunnels.l2tp.remoteTunnelId

       32 bit unsigned gauge value."
   ::= {sr1645v2TvTmplStatEntry 302841856}

sr1645v2TvTmplStatL2tpLocalSessionId OBJECT-TYPE
   SYNTAX      Gauge32
   MAX-ACCESS  read-only
   STATUS      current
   DESCRIPTION
      "Path: tunnels.status.l2tpTunnels.l2tp.localSessionId

       32 bit unsigned gauge value."
   ::= {sr1645v2TvTmplStatEntry 303038464}

sr1645v2TvTmplStatL2tpRemoteSessionId OBJECT-TYPE
   SYNTAX      Gauge32
   MAX-ACCESS  read-only
   STATUS      current
   DESCRIPTION
      "Path: tunnels.status.l2tpTunnels.l2tp.remoteSessionId

       32 bit unsigned gauge value."
   ::= {sr1645v2TvTmplStatEntry 303104000}

sr1645v2TvTmplStatL2tpV3VrfRouter OBJECT-TYPE
   SYNTAX      DisplayString
   MAX-ACCESS  read-only
   STATUS      current
   DESCRIPTION
      "Path: tunnels.status.l2tpTunnels.l2tpV3.vrfRouter"
   ::= {sr1645v2TvTmplStatEntry 319488000}

sr1645v2TvTmplStatL2tpV3LocalIpAddress OBJECT-TYPE
   SYNTAX      IpAddress
   MAX-ACCESS  read-only
   STATUS      current
   DESCRIPTION
      "Path: tunnels.status.l2tpTunnels.l2tpV3.localIpAddress"
   ::= {sr1645v2TvTmplStatEntry 319356928}

sr1645v2TvTmplStatL2tpV3RemAddr OBJECT-TYPE
   SYNTAX      IpAddress
   MAX-ACCESS  read-only
   STATUS      current
   DESCRIPTION
      "Path: tunnels.status.l2tpTunnels.l2tpV3.remoteIpAddress"
   ::= {sr1645v2TvTmplStatEntry 319422464}

sr1645v2TvTmplStatL2tpV3SendingSeqNr OBJECT-TYPE
   SYNTAX      Integer32
   MAX-ACCESS  read-only
   STATUS      current
   DESCRIPTION
      "Path: tunnels.status.l2tpTunnels.l2tpV3.sendingSeqNr"
   ::= {sr1645v2TvTmplStatEntry 318832640}

sr1645v2TvTmplStatL2tpV3ReceivingSeqNr OBJECT-TYPE
   SYNTAX      Integer32
   MAX-ACCESS  read-only
   STATUS      current
   DESCRIPTION
      "Path: tunnels.status.l2tpTunnels.l2tpV3.receivingSeqNr"
   ::= {sr1645v2TvTmplStatEntry 318898176}

sr1645v2TvTmplStatL2tpV3L2tpType OBJECT-TYPE
   SYNTAX      INTEGER
               {
               lac (1),
               lns (2),
               auto (3)
               }
   MAX-ACCESS  read-only
   STATUS      current
   DESCRIPTION
      "Path: tunnels.status.l2tpTunnels.l2tpV3.l2tpType

       Possibilities:
               lac   (1)
               lns   (2)
               auto   (3)"
   ::= {sr1645v2TvTmplStatEntry 318963712}

sr1645v2TvTmplStatL2tpV3ControlState OBJECT-TYPE
   SYNTAX      INTEGER
               {
               idle (1),
               waitCtlReply (2),
               waitCtlConn (3),
               established (4)
               }
   MAX-ACCESS  read-only
   STATUS      current
   DESCRIPTION
      "Path: tunnels.status.l2tpTunnels.l2tpV3.controlState

       Possibilities:
               idle   (1)
               waitCtlReply   (2)
               waitCtlConn   (3)
               established   (4)"
   ::= {sr1645v2TvTmplStatEntry 319029248}

sr1645v2TvTmplStatL2tpV3CallState OBJECT-TYPE
   SYNTAX      INTEGER
               {
               idle (1),
               waitTunnel (2),
               waitReply (3),
               waitConnect (4),
               established (5)
               }
   MAX-ACCESS  read-only
   STATUS      current
   DESCRIPTION
      "Path: tunnels.status.l2tpTunnels.l2tpV3.callState

       Possibilities:
               idle   (1)
               waitTunnel   (2)
               waitReply   (3)
               waitConnect   (4)
               established   (5)"
   ::= {sr1645v2TvTmplStatEntry 319094784}

sr1645v2TvTmplStatL2tpV3DeliveryState OBJECT-TYPE
   SYNTAX      INTEGER
               {
               idle (1),
               operating (2),
               done (3)
               }
   MAX-ACCESS  read-only
   STATUS      current
   DESCRIPTION
      "Path: tunnels.status.l2tpTunnels.l2tpV3.deliveryState

       Possibilities:
               idle   (1)
               operating   (2)
               done   (3)"
   ::= {sr1645v2TvTmplStatEntry 319160320}

sr1645v2TvTmplStatL2tpV3LocalConnectionId OBJECT-TYPE
   SYNTAX      Gauge32
   MAX-ACCESS  read-only
   STATUS      current
   DESCRIPTION
      "Path: tunnels.status.l2tpTunnels.l2tpV3.localConnectionId

       32 bit unsigned gauge value."
   ::= {sr1645v2TvTmplStatEntry 319684608}

sr1645v2TvTmplStatL2tpV3RemoteConnectionId OBJECT-TYPE
   SYNTAX      Gauge32
   MAX-ACCESS  read-only
   STATUS      current
   DESCRIPTION
      "Path: tunnels.status.l2tpTunnels.l2tpV3.remoteConnectionId

       32 bit unsigned gauge value."
   ::= {sr1645v2TvTmplStatEntry 319750144}

sr1645v2TvTmplStatL2tpV3LocalSessionId OBJECT-TYPE
   SYNTAX      Gauge32
   MAX-ACCESS  read-only
   STATUS      current
   DESCRIPTION
      "Path: tunnels.status.l2tpTunnels.l2tpV3.localSessionId

       32 bit unsigned gauge value."
   ::= {sr1645v2TvTmplStatEntry 319815680}

sr1645v2TvTmplStatL2tpV3RemoteSessionId OBJECT-TYPE
   SYNTAX      Gauge32
   MAX-ACCESS  read-only
   STATUS      current
   DESCRIPTION
      "Path: tunnels.status.l2tpTunnels.l2tpV3.remoteSessionId

       32 bit unsigned gauge value."
   ::= {sr1645v2TvTmplStatEntry 319881216}

sr1645v2TvTmplStatL2tpV3LocalCookieLength OBJECT-TYPE
   SYNTAX      Integer32
   MAX-ACCESS  read-only
   STATUS      current
   DESCRIPTION
      "Path: tunnels.status.l2tpTunnels.l2tpV3.localCookieLength"
   ::= {sr1645v2TvTmplStatEntry 319946752}

sr1645v2TvTmplStatL2tpV3RemoteCookieLength OBJECT-TYPE
   SYNTAX      Integer32
   MAX-ACCESS  read-only
   STATUS      current
   DESCRIPTION
      "Path: tunnels.status.l2tpTunnels.l2tpV3.remoteCookieLength"
   ::= {sr1645v2TvTmplStatEntry 320012288}

sr1645v2TvTmplStatL2tpV3LocalDataSeq OBJECT-TYPE
   SYNTAX      INTEGER
               {
               off (0),
               nonIp (1),
               on (2)
               }
   MAX-ACCESS  read-only
   STATUS      current
   DESCRIPTION
      "Path: tunnels.status.l2tpTunnels.l2tpV3.localDataSeq

       Possibilities:
               off   (0)
               nonIp   (1)
               on   (2)"
   ::= {sr1645v2TvTmplStatEntry 320077824}

sr1645v2TvTmplStatL2tpV3RemoteDataSeq OBJECT-TYPE
   SYNTAX      INTEGER
               {
               off (0),
               nonIp (1),
               on (2)
               }
   MAX-ACCESS  read-only
   STATUS      current
   DESCRIPTION
      "Path: tunnels.status.l2tpTunnels.l2tpV3.remoteDataSeq

       Possibilities:
               off   (0)
               nonIp   (1)
               on   (2)"
   ::= {sr1645v2TvTmplStatEntry 320143360}

sr1645v2TvTmplStatL2tpV3ManualVrfRouter OBJECT-TYPE
   SYNTAX      DisplayString
   MAX-ACCESS  read-only
   STATUS      current
   DESCRIPTION
      "Path: tunnels.status.l2tpTunnels.l2tpV3Manual.vrfRouter"
   ::= {sr1645v2TvTmplStatEntry 353042432}

sr1645v2TvTmplStatL2tpV3ManualLocalIpAddress OBJECT-TYPE
   SYNTAX      IpAddress
   MAX-ACCESS  read-only
   STATUS      current
   DESCRIPTION
      "Path: tunnels.status.l2tpTunnels.l2tpV3Manual.localIpAddress"
   ::= {sr1645v2TvTmplStatEntry 352911360}

sr1645v2TvTmplStatL2tpV3ManualRemAddr OBJECT-TYPE
   SYNTAX      IpAddress
   MAX-ACCESS  read-only
   STATUS      current
   DESCRIPTION
      "Path: tunnels.status.l2tpTunnels.l2tpV3Manual.remoteIpAddress"
   ::= {sr1645v2TvTmplStatEntry 352976896}

sr1645v2TvTmplStatL2tpV3ManualLocalSessionId OBJECT-TYPE
   SYNTAX      Gauge32
   MAX-ACCESS  read-only
   STATUS      current
   DESCRIPTION
      "Path: tunnels.status.l2tpTunnels.l2tpV3Manual.localSessionId

       32 bit unsigned gauge value."
   ::= {sr1645v2TvTmplStatEntry 353370112}

sr1645v2TvTmplStatL2tpV3ManualRemoteSessionId OBJECT-TYPE
   SYNTAX      Gauge32
   MAX-ACCESS  read-only
   STATUS      current
   DESCRIPTION
      "Path: tunnels.status.l2tpTunnels.l2tpV3Manual.remoteSessionId

       32 bit unsigned gauge value."
   ::= {sr1645v2TvTmplStatEntry 353435648}

sr1645v2TvTmplStatL2tpV3ManualLocalCookieLength OBJECT-TYPE
   SYNTAX      Integer32
   MAX-ACCESS  read-only
   STATUS      current
   DESCRIPTION
      "Path: tunnels.status.l2tpTunnels.l2tpV3Manual.localCookieLength"
   ::= {sr1645v2TvTmplStatEntry 353501184}

sr1645v2TvTmplStatL2tpV3ManualRemoteCookieLength OBJECT-TYPE
   SYNTAX      Integer32
   MAX-ACCESS  read-only
   STATUS      current
   DESCRIPTION
      "Path: tunnels.status.l2tpTunnels.l2tpV3Manual.remoteCookieLength"
   ::= {sr1645v2TvTmplStatEntry 353566720}

sr1645v2TvTmplStatL2tpV3ManualLocalDataSeq OBJECT-TYPE
   SYNTAX      INTEGER
               {
               off (0),
               nonIp (1),
               on (2)
               }
   MAX-ACCESS  read-only
   STATUS      current
   DESCRIPTION
      "Path: tunnels.status.l2tpTunnels.l2tpV3Manual.localDataSeq

       Possibilities:
               off   (0)
               nonIp   (1)
               on   (2)"
   ::= {sr1645v2TvTmplStatEntry 353632256}

sr1645v2TvTmplStatL2tpV3ManualRemoteDataSeq OBJECT-TYPE
   SYNTAX      INTEGER
               {
               off (0),
               nonIp (1),
               on (2)
               }
   MAX-ACCESS  read-only
   STATUS      current
   DESCRIPTION
      "Path: tunnels.status.l2tpTunnels.l2tpV3Manual.remoteDataSeq

       Possibilities:
               off   (0)
               nonIp   (1)
               on   (2)"
   ::= {sr1645v2TvTmplStatEntry 353697792}

sr1645v2TvTmplStatPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.l2tpTunnels.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TvTmplStatEntry 184614912}

sr1645v2TvTmplStatPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.l2tpTunnels.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TvTmplStatEntry 184680448}

sr1645v2TvTmplStatPppBcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: tunnels.status.l2tpTunnels.ppp.bcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2TvTmplStatEntry 184745984}

sr1645v2TvTmplStatPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: tunnels.status.l2tpTunnels.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2TvTmplStatEntry 185204736}

sr1645v2TvTmplStatPppMyAutUsr OBJECT-TYPE
   SYNTAX      DisplayString
   MAX-ACCESS  read-only
   STATUS      current
   DESCRIPTION
      "Path: tunnels.status.l2tpTunnels.ppp.myAuthenUser"
   ::= {sr1645v2TvTmplStatEntry 185335808}

sr1645v2TvTmplStatPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: tunnels.status.l2tpTunnels.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2TvTmplStatEntry 185270272}


sr1645v2TvTmplSGre OBJECT IDENTIFIER ::= {sr1645v2TvTmpl 22}

sr1645v2TvTmplSGreSSCTable OBJECT-TYPE
   SYNTAX      SEQUENCE OF Sr1645v2TvTmplSGreEntry
   MAX-ACCESS  not-accessible
   STATUS      current
   DESCRIPTION
      ""
   ::= {sr1645v2TvTmplSGre 1}

sr1645v2TvTmplSGreEntry OBJECT-TYPE
   SYNTAX      Sr1645v2TvTmplSGreEntry
   MAX-ACCESS  not-accessible
   STATUS      current
   DESCRIPTION
      ""
   INDEX      { sr1645v2TvTmplSGreTableIx }
   ::= {sr1645v2TvTmplSGreSSCTable 1}

Sr1645v2TvTmplSGreEntry ::=
   SEQUENCE
      {
      sr1645v2TvTmplSGreTableIx
         TableIndex,
      sr1645v2TvTmplSGreName
         DisplayString,
      sr1645v2TvTmplSGreMode
         INTEGER,
      sr1645v2TvTmplSGreIfOperStatus
         INTEGER,
      sr1645v2TvTmplSGreIfLastChange
         TimeTicks,
      sr1645v2TvTmplSGreIfLastChangeDate
         DisplayString,
      sr1645v2TvTmplSGreIpVrfRouter
         DisplayString,
      sr1645v2TvTmplSGreIpAddress
         IpAddress,
      sr1645v2TvTmplSGreIpNetMask
         IpAddress,
      sr1645v2TvTmplSGreIpRemote
         IpAddress,
      sr1645v2TvTmplSGreBrStatus
         INTEGER,
      sr1645v2TvTmplSGreBrSpanningTreePortRole
         INTEGER,
      sr1645v2TvTmplSGreBrSpanningTreePortId
         Integer32,
      sr1645v2TvTmplSGreBrSpanningTreePpCostExtPathCost
         Integer32,
      sr1645v2TvTmplSGreBrSpanningTreePpCostIntPathCost
         Integer32,
      sr1645v2TvTmplSGreBrSpanningTreeExtRpCost
         Integer32,
      sr1645v2TvTmplSGreBrSpanningTreeIntRpCost
         Integer32,
      sr1645v2TvTmplSGreBrSpanningTreeDesBrIdPriority
         Integer32,
      sr1645v2TvTmplSGreBrSpanningTreeDesBrIdMacAddress
         OCTET STRING,
      sr1645v2TvTmplSGreBrSpanningTreeDesPrtId
         Integer32,
      sr1645v2TvTmplSGreBrSpanningTreeDesInt
         INTEGER,
      sr1645v2TvTmplSGreBrSpanningTreeEdgeDetection
         INTEGER,
      sr1645v2TvTmplSGreGreVrfRouter
         DisplayString,
      sr1645v2TvTmplSGreGreLocalIpAddress
         IpAddress,
      sr1645v2TvTmplSGreGreRemoteIpAddress
         IpAddress,
      sr1645v2TvTmplSGreGreVrfRouterV6
         DisplayString,
      sr1645v2TvTmplSGreGreLocalIpV6Address
         Ipv6Address,
      sr1645v2TvTmplSGreGreRemoteIpV6Address
         Ipv6Address,
      sr1645v2TvTmplSGreGreState
         INTEGER,
      sr1645v2TvTmplSGreGreKeepAliveFails
         Counter32,
      sr1645v2TvTmplSGreGreMplsMode
         INTEGER,
      sr1645v2TvTmplSGreGreMplsInLabel
         Integer32,
      sr1645v2TvTmplSGreGreMplsOutLabel
         Integer32
      }

sr1645v2TvTmplSGreTableIx OBJECT-TYPE
   SYNTAX      TableIndex
   MAX-ACCESS  not-accessible
   STATUS      current
   DESCRIPTION
      ""
   ::= {sr1645v2TvTmplSGreEntry 11}

sr1645v2TvTmplSGreName OBJECT-TYPE
   SYNTAX      DisplayString
   MAX-ACCESS  read-only
   STATUS      current
   DESCRIPTION
      "Path: tunnels.status.greTunnels.name"
   ::= {sr1645v2TvTmplSGreEntry 16777216}

sr1645v2TvTmplSGreMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.greTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TvTmplSGreEntry 335544320}

sr1645v2TvTmplSGreIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.greTunnels.ifOperStatus

       Possibilities:
               up   (1)
               down   (2)
               testing   (3)
               unknown   (4)
               dormant   (5)
               notPresent   (6)
               lowerLayerDown   (7)"
   ::= {sr1645v2TvTmplSGreEntry 1795162112}

sr1645v2TvTmplSGreIfLastChange OBJECT-TYPE
   SYNTAX      TimeTicks
   MAX-ACCESS  read-only
   STATUS      current
   DESCRIPTION
      "Path: tunnels.status.greTunnels.ifLastChange

       Time in centi-second."
   ::= {sr1645v2TvTmplSGreEntry 1811939328}

sr1645v2TvTmplSGreIfLastChangeDate OBJECT-TYPE
   SYNTAX      DisplayString
   MAX-ACCESS  read-only
   STATUS      current
   DESCRIPTION
      "Path: tunnels.status.greTunnels.ifLastChangeDate"
   ::= {sr1645v2TvTmplSGreEntry 3070230528}

sr1645v2TvTmplSGreIpVrfRouter OBJECT-TYPE
   SYNTAX      DisplayString
   MAX-ACCESS  read-only
   STATUS      current
   DESCRIPTION
      "Path: tunnels.status.greTunnels.ip.vrfRouter"
   ::= {sr1645v2TvTmplSGreEntry 50397184}

sr1645v2TvTmplSGreIpAddress OBJECT-TYPE
   SYNTAX      IpAddress
   MAX-ACCESS  read-only
   STATUS      current
   DESCRIPTION
      "Path: tunnels.status.greTunnels.ip.address"
   ::= {sr1645v2TvTmplSGreEntry 51380224}

sr1645v2TvTmplSGreIpNetMask OBJECT-TYPE
   SYNTAX      IpAddress
   MAX-ACCESS  read-only
   STATUS      current
   DESCRIPTION
      "Path: tunnels.status.greTunnels.ip.netMask"
   ::= {sr1645v2TvTmplSGreEntry 51445760}

sr1645v2TvTmplSGreIpRemote OBJECT-TYPE
   SYNTAX      IpAddress
   MAX-ACCESS  read-only
   STATUS      current
   DESCRIPTION
      "Path: tunnels.status.greTunnels.ip.remote"
   ::= {sr1645v2TvTmplSGreEntry 51511296}

sr1645v2TvTmplSGreBrStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.greTunnels.bridging.status

       Possibilities:
               disabled   (0)
               discarding   (1)
               learning   (2)
               forwarding   (3)
               backupBlockedIntfDown   (256)
               backupBlockedIntfUp   (259)
               shutdown   (255)"
   ::= {sr1645v2TvTmplSGreEntry 453050368}

sr1645v2TvTmplSGreBrSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.greTunnels.bridging.spanningTree.portRole

       Possibilities:
               none   (0)
               root   (1)
               designated   (2)
               alternate   (3)
               backup   (4)
               disabled   (5)
               master   (6)"
   ::= {sr1645v2TvTmplSGreEntry 453116160}

sr1645v2TvTmplSGreBrSpanningTreePortId OBJECT-TYPE
   SYNTAX      Integer32
   MAX-ACCESS  read-only
   STATUS      current
   DESCRIPTION
      "Path: tunnels.status.greTunnels.bridging.spanningTree.portId"
   ::= {sr1645v2TvTmplSGreEntry 453116416}

sr1645v2TvTmplSGreBrSpanningTreePpCostExtPathCost OBJECT-TYPE
   SYNTAX      Integer32
   MAX-ACCESS  read-only
   STATUS      current
   DESCRIPTION
      "Path: tunnels.status.greTunnels.bridging.spanningTree.portPathCosts.extPathCost"
   ::= {sr1645v2TvTmplSGreEntry 453116673}

sr1645v2TvTmplSGreBrSpanningTreePpCostIntPathCost OBJECT-TYPE
   SYNTAX      Integer32
   MAX-ACCESS  read-only
   STATUS      current
   DESCRIPTION
      "Path: tunnels.status.greTunnels.bridging.spanningTree.portPathCosts.intPathCost"
   ::= {sr1645v2TvTmplSGreEntry 453116674}

sr1645v2TvTmplSGreBrSpanningTreeExtRpCost OBJECT-TYPE
   SYNTAX      Integer32
   MAX-ACCESS  read-only
   STATUS      current
   DESCRIPTION
      "Path: tunnels.status.greTunnels.bridging.spanningTree.extRootPathCost"
   ::= {sr1645v2TvTmplSGreEntry 453116928}

sr1645v2TvTmplSGreBrSpanningTreeIntRpCost OBJECT-TYPE
   SYNTAX      Integer32
   MAX-ACCESS  read-only
   STATUS      current
   DESCRIPTION
      "Path: tunnels.status.greTunnels.bridging.spanningTree.intRootPathCost"
   ::= {sr1645v2TvTmplSGreEntry 453117184}

sr1645v2TvTmplSGreBrSpanningTreeDesBrIdPriority OBJECT-TYPE
   SYNTAX      Integer32
   MAX-ACCESS  read-only
   STATUS      current
   DESCRIPTION
      "Path: tunnels.status.greTunnels.bridging.spanningTree.designatedBridgeId.priority"
   ::= {sr1645v2TvTmplSGreEntry 453117441}

sr1645v2TvTmplSGreBrSpanningTreeDesBrIdMacAddress OBJECT-TYPE
   SYNTAX      OCTET STRING
   MAX-ACCESS  read-only
   STATUS      current
   DESCRIPTION
      "Path: tunnels.status.greTunnels.bridging.spanningTree.designatedBridgeId.macAddress

       MAC address."
   ::= {sr1645v2TvTmplSGreEntry 453117442}

sr1645v2TvTmplSGreBrSpanningTreeDesPrtId OBJECT-TYPE
   SYNTAX      Integer32
   MAX-ACCESS  read-only
   STATUS      current
   DESCRIPTION
      "Path: tunnels.status.greTunnels.bridging.spanningTree.designatedPortId"
   ::= {sr1645v2TvTmplSGreEntry 453117696}

sr1645v2TvTmplSGreBrSpanningTreeDesInt OBJECT-TYPE
   SYNTAX      INTEGER
               {
               no (0),
               yes (1)
               }
   MAX-ACCESS  read-only
   STATUS      current
   DESCRIPTION
      "Path: tunnels.status.greTunnels.bridging.spanningTree.designatedOrInternal

       Possibilities:
               no   (0)
               yes   (1)"
   ::= {sr1645v2TvTmplSGreEntry 453117952}

sr1645v2TvTmplSGreBrSpanningTreeEdgeDetection OBJECT-TYPE
   SYNTAX      INTEGER
               {
               none (0),
               edge (1),
               notEdge (2)
               }
   MAX-ACCESS  read-only
   STATUS      current
   DESCRIPTION
      "Path: tunnels.status.greTunnels.bridging.spanningTree.edgeDetection

       Possibilities:
               none   (0)
               edge   (1)
               notEdge   (2)"
   ::= {sr1645v2TvTmplSGreEntry 453118208}

sr1645v2TvTmplSGreGreVrfRouter OBJECT-TYPE
   SYNTAX      DisplayString
   MAX-ACCESS  read-only
   STATUS      current
   DESCRIPTION
      "Path: tunnels.status.greTunnels.gre.vrfRouter"
   ::= {sr1645v2TvTmplSGreEntry 587661312}

sr1645v2TvTmplSGreGreLocalIpAddress OBJECT-TYPE
   SYNTAX      IpAddress
   MAX-ACCESS  read-only
   STATUS      current
   DESCRIPTION
      "Path: tunnels.status.greTunnels.gre.localIpAddress"
   ::= {sr1645v2TvTmplSGreEntry 587268096}

sr1645v2TvTmplSGreGreRemoteIpAddress OBJECT-TYPE
   SYNTAX      IpAddress
   MAX-ACCESS  read-only
   STATUS      current
   DESCRIPTION
      "Path: tunnels.status.greTunnels.gre.remoteIpAddress"
   ::= {sr1645v2TvTmplSGreEntry 587333632}

sr1645v2TvTmplSGreGreVrfRouterV6 OBJECT-TYPE
   SYNTAX      DisplayString
   MAX-ACCESS  read-only
   STATUS      current
   DESCRIPTION
      "Path: tunnels.status.greTunnels.gre.vrfRouterV6"
   ::= {sr1645v2TvTmplSGreEntry 587857920}

sr1645v2TvTmplSGreGreLocalIpV6Address OBJECT-TYPE
   SYNTAX      Ipv6Address
   MAX-ACCESS  read-only
   STATUS      current
   DESCRIPTION
      "Path: tunnels.status.greTunnels.gre.localIpV6Address

       ipv6 address"
   ::= {sr1645v2TvTmplSGreEntry 587726848}

sr1645v2TvTmplSGreGreRemoteIpV6Address OBJECT-TYPE
   SYNTAX      Ipv6Address
   MAX-ACCESS  read-only
   STATUS      current
   DESCRIPTION
      "Path: tunnels.status.greTunnels.gre.remoteIpV6Address

       ipv6 address"
   ::= {sr1645v2TvTmplSGreEntry 587792384}

sr1645v2TvTmplSGreGreState OBJECT-TYPE
   SYNTAX      INTEGER
               {
               setup (0),
               resolvingRemote (1),
               resolvingLocal (2),
               waitDnsReply (3),
               initParked (4),
               open (5),
               activated (128),
               initActivate (129),
               spoofing (130),
               down (131),
               up (132),
               park (133)
               }
   MAX-ACCESS  read-only
   STATUS      current
   DESCRIPTION
      "Path: tunnels.status.greTunnels.gre.state

       Possibilities:
               setup   (0)
               resolvingRemote   (1)
               resolvingLocal   (2)
               waitDnsReply   (3)
               initParked   (4)
               open   (5)
               activated   (128)
               initActivate   (129)
               spoofing   (130)
               down   (131)
               up   (132)
               park   (133)"
   ::= {sr1645v2TvTmplSGreEntry 587464704}

sr1645v2TvTmplSGreGreKeepAliveFails OBJECT-TYPE
   SYNTAX      Counter32
   MAX-ACCESS  read-only
   STATUS      current
   DESCRIPTION
      "Path: tunnels.status.greTunnels.gre.keepAlive.fails

       32 bit unsigned wrappable counter."
   ::= {sr1645v2TvTmplSGreEntry 587596032}

sr1645v2TvTmplSGreGreMplsMode OBJECT-TYPE
   SYNTAX      INTEGER
               {
               disabled (0),
               enabled (1)
               }
   MAX-ACCESS  read-only
   STATUS      current
   DESCRIPTION
      "Path: tunnels.status.greTunnels.gre.mpls.mode

       Possibilities:
               disabled   (0)
               enabled   (1)"
   ::= {sr1645v2TvTmplSGreEntry 587530496}

sr1645v2TvTmplSGreGreMplsInLabel OBJECT-TYPE
   SYNTAX      Integer32
   MAX-ACCESS  read-only
   STATUS      current
   DESCRIPTION
      "Path: tunnels.status.greTunnels.gre.mpls.inLabel"
   ::= {sr1645v2TvTmplSGreEntry 587530752}

sr1645v2TvTmplSGreGreMplsOutLabel OBJECT-TYPE
   SYNTAX      Integer32
   MAX-ACCESS  read-only
   STATUS      current
   DESCRIPTION
      "Path: tunnels.status.greTunnels.gre.mpls.outLabel"
   ::= {sr1645v2TvTmplSGreEntry 587531008}


sr1645v2TvTmplIpV6toV4 OBJECT IDENTIFIER ::= {sr1645v2TvTmpl 41}

sr1645v2TvTmplIpV6toV4SSCTable OBJECT-TYPE
   SYNTAX      SEQUENCE OF Sr1645v2TvTmplIpV6toV4Entry
   MAX-ACCESS  not-accessible
   STATUS      current
   DESCRIPTION
      ""
   ::= {sr1645v2TvTmplIpV6toV4 1}

sr1645v2TvTmplIpV6toV4Entry OBJECT-TYPE
   SYNTAX      Sr1645v2TvTmplIpV6toV4Entry
   MAX-ACCESS  not-accessible
   STATUS      current
   DESCRIPTION
      ""
   INDEX      { sr1645v2TvTmplIpV6toV4TableIx }
   ::= {sr1645v2TvTmplIpV6toV4SSCTable 1}

Sr1645v2TvTmplIpV6toV4Entry ::=
   SEQUENCE
      {
      sr1645v2TvTmplIpV6toV4TableIx
         TableIndex,
      sr1645v2TvTmplIpV6toV4Name
         DisplayString,
      sr1645v2TvTmplIpV6toV4IfOperStatus
         INTEGER,
      sr1645v2TvTmplIpV6toV4IfLastChange
         TimeTicks,
      sr1645v2TvTmplIpV6toV4IfLastChangeDate
         DisplayString,
      sr1645v2TvTmplIpV6toV4IpV6State
         INTEGER,
      sr1645v2TvTmplIpV6toV4IpV6InterfaceId
         OCTET STRING,
      sr1645v2TvTmplIpV6toV4IpV6LinkMtu
         Integer32,
      sr1645v2TvTmplIpV6toV4IpV6HopLimit
         Integer32,
      sr1645v2TvTmplIpV6toV4IpV6DhcpIaid
         Counter32,
      sr1645v2TvTmplIpV6toV4IpV6RaRcvOption
         Integer32,
      sr1645v2TvTmplIpV6toV4Encaps6To4VrfRouter
         DisplayString,
      sr1645v2TvTmplIpV6toV4Encaps6To4LocalAddress
         IpAddress,
      sr1645v2TvTmplIpV6toV4Encaps6To4RelayAddress
         IpAddress
      }

sr1645v2TvTmplIpV6toV4TableIx OBJECT-TYPE
   SYNTAX      TableIndex
   MAX-ACCESS  not-accessible
   STATUS      current
   DESCRIPTION
      ""
   ::= {sr1645v2TvTmplIpV6toV4Entry 11}

sr1645v2TvTmplIpV6toV4Name OBJECT-TYPE
   SYNTAX      DisplayString
   MAX-ACCESS  read-only
   STATUS      current
   DESCRIPTION
      "Path: tunnels.status.ipV6toV4.name"
   ::= {sr1645v2TvTmplIpV6toV4Entry 16777216}

sr1645v2TvTmplIpV6toV4IfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.ipV6toV4.ifOperStatus

       Possibilities:
               up   (1)
               down   (2)
               testing   (3)
               unknown   (4)
               dormant   (5)
               notPresent   (6)
               lowerLayerDown   (7)"
   ::= {sr1645v2TvTmplIpV6toV4Entry 33554432}

sr1645v2TvTmplIpV6toV4IfLastChange OBJECT-TYPE
   SYNTAX      TimeTicks
   MAX-ACCESS  read-only
   STATUS      current
   DESCRIPTION
      "Path: tunnels.status.ipV6toV4.ifLastChange

       Time in centi-second."
   ::= {sr1645v2TvTmplIpV6toV4Entry 50331648}

sr1645v2TvTmplIpV6toV4IfLastChangeDate OBJECT-TYPE
   SYNTAX      DisplayString
   MAX-ACCESS  read-only
   STATUS      current
   DESCRIPTION
      "Path: tunnels.status.ipV6toV4.ifLastChangeDate"
   ::= {sr1645v2TvTmplIpV6toV4Entry 100663296}

sr1645v2TvTmplIpV6toV4IpV6State OBJECT-TYPE
   SYNTAX      INTEGER
               {
               disabled (0),
               enabled (1)
               }
   MAX-ACCESS  read-only
   STATUS      current
   DESCRIPTION
      "Path: tunnels.status.ipV6toV4.ipV6.state

       Possibilities:
               disabled   (0)
               enabled   (1)"
   ::= {sr1645v2TvTmplIpV6toV4Entry 67174400}

sr1645v2TvTmplIpV6toV4IpV6InterfaceId OBJECT-TYPE
   SYNTAX      OCTET STRING
   MAX-ACCESS  read-only
   STATUS      current
   DESCRIPTION
      "Path: tunnels.status.ipV6toV4.ipV6.interfaceId"
   ::= {sr1645v2TvTmplIpV6toV4Entry 67239936}

sr1645v2TvTmplIpV6toV4IpV6LinkMtu OBJECT-TYPE
   SYNTAX      Integer32
   MAX-ACCESS  read-only
   STATUS      current
   DESCRIPTION
      "Path: tunnels.status.ipV6toV4.ipV6.linkMtu"
   ::= {sr1645v2TvTmplIpV6toV4Entry 67371008}

sr1645v2TvTmplIpV6toV4IpV6HopLimit OBJECT-TYPE
   SYNTAX      Integer32
   MAX-ACCESS  read-only
   STATUS      current
   DESCRIPTION
      "Path: tunnels.status.ipV6toV4.ipV6.hopLimit"
   ::= {sr1645v2TvTmplIpV6toV4Entry 67436544}

sr1645v2TvTmplIpV6toV4IpV6DhcpIaid OBJECT-TYPE
   SYNTAX      Counter32
   MAX-ACCESS  read-only
   STATUS      current
   DESCRIPTION
      "Path: tunnels.status.ipV6toV4.ipV6.dhcp.iaid

       32 bit unsigned wrappable counter."
   ::= {sr1645v2TvTmplIpV6toV4Entry 67502336}

sr1645v2TvTmplIpV6toV4IpV6RaRcvOption OBJECT-TYPE
   SYNTAX      Integer32
   MAX-ACCESS  read-only
   STATUS      current
   DESCRIPTION
      "Path: tunnels.status.ipV6toV4.ipV6.raRcvOption

       Bit meanings:
               bit 0 = linkMtu,
               bit 1 = srcLinkLayer,
               bit 2 = prefixInfo,
               bit 3 = rdnss,
               bit 4 = dnssl"
   ::= {sr1645v2TvTmplIpV6toV4Entry 67567616}

sr1645v2TvTmplIpV6toV4Encaps6To4VrfRouter OBJECT-TYPE
   SYNTAX      DisplayString
   MAX-ACCESS  read-only
   STATUS      current
   DESCRIPTION
      "Path: tunnels.status.ipV6toV4.encaps6To4.vrfRouter"
   ::= {sr1645v2TvTmplIpV6toV4Entry 83951616}

sr1645v2TvTmplIpV6toV4Encaps6To4LocalAddress OBJECT-TYPE
   SYNTAX      IpAddress
   MAX-ACCESS  read-only
   STATUS      current
   DESCRIPTION
      "Path: tunnels.status.ipV6toV4.encaps6To4.localAddress"
   ::= {sr1645v2TvTmplIpV6toV4Entry 84017152}

sr1645v2TvTmplIpV6toV4Encaps6To4RelayAddress OBJECT-TYPE
   SYNTAX      IpAddress
   MAX-ACCESS  read-only
   STATUS      current
   DESCRIPTION
      "Path: tunnels.status.ipV6toV4.encaps6To4.relayAddress"
   ::= {sr1645v2TvTmplIpV6toV4Entry 84082688}

sr1645v2TvTmplIpV6toV4IpV6Addresses OBJECT-TYPE
   SYNTAX      SEQUENCE OF Sr1645v2TvTmplIpV6toV4IpV6AddressesEntry
   MAX-ACCESS  not-accessible
   STATUS      current
   DESCRIPTION
      ""
   ::= {sr1645v2TvTmplIpV6toV4 67305472}

sr1645v2TvTmplIpV6toV4IpV6AddressesEntry OBJECT-TYPE
   SYNTAX      Sr1645v2TvTmplIpV6toV4IpV6AddressesEntry
   MAX-ACCESS  not-accessible
   STATUS      current
   DESCRIPTION
      ""
   INDEX      { sr1645v2TvTmplIpV6toV4TableIx,
                sr1645v2TvTmplIpV6toV4IpV6AddressesTableIx }
   ::= {sr1645v2TvTmplIpV6toV4IpV6Addresses 1}

Sr1645v2TvTmplIpV6toV4IpV6AddressesEntry ::=
   SEQUENCE
      {
      sr1645v2TvTmplIpV6toV4IpV6AddressesTableIx
         TableIndex,
      sr1645v2TvTmplIpV6toV4IpV6AddressesAddress
         Ipv6Address,
      sr1645v2TvTmplIpV6toV4IpV6AddressesPrefixLength
         Integer32,
      sr1645v2TvTmplIpV6toV4IpV6AddressesStatus
         INTEGER,
      sr1645v2TvTmplIpV6toV4IpV6AddressesOrigin
         INTEGER,
      sr1645v2TvTmplIpV6toV4IpV6AddressesFlagsInterfaceId
         INTEGER,
      sr1645v2TvTmplIpV6toV4IpV6AddressesFlagsAnycast
         INTEGER,
      sr1645v2TvTmplIpV6toV4IpV6AddressesTimersValidLifeTime
         TimeTicks,
      sr1645v2TvTmplIpV6toV4IpV6AddressesTimersPrefLifeTime
         TimeTicks
      }

sr1645v2TvTmplIpV6toV4IpV6AddressesTableIx OBJECT-TYPE
   SYNTAX      TableIndex
   MAX-ACCESS  not-accessible
   STATUS      current
   DESCRIPTION
      ""
   ::= {sr1645v2TvTmplIpV6toV4IpV6AddressesEntry 11}

sr1645v2TvTmplIpV6toV4IpV6AddressesAddress OBJECT-TYPE
   SYNTAX      Ipv6Address
   MAX-ACCESS  read-only
   STATUS      current
   DESCRIPTION
      "Path: tunnels.status.ipV6toV4.ipV6.addresses.address

       ipv6 address"
   ::= {sr1645v2TvTmplIpV6toV4IpV6AddressesEntry 16777216}

sr1645v2TvTmplIpV6toV4IpV6AddressesPrefixLength OBJECT-TYPE
   SYNTAX      Integer32
   MAX-ACCESS  read-only
   STATUS      current
   DESCRIPTION
      "Path: tunnels.status.ipV6toV4.ipV6.addresses.prefixLength"
   ::= {sr1645v2TvTmplIpV6toV4IpV6AddressesEntry 33554432}

sr1645v2TvTmplIpV6toV4IpV6AddressesStatus OBJECT-TYPE
   SYNTAX      INTEGER
               {
               invalid (0),
               tentative (1),
               deprecated (2),
               preferred (3)
               }
   MAX-ACCESS  read-only
   STATUS      current
   DESCRIPTION
      "Path: tunnels.status.ipV6toV4.ipV6.addresses.status

       Possibilities:
               invalid   (0)
               tentative   (1)
               deprecated   (2)
               preferred   (3)"
   ::= {sr1645v2TvTmplIpV6toV4IpV6AddressesEntry 50331648}

sr1645v2TvTmplIpV6toV4IpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: tunnels.status.ipV6toV4.ipV6.addresses.origin

       Possibilities:
               unknown   (0)
               manual   (1)
               generalPrefix   (2)
               statelessAuto   (3)
               statefullAuto   (4)"
   ::= {sr1645v2TvTmplIpV6toV4IpV6AddressesEntry 67108864}

sr1645v2TvTmplIpV6toV4IpV6AddressesFlagsInterfaceId OBJECT-TYPE
   SYNTAX      INTEGER
               {
               no (0),
               yes (1)
               }
   MAX-ACCESS  read-only
   STATUS      current
   DESCRIPTION
      "Path: tunnels.status.ipV6toV4.ipV6.addresses.flags.interfaceId

       Possibilities:
               no   (0)
               yes   (1)"
   ::= {sr1645v2TvTmplIpV6toV4IpV6AddressesEntry 83951616}

sr1645v2TvTmplIpV6toV4IpV6AddressesFlagsAnycast OBJECT-TYPE
   SYNTAX      INTEGER
               {
               no (0),
               yes (1)
               }
   MAX-ACCESS  read-only
   STATUS      current
   DESCRIPTION
      "Path: tunnels.status.ipV6toV4.ipV6.addresses.flags.anycast

       Possibilities:
               no   (0)
               yes   (1)"
   ::= {sr1645v2TvTmplIpV6toV4IpV6AddressesEntry 84017152}

sr1645v2TvTmplIpV6toV4IpV6AddressesTimersValidLifeTime OBJECT-TYPE
   SYNTAX      TimeTicks
   MAX-ACCESS  read-only
   STATUS      current
   DESCRIPTION
      "Path: tunnels.status.ipV6toV4.ipV6.addresses.timers.validLifeTime

       Time in centi-second."
   ::= {sr1645v2TvTmplIpV6toV4IpV6AddressesEntry 100794368}

sr1645v2TvTmplIpV6toV4IpV6AddressesTimersPrefLifeTime OBJECT-TYPE
   SYNTAX      TimeTicks
   MAX-ACCESS  read-only
   STATUS      current
   DESCRIPTION
      "Path: tunnels.status.ipV6toV4.ipV6.addresses.timers.prefLifeTime

       Time in centi-second."
   ::= {sr1645v2TvTmplIpV6toV4IpV6AddressesEntry 100728832}

sr1645v2TvTmplIpV6toV4Encaps6To4RemoteAddresses OBJECT-TYPE
   SYNTAX      SEQUENCE OF Sr1645v2TvTmplIpV6toV4Encaps6To4RemoteAddressesEntry
   MAX-ACCESS  not-accessible
   STATUS      current
   DESCRIPTION
      ""
   ::= {sr1645v2TvTmplIpV6toV4 84148224}

sr1645v2TvTmplIpV6toV4Encaps6To4RemoteAddressesEntry OBJECT-TYPE
   SYNTAX      Sr1645v2TvTmplIpV6toV4Encaps6To4RemoteAddressesEntry
   MAX-ACCESS  not-accessible
   STATUS      current
   DESCRIPTION
      ""
   INDEX      { sr1645v2TvTmplIpV6toV4TableIx,
                sr1645v2TvTmplIpV6toV4Encaps6To4RemoteAddressesTableIx }
   ::= {sr1645v2TvTmplIpV6toV4Encaps6To4RemoteAddresses 1}

Sr1645v2TvTmplIpV6toV4Encaps6To4RemoteAddressesEntry ::=
   SEQUENCE
      {
      sr1645v2TvTmplIpV6toV4Encaps6To4RemoteAddressesTableIx
         TableIndex,
      sr1645v2TvTmplIpV6toV4Encaps6To4RemoteAddressesAddress
         IpAddress
      }

sr1645v2TvTmplIpV6toV4Encaps6To4RemoteAddressesTableIx OBJECT-TYPE
   SYNTAX      TableIndex
   MAX-ACCESS  not-accessible
   STATUS      current
   DESCRIPTION
      ""
   ::= {sr1645v2TvTmplIpV6toV4Encaps6To4RemoteAddressesEntry 11}

sr1645v2TvTmplIpV6toV4Encaps6To4RemoteAddressesAddress OBJECT-TYPE
   SYNTAX      IpAddress
   MAX-ACCESS  read-only
   STATUS      current
   DESCRIPTION
      "Path: tunnels.status.ipV6toV4.encaps6To4.remoteAddresses.address"
   ::= {sr1645v2TvTmplIpV6toV4Encaps6To4RemoteAddressesEntry 16777216}


sr1645v2TvTmplVxLanTunnels OBJECT IDENTIFIER ::= {sr1645v2TvTmpl 44}

sr1645v2TvTmplVxLanTunnelsSSCTable OBJECT-TYPE
   SYNTAX      SEQUENCE OF Sr1645v2TvTmplVxLanTunnelsEntry
   MAX-ACCESS  not-accessible
   STATUS      current
   DESCRIPTION
      ""
   ::= {sr1645v2TvTmplVxLanTunnels 1}

sr1645v2TvTmplVxLanTunnelsEntry OBJECT-TYPE
   SYNTAX      Sr1645v2TvTmplVxLanTunnelsEntry
   MAX-ACCESS  not-accessible
   STATUS      current
   DESCRIPTION
      ""
   INDEX      { sr1645v2TvTmplVxLanTunnelsTableIx }
   ::= {sr1645v2TvTmplVxLanTunnelsSSCTable 1}

Sr1645v2TvTmplVxLanTunnelsEntry ::=
   SEQUENCE
      {
      sr1645v2TvTmplVxLanTunnelsTableIx
         TableIndex,
      sr1645v2TvTmplVxLanTunnelsName
         DisplayString,
      sr1645v2TvTmplVxLanTunnelsMode
         INTEGER,
      sr1645v2TvTmplVxLanTunnelsIfOperStatus
         INTEGER,
      sr1645v2TvTmplVxLanTunnelsIfLastChange
         TimeTicks,
      sr1645v2TvTmplVxLanTunnelsIfLastChangeDate
         DisplayString,
      sr1645v2TvTmplVxLanTunnelsBrStatus
         INTEGER,
      sr1645v2TvTmplVxLanTunnelsBrSpanningTreePortRole
         INTEGER,
      sr1645v2TvTmplVxLanTunnelsBrSpanningTreePortId
         Integer32,
      sr1645v2TvTmplVxLanTunnelsBrSpanningTreePpCostExtPathCost
         Integer32,
      sr1645v2TvTmplVxLanTunnelsBrSpanningTreePpCostIntPathCost
         Integer32,
      sr1645v2TvTmplVxLanTunnelsBrSpanningTreeExtRpCost
         Integer32,
      sr1645v2TvTmplVxLanTunnelsBrSpanningTreeIntRpCost
         Integer32,
      sr1645v2TvTmplVxLanTunnelsBrSpanningTreeDesBrIdPriority
         Integer32,
      sr1645v2TvTmplVxLanTunnelsBrSpanningTreeDesBrIdMacAddress
         OCTET STRING,
      sr1645v2TvTmplVxLanTunnelsBrSpanningTreeDesPrtId
         Integer32,
      sr1645v2TvTmplVxLanTunnelsBrSpanningTreeDesInt
         INTEGER,
      sr1645v2TvTmplVxLanTunnelsBrSpanningTreeEdgeDetection
         INTEGER
      }

sr1645v2TvTmplVxLanTunnelsTableIx OBJECT-TYPE
   SYNTAX      TableIndex
   MAX-ACCESS  not-accessible
   STATUS      current
   DESCRIPTION
      ""
   ::= {sr1645v2TvTmplVxLanTunnelsEntry 11}

sr1645v2TvTmplVxLanTunnelsName OBJECT-TYPE
   SYNTAX      DisplayString
   MAX-ACCESS  read-only
   STATUS      current
   DESCRIPTION
      "Path: tunnels.status.vxLanTunnels.name"
   ::= {sr1645v2TvTmplVxLanTunnelsEntry 16777216}

sr1645v2TvTmplVxLanTunnelsMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: tunnels.status.vxLanTunnels.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2TvTmplVxLanTunnelsEntry 335544320}

sr1645v2TvTmplVxLanTunnelsIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: tunnels.status.vxLanTunnels.ifOperStatus

       Possibilities:
               up   (1)
               down   (2)
               testing   (3)
               unknown   (4)
               dormant   (5)
               notPresent   (6)
               lowerLayerDown   (7)"
   ::= {sr1645v2TvTmplVxLanTunnelsEntry 1795162112}

sr1645v2TvTmplVxLanTunnelsIfLastChange OBJECT-TYPE
   SYNTAX      TimeTicks
   MAX-ACCESS  read-only
   STATUS      current
   DESCRIPTION
      "Path: tunnels.status.vxLanTunnels.ifLastChange

       Time in centi-second."
   ::= {sr1645v2TvTmplVxLanTunnelsEntry 1811939328}

sr1645v2TvTmplVxLanTunnelsIfLastChangeDate OBJECT-TYPE
   SYNTAX      DisplayString
   MAX-ACCESS  read-only
   STATUS      current
   DESCRIPTION
      "Path: tunnels.status.vxLanTunnels.ifLastChangeDate"
   ::= {sr1645v2TvTmplVxLanTunnelsEntry 3070230528}

sr1645v2TvTmplVxLanTunnelsBrStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: tunnels.status.vxLanTunnels.bridging.status

       Possibilities:
               disabled   (0)
               discarding   (1)
               learning   (2)
               forwarding   (3)
               backupBlockedIntfDown   (256)
               backupBlockedIntfUp   (259)
               shutdown   (255)"
   ::= {sr1645v2TvTmplVxLanTunnelsEntry 453050368}

sr1645v2TvTmplVxLanTunnelsBrSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: tunnels.status.vxLanTunnels.bridging.spanningTree.portRole

       Possibilities:
               none   (0)
               root   (1)
               designated   (2)
               alternate   (3)
               backup   (4)
               disabled   (5)
               master   (6)"
   ::= {sr1645v2TvTmplVxLanTunnelsEntry 453116160}

sr1645v2TvTmplVxLanTunnelsBrSpanningTreePortId OBJECT-TYPE
   SYNTAX      Integer32
   MAX-ACCESS  read-only
   STATUS      current
   DESCRIPTION
      "Path: tunnels.status.vxLanTunnels.bridging.spanningTree.portId"
   ::= {sr1645v2TvTmplVxLanTunnelsEntry 453116416}

sr1645v2TvTmplVxLanTunnelsBrSpanningTreePpCostExtPathCost OBJECT-TYPE
   SYNTAX      Integer32
   MAX-ACCESS  read-only
   STATUS      current
   DESCRIPTION
      "Path: tunnels.status.vxLanTunnels.bridging.spanningTree.portPathCosts.extPathCost"
   ::= {sr1645v2TvTmplVxLanTunnelsEntry 453116673}

sr1645v2TvTmplVxLanTunnelsBrSpanningTreePpCostIntPathCost OBJECT-TYPE
   SYNTAX      Integer32
   MAX-ACCESS  read-only
   STATUS      current
   DESCRIPTION
      "Path: tunnels.status.vxLanTunnels.bridging.spanningTree.portPathCosts.intPathCost"
   ::= {sr1645v2TvTmplVxLanTunnelsEntry 453116674}

sr1645v2TvTmplVxLanTunnelsBrSpanningTreeExtRpCost OBJECT-TYPE
   SYNTAX      Integer32
   MAX-ACCESS  read-only
   STATUS      current
   DESCRIPTION
      "Path: tunnels.status.vxLanTunnels.bridging.spanningTree.extRootPathCost"
   ::= {sr1645v2TvTmplVxLanTunnelsEntry 453116928}

sr1645v2TvTmplVxLanTunnelsBrSpanningTreeIntRpCost OBJECT-TYPE
   SYNTAX      Integer32
   MAX-ACCESS  read-only
   STATUS      current
   DESCRIPTION
      "Path: tunnels.status.vxLanTunnels.bridging.spanningTree.intRootPathCost"
   ::= {sr1645v2TvTmplVxLanTunnelsEntry 453117184}

sr1645v2TvTmplVxLanTunnelsBrSpanningTreeDesBrIdPriority OBJECT-TYPE
   SYNTAX      Integer32
   MAX-ACCESS  read-only
   STATUS      current
   DESCRIPTION
      "Path: tunnels.status.vxLanTunnels.bridging.spanningTree.designatedBridgeId.priority"
   ::= {sr1645v2TvTmplVxLanTunnelsEntry 453117441}

sr1645v2TvTmplVxLanTunnelsBrSpanningTreeDesBrIdMacAddress OBJECT-TYPE
   SYNTAX      OCTET STRING
   MAX-ACCESS  read-only
   STATUS      current
   DESCRIPTION
      "Path: tunnels.status.vxLanTunnels.bridging.spanningTree.designatedBridgeId.macAddress

       MAC address."
   ::= {sr1645v2TvTmplVxLanTunnelsEntry 453117442}

sr1645v2TvTmplVxLanTunnelsBrSpanningTreeDesPrtId OBJECT-TYPE
   SYNTAX      Integer32
   MAX-ACCESS  read-only
   STATUS      current
   DESCRIPTION
      "Path: tunnels.status.vxLanTunnels.bridging.spanningTree.designatedPortId"
   ::= {sr1645v2TvTmplVxLanTunnelsEntry 453117696}

sr1645v2TvTmplVxLanTunnelsBrSpanningTreeDesInt OBJECT-TYPE
   SYNTAX      INTEGER
               {
               no (0),
               yes (1)
               }
   MAX-ACCESS  read-only
   STATUS      current
   DESCRIPTION
      "Path: tunnels.status.vxLanTunnels.bridging.spanningTree.designatedOrInternal

       Possibilities:
               no   (0)
               yes   (1)"
   ::= {sr1645v2TvTmplVxLanTunnelsEntry 453117952}

sr1645v2TvTmplVxLanTunnelsBrSpanningTreeEdgeDetection OBJECT-TYPE
   SYNTAX      INTEGER
               {
               none (0),
               edge (1),
               notEdge (2)
               }
   MAX-ACCESS  read-only
   STATUS      current
   DESCRIPTION
      "Path: tunnels.status.vxLanTunnels.bridging.spanningTree.edgeDetection

       Possibilities:
               none   (0)
               edge   (1)
               notEdge   (2)"
   ::= {sr1645v2TvTmplVxLanTunnelsEntry 453118208}



pr1645v2TvTmpl OBJECT IDENTIFIER ::= {r1645v2TvTmpl 12}


pr1645v2TvTmplPerf OBJECT IDENTIFIER ::= {pr1645v2TvTmpl 3}

pr1645v2TvTmplPerfSSCTable OBJECT-TYPE
   SYNTAX      SEQUENCE OF Pr1645v2TvTmplPerfEntry
   MAX-ACCESS  not-accessible
   STATUS      current
   DESCRIPTION
      ""
   ::= {pr1645v2TvTmplPerf 1}

pr1645v2TvTmplPerfEntry OBJECT-TYPE
   SYNTAX      Pr1645v2TvTmplPerfEntry
   MAX-ACCESS  not-accessible
   STATUS      current
   DESCRIPTION
      ""
   INDEX      { pr1645v2TvTmplPerfTableIx }
   ::= {pr1645v2TvTmplPerfSSCTable 1}

Pr1645v2TvTmplPerfEntry ::=
   SEQUENCE
      {
      pr1645v2TvTmplPerfTableIx
         TableIndex,
      pr1645v2TvTmplPerfName
         DisplayString,
      pr1645v2TvTmplPerfMCInOctets
         Counter64,
      pr1645v2TvTmplPerfMCInUcast
         Counter64,
      pr1645v2TvTmplPerfMCInNUcastPkts
         Counter64,
      pr1645v2TvTmplPerfMCInBcastPkts
         Counter64,
      pr1645v2TvTmplPerfMCInMcastPkts
         Counter64,
      pr1645v2TvTmplPerfMCInDiscards
         Counter64,
      pr1645v2TvTmplPerfMCInErrors
         Counter64,
      pr1645v2TvTmplPerfMCInUnknownProtos
         Counter64,
      pr1645v2TvTmplPerfMCInDropEx
         Counter64,
      pr1645v2TvTmplPerfMCInDropNoMac
         Counter64,
      pr1645v2TvTmplPerfMCInDropNUCast
         Counter64,
      pr1645v2TvTmplPerfMCInDropFilter
         Counter64,
      pr1645v2TvTmplPerfMCInBandwidth15sec
         Integer32,
      pr1645v2TvTmplPerfMCInBandwidth30sec
         Integer32,
      pr1645v2TvTmplPerfMCInBandwidth1min
         Integer32,
      pr1645v2TvTmplPerfMCInBandwidth2min
         Integer32,
      pr1645v2TvTmplPerfMCInBandwidth5min
         Integer32,
      pr1645v2TvTmplPerfMCOutOctets
         Counter64,
      pr1645v2TvTmplPerfMCOutUcastPkts
         Counter64,
      pr1645v2TvTmplPerfMCOutNUcastPkts
         Counter64,
      pr1645v2TvTmplPerfMCOutBcastPkts
         Counter64,
      pr1645v2TvTmplPerfMCOutMcastPkts
         Counter64,
      pr1645v2TvTmplPerfMCOutDiscards
         Counter64,
      pr1645v2TvTmplPerfMCOutErrors
         Counter64,
      pr1645v2TvTmplPerfMCOutQLen
         Counter32,
      pr1645v2TvTmplPerfMCOutDropEx
         Counter64,
      pr1645v2TvTmplPerfMCOutDropNoArp
         Counter64,
      pr1645v2TvTmplPerfMCOutDropFilter
         Counter64,
      pr1645v2TvTmplPerfMCOutBandwidth15sec
         Integer32,
      pr1645v2TvTmplPerfMCOutBandwidth30sec
         Integer32,
      pr1645v2TvTmplPerfMCOutBandwidth1min
         Integer32,
      pr1645v2TvTmplPerfMCOutBandwidth2min
         Integer32,
      pr1645v2TvTmplPerfMCOutBandwidth5min
         Integer32,
      pr1645v2TvTmplPerfControlHelloSent
         Gauge32,
      pr1645v2TvTmplPerfControlHelloRcvd
         Gauge32,
      pr1645v2TvTmplPerfControlAckSent
         Gauge32,
      pr1645v2TvTmplPerfControlAckRcvd
         Gauge32,
      pr1645v2TvTmplPerfControlDuplicateRcvd
         Gauge32,
      pr1645v2TvTmplPerfControlOutOfSeqRcvd
         Gauge32,
      pr1645v2TvTmplPerfControlRetransmission
         Gauge32,
      pr1645v2TvTmplPerfControlAuthenFailure
         Gauge32,
      pr1645v2TvTmplPerfPppPort
         Counter32,
      pr1645v2TvTmplPerfPppLcpUp
         Counter32,
      pr1645v2TvTmplPerfPppLcpDown
         Counter32,
      pr1645v2TvTmplPerfPppLcpOpen
         Counter32,
      pr1645v2TvTmplPerfPppLcpClose
         Counter32,
      pr1645v2TvTmplPerfPppLcpToP
         Counter32,
      pr1645v2TvTmplPerfPppLcpToM
         Counter32,
      pr1645v2TvTmplPerfPppLcpRcrP
         Counter32,
      pr1645v2TvTmplPerfPppLcpRcrM
         Counter32,
      pr1645v2TvTmplPerfPppLcpRca
         Counter32,
      pr1645v2TvTmplPerfPppLcpRcn
         Counter32,
      pr1645v2TvTmplPerfPppLcpRtr
         Counter32,
      pr1645v2TvTmplPerfPppLcpRta
         Counter32,
      pr1645v2TvTmplPerfPppLcpRuc
         Counter32,
      pr1645v2TvTmplPerfPppLcpRxjP
         Counter32,
      pr1645v2TvTmplPerfPppLcpRxjM
         Counter32,
      pr1645v2TvTmplPerfPppLcpRxr
         Counter32,
      pr1645v2TvTmplPerfPppLcpRrr
         Counter32,
      pr1645v2TvTmplPerfPppLcpRra
         Counter32,
      pr1645v2TvTmplPerfPppLcpDf
         Counter32,
      pr1645v2TvTmplPerfPppLcpIntClose
         Counter32,
      pr1645v2TvTmplPerfPppLcpLm
         Counter32,
      pr1645v2TvTmplPerfPppLcpLmM
         Counter32,
      pr1645v2TvTmplPerfPppAuthMyNegotiated
         INTEGER,
      pr1645v2TvTmplPerfPppAuthMyConfigured
         INTEGER,
      pr1645v2TvTmplPerfPppAuthHisRequested
         INTEGER,
      pr1645v2TvTmplPerfPppAuthRxChallenge
         Counter32,
      pr1645v2TvTmplPerfPppAuthRxResponse
         Counter32,
      pr1645v2TvTmplPerfPppAuthRxSuccess
         Counter32,
      pr1645v2TvTmplPerfPppAuthRxFailure
         Counter32,
      pr1645v2TvTmplPerfPppAuthChallengeTO
         Counter32,
      pr1645v2TvTmplPerfPppAuthResponseTO
         Counter32,
      pr1645v2TvTmplPerfPppAuthTxChallenge
         Counter32,
      pr1645v2TvTmplPerfPppAuthRxRadiusSuccess
         Counter32,
      pr1645v2TvTmplPerfPppAuthRxRadiusFailure
         Counter32,
      pr1645v2TvTmplPerfPppAuthTxSuccess
         Counter32,
      pr1645v2TvTmplPerfPppAuthTxFailure
         Counter32,
      pr1645v2TvTmplPerfPppAuthUnexpected
         Counter32,
      pr1645v2TvTmplPerfPppIpcpUp
         Counter32,
      pr1645v2TvTmplPerfPppIpcpDown
         Counter32,
      pr1645v2TvTmplPerfPppIpcpOpen
         Counter32,
      pr1645v2TvTmplPerfPppIpcpClose
         Counter32,
      pr1645v2TvTmplPerfPppIpcpToP
         Counter32,
      pr1645v2TvTmplPerfPppIpcpToM
         Counter32,
      pr1645v2TvTmplPerfPppIpcpRcrP
         Counter32,
      pr1645v2TvTmplPerfPppIpcpRcrM
         Counter32,
      pr1645v2TvTmplPerfPppIpcpRca
         Counter32,
      pr1645v2TvTmplPerfPppIpcpRcn
         Counter32,
      pr1645v2TvTmplPerfPppIpcpRtr
         Counter32,
      pr1645v2TvTmplPerfPppIpcpRta
         Counter32,
      pr1645v2TvTmplPerfPppIpcpRuc
         Counter32,
      pr1645v2TvTmplPerfPppIpcpRxjP
         Counter32,
      pr1645v2TvTmplPerfPppIpcpRxjM
         Counter32,
      pr1645v2TvTmplPerfPppIpcpRxr
         Counter32,
      pr1645v2TvTmplPerfPppIpcpRrr
         Counter32,
      pr1645v2TvTmplPerfPppIpcpRra
         Counter32,
      pr1645v2TvTmplPerfPppIpcpDf
         Counter32,
      pr1645v2TvTmplPerfPppIpcpIntClose
         Counter32,
      pr1645v2TvTmplPerfPppIpcpLm
         Counter32,
      pr1645v2TvTmplPerfPppIpcpLmM
         Counter32,
      pr1645v2TvTmplPerfPppLinkMonitoringRequestsSent
         Gauge32,
      pr1645v2TvTmplPerfPppLinkMonitoringRepliesRcvd
         Gauge32,
      pr1645v2TvTmplPerfPppLinkMonitoringRequestsRcvd
         Gauge32,
      pr1645v2TvTmplPerfPppLinkMonitoringRepliesSent
         Gauge32
      }

pr1645v2TvTmplPerfTableIx OBJECT-TYPE
   SYNTAX      TableIndex
   MAX-ACCESS  not-accessible
   STATUS      current
   DESCRIPTION
      ""
   ::= {pr1645v2TvTmplPerfEntry 11}

pr1645v2TvTmplPerfName OBJECT-TYPE
   SYNTAX      DisplayString
   MAX-ACCESS  read-only
   STATUS      current
   DESCRIPTION
      "Path: tunnels.performance.l2tpTunnels.name"
   ::= {pr1645v2TvTmplPerfEntry 16777216}

pr1645v2TvTmplPerfMCInOctets OBJECT-TYPE
   SYNTAX      Counter64
   MAX-ACCESS  read-only
   STATUS      current
   DESCRIPTION
      "Path: tunnels.performance.l2tpTunnels.mibCounters.ifInOctets

       64 bit unsigned wrappable counter."
   ::= {pr1645v2TvTmplPerfEntry 40697856}

pr1645v2TvTmplPerfMCInUcast OBJECT-TYPE
   SYNTAX      Counter64
   MAX-ACCESS  read-only
   STATUS      current
   DESCRIPTION
      "Path: tunnels.performance.l2tpTunnels.mibCounters.ifInUcastPkts

       64 bit unsigned wrappable counter."
   ::= {pr1645v2TvTmplPerfEntry 40763392}

pr1645v2TvTmplPerfMCInNUcastPkts OBJECT-TYPE
   SYNTAX      Counter64
   MAX-ACCESS  read-only
   STATUS      current
   DESCRIPTION
      "Path: tunnels.performance.l2tpTunnels.mibCounters.ifInNUcastPkts

       64 bit unsigned wrappable counter."
   ::= {pr1645v2TvTmplPerfEntry 40828928}

pr1645v2TvTmplPerfMCInBcastPkts OBJECT-TYPE
   SYNTAX      Counter64
   MAX-ACCESS  read-only
   STATUS      current
   DESCRIPTION
      "Path: tunnels.performance.l2tpTunnels.mibCounters.ifInBcastPkts

       64 bit unsigned wrappable counter."
   ::= {pr1645v2TvTmplPerfEntry 47382528}

pr1645v2TvTmplPerfMCInMcastPkts OBJECT-TYPE
   SYNTAX      Counter64
   MAX-ACCESS  read-only
   STATUS      current
   DESCRIPTION
      "Path: tunnels.performance.l2tpTunnels.mibCounters.ifInMcastPkts

       64 bit unsigned wrappable counter."
   ::= {pr1645v2TvTmplPerfEntry 48037888}

pr1645v2TvTmplPerfMCInDiscards OBJECT-TYPE
   SYNTAX      Counter64
   MAX-ACCESS  read-only
   STATUS      current
   DESCRIPTION
      "Path: tunnels.performance.l2tpTunnels.mibCounters.ifInDiscards

       64 bit unsigned wrappable counter."
   ::= {pr1645v2TvTmplPerfEntry 40894464}

pr1645v2TvTmplPerfMCInErrors OBJECT-TYPE
   SYNTAX      Counter64
   MAX-ACCESS  read-only
   STATUS      current
   DESCRIPTION
      "Path: tunnels.performance.l2tpTunnels.mibCounters.ifInErrors

       64 bit unsigned wrappable counter."
   ::= {pr1645v2TvTmplPerfEntry 40960000}

pr1645v2TvTmplPerfMCInUnknownProtos OBJECT-TYPE
   SYNTAX      Counter64
   MAX-ACCESS  read-only
   STATUS      current
   DESCRIPTION
      "Path: tunnels.performance.l2tpTunnels.mibCounters.ifInUnknownProtos

       64 bit unsigned wrappable counter."
   ::= {pr1645v2TvTmplPerfEntry 41025536}

pr1645v2TvTmplPerfMCInDropEx OBJECT-TYPE
   SYNTAX      Counter64
   MAX-ACCESS  read-only
   STATUS      current
   DESCRIPTION
      "Path: tunnels.performance.l2tpTunnels.mibCounters.ifInDropLevelExceeded

       64 bit unsigned wrappable counter."
   ::= {pr1645v2TvTmplPerfEntry 42074112}

pr1645v2TvTmplPerfMCInDropNoMac OBJECT-TYPE
   SYNTAX      Counter64
   MAX-ACCESS  read-only
   STATUS      current
   DESCRIPTION
      "Path: tunnels.performance.l2tpTunnels.mibCounters.ifInDiscardsNoMacFit

       64 bit unsigned wrappable counter."
   ::= {pr1645v2TvTmplPerfEntry 42270720}

pr1645v2TvTmplPerfMCInDropNUCast OBJECT-TYPE
   SYNTAX      Counter64
   MAX-ACCESS  read-only
   STATUS      current
   DESCRIPTION
      "Path: tunnels.performance.l2tpTunnels.mibCounters.ifInDiscardsNUCast

       64 bit unsigned wrappable counter."
   ::= {pr1645v2TvTmplPerfEntry 42467328}

pr1645v2TvTmplPerfMCInDropFilter OBJECT-TYPE
   SYNTAX      Counter64
   MAX-ACCESS  read-only
   STATUS      current
   DESCRIPTION
      "Path: tunnels.performance.l2tpTunnels.mibCounters.ifInDiscardsFilter

       64 bit unsigned wrappable counter."
   ::= {pr1645v2TvTmplPerfEntry 42532864}

pr1645v2TvTmplPerfMCInBandwidth15sec OBJECT-TYPE
   SYNTAX      Integer32
   MAX-ACCESS  read-only
   STATUS      current
   DESCRIPTION
      "Path: tunnels.performance.l2tpTunnels.mibCounters.ifInBandwidth.15sec

       unit name = bps
       formula = 8 * ; 8 /"
   ::= {pr1645v2TvTmplPerfEntry 45417728}

pr1645v2TvTmplPerfMCInBandwidth30sec OBJECT-TYPE
   SYNTAX      Integer32
   MAX-ACCESS  read-only
   STATUS      current
   DESCRIPTION
      "Path: tunnels.performance.l2tpTunnels.mibCounters.ifInBandwidth.30sec

       unit name = bps
       formula = 8 * ; 8 /"
   ::= {pr1645v2TvTmplPerfEntry 45419008}

pr1645v2TvTmplPerfMCInBandwidth1min OBJECT-TYPE
   SYNTAX      Integer32
   MAX-ACCESS  read-only
   STATUS      current
   DESCRIPTION
      "Path: tunnels.performance.l2tpTunnels.mibCounters.ifInBandwidth.1min

       unit name = bps
       formula = 8 * ; 8 /"
   ::= {pr1645v2TvTmplPerfEntry 45421568}

pr1645v2TvTmplPerfMCInBandwidth2min OBJECT-TYPE
   SYNTAX      Integer32
   MAX-ACCESS  read-only
   STATUS      current
   DESCRIPTION
      "Path: tunnels.performance.l2tpTunnels.mibCounters.ifInBandwidth.2min

       unit name = bps
       formula = 8 * ; 8 /"
   ::= {pr1645v2TvTmplPerfEntry 45426688}

pr1645v2TvTmplPerfMCInBandwidth5min OBJECT-TYPE
   SYNTAX      Integer32
   MAX-ACCESS  read-only
   STATUS      current
   DESCRIPTION
      "Path: tunnels.performance.l2tpTunnels.mibCounters.ifInBandwidth.5min

       unit name = bps
       formula = 8 * ; 8 /"
   ::= {pr1645v2TvTmplPerfEntry 45442048}

pr1645v2TvTmplPerfMCOutOctets OBJECT-TYPE
   SYNTAX      Counter64
   MAX-ACCESS  read-only
   STATUS      current
   DESCRIPTION
      "Path: tunnels.performance.l2tpTunnels.mibCounters.ifOutOctets

       64 bit unsigned wrappable counter."
   ::= {pr1645v2TvTmplPerfEntry 41091072}

pr1645v2TvTmplPerfMCOutUcastPkts OBJECT-TYPE
   SYNTAX      Counter64
   MAX-ACCESS  read-only
   STATUS      current
   DESCRIPTION
      "Path: tunnels.performance.l2tpTunnels.mibCounters.ifOutUcastPkts

       64 bit unsigned wrappable counter."
   ::= {pr1645v2TvTmplPerfEntry 41156608}

pr1645v2TvTmplPerfMCOutNUcastPkts OBJECT-TYPE
   SYNTAX      Counter64
   MAX-ACCESS  read-only
   STATUS      current
   DESCRIPTION
      "Path: tunnels.performance.l2tpTunnels.mibCounters.ifOutNUcastPkts

       64 bit unsigned wrappable counter."
   ::= {pr1645v2TvTmplPerfEntry 41222144}

pr1645v2TvTmplPerfMCOutBcastPkts OBJECT-TYPE
   SYNTAX      Counter64
   MAX-ACCESS  read-only
   STATUS      current
   DESCRIPTION
      "Path: tunnels.performance.l2tpTunnels.mibCounters.ifOutBcastPkts

       64 bit unsigned wrappable counter."
   ::= {pr1645v2TvTmplPerfEntry 47775744}

pr1645v2TvTmplPerfMCOutMcastPkts OBJECT-TYPE
   SYNTAX      Counter64
   MAX-ACCESS  read-only
   STATUS      current
   DESCRIPTION
      "Path: tunnels.performance.l2tpTunnels.mibCounters.ifOutMcastPkts

       64 bit unsigned wrappable counter."
   ::= {pr1645v2TvTmplPerfEntry 48431104}

pr1645v2TvTmplPerfMCOutDiscards OBJECT-TYPE
   SYNTAX      Counter64
   MAX-ACCESS  read-only
   STATUS      current
   DESCRIPTION
      "Path: tunnels.performance.l2tpTunnels.mibCounters.ifOutDiscards

       64 bit unsigned wrappable counter."
   ::= {pr1645v2TvTmplPerfEntry 41287680}

pr1645v2TvTmplPerfMCOutErrors OBJECT-TYPE
   SYNTAX      Counter64
   MAX-ACCESS  read-only
   STATUS      current
   DESCRIPTION
      "Path: tunnels.performance.l2tpTunnels.mibCounters.ifOutErrors

       64 bit unsigned wrappable counter."
   ::= {pr1645v2TvTmplPerfEntry 41353216}

pr1645v2TvTmplPerfMCOutQLen OBJECT-TYPE
   SYNTAX      Counter32
   MAX-ACCESS  read-only
   STATUS      current
   DESCRIPTION
      "Path: tunnels.performance.l2tpTunnels.mibCounters.ifOutQLen

       32 bit unsigned wrappable counter."
   ::= {pr1645v2TvTmplPerfEntry 41418752}

pr1645v2TvTmplPerfMCOutDropEx OBJECT-TYPE
   SYNTAX      Counter64
   MAX-ACCESS  read-only
   STATUS      current
   DESCRIPTION
      "Path: tunnels.performance.l2tpTunnels.mibCounters.ifOutDropLevelExceeded

       64 bit unsigned wrappable counter."
   ::= {pr1645v2TvTmplPerfEntry 41484288}

pr1645v2TvTmplPerfMCOutDropNoArp OBJECT-TYPE
   SYNTAX      Counter64
   MAX-ACCESS  read-only
   STATUS      current
   DESCRIPTION
      "Path: tunnels.performance.l2tpTunnels.mibCounters.ifOutDiscardsNoArp

       64 bit unsigned wrappable counter."
   ::= {pr1645v2TvTmplPerfEntry 42336256}

pr1645v2TvTmplPerfMCOutDropFilter OBJECT-TYPE
   SYNTAX      Counter64
   MAX-ACCESS  read-only
   STATUS      current
   DESCRIPTION
      "Path: tunnels.performance.l2tpTunnels.mibCounters.ifOutDiscardsFilter

       64 bit unsigned wrappable counter."
   ::= {pr1645v2TvTmplPerfEntry 42598400}

pr1645v2TvTmplPerfMCOutBandwidth15sec OBJECT-TYPE
   SYNTAX      Integer32
   MAX-ACCESS  read-only
   STATUS      current
   DESCRIPTION
      "Path: tunnels.performance.l2tpTunnels.mibCounters.ifOutBandwidth.15sec

       unit name = bps
       formula = 8 * ; 8 /"
   ::= {pr1645v2TvTmplPerfEntry 45483264}

pr1645v2TvTmplPerfMCOutBandwidth30sec OBJECT-TYPE
   SYNTAX      Integer32
   MAX-ACCESS  read-only
   STATUS      current
   DESCRIPTION
      "Path: tunnels.performance.l2tpTunnels.mibCounters.ifOutBandwidth.30sec

       unit name = bps
       formula = 8 * ; 8 /"
   ::= {pr1645v2TvTmplPerfEntry 45484544}

pr1645v2TvTmplPerfMCOutBandwidth1min OBJECT-TYPE
   SYNTAX      Integer32
   MAX-ACCESS  read-only
   STATUS      current
   DESCRIPTION
      "Path: tunnels.performance.l2tpTunnels.mibCounters.ifOutBandwidth.1min

       unit name = bps
       formula = 8 * ; 8 /"
   ::= {pr1645v2TvTmplPerfEntry 45487104}

pr1645v2TvTmplPerfMCOutBandwidth2min OBJECT-TYPE
   SYNTAX      Integer32
   MAX-ACCESS  read-only
   STATUS      current
   DESCRIPTION
      "Path: tunnels.performance.l2tpTunnels.mibCounters.ifOutBandwidth.2min

       unit name = bps
       formula = 8 * ; 8 /"
   ::= {pr1645v2TvTmplPerfEntry 45492224}

pr1645v2TvTmplPerfMCOutBandwidth5min OBJECT-TYPE
   SYNTAX      Integer32
   MAX-ACCESS  read-only
   STATUS      current
   DESCRIPTION
      "Path: tunnels.performance.l2tpTunnels.mibCounters.ifOutBandwidth.5min

       unit name = bps
       formula = 8 * ; 8 /"
   ::= {pr1645v2TvTmplPerfEntry 45507584}

pr1645v2TvTmplPerfControlHelloSent OBJECT-TYPE
   SYNTAX      Gauge32
   MAX-ACCESS  read-only
   STATUS      current
   DESCRIPTION
      "Path: tunnels.performance.l2tpTunnels.control.helloSent

       32 bit unsigned gauge value."
   ::= {pr1645v2TvTmplPerfEntry 117506048}

pr1645v2TvTmplPerfControlHelloRcvd OBJECT-TYPE
   SYNTAX      Gauge32
   MAX-ACCESS  read-only
   STATUS      current
   DESCRIPTION
      "Path: tunnels.performance.l2tpTunnels.control.helloRcvd

       32 bit unsigned gauge value."
   ::= {pr1645v2TvTmplPerfEntry 117637120}

pr1645v2TvTmplPerfControlAckSent OBJECT-TYPE
   SYNTAX      Gauge32
   MAX-ACCESS  read-only
   STATUS      current
   DESCRIPTION
      "Path: tunnels.performance.l2tpTunnels.control.ackSent

       32 bit unsigned gauge value."
   ::= {pr1645v2TvTmplPerfEntry 117702656}

pr1645v2TvTmplPerfControlAckRcvd OBJECT-TYPE
   SYNTAX      Gauge32
   MAX-ACCESS  read-only
   STATUS      current
   DESCRIPTION
      "Path: tunnels.performance.l2tpTunnels.control.ackRcvd

       32 bit unsigned gauge value."
   ::= {pr1645v2TvTmplPerfEntry 117571584}

pr1645v2TvTmplPerfControlDuplicateRcvd OBJECT-TYPE
   SYNTAX      Gauge32
   MAX-ACCESS  read-only
   STATUS      current
   DESCRIPTION
      "Path: tunnels.performance.l2tpTunnels.control.duplicateRcvd

       32 bit unsigned gauge value."
   ::= {pr1645v2TvTmplPerfEntry 117768192}

pr1645v2TvTmplPerfControlOutOfSeqRcvd OBJECT-TYPE
   SYNTAX      Gauge32
   MAX-ACCESS  read-only
   STATUS      current
   DESCRIPTION
      "Path: tunnels.performance.l2tpTunnels.control.outOfSeqRcvd

       32 bit unsigned gauge value."
   ::= {pr1645v2TvTmplPerfEntry 117833728}

pr1645v2TvTmplPerfControlRetransmission OBJECT-TYPE
   SYNTAX      Gauge32
   MAX-ACCESS  read-only
   STATUS      current
   DESCRIPTION
      "Path: tunnels.performance.l2tpTunnels.control.retransmission

       32 bit unsigned gauge value."
   ::= {pr1645v2TvTmplPerfEntry 117899264}

pr1645v2TvTmplPerfControlAuthenFailure OBJECT-TYPE
   SYNTAX      Gauge32
   MAX-ACCESS  read-only
   STATUS      current
   DESCRIPTION
      "Path: tunnels.performance.l2tpTunnels.control.authenFailure

       32 bit unsigned gauge value."
   ::= {pr1645v2TvTmplPerfEntry 117964800}

pr1645v2TvTmplPerfPppPort OBJECT-TYPE
   SYNTAX      Counter32
   MAX-ACCESS  read-only
   STATUS      current
   DESCRIPTION
      "Path: tunnels.performance.l2tpTunnels.ppp.port

       32 bit unsigned wrappable counter."
   ::= {pr1645v2TvTmplPerfEntry 67371008}

pr1645v2TvTmplPerfPppLcpUp OBJECT-TYPE
   SYNTAX      Counter32
   MAX-ACCESS  read-only
   STATUS      current
   DESCRIPTION
      "Path: tunnels.performance.l2tpTunnels.ppp.lcp.up

       32 bit unsigned wrappable counter."
   ::= {pr1645v2TvTmplPerfEntry 67174656}

pr1645v2TvTmplPerfPppLcpDown OBJECT-TYPE
   SYNTAX      Counter32
   MAX-ACCESS  read-only
   STATUS      current
   DESCRIPTION
      "Path: tunnels.performance.l2tpTunnels.ppp.lcp.down

       32 bit unsigned wrappable counter."
   ::= {pr1645v2TvTmplPerfEntry 67174912}

pr1645v2TvTmplPerfPppLcpOpen OBJECT-TYPE
   SYNTAX      Counter32
   MAX-ACCESS  read-only
   STATUS      current
   DESCRIPTION
      "Path: tunnels.performance.l2tpTunnels.ppp.lcp.open

       32 bit unsigned wrappable counter."
   ::= {pr1645v2TvTmplPerfEntry 67175168}

pr1645v2TvTmplPerfPppLcpClose OBJECT-TYPE
   SYNTAX      Counter32
   MAX-ACCESS  read-only
   STATUS      current
   DESCRIPTION
      "Path: tunnels.performance.l2tpTunnels.ppp.lcp.close

       32 bit unsigned wrappable counter."
   ::= {pr1645v2TvTmplPerfEntry 67175424}

pr1645v2TvTmplPerfPppLcpToP OBJECT-TYPE
   SYNTAX      Counter32
   MAX-ACCESS  read-only
   STATUS      current
   DESCRIPTION
      "Path: tunnels.performance.l2tpTunnels.ppp.lcp.toP

       32 bit unsigned wrappable counter."
   ::= {pr1645v2TvTmplPerfEntry 67175680}

pr1645v2TvTmplPerfPppLcpToM OBJECT-TYPE
   SYNTAX      Counter32
   MAX-ACCESS  read-only
   STATUS      current
   DESCRIPTION
      "Path: tunnels.performance.l2tpTunnels.ppp.lcp.toM

       32 bit unsigned wrappable counter."
   ::= {pr1645v2TvTmplPerfEntry 67175936}

pr1645v2TvTmplPerfPppLcpRcrP OBJECT-TYPE
   SYNTAX      Counter32
   MAX-ACCESS  read-only
   STATUS      current
   DESCRIPTION
      "Path: tunnels.performance.l2tpTunnels.ppp.lcp.rcrP

       32 bit unsigned wrappable counter."
   ::= {pr1645v2TvTmplPerfEntry 67176192}

pr1645v2TvTmplPerfPppLcpRcrM OBJECT-TYPE
   SYNTAX      Counter32
   MAX-ACCESS  read-only
   STATUS      current
   DESCRIPTION
      "Path: tunnels.performance.l2tpTunnels.ppp.lcp.rcrM

       32 bit unsigned wrappable counter."
   ::= {pr1645v2TvTmplPerfEntry 67176448}

pr1645v2TvTmplPerfPppLcpRca OBJECT-TYPE
   SYNTAX      Counter32
   MAX-ACCESS  read-only
   STATUS      current
   DESCRIPTION
      "Path: tunnels.performance.l2tpTunnels.ppp.lcp.rca

       32 bit unsigned wrappable counter."
   ::= {pr1645v2TvTmplPerfEntry 67176704}

pr1645v2TvTmplPerfPppLcpRcn OBJECT-TYPE
   SYNTAX      Counter32
   MAX-ACCESS  read-only
   STATUS      current
   DESCRIPTION
      "Path: tunnels.performance.l2tpTunnels.ppp.lcp.rcn

       32 bit unsigned wrappable counter."
   ::= {pr1645v2TvTmplPerfEntry 67176960}

pr1645v2TvTmplPerfPppLcpRtr OBJECT-TYPE
   SYNTAX      Counter32
   MAX-ACCESS  read-only
   STATUS      current
   DESCRIPTION
      "Path: tunnels.performance.l2tpTunnels.ppp.lcp.rtr

       32 bit unsigned wrappable counter."
   ::= {pr1645v2TvTmplPerfEntry 67177216}

pr1645v2TvTmplPerfPppLcpRta OBJECT-TYPE
   SYNTAX      Counter32
   MAX-ACCESS  read-only
   STATUS      current
   DESCRIPTION
      "Path: tunnels.performance.l2tpTunnels.ppp.lcp.rta

       32 bit unsigned wrappable counter."
   ::= {pr1645v2TvTmplPerfEntry 67177472}

pr1645v2TvTmplPerfPppLcpRuc OBJECT-TYPE
   SYNTAX      Counter32
   MAX-ACCESS  read-only
   STATUS      current
   DESCRIPTION
      "Path: tunnels.performance.l2tpTunnels.ppp.lcp.ruc

       32 bit unsigned wrappable counter."
   ::= {pr1645v2TvTmplPerfEntry 67177728}

pr1645v2TvTmplPerfPppLcpRxjP OBJECT-TYPE
   SYNTAX      Counter32
   MAX-ACCESS  read-only
   STATUS      current
   DESCRIPTION
      "Path: tunnels.performance.l2tpTunnels.ppp.lcp.rxjP

       32 bit unsigned wrappable counter."
   ::= {pr1645v2TvTmplPerfEntry 67177984}

pr1645v2TvTmplPerfPppLcpRxjM OBJECT-TYPE
   SYNTAX      Counter32
   MAX-ACCESS  read-only
   STATUS      current
   DESCRIPTION
      "Path: tunnels.performance.l2tpTunnels.ppp.lcp.rxjM

       32 bit unsigned wrappable counter."
   ::= {pr1645v2TvTmplPerfEntry 67178240}

pr1645v2TvTmplPerfPppLcpRxr OBJECT-TYPE
   SYNTAX      Counter32
   MAX-ACCESS  read-only
   STATUS      current
   DESCRIPTION
      "Path: tunnels.performance.l2tpTunnels.ppp.lcp.rxr

       32 bit unsigned wrappable counter."
   ::= {pr1645v2TvTmplPerfEntry 67178496}

pr1645v2TvTmplPerfPppLcpRrr OBJECT-TYPE
   SYNTAX      Counter32
   MAX-ACCESS  read-only
   STATUS      current
   DESCRIPTION
      "Path: tunnels.performance.l2tpTunnels.ppp.lcp.rrr

       32 bit unsigned wrappable counter."
   ::= {pr1645v2TvTmplPerfEntry 67178752}

pr1645v2TvTmplPerfPppLcpRra OBJECT-TYPE
   SYNTAX      Counter32
   MAX-ACCESS  read-only
   STATUS      current
   DESCRIPTION
      "Path: tunnels.performance.l2tpTunnels.ppp.lcp.rra

       32 bit unsigned wrappable counter."
   ::= {pr1645v2TvTmplPerfEntry 67179008}

pr1645v2TvTmplPerfPppLcpDf OBJECT-TYPE
   SYNTAX      Counter32
   MAX-ACCESS  read-only
   STATUS      current
   DESCRIPTION
      "Path: tunnels.performance.l2tpTunnels.ppp.lcp.df

       32 bit unsigned wrappable counter."
   ::= {pr1645v2TvTmplPerfEntry 67179264}

pr1645v2TvTmplPerfPppLcpIntClose OBJECT-TYPE
   SYNTAX      Counter32
   MAX-ACCESS  read-only
   STATUS      current
   DESCRIPTION
      "Path: tunnels.performance.l2tpTunnels.ppp.lcp.intClose

       32 bit unsigned wrappable counter."
   ::= {pr1645v2TvTmplPerfEntry 67179520}

pr1645v2TvTmplPerfPppLcpLm OBJECT-TYPE
   SYNTAX      Counter32
   MAX-ACCESS  read-only
   STATUS      current
   DESCRIPTION
      "Path: tunnels.performance.l2tpTunnels.ppp.lcp.lm

       32 bit unsigned wrappable counter."
   ::= {pr1645v2TvTmplPerfEntry 67179776}

pr1645v2TvTmplPerfPppLcpLmM OBJECT-TYPE
   SYNTAX      Counter32
   MAX-ACCESS  read-only
   STATUS      current
   DESCRIPTION
      "Path: tunnels.performance.l2tpTunnels.ppp.lcp.lmM

       32 bit unsigned wrappable counter."
   ::= {pr1645v2TvTmplPerfEntry 67180032}

pr1645v2TvTmplPerfPppAuthMyNegotiated OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.l2tpTunnels.ppp.auth.myNegotiated

       Possibilities:
               none   (0)
               pap   (1)
               chap   (2)
               msChap   (3)
               msChapV2   (4)
               unknown   (5)
               chapOrPap   (6)"
   ::= {pr1645v2TvTmplPerfEntry 67243264}

pr1645v2TvTmplPerfPppAuthMyConfigured OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.l2tpTunnels.ppp.auth.myConfigured

       Possibilities:
               none   (0)
               pap   (1)
               chap   (2)
               msChap   (3)
               msChapV2   (4)
               unknown   (5)
               chapOrPap   (6)"
   ::= {pr1645v2TvTmplPerfEntry 67243776}

pr1645v2TvTmplPerfPppAuthHisRequested OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.l2tpTunnels.ppp.auth.hisRequested

       Possibilities:
               none   (0)
               pap   (1)
               chap   (2)
               msChap   (3)
               msChapV2   (4)
               unknown   (5)
               chapOrPap   (6)"
   ::= {pr1645v2TvTmplPerfEntry 67243520}

pr1645v2TvTmplPerfPppAuthRxChallenge OBJECT-TYPE
   SYNTAX      Counter32
   MAX-ACCESS  read-only
   STATUS      current
   DESCRIPTION
      "Path: tunnels.performance.l2tpTunnels.ppp.auth.rxChallenge

       32 bit unsigned wrappable counter."
   ::= {pr1645v2TvTmplPerfEntry 67240192}

pr1645v2TvTmplPerfPppAuthRxResponse OBJECT-TYPE
   SYNTAX      Counter32
   MAX-ACCESS  read-only
   STATUS      current
   DESCRIPTION
      "Path: tunnels.performance.l2tpTunnels.ppp.auth.rxResponse

       32 bit unsigned wrappable counter."
   ::= {pr1645v2TvTmplPerfEntry 67240448}

pr1645v2TvTmplPerfPppAuthRxSuccess OBJECT-TYPE
   SYNTAX      Counter32
   MAX-ACCESS  read-only
   STATUS      current
   DESCRIPTION
      "Path: tunnels.performance.l2tpTunnels.ppp.auth.rxSuccess

       32 bit unsigned wrappable counter."
   ::= {pr1645v2TvTmplPerfEntry 67240704}

pr1645v2TvTmplPerfPppAuthRxFailure OBJECT-TYPE
   SYNTAX      Counter32
   MAX-ACCESS  read-only
   STATUS      current
   DESCRIPTION
      "Path: tunnels.performance.l2tpTunnels.ppp.auth.rxFailure

       32 bit unsigned wrappable counter."
   ::= {pr1645v2TvTmplPerfEntry 67240960}

pr1645v2TvTmplPerfPppAuthChallengeTO OBJECT-TYPE
   SYNTAX      Counter32
   MAX-ACCESS  read-only
   STATUS      current
   DESCRIPTION
      "Path: tunnels.performance.l2tpTunnels.ppp.auth.challengeTO

       32 bit unsigned wrappable counter."
   ::= {pr1645v2TvTmplPerfEntry 67241216}

pr1645v2TvTmplPerfPppAuthResponseTO OBJECT-TYPE
   SYNTAX      Counter32
   MAX-ACCESS  read-only
   STATUS      current
   DESCRIPTION
      "Path: tunnels.performance.l2tpTunnels.ppp.auth.responseTO

       32 bit unsigned wrappable counter."
   ::= {pr1645v2TvTmplPerfEntry 67241472}

pr1645v2TvTmplPerfPppAuthTxChallenge OBJECT-TYPE
   SYNTAX      Counter32
   MAX-ACCESS  read-only
   STATUS      current
   DESCRIPTION
      "Path: tunnels.performance.l2tpTunnels.ppp.auth.txChallenge

       32 bit unsigned wrappable counter."
   ::= {pr1645v2TvTmplPerfEntry 67241728}

pr1645v2TvTmplPerfPppAuthRxRadiusSuccess OBJECT-TYPE
   SYNTAX      Counter32
   MAX-ACCESS  read-only
   STATUS      current
   DESCRIPTION
      "Path: tunnels.performance.l2tpTunnels.ppp.auth.rxRadiusSuccess

       32 bit unsigned wrappable counter."
   ::= {pr1645v2TvTmplPerfEntry 67241984}

pr1645v2TvTmplPerfPppAuthRxRadiusFailure OBJECT-TYPE
   SYNTAX      Counter32
   MAX-ACCESS  read-only
   STATUS      current
   DESCRIPTION
      "Path: tunnels.performance.l2tpTunnels.ppp.auth.rxRadiusFailure

       32 bit unsigned wrappable counter."
   ::= {pr1645v2TvTmplPerfEntry 67242240}

pr1645v2TvTmplPerfPppAuthTxSuccess OBJECT-TYPE
   SYNTAX      Counter32
   MAX-ACCESS  read-only
   STATUS      current
   DESCRIPTION
      "Path: tunnels.performance.l2tpTunnels.ppp.auth.txSuccess

       32 bit unsigned wrappable counter."
   ::= {pr1645v2TvTmplPerfEntry 67242496}

pr1645v2TvTmplPerfPppAuthTxFailure OBJECT-TYPE
   SYNTAX      Counter32
   MAX-ACCESS  read-only
   STATUS      current
   DESCRIPTION
      "Path: tunnels.performance.l2tpTunnels.ppp.auth.txFailure

       32 bit unsigned wrappable counter."
   ::= {pr1645v2TvTmplPerfEntry 67242752}

pr1645v2TvTmplPerfPppAuthUnexpected OBJECT-TYPE
   SYNTAX      Counter32
   MAX-ACCESS  read-only
   STATUS      current
   DESCRIPTION
      "Path: tunnels.performance.l2tpTunnels.ppp.auth.unexpected

       32 bit unsigned wrappable counter."
   ::= {pr1645v2TvTmplPerfEntry 67243008}

pr1645v2TvTmplPerfPppIpcpUp OBJECT-TYPE
   SYNTAX      Counter32
   MAX-ACCESS  read-only
   STATUS      current
   DESCRIPTION
      "Path: tunnels.performance.l2tpTunnels.ppp.ipcp.up

       32 bit unsigned wrappable counter."
   ::= {pr1645v2TvTmplPerfEntry 67305728}

pr1645v2TvTmplPerfPppIpcpDown OBJECT-TYPE
   SYNTAX      Counter32
   MAX-ACCESS  read-only
   STATUS      current
   DESCRIPTION
      "Path: tunnels.performance.l2tpTunnels.ppp.ipcp.down

       32 bit unsigned wrappable counter."
   ::= {pr1645v2TvTmplPerfEntry 67305984}

pr1645v2TvTmplPerfPppIpcpOpen OBJECT-TYPE
   SYNTAX      Counter32
   MAX-ACCESS  read-only
   STATUS      current
   DESCRIPTION
      "Path: tunnels.performance.l2tpTunnels.ppp.ipcp.open

       32 bit unsigned wrappable counter."
   ::= {pr1645v2TvTmplPerfEntry 67306240}

pr1645v2TvTmplPerfPppIpcpClose OBJECT-TYPE
   SYNTAX      Counter32
   MAX-ACCESS  read-only
   STATUS      current
   DESCRIPTION
      "Path: tunnels.performance.l2tpTunnels.ppp.ipcp.close

       32 bit unsigned wrappable counter."
   ::= {pr1645v2TvTmplPerfEntry 67306496}

pr1645v2TvTmplPerfPppIpcpToP OBJECT-TYPE
   SYNTAX      Counter32
   MAX-ACCESS  read-only
   STATUS      current
   DESCRIPTION
      "Path: tunnels.performance.l2tpTunnels.ppp.ipcp.toP

       32 bit unsigned wrappable counter."
   ::= {pr1645v2TvTmplPerfEntry 67306752}

pr1645v2TvTmplPerfPppIpcpToM OBJECT-TYPE
   SYNTAX      Counter32
   MAX-ACCESS  read-only
   STATUS      current
   DESCRIPTION
      "Path: tunnels.performance.l2tpTunnels.ppp.ipcp.toM

       32 bit unsigned wrappable counter."
   ::= {pr1645v2TvTmplPerfEntry 67307008}

pr1645v2TvTmplPerfPppIpcpRcrP OBJECT-TYPE
   SYNTAX      Counter32
   MAX-ACCESS  read-only
   STATUS      current
   DESCRIPTION
      "Path: tunnels.performance.l2tpTunnels.ppp.ipcp.rcrP

       32 bit unsigned wrappable counter."
   ::= {pr1645v2TvTmplPerfEntry 67307264}

pr1645v2TvTmplPerfPppIpcpRcrM OBJECT-TYPE
   SYNTAX      Counter32
   MAX-ACCESS  read-only
   STATUS      current
   DESCRIPTION
      "Path: tunnels.performance.l2tpTunnels.ppp.ipcp.rcrM

       32 bit unsigned wrappable counter."
   ::= {pr1645v2TvTmplPerfEntry 67307520}

pr1645v2TvTmplPerfPppIpcpRca OBJECT-TYPE
   SYNTAX      Counter32
   MAX-ACCESS  read-only
   STATUS      current
   DESCRIPTION
      "Path: tunnels.performance.l2tpTunnels.ppp.ipcp.rca

       32 bit unsigned wrappable counter."
   ::= {pr1645v2TvTmplPerfEntry 67307776}

pr1645v2TvTmplPerfPppIpcpRcn OBJECT-TYPE
   SYNTAX      Counter32
   MAX-ACCESS  read-only
   STATUS      current
   DESCRIPTION
      "Path: tunnels.performance.l2tpTunnels.ppp.ipcp.rcn

       32 bit unsigned wrappable counter."
   ::= {pr1645v2TvTmplPerfEntry 67308032}

pr1645v2TvTmplPerfPppIpcpRtr OBJECT-TYPE
   SYNTAX      Counter32
   MAX-ACCESS  read-only
   STATUS      current
   DESCRIPTION
      "Path: tunnels.performance.l2tpTunnels.ppp.ipcp.rtr

       32 bit unsigned wrappable counter."
   ::= {pr1645v2TvTmplPerfEntry 67308288}

pr1645v2TvTmplPerfPppIpcpRta OBJECT-TYPE
   SYNTAX      Counter32
   MAX-ACCESS  read-only
   STATUS      current
   DESCRIPTION
      "Path: tunnels.performance.l2tpTunnels.ppp.ipcp.rta

       32 bit unsigned wrappable counter."
   ::= {pr1645v2TvTmplPerfEntry 67308544}

pr1645v2TvTmplPerfPppIpcpRuc OBJECT-TYPE
   SYNTAX      Counter32
   MAX-ACCESS  read-only
   STATUS      current
   DESCRIPTION
      "Path: tunnels.performance.l2tpTunnels.ppp.ipcp.ruc

       32 bit unsigned wrappable counter."
   ::= {pr1645v2TvTmplPerfEntry 67308800}

pr1645v2TvTmplPerfPppIpcpRxjP OBJECT-TYPE
   SYNTAX      Counter32
   MAX-ACCESS  read-only
   STATUS      current
   DESCRIPTION
      "Path: tunnels.performance.l2tpTunnels.ppp.ipcp.rxjP

       32 bit unsigned wrappable counter."
   ::= {pr1645v2TvTmplPerfEntry 67309056}

pr1645v2TvTmplPerfPppIpcpRxjM OBJECT-TYPE
   SYNTAX      Counter32
   MAX-ACCESS  read-only
   STATUS      current
   DESCRIPTION
      "Path: tunnels.performance.l2tpTunnels.ppp.ipcp.rxjM

       32 bit unsigned wrappable counter."
   ::= {pr1645v2TvTmplPerfEntry 67309312}

pr1645v2TvTmplPerfPppIpcpRxr OBJECT-TYPE
   SYNTAX      Counter32
   MAX-ACCESS  read-only
   STATUS      current
   DESCRIPTION
      "Path: tunnels.performance.l2tpTunnels.ppp.ipcp.rxr

       32 bit unsigned wrappable counter."
   ::= {pr1645v2TvTmplPerfEntry 67309568}

pr1645v2TvTmplPerfPppIpcpRrr OBJECT-TYPE
   SYNTAX      Counter32
   MAX-ACCESS  read-only
   STATUS      current
   DESCRIPTION
      "Path: tunnels.performance.l2tpTunnels.ppp.ipcp.rrr

       32 bit unsigned wrappable counter."
   ::= {pr1645v2TvTmplPerfEntry 67309824}

pr1645v2TvTmplPerfPppIpcpRra OBJECT-TYPE
   SYNTAX      Counter32
   MAX-ACCESS  read-only
   STATUS      current
   DESCRIPTION
      "Path: tunnels.performance.l2tpTunnels.ppp.ipcp.rra

       32 bit unsigned wrappable counter."
   ::= {pr1645v2TvTmplPerfEntry 67310080}

pr1645v2TvTmplPerfPppIpcpDf OBJECT-TYPE
   SYNTAX      Counter32
   MAX-ACCESS  read-only
   STATUS      current
   DESCRIPTION
      "Path: tunnels.performance.l2tpTunnels.ppp.ipcp.df

       32 bit unsigned wrappable counter."
   ::= {pr1645v2TvTmplPerfEntry 67310336}

pr1645v2TvTmplPerfPppIpcpIntClose OBJECT-TYPE
   SYNTAX      Counter32
   MAX-ACCESS  read-only
   STATUS      current
   DESCRIPTION
      "Path: tunnels.performance.l2tpTunnels.ppp.ipcp.intClose

       32 bit unsigned wrappable counter."
   ::= {pr1645v2TvTmplPerfEntry 67310592}

pr1645v2TvTmplPerfPppIpcpLm OBJECT-TYPE
   SYNTAX      Counter32
   MAX-ACCESS  read-only
   STATUS      current
   DESCRIPTION
      "Path: tunnels.performance.l2tpTunnels.ppp.ipcp.lm

       32 bit unsigned wrappable counter."
   ::= {pr1645v2TvTmplPerfEntry 67310848}

pr1645v2TvTmplPerfPppIpcpLmM OBJECT-TYPE
   SYNTAX      Counter32
   MAX-ACCESS  read-only
   STATUS      current
   DESCRIPTION
      "Path: tunnels.performance.l2tpTunnels.ppp.ipcp.lmM

       32 bit unsigned wrappable counter."
   ::= {pr1645v2TvTmplPerfEntry 67311104}

pr1645v2TvTmplPerfPppLinkMonitoringRequestsSent OBJECT-TYPE
   SYNTAX      Gauge32
   MAX-ACCESS  read-only
   STATUS      current
   DESCRIPTION
      "Path: tunnels.performance.l2tpTunnels.ppp.linkMonitoring.requestsSent

       32 bit unsigned gauge value."
   ::= {pr1645v2TvTmplPerfEntry 67436800}

pr1645v2TvTmplPerfPppLinkMonitoringRepliesRcvd OBJECT-TYPE
   SYNTAX      Gauge32
   MAX-ACCESS  read-only
   STATUS      current
   DESCRIPTION
      "Path: tunnels.performance.l2tpTunnels.ppp.linkMonitoring.repliesRcvd

       32 bit unsigned gauge value."
   ::= {pr1645v2TvTmplPerfEntry 67437056}

pr1645v2TvTmplPerfPppLinkMonitoringRequestsRcvd OBJECT-TYPE
   SYNTAX      Gauge32
   MAX-ACCESS  read-only
   STATUS      current
   DESCRIPTION
      "Path: tunnels.performance.l2tpTunnels.ppp.linkMonitoring.requestsRcvd

       32 bit unsigned gauge value."
   ::= {pr1645v2TvTmplPerfEntry 67437312}

pr1645v2TvTmplPerfPppLinkMonitoringRepliesSent OBJECT-TYPE
   SYNTAX      Gauge32
   MAX-ACCESS  read-only
   STATUS      current
   DESCRIPTION
      "Path: tunnels.performance.l2tpTunnels.ppp.linkMonitoring.repliesSent

       32 bit unsigned gauge value."
   ::= {pr1645v2TvTmplPerfEntry 67437568}

pr1645v2TvTmplPerfMCH2P OBJECT-TYPE
   SYNTAX      SEQUENCE OF Pr1645v2TvTmplPerfMCH2PEntry
   MAX-ACCESS  not-accessible
   STATUS      current
   DESCRIPTION
      ""
   ::= {pr1645v2TvTmplPerf 41549824}

pr1645v2TvTmplPerfMCH2PEntry OBJECT-TYPE
   SYNTAX      Pr1645v2TvTmplPerfMCH2PEntry
   MAX-ACCESS  not-accessible
   STATUS      current
   DESCRIPTION
      ""
   INDEX      { pr1645v2TvTmplPerfTableIx,
                pr1645v2TvTmplPerfMCH2PTableIx }
   ::= {pr1645v2TvTmplPerfMCH2P 1}

Pr1645v2TvTmplPerfMCH2PEntry ::=
   SEQUENCE
      {
      pr1645v2TvTmplPerfMCH2PTableIx
         TableIndex,
      pr1645v2TvTmplPerfMCH2PSysUpTime
         TimeTicks,
      pr1645v2TvTmplPerfMCH2PIfUpTime
         TimeTicks,
      pr1645v2TvTmplPerfMCH2PIfStatChanges
         Counter32,
      pr1645v2TvTmplPerfMCH2PIfInOctets
         Counter64,
      pr1645v2TvTmplPerfMCH2PIfInUCPkts
         Counter64,
      pr1645v2TvTmplPerfMCH2PIfInNUCPkts
         Counter64,
      pr1645v2TvTmplPerfMCH2PIfInBCPkts
         Counter64,
      pr1645v2TvTmplPerfMCH2PIfInMCPkts
         Counter64,
      pr1645v2TvTmplPerfMCH2PIfInDiscards
         Counter64,
      pr1645v2TvTmplPerfMCH2PIfInErrors
         Counter64,
      pr1645v2TvTmplPerfMCH2PIfInUnkwn
         Counter64,
      pr1645v2TvTmplPerfMCH2PInDropEx
         Counter64,
      pr1645v2TvTmplPerfMCH2PInDropNoMac
         Counter64,
      pr1645v2TvTmplPerfMCH2PInDropNUCast
         Counter64,
      pr1645v2TvTmplPerfMCH2PInDropFilter
         Counter64,
      pr1645v2TvTmplPerfMCH2PIfInBandwidth
         Integer32,
      pr1645v2TvTmplPerfMCH2PIfOutOctets
         Counter64,
      pr1645v2TvTmplPerfMCH2PIfOutUCPkts
         Counter64,
      pr1645v2TvTmplPerfMCH2PIfOutNUCPkts
         Counter64,
      pr1645v2TvTmplPerfMCH2PIfOutBCPkts
         Counter64,
      pr1645v2TvTmplPerfMCH2PIfOutMCPkts
         Counter64,
      pr1645v2TvTmplPerfMCH2PIfOutDiscards
         Counter64,
      pr1645v2TvTmplPerfMCH2PIfOutErrors
         Counter64,
      pr1645v2TvTmplPerfMCH2POutDropEx
         Counter64,
      pr1645v2TvTmplPerfMCH2POutDropNoArp
         Counter64,
      pr1645v2TvTmplPerfMCH2POutDropFilter
         Counter64,
      pr1645v2TvTmplPerfMCH2PIfOutBandwidth
         Integer32,
      pr1645v2TvTmplPerfMCH2PIfErrSec
         Counter32
      }

pr1645v2TvTmplPerfMCH2PTableIx OBJECT-TYPE
   SYNTAX      TableIndex
   MAX-ACCESS  not-accessible
   STATUS      current
   DESCRIPTION
      ""
   ::= {pr1645v2TvTmplPerfMCH2PEntry 11}

pr1645v2TvTmplPerfMCH2PSysUpTime OBJECT-TYPE
   SYNTAX      TimeTicks
   MAX-ACCESS  read-only
   STATUS      current
   DESCRIPTION
      "Path: tunnels.performance.l2tpTunnels.mibCounters.h2Performance.sysUpTime

       Time in centi-second."
   ::= {pr1645v2TvTmplPerfMCH2PEntry 16777216}

pr1645v2TvTmplPerfMCH2PIfUpTime OBJECT-TYPE
   SYNTAX      TimeTicks
   MAX-ACCESS  read-only
   STATUS      current
   DESCRIPTION
      "Path: tunnels.performance.l2tpTunnels.mibCounters.h2Performance.ifUpTime

       Time in centi-second."
   ::= {pr1645v2TvTmplPerfMCH2PEntry 33554432}

pr1645v2TvTmplPerfMCH2PIfStatChanges OBJECT-TYPE
   SYNTAX      Counter32
   MAX-ACCESS  read-only
   STATUS      current
   DESCRIPTION
      "Path: tunnels.performance.l2tpTunnels.mibCounters.h2Performance.ifStatusChanges

       32 bit unsigned wrappable counter."
   ::= {pr1645v2TvTmplPerfMCH2PEntry 50331648}

pr1645v2TvTmplPerfMCH2PIfInOctets OBJECT-TYPE
   SYNTAX      Counter64
   MAX-ACCESS  read-only
   STATUS      current
   DESCRIPTION
      "Path: tunnels.performance.l2tpTunnels.mibCounters.h2Performance.ifInOctets

       64 bit unsigned wrappable counter."
   ::= {pr1645v2TvTmplPerfMCH2PEntry 67108864}

pr1645v2TvTmplPerfMCH2PIfInUCPkts OBJECT-TYPE
   SYNTAX      Counter64
   MAX-ACCESS  read-only
   STATUS      current
   DESCRIPTION
      "Path: tunnels.performance.l2tpTunnels.mibCounters.h2Performance.ifInUcastPkts

       64 bit unsigned wrappable counter."
   ::= {pr1645v2TvTmplPerfMCH2PEntry 83886080}

pr1645v2TvTmplPerfMCH2PIfInNUCPkts OBJECT-TYPE
   SYNTAX      Counter64
   MAX-ACCESS  read-only
   STATUS      current
   DESCRIPTION
      "Path: tunnels.performance.l2tpTunnels.mibCounters.h2Performance.ifInNUcastPkts

       64 bit unsigned wrappable counter."
   ::= {pr1645v2TvTmplPerfMCH2PEntry 100663296}

pr1645v2TvTmplPerfMCH2PIfInBCPkts OBJECT-TYPE
   SYNTAX      Counter64
   MAX-ACCESS  read-only
   STATUS      current
   DESCRIPTION
      "Path: tunnels.performance.l2tpTunnels.mibCounters.h2Performance.ifInBcastPkts

       64 bit unsigned wrappable counter."
   ::= {pr1645v2TvTmplPerfMCH2PEntry 419430400}

pr1645v2TvTmplPerfMCH2PIfInMCPkts OBJECT-TYPE
   SYNTAX      Counter64
   MAX-ACCESS  read-only
   STATUS      current
   DESCRIPTION
      "Path: tunnels.performance.l2tpTunnels.mibCounters.h2Performance.ifInMcastPkts

       64 bit unsigned wrappable counter."
   ::= {pr1645v2TvTmplPerfMCH2PEntry 436207616}

pr1645v2TvTmplPerfMCH2PIfInDiscards OBJECT-TYPE
   SYNTAX      Counter64
   MAX-ACCESS  read-only
   STATUS      current
   DESCRIPTION
      "Path: tunnels.performance.l2tpTunnels.mibCounters.h2Performance.ifInDiscards

       64 bit unsigned wrappable counter."
   ::= {pr1645v2TvTmplPerfMCH2PEntry 117440512}

pr1645v2TvTmplPerfMCH2PIfInErrors OBJECT-TYPE
   SYNTAX      Counter64
   MAX-ACCESS  read-only
   STATUS      current
   DESCRIPTION
      "Path: tunnels.performance.l2tpTunnels.mibCounters.h2Performance.ifInErrors

       64 bit unsigned wrappable counter."
   ::= {pr1645v2TvTmplPerfMCH2PEntry 134217728}

pr1645v2TvTmplPerfMCH2PIfInUnkwn OBJECT-TYPE
   SYNTAX      Counter64
   MAX-ACCESS  read-only
   STATUS      current
   DESCRIPTION
      "Path: tunnels.performance.l2tpTunnels.mibCounters.h2Performance.ifInUnknownProtos

       64 bit unsigned wrappable counter."
   ::= {pr1645v2TvTmplPerfMCH2PEntry 150994944}

pr1645v2TvTmplPerfMCH2PInDropEx OBJECT-TYPE
   SYNTAX      Counter64
   MAX-ACCESS  read-only
   STATUS      current
   DESCRIPTION
      "Path: tunnels.performance.l2tpTunnels.mibCounters.h2Performance.ifInDropLevelExceeded

       64 bit unsigned wrappable counter."
   ::= {pr1645v2TvTmplPerfMCH2PEntry 335544320}

pr1645v2TvTmplPerfMCH2PInDropNoMac OBJECT-TYPE
   SYNTAX      Counter64
   MAX-ACCESS  read-only
   STATUS      current
   DESCRIPTION
      "Path: tunnels.performance.l2tpTunnels.mibCounters.h2Performance.fInDiscardsNoMacFit

       64 bit unsigned wrappable counter."
   ::= {pr1645v2TvTmplPerfMCH2PEntry 301989888}

pr1645v2TvTmplPerfMCH2PInDropNUCast OBJECT-TYPE
   SYNTAX      Counter64
   MAX-ACCESS  read-only
   STATUS      current
   DESCRIPTION
      "Path: tunnels.performance.l2tpTunnels.mibCounters.h2Performance.fInDiscardsNUCast

       64 bit unsigned wrappable counter."
   ::= {pr1645v2TvTmplPerfMCH2PEntry 318767104}

pr1645v2TvTmplPerfMCH2PInDropFilter OBJECT-TYPE
   SYNTAX      Counter64
   MAX-ACCESS  read-only
   STATUS      current
   DESCRIPTION
      "Path: tunnels.performance.l2tpTunnels.mibCounters.h2Performance.fInDiscardsFilter

       64 bit unsigned wrappable counter."
   ::= {pr1645v2TvTmplPerfMCH2PEntry 385875968}

pr1645v2TvTmplPerfMCH2PIfInBandwidth OBJECT-TYPE
   SYNTAX      Integer32
   MAX-ACCESS  read-only
   STATUS      current
   DESCRIPTION
      "Path: tunnels.performance.l2tpTunnels.mibCounters.h2Performance.ifInBandwidth

       unit name = bps
       formula = 8 * ; 8 /"
   ::= {pr1645v2TvTmplPerfMCH2PEntry 268435456}

pr1645v2TvTmplPerfMCH2PIfOutOctets OBJECT-TYPE
   SYNTAX      Counter64
   MAX-ACCESS  read-only
   STATUS      current
   DESCRIPTION
      "Path: tunnels.performance.l2tpTunnels.mibCounters.h2Performance.ifOutOctets

       64 bit unsigned wrappable counter."
   ::= {pr1645v2TvTmplPerfMCH2PEntry 167772160}

pr1645v2TvTmplPerfMCH2PIfOutUCPkts OBJECT-TYPE
   SYNTAX      Counter64
   MAX-ACCESS  read-only
   STATUS      current
   DESCRIPTION
      "Path: tunnels.performance.l2tpTunnels.mibCounters.h2Performance.ifOutUcastPkts

       64 bit unsigned wrappable counter."
   ::= {pr1645v2TvTmplPerfMCH2PEntry 184549376}

pr1645v2TvTmplPerfMCH2PIfOutNUCPkts OBJECT-TYPE
   SYNTAX      Counter64
   MAX-ACCESS  read-only
   STATUS      current
   DESCRIPTION
      "Path: tunnels.performance.l2tpTunnels.mibCounters.h2Performance.ifOutNUcastPkts

       64 bit unsigned wrappable counter."
   ::= {pr1645v2TvTmplPerfMCH2PEntry 201326592}

pr1645v2TvTmplPerfMCH2PIfOutBCPkts OBJECT-TYPE
   SYNTAX      Counter64
   MAX-ACCESS  read-only
   STATUS      current
   DESCRIPTION
      "Path: tunnels.performance.l2tpTunnels.mibCounters.h2Performance.ifOutBcastPkts

       64 bit unsigned wrappable counter."
   ::= {pr1645v2TvTmplPerfMCH2PEntry 452984832}

pr1645v2TvTmplPerfMCH2PIfOutMCPkts OBJECT-TYPE
   SYNTAX      Counter64
   MAX-ACCESS  read-only
   STATUS      current
   DESCRIPTION
      "Path: tunnels.performance.l2tpTunnels.mibCounters.h2Performance.ifOutMcastPkts

       64 bit unsigned wrappable counter."
   ::= {pr1645v2TvTmplPerfMCH2PEntry 469762048}

pr1645v2TvTmplPerfMCH2PIfOutDiscards OBJECT-TYPE
   SYNTAX      Counter64
   MAX-ACCESS  read-only
   STATUS      current
   DESCRIPTION
      "Path: tunnels.performance.l2tpTunnels.mibCounters.h2Performance.ifOutDiscards

       64 bit unsigned wrappable counter."
   ::= {pr1645v2TvTmplPerfMCH2PEntry 218103808}

pr1645v2TvTmplPerfMCH2PIfOutErrors OBJECT-TYPE
   SYNTAX      Counter64
   MAX-ACCESS  read-only
   STATUS      current
   DESCRIPTION
      "Path: tunnels.performance.l2tpTunnels.mibCounters.h2Performance.ifOutErrors

       64 bit unsigned wrappable counter."
   ::= {pr1645v2TvTmplPerfMCH2PEntry 234881024}

pr1645v2TvTmplPerfMCH2POutDropEx OBJECT-TYPE
   SYNTAX      Counter64
   MAX-ACCESS  read-only
   STATUS      current
   DESCRIPTION
      "Path: tunnels.performance.l2tpTunnels.mibCounters.h2Performance.ifOutDropLevelExceeded

       64 bit unsigned wrappable counter."
   ::= {pr1645v2TvTmplPerfMCH2PEntry 352321536}

pr1645v2TvTmplPerfMCH2POutDropNoArp OBJECT-TYPE
   SYNTAX      Counter64
   MAX-ACCESS  read-only
   STATUS      current
   DESCRIPTION
      "Path: tunnels.performance.l2tpTunnels.mibCounters.h2Performance.ifOutDiscardsNoArp

       64 bit unsigned wrappable counter."
   ::= {pr1645v2TvTmplPerfMCH2PEntry 369098752}

pr1645v2TvTmplPerfMCH2POutDropFilter OBJECT-TYPE
   SYNTAX      Counter64
   MAX-ACCESS  read-only
   STATUS      current
   DESCRIPTION
      "Path: tunnels.performance.l2tpTunnels.mibCounters.h2Performance.ifOutDiscardsFilter

       64 bit unsigned wrappable counter."
   ::= {pr1645v2TvTmplPerfMCH2PEntry 402653184}

pr1645v2TvTmplPerfMCH2PIfOutBandwidth OBJECT-TYPE
   SYNTAX      Integer32
   MAX-ACCESS  read-only
   STATUS      current
   DESCRIPTION
      "Path: tunnels.performance.l2tpTunnels.mibCounters.h2Performance.ifOutBandwidth

       unit name = bps
       formula = 8 * ; 8 /"
   ::= {pr1645v2TvTmplPerfMCH2PEntry 285212672}

pr1645v2TvTmplPerfMCH2PIfErrSec OBJECT-TYPE
   SYNTAX      Counter32
   MAX-ACCESS  read-only
   STATUS      current
   DESCRIPTION
      "Path: tunnels.performance.l2tpTunnels.mibCounters.h2Performance.ifErrSec

       32 bit unsigned wrappable counter."
   ::= {pr1645v2TvTmplPerfMCH2PEntry 251658240}

pr1645v2TvTmplPerfMCH24P OBJECT-TYPE
   SYNTAX      SEQUENCE OF Pr1645v2TvTmplPerfMCH24PEntry
   MAX-ACCESS  not-accessible
   STATUS      current
   DESCRIPTION
      ""
   ::= {pr1645v2TvTmplPerf 41615360}

pr1645v2TvTmplPerfMCH24PEntry OBJECT-TYPE
   SYNTAX      Pr1645v2TvTmplPerfMCH24PEntry
   MAX-ACCESS  not-accessible
   STATUS      current
   DESCRIPTION
      ""
   INDEX      { pr1645v2TvTmplPerfTableIx,
                pr1645v2TvTmplPerfMCH24PTableIx }
   ::= {pr1645v2TvTmplPerfMCH24P 1}

Pr1645v2TvTmplPerfMCH24PEntry ::=
   SEQUENCE
      {
      pr1645v2TvTmplPerfMCH24PTableIx
         TableIndex,
      pr1645v2TvTmplPerfMCH24PSysUpTime
         TimeTicks,
      pr1645v2TvTmplPerfMCH24PIfUpTime
         TimeTicks,
      pr1645v2TvTmplPerfMCH24PIfStatChanges
         Counter32,
      pr1645v2TvTmplPerfMCH24PIfInOctets
         Counter64,
      pr1645v2TvTmplPerfMCH24PIfInUCPkts
         Counter64,
      pr1645v2TvTmplPerfMCH24PIfInNUCPkts
         Counter64,
      pr1645v2TvTmplPerfMCH24PIfInBCPkts
         Counter64,
      pr1645v2TvTmplPerfMCH24PIfInMCPkts
         Counter64,
      pr1645v2TvTmplPerfMCH24PIfInDiscards
         Counter64,
      pr1645v2TvTmplPerfMCH24PIfInErrors
         Counter64,
      pr1645v2TvTmplPerfMCH24PIfInUnkwn
         Counter64,
      pr1645v2TvTmplPerfMCH24PInDropEx
         Counter64,
      pr1645v2TvTmplPerfMCH24PInDropNoMac
         Counter64,
      pr1645v2TvTmplPerfMCH24PInDropNUCast
         Counter64,
      pr1645v2TvTmplPerfMCH24PInDropFilter
         Counter64,
      pr1645v2TvTmplPerfMCH24PIfInBandwidth
         Integer32,
      pr1645v2TvTmplPerfMCH24PIfOutOctets
         Counter64,
      pr1645v2TvTmplPerfMCH24PIfOutUCPkts
         Counter64,
      pr1645v2TvTmplPerfMCH24PIfOutNUCPkts
         Counter64,
      pr1645v2TvTmplPerfMCH24PIfOutBCPkts
         Counter64,
      pr1645v2TvTmplPerfMCH24PIfOutMCPkts
         Counter64,
      pr1645v2TvTmplPerfMCH24PIfOutDiscards
         Counter64,
      pr1645v2TvTmplPerfMCH24PIfOutErrors
         Counter64,
      pr1645v2TvTmplPerfMCH24POutDropEx
         Counter64,
      pr1645v2TvTmplPerfMCH24POutDropNoArp
         Counter64,
      pr1645v2TvTmplPerfMCH24POutDropFilter
         Counter64,
      pr1645v2TvTmplPerfMCH24PIfOutBandwidth
         Integer32,
      pr1645v2TvTmplPerfMCH24PIfErrSec
         Counter32
      }

pr1645v2TvTmplPerfMCH24PTableIx OBJECT-TYPE
   SYNTAX      TableIndex
   MAX-ACCESS  not-accessible
   STATUS      current
   DESCRIPTION
      ""
   ::= {pr1645v2TvTmplPerfMCH24PEntry 11}

pr1645v2TvTmplPerfMCH24PSysUpTime OBJECT-TYPE
   SYNTAX      TimeTicks
   MAX-ACCESS  read-only
   STATUS      current
   DESCRIPTION
      "Path: tunnels.performance.l2tpTunnels.mibCounters.h24Performance.sysUpTime

       Time in centi-second."
   ::= {pr1645v2TvTmplPerfMCH24PEntry 16777216}

pr1645v2TvTmplPerfMCH24PIfUpTime OBJECT-TYPE
   SYNTAX      TimeTicks
   MAX-ACCESS  read-only
   STATUS      current
   DESCRIPTION
      "Path: tunnels.performance.l2tpTunnels.mibCounters.h24Performance.ifUpTime

       Time in centi-second."
   ::= {pr1645v2TvTmplPerfMCH24PEntry 33554432}

pr1645v2TvTmplPerfMCH24PIfStatChanges OBJECT-TYPE
   SYNTAX      Counter32
   MAX-ACCESS  read-only
   STATUS      current
   DESCRIPTION
      "Path: tunnels.performance.l2tpTunnels.mibCounters.h24Performance.ifStatusChanges

       32 bit unsigned wrappable counter."
   ::= {pr1645v2TvTmplPerfMCH24PEntry 50331648}

pr1645v2TvTmplPerfMCH24PIfInOctets OBJECT-TYPE
   SYNTAX      Counter64
   MAX-ACCESS  read-only
   STATUS      current
   DESCRIPTION
      "Path: tunnels.performance.l2tpTunnels.mibCounters.h24Performance.ifInOctets

       64 bit unsigned wrappable counter."
   ::= {pr1645v2TvTmplPerfMCH24PEntry 67108864}

pr1645v2TvTmplPerfMCH24PIfInUCPkts OBJECT-TYPE
   SYNTAX      Counter64
   MAX-ACCESS  read-only
   STATUS      current
   DESCRIPTION
      "Path: tunnels.performance.l2tpTunnels.mibCounters.h24Performance.ifInUcastPkts

       64 bit unsigned wrappable counter."
   ::= {pr1645v2TvTmplPerfMCH24PEntry 83886080}

pr1645v2TvTmplPerfMCH24PIfInNUCPkts OBJECT-TYPE
   SYNTAX      Counter64
   MAX-ACCESS  read-only
   STATUS      current
   DESCRIPTION
      "Path: tunnels.performance.l2tpTunnels.mibCounters.h24Performance.ifInNUcastPkts

       64 bit unsigned wrappable counter."
   ::= {pr1645v2TvTmplPerfMCH24PEntry 100663296}

pr1645v2TvTmplPerfMCH24PIfInBCPkts OBJECT-TYPE
   SYNTAX      Counter64
   MAX-ACCESS  read-only
   STATUS      current
   DESCRIPTION
      "Path: tunnels.performance.l2tpTunnels.mibCounters.h24Performance.ifInBcastPkts

       64 bit unsigned wrappable counter."
   ::= {pr1645v2TvTmplPerfMCH24PEntry 419430400}

pr1645v2TvTmplPerfMCH24PIfInMCPkts OBJECT-TYPE
   SYNTAX      Counter64
   MAX-ACCESS  read-only
   STATUS      current
   DESCRIPTION
      "Path: tunnels.performance.l2tpTunnels.mibCounters.h24Performance.ifInMcastPkts

       64 bit unsigned wrappable counter."
   ::= {pr1645v2TvTmplPerfMCH24PEntry 436207616}

pr1645v2TvTmplPerfMCH24PIfInDiscards OBJECT-TYPE
   SYNTAX      Counter64
   MAX-ACCESS  read-only
   STATUS      current
   DESCRIPTION
      "Path: tunnels.performance.l2tpTunnels.mibCounters.h24Performance.ifInDiscards

       64 bit unsigned wrappable counter."
   ::= {pr1645v2TvTmplPerfMCH24PEntry 117440512}

pr1645v2TvTmplPerfMCH24PIfInErrors OBJECT-TYPE
   SYNTAX      Counter64
   MAX-ACCESS  read-only
   STATUS      current
   DESCRIPTION
      "Path: tunnels.performance.l2tpTunnels.mibCounters.h24Performance.ifInErrors

       64 bit unsigned wrappable counter."
   ::= {pr1645v2TvTmplPerfMCH24PEntry 134217728}

pr1645v2TvTmplPerfMCH24PIfInUnkwn OBJECT-TYPE
   SYNTAX      Counter64
   MAX-ACCESS  read-only
   STATUS      current
   DESCRIPTION
      "Path: tunnels.performance.l2tpTunnels.mibCounters.h24Performance.ifInUnknownProtos

       64 bit unsigned wrappable counter."
   ::= {pr1645v2TvTmplPerfMCH24PEntry 150994944}

pr1645v2TvTmplPerfMCH24PInDropEx OBJECT-TYPE
   SYNTAX      Counter64
   MAX-ACCESS  read-only
   STATUS      current
   DESCRIPTION
      "Path: tunnels.performance.l2tpTunnels.mibCounters.h24Performance.ifInDropLevelExceeded

       64 bit unsigned wrappable counter."
   ::= {pr1645v2TvTmplPerfMCH24PEntry 335544320}

pr1645v2TvTmplPerfMCH24PInDropNoMac OBJECT-TYPE
   SYNTAX      Counter64
   MAX-ACCESS  read-only
   STATUS      current
   DESCRIPTION
      "Path: tunnels.performance.l2tpTunnels.mibCounters.h24Performance.fInDiscardsNoMacFit

       64 bit unsigned wrappable counter."
   ::= {pr1645v2TvTmplPerfMCH24PEntry 301989888}

pr1645v2TvTmplPerfMCH24PInDropNUCast OBJECT-TYPE
   SYNTAX      Counter64
   MAX-ACCESS  read-only
   STATUS      current
   DESCRIPTION
      "Path: tunnels.performance.l2tpTunnels.mibCounters.h24Performance.fInDiscardsNUCast

       64 bit unsigned wrappable counter."
   ::= {pr1645v2TvTmplPerfMCH24PEntry 318767104}

pr1645v2TvTmplPerfMCH24PInDropFilter OBJECT-TYPE
   SYNTAX      Counter64
   MAX-ACCESS  read-only
   STATUS      current
   DESCRIPTION
      "Path: tunnels.performance.l2tpTunnels.mibCounters.h24Performance.fInDiscardsFilter

       64 bit unsigned wrappable counter."
   ::= {pr1645v2TvTmplPerfMCH24PEntry 385875968}

pr1645v2TvTmplPerfMCH24PIfInBandwidth OBJECT-TYPE
   SYNTAX      Integer32
   MAX-ACCESS  read-only
   STATUS      current
   DESCRIPTION
      "Path: tunnels.performance.l2tpTunnels.mibCounters.h24Performance.ifInBandwidth

       unit name = bps
       formula = 8 * ; 8 /"
   ::= {pr1645v2TvTmplPerfMCH24PEntry 268435456}

pr1645v2TvTmplPerfMCH24PIfOutOctets OBJECT-TYPE
   SYNTAX      Counter64
   MAX-ACCESS  read-only
   STATUS      current
   DESCRIPTION
      "Path: tunnels.performance.l2tpTunnels.mibCounters.h24Performance.ifOutOctets

       64 bit unsigned wrappable counter."
   ::= {pr1645v2TvTmplPerfMCH24PEntry 167772160}

pr1645v2TvTmplPerfMCH24PIfOutUCPkts OBJECT-TYPE
   SYNTAX      Counter64
   MAX-ACCESS  read-only
   STATUS      current
   DESCRIPTION
      "Path: tunnels.performance.l2tpTunnels.mibCounters.h24Performance.ifOutUcastPkts

       64 bit unsigned wrappable counter."
   ::= {pr1645v2TvTmplPerfMCH24PEntry 184549376}

pr1645v2TvTmplPerfMCH24PIfOutNUCPkts OBJECT-TYPE
   SYNTAX      Counter64
   MAX-ACCESS  read-only
   STATUS      current
   DESCRIPTION
      "Path: tunnels.performance.l2tpTunnels.mibCounters.h24Performance.ifOutNUcastPkts

       64 bit unsigned wrappable counter."
   ::= {pr1645v2TvTmplPerfMCH24PEntry 201326592}

pr1645v2TvTmplPerfMCH24PIfOutBCPkts OBJECT-TYPE
   SYNTAX      Counter64
   MAX-ACCESS  read-only
   STATUS      current
   DESCRIPTION
      "Path: tunnels.performance.l2tpTunnels.mibCounters.h24Performance.ifOutBcastPkts

       64 bit unsigned wrappable counter."
   ::= {pr1645v2TvTmplPerfMCH24PEntry 452984832}

pr1645v2TvTmplPerfMCH24PIfOutMCPkts OBJECT-TYPE
   SYNTAX      Counter64
   MAX-ACCESS  read-only
   STATUS      current
   DESCRIPTION
      "Path: tunnels.performance.l2tpTunnels.mibCounters.h24Performance.ifOutMcastPkts

       64 bit unsigned wrappable counter."
   ::= {pr1645v2TvTmplPerfMCH24PEntry 469762048}

pr1645v2TvTmplPerfMCH24PIfOutDiscards OBJECT-TYPE
   SYNTAX      Counter64
   MAX-ACCESS  read-only
   STATUS      current
   DESCRIPTION
      "Path: tunnels.performance.l2tpTunnels.mibCounters.h24Performance.ifOutDiscards

       64 bit unsigned wrappable counter."
   ::= {pr1645v2TvTmplPerfMCH24PEntry 218103808}

pr1645v2TvTmplPerfMCH24PIfOutErrors OBJECT-TYPE
   SYNTAX      Counter64
   MAX-ACCESS  read-only
   STATUS      current
   DESCRIPTION
      "Path: tunnels.performance.l2tpTunnels.mibCounters.h24Performance.ifOutErrors

       64 bit unsigned wrappable counter."
   ::= {pr1645v2TvTmplPerfMCH24PEntry 234881024}

pr1645v2TvTmplPerfMCH24POutDropEx OBJECT-TYPE
   SYNTAX      Counter64
   MAX-ACCESS  read-only
   STATUS      current
   DESCRIPTION
      "Path: tunnels.performance.l2tpTunnels.mibCounters.h24Performance.ifOutDropLevelExceeded

       64 bit unsigned wrappable counter."
   ::= {pr1645v2TvTmplPerfMCH24PEntry 352321536}

pr1645v2TvTmplPerfMCH24POutDropNoArp OBJECT-TYPE
   SYNTAX      Counter64
   MAX-ACCESS  read-only
   STATUS      current
   DESCRIPTION
      "Path: tunnels.performance.l2tpTunnels.mibCounters.h24Performance.ifOutDiscardsNoArp

       64 bit unsigned wrappable counter."
   ::= {pr1645v2TvTmplPerfMCH24PEntry 369098752}

pr1645v2TvTmplPerfMCH24POutDropFilter OBJECT-TYPE
   SYNTAX      Counter64
   MAX-ACCESS  read-only
   STATUS      current
   DESCRIPTION
      "Path: tunnels.performance.l2tpTunnels.mibCounters.h24Performance.ifOutDiscardsFilter

       64 bit unsigned wrappable counter."
   ::= {pr1645v2TvTmplPerfMCH24PEntry 402653184}

pr1645v2TvTmplPerfMCH24PIfOutBandwidth OBJECT-TYPE
   SYNTAX      Integer32
   MAX-ACCESS  read-only
   STATUS      current
   DESCRIPTION
      "Path: tunnels.performance.l2tpTunnels.mibCounters.h24Performance.ifOutBandwidth

       unit name = bps
       formula = 8 * ; 8 /"
   ::= {pr1645v2TvTmplPerfMCH24PEntry 285212672}

pr1645v2TvTmplPerfMCH24PIfErrSec OBJECT-TYPE
   SYNTAX      Counter32
   MAX-ACCESS  read-only
   STATUS      current
   DESCRIPTION
      "Path: tunnels.performance.l2tpTunnels.mibCounters.h24Performance.ifErrSec

       32 bit unsigned wrappable counter."
   ::= {pr1645v2TvTmplPerfMCH24PEntry 251658240}

pr1645v2TvTmplPerfMCD7P OBJECT-TYPE
   SYNTAX      SEQUENCE OF Pr1645v2TvTmplPerfMCD7PEntry
   MAX-ACCESS  not-accessible
   STATUS      current
   DESCRIPTION
      ""
   ::= {pr1645v2TvTmplPerf 41680896}

pr1645v2TvTmplPerfMCD7PEntry OBJECT-TYPE
   SYNTAX      Pr1645v2TvTmplPerfMCD7PEntry
   MAX-ACCESS  not-accessible
   STATUS      current
   DESCRIPTION
      ""
   INDEX      { pr1645v2TvTmplPerfTableIx,
                pr1645v2TvTmplPerfMCD7PTableIx }
   ::= {pr1645v2TvTmplPerfMCD7P 1}

Pr1645v2TvTmplPerfMCD7PEntry ::=
   SEQUENCE
      {
      pr1645v2TvTmplPerfMCD7PTableIx
         TableIndex,
      pr1645v2TvTmplPerfMCD7PSysUpTime
         TimeTicks,
      pr1645v2TvTmplPerfMCD7PIfUpTime
         TimeTicks,
      pr1645v2TvTmplPerfMCD7PIfStatChanges
         Counter32,
      pr1645v2TvTmplPerfMCD7PIfInOctets
         Counter64,
      pr1645v2TvTmplPerfMCD7PIfInUCPkts
         Counter64,
      pr1645v2TvTmplPerfMCD7PIfInNUCPkts
         Counter64,
      pr1645v2TvTmplPerfMCD7PIfInBCPkts
         Counter64,
      pr1645v2TvTmplPerfMCD7PIfInMCPkts
         Counter64,
      pr1645v2TvTmplPerfMCD7PIfInDiscards
         Counter64,
      pr1645v2TvTmplPerfMCD7PIfInErrors
         Counter64,
      pr1645v2TvTmplPerfMCD7PIfInUnkwn
         Counter64,
      pr1645v2TvTmplPerfMCD7PInDropEx
         Counter64,
      pr1645v2TvTmplPerfMCD7PInDropNoMac
         Counter64,
      pr1645v2TvTmplPerfMCD7PInDropNUCast
         Counter64,
      pr1645v2TvTmplPerfMCD7PInDropFilter
         Counter64,
      pr1645v2TvTmplPerfMCD7PIfInBandwidth
         Integer32,
      pr1645v2TvTmplPerfMCD7PIfOutOctets
         Counter64,
      pr1645v2TvTmplPerfMCD7PIfOutUCPkts
         Counter64,
      pr1645v2TvTmplPerfMCD7PIfOutNUCPkts
         Counter64,
      pr1645v2TvTmplPerfMCD7PIfOutBCPkts
         Counter64,
      pr1645v2TvTmplPerfMCD7PIfOutMCPkts
         Counter64,
      pr1645v2TvTmplPerfMCD7PIfOutDiscards
         Counter64,
      pr1645v2TvTmplPerfMCD7PIfOutErrors
         Counter64,
      pr1645v2TvTmplPerfMCD7POutDropEx
         Counter64,
      pr1645v2TvTmplPerfMCD7POutDropNoArp
         Counter64,
      pr1645v2TvTmplPerfMCD7POutDropFilter
         Counter64,
      pr1645v2TvTmplPerfMCD7PIfOutBandwidth
         Integer32,
      pr1645v2TvTmplPerfMCD7PIfErrSec
         Counter32
      }

pr1645v2TvTmplPerfMCD7PTableIx OBJECT-TYPE
   SYNTAX      TableIndex
   MAX-ACCESS  not-accessible
   STATUS      current
   DESCRIPTION
      ""
   ::= {pr1645v2TvTmplPerfMCD7PEntry 11}

pr1645v2TvTmplPerfMCD7PSysUpTime OBJECT-TYPE
   SYNTAX      TimeTicks
   MAX-ACCESS  read-only
   STATUS      current
   DESCRIPTION
      "Path: tunnels.performance.l2tpTunnels.mibCounters.d7Performance.sysUpTime

       Time in centi-second."
   ::= {pr1645v2TvTmplPerfMCD7PEntry 16777216}

pr1645v2TvTmplPerfMCD7PIfUpTime OBJECT-TYPE
   SYNTAX      TimeTicks
   MAX-ACCESS  read-only
   STATUS      current
   DESCRIPTION
      "Path: tunnels.performance.l2tpTunnels.mibCounters.d7Performance.ifUpTime

       Time in centi-second."
   ::= {pr1645v2TvTmplPerfMCD7PEntry 33554432}

pr1645v2TvTmplPerfMCD7PIfStatChanges OBJECT-TYPE
   SYNTAX      Counter32
   MAX-ACCESS  read-only
   STATUS      current
   DESCRIPTION
      "Path: tunnels.performance.l2tpTunnels.mibCounters.d7Performance.ifStatusChanges

       32 bit unsigned wrappable counter."
   ::= {pr1645v2TvTmplPerfMCD7PEntry 50331648}

pr1645v2TvTmplPerfMCD7PIfInOctets OBJECT-TYPE
   SYNTAX      Counter64
   MAX-ACCESS  read-only
   STATUS      current
   DESCRIPTION
      "Path: tunnels.performance.l2tpTunnels.mibCounters.d7Performance.ifInOctets

       64 bit unsigned wrappable counter."
   ::= {pr1645v2TvTmplPerfMCD7PEntry 67108864}

pr1645v2TvTmplPerfMCD7PIfInUCPkts OBJECT-TYPE
   SYNTAX      Counter64
   MAX-ACCESS  read-only
   STATUS      current
   DESCRIPTION
      "Path: tunnels.performance.l2tpTunnels.mibCounters.d7Performance.ifInUcastPkts

       64 bit unsigned wrappable counter."
   ::= {pr1645v2TvTmplPerfMCD7PEntry 83886080}

pr1645v2TvTmplPerfMCD7PIfInNUCPkts OBJECT-TYPE
   SYNTAX      Counter64
   MAX-ACCESS  read-only
   STATUS      current
   DESCRIPTION
      "Path: tunnels.performance.l2tpTunnels.mibCounters.d7Performance.ifInNUcastPkts

       64 bit unsigned wrappable counter."
   ::= {pr1645v2TvTmplPerfMCD7PEntry 100663296}

pr1645v2TvTmplPerfMCD7PIfInBCPkts OBJECT-TYPE
   SYNTAX      Counter64
   MAX-ACCESS  read-only
   STATUS      current
   DESCRIPTION
      "Path: tunnels.performance.l2tpTunnels.mibCounters.d7Performance.ifInBcastPkts

       64 bit unsigned wrappable counter."
   ::= {pr1645v2TvTmplPerfMCD7PEntry 419430400}

pr1645v2TvTmplPerfMCD7PIfInMCPkts OBJECT-TYPE
   SYNTAX      Counter64
   MAX-ACCESS  read-only
   STATUS      current
   DESCRIPTION
      "Path: tunnels.performance.l2tpTunnels.mibCounters.d7Performance.ifInMcastPkts

       64 bit unsigned wrappable counter."
   ::= {pr1645v2TvTmplPerfMCD7PEntry 436207616}

pr1645v2TvTmplPerfMCD7PIfInDiscards OBJECT-TYPE
   SYNTAX      Counter64
   MAX-ACCESS  read-only
   STATUS      current
   DESCRIPTION
      "Path: tunnels.performance.l2tpTunnels.mibCounters.d7Performance.ifInDiscards

       64 bit unsigned wrappable counter."
   ::= {pr1645v2TvTmplPerfMCD7PEntry 117440512}

pr1645v2TvTmplPerfMCD7PIfInErrors OBJECT-TYPE
   SYNTAX      Counter64
   MAX-ACCESS  read-only
   STATUS      current
   DESCRIPTION
      "Path: tunnels.performance.l2tpTunnels.mibCounters.d7Performance.ifInErrors

       64 bit unsigned wrappable counter."
   ::= {pr1645v2TvTmplPerfMCD7PEntry 134217728}

pr1645v2TvTmplPerfMCD7PIfInUnkwn OBJECT-TYPE
   SYNTAX      Counter64
   MAX-ACCESS  read-only
   STATUS      current
   DESCRIPTION
      "Path: tunnels.performance.l2tpTunnels.mibCounters.d7Performance.ifInUnknownProtos

       64 bit unsigned wrappable counter."
   ::= {pr1645v2TvTmplPerfMCD7PEntry 150994944}

pr1645v2TvTmplPerfMCD7PInDropEx OBJECT-TYPE
   SYNTAX      Counter64
   MAX-ACCESS  read-only
   STATUS      current
   DESCRIPTION
      "Path: tunnels.performance.l2tpTunnels.mibCounters.d7Performance.ifInDropLevelExceeded

       64 bit unsigned wrappable counter."
   ::= {pr1645v2TvTmplPerfMCD7PEntry 335544320}

pr1645v2TvTmplPerfMCD7PInDropNoMac OBJECT-TYPE
   SYNTAX      Counter64
   MAX-ACCESS  read-only
   STATUS      current
   DESCRIPTION
      "Path: tunnels.performance.l2tpTunnels.mibCounters.d7Performance.fInDiscardsNoMacFit

       64 bit unsigned wrappable counter."
   ::= {pr1645v2TvTmplPerfMCD7PEntry 301989888}

pr1645v2TvTmplPerfMCD7PInDropNUCast OBJECT-TYPE
   SYNTAX      Counter64
   MAX-ACCESS  read-only
   STATUS      current
   DESCRIPTION
      "Path: tunnels.performance.l2tpTunnels.mibCounters.d7Performance.fInDiscardsNUCast

       64 bit unsigned wrappable counter."
   ::= {pr1645v2TvTmplPerfMCD7PEntry 318767104}

pr1645v2TvTmplPerfMCD7PInDropFilter OBJECT-TYPE
   SYNTAX      Counter64
   MAX-ACCESS  read-only
   STATUS      current
   DESCRIPTION
      "Path: tunnels.performance.l2tpTunnels.mibCounters.d7Performance.fInDiscardsFilter

       64 bit unsigned wrappable counter."
   ::= {pr1645v2TvTmplPerfMCD7PEntry 385875968}

pr1645v2TvTmplPerfMCD7PIfInBandwidth OBJECT-TYPE
   SYNTAX      Integer32
   MAX-ACCESS  read-only
   STATUS      current
   DESCRIPTION
      "Path: tunnels.performance.l2tpTunnels.mibCounters.d7Performance.ifInBandwidth

       unit name = bps
       formula = 8 * ; 8 /"
   ::= {pr1645v2TvTmplPerfMCD7PEntry 268435456}

pr1645v2TvTmplPerfMCD7PIfOutOctets OBJECT-TYPE
   SYNTAX      Counter64
   MAX-ACCESS  read-only
   STATUS      current
   DESCRIPTION
      "Path: tunnels.performance.l2tpTunnels.mibCounters.d7Performance.ifOutOctets

       64 bit unsigned wrappable counter."
   ::= {pr1645v2TvTmplPerfMCD7PEntry 167772160}

pr1645v2TvTmplPerfMCD7PIfOutUCPkts OBJECT-TYPE
   SYNTAX      Counter64
   MAX-ACCESS  read-only
   STATUS      current
   DESCRIPTION
      "Path: tunnels.performance.l2tpTunnels.mibCounters.d7Performance.ifOutUcastPkts

       64 bit unsigned wrappable counter."
   ::= {pr1645v2TvTmplPerfMCD7PEntry 184549376}

pr1645v2TvTmplPerfMCD7PIfOutNUCPkts OBJECT-TYPE
   SYNTAX      Counter64
   MAX-ACCESS  read-only
   STATUS      current
   DESCRIPTION
      "Path: tunnels.performance.l2tpTunnels.mibCounters.d7Performance.ifOutNUcastPkts

       64 bit unsigned wrappable counter."
   ::= {pr1645v2TvTmplPerfMCD7PEntry 201326592}

pr1645v2TvTmplPerfMCD7PIfOutBCPkts OBJECT-TYPE
   SYNTAX      Counter64
   MAX-ACCESS  read-only
   STATUS      current
   DESCRIPTION
      "Path: tunnels.performance.l2tpTunnels.mibCounters.d7Performance.ifOutBcastPkts

       64 bit unsigned wrappable counter."
   ::= {pr1645v2TvTmplPerfMCD7PEntry 452984832}

pr1645v2TvTmplPerfMCD7PIfOutMCPkts OBJECT-TYPE
   SYNTAX      Counter64
   MAX-ACCESS  read-only
   STATUS      current
   DESCRIPTION
      "Path: tunnels.performance.l2tpTunnels.mibCounters.d7Performance.ifOutMcastPkts

       64 bit unsigned wrappable counter."
   ::= {pr1645v2TvTmplPerfMCD7PEntry 469762048}

pr1645v2TvTmplPerfMCD7PIfOutDiscards OBJECT-TYPE
   SYNTAX      Counter64
   MAX-ACCESS  read-only
   STATUS      current
   DESCRIPTION
      "Path: tunnels.performance.l2tpTunnels.mibCounters.d7Performance.ifOutDiscards

       64 bit unsigned wrappable counter."
   ::= {pr1645v2TvTmplPerfMCD7PEntry 218103808}

pr1645v2TvTmplPerfMCD7PIfOutErrors OBJECT-TYPE
   SYNTAX      Counter64
   MAX-ACCESS  read-only
   STATUS      current
   DESCRIPTION
      "Path: tunnels.performance.l2tpTunnels.mibCounters.d7Performance.ifOutErrors

       64 bit unsigned wrappable counter."
   ::= {pr1645v2TvTmplPerfMCD7PEntry 234881024}

pr1645v2TvTmplPerfMCD7POutDropEx OBJECT-TYPE
   SYNTAX      Counter64
   MAX-ACCESS  read-only
   STATUS      current
   DESCRIPTION
      "Path: tunnels.performance.l2tpTunnels.mibCounters.d7Performance.ifOutDropLevelExceeded

       64 bit unsigned wrappable counter."
   ::= {pr1645v2TvTmplPerfMCD7PEntry 352321536}

pr1645v2TvTmplPerfMCD7POutDropNoArp OBJECT-TYPE
   SYNTAX      Counter64
   MAX-ACCESS  read-only
   STATUS      current
   DESCRIPTION
      "Path: tunnels.performance.l2tpTunnels.mibCounters.d7Performance.ifOutDiscardsNoArp

       64 bit unsigned wrappable counter."
   ::= {pr1645v2TvTmplPerfMCD7PEntry 369098752}

pr1645v2TvTmplPerfMCD7POutDropFilter OBJECT-TYPE
   SYNTAX      Counter64
   MAX-ACCESS  read-only
   STATUS      current
   DESCRIPTION
      "Path: tunnels.performance.l2tpTunnels.mibCounters.d7Performance.ifOutDiscardsFilter

       64 bit unsigned wrappable counter."
   ::= {pr1645v2TvTmplPerfMCD7PEntry 402653184}

pr1645v2TvTmplPerfMCD7PIfOutBandwidth OBJECT-TYPE
   SYNTAX      Integer32
   MAX-ACCESS  read-only
   STATUS      current
   DESCRIPTION
      "Path: tunnels.performance.l2tpTunnels.mibCounters.d7Performance.ifOutBandwidth

       unit name = bps
       formula = 8 * ; 8 /"
   ::= {pr1645v2TvTmplPerfMCD7PEntry 285212672}

pr1645v2TvTmplPerfMCD7PIfErrSec OBJECT-TYPE
   SYNTAX      Counter32
   MAX-ACCESS  read-only
   STATUS      current
   DESCRIPTION
      "Path: tunnels.performance.l2tpTunnels.mibCounters.d7Performance.ifErrSec

       32 bit unsigned wrappable counter."
   ::= {pr1645v2TvTmplPerfMCD7PEntry 251658240}

pr1645v2TvTmplPerfInPQs OBJECT-TYPE
   SYNTAX      SEQUENCE OF Pr1645v2TvTmplPerfInPQsEntry
   MAX-ACCESS  not-accessible
   STATUS      current
   DESCRIPTION
      ""
   ::= {pr1645v2TvTmplPerf 100663296}

pr1645v2TvTmplPerfInPQsEntry OBJECT-TYPE
   SYNTAX      Pr1645v2TvTmplPerfInPQsEntry
   MAX-ACCESS  not-accessible
   STATUS      current
   DESCRIPTION
      ""
   INDEX      { pr1645v2TvTmplPerfTableIx,
                pr1645v2TvTmplPerfInPQsTableIx }
   ::= {pr1645v2TvTmplPerfInPQs 1}

Pr1645v2TvTmplPerfInPQsEntry ::=
   SEQUENCE
      {
      pr1645v2TvTmplPerfInPQsTableIx
         TableIndex,
      pr1645v2TvTmplPerfInPQsName
         INTEGER,
      pr1645v2TvTmplPerfInPQsLength
         Integer32,
      pr1645v2TvTmplPerfInPQsOctetLength
         Integer32,
      pr1645v2TvTmplPerfInPQsRedLength
         Integer32,
      pr1645v2TvTmplPerfInPQsPacketsTotal
         Counter64,
      pr1645v2TvTmplPerfInPQsPacketsDirectTx
         Counter64,
      pr1645v2TvTmplPerfInPQsPacketsQueued
         Counter64,
      pr1645v2TvTmplPerfInPQsPacketsDropped
         Counter64,
      pr1645v2TvTmplPerfInPQsPacketsRedDropped
         Counter64,
      pr1645v2TvTmplPerfInPQsPacketsCirTx
         Counter64,
      pr1645v2TvTmplPerfInPQsPacketsEirTx
         Counter64,
      pr1645v2TvTmplPerfInPQsPacketsViolateTx
         Counter64,
      pr1645v2TvTmplPerfInPQsOctetsTotal
         Counter64,
      pr1645v2TvTmplPerfInPQsOctetsDirectTx
         Counter64,
      pr1645v2TvTmplPerfInPQsOctetsQueued
         Counter64,
      pr1645v2TvTmplPerfInPQsOctetsDropped
         Counter64,
      pr1645v2TvTmplPerfInPQsOctetsRedDropped
         Counter64,
      pr1645v2TvTmplPerfInPQsOctetsCirTx
         Counter64,
      pr1645v2TvTmplPerfInPQsOctetsEirTx
         Counter64,
      pr1645v2TvTmplPerfInPQsOctetsViolateTx
         Counter64,
      pr1645v2TvTmplPerfInPQsOctetsBandwidth15sec
         Integer32,
      pr1645v2TvTmplPerfInPQsOctetsBandwidth30sec
         Integer32,
      pr1645v2TvTmplPerfInPQsOctetsBandwidth1min
         Integer32,
      pr1645v2TvTmplPerfInPQsOctetsBandwidth2min
         Integer32,
      pr1645v2TvTmplPerfInPQsOctetsBandwidth5min
         Integer32
      }

pr1645v2TvTmplPerfInPQsTableIx OBJECT-TYPE
   SYNTAX      TableIndex
   MAX-ACCESS  not-accessible
   STATUS      current
   DESCRIPTION
      ""
   ::= {pr1645v2TvTmplPerfInPQsEntry 11}

pr1645v2TvTmplPerfInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.l2tpTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPerfInPQsEntry 16777216}

pr1645v2TvTmplPerfInPQsLength OBJECT-TYPE
   SYNTAX      Integer32
   MAX-ACCESS  read-only
   STATUS      current
   DESCRIPTION
      "Path: tunnels.performance.l2tpTunnels.inPriorityQueues.length"
   ::= {pr1645v2TvTmplPerfInPQsEntry 33554432}

pr1645v2TvTmplPerfInPQsOctetLength OBJECT-TYPE
   SYNTAX      Integer32
   MAX-ACCESS  read-only
   STATUS      current
   DESCRIPTION
      "Path: tunnels.performance.l2tpTunnels.inPriorityQueues.octetLength"
   ::= {pr1645v2TvTmplPerfInPQsEntry 150994944}

pr1645v2TvTmplPerfInPQsRedLength OBJECT-TYPE
   SYNTAX      Integer32
   MAX-ACCESS  read-only
   STATUS      current
   DESCRIPTION
      "Path: tunnels.performance.l2tpTunnels.inPriorityQueues.redLength"
   ::= {pr1645v2TvTmplPerfInPQsEntry 134217728}

pr1645v2TvTmplPerfInPQsPacketsTotal OBJECT-TYPE
   SYNTAX      Counter64
   MAX-ACCESS  read-only
   STATUS      current
   DESCRIPTION
      "Path: tunnels.performance.l2tpTunnels.inPriorityQueues.packets.total

       64 bit unsigned wrappable counter."
   ::= {pr1645v2TvTmplPerfInPQsEntry 50790400}

pr1645v2TvTmplPerfInPQsPacketsDirectTx OBJECT-TYPE
   SYNTAX      Counter64
   MAX-ACCESS  read-only
   STATUS      current
   DESCRIPTION
      "Path: tunnels.performance.l2tpTunnels.inPriorityQueues.packets.directTx

       64 bit unsigned wrappable counter."
   ::= {pr1645v2TvTmplPerfInPQsEntry 50397184}

pr1645v2TvTmplPerfInPQsPacketsQueued OBJECT-TYPE
   SYNTAX      Counter64
   MAX-ACCESS  read-only
   STATUS      current
   DESCRIPTION
      "Path: tunnels.performance.l2tpTunnels.inPriorityQueues.packets.queued

       64 bit unsigned wrappable counter."
   ::= {pr1645v2TvTmplPerfInPQsEntry 50462720}

pr1645v2TvTmplPerfInPQsPacketsDropped OBJECT-TYPE
   SYNTAX      Counter64
   MAX-ACCESS  read-only
   STATUS      current
   DESCRIPTION
      "Path: tunnels.performance.l2tpTunnels.inPriorityQueues.packets.dropped

       64 bit unsigned wrappable counter."
   ::= {pr1645v2TvTmplPerfInPQsEntry 50528256}

pr1645v2TvTmplPerfInPQsPacketsRedDropped OBJECT-TYPE
   SYNTAX      Counter64
   MAX-ACCESS  read-only
   STATUS      current
   DESCRIPTION
      "Path: tunnels.performance.l2tpTunnels.inPriorityQueues.packets.redDropped

       64 bit unsigned wrappable counter."
   ::= {pr1645v2TvTmplPerfInPQsEntry 50724864}

pr1645v2TvTmplPerfInPQsPacketsCirTx OBJECT-TYPE
   SYNTAX      Counter64
   MAX-ACCESS  read-only
   STATUS      current
   DESCRIPTION
      "Path: tunnels.performance.l2tpTunnels.inPriorityQueues.packets.cirTx

       64 bit unsigned wrappable counter."
   ::= {pr1645v2TvTmplPerfInPQsEntry 50593792}

pr1645v2TvTmplPerfInPQsPacketsEirTx OBJECT-TYPE
   SYNTAX      Counter64
   MAX-ACCESS  read-only
   STATUS      current
   DESCRIPTION
      "Path: tunnels.performance.l2tpTunnels.inPriorityQueues.packets.eirTx

       64 bit unsigned wrappable counter."
   ::= {pr1645v2TvTmplPerfInPQsEntry 50659328}

pr1645v2TvTmplPerfInPQsPacketsViolateTx OBJECT-TYPE
   SYNTAX      Counter64
   MAX-ACCESS  read-only
   STATUS      current
   DESCRIPTION
      "Path: tunnels.performance.l2tpTunnels.inPriorityQueues.packets.violateTx

       64 bit unsigned wrappable counter."
   ::= {pr1645v2TvTmplPerfInPQsEntry 50855936}

pr1645v2TvTmplPerfInPQsOctetsTotal OBJECT-TYPE
   SYNTAX      Counter64
   MAX-ACCESS  read-only
   STATUS      current
   DESCRIPTION
      "Path: tunnels.performance.l2tpTunnels.inPriorityQueues.octets.total

       64 bit unsigned wrappable counter."
   ::= {pr1645v2TvTmplPerfInPQsEntry 67567616}

pr1645v2TvTmplPerfInPQsOctetsDirectTx OBJECT-TYPE
   SYNTAX      Counter64
   MAX-ACCESS  read-only
   STATUS      current
   DESCRIPTION
      "Path: tunnels.performance.l2tpTunnels.inPriorityQueues.octets.directTx

       64 bit unsigned wrappable counter."
   ::= {pr1645v2TvTmplPerfInPQsEntry 67174400}

pr1645v2TvTmplPerfInPQsOctetsQueued OBJECT-TYPE
   SYNTAX      Counter64
   MAX-ACCESS  read-only
   STATUS      current
   DESCRIPTION
      "Path: tunnels.performance.l2tpTunnels.inPriorityQueues.octets.queued

       64 bit unsigned wrappable counter."
   ::= {pr1645v2TvTmplPerfInPQsEntry 67239936}

pr1645v2TvTmplPerfInPQsOctetsDropped OBJECT-TYPE
   SYNTAX      Counter64
   MAX-ACCESS  read-only
   STATUS      current
   DESCRIPTION
      "Path: tunnels.performance.l2tpTunnels.inPriorityQueues.octets.dropped

       64 bit unsigned wrappable counter."
   ::= {pr1645v2TvTmplPerfInPQsEntry 67305472}

pr1645v2TvTmplPerfInPQsOctetsRedDropped OBJECT-TYPE
   SYNTAX      Counter64
   MAX-ACCESS  read-only
   STATUS      current
   DESCRIPTION
      "Path: tunnels.performance.l2tpTunnels.inPriorityQueues.octets.redDropped

       64 bit unsigned wrappable counter."
   ::= {pr1645v2TvTmplPerfInPQsEntry 67502080}

pr1645v2TvTmplPerfInPQsOctetsCirTx OBJECT-TYPE
   SYNTAX      Counter64
   MAX-ACCESS  read-only
   STATUS      current
   DESCRIPTION
      "Path: tunnels.performance.l2tpTunnels.inPriorityQueues.octets.cirTx

       64 bit unsigned wrappable counter."
   ::= {pr1645v2TvTmplPerfInPQsEntry 67371008}

pr1645v2TvTmplPerfInPQsOctetsEirTx OBJECT-TYPE
   SYNTAX      Counter64
   MAX-ACCESS  read-only
   STATUS      current
   DESCRIPTION
      "Path: tunnels.performance.l2tpTunnels.inPriorityQueues.octets.eirTx

       64 bit unsigned wrappable counter."
   ::= {pr1645v2TvTmplPerfInPQsEntry 67436544}

pr1645v2TvTmplPerfInPQsOctetsViolateTx OBJECT-TYPE
   SYNTAX      Counter64
   MAX-ACCESS  read-only
   STATUS      current
   DESCRIPTION
      "Path: tunnels.performance.l2tpTunnels.inPriorityQueues.octets.violateTx

       64 bit unsigned wrappable counter."
   ::= {pr1645v2TvTmplPerfInPQsEntry 67633152}

pr1645v2TvTmplPerfInPQsOctetsBandwidth15sec OBJECT-TYPE
   SYNTAX      Integer32
   MAX-ACCESS  read-only
   STATUS      current
   DESCRIPTION
      "Path: tunnels.performance.l2tpTunnels.inPriorityQueues.octets.bandwidth.15sec

       unit name = bps
       formula = 8 * ; 8 /"
   ::= {pr1645v2TvTmplPerfInPQsEntry 70386944}

pr1645v2TvTmplPerfInPQsOctetsBandwidth30sec OBJECT-TYPE
   SYNTAX      Integer32
   MAX-ACCESS  read-only
   STATUS      current
   DESCRIPTION
      "Path: tunnels.performance.l2tpTunnels.inPriorityQueues.octets.bandwidth.30sec

       unit name = bps
       formula = 8 * ; 8 /"
   ::= {pr1645v2TvTmplPerfInPQsEntry 70388224}

pr1645v2TvTmplPerfInPQsOctetsBandwidth1min OBJECT-TYPE
   SYNTAX      Integer32
   MAX-ACCESS  read-only
   STATUS      current
   DESCRIPTION
      "Path: tunnels.performance.l2tpTunnels.inPriorityQueues.octets.bandwidth.1min

       unit name = bps
       formula = 8 * ; 8 /"
   ::= {pr1645v2TvTmplPerfInPQsEntry 70390784}

pr1645v2TvTmplPerfInPQsOctetsBandwidth2min OBJECT-TYPE
   SYNTAX      Integer32
   MAX-ACCESS  read-only
   STATUS      current
   DESCRIPTION
      "Path: tunnels.performance.l2tpTunnels.inPriorityQueues.octets.bandwidth.2min

       unit name = bps
       formula = 8 * ; 8 /"
   ::= {pr1645v2TvTmplPerfInPQsEntry 70395904}

pr1645v2TvTmplPerfInPQsOctetsBandwidth5min OBJECT-TYPE
   SYNTAX      Integer32
   MAX-ACCESS  read-only
   STATUS      current
   DESCRIPTION
      "Path: tunnels.performance.l2tpTunnels.inPriorityQueues.octets.bandwidth.5min

       unit name = bps
       formula = 8 * ; 8 /"
   ::= {pr1645v2TvTmplPerfInPQsEntry 70411264}

pr1645v2TvTmplPerfInPQsH2Performance OBJECT-TYPE
   SYNTAX      SEQUENCE OF Pr1645v2TvTmplPerfInPQsH2PerformanceEntry
   MAX-ACCESS  not-accessible
   STATUS      current
   DESCRIPTION
      ""
   ::= {pr1645v2TvTmplPerf 100990976}

pr1645v2TvTmplPerfInPQsH2PerformanceEntry OBJECT-TYPE
   SYNTAX      Pr1645v2TvTmplPerfInPQsH2PerformanceEntry
   MAX-ACCESS  not-accessible
   STATUS      current
   DESCRIPTION
      ""
   INDEX      { pr1645v2TvTmplPerfTableIx,
                pr1645v2TvTmplPerfInPQsTableIx,
                pr1645v2TvTmplPerfInPQsH2PerformanceTableIx }
   ::= {pr1645v2TvTmplPerfInPQsH2Performance 1}

Pr1645v2TvTmplPerfInPQsH2PerformanceEntry ::=
   SEQUENCE
      {
      pr1645v2TvTmplPerfInPQsH2PerformanceTableIx
         TableIndex,
      pr1645v2TvTmplPerfInPQsH2PerformanceSysUpTime
         TimeTicks,
      pr1645v2TvTmplPerfInPQsH2PerformanceTotPkts
         Counter64,
      pr1645v2TvTmplPerfInPQsH2PerformanceDirTxPkts
         Counter64,
      pr1645v2TvTmplPerfInPQsH2PerformanceQdPkts
         Counter64,
      pr1645v2TvTmplPerfInPQsH2PerformanceDropPkts
         Counter64,
      pr1645v2TvTmplPerfInPQsH2PerformanceRDropPkts
         Counter64,
      pr1645v2TvTmplPerfInPQsH2PerformanceCirTxPkts
         Counter64,
      pr1645v2TvTmplPerfInPQsH2PerformanceEirTxPkts
         Counter64,
      pr1645v2TvTmplPerfInPQsH2PerformanceViolTxPkts
         Counter64,
      pr1645v2TvTmplPerfInPQsH2PerformanceTotOcts
         Counter64,
      pr1645v2TvTmplPerfInPQsH2PerformanceDirTxOcts
         Counter64,
      pr1645v2TvTmplPerfInPQsH2PerformanceQdOcts
         Counter64,
      pr1645v2TvTmplPerfInPQsH2PerformanceDropOcts
         Counter64,
      pr1645v2TvTmplPerfInPQsH2PerformanceRDropOcts
         Counter64,
      pr1645v2TvTmplPerfInPQsH2PerformanceCirTxOcts
         Counter64,
      pr1645v2TvTmplPerfInPQsH2PerformanceEirTxOcts
         Counter64,
      pr1645v2TvTmplPerfInPQsH2PerformanceViolTxOcts
         Counter64,
      pr1645v2TvTmplPerfInPQsH2PerformanceBandwidth
         Integer32
      }

pr1645v2TvTmplPerfInPQsH2PerformanceTableIx OBJECT-TYPE
   SYNTAX      TableIndex
   MAX-ACCESS  not-accessible
   STATUS      current
   DESCRIPTION
      ""
   ::= {pr1645v2TvTmplPerfInPQsH2PerformanceEntry 11}

pr1645v2TvTmplPerfInPQsH2PerformanceSysUpTime OBJECT-TYPE
   SYNTAX      TimeTicks
   MAX-ACCESS  read-only
   STATUS      current
   DESCRIPTION
      "Path: tunnels.performance.l2tpTunnels.inPriorityQueues.h2Performance.sysUpTime

       Time in centi-second."
   ::= {pr1645v2TvTmplPerfInPQsH2PerformanceEntry 16777216}

pr1645v2TvTmplPerfInPQsH2PerformanceTotPkts OBJECT-TYPE
   SYNTAX      Counter64
   MAX-ACCESS  read-only
   STATUS      current
   DESCRIPTION
      "Path: tunnels.performance.l2tpTunnels.inPriorityQueues.h2Performance.totalPkts

       64 bit unsigned wrappable counter."
   ::= {pr1645v2TvTmplPerfInPQsH2PerformanceEntry 234881024}

pr1645v2TvTmplPerfInPQsH2PerformanceDirTxPkts OBJECT-TYPE
   SYNTAX      Counter64
   MAX-ACCESS  read-only
   STATUS      current
   DESCRIPTION
      "Path: tunnels.performance.l2tpTunnels.inPriorityQueues.h2Performance.directTxPkts

       64 bit unsigned wrappable counter."
   ::= {pr1645v2TvTmplPerfInPQsH2PerformanceEntry 33554432}

pr1645v2TvTmplPerfInPQsH2PerformanceQdPkts OBJECT-TYPE
   SYNTAX      Counter64
   MAX-ACCESS  read-only
   STATUS      current
   DESCRIPTION
      "Path: tunnels.performance.l2tpTunnels.inPriorityQueues.h2Performance.queuedPkts

       64 bit unsigned wrappable counter."
   ::= {pr1645v2TvTmplPerfInPQsH2PerformanceEntry 50331648}

pr1645v2TvTmplPerfInPQsH2PerformanceDropPkts OBJECT-TYPE
   SYNTAX      Counter64
   MAX-ACCESS  read-only
   STATUS      current
   DESCRIPTION
      "Path: tunnels.performance.l2tpTunnels.inPriorityQueues.h2Performance.droppedPkts

       64 bit unsigned wrappable counter."
   ::= {pr1645v2TvTmplPerfInPQsH2PerformanceEntry 67108864}

pr1645v2TvTmplPerfInPQsH2PerformanceRDropPkts OBJECT-TYPE
   SYNTAX      Counter64
   MAX-ACCESS  read-only
   STATUS      current
   DESCRIPTION
      "Path: tunnels.performance.l2tpTunnels.inPriorityQueues.h2Performance.redDroppedPkts

       64 bit unsigned wrappable counter."
   ::= {pr1645v2TvTmplPerfInPQsH2PerformanceEntry 201326592}

pr1645v2TvTmplPerfInPQsH2PerformanceCirTxPkts OBJECT-TYPE
   SYNTAX      Counter64
   MAX-ACCESS  read-only
   STATUS      current
   DESCRIPTION
      "Path: tunnels.performance.l2tpTunnels.inPriorityQueues.h2Performance.cirTxPkts

       64 bit unsigned wrappable counter."
   ::= {pr1645v2TvTmplPerfInPQsH2PerformanceEntry 83886080}

pr1645v2TvTmplPerfInPQsH2PerformanceEirTxPkts OBJECT-TYPE
   SYNTAX      Counter64
   MAX-ACCESS  read-only
   STATUS      current
   DESCRIPTION
      "Path: tunnels.performance.l2tpTunnels.inPriorityQueues.h2Performance.eirTxPkts

       64 bit unsigned wrappable counter."
   ::= {pr1645v2TvTmplPerfInPQsH2PerformanceEntry 100663296}

pr1645v2TvTmplPerfInPQsH2PerformanceViolTxPkts OBJECT-TYPE
   SYNTAX      Counter64
   MAX-ACCESS  read-only
   STATUS      current
   DESCRIPTION
      "Path: tunnels.performance.l2tpTunnels.inPriorityQueues.h2Performance.violateTxPkts

       64 bit unsigned wrappable counter."
   ::= {pr1645v2TvTmplPerfInPQsH2PerformanceEntry 301989888}

pr1645v2TvTmplPerfInPQsH2PerformanceTotOcts OBJECT-TYPE
   SYNTAX      Counter64
   MAX-ACCESS  read-only
   STATUS      current
   DESCRIPTION
      "Path: tunnels.performance.l2tpTunnels.inPriorityQueues.h2Performance.totalOctets

       64 bit unsigned wrappable counter."
   ::= {pr1645v2TvTmplPerfInPQsH2PerformanceEntry 251658240}

pr1645v2TvTmplPerfInPQsH2PerformanceDirTxOcts OBJECT-TYPE
   SYNTAX      Counter64
   MAX-ACCESS  read-only
   STATUS      current
   DESCRIPTION
      "Path: tunnels.performance.l2tpTunnels.inPriorityQueues.h2Performance.directTxOctets

       64 bit unsigned wrappable counter."
   ::= {pr1645v2TvTmplPerfInPQsH2PerformanceEntry 117440512}

pr1645v2TvTmplPerfInPQsH2PerformanceQdOcts OBJECT-TYPE
   SYNTAX      Counter64
   MAX-ACCESS  read-only
   STATUS      current
   DESCRIPTION
      "Path: tunnels.performance.l2tpTunnels.inPriorityQueues.h2Performance.queuedOctets

       64 bit unsigned wrappable counter."
   ::= {pr1645v2TvTmplPerfInPQsH2PerformanceEntry 134217728}

pr1645v2TvTmplPerfInPQsH2PerformanceDropOcts OBJECT-TYPE
   SYNTAX      Counter64
   MAX-ACCESS  read-only
   STATUS      current
   DESCRIPTION
      "Path: tunnels.performance.l2tpTunnels.inPriorityQueues.h2Performance.droppedOctets

       64 bit unsigned wrappable counter."
   ::= {pr1645v2TvTmplPerfInPQsH2PerformanceEntry 150994944}

pr1645v2TvTmplPerfInPQsH2PerformanceRDropOcts OBJECT-TYPE
   SYNTAX      Counter64
   MAX-ACCESS  read-only
   STATUS      current
   DESCRIPTION
      "Path: tunnels.performance.l2tpTunnels.inPriorityQueues.h2Performance.redDroppedOctets

       64 bit unsigned wrappable counter."
   ::= {pr1645v2TvTmplPerfInPQsH2PerformanceEntry 218103808}

pr1645v2TvTmplPerfInPQsH2PerformanceCirTxOcts OBJECT-TYPE
   SYNTAX      Counter64
   MAX-ACCESS  read-only
   STATUS      current
   DESCRIPTION
      "Path: tunnels.performance.l2tpTunnels.inPriorityQueues.h2Performance.cirTxOctets

       64 bit unsigned wrappable counter."
   ::= {pr1645v2TvTmplPerfInPQsH2PerformanceEntry 167772160}

pr1645v2TvTmplPerfInPQsH2PerformanceEirTxOcts OBJECT-TYPE
   SYNTAX      Counter64
   MAX-ACCESS  read-only
   STATUS      current
   DESCRIPTION
      "Path: tunnels.performance.l2tpTunnels.inPriorityQueues.h2Performance.eirTxOctets

       64 bit unsigned wrappable counter."
   ::= {pr1645v2TvTmplPerfInPQsH2PerformanceEntry 184549376}

pr1645v2TvTmplPerfInPQsH2PerformanceViolTxOcts OBJECT-TYPE
   SYNTAX      Counter64
   MAX-ACCESS  read-only
   STATUS      current
   DESCRIPTION
      "Path: tunnels.performance.l2tpTunnels.inPriorityQueues.h2Performance.violateTxOctets

       64 bit unsigned wrappable counter."
   ::= {pr1645v2TvTmplPerfInPQsH2PerformanceEntry 318767104}

pr1645v2TvTmplPerfInPQsH2PerformanceBandwidth OBJECT-TYPE
   SYNTAX      Integer32
   MAX-ACCESS  read-only
   STATUS      current
   DESCRIPTION
      "Path: tunnels.performance.l2tpTunnels.inPriorityQueues.h2Performance.bandwidth

       unit name = bps
       formula = 8 * ; 8 /"
   ::= {pr1645v2TvTmplPerfInPQsH2PerformanceEntry 268435456}

pr1645v2TvTmplPerfInPQsH24Performance OBJECT-TYPE
   SYNTAX      SEQUENCE OF Pr1645v2TvTmplPerfInPQsH24PerformanceEntry
   MAX-ACCESS  not-accessible
   STATUS      current
   DESCRIPTION
      ""
   ::= {pr1645v2TvTmplPerf 101056512}

pr1645v2TvTmplPerfInPQsH24PerformanceEntry OBJECT-TYPE
   SYNTAX      Pr1645v2TvTmplPerfInPQsH24PerformanceEntry
   MAX-ACCESS  not-accessible
   STATUS      current
   DESCRIPTION
      ""
   INDEX      { pr1645v2TvTmplPerfTableIx,
                pr1645v2TvTmplPerfInPQsTableIx,
                pr1645v2TvTmplPerfInPQsH24PerformanceTableIx }
   ::= {pr1645v2TvTmplPerfInPQsH24Performance 1}

Pr1645v2TvTmplPerfInPQsH24PerformanceEntry ::=
   SEQUENCE
      {
      pr1645v2TvTmplPerfInPQsH24PerformanceTableIx
         TableIndex,
      pr1645v2TvTmplPerfInPQsH24PerformanceSysUpTime
         TimeTicks,
      pr1645v2TvTmplPerfInPQsH24PerformanceTotPkts
         Counter64,
      pr1645v2TvTmplPerfInPQsH24PerformanceDirTxPkts
         Counter64,
      pr1645v2TvTmplPerfInPQsH24PerformanceQdPkts
         Counter64,
      pr1645v2TvTmplPerfInPQsH24PerformanceDropPkts
         Counter64,
      pr1645v2TvTmplPerfInPQsH24PerformanceRDropPkts
         Counter64,
      pr1645v2TvTmplPerfInPQsH24PerformanceCirTxPkts
         Counter64,
      pr1645v2TvTmplPerfInPQsH24PerformanceEirTxPkts
         Counter64,
      pr1645v2TvTmplPerfInPQsH24PerformanceViolTxPkts
         Counter64,
      pr1645v2TvTmplPerfInPQsH24PerformanceTotOcts
         Counter64,
      pr1645v2TvTmplPerfInPQsH24PerformanceDirTxOcts
         Counter64,
      pr1645v2TvTmplPerfInPQsH24PerformanceQdOcts
         Counter64,
      pr1645v2TvTmplPerfInPQsH24PerformanceDropOcts
         Counter64,
      pr1645v2TvTmplPerfInPQsH24PerformanceRDropOcts
         Counter64,
      pr1645v2TvTmplPerfInPQsH24PerformanceCirTxOcts
         Counter64,
      pr1645v2TvTmplPerfInPQsH24PerformanceEirTxOcts
         Counter64,
      pr1645v2TvTmplPerfInPQsH24PerformanceViolTxOcts
         Counter64,
      pr1645v2TvTmplPerfInPQsH24PerformanceBandwidth
         Integer32
      }

pr1645v2TvTmplPerfInPQsH24PerformanceTableIx OBJECT-TYPE
   SYNTAX      TableIndex
   MAX-ACCESS  not-accessible
   STATUS      current
   DESCRIPTION
      ""
   ::= {pr1645v2TvTmplPerfInPQsH24PerformanceEntry 11}

pr1645v2TvTmplPerfInPQsH24PerformanceSysUpTime OBJECT-TYPE
   SYNTAX      TimeTicks
   MAX-ACCESS  read-only
   STATUS      current
   DESCRIPTION
      "Path: tunnels.performance.l2tpTunnels.inPriorityQueues.h24Performance.sysUpTime

       Time in centi-second."
   ::= {pr1645v2TvTmplPerfInPQsH24PerformanceEntry 16777216}

pr1645v2TvTmplPerfInPQsH24PerformanceTotPkts OBJECT-TYPE
   SYNTAX      Counter64
   MAX-ACCESS  read-only
   STATUS      current
   DESCRIPTION
      "Path: tunnels.performance.l2tpTunnels.inPriorityQueues.h24Performance.totalPkts

       64 bit unsigned wrappable counter."
   ::= {pr1645v2TvTmplPerfInPQsH24PerformanceEntry 234881024}

pr1645v2TvTmplPerfInPQsH24PerformanceDirTxPkts OBJECT-TYPE
   SYNTAX      Counter64
   MAX-ACCESS  read-only
   STATUS      current
   DESCRIPTION
      "Path: tunnels.performance.l2tpTunnels.inPriorityQueues.h24Performance.directTxPkts

       64 bit unsigned wrappable counter."
   ::= {pr1645v2TvTmplPerfInPQsH24PerformanceEntry 33554432}

pr1645v2TvTmplPerfInPQsH24PerformanceQdPkts OBJECT-TYPE
   SYNTAX      Counter64
   MAX-ACCESS  read-only
   STATUS      current
   DESCRIPTION
      "Path: tunnels.performance.l2tpTunnels.inPriorityQueues.h24Performance.queuedPkts

       64 bit unsigned wrappable counter."
   ::= {pr1645v2TvTmplPerfInPQsH24PerformanceEntry 50331648}

pr1645v2TvTmplPerfInPQsH24PerformanceDropPkts OBJECT-TYPE
   SYNTAX      Counter64
   MAX-ACCESS  read-only
   STATUS      current
   DESCRIPTION
      "Path: tunnels.performance.l2tpTunnels.inPriorityQueues.h24Performance.droppedPkts

       64 bit unsigned wrappable counter."
   ::= {pr1645v2TvTmplPerfInPQsH24PerformanceEntry 67108864}

pr1645v2TvTmplPerfInPQsH24PerformanceRDropPkts OBJECT-TYPE
   SYNTAX      Counter64
   MAX-ACCESS  read-only
   STATUS      current
   DESCRIPTION
      "Path: tunnels.performance.l2tpTunnels.inPriorityQueues.h24Performance.redDroppedPkts

       64 bit unsigned wrappable counter."
   ::= {pr1645v2TvTmplPerfInPQsH24PerformanceEntry 201326592}

pr1645v2TvTmplPerfInPQsH24PerformanceCirTxPkts OBJECT-TYPE
   SYNTAX      Counter64
   MAX-ACCESS  read-only
   STATUS      current
   DESCRIPTION
      "Path: tunnels.performance.l2tpTunnels.inPriorityQueues.h24Performance.cirTxPkts

       64 bit unsigned wrappable counter."
   ::= {pr1645v2TvTmplPerfInPQsH24PerformanceEntry 83886080}

pr1645v2TvTmplPerfInPQsH24PerformanceEirTxPkts OBJECT-TYPE
   SYNTAX      Counter64
   MAX-ACCESS  read-only
   STATUS      current
   DESCRIPTION
      "Path: tunnels.performance.l2tpTunnels.inPriorityQueues.h24Performance.eirTxPkts

       64 bit unsigned wrappable counter."
   ::= {pr1645v2TvTmplPerfInPQsH24PerformanceEntry 100663296}

pr1645v2TvTmplPerfInPQsH24PerformanceViolTxPkts OBJECT-TYPE
   SYNTAX      Counter64
   MAX-ACCESS  read-only
   STATUS      current
   DESCRIPTION
      "Path: tunnels.performance.l2tpTunnels.inPriorityQueues.h24Performance.violateTxPkts

       64 bit unsigned wrappable counter."
   ::= {pr1645v2TvTmplPerfInPQsH24PerformanceEntry 301989888}

pr1645v2TvTmplPerfInPQsH24PerformanceTotOcts OBJECT-TYPE
   SYNTAX      Counter64
   MAX-ACCESS  read-only
   STATUS      current
   DESCRIPTION
      "Path: tunnels.performance.l2tpTunnels.inPriorityQueues.h24Performance.totalOctets

       64 bit unsigned wrappable counter."
   ::= {pr1645v2TvTmplPerfInPQsH24PerformanceEntry 251658240}

pr1645v2TvTmplPerfInPQsH24PerformanceDirTxOcts OBJECT-TYPE
   SYNTAX      Counter64
   MAX-ACCESS  read-only
   STATUS      current
   DESCRIPTION
      "Path: tunnels.performance.l2tpTunnels.inPriorityQueues.h24Performance.directTxOctets

       64 bit unsigned wrappable counter."
   ::= {pr1645v2TvTmplPerfInPQsH24PerformanceEntry 117440512}

pr1645v2TvTmplPerfInPQsH24PerformanceQdOcts OBJECT-TYPE
   SYNTAX      Counter64
   MAX-ACCESS  read-only
   STATUS      current
   DESCRIPTION
      "Path: tunnels.performance.l2tpTunnels.inPriorityQueues.h24Performance.queuedOctets

       64 bit unsigned wrappable counter."
   ::= {pr1645v2TvTmplPerfInPQsH24PerformanceEntry 134217728}

pr1645v2TvTmplPerfInPQsH24PerformanceDropOcts OBJECT-TYPE
   SYNTAX      Counter64
   MAX-ACCESS  read-only
   STATUS      current
   DESCRIPTION
      "Path: tunnels.performance.l2tpTunnels.inPriorityQueues.h24Performance.droppedOctets

       64 bit unsigned wrappable counter."
   ::= {pr1645v2TvTmplPerfInPQsH24PerformanceEntry 150994944}

pr1645v2TvTmplPerfInPQsH24PerformanceRDropOcts OBJECT-TYPE
   SYNTAX      Counter64
   MAX-ACCESS  read-only
   STATUS      current
   DESCRIPTION
      "Path: tunnels.performance.l2tpTunnels.inPriorityQueues.h24Performance.redDroppedOctets

       64 bit unsigned wrappable counter."
   ::= {pr1645v2TvTmplPerfInPQsH24PerformanceEntry 218103808}

pr1645v2TvTmplPerfInPQsH24PerformanceCirTxOcts OBJECT-TYPE
   SYNTAX      Counter64
   MAX-ACCESS  read-only
   STATUS      current
   DESCRIPTION
      "Path: tunnels.performance.l2tpTunnels.inPriorityQueues.h24Performance.cirTxOctets

       64 bit unsigned wrappable counter."
   ::= {pr1645v2TvTmplPerfInPQsH24PerformanceEntry 167772160}

pr1645v2TvTmplPerfInPQsH24PerformanceEirTxOcts OBJECT-TYPE
   SYNTAX      Counter64
   MAX-ACCESS  read-only
   STATUS      current
   DESCRIPTION
      "Path: tunnels.performance.l2tpTunnels.inPriorityQueues.h24Performance.eirTxOctets

       64 bit unsigned wrappable counter."
   ::= {pr1645v2TvTmplPerfInPQsH24PerformanceEntry 184549376}

pr1645v2TvTmplPerfInPQsH24PerformanceViolTxOcts OBJECT-TYPE
   SYNTAX      Counter64
   MAX-ACCESS  read-only
   STATUS      current
   DESCRIPTION
      "Path: tunnels.performance.l2tpTunnels.inPriorityQueues.h24Performance.violateTxOctets

       64 bit unsigned wrappable counter."
   ::= {pr1645v2TvTmplPerfInPQsH24PerformanceEntry 318767104}

pr1645v2TvTmplPerfInPQsH24PerformanceBandwidth OBJECT-TYPE
   SYNTAX      Integer32
   MAX-ACCESS  read-only
   STATUS      current
   DESCRIPTION
      "Path: tunnels.performance.l2tpTunnels.inPriorityQueues.h24Performance.bandwidth

       unit name = bps
       formula = 8 * ; 8 /"
   ::= {pr1645v2TvTmplPerfInPQsH24PerformanceEntry 268435456}

pr1645v2TvTmplPerfInPQsD7Performance OBJECT-TYPE
   SYNTAX      SEQUENCE OF Pr1645v2TvTmplPerfInPQsD7PerformanceEntry
   MAX-ACCESS  not-accessible
   STATUS      current
   DESCRIPTION
      ""
   ::= {pr1645v2TvTmplPerf 101122048}

pr1645v2TvTmplPerfInPQsD7PerformanceEntry OBJECT-TYPE
   SYNTAX      Pr1645v2TvTmplPerfInPQsD7PerformanceEntry
   MAX-ACCESS  not-accessible
   STATUS      current
   DESCRIPTION
      ""
   INDEX      { pr1645v2TvTmplPerfTableIx,
                pr1645v2TvTmplPerfInPQsTableIx,
                pr1645v2TvTmplPerfInPQsD7PerformanceTableIx }
   ::= {pr1645v2TvTmplPerfInPQsD7Performance 1}

Pr1645v2TvTmplPerfInPQsD7PerformanceEntry ::=
   SEQUENCE
      {
      pr1645v2TvTmplPerfInPQsD7PerformanceTableIx
         TableIndex,
      pr1645v2TvTmplPerfInPQsD7PerformanceSysUpTime
         TimeTicks,
      pr1645v2TvTmplPerfInPQsD7PerformanceTotPkts
         Counter64,
      pr1645v2TvTmplPerfInPQsD7PerformanceDirTxPkts
         Counter64,
      pr1645v2TvTmplPerfInPQsD7PerformanceQdPkts
         Counter64,
      pr1645v2TvTmplPerfInPQsD7PerformanceDropPkts
         Counter64,
      pr1645v2TvTmplPerfInPQsD7PerformanceRDropPkts
         Counter64,
      pr1645v2TvTmplPerfInPQsD7PerformanceCirTxPkts
         Counter64,
      pr1645v2TvTmplPerfInPQsD7PerformanceEirTxPkts
         Counter64,
      pr1645v2TvTmplPerfInPQsD7PerformanceViolTxPkts
         Counter64,
      pr1645v2TvTmplPerfInPQsD7PerformanceTotOcts
         Counter64,
      pr1645v2TvTmplPerfInPQsD7PerformanceDirTxOcts
         Counter64,
      pr1645v2TvTmplPerfInPQsD7PerformanceQdOcts
         Counter64,
      pr1645v2TvTmplPerfInPQsD7PerformanceDropOcts
         Counter64,
      pr1645v2TvTmplPerfInPQsD7PerformanceRDropOcts
         Counter64,
      pr1645v2TvTmplPerfInPQsD7PerformanceCirTxOcts
         Counter64,
      pr1645v2TvTmplPerfInPQsD7PerformanceEirTxOcts
         Counter64,
      pr1645v2TvTmplPerfInPQsD7PerformanceViolTxOcts
         Counter64,
      pr1645v2TvTmplPerfInPQsD7PerformanceBandwidth
         Integer32
      }

pr1645v2TvTmplPerfInPQsD7PerformanceTableIx OBJECT-TYPE
   SYNTAX      TableIndex
   MAX-ACCESS  not-accessible
   STATUS      current
   DESCRIPTION
      ""
   ::= {pr1645v2TvTmplPerfInPQsD7PerformanceEntry 11}

pr1645v2TvTmplPerfInPQsD7PerformanceSysUpTime OBJECT-TYPE
   SYNTAX      TimeTicks
   MAX-ACCESS  read-only
   STATUS      current
   DESCRIPTION
      "Path: tunnels.performance.l2tpTunnels.inPriorityQueues.d7Performance.sysUpTime

       Time in centi-second."
   ::= {pr1645v2TvTmplPerfInPQsD7PerformanceEntry 16777216}

pr1645v2TvTmplPerfInPQsD7PerformanceTotPkts OBJECT-TYPE
   SYNTAX      Counter64
   MAX-ACCESS  read-only
   STATUS      current
   DESCRIPTION
      "Path: tunnels.performance.l2tpTunnels.inPriorityQueues.d7Performance.totalPkts

       64 bit unsigned wrappable counter."
   ::= {pr1645v2TvTmplPerfInPQsD7PerformanceEntry 234881024}

pr1645v2TvTmplPerfInPQsD7PerformanceDirTxPkts OBJECT-TYPE
   SYNTAX      Counter64
   MAX-ACCESS  read-only
   STATUS      current
   DESCRIPTION
      "Path: tunnels.performance.l2tpTunnels.inPriorityQueues.d7Performance.directTxPkts

       64 bit unsigned wrappable counter."
   ::= {pr1645v2TvTmplPerfInPQsD7PerformanceEntry 33554432}

pr1645v2TvTmplPerfInPQsD7PerformanceQdPkts OBJECT-TYPE
   SYNTAX      Counter64
   MAX-ACCESS  read-only
   STATUS      current
   DESCRIPTION
      "Path: tunnels.performance.l2tpTunnels.inPriorityQueues.d7Performance.queuedPkts

       64 bit unsigned wrappable counter."
   ::= {pr1645v2TvTmplPerfInPQsD7PerformanceEntry 50331648}

pr1645v2TvTmplPerfInPQsD7PerformanceDropPkts OBJECT-TYPE
   SYNTAX      Counter64
   MAX-ACCESS  read-only
   STATUS      current
   DESCRIPTION
      "Path: tunnels.performance.l2tpTunnels.inPriorityQueues.d7Performance.droppedPkts

       64 bit unsigned wrappable counter."
   ::= {pr1645v2TvTmplPerfInPQsD7PerformanceEntry 67108864}

pr1645v2TvTmplPerfInPQsD7PerformanceRDropPkts OBJECT-TYPE
   SYNTAX      Counter64
   MAX-ACCESS  read-only
   STATUS      current
   DESCRIPTION
      "Path: tunnels.performance.l2tpTunnels.inPriorityQueues.d7Performance.redDroppedPkts

       64 bit unsigned wrappable counter."
   ::= {pr1645v2TvTmplPerfInPQsD7PerformanceEntry 201326592}

pr1645v2TvTmplPerfInPQsD7PerformanceCirTxPkts OBJECT-TYPE
   SYNTAX      Counter64
   MAX-ACCESS  read-only
   STATUS      current
   DESCRIPTION
      "Path: tunnels.performance.l2tpTunnels.inPriorityQueues.d7Performance.cirTxPkts

       64 bit unsigned wrappable counter."
   ::= {pr1645v2TvTmplPerfInPQsD7PerformanceEntry 83886080}

pr1645v2TvTmplPerfInPQsD7PerformanceEirTxPkts OBJECT-TYPE
   SYNTAX      Counter64
   MAX-ACCESS  read-only
   STATUS      current
   DESCRIPTION
      "Path: tunnels.performance.l2tpTunnels.inPriorityQueues.d7Performance.eirTxPkts

       64 bit unsigned wrappable counter."
   ::= {pr1645v2TvTmplPerfInPQsD7PerformanceEntry 100663296}

pr1645v2TvTmplPerfInPQsD7PerformanceViolTxPkts OBJECT-TYPE
   SYNTAX      Counter64
   MAX-ACCESS  read-only
   STATUS      current
   DESCRIPTION
      "Path: tunnels.performance.l2tpTunnels.inPriorityQueues.d7Performance.violateTxPkts

       64 bit unsigned wrappable counter."
   ::= {pr1645v2TvTmplPerfInPQsD7PerformanceEntry 301989888}

pr1645v2TvTmplPerfInPQsD7PerformanceTotOcts OBJECT-TYPE
   SYNTAX      Counter64
   MAX-ACCESS  read-only
   STATUS      current
   DESCRIPTION
      "Path: tunnels.performance.l2tpTunnels.inPriorityQueues.d7Performance.totalOctets

       64 bit unsigned wrappable counter."
   ::= {pr1645v2TvTmplPerfInPQsD7PerformanceEntry 251658240}

pr1645v2TvTmplPerfInPQsD7PerformanceDirTxOcts OBJECT-TYPE
   SYNTAX      Counter64
   MAX-ACCESS  read-only
   STATUS      current
   DESCRIPTION
      "Path: tunnels.performance.l2tpTunnels.inPriorityQueues.d7Performance.directTxOctets

       64 bit unsigned wrappable counter."
   ::= {pr1645v2TvTmplPerfInPQsD7PerformanceEntry 117440512}

pr1645v2TvTmplPerfInPQsD7PerformanceQdOcts OBJECT-TYPE
   SYNTAX      Counter64
   MAX-ACCESS  read-only
   STATUS      current
   DESCRIPTION
      "Path: tunnels.performance.l2tpTunnels.inPriorityQueues.d7Performance.queuedOctets

       64 bit unsigned wrappable counter."
   ::= {pr1645v2TvTmplPerfInPQsD7PerformanceEntry 134217728}

pr1645v2TvTmplPerfInPQsD7PerformanceDropOcts OBJECT-TYPE
   SYNTAX      Counter64
   MAX-ACCESS  read-only
   STATUS      current
   DESCRIPTION
      "Path: tunnels.performance.l2tpTunnels.inPriorityQueues.d7Performance.droppedOctets

       64 bit unsigned wrappable counter."
   ::= {pr1645v2TvTmplPerfInPQsD7PerformanceEntry 150994944}

pr1645v2TvTmplPerfInPQsD7PerformanceRDropOcts OBJECT-TYPE
   SYNTAX      Counter64
   MAX-ACCESS  read-only
   STATUS      current
   DESCRIPTION
      "Path: tunnels.performance.l2tpTunnels.inPriorityQueues.d7Performance.redDroppedOctets

       64 bit unsigned wrappable counter."
   ::= {pr1645v2TvTmplPerfInPQsD7PerformanceEntry 218103808}

pr1645v2TvTmplPerfInPQsD7PerformanceCirTxOcts OBJECT-TYPE
   SYNTAX      Counter64
   MAX-ACCESS  read-only
   STATUS      current
   DESCRIPTION
      "Path: tunnels.performance.l2tpTunnels.inPriorityQueues.d7Performance.cirTxOctets

       64 bit unsigned wrappable counter."
   ::= {pr1645v2TvTmplPerfInPQsD7PerformanceEntry 167772160}

pr1645v2TvTmplPerfInPQsD7PerformanceEirTxOcts OBJECT-TYPE
   SYNTAX      Counter64
   MAX-ACCESS  read-only
   STATUS      current
   DESCRIPTION
      "Path: tunnels.performance.l2tpTunnels.inPriorityQueues.d7Performance.eirTxOctets

       64 bit unsigned wrappable counter."
   ::= {pr1645v2TvTmplPerfInPQsD7PerformanceEntry 184549376}

pr1645v2TvTmplPerfInPQsD7PerformanceViolTxOcts OBJECT-TYPE
   SYNTAX      Counter64
   MAX-ACCESS  read-only
   STATUS      current
   DESCRIPTION
      "Path: tunnels.performance.l2tpTunnels.inPriorityQueues.d7Performance.violateTxOctets

       64 bit unsigned wrappable counter."
   ::= {pr1645v2TvTmplPerfInPQsD7PerformanceEntry 318767104}

pr1645v2TvTmplPerfInPQsD7PerformanceBandwidth OBJECT-TYPE
   SYNTAX      Integer32
   MAX-ACCESS  read-only
   STATUS      current
   DESCRIPTION
      "Path: tunnels.performance.l2tpTunnels.inPriorityQueues.d7Performance.bandwidth

       unit name = bps
       formula = 8 * ; 8 /"
   ::= {pr1645v2TvTmplPerfInPQsD7PerformanceEntry 268435456}

pr1645v2TvTmplPerfOutPQs OBJECT-TYPE
   SYNTAX      SEQUENCE OF Pr1645v2TvTmplPerfOutPQsEntry
   MAX-ACCESS  not-accessible
   STATUS      current
   DESCRIPTION
      ""
   ::= {pr1645v2TvTmplPerf 83886080}

pr1645v2TvTmplPerfOutPQsEntry OBJECT-TYPE
   SYNTAX      Pr1645v2TvTmplPerfOutPQsEntry
   MAX-ACCESS  not-accessible
   STATUS      current
   DESCRIPTION
      ""
   INDEX      { pr1645v2TvTmplPerfTableIx,
                pr1645v2TvTmplPerfOutPQsTableIx }
   ::= {pr1645v2TvTmplPerfOutPQs 1}

Pr1645v2TvTmplPerfOutPQsEntry ::=
   SEQUENCE
      {
      pr1645v2TvTmplPerfOutPQsTableIx
         TableIndex,
      pr1645v2TvTmplPerfOutPQsName
         INTEGER,
      pr1645v2TvTmplPerfOutPQsLength
         Integer32,
      pr1645v2TvTmplPerfOutPQsOctetLength
         Integer32,
      pr1645v2TvTmplPerfOutPQsRedLength
         Integer32,
      pr1645v2TvTmplPerfOutPQsPacketsTotal
         Counter64,
      pr1645v2TvTmplPerfOutPQsPacketsDirectTx
         Counter64,
      pr1645v2TvTmplPerfOutPQsPacketsQueued
         Counter64,
      pr1645v2TvTmplPerfOutPQsPacketsDropped
         Counter64,
      pr1645v2TvTmplPerfOutPQsPacketsRedDropped
         Counter64,
      pr1645v2TvTmplPerfOutPQsPacketsCirTx
         Counter64,
      pr1645v2TvTmplPerfOutPQsPacketsEirTx
         Counter64,
      pr1645v2TvTmplPerfOutPQsPacketsViolateTx
         Counter64,
      pr1645v2TvTmplPerfOutPQsOctetsTotal
         Counter64,
      pr1645v2TvTmplPerfOutPQsOctetsDirectTx
         Counter64,
      pr1645v2TvTmplPerfOutPQsOctetsQueued
         Counter64,
      pr1645v2TvTmplPerfOutPQsOctetsDropped
         Counter64,
      pr1645v2TvTmplPerfOutPQsOctetsRedDropped
         Counter64,
      pr1645v2TvTmplPerfOutPQsOctetsCirTx
         Counter64,
      pr1645v2TvTmplPerfOutPQsOctetsEirTx
         Counter64,
      pr1645v2TvTmplPerfOutPQsOctetsViolateTx
         Counter64,
      pr1645v2TvTmplPerfOutPQsOctetsBandwidth15sec
         Integer32,
      pr1645v2TvTmplPerfOutPQsOctetsBandwidth30sec
         Integer32,
      pr1645v2TvTmplPerfOutPQsOctetsBandwidth1min
         Integer32,
      pr1645v2TvTmplPerfOutPQsOctetsBandwidth2min
         Integer32,
      pr1645v2TvTmplPerfOutPQsOctetsBandwidth5min
         Integer32
      }

pr1645v2TvTmplPerfOutPQsTableIx OBJECT-TYPE
   SYNTAX      TableIndex
   MAX-ACCESS  not-accessible
   STATUS      current
   DESCRIPTION
      ""
   ::= {pr1645v2TvTmplPerfOutPQsEntry 11}

pr1645v2TvTmplPerfOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.l2tpTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPerfOutPQsEntry 16777216}

pr1645v2TvTmplPerfOutPQsLength OBJECT-TYPE
   SYNTAX      Integer32
   MAX-ACCESS  read-only
   STATUS      current
   DESCRIPTION
      "Path: tunnels.performance.l2tpTunnels.outPriorityQueues.length"
   ::= {pr1645v2TvTmplPerfOutPQsEntry 33554432}

pr1645v2TvTmplPerfOutPQsOctetLength OBJECT-TYPE
   SYNTAX      Integer32
   MAX-ACCESS  read-only
   STATUS      current
   DESCRIPTION
      "Path: tunnels.performance.l2tpTunnels.outPriorityQueues.octetLength"
   ::= {pr1645v2TvTmplPerfOutPQsEntry 150994944}

pr1645v2TvTmplPerfOutPQsRedLength OBJECT-TYPE
   SYNTAX      Integer32
   MAX-ACCESS  read-only
   STATUS      current
   DESCRIPTION
      "Path: tunnels.performance.l2tpTunnels.outPriorityQueues.redLength"
   ::= {pr1645v2TvTmplPerfOutPQsEntry 134217728}

pr1645v2TvTmplPerfOutPQsPacketsTotal OBJECT-TYPE
   SYNTAX      Counter64
   MAX-ACCESS  read-only
   STATUS      current
   DESCRIPTION
      "Path: tunnels.performance.l2tpTunnels.outPriorityQueues.packets.total

       64 bit unsigned wrappable counter."
   ::= {pr1645v2TvTmplPerfOutPQsEntry 50790400}

pr1645v2TvTmplPerfOutPQsPacketsDirectTx OBJECT-TYPE
   SYNTAX      Counter64
   MAX-ACCESS  read-only
   STATUS      current
   DESCRIPTION
      "Path: tunnels.performance.l2tpTunnels.outPriorityQueues.packets.directTx

       64 bit unsigned wrappable counter."
   ::= {pr1645v2TvTmplPerfOutPQsEntry 50397184}

pr1645v2TvTmplPerfOutPQsPacketsQueued OBJECT-TYPE
   SYNTAX      Counter64
   MAX-ACCESS  read-only
   STATUS      current
   DESCRIPTION
      "Path: tunnels.performance.l2tpTunnels.outPriorityQueues.packets.queued

       64 bit unsigned wrappable counter."
   ::= {pr1645v2TvTmplPerfOutPQsEntry 50462720}

pr1645v2TvTmplPerfOutPQsPacketsDropped OBJECT-TYPE
   SYNTAX      Counter64
   MAX-ACCESS  read-only
   STATUS      current
   DESCRIPTION
      "Path: tunnels.performance.l2tpTunnels.outPriorityQueues.packets.dropped

       64 bit unsigned wrappable counter."
   ::= {pr1645v2TvTmplPerfOutPQsEntry 50528256}

pr1645v2TvTmplPerfOutPQsPacketsRedDropped OBJECT-TYPE
   SYNTAX      Counter64
   MAX-ACCESS  read-only
   STATUS      current
   DESCRIPTION
      "Path: tunnels.performance.l2tpTunnels.outPriorityQueues.packets.redDropped

       64 bit unsigned wrappable counter."
   ::= {pr1645v2TvTmplPerfOutPQsEntry 50724864}

pr1645v2TvTmplPerfOutPQsPacketsCirTx OBJECT-TYPE
   SYNTAX      Counter64
   MAX-ACCESS  read-only
   STATUS      current
   DESCRIPTION
      "Path: tunnels.performance.l2tpTunnels.outPriorityQueues.packets.cirTx

       64 bit unsigned wrappable counter."
   ::= {pr1645v2TvTmplPerfOutPQsEntry 50593792}

pr1645v2TvTmplPerfOutPQsPacketsEirTx OBJECT-TYPE
   SYNTAX      Counter64
   MAX-ACCESS  read-only
   STATUS      current
   DESCRIPTION
      "Path: tunnels.performance.l2tpTunnels.outPriorityQueues.packets.eirTx

       64 bit unsigned wrappable counter."
   ::= {pr1645v2TvTmplPerfOutPQsEntry 50659328}

pr1645v2TvTmplPerfOutPQsPacketsViolateTx OBJECT-TYPE
   SYNTAX      Counter64
   MAX-ACCESS  read-only
   STATUS      current
   DESCRIPTION
      "Path: tunnels.performance.l2tpTunnels.outPriorityQueues.packets.violateTx

       64 bit unsigned wrappable counter."
   ::= {pr1645v2TvTmplPerfOutPQsEntry 50855936}

pr1645v2TvTmplPerfOutPQsOctetsTotal OBJECT-TYPE
   SYNTAX      Counter64
   MAX-ACCESS  read-only
   STATUS      current
   DESCRIPTION
      "Path: tunnels.performance.l2tpTunnels.outPriorityQueues.octets.total

       64 bit unsigned wrappable counter."
   ::= {pr1645v2TvTmplPerfOutPQsEntry 67567616}

pr1645v2TvTmplPerfOutPQsOctetsDirectTx OBJECT-TYPE
   SYNTAX      Counter64
   MAX-ACCESS  read-only
   STATUS      current
   DESCRIPTION
      "Path: tunnels.performance.l2tpTunnels.outPriorityQueues.octets.directTx

       64 bit unsigned wrappable counter."
   ::= {pr1645v2TvTmplPerfOutPQsEntry 67174400}

pr1645v2TvTmplPerfOutPQsOctetsQueued OBJECT-TYPE
   SYNTAX      Counter64
   MAX-ACCESS  read-only
   STATUS      current
   DESCRIPTION
      "Path: tunnels.performance.l2tpTunnels.outPriorityQueues.octets.queued

       64 bit unsigned wrappable counter."
   ::= {pr1645v2TvTmplPerfOutPQsEntry 67239936}

pr1645v2TvTmplPerfOutPQsOctetsDropped OBJECT-TYPE
   SYNTAX      Counter64
   MAX-ACCESS  read-only
   STATUS      current
   DESCRIPTION
      "Path: tunnels.performance.l2tpTunnels.outPriorityQueues.octets.dropped

       64 bit unsigned wrappable counter."
   ::= {pr1645v2TvTmplPerfOutPQsEntry 67305472}

pr1645v2TvTmplPerfOutPQsOctetsRedDropped OBJECT-TYPE
   SYNTAX      Counter64
   MAX-ACCESS  read-only
   STATUS      current
   DESCRIPTION
      "Path: tunnels.performance.l2tpTunnels.outPriorityQueues.octets.redDropped

       64 bit unsigned wrappable counter."
   ::= {pr1645v2TvTmplPerfOutPQsEntry 67502080}

pr1645v2TvTmplPerfOutPQsOctetsCirTx OBJECT-TYPE
   SYNTAX      Counter64
   MAX-ACCESS  read-only
   STATUS      current
   DESCRIPTION
      "Path: tunnels.performance.l2tpTunnels.outPriorityQueues.octets.cirTx

       64 bit unsigned wrappable counter."
   ::= {pr1645v2TvTmplPerfOutPQsEntry 67371008}

pr1645v2TvTmplPerfOutPQsOctetsEirTx OBJECT-TYPE
   SYNTAX      Counter64
   MAX-ACCESS  read-only
   STATUS      current
   DESCRIPTION
      "Path: tunnels.performance.l2tpTunnels.outPriorityQueues.octets.eirTx

       64 bit unsigned wrappable counter."
   ::= {pr1645v2TvTmplPerfOutPQsEntry 67436544}

pr1645v2TvTmplPerfOutPQsOctetsViolateTx OBJECT-TYPE
   SYNTAX      Counter64
   MAX-ACCESS  read-only
   STATUS      current
   DESCRIPTION
      "Path: tunnels.performance.l2tpTunnels.outPriorityQueues.octets.violateTx

       64 bit unsigned wrappable counter."
   ::= {pr1645v2TvTmplPerfOutPQsEntry 67633152}

pr1645v2TvTmplPerfOutPQsOctetsBandwidth15sec OBJECT-TYPE
   SYNTAX      Integer32
   MAX-ACCESS  read-only
   STATUS      current
   DESCRIPTION
      "Path: tunnels.performance.l2tpTunnels.outPriorityQueues.octets.bandwidth.15sec

       unit name = bps
       formula = 8 * ; 8 /"
   ::= {pr1645v2TvTmplPerfOutPQsEntry 70386944}

pr1645v2TvTmplPerfOutPQsOctetsBandwidth30sec OBJECT-TYPE
   SYNTAX      Integer32
   MAX-ACCESS  read-only
   STATUS      current
   DESCRIPTION
      "Path: tunnels.performance.l2tpTunnels.outPriorityQueues.octets.bandwidth.30sec

       unit name = bps
       formula = 8 * ; 8 /"
   ::= {pr1645v2TvTmplPerfOutPQsEntry 70388224}

pr1645v2TvTmplPerfOutPQsOctetsBandwidth1min OBJECT-TYPE
   SYNTAX      Integer32
   MAX-ACCESS  read-only
   STATUS      current
   DESCRIPTION
      "Path: tunnels.performance.l2tpTunnels.outPriorityQueues.octets.bandwidth.1min

       unit name = bps
       formula = 8 * ; 8 /"
   ::= {pr1645v2TvTmplPerfOutPQsEntry 70390784}

pr1645v2TvTmplPerfOutPQsOctetsBandwidth2min OBJECT-TYPE
   SYNTAX      Integer32
   MAX-ACCESS  read-only
   STATUS      current
   DESCRIPTION
      "Path: tunnels.performance.l2tpTunnels.outPriorityQueues.octets.bandwidth.2min

       unit name = bps
       formula = 8 * ; 8 /"
   ::= {pr1645v2TvTmplPerfOutPQsEntry 70395904}

pr1645v2TvTmplPerfOutPQsOctetsBandwidth5min OBJECT-TYPE
   SYNTAX      Integer32
   MAX-ACCESS  read-only
   STATUS      current
   DESCRIPTION
      "Path: tunnels.performance.l2tpTunnels.outPriorityQueues.octets.bandwidth.5min

       unit name = bps
       formula = 8 * ; 8 /"
   ::= {pr1645v2TvTmplPerfOutPQsEntry 70411264}

pr1645v2TvTmplPerfOutPQsH2Performance OBJECT-TYPE
   SYNTAX      SEQUENCE OF Pr1645v2TvTmplPerfOutPQsH2PerformanceEntry
   MAX-ACCESS  not-accessible
   STATUS      current
   DESCRIPTION
      ""
   ::= {pr1645v2TvTmplPerf 84213760}

pr1645v2TvTmplPerfOutPQsH2PerformanceEntry OBJECT-TYPE
   SYNTAX      Pr1645v2TvTmplPerfOutPQsH2PerformanceEntry
   MAX-ACCESS  not-accessible
   STATUS      current
   DESCRIPTION
      ""
   INDEX      { pr1645v2TvTmplPerfTableIx,
                pr1645v2TvTmplPerfOutPQsTableIx,
                pr1645v2TvTmplPerfOutPQsH2PerformanceTableIx }
   ::= {pr1645v2TvTmplPerfOutPQsH2Performance 1}

Pr1645v2TvTmplPerfOutPQsH2PerformanceEntry ::=
   SEQUENCE
      {
      pr1645v2TvTmplPerfOutPQsH2PerformanceTableIx
         TableIndex,
      pr1645v2TvTmplPerfOutPQsH2PerformanceSysUpTime
         TimeTicks,
      pr1645v2TvTmplPerfOutPQsH2PerformanceTotPkts
         Counter64,
      pr1645v2TvTmplPerfOutPQsH2PerformanceDirTxPkts
         Counter64,
      pr1645v2TvTmplPerfOutPQsH2PerformanceQdPkts
         Counter64,
      pr1645v2TvTmplPerfOutPQsH2PerformanceDropPkts
         Counter64,
      pr1645v2TvTmplPerfOutPQsH2PerformanceRDropPkts
         Counter64,
      pr1645v2TvTmplPerfOutPQsH2PerformanceCirTxPkts
         Counter64,
      pr1645v2TvTmplPerfOutPQsH2PerformanceEirTxPkts
         Counter64,
      pr1645v2TvTmplPerfOutPQsH2PerformanceViolTxPkts
         Counter64,
      pr1645v2TvTmplPerfOutPQsH2PerformanceTotOcts
         Counter64,
      pr1645v2TvTmplPerfOutPQsH2PerformanceDirTxOcts
         Counter64,
      pr1645v2TvTmplPerfOutPQsH2PerformanceQdOcts
         Counter64,
      pr1645v2TvTmplPerfOutPQsH2PerformanceDropOcts
         Counter64,
      pr1645v2TvTmplPerfOutPQsH2PerformanceRDropOcts
         Counter64,
      pr1645v2TvTmplPerfOutPQsH2PerformanceCirTxOcts
         Counter64,
      pr1645v2TvTmplPerfOutPQsH2PerformanceEirTxOcts
         Counter64,
      pr1645v2TvTmplPerfOutPQsH2PerformanceViolTxOcts
         Counter64,
      pr1645v2TvTmplPerfOutPQsH2PerformanceBandwidth
         Integer32
      }

pr1645v2TvTmplPerfOutPQsH2PerformanceTableIx OBJECT-TYPE
   SYNTAX      TableIndex
   MAX-ACCESS  not-accessible
   STATUS      current
   DESCRIPTION
      ""
   ::= {pr1645v2TvTmplPerfOutPQsH2PerformanceEntry 11}

pr1645v2TvTmplPerfOutPQsH2PerformanceSysUpTime OBJECT-TYPE
   SYNTAX      TimeTicks
   MAX-ACCESS  read-only
   STATUS      current
   DESCRIPTION
      "Path: tunnels.performance.l2tpTunnels.outPriorityQueues.h2Performance.sysUpTime

       Time in centi-second."
   ::= {pr1645v2TvTmplPerfOutPQsH2PerformanceEntry 16777216}

pr1645v2TvTmplPerfOutPQsH2PerformanceTotPkts OBJECT-TYPE
   SYNTAX      Counter64
   MAX-ACCESS  read-only
   STATUS      current
   DESCRIPTION
      "Path: tunnels.performance.l2tpTunnels.outPriorityQueues.h2Performance.totalPkts

       64 bit unsigned wrappable counter."
   ::= {pr1645v2TvTmplPerfOutPQsH2PerformanceEntry 234881024}

pr1645v2TvTmplPerfOutPQsH2PerformanceDirTxPkts OBJECT-TYPE
   SYNTAX      Counter64
   MAX-ACCESS  read-only
   STATUS      current
   DESCRIPTION
      "Path: tunnels.performance.l2tpTunnels.outPriorityQueues.h2Performance.directTxPkts

       64 bit unsigned wrappable counter."
   ::= {pr1645v2TvTmplPerfOutPQsH2PerformanceEntry 33554432}

pr1645v2TvTmplPerfOutPQsH2PerformanceQdPkts OBJECT-TYPE
   SYNTAX      Counter64
   MAX-ACCESS  read-only
   STATUS      current
   DESCRIPTION
      "Path: tunnels.performance.l2tpTunnels.outPriorityQueues.h2Performance.queuedPkts

       64 bit unsigned wrappable counter."
   ::= {pr1645v2TvTmplPerfOutPQsH2PerformanceEntry 50331648}

pr1645v2TvTmplPerfOutPQsH2PerformanceDropPkts OBJECT-TYPE
   SYNTAX      Counter64
   MAX-ACCESS  read-only
   STATUS      current
   DESCRIPTION
      "Path: tunnels.performance.l2tpTunnels.outPriorityQueues.h2Performance.droppedPkts

       64 bit unsigned wrappable counter."
   ::= {pr1645v2TvTmplPerfOutPQsH2PerformanceEntry 67108864}

pr1645v2TvTmplPerfOutPQsH2PerformanceRDropPkts OBJECT-TYPE
   SYNTAX      Counter64
   MAX-ACCESS  read-only
   STATUS      current
   DESCRIPTION
      "Path: tunnels.performance.l2tpTunnels.outPriorityQueues.h2Performance.redDroppedPkts

       64 bit unsigned wrappable counter."
   ::= {pr1645v2TvTmplPerfOutPQsH2PerformanceEntry 201326592}

pr1645v2TvTmplPerfOutPQsH2PerformanceCirTxPkts OBJECT-TYPE
   SYNTAX      Counter64
   MAX-ACCESS  read-only
   STATUS      current
   DESCRIPTION
      "Path: tunnels.performance.l2tpTunnels.outPriorityQueues.h2Performance.cirTxPkts

       64 bit unsigned wrappable counter."
   ::= {pr1645v2TvTmplPerfOutPQsH2PerformanceEntry 83886080}

pr1645v2TvTmplPerfOutPQsH2PerformanceEirTxPkts OBJECT-TYPE
   SYNTAX      Counter64
   MAX-ACCESS  read-only
   STATUS      current
   DESCRIPTION
      "Path: tunnels.performance.l2tpTunnels.outPriorityQueues.h2Performance.eirTxPkts

       64 bit unsigned wrappable counter."
   ::= {pr1645v2TvTmplPerfOutPQsH2PerformanceEntry 100663296}

pr1645v2TvTmplPerfOutPQsH2PerformanceViolTxPkts OBJECT-TYPE
   SYNTAX      Counter64
   MAX-ACCESS  read-only
   STATUS      current
   DESCRIPTION
      "Path: tunnels.performance.l2tpTunnels.outPriorityQueues.h2Performance.violateTxPkts

       64 bit unsigned wrappable counter."
   ::= {pr1645v2TvTmplPerfOutPQsH2PerformanceEntry 301989888}

pr1645v2TvTmplPerfOutPQsH2PerformanceTotOcts OBJECT-TYPE
   SYNTAX      Counter64
   MAX-ACCESS  read-only
   STATUS      current
   DESCRIPTION
      "Path: tunnels.performance.l2tpTunnels.outPriorityQueues.h2Performance.totalOctets

       64 bit unsigned wrappable counter."
   ::= {pr1645v2TvTmplPerfOutPQsH2PerformanceEntry 251658240}

pr1645v2TvTmplPerfOutPQsH2PerformanceDirTxOcts OBJECT-TYPE
   SYNTAX      Counter64
   MAX-ACCESS  read-only
   STATUS      current
   DESCRIPTION
      "Path: tunnels.performance.l2tpTunnels.outPriorityQueues.h2Performance.directTxOctets

       64 bit unsigned wrappable counter."
   ::= {pr1645v2TvTmplPerfOutPQsH2PerformanceEntry 117440512}

pr1645v2TvTmplPerfOutPQsH2PerformanceQdOcts OBJECT-TYPE
   SYNTAX      Counter64
   MAX-ACCESS  read-only
   STATUS      current
   DESCRIPTION
      "Path: tunnels.performance.l2tpTunnels.outPriorityQueues.h2Performance.queuedOctets

       64 bit unsigned wrappable counter."
   ::= {pr1645v2TvTmplPerfOutPQsH2PerformanceEntry 134217728}

pr1645v2TvTmplPerfOutPQsH2PerformanceDropOcts OBJECT-TYPE
   SYNTAX      Counter64
   MAX-ACCESS  read-only
   STATUS      current
   DESCRIPTION
      "Path: tunnels.performance.l2tpTunnels.outPriorityQueues.h2Performance.droppedOctets

       64 bit unsigned wrappable counter."
   ::= {pr1645v2TvTmplPerfOutPQsH2PerformanceEntry 150994944}

pr1645v2TvTmplPerfOutPQsH2PerformanceRDropOcts OBJECT-TYPE
   SYNTAX      Counter64
   MAX-ACCESS  read-only
   STATUS      current
   DESCRIPTION
      "Path: tunnels.performance.l2tpTunnels.outPriorityQueues.h2Performance.redDroppedOctets

       64 bit unsigned wrappable counter."
   ::= {pr1645v2TvTmplPerfOutPQsH2PerformanceEntry 218103808}

pr1645v2TvTmplPerfOutPQsH2PerformanceCirTxOcts OBJECT-TYPE
   SYNTAX      Counter64
   MAX-ACCESS  read-only
   STATUS      current
   DESCRIPTION
      "Path: tunnels.performance.l2tpTunnels.outPriorityQueues.h2Performance.cirTxOctets

       64 bit unsigned wrappable counter."
   ::= {pr1645v2TvTmplPerfOutPQsH2PerformanceEntry 167772160}

pr1645v2TvTmplPerfOutPQsH2PerformanceEirTxOcts OBJECT-TYPE
   SYNTAX      Counter64
   MAX-ACCESS  read-only
   STATUS      current
   DESCRIPTION
      "Path: tunnels.performance.l2tpTunnels.outPriorityQueues.h2Performance.eirTxOctets

       64 bit unsigned wrappable counter."
   ::= {pr1645v2TvTmplPerfOutPQsH2PerformanceEntry 184549376}

pr1645v2TvTmplPerfOutPQsH2PerformanceViolTxOcts OBJECT-TYPE
   SYNTAX      Counter64
   MAX-ACCESS  read-only
   STATUS      current
   DESCRIPTION
      "Path: tunnels.performance.l2tpTunnels.outPriorityQueues.h2Performance.violateTxOctets

       64 bit unsigned wrappable counter."
   ::= {pr1645v2TvTmplPerfOutPQsH2PerformanceEntry 318767104}

pr1645v2TvTmplPerfOutPQsH2PerformanceBandwidth OBJECT-TYPE
   SYNTAX      Integer32
   MAX-ACCESS  read-only
   STATUS      current
   DESCRIPTION
      "Path: tunnels.performance.l2tpTunnels.outPriorityQueues.h2Performance.bandwidth

       unit name = bps
       formula = 8 * ; 8 /"
   ::= {pr1645v2TvTmplPerfOutPQsH2PerformanceEntry 268435456}

pr1645v2TvTmplPerfOutPQsH24Performance OBJECT-TYPE
   SYNTAX      SEQUENCE OF Pr1645v2TvTmplPerfOutPQsH24PerformanceEntry
   MAX-ACCESS  not-accessible
   STATUS      current
   DESCRIPTION
      ""
   ::= {pr1645v2TvTmplPerf 84279296}

pr1645v2TvTmplPerfOutPQsH24PerformanceEntry OBJECT-TYPE
   SYNTAX      Pr1645v2TvTmplPerfOutPQsH24PerformanceEntry
   MAX-ACCESS  not-accessible
   STATUS      current
   DESCRIPTION
      ""
   INDEX      { pr1645v2TvTmplPerfTableIx,
                pr1645v2TvTmplPerfOutPQsTableIx,
                pr1645v2TvTmplPerfOutPQsH24PerformanceTableIx }
   ::= {pr1645v2TvTmplPerfOutPQsH24Performance 1}

Pr1645v2TvTmplPerfOutPQsH24PerformanceEntry ::=
   SEQUENCE
      {
      pr1645v2TvTmplPerfOutPQsH24PerformanceTableIx
         TableIndex,
      pr1645v2TvTmplPerfOutPQsH24PerformanceSysUpTime
         TimeTicks,
      pr1645v2TvTmplPerfOutPQsH24PerformanceTotPkts
         Counter64,
      pr1645v2TvTmplPerfOutPQsH24PerformanceDirTxPkts
         Counter64,
      pr1645v2TvTmplPerfOutPQsH24PerformanceQdPkts
         Counter64,
      pr1645v2TvTmplPerfOutPQsH24PerformanceDropPkts
         Counter64,
      pr1645v2TvTmplPerfOutPQsH24PerformanceRDropPkts
         Counter64,
      pr1645v2TvTmplPerfOutPQsH24PerformanceCirTxPkts
         Counter64,
      pr1645v2TvTmplPerfOutPQsH24PerformanceEirTxPkts
         Counter64,
      pr1645v2TvTmplPerfOutPQsH24PerformanceViolTxPkts
         Counter64,
      pr1645v2TvTmplPerfOutPQsH24PerformanceTotOcts
         Counter64,
      pr1645v2TvTmplPerfOutPQsH24PerformanceDirTxOcts
         Counter64,
      pr1645v2TvTmplPerfOutPQsH24PerformanceQdOcts
         Counter64,
      pr1645v2TvTmplPerfOutPQsH24PerformanceDropOcts
         Counter64,
      pr1645v2TvTmplPerfOutPQsH24PerformanceRDropOcts
         Counter64,
      pr1645v2TvTmplPerfOutPQsH24PerformanceCirTxOcts
         Counter64,
      pr1645v2TvTmplPerfOutPQsH24PerformanceEirTxOcts
         Counter64,
      pr1645v2TvTmplPerfOutPQsH24PerformanceViolTxOcts
         Counter64,
      pr1645v2TvTmplPerfOutPQsH24PerformanceBandwidth
         Integer32
      }

pr1645v2TvTmplPerfOutPQsH24PerformanceTableIx OBJECT-TYPE
   SYNTAX      TableIndex
   MAX-ACCESS  not-accessible
   STATUS      current
   DESCRIPTION
      ""
   ::= {pr1645v2TvTmplPerfOutPQsH24PerformanceEntry 11}

pr1645v2TvTmplPerfOutPQsH24PerformanceSysUpTime OBJECT-TYPE
   SYNTAX      TimeTicks
   MAX-ACCESS  read-only
   STATUS      current
   DESCRIPTION
      "Path: tunnels.performance.l2tpTunnels.outPriorityQueues.h24Performance.sysUpTime

       Time in centi-second."
   ::= {pr1645v2TvTmplPerfOutPQsH24PerformanceEntry 16777216}

pr1645v2TvTmplPerfOutPQsH24PerformanceTotPkts OBJECT-TYPE
   SYNTAX      Counter64
   MAX-ACCESS  read-only
   STATUS      current
   DESCRIPTION
      "Path: tunnels.performance.l2tpTunnels.outPriorityQueues.h24Performance.totalPkts

       64 bit unsigned wrappable counter."
   ::= {pr1645v2TvTmplPerfOutPQsH24PerformanceEntry 234881024}

pr1645v2TvTmplPerfOutPQsH24PerformanceDirTxPkts OBJECT-TYPE
   SYNTAX      Counter64
   MAX-ACCESS  read-only
   STATUS      current
   DESCRIPTION
      "Path: tunnels.performance.l2tpTunnels.outPriorityQueues.h24Performance.directTxPkts

       64 bit unsigned wrappable counter."
   ::= {pr1645v2TvTmplPerfOutPQsH24PerformanceEntry 33554432}

pr1645v2TvTmplPerfOutPQsH24PerformanceQdPkts OBJECT-TYPE
   SYNTAX      Counter64
   MAX-ACCESS  read-only
   STATUS      current
   DESCRIPTION
      "Path: tunnels.performance.l2tpTunnels.outPriorityQueues.h24Performance.queuedPkts

       64 bit unsigned wrappable counter."
   ::= {pr1645v2TvTmplPerfOutPQsH24PerformanceEntry 50331648}

pr1645v2TvTmplPerfOutPQsH24PerformanceDropPkts OBJECT-TYPE
   SYNTAX      Counter64
   MAX-ACCESS  read-only
   STATUS      current
   DESCRIPTION
      "Path: tunnels.performance.l2tpTunnels.outPriorityQueues.h24Performance.droppedPkts

       64 bit unsigned wrappable counter."
   ::= {pr1645v2TvTmplPerfOutPQsH24PerformanceEntry 67108864}

pr1645v2TvTmplPerfOutPQsH24PerformanceRDropPkts OBJECT-TYPE
   SYNTAX      Counter64
   MAX-ACCESS  read-only
   STATUS      current
   DESCRIPTION
      "Path: tunnels.performance.l2tpTunnels.outPriorityQueues.h24Performance.redDroppedPkts

       64 bit unsigned wrappable counter."
   ::= {pr1645v2TvTmplPerfOutPQsH24PerformanceEntry 201326592}

pr1645v2TvTmplPerfOutPQsH24PerformanceCirTxPkts OBJECT-TYPE
   SYNTAX      Counter64
   MAX-ACCESS  read-only
   STATUS      current
   DESCRIPTION
      "Path: tunnels.performance.l2tpTunnels.outPriorityQueues.h24Performance.cirTxPkts

       64 bit unsigned wrappable counter."
   ::= {pr1645v2TvTmplPerfOutPQsH24PerformanceEntry 83886080}

pr1645v2TvTmplPerfOutPQsH24PerformanceEirTxPkts OBJECT-TYPE
   SYNTAX      Counter64
   MAX-ACCESS  read-only
   STATUS      current
   DESCRIPTION
      "Path: tunnels.performance.l2tpTunnels.outPriorityQueues.h24Performance.eirTxPkts

       64 bit unsigned wrappable counter."
   ::= {pr1645v2TvTmplPerfOutPQsH24PerformanceEntry 100663296}

pr1645v2TvTmplPerfOutPQsH24PerformanceViolTxPkts OBJECT-TYPE
   SYNTAX      Counter64
   MAX-ACCESS  read-only
   STATUS      current
   DESCRIPTION
      "Path: tunnels.performance.l2tpTunnels.outPriorityQueues.h24Performance.violateTxPkts

       64 bit unsigned wrappable counter."
   ::= {pr1645v2TvTmplPerfOutPQsH24PerformanceEntry 301989888}

pr1645v2TvTmplPerfOutPQsH24PerformanceTotOcts OBJECT-TYPE
   SYNTAX      Counter64
   MAX-ACCESS  read-only
   STATUS      current
   DESCRIPTION
      "Path: tunnels.performance.l2tpTunnels.outPriorityQueues.h24Performance.totalOctets

       64 bit unsigned wrappable counter."
   ::= {pr1645v2TvTmplPerfOutPQsH24PerformanceEntry 251658240}

pr1645v2TvTmplPerfOutPQsH24PerformanceDirTxOcts OBJECT-TYPE
   SYNTAX      Counter64
   MAX-ACCESS  read-only
   STATUS      current
   DESCRIPTION
      "Path: tunnels.performance.l2tpTunnels.outPriorityQueues.h24Performance.directTxOctets

       64 bit unsigned wrappable counter."
   ::= {pr1645v2TvTmplPerfOutPQsH24PerformanceEntry 117440512}

pr1645v2TvTmplPerfOutPQsH24PerformanceQdOcts OBJECT-TYPE
   SYNTAX      Counter64
   MAX-ACCESS  read-only
   STATUS      current
   DESCRIPTION
      "Path: tunnels.performance.l2tpTunnels.outPriorityQueues.h24Performance.queuedOctets

       64 bit unsigned wrappable counter."
   ::= {pr1645v2TvTmplPerfOutPQsH24PerformanceEntry 134217728}

pr1645v2TvTmplPerfOutPQsH24PerformanceDropOcts OBJECT-TYPE
   SYNTAX      Counter64
   MAX-ACCESS  read-only
   STATUS      current
   DESCRIPTION
      "Path: tunnels.performance.l2tpTunnels.outPriorityQueues.h24Performance.droppedOctets

       64 bit unsigned wrappable counter."
   ::= {pr1645v2TvTmplPerfOutPQsH24PerformanceEntry 150994944}

pr1645v2TvTmplPerfOutPQsH24PerformanceRDropOcts OBJECT-TYPE
   SYNTAX      Counter64
   MAX-ACCESS  read-only
   STATUS      current
   DESCRIPTION
      "Path: tunnels.performance.l2tpTunnels.outPriorityQueues.h24Performance.redDroppedOctets

       64 bit unsigned wrappable counter."
   ::= {pr1645v2TvTmplPerfOutPQsH24PerformanceEntry 218103808}

pr1645v2TvTmplPerfOutPQsH24PerformanceCirTxOcts OBJECT-TYPE
   SYNTAX      Counter64
   MAX-ACCESS  read-only
   STATUS      current
   DESCRIPTION
      "Path: tunnels.performance.l2tpTunnels.outPriorityQueues.h24Performance.cirTxOctets

       64 bit unsigned wrappable counter."
   ::= {pr1645v2TvTmplPerfOutPQsH24PerformanceEntry 167772160}

pr1645v2TvTmplPerfOutPQsH24PerformanceEirTxOcts OBJECT-TYPE
   SYNTAX      Counter64
   MAX-ACCESS  read-only
   STATUS      current
   DESCRIPTION
      "Path: tunnels.performance.l2tpTunnels.outPriorityQueues.h24Performance.eirTxOctets

       64 bit unsigned wrappable counter."
   ::= {pr1645v2TvTmplPerfOutPQsH24PerformanceEntry 184549376}

pr1645v2TvTmplPerfOutPQsH24PerformanceViolTxOcts OBJECT-TYPE
   SYNTAX      Counter64
   MAX-ACCESS  read-only
   STATUS      current
   DESCRIPTION
      "Path: tunnels.performance.l2tpTunnels.outPriorityQueues.h24Performance.violateTxOctets

       64 bit unsigned wrappable counter."
   ::= {pr1645v2TvTmplPerfOutPQsH24PerformanceEntry 318767104}

pr1645v2TvTmplPerfOutPQsH24PerformanceBandwidth OBJECT-TYPE
   SYNTAX      Integer32
   MAX-ACCESS  read-only
   STATUS      current
   DESCRIPTION
      "Path: tunnels.performance.l2tpTunnels.outPriorityQueues.h24Performance.bandwidth

       unit name = bps
       formula = 8 * ; 8 /"
   ::= {pr1645v2TvTmplPerfOutPQsH24PerformanceEntry 268435456}

pr1645v2TvTmplPerfOutPQsD7Performance OBJECT-TYPE
   SYNTAX      SEQUENCE OF Pr1645v2TvTmplPerfOutPQsD7PerformanceEntry
   MAX-ACCESS  not-accessible
   STATUS      current
   DESCRIPTION
      ""
   ::= {pr1645v2TvTmplPerf 84344832}

pr1645v2TvTmplPerfOutPQsD7PerformanceEntry OBJECT-TYPE
   SYNTAX      Pr1645v2TvTmplPerfOutPQsD7PerformanceEntry
   MAX-ACCESS  not-accessible
   STATUS      current
   DESCRIPTION
      ""
   INDEX      { pr1645v2TvTmplPerfTableIx,
                pr1645v2TvTmplPerfOutPQsTableIx,
                pr1645v2TvTmplPerfOutPQsD7PerformanceTableIx }
   ::= {pr1645v2TvTmplPerfOutPQsD7Performance 1}

Pr1645v2TvTmplPerfOutPQsD7PerformanceEntry ::=
   SEQUENCE
      {
      pr1645v2TvTmplPerfOutPQsD7PerformanceTableIx
         TableIndex,
      pr1645v2TvTmplPerfOutPQsD7PerformanceSysUpTime
         TimeTicks,
      pr1645v2TvTmplPerfOutPQsD7PerformanceTotPkts
         Counter64,
      pr1645v2TvTmplPerfOutPQsD7PerformanceDirTxPkts
         Counter64,
      pr1645v2TvTmplPerfOutPQsD7PerformanceQdPkts
         Counter64,
      pr1645v2TvTmplPerfOutPQsD7PerformanceDropPkts
         Counter64,
      pr1645v2TvTmplPerfOutPQsD7PerformanceRDropPkts
         Counter64,
      pr1645v2TvTmplPerfOutPQsD7PerformanceCirTxPkts
         Counter64,
      pr1645v2TvTmplPerfOutPQsD7PerformanceEirTxPkts
         Counter64,
      pr1645v2TvTmplPerfOutPQsD7PerformanceViolTxPkts
         Counter64,
      pr1645v2TvTmplPerfOutPQsD7PerformanceTotOcts
         Counter64,
      pr1645v2TvTmplPerfOutPQsD7PerformanceDirTxOcts
         Counter64,
      pr1645v2TvTmplPerfOutPQsD7PerformanceQdOcts
         Counter64,
      pr1645v2TvTmplPerfOutPQsD7PerformanceDropOcts
         Counter64,
      pr1645v2TvTmplPerfOutPQsD7PerformanceRDropOcts
         Counter64,
      pr1645v2TvTmplPerfOutPQsD7PerformanceCirTxOcts
         Counter64,
      pr1645v2TvTmplPerfOutPQsD7PerformanceEirTxOcts
         Counter64,
      pr1645v2TvTmplPerfOutPQsD7PerformanceViolTxOcts
         Counter64,
      pr1645v2TvTmplPerfOutPQsD7PerformanceBandwidth
         Integer32
      }

pr1645v2TvTmplPerfOutPQsD7PerformanceTableIx OBJECT-TYPE
   SYNTAX      TableIndex
   MAX-ACCESS  not-accessible
   STATUS      current
   DESCRIPTION
      ""
   ::= {pr1645v2TvTmplPerfOutPQsD7PerformanceEntry 11}

pr1645v2TvTmplPerfOutPQsD7PerformanceSysUpTime OBJECT-TYPE
   SYNTAX      TimeTicks
   MAX-ACCESS  read-only
   STATUS      current
   DESCRIPTION
      "Path: tunnels.performance.l2tpTunnels.outPriorityQueues.d7Performance.sysUpTime

       Time in centi-second."
   ::= {pr1645v2TvTmplPerfOutPQsD7PerformanceEntry 16777216}

pr1645v2TvTmplPerfOutPQsD7PerformanceTotPkts OBJECT-TYPE
   SYNTAX      Counter64
   MAX-ACCESS  read-only
   STATUS      current
   DESCRIPTION
      "Path: tunnels.performance.l2tpTunnels.outPriorityQueues.d7Performance.totalPkts

       64 bit unsigned wrappable counter."
   ::= {pr1645v2TvTmplPerfOutPQsD7PerformanceEntry 234881024}

pr1645v2TvTmplPerfOutPQsD7PerformanceDirTxPkts OBJECT-TYPE
   SYNTAX      Counter64
   MAX-ACCESS  read-only
   STATUS      current
   DESCRIPTION
      "Path: tunnels.performance.l2tpTunnels.outPriorityQueues.d7Performance.directTxPkts

       64 bit unsigned wrappable counter."
   ::= {pr1645v2TvTmplPerfOutPQsD7PerformanceEntry 33554432}

pr1645v2TvTmplPerfOutPQsD7PerformanceQdPkts OBJECT-TYPE
   SYNTAX      Counter64
   MAX-ACCESS  read-only
   STATUS      current
   DESCRIPTION
      "Path: tunnels.performance.l2tpTunnels.outPriorityQueues.d7Performance.queuedPkts

       64 bit unsigned wrappable counter."
   ::= {pr1645v2TvTmplPerfOutPQsD7PerformanceEntry 50331648}

pr1645v2TvTmplPerfOutPQsD7PerformanceDropPkts OBJECT-TYPE
   SYNTAX      Counter64
   MAX-ACCESS  read-only
   STATUS      current
   DESCRIPTION
      "Path: tunnels.performance.l2tpTunnels.outPriorityQueues.d7Performance.droppedPkts

       64 bit unsigned wrappable counter."
   ::= {pr1645v2TvTmplPerfOutPQsD7PerformanceEntry 67108864}

pr1645v2TvTmplPerfOutPQsD7PerformanceRDropPkts OBJECT-TYPE
   SYNTAX      Counter64
   MAX-ACCESS  read-only
   STATUS      current
   DESCRIPTION
      "Path: tunnels.performance.l2tpTunnels.outPriorityQueues.d7Performance.redDroppedPkts

       64 bit unsigned wrappable counter."
   ::= {pr1645v2TvTmplPerfOutPQsD7PerformanceEntry 201326592}

pr1645v2TvTmplPerfOutPQsD7PerformanceCirTxPkts OBJECT-TYPE
   SYNTAX      Counter64
   MAX-ACCESS  read-only
   STATUS      current
   DESCRIPTION
      "Path: tunnels.performance.l2tpTunnels.outPriorityQueues.d7Performance.cirTxPkts

       64 bit unsigned wrappable counter."
   ::= {pr1645v2TvTmplPerfOutPQsD7PerformanceEntry 83886080}

pr1645v2TvTmplPerfOutPQsD7PerformanceEirTxPkts OBJECT-TYPE
   SYNTAX      Counter64
   MAX-ACCESS  read-only
   STATUS      current
   DESCRIPTION
      "Path: tunnels.performance.l2tpTunnels.outPriorityQueues.d7Performance.eirTxPkts

       64 bit unsigned wrappable counter."
   ::= {pr1645v2TvTmplPerfOutPQsD7PerformanceEntry 100663296}

pr1645v2TvTmplPerfOutPQsD7PerformanceViolTxPkts OBJECT-TYPE
   SYNTAX      Counter64
   MAX-ACCESS  read-only
   STATUS      current
   DESCRIPTION
      "Path: tunnels.performance.l2tpTunnels.outPriorityQueues.d7Performance.violateTxPkts

       64 bit unsigned wrappable counter."
   ::= {pr1645v2TvTmplPerfOutPQsD7PerformanceEntry 301989888}

pr1645v2TvTmplPerfOutPQsD7PerformanceTotOcts OBJECT-TYPE
   SYNTAX      Counter64
   MAX-ACCESS  read-only
   STATUS      current
   DESCRIPTION
      "Path: tunnels.performance.l2tpTunnels.outPriorityQueues.d7Performance.totalOctets

       64 bit unsigned wrappable counter."
   ::= {pr1645v2TvTmplPerfOutPQsD7PerformanceEntry 251658240}

pr1645v2TvTmplPerfOutPQsD7PerformanceDirTxOcts OBJECT-TYPE
   SYNTAX      Counter64
   MAX-ACCESS  read-only
   STATUS      current
   DESCRIPTION
      "Path: tunnels.performance.l2tpTunnels.outPriorityQueues.d7Performance.directTxOctets

       64 bit unsigned wrappable counter."
   ::= {pr1645v2TvTmplPerfOutPQsD7PerformanceEntry 117440512}

pr1645v2TvTmplPerfOutPQsD7PerformanceQdOcts OBJECT-TYPE
   SYNTAX      Counter64
   MAX-ACCESS  read-only
   STATUS      current
   DESCRIPTION
      "Path: tunnels.performance.l2tpTunnels.outPriorityQueues.d7Performance.queuedOctets

       64 bit unsigned wrappable counter."
   ::= {pr1645v2TvTmplPerfOutPQsD7PerformanceEntry 134217728}

pr1645v2TvTmplPerfOutPQsD7PerformanceDropOcts OBJECT-TYPE
   SYNTAX      Counter64
   MAX-ACCESS  read-only
   STATUS      current
   DESCRIPTION
      "Path: tunnels.performance.l2tpTunnels.outPriorityQueues.d7Performance.droppedOctets

       64 bit unsigned wrappable counter."
   ::= {pr1645v2TvTmplPerfOutPQsD7PerformanceEntry 150994944}

pr1645v2TvTmplPerfOutPQsD7PerformanceRDropOcts OBJECT-TYPE
   SYNTAX      Counter64
   MAX-ACCESS  read-only
   STATUS      current
   DESCRIPTION
      "Path: tunnels.performance.l2tpTunnels.outPriorityQueues.d7Performance.redDroppedOctets

       64 bit unsigned wrappable counter."
   ::= {pr1645v2TvTmplPerfOutPQsD7PerformanceEntry 218103808}

pr1645v2TvTmplPerfOutPQsD7PerformanceCirTxOcts OBJECT-TYPE
   SYNTAX      Counter64
   MAX-ACCESS  read-only
   STATUS      current
   DESCRIPTION
      "Path: tunnels.performance.l2tpTunnels.outPriorityQueues.d7Performance.cirTxOctets

       64 bit unsigned wrappable counter."
   ::= {pr1645v2TvTmplPerfOutPQsD7PerformanceEntry 167772160}

pr1645v2TvTmplPerfOutPQsD7PerformanceEirTxOcts OBJECT-TYPE
   SYNTAX      Counter64
   MAX-ACCESS  read-only
   STATUS      current
   DESCRIPTION
      "Path: tunnels.performance.l2tpTunnels.outPriorityQueues.d7Performance.eirTxOctets

       64 bit unsigned wrappable counter."
   ::= {pr1645v2TvTmplPerfOutPQsD7PerformanceEntry 184549376}

pr1645v2TvTmplPerfOutPQsD7PerformanceViolTxOcts OBJECT-TYPE
   SYNTAX      Counter64
   MAX-ACCESS  read-only
   STATUS      current
   DESCRIPTION
      "Path: tunnels.performance.l2tpTunnels.outPriorityQueues.d7Performance.violateTxOctets

       64 bit unsigned wrappable counter."
   ::= {pr1645v2TvTmplPerfOutPQsD7PerformanceEntry 318767104}

pr1645v2TvTmplPerfOutPQsD7PerformanceBandwidth OBJECT-TYPE
   SYNTAX      Integer32
   MAX-ACCESS  read-only
   STATUS      current
   DESCRIPTION
      "Path: tunnels.performance.l2tpTunnels.outPriorityQueues.d7Performance.bandwidth

       unit name = bps
       formula = 8 * ; 8 /"
   ::= {pr1645v2TvTmplPerfOutPQsD7PerformanceEntry 268435456}


pr1645v2TvTmplPerfi OBJECT IDENTIFIER ::= {pr1645v2TvTmpl 6}

pr1645v2TvTmplPerfiSSCTable OBJECT-TYPE
   SYNTAX      SEQUENCE OF Pr1645v2TvTmplPerfiEntry
   MAX-ACCESS  not-accessible
   STATUS      current
   DESCRIPTION
      ""
   ::= {pr1645v2TvTmplPerfi 1}

pr1645v2TvTmplPerfiEntry OBJECT-TYPE
   SYNTAX      Pr1645v2TvTmplPerfiEntry
   MAX-ACCESS  not-accessible
   STATUS      current
   DESCRIPTION
      ""
   INDEX      { pr1645v2TvTmplPerfiTableIx }
   ::= {pr1645v2TvTmplPerfiSSCTable 1}

Pr1645v2TvTmplPerfiEntry ::=
   SEQUENCE
      {
      pr1645v2TvTmplPerfiTableIx
         TableIndex,
      pr1645v2TvTmplPerfiName
         DisplayString,
      pr1645v2TvTmplPerfiMCInOctets
         Counter64,
      pr1645v2TvTmplPerfiMCInUcast
         Counter64,
      pr1645v2TvTmplPerfiMCInNUcastPkts
         Counter64,
      pr1645v2TvTmplPerfiMCInBcastPkts
         Counter64,
      pr1645v2TvTmplPerfiMCInMcastPkts
         Counter64,
      pr1645v2TvTmplPerfiMCInDiscards
         Counter64,
      pr1645v2TvTmplPerfiMCInErrors
         Counter64,
      pr1645v2TvTmplPerfiMCInUnknownProtos
         Counter64,
      pr1645v2TvTmplPerfiMCInDropEx
         Counter64,
      pr1645v2TvTmplPerfiMCInDropNoMac
         Counter64,
      pr1645v2TvTmplPerfiMCInDropNUCast
         Counter64,
      pr1645v2TvTmplPerfiMCInDropFilter
         Counter64,
      pr1645v2TvTmplPerfiMCInBandwidth15sec
         Integer32,
      pr1645v2TvTmplPerfiMCInBandwidth30sec
         Integer32,
      pr1645v2TvTmplPerfiMCInBandwidth1min
         Integer32,
      pr1645v2TvTmplPerfiMCInBandwidth2min
         Integer32,
      pr1645v2TvTmplPerfiMCInBandwidth5min
         Integer32,
      pr1645v2TvTmplPerfiMCOutOctets
         Counter64,
      pr1645v2TvTmplPerfiMCOutUcastPkts
         Counter64,
      pr1645v2TvTmplPerfiMCOutNUcastPkts
         Counter64,
      pr1645v2TvTmplPerfiMCOutBcastPkts
         Counter64,
      pr1645v2TvTmplPerfiMCOutMcastPkts
         Counter64,
      pr1645v2TvTmplPerfiMCOutDiscards
         Counter64,
      pr1645v2TvTmplPerfiMCOutErrors
         Counter64,
      pr1645v2TvTmplPerfiMCOutQLen
         Counter32,
      pr1645v2TvTmplPerfiMCOutDropEx
         Counter64,
      pr1645v2TvTmplPerfiMCOutDropNoArp
         Counter64,
      pr1645v2TvTmplPerfiMCOutDropFilter
         Counter64,
      pr1645v2TvTmplPerfiMCOutBandwidth15sec
         Integer32,
      pr1645v2TvTmplPerfiMCOutBandwidth30sec
         Integer32,
      pr1645v2TvTmplPerfiMCOutBandwidth1min
         Integer32,
      pr1645v2TvTmplPerfiMCOutBandwidth2min
         Integer32,
      pr1645v2TvTmplPerfiMCOutBandwidth5min
         Integer32,
      pr1645v2TvTmplPerfiControlHelloSent
         Gauge32,
      pr1645v2TvTmplPerfiControlHelloRcvd
         Gauge32,
      pr1645v2TvTmplPerfiControlAckSent
         Gauge32,
      pr1645v2TvTmplPerfiControlAckRcvd
         Gauge32,
      pr1645v2TvTmplPerfiControlDuplicateRcvd
         Gauge32,
      pr1645v2TvTmplPerfiControlOutOfSeqRcvd
         Gauge32,
      pr1645v2TvTmplPerfiControlRetransmission
         Gauge32,
      pr1645v2TvTmplPerfiControlAuthenFailure
         Gauge32,
      pr1645v2TvTmplPerfiPppPort
         Counter32,
      pr1645v2TvTmplPerfiPppLcpUp
         Counter32,
      pr1645v2TvTmplPerfiPppLcpDown
         Counter32,
      pr1645v2TvTmplPerfiPppLcpOpen
         Counter32,
      pr1645v2TvTmplPerfiPppLcpClose
         Counter32,
      pr1645v2TvTmplPerfiPppLcpToP
         Counter32,
      pr1645v2TvTmplPerfiPppLcpToM
         Counter32,
      pr1645v2TvTmplPerfiPppLcpRcrP
         Counter32,
      pr1645v2TvTmplPerfiPppLcpRcrM
         Counter32,
      pr1645v2TvTmplPerfiPppLcpRca
         Counter32,
      pr1645v2TvTmplPerfiPppLcpRcn
         Counter32,
      pr1645v2TvTmplPerfiPppLcpRtr
         Counter32,
      pr1645v2TvTmplPerfiPppLcpRta
         Counter32,
      pr1645v2TvTmplPerfiPppLcpRuc
         Counter32,
      pr1645v2TvTmplPerfiPppLcpRxjP
         Counter32,
      pr1645v2TvTmplPerfiPppLcpRxjM
         Counter32,
      pr1645v2TvTmplPerfiPppLcpRxr
         Counter32,
      pr1645v2TvTmplPerfiPppLcpRrr
         Counter32,
      pr1645v2TvTmplPerfiPppLcpRra
         Counter32,
      pr1645v2TvTmplPerfiPppLcpDf
         Counter32,
      pr1645v2TvTmplPerfiPppLcpIntClose
         Counter32,
      pr1645v2TvTmplPerfiPppLcpLm
         Counter32,
      pr1645v2TvTmplPerfiPppLcpLmM
         Counter32,
      pr1645v2TvTmplPerfiPppAuthMyNegotiated
         INTEGER,
      pr1645v2TvTmplPerfiPppAuthMyConfigured
         INTEGER,
      pr1645v2TvTmplPerfiPppAuthHisRequested
         INTEGER,
      pr1645v2TvTmplPerfiPppAuthRxChallenge
         Counter32,
      pr1645v2TvTmplPerfiPppAuthRxResponse
         Counter32,
      pr1645v2TvTmplPerfiPppAuthRxSuccess
         Counter32,
      pr1645v2TvTmplPerfiPppAuthRxFailure
         Counter32,
      pr1645v2TvTmplPerfiPppAuthChallengeTO
         Counter32,
      pr1645v2TvTmplPerfiPppAuthResponseTO
         Counter32,
      pr1645v2TvTmplPerfiPppAuthTxChallenge
         Counter32,
      pr1645v2TvTmplPerfiPppAuthRxRadiusSuccess
         Counter32,
      pr1645v2TvTmplPerfiPppAuthRxRadiusFailure
         Counter32,
      pr1645v2TvTmplPerfiPppAuthTxSuccess
         Counter32,
      pr1645v2TvTmplPerfiPppAuthTxFailure
         Counter32,
      pr1645v2TvTmplPerfiPppAuthUnexpected
         Counter32,
      pr1645v2TvTmplPerfiPppIpcpUp
         Counter32,
      pr1645v2TvTmplPerfiPppIpcpDown
         Counter32,
      pr1645v2TvTmplPerfiPppIpcpOpen
         Counter32,
      pr1645v2TvTmplPerfiPppIpcpClose
         Counter32,
      pr1645v2TvTmplPerfiPppIpcpToP
         Counter32,
      pr1645v2TvTmplPerfiPppIpcpToM
         Counter32,
      pr1645v2TvTmplPerfiPppIpcpRcrP
         Counter32,
      pr1645v2TvTmplPerfiPppIpcpRcrM
         Counter32,
      pr1645v2TvTmplPerfiPppIpcpRca
         Counter32,
      pr1645v2TvTmplPerfiPppIpcpRcn
         Counter32,
      pr1645v2TvTmplPerfiPppIpcpRtr
         Counter32,
      pr1645v2TvTmplPerfiPppIpcpRta
         Counter32,
      pr1645v2TvTmplPerfiPppIpcpRuc
         Counter32,
      pr1645v2TvTmplPerfiPppIpcpRxjP
         Counter32,
      pr1645v2TvTmplPerfiPppIpcpRxjM
         Counter32,
      pr1645v2TvTmplPerfiPppIpcpRxr
         Counter32,
      pr1645v2TvTmplPerfiPppIpcpRrr
         Counter32,
      pr1645v2TvTmplPerfiPppIpcpRra
         Counter32,
      pr1645v2TvTmplPerfiPppIpcpDf
         Counter32,
      pr1645v2TvTmplPerfiPppIpcpIntClose
         Counter32,
      pr1645v2TvTmplPerfiPppIpcpLm
         Counter32,
      pr1645v2TvTmplPerfiPppIpcpLmM
         Counter32,
      pr1645v2TvTmplPerfiPppLinkMonitoringRequestsSent
         Gauge32,
      pr1645v2TvTmplPerfiPppLinkMonitoringRepliesRcvd
         Gauge32,
      pr1645v2TvTmplPerfiPppLinkMonitoringRequestsRcvd
         Gauge32,
      pr1645v2TvTmplPerfiPppLinkMonitoringRepliesSent
         Gauge32
      }

pr1645v2TvTmplPerfiTableIx OBJECT-TYPE
   SYNTAX      TableIndex
   MAX-ACCESS  not-accessible
   STATUS      current
   DESCRIPTION
      ""
   ::= {pr1645v2TvTmplPerfiEntry 11}

pr1645v2TvTmplPerfiName OBJECT-TYPE
   SYNTAX      DisplayString
   MAX-ACCESS  read-only
   STATUS      current
   DESCRIPTION
      "Path: tunnels.performance.ipsecL2tpTunnels.name"
   ::= {pr1645v2TvTmplPerfiEntry 16777216}

pr1645v2TvTmplPerfiMCInOctets OBJECT-TYPE
   SYNTAX      Counter64
   MAX-ACCESS  read-only
   STATUS      current
   DESCRIPTION
      "Path: tunnels.performance.ipsecL2tpTunnels.mibCounters.ifInOctets

       64 bit unsigned wrappable counter."
   ::= {pr1645v2TvTmplPerfiEntry 40697856}

pr1645v2TvTmplPerfiMCInUcast OBJECT-TYPE
   SYNTAX      Counter64
   MAX-ACCESS  read-only
   STATUS      current
   DESCRIPTION
      "Path: tunnels.performance.ipsecL2tpTunnels.mibCounters.ifInUcastPkts

       64 bit unsigned wrappable counter."
   ::= {pr1645v2TvTmplPerfiEntry 40763392}

pr1645v2TvTmplPerfiMCInNUcastPkts OBJECT-TYPE
   SYNTAX      Counter64
   MAX-ACCESS  read-only
   STATUS      current
   DESCRIPTION
      "Path: tunnels.performance.ipsecL2tpTunnels.mibCounters.ifInNUcastPkts

       64 bit unsigned wrappable counter."
   ::= {pr1645v2TvTmplPerfiEntry 40828928}

pr1645v2TvTmplPerfiMCInBcastPkts OBJECT-TYPE
   SYNTAX      Counter64
   MAX-ACCESS  read-only
   STATUS      current
   DESCRIPTION
      "Path: tunnels.performance.ipsecL2tpTunnels.mibCounters.ifInBcastPkts

       64 bit unsigned wrappable counter."
   ::= {pr1645v2TvTmplPerfiEntry 47382528}

pr1645v2TvTmplPerfiMCInMcastPkts OBJECT-TYPE
   SYNTAX      Counter64
   MAX-ACCESS  read-only
   STATUS      current
   DESCRIPTION
      "Path: tunnels.performance.ipsecL2tpTunnels.mibCounters.ifInMcastPkts

       64 bit unsigned wrappable counter."
   ::= {pr1645v2TvTmplPerfiEntry 48037888}

pr1645v2TvTmplPerfiMCInDiscards OBJECT-TYPE
   SYNTAX      Counter64
   MAX-ACCESS  read-only
   STATUS      current
   DESCRIPTION
      "Path: tunnels.performance.ipsecL2tpTunnels.mibCounters.ifInDiscards

       64 bit unsigned wrappable counter."
   ::= {pr1645v2TvTmplPerfiEntry 40894464}

pr1645v2TvTmplPerfiMCInErrors OBJECT-TYPE
   SYNTAX      Counter64
   MAX-ACCESS  read-only
   STATUS      current
   DESCRIPTION
      "Path: tunnels.performance.ipsecL2tpTunnels.mibCounters.ifInErrors

       64 bit unsigned wrappable counter."
   ::= {pr1645v2TvTmplPerfiEntry 40960000}

pr1645v2TvTmplPerfiMCInUnknownProtos OBJECT-TYPE
   SYNTAX      Counter64
   MAX-ACCESS  read-only
   STATUS      current
   DESCRIPTION
      "Path: tunnels.performance.ipsecL2tpTunnels.mibCounters.ifInUnknownProtos

       64 bit unsigned wrappable counter."
   ::= {pr1645v2TvTmplPerfiEntry 41025536}

pr1645v2TvTmplPerfiMCInDropEx OBJECT-TYPE
   SYNTAX      Counter64
   MAX-ACCESS  read-only
   STATUS      current
   DESCRIPTION
      "Path: tunnels.performance.ipsecL2tpTunnels.mibCounters.ifInDropLevelExceeded

       64 bit unsigned wrappable counter."
   ::= {pr1645v2TvTmplPerfiEntry 42074112}

pr1645v2TvTmplPerfiMCInDropNoMac OBJECT-TYPE
   SYNTAX      Counter64
   MAX-ACCESS  read-only
   STATUS      current
   DESCRIPTION
      "Path: tunnels.performance.ipsecL2tpTunnels.mibCounters.ifInDiscardsNoMacFit

       64 bit unsigned wrappable counter."
   ::= {pr1645v2TvTmplPerfiEntry 42270720}

pr1645v2TvTmplPerfiMCInDropNUCast OBJECT-TYPE
   SYNTAX      Counter64
   MAX-ACCESS  read-only
   STATUS      current
   DESCRIPTION
      "Path: tunnels.performance.ipsecL2tpTunnels.mibCounters.ifInDiscardsNUCast

       64 bit unsigned wrappable counter."
   ::= {pr1645v2TvTmplPerfiEntry 42467328}

pr1645v2TvTmplPerfiMCInDropFilter OBJECT-TYPE
   SYNTAX      Counter64
   MAX-ACCESS  read-only
   STATUS      current
   DESCRIPTION
      "Path: tunnels.performance.ipsecL2tpTunnels.mibCounters.ifInDiscardsFilter

       64 bit unsigned wrappable counter."
   ::= {pr1645v2TvTmplPerfiEntry 42532864}

pr1645v2TvTmplPerfiMCInBandwidth15sec OBJECT-TYPE
   SYNTAX      Integer32
   MAX-ACCESS  read-only
   STATUS      current
   DESCRIPTION
      "Path: tunnels.performance.ipsecL2tpTunnels.mibCounters.ifInBandwidth.15sec

       unit name = bps
       formula = 8 * ; 8 /"
   ::= {pr1645v2TvTmplPerfiEntry 45417728}

pr1645v2TvTmplPerfiMCInBandwidth30sec OBJECT-TYPE
   SYNTAX      Integer32
   MAX-ACCESS  read-only
   STATUS      current
   DESCRIPTION
      "Path: tunnels.performance.ipsecL2tpTunnels.mibCounters.ifInBandwidth.30sec

       unit name = bps
       formula = 8 * ; 8 /"
   ::= {pr1645v2TvTmplPerfiEntry 45419008}

pr1645v2TvTmplPerfiMCInBandwidth1min OBJECT-TYPE
   SYNTAX      Integer32
   MAX-ACCESS  read-only
   STATUS      current
   DESCRIPTION
      "Path: tunnels.performance.ipsecL2tpTunnels.mibCounters.ifInBandwidth.1min

       unit name = bps
       formula = 8 * ; 8 /"
   ::= {pr1645v2TvTmplPerfiEntry 45421568}

pr1645v2TvTmplPerfiMCInBandwidth2min OBJECT-TYPE
   SYNTAX      Integer32
   MAX-ACCESS  read-only
   STATUS      current
   DESCRIPTION
      "Path: tunnels.performance.ipsecL2tpTunnels.mibCounters.ifInBandwidth.2min

       unit name = bps
       formula = 8 * ; 8 /"
   ::= {pr1645v2TvTmplPerfiEntry 45426688}

pr1645v2TvTmplPerfiMCInBandwidth5min OBJECT-TYPE
   SYNTAX      Integer32
   MAX-ACCESS  read-only
   STATUS      current
   DESCRIPTION
      "Path: tunnels.performance.ipsecL2tpTunnels.mibCounters.ifInBandwidth.5min

       unit name = bps
       formula = 8 * ; 8 /"
   ::= {pr1645v2TvTmplPerfiEntry 45442048}

pr1645v2TvTmplPerfiMCOutOctets OBJECT-TYPE
   SYNTAX      Counter64
   MAX-ACCESS  read-only
   STATUS      current
   DESCRIPTION
      "Path: tunnels.performance.ipsecL2tpTunnels.mibCounters.ifOutOctets

       64 bit unsigned wrappable counter."
   ::= {pr1645v2TvTmplPerfiEntry 41091072}

pr1645v2TvTmplPerfiMCOutUcastPkts OBJECT-TYPE
   SYNTAX      Counter64
   MAX-ACCESS  read-only
   STATUS      current
   DESCRIPTION
      "Path: tunnels.performance.ipsecL2tpTunnels.mibCounters.ifOutUcastPkts

       64 bit unsigned wrappable counter."
   ::= {pr1645v2TvTmplPerfiEntry 41156608}

pr1645v2TvTmplPerfiMCOutNUcastPkts OBJECT-TYPE
   SYNTAX      Counter64
   MAX-ACCESS  read-only
   STATUS      current
   DESCRIPTION
      "Path: tunnels.performance.ipsecL2tpTunnels.mibCounters.ifOutNUcastPkts

       64 bit unsigned wrappable counter."
   ::= {pr1645v2TvTmplPerfiEntry 41222144}

pr1645v2TvTmplPerfiMCOutBcastPkts OBJECT-TYPE
   SYNTAX      Counter64
   MAX-ACCESS  read-only
   STATUS      current
   DESCRIPTION
      "Path: tunnels.performance.ipsecL2tpTunnels.mibCounters.ifOutBcastPkts

       64 bit unsigned wrappable counter."
   ::= {pr1645v2TvTmplPerfiEntry 47775744}

pr1645v2TvTmplPerfiMCOutMcastPkts OBJECT-TYPE
   SYNTAX      Counter64
   MAX-ACCESS  read-only
   STATUS      current
   DESCRIPTION
      "Path: tunnels.performance.ipsecL2tpTunnels.mibCounters.ifOutMcastPkts

       64 bit unsigned wrappable counter."
   ::= {pr1645v2TvTmplPerfiEntry 48431104}

pr1645v2TvTmplPerfiMCOutDiscards OBJECT-TYPE
   SYNTAX      Counter64
   MAX-ACCESS  read-only
   STATUS      current
   DESCRIPTION
      "Path: tunnels.performance.ipsecL2tpTunnels.mibCounters.ifOutDiscards

       64 bit unsigned wrappable counter."
   ::= {pr1645v2TvTmplPerfiEntry 41287680}

pr1645v2TvTmplPerfiMCOutErrors OBJECT-TYPE
   SYNTAX      Counter64
   MAX-ACCESS  read-only
   STATUS      current
   DESCRIPTION
      "Path: tunnels.performance.ipsecL2tpTunnels.mibCounters.ifOutErrors

       64 bit unsigned wrappable counter."
   ::= {pr1645v2TvTmplPerfiEntry 41353216}

pr1645v2TvTmplPerfiMCOutQLen OBJECT-TYPE
   SYNTAX      Counter32
   MAX-ACCESS  read-only
   STATUS      current
   DESCRIPTION
      "Path: tunnels.performance.ipsecL2tpTunnels.mibCounters.ifOutQLen

       32 bit unsigned wrappable counter."
   ::= {pr1645v2TvTmplPerfiEntry 41418752}

pr1645v2TvTmplPerfiMCOutDropEx OBJECT-TYPE
   SYNTAX      Counter64
   MAX-ACCESS  read-only
   STATUS      current
   DESCRIPTION
      "Path: tunnels.performance.ipsecL2tpTunnels.mibCounters.ifOutDropLevelExceeded

       64 bit unsigned wrappable counter."
   ::= {pr1645v2TvTmplPerfiEntry 41484288}

pr1645v2TvTmplPerfiMCOutDropNoArp OBJECT-TYPE
   SYNTAX      Counter64
   MAX-ACCESS  read-only
   STATUS      current
   DESCRIPTION
      "Path: tunnels.performance.ipsecL2tpTunnels.mibCounters.ifOutDiscardsNoArp

       64 bit unsigned wrappable counter."
   ::= {pr1645v2TvTmplPerfiEntry 42336256}

pr1645v2TvTmplPerfiMCOutDropFilter OBJECT-TYPE
   SYNTAX      Counter64
   MAX-ACCESS  read-only
   STATUS      current
   DESCRIPTION
      "Path: tunnels.performance.ipsecL2tpTunnels.mibCounters.ifOutDiscardsFilter

       64 bit unsigned wrappable counter."
   ::= {pr1645v2TvTmplPerfiEntry 42598400}

pr1645v2TvTmplPerfiMCOutBandwidth15sec OBJECT-TYPE
   SYNTAX      Integer32
   MAX-ACCESS  read-only
   STATUS      current
   DESCRIPTION
      "Path: tunnels.performance.ipsecL2tpTunnels.mibCounters.ifOutBandwidth.15sec

       unit name = bps
       formula = 8 * ; 8 /"
   ::= {pr1645v2TvTmplPerfiEntry 45483264}

pr1645v2TvTmplPerfiMCOutBandwidth30sec OBJECT-TYPE
   SYNTAX      Integer32
   MAX-ACCESS  read-only
   STATUS      current
   DESCRIPTION
      "Path: tunnels.performance.ipsecL2tpTunnels.mibCounters.ifOutBandwidth.30sec

       unit name = bps
       formula = 8 * ; 8 /"
   ::= {pr1645v2TvTmplPerfiEntry 45484544}

pr1645v2TvTmplPerfiMCOutBandwidth1min OBJECT-TYPE
   SYNTAX      Integer32
   MAX-ACCESS  read-only
   STATUS      current
   DESCRIPTION
      "Path: tunnels.performance.ipsecL2tpTunnels.mibCounters.ifOutBandwidth.1min

       unit name = bps
       formula = 8 * ; 8 /"
   ::= {pr1645v2TvTmplPerfiEntry 45487104}

pr1645v2TvTmplPerfiMCOutBandwidth2min OBJECT-TYPE
   SYNTAX      Integer32
   MAX-ACCESS  read-only
   STATUS      current
   DESCRIPTION
      "Path: tunnels.performance.ipsecL2tpTunnels.mibCounters.ifOutBandwidth.2min

       unit name = bps
       formula = 8 * ; 8 /"
   ::= {pr1645v2TvTmplPerfiEntry 45492224}

pr1645v2TvTmplPerfiMCOutBandwidth5min OBJECT-TYPE
   SYNTAX      Integer32
   MAX-ACCESS  read-only
   STATUS      current
   DESCRIPTION
      "Path: tunnels.performance.ipsecL2tpTunnels.mibCounters.ifOutBandwidth.5min

       unit name = bps
       formula = 8 * ; 8 /"
   ::= {pr1645v2TvTmplPerfiEntry 45507584}

pr1645v2TvTmplPerfiControlHelloSent OBJECT-TYPE
   SYNTAX      Gauge32
   MAX-ACCESS  read-only
   STATUS      current
   DESCRIPTION
      "Path: tunnels.performance.ipsecL2tpTunnels.control.helloSent

       32 bit unsigned gauge value."
   ::= {pr1645v2TvTmplPerfiEntry 117506048}

pr1645v2TvTmplPerfiControlHelloRcvd OBJECT-TYPE
   SYNTAX      Gauge32
   MAX-ACCESS  read-only
   STATUS      current
   DESCRIPTION
      "Path: tunnels.performance.ipsecL2tpTunnels.control.helloRcvd

       32 bit unsigned gauge value."
   ::= {pr1645v2TvTmplPerfiEntry 117637120}

pr1645v2TvTmplPerfiControlAckSent OBJECT-TYPE
   SYNTAX      Gauge32
   MAX-ACCESS  read-only
   STATUS      current
   DESCRIPTION
      "Path: tunnels.performance.ipsecL2tpTunnels.control.ackSent

       32 bit unsigned gauge value."
   ::= {pr1645v2TvTmplPerfiEntry 117702656}

pr1645v2TvTmplPerfiControlAckRcvd OBJECT-TYPE
   SYNTAX      Gauge32
   MAX-ACCESS  read-only
   STATUS      current
   DESCRIPTION
      "Path: tunnels.performance.ipsecL2tpTunnels.control.ackRcvd

       32 bit unsigned gauge value."
   ::= {pr1645v2TvTmplPerfiEntry 117571584}

pr1645v2TvTmplPerfiControlDuplicateRcvd OBJECT-TYPE
   SYNTAX      Gauge32
   MAX-ACCESS  read-only
   STATUS      current
   DESCRIPTION
      "Path: tunnels.performance.ipsecL2tpTunnels.control.duplicateRcvd

       32 bit unsigned gauge value."
   ::= {pr1645v2TvTmplPerfiEntry 117768192}

pr1645v2TvTmplPerfiControlOutOfSeqRcvd OBJECT-TYPE
   SYNTAX      Gauge32
   MAX-ACCESS  read-only
   STATUS      current
   DESCRIPTION
      "Path: tunnels.performance.ipsecL2tpTunnels.control.outOfSeqRcvd

       32 bit unsigned gauge value."
   ::= {pr1645v2TvTmplPerfiEntry 117833728}

pr1645v2TvTmplPerfiControlRetransmission OBJECT-TYPE
   SYNTAX      Gauge32
   MAX-ACCESS  read-only
   STATUS      current
   DESCRIPTION
      "Path: tunnels.performance.ipsecL2tpTunnels.control.retransmission

       32 bit unsigned gauge value."
   ::= {pr1645v2TvTmplPerfiEntry 117899264}

pr1645v2TvTmplPerfiControlAuthenFailure OBJECT-TYPE
   SYNTAX      Gauge32
   MAX-ACCESS  read-only
   STATUS      current
   DESCRIPTION
      "Path: tunnels.performance.ipsecL2tpTunnels.control.authenFailure

       32 bit unsigned gauge value."
   ::= {pr1645v2TvTmplPerfiEntry 117964800}

pr1645v2TvTmplPerfiPppPort OBJECT-TYPE
   SYNTAX      Counter32
   MAX-ACCESS  read-only
   STATUS      current
   DESCRIPTION
      "Path: tunnels.performance.ipsecL2tpTunnels.ppp.port

       32 bit unsigned wrappable counter."
   ::= {pr1645v2TvTmplPerfiEntry 67371008}

pr1645v2TvTmplPerfiPppLcpUp OBJECT-TYPE
   SYNTAX      Counter32
   MAX-ACCESS  read-only
   STATUS      current
   DESCRIPTION
      "Path: tunnels.performance.ipsecL2tpTunnels.ppp.lcp.up

       32 bit unsigned wrappable counter."
   ::= {pr1645v2TvTmplPerfiEntry 67174656}

pr1645v2TvTmplPerfiPppLcpDown OBJECT-TYPE
   SYNTAX      Counter32
   MAX-ACCESS  read-only
   STATUS      current
   DESCRIPTION
      "Path: tunnels.performance.ipsecL2tpTunnels.ppp.lcp.down

       32 bit unsigned wrappable counter."
   ::= {pr1645v2TvTmplPerfiEntry 67174912}

pr1645v2TvTmplPerfiPppLcpOpen OBJECT-TYPE
   SYNTAX      Counter32
   MAX-ACCESS  read-only
   STATUS      current
   DESCRIPTION
      "Path: tunnels.performance.ipsecL2tpTunnels.ppp.lcp.open

       32 bit unsigned wrappable counter."
   ::= {pr1645v2TvTmplPerfiEntry 67175168}

pr1645v2TvTmplPerfiPppLcpClose OBJECT-TYPE
   SYNTAX      Counter32
   MAX-ACCESS  read-only
   STATUS      current
   DESCRIPTION
      "Path: tunnels.performance.ipsecL2tpTunnels.ppp.lcp.close

       32 bit unsigned wrappable counter."
   ::= {pr1645v2TvTmplPerfiEntry 67175424}

pr1645v2TvTmplPerfiPppLcpToP OBJECT-TYPE
   SYNTAX      Counter32
   MAX-ACCESS  read-only
   STATUS      current
   DESCRIPTION
      "Path: tunnels.performance.ipsecL2tpTunnels.ppp.lcp.toP

       32 bit unsigned wrappable counter."
   ::= {pr1645v2TvTmplPerfiEntry 67175680}

pr1645v2TvTmplPerfiPppLcpToM OBJECT-TYPE
   SYNTAX      Counter32
   MAX-ACCESS  read-only
   STATUS      current
   DESCRIPTION
      "Path: tunnels.performance.ipsecL2tpTunnels.ppp.lcp.toM

       32 bit unsigned wrappable counter."
   ::= {pr1645v2TvTmplPerfiEntry 67175936}

pr1645v2TvTmplPerfiPppLcpRcrP OBJECT-TYPE
   SYNTAX      Counter32
   MAX-ACCESS  read-only
   STATUS      current
   DESCRIPTION
      "Path: tunnels.performance.ipsecL2tpTunnels.ppp.lcp.rcrP

       32 bit unsigned wrappable counter."
   ::= {pr1645v2TvTmplPerfiEntry 67176192}

pr1645v2TvTmplPerfiPppLcpRcrM OBJECT-TYPE
   SYNTAX      Counter32
   MAX-ACCESS  read-only
   STATUS      current
   DESCRIPTION
      "Path: tunnels.performance.ipsecL2tpTunnels.ppp.lcp.rcrM

       32 bit unsigned wrappable counter."
   ::= {pr1645v2TvTmplPerfiEntry 67176448}

pr1645v2TvTmplPerfiPppLcpRca OBJECT-TYPE
   SYNTAX      Counter32
   MAX-ACCESS  read-only
   STATUS      current
   DESCRIPTION
      "Path: tunnels.performance.ipsecL2tpTunnels.ppp.lcp.rca

       32 bit unsigned wrappable counter."
   ::= {pr1645v2TvTmplPerfiEntry 67176704}

pr1645v2TvTmplPerfiPppLcpRcn OBJECT-TYPE
   SYNTAX      Counter32
   MAX-ACCESS  read-only
   STATUS      current
   DESCRIPTION
      "Path: tunnels.performance.ipsecL2tpTunnels.ppp.lcp.rcn

       32 bit unsigned wrappable counter."
   ::= {pr1645v2TvTmplPerfiEntry 67176960}

pr1645v2TvTmplPerfiPppLcpRtr OBJECT-TYPE
   SYNTAX      Counter32
   MAX-ACCESS  read-only
   STATUS      current
   DESCRIPTION
      "Path: tunnels.performance.ipsecL2tpTunnels.ppp.lcp.rtr

       32 bit unsigned wrappable counter."
   ::= {pr1645v2TvTmplPerfiEntry 67177216}

pr1645v2TvTmplPerfiPppLcpRta OBJECT-TYPE
   SYNTAX      Counter32
   MAX-ACCESS  read-only
   STATUS      current
   DESCRIPTION
      "Path: tunnels.performance.ipsecL2tpTunnels.ppp.lcp.rta

       32 bit unsigned wrappable counter."
   ::= {pr1645v2TvTmplPerfiEntry 67177472}

pr1645v2TvTmplPerfiPppLcpRuc OBJECT-TYPE
   SYNTAX      Counter32
   MAX-ACCESS  read-only
   STATUS      current
   DESCRIPTION
      "Path: tunnels.performance.ipsecL2tpTunnels.ppp.lcp.ruc

       32 bit unsigned wrappable counter."
   ::= {pr1645v2TvTmplPerfiEntry 67177728}

pr1645v2TvTmplPerfiPppLcpRxjP OBJECT-TYPE
   SYNTAX      Counter32
   MAX-ACCESS  read-only
   STATUS      current
   DESCRIPTION
      "Path: tunnels.performance.ipsecL2tpTunnels.ppp.lcp.rxjP

       32 bit unsigned wrappable counter."
   ::= {pr1645v2TvTmplPerfiEntry 67177984}

pr1645v2TvTmplPerfiPppLcpRxjM OBJECT-TYPE
   SYNTAX      Counter32
   MAX-ACCESS  read-only
   STATUS      current
   DESCRIPTION
      "Path: tunnels.performance.ipsecL2tpTunnels.ppp.lcp.rxjM

       32 bit unsigned wrappable counter."
   ::= {pr1645v2TvTmplPerfiEntry 67178240}

pr1645v2TvTmplPerfiPppLcpRxr OBJECT-TYPE
   SYNTAX      Counter32
   MAX-ACCESS  read-only
   STATUS      current
   DESCRIPTION
      "Path: tunnels.performance.ipsecL2tpTunnels.ppp.lcp.rxr

       32 bit unsigned wrappable counter."
   ::= {pr1645v2TvTmplPerfiEntry 67178496}

pr1645v2TvTmplPerfiPppLcpRrr OBJECT-TYPE
   SYNTAX      Counter32
   MAX-ACCESS  read-only
   STATUS      current
   DESCRIPTION
      "Path: tunnels.performance.ipsecL2tpTunnels.ppp.lcp.rrr

       32 bit unsigned wrappable counter."
   ::= {pr1645v2TvTmplPerfiEntry 67178752}

pr1645v2TvTmplPerfiPppLcpRra OBJECT-TYPE
   SYNTAX      Counter32
   MAX-ACCESS  read-only
   STATUS      current
   DESCRIPTION
      "Path: tunnels.performance.ipsecL2tpTunnels.ppp.lcp.rra

       32 bit unsigned wrappable counter."
   ::= {pr1645v2TvTmplPerfiEntry 67179008}

pr1645v2TvTmplPerfiPppLcpDf OBJECT-TYPE
   SYNTAX      Counter32
   MAX-ACCESS  read-only
   STATUS      current
   DESCRIPTION
      "Path: tunnels.performance.ipsecL2tpTunnels.ppp.lcp.df

       32 bit unsigned wrappable counter."
   ::= {pr1645v2TvTmplPerfiEntry 67179264}

pr1645v2TvTmplPerfiPppLcpIntClose OBJECT-TYPE
   SYNTAX      Counter32
   MAX-ACCESS  read-only
   STATUS      current
   DESCRIPTION
      "Path: tunnels.performance.ipsecL2tpTunnels.ppp.lcp.intClose

       32 bit unsigned wrappable counter."
   ::= {pr1645v2TvTmplPerfiEntry 67179520}

pr1645v2TvTmplPerfiPppLcpLm OBJECT-TYPE
   SYNTAX      Counter32
   MAX-ACCESS  read-only
   STATUS      current
   DESCRIPTION
      "Path: tunnels.performance.ipsecL2tpTunnels.ppp.lcp.lm

       32 bit unsigned wrappable counter."
   ::= {pr1645v2TvTmplPerfiEntry 67179776}

pr1645v2TvTmplPerfiPppLcpLmM OBJECT-TYPE
   SYNTAX      Counter32
   MAX-ACCESS  read-only
   STATUS      current
   DESCRIPTION
      "Path: tunnels.performance.ipsecL2tpTunnels.ppp.lcp.lmM

       32 bit unsigned wrappable counter."
   ::= {pr1645v2TvTmplPerfiEntry 67180032}

pr1645v2TvTmplPerfiPppAuthMyNegotiated OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.ipsecL2tpTunnels.ppp.auth.myNegotiated

       Possibilities:
               none   (0)
               pap   (1)
               chap   (2)
               msChap   (3)
               msChapV2   (4)
               unknown   (5)
               chapOrPap   (6)"
   ::= {pr1645v2TvTmplPerfiEntry 67243264}

pr1645v2TvTmplPerfiPppAuthMyConfigured OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.ipsecL2tpTunnels.ppp.auth.myConfigured

       Possibilities:
               none   (0)
               pap   (1)
               chap   (2)
               msChap   (3)
               msChapV2   (4)
               unknown   (5)
               chapOrPap   (6)"
   ::= {pr1645v2TvTmplPerfiEntry 67243776}

pr1645v2TvTmplPerfiPppAuthHisRequested OBJECT-TYPE
   SYNTAX      INTEGER
               {
               none (0),
               pap (1),
               chap (2),
               msChap (3),
               msChapV2 (4),
               unknown (5),
               chapOrPap (6)
               }
   MAX-ACCESS  read-only
   STATUS      current
   DESCRIPTION
      "Path: tunnels.performance.ipsecL2tpTunnels.ppp.auth.hisRequested

       Possibilities:
               none   (0)
               pap   (1)
               chap   (2)
               msChap   (3)
               msChapV2   (4)
               unknown   (5)
               chapOrPap   (6)"
   ::= {pr1645v2TvTmplPerfiEntry 67243520}

pr1645v2TvTmplPerfiPppAuthRxChallenge OBJECT-TYPE
   SYNTAX      Counter32
   MAX-ACCESS  read-only
   STATUS      current
   DESCRIPTION
      "Path: tunnels.performance.ipsecL2tpTunnels.ppp.auth.rxChallenge

       32 bit unsigned wrappable counter."
   ::= {pr1645v2TvTmplPerfiEntry 67240192}

pr1645v2TvTmplPerfiPppAuthRxResponse OBJECT-TYPE
   SYNTAX      Counter32
   MAX-ACCESS  read-only
   STATUS      current
   DESCRIPTION
      "Path: tunnels.performance.ipsecL2tpTunnels.ppp.auth.rxResponse

       32 bit unsigned wrappable counter."
   ::= {pr1645v2TvTmplPerfiEntry 67240448}

pr1645v2TvTmplPerfiPppAuthRxSuccess OBJECT-TYPE
   SYNTAX      Counter32
   MAX-ACCESS  read-only
   STATUS      current
   DESCRIPTION
      "Path: tunnels.performance.ipsecL2tpTunnels.ppp.auth.rxSuccess

       32 bit unsigned wrappable counter."
   ::= {pr1645v2TvTmplPerfiEntry 67240704}

pr1645v2TvTmplPerfiPppAuthRxFailure OBJECT-TYPE
   SYNTAX      Counter32
   MAX-ACCESS  read-only
   STATUS      current
   DESCRIPTION
      "Path: tunnels.performance.ipsecL2tpTunnels.ppp.auth.rxFailure

       32 bit unsigned wrappable counter."
   ::= {pr1645v2TvTmplPerfiEntry 67240960}

pr1645v2TvTmplPerfiPppAuthChallengeTO OBJECT-TYPE
   SYNTAX      Counter32
   MAX-ACCESS  read-only
   STATUS      current
   DESCRIPTION
      "Path: tunnels.performance.ipsecL2tpTunnels.ppp.auth.challengeTO

       32 bit unsigned wrappable counter."
   ::= {pr1645v2TvTmplPerfiEntry 67241216}

pr1645v2TvTmplPerfiPppAuthResponseTO OBJECT-TYPE
   SYNTAX      Counter32
   MAX-ACCESS  read-only
   STATUS      current
   DESCRIPTION
      "Path: tunnels.performance.ipsecL2tpTunnels.ppp.auth.responseTO

       32 bit unsigned wrappable counter."
   ::= {pr1645v2TvTmplPerfiEntry 67241472}

pr1645v2TvTmplPerfiPppAuthTxChallenge OBJECT-TYPE
   SYNTAX      Counter32
   MAX-ACCESS  read-only
   STATUS      current
   DESCRIPTION
      "Path: tunnels.performance.ipsecL2tpTunnels.ppp.auth.txChallenge

       32 bit unsigned wrappable counter."
   ::= {pr1645v2TvTmplPerfiEntry 67241728}

pr1645v2TvTmplPerfiPppAuthRxRadiusSuccess OBJECT-TYPE
   SYNTAX      Counter32
   MAX-ACCESS  read-only
   STATUS      current
   DESCRIPTION
      "Path: tunnels.performance.ipsecL2tpTunnels.ppp.auth.rxRadiusSuccess

       32 bit unsigned wrappable counter."
   ::= {pr1645v2TvTmplPerfiEntry 67241984}

pr1645v2TvTmplPerfiPppAuthRxRadiusFailure OBJECT-TYPE
   SYNTAX      Counter32
   MAX-ACCESS  read-only
   STATUS      current
   DESCRIPTION
      "Path: tunnels.performance.ipsecL2tpTunnels.ppp.auth.rxRadiusFailure

       32 bit unsigned wrappable counter."
   ::= {pr1645v2TvTmplPerfiEntry 67242240}

pr1645v2TvTmplPerfiPppAuthTxSuccess OBJECT-TYPE
   SYNTAX      Counter32
   MAX-ACCESS  read-only
   STATUS      current
   DESCRIPTION
      "Path: tunnels.performance.ipsecL2tpTunnels.ppp.auth.txSuccess

       32 bit unsigned wrappable counter."
   ::= {pr1645v2TvTmplPerfiEntry 67242496}

pr1645v2TvTmplPerfiPppAuthTxFailure OBJECT-TYPE
   SYNTAX      Counter32
   MAX-ACCESS  read-only
   STATUS      current
   DESCRIPTION
      "Path: tunnels.performance.ipsecL2tpTunnels.ppp.auth.txFailure

       32 bit unsigned wrappable counter."
   ::= {pr1645v2TvTmplPerfiEntry 67242752}

pr1645v2TvTmplPerfiPppAuthUnexpected OBJECT-TYPE
   SYNTAX      Counter32
   MAX-ACCESS  read-only
   STATUS      current
   DESCRIPTION
      "Path: tunnels.performance.ipsecL2tpTunnels.ppp.auth.unexpected

       32 bit unsigned wrappable counter."
   ::= {pr1645v2TvTmplPerfiEntry 67243008}

pr1645v2TvTmplPerfiPppIpcpUp OBJECT-TYPE
   SYNTAX      Counter32
   MAX-ACCESS  read-only
   STATUS      current
   DESCRIPTION
      "Path: tunnels.performance.ipsecL2tpTunnels.ppp.ipcp.up

       32 bit unsigned wrappable counter."
   ::= {pr1645v2TvTmplPerfiEntry 67305728}

pr1645v2TvTmplPerfiPppIpcpDown OBJECT-TYPE
   SYNTAX      Counter32
   MAX-ACCESS  read-only
   STATUS      current
   DESCRIPTION
      "Path: tunnels.performance.ipsecL2tpTunnels.ppp.ipcp.down

       32 bit unsigned wrappable counter."
   ::= {pr1645v2TvTmplPerfiEntry 67305984}

pr1645v2TvTmplPerfiPppIpcpOpen OBJECT-TYPE
   SYNTAX      Counter32
   MAX-ACCESS  read-only
   STATUS      current
   DESCRIPTION
      "Path: tunnels.performance.ipsecL2tpTunnels.ppp.ipcp.open

       32 bit unsigned wrappable counter."
   ::= {pr1645v2TvTmplPerfiEntry 67306240}

pr1645v2TvTmplPerfiPppIpcpClose OBJECT-TYPE
   SYNTAX      Counter32
   MAX-ACCESS  read-only
   STATUS      current
   DESCRIPTION
      "Path: tunnels.performance.ipsecL2tpTunnels.ppp.ipcp.close

       32 bit unsigned wrappable counter."
   ::= {pr1645v2TvTmplPerfiEntry 67306496}

pr1645v2TvTmplPerfiPppIpcpToP OBJECT-TYPE
   SYNTAX      Counter32
   MAX-ACCESS  read-only
   STATUS      current
   DESCRIPTION
      "Path: tunnels.performance.ipsecL2tpTunnels.ppp.ipcp.toP

       32 bit unsigned wrappable counter."
   ::= {pr1645v2TvTmplPerfiEntry 67306752}

pr1645v2TvTmplPerfiPppIpcpToM OBJECT-TYPE
   SYNTAX      Counter32
   MAX-ACCESS  read-only
   STATUS      current
   DESCRIPTION
      "Path: tunnels.performance.ipsecL2tpTunnels.ppp.ipcp.toM

       32 bit unsigned wrappable counter."
   ::= {pr1645v2TvTmplPerfiEntry 67307008}

pr1645v2TvTmplPerfiPppIpcpRcrP OBJECT-TYPE
   SYNTAX      Counter32
   MAX-ACCESS  read-only
   STATUS      current
   DESCRIPTION
      "Path: tunnels.performance.ipsecL2tpTunnels.ppp.ipcp.rcrP

       32 bit unsigned wrappable counter."
   ::= {pr1645v2TvTmplPerfiEntry 67307264}

pr1645v2TvTmplPerfiPppIpcpRcrM OBJECT-TYPE
   SYNTAX      Counter32
   MAX-ACCESS  read-only
   STATUS      current
   DESCRIPTION
      "Path: tunnels.performance.ipsecL2tpTunnels.ppp.ipcp.rcrM

       32 bit unsigned wrappable counter."
   ::= {pr1645v2TvTmplPerfiEntry 67307520}

pr1645v2TvTmplPerfiPppIpcpRca OBJECT-TYPE
   SYNTAX      Counter32
   MAX-ACCESS  read-only
   STATUS      current
   DESCRIPTION
      "Path: tunnels.performance.ipsecL2tpTunnels.ppp.ipcp.rca

       32 bit unsigned wrappable counter."
   ::= {pr1645v2TvTmplPerfiEntry 67307776}

pr1645v2TvTmplPerfiPppIpcpRcn OBJECT-TYPE
   SYNTAX      Counter32
   MAX-ACCESS  read-only
   STATUS      current
   DESCRIPTION
      "Path: tunnels.performance.ipsecL2tpTunnels.ppp.ipcp.rcn

       32 bit unsigned wrappable counter."
   ::= {pr1645v2TvTmplPerfiEntry 67308032}

pr1645v2TvTmplPerfiPppIpcpRtr OBJECT-TYPE
   SYNTAX      Counter32
   MAX-ACCESS  read-only
   STATUS      current
   DESCRIPTION
      "Path: tunnels.performance.ipsecL2tpTunnels.ppp.ipcp.rtr

       32 bit unsigned wrappable counter."
   ::= {pr1645v2TvTmplPerfiEntry 67308288}

pr1645v2TvTmplPerfiPppIpcpRta OBJECT-TYPE
   SYNTAX      Counter32
   MAX-ACCESS  read-only
   STATUS      current
   DESCRIPTION
      "Path: tunnels.performance.ipsecL2tpTunnels.ppp.ipcp.rta

       32 bit unsigned wrappable counter."
   ::= {pr1645v2TvTmplPerfiEntry 67308544}

pr1645v2TvTmplPerfiPppIpcpRuc OBJECT-TYPE
   SYNTAX      Counter32
   MAX-ACCESS  read-only
   STATUS      current
   DESCRIPTION
      "Path: tunnels.performance.ipsecL2tpTunnels.ppp.ipcp.ruc

       32 bit unsigned wrappable counter."
   ::= {pr1645v2TvTmplPerfiEntry 67308800}

pr1645v2TvTmplPerfiPppIpcpRxjP OBJECT-TYPE
   SYNTAX      Counter32
   MAX-ACCESS  read-only
   STATUS      current
   DESCRIPTION
      "Path: tunnels.performance.ipsecL2tpTunnels.ppp.ipcp.rxjP

       32 bit unsigned wrappable counter."
   ::= {pr1645v2TvTmplPerfiEntry 67309056}

pr1645v2TvTmplPerfiPppIpcpRxjM OBJECT-TYPE
   SYNTAX      Counter32
   MAX-ACCESS  read-only
   STATUS      current
   DESCRIPTION
      "Path: tunnels.performance.ipsecL2tpTunnels.ppp.ipcp.rxjM

       32 bit unsigned wrappable counter."
   ::= {pr1645v2TvTmplPerfiEntry 67309312}

pr1645v2TvTmplPerfiPppIpcpRxr OBJECT-TYPE
   SYNTAX      Counter32
   MAX-ACCESS  read-only
   STATUS      current
   DESCRIPTION
      "Path: tunnels.performance.ipsecL2tpTunnels.ppp.ipcp.rxr

       32 bit unsigned wrappable counter."
   ::= {pr1645v2TvTmplPerfiEntry 67309568}

pr1645v2TvTmplPerfiPppIpcpRrr OBJECT-TYPE
   SYNTAX      Counter32
   MAX-ACCESS  read-only
   STATUS      current
   DESCRIPTION
      "Path: tunnels.performance.ipsecL2tpTunnels.ppp.ipcp.rrr

       32 bit unsigned wrappable counter."
   ::= {pr1645v2TvTmplPerfiEntry 67309824}

pr1645v2TvTmplPerfiPppIpcpRra OBJECT-TYPE
   SYNTAX      Counter32
   MAX-ACCESS  read-only
   STATUS      current
   DESCRIPTION
      "Path: tunnels.performance.ipsecL2tpTunnels.ppp.ipcp.rra

       32 bit unsigned wrappable counter."
   ::= {pr1645v2TvTmplPerfiEntry 67310080}

pr1645v2TvTmplPerfiPppIpcpDf OBJECT-TYPE
   SYNTAX      Counter32
   MAX-ACCESS  read-only
   STATUS      current
   DESCRIPTION
      "Path: tunnels.performance.ipsecL2tpTunnels.ppp.ipcp.df

       32 bit unsigned wrappable counter."
   ::= {pr1645v2TvTmplPerfiEntry 67310336}

pr1645v2TvTmplPerfiPppIpcpIntClose OBJECT-TYPE
   SYNTAX      Counter32
   MAX-ACCESS  read-only
   STATUS      current
   DESCRIPTION
      "Path: tunnels.performance.ipsecL2tpTunnels.ppp.ipcp.intClose

       32 bit unsigned wrappable counter."
   ::= {pr1645v2TvTmplPerfiEntry 67310592}

pr1645v2TvTmplPerfiPppIpcpLm OBJECT-TYPE
   SYNTAX      Counter32
   MAX-ACCESS  read-only
   STATUS      current
   DESCRIPTION
      "Path: tunnels.performance.ipsecL2tpTunnels.ppp.ipcp.lm

       32 bit unsigned wrappable counter."
   ::= {pr1645v2TvTmplPerfiEntry 67310848}

pr1645v2TvTmplPerfiPppIpcpLmM OBJECT-TYPE
   SYNTAX      Counter32
   MAX-ACCESS  read-only
   STATUS      current
   DESCRIPTION
      "Path: tunnels.performance.ipsecL2tpTunnels.ppp.ipcp.lmM

       32 bit unsigned wrappable counter."
   ::= {pr1645v2TvTmplPerfiEntry 67311104}

pr1645v2TvTmplPerfiPppLinkMonitoringRequestsSent OBJECT-TYPE
   SYNTAX      Gauge32
   MAX-ACCESS  read-only
   STATUS      current
   DESCRIPTION
      "Path: tunnels.performance.ipsecL2tpTunnels.ppp.linkMonitoring.requestsSent

       32 bit unsigned gauge value."
   ::= {pr1645v2TvTmplPerfiEntry 67436800}

pr1645v2TvTmplPerfiPppLinkMonitoringRepliesRcvd OBJECT-TYPE
   SYNTAX      Gauge32
   MAX-ACCESS  read-only
   STATUS      current
   DESCRIPTION
      "Path: tunnels.performance.ipsecL2tpTunnels.ppp.linkMonitoring.repliesRcvd

       32 bit unsigned gauge value."
   ::= {pr1645v2TvTmplPerfiEntry 67437056}

pr1645v2TvTmplPerfiPppLinkMonitoringRequestsRcvd OBJECT-TYPE
   SYNTAX      Gauge32
   MAX-ACCESS  read-only
   STATUS      current
   DESCRIPTION
      "Path: tunnels.performance.ipsecL2tpTunnels.ppp.linkMonitoring.requestsRcvd

       32 bit unsigned gauge value."
   ::= {pr1645v2TvTmplPerfiEntry 67437312}

pr1645v2TvTmplPerfiPppLinkMonitoringRepliesSent OBJECT-TYPE
   SYNTAX      Gauge32
   MAX-ACCESS  read-only
   STATUS      current
   DESCRIPTION
      "Path: tunnels.performance.ipsecL2tpTunnels.ppp.linkMonitoring.repliesSent

       32 bit unsigned gauge value."
   ::= {pr1645v2TvTmplPerfiEntry 67437568}

pr1645v2TvTmplPerfiMCH2P OBJECT-TYPE
   SYNTAX      SEQUENCE OF Pr1645v2TvTmplPerfiMCH2PEntry
   MAX-ACCESS  not-accessible
   STATUS      current
   DESCRIPTION
      ""
   ::= {pr1645v2TvTmplPerfi 41549824}

pr1645v2TvTmplPerfiMCH2PEntry OBJECT-TYPE
   SYNTAX      Pr1645v2TvTmplPerfiMCH2PEntry
   MAX-ACCESS  not-accessible
   STATUS      current
   DESCRIPTION
      ""
   INDEX      { pr1645v2TvTmplPerfiTableIx,
                pr1645v2TvTmplPerfiMCH2PTableIx }
   ::= {pr1645v2TvTmplPerfiMCH2P 1}

Pr1645v2TvTmplPerfiMCH2PEntry ::=
   SEQUENCE
      {
      pr1645v2TvTmplPerfiMCH2PTableIx
         TableIndex,
      pr1645v2TvTmplPerfiMCH2PSysUpTime
         TimeTicks,
      pr1645v2TvTmplPerfiMCH2PIfUpTime
         TimeTicks,
      pr1645v2TvTmplPerfiMCH2PIfStatChanges
         Counter32,
      pr1645v2TvTmplPerfiMCH2PIfInOctets
         Counter64,
      pr1645v2TvTmplPerfiMCH2PIfInUCPkts
         Counter64,
      pr1645v2TvTmplPerfiMCH2PIfInNUCPkts
         Counter64,
      pr1645v2TvTmplPerfiMCH2PIfInBCPkts
         Counter64,
      pr1645v2TvTmplPerfiMCH2PIfInMCPkts
         Counter64,
      pr1645v2TvTmplPerfiMCH2PIfInDiscards
         Counter64,
      pr1645v2TvTmplPerfiMCH2PIfInErrors
         Counter64,
      pr1645v2TvTmplPerfiMCH2PIfInUnkwn
         Counter64,
      pr1645v2TvTmplPerfiMCH2PInDropEx
         Counter64,
      pr1645v2TvTmplPerfiMCH2PInDropNoMac
         Counter64,
      pr1645v2TvTmplPerfiMCH2PInDropNUCast
         Counter64,
      pr1645v2TvTmplPerfiMCH2PInDropFilter
         Counter64,
      pr1645v2TvTmplPerfiMCH2PIfInBandwidth
         Integer32,
      pr1645v2TvTmplPerfiMCH2PIfOutOctets
         Counter64,
      pr1645v2TvTmplPerfiMCH2PIfOutUCPkts
         Counter64,
      pr1645v2TvTmplPerfiMCH2PIfOutNUCPkts
         Counter64,
      pr1645v2TvTmplPerfiMCH2PIfOutBCPkts
         Counter64,
      pr1645v2TvTmplPerfiMCH2PIfOutMCPkts
         Counter64,
      pr1645v2TvTmplPerfiMCH2PIfOutDiscards
         Counter64,
      pr1645v2TvTmplPerfiMCH2PIfOutErrors
         Counter64,
      pr1645v2TvTmplPerfiMCH2POutDropEx
         Counter64,
      pr1645v2TvTmplPerfiMCH2POutDropNoArp
         Counter64,
      pr1645v2TvTmplPerfiMCH2POutDropFilter
         Counter64,
      pr1645v2TvTmplPerfiMCH2PIfOutBandwidth
         Integer32,
      pr1645v2TvTmplPerfiMCH2PIfErrSec
         Counter32
      }

pr1645v2TvTmplPerfiMCH2PTableIx OBJECT-TYPE
   SYNTAX      TableIndex
   MAX-ACCESS  not-accessible
   STATUS      current
   DESCRIPTION
      ""
   ::= {pr1645v2TvTmplPerfiMCH2PEntry 11}

pr1645v2TvTmplPerfiMCH2PSysUpTime OBJECT-TYPE
   SYNTAX      TimeTicks
   MAX-ACCESS  read-only
   STATUS      current
   DESCRIPTION
      "Path: tunnels.performance.ipsecL2tpTunnels.mibCounters.h2Performance.sysUpTime

       Time in centi-second."
   ::= {pr1645v2TvTmplPerfiMCH2PEntry 16777216}

pr1645v2TvTmplPerfiMCH2PIfUpTime OBJECT-TYPE
   SYNTAX      TimeTicks
   MAX-ACCESS  read-only
   STATUS      current
   DESCRIPTION
      "Path: tunnels.performance.ipsecL2tpTunnels.mibCounters.h2Performance.ifUpTime

       Time in centi-second."
   ::= {pr1645v2TvTmplPerfiMCH2PEntry 33554432}

pr1645v2TvTmplPerfiMCH2PIfStatChanges OBJECT-TYPE
   SYNTAX      Counter32
   MAX-ACCESS  read-only
   STATUS      current
   DESCRIPTION
      "Path: tunnels.performance.ipsecL2tpTunnels.mibCounters.h2Performance.ifStatusChanges

       32 bit unsigned wrappable counter."
   ::= {pr1645v2TvTmplPerfiMCH2PEntry 50331648}

pr1645v2TvTmplPerfiMCH2PIfInOctets OBJECT-TYPE
   SYNTAX      Counter64
   MAX-ACCESS  read-only
   STATUS      current
   DESCRIPTION
      "Path: tunnels.performance.ipsecL2tpTunnels.mibCounters.h2Performance.ifInOctets

       64 bit unsigned wrappable counter."
   ::= {pr1645v2TvTmplPerfiMCH2PEntry 67108864}

pr1645v2TvTmplPerfiMCH2PIfInUCPkts OBJECT-TYPE
   SYNTAX      Counter64
   MAX-ACCESS  read-only
   STATUS      current
   DESCRIPTION
      "Path: tunnels.performance.ipsecL2tpTunnels.mibCounters.h2Performance.ifInUcastPkts

       64 bit unsigned wrappable counter."
   ::= {pr1645v2TvTmplPerfiMCH2PEntry 83886080}

pr1645v2TvTmplPerfiMCH2PIfInNUCPkts OBJECT-TYPE
   SYNTAX      Counter64
   MAX-ACCESS  read-only
   STATUS      current
   DESCRIPTION
      "Path: tunnels.performance.ipsecL2tpTunnels.mibCounters.h2Performance.ifInNUcastPkts

       64 bit unsigned wrappable counter."
   ::= {pr1645v2TvTmplPerfiMCH2PEntry 100663296}

pr1645v2TvTmplPerfiMCH2PIfInBCPkts OBJECT-TYPE
   SYNTAX      Counter64
   MAX-ACCESS  read-only
   STATUS      current
   DESCRIPTION
      "Path: tunnels.performance.ipsecL2tpTunnels.mibCounters.h2Performance.ifInBcastPkts

       64 bit unsigned wrappable counter."
   ::= {pr1645v2TvTmplPerfiMCH2PEntry 419430400}

pr1645v2TvTmplPerfiMCH2PIfInMCPkts OBJECT-TYPE
   SYNTAX      Counter64
   MAX-ACCESS  read-only
   STATUS      current
   DESCRIPTION
      "Path: tunnels.performance.ipsecL2tpTunnels.mibCounters.h2Performance.ifInMcastPkts

       64 bit unsigned wrappable counter."
   ::= {pr1645v2TvTmplPerfiMCH2PEntry 436207616}

pr1645v2TvTmplPerfiMCH2PIfInDiscards OBJECT-TYPE
   SYNTAX      Counter64
   MAX-ACCESS  read-only
   STATUS      current
   DESCRIPTION
      "Path: tunnels.performance.ipsecL2tpTunnels.mibCounters.h2Performance.ifInDiscards

       64 bit unsigned wrappable counter."
   ::= {pr1645v2TvTmplPerfiMCH2PEntry 117440512}

pr1645v2TvTmplPerfiMCH2PIfInErrors OBJECT-TYPE
   SYNTAX      Counter64
   MAX-ACCESS  read-only
   STATUS      current
   DESCRIPTION
      "Path: tunnels.performance.ipsecL2tpTunnels.mibCounters.h2Performance.ifInErrors

       64 bit unsigned wrappable counter."
   ::= {pr1645v2TvTmplPerfiMCH2PEntry 134217728}

pr1645v2TvTmplPerfiMCH2PIfInUnkwn OBJECT-TYPE
   SYNTAX      Counter64
   MAX-ACCESS  read-only
   STATUS      current
   DESCRIPTION
      "Path: tunnels.performance.ipsecL2tpTunnels.mibCounters.h2Performance.ifInUnknownProtos

       64 bit unsigned wrappable counter."
   ::= {pr1645v2TvTmplPerfiMCH2PEntry 150994944}

pr1645v2TvTmplPerfiMCH2PInDropEx OBJECT-TYPE
   SYNTAX      Counter64
   MAX-ACCESS  read-only
   STATUS      current
   DESCRIPTION
      "Path: tunnels.performance.ipsecL2tpTunnels.mibCounters.h2Performance.ifInDropLevelExceeded

       64 bit unsigned wrappable counter."
   ::= {pr1645v2TvTmplPerfiMCH2PEntry 335544320}

pr1645v2TvTmplPerfiMCH2PInDropNoMac OBJECT-TYPE
   SYNTAX      Counter64
   MAX-ACCESS  read-only
   STATUS      current
   DESCRIPTION
      "Path: tunnels.performance.ipsecL2tpTunnels.mibCounters.h2Performance.fInDiscardsNoMacFit

       64 bit unsigned wrappable counter."
   ::= {pr1645v2TvTmplPerfiMCH2PEntry 301989888}

pr1645v2TvTmplPerfiMCH2PInDropNUCast OBJECT-TYPE
   SYNTAX      Counter64
   MAX-ACCESS  read-only
   STATUS      current
   DESCRIPTION
      "Path: tunnels.performance.ipsecL2tpTunnels.mibCounters.h2Performance.fInDiscardsNUCast

       64 bit unsigned wrappable counter."
   ::= {pr1645v2TvTmplPerfiMCH2PEntry 318767104}

pr1645v2TvTmplPerfiMCH2PInDropFilter OBJECT-TYPE
   SYNTAX      Counter64
   MAX-ACCESS  read-only
   STATUS      current
   DESCRIPTION
      "Path: tunnels.performance.ipsecL2tpTunnels.mibCounters.h2Performance.fInDiscardsFilter

       64 bit unsigned wrappable counter."
   ::= {pr1645v2TvTmplPerfiMCH2PEntry 385875968}

pr1645v2TvTmplPerfiMCH2PIfInBandwidth OBJECT-TYPE
   SYNTAX      Integer32
   MAX-ACCESS  read-only
   STATUS      current
   DESCRIPTION
      "Path: tunnels.performance.ipsecL2tpTunnels.mibCounters.h2Performance.ifInBandwidth

       unit name = bps
       formula = 8 * ; 8 /"
   ::= {pr1645v2TvTmplPerfiMCH2PEntry 268435456}

pr1645v2TvTmplPerfiMCH2PIfOutOctets OBJECT-TYPE
   SYNTAX      Counter64
   MAX-ACCESS  read-only
   STATUS      current
   DESCRIPTION
      "Path: tunnels.performance.ipsecL2tpTunnels.mibCounters.h2Performance.ifOutOctets

       64 bit unsigned wrappable counter."
   ::= {pr1645v2TvTmplPerfiMCH2PEntry 167772160}

pr1645v2TvTmplPerfiMCH2PIfOutUCPkts OBJECT-TYPE
   SYNTAX      Counter64
   MAX-ACCESS  read-only
   STATUS      current
   DESCRIPTION
      "Path: tunnels.performance.ipsecL2tpTunnels.mibCounters.h2Performance.ifOutUcastPkts

       64 bit unsigned wrappable counter."
   ::= {pr1645v2TvTmplPerfiMCH2PEntry 184549376}

pr1645v2TvTmplPerfiMCH2PIfOutNUCPkts OBJECT-TYPE
   SYNTAX      Counter64
   MAX-ACCESS  read-only
   STATUS      current
   DESCRIPTION
      "Path: tunnels.performance.ipsecL2tpTunnels.mibCounters.h2Performance.ifOutNUcastPkts

       64 bit unsigned wrappable counter."
   ::= {pr1645v2TvTmplPerfiMCH2PEntry 201326592}

pr1645v2TvTmplPerfiMCH2PIfOutBCPkts OBJECT-TYPE
   SYNTAX      Counter64
   MAX-ACCESS  read-only
   STATUS      current
   DESCRIPTION
      "Path: tunnels.performance.ipsecL2tpTunnels.mibCounters.h2Performance.ifOutBcastPkts

       64 bit unsigned wrappable counter."
   ::= {pr1645v2TvTmplPerfiMCH2PEntry 452984832}

pr1645v2TvTmplPerfiMCH2PIfOutMCPkts OBJECT-TYPE
   SYNTAX      Counter64
   MAX-ACCESS  read-only
   STATUS      current
   DESCRIPTION
      "Path: tunnels.performance.ipsecL2tpTunnels.mibCounters.h2Performance.ifOutMcastPkts

       64 bit unsigned wrappable counter."
   ::= {pr1645v2TvTmplPerfiMCH2PEntry 469762048}

pr1645v2TvTmplPerfiMCH2PIfOutDiscards OBJECT-TYPE
   SYNTAX      Counter64
   MAX-ACCESS  read-only
   STATUS      current
   DESCRIPTION
      "Path: tunnels.performance.ipsecL2tpTunnels.mibCounters.h2Performance.ifOutDiscards

       64 bit unsigned wrappable counter."
   ::= {pr1645v2TvTmplPerfiMCH2PEntry 218103808}

pr1645v2TvTmplPerfiMCH2PIfOutErrors OBJECT-TYPE
   SYNTAX      Counter64
   MAX-ACCESS  read-only
   STATUS      current
   DESCRIPTION
      "Path: tunnels.performance.ipsecL2tpTunnels.mibCounters.h2Performance.ifOutErrors

       64 bit unsigned wrappable counter."
   ::= {pr1645v2TvTmplPerfiMCH2PEntry 234881024}

pr1645v2TvTmplPerfiMCH2POutDropEx OBJECT-TYPE
   SYNTAX      Counter64
   MAX-ACCESS  read-only
   STATUS      current
   DESCRIPTION
      "Path: tunnels.performance.ipsecL2tpTunnels.mibCounters.h2Performance.ifOutDropLevelExceeded

       64 bit unsigned wrappable counter."
   ::= {pr1645v2TvTmplPerfiMCH2PEntry 352321536}

pr1645v2TvTmplPerfiMCH2POutDropNoArp OBJECT-TYPE
   SYNTAX      Counter64
   MAX-ACCESS  read-only
   STATUS      current
   DESCRIPTION
      "Path: tunnels.performance.ipsecL2tpTunnels.mibCounters.h2Performance.ifOutDiscardsNoArp

       64 bit unsigned wrappable counter."
   ::= {pr1645v2TvTmplPerfiMCH2PEntry 369098752}

pr1645v2TvTmplPerfiMCH2POutDropFilter OBJECT-TYPE
   SYNTAX      Counter64
   MAX-ACCESS  read-only
   STATUS      current
   DESCRIPTION
      "Path: tunnels.performance.ipsecL2tpTunnels.mibCounters.h2Performance.ifOutDiscardsFilter

       64 bit unsigned wrappable counter."
   ::= {pr1645v2TvTmplPerfiMCH2PEntry 402653184}

pr1645v2TvTmplPerfiMCH2PIfOutBandwidth OBJECT-TYPE
   SYNTAX      Integer32
   MAX-ACCESS  read-only
   STATUS      current
   DESCRIPTION
      "Path: tunnels.performance.ipsecL2tpTunnels.mibCounters.h2Performance.ifOutBandwidth

       unit name = bps
       formula = 8 * ; 8 /"
   ::= {pr1645v2TvTmplPerfiMCH2PEntry 285212672}

pr1645v2TvTmplPerfiMCH2PIfErrSec OBJECT-TYPE
   SYNTAX      Counter32
   MAX-ACCESS  read-only
   STATUS      current
   DESCRIPTION
      "Path: tunnels.performance.ipsecL2tpTunnels.mibCounters.h2Performance.ifErrSec

       32 bit unsigned wrappable counter."
   ::= {pr1645v2TvTmplPerfiMCH2PEntry 251658240}

pr1645v2TvTmplPerfiMCH24P OBJECT-TYPE
   SYNTAX      SEQUENCE OF Pr1645v2TvTmplPerfiMCH24PEntry
   MAX-ACCESS  not-accessible
   STATUS      current
   DESCRIPTION
      ""
   ::= {pr1645v2TvTmplPerfi 41615360}

pr1645v2TvTmplPerfiMCH24PEntry OBJECT-TYPE
   SYNTAX      Pr1645v2TvTmplPerfiMCH24PEntry
   MAX-ACCESS  not-accessible
   STATUS      current
   DESCRIPTION
      ""
   INDEX      { pr1645v2TvTmplPerfiTableIx,
                pr1645v2TvTmplPerfiMCH24PTableIx }
   ::= {pr1645v2TvTmplPerfiMCH24P 1}

Pr1645v2TvTmplPerfiMCH24PEntry ::=
   SEQUENCE
      {
      pr1645v2TvTmplPerfiMCH24PTableIx
         TableIndex,
      pr1645v2TvTmplPerfiMCH24PSysUpTime
         TimeTicks,
      pr1645v2TvTmplPerfiMCH24PIfUpTime
         TimeTicks,
      pr1645v2TvTmplPerfiMCH24PIfStatChanges
         Counter32,
      pr1645v2TvTmplPerfiMCH24PIfInOctets
         Counter64,
      pr1645v2TvTmplPerfiMCH24PIfInUCPkts
         Counter64,
      pr1645v2TvTmplPerfiMCH24PIfInNUCPkts
         Counter64,
      pr1645v2TvTmplPerfiMCH24PIfInBCPkts
         Counter64,
      pr1645v2TvTmplPerfiMCH24PIfInMCPkts
         Counter64,
      pr1645v2TvTmplPerfiMCH24PIfInDiscards
         Counter64,
      pr1645v2TvTmplPerfiMCH24PIfInErrors
         Counter64,
      pr1645v2TvTmplPerfiMCH24PIfInUnkwn
         Counter64,
      pr1645v2TvTmplPerfiMCH24PInDropEx
         Counter64,
      pr1645v2TvTmplPerfiMCH24PInDropNoMac
         Counter64,
      pr1645v2TvTmplPerfiMCH24PInDropNUCast
         Counter64,
      pr1645v2TvTmplPerfiMCH24PInDropFilter
         Counter64,
      pr1645v2TvTmplPerfiMCH24PIfInBandwidth
         Integer32,
      pr1645v2TvTmplPerfiMCH24PIfOutOctets
         Counter64,
      pr1645v2TvTmplPerfiMCH24PIfOutUCPkts
         Counter64,
      pr1645v2TvTmplPerfiMCH24PIfOutNUCPkts
         Counter64,
      pr1645v2TvTmplPerfiMCH24PIfOutBCPkts
         Counter64,
      pr1645v2TvTmplPerfiMCH24PIfOutMCPkts
         Counter64,
      pr1645v2TvTmplPerfiMCH24PIfOutDiscards
         Counter64,
      pr1645v2TvTmplPerfiMCH24PIfOutErrors
         Counter64,
      pr1645v2TvTmplPerfiMCH24POutDropEx
         Counter64,
      pr1645v2TvTmplPerfiMCH24POutDropNoArp
         Counter64,
      pr1645v2TvTmplPerfiMCH24POutDropFilter
         Counter64,
      pr1645v2TvTmplPerfiMCH24PIfOutBandwidth
         Integer32,
      pr1645v2TvTmplPerfiMCH24PIfErrSec
         Counter32
      }

pr1645v2TvTmplPerfiMCH24PTableIx OBJECT-TYPE
   SYNTAX      TableIndex
   MAX-ACCESS  not-accessible
   STATUS      current
   DESCRIPTION
      ""
   ::= {pr1645v2TvTmplPerfiMCH24PEntry 11}

pr1645v2TvTmplPerfiMCH24PSysUpTime OBJECT-TYPE
   SYNTAX      TimeTicks
   MAX-ACCESS  read-only
   STATUS      current
   DESCRIPTION
      "Path: tunnels.performance.ipsecL2tpTunnels.mibCounters.h24Performance.sysUpTime

       Time in centi-second."
   ::= {pr1645v2TvTmplPerfiMCH24PEntry 16777216}

pr1645v2TvTmplPerfiMCH24PIfUpTime OBJECT-TYPE
   SYNTAX      TimeTicks
   MAX-ACCESS  read-only
   STATUS      current
   DESCRIPTION
      "Path: tunnels.performance.ipsecL2tpTunnels.mibCounters.h24Performance.ifUpTime

       Time in centi-second."
   ::= {pr1645v2TvTmplPerfiMCH24PEntry 33554432}

pr1645v2TvTmplPerfiMCH24PIfStatChanges OBJECT-TYPE
   SYNTAX      Counter32
   MAX-ACCESS  read-only
   STATUS      current
   DESCRIPTION
      "Path: tunnels.performance.ipsecL2tpTunnels.mibCounters.h24Performance.ifStatusChanges

       32 bit unsigned wrappable counter."
   ::= {pr1645v2TvTmplPerfiMCH24PEntry 50331648}

pr1645v2TvTmplPerfiMCH24PIfInOctets OBJECT-TYPE
   SYNTAX      Counter64
   MAX-ACCESS  read-only
   STATUS      current
   DESCRIPTION
      "Path: tunnels.performance.ipsecL2tpTunnels.mibCounters.h24Performance.ifInOctets

       64 bit unsigned wrappable counter."
   ::= {pr1645v2TvTmplPerfiMCH24PEntry 67108864}

pr1645v2TvTmplPerfiMCH24PIfInUCPkts OBJECT-TYPE
   SYNTAX      Counter64
   MAX-ACCESS  read-only
   STATUS      current
   DESCRIPTION
      "Path: tunnels.performance.ipsecL2tpTunnels.mibCounters.h24Performance.ifInUcastPkts

       64 bit unsigned wrappable counter."
   ::= {pr1645v2TvTmplPerfiMCH24PEntry 83886080}

pr1645v2TvTmplPerfiMCH24PIfInNUCPkts OBJECT-TYPE
   SYNTAX      Counter64
   MAX-ACCESS  read-only
   STATUS      current
   DESCRIPTION
      "Path: tunnels.performance.ipsecL2tpTunnels.mibCounters.h24Performance.ifInNUcastPkts

       64 bit unsigned wrappable counter."
   ::= {pr1645v2TvTmplPerfiMCH24PEntry 100663296}

pr1645v2TvTmplPerfiMCH24PIfInBCPkts OBJECT-TYPE
   SYNTAX      Counter64
   MAX-ACCESS  read-only
   STATUS      current
   DESCRIPTION
      "Path: tunnels.performance.ipsecL2tpTunnels.mibCounters.h24Performance.ifInBcastPkts

       64 bit unsigned wrappable counter."
   ::= {pr1645v2TvTmplPerfiMCH24PEntry 419430400}

pr1645v2TvTmplPerfiMCH24PIfInMCPkts OBJECT-TYPE
   SYNTAX      Counter64
   MAX-ACCESS  read-only
   STATUS      current
   DESCRIPTION
      "Path: tunnels.performance.ipsecL2tpTunnels.mibCounters.h24Performance.ifInMcastPkts

       64 bit unsigned wrappable counter."
   ::= {pr1645v2TvTmplPerfiMCH24PEntry 436207616}

pr1645v2TvTmplPerfiMCH24PIfInDiscards OBJECT-TYPE
   SYNTAX      Counter64
   MAX-ACCESS  read-only
   STATUS      current
   DESCRIPTION
      "Path: tunnels.performance.ipsecL2tpTunnels.mibCounters.h24Performance.ifInDiscards

       64 bit unsigned wrappable counter."
   ::= {pr1645v2TvTmplPerfiMCH24PEntry 117440512}

pr1645v2TvTmplPerfiMCH24PIfInErrors OBJECT-TYPE
   SYNTAX      Counter64
   MAX-ACCESS  read-only
   STATUS      current
   DESCRIPTION
      "Path: tunnels.performance.ipsecL2tpTunnels.mibCounters.h24Performance.ifInErrors

       64 bit unsigned wrappable counter."
   ::= {pr1645v2TvTmplPerfiMCH24PEntry 134217728}

pr1645v2TvTmplPerfiMCH24PIfInUnkwn OBJECT-TYPE
   SYNTAX      Counter64
   MAX-ACCESS  read-only
   STATUS      current
   DESCRIPTION
      "Path: tunnels.performance.ipsecL2tpTunnels.mibCounters.h24Performance.ifInUnknownProtos

       64 bit unsigned wrappable counter."
   ::= {pr1645v2TvTmplPerfiMCH24PEntry 150994944}

pr1645v2TvTmplPerfiMCH24PInDropEx OBJECT-TYPE
   SYNTAX      Counter64
   MAX-ACCESS  read-only
   STATUS      current
   DESCRIPTION
      "Path: tunnels.performance.ipsecL2tpTunnels.mibCounters.h24Performance.ifInDropLevelExceeded

       64 bit unsigned wrappable counter."
   ::= {pr1645v2TvTmplPerfiMCH24PEntry 335544320}

pr1645v2TvTmplPerfiMCH24PInDropNoMac OBJECT-TYPE
   SYNTAX      Counter64
   MAX-ACCESS  read-only
   STATUS      current
   DESCRIPTION
      "Path: tunnels.performance.ipsecL2tpTunnels.mibCounters.h24Performance.fInDiscardsNoMacFit

       64 bit unsigned wrappable counter."
   ::= {pr1645v2TvTmplPerfiMCH24PEntry 301989888}

pr1645v2TvTmplPerfiMCH24PInDropNUCast OBJECT-TYPE
   SYNTAX      Counter64
   MAX-ACCESS  read-only
   STATUS      current
   DESCRIPTION
      "Path: tunnels.performance.ipsecL2tpTunnels.mibCounters.h24Performance.fInDiscardsNUCast

       64 bit unsigned wrappable counter."
   ::= {pr1645v2TvTmplPerfiMCH24PEntry 318767104}

pr1645v2TvTmplPerfiMCH24PInDropFilter OBJECT-TYPE
   SYNTAX      Counter64
   MAX-ACCESS  read-only
   STATUS      current
   DESCRIPTION
      "Path: tunnels.performance.ipsecL2tpTunnels.mibCounters.h24Performance.fInDiscardsFilter

       64 bit unsigned wrappable counter."
   ::= {pr1645v2TvTmplPerfiMCH24PEntry 385875968}

pr1645v2TvTmplPerfiMCH24PIfInBandwidth OBJECT-TYPE
   SYNTAX      Integer32
   MAX-ACCESS  read-only
   STATUS      current
   DESCRIPTION
      "Path: tunnels.performance.ipsecL2tpTunnels.mibCounters.h24Performance.ifInBandwidth

       unit name = bps
       formula = 8 * ; 8 /"
   ::= {pr1645v2TvTmplPerfiMCH24PEntry 268435456}

pr1645v2TvTmplPerfiMCH24PIfOutOctets OBJECT-TYPE
   SYNTAX      Counter64
   MAX-ACCESS  read-only
   STATUS      current
   DESCRIPTION
      "Path: tunnels.performance.ipsecL2tpTunnels.mibCounters.h24Performance.ifOutOctets

       64 bit unsigned wrappable counter."
   ::= {pr1645v2TvTmplPerfiMCH24PEntry 167772160}

pr1645v2TvTmplPerfiMCH24PIfOutUCPkts OBJECT-TYPE
   SYNTAX      Counter64
   MAX-ACCESS  read-only
   STATUS      current
   DESCRIPTION
      "Path: tunnels.performance.ipsecL2tpTunnels.mibCounters.h24Performance.ifOutUcastPkts

       64 bit unsigned wrappable counter."
   ::= {pr1645v2TvTmplPerfiMCH24PEntry 184549376}

pr1645v2TvTmplPerfiMCH24PIfOutNUCPkts OBJECT-TYPE
   SYNTAX      Counter64
   MAX-ACCESS  read-only
   STATUS      current
   DESCRIPTION
      "Path: tunnels.performance.ipsecL2tpTunnels.mibCounters.h24Performance.ifOutNUcastPkts

       64 bit unsigned wrappable counter."
   ::= {pr1645v2TvTmplPerfiMCH24PEntry 201326592}

pr1645v2TvTmplPerfiMCH24PIfOutBCPkts OBJECT-TYPE
   SYNTAX      Counter64
   MAX-ACCESS  read-only
   STATUS      current
   DESCRIPTION
      "Path: tunnels.performance.ipsecL2tpTunnels.mibCounters.h24Performance.ifOutBcastPkts

       64 bit unsigned wrappable counter."
   ::= {pr1645v2TvTmplPerfiMCH24PEntry 452984832}

pr1645v2TvTmplPerfiMCH24PIfOutMCPkts OBJECT-TYPE
   SYNTAX      Counter64
   MAX-ACCESS  read-only
   STATUS      current
   DESCRIPTION
      "Path: tunnels.performance.ipsecL2tpTunnels.mibCounters.h24Performance.ifOutMcastPkts

       64 bit unsigned wrappable counter."
   ::= {pr1645v2TvTmplPerfiMCH24PEntry 469762048}

pr1645v2TvTmplPerfiMCH24PIfOutDiscards OBJECT-TYPE
   SYNTAX      Counter64
   MAX-ACCESS  read-only
   STATUS      current
   DESCRIPTION
      "Path: tunnels.performance.ipsecL2tpTunnels.mibCounters.h24Performance.ifOutDiscards

       64 bit unsigned wrappable counter."
   ::= {pr1645v2TvTmplPerfiMCH24PEntry 218103808}

pr1645v2TvTmplPerfiMCH24PIfOutErrors OBJECT-TYPE
   SYNTAX      Counter64
   MAX-ACCESS  read-only
   STATUS      current
   DESCRIPTION
      "Path: tunnels.performance.ipsecL2tpTunnels.mibCounters.h24Performance.ifOutErrors

       64 bit unsigned wrappable counter."
   ::= {pr1645v2TvTmplPerfiMCH24PEntry 234881024}

pr1645v2TvTmplPerfiMCH24POutDropEx OBJECT-TYPE
   SYNTAX      Counter64
   MAX-ACCESS  read-only
   STATUS      current
   DESCRIPTION
      "Path: tunnels.performance.ipsecL2tpTunnels.mibCounters.h24Performance.ifOutDropLevelExceeded

       64 bit unsigned wrappable counter."
   ::= {pr1645v2TvTmplPerfiMCH24PEntry 352321536}

pr1645v2TvTmplPerfiMCH24POutDropNoArp OBJECT-TYPE
   SYNTAX      Counter64
   MAX-ACCESS  read-only
   STATUS      current
   DESCRIPTION
      "Path: tunnels.performance.ipsecL2tpTunnels.mibCounters.h24Performance.ifOutDiscardsNoArp

       64 bit unsigned wrappable counter."
   ::= {pr1645v2TvTmplPerfiMCH24PEntry 369098752}

pr1645v2TvTmplPerfiMCH24POutDropFilter OBJECT-TYPE
   SYNTAX      Counter64
   MAX-ACCESS  read-only
   STATUS      current
   DESCRIPTION
      "Path: tunnels.performance.ipsecL2tpTunnels.mibCounters.h24Performance.ifOutDiscardsFilter

       64 bit unsigned wrappable counter."
   ::= {pr1645v2TvTmplPerfiMCH24PEntry 402653184}

pr1645v2TvTmplPerfiMCH24PIfOutBandwidth OBJECT-TYPE
   SYNTAX      Integer32
   MAX-ACCESS  read-only
   STATUS      current
   DESCRIPTION
      "Path: tunnels.performance.ipsecL2tpTunnels.mibCounters.h24Performance.ifOutBandwidth

       unit name = bps
       formula = 8 * ; 8 /"
   ::= {pr1645v2TvTmplPerfiMCH24PEntry 285212672}

pr1645v2TvTmplPerfiMCH24PIfErrSec OBJECT-TYPE
   SYNTAX      Counter32
   MAX-ACCESS  read-only
   STATUS      current
   DESCRIPTION
      "Path: tunnels.performance.ipsecL2tpTunnels.mibCounters.h24Performance.ifErrSec

       32 bit unsigned wrappable counter."
   ::= {pr1645v2TvTmplPerfiMCH24PEntry 251658240}

pr1645v2TvTmplPerfiMCD7P OBJECT-TYPE
   SYNTAX      SEQUENCE OF Pr1645v2TvTmplPerfiMCD7PEntry
   MAX-ACCESS  not-accessible
   STATUS      current
   DESCRIPTION
      ""
   ::= {pr1645v2TvTmplPerfi 41680896}

pr1645v2TvTmplPerfiMCD7PEntry OBJECT-TYPE
   SYNTAX      Pr1645v2TvTmplPerfiMCD7PEntry
   MAX-ACCESS  not-accessible
   STATUS      current
   DESCRIPTION
      ""
   INDEX      { pr1645v2TvTmplPerfiTableIx,
                pr1645v2TvTmplPerfiMCD7PTableIx }
   ::= {pr1645v2TvTmplPerfiMCD7P 1}

Pr1645v2TvTmplPerfiMCD7PEntry ::=
   SEQUENCE
      {
      pr1645v2TvTmplPerfiMCD7PTableIx
         TableIndex,
      pr1645v2TvTmplPerfiMCD7PSysUpTime
         TimeTicks,
      pr1645v2TvTmplPerfiMCD7PIfUpTime
         TimeTicks,
      pr1645v2TvTmplPerfiMCD7PIfStatChanges
         Counter32,
      pr1645v2TvTmplPerfiMCD7PIfInOctets
         Counter64,
      pr1645v2TvTmplPerfiMCD7PIfInUCPkts
         Counter64,
      pr1645v2TvTmplPerfiMCD7PIfInNUCPkts
         Counter64,
      pr1645v2TvTmplPerfiMCD7PIfInBCPkts
         Counter64,
      pr1645v2TvTmplPerfiMCD7PIfInMCPkts
         Counter64,
      pr1645v2TvTmplPerfiMCD7PIfInDiscards
         Counter64,
      pr1645v2TvTmplPerfiMCD7PIfInErrors
         Counter64,
      pr1645v2TvTmplPerfiMCD7PIfInUnkwn
         Counter64,
      pr1645v2TvTmplPerfiMCD7PInDropEx
         Counter64,
      pr1645v2TvTmplPerfiMCD7PInDropNoMac
         Counter64,
      pr1645v2TvTmplPerfiMCD7PInDropNUCast
         Counter64,
      pr1645v2TvTmplPerfiMCD7PInDropFilter
         Counter64,
      pr1645v2TvTmplPerfiMCD7PIfInBandwidth
         Integer32,
      pr1645v2TvTmplPerfiMCD7PIfOutOctets
         Counter64,
      pr1645v2TvTmplPerfiMCD7PIfOutUCPkts
         Counter64,
      pr1645v2TvTmplPerfiMCD7PIfOutNUCPkts
         Counter64,
      pr1645v2TvTmplPerfiMCD7PIfOutBCPkts
         Counter64,
      pr1645v2TvTmplPerfiMCD7PIfOutMCPkts
         Counter64,
      pr1645v2TvTmplPerfiMCD7PIfOutDiscards
         Counter64,
      pr1645v2TvTmplPerfiMCD7PIfOutErrors
         Counter64,
      pr1645v2TvTmplPerfiMCD7POutDropEx
         Counter64,
      pr1645v2TvTmplPerfiMCD7POutDropNoArp
         Counter64,
      pr1645v2TvTmplPerfiMCD7POutDropFilter
         Counter64,
      pr1645v2TvTmplPerfiMCD7PIfOutBandwidth
         Integer32,
      pr1645v2TvTmplPerfiMCD7PIfErrSec
         Counter32
      }

pr1645v2TvTmplPerfiMCD7PTableIx OBJECT-TYPE
   SYNTAX      TableIndex
   MAX-ACCESS  not-accessible
   STATUS      current
   DESCRIPTION
      ""
   ::= {pr1645v2TvTmplPerfiMCD7PEntry 11}

pr1645v2TvTmplPerfiMCD7PSysUpTime OBJECT-TYPE
   SYNTAX      TimeTicks
   MAX-ACCESS  read-only
   STATUS      current
   DESCRIPTION
      "Path: tunnels.performance.ipsecL2tpTunnels.mibCounters.d7Performance.sysUpTime

       Time in centi-second."
   ::= {pr1645v2TvTmplPerfiMCD7PEntry 16777216}

pr1645v2TvTmplPerfiMCD7PIfUpTime OBJECT-TYPE
   SYNTAX      TimeTicks
   MAX-ACCESS  read-only
   STATUS      current
   DESCRIPTION
      "Path: tunnels.performance.ipsecL2tpTunnels.mibCounters.d7Performance.ifUpTime

       Time in centi-second."
   ::= {pr1645v2TvTmplPerfiMCD7PEntry 33554432}

pr1645v2TvTmplPerfiMCD7PIfStatChanges OBJECT-TYPE
   SYNTAX      Counter32
   MAX-ACCESS  read-only
   STATUS      current
   DESCRIPTION
      "Path: tunnels.performance.ipsecL2tpTunnels.mibCounters.d7Performance.ifStatusChanges

       32 bit unsigned wrappable counter."
   ::= {pr1645v2TvTmplPerfiMCD7PEntry 50331648}

pr1645v2TvTmplPerfiMCD7PIfInOctets OBJECT-TYPE
   SYNTAX      Counter64
   MAX-ACCESS  read-only
   STATUS      current
   DESCRIPTION
      "Path: tunnels.performance.ipsecL2tpTunnels.mibCounters.d7Performance.ifInOctets

       64 bit unsigned wrappable counter."
   ::= {pr1645v2TvTmplPerfiMCD7PEntry 67108864}

pr1645v2TvTmplPerfiMCD7PIfInUCPkts OBJECT-TYPE
   SYNTAX      Counter64
   MAX-ACCESS  read-only
   STATUS      current
   DESCRIPTION
      "Path: tunnels.performance.ipsecL2tpTunnels.mibCounters.d7Performance.ifInUcastPkts

       64 bit unsigned wrappable counter."
   ::= {pr1645v2TvTmplPerfiMCD7PEntry 83886080}

pr1645v2TvTmplPerfiMCD7PIfInNUCPkts OBJECT-TYPE
   SYNTAX      Counter64
   MAX-ACCESS  read-only
   STATUS      current
   DESCRIPTION
      "Path: tunnels.performance.ipsecL2tpTunnels.mibCounters.d7Performance.ifInNUcastPkts

       64 bit unsigned wrappable counter."
   ::= {pr1645v2TvTmplPerfiMCD7PEntry 100663296}

pr1645v2TvTmplPerfiMCD7PIfInBCPkts OBJECT-TYPE
   SYNTAX      Counter64
   MAX-ACCESS  read-only
   STATUS      current
   DESCRIPTION
      "Path: tunnels.performance.ipsecL2tpTunnels.mibCounters.d7Performance.ifInBcastPkts

       64 bit unsigned wrappable counter."
   ::= {pr1645v2TvTmplPerfiMCD7PEntry 419430400}

pr1645v2TvTmplPerfiMCD7PIfInMCPkts OBJECT-TYPE
   SYNTAX      Counter64
   MAX-ACCESS  read-only
   STATUS      current
   DESCRIPTION
      "Path: tunnels.performance.ipsecL2tpTunnels.mibCounters.d7Performance.ifInMcastPkts

       64 bit unsigned wrappable counter."
   ::= {pr1645v2TvTmplPerfiMCD7PEntry 436207616}

pr1645v2TvTmplPerfiMCD7PIfInDiscards OBJECT-TYPE
   SYNTAX      Counter64
   MAX-ACCESS  read-only
   STATUS      current
   DESCRIPTION
      "Path: tunnels.performance.ipsecL2tpTunnels.mibCounters.d7Performance.ifInDiscards

       64 bit unsigned wrappable counter."
   ::= {pr1645v2TvTmplPerfiMCD7PEntry 117440512}

pr1645v2TvTmplPerfiMCD7PIfInErrors OBJECT-TYPE
   SYNTAX      Counter64
   MAX-ACCESS  read-only
   STATUS      current
   DESCRIPTION
      "Path: tunnels.performance.ipsecL2tpTunnels.mibCounters.d7Performance.ifInErrors

       64 bit unsigned wrappable counter."
   ::= {pr1645v2TvTmplPerfiMCD7PEntry 134217728}

pr1645v2TvTmplPerfiMCD7PIfInUnkwn OBJECT-TYPE
   SYNTAX      Counter64
   MAX-ACCESS  read-only
   STATUS      current
   DESCRIPTION
      "Path: tunnels.performance.ipsecL2tpTunnels.mibCounters.d7Performance.ifInUnknownProtos

       64 bit unsigned wrappable counter."
   ::= {pr1645v2TvTmplPerfiMCD7PEntry 150994944}

pr1645v2TvTmplPerfiMCD7PInDropEx OBJECT-TYPE
   SYNTAX      Counter64
   MAX-ACCESS  read-only
   STATUS      current
   DESCRIPTION
      "Path: tunnels.performance.ipsecL2tpTunnels.mibCounters.d7Performance.ifInDropLevelExceeded

       64 bit unsigned wrappable counter."
   ::= {pr1645v2TvTmplPerfiMCD7PEntry 335544320}

pr1645v2TvTmplPerfiMCD7PInDropNoMac OBJECT-TYPE
   SYNTAX      Counter64
   MAX-ACCESS  read-only
   STATUS      current
   DESCRIPTION
      "Path: tunnels.performance.ipsecL2tpTunnels.mibCounters.d7Performance.fInDiscardsNoMacFit

       64 bit unsigned wrappable counter."
   ::= {pr1645v2TvTmplPerfiMCD7PEntry 301989888}

pr1645v2TvTmplPerfiMCD7PInDropNUCast OBJECT-TYPE
   SYNTAX      Counter64
   MAX-ACCESS  read-only
   STATUS      current
   DESCRIPTION
      "Path: tunnels.performance.ipsecL2tpTunnels.mibCounters.d7Performance.fInDiscardsNUCast

       64 bit unsigned wrappable counter."
   ::= {pr1645v2TvTmplPerfiMCD7PEntry 318767104}

pr1645v2TvTmplPerfiMCD7PInDropFilter OBJECT-TYPE
   SYNTAX      Counter64
   MAX-ACCESS  read-only
   STATUS      current
   DESCRIPTION
      "Path: tunnels.performance.ipsecL2tpTunnels.mibCounters.d7Performance.fInDiscardsFilter

       64 bit unsigned wrappable counter."
   ::= {pr1645v2TvTmplPerfiMCD7PEntry 385875968}

pr1645v2TvTmplPerfiMCD7PIfInBandwidth OBJECT-TYPE
   SYNTAX      Integer32
   MAX-ACCESS  read-only
   STATUS      current
   DESCRIPTION
      "Path: tunnels.performance.ipsecL2tpTunnels.mibCounters.d7Performance.ifInBandwidth

       unit name = bps
       formula = 8 * ; 8 /"
   ::= {pr1645v2TvTmplPerfiMCD7PEntry 268435456}

pr1645v2TvTmplPerfiMCD7PIfOutOctets OBJECT-TYPE
   SYNTAX      Counter64
   MAX-ACCESS  read-only
   STATUS      current
   DESCRIPTION
      "Path: tunnels.performance.ipsecL2tpTunnels.mibCounters.d7Performance.ifOutOctets

       64 bit unsigned wrappable counter."
   ::= {pr1645v2TvTmplPerfiMCD7PEntry 167772160}

pr1645v2TvTmplPerfiMCD7PIfOutUCPkts OBJECT-TYPE
   SYNTAX      Counter64
   MAX-ACCESS  read-only
   STATUS      current
   DESCRIPTION
      "Path: tunnels.performance.ipsecL2tpTunnels.mibCounters.d7Performance.ifOutUcastPkts

       64 bit unsigned wrappable counter."
   ::= {pr1645v2TvTmplPerfiMCD7PEntry 184549376}

pr1645v2TvTmplPerfiMCD7PIfOutNUCPkts OBJECT-TYPE
   SYNTAX      Counter64
   MAX-ACCESS  read-only
   STATUS      current
   DESCRIPTION
      "Path: tunnels.performance.ipsecL2tpTunnels.mibCounters.d7Performance.ifOutNUcastPkts

       64 bit unsigned wrappable counter."
   ::= {pr1645v2TvTmplPerfiMCD7PEntry 201326592}

pr1645v2TvTmplPerfiMCD7PIfOutBCPkts OBJECT-TYPE
   SYNTAX      Counter64
   MAX-ACCESS  read-only
   STATUS      current
   DESCRIPTION
      "Path: tunnels.performance.ipsecL2tpTunnels.mibCounters.d7Performance.ifOutBcastPkts

       64 bit unsigned wrappable counter."
   ::= {pr1645v2TvTmplPerfiMCD7PEntry 452984832}

pr1645v2TvTmplPerfiMCD7PIfOutMCPkts OBJECT-TYPE
   SYNTAX      Counter64
   MAX-ACCESS  read-only
   STATUS      current
   DESCRIPTION
      "Path: tunnels.performance.ipsecL2tpTunnels.mibCounters.d7Performance.ifOutMcastPkts

       64 bit unsigned wrappable counter."
   ::= {pr1645v2TvTmplPerfiMCD7PEntry 469762048}

pr1645v2TvTmplPerfiMCD7PIfOutDiscards OBJECT-TYPE
   SYNTAX      Counter64
   MAX-ACCESS  read-only
   STATUS      current
   DESCRIPTION
      "Path: tunnels.performance.ipsecL2tpTunnels.mibCounters.d7Performance.ifOutDiscards

       64 bit unsigned wrappable counter."
   ::= {pr1645v2TvTmplPerfiMCD7PEntry 218103808}

pr1645v2TvTmplPerfiMCD7PIfOutErrors OBJECT-TYPE
   SYNTAX      Counter64
   MAX-ACCESS  read-only
   STATUS      current
   DESCRIPTION
      "Path: tunnels.performance.ipsecL2tpTunnels.mibCounters.d7Performance.ifOutErrors

       64 bit unsigned wrappable counter."
   ::= {pr1645v2TvTmplPerfiMCD7PEntry 234881024}

pr1645v2TvTmplPerfiMCD7POutDropEx OBJECT-TYPE
   SYNTAX      Counter64
   MAX-ACCESS  read-only
   STATUS      current
   DESCRIPTION
      "Path: tunnels.performance.ipsecL2tpTunnels.mibCounters.d7Performance.ifOutDropLevelExceeded

       64 bit unsigned wrappable counter."
   ::= {pr1645v2TvTmplPerfiMCD7PEntry 352321536}

pr1645v2TvTmplPerfiMCD7POutDropNoArp OBJECT-TYPE
   SYNTAX      Counter64
   MAX-ACCESS  read-only
   STATUS      current
   DESCRIPTION
      "Path: tunnels.performance.ipsecL2tpTunnels.mibCounters.d7Performance.ifOutDiscardsNoArp

       64 bit unsigned wrappable counter."
   ::= {pr1645v2TvTmplPerfiMCD7PEntry 369098752}

pr1645v2TvTmplPerfiMCD7POutDropFilter OBJECT-TYPE
   SYNTAX      Counter64
   MAX-ACCESS  read-only
   STATUS      current
   DESCRIPTION
      "Path: tunnels.performance.ipsecL2tpTunnels.mibCounters.d7Performance.ifOutDiscardsFilter

       64 bit unsigned wrappable counter."
   ::= {pr1645v2TvTmplPerfiMCD7PEntry 402653184}

pr1645v2TvTmplPerfiMCD7PIfOutBandwidth OBJECT-TYPE
   SYNTAX      Integer32
   MAX-ACCESS  read-only
   STATUS      current
   DESCRIPTION
      "Path: tunnels.performance.ipsecL2tpTunnels.mibCounters.d7Performance.ifOutBandwidth

       unit name = bps
       formula = 8 * ; 8 /"
   ::= {pr1645v2TvTmplPerfiMCD7PEntry 285212672}

pr1645v2TvTmplPerfiMCD7PIfErrSec OBJECT-TYPE
   SYNTAX      Counter32
   MAX-ACCESS  read-only
   STATUS      current
   DESCRIPTION
      "Path: tunnels.performance.ipsecL2tpTunnels.mibCounters.d7Performance.ifErrSec

       32 bit unsigned wrappable counter."
   ::= {pr1645v2TvTmplPerfiMCD7PEntry 251658240}

pr1645v2TvTmplPerfiInPQs OBJECT-TYPE
   SYNTAX      SEQUENCE OF Pr1645v2TvTmplPerfiInPQsEntry
   MAX-ACCESS  not-accessible
   STATUS      current
   DESCRIPTION
      ""
   ::= {pr1645v2TvTmplPerfi 100663296}

pr1645v2TvTmplPerfiInPQsEntry OBJECT-TYPE
   SYNTAX      Pr1645v2TvTmplPerfiInPQsEntry
   MAX-ACCESS  not-accessible
   STATUS      current
   DESCRIPTION
      ""
   INDEX      { pr1645v2TvTmplPerfiTableIx,
                pr1645v2TvTmplPerfiInPQsTableIx }
   ::= {pr1645v2TvTmplPerfiInPQs 1}

Pr1645v2TvTmplPerfiInPQsEntry ::=
   SEQUENCE
      {
      pr1645v2TvTmplPerfiInPQsTableIx
         TableIndex,
      pr1645v2TvTmplPerfiInPQsName
         INTEGER,
      pr1645v2TvTmplPerfiInPQsLength
         Integer32,
      pr1645v2TvTmplPerfiInPQsOctetLength
         Integer32,
      pr1645v2TvTmplPerfiInPQsRedLength
         Integer32,
      pr1645v2TvTmplPerfiInPQsPacketsTotal
         Counter64,
      pr1645v2TvTmplPerfiInPQsPacketsDirectTx
         Counter64,
      pr1645v2TvTmplPerfiInPQsPacketsQueued
         Counter64,
      pr1645v2TvTmplPerfiInPQsPacketsDropped
         Counter64,
      pr1645v2TvTmplPerfiInPQsPacketsRedDropped
         Counter64,
      pr1645v2TvTmplPerfiInPQsPacketsCirTx
         Counter64,
      pr1645v2TvTmplPerfiInPQsPacketsEirTx
         Counter64,
      pr1645v2TvTmplPerfiInPQsPacketsViolateTx
         Counter64,
      pr1645v2TvTmplPerfiInPQsOctetsTotal
         Counter64,
      pr1645v2TvTmplPerfiInPQsOctetsDirectTx
         Counter64,
      pr1645v2TvTmplPerfiInPQsOctetsQueued
         Counter64,
      pr1645v2TvTmplPerfiInPQsOctetsDropped
         Counter64,
      pr1645v2TvTmplPerfiInPQsOctetsRedDropped
         Counter64,
      pr1645v2TvTmplPerfiInPQsOctetsCirTx
         Counter64,
      pr1645v2TvTmplPerfiInPQsOctetsEirTx
         Counter64,
      pr1645v2TvTmplPerfiInPQsOctetsViolateTx
         Counter64,
      pr1645v2TvTmplPerfiInPQsOctetsBandwidth15sec
         Integer32,
      pr1645v2TvTmplPerfiInPQsOctetsBandwidth30sec
         Integer32,
      pr1645v2TvTmplPerfiInPQsOctetsBandwidth1min
         Integer32,
      pr1645v2TvTmplPerfiInPQsOctetsBandwidth2min
         Integer32,
      pr1645v2TvTmplPerfiInPQsOctetsBandwidth5min
         Integer32
      }

pr1645v2TvTmplPerfiInPQsTableIx OBJECT-TYPE
   SYNTAX      TableIndex
   MAX-ACCESS  not-accessible
   STATUS      current
   DESCRIPTION
      ""
   ::= {pr1645v2TvTmplPerfiInPQsEntry 11}

pr1645v2TvTmplPerfiInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecL2tpTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPerfiInPQsEntry 16777216}

pr1645v2TvTmplPerfiInPQsLength OBJECT-TYPE
   SYNTAX      Integer32
   MAX-ACCESS  read-only
   STATUS      current
   DESCRIPTION
      "Path: tunnels.performance.ipsecL2tpTunnels.inPriorityQueues.length"
   ::= {pr1645v2TvTmplPerfiInPQsEntry 33554432}

pr1645v2TvTmplPerfiInPQsOctetLength OBJECT-TYPE
   SYNTAX      Integer32
   MAX-ACCESS  read-only
   STATUS      current
   DESCRIPTION
      "Path: tunnels.performance.ipsecL2tpTunnels.inPriorityQueues.octetLength"
   ::= {pr1645v2TvTmplPerfiInPQsEntry 150994944}

pr1645v2TvTmplPerfiInPQsRedLength OBJECT-TYPE
   SYNTAX      Integer32
   MAX-ACCESS  read-only
   STATUS      current
   DESCRIPTION
      "Path: tunnels.performance.ipsecL2tpTunnels.inPriorityQueues.redLength"
   ::= {pr1645v2TvTmplPerfiInPQsEntry 134217728}

pr1645v2TvTmplPerfiInPQsPacketsTotal OBJECT-TYPE
   SYNTAX      Counter64
   MAX-ACCESS  read-only
   STATUS      current
   DESCRIPTION
      "Path: tunnels.performance.ipsecL2tpTunnels.inPriorityQueues.packets.total

       64 bit unsigned wrappable counter."
   ::= {pr1645v2TvTmplPerfiInPQsEntry 50790400}

pr1645v2TvTmplPerfiInPQsPacketsDirectTx OBJECT-TYPE
   SYNTAX      Counter64
   MAX-ACCESS  read-only
   STATUS      current
   DESCRIPTION
      "Path: tunnels.performance.ipsecL2tpTunnels.inPriorityQueues.packets.directTx

       64 bit unsigned wrappable counter."
   ::= {pr1645v2TvTmplPerfiInPQsEntry 50397184}

pr1645v2TvTmplPerfiInPQsPacketsQueued OBJECT-TYPE
   SYNTAX      Counter64
   MAX-ACCESS  read-only
   STATUS      current
   DESCRIPTION
      "Path: tunnels.performance.ipsecL2tpTunnels.inPriorityQueues.packets.queued

       64 bit unsigned wrappable counter."
   ::= {pr1645v2TvTmplPerfiInPQsEntry 50462720}

pr1645v2TvTmplPerfiInPQsPacketsDropped OBJECT-TYPE
   SYNTAX      Counter64
   MAX-ACCESS  read-only
   STATUS      current
   DESCRIPTION
      "Path: tunnels.performance.ipsecL2tpTunnels.inPriorityQueues.packets.dropped

       64 bit unsigned wrappable counter."
   ::= {pr1645v2TvTmplPerfiInPQsEntry 50528256}

pr1645v2TvTmplPerfiInPQsPacketsRedDropped OBJECT-TYPE
   SYNTAX      Counter64
   MAX-ACCESS  read-only
   STATUS      current
   DESCRIPTION
      "Path: tunnels.performance.ipsecL2tpTunnels.inPriorityQueues.packets.redDropped

       64 bit unsigned wrappable counter."
   ::= {pr1645v2TvTmplPerfiInPQsEntry 50724864}

pr1645v2TvTmplPerfiInPQsPacketsCirTx OBJECT-TYPE
   SYNTAX      Counter64
   MAX-ACCESS  read-only
   STATUS      current
   DESCRIPTION
      "Path: tunnels.performance.ipsecL2tpTunnels.inPriorityQueues.packets.cirTx

       64 bit unsigned wrappable counter."
   ::= {pr1645v2TvTmplPerfiInPQsEntry 50593792}

pr1645v2TvTmplPerfiInPQsPacketsEirTx OBJECT-TYPE
   SYNTAX      Counter64
   MAX-ACCESS  read-only
   STATUS      current
   DESCRIPTION
      "Path: tunnels.performance.ipsecL2tpTunnels.inPriorityQueues.packets.eirTx

       64 bit unsigned wrappable counter."
   ::= {pr1645v2TvTmplPerfiInPQsEntry 50659328}

pr1645v2TvTmplPerfiInPQsPacketsViolateTx OBJECT-TYPE
   SYNTAX      Counter64
   MAX-ACCESS  read-only
   STATUS      current
   DESCRIPTION
      "Path: tunnels.performance.ipsecL2tpTunnels.inPriorityQueues.packets.violateTx

       64 bit unsigned wrappable counter."
   ::= {pr1645v2TvTmplPerfiInPQsEntry 50855936}

pr1645v2TvTmplPerfiInPQsOctetsTotal OBJECT-TYPE
   SYNTAX      Counter64
   MAX-ACCESS  read-only
   STATUS      current
   DESCRIPTION
      "Path: tunnels.performance.ipsecL2tpTunnels.inPriorityQueues.octets.total

       64 bit unsigned wrappable counter."
   ::= {pr1645v2TvTmplPerfiInPQsEntry 67567616}

pr1645v2TvTmplPerfiInPQsOctetsDirectTx OBJECT-TYPE
   SYNTAX      Counter64
   MAX-ACCESS  read-only
   STATUS      current
   DESCRIPTION
      "Path: tunnels.performance.ipsecL2tpTunnels.inPriorityQueues.octets.directTx

       64 bit unsigned wrappable counter."
   ::= {pr1645v2TvTmplPerfiInPQsEntry 67174400}

pr1645v2TvTmplPerfiInPQsOctetsQueued OBJECT-TYPE
   SYNTAX      Counter64
   MAX-ACCESS  read-only
   STATUS      current
   DESCRIPTION
      "Path: tunnels.performance.ipsecL2tpTunnels.inPriorityQueues.octets.queued

       64 bit unsigned wrappable counter."
   ::= {pr1645v2TvTmplPerfiInPQsEntry 67239936}

pr1645v2TvTmplPerfiInPQsOctetsDropped OBJECT-TYPE
   SYNTAX      Counter64
   MAX-ACCESS  read-only
   STATUS      current
   DESCRIPTION
      "Path: tunnels.performance.ipsecL2tpTunnels.inPriorityQueues.octets.dropped

       64 bit unsigned wrappable counter."
   ::= {pr1645v2TvTmplPerfiInPQsEntry 67305472}

pr1645v2TvTmplPerfiInPQsOctetsRedDropped OBJECT-TYPE
   SYNTAX      Counter64
   MAX-ACCESS  read-only
   STATUS      current
   DESCRIPTION
      "Path: tunnels.performance.ipsecL2tpTunnels.inPriorityQueues.octets.redDropped

       64 bit unsigned wrappable counter."
   ::= {pr1645v2TvTmplPerfiInPQsEntry 67502080}

pr1645v2TvTmplPerfiInPQsOctetsCirTx OBJECT-TYPE
   SYNTAX      Counter64
   MAX-ACCESS  read-only
   STATUS      current
   DESCRIPTION
      "Path: tunnels.performance.ipsecL2tpTunnels.inPriorityQueues.octets.cirTx

       64 bit unsigned wrappable counter."
   ::= {pr1645v2TvTmplPerfiInPQsEntry 67371008}

pr1645v2TvTmplPerfiInPQsOctetsEirTx OBJECT-TYPE
   SYNTAX      Counter64
   MAX-ACCESS  read-only
   STATUS      current
   DESCRIPTION
      "Path: tunnels.performance.ipsecL2tpTunnels.inPriorityQueues.octets.eirTx

       64 bit unsigned wrappable counter."
   ::= {pr1645v2TvTmplPerfiInPQsEntry 67436544}

pr1645v2TvTmplPerfiInPQsOctetsViolateTx OBJECT-TYPE
   SYNTAX      Counter64
   MAX-ACCESS  read-only
   STATUS      current
   DESCRIPTION
      "Path: tunnels.performance.ipsecL2tpTunnels.inPriorityQueues.octets.violateTx

       64 bit unsigned wrappable counter."
   ::= {pr1645v2TvTmplPerfiInPQsEntry 67633152}

pr1645v2TvTmplPerfiInPQsOctetsBandwidth15sec OBJECT-TYPE
   SYNTAX      Integer32
   MAX-ACCESS  read-only
   STATUS      current
   DESCRIPTION
      "Path: tunnels.performance.ipsecL2tpTunnels.inPriorityQueues.octets.bandwidth.15sec

       unit name = bps
       formula = 8 * ; 8 /"
   ::= {pr1645v2TvTmplPerfiInPQsEntry 70386944}

pr1645v2TvTmplPerfiInPQsOctetsBandwidth30sec OBJECT-TYPE
   SYNTAX      Integer32
   MAX-ACCESS  read-only
   STATUS      current
   DESCRIPTION
      "Path: tunnels.performance.ipsecL2tpTunnels.inPriorityQueues.octets.bandwidth.30sec

       unit name = bps
       formula = 8 * ; 8 /"
   ::= {pr1645v2TvTmplPerfiInPQsEntry 70388224}

pr1645v2TvTmplPerfiInPQsOctetsBandwidth1min OBJECT-TYPE
   SYNTAX      Integer32
   MAX-ACCESS  read-only
   STATUS      current
   DESCRIPTION
      "Path: tunnels.performance.ipsecL2tpTunnels.inPriorityQueues.octets.bandwidth.1min

       unit name = bps
       formula = 8 * ; 8 /"
   ::= {pr1645v2TvTmplPerfiInPQsEntry 70390784}

pr1645v2TvTmplPerfiInPQsOctetsBandwidth2min OBJECT-TYPE
   SYNTAX      Integer32
   MAX-ACCESS  read-only
   STATUS      current
   DESCRIPTION
      "Path: tunnels.performance.ipsecL2tpTunnels.inPriorityQueues.octets.bandwidth.2min

       unit name = bps
       formula = 8 * ; 8 /"
   ::= {pr1645v2TvTmplPerfiInPQsEntry 70395904}

pr1645v2TvTmplPerfiInPQsOctetsBandwidth5min OBJECT-TYPE
   SYNTAX      Integer32
   MAX-ACCESS  read-only
   STATUS      current
   DESCRIPTION
      "Path: tunnels.performance.ipsecL2tpTunnels.inPriorityQueues.octets.bandwidth.5min

       unit name = bps
       formula = 8 * ; 8 /"
   ::= {pr1645v2TvTmplPerfiInPQsEntry 70411264}

pr1645v2TvTmplPerfiInPQsH2Performance OBJECT-TYPE
   SYNTAX      SEQUENCE OF Pr1645v2TvTmplPerfiInPQsH2PerformanceEntry
   MAX-ACCESS  not-accessible
   STATUS      current
   DESCRIPTION
      ""
   ::= {pr1645v2TvTmplPerfi 100990976}

pr1645v2TvTmplPerfiInPQsH2PerformanceEntry OBJECT-TYPE
   SYNTAX      Pr1645v2TvTmplPerfiInPQsH2PerformanceEntry
   MAX-ACCESS  not-accessible
   STATUS      current
   DESCRIPTION
      ""
   INDEX      { pr1645v2TvTmplPerfiTableIx,
                pr1645v2TvTmplPerfiInPQsTableIx,
                pr1645v2TvTmplPerfiInPQsH2PerformanceTableIx }
   ::= {pr1645v2TvTmplPerfiInPQsH2Performance 1}

Pr1645v2TvTmplPerfiInPQsH2PerformanceEntry ::=
   SEQUENCE
      {
      pr1645v2TvTmplPerfiInPQsH2PerformanceTableIx
         TableIndex,
      pr1645v2TvTmplPerfiInPQsH2PerformanceSysUpTime
         TimeTicks,
      pr1645v2TvTmplPerfiInPQsH2PerformanceTotPkts
         Counter64,
      pr1645v2TvTmplPerfiInPQsH2PerformanceDirTxPkts
         Counter64,
      pr1645v2TvTmplPerfiInPQsH2PerformanceQdPkts
         Counter64,
      pr1645v2TvTmplPerfiInPQsH2PerformanceDropPkts
         Counter64,
      pr1645v2TvTmplPerfiInPQsH2PerformanceRDropPkts
         Counter64,
      pr1645v2TvTmplPerfiInPQsH2PerformanceCirTxPkts
         Counter64,
      pr1645v2TvTmplPerfiInPQsH2PerformanceEirTxPkts
         Counter64,
      pr1645v2TvTmplPerfiInPQsH2PerformanceViolTxPkts
         Counter64,
      pr1645v2TvTmplPerfiInPQsH2PerformanceTotOcts
         Counter64,
      pr1645v2TvTmplPerfiInPQsH2PerformanceDirTxOcts
         Counter64,
      pr1645v2TvTmplPerfiInPQsH2PerformanceQdOcts
         Counter64,
      pr1645v2TvTmplPerfiInPQsH2PerformanceDropOcts
         Counter64,
      pr1645v2TvTmplPerfiInPQsH2PerformanceRDropOcts
         Counter64,
      pr1645v2TvTmplPerfiInPQsH2PerformanceCirTxOcts
         Counter64,
      pr1645v2TvTmplPerfiInPQsH2PerformanceEirTxOcts
         Counter64,
      pr1645v2TvTmplPerfiInPQsH2PerformanceViolTxOcts
         Counter64,
      pr1645v2TvTmplPerfiInPQsH2PerformanceBandwidth
         Integer32
      }

pr1645v2TvTmplPerfiInPQsH2PerformanceTableIx OBJECT-TYPE
   SYNTAX      TableIndex
   MAX-ACCESS  not-accessible
   STATUS      current
   DESCRIPTION
      ""
   ::= {pr1645v2TvTmplPerfiInPQsH2PerformanceEntry 11}

pr1645v2TvTmplPerfiInPQsH2PerformanceSysUpTime OBJECT-TYPE
   SYNTAX      TimeTicks
   MAX-ACCESS  read-only
   STATUS      current
   DESCRIPTION
      "Path: tunnels.performance.ipsecL2tpTunnels.inPriorityQueues.h2Performance.sysUpTime

       Time in centi-second."
   ::= {pr1645v2TvTmplPerfiInPQsH2PerformanceEntry 16777216}

pr1645v2TvTmplPerfiInPQsH2PerformanceTotPkts OBJECT-TYPE
   SYNTAX      Counter64
   MAX-ACCESS  read-only
   STATUS      current
   DESCRIPTION
      "Path: tunnels.performance.ipsecL2tpTunnels.inPriorityQueues.h2Performance.totalPkts

       64 bit unsigned wrappable counter."
   ::= {pr1645v2TvTmplPerfiInPQsH2PerformanceEntry 234881024}

pr1645v2TvTmplPerfiInPQsH2PerformanceDirTxPkts OBJECT-TYPE
   SYNTAX      Counter64
   MAX-ACCESS  read-only
   STATUS      current
   DESCRIPTION
      "Path: tunnels.performance.ipsecL2tpTunnels.inPriorityQueues.h2Performance.directTxPkts

       64 bit unsigned wrappable counter."
   ::= {pr1645v2TvTmplPerfiInPQsH2PerformanceEntry 33554432}

pr1645v2TvTmplPerfiInPQsH2PerformanceQdPkts OBJECT-TYPE
   SYNTAX      Counter64
   MAX-ACCESS  read-only
   STATUS      current
   DESCRIPTION
      "Path: tunnels.performance.ipsecL2tpTunnels.inPriorityQueues.h2Performance.queuedPkts

       64 bit unsigned wrappable counter."
   ::= {pr1645v2TvTmplPerfiInPQsH2PerformanceEntry 50331648}

pr1645v2TvTmplPerfiInPQsH2PerformanceDropPkts OBJECT-TYPE
   SYNTAX      Counter64
   MAX-ACCESS  read-only
   STATUS      current
   DESCRIPTION
      "Path: tunnels.performance.ipsecL2tpTunnels.inPriorityQueues.h2Performance.droppedPkts

       64 bit unsigned wrappable counter."
   ::= {pr1645v2TvTmplPerfiInPQsH2PerformanceEntry 67108864}

pr1645v2TvTmplPerfiInPQsH2PerformanceRDropPkts OBJECT-TYPE
   SYNTAX      Counter64
   MAX-ACCESS  read-only
   STATUS      current
   DESCRIPTION
      "Path: tunnels.performance.ipsecL2tpTunnels.inPriorityQueues.h2Performance.redDroppedPkts

       64 bit unsigned wrappable counter."
   ::= {pr1645v2TvTmplPerfiInPQsH2PerformanceEntry 201326592}

pr1645v2TvTmplPerfiInPQsH2PerformanceCirTxPkts OBJECT-TYPE
   SYNTAX      Counter64
   MAX-ACCESS  read-only
   STATUS      current
   DESCRIPTION
      "Path: tunnels.performance.ipsecL2tpTunnels.inPriorityQueues.h2Performance.cirTxPkts

       64 bit unsigned wrappable counter."
   ::= {pr1645v2TvTmplPerfiInPQsH2PerformanceEntry 83886080}

pr1645v2TvTmplPerfiInPQsH2PerformanceEirTxPkts OBJECT-TYPE
   SYNTAX      Counter64
   MAX-ACCESS  read-only
   STATUS      current
   DESCRIPTION
      "Path: tunnels.performance.ipsecL2tpTunnels.inPriorityQueues.h2Performance.eirTxPkts

       64 bit unsigned wrappable counter."
   ::= {pr1645v2TvTmplPerfiInPQsH2PerformanceEntry 100663296}

pr1645v2TvTmplPerfiInPQsH2PerformanceViolTxPkts OBJECT-TYPE
   SYNTAX      Counter64
   MAX-ACCESS  read-only
   STATUS      current
   DESCRIPTION
      "Path: tunnels.performance.ipsecL2tpTunnels.inPriorityQueues.h2Performance.violateTxPkts

       64 bit unsigned wrappable counter."
   ::= {pr1645v2TvTmplPerfiInPQsH2PerformanceEntry 301989888}

pr1645v2TvTmplPerfiInPQsH2PerformanceTotOcts OBJECT-TYPE
   SYNTAX      Counter64
   MAX-ACCESS  read-only
   STATUS      current
   DESCRIPTION
      "Path: tunnels.performance.ipsecL2tpTunnels.inPriorityQueues.h2Performance.totalOctets

       64 bit unsigned wrappable counter."
   ::= {pr1645v2TvTmplPerfiInPQsH2PerformanceEntry 251658240}

pr1645v2TvTmplPerfiInPQsH2PerformanceDirTxOcts OBJECT-TYPE
   SYNTAX      Counter64
   MAX-ACCESS  read-only
   STATUS      current
   DESCRIPTION
      "Path: tunnels.performance.ipsecL2tpTunnels.inPriorityQueues.h2Performance.directTxOctets

       64 bit unsigned wrappable counter."
   ::= {pr1645v2TvTmplPerfiInPQsH2PerformanceEntry 117440512}

pr1645v2TvTmplPerfiInPQsH2PerformanceQdOcts OBJECT-TYPE
   SYNTAX      Counter64
   MAX-ACCESS  read-only
   STATUS      current
   DESCRIPTION
      "Path: tunnels.performance.ipsecL2tpTunnels.inPriorityQueues.h2Performance.queuedOctets

       64 bit unsigned wrappable counter."
   ::= {pr1645v2TvTmplPerfiInPQsH2PerformanceEntry 134217728}

pr1645v2TvTmplPerfiInPQsH2PerformanceDropOcts OBJECT-TYPE
   SYNTAX      Counter64
   MAX-ACCESS  read-only
   STATUS      current
   DESCRIPTION
      "Path: tunnels.performance.ipsecL2tpTunnels.inPriorityQueues.h2Performance.droppedOctets

       64 bit unsigned wrappable counter."
   ::= {pr1645v2TvTmplPerfiInPQsH2PerformanceEntry 150994944}

pr1645v2TvTmplPerfiInPQsH2PerformanceRDropOcts OBJECT-TYPE
   SYNTAX      Counter64
   MAX-ACCESS  read-only
   STATUS      current
   DESCRIPTION
      "Path: tunnels.performance.ipsecL2tpTunnels.inPriorityQueues.h2Performance.redDroppedOctets

       64 bit unsigned wrappable counter."
   ::= {pr1645v2TvTmplPerfiInPQsH2PerformanceEntry 218103808}

pr1645v2TvTmplPerfiInPQsH2PerformanceCirTxOcts OBJECT-TYPE
   SYNTAX      Counter64
   MAX-ACCESS  read-only
   STATUS      current
   DESCRIPTION
      "Path: tunnels.performance.ipsecL2tpTunnels.inPriorityQueues.h2Performance.cirTxOctets

       64 bit unsigned wrappable counter."
   ::= {pr1645v2TvTmplPerfiInPQsH2PerformanceEntry 167772160}

pr1645v2TvTmplPerfiInPQsH2PerformanceEirTxOcts OBJECT-TYPE
   SYNTAX      Counter64
   MAX-ACCESS  read-only
   STATUS      current
   DESCRIPTION
      "Path: tunnels.performance.ipsecL2tpTunnels.inPriorityQueues.h2Performance.eirTxOctets

       64 bit unsigned wrappable counter."
   ::= {pr1645v2TvTmplPerfiInPQsH2PerformanceEntry 184549376}

pr1645v2TvTmplPerfiInPQsH2PerformanceViolTxOcts OBJECT-TYPE
   SYNTAX      Counter64
   MAX-ACCESS  read-only
   STATUS      current
   DESCRIPTION
      "Path: tunnels.performance.ipsecL2tpTunnels.inPriorityQueues.h2Performance.violateTxOctets

       64 bit unsigned wrappable counter."
   ::= {pr1645v2TvTmplPerfiInPQsH2PerformanceEntry 318767104}

pr1645v2TvTmplPerfiInPQsH2PerformanceBandwidth OBJECT-TYPE
   SYNTAX      Integer32
   MAX-ACCESS  read-only
   STATUS      current
   DESCRIPTION
      "Path: tunnels.performance.ipsecL2tpTunnels.inPriorityQueues.h2Performance.bandwidth

       unit name = bps
       formula = 8 * ; 8 /"
   ::= {pr1645v2TvTmplPerfiInPQsH2PerformanceEntry 268435456}

pr1645v2TvTmplPerfiInPQsH24Performance OBJECT-TYPE
   SYNTAX      SEQUENCE OF Pr1645v2TvTmplPerfiInPQsH24PerformanceEntry
   MAX-ACCESS  not-accessible
   STATUS      current
   DESCRIPTION
      ""
   ::= {pr1645v2TvTmplPerfi 101056512}

pr1645v2TvTmplPerfiInPQsH24PerformanceEntry OBJECT-TYPE
   SYNTAX      Pr1645v2TvTmplPerfiInPQsH24PerformanceEntry
   MAX-ACCESS  not-accessible
   STATUS      current
   DESCRIPTION
      ""
   INDEX      { pr1645v2TvTmplPerfiTableIx,
                pr1645v2TvTmplPerfiInPQsTableIx,
                pr1645v2TvTmplPerfiInPQsH24PerformanceTableIx }
   ::= {pr1645v2TvTmplPerfiInPQsH24Performance 1}

Pr1645v2TvTmplPerfiInPQsH24PerformanceEntry ::=
   SEQUENCE
      {
      pr1645v2TvTmplPerfiInPQsH24PerformanceTableIx
         TableIndex,
      pr1645v2TvTmplPerfiInPQsH24PerformanceSysUpTime
         TimeTicks,
      pr1645v2TvTmplPerfiInPQsH24PerformanceTotPkts
         Counter64,
      pr1645v2TvTmplPerfiInPQsH24PerformanceDirTxPkts
         Counter64,
      pr1645v2TvTmplPerfiInPQsH24PerformanceQdPkts
         Counter64,
      pr1645v2TvTmplPerfiInPQsH24PerformanceDropPkts
         Counter64,
      pr1645v2TvTmplPerfiInPQsH24PerformanceRDropPkts
         Counter64,
      pr1645v2TvTmplPerfiInPQsH24PerformanceCirTxPkts
         Counter64,
      pr1645v2TvTmplPerfiInPQsH24PerformanceEirTxPkts
         Counter64,
      pr1645v2TvTmplPerfiInPQsH24PerformanceViolTxPkts
         Counter64,
      pr1645v2TvTmplPerfiInPQsH24PerformanceTotOcts
         Counter64,
      pr1645v2TvTmplPerfiInPQsH24PerformanceDirTxOcts
         Counter64,
      pr1645v2TvTmplPerfiInPQsH24PerformanceQdOcts
         Counter64,
      pr1645v2TvTmplPerfiInPQsH24PerformanceDropOcts
         Counter64,
      pr1645v2TvTmplPerfiInPQsH24PerformanceRDropOcts
         Counter64,
      pr1645v2TvTmplPerfiInPQsH24PerformanceCirTxOcts
         Counter64,
      pr1645v2TvTmplPerfiInPQsH24PerformanceEirTxOcts
         Counter64,
      pr1645v2TvTmplPerfiInPQsH24PerformanceViolTxOcts
         Counter64,
      pr1645v2TvTmplPerfiInPQsH24PerformanceBandwidth
         Integer32
      }

pr1645v2TvTmplPerfiInPQsH24PerformanceTableIx OBJECT-TYPE
   SYNTAX      TableIndex
   MAX-ACCESS  not-accessible
   STATUS      current
   DESCRIPTION
      ""
   ::= {pr1645v2TvTmplPerfiInPQsH24PerformanceEntry 11}

pr1645v2TvTmplPerfiInPQsH24PerformanceSysUpTime OBJECT-TYPE
   SYNTAX      TimeTicks
   MAX-ACCESS  read-only
   STATUS      current
   DESCRIPTION
      "Path: tunnels.performance.ipsecL2tpTunnels.inPriorityQueues.h24Performance.sysUpTime

       Time in centi-second."
   ::= {pr1645v2TvTmplPerfiInPQsH24PerformanceEntry 16777216}

pr1645v2TvTmplPerfiInPQsH24PerformanceTotPkts OBJECT-TYPE
   SYNTAX      Counter64
   MAX-ACCESS  read-only
   STATUS      current
   DESCRIPTION
      "Path: tunnels.performance.ipsecL2tpTunnels.inPriorityQueues.h24Performance.totalPkts

       64 bit unsigned wrappable counter."
   ::= {pr1645v2TvTmplPerfiInPQsH24PerformanceEntry 234881024}

pr1645v2TvTmplPerfiInPQsH24PerformanceDirTxPkts OBJECT-TYPE
   SYNTAX      Counter64
   MAX-ACCESS  read-only
   STATUS      current
   DESCRIPTION
      "Path: tunnels.performance.ipsecL2tpTunnels.inPriorityQueues.h24Performance.directTxPkts

       64 bit unsigned wrappable counter."
   ::= {pr1645v2TvTmplPerfiInPQsH24PerformanceEntry 33554432}

pr1645v2TvTmplPerfiInPQsH24PerformanceQdPkts OBJECT-TYPE
   SYNTAX      Counter64
   MAX-ACCESS  read-only
   STATUS      current
   DESCRIPTION
      "Path: tunnels.performance.ipsecL2tpTunnels.inPriorityQueues.h24Performance.queuedPkts

       64 bit unsigned wrappable counter."
   ::= {pr1645v2TvTmplPerfiInPQsH24PerformanceEntry 50331648}

pr1645v2TvTmplPerfiInPQsH24PerformanceDropPkts OBJECT-TYPE
   SYNTAX      Counter64
   MAX-ACCESS  read-only
   STATUS      current
   DESCRIPTION
      "Path: tunnels.performance.ipsecL2tpTunnels.inPriorityQueues.h24Performance.droppedPkts

       64 bit unsigned wrappable counter."
   ::= {pr1645v2TvTmplPerfiInPQsH24PerformanceEntry 67108864}

pr1645v2TvTmplPerfiInPQsH24PerformanceRDropPkts OBJECT-TYPE
   SYNTAX      Counter64
   MAX-ACCESS  read-only
   STATUS      current
   DESCRIPTION
      "Path: tunnels.performance.ipsecL2tpTunnels.inPriorityQueues.h24Performance.redDroppedPkts

       64 bit unsigned wrappable counter."
   ::= {pr1645v2TvTmplPerfiInPQsH24PerformanceEntry 201326592}

pr1645v2TvTmplPerfiInPQsH24PerformanceCirTxPkts OBJECT-TYPE
   SYNTAX      Counter64
   MAX-ACCESS  read-only
   STATUS      current
   DESCRIPTION
      "Path: tunnels.performance.ipsecL2tpTunnels.inPriorityQueues.h24Performance.cirTxPkts

       64 bit unsigned wrappable counter."
   ::= {pr1645v2TvTmplPerfiInPQsH24PerformanceEntry 83886080}

pr1645v2TvTmplPerfiInPQsH24PerformanceEirTxPkts OBJECT-TYPE
   SYNTAX      Counter64
   MAX-ACCESS  read-only
   STATUS      current
   DESCRIPTION
      "Path: tunnels.performance.ipsecL2tpTunnels.inPriorityQueues.h24Performance.eirTxPkts

       64 bit unsigned wrappable counter."
   ::= {pr1645v2TvTmplPerfiInPQsH24PerformanceEntry 100663296}

pr1645v2TvTmplPerfiInPQsH24PerformanceViolTxPkts OBJECT-TYPE
   SYNTAX      Counter64
   MAX-ACCESS  read-only
   STATUS      current
   DESCRIPTION
      "Path: tunnels.performance.ipsecL2tpTunnels.inPriorityQueues.h24Performance.violateTxPkts

       64 bit unsigned wrappable counter."
   ::= {pr1645v2TvTmplPerfiInPQsH24PerformanceEntry 301989888}

pr1645v2TvTmplPerfiInPQsH24PerformanceTotOcts OBJECT-TYPE
   SYNTAX      Counter64
   MAX-ACCESS  read-only
   STATUS      current
   DESCRIPTION
      "Path: tunnels.performance.ipsecL2tpTunnels.inPriorityQueues.h24Performance.totalOctets

       64 bit unsigned wrappable counter."
   ::= {pr1645v2TvTmplPerfiInPQsH24PerformanceEntry 251658240}

pr1645v2TvTmplPerfiInPQsH24PerformanceDirTxOcts OBJECT-TYPE
   SYNTAX      Counter64
   MAX-ACCESS  read-only
   STATUS      current
   DESCRIPTION
      "Path: tunnels.performance.ipsecL2tpTunnels.inPriorityQueues.h24Performance.directTxOctets

       64 bit unsigned wrappable counter."
   ::= {pr1645v2TvTmplPerfiInPQsH24PerformanceEntry 117440512}

pr1645v2TvTmplPerfiInPQsH24PerformanceQdOcts OBJECT-TYPE
   SYNTAX      Counter64
   MAX-ACCESS  read-only
   STATUS      current
   DESCRIPTION
      "Path: tunnels.performance.ipsecL2tpTunnels.inPriorityQueues.h24Performance.queuedOctets

       64 bit unsigned wrappable counter."
   ::= {pr1645v2TvTmplPerfiInPQsH24PerformanceEntry 134217728}

pr1645v2TvTmplPerfiInPQsH24PerformanceDropOcts OBJECT-TYPE
   SYNTAX      Counter64
   MAX-ACCESS  read-only
   STATUS      current
   DESCRIPTION
      "Path: tunnels.performance.ipsecL2tpTunnels.inPriorityQueues.h24Performance.droppedOctets

       64 bit unsigned wrappable counter."
   ::= {pr1645v2TvTmplPerfiInPQsH24PerformanceEntry 150994944}

pr1645v2TvTmplPerfiInPQsH24PerformanceRDropOcts OBJECT-TYPE
   SYNTAX      Counter64
   MAX-ACCESS  read-only
   STATUS      current
   DESCRIPTION
      "Path: tunnels.performance.ipsecL2tpTunnels.inPriorityQueues.h24Performance.redDroppedOctets

       64 bit unsigned wrappable counter."
   ::= {pr1645v2TvTmplPerfiInPQsH24PerformanceEntry 218103808}

pr1645v2TvTmplPerfiInPQsH24PerformanceCirTxOcts OBJECT-TYPE
   SYNTAX      Counter64
   MAX-ACCESS  read-only
   STATUS      current
   DESCRIPTION
      "Path: tunnels.performance.ipsecL2tpTunnels.inPriorityQueues.h24Performance.cirTxOctets

       64 bit unsigned wrappable counter."
   ::= {pr1645v2TvTmplPerfiInPQsH24PerformanceEntry 167772160}

pr1645v2TvTmplPerfiInPQsH24PerformanceEirTxOcts OBJECT-TYPE
   SYNTAX      Counter64
   MAX-ACCESS  read-only
   STATUS      current
   DESCRIPTION
      "Path: tunnels.performance.ipsecL2tpTunnels.inPriorityQueues.h24Performance.eirTxOctets

       64 bit unsigned wrappable counter."
   ::= {pr1645v2TvTmplPerfiInPQsH24PerformanceEntry 184549376}

pr1645v2TvTmplPerfiInPQsH24PerformanceViolTxOcts OBJECT-TYPE
   SYNTAX      Counter64
   MAX-ACCESS  read-only
   STATUS      current
   DESCRIPTION
      "Path: tunnels.performance.ipsecL2tpTunnels.inPriorityQueues.h24Performance.violateTxOctets

       64 bit unsigned wrappable counter."
   ::= {pr1645v2TvTmplPerfiInPQsH24PerformanceEntry 318767104}

pr1645v2TvTmplPerfiInPQsH24PerformanceBandwidth OBJECT-TYPE
   SYNTAX      Integer32
   MAX-ACCESS  read-only
   STATUS      current
   DESCRIPTION
      "Path: tunnels.performance.ipsecL2tpTunnels.inPriorityQueues.h24Performance.bandwidth

       unit name = bps
       formula = 8 * ; 8 /"
   ::= {pr1645v2TvTmplPerfiInPQsH24PerformanceEntry 268435456}

pr1645v2TvTmplPerfiInPQsD7Performance OBJECT-TYPE
   SYNTAX      SEQUENCE OF Pr1645v2TvTmplPerfiInPQsD7PerformanceEntry
   MAX-ACCESS  not-accessible
   STATUS      current
   DESCRIPTION
      ""
   ::= {pr1645v2TvTmplPerfi 101122048}

pr1645v2TvTmplPerfiInPQsD7PerformanceEntry OBJECT-TYPE
   SYNTAX      Pr1645v2TvTmplPerfiInPQsD7PerformanceEntry
   MAX-ACCESS  not-accessible
   STATUS      current
   DESCRIPTION
      ""
   INDEX      { pr1645v2TvTmplPerfiTableIx,
                pr1645v2TvTmplPerfiInPQsTableIx,
                pr1645v2TvTmplPerfiInPQsD7PerformanceTableIx }
   ::= {pr1645v2TvTmplPerfiInPQsD7Performance 1}

Pr1645v2TvTmplPerfiInPQsD7PerformanceEntry ::=
   SEQUENCE
      {
      pr1645v2TvTmplPerfiInPQsD7PerformanceTableIx
         TableIndex,
      pr1645v2TvTmplPerfiInPQsD7PerformanceSysUpTime
         TimeTicks,
      pr1645v2TvTmplPerfiInPQsD7PerformanceTotPkts
         Counter64,
      pr1645v2TvTmplPerfiInPQsD7PerformanceDirTxPkts
         Counter64,
      pr1645v2TvTmplPerfiInPQsD7PerformanceQdPkts
         Counter64,
      pr1645v2TvTmplPerfiInPQsD7PerformanceDropPkts
         Counter64,
      pr1645v2TvTmplPerfiInPQsD7PerformanceRDropPkts
         Counter64,
      pr1645v2TvTmplPerfiInPQsD7PerformanceCirTxPkts
         Counter64,
      pr1645v2TvTmplPerfiInPQsD7PerformanceEirTxPkts
         Counter64,
      pr1645v2TvTmplPerfiInPQsD7PerformanceViolTxPkts
         Counter64,
      pr1645v2TvTmplPerfiInPQsD7PerformanceTotOcts
         Counter64,
      pr1645v2TvTmplPerfiInPQsD7PerformanceDirTxOcts
         Counter64,
      pr1645v2TvTmplPerfiInPQsD7PerformanceQdOcts
         Counter64,
      pr1645v2TvTmplPerfiInPQsD7PerformanceDropOcts
         Counter64,
      pr1645v2TvTmplPerfiInPQsD7PerformanceRDropOcts
         Counter64,
      pr1645v2TvTmplPerfiInPQsD7PerformanceCirTxOcts
         Counter64,
      pr1645v2TvTmplPerfiInPQsD7PerformanceEirTxOcts
         Counter64,
      pr1645v2TvTmplPerfiInPQsD7PerformanceViolTxOcts
         Counter64,
      pr1645v2TvTmplPerfiInPQsD7PerformanceBandwidth
         Integer32
      }

pr1645v2TvTmplPerfiInPQsD7PerformanceTableIx OBJECT-TYPE
   SYNTAX      TableIndex
   MAX-ACCESS  not-accessible
   STATUS      current
   DESCRIPTION
      ""
   ::= {pr1645v2TvTmplPerfiInPQsD7PerformanceEntry 11}

pr1645v2TvTmplPerfiInPQsD7PerformanceSysUpTime OBJECT-TYPE
   SYNTAX      TimeTicks
   MAX-ACCESS  read-only
   STATUS      current
   DESCRIPTION
      "Path: tunnels.performance.ipsecL2tpTunnels.inPriorityQueues.d7Performance.sysUpTime

       Time in centi-second."
   ::= {pr1645v2TvTmplPerfiInPQsD7PerformanceEntry 16777216}

pr1645v2TvTmplPerfiInPQsD7PerformanceTotPkts OBJECT-TYPE
   SYNTAX      Counter64
   MAX-ACCESS  read-only
   STATUS      current
   DESCRIPTION
      "Path: tunnels.performance.ipsecL2tpTunnels.inPriorityQueues.d7Performance.totalPkts

       64 bit unsigned wrappable counter."
   ::= {pr1645v2TvTmplPerfiInPQsD7PerformanceEntry 234881024}

pr1645v2TvTmplPerfiInPQsD7PerformanceDirTxPkts OBJECT-TYPE
   SYNTAX      Counter64
   MAX-ACCESS  read-only
   STATUS      current
   DESCRIPTION
      "Path: tunnels.performance.ipsecL2tpTunnels.inPriorityQueues.d7Performance.directTxPkts

       64 bit unsigned wrappable counter."
   ::= {pr1645v2TvTmplPerfiInPQsD7PerformanceEntry 33554432}

pr1645v2TvTmplPerfiInPQsD7PerformanceQdPkts OBJECT-TYPE
   SYNTAX      Counter64
   MAX-ACCESS  read-only
   STATUS      current
   DESCRIPTION
      "Path: tunnels.performance.ipsecL2tpTunnels.inPriorityQueues.d7Performance.queuedPkts

       64 bit unsigned wrappable counter."
   ::= {pr1645v2TvTmplPerfiInPQsD7PerformanceEntry 50331648}

pr1645v2TvTmplPerfiInPQsD7PerformanceDropPkts OBJECT-TYPE
   SYNTAX      Counter64
   MAX-ACCESS  read-only
   STATUS      current
   DESCRIPTION
      "Path: tunnels.performance.ipsecL2tpTunnels.inPriorityQueues.d7Performance.droppedPkts

       64 bit unsigned wrappable counter."
   ::= {pr1645v2TvTmplPerfiInPQsD7PerformanceEntry 67108864}

pr1645v2TvTmplPerfiInPQsD7PerformanceRDropPkts OBJECT-TYPE
   SYNTAX      Counter64
   MAX-ACCESS  read-only
   STATUS      current
   DESCRIPTION
      "Path: tunnels.performance.ipsecL2tpTunnels.inPriorityQueues.d7Performance.redDroppedPkts

       64 bit unsigned wrappable counter."
   ::= {pr1645v2TvTmplPerfiInPQsD7PerformanceEntry 201326592}

pr1645v2TvTmplPerfiInPQsD7PerformanceCirTxPkts OBJECT-TYPE
   SYNTAX      Counter64
   MAX-ACCESS  read-only
   STATUS      current
   DESCRIPTION
      "Path: tunnels.performance.ipsecL2tpTunnels.inPriorityQueues.d7Performance.cirTxPkts

       64 bit unsigned wrappable counter."
   ::= {pr1645v2TvTmplPerfiInPQsD7PerformanceEntry 83886080}

pr1645v2TvTmplPerfiInPQsD7PerformanceEirTxPkts OBJECT-TYPE
   SYNTAX      Counter64
   MAX-ACCESS  read-only
   STATUS      current
   DESCRIPTION
      "Path: tunnels.performance.ipsecL2tpTunnels.inPriorityQueues.d7Performance.eirTxPkts

       64 bit unsigned wrappable counter."
   ::= {pr1645v2TvTmplPerfiInPQsD7PerformanceEntry 100663296}

pr1645v2TvTmplPerfiInPQsD7PerformanceViolTxPkts OBJECT-TYPE
   SYNTAX      Counter64
   MAX-ACCESS  read-only
   STATUS      current
   DESCRIPTION
      "Path: tunnels.performance.ipsecL2tpTunnels.inPriorityQueues.d7Performance.violateTxPkts

       64 bit unsigned wrappable counter."
   ::= {pr1645v2TvTmplPerfiInPQsD7PerformanceEntry 301989888}

pr1645v2TvTmplPerfiInPQsD7PerformanceTotOcts OBJECT-TYPE
   SYNTAX      Counter64
   MAX-ACCESS  read-only
   STATUS      current
   DESCRIPTION
      "Path: tunnels.performance.ipsecL2tpTunnels.inPriorityQueues.d7Performance.totalOctets

       64 bit unsigned wrappable counter."
   ::= {pr1645v2TvTmplPerfiInPQsD7PerformanceEntry 251658240}

pr1645v2TvTmplPerfiInPQsD7PerformanceDirTxOcts OBJECT-TYPE
   SYNTAX      Counter64
   MAX-ACCESS  read-only
   STATUS      current
   DESCRIPTION
      "Path: tunnels.performance.ipsecL2tpTunnels.inPriorityQueues.d7Performance.directTxOctets

       64 bit unsigned wrappable counter."
   ::= {pr1645v2TvTmplPerfiInPQsD7PerformanceEntry 117440512}

pr1645v2TvTmplPerfiInPQsD7PerformanceQdOcts OBJECT-TYPE
   SYNTAX      Counter64
   MAX-ACCESS  read-only
   STATUS      current
   DESCRIPTION
      "Path: tunnels.performance.ipsecL2tpTunnels.inPriorityQueues.d7Performance.queuedOctets

       64 bit unsigned wrappable counter."
   ::= {pr1645v2TvTmplPerfiInPQsD7PerformanceEntry 134217728}

pr1645v2TvTmplPerfiInPQsD7PerformanceDropOcts OBJECT-TYPE
   SYNTAX      Counter64
   MAX-ACCESS  read-only
   STATUS      current
   DESCRIPTION
      "Path: tunnels.performance.ipsecL2tpTunnels.inPriorityQueues.d7Performance.droppedOctets

       64 bit unsigned wrappable counter."
   ::= {pr1645v2TvTmplPerfiInPQsD7PerformanceEntry 150994944}

pr1645v2TvTmplPerfiInPQsD7PerformanceRDropOcts OBJECT-TYPE
   SYNTAX      Counter64
   MAX-ACCESS  read-only
   STATUS      current
   DESCRIPTION
      "Path: tunnels.performance.ipsecL2tpTunnels.inPriorityQueues.d7Performance.redDroppedOctets

       64 bit unsigned wrappable counter."
   ::= {pr1645v2TvTmplPerfiInPQsD7PerformanceEntry 218103808}

pr1645v2TvTmplPerfiInPQsD7PerformanceCirTxOcts OBJECT-TYPE
   SYNTAX      Counter64
   MAX-ACCESS  read-only
   STATUS      current
   DESCRIPTION
      "Path: tunnels.performance.ipsecL2tpTunnels.inPriorityQueues.d7Performance.cirTxOctets

       64 bit unsigned wrappable counter."
   ::= {pr1645v2TvTmplPerfiInPQsD7PerformanceEntry 167772160}

pr1645v2TvTmplPerfiInPQsD7PerformanceEirTxOcts OBJECT-TYPE
   SYNTAX      Counter64
   MAX-ACCESS  read-only
   STATUS      current
   DESCRIPTION
      "Path: tunnels.performance.ipsecL2tpTunnels.inPriorityQueues.d7Performance.eirTxOctets

       64 bit unsigned wrappable counter."
   ::= {pr1645v2TvTmplPerfiInPQsD7PerformanceEntry 184549376}

pr1645v2TvTmplPerfiInPQsD7PerformanceViolTxOcts OBJECT-TYPE
   SYNTAX      Counter64
   MAX-ACCESS  read-only
   STATUS      current
   DESCRIPTION
      "Path: tunnels.performance.ipsecL2tpTunnels.inPriorityQueues.d7Performance.violateTxOctets

       64 bit unsigned wrappable counter."
   ::= {pr1645v2TvTmplPerfiInPQsD7PerformanceEntry 318767104}

pr1645v2TvTmplPerfiInPQsD7PerformanceBandwidth OBJECT-TYPE
   SYNTAX      Integer32
   MAX-ACCESS  read-only
   STATUS      current
   DESCRIPTION
      "Path: tunnels.performance.ipsecL2tpTunnels.inPriorityQueues.d7Performance.bandwidth

       unit name = bps
       formula = 8 * ; 8 /"
   ::= {pr1645v2TvTmplPerfiInPQsD7PerformanceEntry 268435456}

pr1645v2TvTmplPerfiOutPQs OBJECT-TYPE
   SYNTAX      SEQUENCE OF Pr1645v2TvTmplPerfiOutPQsEntry
   MAX-ACCESS  not-accessible
   STATUS      current
   DESCRIPTION
      ""
   ::= {pr1645v2TvTmplPerfi 83886080}

pr1645v2TvTmplPerfiOutPQsEntry OBJECT-TYPE
   SYNTAX      Pr1645v2TvTmplPerfiOutPQsEntry
   MAX-ACCESS  not-accessible
   STATUS      current
   DESCRIPTION
      ""
   INDEX      { pr1645v2TvTmplPerfiTableIx,
                pr1645v2TvTmplPerfiOutPQsTableIx }
   ::= {pr1645v2TvTmplPerfiOutPQs 1}

Pr1645v2TvTmplPerfiOutPQsEntry ::=
   SEQUENCE
      {
      pr1645v2TvTmplPerfiOutPQsTableIx
         TableIndex,
      pr1645v2TvTmplPerfiOutPQsName
         INTEGER,
      pr1645v2TvTmplPerfiOutPQsLength
         Integer32,
      pr1645v2TvTmplPerfiOutPQsOctetLength
         Integer32,
      pr1645v2TvTmplPerfiOutPQsRedLength
         Integer32,
      pr1645v2TvTmplPerfiOutPQsPacketsTotal
         Counter64,
      pr1645v2TvTmplPerfiOutPQsPacketsDirectTx
         Counter64,
      pr1645v2TvTmplPerfiOutPQsPacketsQueued
         Counter64,
      pr1645v2TvTmplPerfiOutPQsPacketsDropped
         Counter64,
      pr1645v2TvTmplPerfiOutPQsPacketsRedDropped
         Counter64,
      pr1645v2TvTmplPerfiOutPQsPacketsCirTx
         Counter64,
      pr1645v2TvTmplPerfiOutPQsPacketsEirTx
         Counter64,
      pr1645v2TvTmplPerfiOutPQsPacketsViolateTx
         Counter64,
      pr1645v2TvTmplPerfiOutPQsOctetsTotal
         Counter64,
      pr1645v2TvTmplPerfiOutPQsOctetsDirectTx
         Counter64,
      pr1645v2TvTmplPerfiOutPQsOctetsQueued
         Counter64,
      pr1645v2TvTmplPerfiOutPQsOctetsDropped
         Counter64,
      pr1645v2TvTmplPerfiOutPQsOctetsRedDropped
         Counter64,
      pr1645v2TvTmplPerfiOutPQsOctetsCirTx
         Counter64,
      pr1645v2TvTmplPerfiOutPQsOctetsEirTx
         Counter64,
      pr1645v2TvTmplPerfiOutPQsOctetsViolateTx
         Counter64,
      pr1645v2TvTmplPerfiOutPQsOctetsBandwidth15sec
         Integer32,
      pr1645v2TvTmplPerfiOutPQsOctetsBandwidth30sec
         Integer32,
      pr1645v2TvTmplPerfiOutPQsOctetsBandwidth1min
         Integer32,
      pr1645v2TvTmplPerfiOutPQsOctetsBandwidth2min
         Integer32,
      pr1645v2TvTmplPerfiOutPQsOctetsBandwidth5min
         Integer32
      }

pr1645v2TvTmplPerfiOutPQsTableIx OBJECT-TYPE
   SYNTAX      TableIndex
   MAX-ACCESS  not-accessible
   STATUS      current
   DESCRIPTION
      ""
   ::= {pr1645v2TvTmplPerfiOutPQsEntry 11}

pr1645v2TvTmplPerfiOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecL2tpTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPerfiOutPQsEntry 16777216}

pr1645v2TvTmplPerfiOutPQsLength OBJECT-TYPE
   SYNTAX      Integer32
   MAX-ACCESS  read-only
   STATUS      current
   DESCRIPTION
      "Path: tunnels.performance.ipsecL2tpTunnels.outPriorityQueues.length"
   ::= {pr1645v2TvTmplPerfiOutPQsEntry 33554432}

pr1645v2TvTmplPerfiOutPQsOctetLength OBJECT-TYPE
   SYNTAX      Integer32
   MAX-ACCESS  read-only
   STATUS      current
   DESCRIPTION
      "Path: tunnels.performance.ipsecL2tpTunnels.outPriorityQueues.octetLength"
   ::= {pr1645v2TvTmplPerfiOutPQsEntry 150994944}

pr1645v2TvTmplPerfiOutPQsRedLength OBJECT-TYPE
   SYNTAX      Integer32
   MAX-ACCESS  read-only
   STATUS      current
   DESCRIPTION
      "Path: tunnels.performance.ipsecL2tpTunnels.outPriorityQueues.redLength"
   ::= {pr1645v2TvTmplPerfiOutPQsEntry 134217728}

pr1645v2TvTmplPerfiOutPQsPacketsTotal OBJECT-TYPE
   SYNTAX      Counter64
   MAX-ACCESS  read-only
   STATUS      current
   DESCRIPTION
      "Path: tunnels.performance.ipsecL2tpTunnels.outPriorityQueues.packets.total

       64 bit unsigned wrappable counter."
   ::= {pr1645v2TvTmplPerfiOutPQsEntry 50790400}

pr1645v2TvTmplPerfiOutPQsPacketsDirectTx OBJECT-TYPE
   SYNTAX      Counter64
   MAX-ACCESS  read-only
   STATUS      current
   DESCRIPTION
      "Path: tunnels.performance.ipsecL2tpTunnels.outPriorityQueues.packets.directTx

       64 bit unsigned wrappable counter."
   ::= {pr1645v2TvTmplPerfiOutPQsEntry 50397184}

pr1645v2TvTmplPerfiOutPQsPacketsQueued OBJECT-TYPE
   SYNTAX      Counter64
   MAX-ACCESS  read-only
   STATUS      current
   DESCRIPTION
      "Path: tunnels.performance.ipsecL2tpTunnels.outPriorityQueues.packets.queued

       64 bit unsigned wrappable counter."
   ::= {pr1645v2TvTmplPerfiOutPQsEntry 50462720}

pr1645v2TvTmplPerfiOutPQsPacketsDropped OBJECT-TYPE
   SYNTAX      Counter64
   MAX-ACCESS  read-only
   STATUS      current
   DESCRIPTION
      "Path: tunnels.performance.ipsecL2tpTunnels.outPriorityQueues.packets.dropped

       64 bit unsigned wrappable counter."
   ::= {pr1645v2TvTmplPerfiOutPQsEntry 50528256}

pr1645v2TvTmplPerfiOutPQsPacketsRedDropped OBJECT-TYPE
   SYNTAX      Counter64
   MAX-ACCESS  read-only
   STATUS      current
   DESCRIPTION
      "Path: tunnels.performance.ipsecL2tpTunnels.outPriorityQueues.packets.redDropped

       64 bit unsigned wrappable counter."
   ::= {pr1645v2TvTmplPerfiOutPQsEntry 50724864}

pr1645v2TvTmplPerfiOutPQsPacketsCirTx OBJECT-TYPE
   SYNTAX      Counter64
   MAX-ACCESS  read-only
   STATUS      current
   DESCRIPTION
      "Path: tunnels.performance.ipsecL2tpTunnels.outPriorityQueues.packets.cirTx

       64 bit unsigned wrappable counter."
   ::= {pr1645v2TvTmplPerfiOutPQsEntry 50593792}

pr1645v2TvTmplPerfiOutPQsPacketsEirTx OBJECT-TYPE
   SYNTAX      Counter64
   MAX-ACCESS  read-only
   STATUS      current
   DESCRIPTION
      "Path: tunnels.performance.ipsecL2tpTunnels.outPriorityQueues.packets.eirTx

       64 bit unsigned wrappable counter."
   ::= {pr1645v2TvTmplPerfiOutPQsEntry 50659328}

pr1645v2TvTmplPerfiOutPQsPacketsViolateTx OBJECT-TYPE
   SYNTAX      Counter64
   MAX-ACCESS  read-only
   STATUS      current
   DESCRIPTION
      "Path: tunnels.performance.ipsecL2tpTunnels.outPriorityQueues.packets.violateTx

       64 bit unsigned wrappable counter."
   ::= {pr1645v2TvTmplPerfiOutPQsEntry 50855936}

pr1645v2TvTmplPerfiOutPQsOctetsTotal OBJECT-TYPE
   SYNTAX      Counter64
   MAX-ACCESS  read-only
   STATUS      current
   DESCRIPTION
      "Path: tunnels.performance.ipsecL2tpTunnels.outPriorityQueues.octets.total

       64 bit unsigned wrappable counter."
   ::= {pr1645v2TvTmplPerfiOutPQsEntry 67567616}

pr1645v2TvTmplPerfiOutPQsOctetsDirectTx OBJECT-TYPE
   SYNTAX      Counter64
   MAX-ACCESS  read-only
   STATUS      current
   DESCRIPTION
      "Path: tunnels.performance.ipsecL2tpTunnels.outPriorityQueues.octets.directTx

       64 bit unsigned wrappable counter."
   ::= {pr1645v2TvTmplPerfiOutPQsEntry 67174400}

pr1645v2TvTmplPerfiOutPQsOctetsQueued OBJECT-TYPE
   SYNTAX      Counter64
   MAX-ACCESS  read-only
   STATUS      current
   DESCRIPTION
      "Path: tunnels.performance.ipsecL2tpTunnels.outPriorityQueues.octets.queued

       64 bit unsigned wrappable counter."
   ::= {pr1645v2TvTmplPerfiOutPQsEntry 67239936}

pr1645v2TvTmplPerfiOutPQsOctetsDropped OBJECT-TYPE
   SYNTAX      Counter64
   MAX-ACCESS  read-only
   STATUS      current
   DESCRIPTION
      "Path: tunnels.performance.ipsecL2tpTunnels.outPriorityQueues.octets.dropped

       64 bit unsigned wrappable counter."
   ::= {pr1645v2TvTmplPerfiOutPQsEntry 67305472}

pr1645v2TvTmplPerfiOutPQsOctetsRedDropped OBJECT-TYPE
   SYNTAX      Counter64
   MAX-ACCESS  read-only
   STATUS      current
   DESCRIPTION
      "Path: tunnels.performance.ipsecL2tpTunnels.outPriorityQueues.octets.redDropped

       64 bit unsigned wrappable counter."
   ::= {pr1645v2TvTmplPerfiOutPQsEntry 67502080}

pr1645v2TvTmplPerfiOutPQsOctetsCirTx OBJECT-TYPE
   SYNTAX      Counter64
   MAX-ACCESS  read-only
   STATUS      current
   DESCRIPTION
      "Path: tunnels.performance.ipsecL2tpTunnels.outPriorityQueues.octets.cirTx

       64 bit unsigned wrappable counter."
   ::= {pr1645v2TvTmplPerfiOutPQsEntry 67371008}

pr1645v2TvTmplPerfiOutPQsOctetsEirTx OBJECT-TYPE
   SYNTAX      Counter64
   MAX-ACCESS  read-only
   STATUS      current
   DESCRIPTION
      "Path: tunnels.performance.ipsecL2tpTunnels.outPriorityQueues.octets.eirTx

       64 bit unsigned wrappable counter."
   ::= {pr1645v2TvTmplPerfiOutPQsEntry 67436544}

pr1645v2TvTmplPerfiOutPQsOctetsViolateTx OBJECT-TYPE
   SYNTAX      Counter64
   MAX-ACCESS  read-only
   STATUS      current
   DESCRIPTION
      "Path: tunnels.performance.ipsecL2tpTunnels.outPriorityQueues.octets.violateTx

       64 bit unsigned wrappable counter."
   ::= {pr1645v2TvTmplPerfiOutPQsEntry 67633152}

pr1645v2TvTmplPerfiOutPQsOctetsBandwidth15sec OBJECT-TYPE
   SYNTAX      Integer32
   MAX-ACCESS  read-only
   STATUS      current
   DESCRIPTION
      "Path: tunnels.performance.ipsecL2tpTunnels.outPriorityQueues.octets.bandwidth.15sec

       unit name = bps
       formula = 8 * ; 8 /"
   ::= {pr1645v2TvTmplPerfiOutPQsEntry 70386944}

pr1645v2TvTmplPerfiOutPQsOctetsBandwidth30sec OBJECT-TYPE
   SYNTAX      Integer32
   MAX-ACCESS  read-only
   STATUS      current
   DESCRIPTION
      "Path: tunnels.performance.ipsecL2tpTunnels.outPriorityQueues.octets.bandwidth.30sec

       unit name = bps
       formula = 8 * ; 8 /"
   ::= {pr1645v2TvTmplPerfiOutPQsEntry 70388224}

pr1645v2TvTmplPerfiOutPQsOctetsBandwidth1min OBJECT-TYPE
   SYNTAX      Integer32
   MAX-ACCESS  read-only
   STATUS      current
   DESCRIPTION
      "Path: tunnels.performance.ipsecL2tpTunnels.outPriorityQueues.octets.bandwidth.1min

       unit name = bps
       formula = 8 * ; 8 /"
   ::= {pr1645v2TvTmplPerfiOutPQsEntry 70390784}

pr1645v2TvTmplPerfiOutPQsOctetsBandwidth2min OBJECT-TYPE
   SYNTAX      Integer32
   MAX-ACCESS  read-only
   STATUS      current
   DESCRIPTION
      "Path: tunnels.performance.ipsecL2tpTunnels.outPriorityQueues.octets.bandwidth.2min

       unit name = bps
       formula = 8 * ; 8 /"
   ::= {pr1645v2TvTmplPerfiOutPQsEntry 70395904}

pr1645v2TvTmplPerfiOutPQsOctetsBandwidth5min OBJECT-TYPE
   SYNTAX      Integer32
   MAX-ACCESS  read-only
   STATUS      current
   DESCRIPTION
      "Path: tunnels.performance.ipsecL2tpTunnels.outPriorityQueues.octets.bandwidth.5min

       unit name = bps
       formula = 8 * ; 8 /"
   ::= {pr1645v2TvTmplPerfiOutPQsEntry 70411264}

pr1645v2TvTmplPerfiOutPQsH2Performance OBJECT-TYPE
   SYNTAX      SEQUENCE OF Pr1645v2TvTmplPerfiOutPQsH2PerformanceEntry
   MAX-ACCESS  not-accessible
   STATUS      current
   DESCRIPTION
      ""
   ::= {pr1645v2TvTmplPerfi 84213760}

pr1645v2TvTmplPerfiOutPQsH2PerformanceEntry OBJECT-TYPE
   SYNTAX      Pr1645v2TvTmplPerfiOutPQsH2PerformanceEntry
   MAX-ACCESS  not-accessible
   STATUS      current
   DESCRIPTION
      ""
   INDEX      { pr1645v2TvTmplPerfiTableIx,
                pr1645v2TvTmplPerfiOutPQsTableIx,
                pr1645v2TvTmplPerfiOutPQsH2PerformanceTableIx }
   ::= {pr1645v2TvTmplPerfiOutPQsH2Performance 1}

Pr1645v2TvTmplPerfiOutPQsH2PerformanceEntry ::=
   SEQUENCE
      {
      pr1645v2TvTmplPerfiOutPQsH2PerformanceTableIx
         TableIndex,
      pr1645v2TvTmplPerfiOutPQsH2PerformanceSysUpTime
         TimeTicks,
      pr1645v2TvTmplPerfiOutPQsH2PerformanceTotPkts
         Counter64,
      pr1645v2TvTmplPerfiOutPQsH2PerformanceDirTxPkts
         Counter64,
      pr1645v2TvTmplPerfiOutPQsH2PerformanceQdPkts
         Counter64,
      pr1645v2TvTmplPerfiOutPQsH2PerformanceDropPkts
         Counter64,
      pr1645v2TvTmplPerfiOutPQsH2PerformanceRDropPkts
         Counter64,
      pr1645v2TvTmplPerfiOutPQsH2PerformanceCirTxPkts
         Counter64,
      pr1645v2TvTmplPerfiOutPQsH2PerformanceEirTxPkts
         Counter64,
      pr1645v2TvTmplPerfiOutPQsH2PerformanceViolTxPkts
         Counter64,
      pr1645v2TvTmplPerfiOutPQsH2PerformanceTotOcts
         Counter64,
      pr1645v2TvTmplPerfiOutPQsH2PerformanceDirTxOcts
         Counter64,
      pr1645v2TvTmplPerfiOutPQsH2PerformanceQdOcts
         Counter64,
      pr1645v2TvTmplPerfiOutPQsH2PerformanceDropOcts
         Counter64,
      pr1645v2TvTmplPerfiOutPQsH2PerformanceRDropOcts
         Counter64,
      pr1645v2TvTmplPerfiOutPQsH2PerformanceCirTxOcts
         Counter64,
      pr1645v2TvTmplPerfiOutPQsH2PerformanceEirTxOcts
         Counter64,
      pr1645v2TvTmplPerfiOutPQsH2PerformanceViolTxOcts
         Counter64,
      pr1645v2TvTmplPerfiOutPQsH2PerformanceBandwidth
         Integer32
      }

pr1645v2TvTmplPerfiOutPQsH2PerformanceTableIx OBJECT-TYPE
   SYNTAX      TableIndex
   MAX-ACCESS  not-accessible
   STATUS      current
   DESCRIPTION
      ""
   ::= {pr1645v2TvTmplPerfiOutPQsH2PerformanceEntry 11}

pr1645v2TvTmplPerfiOutPQsH2PerformanceSysUpTime OBJECT-TYPE
   SYNTAX      TimeTicks
   MAX-ACCESS  read-only
   STATUS      current
   DESCRIPTION
      "Path: tunnels.performance.ipsecL2tpTunnels.outPriorityQueues.h2Performance.sysUpTime

       Time in centi-second."
   ::= {pr1645v2TvTmplPerfiOutPQsH2PerformanceEntry 16777216}

pr1645v2TvTmplPerfiOutPQsH2PerformanceTotPkts OBJECT-TYPE
   SYNTAX      Counter64
   MAX-ACCESS  read-only
   STATUS      current
   DESCRIPTION
      "Path: tunnels.performance.ipsecL2tpTunnels.outPriorityQueues.h2Performance.totalPkts

       64 bit unsigned wrappable counter."
   ::= {pr1645v2TvTmplPerfiOutPQsH2PerformanceEntry 234881024}

pr1645v2TvTmplPerfiOutPQsH2PerformanceDirTxPkts OBJECT-TYPE
   SYNTAX      Counter64
   MAX-ACCESS  read-only
   STATUS      current
   DESCRIPTION
      "Path: tunnels.performance.ipsecL2tpTunnels.outPriorityQueues.h2Performance.directTxPkts

       64 bit unsigned wrappable counter."
   ::= {pr1645v2TvTmplPerfiOutPQsH2PerformanceEntry 33554432}

pr1645v2TvTmplPerfiOutPQsH2PerformanceQdPkts OBJECT-TYPE
   SYNTAX      Counter64
   MAX-ACCESS  read-only
   STATUS      current
   DESCRIPTION
      "Path: tunnels.performance.ipsecL2tpTunnels.outPriorityQueues.h2Performance.queuedPkts

       64 bit unsigned wrappable counter."
   ::= {pr1645v2TvTmplPerfiOutPQsH2PerformanceEntry 50331648}

pr1645v2TvTmplPerfiOutPQsH2PerformanceDropPkts OBJECT-TYPE
   SYNTAX      Counter64
   MAX-ACCESS  read-only
   STATUS      current
   DESCRIPTION
      "Path: tunnels.performance.ipsecL2tpTunnels.outPriorityQueues.h2Performance.droppedPkts

       64 bit unsigned wrappable counter."
   ::= {pr1645v2TvTmplPerfiOutPQsH2PerformanceEntry 67108864}

pr1645v2TvTmplPerfiOutPQsH2PerformanceRDropPkts OBJECT-TYPE
   SYNTAX      Counter64
   MAX-ACCESS  read-only
   STATUS      current
   DESCRIPTION
      "Path: tunnels.performance.ipsecL2tpTunnels.outPriorityQueues.h2Performance.redDroppedPkts

       64 bit unsigned wrappable counter."
   ::= {pr1645v2TvTmplPerfiOutPQsH2PerformanceEntry 201326592}

pr1645v2TvTmplPerfiOutPQsH2PerformanceCirTxPkts OBJECT-TYPE
   SYNTAX      Counter64
   MAX-ACCESS  read-only
   STATUS      current
   DESCRIPTION
      "Path: tunnels.performance.ipsecL2tpTunnels.outPriorityQueues.h2Performance.cirTxPkts

       64 bit unsigned wrappable counter."
   ::= {pr1645v2TvTmplPerfiOutPQsH2PerformanceEntry 83886080}

pr1645v2TvTmplPerfiOutPQsH2PerformanceEirTxPkts OBJECT-TYPE
   SYNTAX      Counter64
   MAX-ACCESS  read-only
   STATUS      current
   DESCRIPTION
      "Path: tunnels.performance.ipsecL2tpTunnels.outPriorityQueues.h2Performance.eirTxPkts

       64 bit unsigned wrappable counter."
   ::= {pr1645v2TvTmplPerfiOutPQsH2PerformanceEntry 100663296}

pr1645v2TvTmplPerfiOutPQsH2PerformanceViolTxPkts OBJECT-TYPE
   SYNTAX      Counter64
   MAX-ACCESS  read-only
   STATUS      current
   DESCRIPTION
      "Path: tunnels.performance.ipsecL2tpTunnels.outPriorityQueues.h2Performance.violateTxPkts

       64 bit unsigned wrappable counter."
   ::= {pr1645v2TvTmplPerfiOutPQsH2PerformanceEntry 301989888}

pr1645v2TvTmplPerfiOutPQsH2PerformanceTotOcts OBJECT-TYPE
   SYNTAX      Counter64
   MAX-ACCESS  read-only
   STATUS      current
   DESCRIPTION
      "Path: tunnels.performance.ipsecL2tpTunnels.outPriorityQueues.h2Performance.totalOctets

       64 bit unsigned wrappable counter."
   ::= {pr1645v2TvTmplPerfiOutPQsH2PerformanceEntry 251658240}

pr1645v2TvTmplPerfiOutPQsH2PerformanceDirTxOcts OBJECT-TYPE
   SYNTAX      Counter64
   MAX-ACCESS  read-only
   STATUS      current
   DESCRIPTION
      "Path: tunnels.performance.ipsecL2tpTunnels.outPriorityQueues.h2Performance.directTxOctets

       64 bit unsigned wrappable counter."
   ::= {pr1645v2TvTmplPerfiOutPQsH2PerformanceEntry 117440512}

pr1645v2TvTmplPerfiOutPQsH2PerformanceQdOcts OBJECT-TYPE
   SYNTAX      Counter64
   MAX-ACCESS  read-only
   STATUS      current
   DESCRIPTION
      "Path: tunnels.performance.ipsecL2tpTunnels.outPriorityQueues.h2Performance.queuedOctets

       64 bit unsigned wrappable counter."
   ::= {pr1645v2TvTmplPerfiOutPQsH2PerformanceEntry 134217728}

pr1645v2TvTmplPerfiOutPQsH2PerformanceDropOcts OBJECT-TYPE
   SYNTAX      Counter64
   MAX-ACCESS  read-only
   STATUS      current
   DESCRIPTION
      "Path: tunnels.performance.ipsecL2tpTunnels.outPriorityQueues.h2Performance.droppedOctets

       64 bit unsigned wrappable counter."
   ::= {pr1645v2TvTmplPerfiOutPQsH2PerformanceEntry 150994944}

pr1645v2TvTmplPerfiOutPQsH2PerformanceRDropOcts OBJECT-TYPE
   SYNTAX      Counter64
   MAX-ACCESS  read-only
   STATUS      current
   DESCRIPTION
      "Path: tunnels.performance.ipsecL2tpTunnels.outPriorityQueues.h2Performance.redDroppedOctets

       64 bit unsigned wrappable counter."
   ::= {pr1645v2TvTmplPerfiOutPQsH2PerformanceEntry 218103808}

pr1645v2TvTmplPerfiOutPQsH2PerformanceCirTxOcts OBJECT-TYPE
   SYNTAX      Counter64
   MAX-ACCESS  read-only
   STATUS      current
   DESCRIPTION
      "Path: tunnels.performance.ipsecL2tpTunnels.outPriorityQueues.h2Performance.cirTxOctets

       64 bit unsigned wrappable counter."
   ::= {pr1645v2TvTmplPerfiOutPQsH2PerformanceEntry 167772160}

pr1645v2TvTmplPerfiOutPQsH2PerformanceEirTxOcts OBJECT-TYPE
   SYNTAX      Counter64
   MAX-ACCESS  read-only
   STATUS      current
   DESCRIPTION
      "Path: tunnels.performance.ipsecL2tpTunnels.outPriorityQueues.h2Performance.eirTxOctets

       64 bit unsigned wrappable counter."
   ::= {pr1645v2TvTmplPerfiOutPQsH2PerformanceEntry 184549376}

pr1645v2TvTmplPerfiOutPQsH2PerformanceViolTxOcts OBJECT-TYPE
   SYNTAX      Counter64
   MAX-ACCESS  read-only
   STATUS      current
   DESCRIPTION
      "Path: tunnels.performance.ipsecL2tpTunnels.outPriorityQueues.h2Performance.violateTxOctets

       64 bit unsigned wrappable counter."
   ::= {pr1645v2TvTmplPerfiOutPQsH2PerformanceEntry 318767104}

pr1645v2TvTmplPerfiOutPQsH2PerformanceBandwidth OBJECT-TYPE
   SYNTAX      Integer32
   MAX-ACCESS  read-only
   STATUS      current
   DESCRIPTION
      "Path: tunnels.performance.ipsecL2tpTunnels.outPriorityQueues.h2Performance.bandwidth

       unit name = bps
       formula = 8 * ; 8 /"
   ::= {pr1645v2TvTmplPerfiOutPQsH2PerformanceEntry 268435456}

pr1645v2TvTmplPerfiOutPQsH24Performance OBJECT-TYPE
   SYNTAX      SEQUENCE OF Pr1645v2TvTmplPerfiOutPQsH24PerformanceEntry
   MAX-ACCESS  not-accessible
   STATUS      current
   DESCRIPTION
      ""
   ::= {pr1645v2TvTmplPerfi 84279296}

pr1645v2TvTmplPerfiOutPQsH24PerformanceEntry OBJECT-TYPE
   SYNTAX      Pr1645v2TvTmplPerfiOutPQsH24PerformanceEntry
   MAX-ACCESS  not-accessible
   STATUS      current
   DESCRIPTION
      ""
   INDEX      { pr1645v2TvTmplPerfiTableIx,
                pr1645v2TvTmplPerfiOutPQsTableIx,
                pr1645v2TvTmplPerfiOutPQsH24PerformanceTableIx }
   ::= {pr1645v2TvTmplPerfiOutPQsH24Performance 1}

Pr1645v2TvTmplPerfiOutPQsH24PerformanceEntry ::=
   SEQUENCE
      {
      pr1645v2TvTmplPerfiOutPQsH24PerformanceTableIx
         TableIndex,
      pr1645v2TvTmplPerfiOutPQsH24PerformanceSysUpTime
         TimeTicks,
      pr1645v2TvTmplPerfiOutPQsH24PerformanceTotPkts
         Counter64,
      pr1645v2TvTmplPerfiOutPQsH24PerformanceDirTxPkts
         Counter64,
      pr1645v2TvTmplPerfiOutPQsH24PerformanceQdPkts
         Counter64,
      pr1645v2TvTmplPerfiOutPQsH24PerformanceDropPkts
         Counter64,
      pr1645v2TvTmplPerfiOutPQsH24PerformanceRDropPkts
         Counter64,
      pr1645v2TvTmplPerfiOutPQsH24PerformanceCirTxPkts
         Counter64,
      pr1645v2TvTmplPerfiOutPQsH24PerformanceEirTxPkts
         Counter64,
      pr1645v2TvTmplPerfiOutPQsH24PerformanceViolTxPkts
         Counter64,
      pr1645v2TvTmplPerfiOutPQsH24PerformanceTotOcts
         Counter64,
      pr1645v2TvTmplPerfiOutPQsH24PerformanceDirTxOcts
         Counter64,
      pr1645v2TvTmplPerfiOutPQsH24PerformanceQdOcts
         Counter64,
      pr1645v2TvTmplPerfiOutPQsH24PerformanceDropOcts
         Counter64,
      pr1645v2TvTmplPerfiOutPQsH24PerformanceRDropOcts
         Counter64,
      pr1645v2TvTmplPerfiOutPQsH24PerformanceCirTxOcts
         Counter64,
      pr1645v2TvTmplPerfiOutPQsH24PerformanceEirTxOcts
         Counter64,
      pr1645v2TvTmplPerfiOutPQsH24PerformanceViolTxOcts
         Counter64,
      pr1645v2TvTmplPerfiOutPQsH24PerformanceBandwidth
         Integer32
      }

pr1645v2TvTmplPerfiOutPQsH24PerformanceTableIx OBJECT-TYPE
   SYNTAX      TableIndex
   MAX-ACCESS  not-accessible
   STATUS      current
   DESCRIPTION
      ""
   ::= {pr1645v2TvTmplPerfiOutPQsH24PerformanceEntry 11}

pr1645v2TvTmplPerfiOutPQsH24PerformanceSysUpTime OBJECT-TYPE
   SYNTAX      TimeTicks
   MAX-ACCESS  read-only
   STATUS      current
   DESCRIPTION
      "Path: tunnels.performance.ipsecL2tpTunnels.outPriorityQueues.h24Performance.sysUpTime

       Time in centi-second."
   ::= {pr1645v2TvTmplPerfiOutPQsH24PerformanceEntry 16777216}

pr1645v2TvTmplPerfiOutPQsH24PerformanceTotPkts OBJECT-TYPE
   SYNTAX      Counter64
   MAX-ACCESS  read-only
   STATUS      current
   DESCRIPTION
      "Path: tunnels.performance.ipsecL2tpTunnels.outPriorityQueues.h24Performance.totalPkts

       64 bit unsigned wrappable counter."
   ::= {pr1645v2TvTmplPerfiOutPQsH24PerformanceEntry 234881024}

pr1645v2TvTmplPerfiOutPQsH24PerformanceDirTxPkts OBJECT-TYPE
   SYNTAX      Counter64
   MAX-ACCESS  read-only
   STATUS      current
   DESCRIPTION
      "Path: tunnels.performance.ipsecL2tpTunnels.outPriorityQueues.h24Performance.directTxPkts

       64 bit unsigned wrappable counter."
   ::= {pr1645v2TvTmplPerfiOutPQsH24PerformanceEntry 33554432}

pr1645v2TvTmplPerfiOutPQsH24PerformanceQdPkts OBJECT-TYPE
   SYNTAX      Counter64
   MAX-ACCESS  read-only
   STATUS      current
   DESCRIPTION
      "Path: tunnels.performance.ipsecL2tpTunnels.outPriorityQueues.h24Performance.queuedPkts

       64 bit unsigned wrappable counter."
   ::= {pr1645v2TvTmplPerfiOutPQsH24PerformanceEntry 50331648}

pr1645v2TvTmplPerfiOutPQsH24PerformanceDropPkts OBJECT-TYPE
   SYNTAX      Counter64
   MAX-ACCESS  read-only
   STATUS      current
   DESCRIPTION
      "Path: tunnels.performance.ipsecL2tpTunnels.outPriorityQueues.h24Performance.droppedPkts

       64 bit unsigned wrappable counter."
   ::= {pr1645v2TvTmplPerfiOutPQsH24PerformanceEntry 67108864}

pr1645v2TvTmplPerfiOutPQsH24PerformanceRDropPkts OBJECT-TYPE
   SYNTAX      Counter64
   MAX-ACCESS  read-only
   STATUS      current
   DESCRIPTION
      "Path: tunnels.performance.ipsecL2tpTunnels.outPriorityQueues.h24Performance.redDroppedPkts

       64 bit unsigned wrappable counter."
   ::= {pr1645v2TvTmplPerfiOutPQsH24PerformanceEntry 201326592}

pr1645v2TvTmplPerfiOutPQsH24PerformanceCirTxPkts OBJECT-TYPE
   SYNTAX      Counter64
   MAX-ACCESS  read-only
   STATUS      current
   DESCRIPTION
      "Path: tunnels.performance.ipsecL2tpTunnels.outPriorityQueues.h24Performance.cirTxPkts

       64 bit unsigned wrappable counter."
   ::= {pr1645v2TvTmplPerfiOutPQsH24PerformanceEntry 83886080}

pr1645v2TvTmplPerfiOutPQsH24PerformanceEirTxPkts OBJECT-TYPE
   SYNTAX      Counter64
   MAX-ACCESS  read-only
   STATUS      current
   DESCRIPTION
      "Path: tunnels.performance.ipsecL2tpTunnels.outPriorityQueues.h24Performance.eirTxPkts

       64 bit unsigned wrappable counter."
   ::= {pr1645v2TvTmplPerfiOutPQsH24PerformanceEntry 100663296}

pr1645v2TvTmplPerfiOutPQsH24PerformanceViolTxPkts OBJECT-TYPE
   SYNTAX      Counter64
   MAX-ACCESS  read-only
   STATUS      current
   DESCRIPTION
      "Path: tunnels.performance.ipsecL2tpTunnels.outPriorityQueues.h24Performance.violateTxPkts

       64 bit unsigned wrappable counter."
   ::= {pr1645v2TvTmplPerfiOutPQsH24PerformanceEntry 301989888}

pr1645v2TvTmplPerfiOutPQsH24PerformanceTotOcts OBJECT-TYPE
   SYNTAX      Counter64
   MAX-ACCESS  read-only
   STATUS      current
   DESCRIPTION
      "Path: tunnels.performance.ipsecL2tpTunnels.outPriorityQueues.h24Performance.totalOctets

       64 bit unsigned wrappable counter."
   ::= {pr1645v2TvTmplPerfiOutPQsH24PerformanceEntry 251658240}

pr1645v2TvTmplPerfiOutPQsH24PerformanceDirTxOcts OBJECT-TYPE
   SYNTAX      Counter64
   MAX-ACCESS  read-only
   STATUS      current
   DESCRIPTION
      "Path: tunnels.performance.ipsecL2tpTunnels.outPriorityQueues.h24Performance.directTxOctets

       64 bit unsigned wrappable counter."
   ::= {pr1645v2TvTmplPerfiOutPQsH24PerformanceEntry 117440512}

pr1645v2TvTmplPerfiOutPQsH24PerformanceQdOcts OBJECT-TYPE
   SYNTAX      Counter64
   MAX-ACCESS  read-only
   STATUS      current
   DESCRIPTION
      "Path: tunnels.performance.ipsecL2tpTunnels.outPriorityQueues.h24Performance.queuedOctets

       64 bit unsigned wrappable counter."
   ::= {pr1645v2TvTmplPerfiOutPQsH24PerformanceEntry 134217728}

pr1645v2TvTmplPerfiOutPQsH24PerformanceDropOcts OBJECT-TYPE
   SYNTAX      Counter64
   MAX-ACCESS  read-only
   STATUS      current
   DESCRIPTION
      "Path: tunnels.performance.ipsecL2tpTunnels.outPriorityQueues.h24Performance.droppedOctets

       64 bit unsigned wrappable counter."
   ::= {pr1645v2TvTmplPerfiOutPQsH24PerformanceEntry 150994944}

pr1645v2TvTmplPerfiOutPQsH24PerformanceRDropOcts OBJECT-TYPE
   SYNTAX      Counter64
   MAX-ACCESS  read-only
   STATUS      current
   DESCRIPTION
      "Path: tunnels.performance.ipsecL2tpTunnels.outPriorityQueues.h24Performance.redDroppedOctets

       64 bit unsigned wrappable counter."
   ::= {pr1645v2TvTmplPerfiOutPQsH24PerformanceEntry 218103808}

pr1645v2TvTmplPerfiOutPQsH24PerformanceCirTxOcts OBJECT-TYPE
   SYNTAX      Counter64
   MAX-ACCESS  read-only
   STATUS      current
   DESCRIPTION
      "Path: tunnels.performance.ipsecL2tpTunnels.outPriorityQueues.h24Performance.cirTxOctets

       64 bit unsigned wrappable counter."
   ::= {pr1645v2TvTmplPerfiOutPQsH24PerformanceEntry 167772160}

pr1645v2TvTmplPerfiOutPQsH24PerformanceEirTxOcts OBJECT-TYPE
   SYNTAX      Counter64
   MAX-ACCESS  read-only
   STATUS      current
   DESCRIPTION
      "Path: tunnels.performance.ipsecL2tpTunnels.outPriorityQueues.h24Performance.eirTxOctets

       64 bit unsigned wrappable counter."
   ::= {pr1645v2TvTmplPerfiOutPQsH24PerformanceEntry 184549376}

pr1645v2TvTmplPerfiOutPQsH24PerformanceViolTxOcts OBJECT-TYPE
   SYNTAX      Counter64
   MAX-ACCESS  read-only
   STATUS      current
   DESCRIPTION
      "Path: tunnels.performance.ipsecL2tpTunnels.outPriorityQueues.h24Performance.violateTxOctets

       64 bit unsigned wrappable counter."
   ::= {pr1645v2TvTmplPerfiOutPQsH24PerformanceEntry 318767104}

pr1645v2TvTmplPerfiOutPQsH24PerformanceBandwidth OBJECT-TYPE
   SYNTAX      Integer32
   MAX-ACCESS  read-only
   STATUS      current
   DESCRIPTION
      "Path: tunnels.performance.ipsecL2tpTunnels.outPriorityQueues.h24Performance.bandwidth

       unit name = bps
       formula = 8 * ; 8 /"
   ::= {pr1645v2TvTmplPerfiOutPQsH24PerformanceEntry 268435456}

pr1645v2TvTmplPerfiOutPQsD7Performance OBJECT-TYPE
   SYNTAX      SEQUENCE OF Pr1645v2TvTmplPerfiOutPQsD7PerformanceEntry
   MAX-ACCESS  not-accessible
   STATUS      current
   DESCRIPTION
      ""
   ::= {pr1645v2TvTmplPerfi 84344832}

pr1645v2TvTmplPerfiOutPQsD7PerformanceEntry OBJECT-TYPE
   SYNTAX      Pr1645v2TvTmplPerfiOutPQsD7PerformanceEntry
   MAX-ACCESS  not-accessible
   STATUS      current
   DESCRIPTION
      ""
   INDEX      { pr1645v2TvTmplPerfiTableIx,
                pr1645v2TvTmplPerfiOutPQsTableIx,
                pr1645v2TvTmplPerfiOutPQsD7PerformanceTableIx }
   ::= {pr1645v2TvTmplPerfiOutPQsD7Performance 1}

Pr1645v2TvTmplPerfiOutPQsD7PerformanceEntry ::=
   SEQUENCE
      {
      pr1645v2TvTmplPerfiOutPQsD7PerformanceTableIx
         TableIndex,
      pr1645v2TvTmplPerfiOutPQsD7PerformanceSysUpTime
         TimeTicks,
      pr1645v2TvTmplPerfiOutPQsD7PerformanceTotPkts
         Counter64,
      pr1645v2TvTmplPerfiOutPQsD7PerformanceDirTxPkts
         Counter64,
      pr1645v2TvTmplPerfiOutPQsD7PerformanceQdPkts
         Counter64,
      pr1645v2TvTmplPerfiOutPQsD7PerformanceDropPkts
         Counter64,
      pr1645v2TvTmplPerfiOutPQsD7PerformanceRDropPkts
         Counter64,
      pr1645v2TvTmplPerfiOutPQsD7PerformanceCirTxPkts
         Counter64,
      pr1645v2TvTmplPerfiOutPQsD7PerformanceEirTxPkts
         Counter64,
      pr1645v2TvTmplPerfiOutPQsD7PerformanceViolTxPkts
         Counter64,
      pr1645v2TvTmplPerfiOutPQsD7PerformanceTotOcts
         Counter64,
      pr1645v2TvTmplPerfiOutPQsD7PerformanceDirTxOcts
         Counter64,
      pr1645v2TvTmplPerfiOutPQsD7PerformanceQdOcts
         Counter64,
      pr1645v2TvTmplPerfiOutPQsD7PerformanceDropOcts
         Counter64,
      pr1645v2TvTmplPerfiOutPQsD7PerformanceRDropOcts
         Counter64,
      pr1645v2TvTmplPerfiOutPQsD7PerformanceCirTxOcts
         Counter64,
      pr1645v2TvTmplPerfiOutPQsD7PerformanceEirTxOcts
         Counter64,
      pr1645v2TvTmplPerfiOutPQsD7PerformanceViolTxOcts
         Counter64,
      pr1645v2TvTmplPerfiOutPQsD7PerformanceBandwidth
         Integer32
      }

pr1645v2TvTmplPerfiOutPQsD7PerformanceTableIx OBJECT-TYPE
   SYNTAX      TableIndex
   MAX-ACCESS  not-accessible
   STATUS      current
   DESCRIPTION
      ""
   ::= {pr1645v2TvTmplPerfiOutPQsD7PerformanceEntry 11}

pr1645v2TvTmplPerfiOutPQsD7PerformanceSysUpTime OBJECT-TYPE
   SYNTAX      TimeTicks
   MAX-ACCESS  read-only
   STATUS      current
   DESCRIPTION
      "Path: tunnels.performance.ipsecL2tpTunnels.outPriorityQueues.d7Performance.sysUpTime

       Time in centi-second."
   ::= {pr1645v2TvTmplPerfiOutPQsD7PerformanceEntry 16777216}

pr1645v2TvTmplPerfiOutPQsD7PerformanceTotPkts OBJECT-TYPE
   SYNTAX      Counter64
   MAX-ACCESS  read-only
   STATUS      current
   DESCRIPTION
      "Path: tunnels.performance.ipsecL2tpTunnels.outPriorityQueues.d7Performance.totalPkts

       64 bit unsigned wrappable counter."
   ::= {pr1645v2TvTmplPerfiOutPQsD7PerformanceEntry 234881024}

pr1645v2TvTmplPerfiOutPQsD7PerformanceDirTxPkts OBJECT-TYPE
   SYNTAX      Counter64
   MAX-ACCESS  read-only
   STATUS      current
   DESCRIPTION
      "Path: tunnels.performance.ipsecL2tpTunnels.outPriorityQueues.d7Performance.directTxPkts

       64 bit unsigned wrappable counter."
   ::= {pr1645v2TvTmplPerfiOutPQsD7PerformanceEntry 33554432}

pr1645v2TvTmplPerfiOutPQsD7PerformanceQdPkts OBJECT-TYPE
   SYNTAX      Counter64
   MAX-ACCESS  read-only
   STATUS      current
   DESCRIPTION
      "Path: tunnels.performance.ipsecL2tpTunnels.outPriorityQueues.d7Performance.queuedPkts

       64 bit unsigned wrappable counter."
   ::= {pr1645v2TvTmplPerfiOutPQsD7PerformanceEntry 50331648}

pr1645v2TvTmplPerfiOutPQsD7PerformanceDropPkts OBJECT-TYPE
   SYNTAX      Counter64
   MAX-ACCESS  read-only
   STATUS      current
   DESCRIPTION
      "Path: tunnels.performance.ipsecL2tpTunnels.outPriorityQueues.d7Performance.droppedPkts

       64 bit unsigned wrappable counter."
   ::= {pr1645v2TvTmplPerfiOutPQsD7PerformanceEntry 67108864}

pr1645v2TvTmplPerfiOutPQsD7PerformanceRDropPkts OBJECT-TYPE
   SYNTAX      Counter64
   MAX-ACCESS  read-only
   STATUS      current
   DESCRIPTION
      "Path: tunnels.performance.ipsecL2tpTunnels.outPriorityQueues.d7Performance.redDroppedPkts

       64 bit unsigned wrappable counter."
   ::= {pr1645v2TvTmplPerfiOutPQsD7PerformanceEntry 201326592}

pr1645v2TvTmplPerfiOutPQsD7PerformanceCirTxPkts OBJECT-TYPE
   SYNTAX      Counter64
   MAX-ACCESS  read-only
   STATUS      current
   DESCRIPTION
      "Path: tunnels.performance.ipsecL2tpTunnels.outPriorityQueues.d7Performance.cirTxPkts

       64 bit unsigned wrappable counter."
   ::= {pr1645v2TvTmplPerfiOutPQsD7PerformanceEntry 83886080}

pr1645v2TvTmplPerfiOutPQsD7PerformanceEirTxPkts OBJECT-TYPE
   SYNTAX      Counter64
   MAX-ACCESS  read-only
   STATUS      current
   DESCRIPTION
      "Path: tunnels.performance.ipsecL2tpTunnels.outPriorityQueues.d7Performance.eirTxPkts

       64 bit unsigned wrappable counter."
   ::= {pr1645v2TvTmplPerfiOutPQsD7PerformanceEntry 100663296}

pr1645v2TvTmplPerfiOutPQsD7PerformanceViolTxPkts OBJECT-TYPE
   SYNTAX      Counter64
   MAX-ACCESS  read-only
   STATUS      current
   DESCRIPTION
      "Path: tunnels.performance.ipsecL2tpTunnels.outPriorityQueues.d7Performance.violateTxPkts

       64 bit unsigned wrappable counter."
   ::= {pr1645v2TvTmplPerfiOutPQsD7PerformanceEntry 301989888}

pr1645v2TvTmplPerfiOutPQsD7PerformanceTotOcts OBJECT-TYPE
   SYNTAX      Counter64
   MAX-ACCESS  read-only
   STATUS      current
   DESCRIPTION
      "Path: tunnels.performance.ipsecL2tpTunnels.outPriorityQueues.d7Performance.totalOctets

       64 bit unsigned wrappable counter."
   ::= {pr1645v2TvTmplPerfiOutPQsD7PerformanceEntry 251658240}

pr1645v2TvTmplPerfiOutPQsD7PerformanceDirTxOcts OBJECT-TYPE
   SYNTAX      Counter64
   MAX-ACCESS  read-only
   STATUS      current
   DESCRIPTION
      "Path: tunnels.performance.ipsecL2tpTunnels.outPriorityQueues.d7Performance.directTxOctets

       64 bit unsigned wrappable counter."
   ::= {pr1645v2TvTmplPerfiOutPQsD7PerformanceEntry 117440512}

pr1645v2TvTmplPerfiOutPQsD7PerformanceQdOcts OBJECT-TYPE
   SYNTAX      Counter64
   MAX-ACCESS  read-only
   STATUS      current
   DESCRIPTION
      "Path: tunnels.performance.ipsecL2tpTunnels.outPriorityQueues.d7Performance.queuedOctets

       64 bit unsigned wrappable counter."
   ::= {pr1645v2TvTmplPerfiOutPQsD7PerformanceEntry 134217728}

pr1645v2TvTmplPerfiOutPQsD7PerformanceDropOcts OBJECT-TYPE
   SYNTAX      Counter64
   MAX-ACCESS  read-only
   STATUS      current
   DESCRIPTION
      "Path: tunnels.performance.ipsecL2tpTunnels.outPriorityQueues.d7Performance.droppedOctets

       64 bit unsigned wrappable counter."
   ::= {pr1645v2TvTmplPerfiOutPQsD7PerformanceEntry 150994944}

pr1645v2TvTmplPerfiOutPQsD7PerformanceRDropOcts OBJECT-TYPE
   SYNTAX      Counter64
   MAX-ACCESS  read-only
   STATUS      current
   DESCRIPTION
      "Path: tunnels.performance.ipsecL2tpTunnels.outPriorityQueues.d7Performance.redDroppedOctets

       64 bit unsigned wrappable counter."
   ::= {pr1645v2TvTmplPerfiOutPQsD7PerformanceEntry 218103808}

pr1645v2TvTmplPerfiOutPQsD7PerformanceCirTxOcts OBJECT-TYPE
   SYNTAX      Counter64
   MAX-ACCESS  read-only
   STATUS      current
   DESCRIPTION
      "Path: tunnels.performance.ipsecL2tpTunnels.outPriorityQueues.d7Performance.cirTxOctets

       64 bit unsigned wrappable counter."
   ::= {pr1645v2TvTmplPerfiOutPQsD7PerformanceEntry 167772160}

pr1645v2TvTmplPerfiOutPQsD7PerformanceEirTxOcts OBJECT-TYPE
   SYNTAX      Counter64
   MAX-ACCESS  read-only
   STATUS      current
   DESCRIPTION
      "Path: tunnels.performance.ipsecL2tpTunnels.outPriorityQueues.d7Performance.eirTxOctets

       64 bit unsigned wrappable counter."
   ::= {pr1645v2TvTmplPerfiOutPQsD7PerformanceEntry 184549376}

pr1645v2TvTmplPerfiOutPQsD7PerformanceViolTxOcts OBJECT-TYPE
   SYNTAX      Counter64
   MAX-ACCESS  read-only
   STATUS      current
   DESCRIPTION
      "Path: tunnels.performance.ipsecL2tpTunnels.outPriorityQueues.d7Performance.violateTxOctets

       64 bit unsigned wrappable counter."
   ::= {pr1645v2TvTmplPerfiOutPQsD7PerformanceEntry 318767104}

pr1645v2TvTmplPerfiOutPQsD7PerformanceBandwidth OBJECT-TYPE
   SYNTAX      Integer32
   MAX-ACCESS  read-only
   STATUS      current
   DESCRIPTION
      "Path: tunnels.performance.ipsecL2tpTunnels.outPriorityQueues.d7Performance.bandwidth

       unit name = bps
       formula = 8 * ; 8 /"
   ::= {pr1645v2TvTmplPerfiOutPQsD7PerformanceEntry 268435456}


pr1645v2TvTmplPGre OBJECT IDENTIFIER ::= {pr1645v2TvTmpl 23}

pr1645v2TvTmplPGreSSCTable OBJECT-TYPE
   SYNTAX      SEQUENCE OF Pr1645v2TvTmplPGreEntry
   MAX-ACCESS  not-accessible
   STATUS      current
   DESCRIPTION
      ""
   ::= {pr1645v2TvTmplPGre 1}

pr1645v2TvTmplPGreEntry OBJECT-TYPE
   SYNTAX      Pr1645v2TvTmplPGreEntry
   MAX-ACCESS  not-accessible
   STATUS      current
   DESCRIPTION
      ""
   INDEX      { pr1645v2TvTmplPGreTableIx }
   ::= {pr1645v2TvTmplPGreSSCTable 1}

Pr1645v2TvTmplPGreEntry ::=
   SEQUENCE
      {
      pr1645v2TvTmplPGreTableIx
         TableIndex,
      pr1645v2TvTmplPGreName
         DisplayString,
      pr1645v2TvTmplPGreMCInOctets
         Counter64,
      pr1645v2TvTmplPGreMCInUcast
         Counter64,
      pr1645v2TvTmplPGreMCInNUcastPkts
         Counter64,
      pr1645v2TvTmplPGreMCInBcastPkts
         Counter64,
      pr1645v2TvTmplPGreMCInMcastPkts
         Counter64,
      pr1645v2TvTmplPGreMCInDiscards
         Counter64,
      pr1645v2TvTmplPGreMCInErrors
         Counter64,
      pr1645v2TvTmplPGreMCInUnknownProtos
         Counter64,
      pr1645v2TvTmplPGreMCInDropEx
         Counter64,
      pr1645v2TvTmplPGreMCInDropNoMac
         Counter64,
      pr1645v2TvTmplPGreMCInDropNUCast
         Counter64,
      pr1645v2TvTmplPGreMCInDropFilter
         Counter64,
      pr1645v2TvTmplPGreMCInBandwidth15sec
         Integer32,
      pr1645v2TvTmplPGreMCInBandwidth30sec
         Integer32,
      pr1645v2TvTmplPGreMCInBandwidth1min
         Integer32,
      pr1645v2TvTmplPGreMCInBandwidth2min
         Integer32,
      pr1645v2TvTmplPGreMCInBandwidth5min
         Integer32,
      pr1645v2TvTmplPGreMCOutOctets
         Counter64,
      pr1645v2TvTmplPGreMCOutUcastPkts
         Counter64,
      pr1645v2TvTmplPGreMCOutNUcastPkts
         Counter64,
      pr1645v2TvTmplPGreMCOutBcastPkts
         Counter64,
      pr1645v2TvTmplPGreMCOutMcastPkts
         Counter64,
      pr1645v2TvTmplPGreMCOutDiscards
         Counter64,
      pr1645v2TvTmplPGreMCOutErrors
         Counter64,
      pr1645v2TvTmplPGreMCOutQLen
         Counter32,
      pr1645v2TvTmplPGreMCOutDropEx
         Counter64,
      pr1645v2TvTmplPGreMCOutDropNoArp
         Counter64,
      pr1645v2TvTmplPGreMCOutDropFilter
         Counter64,
      pr1645v2TvTmplPGreMCOutBandwidth15sec
         Integer32,
      pr1645v2TvTmplPGreMCOutBandwidth30sec
         Integer32,
      pr1645v2TvTmplPGreMCOutBandwidth1min
         Integer32,
      pr1645v2TvTmplPGreMCOutBandwidth2min
         Integer32,
      pr1645v2TvTmplPGreMCOutBandwidth5min
         Integer32,
      pr1645v2TvTmplPGreGreKeepAliveRequestsSent
         Counter32,
      pr1645v2TvTmplPGreGreKeepAliveRepliesRcvd
         Counter32
      }

pr1645v2TvTmplPGreTableIx OBJECT-TYPE
   SYNTAX      TableIndex
   MAX-ACCESS  not-accessible
   STATUS      current
   DESCRIPTION
      ""
   ::= {pr1645v2TvTmplPGreEntry 11}

pr1645v2TvTmplPGreName OBJECT-TYPE
   SYNTAX      DisplayString
   MAX-ACCESS  read-only
   STATUS      current
   DESCRIPTION
      "Path: tunnels.performance.greTunnels.name"
   ::= {pr1645v2TvTmplPGreEntry 16777216}

pr1645v2TvTmplPGreMCInOctets OBJECT-TYPE
   SYNTAX      Counter64
   MAX-ACCESS  read-only
   STATUS      current
   DESCRIPTION
      "Path: tunnels.performance.greTunnels.mibCounters.ifInOctets

       64 bit unsigned wrappable counter."
   ::= {pr1645v2TvTmplPGreEntry 40697856}

pr1645v2TvTmplPGreMCInUcast OBJECT-TYPE
   SYNTAX      Counter64
   MAX-ACCESS  read-only
   STATUS      current
   DESCRIPTION
      "Path: tunnels.performance.greTunnels.mibCounters.ifInUcastPkts

       64 bit unsigned wrappable counter."
   ::= {pr1645v2TvTmplPGreEntry 40763392}

pr1645v2TvTmplPGreMCInNUcastPkts OBJECT-TYPE
   SYNTAX      Counter64
   MAX-ACCESS  read-only
   STATUS      current
   DESCRIPTION
      "Path: tunnels.performance.greTunnels.mibCounters.ifInNUcastPkts

       64 bit unsigned wrappable counter."
   ::= {pr1645v2TvTmplPGreEntry 40828928}

pr1645v2TvTmplPGreMCInBcastPkts OBJECT-TYPE
   SYNTAX      Counter64
   MAX-ACCESS  read-only
   STATUS      current
   DESCRIPTION
      "Path: tunnels.performance.greTunnels.mibCounters.ifInBcastPkts

       64 bit unsigned wrappable counter."
   ::= {pr1645v2TvTmplPGreEntry 47382528}

pr1645v2TvTmplPGreMCInMcastPkts OBJECT-TYPE
   SYNTAX      Counter64
   MAX-ACCESS  read-only
   STATUS      current
   DESCRIPTION
      "Path: tunnels.performance.greTunnels.mibCounters.ifInMcastPkts

       64 bit unsigned wrappable counter."
   ::= {pr1645v2TvTmplPGreEntry 48037888}

pr1645v2TvTmplPGreMCInDiscards OBJECT-TYPE
   SYNTAX      Counter64
   MAX-ACCESS  read-only
   STATUS      current
   DESCRIPTION
      "Path: tunnels.performance.greTunnels.mibCounters.ifInDiscards

       64 bit unsigned wrappable counter."
   ::= {pr1645v2TvTmplPGreEntry 40894464}

pr1645v2TvTmplPGreMCInErrors OBJECT-TYPE
   SYNTAX      Counter64
   MAX-ACCESS  read-only
   STATUS      current
   DESCRIPTION
      "Path: tunnels.performance.greTunnels.mibCounters.ifInErrors

       64 bit unsigned wrappable counter."
   ::= {pr1645v2TvTmplPGreEntry 40960000}

pr1645v2TvTmplPGreMCInUnknownProtos OBJECT-TYPE
   SYNTAX      Counter64
   MAX-ACCESS  read-only
   STATUS      current
   DESCRIPTION
      "Path: tunnels.performance.greTunnels.mibCounters.ifInUnknownProtos

       64 bit unsigned wrappable counter."
   ::= {pr1645v2TvTmplPGreEntry 41025536}

pr1645v2TvTmplPGreMCInDropEx OBJECT-TYPE
   SYNTAX      Counter64
   MAX-ACCESS  read-only
   STATUS      current
   DESCRIPTION
      "Path: tunnels.performance.greTunnels.mibCounters.ifInDropLevelExceeded

       64 bit unsigned wrappable counter."
   ::= {pr1645v2TvTmplPGreEntry 42074112}

pr1645v2TvTmplPGreMCInDropNoMac OBJECT-TYPE
   SYNTAX      Counter64
   MAX-ACCESS  read-only
   STATUS      current
   DESCRIPTION
      "Path: tunnels.performance.greTunnels.mibCounters.ifInDiscardsNoMacFit

       64 bit unsigned wrappable counter."
   ::= {pr1645v2TvTmplPGreEntry 42270720}

pr1645v2TvTmplPGreMCInDropNUCast OBJECT-TYPE
   SYNTAX      Counter64
   MAX-ACCESS  read-only
   STATUS      current
   DESCRIPTION
      "Path: tunnels.performance.greTunnels.mibCounters.ifInDiscardsNUCast

       64 bit unsigned wrappable counter."
   ::= {pr1645v2TvTmplPGreEntry 42467328}

pr1645v2TvTmplPGreMCInDropFilter OBJECT-TYPE
   SYNTAX      Counter64
   MAX-ACCESS  read-only
   STATUS      current
   DESCRIPTION
      "Path: tunnels.performance.greTunnels.mibCounters.ifInDiscardsFilter

       64 bit unsigned wrappable counter."
   ::= {pr1645v2TvTmplPGreEntry 42532864}

pr1645v2TvTmplPGreMCInBandwidth15sec OBJECT-TYPE
   SYNTAX      Integer32
   MAX-ACCESS  read-only
   STATUS      current
   DESCRIPTION
      "Path: tunnels.performance.greTunnels.mibCounters.ifInBandwidth.15sec

       unit name = bps
       formula = 8 * ; 8 /"
   ::= {pr1645v2TvTmplPGreEntry 45417728}

pr1645v2TvTmplPGreMCInBandwidth30sec OBJECT-TYPE
   SYNTAX      Integer32
   MAX-ACCESS  read-only
   STATUS      current
   DESCRIPTION
      "Path: tunnels.performance.greTunnels.mibCounters.ifInBandwidth.30sec

       unit name = bps
       formula = 8 * ; 8 /"
   ::= {pr1645v2TvTmplPGreEntry 45419008}

pr1645v2TvTmplPGreMCInBandwidth1min OBJECT-TYPE
   SYNTAX      Integer32
   MAX-ACCESS  read-only
   STATUS      current
   DESCRIPTION
      "Path: tunnels.performance.greTunnels.mibCounters.ifInBandwidth.1min

       unit name = bps
       formula = 8 * ; 8 /"
   ::= {pr1645v2TvTmplPGreEntry 45421568}

pr1645v2TvTmplPGreMCInBandwidth2min OBJECT-TYPE
   SYNTAX      Integer32
   MAX-ACCESS  read-only
   STATUS      current
   DESCRIPTION
      "Path: tunnels.performance.greTunnels.mibCounters.ifInBandwidth.2min

       unit name = bps
       formula = 8 * ; 8 /"
   ::= {pr1645v2TvTmplPGreEntry 45426688}

pr1645v2TvTmplPGreMCInBandwidth5min OBJECT-TYPE
   SYNTAX      Integer32
   MAX-ACCESS  read-only
   STATUS      current
   DESCRIPTION
      "Path: tunnels.performance.greTunnels.mibCounters.ifInBandwidth.5min

       unit name = bps
       formula = 8 * ; 8 /"
   ::= {pr1645v2TvTmplPGreEntry 45442048}

pr1645v2TvTmplPGreMCOutOctets OBJECT-TYPE
   SYNTAX      Counter64
   MAX-ACCESS  read-only
   STATUS      current
   DESCRIPTION
      "Path: tunnels.performance.greTunnels.mibCounters.ifOutOctets

       64 bit unsigned wrappable counter."
   ::= {pr1645v2TvTmplPGreEntry 41091072}

pr1645v2TvTmplPGreMCOutUcastPkts OBJECT-TYPE
   SYNTAX      Counter64
   MAX-ACCESS  read-only
   STATUS      current
   DESCRIPTION
      "Path: tunnels.performance.greTunnels.mibCounters.ifOutUcastPkts

       64 bit unsigned wrappable counter."
   ::= {pr1645v2TvTmplPGreEntry 41156608}

pr1645v2TvTmplPGreMCOutNUcastPkts OBJECT-TYPE
   SYNTAX      Counter64
   MAX-ACCESS  read-only
   STATUS      current
   DESCRIPTION
      "Path: tunnels.performance.greTunnels.mibCounters.ifOutNUcastPkts

       64 bit unsigned wrappable counter."
   ::= {pr1645v2TvTmplPGreEntry 41222144}

pr1645v2TvTmplPGreMCOutBcastPkts OBJECT-TYPE
   SYNTAX      Counter64
   MAX-ACCESS  read-only
   STATUS      current
   DESCRIPTION
      "Path: tunnels.performance.greTunnels.mibCounters.ifOutBcastPkts

       64 bit unsigned wrappable counter."
   ::= {pr1645v2TvTmplPGreEntry 47775744}

pr1645v2TvTmplPGreMCOutMcastPkts OBJECT-TYPE
   SYNTAX      Counter64
   MAX-ACCESS  read-only
   STATUS      current
   DESCRIPTION
      "Path: tunnels.performance.greTunnels.mibCounters.ifOutMcastPkts

       64 bit unsigned wrappable counter."
   ::= {pr1645v2TvTmplPGreEntry 48431104}

pr1645v2TvTmplPGreMCOutDiscards OBJECT-TYPE
   SYNTAX      Counter64
   MAX-ACCESS  read-only
   STATUS      current
   DESCRIPTION
      "Path: tunnels.performance.greTunnels.mibCounters.ifOutDiscards

       64 bit unsigned wrappable counter."
   ::= {pr1645v2TvTmplPGreEntry 41287680}

pr1645v2TvTmplPGreMCOutErrors OBJECT-TYPE
   SYNTAX      Counter64
   MAX-ACCESS  read-only
   STATUS      current
   DESCRIPTION
      "Path: tunnels.performance.greTunnels.mibCounters.ifOutErrors

       64 bit unsigned wrappable counter."
   ::= {pr1645v2TvTmplPGreEntry 41353216}

pr1645v2TvTmplPGreMCOutQLen OBJECT-TYPE
   SYNTAX      Counter32
   MAX-ACCESS  read-only
   STATUS      current
   DESCRIPTION
      "Path: tunnels.performance.greTunnels.mibCounters.ifOutQLen

       32 bit unsigned wrappable counter."
   ::= {pr1645v2TvTmplPGreEntry 41418752}

pr1645v2TvTmplPGreMCOutDropEx OBJECT-TYPE
   SYNTAX      Counter64
   MAX-ACCESS  read-only
   STATUS      current
   DESCRIPTION
      "Path: tunnels.performance.greTunnels.mibCounters.ifOutDropLevelExceeded

       64 bit unsigned wrappable counter."
   ::= {pr1645v2TvTmplPGreEntry 41484288}

pr1645v2TvTmplPGreMCOutDropNoArp OBJECT-TYPE
   SYNTAX      Counter64
   MAX-ACCESS  read-only
   STATUS      current
   DESCRIPTION
      "Path: tunnels.performance.greTunnels.mibCounters.ifOutDiscardsNoArp

       64 bit unsigned wrappable counter."
   ::= {pr1645v2TvTmplPGreEntry 42336256}

pr1645v2TvTmplPGreMCOutDropFilter OBJECT-TYPE
   SYNTAX      Counter64
   MAX-ACCESS  read-only
   STATUS      current
   DESCRIPTION
      "Path: tunnels.performance.greTunnels.mibCounters.ifOutDiscardsFilter

       64 bit unsigned wrappable counter."
   ::= {pr1645v2TvTmplPGreEntry 42598400}

pr1645v2TvTmplPGreMCOutBandwidth15sec OBJECT-TYPE
   SYNTAX      Integer32
   MAX-ACCESS  read-only
   STATUS      current
   DESCRIPTION
      "Path: tunnels.performance.greTunnels.mibCounters.ifOutBandwidth.15sec

       unit name = bps
       formula = 8 * ; 8 /"
   ::= {pr1645v2TvTmplPGreEntry 45483264}

pr1645v2TvTmplPGreMCOutBandwidth30sec OBJECT-TYPE
   SYNTAX      Integer32
   MAX-ACCESS  read-only
   STATUS      current
   DESCRIPTION
      "Path: tunnels.performance.greTunnels.mibCounters.ifOutBandwidth.30sec

       unit name = bps
       formula = 8 * ; 8 /"
   ::= {pr1645v2TvTmplPGreEntry 45484544}

pr1645v2TvTmplPGreMCOutBandwidth1min OBJECT-TYPE
   SYNTAX      Integer32
   MAX-ACCESS  read-only
   STATUS      current
   DESCRIPTION
      "Path: tunnels.performance.greTunnels.mibCounters.ifOutBandwidth.1min

       unit name = bps
       formula = 8 * ; 8 /"
   ::= {pr1645v2TvTmplPGreEntry 45487104}

pr1645v2TvTmplPGreMCOutBandwidth2min OBJECT-TYPE
   SYNTAX      Integer32
   MAX-ACCESS  read-only
   STATUS      current
   DESCRIPTION
      "Path: tunnels.performance.greTunnels.mibCounters.ifOutBandwidth.2min

       unit name = bps
       formula = 8 * ; 8 /"
   ::= {pr1645v2TvTmplPGreEntry 45492224}

pr1645v2TvTmplPGreMCOutBandwidth5min OBJECT-TYPE
   SYNTAX      Integer32
   MAX-ACCESS  read-only
   STATUS      current
   DESCRIPTION
      "Path: tunnels.performance.greTunnels.mibCounters.ifOutBandwidth.5min

       unit name = bps
       formula = 8 * ; 8 /"
   ::= {pr1645v2TvTmplPGreEntry 45507584}

pr1645v2TvTmplPGreGreKeepAliveRequestsSent OBJECT-TYPE
   SYNTAX      Counter32
   MAX-ACCESS  read-only
   STATUS      current
   DESCRIPTION
      "Path: tunnels.performance.greTunnels.gre.keepAlive.requestsSent

       32 bit unsigned wrappable counter."
   ::= {pr1645v2TvTmplPGreEntry 117506304}

pr1645v2TvTmplPGreGreKeepAliveRepliesRcvd OBJECT-TYPE
   SYNTAX      Counter32
   MAX-ACCESS  read-only
   STATUS      current
   DESCRIPTION
      "Path: tunnels.performance.greTunnels.gre.keepAlive.repliesRcvd

       32 bit unsigned wrappable counter."
   ::= {pr1645v2TvTmplPGreEntry 117506560}

pr1645v2TvTmplPGreMCH2P OBJECT-TYPE
   SYNTAX      SEQUENCE OF Pr1645v2TvTmplPGreMCH2PEntry
   MAX-ACCESS  not-accessible
   STATUS      current
   DESCRIPTION
      ""
   ::= {pr1645v2TvTmplPGre 41549824}

pr1645v2TvTmplPGreMCH2PEntry OBJECT-TYPE
   SYNTAX      Pr1645v2TvTmplPGreMCH2PEntry
   MAX-ACCESS  not-accessible
   STATUS      current
   DESCRIPTION
      ""
   INDEX      { pr1645v2TvTmplPGreTableIx,
                pr1645v2TvTmplPGreMCH2PTableIx }
   ::= {pr1645v2TvTmplPGreMCH2P 1}

Pr1645v2TvTmplPGreMCH2PEntry ::=
   SEQUENCE
      {
      pr1645v2TvTmplPGreMCH2PTableIx
         TableIndex,
      pr1645v2TvTmplPGreMCH2PSysUpTime
         TimeTicks,
      pr1645v2TvTmplPGreMCH2PIfUpTime
         TimeTicks,
      pr1645v2TvTmplPGreMCH2PIfStatChanges
         Counter32,
      pr1645v2TvTmplPGreMCH2PIfInOctets
         Counter64,
      pr1645v2TvTmplPGreMCH2PIfInUCPkts
         Counter64,
      pr1645v2TvTmplPGreMCH2PIfInNUCPkts
         Counter64,
      pr1645v2TvTmplPGreMCH2PIfInBCPkts
         Counter64,
      pr1645v2TvTmplPGreMCH2PIfInMCPkts
         Counter64,
      pr1645v2TvTmplPGreMCH2PIfInDiscards
         Counter64,
      pr1645v2TvTmplPGreMCH2PIfInErrors
         Counter64,
      pr1645v2TvTmplPGreMCH2PIfInUnkwn
         Counter64,
      pr1645v2TvTmplPGreMCH2PInDropEx
         Counter64,
      pr1645v2TvTmplPGreMCH2PInDropNoMac
         Counter64,
      pr1645v2TvTmplPGreMCH2PInDropNUCast
         Counter64,
      pr1645v2TvTmplPGreMCH2PInDropFilter
         Counter64,
      pr1645v2TvTmplPGreMCH2PIfInBandwidth
         Integer32,
      pr1645v2TvTmplPGreMCH2PIfOutOctets
         Counter64,
      pr1645v2TvTmplPGreMCH2PIfOutUCPkts
         Counter64,
      pr1645v2TvTmplPGreMCH2PIfOutNUCPkts
         Counter64,
      pr1645v2TvTmplPGreMCH2PIfOutBCPkts
         Counter64,
      pr1645v2TvTmplPGreMCH2PIfOutMCPkts
         Counter64,
      pr1645v2TvTmplPGreMCH2PIfOutDiscards
         Counter64,
      pr1645v2TvTmplPGreMCH2PIfOutErrors
         Counter64,
      pr1645v2TvTmplPGreMCH2POutDropEx
         Counter64,
      pr1645v2TvTmplPGreMCH2POutDropNoArp
         Counter64,
      pr1645v2TvTmplPGreMCH2POutDropFilter
         Counter64,
      pr1645v2TvTmplPGreMCH2PIfOutBandwidth
         Integer32,
      pr1645v2TvTmplPGreMCH2PIfErrSec
         Counter32
      }

pr1645v2TvTmplPGreMCH2PTableIx OBJECT-TYPE
   SYNTAX      TableIndex
   MAX-ACCESS  not-accessible
   STATUS      current
   DESCRIPTION
      ""
   ::= {pr1645v2TvTmplPGreMCH2PEntry 11}

pr1645v2TvTmplPGreMCH2PSysUpTime OBJECT-TYPE
   SYNTAX      TimeTicks
   MAX-ACCESS  read-only
   STATUS      current
   DESCRIPTION
      "Path: tunnels.performance.greTunnels.mibCounters.h2Performance.sysUpTime

       Time in centi-second."
   ::= {pr1645v2TvTmplPGreMCH2PEntry 16777216}

pr1645v2TvTmplPGreMCH2PIfUpTime OBJECT-TYPE
   SYNTAX      TimeTicks
   MAX-ACCESS  read-only
   STATUS      current
   DESCRIPTION
      "Path: tunnels.performance.greTunnels.mibCounters.h2Performance.ifUpTime

       Time in centi-second."
   ::= {pr1645v2TvTmplPGreMCH2PEntry 33554432}

pr1645v2TvTmplPGreMCH2PIfStatChanges OBJECT-TYPE
   SYNTAX      Counter32
   MAX-ACCESS  read-only
   STATUS      current
   DESCRIPTION
      "Path: tunnels.performance.greTunnels.mibCounters.h2Performance.ifStatusChanges

       32 bit unsigned wrappable counter."
   ::= {pr1645v2TvTmplPGreMCH2PEntry 50331648}

pr1645v2TvTmplPGreMCH2PIfInOctets OBJECT-TYPE
   SYNTAX      Counter64
   MAX-ACCESS  read-only
   STATUS      current
   DESCRIPTION
      "Path: tunnels.performance.greTunnels.mibCounters.h2Performance.ifInOctets

       64 bit unsigned wrappable counter."
   ::= {pr1645v2TvTmplPGreMCH2PEntry 67108864}

pr1645v2TvTmplPGreMCH2PIfInUCPkts OBJECT-TYPE
   SYNTAX      Counter64
   MAX-ACCESS  read-only
   STATUS      current
   DESCRIPTION
      "Path: tunnels.performance.greTunnels.mibCounters.h2Performance.ifInUcastPkts

       64 bit unsigned wrappable counter."
   ::= {pr1645v2TvTmplPGreMCH2PEntry 83886080}

pr1645v2TvTmplPGreMCH2PIfInNUCPkts OBJECT-TYPE
   SYNTAX      Counter64
   MAX-ACCESS  read-only
   STATUS      current
   DESCRIPTION
      "Path: tunnels.performance.greTunnels.mibCounters.h2Performance.ifInNUcastPkts

       64 bit unsigned wrappable counter."
   ::= {pr1645v2TvTmplPGreMCH2PEntry 100663296}

pr1645v2TvTmplPGreMCH2PIfInBCPkts OBJECT-TYPE
   SYNTAX      Counter64
   MAX-ACCESS  read-only
   STATUS      current
   DESCRIPTION
      "Path: tunnels.performance.greTunnels.mibCounters.h2Performance.ifInBcastPkts

       64 bit unsigned wrappable counter."
   ::= {pr1645v2TvTmplPGreMCH2PEntry 419430400}

pr1645v2TvTmplPGreMCH2PIfInMCPkts OBJECT-TYPE
   SYNTAX      Counter64
   MAX-ACCESS  read-only
   STATUS      current
   DESCRIPTION
      "Path: tunnels.performance.greTunnels.mibCounters.h2Performance.ifInMcastPkts

       64 bit unsigned wrappable counter."
   ::= {pr1645v2TvTmplPGreMCH2PEntry 436207616}

pr1645v2TvTmplPGreMCH2PIfInDiscards OBJECT-TYPE
   SYNTAX      Counter64
   MAX-ACCESS  read-only
   STATUS      current
   DESCRIPTION
      "Path: tunnels.performance.greTunnels.mibCounters.h2Performance.ifInDiscards

       64 bit unsigned wrappable counter."
   ::= {pr1645v2TvTmplPGreMCH2PEntry 117440512}

pr1645v2TvTmplPGreMCH2PIfInErrors OBJECT-TYPE
   SYNTAX      Counter64
   MAX-ACCESS  read-only
   STATUS      current
   DESCRIPTION
      "Path: tunnels.performance.greTunnels.mibCounters.h2Performance.ifInErrors

       64 bit unsigned wrappable counter."
   ::= {pr1645v2TvTmplPGreMCH2PEntry 134217728}

pr1645v2TvTmplPGreMCH2PIfInUnkwn OBJECT-TYPE
   SYNTAX      Counter64
   MAX-ACCESS  read-only
   STATUS      current
   DESCRIPTION
      "Path: tunnels.performance.greTunnels.mibCounters.h2Performance.ifInUnknownProtos

       64 bit unsigned wrappable counter."
   ::= {pr1645v2TvTmplPGreMCH2PEntry 150994944}

pr1645v2TvTmplPGreMCH2PInDropEx OBJECT-TYPE
   SYNTAX      Counter64
   MAX-ACCESS  read-only
   STATUS      current
   DESCRIPTION
      "Path: tunnels.performance.greTunnels.mibCounters.h2Performance.ifInDropLevelExceeded

       64 bit unsigned wrappable counter."
   ::= {pr1645v2TvTmplPGreMCH2PEntry 335544320}

pr1645v2TvTmplPGreMCH2PInDropNoMac OBJECT-TYPE
   SYNTAX      Counter64
   MAX-ACCESS  read-only
   STATUS      current
   DESCRIPTION
      "Path: tunnels.performance.greTunnels.mibCounters.h2Performance.fInDiscardsNoMacFit

       64 bit unsigned wrappable counter."
   ::= {pr1645v2TvTmplPGreMCH2PEntry 301989888}

pr1645v2TvTmplPGreMCH2PInDropNUCast OBJECT-TYPE
   SYNTAX      Counter64
   MAX-ACCESS  read-only
   STATUS      current
   DESCRIPTION
      "Path: tunnels.performance.greTunnels.mibCounters.h2Performance.fInDiscardsNUCast

       64 bit unsigned wrappable counter."
   ::= {pr1645v2TvTmplPGreMCH2PEntry 318767104}

pr1645v2TvTmplPGreMCH2PInDropFilter OBJECT-TYPE
   SYNTAX      Counter64
   MAX-ACCESS  read-only
   STATUS      current
   DESCRIPTION
      "Path: tunnels.performance.greTunnels.mibCounters.h2Performance.fInDiscardsFilter

       64 bit unsigned wrappable counter."
   ::= {pr1645v2TvTmplPGreMCH2PEntry 385875968}

pr1645v2TvTmplPGreMCH2PIfInBandwidth OBJECT-TYPE
   SYNTAX      Integer32
   MAX-ACCESS  read-only
   STATUS      current
   DESCRIPTION
      "Path: tunnels.performance.greTunnels.mibCounters.h2Performance.ifInBandwidth

       unit name = bps
       formula = 8 * ; 8 /"
   ::= {pr1645v2TvTmplPGreMCH2PEntry 268435456}

pr1645v2TvTmplPGreMCH2PIfOutOctets OBJECT-TYPE
   SYNTAX      Counter64
   MAX-ACCESS  read-only
   STATUS      current
   DESCRIPTION
      "Path: tunnels.performance.greTunnels.mibCounters.h2Performance.ifOutOctets

       64 bit unsigned wrappable counter."
   ::= {pr1645v2TvTmplPGreMCH2PEntry 167772160}

pr1645v2TvTmplPGreMCH2PIfOutUCPkts OBJECT-TYPE
   SYNTAX      Counter64
   MAX-ACCESS  read-only
   STATUS      current
   DESCRIPTION
      "Path: tunnels.performance.greTunnels.mibCounters.h2Performance.ifOutUcastPkts

       64 bit unsigned wrappable counter."
   ::= {pr1645v2TvTmplPGreMCH2PEntry 184549376}

pr1645v2TvTmplPGreMCH2PIfOutNUCPkts OBJECT-TYPE
   SYNTAX      Counter64
   MAX-ACCESS  read-only
   STATUS      current
   DESCRIPTION
      "Path: tunnels.performance.greTunnels.mibCounters.h2Performance.ifOutNUcastPkts

       64 bit unsigned wrappable counter."
   ::= {pr1645v2TvTmplPGreMCH2PEntry 201326592}

pr1645v2TvTmplPGreMCH2PIfOutBCPkts OBJECT-TYPE
   SYNTAX      Counter64
   MAX-ACCESS  read-only
   STATUS      current
   DESCRIPTION
      "Path: tunnels.performance.greTunnels.mibCounters.h2Performance.ifOutBcastPkts

       64 bit unsigned wrappable counter."
   ::= {pr1645v2TvTmplPGreMCH2PEntry 452984832}

pr1645v2TvTmplPGreMCH2PIfOutMCPkts OBJECT-TYPE
   SYNTAX      Counter64
   MAX-ACCESS  read-only
   STATUS      current
   DESCRIPTION
      "Path: tunnels.performance.greTunnels.mibCounters.h2Performance.ifOutMcastPkts

       64 bit unsigned wrappable counter."
   ::= {pr1645v2TvTmplPGreMCH2PEntry 469762048}

pr1645v2TvTmplPGreMCH2PIfOutDiscards OBJECT-TYPE
   SYNTAX      Counter64
   MAX-ACCESS  read-only
   STATUS      current
   DESCRIPTION
      "Path: tunnels.performance.greTunnels.mibCounters.h2Performance.ifOutDiscards

       64 bit unsigned wrappable counter."
   ::= {pr1645v2TvTmplPGreMCH2PEntry 218103808}

pr1645v2TvTmplPGreMCH2PIfOutErrors OBJECT-TYPE
   SYNTAX      Counter64
   MAX-ACCESS  read-only
   STATUS      current
   DESCRIPTION
      "Path: tunnels.performance.greTunnels.mibCounters.h2Performance.ifOutErrors

       64 bit unsigned wrappable counter."
   ::= {pr1645v2TvTmplPGreMCH2PEntry 234881024}

pr1645v2TvTmplPGreMCH2POutDropEx OBJECT-TYPE
   SYNTAX      Counter64
   MAX-ACCESS  read-only
   STATUS      current
   DESCRIPTION
      "Path: tunnels.performance.greTunnels.mibCounters.h2Performance.ifOutDropLevelExceeded

       64 bit unsigned wrappable counter."
   ::= {pr1645v2TvTmplPGreMCH2PEntry 352321536}

pr1645v2TvTmplPGreMCH2POutDropNoArp OBJECT-TYPE
   SYNTAX      Counter64
   MAX-ACCESS  read-only
   STATUS      current
   DESCRIPTION
      "Path: tunnels.performance.greTunnels.mibCounters.h2Performance.ifOutDiscardsNoArp

       64 bit unsigned wrappable counter."
   ::= {pr1645v2TvTmplPGreMCH2PEntry 369098752}

pr1645v2TvTmplPGreMCH2POutDropFilter OBJECT-TYPE
   SYNTAX      Counter64
   MAX-ACCESS  read-only
   STATUS      current
   DESCRIPTION
      "Path: tunnels.performance.greTunnels.mibCounters.h2Performance.ifOutDiscardsFilter

       64 bit unsigned wrappable counter."
   ::= {pr1645v2TvTmplPGreMCH2PEntry 402653184}

pr1645v2TvTmplPGreMCH2PIfOutBandwidth OBJECT-TYPE
   SYNTAX      Integer32
   MAX-ACCESS  read-only
   STATUS      current
   DESCRIPTION
      "Path: tunnels.performance.greTunnels.mibCounters.h2Performance.ifOutBandwidth

       unit name = bps
       formula = 8 * ; 8 /"
   ::= {pr1645v2TvTmplPGreMCH2PEntry 285212672}

pr1645v2TvTmplPGreMCH2PIfErrSec OBJECT-TYPE
   SYNTAX      Counter32
   MAX-ACCESS  read-only
   STATUS      current
   DESCRIPTION
      "Path: tunnels.performance.greTunnels.mibCounters.h2Performance.ifErrSec

       32 bit unsigned wrappable counter."
   ::= {pr1645v2TvTmplPGreMCH2PEntry 251658240}

pr1645v2TvTmplPGreMCH24P OBJECT-TYPE
   SYNTAX      SEQUENCE OF Pr1645v2TvTmplPGreMCH24PEntry
   MAX-ACCESS  not-accessible
   STATUS      current
   DESCRIPTION
      ""
   ::= {pr1645v2TvTmplPGre 41615360}

pr1645v2TvTmplPGreMCH24PEntry OBJECT-TYPE
   SYNTAX      Pr1645v2TvTmplPGreMCH24PEntry
   MAX-ACCESS  not-accessible
   STATUS      current
   DESCRIPTION
      ""
   INDEX      { pr1645v2TvTmplPGreTableIx,
                pr1645v2TvTmplPGreMCH24PTableIx }
   ::= {pr1645v2TvTmplPGreMCH24P 1}

Pr1645v2TvTmplPGreMCH24PEntry ::=
   SEQUENCE
      {
      pr1645v2TvTmplPGreMCH24PTableIx
         TableIndex,
      pr1645v2TvTmplPGreMCH24PSysUpTime
         TimeTicks,
      pr1645v2TvTmplPGreMCH24PIfUpTime
         TimeTicks,
      pr1645v2TvTmplPGreMCH24PIfStatChanges
         Counter32,
      pr1645v2TvTmplPGreMCH24PIfInOctets
         Counter64,
      pr1645v2TvTmplPGreMCH24PIfInUCPkts
         Counter64,
      pr1645v2TvTmplPGreMCH24PIfInNUCPkts
         Counter64,
      pr1645v2TvTmplPGreMCH24PIfInBCPkts
         Counter64,
      pr1645v2TvTmplPGreMCH24PIfInMCPkts
         Counter64,
      pr1645v2TvTmplPGreMCH24PIfInDiscards
         Counter64,
      pr1645v2TvTmplPGreMCH24PIfInErrors
         Counter64,
      pr1645v2TvTmplPGreMCH24PIfInUnkwn
         Counter64,
      pr1645v2TvTmplPGreMCH24PInDropEx
         Counter64,
      pr1645v2TvTmplPGreMCH24PInDropNoMac
         Counter64,
      pr1645v2TvTmplPGreMCH24PInDropNUCast
         Counter64,
      pr1645v2TvTmplPGreMCH24PInDropFilter
         Counter64,
      pr1645v2TvTmplPGreMCH24PIfInBandwidth
         Integer32,
      pr1645v2TvTmplPGreMCH24PIfOutOctets
         Counter64,
      pr1645v2TvTmplPGreMCH24PIfOutUCPkts
         Counter64,
      pr1645v2TvTmplPGreMCH24PIfOutNUCPkts
         Counter64,
      pr1645v2TvTmplPGreMCH24PIfOutBCPkts
         Counter64,
      pr1645v2TvTmplPGreMCH24PIfOutMCPkts
         Counter64,
      pr1645v2TvTmplPGreMCH24PIfOutDiscards
         Counter64,
      pr1645v2TvTmplPGreMCH24PIfOutErrors
         Counter64,
      pr1645v2TvTmplPGreMCH24POutDropEx
         Counter64,
      pr1645v2TvTmplPGreMCH24POutDropNoArp
         Counter64,
      pr1645v2TvTmplPGreMCH24POutDropFilter
         Counter64,
      pr1645v2TvTmplPGreMCH24PIfOutBandwidth
         Integer32,
      pr1645v2TvTmplPGreMCH24PIfErrSec
         Counter32
      }

pr1645v2TvTmplPGreMCH24PTableIx OBJECT-TYPE
   SYNTAX      TableIndex
   MAX-ACCESS  not-accessible
   STATUS      current
   DESCRIPTION
      ""
   ::= {pr1645v2TvTmplPGreMCH24PEntry 11}

pr1645v2TvTmplPGreMCH24PSysUpTime OBJECT-TYPE
   SYNTAX      TimeTicks
   MAX-ACCESS  read-only
   STATUS      current
   DESCRIPTION
      "Path: tunnels.performance.greTunnels.mibCounters.h24Performance.sysUpTime

       Time in centi-second."
   ::= {pr1645v2TvTmplPGreMCH24PEntry 16777216}

pr1645v2TvTmplPGreMCH24PIfUpTime OBJECT-TYPE
   SYNTAX      TimeTicks
   MAX-ACCESS  read-only
   STATUS      current
   DESCRIPTION
      "Path: tunnels.performance.greTunnels.mibCounters.h24Performance.ifUpTime

       Time in centi-second."
   ::= {pr1645v2TvTmplPGreMCH24PEntry 33554432}

pr1645v2TvTmplPGreMCH24PIfStatChanges OBJECT-TYPE
   SYNTAX      Counter32
   MAX-ACCESS  read-only
   STATUS      current
   DESCRIPTION
      "Path: tunnels.performance.greTunnels.mibCounters.h24Performance.ifStatusChanges

       32 bit unsigned wrappable counter."
   ::= {pr1645v2TvTmplPGreMCH24PEntry 50331648}

pr1645v2TvTmplPGreMCH24PIfInOctets OBJECT-TYPE
   SYNTAX      Counter64
   MAX-ACCESS  read-only
   STATUS      current
   DESCRIPTION
      "Path: tunnels.performance.greTunnels.mibCounters.h24Performance.ifInOctets

       64 bit unsigned wrappable counter."
   ::= {pr1645v2TvTmplPGreMCH24PEntry 67108864}

pr1645v2TvTmplPGreMCH24PIfInUCPkts OBJECT-TYPE
   SYNTAX      Counter64
   MAX-ACCESS  read-only
   STATUS      current
   DESCRIPTION
      "Path: tunnels.performance.greTunnels.mibCounters.h24Performance.ifInUcastPkts

       64 bit unsigned wrappable counter."
   ::= {pr1645v2TvTmplPGreMCH24PEntry 83886080}

pr1645v2TvTmplPGreMCH24PIfInNUCPkts OBJECT-TYPE
   SYNTAX      Counter64
   MAX-ACCESS  read-only
   STATUS      current
   DESCRIPTION
      "Path: tunnels.performance.greTunnels.mibCounters.h24Performance.ifInNUcastPkts

       64 bit unsigned wrappable counter."
   ::= {pr1645v2TvTmplPGreMCH24PEntry 100663296}

pr1645v2TvTmplPGreMCH24PIfInBCPkts OBJECT-TYPE
   SYNTAX      Counter64
   MAX-ACCESS  read-only
   STATUS      current
   DESCRIPTION
      "Path: tunnels.performance.greTunnels.mibCounters.h24Performance.ifInBcastPkts

       64 bit unsigned wrappable counter."
   ::= {pr1645v2TvTmplPGreMCH24PEntry 419430400}

pr1645v2TvTmplPGreMCH24PIfInMCPkts OBJECT-TYPE
   SYNTAX      Counter64
   MAX-ACCESS  read-only
   STATUS      current
   DESCRIPTION
      "Path: tunnels.performance.greTunnels.mibCounters.h24Performance.ifInMcastPkts

       64 bit unsigned wrappable counter."
   ::= {pr1645v2TvTmplPGreMCH24PEntry 436207616}

pr1645v2TvTmplPGreMCH24PIfInDiscards OBJECT-TYPE
   SYNTAX      Counter64
   MAX-ACCESS  read-only
   STATUS      current
   DESCRIPTION
      "Path: tunnels.performance.greTunnels.mibCounters.h24Performance.ifInDiscards

       64 bit unsigned wrappable counter."
   ::= {pr1645v2TvTmplPGreMCH24PEntry 117440512}

pr1645v2TvTmplPGreMCH24PIfInErrors OBJECT-TYPE
   SYNTAX      Counter64
   MAX-ACCESS  read-only
   STATUS      current
   DESCRIPTION
      "Path: tunnels.performance.greTunnels.mibCounters.h24Performance.ifInErrors

       64 bit unsigned wrappable counter."
   ::= {pr1645v2TvTmplPGreMCH24PEntry 134217728}

pr1645v2TvTmplPGreMCH24PIfInUnkwn OBJECT-TYPE
   SYNTAX      Counter64
   MAX-ACCESS  read-only
   STATUS      current
   DESCRIPTION
      "Path: tunnels.performance.greTunnels.mibCounters.h24Performance.ifInUnknownProtos

       64 bit unsigned wrappable counter."
   ::= {pr1645v2TvTmplPGreMCH24PEntry 150994944}

pr1645v2TvTmplPGreMCH24PInDropEx OBJECT-TYPE
   SYNTAX      Counter64
   MAX-ACCESS  read-only
   STATUS      current
   DESCRIPTION
      "Path: tunnels.performance.greTunnels.mibCounters.h24Performance.ifInDropLevelExceeded

       64 bit unsigned wrappable counter."
   ::= {pr1645v2TvTmplPGreMCH24PEntry 335544320}

pr1645v2TvTmplPGreMCH24PInDropNoMac OBJECT-TYPE
   SYNTAX      Counter64
   MAX-ACCESS  read-only
   STATUS      current
   DESCRIPTION
      "Path: tunnels.performance.greTunnels.mibCounters.h24Performance.fInDiscardsNoMacFit

       64 bit unsigned wrappable counter."
   ::= {pr1645v2TvTmplPGreMCH24PEntry 301989888}

pr1645v2TvTmplPGreMCH24PInDropNUCast OBJECT-TYPE
   SYNTAX      Counter64
   MAX-ACCESS  read-only
   STATUS      current
   DESCRIPTION
      "Path: tunnels.performance.greTunnels.mibCounters.h24Performance.fInDiscardsNUCast

       64 bit unsigned wrappable counter."
   ::= {pr1645v2TvTmplPGreMCH24PEntry 318767104}

pr1645v2TvTmplPGreMCH24PInDropFilter OBJECT-TYPE
   SYNTAX      Counter64
   MAX-ACCESS  read-only
   STATUS      current
   DESCRIPTION
      "Path: tunnels.performance.greTunnels.mibCounters.h24Performance.fInDiscardsFilter

       64 bit unsigned wrappable counter."
   ::= {pr1645v2TvTmplPGreMCH24PEntry 385875968}

pr1645v2TvTmplPGreMCH24PIfInBandwidth OBJECT-TYPE
   SYNTAX      Integer32
   MAX-ACCESS  read-only
   STATUS      current
   DESCRIPTION
      "Path: tunnels.performance.greTunnels.mibCounters.h24Performance.ifInBandwidth

       unit name = bps
       formula = 8 * ; 8 /"
   ::= {pr1645v2TvTmplPGreMCH24PEntry 268435456}

pr1645v2TvTmplPGreMCH24PIfOutOctets OBJECT-TYPE
   SYNTAX      Counter64
   MAX-ACCESS  read-only
   STATUS      current
   DESCRIPTION
      "Path: tunnels.performance.greTunnels.mibCounters.h24Performance.ifOutOctets

       64 bit unsigned wrappable counter."
   ::= {pr1645v2TvTmplPGreMCH24PEntry 167772160}

pr1645v2TvTmplPGreMCH24PIfOutUCPkts OBJECT-TYPE
   SYNTAX      Counter64
   MAX-ACCESS  read-only
   STATUS      current
   DESCRIPTION
      "Path: tunnels.performance.greTunnels.mibCounters.h24Performance.ifOutUcastPkts

       64 bit unsigned wrappable counter."
   ::= {pr1645v2TvTmplPGreMCH24PEntry 184549376}

pr1645v2TvTmplPGreMCH24PIfOutNUCPkts OBJECT-TYPE
   SYNTAX      Counter64
   MAX-ACCESS  read-only
   STATUS      current
   DESCRIPTION
      "Path: tunnels.performance.greTunnels.mibCounters.h24Performance.ifOutNUcastPkts

       64 bit unsigned wrappable counter."
   ::= {pr1645v2TvTmplPGreMCH24PEntry 201326592}

pr1645v2TvTmplPGreMCH24PIfOutBCPkts OBJECT-TYPE
   SYNTAX      Counter64
   MAX-ACCESS  read-only
   STATUS      current
   DESCRIPTION
      "Path: tunnels.performance.greTunnels.mibCounters.h24Performance.ifOutBcastPkts

       64 bit unsigned wrappable counter."
   ::= {pr1645v2TvTmplPGreMCH24PEntry 452984832}

pr1645v2TvTmplPGreMCH24PIfOutMCPkts OBJECT-TYPE
   SYNTAX      Counter64
   MAX-ACCESS  read-only
   STATUS      current
   DESCRIPTION
      "Path: tunnels.performance.greTunnels.mibCounters.h24Performance.ifOutMcastPkts

       64 bit unsigned wrappable counter."
   ::= {pr1645v2TvTmplPGreMCH24PEntry 469762048}

pr1645v2TvTmplPGreMCH24PIfOutDiscards OBJECT-TYPE
   SYNTAX      Counter64
   MAX-ACCESS  read-only
   STATUS      current
   DESCRIPTION
      "Path: tunnels.performance.greTunnels.mibCounters.h24Performance.ifOutDiscards

       64 bit unsigned wrappable counter."
   ::= {pr1645v2TvTmplPGreMCH24PEntry 218103808}

pr1645v2TvTmplPGreMCH24PIfOutErrors OBJECT-TYPE
   SYNTAX      Counter64
   MAX-ACCESS  read-only
   STATUS      current
   DESCRIPTION
      "Path: tunnels.performance.greTunnels.mibCounters.h24Performance.ifOutErrors

       64 bit unsigned wrappable counter."
   ::= {pr1645v2TvTmplPGreMCH24PEntry 234881024}

pr1645v2TvTmplPGreMCH24POutDropEx OBJECT-TYPE
   SYNTAX      Counter64
   MAX-ACCESS  read-only
   STATUS      current
   DESCRIPTION
      "Path: tunnels.performance.greTunnels.mibCounters.h24Performance.ifOutDropLevelExceeded

       64 bit unsigned wrappable counter."
   ::= {pr1645v2TvTmplPGreMCH24PEntry 352321536}

pr1645v2TvTmplPGreMCH24POutDropNoArp OBJECT-TYPE
   SYNTAX      Counter64
   MAX-ACCESS  read-only
   STATUS      current
   DESCRIPTION
      "Path: tunnels.performance.greTunnels.mibCounters.h24Performance.ifOutDiscardsNoArp

       64 bit unsigned wrappable counter."
   ::= {pr1645v2TvTmplPGreMCH24PEntry 369098752}

pr1645v2TvTmplPGreMCH24POutDropFilter OBJECT-TYPE
   SYNTAX      Counter64
   MAX-ACCESS  read-only
   STATUS      current
   DESCRIPTION
      "Path: tunnels.performance.greTunnels.mibCounters.h24Performance.ifOutDiscardsFilter

       64 bit unsigned wrappable counter."
   ::= {pr1645v2TvTmplPGreMCH24PEntry 402653184}

pr1645v2TvTmplPGreMCH24PIfOutBandwidth OBJECT-TYPE
   SYNTAX      Integer32
   MAX-ACCESS  read-only
   STATUS      current
   DESCRIPTION
      "Path: tunnels.performance.greTunnels.mibCounters.h24Performance.ifOutBandwidth

       unit name = bps
       formula = 8 * ; 8 /"
   ::= {pr1645v2TvTmplPGreMCH24PEntry 285212672}

pr1645v2TvTmplPGreMCH24PIfErrSec OBJECT-TYPE
   SYNTAX      Counter32
   MAX-ACCESS  read-only
   STATUS      current
   DESCRIPTION
      "Path: tunnels.performance.greTunnels.mibCounters.h24Performance.ifErrSec

       32 bit unsigned wrappable counter."
   ::= {pr1645v2TvTmplPGreMCH24PEntry 251658240}

pr1645v2TvTmplPGreMCD7P OBJECT-TYPE
   SYNTAX      SEQUENCE OF Pr1645v2TvTmplPGreMCD7PEntry
   MAX-ACCESS  not-accessible
   STATUS      current
   DESCRIPTION
      ""
   ::= {pr1645v2TvTmplPGre 41680896}

pr1645v2TvTmplPGreMCD7PEntry OBJECT-TYPE
   SYNTAX      Pr1645v2TvTmplPGreMCD7PEntry
   MAX-ACCESS  not-accessible
   STATUS      current
   DESCRIPTION
      ""
   INDEX      { pr1645v2TvTmplPGreTableIx,
                pr1645v2TvTmplPGreMCD7PTableIx }
   ::= {pr1645v2TvTmplPGreMCD7P 1}

Pr1645v2TvTmplPGreMCD7PEntry ::=
   SEQUENCE
      {
      pr1645v2TvTmplPGreMCD7PTableIx
         TableIndex,
      pr1645v2TvTmplPGreMCD7PSysUpTime
         TimeTicks,
      pr1645v2TvTmplPGreMCD7PIfUpTime
         TimeTicks,
      pr1645v2TvTmplPGreMCD7PIfStatChanges
         Counter32,
      pr1645v2TvTmplPGreMCD7PIfInOctets
         Counter64,
      pr1645v2TvTmplPGreMCD7PIfInUCPkts
         Counter64,
      pr1645v2TvTmplPGreMCD7PIfInNUCPkts
         Counter64,
      pr1645v2TvTmplPGreMCD7PIfInBCPkts
         Counter64,
      pr1645v2TvTmplPGreMCD7PIfInMCPkts
         Counter64,
      pr1645v2TvTmplPGreMCD7PIfInDiscards
         Counter64,
      pr1645v2TvTmplPGreMCD7PIfInErrors
         Counter64,
      pr1645v2TvTmplPGreMCD7PIfInUnkwn
         Counter64,
      pr1645v2TvTmplPGreMCD7PInDropEx
         Counter64,
      pr1645v2TvTmplPGreMCD7PInDropNoMac
         Counter64,
      pr1645v2TvTmplPGreMCD7PInDropNUCast
         Counter64,
      pr1645v2TvTmplPGreMCD7PInDropFilter
         Counter64,
      pr1645v2TvTmplPGreMCD7PIfInBandwidth
         Integer32,
      pr1645v2TvTmplPGreMCD7PIfOutOctets
         Counter64,
      pr1645v2TvTmplPGreMCD7PIfOutUCPkts
         Counter64,
      pr1645v2TvTmplPGreMCD7PIfOutNUCPkts
         Counter64,
      pr1645v2TvTmplPGreMCD7PIfOutBCPkts
         Counter64,
      pr1645v2TvTmplPGreMCD7PIfOutMCPkts
         Counter64,
      pr1645v2TvTmplPGreMCD7PIfOutDiscards
         Counter64,
      pr1645v2TvTmplPGreMCD7PIfOutErrors
         Counter64,
      pr1645v2TvTmplPGreMCD7POutDropEx
         Counter64,
      pr1645v2TvTmplPGreMCD7POutDropNoArp
         Counter64,
      pr1645v2TvTmplPGreMCD7POutDropFilter
         Counter64,
      pr1645v2TvTmplPGreMCD7PIfOutBandwidth
         Integer32,
      pr1645v2TvTmplPGreMCD7PIfErrSec
         Counter32
      }

pr1645v2TvTmplPGreMCD7PTableIx OBJECT-TYPE
   SYNTAX      TableIndex
   MAX-ACCESS  not-accessible
   STATUS      current
   DESCRIPTION
      ""
   ::= {pr1645v2TvTmplPGreMCD7PEntry 11}

pr1645v2TvTmplPGreMCD7PSysUpTime OBJECT-TYPE
   SYNTAX      TimeTicks
   MAX-ACCESS  read-only
   STATUS      current
   DESCRIPTION
      "Path: tunnels.performance.greTunnels.mibCounters.d7Performance.sysUpTime

       Time in centi-second."
   ::= {pr1645v2TvTmplPGreMCD7PEntry 16777216}

pr1645v2TvTmplPGreMCD7PIfUpTime OBJECT-TYPE
   SYNTAX      TimeTicks
   MAX-ACCESS  read-only
   STATUS      current
   DESCRIPTION
      "Path: tunnels.performance.greTunnels.mibCounters.d7Performance.ifUpTime

       Time in centi-second."
   ::= {pr1645v2TvTmplPGreMCD7PEntry 33554432}

pr1645v2TvTmplPGreMCD7PIfStatChanges OBJECT-TYPE
   SYNTAX      Counter32
   MAX-ACCESS  read-only
   STATUS      current
   DESCRIPTION
      "Path: tunnels.performance.greTunnels.mibCounters.d7Performance.ifStatusChanges

       32 bit unsigned wrappable counter."
   ::= {pr1645v2TvTmplPGreMCD7PEntry 50331648}

pr1645v2TvTmplPGreMCD7PIfInOctets OBJECT-TYPE
   SYNTAX      Counter64
   MAX-ACCESS  read-only
   STATUS      current
   DESCRIPTION
      "Path: tunnels.performance.greTunnels.mibCounters.d7Performance.ifInOctets

       64 bit unsigned wrappable counter."
   ::= {pr1645v2TvTmplPGreMCD7PEntry 67108864}

pr1645v2TvTmplPGreMCD7PIfInUCPkts OBJECT-TYPE
   SYNTAX      Counter64
   MAX-ACCESS  read-only
   STATUS      current
   DESCRIPTION
      "Path: tunnels.performance.greTunnels.mibCounters.d7Performance.ifInUcastPkts

       64 bit unsigned wrappable counter."
   ::= {pr1645v2TvTmplPGreMCD7PEntry 83886080}

pr1645v2TvTmplPGreMCD7PIfInNUCPkts OBJECT-TYPE
   SYNTAX      Counter64
   MAX-ACCESS  read-only
   STATUS      current
   DESCRIPTION
      "Path: tunnels.performance.greTunnels.mibCounters.d7Performance.ifInNUcastPkts

       64 bit unsigned wrappable counter."
   ::= {pr1645v2TvTmplPGreMCD7PEntry 100663296}

pr1645v2TvTmplPGreMCD7PIfInBCPkts OBJECT-TYPE
   SYNTAX      Counter64
   MAX-ACCESS  read-only
   STATUS      current
   DESCRIPTION
      "Path: tunnels.performance.greTunnels.mibCounters.d7Performance.ifInBcastPkts

       64 bit unsigned wrappable counter."
   ::= {pr1645v2TvTmplPGreMCD7PEntry 419430400}

pr1645v2TvTmplPGreMCD7PIfInMCPkts OBJECT-TYPE
   SYNTAX      Counter64
   MAX-ACCESS  read-only
   STATUS      current
   DESCRIPTION
      "Path: tunnels.performance.greTunnels.mibCounters.d7Performance.ifInMcastPkts

       64 bit unsigned wrappable counter."
   ::= {pr1645v2TvTmplPGreMCD7PEntry 436207616}

pr1645v2TvTmplPGreMCD7PIfInDiscards OBJECT-TYPE
   SYNTAX      Counter64
   MAX-ACCESS  read-only
   STATUS      current
   DESCRIPTION
      "Path: tunnels.performance.greTunnels.mibCounters.d7Performance.ifInDiscards

       64 bit unsigned wrappable counter."
   ::= {pr1645v2TvTmplPGreMCD7PEntry 117440512}

pr1645v2TvTmplPGreMCD7PIfInErrors OBJECT-TYPE
   SYNTAX      Counter64
   MAX-ACCESS  read-only
   STATUS      current
   DESCRIPTION
      "Path: tunnels.performance.greTunnels.mibCounters.d7Performance.ifInErrors

       64 bit unsigned wrappable counter."
   ::= {pr1645v2TvTmplPGreMCD7PEntry 134217728}

pr1645v2TvTmplPGreMCD7PIfInUnkwn OBJECT-TYPE
   SYNTAX      Counter64
   MAX-ACCESS  read-only
   STATUS      current
   DESCRIPTION
      "Path: tunnels.performance.greTunnels.mibCounters.d7Performance.ifInUnknownProtos

       64 bit unsigned wrappable counter."
   ::= {pr1645v2TvTmplPGreMCD7PEntry 150994944}

pr1645v2TvTmplPGreMCD7PInDropEx OBJECT-TYPE
   SYNTAX      Counter64
   MAX-ACCESS  read-only
   STATUS      current
   DESCRIPTION
      "Path: tunnels.performance.greTunnels.mibCounters.d7Performance.ifInDropLevelExceeded

       64 bit unsigned wrappable counter."
   ::= {pr1645v2TvTmplPGreMCD7PEntry 335544320}

pr1645v2TvTmplPGreMCD7PInDropNoMac OBJECT-TYPE
   SYNTAX      Counter64
   MAX-ACCESS  read-only
   STATUS      current
   DESCRIPTION
      "Path: tunnels.performance.greTunnels.mibCounters.d7Performance.fInDiscardsNoMacFit

       64 bit unsigned wrappable counter."
   ::= {pr1645v2TvTmplPGreMCD7PEntry 301989888}

pr1645v2TvTmplPGreMCD7PInDropNUCast OBJECT-TYPE
   SYNTAX      Counter64
   MAX-ACCESS  read-only
   STATUS      current
   DESCRIPTION
      "Path: tunnels.performance.greTunnels.mibCounters.d7Performance.fInDiscardsNUCast

       64 bit unsigned wrappable counter."
   ::= {pr1645v2TvTmplPGreMCD7PEntry 318767104}

pr1645v2TvTmplPGreMCD7PInDropFilter OBJECT-TYPE
   SYNTAX      Counter64
   MAX-ACCESS  read-only
   STATUS      current
   DESCRIPTION
      "Path: tunnels.performance.greTunnels.mibCounters.d7Performance.fInDiscardsFilter

       64 bit unsigned wrappable counter."
   ::= {pr1645v2TvTmplPGreMCD7PEntry 385875968}

pr1645v2TvTmplPGreMCD7PIfInBandwidth OBJECT-TYPE
   SYNTAX      Integer32
   MAX-ACCESS  read-only
   STATUS      current
   DESCRIPTION
      "Path: tunnels.performance.greTunnels.mibCounters.d7Performance.ifInBandwidth

       unit name = bps
       formula = 8 * ; 8 /"
   ::= {pr1645v2TvTmplPGreMCD7PEntry 268435456}

pr1645v2TvTmplPGreMCD7PIfOutOctets OBJECT-TYPE
   SYNTAX      Counter64
   MAX-ACCESS  read-only
   STATUS      current
   DESCRIPTION
      "Path: tunnels.performance.greTunnels.mibCounters.d7Performance.ifOutOctets

       64 bit unsigned wrappable counter."
   ::= {pr1645v2TvTmplPGreMCD7PEntry 167772160}

pr1645v2TvTmplPGreMCD7PIfOutUCPkts OBJECT-TYPE
   SYNTAX      Counter64
   MAX-ACCESS  read-only
   STATUS      current
   DESCRIPTION
      "Path: tunnels.performance.greTunnels.mibCounters.d7Performance.ifOutUcastPkts

       64 bit unsigned wrappable counter."
   ::= {pr1645v2TvTmplPGreMCD7PEntry 184549376}

pr1645v2TvTmplPGreMCD7PIfOutNUCPkts OBJECT-TYPE
   SYNTAX      Counter64
   MAX-ACCESS  read-only
   STATUS      current
   DESCRIPTION
      "Path: tunnels.performance.greTunnels.mibCounters.d7Performance.ifOutNUcastPkts

       64 bit unsigned wrappable counter."
   ::= {pr1645v2TvTmplPGreMCD7PEntry 201326592}

pr1645v2TvTmplPGreMCD7PIfOutBCPkts OBJECT-TYPE
   SYNTAX      Counter64
   MAX-ACCESS  read-only
   STATUS      current
   DESCRIPTION
      "Path: tunnels.performance.greTunnels.mibCounters.d7Performance.ifOutBcastPkts

       64 bit unsigned wrappable counter."
   ::= {pr1645v2TvTmplPGreMCD7PEntry 452984832}

pr1645v2TvTmplPGreMCD7PIfOutMCPkts OBJECT-TYPE
   SYNTAX      Counter64
   MAX-ACCESS  read-only
   STATUS      current
   DESCRIPTION
      "Path: tunnels.performance.greTunnels.mibCounters.d7Performance.ifOutMcastPkts

       64 bit unsigned wrappable counter."
   ::= {pr1645v2TvTmplPGreMCD7PEntry 469762048}

pr1645v2TvTmplPGreMCD7PIfOutDiscards OBJECT-TYPE
   SYNTAX      Counter64
   MAX-ACCESS  read-only
   STATUS      current
   DESCRIPTION
      "Path: tunnels.performance.greTunnels.mibCounters.d7Performance.ifOutDiscards

       64 bit unsigned wrappable counter."
   ::= {pr1645v2TvTmplPGreMCD7PEntry 218103808}

pr1645v2TvTmplPGreMCD7PIfOutErrors OBJECT-TYPE
   SYNTAX      Counter64
   MAX-ACCESS  read-only
   STATUS      current
   DESCRIPTION
      "Path: tunnels.performance.greTunnels.mibCounters.d7Performance.ifOutErrors

       64 bit unsigned wrappable counter."
   ::= {pr1645v2TvTmplPGreMCD7PEntry 234881024}

pr1645v2TvTmplPGreMCD7POutDropEx OBJECT-TYPE
   SYNTAX      Counter64
   MAX-ACCESS  read-only
   STATUS      current
   DESCRIPTION
      "Path: tunnels.performance.greTunnels.mibCounters.d7Performance.ifOutDropLevelExceeded

       64 bit unsigned wrappable counter."
   ::= {pr1645v2TvTmplPGreMCD7PEntry 352321536}

pr1645v2TvTmplPGreMCD7POutDropNoArp OBJECT-TYPE
   SYNTAX      Counter64
   MAX-ACCESS  read-only
   STATUS      current
   DESCRIPTION
      "Path: tunnels.performance.greTunnels.mibCounters.d7Performance.ifOutDiscardsNoArp

       64 bit unsigned wrappable counter."
   ::= {pr1645v2TvTmplPGreMCD7PEntry 369098752}

pr1645v2TvTmplPGreMCD7POutDropFilter OBJECT-TYPE
   SYNTAX      Counter64
   MAX-ACCESS  read-only
   STATUS      current
   DESCRIPTION
      "Path: tunnels.performance.greTunnels.mibCounters.d7Performance.ifOutDiscardsFilter

       64 bit unsigned wrappable counter."
   ::= {pr1645v2TvTmplPGreMCD7PEntry 402653184}

pr1645v2TvTmplPGreMCD7PIfOutBandwidth OBJECT-TYPE
   SYNTAX      Integer32
   MAX-ACCESS  read-only
   STATUS      current
   DESCRIPTION
      "Path: tunnels.performance.greTunnels.mibCounters.d7Performance.ifOutBandwidth

       unit name = bps
       formula = 8 * ; 8 /"
   ::= {pr1645v2TvTmplPGreMCD7PEntry 285212672}

pr1645v2TvTmplPGreMCD7PIfErrSec OBJECT-TYPE
   SYNTAX      Counter32
   MAX-ACCESS  read-only
   STATUS      current
   DESCRIPTION
      "Path: tunnels.performance.greTunnels.mibCounters.d7Performance.ifErrSec

       32 bit unsigned wrappable counter."
   ::= {pr1645v2TvTmplPGreMCD7PEntry 251658240}

pr1645v2TvTmplPGreInPQs OBJECT-TYPE
   SYNTAX      SEQUENCE OF Pr1645v2TvTmplPGreInPQsEntry
   MAX-ACCESS  not-accessible
   STATUS      current
   DESCRIPTION
      ""
   ::= {pr1645v2TvTmplPGre 100663296}

pr1645v2TvTmplPGreInPQsEntry OBJECT-TYPE
   SYNTAX      Pr1645v2TvTmplPGreInPQsEntry
   MAX-ACCESS  not-accessible
   STATUS      current
   DESCRIPTION
      ""
   INDEX      { pr1645v2TvTmplPGreTableIx,
                pr1645v2TvTmplPGreInPQsTableIx }
   ::= {pr1645v2TvTmplPGreInPQs 1}

Pr1645v2TvTmplPGreInPQsEntry ::=
   SEQUENCE
      {
      pr1645v2TvTmplPGreInPQsTableIx
         TableIndex,
      pr1645v2TvTmplPGreInPQsName
         INTEGER,
      pr1645v2TvTmplPGreInPQsLength
         Integer32,
      pr1645v2TvTmplPGreInPQsOctetLength
         Integer32,
      pr1645v2TvTmplPGreInPQsRedLength
         Integer32,
      pr1645v2TvTmplPGreInPQsPacketsTotal
         Counter64,
      pr1645v2TvTmplPGreInPQsPacketsDirectTx
         Counter64,
      pr1645v2TvTmplPGreInPQsPacketsQueued
         Counter64,
      pr1645v2TvTmplPGreInPQsPacketsDropped
         Counter64,
      pr1645v2TvTmplPGreInPQsPacketsRedDropped
         Counter64,
      pr1645v2TvTmplPGreInPQsPacketsCirTx
         Counter64,
      pr1645v2TvTmplPGreInPQsPacketsEirTx
         Counter64,
      pr1645v2TvTmplPGreInPQsPacketsViolateTx
         Counter64,
      pr1645v2TvTmplPGreInPQsOctetsTotal
         Counter64,
      pr1645v2TvTmplPGreInPQsOctetsDirectTx
         Counter64,
      pr1645v2TvTmplPGreInPQsOctetsQueued
         Counter64,
      pr1645v2TvTmplPGreInPQsOctetsDropped
         Counter64,
      pr1645v2TvTmplPGreInPQsOctetsRedDropped
         Counter64,
      pr1645v2TvTmplPGreInPQsOctetsCirTx
         Counter64,
      pr1645v2TvTmplPGreInPQsOctetsEirTx
         Counter64,
      pr1645v2TvTmplPGreInPQsOctetsViolateTx
         Counter64,
      pr1645v2TvTmplPGreInPQsOctetsBandwidth15sec
         Integer32,
      pr1645v2TvTmplPGreInPQsOctetsBandwidth30sec
         Integer32,
      pr1645v2TvTmplPGreInPQsOctetsBandwidth1min
         Integer32,
      pr1645v2TvTmplPGreInPQsOctetsBandwidth2min
         Integer32,
      pr1645v2TvTmplPGreInPQsOctetsBandwidth5min
         Integer32
      }

pr1645v2TvTmplPGreInPQsTableIx OBJECT-TYPE
   SYNTAX      TableIndex
   MAX-ACCESS  not-accessible
   STATUS      current
   DESCRIPTION
      ""
   ::= {pr1645v2TvTmplPGreInPQsEntry 11}

pr1645v2TvTmplPGreInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.greTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPGreInPQsEntry 16777216}

pr1645v2TvTmplPGreInPQsLength OBJECT-TYPE
   SYNTAX      Integer32
   MAX-ACCESS  read-only
   STATUS      current
   DESCRIPTION
      "Path: tunnels.performance.greTunnels.inPriorityQueues.length"
   ::= {pr1645v2TvTmplPGreInPQsEntry 33554432}

pr1645v2TvTmplPGreInPQsOctetLength OBJECT-TYPE
   SYNTAX      Integer32
   MAX-ACCESS  read-only
   STATUS      current
   DESCRIPTION
      "Path: tunnels.performance.greTunnels.inPriorityQueues.octetLength"
   ::= {pr1645v2TvTmplPGreInPQsEntry 150994944}

pr1645v2TvTmplPGreInPQsRedLength OBJECT-TYPE
   SYNTAX      Integer32
   MAX-ACCESS  read-only
   STATUS      current
   DESCRIPTION
      "Path: tunnels.performance.greTunnels.inPriorityQueues.redLength"
   ::= {pr1645v2TvTmplPGreInPQsEntry 134217728}

pr1645v2TvTmplPGreInPQsPacketsTotal OBJECT-TYPE
   SYNTAX      Counter64
   MAX-ACCESS  read-only
   STATUS      current
   DESCRIPTION
      "Path: tunnels.performance.greTunnels.inPriorityQueues.packets.total

       64 bit unsigned wrappable counter."
   ::= {pr1645v2TvTmplPGreInPQsEntry 50790400}

pr1645v2TvTmplPGreInPQsPacketsDirectTx OBJECT-TYPE
   SYNTAX      Counter64
   MAX-ACCESS  read-only
   STATUS      current
   DESCRIPTION
      "Path: tunnels.performance.greTunnels.inPriorityQueues.packets.directTx

       64 bit unsigned wrappable counter."
   ::= {pr1645v2TvTmplPGreInPQsEntry 50397184}

pr1645v2TvTmplPGreInPQsPacketsQueued OBJECT-TYPE
   SYNTAX      Counter64
   MAX-ACCESS  read-only
   STATUS      current
   DESCRIPTION
      "Path: tunnels.performance.greTunnels.inPriorityQueues.packets.queued

       64 bit unsigned wrappable counter."
   ::= {pr1645v2TvTmplPGreInPQsEntry 50462720}

pr1645v2TvTmplPGreInPQsPacketsDropped OBJECT-TYPE
   SYNTAX      Counter64
   MAX-ACCESS  read-only
   STATUS      current
   DESCRIPTION
      "Path: tunnels.performance.greTunnels.inPriorityQueues.packets.dropped

       64 bit unsigned wrappable counter."
   ::= {pr1645v2TvTmplPGreInPQsEntry 50528256}

pr1645v2TvTmplPGreInPQsPacketsRedDropped OBJECT-TYPE
   SYNTAX      Counter64
   MAX-ACCESS  read-only
   STATUS      current
   DESCRIPTION
      "Path: tunnels.performance.greTunnels.inPriorityQueues.packets.redDropped

       64 bit unsigned wrappable counter."
   ::= {pr1645v2TvTmplPGreInPQsEntry 50724864}

pr1645v2TvTmplPGreInPQsPacketsCirTx OBJECT-TYPE
   SYNTAX      Counter64
   MAX-ACCESS  read-only
   STATUS      current
   DESCRIPTION
      "Path: tunnels.performance.greTunnels.inPriorityQueues.packets.cirTx

       64 bit unsigned wrappable counter."
   ::= {pr1645v2TvTmplPGreInPQsEntry 50593792}

pr1645v2TvTmplPGreInPQsPacketsEirTx OBJECT-TYPE
   SYNTAX      Counter64
   MAX-ACCESS  read-only
   STATUS      current
   DESCRIPTION
      "Path: tunnels.performance.greTunnels.inPriorityQueues.packets.eirTx

       64 bit unsigned wrappable counter."
   ::= {pr1645v2TvTmplPGreInPQsEntry 50659328}

pr1645v2TvTmplPGreInPQsPacketsViolateTx OBJECT-TYPE
   SYNTAX      Counter64
   MAX-ACCESS  read-only
   STATUS      current
   DESCRIPTION
      "Path: tunnels.performance.greTunnels.inPriorityQueues.packets.violateTx

       64 bit unsigned wrappable counter."
   ::= {pr1645v2TvTmplPGreInPQsEntry 50855936}

pr1645v2TvTmplPGreInPQsOctetsTotal OBJECT-TYPE
   SYNTAX      Counter64
   MAX-ACCESS  read-only
   STATUS      current
   DESCRIPTION
      "Path: tunnels.performance.greTunnels.inPriorityQueues.octets.total

       64 bit unsigned wrappable counter."
   ::= {pr1645v2TvTmplPGreInPQsEntry 67567616}

pr1645v2TvTmplPGreInPQsOctetsDirectTx OBJECT-TYPE
   SYNTAX      Counter64
   MAX-ACCESS  read-only
   STATUS      current
   DESCRIPTION
      "Path: tunnels.performance.greTunnels.inPriorityQueues.octets.directTx

       64 bit unsigned wrappable counter."
   ::= {pr1645v2TvTmplPGreInPQsEntry 67174400}

pr1645v2TvTmplPGreInPQsOctetsQueued OBJECT-TYPE
   SYNTAX      Counter64
   MAX-ACCESS  read-only
   STATUS      current
   DESCRIPTION
      "Path: tunnels.performance.greTunnels.inPriorityQueues.octets.queued

       64 bit unsigned wrappable counter."
   ::= {pr1645v2TvTmplPGreInPQsEntry 67239936}

pr1645v2TvTmplPGreInPQsOctetsDropped OBJECT-TYPE
   SYNTAX      Counter64
   MAX-ACCESS  read-only
   STATUS      current
   DESCRIPTION
      "Path: tunnels.performance.greTunnels.inPriorityQueues.octets.dropped

       64 bit unsigned wrappable counter."
   ::= {pr1645v2TvTmplPGreInPQsEntry 67305472}

pr1645v2TvTmplPGreInPQsOctetsRedDropped OBJECT-TYPE
   SYNTAX      Counter64
   MAX-ACCESS  read-only
   STATUS      current
   DESCRIPTION
      "Path: tunnels.performance.greTunnels.inPriorityQueues.octets.redDropped

       64 bit unsigned wrappable counter."
   ::= {pr1645v2TvTmplPGreInPQsEntry 67502080}

pr1645v2TvTmplPGreInPQsOctetsCirTx OBJECT-TYPE
   SYNTAX      Counter64
   MAX-ACCESS  read-only
   STATUS      current
   DESCRIPTION
      "Path: tunnels.performance.greTunnels.inPriorityQueues.octets.cirTx

       64 bit unsigned wrappable counter."
   ::= {pr1645v2TvTmplPGreInPQsEntry 67371008}

pr1645v2TvTmplPGreInPQsOctetsEirTx OBJECT-TYPE
   SYNTAX      Counter64
   MAX-ACCESS  read-only
   STATUS      current
   DESCRIPTION
      "Path: tunnels.performance.greTunnels.inPriorityQueues.octets.eirTx

       64 bit unsigned wrappable counter."
   ::= {pr1645v2TvTmplPGreInPQsEntry 67436544}

pr1645v2TvTmplPGreInPQsOctetsViolateTx OBJECT-TYPE
   SYNTAX      Counter64
   MAX-ACCESS  read-only
   STATUS      current
   DESCRIPTION
      "Path: tunnels.performance.greTunnels.inPriorityQueues.octets.violateTx

       64 bit unsigned wrappable counter."
   ::= {pr1645v2TvTmplPGreInPQsEntry 67633152}

pr1645v2TvTmplPGreInPQsOctetsBandwidth15sec OBJECT-TYPE
   SYNTAX      Integer32
   MAX-ACCESS  read-only
   STATUS      current
   DESCRIPTION
      "Path: tunnels.performance.greTunnels.inPriorityQueues.octets.bandwidth.15sec

       unit name = bps
       formula = 8 * ; 8 /"
   ::= {pr1645v2TvTmplPGreInPQsEntry 70386944}

pr1645v2TvTmplPGreInPQsOctetsBandwidth30sec OBJECT-TYPE
   SYNTAX      Integer32
   MAX-ACCESS  read-only
   STATUS      current
   DESCRIPTION
      "Path: tunnels.performance.greTunnels.inPriorityQueues.octets.bandwidth.30sec

       unit name = bps
       formula = 8 * ; 8 /"
   ::= {pr1645v2TvTmplPGreInPQsEntry 70388224}

pr1645v2TvTmplPGreInPQsOctetsBandwidth1min OBJECT-TYPE
   SYNTAX      Integer32
   MAX-ACCESS  read-only
   STATUS      current
   DESCRIPTION
      "Path: tunnels.performance.greTunnels.inPriorityQueues.octets.bandwidth.1min

       unit name = bps
       formula = 8 * ; 8 /"
   ::= {pr1645v2TvTmplPGreInPQsEntry 70390784}

pr1645v2TvTmplPGreInPQsOctetsBandwidth2min OBJECT-TYPE
   SYNTAX      Integer32
   MAX-ACCESS  read-only
   STATUS      current
   DESCRIPTION
      "Path: tunnels.performance.greTunnels.inPriorityQueues.octets.bandwidth.2min

       unit name = bps
       formula = 8 * ; 8 /"
   ::= {pr1645v2TvTmplPGreInPQsEntry 70395904}

pr1645v2TvTmplPGreInPQsOctetsBandwidth5min OBJECT-TYPE
   SYNTAX      Integer32
   MAX-ACCESS  read-only
   STATUS      current
   DESCRIPTION
      "Path: tunnels.performance.greTunnels.inPriorityQueues.octets.bandwidth.5min

       unit name = bps
       formula = 8 * ; 8 /"
   ::= {pr1645v2TvTmplPGreInPQsEntry 70411264}

pr1645v2TvTmplPGreInPQsH2Performance OBJECT-TYPE
   SYNTAX      SEQUENCE OF Pr1645v2TvTmplPGreInPQsH2PerformanceEntry
   MAX-ACCESS  not-accessible
   STATUS      current
   DESCRIPTION
      ""
   ::= {pr1645v2TvTmplPGre 100990976}

pr1645v2TvTmplPGreInPQsH2PerformanceEntry OBJECT-TYPE
   SYNTAX      Pr1645v2TvTmplPGreInPQsH2PerformanceEntry
   MAX-ACCESS  not-accessible
   STATUS      current
   DESCRIPTION
      ""
   INDEX      { pr1645v2TvTmplPGreTableIx,
                pr1645v2TvTmplPGreInPQsTableIx,
                pr1645v2TvTmplPGreInPQsH2PerformanceTableIx }
   ::= {pr1645v2TvTmplPGreInPQsH2Performance 1}

Pr1645v2TvTmplPGreInPQsH2PerformanceEntry ::=
   SEQUENCE
      {
      pr1645v2TvTmplPGreInPQsH2PerformanceTableIx
         TableIndex,
      pr1645v2TvTmplPGreInPQsH2PerformanceSysUpTime
         TimeTicks,
      pr1645v2TvTmplPGreInPQsH2PerformanceTotPkts
         Counter64,
      pr1645v2TvTmplPGreInPQsH2PerformanceDirTxPkts
         Counter64,
      pr1645v2TvTmplPGreInPQsH2PerformanceQdPkts
         Counter64,
      pr1645v2TvTmplPGreInPQsH2PerformanceDropPkts
         Counter64,
      pr1645v2TvTmplPGreInPQsH2PerformanceRDropPkts
         Counter64,
      pr1645v2TvTmplPGreInPQsH2PerformanceCirTxPkts
         Counter64,
      pr1645v2TvTmplPGreInPQsH2PerformanceEirTxPkts
         Counter64,
      pr1645v2TvTmplPGreInPQsH2PerformanceViolTxPkts
         Counter64,
      pr1645v2TvTmplPGreInPQsH2PerformanceTotOcts
         Counter64,
      pr1645v2TvTmplPGreInPQsH2PerformanceDirTxOcts
         Counter64,
      pr1645v2TvTmplPGreInPQsH2PerformanceQdOcts
         Counter64,
      pr1645v2TvTmplPGreInPQsH2PerformanceDropOcts
         Counter64,
      pr1645v2TvTmplPGreInPQsH2PerformanceRDropOcts
         Counter64,
      pr1645v2TvTmplPGreInPQsH2PerformanceCirTxOcts
         Counter64,
      pr1645v2TvTmplPGreInPQsH2PerformanceEirTxOcts
         Counter64,
      pr1645v2TvTmplPGreInPQsH2PerformanceViolTxOcts
         Counter64,
      pr1645v2TvTmplPGreInPQsH2PerformanceBandwidth
         Integer32
      }

pr1645v2TvTmplPGreInPQsH2PerformanceTableIx OBJECT-TYPE
   SYNTAX      TableIndex
   MAX-ACCESS  not-accessible
   STATUS      current
   DESCRIPTION
      ""
   ::= {pr1645v2TvTmplPGreInPQsH2PerformanceEntry 11}

pr1645v2TvTmplPGreInPQsH2PerformanceSysUpTime OBJECT-TYPE
   SYNTAX      TimeTicks
   MAX-ACCESS  read-only
   STATUS      current
   DESCRIPTION
      "Path: tunnels.performance.greTunnels.inPriorityQueues.h2Performance.sysUpTime

       Time in centi-second."
   ::= {pr1645v2TvTmplPGreInPQsH2PerformanceEntry 16777216}

pr1645v2TvTmplPGreInPQsH2PerformanceTotPkts OBJECT-TYPE
   SYNTAX      Counter64
   MAX-ACCESS  read-only
   STATUS      current
   DESCRIPTION
      "Path: tunnels.performance.greTunnels.inPriorityQueues.h2Performance.totalPkts

       64 bit unsigned wrappable counter."
   ::= {pr1645v2TvTmplPGreInPQsH2PerformanceEntry 234881024}

pr1645v2TvTmplPGreInPQsH2PerformanceDirTxPkts OBJECT-TYPE
   SYNTAX      Counter64
   MAX-ACCESS  read-only
   STATUS      current
   DESCRIPTION
      "Path: tunnels.performance.greTunnels.inPriorityQueues.h2Performance.directTxPkts

       64 bit unsigned wrappable counter."
   ::= {pr1645v2TvTmplPGreInPQsH2PerformanceEntry 33554432}

pr1645v2TvTmplPGreInPQsH2PerformanceQdPkts OBJECT-TYPE
   SYNTAX      Counter64
   MAX-ACCESS  read-only
   STATUS      current
   DESCRIPTION
      "Path: tunnels.performance.greTunnels.inPriorityQueues.h2Performance.queuedPkts

       64 bit unsigned wrappable counter."
   ::= {pr1645v2TvTmplPGreInPQsH2PerformanceEntry 50331648}

pr1645v2TvTmplPGreInPQsH2PerformanceDropPkts OBJECT-TYPE
   SYNTAX      Counter64
   MAX-ACCESS  read-only
   STATUS      current
   DESCRIPTION
      "Path: tunnels.performance.greTunnels.inPriorityQueues.h2Performance.droppedPkts

       64 bit unsigned wrappable counter."
   ::= {pr1645v2TvTmplPGreInPQsH2PerformanceEntry 67108864}

pr1645v2TvTmplPGreInPQsH2PerformanceRDropPkts OBJECT-TYPE
   SYNTAX      Counter64
   MAX-ACCESS  read-only
   STATUS      current
   DESCRIPTION
      "Path: tunnels.performance.greTunnels.inPriorityQueues.h2Performance.redDroppedPkts

       64 bit unsigned wrappable counter."
   ::= {pr1645v2TvTmplPGreInPQsH2PerformanceEntry 201326592}

pr1645v2TvTmplPGreInPQsH2PerformanceCirTxPkts OBJECT-TYPE
   SYNTAX      Counter64
   MAX-ACCESS  read-only
   STATUS      current
   DESCRIPTION
      "Path: tunnels.performance.greTunnels.inPriorityQueues.h2Performance.cirTxPkts

       64 bit unsigned wrappable counter."
   ::= {pr1645v2TvTmplPGreInPQsH2PerformanceEntry 83886080}

pr1645v2TvTmplPGreInPQsH2PerformanceEirTxPkts OBJECT-TYPE
   SYNTAX      Counter64
   MAX-ACCESS  read-only
   STATUS      current
   DESCRIPTION
      "Path: tunnels.performance.greTunnels.inPriorityQueues.h2Performance.eirTxPkts

       64 bit unsigned wrappable counter."
   ::= {pr1645v2TvTmplPGreInPQsH2PerformanceEntry 100663296}

pr1645v2TvTmplPGreInPQsH2PerformanceViolTxPkts OBJECT-TYPE
   SYNTAX      Counter64
   MAX-ACCESS  read-only
   STATUS      current
   DESCRIPTION
      "Path: tunnels.performance.greTunnels.inPriorityQueues.h2Performance.violateTxPkts

       64 bit unsigned wrappable counter."
   ::= {pr1645v2TvTmplPGreInPQsH2PerformanceEntry 301989888}

pr1645v2TvTmplPGreInPQsH2PerformanceTotOcts OBJECT-TYPE
   SYNTAX      Counter64
   MAX-ACCESS  read-only
   STATUS      current
   DESCRIPTION
      "Path: tunnels.performance.greTunnels.inPriorityQueues.h2Performance.totalOctets

       64 bit unsigned wrappable counter."
   ::= {pr1645v2TvTmplPGreInPQsH2PerformanceEntry 251658240}

pr1645v2TvTmplPGreInPQsH2PerformanceDirTxOcts OBJECT-TYPE
   SYNTAX      Counter64
   MAX-ACCESS  read-only
   STATUS      current
   DESCRIPTION
      "Path: tunnels.performance.greTunnels.inPriorityQueues.h2Performance.directTxOctets

       64 bit unsigned wrappable counter."
   ::= {pr1645v2TvTmplPGreInPQsH2PerformanceEntry 117440512}

pr1645v2TvTmplPGreInPQsH2PerformanceQdOcts OBJECT-TYPE
   SYNTAX      Counter64
   MAX-ACCESS  read-only
   STATUS      current
   DESCRIPTION
      "Path: tunnels.performance.greTunnels.inPriorityQueues.h2Performance.queuedOctets

       64 bit unsigned wrappable counter."
   ::= {pr1645v2TvTmplPGreInPQsH2PerformanceEntry 134217728}

pr1645v2TvTmplPGreInPQsH2PerformanceDropOcts OBJECT-TYPE
   SYNTAX      Counter64
   MAX-ACCESS  read-only
   STATUS      current
   DESCRIPTION
      "Path: tunnels.performance.greTunnels.inPriorityQueues.h2Performance.droppedOctets

       64 bit unsigned wrappable counter."
   ::= {pr1645v2TvTmplPGreInPQsH2PerformanceEntry 150994944}

pr1645v2TvTmplPGreInPQsH2PerformanceRDropOcts OBJECT-TYPE
   SYNTAX      Counter64
   MAX-ACCESS  read-only
   STATUS      current
   DESCRIPTION
      "Path: tunnels.performance.greTunnels.inPriorityQueues.h2Performance.redDroppedOctets

       64 bit unsigned wrappable counter."
   ::= {pr1645v2TvTmplPGreInPQsH2PerformanceEntry 218103808}

pr1645v2TvTmplPGreInPQsH2PerformanceCirTxOcts OBJECT-TYPE
   SYNTAX      Counter64
   MAX-ACCESS  read-only
   STATUS      current
   DESCRIPTION
      "Path: tunnels.performance.greTunnels.inPriorityQueues.h2Performance.cirTxOctets

       64 bit unsigned wrappable counter."
   ::= {pr1645v2TvTmplPGreInPQsH2PerformanceEntry 167772160}

pr1645v2TvTmplPGreInPQsH2PerformanceEirTxOcts OBJECT-TYPE
   SYNTAX      Counter64
   MAX-ACCESS  read-only
   STATUS      current
   DESCRIPTION
      "Path: tunnels.performance.greTunnels.inPriorityQueues.h2Performance.eirTxOctets

       64 bit unsigned wrappable counter."
   ::= {pr1645v2TvTmplPGreInPQsH2PerformanceEntry 184549376}

pr1645v2TvTmplPGreInPQsH2PerformanceViolTxOcts OBJECT-TYPE
   SYNTAX      Counter64
   MAX-ACCESS  read-only
   STATUS      current
   DESCRIPTION
      "Path: tunnels.performance.greTunnels.inPriorityQueues.h2Performance.violateTxOctets

       64 bit unsigned wrappable counter."
   ::= {pr1645v2TvTmplPGreInPQsH2PerformanceEntry 318767104}

pr1645v2TvTmplPGreInPQsH2PerformanceBandwidth OBJECT-TYPE
   SYNTAX      Integer32
   MAX-ACCESS  read-only
   STATUS      current
   DESCRIPTION
      "Path: tunnels.performance.greTunnels.inPriorityQueues.h2Performance.bandwidth

       unit name = bps
       formula = 8 * ; 8 /"
   ::= {pr1645v2TvTmplPGreInPQsH2PerformanceEntry 268435456}

pr1645v2TvTmplPGreInPQsH24Performance OBJECT-TYPE
   SYNTAX      SEQUENCE OF Pr1645v2TvTmplPGreInPQsH24PerformanceEntry
   MAX-ACCESS  not-accessible
   STATUS      current
   DESCRIPTION
      ""
   ::= {pr1645v2TvTmplPGre 101056512}

pr1645v2TvTmplPGreInPQsH24PerformanceEntry OBJECT-TYPE
   SYNTAX      Pr1645v2TvTmplPGreInPQsH24PerformanceEntry
   MAX-ACCESS  not-accessible
   STATUS      current
   DESCRIPTION
      ""
   INDEX      { pr1645v2TvTmplPGreTableIx,
                pr1645v2TvTmplPGreInPQsTableIx,
                pr1645v2TvTmplPGreInPQsH24PerformanceTableIx }
   ::= {pr1645v2TvTmplPGreInPQsH24Performance 1}

Pr1645v2TvTmplPGreInPQsH24PerformanceEntry ::=
   SEQUENCE
      {
      pr1645v2TvTmplPGreInPQsH24PerformanceTableIx
         TableIndex,
      pr1645v2TvTmplPGreInPQsH24PerformanceSysUpTime
         TimeTicks,
      pr1645v2TvTmplPGreInPQsH24PerformanceTotPkts
         Counter64,
      pr1645v2TvTmplPGreInPQsH24PerformanceDirTxPkts
         Counter64,
      pr1645v2TvTmplPGreInPQsH24PerformanceQdPkts
         Counter64,
      pr1645v2TvTmplPGreInPQsH24PerformanceDropPkts
         Counter64,
      pr1645v2TvTmplPGreInPQsH24PerformanceRDropPkts
         Counter64,
      pr1645v2TvTmplPGreInPQsH24PerformanceCirTxPkts
         Counter64,
      pr1645v2TvTmplPGreInPQsH24PerformanceEirTxPkts
         Counter64,
      pr1645v2TvTmplPGreInPQsH24PerformanceViolTxPkts
         Counter64,
      pr1645v2TvTmplPGreInPQsH24PerformanceTotOcts
         Counter64,
      pr1645v2TvTmplPGreInPQsH24PerformanceDirTxOcts
         Counter64,
      pr1645v2TvTmplPGreInPQsH24PerformanceQdOcts
         Counter64,
      pr1645v2TvTmplPGreInPQsH24PerformanceDropOcts
         Counter64,
      pr1645v2TvTmplPGreInPQsH24PerformanceRDropOcts
         Counter64,
      pr1645v2TvTmplPGreInPQsH24PerformanceCirTxOcts
         Counter64,
      pr1645v2TvTmplPGreInPQsH24PerformanceEirTxOcts
         Counter64,
      pr1645v2TvTmplPGreInPQsH24PerformanceViolTxOcts
         Counter64,
      pr1645v2TvTmplPGreInPQsH24PerformanceBandwidth
         Integer32
      }

pr1645v2TvTmplPGreInPQsH24PerformanceTableIx OBJECT-TYPE
   SYNTAX      TableIndex
   MAX-ACCESS  not-accessible
   STATUS      current
   DESCRIPTION
      ""
   ::= {pr1645v2TvTmplPGreInPQsH24PerformanceEntry 11}

pr1645v2TvTmplPGreInPQsH24PerformanceSysUpTime OBJECT-TYPE
   SYNTAX      TimeTicks
   MAX-ACCESS  read-only
   STATUS      current
   DESCRIPTION
      "Path: tunnels.performance.greTunnels.inPriorityQueues.h24Performance.sysUpTime

       Time in centi-second."
   ::= {pr1645v2TvTmplPGreInPQsH24PerformanceEntry 16777216}

pr1645v2TvTmplPGreInPQsH24PerformanceTotPkts OBJECT-TYPE
   SYNTAX      Counter64
   MAX-ACCESS  read-only
   STATUS      current
   DESCRIPTION
      "Path: tunnels.performance.greTunnels.inPriorityQueues.h24Performance.totalPkts

       64 bit unsigned wrappable counter."
   ::= {pr1645v2TvTmplPGreInPQsH24PerformanceEntry 234881024}

pr1645v2TvTmplPGreInPQsH24PerformanceDirTxPkts OBJECT-TYPE
   SYNTAX      Counter64
   MAX-ACCESS  read-only
   STATUS      current
   DESCRIPTION
      "Path: tunnels.performance.greTunnels.inPriorityQueues.h24Performance.directTxPkts

       64 bit unsigned wrappable counter."
   ::= {pr1645v2TvTmplPGreInPQsH24PerformanceEntry 33554432}

pr1645v2TvTmplPGreInPQsH24PerformanceQdPkts OBJECT-TYPE
   SYNTAX      Counter64
   MAX-ACCESS  read-only
   STATUS      current
   DESCRIPTION
      "Path: tunnels.performance.greTunnels.inPriorityQueues.h24Performance.queuedPkts

       64 bit unsigned wrappable counter."
   ::= {pr1645v2TvTmplPGreInPQsH24PerformanceEntry 50331648}

pr1645v2TvTmplPGreInPQsH24PerformanceDropPkts OBJECT-TYPE
   SYNTAX      Counter64
   MAX-ACCESS  read-only
   STATUS      current
   DESCRIPTION
      "Path: tunnels.performance.greTunnels.inPriorityQueues.h24Performance.droppedPkts

       64 bit unsigned wrappable counter."
   ::= {pr1645v2TvTmplPGreInPQsH24PerformanceEntry 67108864}

pr1645v2TvTmplPGreInPQsH24PerformanceRDropPkts OBJECT-TYPE
   SYNTAX      Counter64
   MAX-ACCESS  read-only
   STATUS      current
   DESCRIPTION
      "Path: tunnels.performance.greTunnels.inPriorityQueues.h24Performance.redDroppedPkts

       64 bit unsigned wrappable counter."
   ::= {pr1645v2TvTmplPGreInPQsH24PerformanceEntry 201326592}

pr1645v2TvTmplPGreInPQsH24PerformanceCirTxPkts OBJECT-TYPE
   SYNTAX      Counter64
   MAX-ACCESS  read-only
   STATUS      current
   DESCRIPTION
      "Path: tunnels.performance.greTunnels.inPriorityQueues.h24Performance.cirTxPkts

       64 bit unsigned wrappable counter."
   ::= {pr1645v2TvTmplPGreInPQsH24PerformanceEntry 83886080}

pr1645v2TvTmplPGreInPQsH24PerformanceEirTxPkts OBJECT-TYPE
   SYNTAX      Counter64
   MAX-ACCESS  read-only
   STATUS      current
   DESCRIPTION
      "Path: tunnels.performance.greTunnels.inPriorityQueues.h24Performance.eirTxPkts

       64 bit unsigned wrappable counter."
   ::= {pr1645v2TvTmplPGreInPQsH24PerformanceEntry 100663296}

pr1645v2TvTmplPGreInPQsH24PerformanceViolTxPkts OBJECT-TYPE
   SYNTAX      Counter64
   MAX-ACCESS  read-only
   STATUS      current
   DESCRIPTION
      "Path: tunnels.performance.greTunnels.inPriorityQueues.h24Performance.violateTxPkts

       64 bit unsigned wrappable counter."
   ::= {pr1645v2TvTmplPGreInPQsH24PerformanceEntry 301989888}

pr1645v2TvTmplPGreInPQsH24PerformanceTotOcts OBJECT-TYPE
   SYNTAX      Counter64
   MAX-ACCESS  read-only
   STATUS      current
   DESCRIPTION
      "Path: tunnels.performance.greTunnels.inPriorityQueues.h24Performance.totalOctets

       64 bit unsigned wrappable counter."
   ::= {pr1645v2TvTmplPGreInPQsH24PerformanceEntry 251658240}

pr1645v2TvTmplPGreInPQsH24PerformanceDirTxOcts OBJECT-TYPE
   SYNTAX      Counter64
   MAX-ACCESS  read-only
   STATUS      current
   DESCRIPTION
      "Path: tunnels.performance.greTunnels.inPriorityQueues.h24Performance.directTxOctets

       64 bit unsigned wrappable counter."
   ::= {pr1645v2TvTmplPGreInPQsH24PerformanceEntry 117440512}

pr1645v2TvTmplPGreInPQsH24PerformanceQdOcts OBJECT-TYPE
   SYNTAX      Counter64
   MAX-ACCESS  read-only
   STATUS      current
   DESCRIPTION
      "Path: tunnels.performance.greTunnels.inPriorityQueues.h24Performance.queuedOctets

       64 bit unsigned wrappable counter."
   ::= {pr1645v2TvTmplPGreInPQsH24PerformanceEntry 134217728}

pr1645v2TvTmplPGreInPQsH24PerformanceDropOcts OBJECT-TYPE
   SYNTAX      Counter64
   MAX-ACCESS  read-only
   STATUS      current
   DESCRIPTION
      "Path: tunnels.performance.greTunnels.inPriorityQueues.h24Performance.droppedOctets

       64 bit unsigned wrappable counter."
   ::= {pr1645v2TvTmplPGreInPQsH24PerformanceEntry 150994944}

pr1645v2TvTmplPGreInPQsH24PerformanceRDropOcts OBJECT-TYPE
   SYNTAX      Counter64
   MAX-ACCESS  read-only
   STATUS      current
   DESCRIPTION
      "Path: tunnels.performance.greTunnels.inPriorityQueues.h24Performance.redDroppedOctets

       64 bit unsigned wrappable counter."
   ::= {pr1645v2TvTmplPGreInPQsH24PerformanceEntry 218103808}

pr1645v2TvTmplPGreInPQsH24PerformanceCirTxOcts OBJECT-TYPE
   SYNTAX      Counter64
   MAX-ACCESS  read-only
   STATUS      current
   DESCRIPTION
      "Path: tunnels.performance.greTunnels.inPriorityQueues.h24Performance.cirTxOctets

       64 bit unsigned wrappable counter."
   ::= {pr1645v2TvTmplPGreInPQsH24PerformanceEntry 167772160}

pr1645v2TvTmplPGreInPQsH24PerformanceEirTxOcts OBJECT-TYPE
   SYNTAX      Counter64
   MAX-ACCESS  read-only
   STATUS      current
   DESCRIPTION
      "Path: tunnels.performance.greTunnels.inPriorityQueues.h24Performance.eirTxOctets

       64 bit unsigned wrappable counter."
   ::= {pr1645v2TvTmplPGreInPQsH24PerformanceEntry 184549376}

pr1645v2TvTmplPGreInPQsH24PerformanceViolTxOcts OBJECT-TYPE
   SYNTAX      Counter64
   MAX-ACCESS  read-only
   STATUS      current
   DESCRIPTION
      "Path: tunnels.performance.greTunnels.inPriorityQueues.h24Performance.violateTxOctets

       64 bit unsigned wrappable counter."
   ::= {pr1645v2TvTmplPGreInPQsH24PerformanceEntry 318767104}

pr1645v2TvTmplPGreInPQsH24PerformanceBandwidth OBJECT-TYPE
   SYNTAX      Integer32
   MAX-ACCESS  read-only
   STATUS      current
   DESCRIPTION
      "Path: tunnels.performance.greTunnels.inPriorityQueues.h24Performance.bandwidth

       unit name = bps
       formula = 8 * ; 8 /"
   ::= {pr1645v2TvTmplPGreInPQsH24PerformanceEntry 268435456}

pr1645v2TvTmplPGreInPQsD7Performance OBJECT-TYPE
   SYNTAX      SEQUENCE OF Pr1645v2TvTmplPGreInPQsD7PerformanceEntry
   MAX-ACCESS  not-accessible
   STATUS      current
   DESCRIPTION
      ""
   ::= {pr1645v2TvTmplPGre 101122048}

pr1645v2TvTmplPGreInPQsD7PerformanceEntry OBJECT-TYPE
   SYNTAX      Pr1645v2TvTmplPGreInPQsD7PerformanceEntry
   MAX-ACCESS  not-accessible
   STATUS      current
   DESCRIPTION
      ""
   INDEX      { pr1645v2TvTmplPGreTableIx,
                pr1645v2TvTmplPGreInPQsTableIx,
                pr1645v2TvTmplPGreInPQsD7PerformanceTableIx }
   ::= {pr1645v2TvTmplPGreInPQsD7Performance 1}

Pr1645v2TvTmplPGreInPQsD7PerformanceEntry ::=
   SEQUENCE
      {
      pr1645v2TvTmplPGreInPQsD7PerformanceTableIx
         TableIndex,
      pr1645v2TvTmplPGreInPQsD7PerformanceSysUpTime
         TimeTicks,
      pr1645v2TvTmplPGreInPQsD7PerformanceTotPkts
         Counter64,
      pr1645v2TvTmplPGreInPQsD7PerformanceDirTxPkts
         Counter64,
      pr1645v2TvTmplPGreInPQsD7PerformanceQdPkts
         Counter64,
      pr1645v2TvTmplPGreInPQsD7PerformanceDropPkts
         Counter64,
      pr1645v2TvTmplPGreInPQsD7PerformanceRDropPkts
         Counter64,
      pr1645v2TvTmplPGreInPQsD7PerformanceCirTxPkts
         Counter64,
      pr1645v2TvTmplPGreInPQsD7PerformanceEirTxPkts
         Counter64,
      pr1645v2TvTmplPGreInPQsD7PerformanceViolTxPkts
         Counter64,
      pr1645v2TvTmplPGreInPQsD7PerformanceTotOcts
         Counter64,
      pr1645v2TvTmplPGreInPQsD7PerformanceDirTxOcts
         Counter64,
      pr1645v2TvTmplPGreInPQsD7PerformanceQdOcts
         Counter64,
      pr1645v2TvTmplPGreInPQsD7PerformanceDropOcts
         Counter64,
      pr1645v2TvTmplPGreInPQsD7PerformanceRDropOcts
         Counter64,
      pr1645v2TvTmplPGreInPQsD7PerformanceCirTxOcts
         Counter64,
      pr1645v2TvTmplPGreInPQsD7PerformanceEirTxOcts
         Counter64,
      pr1645v2TvTmplPGreInPQsD7PerformanceViolTxOcts
         Counter64,
      pr1645v2TvTmplPGreInPQsD7PerformanceBandwidth
         Integer32
      }

pr1645v2TvTmplPGreInPQsD7PerformanceTableIx OBJECT-TYPE
   SYNTAX      TableIndex
   MAX-ACCESS  not-accessible
   STATUS      current
   DESCRIPTION
      ""
   ::= {pr1645v2TvTmplPGreInPQsD7PerformanceEntry 11}

pr1645v2TvTmplPGreInPQsD7PerformanceSysUpTime OBJECT-TYPE
   SYNTAX      TimeTicks
   MAX-ACCESS  read-only
   STATUS      current
   DESCRIPTION
      "Path: tunnels.performance.greTunnels.inPriorityQueues.d7Performance.sysUpTime

       Time in centi-second."
   ::= {pr1645v2TvTmplPGreInPQsD7PerformanceEntry 16777216}

pr1645v2TvTmplPGreInPQsD7PerformanceTotPkts OBJECT-TYPE
   SYNTAX      Counter64
   MAX-ACCESS  read-only
   STATUS      current
   DESCRIPTION
      "Path: tunnels.performance.greTunnels.inPriorityQueues.d7Performance.totalPkts

       64 bit unsigned wrappable counter."
   ::= {pr1645v2TvTmplPGreInPQsD7PerformanceEntry 234881024}

pr1645v2TvTmplPGreInPQsD7PerformanceDirTxPkts OBJECT-TYPE
   SYNTAX      Counter64
   MAX-ACCESS  read-only
   STATUS      current
   DESCRIPTION
      "Path: tunnels.performance.greTunnels.inPriorityQueues.d7Performance.directTxPkts

       64 bit unsigned wrappable counter."
   ::= {pr1645v2TvTmplPGreInPQsD7PerformanceEntry 33554432}

pr1645v2TvTmplPGreInPQsD7PerformanceQdPkts OBJECT-TYPE
   SYNTAX      Counter64
   MAX-ACCESS  read-only
   STATUS      current
   DESCRIPTION
      "Path: tunnels.performance.greTunnels.inPriorityQueues.d7Performance.queuedPkts

       64 bit unsigned wrappable counter."
   ::= {pr1645v2TvTmplPGreInPQsD7PerformanceEntry 50331648}

pr1645v2TvTmplPGreInPQsD7PerformanceDropPkts OBJECT-TYPE
   SYNTAX      Counter64
   MAX-ACCESS  read-only
   STATUS      current
   DESCRIPTION
      "Path: tunnels.performance.greTunnels.inPriorityQueues.d7Performance.droppedPkts

       64 bit unsigned wrappable counter."
   ::= {pr1645v2TvTmplPGreInPQsD7PerformanceEntry 67108864}

pr1645v2TvTmplPGreInPQsD7PerformanceRDropPkts OBJECT-TYPE
   SYNTAX      Counter64
   MAX-ACCESS  read-only
   STATUS      current
   DESCRIPTION
      "Path: tunnels.performance.greTunnels.inPriorityQueues.d7Performance.redDroppedPkts

       64 bit unsigned wrappable counter."
   ::= {pr1645v2TvTmplPGreInPQsD7PerformanceEntry 201326592}

pr1645v2TvTmplPGreInPQsD7PerformanceCirTxPkts OBJECT-TYPE
   SYNTAX      Counter64
   MAX-ACCESS  read-only
   STATUS      current
   DESCRIPTION
      "Path: tunnels.performance.greTunnels.inPriorityQueues.d7Performance.cirTxPkts

       64 bit unsigned wrappable counter."
   ::= {pr1645v2TvTmplPGreInPQsD7PerformanceEntry 83886080}

pr1645v2TvTmplPGreInPQsD7PerformanceEirTxPkts OBJECT-TYPE
   SYNTAX      Counter64
   MAX-ACCESS  read-only
   STATUS      current
   DESCRIPTION
      "Path: tunnels.performance.greTunnels.inPriorityQueues.d7Performance.eirTxPkts

       64 bit unsigned wrappable counter."
   ::= {pr1645v2TvTmplPGreInPQsD7PerformanceEntry 100663296}

pr1645v2TvTmplPGreInPQsD7PerformanceViolTxPkts OBJECT-TYPE
   SYNTAX      Counter64
   MAX-ACCESS  read-only
   STATUS      current
   DESCRIPTION
      "Path: tunnels.performance.greTunnels.inPriorityQueues.d7Performance.violateTxPkts

       64 bit unsigned wrappable counter."
   ::= {pr1645v2TvTmplPGreInPQsD7PerformanceEntry 301989888}

pr1645v2TvTmplPGreInPQsD7PerformanceTotOcts OBJECT-TYPE
   SYNTAX      Counter64
   MAX-ACCESS  read-only
   STATUS      current
   DESCRIPTION
      "Path: tunnels.performance.greTunnels.inPriorityQueues.d7Performance.totalOctets

       64 bit unsigned wrappable counter."
   ::= {pr1645v2TvTmplPGreInPQsD7PerformanceEntry 251658240}

pr1645v2TvTmplPGreInPQsD7PerformanceDirTxOcts OBJECT-TYPE
   SYNTAX      Counter64
   MAX-ACCESS  read-only
   STATUS      current
   DESCRIPTION
      "Path: tunnels.performance.greTunnels.inPriorityQueues.d7Performance.directTxOctets

       64 bit unsigned wrappable counter."
   ::= {pr1645v2TvTmplPGreInPQsD7PerformanceEntry 117440512}

pr1645v2TvTmplPGreInPQsD7PerformanceQdOcts OBJECT-TYPE
   SYNTAX      Counter64
   MAX-ACCESS  read-only
   STATUS      current
   DESCRIPTION
      "Path: tunnels.performance.greTunnels.inPriorityQueues.d7Performance.queuedOctets

       64 bit unsigned wrappable counter."
   ::= {pr1645v2TvTmplPGreInPQsD7PerformanceEntry 134217728}

pr1645v2TvTmplPGreInPQsD7PerformanceDropOcts OBJECT-TYPE
   SYNTAX      Counter64
   MAX-ACCESS  read-only
   STATUS      current
   DESCRIPTION
      "Path: tunnels.performance.greTunnels.inPriorityQueues.d7Performance.droppedOctets

       64 bit unsigned wrappable counter."
   ::= {pr1645v2TvTmplPGreInPQsD7PerformanceEntry 150994944}

pr1645v2TvTmplPGreInPQsD7PerformanceRDropOcts OBJECT-TYPE
   SYNTAX      Counter64
   MAX-ACCESS  read-only
   STATUS      current
   DESCRIPTION
      "Path: tunnels.performance.greTunnels.inPriorityQueues.d7Performance.redDroppedOctets

       64 bit unsigned wrappable counter."
   ::= {pr1645v2TvTmplPGreInPQsD7PerformanceEntry 218103808}

pr1645v2TvTmplPGreInPQsD7PerformanceCirTxOcts OBJECT-TYPE
   SYNTAX      Counter64
   MAX-ACCESS  read-only
   STATUS      current
   DESCRIPTION
      "Path: tunnels.performance.greTunnels.inPriorityQueues.d7Performance.cirTxOctets

       64 bit unsigned wrappable counter."
   ::= {pr1645v2TvTmplPGreInPQsD7PerformanceEntry 167772160}

pr1645v2TvTmplPGreInPQsD7PerformanceEirTxOcts OBJECT-TYPE
   SYNTAX      Counter64
   MAX-ACCESS  read-only
   STATUS      current
   DESCRIPTION
      "Path: tunnels.performance.greTunnels.inPriorityQueues.d7Performance.eirTxOctets

       64 bit unsigned wrappable counter."
   ::= {pr1645v2TvTmplPGreInPQsD7PerformanceEntry 184549376}

pr1645v2TvTmplPGreInPQsD7PerformanceViolTxOcts OBJECT-TYPE
   SYNTAX      Counter64
   MAX-ACCESS  read-only
   STATUS      current
   DESCRIPTION
      "Path: tunnels.performance.greTunnels.inPriorityQueues.d7Performance.violateTxOctets

       64 bit unsigned wrappable counter."
   ::= {pr1645v2TvTmplPGreInPQsD7PerformanceEntry 318767104}

pr1645v2TvTmplPGreInPQsD7PerformanceBandwidth OBJECT-TYPE
   SYNTAX      Integer32
   MAX-ACCESS  read-only
   STATUS      current
   DESCRIPTION
      "Path: tunnels.performance.greTunnels.inPriorityQueues.d7Performance.bandwidth

       unit name = bps
       formula = 8 * ; 8 /"
   ::= {pr1645v2TvTmplPGreInPQsD7PerformanceEntry 268435456}

pr1645v2TvTmplPGreOutPQs OBJECT-TYPE
   SYNTAX      SEQUENCE OF Pr1645v2TvTmplPGreOutPQsEntry
   MAX-ACCESS  not-accessible
   STATUS      current
   DESCRIPTION
      ""
   ::= {pr1645v2TvTmplPGre 83886080}

pr1645v2TvTmplPGreOutPQsEntry OBJECT-TYPE
   SYNTAX      Pr1645v2TvTmplPGreOutPQsEntry
   MAX-ACCESS  not-accessible
   STATUS      current
   DESCRIPTION
      ""
   INDEX      { pr1645v2TvTmplPGreTableIx,
                pr1645v2TvTmplPGreOutPQsTableIx }
   ::= {pr1645v2TvTmplPGreOutPQs 1}

Pr1645v2TvTmplPGreOutPQsEntry ::=
   SEQUENCE
      {
      pr1645v2TvTmplPGreOutPQsTableIx
         TableIndex,
      pr1645v2TvTmplPGreOutPQsName
         INTEGER,
      pr1645v2TvTmplPGreOutPQsLength
         Integer32,
      pr1645v2TvTmplPGreOutPQsOctetLength
         Integer32,
      pr1645v2TvTmplPGreOutPQsRedLength
         Integer32,
      pr1645v2TvTmplPGreOutPQsPacketsTotal
         Counter64,
      pr1645v2TvTmplPGreOutPQsPacketsDirectTx
         Counter64,
      pr1645v2TvTmplPGreOutPQsPacketsQueued
         Counter64,
      pr1645v2TvTmplPGreOutPQsPacketsDropped
         Counter64,
      pr1645v2TvTmplPGreOutPQsPacketsRedDropped
         Counter64,
      pr1645v2TvTmplPGreOutPQsPacketsCirTx
         Counter64,
      pr1645v2TvTmplPGreOutPQsPacketsEirTx
         Counter64,
      pr1645v2TvTmplPGreOutPQsPacketsViolateTx
         Counter64,
      pr1645v2TvTmplPGreOutPQsOctetsTotal
         Counter64,
      pr1645v2TvTmplPGreOutPQsOctetsDirectTx
         Counter64,
      pr1645v2TvTmplPGreOutPQsOctetsQueued
         Counter64,
      pr1645v2TvTmplPGreOutPQsOctetsDropped
         Counter64,
      pr1645v2TvTmplPGreOutPQsOctetsRedDropped
         Counter64,
      pr1645v2TvTmplPGreOutPQsOctetsCirTx
         Counter64,
      pr1645v2TvTmplPGreOutPQsOctetsEirTx
         Counter64,
      pr1645v2TvTmplPGreOutPQsOctetsViolateTx
         Counter64,
      pr1645v2TvTmplPGreOutPQsOctetsBandwidth15sec
         Integer32,
      pr1645v2TvTmplPGreOutPQsOctetsBandwidth30sec
         Integer32,
      pr1645v2TvTmplPGreOutPQsOctetsBandwidth1min
         Integer32,
      pr1645v2TvTmplPGreOutPQsOctetsBandwidth2min
         Integer32,
      pr1645v2TvTmplPGreOutPQsOctetsBandwidth5min
         Integer32
      }

pr1645v2TvTmplPGreOutPQsTableIx OBJECT-TYPE
   SYNTAX      TableIndex
   MAX-ACCESS  not-accessible
   STATUS      current
   DESCRIPTION
      ""
   ::= {pr1645v2TvTmplPGreOutPQsEntry 11}

pr1645v2TvTmplPGreOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.greTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPGreOutPQsEntry 16777216}

pr1645v2TvTmplPGreOutPQsLength OBJECT-TYPE
   SYNTAX      Integer32
   MAX-ACCESS  read-only
   STATUS      current
   DESCRIPTION
      "Path: tunnels.performance.greTunnels.outPriorityQueues.length"
   ::= {pr1645v2TvTmplPGreOutPQsEntry 33554432}

pr1645v2TvTmplPGreOutPQsOctetLength OBJECT-TYPE
   SYNTAX      Integer32
   MAX-ACCESS  read-only
   STATUS      current
   DESCRIPTION
      "Path: tunnels.performance.greTunnels.outPriorityQueues.octetLength"
   ::= {pr1645v2TvTmplPGreOutPQsEntry 150994944}

pr1645v2TvTmplPGreOutPQsRedLength OBJECT-TYPE
   SYNTAX      Integer32
   MAX-ACCESS  read-only
   STATUS      current
   DESCRIPTION
      "Path: tunnels.performance.greTunnels.outPriorityQueues.redLength"
   ::= {pr1645v2TvTmplPGreOutPQsEntry 134217728}

pr1645v2TvTmplPGreOutPQsPacketsTotal OBJECT-TYPE
   SYNTAX      Counter64
   MAX-ACCESS  read-only
   STATUS      current
   DESCRIPTION
      "Path: tunnels.performance.greTunnels.outPriorityQueues.packets.total

       64 bit unsigned wrappable counter."
   ::= {pr1645v2TvTmplPGreOutPQsEntry 50790400}

pr1645v2TvTmplPGreOutPQsPacketsDirectTx OBJECT-TYPE
   SYNTAX      Counter64
   MAX-ACCESS  read-only
   STATUS      current
   DESCRIPTION
      "Path: tunnels.performance.greTunnels.outPriorityQueues.packets.directTx

       64 bit unsigned wrappable counter."
   ::= {pr1645v2TvTmplPGreOutPQsEntry 50397184}

pr1645v2TvTmplPGreOutPQsPacketsQueued OBJECT-TYPE
   SYNTAX      Counter64
   MAX-ACCESS  read-only
   STATUS      current
   DESCRIPTION
      "Path: tunnels.performance.greTunnels.outPriorityQueues.packets.queued

       64 bit unsigned wrappable counter."
   ::= {pr1645v2TvTmplPGreOutPQsEntry 50462720}

pr1645v2TvTmplPGreOutPQsPacketsDropped OBJECT-TYPE
   SYNTAX      Counter64
   MAX-ACCESS  read-only
   STATUS      current
   DESCRIPTION
      "Path: tunnels.performance.greTunnels.outPriorityQueues.packets.dropped

       64 bit unsigned wrappable counter."
   ::= {pr1645v2TvTmplPGreOutPQsEntry 50528256}

pr1645v2TvTmplPGreOutPQsPacketsRedDropped OBJECT-TYPE
   SYNTAX      Counter64
   MAX-ACCESS  read-only
   STATUS      current
   DESCRIPTION
      "Path: tunnels.performance.greTunnels.outPriorityQueues.packets.redDropped

       64 bit unsigned wrappable counter."
   ::= {pr1645v2TvTmplPGreOutPQsEntry 50724864}

pr1645v2TvTmplPGreOutPQsPacketsCirTx OBJECT-TYPE
   SYNTAX      Counter64
   MAX-ACCESS  read-only
   STATUS      current
   DESCRIPTION
      "Path: tunnels.performance.greTunnels.outPriorityQueues.packets.cirTx

       64 bit unsigned wrappable counter."
   ::= {pr1645v2TvTmplPGreOutPQsEntry 50593792}

pr1645v2TvTmplPGreOutPQsPacketsEirTx OBJECT-TYPE
   SYNTAX      Counter64
   MAX-ACCESS  read-only
   STATUS      current
   DESCRIPTION
      "Path: tunnels.performance.greTunnels.outPriorityQueues.packets.eirTx

       64 bit unsigned wrappable counter."
   ::= {pr1645v2TvTmplPGreOutPQsEntry 50659328}

pr1645v2TvTmplPGreOutPQsPacketsViolateTx OBJECT-TYPE
   SYNTAX      Counter64
   MAX-ACCESS  read-only
   STATUS      current
   DESCRIPTION
      "Path: tunnels.performance.greTunnels.outPriorityQueues.packets.violateTx

       64 bit unsigned wrappable counter."
   ::= {pr1645v2TvTmplPGreOutPQsEntry 50855936}

pr1645v2TvTmplPGreOutPQsOctetsTotal OBJECT-TYPE
   SYNTAX      Counter64
   MAX-ACCESS  read-only
   STATUS      current
   DESCRIPTION
      "Path: tunnels.performance.greTunnels.outPriorityQueues.octets.total

       64 bit unsigned wrappable counter."
   ::= {pr1645v2TvTmplPGreOutPQsEntry 67567616}

pr1645v2TvTmplPGreOutPQsOctetsDirectTx OBJECT-TYPE
   SYNTAX      Counter64
   MAX-ACCESS  read-only
   STATUS      current
   DESCRIPTION
      "Path: tunnels.performance.greTunnels.outPriorityQueues.octets.directTx

       64 bit unsigned wrappable counter."
   ::= {pr1645v2TvTmplPGreOutPQsEntry 67174400}

pr1645v2TvTmplPGreOutPQsOctetsQueued OBJECT-TYPE
   SYNTAX      Counter64
   MAX-ACCESS  read-only
   STATUS      current
   DESCRIPTION
      "Path: tunnels.performance.greTunnels.outPriorityQueues.octets.queued

       64 bit unsigned wrappable counter."
   ::= {pr1645v2TvTmplPGreOutPQsEntry 67239936}

pr1645v2TvTmplPGreOutPQsOctetsDropped OBJECT-TYPE
   SYNTAX      Counter64
   MAX-ACCESS  read-only
   STATUS      current
   DESCRIPTION
      "Path: tunnels.performance.greTunnels.outPriorityQueues.octets.dropped

       64 bit unsigned wrappable counter."
   ::= {pr1645v2TvTmplPGreOutPQsEntry 67305472}

pr1645v2TvTmplPGreOutPQsOctetsRedDropped OBJECT-TYPE
   SYNTAX      Counter64
   MAX-ACCESS  read-only
   STATUS      current
   DESCRIPTION
      "Path: tunnels.performance.greTunnels.outPriorityQueues.octets.redDropped

       64 bit unsigned wrappable counter."
   ::= {pr1645v2TvTmplPGreOutPQsEntry 67502080}

pr1645v2TvTmplPGreOutPQsOctetsCirTx OBJECT-TYPE
   SYNTAX      Counter64
   MAX-ACCESS  read-only
   STATUS      current
   DESCRIPTION
      "Path: tunnels.performance.greTunnels.outPriorityQueues.octets.cirTx

       64 bit unsigned wrappable counter."
   ::= {pr1645v2TvTmplPGreOutPQsEntry 67371008}

pr1645v2TvTmplPGreOutPQsOctetsEirTx OBJECT-TYPE
   SYNTAX      Counter64
   MAX-ACCESS  read-only
   STATUS      current
   DESCRIPTION
      "Path: tunnels.performance.greTunnels.outPriorityQueues.octets.eirTx

       64 bit unsigned wrappable counter."
   ::= {pr1645v2TvTmplPGreOutPQsEntry 67436544}

pr1645v2TvTmplPGreOutPQsOctetsViolateTx OBJECT-TYPE
   SYNTAX      Counter64
   MAX-ACCESS  read-only
   STATUS      current
   DESCRIPTION
      "Path: tunnels.performance.greTunnels.outPriorityQueues.octets.violateTx

       64 bit unsigned wrappable counter."
   ::= {pr1645v2TvTmplPGreOutPQsEntry 67633152}

pr1645v2TvTmplPGreOutPQsOctetsBandwidth15sec OBJECT-TYPE
   SYNTAX      Integer32
   MAX-ACCESS  read-only
   STATUS      current
   DESCRIPTION
      "Path: tunnels.performance.greTunnels.outPriorityQueues.octets.bandwidth.15sec

       unit name = bps
       formula = 8 * ; 8 /"
   ::= {pr1645v2TvTmplPGreOutPQsEntry 70386944}

pr1645v2TvTmplPGreOutPQsOctetsBandwidth30sec OBJECT-TYPE
   SYNTAX      Integer32
   MAX-ACCESS  read-only
   STATUS      current
   DESCRIPTION
      "Path: tunnels.performance.greTunnels.outPriorityQueues.octets.bandwidth.30sec

       unit name = bps
       formula = 8 * ; 8 /"
   ::= {pr1645v2TvTmplPGreOutPQsEntry 70388224}

pr1645v2TvTmplPGreOutPQsOctetsBandwidth1min OBJECT-TYPE
   SYNTAX      Integer32
   MAX-ACCESS  read-only
   STATUS      current
   DESCRIPTION
      "Path: tunnels.performance.greTunnels.outPriorityQueues.octets.bandwidth.1min

       unit name = bps
       formula = 8 * ; 8 /"
   ::= {pr1645v2TvTmplPGreOutPQsEntry 70390784}

pr1645v2TvTmplPGreOutPQsOctetsBandwidth2min OBJECT-TYPE
   SYNTAX      Integer32
   MAX-ACCESS  read-only
   STATUS      current
   DESCRIPTION
      "Path: tunnels.performance.greTunnels.outPriorityQueues.octets.bandwidth.2min

       unit name = bps
       formula = 8 * ; 8 /"
   ::= {pr1645v2TvTmplPGreOutPQsEntry 70395904}

pr1645v2TvTmplPGreOutPQsOctetsBandwidth5min OBJECT-TYPE
   SYNTAX      Integer32
   MAX-ACCESS  read-only
   STATUS      current
   DESCRIPTION
      "Path: tunnels.performance.greTunnels.outPriorityQueues.octets.bandwidth.5min

       unit name = bps
       formula = 8 * ; 8 /"
   ::= {pr1645v2TvTmplPGreOutPQsEntry 70411264}

pr1645v2TvTmplPGreOutPQsH2Performance OBJECT-TYPE
   SYNTAX      SEQUENCE OF Pr1645v2TvTmplPGreOutPQsH2PerformanceEntry
   MAX-ACCESS  not-accessible
   STATUS      current
   DESCRIPTION
      ""
   ::= {pr1645v2TvTmplPGre 84213760}

pr1645v2TvTmplPGreOutPQsH2PerformanceEntry OBJECT-TYPE
   SYNTAX      Pr1645v2TvTmplPGreOutPQsH2PerformanceEntry
   MAX-ACCESS  not-accessible
   STATUS      current
   DESCRIPTION
      ""
   INDEX      { pr1645v2TvTmplPGreTableIx,
                pr1645v2TvTmplPGreOutPQsTableIx,
                pr1645v2TvTmplPGreOutPQsH2PerformanceTableIx }
   ::= {pr1645v2TvTmplPGreOutPQsH2Performance 1}

Pr1645v2TvTmplPGreOutPQsH2PerformanceEntry ::=
   SEQUENCE
      {
      pr1645v2TvTmplPGreOutPQsH2PerformanceTableIx
         TableIndex,
      pr1645v2TvTmplPGreOutPQsH2PerformanceSysUpTime
         TimeTicks,
      pr1645v2TvTmplPGreOutPQsH2PerformanceTotPkts
         Counter64,
      pr1645v2TvTmplPGreOutPQsH2PerformanceDirTxPkts
         Counter64,
      pr1645v2TvTmplPGreOutPQsH2PerformanceQdPkts
         Counter64,
      pr1645v2TvTmplPGreOutPQsH2PerformanceDropPkts
         Counter64,
      pr1645v2TvTmplPGreOutPQsH2PerformanceRDropPkts
         Counter64,
      pr1645v2TvTmplPGreOutPQsH2PerformanceCirTxPkts
         Counter64,
      pr1645v2TvTmplPGreOutPQsH2PerformanceEirTxPkts
         Counter64,
      pr1645v2TvTmplPGreOutPQsH2PerformanceViolTxPkts
         Counter64,
      pr1645v2TvTmplPGreOutPQsH2PerformanceTotOcts
         Counter64,
      pr1645v2TvTmplPGreOutPQsH2PerformanceDirTxOcts
         Counter64,
      pr1645v2TvTmplPGreOutPQsH2PerformanceQdOcts
         Counter64,
      pr1645v2TvTmplPGreOutPQsH2PerformanceDropOcts
         Counter64,
      pr1645v2TvTmplPGreOutPQsH2PerformanceRDropOcts
         Counter64,
      pr1645v2TvTmplPGreOutPQsH2PerformanceCirTxOcts
         Counter64,
      pr1645v2TvTmplPGreOutPQsH2PerformanceEirTxOcts
         Counter64,
      pr1645v2TvTmplPGreOutPQsH2PerformanceViolTxOcts
         Counter64,
      pr1645v2TvTmplPGreOutPQsH2PerformanceBandwidth
         Integer32
      }

pr1645v2TvTmplPGreOutPQsH2PerformanceTableIx OBJECT-TYPE
   SYNTAX      TableIndex
   MAX-ACCESS  not-accessible
   STATUS      current
   DESCRIPTION
      ""
   ::= {pr1645v2TvTmplPGreOutPQsH2PerformanceEntry 11}

pr1645v2TvTmplPGreOutPQsH2PerformanceSysUpTime OBJECT-TYPE
   SYNTAX      TimeTicks
   MAX-ACCESS  read-only
   STATUS      current
   DESCRIPTION
      "Path: tunnels.performance.greTunnels.outPriorityQueues.h2Performance.sysUpTime

       Time in centi-second."
   ::= {pr1645v2TvTmplPGreOutPQsH2PerformanceEntry 16777216}

pr1645v2TvTmplPGreOutPQsH2PerformanceTotPkts OBJECT-TYPE
   SYNTAX      Counter64
   MAX-ACCESS  read-only
   STATUS      current
   DESCRIPTION
      "Path: tunnels.performance.greTunnels.outPriorityQueues.h2Performance.totalPkts

       64 bit unsigned wrappable counter."
   ::= {pr1645v2TvTmplPGreOutPQsH2PerformanceEntry 234881024}

pr1645v2TvTmplPGreOutPQsH2PerformanceDirTxPkts OBJECT-TYPE
   SYNTAX      Counter64
   MAX-ACCESS  read-only
   STATUS      current
   DESCRIPTION
      "Path: tunnels.performance.greTunnels.outPriorityQueues.h2Performance.directTxPkts

       64 bit unsigned wrappable counter."
   ::= {pr1645v2TvTmplPGreOutPQsH2PerformanceEntry 33554432}

pr1645v2TvTmplPGreOutPQsH2PerformanceQdPkts OBJECT-TYPE
   SYNTAX      Counter64
   MAX-ACCESS  read-only
   STATUS      current
   DESCRIPTION
      "Path: tunnels.performance.greTunnels.outPriorityQueues.h2Performance.queuedPkts

       64 bit unsigned wrappable counter."
   ::= {pr1645v2TvTmplPGreOutPQsH2PerformanceEntry 50331648}

pr1645v2TvTmplPGreOutPQsH2PerformanceDropPkts OBJECT-TYPE
   SYNTAX      Counter64
   MAX-ACCESS  read-only
   STATUS      current
   DESCRIPTION
      "Path: tunnels.performance.greTunnels.outPriorityQueues.h2Performance.droppedPkts

       64 bit unsigned wrappable counter."
   ::= {pr1645v2TvTmplPGreOutPQsH2PerformanceEntry 67108864}

pr1645v2TvTmplPGreOutPQsH2PerformanceRDropPkts OBJECT-TYPE
   SYNTAX      Counter64
   MAX-ACCESS  read-only
   STATUS      current
   DESCRIPTION
      "Path: tunnels.performance.greTunnels.outPriorityQueues.h2Performance.redDroppedPkts

       64 bit unsigned wrappable counter."
   ::= {pr1645v2TvTmplPGreOutPQsH2PerformanceEntry 201326592}

pr1645v2TvTmplPGreOutPQsH2PerformanceCirTxPkts OBJECT-TYPE
   SYNTAX      Counter64
   MAX-ACCESS  read-only
   STATUS      current
   DESCRIPTION
      "Path: tunnels.performance.greTunnels.outPriorityQueues.h2Performance.cirTxPkts

       64 bit unsigned wrappable counter."
   ::= {pr1645v2TvTmplPGreOutPQsH2PerformanceEntry 83886080}

pr1645v2TvTmplPGreOutPQsH2PerformanceEirTxPkts OBJECT-TYPE
   SYNTAX      Counter64
   MAX-ACCESS  read-only
   STATUS      current
   DESCRIPTION
      "Path: tunnels.performance.greTunnels.outPriorityQueues.h2Performance.eirTxPkts

       64 bit unsigned wrappable counter."
   ::= {pr1645v2TvTmplPGreOutPQsH2PerformanceEntry 100663296}

pr1645v2TvTmplPGreOutPQsH2PerformanceViolTxPkts OBJECT-TYPE
   SYNTAX      Counter64
   MAX-ACCESS  read-only
   STATUS      current
   DESCRIPTION
      "Path: tunnels.performance.greTunnels.outPriorityQueues.h2Performance.violateTxPkts

       64 bit unsigned wrappable counter."
   ::= {pr1645v2TvTmplPGreOutPQsH2PerformanceEntry 301989888}

pr1645v2TvTmplPGreOutPQsH2PerformanceTotOcts OBJECT-TYPE
   SYNTAX      Counter64
   MAX-ACCESS  read-only
   STATUS      current
   DESCRIPTION
      "Path: tunnels.performance.greTunnels.outPriorityQueues.h2Performance.totalOctets

       64 bit unsigned wrappable counter."
   ::= {pr1645v2TvTmplPGreOutPQsH2PerformanceEntry 251658240}

pr1645v2TvTmplPGreOutPQsH2PerformanceDirTxOcts OBJECT-TYPE
   SYNTAX      Counter64
   MAX-ACCESS  read-only
   STATUS      current
   DESCRIPTION
      "Path: tunnels.performance.greTunnels.outPriorityQueues.h2Performance.directTxOctets

       64 bit unsigned wrappable counter."
   ::= {pr1645v2TvTmplPGreOutPQsH2PerformanceEntry 117440512}

pr1645v2TvTmplPGreOutPQsH2PerformanceQdOcts OBJECT-TYPE
   SYNTAX      Counter64
   MAX-ACCESS  read-only
   STATUS      current
   DESCRIPTION
      "Path: tunnels.performance.greTunnels.outPriorityQueues.h2Performance.queuedOctets

       64 bit unsigned wrappable counter."
   ::= {pr1645v2TvTmplPGreOutPQsH2PerformanceEntry 134217728}

pr1645v2TvTmplPGreOutPQsH2PerformanceDropOcts OBJECT-TYPE
   SYNTAX      Counter64
   MAX-ACCESS  read-only
   STATUS      current
   DESCRIPTION
      "Path: tunnels.performance.greTunnels.outPriorityQueues.h2Performance.droppedOctets

       64 bit unsigned wrappable counter."
   ::= {pr1645v2TvTmplPGreOutPQsH2PerformanceEntry 150994944}

pr1645v2TvTmplPGreOutPQsH2PerformanceRDropOcts OBJECT-TYPE
   SYNTAX      Counter64
   MAX-ACCESS  read-only
   STATUS      current
   DESCRIPTION
      "Path: tunnels.performance.greTunnels.outPriorityQueues.h2Performance.redDroppedOctets

       64 bit unsigned wrappable counter."
   ::= {pr1645v2TvTmplPGreOutPQsH2PerformanceEntry 218103808}

pr1645v2TvTmplPGreOutPQsH2PerformanceCirTxOcts OBJECT-TYPE
   SYNTAX      Counter64
   MAX-ACCESS  read-only
   STATUS      current
   DESCRIPTION
      "Path: tunnels.performance.greTunnels.outPriorityQueues.h2Performance.cirTxOctets

       64 bit unsigned wrappable counter."
   ::= {pr1645v2TvTmplPGreOutPQsH2PerformanceEntry 167772160}

pr1645v2TvTmplPGreOutPQsH2PerformanceEirTxOcts OBJECT-TYPE
   SYNTAX      Counter64
   MAX-ACCESS  read-only
   STATUS      current
   DESCRIPTION
      "Path: tunnels.performance.greTunnels.outPriorityQueues.h2Performance.eirTxOctets

       64 bit unsigned wrappable counter."
   ::= {pr1645v2TvTmplPGreOutPQsH2PerformanceEntry 184549376}

pr1645v2TvTmplPGreOutPQsH2PerformanceViolTxOcts OBJECT-TYPE
   SYNTAX      Counter64
   MAX-ACCESS  read-only
   STATUS      current
   DESCRIPTION
      "Path: tunnels.performance.greTunnels.outPriorityQueues.h2Performance.violateTxOctets

       64 bit unsigned wrappable counter."
   ::= {pr1645v2TvTmplPGreOutPQsH2PerformanceEntry 318767104}

pr1645v2TvTmplPGreOutPQsH2PerformanceBandwidth OBJECT-TYPE
   SYNTAX      Integer32
   MAX-ACCESS  read-only
   STATUS      current
   DESCRIPTION
      "Path: tunnels.performance.greTunnels.outPriorityQueues.h2Performance.bandwidth

       unit name = bps
       formula = 8 * ; 8 /"
   ::= {pr1645v2TvTmplPGreOutPQsH2PerformanceEntry 268435456}

pr1645v2TvTmplPGreOutPQsH24Performance OBJECT-TYPE
   SYNTAX      SEQUENCE OF Pr1645v2TvTmplPGreOutPQsH24PerformanceEntry
   MAX-ACCESS  not-accessible
   STATUS      current
   DESCRIPTION
      ""
   ::= {pr1645v2TvTmplPGre 84279296}

pr1645v2TvTmplPGreOutPQsH24PerformanceEntry OBJECT-TYPE
   SYNTAX      Pr1645v2TvTmplPGreOutPQsH24PerformanceEntry
   MAX-ACCESS  not-accessible
   STATUS      current
   DESCRIPTION
      ""
   INDEX      { pr1645v2TvTmplPGreTableIx,
                pr1645v2TvTmplPGreOutPQsTableIx,
                pr1645v2TvTmplPGreOutPQsH24PerformanceTableIx }
   ::= {pr1645v2TvTmplPGreOutPQsH24Performance 1}

Pr1645v2TvTmplPGreOutPQsH24PerformanceEntry ::=
   SEQUENCE
      {
      pr1645v2TvTmplPGreOutPQsH24PerformanceTableIx
         TableIndex,
      pr1645v2TvTmplPGreOutPQsH24PerformanceSysUpTime
         TimeTicks,
      pr1645v2TvTmplPGreOutPQsH24PerformanceTotPkts
         Counter64,
      pr1645v2TvTmplPGreOutPQsH24PerformanceDirTxPkts
         Counter64,
      pr1645v2TvTmplPGreOutPQsH24PerformanceQdPkts
         Counter64,
      pr1645v2TvTmplPGreOutPQsH24PerformanceDropPkts
         Counter64,
      pr1645v2TvTmplPGreOutPQsH24PerformanceRDropPkts
         Counter64,
      pr1645v2TvTmplPGreOutPQsH24PerformanceCirTxPkts
         Counter64,
      pr1645v2TvTmplPGreOutPQsH24PerformanceEirTxPkts
         Counter64,
      pr1645v2TvTmplPGreOutPQsH24PerformanceViolTxPkts
         Counter64,
      pr1645v2TvTmplPGreOutPQsH24PerformanceTotOcts
         Counter64,
      pr1645v2TvTmplPGreOutPQsH24PerformanceDirTxOcts
         Counter64,
      pr1645v2TvTmplPGreOutPQsH24PerformanceQdOcts
         Counter64,
      pr1645v2TvTmplPGreOutPQsH24PerformanceDropOcts
         Counter64,
      pr1645v2TvTmplPGreOutPQsH24PerformanceRDropOcts
         Counter64,
      pr1645v2TvTmplPGreOutPQsH24PerformanceCirTxOcts
         Counter64,
      pr1645v2TvTmplPGreOutPQsH24PerformanceEirTxOcts
         Counter64,
      pr1645v2TvTmplPGreOutPQsH24PerformanceViolTxOcts
         Counter64,
      pr1645v2TvTmplPGreOutPQsH24PerformanceBandwidth
         Integer32
      }

pr1645v2TvTmplPGreOutPQsH24PerformanceTableIx OBJECT-TYPE
   SYNTAX      TableIndex
   MAX-ACCESS  not-accessible
   STATUS      current
   DESCRIPTION
      ""
   ::= {pr1645v2TvTmplPGreOutPQsH24PerformanceEntry 11}

pr1645v2TvTmplPGreOutPQsH24PerformanceSysUpTime OBJECT-TYPE
   SYNTAX      TimeTicks
   MAX-ACCESS  read-only
   STATUS      current
   DESCRIPTION
      "Path: tunnels.performance.greTunnels.outPriorityQueues.h24Performance.sysUpTime

       Time in centi-second."
   ::= {pr1645v2TvTmplPGreOutPQsH24PerformanceEntry 16777216}

pr1645v2TvTmplPGreOutPQsH24PerformanceTotPkts OBJECT-TYPE
   SYNTAX      Counter64
   MAX-ACCESS  read-only
   STATUS      current
   DESCRIPTION
      "Path: tunnels.performance.greTunnels.outPriorityQueues.h24Performance.totalPkts

       64 bit unsigned wrappable counter."
   ::= {pr1645v2TvTmplPGreOutPQsH24PerformanceEntry 234881024}

pr1645v2TvTmplPGreOutPQsH24PerformanceDirTxPkts OBJECT-TYPE
   SYNTAX      Counter64
   MAX-ACCESS  read-only
   STATUS      current
   DESCRIPTION
      "Path: tunnels.performance.greTunnels.outPriorityQueues.h24Performance.directTxPkts

       64 bit unsigned wrappable counter."
   ::= {pr1645v2TvTmplPGreOutPQsH24PerformanceEntry 33554432}

pr1645v2TvTmplPGreOutPQsH24PerformanceQdPkts OBJECT-TYPE
   SYNTAX      Counter64
   MAX-ACCESS  read-only
   STATUS      current
   DESCRIPTION
      "Path: tunnels.performance.greTunnels.outPriorityQueues.h24Performance.queuedPkts

       64 bit unsigned wrappable counter."
   ::= {pr1645v2TvTmplPGreOutPQsH24PerformanceEntry 50331648}

pr1645v2TvTmplPGreOutPQsH24PerformanceDropPkts OBJECT-TYPE
   SYNTAX      Counter64
   MAX-ACCESS  read-only
   STATUS      current
   DESCRIPTION
      "Path: tunnels.performance.greTunnels.outPriorityQueues.h24Performance.droppedPkts

       64 bit unsigned wrappable counter."
   ::= {pr1645v2TvTmplPGreOutPQsH24PerformanceEntry 67108864}

pr1645v2TvTmplPGreOutPQsH24PerformanceRDropPkts OBJECT-TYPE
   SYNTAX      Counter64
   MAX-ACCESS  read-only
   STATUS      current
   DESCRIPTION
      "Path: tunnels.performance.greTunnels.outPriorityQueues.h24Performance.redDroppedPkts

       64 bit unsigned wrappable counter."
   ::= {pr1645v2TvTmplPGreOutPQsH24PerformanceEntry 201326592}

pr1645v2TvTmplPGreOutPQsH24PerformanceCirTxPkts OBJECT-TYPE
   SYNTAX      Counter64
   MAX-ACCESS  read-only
   STATUS      current
   DESCRIPTION
      "Path: tunnels.performance.greTunnels.outPriorityQueues.h24Performance.cirTxPkts

       64 bit unsigned wrappable counter."
   ::= {pr1645v2TvTmplPGreOutPQsH24PerformanceEntry 83886080}

pr1645v2TvTmplPGreOutPQsH24PerformanceEirTxPkts OBJECT-TYPE
   SYNTAX      Counter64
   MAX-ACCESS  read-only
   STATUS      current
   DESCRIPTION
      "Path: tunnels.performance.greTunnels.outPriorityQueues.h24Performance.eirTxPkts

       64 bit unsigned wrappable counter."
   ::= {pr1645v2TvTmplPGreOutPQsH24PerformanceEntry 100663296}

pr1645v2TvTmplPGreOutPQsH24PerformanceViolTxPkts OBJECT-TYPE
   SYNTAX      Counter64
   MAX-ACCESS  read-only
   STATUS      current
   DESCRIPTION
      "Path: tunnels.performance.greTunnels.outPriorityQueues.h24Performance.violateTxPkts

       64 bit unsigned wrappable counter."
   ::= {pr1645v2TvTmplPGreOutPQsH24PerformanceEntry 301989888}

pr1645v2TvTmplPGreOutPQsH24PerformanceTotOcts OBJECT-TYPE
   SYNTAX      Counter64
   MAX-ACCESS  read-only
   STATUS      current
   DESCRIPTION
      "Path: tunnels.performance.greTunnels.outPriorityQueues.h24Performance.totalOctets

       64 bit unsigned wrappable counter."
   ::= {pr1645v2TvTmplPGreOutPQsH24PerformanceEntry 251658240}

pr1645v2TvTmplPGreOutPQsH24PerformanceDirTxOcts OBJECT-TYPE
   SYNTAX      Counter64
   MAX-ACCESS  read-only
   STATUS      current
   DESCRIPTION
      "Path: tunnels.performance.greTunnels.outPriorityQueues.h24Performance.directTxOctets

       64 bit unsigned wrappable counter."
   ::= {pr1645v2TvTmplPGreOutPQsH24PerformanceEntry 117440512}

pr1645v2TvTmplPGreOutPQsH24PerformanceQdOcts OBJECT-TYPE
   SYNTAX      Counter64
   MAX-ACCESS  read-only
   STATUS      current
   DESCRIPTION
      "Path: tunnels.performance.greTunnels.outPriorityQueues.h24Performance.queuedOctets

       64 bit unsigned wrappable counter."
   ::= {pr1645v2TvTmplPGreOutPQsH24PerformanceEntry 134217728}

pr1645v2TvTmplPGreOutPQsH24PerformanceDropOcts OBJECT-TYPE
   SYNTAX      Counter64
   MAX-ACCESS  read-only
   STATUS      current
   DESCRIPTION
      "Path: tunnels.performance.greTunnels.outPriorityQueues.h24Performance.droppedOctets

       64 bit unsigned wrappable counter."
   ::= {pr1645v2TvTmplPGreOutPQsH24PerformanceEntry 150994944}

pr1645v2TvTmplPGreOutPQsH24PerformanceRDropOcts OBJECT-TYPE
   SYNTAX      Counter64
   MAX-ACCESS  read-only
   STATUS      current
   DESCRIPTION
      "Path: tunnels.performance.greTunnels.outPriorityQueues.h24Performance.redDroppedOctets

       64 bit unsigned wrappable counter."
   ::= {pr1645v2TvTmplPGreOutPQsH24PerformanceEntry 218103808}

pr1645v2TvTmplPGreOutPQsH24PerformanceCirTxOcts OBJECT-TYPE
   SYNTAX      Counter64
   MAX-ACCESS  read-only
   STATUS      current
   DESCRIPTION
      "Path: tunnels.performance.greTunnels.outPriorityQueues.h24Performance.cirTxOctets

       64 bit unsigned wrappable counter."
   ::= {pr1645v2TvTmplPGreOutPQsH24PerformanceEntry 167772160}

pr1645v2TvTmplPGreOutPQsH24PerformanceEirTxOcts OBJECT-TYPE
   SYNTAX      Counter64
   MAX-ACCESS  read-only
   STATUS      current
   DESCRIPTION
      "Path: tunnels.performance.greTunnels.outPriorityQueues.h24Performance.eirTxOctets

       64 bit unsigned wrappable counter."
   ::= {pr1645v2TvTmplPGreOutPQsH24PerformanceEntry 184549376}

pr1645v2TvTmplPGreOutPQsH24PerformanceViolTxOcts OBJECT-TYPE
   SYNTAX      Counter64
   MAX-ACCESS  read-only
   STATUS      current
   DESCRIPTION
      "Path: tunnels.performance.greTunnels.outPriorityQueues.h24Performance.violateTxOctets

       64 bit unsigned wrappable counter."
   ::= {pr1645v2TvTmplPGreOutPQsH24PerformanceEntry 318767104}

pr1645v2TvTmplPGreOutPQsH24PerformanceBandwidth OBJECT-TYPE
   SYNTAX      Integer32
   MAX-ACCESS  read-only
   STATUS      current
   DESCRIPTION
      "Path: tunnels.performance.greTunnels.outPriorityQueues.h24Performance.bandwidth

       unit name = bps
       formula = 8 * ; 8 /"
   ::= {pr1645v2TvTmplPGreOutPQsH24PerformanceEntry 268435456}

pr1645v2TvTmplPGreOutPQsD7Performance OBJECT-TYPE
   SYNTAX      SEQUENCE OF Pr1645v2TvTmplPGreOutPQsD7PerformanceEntry
   MAX-ACCESS  not-accessible
   STATUS      current
   DESCRIPTION
      ""
   ::= {pr1645v2TvTmplPGre 84344832}

pr1645v2TvTmplPGreOutPQsD7PerformanceEntry OBJECT-TYPE
   SYNTAX      Pr1645v2TvTmplPGreOutPQsD7PerformanceEntry
   MAX-ACCESS  not-accessible
   STATUS      current
   DESCRIPTION
      ""
   INDEX      { pr1645v2TvTmplPGreTableIx,
                pr1645v2TvTmplPGreOutPQsTableIx,
                pr1645v2TvTmplPGreOutPQsD7PerformanceTableIx }
   ::= {pr1645v2TvTmplPGreOutPQsD7Performance 1}

Pr1645v2TvTmplPGreOutPQsD7PerformanceEntry ::=
   SEQUENCE
      {
      pr1645v2TvTmplPGreOutPQsD7PerformanceTableIx
         TableIndex,
      pr1645v2TvTmplPGreOutPQsD7PerformanceSysUpTime
         TimeTicks,
      pr1645v2TvTmplPGreOutPQsD7PerformanceTotPkts
         Counter64,
      pr1645v2TvTmplPGreOutPQsD7PerformanceDirTxPkts
         Counter64,
      pr1645v2TvTmplPGreOutPQsD7PerformanceQdPkts
         Counter64,
      pr1645v2TvTmplPGreOutPQsD7PerformanceDropPkts
         Counter64,
      pr1645v2TvTmplPGreOutPQsD7PerformanceRDropPkts
         Counter64,
      pr1645v2TvTmplPGreOutPQsD7PerformanceCirTxPkts
         Counter64,
      pr1645v2TvTmplPGreOutPQsD7PerformanceEirTxPkts
         Counter64,
      pr1645v2TvTmplPGreOutPQsD7PerformanceViolTxPkts
         Counter64,
      pr1645v2TvTmplPGreOutPQsD7PerformanceTotOcts
         Counter64,
      pr1645v2TvTmplPGreOutPQsD7PerformanceDirTxOcts
         Counter64,
      pr1645v2TvTmplPGreOutPQsD7PerformanceQdOcts
         Counter64,
      pr1645v2TvTmplPGreOutPQsD7PerformanceDropOcts
         Counter64,
      pr1645v2TvTmplPGreOutPQsD7PerformanceRDropOcts
         Counter64,
      pr1645v2TvTmplPGreOutPQsD7PerformanceCirTxOcts
         Counter64,
      pr1645v2TvTmplPGreOutPQsD7PerformanceEirTxOcts
         Counter64,
      pr1645v2TvTmplPGreOutPQsD7PerformanceViolTxOcts
         Counter64,
      pr1645v2TvTmplPGreOutPQsD7PerformanceBandwidth
         Integer32
      }

pr1645v2TvTmplPGreOutPQsD7PerformanceTableIx OBJECT-TYPE
   SYNTAX      TableIndex
   MAX-ACCESS  not-accessible
   STATUS      current
   DESCRIPTION
      ""
   ::= {pr1645v2TvTmplPGreOutPQsD7PerformanceEntry 11}

pr1645v2TvTmplPGreOutPQsD7PerformanceSysUpTime OBJECT-TYPE
   SYNTAX      TimeTicks
   MAX-ACCESS  read-only
   STATUS      current
   DESCRIPTION
      "Path: tunnels.performance.greTunnels.outPriorityQueues.d7Performance.sysUpTime

       Time in centi-second."
   ::= {pr1645v2TvTmplPGreOutPQsD7PerformanceEntry 16777216}

pr1645v2TvTmplPGreOutPQsD7PerformanceTotPkts OBJECT-TYPE
   SYNTAX      Counter64
   MAX-ACCESS  read-only
   STATUS      current
   DESCRIPTION
      "Path: tunnels.performance.greTunnels.outPriorityQueues.d7Performance.totalPkts

       64 bit unsigned wrappable counter."
   ::= {pr1645v2TvTmplPGreOutPQsD7PerformanceEntry 234881024}

pr1645v2TvTmplPGreOutPQsD7PerformanceDirTxPkts OBJECT-TYPE
   SYNTAX      Counter64
   MAX-ACCESS  read-only
   STATUS      current
   DESCRIPTION
      "Path: tunnels.performance.greTunnels.outPriorityQueues.d7Performance.directTxPkts

       64 bit unsigned wrappable counter."
   ::= {pr1645v2TvTmplPGreOutPQsD7PerformanceEntry 33554432}

pr1645v2TvTmplPGreOutPQsD7PerformanceQdPkts OBJECT-TYPE
   SYNTAX      Counter64
   MAX-ACCESS  read-only
   STATUS      current
   DESCRIPTION
      "Path: tunnels.performance.greTunnels.outPriorityQueues.d7Performance.queuedPkts

       64 bit unsigned wrappable counter."
   ::= {pr1645v2TvTmplPGreOutPQsD7PerformanceEntry 50331648}

pr1645v2TvTmplPGreOutPQsD7PerformanceDropPkts OBJECT-TYPE
   SYNTAX      Counter64
   MAX-ACCESS  read-only
   STATUS      current
   DESCRIPTION
      "Path: tunnels.performance.greTunnels.outPriorityQueues.d7Performance.droppedPkts

       64 bit unsigned wrappable counter."
   ::= {pr1645v2TvTmplPGreOutPQsD7PerformanceEntry 67108864}

pr1645v2TvTmplPGreOutPQsD7PerformanceRDropPkts OBJECT-TYPE
   SYNTAX      Counter64
   MAX-ACCESS  read-only
   STATUS      current
   DESCRIPTION
      "Path: tunnels.performance.greTunnels.outPriorityQueues.d7Performance.redDroppedPkts

       64 bit unsigned wrappable counter."
   ::= {pr1645v2TvTmplPGreOutPQsD7PerformanceEntry 201326592}

pr1645v2TvTmplPGreOutPQsD7PerformanceCirTxPkts OBJECT-TYPE
   SYNTAX      Counter64
   MAX-ACCESS  read-only
   STATUS      current
   DESCRIPTION
      "Path: tunnels.performance.greTunnels.outPriorityQueues.d7Performance.cirTxPkts

       64 bit unsigned wrappable counter."
   ::= {pr1645v2TvTmplPGreOutPQsD7PerformanceEntry 83886080}

pr1645v2TvTmplPGreOutPQsD7PerformanceEirTxPkts OBJECT-TYPE
   SYNTAX      Counter64
   MAX-ACCESS  read-only
   STATUS      current
   DESCRIPTION
      "Path: tunnels.performance.greTunnels.outPriorityQueues.d7Performance.eirTxPkts

       64 bit unsigned wrappable counter."
   ::= {pr1645v2TvTmplPGreOutPQsD7PerformanceEntry 100663296}

pr1645v2TvTmplPGreOutPQsD7PerformanceViolTxPkts OBJECT-TYPE
   SYNTAX      Counter64
   MAX-ACCESS  read-only
   STATUS      current
   DESCRIPTION
      "Path: tunnels.performance.greTunnels.outPriorityQueues.d7Performance.violateTxPkts

       64 bit unsigned wrappable counter."
   ::= {pr1645v2TvTmplPGreOutPQsD7PerformanceEntry 301989888}

pr1645v2TvTmplPGreOutPQsD7PerformanceTotOcts OBJECT-TYPE
   SYNTAX      Counter64
   MAX-ACCESS  read-only
   STATUS      current
   DESCRIPTION
      "Path: tunnels.performance.greTunnels.outPriorityQueues.d7Performance.totalOctets

       64 bit unsigned wrappable counter."
   ::= {pr1645v2TvTmplPGreOutPQsD7PerformanceEntry 251658240}

pr1645v2TvTmplPGreOutPQsD7PerformanceDirTxOcts OBJECT-TYPE
   SYNTAX      Counter64
   MAX-ACCESS  read-only
   STATUS      current
   DESCRIPTION
      "Path: tunnels.performance.greTunnels.outPriorityQueues.d7Performance.directTxOctets

       64 bit unsigned wrappable counter."
   ::= {pr1645v2TvTmplPGreOutPQsD7PerformanceEntry 117440512}

pr1645v2TvTmplPGreOutPQsD7PerformanceQdOcts OBJECT-TYPE
   SYNTAX      Counter64
   MAX-ACCESS  read-only
   STATUS      current
   DESCRIPTION
      "Path: tunnels.performance.greTunnels.outPriorityQueues.d7Performance.queuedOctets

       64 bit unsigned wrappable counter."
   ::= {pr1645v2TvTmplPGreOutPQsD7PerformanceEntry 134217728}

pr1645v2TvTmplPGreOutPQsD7PerformanceDropOcts OBJECT-TYPE
   SYNTAX      Counter64
   MAX-ACCESS  read-only
   STATUS      current
   DESCRIPTION
      "Path: tunnels.performance.greTunnels.outPriorityQueues.d7Performance.droppedOctets

       64 bit unsigned wrappable counter."
   ::= {pr1645v2TvTmplPGreOutPQsD7PerformanceEntry 150994944}

pr1645v2TvTmplPGreOutPQsD7PerformanceRDropOcts OBJECT-TYPE
   SYNTAX      Counter64
   MAX-ACCESS  read-only
   STATUS      current
   DESCRIPTION
      "Path: tunnels.performance.greTunnels.outPriorityQueues.d7Performance.redDroppedOctets

       64 bit unsigned wrappable counter."
   ::= {pr1645v2TvTmplPGreOutPQsD7PerformanceEntry 218103808}

pr1645v2TvTmplPGreOutPQsD7PerformanceCirTxOcts OBJECT-TYPE
   SYNTAX      Counter64
   MAX-ACCESS  read-only
   STATUS      current
   DESCRIPTION
      "Path: tunnels.performance.greTunnels.outPriorityQueues.d7Performance.cirTxOctets

       64 bit unsigned wrappable counter."
   ::= {pr1645v2TvTmplPGreOutPQsD7PerformanceEntry 167772160}

pr1645v2TvTmplPGreOutPQsD7PerformanceEirTxOcts OBJECT-TYPE
   SYNTAX      Counter64
   MAX-ACCESS  read-only
   STATUS      current
   DESCRIPTION
      "Path: tunnels.performance.greTunnels.outPriorityQueues.d7Performance.eirTxOctets

       64 bit unsigned wrappable counter."
   ::= {pr1645v2TvTmplPGreOutPQsD7PerformanceEntry 184549376}

pr1645v2TvTmplPGreOutPQsD7PerformanceViolTxOcts OBJECT-TYPE
   SYNTAX      Counter64
   MAX-ACCESS  read-only
   STATUS      current
   DESCRIPTION
      "Path: tunnels.performance.greTunnels.outPriorityQueues.d7Performance.violateTxOctets

       64 bit unsigned wrappable counter."
   ::= {pr1645v2TvTmplPGreOutPQsD7PerformanceEntry 318767104}

pr1645v2TvTmplPGreOutPQsD7PerformanceBandwidth OBJECT-TYPE
   SYNTAX      Integer32
   MAX-ACCESS  read-only
   STATUS      current
   DESCRIPTION
      "Path: tunnels.performance.greTunnels.outPriorityQueues.d7Performance.bandwidth

       unit name = bps
       formula = 8 * ; 8 /"
   ::= {pr1645v2TvTmplPGreOutPQsD7PerformanceEntry 268435456}


pr1645v2TvTmplPiGre OBJECT IDENTIFIER ::= {pr1645v2TvTmpl 26}

pr1645v2TvTmplPiGreSSCTable OBJECT-TYPE
   SYNTAX      SEQUENCE OF Pr1645v2TvTmplPiGreEntry
   MAX-ACCESS  not-accessible
   STATUS      current
   DESCRIPTION
      ""
   ::= {pr1645v2TvTmplPiGre 1}

pr1645v2TvTmplPiGreEntry OBJECT-TYPE
   SYNTAX      Pr1645v2TvTmplPiGreEntry
   MAX-ACCESS  not-accessible
   STATUS      current
   DESCRIPTION
      ""
   INDEX      { pr1645v2TvTmplPiGreTableIx }
   ::= {pr1645v2TvTmplPiGreSSCTable 1}

Pr1645v2TvTmplPiGreEntry ::=
   SEQUENCE
      {
      pr1645v2TvTmplPiGreTableIx
         TableIndex,
      pr1645v2TvTmplPiGreName
         DisplayString,
      pr1645v2TvTmplPiGreMCInOctets
         Counter64,
      pr1645v2TvTmplPiGreMCInUcast
         Counter64,
      pr1645v2TvTmplPiGreMCInNUcastPkts
         Counter64,
      pr1645v2TvTmplPiGreMCInBcastPkts
         Counter64,
      pr1645v2TvTmplPiGreMCInMcastPkts
         Counter64,
      pr1645v2TvTmplPiGreMCInDiscards
         Counter64,
      pr1645v2TvTmplPiGreMCInErrors
         Counter64,
      pr1645v2TvTmplPiGreMCInUnknownProtos
         Counter64,
      pr1645v2TvTmplPiGreMCInDropEx
         Counter64,
      pr1645v2TvTmplPiGreMCInDropNoMac
         Counter64,
      pr1645v2TvTmplPiGreMCInDropNUCast
         Counter64,
      pr1645v2TvTmplPiGreMCInDropFilter
         Counter64,
      pr1645v2TvTmplPiGreMCInBandwidth15sec
         Integer32,
      pr1645v2TvTmplPiGreMCInBandwidth30sec
         Integer32,
      pr1645v2TvTmplPiGreMCInBandwidth1min
         Integer32,
      pr1645v2TvTmplPiGreMCInBandwidth2min
         Integer32,
      pr1645v2TvTmplPiGreMCInBandwidth5min
         Integer32,
      pr1645v2TvTmplPiGreMCOutOctets
         Counter64,
      pr1645v2TvTmplPiGreMCOutUcastPkts
         Counter64,
      pr1645v2TvTmplPiGreMCOutNUcastPkts
         Counter64,
      pr1645v2TvTmplPiGreMCOutBcastPkts
         Counter64,
      pr1645v2TvTmplPiGreMCOutMcastPkts
         Counter64,
      pr1645v2TvTmplPiGreMCOutDiscards
         Counter64,
      pr1645v2TvTmplPiGreMCOutErrors
         Counter64,
      pr1645v2TvTmplPiGreMCOutQLen
         Counter32,
      pr1645v2TvTmplPiGreMCOutDropEx
         Counter64,
      pr1645v2TvTmplPiGreMCOutDropNoArp
         Counter64,
      pr1645v2TvTmplPiGreMCOutDropFilter
         Counter64,
      pr1645v2TvTmplPiGreMCOutBandwidth15sec
         Integer32,
      pr1645v2TvTmplPiGreMCOutBandwidth30sec
         Integer32,
      pr1645v2TvTmplPiGreMCOutBandwidth1min
         Integer32,
      pr1645v2TvTmplPiGreMCOutBandwidth2min
         Integer32,
      pr1645v2TvTmplPiGreMCOutBandwidth5min
         Integer32,
      pr1645v2TvTmplPiGreGreKeepAliveRequestsSent
         Counter32,
      pr1645v2TvTmplPiGreGreKeepAliveRepliesRcvd
         Counter32
      }

pr1645v2TvTmplPiGreTableIx OBJECT-TYPE
   SYNTAX      TableIndex
   MAX-ACCESS  not-accessible
   STATUS      current
   DESCRIPTION
      ""
   ::= {pr1645v2TvTmplPiGreEntry 11}

pr1645v2TvTmplPiGreName OBJECT-TYPE
   SYNTAX      DisplayString
   MAX-ACCESS  read-only
   STATUS      current
   DESCRIPTION
      "Path: tunnels.performance.ipsecGreTunnels.name"
   ::= {pr1645v2TvTmplPiGreEntry 16777216}

pr1645v2TvTmplPiGreMCInOctets OBJECT-TYPE
   SYNTAX      Counter64
   MAX-ACCESS  read-only
   STATUS      current
   DESCRIPTION
      "Path: tunnels.performance.ipsecGreTunnels.mibCounters.ifInOctets

       64 bit unsigned wrappable counter."
   ::= {pr1645v2TvTmplPiGreEntry 40697856}

pr1645v2TvTmplPiGreMCInUcast OBJECT-TYPE
   SYNTAX      Counter64
   MAX-ACCESS  read-only
   STATUS      current
   DESCRIPTION
      "Path: tunnels.performance.ipsecGreTunnels.mibCounters.ifInUcastPkts

       64 bit unsigned wrappable counter."
   ::= {pr1645v2TvTmplPiGreEntry 40763392}

pr1645v2TvTmplPiGreMCInNUcastPkts OBJECT-TYPE
   SYNTAX      Counter64
   MAX-ACCESS  read-only
   STATUS      current
   DESCRIPTION
      "Path: tunnels.performance.ipsecGreTunnels.mibCounters.ifInNUcastPkts

       64 bit unsigned wrappable counter."
   ::= {pr1645v2TvTmplPiGreEntry 40828928}

pr1645v2TvTmplPiGreMCInBcastPkts OBJECT-TYPE
   SYNTAX      Counter64
   MAX-ACCESS  read-only
   STATUS      current
   DESCRIPTION
      "Path: tunnels.performance.ipsecGreTunnels.mibCounters.ifInBcastPkts

       64 bit unsigned wrappable counter."
   ::= {pr1645v2TvTmplPiGreEntry 47382528}

pr1645v2TvTmplPiGreMCInMcastPkts OBJECT-TYPE
   SYNTAX      Counter64
   MAX-ACCESS  read-only
   STATUS      current
   DESCRIPTION
      "Path: tunnels.performance.ipsecGreTunnels.mibCounters.ifInMcastPkts

       64 bit unsigned wrappable counter."
   ::= {pr1645v2TvTmplPiGreEntry 48037888}

pr1645v2TvTmplPiGreMCInDiscards OBJECT-TYPE
   SYNTAX      Counter64
   MAX-ACCESS  read-only
   STATUS      current
   DESCRIPTION
      "Path: tunnels.performance.ipsecGreTunnels.mibCounters.ifInDiscards

       64 bit unsigned wrappable counter."
   ::= {pr1645v2TvTmplPiGreEntry 40894464}

pr1645v2TvTmplPiGreMCInErrors OBJECT-TYPE
   SYNTAX      Counter64
   MAX-ACCESS  read-only
   STATUS      current
   DESCRIPTION
      "Path: tunnels.performance.ipsecGreTunnels.mibCounters.ifInErrors

       64 bit unsigned wrappable counter."
   ::= {pr1645v2TvTmplPiGreEntry 40960000}

pr1645v2TvTmplPiGreMCInUnknownProtos OBJECT-TYPE
   SYNTAX      Counter64
   MAX-ACCESS  read-only
   STATUS      current
   DESCRIPTION
      "Path: tunnels.performance.ipsecGreTunnels.mibCounters.ifInUnknownProtos

       64 bit unsigned wrappable counter."
   ::= {pr1645v2TvTmplPiGreEntry 41025536}

pr1645v2TvTmplPiGreMCInDropEx OBJECT-TYPE
   SYNTAX      Counter64
   MAX-ACCESS  read-only
   STATUS      current
   DESCRIPTION
      "Path: tunnels.performance.ipsecGreTunnels.mibCounters.ifInDropLevelExceeded

       64 bit unsigned wrappable counter."
   ::= {pr1645v2TvTmplPiGreEntry 42074112}

pr1645v2TvTmplPiGreMCInDropNoMac OBJECT-TYPE
   SYNTAX      Counter64
   MAX-ACCESS  read-only
   STATUS      current
   DESCRIPTION
      "Path: tunnels.performance.ipsecGreTunnels.mibCounters.ifInDiscardsNoMacFit

       64 bit unsigned wrappable counter."
   ::= {pr1645v2TvTmplPiGreEntry 42270720}

pr1645v2TvTmplPiGreMCInDropNUCast OBJECT-TYPE
   SYNTAX      Counter64
   MAX-ACCESS  read-only
   STATUS      current
   DESCRIPTION
      "Path: tunnels.performance.ipsecGreTunnels.mibCounters.ifInDiscardsNUCast

       64 bit unsigned wrappable counter."
   ::= {pr1645v2TvTmplPiGreEntry 42467328}

pr1645v2TvTmplPiGreMCInDropFilter OBJECT-TYPE
   SYNTAX      Counter64
   MAX-ACCESS  read-only
   STATUS      current
   DESCRIPTION
      "Path: tunnels.performance.ipsecGreTunnels.mibCounters.ifInDiscardsFilter

       64 bit unsigned wrappable counter."
   ::= {pr1645v2TvTmplPiGreEntry 42532864}

pr1645v2TvTmplPiGreMCInBandwidth15sec OBJECT-TYPE
   SYNTAX      Integer32
   MAX-ACCESS  read-only
   STATUS      current
   DESCRIPTION
      "Path: tunnels.performance.ipsecGreTunnels.mibCounters.ifInBandwidth.15sec

       unit name = bps
       formula = 8 * ; 8 /"
   ::= {pr1645v2TvTmplPiGreEntry 45417728}

pr1645v2TvTmplPiGreMCInBandwidth30sec OBJECT-TYPE
   SYNTAX      Integer32
   MAX-ACCESS  read-only
   STATUS      current
   DESCRIPTION
      "Path: tunnels.performance.ipsecGreTunnels.mibCounters.ifInBandwidth.30sec

       unit name = bps
       formula = 8 * ; 8 /"
   ::= {pr1645v2TvTmplPiGreEntry 45419008}

pr1645v2TvTmplPiGreMCInBandwidth1min OBJECT-TYPE
   SYNTAX      Integer32
   MAX-ACCESS  read-only
   STATUS      current
   DESCRIPTION
      "Path: tunnels.performance.ipsecGreTunnels.mibCounters.ifInBandwidth.1min

       unit name = bps
       formula = 8 * ; 8 /"
   ::= {pr1645v2TvTmplPiGreEntry 45421568}

pr1645v2TvTmplPiGreMCInBandwidth2min OBJECT-TYPE
   SYNTAX      Integer32
   MAX-ACCESS  read-only
   STATUS      current
   DESCRIPTION
      "Path: tunnels.performance.ipsecGreTunnels.mibCounters.ifInBandwidth.2min

       unit name = bps
       formula = 8 * ; 8 /"
   ::= {pr1645v2TvTmplPiGreEntry 45426688}

pr1645v2TvTmplPiGreMCInBandwidth5min OBJECT-TYPE
   SYNTAX      Integer32
   MAX-ACCESS  read-only
   STATUS      current
   DESCRIPTION
      "Path: tunnels.performance.ipsecGreTunnels.mibCounters.ifInBandwidth.5min

       unit name = bps
       formula = 8 * ; 8 /"
   ::= {pr1645v2TvTmplPiGreEntry 45442048}

pr1645v2TvTmplPiGreMCOutOctets OBJECT-TYPE
   SYNTAX      Counter64
   MAX-ACCESS  read-only
   STATUS      current
   DESCRIPTION
      "Path: tunnels.performance.ipsecGreTunnels.mibCounters.ifOutOctets

       64 bit unsigned wrappable counter."
   ::= {pr1645v2TvTmplPiGreEntry 41091072}

pr1645v2TvTmplPiGreMCOutUcastPkts OBJECT-TYPE
   SYNTAX      Counter64
   MAX-ACCESS  read-only
   STATUS      current
   DESCRIPTION
      "Path: tunnels.performance.ipsecGreTunnels.mibCounters.ifOutUcastPkts

       64 bit unsigned wrappable counter."
   ::= {pr1645v2TvTmplPiGreEntry 41156608}

pr1645v2TvTmplPiGreMCOutNUcastPkts OBJECT-TYPE
   SYNTAX      Counter64
   MAX-ACCESS  read-only
   STATUS      current
   DESCRIPTION
      "Path: tunnels.performance.ipsecGreTunnels.mibCounters.ifOutNUcastPkts

       64 bit unsigned wrappable counter."
   ::= {pr1645v2TvTmplPiGreEntry 41222144}

pr1645v2TvTmplPiGreMCOutBcastPkts OBJECT-TYPE
   SYNTAX      Counter64
   MAX-ACCESS  read-only
   STATUS      current
   DESCRIPTION
      "Path: tunnels.performance.ipsecGreTunnels.mibCounters.ifOutBcastPkts

       64 bit unsigned wrappable counter."
   ::= {pr1645v2TvTmplPiGreEntry 47775744}

pr1645v2TvTmplPiGreMCOutMcastPkts OBJECT-TYPE
   SYNTAX      Counter64
   MAX-ACCESS  read-only
   STATUS      current
   DESCRIPTION
      "Path: tunnels.performance.ipsecGreTunnels.mibCounters.ifOutMcastPkts

       64 bit unsigned wrappable counter."
   ::= {pr1645v2TvTmplPiGreEntry 48431104}

pr1645v2TvTmplPiGreMCOutDiscards OBJECT-TYPE
   SYNTAX      Counter64
   MAX-ACCESS  read-only
   STATUS      current
   DESCRIPTION
      "Path: tunnels.performance.ipsecGreTunnels.mibCounters.ifOutDiscards

       64 bit unsigned wrappable counter."
   ::= {pr1645v2TvTmplPiGreEntry 41287680}

pr1645v2TvTmplPiGreMCOutErrors OBJECT-TYPE
   SYNTAX      Counter64
   MAX-ACCESS  read-only
   STATUS      current
   DESCRIPTION
      "Path: tunnels.performance.ipsecGreTunnels.mibCounters.ifOutErrors

       64 bit unsigned wrappable counter."
   ::= {pr1645v2TvTmplPiGreEntry 41353216}

pr1645v2TvTmplPiGreMCOutQLen OBJECT-TYPE
   SYNTAX      Counter32
   MAX-ACCESS  read-only
   STATUS      current
   DESCRIPTION
      "Path: tunnels.performance.ipsecGreTunnels.mibCounters.ifOutQLen

       32 bit unsigned wrappable counter."
   ::= {pr1645v2TvTmplPiGreEntry 41418752}

pr1645v2TvTmplPiGreMCOutDropEx OBJECT-TYPE
   SYNTAX      Counter64
   MAX-ACCESS  read-only
   STATUS      current
   DESCRIPTION
      "Path: tunnels.performance.ipsecGreTunnels.mibCounters.ifOutDropLevelExceeded

       64 bit unsigned wrappable counter."
   ::= {pr1645v2TvTmplPiGreEntry 41484288}

pr1645v2TvTmplPiGreMCOutDropNoArp OBJECT-TYPE
   SYNTAX      Counter64
   MAX-ACCESS  read-only
   STATUS      current
   DESCRIPTION
      "Path: tunnels.performance.ipsecGreTunnels.mibCounters.ifOutDiscardsNoArp

       64 bit unsigned wrappable counter."
   ::= {pr1645v2TvTmplPiGreEntry 42336256}

pr1645v2TvTmplPiGreMCOutDropFilter OBJECT-TYPE
   SYNTAX      Counter64
   MAX-ACCESS  read-only
   STATUS      current
   DESCRIPTION
      "Path: tunnels.performance.ipsecGreTunnels.mibCounters.ifOutDiscardsFilter

       64 bit unsigned wrappable counter."
   ::= {pr1645v2TvTmplPiGreEntry 42598400}

pr1645v2TvTmplPiGreMCOutBandwidth15sec OBJECT-TYPE
   SYNTAX      Integer32
   MAX-ACCESS  read-only
   STATUS      current
   DESCRIPTION
      "Path: tunnels.performance.ipsecGreTunnels.mibCounters.ifOutBandwidth.15sec

       unit name = bps
       formula = 8 * ; 8 /"
   ::= {pr1645v2TvTmplPiGreEntry 45483264}

pr1645v2TvTmplPiGreMCOutBandwidth30sec OBJECT-TYPE
   SYNTAX      Integer32
   MAX-ACCESS  read-only
   STATUS      current
   DESCRIPTION
      "Path: tunnels.performance.ipsecGreTunnels.mibCounters.ifOutBandwidth.30sec

       unit name = bps
       formula = 8 * ; 8 /"
   ::= {pr1645v2TvTmplPiGreEntry 45484544}

pr1645v2TvTmplPiGreMCOutBandwidth1min OBJECT-TYPE
   SYNTAX      Integer32
   MAX-ACCESS  read-only
   STATUS      current
   DESCRIPTION
      "Path: tunnels.performance.ipsecGreTunnels.mibCounters.ifOutBandwidth.1min

       unit name = bps
       formula = 8 * ; 8 /"
   ::= {pr1645v2TvTmplPiGreEntry 45487104}

pr1645v2TvTmplPiGreMCOutBandwidth2min OBJECT-TYPE
   SYNTAX      Integer32
   MAX-ACCESS  read-only
   STATUS      current
   DESCRIPTION
      "Path: tunnels.performance.ipsecGreTunnels.mibCounters.ifOutBandwidth.2min

       unit name = bps
       formula = 8 * ; 8 /"
   ::= {pr1645v2TvTmplPiGreEntry 45492224}

pr1645v2TvTmplPiGreMCOutBandwidth5min OBJECT-TYPE
   SYNTAX      Integer32
   MAX-ACCESS  read-only
   STATUS      current
   DESCRIPTION
      "Path: tunnels.performance.ipsecGreTunnels.mibCounters.ifOutBandwidth.5min

       unit name = bps
       formula = 8 * ; 8 /"
   ::= {pr1645v2TvTmplPiGreEntry 45507584}

pr1645v2TvTmplPiGreGreKeepAliveRequestsSent OBJECT-TYPE
   SYNTAX      Counter32
   MAX-ACCESS  read-only
   STATUS      current
   DESCRIPTION
      "Path: tunnels.performance.ipsecGreTunnels.gre.keepAlive.requestsSent

       32 bit unsigned wrappable counter."
   ::= {pr1645v2TvTmplPiGreEntry 117506304}

pr1645v2TvTmplPiGreGreKeepAliveRepliesRcvd OBJECT-TYPE
   SYNTAX      Counter32
   MAX-ACCESS  read-only
   STATUS      current
   DESCRIPTION
      "Path: tunnels.performance.ipsecGreTunnels.gre.keepAlive.repliesRcvd

       32 bit unsigned wrappable counter."
   ::= {pr1645v2TvTmplPiGreEntry 117506560}

pr1645v2TvTmplPiGreMCH2P OBJECT-TYPE
   SYNTAX      SEQUENCE OF Pr1645v2TvTmplPiGreMCH2PEntry
   MAX-ACCESS  not-accessible
   STATUS      current
   DESCRIPTION
      ""
   ::= {pr1645v2TvTmplPiGre 41549824}

pr1645v2TvTmplPiGreMCH2PEntry OBJECT-TYPE
   SYNTAX      Pr1645v2TvTmplPiGreMCH2PEntry
   MAX-ACCESS  not-accessible
   STATUS      current
   DESCRIPTION
      ""
   INDEX      { pr1645v2TvTmplPiGreTableIx,
                pr1645v2TvTmplPiGreMCH2PTableIx }
   ::= {pr1645v2TvTmplPiGreMCH2P 1}

Pr1645v2TvTmplPiGreMCH2PEntry ::=
   SEQUENCE
      {
      pr1645v2TvTmplPiGreMCH2PTableIx
         TableIndex,
      pr1645v2TvTmplPiGreMCH2PSysUpTime
         TimeTicks,
      pr1645v2TvTmplPiGreMCH2PIfUpTime
         TimeTicks,
      pr1645v2TvTmplPiGreMCH2PIfStatChanges
         Counter32,
      pr1645v2TvTmplPiGreMCH2PIfInOctets
         Counter64,
      pr1645v2TvTmplPiGreMCH2PIfInUCPkts
         Counter64,
      pr1645v2TvTmplPiGreMCH2PIfInNUCPkts
         Counter64,
      pr1645v2TvTmplPiGreMCH2PIfInBCPkts
         Counter64,
      pr1645v2TvTmplPiGreMCH2PIfInMCPkts
         Counter64,
      pr1645v2TvTmplPiGreMCH2PIfInDiscards
         Counter64,
      pr1645v2TvTmplPiGreMCH2PIfInErrors
         Counter64,
      pr1645v2TvTmplPiGreMCH2PIfInUnkwn
         Counter64,
      pr1645v2TvTmplPiGreMCH2PInDropEx
         Counter64,
      pr1645v2TvTmplPiGreMCH2PInDropNoMac
         Counter64,
      pr1645v2TvTmplPiGreMCH2PInDropNUCast
         Counter64,
      pr1645v2TvTmplPiGreMCH2PInDropFilter
         Counter64,
      pr1645v2TvTmplPiGreMCH2PIfInBandwidth
         Integer32,
      pr1645v2TvTmplPiGreMCH2PIfOutOctets
         Counter64,
      pr1645v2TvTmplPiGreMCH2PIfOutUCPkts
         Counter64,
      pr1645v2TvTmplPiGreMCH2PIfOutNUCPkts
         Counter64,
      pr1645v2TvTmplPiGreMCH2PIfOutBCPkts
         Counter64,
      pr1645v2TvTmplPiGreMCH2PIfOutMCPkts
         Counter64,
      pr1645v2TvTmplPiGreMCH2PIfOutDiscards
         Counter64,
      pr1645v2TvTmplPiGreMCH2PIfOutErrors
         Counter64,
      pr1645v2TvTmplPiGreMCH2POutDropEx
         Counter64,
      pr1645v2TvTmplPiGreMCH2POutDropNoArp
         Counter64,
      pr1645v2TvTmplPiGreMCH2POutDropFilter
         Counter64,
      pr1645v2TvTmplPiGreMCH2PIfOutBandwidth
         Integer32,
      pr1645v2TvTmplPiGreMCH2PIfErrSec
         Counter32
      }

pr1645v2TvTmplPiGreMCH2PTableIx OBJECT-TYPE
   SYNTAX      TableIndex
   MAX-ACCESS  not-accessible
   STATUS      current
   DESCRIPTION
      ""
   ::= {pr1645v2TvTmplPiGreMCH2PEntry 11}

pr1645v2TvTmplPiGreMCH2PSysUpTime OBJECT-TYPE
   SYNTAX      TimeTicks
   MAX-ACCESS  read-only
   STATUS      current
   DESCRIPTION
      "Path: tunnels.performance.ipsecGreTunnels.mibCounters.h2Performance.sysUpTime

       Time in centi-second."
   ::= {pr1645v2TvTmplPiGreMCH2PEntry 16777216}

pr1645v2TvTmplPiGreMCH2PIfUpTime OBJECT-TYPE
   SYNTAX      TimeTicks
   MAX-ACCESS  read-only
   STATUS      current
   DESCRIPTION
      "Path: tunnels.performance.ipsecGreTunnels.mibCounters.h2Performance.ifUpTime

       Time in centi-second."
   ::= {pr1645v2TvTmplPiGreMCH2PEntry 33554432}

pr1645v2TvTmplPiGreMCH2PIfStatChanges OBJECT-TYPE
   SYNTAX      Counter32
   MAX-ACCESS  read-only
   STATUS      current
   DESCRIPTION
      "Path: tunnels.performance.ipsecGreTunnels.mibCounters.h2Performance.ifStatusChanges

       32 bit unsigned wrappable counter."
   ::= {pr1645v2TvTmplPiGreMCH2PEntry 50331648}

pr1645v2TvTmplPiGreMCH2PIfInOctets OBJECT-TYPE
   SYNTAX      Counter64
   MAX-ACCESS  read-only
   STATUS      current
   DESCRIPTION
      "Path: tunnels.performance.ipsecGreTunnels.mibCounters.h2Performance.ifInOctets

       64 bit unsigned wrappable counter."
   ::= {pr1645v2TvTmplPiGreMCH2PEntry 67108864}

pr1645v2TvTmplPiGreMCH2PIfInUCPkts OBJECT-TYPE
   SYNTAX      Counter64
   MAX-ACCESS  read-only
   STATUS      current
   DESCRIPTION
      "Path: tunnels.performance.ipsecGreTunnels.mibCounters.h2Performance.ifInUcastPkts

       64 bit unsigned wrappable counter."
   ::= {pr1645v2TvTmplPiGreMCH2PEntry 83886080}

pr1645v2TvTmplPiGreMCH2PIfInNUCPkts OBJECT-TYPE
   SYNTAX      Counter64
   MAX-ACCESS  read-only
   STATUS      current
   DESCRIPTION
      "Path: tunnels.performance.ipsecGreTunnels.mibCounters.h2Performance.ifInNUcastPkts

       64 bit unsigned wrappable counter."
   ::= {pr1645v2TvTmplPiGreMCH2PEntry 100663296}

pr1645v2TvTmplPiGreMCH2PIfInBCPkts OBJECT-TYPE
   SYNTAX      Counter64
   MAX-ACCESS  read-only
   STATUS      current
   DESCRIPTION
      "Path: tunnels.performance.ipsecGreTunnels.mibCounters.h2Performance.ifInBcastPkts

       64 bit unsigned wrappable counter."
   ::= {pr1645v2TvTmplPiGreMCH2PEntry 419430400}

pr1645v2TvTmplPiGreMCH2PIfInMCPkts OBJECT-TYPE
   SYNTAX      Counter64
   MAX-ACCESS  read-only
   STATUS      current
   DESCRIPTION
      "Path: tunnels.performance.ipsecGreTunnels.mibCounters.h2Performance.ifInMcastPkts

       64 bit unsigned wrappable counter."
   ::= {pr1645v2TvTmplPiGreMCH2PEntry 436207616}

pr1645v2TvTmplPiGreMCH2PIfInDiscards OBJECT-TYPE
   SYNTAX      Counter64
   MAX-ACCESS  read-only
   STATUS      current
   DESCRIPTION
      "Path: tunnels.performance.ipsecGreTunnels.mibCounters.h2Performance.ifInDiscards

       64 bit unsigned wrappable counter."
   ::= {pr1645v2TvTmplPiGreMCH2PEntry 117440512}

pr1645v2TvTmplPiGreMCH2PIfInErrors OBJECT-TYPE
   SYNTAX      Counter64
   MAX-ACCESS  read-only
   STATUS      current
   DESCRIPTION
      "Path: tunnels.performance.ipsecGreTunnels.mibCounters.h2Performance.ifInErrors

       64 bit unsigned wrappable counter."
   ::= {pr1645v2TvTmplPiGreMCH2PEntry 134217728}

pr1645v2TvTmplPiGreMCH2PIfInUnkwn OBJECT-TYPE
   SYNTAX      Counter64
   MAX-ACCESS  read-only
   STATUS      current
   DESCRIPTION
      "Path: tunnels.performance.ipsecGreTunnels.mibCounters.h2Performance.ifInUnknownProtos

       64 bit unsigned wrappable counter."
   ::= {pr1645v2TvTmplPiGreMCH2PEntry 150994944}

pr1645v2TvTmplPiGreMCH2PInDropEx OBJECT-TYPE
   SYNTAX      Counter64
   MAX-ACCESS  read-only
   STATUS      current
   DESCRIPTION
      "Path: tunnels.performance.ipsecGreTunnels.mibCounters.h2Performance.ifInDropLevelExceeded

       64 bit unsigned wrappable counter."
   ::= {pr1645v2TvTmplPiGreMCH2PEntry 335544320}

pr1645v2TvTmplPiGreMCH2PInDropNoMac OBJECT-TYPE
   SYNTAX      Counter64
   MAX-ACCESS  read-only
   STATUS      current
   DESCRIPTION
      "Path: tunnels.performance.ipsecGreTunnels.mibCounters.h2Performance.fInDiscardsNoMacFit

       64 bit unsigned wrappable counter."
   ::= {pr1645v2TvTmplPiGreMCH2PEntry 301989888}

pr1645v2TvTmplPiGreMCH2PInDropNUCast OBJECT-TYPE
   SYNTAX      Counter64
   MAX-ACCESS  read-only
   STATUS      current
   DESCRIPTION
      "Path: tunnels.performance.ipsecGreTunnels.mibCounters.h2Performance.fInDiscardsNUCast

       64 bit unsigned wrappable counter."
   ::= {pr1645v2TvTmplPiGreMCH2PEntry 318767104}

pr1645v2TvTmplPiGreMCH2PInDropFilter OBJECT-TYPE
   SYNTAX      Counter64
   MAX-ACCESS  read-only
   STATUS      current
   DESCRIPTION
      "Path: tunnels.performance.ipsecGreTunnels.mibCounters.h2Performance.fInDiscardsFilter

       64 bit unsigned wrappable counter."
   ::= {pr1645v2TvTmplPiGreMCH2PEntry 385875968}

pr1645v2TvTmplPiGreMCH2PIfInBandwidth OBJECT-TYPE
   SYNTAX      Integer32
   MAX-ACCESS  read-only
   STATUS      current
   DESCRIPTION
      "Path: tunnels.performance.ipsecGreTunnels.mibCounters.h2Performance.ifInBandwidth

       unit name = bps
       formula = 8 * ; 8 /"
   ::= {pr1645v2TvTmplPiGreMCH2PEntry 268435456}

pr1645v2TvTmplPiGreMCH2PIfOutOctets OBJECT-TYPE
   SYNTAX      Counter64
   MAX-ACCESS  read-only
   STATUS      current
   DESCRIPTION
      "Path: tunnels.performance.ipsecGreTunnels.mibCounters.h2Performance.ifOutOctets

       64 bit unsigned wrappable counter."
   ::= {pr1645v2TvTmplPiGreMCH2PEntry 167772160}

pr1645v2TvTmplPiGreMCH2PIfOutUCPkts OBJECT-TYPE
   SYNTAX      Counter64
   MAX-ACCESS  read-only
   STATUS      current
   DESCRIPTION
      "Path: tunnels.performance.ipsecGreTunnels.mibCounters.h2Performance.ifOutUcastPkts

       64 bit unsigned wrappable counter."
   ::= {pr1645v2TvTmplPiGreMCH2PEntry 184549376}

pr1645v2TvTmplPiGreMCH2PIfOutNUCPkts OBJECT-TYPE
   SYNTAX      Counter64
   MAX-ACCESS  read-only
   STATUS      current
   DESCRIPTION
      "Path: tunnels.performance.ipsecGreTunnels.mibCounters.h2Performance.ifOutNUcastPkts

       64 bit unsigned wrappable counter."
   ::= {pr1645v2TvTmplPiGreMCH2PEntry 201326592}

pr1645v2TvTmplPiGreMCH2PIfOutBCPkts OBJECT-TYPE
   SYNTAX      Counter64
   MAX-ACCESS  read-only
   STATUS      current
   DESCRIPTION
      "Path: tunnels.performance.ipsecGreTunnels.mibCounters.h2Performance.ifOutBcastPkts

       64 bit unsigned wrappable counter."
   ::= {pr1645v2TvTmplPiGreMCH2PEntry 452984832}

pr1645v2TvTmplPiGreMCH2PIfOutMCPkts OBJECT-TYPE
   SYNTAX      Counter64
   MAX-ACCESS  read-only
   STATUS      current
   DESCRIPTION
      "Path: tunnels.performance.ipsecGreTunnels.mibCounters.h2Performance.ifOutMcastPkts

       64 bit unsigned wrappable counter."
   ::= {pr1645v2TvTmplPiGreMCH2PEntry 469762048}

pr1645v2TvTmplPiGreMCH2PIfOutDiscards OBJECT-TYPE
   SYNTAX      Counter64
   MAX-ACCESS  read-only
   STATUS      current
   DESCRIPTION
      "Path: tunnels.performance.ipsecGreTunnels.mibCounters.h2Performance.ifOutDiscards

       64 bit unsigned wrappable counter."
   ::= {pr1645v2TvTmplPiGreMCH2PEntry 218103808}

pr1645v2TvTmplPiGreMCH2PIfOutErrors OBJECT-TYPE
   SYNTAX      Counter64
   MAX-ACCESS  read-only
   STATUS      current
   DESCRIPTION
      "Path: tunnels.performance.ipsecGreTunnels.mibCounters.h2Performance.ifOutErrors

       64 bit unsigned wrappable counter."
   ::= {pr1645v2TvTmplPiGreMCH2PEntry 234881024}

pr1645v2TvTmplPiGreMCH2POutDropEx OBJECT-TYPE
   SYNTAX      Counter64
   MAX-ACCESS  read-only
   STATUS      current
   DESCRIPTION
      "Path: tunnels.performance.ipsecGreTunnels.mibCounters.h2Performance.ifOutDropLevelExceeded

       64 bit unsigned wrappable counter."
   ::= {pr1645v2TvTmplPiGreMCH2PEntry 352321536}

pr1645v2TvTmplPiGreMCH2POutDropNoArp OBJECT-TYPE
   SYNTAX      Counter64
   MAX-ACCESS  read-only
   STATUS      current
   DESCRIPTION
      "Path: tunnels.performance.ipsecGreTunnels.mibCounters.h2Performance.ifOutDiscardsNoArp

       64 bit unsigned wrappable counter."
   ::= {pr1645v2TvTmplPiGreMCH2PEntry 369098752}

pr1645v2TvTmplPiGreMCH2POutDropFilter OBJECT-TYPE
   SYNTAX      Counter64
   MAX-ACCESS  read-only
   STATUS      current
   DESCRIPTION
      "Path: tunnels.performance.ipsecGreTunnels.mibCounters.h2Performance.ifOutDiscardsFilter

       64 bit unsigned wrappable counter."
   ::= {pr1645v2TvTmplPiGreMCH2PEntry 402653184}

pr1645v2TvTmplPiGreMCH2PIfOutBandwidth OBJECT-TYPE
   SYNTAX      Integer32
   MAX-ACCESS  read-only
   STATUS      current
   DESCRIPTION
      "Path: tunnels.performance.ipsecGreTunnels.mibCounters.h2Performance.ifOutBandwidth

       unit name = bps
       formula = 8 * ; 8 /"
   ::= {pr1645v2TvTmplPiGreMCH2PEntry 285212672}

pr1645v2TvTmplPiGreMCH2PIfErrSec OBJECT-TYPE
   SYNTAX      Counter32
   MAX-ACCESS  read-only
   STATUS      current
   DESCRIPTION
      "Path: tunnels.performance.ipsecGreTunnels.mibCounters.h2Performance.ifErrSec

       32 bit unsigned wrappable counter."
   ::= {pr1645v2TvTmplPiGreMCH2PEntry 251658240}

pr1645v2TvTmplPiGreMCH24P OBJECT-TYPE
   SYNTAX      SEQUENCE OF Pr1645v2TvTmplPiGreMCH24PEntry
   MAX-ACCESS  not-accessible
   STATUS      current
   DESCRIPTION
      ""
   ::= {pr1645v2TvTmplPiGre 41615360}

pr1645v2TvTmplPiGreMCH24PEntry OBJECT-TYPE
   SYNTAX      Pr1645v2TvTmplPiGreMCH24PEntry
   MAX-ACCESS  not-accessible
   STATUS      current
   DESCRIPTION
      ""
   INDEX      { pr1645v2TvTmplPiGreTableIx,
                pr1645v2TvTmplPiGreMCH24PTableIx }
   ::= {pr1645v2TvTmplPiGreMCH24P 1}

Pr1645v2TvTmplPiGreMCH24PEntry ::=
   SEQUENCE
      {
      pr1645v2TvTmplPiGreMCH24PTableIx
         TableIndex,
      pr1645v2TvTmplPiGreMCH24PSysUpTime
         TimeTicks,
      pr1645v2TvTmplPiGreMCH24PIfUpTime
         TimeTicks,
      pr1645v2TvTmplPiGreMCH24PIfStatChanges
         Counter32,
      pr1645v2TvTmplPiGreMCH24PIfInOctets
         Counter64,
      pr1645v2TvTmplPiGreMCH24PIfInUCPkts
         Counter64,
      pr1645v2TvTmplPiGreMCH24PIfInNUCPkts
         Counter64,
      pr1645v2TvTmplPiGreMCH24PIfInBCPkts
         Counter64,
      pr1645v2TvTmplPiGreMCH24PIfInMCPkts
         Counter64,
      pr1645v2TvTmplPiGreMCH24PIfInDiscards
         Counter64,
      pr1645v2TvTmplPiGreMCH24PIfInErrors
         Counter64,
      pr1645v2TvTmplPiGreMCH24PIfInUnkwn
         Counter64,
      pr1645v2TvTmplPiGreMCH24PInDropEx
         Counter64,
      pr1645v2TvTmplPiGreMCH24PInDropNoMac
         Counter64,
      pr1645v2TvTmplPiGreMCH24PInDropNUCast
         Counter64,
      pr1645v2TvTmplPiGreMCH24PInDropFilter
         Counter64,
      pr1645v2TvTmplPiGreMCH24PIfInBandwidth
         Integer32,
      pr1645v2TvTmplPiGreMCH24PIfOutOctets
         Counter64,
      pr1645v2TvTmplPiGreMCH24PIfOutUCPkts
         Counter64,
      pr1645v2TvTmplPiGreMCH24PIfOutNUCPkts
         Counter64,
      pr1645v2TvTmplPiGreMCH24PIfOutBCPkts
         Counter64,
      pr1645v2TvTmplPiGreMCH24PIfOutMCPkts
         Counter64,
      pr1645v2TvTmplPiGreMCH24PIfOutDiscards
         Counter64,
      pr1645v2TvTmplPiGreMCH24PIfOutErrors
         Counter64,
      pr1645v2TvTmplPiGreMCH24POutDropEx
         Counter64,
      pr1645v2TvTmplPiGreMCH24POutDropNoArp
         Counter64,
      pr1645v2TvTmplPiGreMCH24POutDropFilter
         Counter64,
      pr1645v2TvTmplPiGreMCH24PIfOutBandwidth
         Integer32,
      pr1645v2TvTmplPiGreMCH24PIfErrSec
         Counter32
      }

pr1645v2TvTmplPiGreMCH24PTableIx OBJECT-TYPE
   SYNTAX      TableIndex
   MAX-ACCESS  not-accessible
   STATUS      current
   DESCRIPTION
      ""
   ::= {pr1645v2TvTmplPiGreMCH24PEntry 11}

pr1645v2TvTmplPiGreMCH24PSysUpTime OBJECT-TYPE
   SYNTAX      TimeTicks
   MAX-ACCESS  read-only
   STATUS      current
   DESCRIPTION
      "Path: tunnels.performance.ipsecGreTunnels.mibCounters.h24Performance.sysUpTime

       Time in centi-second."
   ::= {pr1645v2TvTmplPiGreMCH24PEntry 16777216}

pr1645v2TvTmplPiGreMCH24PIfUpTime OBJECT-TYPE
   SYNTAX      TimeTicks
   MAX-ACCESS  read-only
   STATUS      current
   DESCRIPTION
      "Path: tunnels.performance.ipsecGreTunnels.mibCounters.h24Performance.ifUpTime

       Time in centi-second."
   ::= {pr1645v2TvTmplPiGreMCH24PEntry 33554432}

pr1645v2TvTmplPiGreMCH24PIfStatChanges OBJECT-TYPE
   SYNTAX      Counter32
   MAX-ACCESS  read-only
   STATUS      current
   DESCRIPTION
      "Path: tunnels.performance.ipsecGreTunnels.mibCounters.h24Performance.ifStatusChanges

       32 bit unsigned wrappable counter."
   ::= {pr1645v2TvTmplPiGreMCH24PEntry 50331648}

pr1645v2TvTmplPiGreMCH24PIfInOctets OBJECT-TYPE
   SYNTAX      Counter64
   MAX-ACCESS  read-only
   STATUS      current
   DESCRIPTION
      "Path: tunnels.performance.ipsecGreTunnels.mibCounters.h24Performance.ifInOctets

       64 bit unsigned wrappable counter."
   ::= {pr1645v2TvTmplPiGreMCH24PEntry 67108864}

pr1645v2TvTmplPiGreMCH24PIfInUCPkts OBJECT-TYPE
   SYNTAX      Counter64
   MAX-ACCESS  read-only
   STATUS      current
   DESCRIPTION
      "Path: tunnels.performance.ipsecGreTunnels.mibCounters.h24Performance.ifInUcastPkts

       64 bit unsigned wrappable counter."
   ::= {pr1645v2TvTmplPiGreMCH24PEntry 83886080}

pr1645v2TvTmplPiGreMCH24PIfInNUCPkts OBJECT-TYPE
   SYNTAX      Counter64
   MAX-ACCESS  read-only
   STATUS      current
   DESCRIPTION
      "Path: tunnels.performance.ipsecGreTunnels.mibCounters.h24Performance.ifInNUcastPkts

       64 bit unsigned wrappable counter."
   ::= {pr1645v2TvTmplPiGreMCH24PEntry 100663296}

pr1645v2TvTmplPiGreMCH24PIfInBCPkts OBJECT-TYPE
   SYNTAX      Counter64
   MAX-ACCESS  read-only
   STATUS      current
   DESCRIPTION
      "Path: tunnels.performance.ipsecGreTunnels.mibCounters.h24Performance.ifInBcastPkts

       64 bit unsigned wrappable counter."
   ::= {pr1645v2TvTmplPiGreMCH24PEntry 419430400}

pr1645v2TvTmplPiGreMCH24PIfInMCPkts OBJECT-TYPE
   SYNTAX      Counter64
   MAX-ACCESS  read-only
   STATUS      current
   DESCRIPTION
      "Path: tunnels.performance.ipsecGreTunnels.mibCounters.h24Performance.ifInMcastPkts

       64 bit unsigned wrappable counter."
   ::= {pr1645v2TvTmplPiGreMCH24PEntry 436207616}

pr1645v2TvTmplPiGreMCH24PIfInDiscards OBJECT-TYPE
   SYNTAX      Counter64
   MAX-ACCESS  read-only
   STATUS      current
   DESCRIPTION
      "Path: tunnels.performance.ipsecGreTunnels.mibCounters.h24Performance.ifInDiscards

       64 bit unsigned wrappable counter."
   ::= {pr1645v2TvTmplPiGreMCH24PEntry 117440512}

pr1645v2TvTmplPiGreMCH24PIfInErrors OBJECT-TYPE
   SYNTAX      Counter64
   MAX-ACCESS  read-only
   STATUS      current
   DESCRIPTION
      "Path: tunnels.performance.ipsecGreTunnels.mibCounters.h24Performance.ifInErrors

       64 bit unsigned wrappable counter."
   ::= {pr1645v2TvTmplPiGreMCH24PEntry 134217728}

pr1645v2TvTmplPiGreMCH24PIfInUnkwn OBJECT-TYPE
   SYNTAX      Counter64
   MAX-ACCESS  read-only
   STATUS      current
   DESCRIPTION
      "Path: tunnels.performance.ipsecGreTunnels.mibCounters.h24Performance.ifInUnknownProtos

       64 bit unsigned wrappable counter."
   ::= {pr1645v2TvTmplPiGreMCH24PEntry 150994944}

pr1645v2TvTmplPiGreMCH24PInDropEx OBJECT-TYPE
   SYNTAX      Counter64
   MAX-ACCESS  read-only
   STATUS      current
   DESCRIPTION
      "Path: tunnels.performance.ipsecGreTunnels.mibCounters.h24Performance.ifInDropLevelExceeded

       64 bit unsigned wrappable counter."
   ::= {pr1645v2TvTmplPiGreMCH24PEntry 335544320}

pr1645v2TvTmplPiGreMCH24PInDropNoMac OBJECT-TYPE
   SYNTAX      Counter64
   MAX-ACCESS  read-only
   STATUS      current
   DESCRIPTION
      "Path: tunnels.performance.ipsecGreTunnels.mibCounters.h24Performance.fInDiscardsNoMacFit

       64 bit unsigned wrappable counter."
   ::= {pr1645v2TvTmplPiGreMCH24PEntry 301989888}

pr1645v2TvTmplPiGreMCH24PInDropNUCast OBJECT-TYPE
   SYNTAX      Counter64
   MAX-ACCESS  read-only
   STATUS      current
   DESCRIPTION
      "Path: tunnels.performance.ipsecGreTunnels.mibCounters.h24Performance.fInDiscardsNUCast

       64 bit unsigned wrappable counter."
   ::= {pr1645v2TvTmplPiGreMCH24PEntry 318767104}

pr1645v2TvTmplPiGreMCH24PInDropFilter OBJECT-TYPE
   SYNTAX      Counter64
   MAX-ACCESS  read-only
   STATUS      current
   DESCRIPTION
      "Path: tunnels.performance.ipsecGreTunnels.mibCounters.h24Performance.fInDiscardsFilter

       64 bit unsigned wrappable counter."
   ::= {pr1645v2TvTmplPiGreMCH24PEntry 385875968}

pr1645v2TvTmplPiGreMCH24PIfInBandwidth OBJECT-TYPE
   SYNTAX      Integer32
   MAX-ACCESS  read-only
   STATUS      current
   DESCRIPTION
      "Path: tunnels.performance.ipsecGreTunnels.mibCounters.h24Performance.ifInBandwidth

       unit name = bps
       formula = 8 * ; 8 /"
   ::= {pr1645v2TvTmplPiGreMCH24PEntry 268435456}

pr1645v2TvTmplPiGreMCH24PIfOutOctets OBJECT-TYPE
   SYNTAX      Counter64
   MAX-ACCESS  read-only
   STATUS      current
   DESCRIPTION
      "Path: tunnels.performance.ipsecGreTunnels.mibCounters.h24Performance.ifOutOctets

       64 bit unsigned wrappable counter."
   ::= {pr1645v2TvTmplPiGreMCH24PEntry 167772160}

pr1645v2TvTmplPiGreMCH24PIfOutUCPkts OBJECT-TYPE
   SYNTAX      Counter64
   MAX-ACCESS  read-only
   STATUS      current
   DESCRIPTION
      "Path: tunnels.performance.ipsecGreTunnels.mibCounters.h24Performance.ifOutUcastPkts

       64 bit unsigned wrappable counter."
   ::= {pr1645v2TvTmplPiGreMCH24PEntry 184549376}

pr1645v2TvTmplPiGreMCH24PIfOutNUCPkts OBJECT-TYPE
   SYNTAX      Counter64
   MAX-ACCESS  read-only
   STATUS      current
   DESCRIPTION
      "Path: tunnels.performance.ipsecGreTunnels.mibCounters.h24Performance.ifOutNUcastPkts

       64 bit unsigned wrappable counter."
   ::= {pr1645v2TvTmplPiGreMCH24PEntry 201326592}

pr1645v2TvTmplPiGreMCH24PIfOutBCPkts OBJECT-TYPE
   SYNTAX      Counter64
   MAX-ACCESS  read-only
   STATUS      current
   DESCRIPTION
      "Path: tunnels.performance.ipsecGreTunnels.mibCounters.h24Performance.ifOutBcastPkts

       64 bit unsigned wrappable counter."
   ::= {pr1645v2TvTmplPiGreMCH24PEntry 452984832}

pr1645v2TvTmplPiGreMCH24PIfOutMCPkts OBJECT-TYPE
   SYNTAX      Counter64
   MAX-ACCESS  read-only
   STATUS      current
   DESCRIPTION
      "Path: tunnels.performance.ipsecGreTunnels.mibCounters.h24Performance.ifOutMcastPkts

       64 bit unsigned wrappable counter."
   ::= {pr1645v2TvTmplPiGreMCH24PEntry 469762048}

pr1645v2TvTmplPiGreMCH24PIfOutDiscards OBJECT-TYPE
   SYNTAX      Counter64
   MAX-ACCESS  read-only
   STATUS      current
   DESCRIPTION
      "Path: tunnels.performance.ipsecGreTunnels.mibCounters.h24Performance.ifOutDiscards

       64 bit unsigned wrappable counter."
   ::= {pr1645v2TvTmplPiGreMCH24PEntry 218103808}

pr1645v2TvTmplPiGreMCH24PIfOutErrors OBJECT-TYPE
   SYNTAX      Counter64
   MAX-ACCESS  read-only
   STATUS      current
   DESCRIPTION
      "Path: tunnels.performance.ipsecGreTunnels.mibCounters.h24Performance.ifOutErrors

       64 bit unsigned wrappable counter."
   ::= {pr1645v2TvTmplPiGreMCH24PEntry 234881024}

pr1645v2TvTmplPiGreMCH24POutDropEx OBJECT-TYPE
   SYNTAX      Counter64
   MAX-ACCESS  read-only
   STATUS      current
   DESCRIPTION
      "Path: tunnels.performance.ipsecGreTunnels.mibCounters.h24Performance.ifOutDropLevelExceeded

       64 bit unsigned wrappable counter."
   ::= {pr1645v2TvTmplPiGreMCH24PEntry 352321536}

pr1645v2TvTmplPiGreMCH24POutDropNoArp OBJECT-TYPE
   SYNTAX      Counter64
   MAX-ACCESS  read-only
   STATUS      current
   DESCRIPTION
      "Path: tunnels.performance.ipsecGreTunnels.mibCounters.h24Performance.ifOutDiscardsNoArp

       64 bit unsigned wrappable counter."
   ::= {pr1645v2TvTmplPiGreMCH24PEntry 369098752}

pr1645v2TvTmplPiGreMCH24POutDropFilter OBJECT-TYPE
   SYNTAX      Counter64
   MAX-ACCESS  read-only
   STATUS      current
   DESCRIPTION
      "Path: tunnels.performance.ipsecGreTunnels.mibCounters.h24Performance.ifOutDiscardsFilter

       64 bit unsigned wrappable counter."
   ::= {pr1645v2TvTmplPiGreMCH24PEntry 402653184}

pr1645v2TvTmplPiGreMCH24PIfOutBandwidth OBJECT-TYPE
   SYNTAX      Integer32
   MAX-ACCESS  read-only
   STATUS      current
   DESCRIPTION
      "Path: tunnels.performance.ipsecGreTunnels.mibCounters.h24Performance.ifOutBandwidth

       unit name = bps
       formula = 8 * ; 8 /"
   ::= {pr1645v2TvTmplPiGreMCH24PEntry 285212672}

pr1645v2TvTmplPiGreMCH24PIfErrSec OBJECT-TYPE
   SYNTAX      Counter32
   MAX-ACCESS  read-only
   STATUS      current
   DESCRIPTION
      "Path: tunnels.performance.ipsecGreTunnels.mibCounters.h24Performance.ifErrSec

       32 bit unsigned wrappable counter."
   ::= {pr1645v2TvTmplPiGreMCH24PEntry 251658240}

pr1645v2TvTmplPiGreMCD7P OBJECT-TYPE
   SYNTAX      SEQUENCE OF Pr1645v2TvTmplPiGreMCD7PEntry
   MAX-ACCESS  not-accessible
   STATUS      current
   DESCRIPTION
      ""
   ::= {pr1645v2TvTmplPiGre 41680896}

pr1645v2TvTmplPiGreMCD7PEntry OBJECT-TYPE
   SYNTAX      Pr1645v2TvTmplPiGreMCD7PEntry
   MAX-ACCESS  not-accessible
   STATUS      current
   DESCRIPTION
      ""
   INDEX      { pr1645v2TvTmplPiGreTableIx,
                pr1645v2TvTmplPiGreMCD7PTableIx }
   ::= {pr1645v2TvTmplPiGreMCD7P 1}

Pr1645v2TvTmplPiGreMCD7PEntry ::=
   SEQUENCE
      {
      pr1645v2TvTmplPiGreMCD7PTableIx
         TableIndex,
      pr1645v2TvTmplPiGreMCD7PSysUpTime
         TimeTicks,
      pr1645v2TvTmplPiGreMCD7PIfUpTime
         TimeTicks,
      pr1645v2TvTmplPiGreMCD7PIfStatChanges
         Counter32,
      pr1645v2TvTmplPiGreMCD7PIfInOctets
         Counter64,
      pr1645v2TvTmplPiGreMCD7PIfInUCPkts
         Counter64,
      pr1645v2TvTmplPiGreMCD7PIfInNUCPkts
         Counter64,
      pr1645v2TvTmplPiGreMCD7PIfInBCPkts
         Counter64,
      pr1645v2TvTmplPiGreMCD7PIfInMCPkts
         Counter64,
      pr1645v2TvTmplPiGreMCD7PIfInDiscards
         Counter64,
      pr1645v2TvTmplPiGreMCD7PIfInErrors
         Counter64,
      pr1645v2TvTmplPiGreMCD7PIfInUnkwn
         Counter64,
      pr1645v2TvTmplPiGreMCD7PInDropEx
         Counter64,
      pr1645v2TvTmplPiGreMCD7PInDropNoMac
         Counter64,
      pr1645v2TvTmplPiGreMCD7PInDropNUCast
         Counter64,
      pr1645v2TvTmplPiGreMCD7PInDropFilter
         Counter64,
      pr1645v2TvTmplPiGreMCD7PIfInBandwidth
         Integer32,
      pr1645v2TvTmplPiGreMCD7PIfOutOctets
         Counter64,
      pr1645v2TvTmplPiGreMCD7PIfOutUCPkts
         Counter64,
      pr1645v2TvTmplPiGreMCD7PIfOutNUCPkts
         Counter64,
      pr1645v2TvTmplPiGreMCD7PIfOutBCPkts
         Counter64,
      pr1645v2TvTmplPiGreMCD7PIfOutMCPkts
         Counter64,
      pr1645v2TvTmplPiGreMCD7PIfOutDiscards
         Counter64,
      pr1645v2TvTmplPiGreMCD7PIfOutErrors
         Counter64,
      pr1645v2TvTmplPiGreMCD7POutDropEx
         Counter64,
      pr1645v2TvTmplPiGreMCD7POutDropNoArp
         Counter64,
      pr1645v2TvTmplPiGreMCD7POutDropFilter
         Counter64,
      pr1645v2TvTmplPiGreMCD7PIfOutBandwidth
         Integer32,
      pr1645v2TvTmplPiGreMCD7PIfErrSec
         Counter32
      }

pr1645v2TvTmplPiGreMCD7PTableIx OBJECT-TYPE
   SYNTAX      TableIndex
   MAX-ACCESS  not-accessible
   STATUS      current
   DESCRIPTION
      ""
   ::= {pr1645v2TvTmplPiGreMCD7PEntry 11}

pr1645v2TvTmplPiGreMCD7PSysUpTime OBJECT-TYPE
   SYNTAX      TimeTicks
   MAX-ACCESS  read-only
   STATUS      current
   DESCRIPTION
      "Path: tunnels.performance.ipsecGreTunnels.mibCounters.d7Performance.sysUpTime

       Time in centi-second."
   ::= {pr1645v2TvTmplPiGreMCD7PEntry 16777216}

pr1645v2TvTmplPiGreMCD7PIfUpTime OBJECT-TYPE
   SYNTAX      TimeTicks
   MAX-ACCESS  read-only
   STATUS      current
   DESCRIPTION
      "Path: tunnels.performance.ipsecGreTunnels.mibCounters.d7Performance.ifUpTime

       Time in centi-second."
   ::= {pr1645v2TvTmplPiGreMCD7PEntry 33554432}

pr1645v2TvTmplPiGreMCD7PIfStatChanges OBJECT-TYPE
   SYNTAX      Counter32
   MAX-ACCESS  read-only
   STATUS      current
   DESCRIPTION
      "Path: tunnels.performance.ipsecGreTunnels.mibCounters.d7Performance.ifStatusChanges

       32 bit unsigned wrappable counter."
   ::= {pr1645v2TvTmplPiGreMCD7PEntry 50331648}

pr1645v2TvTmplPiGreMCD7PIfInOctets OBJECT-TYPE
   SYNTAX      Counter64
   MAX-ACCESS  read-only
   STATUS      current
   DESCRIPTION
      "Path: tunnels.performance.ipsecGreTunnels.mibCounters.d7Performance.ifInOctets

       64 bit unsigned wrappable counter."
   ::= {pr1645v2TvTmplPiGreMCD7PEntry 67108864}

pr1645v2TvTmplPiGreMCD7PIfInUCPkts OBJECT-TYPE
   SYNTAX      Counter64
   MAX-ACCESS  read-only
   STATUS      current
   DESCRIPTION
      "Path: tunnels.performance.ipsecGreTunnels.mibCounters.d7Performance.ifInUcastPkts

       64 bit unsigned wrappable counter."
   ::= {pr1645v2TvTmplPiGreMCD7PEntry 83886080}

pr1645v2TvTmplPiGreMCD7PIfInNUCPkts OBJECT-TYPE
   SYNTAX      Counter64
   MAX-ACCESS  read-only
   STATUS      current
   DESCRIPTION
      "Path: tunnels.performance.ipsecGreTunnels.mibCounters.d7Performance.ifInNUcastPkts

       64 bit unsigned wrappable counter."
   ::= {pr1645v2TvTmplPiGreMCD7PEntry 100663296}

pr1645v2TvTmplPiGreMCD7PIfInBCPkts OBJECT-TYPE
   SYNTAX      Counter64
   MAX-ACCESS  read-only
   STATUS      current
   DESCRIPTION
      "Path: tunnels.performance.ipsecGreTunnels.mibCounters.d7Performance.ifInBcastPkts

       64 bit unsigned wrappable counter."
   ::= {pr1645v2TvTmplPiGreMCD7PEntry 419430400}

pr1645v2TvTmplPiGreMCD7PIfInMCPkts OBJECT-TYPE
   SYNTAX      Counter64
   MAX-ACCESS  read-only
   STATUS      current
   DESCRIPTION
      "Path: tunnels.performance.ipsecGreTunnels.mibCounters.d7Performance.ifInMcastPkts

       64 bit unsigned wrappable counter."
   ::= {pr1645v2TvTmplPiGreMCD7PEntry 436207616}

pr1645v2TvTmplPiGreMCD7PIfInDiscards OBJECT-TYPE
   SYNTAX      Counter64
   MAX-ACCESS  read-only
   STATUS      current
   DESCRIPTION
      "Path: tunnels.performance.ipsecGreTunnels.mibCounters.d7Performance.ifInDiscards

       64 bit unsigned wrappable counter."
   ::= {pr1645v2TvTmplPiGreMCD7PEntry 117440512}

pr1645v2TvTmplPiGreMCD7PIfInErrors OBJECT-TYPE
   SYNTAX      Counter64
   MAX-ACCESS  read-only
   STATUS      current
   DESCRIPTION
      "Path: tunnels.performance.ipsecGreTunnels.mibCounters.d7Performance.ifInErrors

       64 bit unsigned wrappable counter."
   ::= {pr1645v2TvTmplPiGreMCD7PEntry 134217728}

pr1645v2TvTmplPiGreMCD7PIfInUnkwn OBJECT-TYPE
   SYNTAX      Counter64
   MAX-ACCESS  read-only
   STATUS      current
   DESCRIPTION
      "Path: tunnels.performance.ipsecGreTunnels.mibCounters.d7Performance.ifInUnknownProtos

       64 bit unsigned wrappable counter."
   ::= {pr1645v2TvTmplPiGreMCD7PEntry 150994944}

pr1645v2TvTmplPiGreMCD7PInDropEx OBJECT-TYPE
   SYNTAX      Counter64
   MAX-ACCESS  read-only
   STATUS      current
   DESCRIPTION
      "Path: tunnels.performance.ipsecGreTunnels.mibCounters.d7Performance.ifInDropLevelExceeded

       64 bit unsigned wrappable counter."
   ::= {pr1645v2TvTmplPiGreMCD7PEntry 335544320}

pr1645v2TvTmplPiGreMCD7PInDropNoMac OBJECT-TYPE
   SYNTAX      Counter64
   MAX-ACCESS  read-only
   STATUS      current
   DESCRIPTION
      "Path: tunnels.performance.ipsecGreTunnels.mibCounters.d7Performance.fInDiscardsNoMacFit

       64 bit unsigned wrappable counter."
   ::= {pr1645v2TvTmplPiGreMCD7PEntry 301989888}

pr1645v2TvTmplPiGreMCD7PInDropNUCast OBJECT-TYPE
   SYNTAX      Counter64
   MAX-ACCESS  read-only
   STATUS      current
   DESCRIPTION
      "Path: tunnels.performance.ipsecGreTunnels.mibCounters.d7Performance.fInDiscardsNUCast

       64 bit unsigned wrappable counter."
   ::= {pr1645v2TvTmplPiGreMCD7PEntry 318767104}

pr1645v2TvTmplPiGreMCD7PInDropFilter OBJECT-TYPE
   SYNTAX      Counter64
   MAX-ACCESS  read-only
   STATUS      current
   DESCRIPTION
      "Path: tunnels.performance.ipsecGreTunnels.mibCounters.d7Performance.fInDiscardsFilter

       64 bit unsigned wrappable counter."
   ::= {pr1645v2TvTmplPiGreMCD7PEntry 385875968}

pr1645v2TvTmplPiGreMCD7PIfInBandwidth OBJECT-TYPE
   SYNTAX      Integer32
   MAX-ACCESS  read-only
   STATUS      current
   DESCRIPTION
      "Path: tunnels.performance.ipsecGreTunnels.mibCounters.d7Performance.ifInBandwidth

       unit name = bps
       formula = 8 * ; 8 /"
   ::= {pr1645v2TvTmplPiGreMCD7PEntry 268435456}

pr1645v2TvTmplPiGreMCD7PIfOutOctets OBJECT-TYPE
   SYNTAX      Counter64
   MAX-ACCESS  read-only
   STATUS      current
   DESCRIPTION
      "Path: tunnels.performance.ipsecGreTunnels.mibCounters.d7Performance.ifOutOctets

       64 bit unsigned wrappable counter."
   ::= {pr1645v2TvTmplPiGreMCD7PEntry 167772160}

pr1645v2TvTmplPiGreMCD7PIfOutUCPkts OBJECT-TYPE
   SYNTAX      Counter64
   MAX-ACCESS  read-only
   STATUS      current
   DESCRIPTION
      "Path: tunnels.performance.ipsecGreTunnels.mibCounters.d7Performance.ifOutUcastPkts

       64 bit unsigned wrappable counter."
   ::= {pr1645v2TvTmplPiGreMCD7PEntry 184549376}

pr1645v2TvTmplPiGreMCD7PIfOutNUCPkts OBJECT-TYPE
   SYNTAX      Counter64
   MAX-ACCESS  read-only
   STATUS      current
   DESCRIPTION
      "Path: tunnels.performance.ipsecGreTunnels.mibCounters.d7Performance.ifOutNUcastPkts

       64 bit unsigned wrappable counter."
   ::= {pr1645v2TvTmplPiGreMCD7PEntry 201326592}

pr1645v2TvTmplPiGreMCD7PIfOutBCPkts OBJECT-TYPE
   SYNTAX      Counter64
   MAX-ACCESS  read-only
   STATUS      current
   DESCRIPTION
      "Path: tunnels.performance.ipsecGreTunnels.mibCounters.d7Performance.ifOutBcastPkts

       64 bit unsigned wrappable counter."
   ::= {pr1645v2TvTmplPiGreMCD7PEntry 452984832}

pr1645v2TvTmplPiGreMCD7PIfOutMCPkts OBJECT-TYPE
   SYNTAX      Counter64
   MAX-ACCESS  read-only
   STATUS      current
   DESCRIPTION
      "Path: tunnels.performance.ipsecGreTunnels.mibCounters.d7Performance.ifOutMcastPkts

       64 bit unsigned wrappable counter."
   ::= {pr1645v2TvTmplPiGreMCD7PEntry 469762048}

pr1645v2TvTmplPiGreMCD7PIfOutDiscards OBJECT-TYPE
   SYNTAX      Counter64
   MAX-ACCESS  read-only
   STATUS      current
   DESCRIPTION
      "Path: tunnels.performance.ipsecGreTunnels.mibCounters.d7Performance.ifOutDiscards

       64 bit unsigned wrappable counter."
   ::= {pr1645v2TvTmplPiGreMCD7PEntry 218103808}

pr1645v2TvTmplPiGreMCD7PIfOutErrors OBJECT-TYPE
   SYNTAX      Counter64
   MAX-ACCESS  read-only
   STATUS      current
   DESCRIPTION
      "Path: tunnels.performance.ipsecGreTunnels.mibCounters.d7Performance.ifOutErrors

       64 bit unsigned wrappable counter."
   ::= {pr1645v2TvTmplPiGreMCD7PEntry 234881024}

pr1645v2TvTmplPiGreMCD7POutDropEx OBJECT-TYPE
   SYNTAX      Counter64
   MAX-ACCESS  read-only
   STATUS      current
   DESCRIPTION
      "Path: tunnels.performance.ipsecGreTunnels.mibCounters.d7Performance.ifOutDropLevelExceeded

       64 bit unsigned wrappable counter."
   ::= {pr1645v2TvTmplPiGreMCD7PEntry 352321536}

pr1645v2TvTmplPiGreMCD7POutDropNoArp OBJECT-TYPE
   SYNTAX      Counter64
   MAX-ACCESS  read-only
   STATUS      current
   DESCRIPTION
      "Path: tunnels.performance.ipsecGreTunnels.mibCounters.d7Performance.ifOutDiscardsNoArp

       64 bit unsigned wrappable counter."
   ::= {pr1645v2TvTmplPiGreMCD7PEntry 369098752}

pr1645v2TvTmplPiGreMCD7POutDropFilter OBJECT-TYPE
   SYNTAX      Counter64
   MAX-ACCESS  read-only
   STATUS      current
   DESCRIPTION
      "Path: tunnels.performance.ipsecGreTunnels.mibCounters.d7Performance.ifOutDiscardsFilter

       64 bit unsigned wrappable counter."
   ::= {pr1645v2TvTmplPiGreMCD7PEntry 402653184}

pr1645v2TvTmplPiGreMCD7PIfOutBandwidth OBJECT-TYPE
   SYNTAX      Integer32
   MAX-ACCESS  read-only
   STATUS      current
   DESCRIPTION
      "Path: tunnels.performance.ipsecGreTunnels.mibCounters.d7Performance.ifOutBandwidth

       unit name = bps
       formula = 8 * ; 8 /"
   ::= {pr1645v2TvTmplPiGreMCD7PEntry 285212672}

pr1645v2TvTmplPiGreMCD7PIfErrSec OBJECT-TYPE
   SYNTAX      Counter32
   MAX-ACCESS  read-only
   STATUS      current
   DESCRIPTION
      "Path: tunnels.performance.ipsecGreTunnels.mibCounters.d7Performance.ifErrSec

       32 bit unsigned wrappable counter."
   ::= {pr1645v2TvTmplPiGreMCD7PEntry 251658240}

pr1645v2TvTmplPiGreInPQs OBJECT-TYPE
   SYNTAX      SEQUENCE OF Pr1645v2TvTmplPiGreInPQsEntry
   MAX-ACCESS  not-accessible
   STATUS      current
   DESCRIPTION
      ""
   ::= {pr1645v2TvTmplPiGre 100663296}

pr1645v2TvTmplPiGreInPQsEntry OBJECT-TYPE
   SYNTAX      Pr1645v2TvTmplPiGreInPQsEntry
   MAX-ACCESS  not-accessible
   STATUS      current
   DESCRIPTION
      ""
   INDEX      { pr1645v2TvTmplPiGreTableIx,
                pr1645v2TvTmplPiGreInPQsTableIx }
   ::= {pr1645v2TvTmplPiGreInPQs 1}

Pr1645v2TvTmplPiGreInPQsEntry ::=
   SEQUENCE
      {
      pr1645v2TvTmplPiGreInPQsTableIx
         TableIndex,
      pr1645v2TvTmplPiGreInPQsName
         INTEGER,
      pr1645v2TvTmplPiGreInPQsLength
         Integer32,
      pr1645v2TvTmplPiGreInPQsOctetLength
         Integer32,
      pr1645v2TvTmplPiGreInPQsRedLength
         Integer32,
      pr1645v2TvTmplPiGreInPQsPacketsTotal
         Counter64,
      pr1645v2TvTmplPiGreInPQsPacketsDirectTx
         Counter64,
      pr1645v2TvTmplPiGreInPQsPacketsQueued
         Counter64,
      pr1645v2TvTmplPiGreInPQsPacketsDropped
         Counter64,
      pr1645v2TvTmplPiGreInPQsPacketsRedDropped
         Counter64,
      pr1645v2TvTmplPiGreInPQsPacketsCirTx
         Counter64,
      pr1645v2TvTmplPiGreInPQsPacketsEirTx
         Counter64,
      pr1645v2TvTmplPiGreInPQsPacketsViolateTx
         Counter64,
      pr1645v2TvTmplPiGreInPQsOctetsTotal
         Counter64,
      pr1645v2TvTmplPiGreInPQsOctetsDirectTx
         Counter64,
      pr1645v2TvTmplPiGreInPQsOctetsQueued
         Counter64,
      pr1645v2TvTmplPiGreInPQsOctetsDropped
         Counter64,
      pr1645v2TvTmplPiGreInPQsOctetsRedDropped
         Counter64,
      pr1645v2TvTmplPiGreInPQsOctetsCirTx
         Counter64,
      pr1645v2TvTmplPiGreInPQsOctetsEirTx
         Counter64,
      pr1645v2TvTmplPiGreInPQsOctetsViolateTx
         Counter64,
      pr1645v2TvTmplPiGreInPQsOctetsBandwidth15sec
         Integer32,
      pr1645v2TvTmplPiGreInPQsOctetsBandwidth30sec
         Integer32,
      pr1645v2TvTmplPiGreInPQsOctetsBandwidth1min
         Integer32,
      pr1645v2TvTmplPiGreInPQsOctetsBandwidth2min
         Integer32,
      pr1645v2TvTmplPiGreInPQsOctetsBandwidth5min
         Integer32
      }

pr1645v2TvTmplPiGreInPQsTableIx OBJECT-TYPE
   SYNTAX      TableIndex
   MAX-ACCESS  not-accessible
   STATUS      current
   DESCRIPTION
      ""
   ::= {pr1645v2TvTmplPiGreInPQsEntry 11}

pr1645v2TvTmplPiGreInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecGreTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPiGreInPQsEntry 16777216}

pr1645v2TvTmplPiGreInPQsLength OBJECT-TYPE
   SYNTAX      Integer32
   MAX-ACCESS  read-only
   STATUS      current
   DESCRIPTION
      "Path: tunnels.performance.ipsecGreTunnels.inPriorityQueues.length"
   ::= {pr1645v2TvTmplPiGreInPQsEntry 33554432}

pr1645v2TvTmplPiGreInPQsOctetLength OBJECT-TYPE
   SYNTAX      Integer32
   MAX-ACCESS  read-only
   STATUS      current
   DESCRIPTION
      "Path: tunnels.performance.ipsecGreTunnels.inPriorityQueues.octetLength"
   ::= {pr1645v2TvTmplPiGreInPQsEntry 150994944}

pr1645v2TvTmplPiGreInPQsRedLength OBJECT-TYPE
   SYNTAX      Integer32
   MAX-ACCESS  read-only
   STATUS      current
   DESCRIPTION
      "Path: tunnels.performance.ipsecGreTunnels.inPriorityQueues.redLength"
   ::= {pr1645v2TvTmplPiGreInPQsEntry 134217728}

pr1645v2TvTmplPiGreInPQsPacketsTotal OBJECT-TYPE
   SYNTAX      Counter64
   MAX-ACCESS  read-only
   STATUS      current
   DESCRIPTION
      "Path: tunnels.performance.ipsecGreTunnels.inPriorityQueues.packets.total

       64 bit unsigned wrappable counter."
   ::= {pr1645v2TvTmplPiGreInPQsEntry 50790400}

pr1645v2TvTmplPiGreInPQsPacketsDirectTx OBJECT-TYPE
   SYNTAX      Counter64
   MAX-ACCESS  read-only
   STATUS      current
   DESCRIPTION
      "Path: tunnels.performance.ipsecGreTunnels.inPriorityQueues.packets.directTx

       64 bit unsigned wrappable counter."
   ::= {pr1645v2TvTmplPiGreInPQsEntry 50397184}

pr1645v2TvTmplPiGreInPQsPacketsQueued OBJECT-TYPE
   SYNTAX      Counter64
   MAX-ACCESS  read-only
   STATUS      current
   DESCRIPTION
      "Path: tunnels.performance.ipsecGreTunnels.inPriorityQueues.packets.queued

       64 bit unsigned wrappable counter."
   ::= {pr1645v2TvTmplPiGreInPQsEntry 50462720}

pr1645v2TvTmplPiGreInPQsPacketsDropped OBJECT-TYPE
   SYNTAX      Counter64
   MAX-ACCESS  read-only
   STATUS      current
   DESCRIPTION
      "Path: tunnels.performance.ipsecGreTunnels.inPriorityQueues.packets.dropped

       64 bit unsigned wrappable counter."
   ::= {pr1645v2TvTmplPiGreInPQsEntry 50528256}

pr1645v2TvTmplPiGreInPQsPacketsRedDropped OBJECT-TYPE
   SYNTAX      Counter64
   MAX-ACCESS  read-only
   STATUS      current
   DESCRIPTION
      "Path: tunnels.performance.ipsecGreTunnels.inPriorityQueues.packets.redDropped

       64 bit unsigned wrappable counter."
   ::= {pr1645v2TvTmplPiGreInPQsEntry 50724864}

pr1645v2TvTmplPiGreInPQsPacketsCirTx OBJECT-TYPE
   SYNTAX      Counter64
   MAX-ACCESS  read-only
   STATUS      current
   DESCRIPTION
      "Path: tunnels.performance.ipsecGreTunnels.inPriorityQueues.packets.cirTx

       64 bit unsigned wrappable counter."
   ::= {pr1645v2TvTmplPiGreInPQsEntry 50593792}

pr1645v2TvTmplPiGreInPQsPacketsEirTx OBJECT-TYPE
   SYNTAX      Counter64
   MAX-ACCESS  read-only
   STATUS      current
   DESCRIPTION
      "Path: tunnels.performance.ipsecGreTunnels.inPriorityQueues.packets.eirTx

       64 bit unsigned wrappable counter."
   ::= {pr1645v2TvTmplPiGreInPQsEntry 50659328}

pr1645v2TvTmplPiGreInPQsPacketsViolateTx OBJECT-TYPE
   SYNTAX      Counter64
   MAX-ACCESS  read-only
   STATUS      current
   DESCRIPTION
      "Path: tunnels.performance.ipsecGreTunnels.inPriorityQueues.packets.violateTx

       64 bit unsigned wrappable counter."
   ::= {pr1645v2TvTmplPiGreInPQsEntry 50855936}

pr1645v2TvTmplPiGreInPQsOctetsTotal OBJECT-TYPE
   SYNTAX      Counter64
   MAX-ACCESS  read-only
   STATUS      current
   DESCRIPTION
      "Path: tunnels.performance.ipsecGreTunnels.inPriorityQueues.octets.total

       64 bit unsigned wrappable counter."
   ::= {pr1645v2TvTmplPiGreInPQsEntry 67567616}

pr1645v2TvTmplPiGreInPQsOctetsDirectTx OBJECT-TYPE
   SYNTAX      Counter64
   MAX-ACCESS  read-only
   STATUS      current
   DESCRIPTION
      "Path: tunnels.performance.ipsecGreTunnels.inPriorityQueues.octets.directTx

       64 bit unsigned wrappable counter."
   ::= {pr1645v2TvTmplPiGreInPQsEntry 67174400}

pr1645v2TvTmplPiGreInPQsOctetsQueued OBJECT-TYPE
   SYNTAX      Counter64
   MAX-ACCESS  read-only
   STATUS      current
   DESCRIPTION
      "Path: tunnels.performance.ipsecGreTunnels.inPriorityQueues.octets.queued

       64 bit unsigned wrappable counter."
   ::= {pr1645v2TvTmplPiGreInPQsEntry 67239936}

pr1645v2TvTmplPiGreInPQsOctetsDropped OBJECT-TYPE
   SYNTAX      Counter64
   MAX-ACCESS  read-only
   STATUS      current
   DESCRIPTION
      "Path: tunnels.performance.ipsecGreTunnels.inPriorityQueues.octets.dropped

       64 bit unsigned wrappable counter."
   ::= {pr1645v2TvTmplPiGreInPQsEntry 67305472}

pr1645v2TvTmplPiGreInPQsOctetsRedDropped OBJECT-TYPE
   SYNTAX      Counter64
   MAX-ACCESS  read-only
   STATUS      current
   DESCRIPTION
      "Path: tunnels.performance.ipsecGreTunnels.inPriorityQueues.octets.redDropped

       64 bit unsigned wrappable counter."
   ::= {pr1645v2TvTmplPiGreInPQsEntry 67502080}

pr1645v2TvTmplPiGreInPQsOctetsCirTx OBJECT-TYPE
   SYNTAX      Counter64
   MAX-ACCESS  read-only
   STATUS      current
   DESCRIPTION
      "Path: tunnels.performance.ipsecGreTunnels.inPriorityQueues.octets.cirTx

       64 bit unsigned wrappable counter."
   ::= {pr1645v2TvTmplPiGreInPQsEntry 67371008}

pr1645v2TvTmplPiGreInPQsOctetsEirTx OBJECT-TYPE
   SYNTAX      Counter64
   MAX-ACCESS  read-only
   STATUS      current
   DESCRIPTION
      "Path: tunnels.performance.ipsecGreTunnels.inPriorityQueues.octets.eirTx

       64 bit unsigned wrappable counter."
   ::= {pr1645v2TvTmplPiGreInPQsEntry 67436544}

pr1645v2TvTmplPiGreInPQsOctetsViolateTx OBJECT-TYPE
   SYNTAX      Counter64
   MAX-ACCESS  read-only
   STATUS      current
   DESCRIPTION
      "Path: tunnels.performance.ipsecGreTunnels.inPriorityQueues.octets.violateTx

       64 bit unsigned wrappable counter."
   ::= {pr1645v2TvTmplPiGreInPQsEntry 67633152}

pr1645v2TvTmplPiGreInPQsOctetsBandwidth15sec OBJECT-TYPE
   SYNTAX      Integer32
   MAX-ACCESS  read-only
   STATUS      current
   DESCRIPTION
      "Path: tunnels.performance.ipsecGreTunnels.inPriorityQueues.octets.bandwidth.15sec

       unit name = bps
       formula = 8 * ; 8 /"
   ::= {pr1645v2TvTmplPiGreInPQsEntry 70386944}

pr1645v2TvTmplPiGreInPQsOctetsBandwidth30sec OBJECT-TYPE
   SYNTAX      Integer32
   MAX-ACCESS  read-only
   STATUS      current
   DESCRIPTION
      "Path: tunnels.performance.ipsecGreTunnels.inPriorityQueues.octets.bandwidth.30sec

       unit name = bps
       formula = 8 * ; 8 /"
   ::= {pr1645v2TvTmplPiGreInPQsEntry 70388224}

pr1645v2TvTmplPiGreInPQsOctetsBandwidth1min OBJECT-TYPE
   SYNTAX      Integer32
   MAX-ACCESS  read-only
   STATUS      current
   DESCRIPTION
      "Path: tunnels.performance.ipsecGreTunnels.inPriorityQueues.octets.bandwidth.1min

       unit name = bps
       formula = 8 * ; 8 /"
   ::= {pr1645v2TvTmplPiGreInPQsEntry 70390784}

pr1645v2TvTmplPiGreInPQsOctetsBandwidth2min OBJECT-TYPE
   SYNTAX      Integer32
   MAX-ACCESS  read-only
   STATUS      current
   DESCRIPTION
      "Path: tunnels.performance.ipsecGreTunnels.inPriorityQueues.octets.bandwidth.2min

       unit name = bps
       formula = 8 * ; 8 /"
   ::= {pr1645v2TvTmplPiGreInPQsEntry 70395904}

pr1645v2TvTmplPiGreInPQsOctetsBandwidth5min OBJECT-TYPE
   SYNTAX      Integer32
   MAX-ACCESS  read-only
   STATUS      current
   DESCRIPTION
      "Path: tunnels.performance.ipsecGreTunnels.inPriorityQueues.octets.bandwidth.5min

       unit name = bps
       formula = 8 * ; 8 /"
   ::= {pr1645v2TvTmplPiGreInPQsEntry 70411264}

pr1645v2TvTmplPiGreInPQsH2Performance OBJECT-TYPE
   SYNTAX      SEQUENCE OF Pr1645v2TvTmplPiGreInPQsH2PerformanceEntry
   MAX-ACCESS  not-accessible
   STATUS      current
   DESCRIPTION
      ""
   ::= {pr1645v2TvTmplPiGre 100990976}

pr1645v2TvTmplPiGreInPQsH2PerformanceEntry OBJECT-TYPE
   SYNTAX      Pr1645v2TvTmplPiGreInPQsH2PerformanceEntry
   MAX-ACCESS  not-accessible
   STATUS      current
   DESCRIPTION
      ""
   INDEX      { pr1645v2TvTmplPiGreTableIx,
                pr1645v2TvTmplPiGreInPQsTableIx,
                pr1645v2TvTmplPiGreInPQsH2PerformanceTableIx }
   ::= {pr1645v2TvTmplPiGreInPQsH2Performance 1}

Pr1645v2TvTmplPiGreInPQsH2PerformanceEntry ::=
   SEQUENCE
      {
      pr1645v2TvTmplPiGreInPQsH2PerformanceTableIx
         TableIndex,
      pr1645v2TvTmplPiGreInPQsH2PerformanceSysUpTime
         TimeTicks,
      pr1645v2TvTmplPiGreInPQsH2PerformanceTotPkts
         Counter64,
      pr1645v2TvTmplPiGreInPQsH2PerformanceDirTxPkts
         Counter64,
      pr1645v2TvTmplPiGreInPQsH2PerformanceQdPkts
         Counter64,
      pr1645v2TvTmplPiGreInPQsH2PerformanceDropPkts
         Counter64,
      pr1645v2TvTmplPiGreInPQsH2PerformanceRDropPkts
         Counter64,
      pr1645v2TvTmplPiGreInPQsH2PerformanceCirTxPkts
         Counter64,
      pr1645v2TvTmplPiGreInPQsH2PerformanceEirTxPkts
         Counter64,
      pr1645v2TvTmplPiGreInPQsH2PerformanceViolTxPkts
         Counter64,
      pr1645v2TvTmplPiGreInPQsH2PerformanceTotOcts
         Counter64,
      pr1645v2TvTmplPiGreInPQsH2PerformanceDirTxOcts
         Counter64,
      pr1645v2TvTmplPiGreInPQsH2PerformanceQdOcts
         Counter64,
      pr1645v2TvTmplPiGreInPQsH2PerformanceDropOcts
         Counter64,
      pr1645v2TvTmplPiGreInPQsH2PerformanceRDropOcts
         Counter64,
      pr1645v2TvTmplPiGreInPQsH2PerformanceCirTxOcts
         Counter64,
      pr1645v2TvTmplPiGreInPQsH2PerformanceEirTxOcts
         Counter64,
      pr1645v2TvTmplPiGreInPQsH2PerformanceViolTxOcts
         Counter64,
      pr1645v2TvTmplPiGreInPQsH2PerformanceBandwidth
         Integer32
      }

pr1645v2TvTmplPiGreInPQsH2PerformanceTableIx OBJECT-TYPE
   SYNTAX      TableIndex
   MAX-ACCESS  not-accessible
   STATUS      current
   DESCRIPTION
      ""
   ::= {pr1645v2TvTmplPiGreInPQsH2PerformanceEntry 11}

pr1645v2TvTmplPiGreInPQsH2PerformanceSysUpTime OBJECT-TYPE
   SYNTAX      TimeTicks
   MAX-ACCESS  read-only
   STATUS      current
   DESCRIPTION
      "Path: tunnels.performance.ipsecGreTunnels.inPriorityQueues.h2Performance.sysUpTime

       Time in centi-second."
   ::= {pr1645v2TvTmplPiGreInPQsH2PerformanceEntry 16777216}

pr1645v2TvTmplPiGreInPQsH2PerformanceTotPkts OBJECT-TYPE
   SYNTAX      Counter64
   MAX-ACCESS  read-only
   STATUS      current
   DESCRIPTION
      "Path: tunnels.performance.ipsecGreTunnels.inPriorityQueues.h2Performance.totalPkts

       64 bit unsigned wrappable counter."
   ::= {pr1645v2TvTmplPiGreInPQsH2PerformanceEntry 234881024}

pr1645v2TvTmplPiGreInPQsH2PerformanceDirTxPkts OBJECT-TYPE
   SYNTAX      Counter64
   MAX-ACCESS  read-only
   STATUS      current
   DESCRIPTION
      "Path: tunnels.performance.ipsecGreTunnels.inPriorityQueues.h2Performance.directTxPkts

       64 bit unsigned wrappable counter."
   ::= {pr1645v2TvTmplPiGreInPQsH2PerformanceEntry 33554432}

pr1645v2TvTmplPiGreInPQsH2PerformanceQdPkts OBJECT-TYPE
   SYNTAX      Counter64
   MAX-ACCESS  read-only
   STATUS      current
   DESCRIPTION
      "Path: tunnels.performance.ipsecGreTunnels.inPriorityQueues.h2Performance.queuedPkts

       64 bit unsigned wrappable counter."
   ::= {pr1645v2TvTmplPiGreInPQsH2PerformanceEntry 50331648}

pr1645v2TvTmplPiGreInPQsH2PerformanceDropPkts OBJECT-TYPE
   SYNTAX      Counter64
   MAX-ACCESS  read-only
   STATUS      current
   DESCRIPTION
      "Path: tunnels.performance.ipsecGreTunnels.inPriorityQueues.h2Performance.droppedPkts

       64 bit unsigned wrappable counter."
   ::= {pr1645v2TvTmplPiGreInPQsH2PerformanceEntry 67108864}

pr1645v2TvTmplPiGreInPQsH2PerformanceRDropPkts OBJECT-TYPE
   SYNTAX      Counter64
   MAX-ACCESS  read-only
   STATUS      current
   DESCRIPTION
      "Path: tunnels.performance.ipsecGreTunnels.inPriorityQueues.h2Performance.redDroppedPkts

       64 bit unsigned wrappable counter."
   ::= {pr1645v2TvTmplPiGreInPQsH2PerformanceEntry 201326592}

pr1645v2TvTmplPiGreInPQsH2PerformanceCirTxPkts OBJECT-TYPE
   SYNTAX      Counter64
   MAX-ACCESS  read-only
   STATUS      current
   DESCRIPTION
      "Path: tunnels.performance.ipsecGreTunnels.inPriorityQueues.h2Performance.cirTxPkts

       64 bit unsigned wrappable counter."
   ::= {pr1645v2TvTmplPiGreInPQsH2PerformanceEntry 83886080}

pr1645v2TvTmplPiGreInPQsH2PerformanceEirTxPkts OBJECT-TYPE
   SYNTAX      Counter64
   MAX-ACCESS  read-only
   STATUS      current
   DESCRIPTION
      "Path: tunnels.performance.ipsecGreTunnels.inPriorityQueues.h2Performance.eirTxPkts

       64 bit unsigned wrappable counter."
   ::= {pr1645v2TvTmplPiGreInPQsH2PerformanceEntry 100663296}

pr1645v2TvTmplPiGreInPQsH2PerformanceViolTxPkts OBJECT-TYPE
   SYNTAX      Counter64
   MAX-ACCESS  read-only
   STATUS      current
   DESCRIPTION
      "Path: tunnels.performance.ipsecGreTunnels.inPriorityQueues.h2Performance.violateTxPkts

       64 bit unsigned wrappable counter."
   ::= {pr1645v2TvTmplPiGreInPQsH2PerformanceEntry 301989888}

pr1645v2TvTmplPiGreInPQsH2PerformanceTotOcts OBJECT-TYPE
   SYNTAX      Counter64
   MAX-ACCESS  read-only
   STATUS      current
   DESCRIPTION
      "Path: tunnels.performance.ipsecGreTunnels.inPriorityQueues.h2Performance.totalOctets

       64 bit unsigned wrappable counter."
   ::= {pr1645v2TvTmplPiGreInPQsH2PerformanceEntry 251658240}

pr1645v2TvTmplPiGreInPQsH2PerformanceDirTxOcts OBJECT-TYPE
   SYNTAX      Counter64
   MAX-ACCESS  read-only
   STATUS      current
   DESCRIPTION
      "Path: tunnels.performance.ipsecGreTunnels.inPriorityQueues.h2Performance.directTxOctets

       64 bit unsigned wrappable counter."
   ::= {pr1645v2TvTmplPiGreInPQsH2PerformanceEntry 117440512}

pr1645v2TvTmplPiGreInPQsH2PerformanceQdOcts OBJECT-TYPE
   SYNTAX      Counter64
   MAX-ACCESS  read-only
   STATUS      current
   DESCRIPTION
      "Path: tunnels.performance.ipsecGreTunnels.inPriorityQueues.h2Performance.queuedOctets

       64 bit unsigned wrappable counter."
   ::= {pr1645v2TvTmplPiGreInPQsH2PerformanceEntry 134217728}

pr1645v2TvTmplPiGreInPQsH2PerformanceDropOcts OBJECT-TYPE
   SYNTAX      Counter64
   MAX-ACCESS  read-only
   STATUS      current
   DESCRIPTION
      "Path: tunnels.performance.ipsecGreTunnels.inPriorityQueues.h2Performance.droppedOctets

       64 bit unsigned wrappable counter."
   ::= {pr1645v2TvTmplPiGreInPQsH2PerformanceEntry 150994944}

pr1645v2TvTmplPiGreInPQsH2PerformanceRDropOcts OBJECT-TYPE
   SYNTAX      Counter64
   MAX-ACCESS  read-only
   STATUS      current
   DESCRIPTION
      "Path: tunnels.performance.ipsecGreTunnels.inPriorityQueues.h2Performance.redDroppedOctets

       64 bit unsigned wrappable counter."
   ::= {pr1645v2TvTmplPiGreInPQsH2PerformanceEntry 218103808}

pr1645v2TvTmplPiGreInPQsH2PerformanceCirTxOcts OBJECT-TYPE
   SYNTAX      Counter64
   MAX-ACCESS  read-only
   STATUS      current
   DESCRIPTION
      "Path: tunnels.performance.ipsecGreTunnels.inPriorityQueues.h2Performance.cirTxOctets

       64 bit unsigned wrappable counter."
   ::= {pr1645v2TvTmplPiGreInPQsH2PerformanceEntry 167772160}

pr1645v2TvTmplPiGreInPQsH2PerformanceEirTxOcts OBJECT-TYPE
   SYNTAX      Counter64
   MAX-ACCESS  read-only
   STATUS      current
   DESCRIPTION
      "Path: tunnels.performance.ipsecGreTunnels.inPriorityQueues.h2Performance.eirTxOctets

       64 bit unsigned wrappable counter."
   ::= {pr1645v2TvTmplPiGreInPQsH2PerformanceEntry 184549376}

pr1645v2TvTmplPiGreInPQsH2PerformanceViolTxOcts OBJECT-TYPE
   SYNTAX      Counter64
   MAX-ACCESS  read-only
   STATUS      current
   DESCRIPTION
      "Path: tunnels.performance.ipsecGreTunnels.inPriorityQueues.h2Performance.violateTxOctets

       64 bit unsigned wrappable counter."
   ::= {pr1645v2TvTmplPiGreInPQsH2PerformanceEntry 318767104}

pr1645v2TvTmplPiGreInPQsH2PerformanceBandwidth OBJECT-TYPE
   SYNTAX      Integer32
   MAX-ACCESS  read-only
   STATUS      current
   DESCRIPTION
      "Path: tunnels.performance.ipsecGreTunnels.inPriorityQueues.h2Performance.bandwidth

       unit name = bps
       formula = 8 * ; 8 /"
   ::= {pr1645v2TvTmplPiGreInPQsH2PerformanceEntry 268435456}

pr1645v2TvTmplPiGreInPQsH24Performance OBJECT-TYPE
   SYNTAX      SEQUENCE OF Pr1645v2TvTmplPiGreInPQsH24PerformanceEntry
   MAX-ACCESS  not-accessible
   STATUS      current
   DESCRIPTION
      ""
   ::= {pr1645v2TvTmplPiGre 101056512}

pr1645v2TvTmplPiGreInPQsH24PerformanceEntry OBJECT-TYPE
   SYNTAX      Pr1645v2TvTmplPiGreInPQsH24PerformanceEntry
   MAX-ACCESS  not-accessible
   STATUS      current
   DESCRIPTION
      ""
   INDEX      { pr1645v2TvTmplPiGreTableIx,
                pr1645v2TvTmplPiGreInPQsTableIx,
                pr1645v2TvTmplPiGreInPQsH24PerformanceTableIx }
   ::= {pr1645v2TvTmplPiGreInPQsH24Performance 1}

Pr1645v2TvTmplPiGreInPQsH24PerformanceEntry ::=
   SEQUENCE
      {
      pr1645v2TvTmplPiGreInPQsH24PerformanceTableIx
         TableIndex,
      pr1645v2TvTmplPiGreInPQsH24PerformanceSysUpTime
         TimeTicks,
      pr1645v2TvTmplPiGreInPQsH24PerformanceTotPkts
         Counter64,
      pr1645v2TvTmplPiGreInPQsH24PerformanceDirTxPkts
         Counter64,
      pr1645v2TvTmplPiGreInPQsH24PerformanceQdPkts
         Counter64,
      pr1645v2TvTmplPiGreInPQsH24PerformanceDropPkts
         Counter64,
      pr1645v2TvTmplPiGreInPQsH24PerformanceRDropPkts
         Counter64,
      pr1645v2TvTmplPiGreInPQsH24PerformanceCirTxPkts
         Counter64,
      pr1645v2TvTmplPiGreInPQsH24PerformanceEirTxPkts
         Counter64,
      pr1645v2TvTmplPiGreInPQsH24PerformanceViolTxPkts
         Counter64,
      pr1645v2TvTmplPiGreInPQsH24PerformanceTotOcts
         Counter64,
      pr1645v2TvTmplPiGreInPQsH24PerformanceDirTxOcts
         Counter64,
      pr1645v2TvTmplPiGreInPQsH24PerformanceQdOcts
         Counter64,
      pr1645v2TvTmplPiGreInPQsH24PerformanceDropOcts
         Counter64,
      pr1645v2TvTmplPiGreInPQsH24PerformanceRDropOcts
         Counter64,
      pr1645v2TvTmplPiGreInPQsH24PerformanceCirTxOcts
         Counter64,
      pr1645v2TvTmplPiGreInPQsH24PerformanceEirTxOcts
         Counter64,
      pr1645v2TvTmplPiGreInPQsH24PerformanceViolTxOcts
         Counter64,
      pr1645v2TvTmplPiGreInPQsH24PerformanceBandwidth
         Integer32
      }

pr1645v2TvTmplPiGreInPQsH24PerformanceTableIx OBJECT-TYPE
   SYNTAX      TableIndex
   MAX-ACCESS  not-accessible
   STATUS      current
   DESCRIPTION
      ""
   ::= {pr1645v2TvTmplPiGreInPQsH24PerformanceEntry 11}

pr1645v2TvTmplPiGreInPQsH24PerformanceSysUpTime OBJECT-TYPE
   SYNTAX      TimeTicks
   MAX-ACCESS  read-only
   STATUS      current
   DESCRIPTION
      "Path: tunnels.performance.ipsecGreTunnels.inPriorityQueues.h24Performance.sysUpTime

       Time in centi-second."
   ::= {pr1645v2TvTmplPiGreInPQsH24PerformanceEntry 16777216}

pr1645v2TvTmplPiGreInPQsH24PerformanceTotPkts OBJECT-TYPE
   SYNTAX      Counter64
   MAX-ACCESS  read-only
   STATUS      current
   DESCRIPTION
      "Path: tunnels.performance.ipsecGreTunnels.inPriorityQueues.h24Performance.totalPkts

       64 bit unsigned wrappable counter."
   ::= {pr1645v2TvTmplPiGreInPQsH24PerformanceEntry 234881024}

pr1645v2TvTmplPiGreInPQsH24PerformanceDirTxPkts OBJECT-TYPE
   SYNTAX      Counter64
   MAX-ACCESS  read-only
   STATUS      current
   DESCRIPTION
      "Path: tunnels.performance.ipsecGreTunnels.inPriorityQueues.h24Performance.directTxPkts

       64 bit unsigned wrappable counter."
   ::= {pr1645v2TvTmplPiGreInPQsH24PerformanceEntry 33554432}

pr1645v2TvTmplPiGreInPQsH24PerformanceQdPkts OBJECT-TYPE
   SYNTAX      Counter64
   MAX-ACCESS  read-only
   STATUS      current
   DESCRIPTION
      "Path: tunnels.performance.ipsecGreTunnels.inPriorityQueues.h24Performance.queuedPkts

       64 bit unsigned wrappable counter."
   ::= {pr1645v2TvTmplPiGreInPQsH24PerformanceEntry 50331648}

pr1645v2TvTmplPiGreInPQsH24PerformanceDropPkts OBJECT-TYPE
   SYNTAX      Counter64
   MAX-ACCESS  read-only
   STATUS      current
   DESCRIPTION
      "Path: tunnels.performance.ipsecGreTunnels.inPriorityQueues.h24Performance.droppedPkts

       64 bit unsigned wrappable counter."
   ::= {pr1645v2TvTmplPiGreInPQsH24PerformanceEntry 67108864}

pr1645v2TvTmplPiGreInPQsH24PerformanceRDropPkts OBJECT-TYPE
   SYNTAX      Counter64
   MAX-ACCESS  read-only
   STATUS      current
   DESCRIPTION
      "Path: tunnels.performance.ipsecGreTunnels.inPriorityQueues.h24Performance.redDroppedPkts

       64 bit unsigned wrappable counter."
   ::= {pr1645v2TvTmplPiGreInPQsH24PerformanceEntry 201326592}

pr1645v2TvTmplPiGreInPQsH24PerformanceCirTxPkts OBJECT-TYPE
   SYNTAX      Counter64
   MAX-ACCESS  read-only
   STATUS      current
   DESCRIPTION
      "Path: tunnels.performance.ipsecGreTunnels.inPriorityQueues.h24Performance.cirTxPkts

       64 bit unsigned wrappable counter."
   ::= {pr1645v2TvTmplPiGreInPQsH24PerformanceEntry 83886080}

pr1645v2TvTmplPiGreInPQsH24PerformanceEirTxPkts OBJECT-TYPE
   SYNTAX      Counter64
   MAX-ACCESS  read-only
   STATUS      current
   DESCRIPTION
      "Path: tunnels.performance.ipsecGreTunnels.inPriorityQueues.h24Performance.eirTxPkts

       64 bit unsigned wrappable counter."
   ::= {pr1645v2TvTmplPiGreInPQsH24PerformanceEntry 100663296}

pr1645v2TvTmplPiGreInPQsH24PerformanceViolTxPkts OBJECT-TYPE
   SYNTAX      Counter64
   MAX-ACCESS  read-only
   STATUS      current
   DESCRIPTION
      "Path: tunnels.performance.ipsecGreTunnels.inPriorityQueues.h24Performance.violateTxPkts

       64 bit unsigned wrappable counter."
   ::= {pr1645v2TvTmplPiGreInPQsH24PerformanceEntry 301989888}

pr1645v2TvTmplPiGreInPQsH24PerformanceTotOcts OBJECT-TYPE
   SYNTAX      Counter64
   MAX-ACCESS  read-only
   STATUS      current
   DESCRIPTION
      "Path: tunnels.performance.ipsecGreTunnels.inPriorityQueues.h24Performance.totalOctets

       64 bit unsigned wrappable counter."
   ::= {pr1645v2TvTmplPiGreInPQsH24PerformanceEntry 251658240}

pr1645v2TvTmplPiGreInPQsH24PerformanceDirTxOcts OBJECT-TYPE
   SYNTAX      Counter64
   MAX-ACCESS  read-only
   STATUS      current
   DESCRIPTION
      "Path: tunnels.performance.ipsecGreTunnels.inPriorityQueues.h24Performance.directTxOctets

       64 bit unsigned wrappable counter."
   ::= {pr1645v2TvTmplPiGreInPQsH24PerformanceEntry 117440512}

pr1645v2TvTmplPiGreInPQsH24PerformanceQdOcts OBJECT-TYPE
   SYNTAX      Counter64
   MAX-ACCESS  read-only
   STATUS      current
   DESCRIPTION
      "Path: tunnels.performance.ipsecGreTunnels.inPriorityQueues.h24Performance.queuedOctets

       64 bit unsigned wrappable counter."
   ::= {pr1645v2TvTmplPiGreInPQsH24PerformanceEntry 134217728}

pr1645v2TvTmplPiGreInPQsH24PerformanceDropOcts OBJECT-TYPE
   SYNTAX      Counter64
   MAX-ACCESS  read-only
   STATUS      current
   DESCRIPTION
      "Path: tunnels.performance.ipsecGreTunnels.inPriorityQueues.h24Performance.droppedOctets

       64 bit unsigned wrappable counter."
   ::= {pr1645v2TvTmplPiGreInPQsH24PerformanceEntry 150994944}

pr1645v2TvTmplPiGreInPQsH24PerformanceRDropOcts OBJECT-TYPE
   SYNTAX      Counter64
   MAX-ACCESS  read-only
   STATUS      current
   DESCRIPTION
      "Path: tunnels.performance.ipsecGreTunnels.inPriorityQueues.h24Performance.redDroppedOctets

       64 bit unsigned wrappable counter."
   ::= {pr1645v2TvTmplPiGreInPQsH24PerformanceEntry 218103808}

pr1645v2TvTmplPiGreInPQsH24PerformanceCirTxOcts OBJECT-TYPE
   SYNTAX      Counter64
   MAX-ACCESS  read-only
   STATUS      current
   DESCRIPTION
      "Path: tunnels.performance.ipsecGreTunnels.inPriorityQueues.h24Performance.cirTxOctets

       64 bit unsigned wrappable counter."
   ::= {pr1645v2TvTmplPiGreInPQsH24PerformanceEntry 167772160}

pr1645v2TvTmplPiGreInPQsH24PerformanceEirTxOcts OBJECT-TYPE
   SYNTAX      Counter64
   MAX-ACCESS  read-only
   STATUS      current
   DESCRIPTION
      "Path: tunnels.performance.ipsecGreTunnels.inPriorityQueues.h24Performance.eirTxOctets

       64 bit unsigned wrappable counter."
   ::= {pr1645v2TvTmplPiGreInPQsH24PerformanceEntry 184549376}

pr1645v2TvTmplPiGreInPQsH24PerformanceViolTxOcts OBJECT-TYPE
   SYNTAX      Counter64
   MAX-ACCESS  read-only
   STATUS      current
   DESCRIPTION
      "Path: tunnels.performance.ipsecGreTunnels.inPriorityQueues.h24Performance.violateTxOctets

       64 bit unsigned wrappable counter."
   ::= {pr1645v2TvTmplPiGreInPQsH24PerformanceEntry 318767104}

pr1645v2TvTmplPiGreInPQsH24PerformanceBandwidth OBJECT-TYPE
   SYNTAX      Integer32
   MAX-ACCESS  read-only
   STATUS      current
   DESCRIPTION
      "Path: tunnels.performance.ipsecGreTunnels.inPriorityQueues.h24Performance.bandwidth

       unit name = bps
       formula = 8 * ; 8 /"
   ::= {pr1645v2TvTmplPiGreInPQsH24PerformanceEntry 268435456}

pr1645v2TvTmplPiGreInPQsD7Performance OBJECT-TYPE
   SYNTAX      SEQUENCE OF Pr1645v2TvTmplPiGreInPQsD7PerformanceEntry
   MAX-ACCESS  not-accessible
   STATUS      current
   DESCRIPTION
      ""
   ::= {pr1645v2TvTmplPiGre 101122048}

pr1645v2TvTmplPiGreInPQsD7PerformanceEntry OBJECT-TYPE
   SYNTAX      Pr1645v2TvTmplPiGreInPQsD7PerformanceEntry
   MAX-ACCESS  not-accessible
   STATUS      current
   DESCRIPTION
      ""
   INDEX      { pr1645v2TvTmplPiGreTableIx,
                pr1645v2TvTmplPiGreInPQsTableIx,
                pr1645v2TvTmplPiGreInPQsD7PerformanceTableIx }
   ::= {pr1645v2TvTmplPiGreInPQsD7Performance 1}

Pr1645v2TvTmplPiGreInPQsD7PerformanceEntry ::=
   SEQUENCE
      {
      pr1645v2TvTmplPiGreInPQsD7PerformanceTableIx
         TableIndex,
      pr1645v2TvTmplPiGreInPQsD7PerformanceSysUpTime
         TimeTicks,
      pr1645v2TvTmplPiGreInPQsD7PerformanceTotPkts
         Counter64,
      pr1645v2TvTmplPiGreInPQsD7PerformanceDirTxPkts
         Counter64,
      pr1645v2TvTmplPiGreInPQsD7PerformanceQdPkts
         Counter64,
      pr1645v2TvTmplPiGreInPQsD7PerformanceDropPkts
         Counter64,
      pr1645v2TvTmplPiGreInPQsD7PerformanceRDropPkts
         Counter64,
      pr1645v2TvTmplPiGreInPQsD7PerformanceCirTxPkts
         Counter64,
      pr1645v2TvTmplPiGreInPQsD7PerformanceEirTxPkts
         Counter64,
      pr1645v2TvTmplPiGreInPQsD7PerformanceViolTxPkts
         Counter64,
      pr1645v2TvTmplPiGreInPQsD7PerformanceTotOcts
         Counter64,
      pr1645v2TvTmplPiGreInPQsD7PerformanceDirTxOcts
         Counter64,
      pr1645v2TvTmplPiGreInPQsD7PerformanceQdOcts
         Counter64,
      pr1645v2TvTmplPiGreInPQsD7PerformanceDropOcts
         Counter64,
      pr1645v2TvTmplPiGreInPQsD7PerformanceRDropOcts
         Counter64,
      pr1645v2TvTmplPiGreInPQsD7PerformanceCirTxOcts
         Counter64,
      pr1645v2TvTmplPiGreInPQsD7PerformanceEirTxOcts
         Counter64,
      pr1645v2TvTmplPiGreInPQsD7PerformanceViolTxOcts
         Counter64,
      pr1645v2TvTmplPiGreInPQsD7PerformanceBandwidth
         Integer32
      }

pr1645v2TvTmplPiGreInPQsD7PerformanceTableIx OBJECT-TYPE
   SYNTAX      TableIndex
   MAX-ACCESS  not-accessible
   STATUS      current
   DESCRIPTION
      ""
   ::= {pr1645v2TvTmplPiGreInPQsD7PerformanceEntry 11}

pr1645v2TvTmplPiGreInPQsD7PerformanceSysUpTime OBJECT-TYPE
   SYNTAX      TimeTicks
   MAX-ACCESS  read-only
   STATUS      current
   DESCRIPTION
      "Path: tunnels.performance.ipsecGreTunnels.inPriorityQueues.d7Performance.sysUpTime

       Time in centi-second."
   ::= {pr1645v2TvTmplPiGreInPQsD7PerformanceEntry 16777216}

pr1645v2TvTmplPiGreInPQsD7PerformanceTotPkts OBJECT-TYPE
   SYNTAX      Counter64
   MAX-ACCESS  read-only
   STATUS      current
   DESCRIPTION
      "Path: tunnels.performance.ipsecGreTunnels.inPriorityQueues.d7Performance.totalPkts

       64 bit unsigned wrappable counter."
   ::= {pr1645v2TvTmplPiGreInPQsD7PerformanceEntry 234881024}

pr1645v2TvTmplPiGreInPQsD7PerformanceDirTxPkts OBJECT-TYPE
   SYNTAX      Counter64
   MAX-ACCESS  read-only
   STATUS      current
   DESCRIPTION
      "Path: tunnels.performance.ipsecGreTunnels.inPriorityQueues.d7Performance.directTxPkts

       64 bit unsigned wrappable counter."
   ::= {pr1645v2TvTmplPiGreInPQsD7PerformanceEntry 33554432}

pr1645v2TvTmplPiGreInPQsD7PerformanceQdPkts OBJECT-TYPE
   SYNTAX      Counter64
   MAX-ACCESS  read-only
   STATUS      current
   DESCRIPTION
      "Path: tunnels.performance.ipsecGreTunnels.inPriorityQueues.d7Performance.queuedPkts

       64 bit unsigned wrappable counter."
   ::= {pr1645v2TvTmplPiGreInPQsD7PerformanceEntry 50331648}

pr1645v2TvTmplPiGreInPQsD7PerformanceDropPkts OBJECT-TYPE
   SYNTAX      Counter64
   MAX-ACCESS  read-only
   STATUS      current
   DESCRIPTION
      "Path: tunnels.performance.ipsecGreTunnels.inPriorityQueues.d7Performance.droppedPkts

       64 bit unsigned wrappable counter."
   ::= {pr1645v2TvTmplPiGreInPQsD7PerformanceEntry 67108864}

pr1645v2TvTmplPiGreInPQsD7PerformanceRDropPkts OBJECT-TYPE
   SYNTAX      Counter64
   MAX-ACCESS  read-only
   STATUS      current
   DESCRIPTION
      "Path: tunnels.performance.ipsecGreTunnels.inPriorityQueues.d7Performance.redDroppedPkts

       64 bit unsigned wrappable counter."
   ::= {pr1645v2TvTmplPiGreInPQsD7PerformanceEntry 201326592}

pr1645v2TvTmplPiGreInPQsD7PerformanceCirTxPkts OBJECT-TYPE
   SYNTAX      Counter64
   MAX-ACCESS  read-only
   STATUS      current
   DESCRIPTION
      "Path: tunnels.performance.ipsecGreTunnels.inPriorityQueues.d7Performance.cirTxPkts

       64 bit unsigned wrappable counter."
   ::= {pr1645v2TvTmplPiGreInPQsD7PerformanceEntry 83886080}

pr1645v2TvTmplPiGreInPQsD7PerformanceEirTxPkts OBJECT-TYPE
   SYNTAX      Counter64
   MAX-ACCESS  read-only
   STATUS      current
   DESCRIPTION
      "Path: tunnels.performance.ipsecGreTunnels.inPriorityQueues.d7Performance.eirTxPkts

       64 bit unsigned wrappable counter."
   ::= {pr1645v2TvTmplPiGreInPQsD7PerformanceEntry 100663296}

pr1645v2TvTmplPiGreInPQsD7PerformanceViolTxPkts OBJECT-TYPE
   SYNTAX      Counter64
   MAX-ACCESS  read-only
   STATUS      current
   DESCRIPTION
      "Path: tunnels.performance.ipsecGreTunnels.inPriorityQueues.d7Performance.violateTxPkts

       64 bit unsigned wrappable counter."
   ::= {pr1645v2TvTmplPiGreInPQsD7PerformanceEntry 301989888}

pr1645v2TvTmplPiGreInPQsD7PerformanceTotOcts OBJECT-TYPE
   SYNTAX      Counter64
   MAX-ACCESS  read-only
   STATUS      current
   DESCRIPTION
      "Path: tunnels.performance.ipsecGreTunnels.inPriorityQueues.d7Performance.totalOctets

       64 bit unsigned wrappable counter."
   ::= {pr1645v2TvTmplPiGreInPQsD7PerformanceEntry 251658240}

pr1645v2TvTmplPiGreInPQsD7PerformanceDirTxOcts OBJECT-TYPE
   SYNTAX      Counter64
   MAX-ACCESS  read-only
   STATUS      current
   DESCRIPTION
      "Path: tunnels.performance.ipsecGreTunnels.inPriorityQueues.d7Performance.directTxOctets

       64 bit unsigned wrappable counter."
   ::= {pr1645v2TvTmplPiGreInPQsD7PerformanceEntry 117440512}

pr1645v2TvTmplPiGreInPQsD7PerformanceQdOcts OBJECT-TYPE
   SYNTAX      Counter64
   MAX-ACCESS  read-only
   STATUS      current
   DESCRIPTION
      "Path: tunnels.performance.ipsecGreTunnels.inPriorityQueues.d7Performance.queuedOctets

       64 bit unsigned wrappable counter."
   ::= {pr1645v2TvTmplPiGreInPQsD7PerformanceEntry 134217728}

pr1645v2TvTmplPiGreInPQsD7PerformanceDropOcts OBJECT-TYPE
   SYNTAX      Counter64
   MAX-ACCESS  read-only
   STATUS      current
   DESCRIPTION
      "Path: tunnels.performance.ipsecGreTunnels.inPriorityQueues.d7Performance.droppedOctets

       64 bit unsigned wrappable counter."
   ::= {pr1645v2TvTmplPiGreInPQsD7PerformanceEntry 150994944}

pr1645v2TvTmplPiGreInPQsD7PerformanceRDropOcts OBJECT-TYPE
   SYNTAX      Counter64
   MAX-ACCESS  read-only
   STATUS      current
   DESCRIPTION
      "Path: tunnels.performance.ipsecGreTunnels.inPriorityQueues.d7Performance.redDroppedOctets

       64 bit unsigned wrappable counter."
   ::= {pr1645v2TvTmplPiGreInPQsD7PerformanceEntry 218103808}

pr1645v2TvTmplPiGreInPQsD7PerformanceCirTxOcts OBJECT-TYPE
   SYNTAX      Counter64
   MAX-ACCESS  read-only
   STATUS      current
   DESCRIPTION
      "Path: tunnels.performance.ipsecGreTunnels.inPriorityQueues.d7Performance.cirTxOctets

       64 bit unsigned wrappable counter."
   ::= {pr1645v2TvTmplPiGreInPQsD7PerformanceEntry 167772160}

pr1645v2TvTmplPiGreInPQsD7PerformanceEirTxOcts OBJECT-TYPE
   SYNTAX      Counter64
   MAX-ACCESS  read-only
   STATUS      current
   DESCRIPTION
      "Path: tunnels.performance.ipsecGreTunnels.inPriorityQueues.d7Performance.eirTxOctets

       64 bit unsigned wrappable counter."
   ::= {pr1645v2TvTmplPiGreInPQsD7PerformanceEntry 184549376}

pr1645v2TvTmplPiGreInPQsD7PerformanceViolTxOcts OBJECT-TYPE
   SYNTAX      Counter64
   MAX-ACCESS  read-only
   STATUS      current
   DESCRIPTION
      "Path: tunnels.performance.ipsecGreTunnels.inPriorityQueues.d7Performance.violateTxOctets

       64 bit unsigned wrappable counter."
   ::= {pr1645v2TvTmplPiGreInPQsD7PerformanceEntry 318767104}

pr1645v2TvTmplPiGreInPQsD7PerformanceBandwidth OBJECT-TYPE
   SYNTAX      Integer32
   MAX-ACCESS  read-only
   STATUS      current
   DESCRIPTION
      "Path: tunnels.performance.ipsecGreTunnels.inPriorityQueues.d7Performance.bandwidth

       unit name = bps
       formula = 8 * ; 8 /"
   ::= {pr1645v2TvTmplPiGreInPQsD7PerformanceEntry 268435456}

pr1645v2TvTmplPiGreOutPQs OBJECT-TYPE
   SYNTAX      SEQUENCE OF Pr1645v2TvTmplPiGreOutPQsEntry
   MAX-ACCESS  not-accessible
   STATUS      current
   DESCRIPTION
      ""
   ::= {pr1645v2TvTmplPiGre 83886080}

pr1645v2TvTmplPiGreOutPQsEntry OBJECT-TYPE
   SYNTAX      Pr1645v2TvTmplPiGreOutPQsEntry
   MAX-ACCESS  not-accessible
   STATUS      current
   DESCRIPTION
      ""
   INDEX      { pr1645v2TvTmplPiGreTableIx,
                pr1645v2TvTmplPiGreOutPQsTableIx }
   ::= {pr1645v2TvTmplPiGreOutPQs 1}

Pr1645v2TvTmplPiGreOutPQsEntry ::=
   SEQUENCE
      {
      pr1645v2TvTmplPiGreOutPQsTableIx
         TableIndex,
      pr1645v2TvTmplPiGreOutPQsName
         INTEGER,
      pr1645v2TvTmplPiGreOutPQsLength
         Integer32,
      pr1645v2TvTmplPiGreOutPQsOctetLength
         Integer32,
      pr1645v2TvTmplPiGreOutPQsRedLength
         Integer32,
      pr1645v2TvTmplPiGreOutPQsPacketsTotal
         Counter64,
      pr1645v2TvTmplPiGreOutPQsPacketsDirectTx
         Counter64,
      pr1645v2TvTmplPiGreOutPQsPacketsQueued
         Counter64,
      pr1645v2TvTmplPiGreOutPQsPacketsDropped
         Counter64,
      pr1645v2TvTmplPiGreOutPQsPacketsRedDropped
         Counter64,
      pr1645v2TvTmplPiGreOutPQsPacketsCirTx
         Counter64,
      pr1645v2TvTmplPiGreOutPQsPacketsEirTx
         Counter64,
      pr1645v2TvTmplPiGreOutPQsPacketsViolateTx
         Counter64,
      pr1645v2TvTmplPiGreOutPQsOctetsTotal
         Counter64,
      pr1645v2TvTmplPiGreOutPQsOctetsDirectTx
         Counter64,
      pr1645v2TvTmplPiGreOutPQsOctetsQueued
         Counter64,
      pr1645v2TvTmplPiGreOutPQsOctetsDropped
         Counter64,
      pr1645v2TvTmplPiGreOutPQsOctetsRedDropped
         Counter64,
      pr1645v2TvTmplPiGreOutPQsOctetsCirTx
         Counter64,
      pr1645v2TvTmplPiGreOutPQsOctetsEirTx
         Counter64,
      pr1645v2TvTmplPiGreOutPQsOctetsViolateTx
         Counter64,
      pr1645v2TvTmplPiGreOutPQsOctetsBandwidth15sec
         Integer32,
      pr1645v2TvTmplPiGreOutPQsOctetsBandwidth30sec
         Integer32,
      pr1645v2TvTmplPiGreOutPQsOctetsBandwidth1min
         Integer32,
      pr1645v2TvTmplPiGreOutPQsOctetsBandwidth2min
         Integer32,
      pr1645v2TvTmplPiGreOutPQsOctetsBandwidth5min
         Integer32
      }

pr1645v2TvTmplPiGreOutPQsTableIx OBJECT-TYPE
   SYNTAX      TableIndex
   MAX-ACCESS  not-accessible
   STATUS      current
   DESCRIPTION
      ""
   ::= {pr1645v2TvTmplPiGreOutPQsEntry 11}

pr1645v2TvTmplPiGreOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.ipsecGreTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplPiGreOutPQsEntry 16777216}

pr1645v2TvTmplPiGreOutPQsLength OBJECT-TYPE
   SYNTAX      Integer32
   MAX-ACCESS  read-only
   STATUS      current
   DESCRIPTION
      "Path: tunnels.performance.ipsecGreTunnels.outPriorityQueues.length"
   ::= {pr1645v2TvTmplPiGreOutPQsEntry 33554432}

pr1645v2TvTmplPiGreOutPQsOctetLength OBJECT-TYPE
   SYNTAX      Integer32
   MAX-ACCESS  read-only
   STATUS      current
   DESCRIPTION
      "Path: tunnels.performance.ipsecGreTunnels.outPriorityQueues.octetLength"
   ::= {pr1645v2TvTmplPiGreOutPQsEntry 150994944}

pr1645v2TvTmplPiGreOutPQsRedLength OBJECT-TYPE
   SYNTAX      Integer32
   MAX-ACCESS  read-only
   STATUS      current
   DESCRIPTION
      "Path: tunnels.performance.ipsecGreTunnels.outPriorityQueues.redLength"
   ::= {pr1645v2TvTmplPiGreOutPQsEntry 134217728}

pr1645v2TvTmplPiGreOutPQsPacketsTotal OBJECT-TYPE
   SYNTAX      Counter64
   MAX-ACCESS  read-only
   STATUS      current
   DESCRIPTION
      "Path: tunnels.performance.ipsecGreTunnels.outPriorityQueues.packets.total

       64 bit unsigned wrappable counter."
   ::= {pr1645v2TvTmplPiGreOutPQsEntry 50790400}

pr1645v2TvTmplPiGreOutPQsPacketsDirectTx OBJECT-TYPE
   SYNTAX      Counter64
   MAX-ACCESS  read-only
   STATUS      current
   DESCRIPTION
      "Path: tunnels.performance.ipsecGreTunnels.outPriorityQueues.packets.directTx

       64 bit unsigned wrappable counter."
   ::= {pr1645v2TvTmplPiGreOutPQsEntry 50397184}

pr1645v2TvTmplPiGreOutPQsPacketsQueued OBJECT-TYPE
   SYNTAX      Counter64
   MAX-ACCESS  read-only
   STATUS      current
   DESCRIPTION
      "Path: tunnels.performance.ipsecGreTunnels.outPriorityQueues.packets.queued

       64 bit unsigned wrappable counter."
   ::= {pr1645v2TvTmplPiGreOutPQsEntry 50462720}

pr1645v2TvTmplPiGreOutPQsPacketsDropped OBJECT-TYPE
   SYNTAX      Counter64
   MAX-ACCESS  read-only
   STATUS      current
   DESCRIPTION
      "Path: tunnels.performance.ipsecGreTunnels.outPriorityQueues.packets.dropped

       64 bit unsigned wrappable counter."
   ::= {pr1645v2TvTmplPiGreOutPQsEntry 50528256}

pr1645v2TvTmplPiGreOutPQsPacketsRedDropped OBJECT-TYPE
   SYNTAX      Counter64
   MAX-ACCESS  read-only
   STATUS      current
   DESCRIPTION
      "Path: tunnels.performance.ipsecGreTunnels.outPriorityQueues.packets.redDropped

       64 bit unsigned wrappable counter."
   ::= {pr1645v2TvTmplPiGreOutPQsEntry 50724864}

pr1645v2TvTmplPiGreOutPQsPacketsCirTx OBJECT-TYPE
   SYNTAX      Counter64
   MAX-ACCESS  read-only
   STATUS      current
   DESCRIPTION
      "Path: tunnels.performance.ipsecGreTunnels.outPriorityQueues.packets.cirTx

       64 bit unsigned wrappable counter."
   ::= {pr1645v2TvTmplPiGreOutPQsEntry 50593792}

pr1645v2TvTmplPiGreOutPQsPacketsEirTx OBJECT-TYPE
   SYNTAX      Counter64
   MAX-ACCESS  read-only
   STATUS      current
   DESCRIPTION
      "Path: tunnels.performance.ipsecGreTunnels.outPriorityQueues.packets.eirTx

       64 bit unsigned wrappable counter."
   ::= {pr1645v2TvTmplPiGreOutPQsEntry 50659328}

pr1645v2TvTmplPiGreOutPQsPacketsViolateTx OBJECT-TYPE
   SYNTAX      Counter64
   MAX-ACCESS  read-only
   STATUS      current
   DESCRIPTION
      "Path: tunnels.performance.ipsecGreTunnels.outPriorityQueues.packets.violateTx

       64 bit unsigned wrappable counter."
   ::= {pr1645v2TvTmplPiGreOutPQsEntry 50855936}

pr1645v2TvTmplPiGreOutPQsOctetsTotal OBJECT-TYPE
   SYNTAX      Counter64
   MAX-ACCESS  read-only
   STATUS      current
   DESCRIPTION
      "Path: tunnels.performance.ipsecGreTunnels.outPriorityQueues.octets.total

       64 bit unsigned wrappable counter."
   ::= {pr1645v2TvTmplPiGreOutPQsEntry 67567616}

pr1645v2TvTmplPiGreOutPQsOctetsDirectTx OBJECT-TYPE
   SYNTAX      Counter64
   MAX-ACCESS  read-only
   STATUS      current
   DESCRIPTION
      "Path: tunnels.performance.ipsecGreTunnels.outPriorityQueues.octets.directTx

       64 bit unsigned wrappable counter."
   ::= {pr1645v2TvTmplPiGreOutPQsEntry 67174400}

pr1645v2TvTmplPiGreOutPQsOctetsQueued OBJECT-TYPE
   SYNTAX      Counter64
   MAX-ACCESS  read-only
   STATUS      current
   DESCRIPTION
      "Path: tunnels.performance.ipsecGreTunnels.outPriorityQueues.octets.queued

       64 bit unsigned wrappable counter."
   ::= {pr1645v2TvTmplPiGreOutPQsEntry 67239936}

pr1645v2TvTmplPiGreOutPQsOctetsDropped OBJECT-TYPE
   SYNTAX      Counter64
   MAX-ACCESS  read-only
   STATUS      current
   DESCRIPTION
      "Path: tunnels.performance.ipsecGreTunnels.outPriorityQueues.octets.dropped

       64 bit unsigned wrappable counter."
   ::= {pr1645v2TvTmplPiGreOutPQsEntry 67305472}

pr1645v2TvTmplPiGreOutPQsOctetsRedDropped OBJECT-TYPE
   SYNTAX      Counter64
   MAX-ACCESS  read-only
   STATUS      current
   DESCRIPTION
      "Path: tunnels.performance.ipsecGreTunnels.outPriorityQueues.octets.redDropped

       64 bit unsigned wrappable counter."
   ::= {pr1645v2TvTmplPiGreOutPQsEntry 67502080}

pr1645v2TvTmplPiGreOutPQsOctetsCirTx OBJECT-TYPE
   SYNTAX      Counter64
   MAX-ACCESS  read-only
   STATUS      current
   DESCRIPTION
      "Path: tunnels.performance.ipsecGreTunnels.outPriorityQueues.octets.cirTx

       64 bit unsigned wrappable counter."
   ::= {pr1645v2TvTmplPiGreOutPQsEntry 67371008}

pr1645v2TvTmplPiGreOutPQsOctetsEirTx OBJECT-TYPE
   SYNTAX      Counter64
   MAX-ACCESS  read-only
   STATUS      current
   DESCRIPTION
      "Path: tunnels.performance.ipsecGreTunnels.outPriorityQueues.octets.eirTx

       64 bit unsigned wrappable counter."
   ::= {pr1645v2TvTmplPiGreOutPQsEntry 67436544}

pr1645v2TvTmplPiGreOutPQsOctetsViolateTx OBJECT-TYPE
   SYNTAX      Counter64
   MAX-ACCESS  read-only
   STATUS      current
   DESCRIPTION
      "Path: tunnels.performance.ipsecGreTunnels.outPriorityQueues.octets.violateTx

       64 bit unsigned wrappable counter."
   ::= {pr1645v2TvTmplPiGreOutPQsEntry 67633152}

pr1645v2TvTmplPiGreOutPQsOctetsBandwidth15sec OBJECT-TYPE
   SYNTAX      Integer32
   MAX-ACCESS  read-only
   STATUS      current
   DESCRIPTION
      "Path: tunnels.performance.ipsecGreTunnels.outPriorityQueues.octets.bandwidth.15sec

       unit name = bps
       formula = 8 * ; 8 /"
   ::= {pr1645v2TvTmplPiGreOutPQsEntry 70386944}

pr1645v2TvTmplPiGreOutPQsOctetsBandwidth30sec OBJECT-TYPE
   SYNTAX      Integer32
   MAX-ACCESS  read-only
   STATUS      current
   DESCRIPTION
      "Path: tunnels.performance.ipsecGreTunnels.outPriorityQueues.octets.bandwidth.30sec

       unit name = bps
       formula = 8 * ; 8 /"
   ::= {pr1645v2TvTmplPiGreOutPQsEntry 70388224}

pr1645v2TvTmplPiGreOutPQsOctetsBandwidth1min OBJECT-TYPE
   SYNTAX      Integer32
   MAX-ACCESS  read-only
   STATUS      current
   DESCRIPTION
      "Path: tunnels.performance.ipsecGreTunnels.outPriorityQueues.octets.bandwidth.1min

       unit name = bps
       formula = 8 * ; 8 /"
   ::= {pr1645v2TvTmplPiGreOutPQsEntry 70390784}

pr1645v2TvTmplPiGreOutPQsOctetsBandwidth2min OBJECT-TYPE
   SYNTAX      Integer32
   MAX-ACCESS  read-only
   STATUS      current
   DESCRIPTION
      "Path: tunnels.performance.ipsecGreTunnels.outPriorityQueues.octets.bandwidth.2min

       unit name = bps
       formula = 8 * ; 8 /"
   ::= {pr1645v2TvTmplPiGreOutPQsEntry 70395904}

pr1645v2TvTmplPiGreOutPQsOctetsBandwidth5min OBJECT-TYPE
   SYNTAX      Integer32
   MAX-ACCESS  read-only
   STATUS      current
   DESCRIPTION
      "Path: tunnels.performance.ipsecGreTunnels.outPriorityQueues.octets.bandwidth.5min

       unit name = bps
       formula = 8 * ; 8 /"
   ::= {pr1645v2TvTmplPiGreOutPQsEntry 70411264}

pr1645v2TvTmplPiGreOutPQsH2Performance OBJECT-TYPE
   SYNTAX      SEQUENCE OF Pr1645v2TvTmplPiGreOutPQsH2PerformanceEntry
   MAX-ACCESS  not-accessible
   STATUS      current
   DESCRIPTION
      ""
   ::= {pr1645v2TvTmplPiGre 84213760}

pr1645v2TvTmplPiGreOutPQsH2PerformanceEntry OBJECT-TYPE
   SYNTAX      Pr1645v2TvTmplPiGreOutPQsH2PerformanceEntry
   MAX-ACCESS  not-accessible
   STATUS      current
   DESCRIPTION
      ""
   INDEX      { pr1645v2TvTmplPiGreTableIx,
                pr1645v2TvTmplPiGreOutPQsTableIx,
                pr1645v2TvTmplPiGreOutPQsH2PerformanceTableIx }
   ::= {pr1645v2TvTmplPiGreOutPQsH2Performance 1}

Pr1645v2TvTmplPiGreOutPQsH2PerformanceEntry ::=
   SEQUENCE
      {
      pr1645v2TvTmplPiGreOutPQsH2PerformanceTableIx
         TableIndex,
      pr1645v2TvTmplPiGreOutPQsH2PerformanceSysUpTime
         TimeTicks,
      pr1645v2TvTmplPiGreOutPQsH2PerformanceTotPkts
         Counter64,
      pr1645v2TvTmplPiGreOutPQsH2PerformanceDirTxPkts
         Counter64,
      pr1645v2TvTmplPiGreOutPQsH2PerformanceQdPkts
         Counter64,
      pr1645v2TvTmplPiGreOutPQsH2PerformanceDropPkts
         Counter64,
      pr1645v2TvTmplPiGreOutPQsH2PerformanceRDropPkts
         Counter64,
      pr1645v2TvTmplPiGreOutPQsH2PerformanceCirTxPkts
         Counter64,
      pr1645v2TvTmplPiGreOutPQsH2PerformanceEirTxPkts
         Counter64,
      pr1645v2TvTmplPiGreOutPQsH2PerformanceViolTxPkts
         Counter64,
      pr1645v2TvTmplPiGreOutPQsH2PerformanceTotOcts
         Counter64,
      pr1645v2TvTmplPiGreOutPQsH2PerformanceDirTxOcts
         Counter64,
      pr1645v2TvTmplPiGreOutPQsH2PerformanceQdOcts
         Counter64,
      pr1645v2TvTmplPiGreOutPQsH2PerformanceDropOcts
         Counter64,
      pr1645v2TvTmplPiGreOutPQsH2PerformanceRDropOcts
         Counter64,
      pr1645v2TvTmplPiGreOutPQsH2PerformanceCirTxOcts
         Counter64,
      pr1645v2TvTmplPiGreOutPQsH2PerformanceEirTxOcts
         Counter64,
      pr1645v2TvTmplPiGreOutPQsH2PerformanceViolTxOcts
         Counter64,
      pr1645v2TvTmplPiGreOutPQsH2PerformanceBandwidth
         Integer32
      }

pr1645v2TvTmplPiGreOutPQsH2PerformanceTableIx OBJECT-TYPE
   SYNTAX      TableIndex
   MAX-ACCESS  not-accessible
   STATUS      current
   DESCRIPTION
      ""
   ::= {pr1645v2TvTmplPiGreOutPQsH2PerformanceEntry 11}

pr1645v2TvTmplPiGreOutPQsH2PerformanceSysUpTime OBJECT-TYPE
   SYNTAX      TimeTicks
   MAX-ACCESS  read-only
   STATUS      current
   DESCRIPTION
      "Path: tunnels.performance.ipsecGreTunnels.outPriorityQueues.h2Performance.sysUpTime

       Time in centi-second."
   ::= {pr1645v2TvTmplPiGreOutPQsH2PerformanceEntry 16777216}

pr1645v2TvTmplPiGreOutPQsH2PerformanceTotPkts OBJECT-TYPE
   SYNTAX      Counter64
   MAX-ACCESS  read-only
   STATUS      current
   DESCRIPTION
      "Path: tunnels.performance.ipsecGreTunnels.outPriorityQueues.h2Performance.totalPkts

       64 bit unsigned wrappable counter."
   ::= {pr1645v2TvTmplPiGreOutPQsH2PerformanceEntry 234881024}

pr1645v2TvTmplPiGreOutPQsH2PerformanceDirTxPkts OBJECT-TYPE
   SYNTAX      Counter64
   MAX-ACCESS  read-only
   STATUS      current
   DESCRIPTION
      "Path: tunnels.performance.ipsecGreTunnels.outPriorityQueues.h2Performance.directTxPkts

       64 bit unsigned wrappable counter."
   ::= {pr1645v2TvTmplPiGreOutPQsH2PerformanceEntry 33554432}

pr1645v2TvTmplPiGreOutPQsH2PerformanceQdPkts OBJECT-TYPE
   SYNTAX      Counter64
   MAX-ACCESS  read-only
   STATUS      current
   DESCRIPTION
      "Path: tunnels.performance.ipsecGreTunnels.outPriorityQueues.h2Performance.queuedPkts

       64 bit unsigned wrappable counter."
   ::= {pr1645v2TvTmplPiGreOutPQsH2PerformanceEntry 50331648}

pr1645v2TvTmplPiGreOutPQsH2PerformanceDropPkts OBJECT-TYPE
   SYNTAX      Counter64
   MAX-ACCESS  read-only
   STATUS      current
   DESCRIPTION
      "Path: tunnels.performance.ipsecGreTunnels.outPriorityQueues.h2Performance.droppedPkts

       64 bit unsigned wrappable counter."
   ::= {pr1645v2TvTmplPiGreOutPQsH2PerformanceEntry 67108864}

pr1645v2TvTmplPiGreOutPQsH2PerformanceRDropPkts OBJECT-TYPE
   SYNTAX      Counter64
   MAX-ACCESS  read-only
   STATUS      current
   DESCRIPTION
      "Path: tunnels.performance.ipsecGreTunnels.outPriorityQueues.h2Performance.redDroppedPkts

       64 bit unsigned wrappable counter."
   ::= {pr1645v2TvTmplPiGreOutPQsH2PerformanceEntry 201326592}

pr1645v2TvTmplPiGreOutPQsH2PerformanceCirTxPkts OBJECT-TYPE
   SYNTAX      Counter64
   MAX-ACCESS  read-only
   STATUS      current
   DESCRIPTION
      "Path: tunnels.performance.ipsecGreTunnels.outPriorityQueues.h2Performance.cirTxPkts

       64 bit unsigned wrappable counter."
   ::= {pr1645v2TvTmplPiGreOutPQsH2PerformanceEntry 83886080}

pr1645v2TvTmplPiGreOutPQsH2PerformanceEirTxPkts OBJECT-TYPE
   SYNTAX      Counter64
   MAX-ACCESS  read-only
   STATUS      current
   DESCRIPTION
      "Path: tunnels.performance.ipsecGreTunnels.outPriorityQueues.h2Performance.eirTxPkts

       64 bit unsigned wrappable counter."
   ::= {pr1645v2TvTmplPiGreOutPQsH2PerformanceEntry 100663296}

pr1645v2TvTmplPiGreOutPQsH2PerformanceViolTxPkts OBJECT-TYPE
   SYNTAX      Counter64
   MAX-ACCESS  read-only
   STATUS      current
   DESCRIPTION
      "Path: tunnels.performance.ipsecGreTunnels.outPriorityQueues.h2Performance.violateTxPkts

       64 bit unsigned wrappable counter."
   ::= {pr1645v2TvTmplPiGreOutPQsH2PerformanceEntry 301989888}

pr1645v2TvTmplPiGreOutPQsH2PerformanceTotOcts OBJECT-TYPE
   SYNTAX      Counter64
   MAX-ACCESS  read-only
   STATUS      current
   DESCRIPTION
      "Path: tunnels.performance.ipsecGreTunnels.outPriorityQueues.h2Performance.totalOctets

       64 bit unsigned wrappable counter."
   ::= {pr1645v2TvTmplPiGreOutPQsH2PerformanceEntry 251658240}

pr1645v2TvTmplPiGreOutPQsH2PerformanceDirTxOcts OBJECT-TYPE
   SYNTAX      Counter64
   MAX-ACCESS  read-only
   STATUS      current
   DESCRIPTION
      "Path: tunnels.performance.ipsecGreTunnels.outPriorityQueues.h2Performance.directTxOctets

       64 bit unsigned wrappable counter."
   ::= {pr1645v2TvTmplPiGreOutPQsH2PerformanceEntry 117440512}

pr1645v2TvTmplPiGreOutPQsH2PerformanceQdOcts OBJECT-TYPE
   SYNTAX      Counter64
   MAX-ACCESS  read-only
   STATUS      current
   DESCRIPTION
      "Path: tunnels.performance.ipsecGreTunnels.outPriorityQueues.h2Performance.queuedOctets

       64 bit unsigned wrappable counter."
   ::= {pr1645v2TvTmplPiGreOutPQsH2PerformanceEntry 134217728}

pr1645v2TvTmplPiGreOutPQsH2PerformanceDropOcts OBJECT-TYPE
   SYNTAX      Counter64
   MAX-ACCESS  read-only
   STATUS      current
   DESCRIPTION
      "Path: tunnels.performance.ipsecGreTunnels.outPriorityQueues.h2Performance.droppedOctets

       64 bit unsigned wrappable counter."
   ::= {pr1645v2TvTmplPiGreOutPQsH2PerformanceEntry 150994944}

pr1645v2TvTmplPiGreOutPQsH2PerformanceRDropOcts OBJECT-TYPE
   SYNTAX      Counter64
   MAX-ACCESS  read-only
   STATUS      current
   DESCRIPTION
      "Path: tunnels.performance.ipsecGreTunnels.outPriorityQueues.h2Performance.redDroppedOctets

       64 bit unsigned wrappable counter."
   ::= {pr1645v2TvTmplPiGreOutPQsH2PerformanceEntry 218103808}

pr1645v2TvTmplPiGreOutPQsH2PerformanceCirTxOcts OBJECT-TYPE
   SYNTAX      Counter64
   MAX-ACCESS  read-only
   STATUS      current
   DESCRIPTION
      "Path: tunnels.performance.ipsecGreTunnels.outPriorityQueues.h2Performance.cirTxOctets

       64 bit unsigned wrappable counter."
   ::= {pr1645v2TvTmplPiGreOutPQsH2PerformanceEntry 167772160}

pr1645v2TvTmplPiGreOutPQsH2PerformanceEirTxOcts OBJECT-TYPE
   SYNTAX      Counter64
   MAX-ACCESS  read-only
   STATUS      current
   DESCRIPTION
      "Path: tunnels.performance.ipsecGreTunnels.outPriorityQueues.h2Performance.eirTxOctets

       64 bit unsigned wrappable counter."
   ::= {pr1645v2TvTmplPiGreOutPQsH2PerformanceEntry 184549376}

pr1645v2TvTmplPiGreOutPQsH2PerformanceViolTxOcts OBJECT-TYPE
   SYNTAX      Counter64
   MAX-ACCESS  read-only
   STATUS      current
   DESCRIPTION
      "Path: tunnels.performance.ipsecGreTunnels.outPriorityQueues.h2Performance.violateTxOctets

       64 bit unsigned wrappable counter."
   ::= {pr1645v2TvTmplPiGreOutPQsH2PerformanceEntry 318767104}

pr1645v2TvTmplPiGreOutPQsH2PerformanceBandwidth OBJECT-TYPE
   SYNTAX      Integer32
   MAX-ACCESS  read-only
   STATUS      current
   DESCRIPTION
      "Path: tunnels.performance.ipsecGreTunnels.outPriorityQueues.h2Performance.bandwidth

       unit name = bps
       formula = 8 * ; 8 /"
   ::= {pr1645v2TvTmplPiGreOutPQsH2PerformanceEntry 268435456}

pr1645v2TvTmplPiGreOutPQsH24Performance OBJECT-TYPE
   SYNTAX      SEQUENCE OF Pr1645v2TvTmplPiGreOutPQsH24PerformanceEntry
   MAX-ACCESS  not-accessible
   STATUS      current
   DESCRIPTION
      ""
   ::= {pr1645v2TvTmplPiGre 84279296}

pr1645v2TvTmplPiGreOutPQsH24PerformanceEntry OBJECT-TYPE
   SYNTAX      Pr1645v2TvTmplPiGreOutPQsH24PerformanceEntry
   MAX-ACCESS  not-accessible
   STATUS      current
   DESCRIPTION
      ""
   INDEX      { pr1645v2TvTmplPiGreTableIx,
                pr1645v2TvTmplPiGreOutPQsTableIx,
                pr1645v2TvTmplPiGreOutPQsH24PerformanceTableIx }
   ::= {pr1645v2TvTmplPiGreOutPQsH24Performance 1}

Pr1645v2TvTmplPiGreOutPQsH24PerformanceEntry ::=
   SEQUENCE
      {
      pr1645v2TvTmplPiGreOutPQsH24PerformanceTableIx
         TableIndex,
      pr1645v2TvTmplPiGreOutPQsH24PerformanceSysUpTime
         TimeTicks,
      pr1645v2TvTmplPiGreOutPQsH24PerformanceTotPkts
         Counter64,
      pr1645v2TvTmplPiGreOutPQsH24PerformanceDirTxPkts
         Counter64,
      pr1645v2TvTmplPiGreOutPQsH24PerformanceQdPkts
         Counter64,
      pr1645v2TvTmplPiGreOutPQsH24PerformanceDropPkts
         Counter64,
      pr1645v2TvTmplPiGreOutPQsH24PerformanceRDropPkts
         Counter64,
      pr1645v2TvTmplPiGreOutPQsH24PerformanceCirTxPkts
         Counter64,
      pr1645v2TvTmplPiGreOutPQsH24PerformanceEirTxPkts
         Counter64,
      pr1645v2TvTmplPiGreOutPQsH24PerformanceViolTxPkts
         Counter64,
      pr1645v2TvTmplPiGreOutPQsH24PerformanceTotOcts
         Counter64,
      pr1645v2TvTmplPiGreOutPQsH24PerformanceDirTxOcts
         Counter64,
      pr1645v2TvTmplPiGreOutPQsH24PerformanceQdOcts
         Counter64,
      pr1645v2TvTmplPiGreOutPQsH24PerformanceDropOcts
         Counter64,
      pr1645v2TvTmplPiGreOutPQsH24PerformanceRDropOcts
         Counter64,
      pr1645v2TvTmplPiGreOutPQsH24PerformanceCirTxOcts
         Counter64,
      pr1645v2TvTmplPiGreOutPQsH24PerformanceEirTxOcts
         Counter64,
      pr1645v2TvTmplPiGreOutPQsH24PerformanceViolTxOcts
         Counter64,
      pr1645v2TvTmplPiGreOutPQsH24PerformanceBandwidth
         Integer32
      }

pr1645v2TvTmplPiGreOutPQsH24PerformanceTableIx OBJECT-TYPE
   SYNTAX      TableIndex
   MAX-ACCESS  not-accessible
   STATUS      current
   DESCRIPTION
      ""
   ::= {pr1645v2TvTmplPiGreOutPQsH24PerformanceEntry 11}

pr1645v2TvTmplPiGreOutPQsH24PerformanceSysUpTime OBJECT-TYPE
   SYNTAX      TimeTicks
   MAX-ACCESS  read-only
   STATUS      current
   DESCRIPTION
      "Path: tunnels.performance.ipsecGreTunnels.outPriorityQueues.h24Performance.sysUpTime

       Time in centi-second."
   ::= {pr1645v2TvTmplPiGreOutPQsH24PerformanceEntry 16777216}

pr1645v2TvTmplPiGreOutPQsH24PerformanceTotPkts OBJECT-TYPE
   SYNTAX      Counter64
   MAX-ACCESS  read-only
   STATUS      current
   DESCRIPTION
      "Path: tunnels.performance.ipsecGreTunnels.outPriorityQueues.h24Performance.totalPkts

       64 bit unsigned wrappable counter."
   ::= {pr1645v2TvTmplPiGreOutPQsH24PerformanceEntry 234881024}

pr1645v2TvTmplPiGreOutPQsH24PerformanceDirTxPkts OBJECT-TYPE
   SYNTAX      Counter64
   MAX-ACCESS  read-only
   STATUS      current
   DESCRIPTION
      "Path: tunnels.performance.ipsecGreTunnels.outPriorityQueues.h24Performance.directTxPkts

       64 bit unsigned wrappable counter."
   ::= {pr1645v2TvTmplPiGreOutPQsH24PerformanceEntry 33554432}

pr1645v2TvTmplPiGreOutPQsH24PerformanceQdPkts OBJECT-TYPE
   SYNTAX      Counter64
   MAX-ACCESS  read-only
   STATUS      current
   DESCRIPTION
      "Path: tunnels.performance.ipsecGreTunnels.outPriorityQueues.h24Performance.queuedPkts

       64 bit unsigned wrappable counter."
   ::= {pr1645v2TvTmplPiGreOutPQsH24PerformanceEntry 50331648}

pr1645v2TvTmplPiGreOutPQsH24PerformanceDropPkts OBJECT-TYPE
   SYNTAX      Counter64
   MAX-ACCESS  read-only
   STATUS      current
   DESCRIPTION
      "Path: tunnels.performance.ipsecGreTunnels.outPriorityQueues.h24Performance.droppedPkts

       64 bit unsigned wrappable counter."
   ::= {pr1645v2TvTmplPiGreOutPQsH24PerformanceEntry 67108864}

pr1645v2TvTmplPiGreOutPQsH24PerformanceRDropPkts OBJECT-TYPE
   SYNTAX      Counter64
   MAX-ACCESS  read-only
   STATUS      current
   DESCRIPTION
      "Path: tunnels.performance.ipsecGreTunnels.outPriorityQueues.h24Performance.redDroppedPkts

       64 bit unsigned wrappable counter."
   ::= {pr1645v2TvTmplPiGreOutPQsH24PerformanceEntry 201326592}

pr1645v2TvTmplPiGreOutPQsH24PerformanceCirTxPkts OBJECT-TYPE
   SYNTAX      Counter64
   MAX-ACCESS  read-only
   STATUS      current
   DESCRIPTION
      "Path: tunnels.performance.ipsecGreTunnels.outPriorityQueues.h24Performance.cirTxPkts

       64 bit unsigned wrappable counter."
   ::= {pr1645v2TvTmplPiGreOutPQsH24PerformanceEntry 83886080}

pr1645v2TvTmplPiGreOutPQsH24PerformanceEirTxPkts OBJECT-TYPE
   SYNTAX      Counter64
   MAX-ACCESS  read-only
   STATUS      current
   DESCRIPTION
      "Path: tunnels.performance.ipsecGreTunnels.outPriorityQueues.h24Performance.eirTxPkts

       64 bit unsigned wrappable counter."
   ::= {pr1645v2TvTmplPiGreOutPQsH24PerformanceEntry 100663296}

pr1645v2TvTmplPiGreOutPQsH24PerformanceViolTxPkts OBJECT-TYPE
   SYNTAX      Counter64
   MAX-ACCESS  read-only
   STATUS      current
   DESCRIPTION
      "Path: tunnels.performance.ipsecGreTunnels.outPriorityQueues.h24Performance.violateTxPkts

       64 bit unsigned wrappable counter."
   ::= {pr1645v2TvTmplPiGreOutPQsH24PerformanceEntry 301989888}

pr1645v2TvTmplPiGreOutPQsH24PerformanceTotOcts OBJECT-TYPE
   SYNTAX      Counter64
   MAX-ACCESS  read-only
   STATUS      current
   DESCRIPTION
      "Path: tunnels.performance.ipsecGreTunnels.outPriorityQueues.h24Performance.totalOctets

       64 bit unsigned wrappable counter."
   ::= {pr1645v2TvTmplPiGreOutPQsH24PerformanceEntry 251658240}

pr1645v2TvTmplPiGreOutPQsH24PerformanceDirTxOcts OBJECT-TYPE
   SYNTAX      Counter64
   MAX-ACCESS  read-only
   STATUS      current
   DESCRIPTION
      "Path: tunnels.performance.ipsecGreTunnels.outPriorityQueues.h24Performance.directTxOctets

       64 bit unsigned wrappable counter."
   ::= {pr1645v2TvTmplPiGreOutPQsH24PerformanceEntry 117440512}

pr1645v2TvTmplPiGreOutPQsH24PerformanceQdOcts OBJECT-TYPE
   SYNTAX      Counter64
   MAX-ACCESS  read-only
   STATUS      current
   DESCRIPTION
      "Path: tunnels.performance.ipsecGreTunnels.outPriorityQueues.h24Performance.queuedOctets

       64 bit unsigned wrappable counter."
   ::= {pr1645v2TvTmplPiGreOutPQsH24PerformanceEntry 134217728}

pr1645v2TvTmplPiGreOutPQsH24PerformanceDropOcts OBJECT-TYPE
   SYNTAX      Counter64
   MAX-ACCESS  read-only
   STATUS      current
   DESCRIPTION
      "Path: tunnels.performance.ipsecGreTunnels.outPriorityQueues.h24Performance.droppedOctets

       64 bit unsigned wrappable counter."
   ::= {pr1645v2TvTmplPiGreOutPQsH24PerformanceEntry 150994944}

pr1645v2TvTmplPiGreOutPQsH24PerformanceRDropOcts OBJECT-TYPE
   SYNTAX      Counter64
   MAX-ACCESS  read-only
   STATUS      current
   DESCRIPTION
      "Path: tunnels.performance.ipsecGreTunnels.outPriorityQueues.h24Performance.redDroppedOctets

       64 bit unsigned wrappable counter."
   ::= {pr1645v2TvTmplPiGreOutPQsH24PerformanceEntry 218103808}

pr1645v2TvTmplPiGreOutPQsH24PerformanceCirTxOcts OBJECT-TYPE
   SYNTAX      Counter64
   MAX-ACCESS  read-only
   STATUS      current
   DESCRIPTION
      "Path: tunnels.performance.ipsecGreTunnels.outPriorityQueues.h24Performance.cirTxOctets

       64 bit unsigned wrappable counter."
   ::= {pr1645v2TvTmplPiGreOutPQsH24PerformanceEntry 167772160}

pr1645v2TvTmplPiGreOutPQsH24PerformanceEirTxOcts OBJECT-TYPE
   SYNTAX      Counter64
   MAX-ACCESS  read-only
   STATUS      current
   DESCRIPTION
      "Path: tunnels.performance.ipsecGreTunnels.outPriorityQueues.h24Performance.eirTxOctets

       64 bit unsigned wrappable counter."
   ::= {pr1645v2TvTmplPiGreOutPQsH24PerformanceEntry 184549376}

pr1645v2TvTmplPiGreOutPQsH24PerformanceViolTxOcts OBJECT-TYPE
   SYNTAX      Counter64
   MAX-ACCESS  read-only
   STATUS      current
   DESCRIPTION
      "Path: tunnels.performance.ipsecGreTunnels.outPriorityQueues.h24Performance.violateTxOctets

       64 bit unsigned wrappable counter."
   ::= {pr1645v2TvTmplPiGreOutPQsH24PerformanceEntry 318767104}

pr1645v2TvTmplPiGreOutPQsH24PerformanceBandwidth OBJECT-TYPE
   SYNTAX      Integer32
   MAX-ACCESS  read-only
   STATUS      current
   DESCRIPTION
      "Path: tunnels.performance.ipsecGreTunnels.outPriorityQueues.h24Performance.bandwidth

       unit name = bps
       formula = 8 * ; 8 /"
   ::= {pr1645v2TvTmplPiGreOutPQsH24PerformanceEntry 268435456}

pr1645v2TvTmplPiGreOutPQsD7Performance OBJECT-TYPE
   SYNTAX      SEQUENCE OF Pr1645v2TvTmplPiGreOutPQsD7PerformanceEntry
   MAX-ACCESS  not-accessible
   STATUS      current
   DESCRIPTION
      ""
   ::= {pr1645v2TvTmplPiGre 84344832}

pr1645v2TvTmplPiGreOutPQsD7PerformanceEntry OBJECT-TYPE
   SYNTAX      Pr1645v2TvTmplPiGreOutPQsD7PerformanceEntry
   MAX-ACCESS  not-accessible
   STATUS      current
   DESCRIPTION
      ""
   INDEX      { pr1645v2TvTmplPiGreTableIx,
                pr1645v2TvTmplPiGreOutPQsTableIx,
                pr1645v2TvTmplPiGreOutPQsD7PerformanceTableIx }
   ::= {pr1645v2TvTmplPiGreOutPQsD7Performance 1}

Pr1645v2TvTmplPiGreOutPQsD7PerformanceEntry ::=
   SEQUENCE
      {
      pr1645v2TvTmplPiGreOutPQsD7PerformanceTableIx
         TableIndex,
      pr1645v2TvTmplPiGreOutPQsD7PerformanceSysUpTime
         TimeTicks,
      pr1645v2TvTmplPiGreOutPQsD7PerformanceTotPkts
         Counter64,
      pr1645v2TvTmplPiGreOutPQsD7PerformanceDirTxPkts
         Counter64,
      pr1645v2TvTmplPiGreOutPQsD7PerformanceQdPkts
         Counter64,
      pr1645v2TvTmplPiGreOutPQsD7PerformanceDropPkts
         Counter64,
      pr1645v2TvTmplPiGreOutPQsD7PerformanceRDropPkts
         Counter64,
      pr1645v2TvTmplPiGreOutPQsD7PerformanceCirTxPkts
         Counter64,
      pr1645v2TvTmplPiGreOutPQsD7PerformanceEirTxPkts
         Counter64,
      pr1645v2TvTmplPiGreOutPQsD7PerformanceViolTxPkts
         Counter64,
      pr1645v2TvTmplPiGreOutPQsD7PerformanceTotOcts
         Counter64,
      pr1645v2TvTmplPiGreOutPQsD7PerformanceDirTxOcts
         Counter64,
      pr1645v2TvTmplPiGreOutPQsD7PerformanceQdOcts
         Counter64,
      pr1645v2TvTmplPiGreOutPQsD7PerformanceDropOcts
         Counter64,
      pr1645v2TvTmplPiGreOutPQsD7PerformanceRDropOcts
         Counter64,
      pr1645v2TvTmplPiGreOutPQsD7PerformanceCirTxOcts
         Counter64,
      pr1645v2TvTmplPiGreOutPQsD7PerformanceEirTxOcts
         Counter64,
      pr1645v2TvTmplPiGreOutPQsD7PerformanceViolTxOcts
         Counter64,
      pr1645v2TvTmplPiGreOutPQsD7PerformanceBandwidth
         Integer32
      }

pr1645v2TvTmplPiGreOutPQsD7PerformanceTableIx OBJECT-TYPE
   SYNTAX      TableIndex
   MAX-ACCESS  not-accessible
   STATUS      current
   DESCRIPTION
      ""
   ::= {pr1645v2TvTmplPiGreOutPQsD7PerformanceEntry 11}

pr1645v2TvTmplPiGreOutPQsD7PerformanceSysUpTime OBJECT-TYPE
   SYNTAX      TimeTicks
   MAX-ACCESS  read-only
   STATUS      current
   DESCRIPTION
      "Path: tunnels.performance.ipsecGreTunnels.outPriorityQueues.d7Performance.sysUpTime

       Time in centi-second."
   ::= {pr1645v2TvTmplPiGreOutPQsD7PerformanceEntry 16777216}

pr1645v2TvTmplPiGreOutPQsD7PerformanceTotPkts OBJECT-TYPE
   SYNTAX      Counter64
   MAX-ACCESS  read-only
   STATUS      current
   DESCRIPTION
      "Path: tunnels.performance.ipsecGreTunnels.outPriorityQueues.d7Performance.totalPkts

       64 bit unsigned wrappable counter."
   ::= {pr1645v2TvTmplPiGreOutPQsD7PerformanceEntry 234881024}

pr1645v2TvTmplPiGreOutPQsD7PerformanceDirTxPkts OBJECT-TYPE
   SYNTAX      Counter64
   MAX-ACCESS  read-only
   STATUS      current
   DESCRIPTION
      "Path: tunnels.performance.ipsecGreTunnels.outPriorityQueues.d7Performance.directTxPkts

       64 bit unsigned wrappable counter."
   ::= {pr1645v2TvTmplPiGreOutPQsD7PerformanceEntry 33554432}

pr1645v2TvTmplPiGreOutPQsD7PerformanceQdPkts OBJECT-TYPE
   SYNTAX      Counter64
   MAX-ACCESS  read-only
   STATUS      current
   DESCRIPTION
      "Path: tunnels.performance.ipsecGreTunnels.outPriorityQueues.d7Performance.queuedPkts

       64 bit unsigned wrappable counter."
   ::= {pr1645v2TvTmplPiGreOutPQsD7PerformanceEntry 50331648}

pr1645v2TvTmplPiGreOutPQsD7PerformanceDropPkts OBJECT-TYPE
   SYNTAX      Counter64
   MAX-ACCESS  read-only
   STATUS      current
   DESCRIPTION
      "Path: tunnels.performance.ipsecGreTunnels.outPriorityQueues.d7Performance.droppedPkts

       64 bit unsigned wrappable counter."
   ::= {pr1645v2TvTmplPiGreOutPQsD7PerformanceEntry 67108864}

pr1645v2TvTmplPiGreOutPQsD7PerformanceRDropPkts OBJECT-TYPE
   SYNTAX      Counter64
   MAX-ACCESS  read-only
   STATUS      current
   DESCRIPTION
      "Path: tunnels.performance.ipsecGreTunnels.outPriorityQueues.d7Performance.redDroppedPkts

       64 bit unsigned wrappable counter."
   ::= {pr1645v2TvTmplPiGreOutPQsD7PerformanceEntry 201326592}

pr1645v2TvTmplPiGreOutPQsD7PerformanceCirTxPkts OBJECT-TYPE
   SYNTAX      Counter64
   MAX-ACCESS  read-only
   STATUS      current
   DESCRIPTION
      "Path: tunnels.performance.ipsecGreTunnels.outPriorityQueues.d7Performance.cirTxPkts

       64 bit unsigned wrappable counter."
   ::= {pr1645v2TvTmplPiGreOutPQsD7PerformanceEntry 83886080}

pr1645v2TvTmplPiGreOutPQsD7PerformanceEirTxPkts OBJECT-TYPE
   SYNTAX      Counter64
   MAX-ACCESS  read-only
   STATUS      current
   DESCRIPTION
      "Path: tunnels.performance.ipsecGreTunnels.outPriorityQueues.d7Performance.eirTxPkts

       64 bit unsigned wrappable counter."
   ::= {pr1645v2TvTmplPiGreOutPQsD7PerformanceEntry 100663296}

pr1645v2TvTmplPiGreOutPQsD7PerformanceViolTxPkts OBJECT-TYPE
   SYNTAX      Counter64
   MAX-ACCESS  read-only
   STATUS      current
   DESCRIPTION
      "Path: tunnels.performance.ipsecGreTunnels.outPriorityQueues.d7Performance.violateTxPkts

       64 bit unsigned wrappable counter."
   ::= {pr1645v2TvTmplPiGreOutPQsD7PerformanceEntry 301989888}

pr1645v2TvTmplPiGreOutPQsD7PerformanceTotOcts OBJECT-TYPE
   SYNTAX      Counter64
   MAX-ACCESS  read-only
   STATUS      current
   DESCRIPTION
      "Path: tunnels.performance.ipsecGreTunnels.outPriorityQueues.d7Performance.totalOctets

       64 bit unsigned wrappable counter."
   ::= {pr1645v2TvTmplPiGreOutPQsD7PerformanceEntry 251658240}

pr1645v2TvTmplPiGreOutPQsD7PerformanceDirTxOcts OBJECT-TYPE
   SYNTAX      Counter64
   MAX-ACCESS  read-only
   STATUS      current
   DESCRIPTION
      "Path: tunnels.performance.ipsecGreTunnels.outPriorityQueues.d7Performance.directTxOctets

       64 bit unsigned wrappable counter."
   ::= {pr1645v2TvTmplPiGreOutPQsD7PerformanceEntry 117440512}

pr1645v2TvTmplPiGreOutPQsD7PerformanceQdOcts OBJECT-TYPE
   SYNTAX      Counter64
   MAX-ACCESS  read-only
   STATUS      current
   DESCRIPTION
      "Path: tunnels.performance.ipsecGreTunnels.outPriorityQueues.d7Performance.queuedOctets

       64 bit unsigned wrappable counter."
   ::= {pr1645v2TvTmplPiGreOutPQsD7PerformanceEntry 134217728}

pr1645v2TvTmplPiGreOutPQsD7PerformanceDropOcts OBJECT-TYPE
   SYNTAX      Counter64
   MAX-ACCESS  read-only
   STATUS      current
   DESCRIPTION
      "Path: tunnels.performance.ipsecGreTunnels.outPriorityQueues.d7Performance.droppedOctets

       64 bit unsigned wrappable counter."
   ::= {pr1645v2TvTmplPiGreOutPQsD7PerformanceEntry 150994944}

pr1645v2TvTmplPiGreOutPQsD7PerformanceRDropOcts OBJECT-TYPE
   SYNTAX      Counter64
   MAX-ACCESS  read-only
   STATUS      current
   DESCRIPTION
      "Path: tunnels.performance.ipsecGreTunnels.outPriorityQueues.d7Performance.redDroppedOctets

       64 bit unsigned wrappable counter."
   ::= {pr1645v2TvTmplPiGreOutPQsD7PerformanceEntry 218103808}

pr1645v2TvTmplPiGreOutPQsD7PerformanceCirTxOcts OBJECT-TYPE
   SYNTAX      Counter64
   MAX-ACCESS  read-only
   STATUS      current
   DESCRIPTION
      "Path: tunnels.performance.ipsecGreTunnels.outPriorityQueues.d7Performance.cirTxOctets

       64 bit unsigned wrappable counter."
   ::= {pr1645v2TvTmplPiGreOutPQsD7PerformanceEntry 167772160}

pr1645v2TvTmplPiGreOutPQsD7PerformanceEirTxOcts OBJECT-TYPE
   SYNTAX      Counter64
   MAX-ACCESS  read-only
   STATUS      current
   DESCRIPTION
      "Path: tunnels.performance.ipsecGreTunnels.outPriorityQueues.d7Performance.eirTxOctets

       64 bit unsigned wrappable counter."
   ::= {pr1645v2TvTmplPiGreOutPQsD7PerformanceEntry 184549376}

pr1645v2TvTmplPiGreOutPQsD7PerformanceViolTxOcts OBJECT-TYPE
   SYNTAX      Counter64
   MAX-ACCESS  read-only
   STATUS      current
   DESCRIPTION
      "Path: tunnels.performance.ipsecGreTunnels.outPriorityQueues.d7Performance.violateTxOctets

       64 bit unsigned wrappable counter."
   ::= {pr1645v2TvTmplPiGreOutPQsD7PerformanceEntry 318767104}

pr1645v2TvTmplPiGreOutPQsD7PerformanceBandwidth OBJECT-TYPE
   SYNTAX      Integer32
   MAX-ACCESS  read-only
   STATUS      current
   DESCRIPTION
      "Path: tunnels.performance.ipsecGreTunnels.outPriorityQueues.d7Performance.bandwidth

       unit name = bps
       formula = 8 * ; 8 /"
   ::= {pr1645v2TvTmplPiGreOutPQsD7PerformanceEntry 268435456}


pr1645v2TvTmplPerfin OBJECT IDENTIFIER ::= {pr1645v2TvTmpl 12}

pr1645v2TvTmplPerfinSSCTable OBJECT-TYPE
   SYNTAX      SEQUENCE OF Pr1645v2TvTmplPerfinEntry
   MAX-ACCESS  not-accessible
   STATUS      current
   DESCRIPTION
      ""
   ::= {pr1645v2TvTmplPerfin 1}

pr1645v2TvTmplPerfinEntry OBJECT-TYPE
   SYNTAX      Pr1645v2TvTmplPerfinEntry
   MAX-ACCESS  not-accessible
   STATUS      current
   DESCRIPTION
      ""
   INDEX      { pr1645v2TvTmplPerfinTableIx }
   ::= {pr1645v2TvTmplPerfinSSCTable 1}

Pr1645v2TvTmplPerfinEntry ::=
   SEQUENCE
      {
      pr1645v2TvTmplPerfinTableIx
         TableIndex,
      pr1645v2TvTmplPerfinName
         DisplayString,
      pr1645v2TvTmplPerfinMCInOctets
         Counter64,
      pr1645v2TvTmplPerfinMCInUcast
         Counter64,
      pr1645v2TvTmplPerfinMCInNUcastPkts
         Counter64,
      pr1645v2TvTmplPerfinMCInBcastPkts
         Counter64,
      pr1645v2TvTmplPerfinMCInMcastPkts
         Counter64,
      pr1645v2TvTmplPerfinMCInDiscards
         Counter64,
      pr1645v2TvTmplPerfinMCInErrors
         Counter64,
      pr1645v2TvTmplPerfinMCInUnknownProtos
         Counter64,
      pr1645v2TvTmplPerfinMCInDropEx
         Counter64,
      pr1645v2TvTmplPerfinMCInDropNoMac
         Counter64,
      pr1645v2TvTmplPerfinMCInDropNUCast
         Counter64,
      pr1645v2TvTmplPerfinMCInDropFilter
         Counter64,
      pr1645v2TvTmplPerfinMCInBandwidth15sec
         Integer32,
      pr1645v2TvTmplPerfinMCInBandwidth30sec
         Integer32,
      pr1645v2TvTmplPerfinMCInBandwidth1min
         Integer32,
      pr1645v2TvTmplPerfinMCInBandwidth2min
         Integer32,
      pr1645v2TvTmplPerfinMCInBandwidth5min
         Integer32,
      pr1645v2TvTmplPerfinMCOutOctets
         Counter64,
      pr1645v2TvTmplPerfinMCOutUcastPkts
         Counter64,
      pr1645v2TvTmplPerfinMCOutNUcastPkts
         Counter64,
      pr1645v2TvTmplPerfinMCOutBcastPkts
         Counter64,
      pr1645v2TvTmplPerfinMCOutMcastPkts
         Counter64,
      pr1645v2TvTmplPerfinMCOutDiscards
         Counter64,
      pr1645v2TvTmplPerfinMCOutErrors
         Counter64,
      pr1645v2TvTmplPerfinMCOutQLen
         Counter32,
      pr1645v2TvTmplPerfinMCOutDropEx
         Counter64,
      pr1645v2TvTmplPerfinMCOutDropNoArp
         Counter64,
      pr1645v2TvTmplPerfinMCOutDropFilter
         Counter64,
      pr1645v2TvTmplPerfinMCOutBandwidth15sec
         Integer32,
      pr1645v2TvTmplPerfinMCOutBandwidth30sec
         Integer32,
      pr1645v2TvTmplPerfinMCOutBandwidth1min
         Integer32,
      pr1645v2TvTmplPerfinMCOutBandwidth2min
         Integer32,
      pr1645v2TvTmplPerfinMCOutBandwidth5min
         Integer32
      }

pr1645v2TvTmplPerfinTableIx OBJECT-TYPE
   SYNTAX      TableIndex
   MAX-ACCESS  not-accessible
   STATUS      current
   DESCRIPTION
      ""
   ::= {pr1645v2TvTmplPerfinEntry 11}

pr1645v2TvTmplPerfinName OBJECT-TYPE
   SYNTAX      DisplayString
   MAX-ACCESS  read-only
   STATUS      current
   DESCRIPTION
      "Path: tunnels.performance.ipsecTunnels.name"
   ::= {pr1645v2TvTmplPerfinEntry 16777216}

pr1645v2TvTmplPerfinMCInOctets OBJECT-TYPE
   SYNTAX      Counter64
   MAX-ACCESS  read-only
   STATUS      current
   DESCRIPTION
      "Path: tunnels.performance.ipsecTunnels.mibCounters.ifInOctets

       64 bit unsigned wrappable counter."
   ::= {pr1645v2TvTmplPerfinEntry 40697856}

pr1645v2TvTmplPerfinMCInUcast OBJECT-TYPE
   SYNTAX      Counter64
   MAX-ACCESS  read-only
   STATUS      current
   DESCRIPTION
      "Path: tunnels.performance.ipsecTunnels.mibCounters.ifInUcastPkts

       64 bit unsigned wrappable counter."
   ::= {pr1645v2TvTmplPerfinEntry 40763392}

pr1645v2TvTmplPerfinMCInNUcastPkts OBJECT-TYPE
   SYNTAX      Counter64
   MAX-ACCESS  read-only
   STATUS      current
   DESCRIPTION
      "Path: tunnels.performance.ipsecTunnels.mibCounters.ifInNUcastPkts

       64 bit unsigned wrappable counter."
   ::= {pr1645v2TvTmplPerfinEntry 40828928}

pr1645v2TvTmplPerfinMCInBcastPkts OBJECT-TYPE
   SYNTAX      Counter64
   MAX-ACCESS  read-only
   STATUS      current
   DESCRIPTION
      "Path: tunnels.performance.ipsecTunnels.mibCounters.ifInBcastPkts

       64 bit unsigned wrappable counter."
   ::= {pr1645v2TvTmplPerfinEntry 47382528}

pr1645v2TvTmplPerfinMCInMcastPkts OBJECT-TYPE
   SYNTAX      Counter64
   MAX-ACCESS  read-only
   STATUS      current
   DESCRIPTION
      "Path: tunnels.performance.ipsecTunnels.mibCounters.ifInMcastPkts

       64 bit unsigned wrappable counter."
   ::= {pr1645v2TvTmplPerfinEntry 48037888}

pr1645v2TvTmplPerfinMCInDiscards OBJECT-TYPE
   SYNTAX      Counter64
   MAX-ACCESS  read-only
   STATUS      current
   DESCRIPTION
      "Path: tunnels.performance.ipsecTunnels.mibCounters.ifInDiscards

       64 bit unsigned wrappable counter."
   ::= {pr1645v2TvTmplPerfinEntry 40894464}

pr1645v2TvTmplPerfinMCInErrors OBJECT-TYPE
   SYNTAX      Counter64
   MAX-ACCESS  read-only
   STATUS      current
   DESCRIPTION
      "Path: tunnels.performance.ipsecTunnels.mibCounters.ifInErrors

       64 bit unsigned wrappable counter."
   ::= {pr1645v2TvTmplPerfinEntry 40960000}

pr1645v2TvTmplPerfinMCInUnknownProtos OBJECT-TYPE
   SYNTAX      Counter64
   MAX-ACCESS  read-only
   STATUS      current
   DESCRIPTION
      "Path: tunnels.performance.ipsecTunnels.mibCounters.ifInUnknownProtos

       64 bit unsigned wrappable counter."
   ::= {pr1645v2TvTmplPerfinEntry 41025536}

pr1645v2TvTmplPerfinMCInDropEx OBJECT-TYPE
   SYNTAX      Counter64
   MAX-ACCESS  read-only
   STATUS      current
   DESCRIPTION
      "Path: tunnels.performance.ipsecTunnels.mibCounters.ifInDropLevelExceeded

       64 bit unsigned wrappable counter."
   ::= {pr1645v2TvTmplPerfinEntry 42074112}

pr1645v2TvTmplPerfinMCInDropNoMac OBJECT-TYPE
   SYNTAX      Counter64
   MAX-ACCESS  read-only
   STATUS      current
   DESCRIPTION
      "Path: tunnels.performance.ipsecTunnels.mibCounters.ifInDiscardsNoMacFit

       64 bit unsigned wrappable counter."
   ::= {pr1645v2TvTmplPerfinEntry 42270720}

pr1645v2TvTmplPerfinMCInDropNUCast OBJECT-TYPE
   SYNTAX      Counter64
   MAX-ACCESS  read-only
   STATUS      current
   DESCRIPTION
      "Path: tunnels.performance.ipsecTunnels.mibCounters.ifInDiscardsNUCast

       64 bit unsigned wrappable counter."
   ::= {pr1645v2TvTmplPerfinEntry 42467328}

pr1645v2TvTmplPerfinMCInDropFilter OBJECT-TYPE
   SYNTAX      Counter64
   MAX-ACCESS  read-only
   STATUS      current
   DESCRIPTION
      "Path: tunnels.performance.ipsecTunnels.mibCounters.ifInDiscardsFilter

       64 bit unsigned wrappable counter."
   ::= {pr1645v2TvTmplPerfinEntry 42532864}

pr1645v2TvTmplPerfinMCInBandwidth15sec OBJECT-TYPE
   SYNTAX      Integer32
   MAX-ACCESS  read-only
   STATUS      current
   DESCRIPTION
      "Path: tunnels.performance.ipsecTunnels.mibCounters.ifInBandwidth.15sec

       unit name = bps
       formula = 8 * ; 8 /"
   ::= {pr1645v2TvTmplPerfinEntry 45417728}

pr1645v2TvTmplPerfinMCInBandwidth30sec OBJECT-TYPE
   SYNTAX      Integer32
   MAX-ACCESS  read-only
   STATUS      current
   DESCRIPTION
      "Path: tunnels.performance.ipsecTunnels.mibCounters.ifInBandwidth.30sec

       unit name = bps
       formula = 8 * ; 8 /"
   ::= {pr1645v2TvTmplPerfinEntry 45419008}

pr1645v2TvTmplPerfinMCInBandwidth1min OBJECT-TYPE
   SYNTAX      Integer32
   MAX-ACCESS  read-only
   STATUS      current
   DESCRIPTION
      "Path: tunnels.performance.ipsecTunnels.mibCounters.ifInBandwidth.1min

       unit name = bps
       formula = 8 * ; 8 /"
   ::= {pr1645v2TvTmplPerfinEntry 45421568}

pr1645v2TvTmplPerfinMCInBandwidth2min OBJECT-TYPE
   SYNTAX      Integer32
   MAX-ACCESS  read-only
   STATUS      current
   DESCRIPTION
      "Path: tunnels.performance.ipsecTunnels.mibCounters.ifInBandwidth.2min

       unit name = bps
       formula = 8 * ; 8 /"
   ::= {pr1645v2TvTmplPerfinEntry 45426688}

pr1645v2TvTmplPerfinMCInBandwidth5min OBJECT-TYPE
   SYNTAX      Integer32
   MAX-ACCESS  read-only
   STATUS      current
   DESCRIPTION
      "Path: tunnels.performance.ipsecTunnels.mibCounters.ifInBandwidth.5min

       unit name = bps
       formula = 8 * ; 8 /"
   ::= {pr1645v2TvTmplPerfinEntry 45442048}

pr1645v2TvTmplPerfinMCOutOctets OBJECT-TYPE
   SYNTAX      Counter64
   MAX-ACCESS  read-only
   STATUS      current
   DESCRIPTION
      "Path: tunnels.performance.ipsecTunnels.mibCounters.ifOutOctets

       64 bit unsigned wrappable counter."
   ::= {pr1645v2TvTmplPerfinEntry 41091072}

pr1645v2TvTmplPerfinMCOutUcastPkts OBJECT-TYPE
   SYNTAX      Counter64
   MAX-ACCESS  read-only
   STATUS      current
   DESCRIPTION
      "Path: tunnels.performance.ipsecTunnels.mibCounters.ifOutUcastPkts

       64 bit unsigned wrappable counter."
   ::= {pr1645v2TvTmplPerfinEntry 41156608}

pr1645v2TvTmplPerfinMCOutNUcastPkts OBJECT-TYPE
   SYNTAX      Counter64
   MAX-ACCESS  read-only
   STATUS      current
   DESCRIPTION
      "Path: tunnels.performance.ipsecTunnels.mibCounters.ifOutNUcastPkts

       64 bit unsigned wrappable counter."
   ::= {pr1645v2TvTmplPerfinEntry 41222144}

pr1645v2TvTmplPerfinMCOutBcastPkts OBJECT-TYPE
   SYNTAX      Counter64
   MAX-ACCESS  read-only
   STATUS      current
   DESCRIPTION
      "Path: tunnels.performance.ipsecTunnels.mibCounters.ifOutBcastPkts

       64 bit unsigned wrappable counter."
   ::= {pr1645v2TvTmplPerfinEntry 47775744}

pr1645v2TvTmplPerfinMCOutMcastPkts OBJECT-TYPE
   SYNTAX      Counter64
   MAX-ACCESS  read-only
   STATUS      current
   DESCRIPTION
      "Path: tunnels.performance.ipsecTunnels.mibCounters.ifOutMcastPkts

       64 bit unsigned wrappable counter."
   ::= {pr1645v2TvTmplPerfinEntry 48431104}

pr1645v2TvTmplPerfinMCOutDiscards OBJECT-TYPE
   SYNTAX      Counter64
   MAX-ACCESS  read-only
   STATUS      current
   DESCRIPTION
      "Path: tunnels.performance.ipsecTunnels.mibCounters.ifOutDiscards

       64 bit unsigned wrappable counter."
   ::= {pr1645v2TvTmplPerfinEntry 41287680}

pr1645v2TvTmplPerfinMCOutErrors OBJECT-TYPE
   SYNTAX      Counter64
   MAX-ACCESS  read-only
   STATUS      current
   DESCRIPTION
      "Path: tunnels.performance.ipsecTunnels.mibCounters.ifOutErrors

       64 bit unsigned wrappable counter."
   ::= {pr1645v2TvTmplPerfinEntry 41353216}

pr1645v2TvTmplPerfinMCOutQLen OBJECT-TYPE
   SYNTAX      Counter32
   MAX-ACCESS  read-only
   STATUS      current
   DESCRIPTION
      "Path: tunnels.performance.ipsecTunnels.mibCounters.ifOutQLen

       32 bit unsigned wrappable counter."
   ::= {pr1645v2TvTmplPerfinEntry 41418752}

pr1645v2TvTmplPerfinMCOutDropEx OBJECT-TYPE
   SYNTAX      Counter64
   MAX-ACCESS  read-only
   STATUS      current
   DESCRIPTION
      "Path: tunnels.performance.ipsecTunnels.mibCounters.ifOutDropLevelExceeded

       64 bit unsigned wrappable counter."
   ::= {pr1645v2TvTmplPerfinEntry 41484288}

pr1645v2TvTmplPerfinMCOutDropNoArp OBJECT-TYPE
   SYNTAX      Counter64
   MAX-ACCESS  read-only
   STATUS      current
   DESCRIPTION
      "Path: tunnels.performance.ipsecTunnels.mibCounters.ifOutDiscardsNoArp

       64 bit unsigned wrappable counter."
   ::= {pr1645v2TvTmplPerfinEntry 42336256}

pr1645v2TvTmplPerfinMCOutDropFilter OBJECT-TYPE
   SYNTAX      Counter64
   MAX-ACCESS  read-only
   STATUS      current
   DESCRIPTION
      "Path: tunnels.performance.ipsecTunnels.mibCounters.ifOutDiscardsFilter

       64 bit unsigned wrappable counter."
   ::= {pr1645v2TvTmplPerfinEntry 42598400}

pr1645v2TvTmplPerfinMCOutBandwidth15sec OBJECT-TYPE
   SYNTAX      Integer32
   MAX-ACCESS  read-only
   STATUS      current
   DESCRIPTION
      "Path: tunnels.performance.ipsecTunnels.mibCounters.ifOutBandwidth.15sec

       unit name = bps
       formula = 8 * ; 8 /"
   ::= {pr1645v2TvTmplPerfinEntry 45483264}

pr1645v2TvTmplPerfinMCOutBandwidth30sec OBJECT-TYPE
   SYNTAX      Integer32
   MAX-ACCESS  read-only
   STATUS      current
   DESCRIPTION
      "Path: tunnels.performance.ipsecTunnels.mibCounters.ifOutBandwidth.30sec

       unit name = bps
       formula = 8 * ; 8 /"
   ::= {pr1645v2TvTmplPerfinEntry 45484544}

pr1645v2TvTmplPerfinMCOutBandwidth1min OBJECT-TYPE
   SYNTAX      Integer32
   MAX-ACCESS  read-only
   STATUS      current
   DESCRIPTION
      "Path: tunnels.performance.ipsecTunnels.mibCounters.ifOutBandwidth.1min

       unit name = bps
       formula = 8 * ; 8 /"
   ::= {pr1645v2TvTmplPerfinEntry 45487104}

pr1645v2TvTmplPerfinMCOutBandwidth2min OBJECT-TYPE
   SYNTAX      Integer32
   MAX-ACCESS  read-only
   STATUS      current
   DESCRIPTION
      "Path: tunnels.performance.ipsecTunnels.mibCounters.ifOutBandwidth.2min

       unit name = bps
       formula = 8 * ; 8 /"
   ::= {pr1645v2TvTmplPerfinEntry 45492224}

pr1645v2TvTmplPerfinMCOutBandwidth5min OBJECT-TYPE
   SYNTAX      Integer32
   MAX-ACCESS  read-only
   STATUS      current
   DESCRIPTION
      "Path: tunnels.performance.ipsecTunnels.mibCounters.ifOutBandwidth.5min

       unit name = bps
       formula = 8 * ; 8 /"
   ::= {pr1645v2TvTmplPerfinEntry 45507584}

pr1645v2TvTmplPerfinMCH2P OBJECT-TYPE
   SYNTAX      SEQUENCE OF Pr1645v2TvTmplPerfinMCH2PEntry
   MAX-ACCESS  not-accessible
   STATUS      current
   DESCRIPTION
      ""
   ::= {pr1645v2TvTmplPerfin 41549824}

pr1645v2TvTmplPerfinMCH2PEntry OBJECT-TYPE
   SYNTAX      Pr1645v2TvTmplPerfinMCH2PEntry
   MAX-ACCESS  not-accessible
   STATUS      current
   DESCRIPTION
      ""
   INDEX      { pr1645v2TvTmplPerfinTableIx,
                pr1645v2TvTmplPerfinMCH2PTableIx }
   ::= {pr1645v2TvTmplPerfinMCH2P 1}

Pr1645v2TvTmplPerfinMCH2PEntry ::=
   SEQUENCE
      {
      pr1645v2TvTmplPerfinMCH2PTableIx
         TableIndex,
      pr1645v2TvTmplPerfinMCH2PSysUpTime
         TimeTicks,
      pr1645v2TvTmplPerfinMCH2PIfUpTime
         TimeTicks,
      pr1645v2TvTmplPerfinMCH2PIfStatChanges
         Counter32,
      pr1645v2TvTmplPerfinMCH2PIfInOctets
         Counter64,
      pr1645v2TvTmplPerfinMCH2PIfInUCPkts
         Counter64,
      pr1645v2TvTmplPerfinMCH2PIfInNUCPkts
         Counter64,
      pr1645v2TvTmplPerfinMCH2PIfInBCPkts
         Counter64,
      pr1645v2TvTmplPerfinMCH2PIfInMCPkts
         Counter64,
      pr1645v2TvTmplPerfinMCH2PIfInDiscards
         Counter64,
      pr1645v2TvTmplPerfinMCH2PIfInErrors
         Counter64,
      pr1645v2TvTmplPerfinMCH2PIfInUnkwn
         Counter64,
      pr1645v2TvTmplPerfinMCH2PInDropEx
         Counter64,
      pr1645v2TvTmplPerfinMCH2PInDropNoMac
         Counter64,
      pr1645v2TvTmplPerfinMCH2PInDropNUCast
         Counter64,
      pr1645v2TvTmplPerfinMCH2PInDropFilter
         Counter64,
      pr1645v2TvTmplPerfinMCH2PIfInBandwidth
         Integer32,
      pr1645v2TvTmplPerfinMCH2PIfOutOctets
         Counter64,
      pr1645v2TvTmplPerfinMCH2PIfOutUCPkts
         Counter64,
      pr1645v2TvTmplPerfinMCH2PIfOutNUCPkts
         Counter64,
      pr1645v2TvTmplPerfinMCH2PIfOutBCPkts
         Counter64,
      pr1645v2TvTmplPerfinMCH2PIfOutMCPkts
         Counter64,
      pr1645v2TvTmplPerfinMCH2PIfOutDiscards
         Counter64,
      pr1645v2TvTmplPerfinMCH2PIfOutErrors
         Counter64,
      pr1645v2TvTmplPerfinMCH2POutDropEx
         Counter64,
      pr1645v2TvTmplPerfinMCH2POutDropNoArp
         Counter64,
      pr1645v2TvTmplPerfinMCH2POutDropFilter
         Counter64,
      pr1645v2TvTmplPerfinMCH2PIfOutBandwidth
         Integer32,
      pr1645v2TvTmplPerfinMCH2PIfErrSec
         Counter32
      }

pr1645v2TvTmplPerfinMCH2PTableIx OBJECT-TYPE
   SYNTAX      TableIndex
   MAX-ACCESS  not-accessible
   STATUS      current
   DESCRIPTION
      ""
   ::= {pr1645v2TvTmplPerfinMCH2PEntry 11}

pr1645v2TvTmplPerfinMCH2PSysUpTime OBJECT-TYPE
   SYNTAX      TimeTicks
   MAX-ACCESS  read-only
   STATUS      current
   DESCRIPTION
      "Path: tunnels.performance.ipsecTunnels.mibCounters.h2Performance.sysUpTime

       Time in centi-second."
   ::= {pr1645v2TvTmplPerfinMCH2PEntry 16777216}

pr1645v2TvTmplPerfinMCH2PIfUpTime OBJECT-TYPE
   SYNTAX      TimeTicks
   MAX-ACCESS  read-only
   STATUS      current
   DESCRIPTION
      "Path: tunnels.performance.ipsecTunnels.mibCounters.h2Performance.ifUpTime

       Time in centi-second."
   ::= {pr1645v2TvTmplPerfinMCH2PEntry 33554432}

pr1645v2TvTmplPerfinMCH2PIfStatChanges OBJECT-TYPE
   SYNTAX      Counter32
   MAX-ACCESS  read-only
   STATUS      current
   DESCRIPTION
      "Path: tunnels.performance.ipsecTunnels.mibCounters.h2Performance.ifStatusChanges

       32 bit unsigned wrappable counter."
   ::= {pr1645v2TvTmplPerfinMCH2PEntry 50331648}

pr1645v2TvTmplPerfinMCH2PIfInOctets OBJECT-TYPE
   SYNTAX      Counter64
   MAX-ACCESS  read-only
   STATUS      current
   DESCRIPTION
      "Path: tunnels.performance.ipsecTunnels.mibCounters.h2Performance.ifInOctets

       64 bit unsigned wrappable counter."
   ::= {pr1645v2TvTmplPerfinMCH2PEntry 67108864}

pr1645v2TvTmplPerfinMCH2PIfInUCPkts OBJECT-TYPE
   SYNTAX      Counter64
   MAX-ACCESS  read-only
   STATUS      current
   DESCRIPTION
      "Path: tunnels.performance.ipsecTunnels.mibCounters.h2Performance.ifInUcastPkts

       64 bit unsigned wrappable counter."
   ::= {pr1645v2TvTmplPerfinMCH2PEntry 83886080}

pr1645v2TvTmplPerfinMCH2PIfInNUCPkts OBJECT-TYPE
   SYNTAX      Counter64
   MAX-ACCESS  read-only
   STATUS      current
   DESCRIPTION
      "Path: tunnels.performance.ipsecTunnels.mibCounters.h2Performance.ifInNUcastPkts

       64 bit unsigned wrappable counter."
   ::= {pr1645v2TvTmplPerfinMCH2PEntry 100663296}

pr1645v2TvTmplPerfinMCH2PIfInBCPkts OBJECT-TYPE
   SYNTAX      Counter64
   MAX-ACCESS  read-only
   STATUS      current
   DESCRIPTION
      "Path: tunnels.performance.ipsecTunnels.mibCounters.h2Performance.ifInBcastPkts

       64 bit unsigned wrappable counter."
   ::= {pr1645v2TvTmplPerfinMCH2PEntry 419430400}

pr1645v2TvTmplPerfinMCH2PIfInMCPkts OBJECT-TYPE
   SYNTAX      Counter64
   MAX-ACCESS  read-only
   STATUS      current
   DESCRIPTION
      "Path: tunnels.performance.ipsecTunnels.mibCounters.h2Performance.ifInMcastPkts

       64 bit unsigned wrappable counter."
   ::= {pr1645v2TvTmplPerfinMCH2PEntry 436207616}

pr1645v2TvTmplPerfinMCH2PIfInDiscards OBJECT-TYPE
   SYNTAX      Counter64
   MAX-ACCESS  read-only
   STATUS      current
   DESCRIPTION
      "Path: tunnels.performance.ipsecTunnels.mibCounters.h2Performance.ifInDiscards

       64 bit unsigned wrappable counter."
   ::= {pr1645v2TvTmplPerfinMCH2PEntry 117440512}

pr1645v2TvTmplPerfinMCH2PIfInErrors OBJECT-TYPE
   SYNTAX      Counter64
   MAX-ACCESS  read-only
   STATUS      current
   DESCRIPTION
      "Path: tunnels.performance.ipsecTunnels.mibCounters.h2Performance.ifInErrors

       64 bit unsigned wrappable counter."
   ::= {pr1645v2TvTmplPerfinMCH2PEntry 134217728}

pr1645v2TvTmplPerfinMCH2PIfInUnkwn OBJECT-TYPE
   SYNTAX      Counter64
   MAX-ACCESS  read-only
   STATUS      current
   DESCRIPTION
      "Path: tunnels.performance.ipsecTunnels.mibCounters.h2Performance.ifInUnknownProtos

       64 bit unsigned wrappable counter."
   ::= {pr1645v2TvTmplPerfinMCH2PEntry 150994944}

pr1645v2TvTmplPerfinMCH2PInDropEx OBJECT-TYPE
   SYNTAX      Counter64
   MAX-ACCESS  read-only
   STATUS      current
   DESCRIPTION
      "Path: tunnels.performance.ipsecTunnels.mibCounters.h2Performance.ifInDropLevelExceeded

       64 bit unsigned wrappable counter."
   ::= {pr1645v2TvTmplPerfinMCH2PEntry 335544320}

pr1645v2TvTmplPerfinMCH2PInDropNoMac OBJECT-TYPE
   SYNTAX      Counter64
   MAX-ACCESS  read-only
   STATUS      current
   DESCRIPTION
      "Path: tunnels.performance.ipsecTunnels.mibCounters.h2Performance.fInDiscardsNoMacFit

       64 bit unsigned wrappable counter."
   ::= {pr1645v2TvTmplPerfinMCH2PEntry 301989888}

pr1645v2TvTmplPerfinMCH2PInDropNUCast OBJECT-TYPE
   SYNTAX      Counter64
   MAX-ACCESS  read-only
   STATUS      current
   DESCRIPTION
      "Path: tunnels.performance.ipsecTunnels.mibCounters.h2Performance.fInDiscardsNUCast

       64 bit unsigned wrappable counter."
   ::= {pr1645v2TvTmplPerfinMCH2PEntry 318767104}

pr1645v2TvTmplPerfinMCH2PInDropFilter OBJECT-TYPE
   SYNTAX      Counter64
   MAX-ACCESS  read-only
   STATUS      current
   DESCRIPTION
      "Path: tunnels.performance.ipsecTunnels.mibCounters.h2Performance.fInDiscardsFilter

       64 bit unsigned wrappable counter."
   ::= {pr1645v2TvTmplPerfinMCH2PEntry 385875968}

pr1645v2TvTmplPerfinMCH2PIfInBandwidth OBJECT-TYPE
   SYNTAX      Integer32
   MAX-ACCESS  read-only
   STATUS      current
   DESCRIPTION
      "Path: tunnels.performance.ipsecTunnels.mibCounters.h2Performance.ifInBandwidth

       unit name = bps
       formula = 8 * ; 8 /"
   ::= {pr1645v2TvTmplPerfinMCH2PEntry 268435456}

pr1645v2TvTmplPerfinMCH2PIfOutOctets OBJECT-TYPE
   SYNTAX      Counter64
   MAX-ACCESS  read-only
   STATUS      current
   DESCRIPTION
      "Path: tunnels.performance.ipsecTunnels.mibCounters.h2Performance.ifOutOctets

       64 bit unsigned wrappable counter."
   ::= {pr1645v2TvTmplPerfinMCH2PEntry 167772160}

pr1645v2TvTmplPerfinMCH2PIfOutUCPkts OBJECT-TYPE
   SYNTAX      Counter64
   MAX-ACCESS  read-only
   STATUS      current
   DESCRIPTION
      "Path: tunnels.performance.ipsecTunnels.mibCounters.h2Performance.ifOutUcastPkts

       64 bit unsigned wrappable counter."
   ::= {pr1645v2TvTmplPerfinMCH2PEntry 184549376}

pr1645v2TvTmplPerfinMCH2PIfOutNUCPkts OBJECT-TYPE
   SYNTAX      Counter64
   MAX-ACCESS  read-only
   STATUS      current
   DESCRIPTION
      "Path: tunnels.performance.ipsecTunnels.mibCounters.h2Performance.ifOutNUcastPkts

       64 bit unsigned wrappable counter."
   ::= {pr1645v2TvTmplPerfinMCH2PEntry 201326592}

pr1645v2TvTmplPerfinMCH2PIfOutBCPkts OBJECT-TYPE
   SYNTAX      Counter64
   MAX-ACCESS  read-only
   STATUS      current
   DESCRIPTION
      "Path: tunnels.performance.ipsecTunnels.mibCounters.h2Performance.ifOutBcastPkts

       64 bit unsigned wrappable counter."
   ::= {pr1645v2TvTmplPerfinMCH2PEntry 452984832}

pr1645v2TvTmplPerfinMCH2PIfOutMCPkts OBJECT-TYPE
   SYNTAX      Counter64
   MAX-ACCESS  read-only
   STATUS      current
   DESCRIPTION
      "Path: tunnels.performance.ipsecTunnels.mibCounters.h2Performance.ifOutMcastPkts

       64 bit unsigned wrappable counter."
   ::= {pr1645v2TvTmplPerfinMCH2PEntry 469762048}

pr1645v2TvTmplPerfinMCH2PIfOutDiscards OBJECT-TYPE
   SYNTAX      Counter64
   MAX-ACCESS  read-only
   STATUS      current
   DESCRIPTION
      "Path: tunnels.performance.ipsecTunnels.mibCounters.h2Performance.ifOutDiscards

       64 bit unsigned wrappable counter."
   ::= {pr1645v2TvTmplPerfinMCH2PEntry 218103808}

pr1645v2TvTmplPerfinMCH2PIfOutErrors OBJECT-TYPE
   SYNTAX      Counter64
   MAX-ACCESS  read-only
   STATUS      current
   DESCRIPTION
      "Path: tunnels.performance.ipsecTunnels.mibCounters.h2Performance.ifOutErrors

       64 bit unsigned wrappable counter."
   ::= {pr1645v2TvTmplPerfinMCH2PEntry 234881024}

pr1645v2TvTmplPerfinMCH2POutDropEx OBJECT-TYPE
   SYNTAX      Counter64
   MAX-ACCESS  read-only
   STATUS      current
   DESCRIPTION
      "Path: tunnels.performance.ipsecTunnels.mibCounters.h2Performance.ifOutDropLevelExceeded

       64 bit unsigned wrappable counter."
   ::= {pr1645v2TvTmplPerfinMCH2PEntry 352321536}

pr1645v2TvTmplPerfinMCH2POutDropNoArp OBJECT-TYPE
   SYNTAX      Counter64
   MAX-ACCESS  read-only
   STATUS      current
   DESCRIPTION
      "Path: tunnels.performance.ipsecTunnels.mibCounters.h2Performance.ifOutDiscardsNoArp

       64 bit unsigned wrappable counter."
   ::= {pr1645v2TvTmplPerfinMCH2PEntry 369098752}

pr1645v2TvTmplPerfinMCH2POutDropFilter OBJECT-TYPE
   SYNTAX      Counter64
   MAX-ACCESS  read-only
   STATUS      current
   DESCRIPTION
      "Path: tunnels.performance.ipsecTunnels.mibCounters.h2Performance.ifOutDiscardsFilter

       64 bit unsigned wrappable counter."
   ::= {pr1645v2TvTmplPerfinMCH2PEntry 402653184}

pr1645v2TvTmplPerfinMCH2PIfOutBandwidth OBJECT-TYPE
   SYNTAX      Integer32
   MAX-ACCESS  read-only
   STATUS      current
   DESCRIPTION
      "Path: tunnels.performance.ipsecTunnels.mibCounters.h2Performance.ifOutBandwidth

       unit name = bps
       formula = 8 * ; 8 /"
   ::= {pr1645v2TvTmplPerfinMCH2PEntry 285212672}

pr1645v2TvTmplPerfinMCH2PIfErrSec OBJECT-TYPE
   SYNTAX      Counter32
   MAX-ACCESS  read-only
   STATUS      current
   DESCRIPTION
      "Path: tunnels.performance.ipsecTunnels.mibCounters.h2Performance.ifErrSec

       32 bit unsigned wrappable counter."
   ::= {pr1645v2TvTmplPerfinMCH2PEntry 251658240}

pr1645v2TvTmplPerfinMCH24P OBJECT-TYPE
   SYNTAX      SEQUENCE OF Pr1645v2TvTmplPerfinMCH24PEntry
   MAX-ACCESS  not-accessible
   STATUS      current
   DESCRIPTION
      ""
   ::= {pr1645v2TvTmplPerfin 41615360}

pr1645v2TvTmplPerfinMCH24PEntry OBJECT-TYPE
   SYNTAX      Pr1645v2TvTmplPerfinMCH24PEntry
   MAX-ACCESS  not-accessible
   STATUS      current
   DESCRIPTION
      ""
   INDEX      { pr1645v2TvTmplPerfinTableIx,
                pr1645v2TvTmplPerfinMCH24PTableIx }
   ::= {pr1645v2TvTmplPerfinMCH24P 1}

Pr1645v2TvTmplPerfinMCH24PEntry ::=
   SEQUENCE
      {
      pr1645v2TvTmplPerfinMCH24PTableIx
         TableIndex,
      pr1645v2TvTmplPerfinMCH24PSysUpTime
         TimeTicks,
      pr1645v2TvTmplPerfinMCH24PIfUpTime
         TimeTicks,
      pr1645v2TvTmplPerfinMCH24PIfStatChanges
         Counter32,
      pr1645v2TvTmplPerfinMCH24PIfInOctets
         Counter64,
      pr1645v2TvTmplPerfinMCH24PIfInUCPkts
         Counter64,
      pr1645v2TvTmplPerfinMCH24PIfInNUCPkts
         Counter64,
      pr1645v2TvTmplPerfinMCH24PIfInBCPkts
         Counter64,
      pr1645v2TvTmplPerfinMCH24PIfInMCPkts
         Counter64,
      pr1645v2TvTmplPerfinMCH24PIfInDiscards
         Counter64,
      pr1645v2TvTmplPerfinMCH24PIfInErrors
         Counter64,
      pr1645v2TvTmplPerfinMCH24PIfInUnkwn
         Counter64,
      pr1645v2TvTmplPerfinMCH24PInDropEx
         Counter64,
      pr1645v2TvTmplPerfinMCH24PInDropNoMac
         Counter64,
      pr1645v2TvTmplPerfinMCH24PInDropNUCast
         Counter64,
      pr1645v2TvTmplPerfinMCH24PInDropFilter
         Counter64,
      pr1645v2TvTmplPerfinMCH24PIfInBandwidth
         Integer32,
      pr1645v2TvTmplPerfinMCH24PIfOutOctets
         Counter64,
      pr1645v2TvTmplPerfinMCH24PIfOutUCPkts
         Counter64,
      pr1645v2TvTmplPerfinMCH24PIfOutNUCPkts
         Counter64,
      pr1645v2TvTmplPerfinMCH24PIfOutBCPkts
         Counter64,
      pr1645v2TvTmplPerfinMCH24PIfOutMCPkts
         Counter64,
      pr1645v2TvTmplPerfinMCH24PIfOutDiscards
         Counter64,
      pr1645v2TvTmplPerfinMCH24PIfOutErrors
         Counter64,
      pr1645v2TvTmplPerfinMCH24POutDropEx
         Counter64,
      pr1645v2TvTmplPerfinMCH24POutDropNoArp
         Counter64,
      pr1645v2TvTmplPerfinMCH24POutDropFilter
         Counter64,
      pr1645v2TvTmplPerfinMCH24PIfOutBandwidth
         Integer32,
      pr1645v2TvTmplPerfinMCH24PIfErrSec
         Counter32
      }

pr1645v2TvTmplPerfinMCH24PTableIx OBJECT-TYPE
   SYNTAX      TableIndex
   MAX-ACCESS  not-accessible
   STATUS      current
   DESCRIPTION
      ""
   ::= {pr1645v2TvTmplPerfinMCH24PEntry 11}

pr1645v2TvTmplPerfinMCH24PSysUpTime OBJECT-TYPE
   SYNTAX      TimeTicks
   MAX-ACCESS  read-only
   STATUS      current
   DESCRIPTION
      "Path: tunnels.performance.ipsecTunnels.mibCounters.h24Performance.sysUpTime

       Time in centi-second."
   ::= {pr1645v2TvTmplPerfinMCH24PEntry 16777216}

pr1645v2TvTmplPerfinMCH24PIfUpTime OBJECT-TYPE
   SYNTAX      TimeTicks
   MAX-ACCESS  read-only
   STATUS      current
   DESCRIPTION
      "Path: tunnels.performance.ipsecTunnels.mibCounters.h24Performance.ifUpTime

       Time in centi-second."
   ::= {pr1645v2TvTmplPerfinMCH24PEntry 33554432}

pr1645v2TvTmplPerfinMCH24PIfStatChanges OBJECT-TYPE
   SYNTAX      Counter32
   MAX-ACCESS  read-only
   STATUS      current
   DESCRIPTION
      "Path: tunnels.performance.ipsecTunnels.mibCounters.h24Performance.ifStatusChanges

       32 bit unsigned wrappable counter."
   ::= {pr1645v2TvTmplPerfinMCH24PEntry 50331648}

pr1645v2TvTmplPerfinMCH24PIfInOctets OBJECT-TYPE
   SYNTAX      Counter64
   MAX-ACCESS  read-only
   STATUS      current
   DESCRIPTION
      "Path: tunnels.performance.ipsecTunnels.mibCounters.h24Performance.ifInOctets

       64 bit unsigned wrappable counter."
   ::= {pr1645v2TvTmplPerfinMCH24PEntry 67108864}

pr1645v2TvTmplPerfinMCH24PIfInUCPkts OBJECT-TYPE
   SYNTAX      Counter64
   MAX-ACCESS  read-only
   STATUS      current
   DESCRIPTION
      "Path: tunnels.performance.ipsecTunnels.mibCounters.h24Performance.ifInUcastPkts

       64 bit unsigned wrappable counter."
   ::= {pr1645v2TvTmplPerfinMCH24PEntry 83886080}

pr1645v2TvTmplPerfinMCH24PIfInNUCPkts OBJECT-TYPE
   SYNTAX      Counter64
   MAX-ACCESS  read-only
   STATUS      current
   DESCRIPTION
      "Path: tunnels.performance.ipsecTunnels.mibCounters.h24Performance.ifInNUcastPkts

       64 bit unsigned wrappable counter."
   ::= {pr1645v2TvTmplPerfinMCH24PEntry 100663296}

pr1645v2TvTmplPerfinMCH24PIfInBCPkts OBJECT-TYPE
   SYNTAX      Counter64
   MAX-ACCESS  read-only
   STATUS      current
   DESCRIPTION
      "Path: tunnels.performance.ipsecTunnels.mibCounters.h24Performance.ifInBcastPkts

       64 bit unsigned wrappable counter."
   ::= {pr1645v2TvTmplPerfinMCH24PEntry 419430400}

pr1645v2TvTmplPerfinMCH24PIfInMCPkts OBJECT-TYPE
   SYNTAX      Counter64
   MAX-ACCESS  read-only
   STATUS      current
   DESCRIPTION
      "Path: tunnels.performance.ipsecTunnels.mibCounters.h24Performance.ifInMcastPkts

       64 bit unsigned wrappable counter."
   ::= {pr1645v2TvTmplPerfinMCH24PEntry 436207616}

pr1645v2TvTmplPerfinMCH24PIfInDiscards OBJECT-TYPE
   SYNTAX      Counter64
   MAX-ACCESS  read-only
   STATUS      current
   DESCRIPTION
      "Path: tunnels.performance.ipsecTunnels.mibCounters.h24Performance.ifInDiscards

       64 bit unsigned wrappable counter."
   ::= {pr1645v2TvTmplPerfinMCH24PEntry 117440512}

pr1645v2TvTmplPerfinMCH24PIfInErrors OBJECT-TYPE
   SYNTAX      Counter64
   MAX-ACCESS  read-only
   STATUS      current
   DESCRIPTION
      "Path: tunnels.performance.ipsecTunnels.mibCounters.h24Performance.ifInErrors

       64 bit unsigned wrappable counter."
   ::= {pr1645v2TvTmplPerfinMCH24PEntry 134217728}

pr1645v2TvTmplPerfinMCH24PIfInUnkwn OBJECT-TYPE
   SYNTAX      Counter64
   MAX-ACCESS  read-only
   STATUS      current
   DESCRIPTION
      "Path: tunnels.performance.ipsecTunnels.mibCounters.h24Performance.ifInUnknownProtos

       64 bit unsigned wrappable counter."
   ::= {pr1645v2TvTmplPerfinMCH24PEntry 150994944}

pr1645v2TvTmplPerfinMCH24PInDropEx OBJECT-TYPE
   SYNTAX      Counter64
   MAX-ACCESS  read-only
   STATUS      current
   DESCRIPTION
      "Path: tunnels.performance.ipsecTunnels.mibCounters.h24Performance.ifInDropLevelExceeded

       64 bit unsigned wrappable counter."
   ::= {pr1645v2TvTmplPerfinMCH24PEntry 335544320}

pr1645v2TvTmplPerfinMCH24PInDropNoMac OBJECT-TYPE
   SYNTAX      Counter64
   MAX-ACCESS  read-only
   STATUS      current
   DESCRIPTION
      "Path: tunnels.performance.ipsecTunnels.mibCounters.h24Performance.fInDiscardsNoMacFit

       64 bit unsigned wrappable counter."
   ::= {pr1645v2TvTmplPerfinMCH24PEntry 301989888}

pr1645v2TvTmplPerfinMCH24PInDropNUCast OBJECT-TYPE
   SYNTAX      Counter64
   MAX-ACCESS  read-only
   STATUS      current
   DESCRIPTION
      "Path: tunnels.performance.ipsecTunnels.mibCounters.h24Performance.fInDiscardsNUCast

       64 bit unsigned wrappable counter."
   ::= {pr1645v2TvTmplPerfinMCH24PEntry 318767104}

pr1645v2TvTmplPerfinMCH24PInDropFilter OBJECT-TYPE
   SYNTAX      Counter64
   MAX-ACCESS  read-only
   STATUS      current
   DESCRIPTION
      "Path: tunnels.performance.ipsecTunnels.mibCounters.h24Performance.fInDiscardsFilter

       64 bit unsigned wrappable counter."
   ::= {pr1645v2TvTmplPerfinMCH24PEntry 385875968}

pr1645v2TvTmplPerfinMCH24PIfInBandwidth OBJECT-TYPE
   SYNTAX      Integer32
   MAX-ACCESS  read-only
   STATUS      current
   DESCRIPTION
      "Path: tunnels.performance.ipsecTunnels.mibCounters.h24Performance.ifInBandwidth

       unit name = bps
       formula = 8 * ; 8 /"
   ::= {pr1645v2TvTmplPerfinMCH24PEntry 268435456}

pr1645v2TvTmplPerfinMCH24PIfOutOctets OBJECT-TYPE
   SYNTAX      Counter64
   MAX-ACCESS  read-only
   STATUS      current
   DESCRIPTION
      "Path: tunnels.performance.ipsecTunnels.mibCounters.h24Performance.ifOutOctets

       64 bit unsigned wrappable counter."
   ::= {pr1645v2TvTmplPerfinMCH24PEntry 167772160}

pr1645v2TvTmplPerfinMCH24PIfOutUCPkts OBJECT-TYPE
   SYNTAX      Counter64
   MAX-ACCESS  read-only
   STATUS      current
   DESCRIPTION
      "Path: tunnels.performance.ipsecTunnels.mibCounters.h24Performance.ifOutUcastPkts

       64 bit unsigned wrappable counter."
   ::= {pr1645v2TvTmplPerfinMCH24PEntry 184549376}

pr1645v2TvTmplPerfinMCH24PIfOutNUCPkts OBJECT-TYPE
   SYNTAX      Counter64
   MAX-ACCESS  read-only
   STATUS      current
   DESCRIPTION
      "Path: tunnels.performance.ipsecTunnels.mibCounters.h24Performance.ifOutNUcastPkts

       64 bit unsigned wrappable counter."
   ::= {pr1645v2TvTmplPerfinMCH24PEntry 201326592}

pr1645v2TvTmplPerfinMCH24PIfOutBCPkts OBJECT-TYPE
   SYNTAX      Counter64
   MAX-ACCESS  read-only
   STATUS      current
   DESCRIPTION
      "Path: tunnels.performance.ipsecTunnels.mibCounters.h24Performance.ifOutBcastPkts

       64 bit unsigned wrappable counter."
   ::= {pr1645v2TvTmplPerfinMCH24PEntry 452984832}

pr1645v2TvTmplPerfinMCH24PIfOutMCPkts OBJECT-TYPE
   SYNTAX      Counter64
   MAX-ACCESS  read-only
   STATUS      current
   DESCRIPTION
      "Path: tunnels.performance.ipsecTunnels.mibCounters.h24Performance.ifOutMcastPkts

       64 bit unsigned wrappable counter."
   ::= {pr1645v2TvTmplPerfinMCH24PEntry 469762048}

pr1645v2TvTmplPerfinMCH24PIfOutDiscards OBJECT-TYPE
   SYNTAX      Counter64
   MAX-ACCESS  read-only
   STATUS      current
   DESCRIPTION
      "Path: tunnels.performance.ipsecTunnels.mibCounters.h24Performance.ifOutDiscards

       64 bit unsigned wrappable counter."
   ::= {pr1645v2TvTmplPerfinMCH24PEntry 218103808}

pr1645v2TvTmplPerfinMCH24PIfOutErrors OBJECT-TYPE
   SYNTAX      Counter64
   MAX-ACCESS  read-only
   STATUS      current
   DESCRIPTION
      "Path: tunnels.performance.ipsecTunnels.mibCounters.h24Performance.ifOutErrors

       64 bit unsigned wrappable counter."
   ::= {pr1645v2TvTmplPerfinMCH24PEntry 234881024}

pr1645v2TvTmplPerfinMCH24POutDropEx OBJECT-TYPE
   SYNTAX      Counter64
   MAX-ACCESS  read-only
   STATUS      current
   DESCRIPTION
      "Path: tunnels.performance.ipsecTunnels.mibCounters.h24Performance.ifOutDropLevelExceeded

       64 bit unsigned wrappable counter."
   ::= {pr1645v2TvTmplPerfinMCH24PEntry 352321536}

pr1645v2TvTmplPerfinMCH24POutDropNoArp OBJECT-TYPE
   SYNTAX      Counter64
   MAX-ACCESS  read-only
   STATUS      current
   DESCRIPTION
      "Path: tunnels.performance.ipsecTunnels.mibCounters.h24Performance.ifOutDiscardsNoArp

       64 bit unsigned wrappable counter."
   ::= {pr1645v2TvTmplPerfinMCH24PEntry 369098752}

pr1645v2TvTmplPerfinMCH24POutDropFilter OBJECT-TYPE
   SYNTAX      Counter64
   MAX-ACCESS  read-only
   STATUS      current
   DESCRIPTION
      "Path: tunnels.performance.ipsecTunnels.mibCounters.h24Performance.ifOutDiscardsFilter

       64 bit unsigned wrappable counter."
   ::= {pr1645v2TvTmplPerfinMCH24PEntry 402653184}

pr1645v2TvTmplPerfinMCH24PIfOutBandwidth OBJECT-TYPE
   SYNTAX      Integer32
   MAX-ACCESS  read-only
   STATUS      current
   DESCRIPTION
      "Path: tunnels.performance.ipsecTunnels.mibCounters.h24Performance.ifOutBandwidth

       unit name = bps
       formula = 8 * ; 8 /"
   ::= {pr1645v2TvTmplPerfinMCH24PEntry 285212672}

pr1645v2TvTmplPerfinMCH24PIfErrSec OBJECT-TYPE
   SYNTAX      Counter32
   MAX-ACCESS  read-only
   STATUS      current
   DESCRIPTION
      "Path: tunnels.performance.ipsecTunnels.mibCounters.h24Performance.ifErrSec

       32 bit unsigned wrappable counter."
   ::= {pr1645v2TvTmplPerfinMCH24PEntry 251658240}

pr1645v2TvTmplPerfinMCD7P OBJECT-TYPE
   SYNTAX      SEQUENCE OF Pr1645v2TvTmplPerfinMCD7PEntry
   MAX-ACCESS  not-accessible
   STATUS      current
   DESCRIPTION
      ""
   ::= {pr1645v2TvTmplPerfin 41680896}

pr1645v2TvTmplPerfinMCD7PEntry OBJECT-TYPE
   SYNTAX      Pr1645v2TvTmplPerfinMCD7PEntry
   MAX-ACCESS  not-accessible
   STATUS      current
   DESCRIPTION
      ""
   INDEX      { pr1645v2TvTmplPerfinTableIx,
                pr1645v2TvTmplPerfinMCD7PTableIx }
   ::= {pr1645v2TvTmplPerfinMCD7P 1}

Pr1645v2TvTmplPerfinMCD7PEntry ::=
   SEQUENCE
      {
      pr1645v2TvTmplPerfinMCD7PTableIx
         TableIndex,
      pr1645v2TvTmplPerfinMCD7PSysUpTime
         TimeTicks,
      pr1645v2TvTmplPerfinMCD7PIfUpTime
         TimeTicks,
      pr1645v2TvTmplPerfinMCD7PIfStatChanges
         Counter32,
      pr1645v2TvTmplPerfinMCD7PIfInOctets
         Counter64,
      pr1645v2TvTmplPerfinMCD7PIfInUCPkts
         Counter64,
      pr1645v2TvTmplPerfinMCD7PIfInNUCPkts
         Counter64,
      pr1645v2TvTmplPerfinMCD7PIfInBCPkts
         Counter64,
      pr1645v2TvTmplPerfinMCD7PIfInMCPkts
         Counter64,
      pr1645v2TvTmplPerfinMCD7PIfInDiscards
         Counter64,
      pr1645v2TvTmplPerfinMCD7PIfInErrors
         Counter64,
      pr1645v2TvTmplPerfinMCD7PIfInUnkwn
         Counter64,
      pr1645v2TvTmplPerfinMCD7PInDropEx
         Counter64,
      pr1645v2TvTmplPerfinMCD7PInDropNoMac
         Counter64,
      pr1645v2TvTmplPerfinMCD7PInDropNUCast
         Counter64,
      pr1645v2TvTmplPerfinMCD7PInDropFilter
         Counter64,
      pr1645v2TvTmplPerfinMCD7PIfInBandwidth
         Integer32,
      pr1645v2TvTmplPerfinMCD7PIfOutOctets
         Counter64,
      pr1645v2TvTmplPerfinMCD7PIfOutUCPkts
         Counter64,
      pr1645v2TvTmplPerfinMCD7PIfOutNUCPkts
         Counter64,
      pr1645v2TvTmplPerfinMCD7PIfOutBCPkts
         Counter64,
      pr1645v2TvTmplPerfinMCD7PIfOutMCPkts
         Counter64,
      pr1645v2TvTmplPerfinMCD7PIfOutDiscards
         Counter64,
      pr1645v2TvTmplPerfinMCD7PIfOutErrors
         Counter64,
      pr1645v2TvTmplPerfinMCD7POutDropEx
         Counter64,
      pr1645v2TvTmplPerfinMCD7POutDropNoArp
         Counter64,
      pr1645v2TvTmplPerfinMCD7POutDropFilter
         Counter64,
      pr1645v2TvTmplPerfinMCD7PIfOutBandwidth
         Integer32,
      pr1645v2TvTmplPerfinMCD7PIfErrSec
         Counter32
      }

pr1645v2TvTmplPerfinMCD7PTableIx OBJECT-TYPE
   SYNTAX      TableIndex
   MAX-ACCESS  not-accessible
   STATUS      current
   DESCRIPTION
      ""
   ::= {pr1645v2TvTmplPerfinMCD7PEntry 11}

pr1645v2TvTmplPerfinMCD7PSysUpTime OBJECT-TYPE
   SYNTAX      TimeTicks
   MAX-ACCESS  read-only
   STATUS      current
   DESCRIPTION
      "Path: tunnels.performance.ipsecTunnels.mibCounters.d7Performance.sysUpTime

       Time in centi-second."
   ::= {pr1645v2TvTmplPerfinMCD7PEntry 16777216}

pr1645v2TvTmplPerfinMCD7PIfUpTime OBJECT-TYPE
   SYNTAX      TimeTicks
   MAX-ACCESS  read-only
   STATUS      current
   DESCRIPTION
      "Path: tunnels.performance.ipsecTunnels.mibCounters.d7Performance.ifUpTime

       Time in centi-second."
   ::= {pr1645v2TvTmplPerfinMCD7PEntry 33554432}

pr1645v2TvTmplPerfinMCD7PIfStatChanges OBJECT-TYPE
   SYNTAX      Counter32
   MAX-ACCESS  read-only
   STATUS      current
   DESCRIPTION
      "Path: tunnels.performance.ipsecTunnels.mibCounters.d7Performance.ifStatusChanges

       32 bit unsigned wrappable counter."
   ::= {pr1645v2TvTmplPerfinMCD7PEntry 50331648}

pr1645v2TvTmplPerfinMCD7PIfInOctets OBJECT-TYPE
   SYNTAX      Counter64
   MAX-ACCESS  read-only
   STATUS      current
   DESCRIPTION
      "Path: tunnels.performance.ipsecTunnels.mibCounters.d7Performance.ifInOctets

       64 bit unsigned wrappable counter."
   ::= {pr1645v2TvTmplPerfinMCD7PEntry 67108864}

pr1645v2TvTmplPerfinMCD7PIfInUCPkts OBJECT-TYPE
   SYNTAX      Counter64
   MAX-ACCESS  read-only
   STATUS      current
   DESCRIPTION
      "Path: tunnels.performance.ipsecTunnels.mibCounters.d7Performance.ifInUcastPkts

       64 bit unsigned wrappable counter."
   ::= {pr1645v2TvTmplPerfinMCD7PEntry 83886080}

pr1645v2TvTmplPerfinMCD7PIfInNUCPkts OBJECT-TYPE
   SYNTAX      Counter64
   MAX-ACCESS  read-only
   STATUS      current
   DESCRIPTION
      "Path: tunnels.performance.ipsecTunnels.mibCounters.d7Performance.ifInNUcastPkts

       64 bit unsigned wrappable counter."
   ::= {pr1645v2TvTmplPerfinMCD7PEntry 100663296}

pr1645v2TvTmplPerfinMCD7PIfInBCPkts OBJECT-TYPE
   SYNTAX      Counter64
   MAX-ACCESS  read-only
   STATUS      current
   DESCRIPTION
      "Path: tunnels.performance.ipsecTunnels.mibCounters.d7Performance.ifInBcastPkts

       64 bit unsigned wrappable counter."
   ::= {pr1645v2TvTmplPerfinMCD7PEntry 419430400}

pr1645v2TvTmplPerfinMCD7PIfInMCPkts OBJECT-TYPE
   SYNTAX      Counter64
   MAX-ACCESS  read-only
   STATUS      current
   DESCRIPTION
      "Path: tunnels.performance.ipsecTunnels.mibCounters.d7Performance.ifInMcastPkts

       64 bit unsigned wrappable counter."
   ::= {pr1645v2TvTmplPerfinMCD7PEntry 436207616}

pr1645v2TvTmplPerfinMCD7PIfInDiscards OBJECT-TYPE
   SYNTAX      Counter64
   MAX-ACCESS  read-only
   STATUS      current
   DESCRIPTION
      "Path: tunnels.performance.ipsecTunnels.mibCounters.d7Performance.ifInDiscards

       64 bit unsigned wrappable counter."
   ::= {pr1645v2TvTmplPerfinMCD7PEntry 117440512}

pr1645v2TvTmplPerfinMCD7PIfInErrors OBJECT-TYPE
   SYNTAX      Counter64
   MAX-ACCESS  read-only
   STATUS      current
   DESCRIPTION
      "Path: tunnels.performance.ipsecTunnels.mibCounters.d7Performance.ifInErrors

       64 bit unsigned wrappable counter."
   ::= {pr1645v2TvTmplPerfinMCD7PEntry 134217728}

pr1645v2TvTmplPerfinMCD7PIfInUnkwn OBJECT-TYPE
   SYNTAX      Counter64
   MAX-ACCESS  read-only
   STATUS      current
   DESCRIPTION
      "Path: tunnels.performance.ipsecTunnels.mibCounters.d7Performance.ifInUnknownProtos

       64 bit unsigned wrappable counter."
   ::= {pr1645v2TvTmplPerfinMCD7PEntry 150994944}

pr1645v2TvTmplPerfinMCD7PInDropEx OBJECT-TYPE
   SYNTAX      Counter64
   MAX-ACCESS  read-only
   STATUS      current
   DESCRIPTION
      "Path: tunnels.performance.ipsecTunnels.mibCounters.d7Performance.ifInDropLevelExceeded

       64 bit unsigned wrappable counter."
   ::= {pr1645v2TvTmplPerfinMCD7PEntry 335544320}

pr1645v2TvTmplPerfinMCD7PInDropNoMac OBJECT-TYPE
   SYNTAX      Counter64
   MAX-ACCESS  read-only
   STATUS      current
   DESCRIPTION
      "Path: tunnels.performance.ipsecTunnels.mibCounters.d7Performance.fInDiscardsNoMacFit

       64 bit unsigned wrappable counter."
   ::= {pr1645v2TvTmplPerfinMCD7PEntry 301989888}

pr1645v2TvTmplPerfinMCD7PInDropNUCast OBJECT-TYPE
   SYNTAX      Counter64
   MAX-ACCESS  read-only
   STATUS      current
   DESCRIPTION
      "Path: tunnels.performance.ipsecTunnels.mibCounters.d7Performance.fInDiscardsNUCast

       64 bit unsigned wrappable counter."
   ::= {pr1645v2TvTmplPerfinMCD7PEntry 318767104}

pr1645v2TvTmplPerfinMCD7PInDropFilter OBJECT-TYPE
   SYNTAX      Counter64
   MAX-ACCESS  read-only
   STATUS      current
   DESCRIPTION
      "Path: tunnels.performance.ipsecTunnels.mibCounters.d7Performance.fInDiscardsFilter

       64 bit unsigned wrappable counter."
   ::= {pr1645v2TvTmplPerfinMCD7PEntry 385875968}

pr1645v2TvTmplPerfinMCD7PIfInBandwidth OBJECT-TYPE
   SYNTAX      Integer32
   MAX-ACCESS  read-only
   STATUS      current
   DESCRIPTION
      "Path: tunnels.performance.ipsecTunnels.mibCounters.d7Performance.ifInBandwidth

       unit name = bps
       formula = 8 * ; 8 /"
   ::= {pr1645v2TvTmplPerfinMCD7PEntry 268435456}

pr1645v2TvTmplPerfinMCD7PIfOutOctets OBJECT-TYPE
   SYNTAX      Counter64
   MAX-ACCESS  read-only
   STATUS      current
   DESCRIPTION
      "Path: tunnels.performance.ipsecTunnels.mibCounters.d7Performance.ifOutOctets

       64 bit unsigned wrappable counter."
   ::= {pr1645v2TvTmplPerfinMCD7PEntry 167772160}

pr1645v2TvTmplPerfinMCD7PIfOutUCPkts OBJECT-TYPE
   SYNTAX      Counter64
   MAX-ACCESS  read-only
   STATUS      current
   DESCRIPTION
      "Path: tunnels.performance.ipsecTunnels.mibCounters.d7Performance.ifOutUcastPkts

       64 bit unsigned wrappable counter."
   ::= {pr1645v2TvTmplPerfinMCD7PEntry 184549376}

pr1645v2TvTmplPerfinMCD7PIfOutNUCPkts OBJECT-TYPE
   SYNTAX      Counter64
   MAX-ACCESS  read-only
   STATUS      current
   DESCRIPTION
      "Path: tunnels.performance.ipsecTunnels.mibCounters.d7Performance.ifOutNUcastPkts

       64 bit unsigned wrappable counter."
   ::= {pr1645v2TvTmplPerfinMCD7PEntry 201326592}

pr1645v2TvTmplPerfinMCD7PIfOutBCPkts OBJECT-TYPE
   SYNTAX      Counter64
   MAX-ACCESS  read-only
   STATUS      current
   DESCRIPTION
      "Path: tunnels.performance.ipsecTunnels.mibCounters.d7Performance.ifOutBcastPkts

       64 bit unsigned wrappable counter."
   ::= {pr1645v2TvTmplPerfinMCD7PEntry 452984832}

pr1645v2TvTmplPerfinMCD7PIfOutMCPkts OBJECT-TYPE
   SYNTAX      Counter64
   MAX-ACCESS  read-only
   STATUS      current
   DESCRIPTION
      "Path: tunnels.performance.ipsecTunnels.mibCounters.d7Performance.ifOutMcastPkts

       64 bit unsigned wrappable counter."
   ::= {pr1645v2TvTmplPerfinMCD7PEntry 469762048}

pr1645v2TvTmplPerfinMCD7PIfOutDiscards OBJECT-TYPE
   SYNTAX      Counter64
   MAX-ACCESS  read-only
   STATUS      current
   DESCRIPTION
      "Path: tunnels.performance.ipsecTunnels.mibCounters.d7Performance.ifOutDiscards

       64 bit unsigned wrappable counter."
   ::= {pr1645v2TvTmplPerfinMCD7PEntry 218103808}

pr1645v2TvTmplPerfinMCD7PIfOutErrors OBJECT-TYPE
   SYNTAX      Counter64
   MAX-ACCESS  read-only
   STATUS      current
   DESCRIPTION
      "Path: tunnels.performance.ipsecTunnels.mibCounters.d7Performance.ifOutErrors

       64 bit unsigned wrappable counter."
   ::= {pr1645v2TvTmplPerfinMCD7PEntry 234881024}

pr1645v2TvTmplPerfinMCD7POutDropEx OBJECT-TYPE
   SYNTAX      Counter64
   MAX-ACCESS  read-only
   STATUS      current
   DESCRIPTION
      "Path: tunnels.performance.ipsecTunnels.mibCounters.d7Performance.ifOutDropLevelExceeded

       64 bit unsigned wrappable counter."
   ::= {pr1645v2TvTmplPerfinMCD7PEntry 352321536}

pr1645v2TvTmplPerfinMCD7POutDropNoArp OBJECT-TYPE
   SYNTAX      Counter64
   MAX-ACCESS  read-only
   STATUS      current
   DESCRIPTION
      "Path: tunnels.performance.ipsecTunnels.mibCounters.d7Performance.ifOutDiscardsNoArp

       64 bit unsigned wrappable counter."
   ::= {pr1645v2TvTmplPerfinMCD7PEntry 369098752}

pr1645v2TvTmplPerfinMCD7POutDropFilter OBJECT-TYPE
   SYNTAX      Counter64
   MAX-ACCESS  read-only
   STATUS      current
   DESCRIPTION
      "Path: tunnels.performance.ipsecTunnels.mibCounters.d7Performance.ifOutDiscardsFilter

       64 bit unsigned wrappable counter."
   ::= {pr1645v2TvTmplPerfinMCD7PEntry 402653184}

pr1645v2TvTmplPerfinMCD7PIfOutBandwidth OBJECT-TYPE
   SYNTAX      Integer32
   MAX-ACCESS  read-only
   STATUS      current
   DESCRIPTION
      "Path: tunnels.performance.ipsecTunnels.mibCounters.d7Performance.ifOutBandwidth

       unit name = bps
       formula = 8 * ; 8 /"
   ::= {pr1645v2TvTmplPerfinMCD7PEntry 285212672}

pr1645v2TvTmplPerfinMCD7PIfErrSec OBJECT-TYPE
   SYNTAX      Counter32
   MAX-ACCESS  read-only
   STATUS      current
   DESCRIPTION
      "Path: tunnels.performance.ipsecTunnels.mibCounters.d7Performance.ifErrSec

       32 bit unsigned wrappable counter."
   ::= {pr1645v2TvTmplPerfinMCD7PEntry 251658240}


pr1645v2TvTmplIpV6toV4 OBJECT IDENTIFIER ::= {pr1645v2TvTmpl 42}

pr1645v2TvTmplIpV6toV4SSCTable OBJECT-TYPE
   SYNTAX      SEQUENCE OF Pr1645v2TvTmplIpV6toV4Entry
   MAX-ACCESS  not-accessible
   STATUS      current
   DESCRIPTION
      ""
   ::= {pr1645v2TvTmplIpV6toV4 1}

pr1645v2TvTmplIpV6toV4Entry OBJECT-TYPE
   SYNTAX      Pr1645v2TvTmplIpV6toV4Entry
   MAX-ACCESS  not-accessible
   STATUS      current
   DESCRIPTION
      ""
   INDEX      { pr1645v2TvTmplIpV6toV4TableIx }
   ::= {pr1645v2TvTmplIpV6toV4SSCTable 1}

Pr1645v2TvTmplIpV6toV4Entry ::=
   SEQUENCE
      {
      pr1645v2TvTmplIpV6toV4TableIx
         TableIndex,
      pr1645v2TvTmplIpV6toV4Name
         DisplayString,
      pr1645v2TvTmplIpV6toV4MibCountersInOctets
         Counter64,
      pr1645v2TvTmplIpV6toV4MibCountersInUcast
         Counter64,
      pr1645v2TvTmplIpV6toV4MibCountersInNUcastPkts
         Counter64,
      pr1645v2TvTmplIpV6toV4MibCountersInBcastPkts
         Counter64,
      pr1645v2TvTmplIpV6toV4MibCountersInMcastPkts
         Counter64,
      pr1645v2TvTmplIpV6toV4MibCountersInDiscards
         Counter64,
      pr1645v2TvTmplIpV6toV4MibCountersInErrors
         Counter64,
      pr1645v2TvTmplIpV6toV4MibCountersInUnknownProtos
         Counter64,
      pr1645v2TvTmplIpV6toV4MibCountersInDropEx
         Counter64,
      pr1645v2TvTmplIpV6toV4MibCountersInDropNoMac
         Counter64,
      pr1645v2TvTmplIpV6toV4MibCountersInDropNUCast
         Counter64,
      pr1645v2TvTmplIpV6toV4MibCountersInDropFilter
         Counter64,
      pr1645v2TvTmplIpV6toV4MibCountersInBandwidth15sec
         Integer32,
      pr1645v2TvTmplIpV6toV4MibCountersInBandwidth30sec
         Integer32,
      pr1645v2TvTmplIpV6toV4MibCountersInBandwidth1min
         Integer32,
      pr1645v2TvTmplIpV6toV4MibCountersInBandwidth2min
         Integer32,
      pr1645v2TvTmplIpV6toV4MibCountersInBandwidth5min
         Integer32,
      pr1645v2TvTmplIpV6toV4MibCountersOutOctets
         Counter64,
      pr1645v2TvTmplIpV6toV4MibCountersOutUcastPkts
         Counter64,
      pr1645v2TvTmplIpV6toV4MibCountersOutNUcastPkts
         Counter64,
      pr1645v2TvTmplIpV6toV4MibCountersOutBcastPkts
         Counter64,
      pr1645v2TvTmplIpV6toV4MibCountersOutMcastPkts
         Counter64,
      pr1645v2TvTmplIpV6toV4MibCountersOutDiscards
         Counter64,
      pr1645v2TvTmplIpV6toV4MibCountersOutErrors
         Counter64,
      pr1645v2TvTmplIpV6toV4MibCountersOutQLen
         Counter32,
      pr1645v2TvTmplIpV6toV4MibCountersOutDropEx
         Counter64,
      pr1645v2TvTmplIpV6toV4MibCountersOutDropNoArp
         Counter64,
      pr1645v2TvTmplIpV6toV4MibCountersOutDropFilter
         Counter64,
      pr1645v2TvTmplIpV6toV4MibCountersOutBandwidth15sec
         Integer32,
      pr1645v2TvTmplIpV6toV4MibCountersOutBandwidth30sec
         Integer32,
      pr1645v2TvTmplIpV6toV4MibCountersOutBandwidth1min
         Integer32,
      pr1645v2TvTmplIpV6toV4MibCountersOutBandwidth2min
         Integer32,
      pr1645v2TvTmplIpV6toV4MibCountersOutBandwidth5min
         Integer32
      }

pr1645v2TvTmplIpV6toV4TableIx OBJECT-TYPE
   SYNTAX      TableIndex
   MAX-ACCESS  not-accessible
   STATUS      current
   DESCRIPTION
      ""
   ::= {pr1645v2TvTmplIpV6toV4Entry 11}

pr1645v2TvTmplIpV6toV4Name OBJECT-TYPE
   SYNTAX      DisplayString
   MAX-ACCESS  read-only
   STATUS      current
   DESCRIPTION
      "Path: tunnels.performance.ipV6toV4.name"
   ::= {pr1645v2TvTmplIpV6toV4Entry 16777216}

pr1645v2TvTmplIpV6toV4MibCountersInOctets OBJECT-TYPE
   SYNTAX      Counter64
   MAX-ACCESS  read-only
   STATUS      current
   DESCRIPTION
      "Path: tunnels.performance.ipV6toV4.mibCounters.ifInOctets

       64 bit unsigned wrappable counter."
   ::= {pr1645v2TvTmplIpV6toV4Entry 40697856}

pr1645v2TvTmplIpV6toV4MibCountersInUcast OBJECT-TYPE
   SYNTAX      Counter64
   MAX-ACCESS  read-only
   STATUS      current
   DESCRIPTION
      "Path: tunnels.performance.ipV6toV4.mibCounters.ifInUcastPkts

       64 bit unsigned wrappable counter."
   ::= {pr1645v2TvTmplIpV6toV4Entry 40763392}

pr1645v2TvTmplIpV6toV4MibCountersInNUcastPkts OBJECT-TYPE
   SYNTAX      Counter64
   MAX-ACCESS  read-only
   STATUS      current
   DESCRIPTION
      "Path: tunnels.performance.ipV6toV4.mibCounters.ifInNUcastPkts

       64 bit unsigned wrappable counter."
   ::= {pr1645v2TvTmplIpV6toV4Entry 40828928}

pr1645v2TvTmplIpV6toV4MibCountersInBcastPkts OBJECT-TYPE
   SYNTAX      Counter64
   MAX-ACCESS  read-only
   STATUS      current
   DESCRIPTION
      "Path: tunnels.performance.ipV6toV4.mibCounters.ifInBcastPkts

       64 bit unsigned wrappable counter."
   ::= {pr1645v2TvTmplIpV6toV4Entry 47382528}

pr1645v2TvTmplIpV6toV4MibCountersInMcastPkts OBJECT-TYPE
   SYNTAX      Counter64
   MAX-ACCESS  read-only
   STATUS      current
   DESCRIPTION
      "Path: tunnels.performance.ipV6toV4.mibCounters.ifInMcastPkts

       64 bit unsigned wrappable counter."
   ::= {pr1645v2TvTmplIpV6toV4Entry 48037888}

pr1645v2TvTmplIpV6toV4MibCountersInDiscards OBJECT-TYPE
   SYNTAX      Counter64
   MAX-ACCESS  read-only
   STATUS      current
   DESCRIPTION
      "Path: tunnels.performance.ipV6toV4.mibCounters.ifInDiscards

       64 bit unsigned wrappable counter."
   ::= {pr1645v2TvTmplIpV6toV4Entry 40894464}

pr1645v2TvTmplIpV6toV4MibCountersInErrors OBJECT-TYPE
   SYNTAX      Counter64
   MAX-ACCESS  read-only
   STATUS      current
   DESCRIPTION
      "Path: tunnels.performance.ipV6toV4.mibCounters.ifInErrors

       64 bit unsigned wrappable counter."
   ::= {pr1645v2TvTmplIpV6toV4Entry 40960000}

pr1645v2TvTmplIpV6toV4MibCountersInUnknownProtos OBJECT-TYPE
   SYNTAX      Counter64
   MAX-ACCESS  read-only
   STATUS      current
   DESCRIPTION
      "Path: tunnels.performance.ipV6toV4.mibCounters.ifInUnknownProtos

       64 bit unsigned wrappable counter."
   ::= {pr1645v2TvTmplIpV6toV4Entry 41025536}

pr1645v2TvTmplIpV6toV4MibCountersInDropEx OBJECT-TYPE
   SYNTAX      Counter64
   MAX-ACCESS  read-only
   STATUS      current
   DESCRIPTION
      "Path: tunnels.performance.ipV6toV4.mibCounters.ifInDropLevelExceeded

       64 bit unsigned wrappable counter."
   ::= {pr1645v2TvTmplIpV6toV4Entry 42074112}

pr1645v2TvTmplIpV6toV4MibCountersInDropNoMac OBJECT-TYPE
   SYNTAX      Counter64
   MAX-ACCESS  read-only
   STATUS      current
   DESCRIPTION
      "Path: tunnels.performance.ipV6toV4.mibCounters.ifInDiscardsNoMacFit

       64 bit unsigned wrappable counter."
   ::= {pr1645v2TvTmplIpV6toV4Entry 42270720}

pr1645v2TvTmplIpV6toV4MibCountersInDropNUCast OBJECT-TYPE
   SYNTAX      Counter64
   MAX-ACCESS  read-only
   STATUS      current
   DESCRIPTION
      "Path: tunnels.performance.ipV6toV4.mibCounters.ifInDiscardsNUCast

       64 bit unsigned wrappable counter."
   ::= {pr1645v2TvTmplIpV6toV4Entry 42467328}

pr1645v2TvTmplIpV6toV4MibCountersInDropFilter OBJECT-TYPE
   SYNTAX      Counter64
   MAX-ACCESS  read-only
   STATUS      current
   DESCRIPTION
      "Path: tunnels.performance.ipV6toV4.mibCounters.ifInDiscardsFilter

       64 bit unsigned wrappable counter."
   ::= {pr1645v2TvTmplIpV6toV4Entry 42532864}

pr1645v2TvTmplIpV6toV4MibCountersInBandwidth15sec OBJECT-TYPE
   SYNTAX      Integer32
   MAX-ACCESS  read-only
   STATUS      current
   DESCRIPTION
      "Path: tunnels.performance.ipV6toV4.mibCounters.ifInBandwidth.15sec

       unit name = bps
       formula = 8 * ; 8 /"
   ::= {pr1645v2TvTmplIpV6toV4Entry 45417728}

pr1645v2TvTmplIpV6toV4MibCountersInBandwidth30sec OBJECT-TYPE
   SYNTAX      Integer32
   MAX-ACCESS  read-only
   STATUS      current
   DESCRIPTION
      "Path: tunnels.performance.ipV6toV4.mibCounters.ifInBandwidth.30sec

       unit name = bps
       formula = 8 * ; 8 /"
   ::= {pr1645v2TvTmplIpV6toV4Entry 45419008}

pr1645v2TvTmplIpV6toV4MibCountersInBandwidth1min OBJECT-TYPE
   SYNTAX      Integer32
   MAX-ACCESS  read-only
   STATUS      current
   DESCRIPTION
      "Path: tunnels.performance.ipV6toV4.mibCounters.ifInBandwidth.1min

       unit name = bps
       formula = 8 * ; 8 /"
   ::= {pr1645v2TvTmplIpV6toV4Entry 45421568}

pr1645v2TvTmplIpV6toV4MibCountersInBandwidth2min OBJECT-TYPE
   SYNTAX      Integer32
   MAX-ACCESS  read-only
   STATUS      current
   DESCRIPTION
      "Path: tunnels.performance.ipV6toV4.mibCounters.ifInBandwidth.2min

       unit name = bps
       formula = 8 * ; 8 /"
   ::= {pr1645v2TvTmplIpV6toV4Entry 45426688}

pr1645v2TvTmplIpV6toV4MibCountersInBandwidth5min OBJECT-TYPE
   SYNTAX      Integer32
   MAX-ACCESS  read-only
   STATUS      current
   DESCRIPTION
      "Path: tunnels.performance.ipV6toV4.mibCounters.ifInBandwidth.5min

       unit name = bps
       formula = 8 * ; 8 /"
   ::= {pr1645v2TvTmplIpV6toV4Entry 45442048}

pr1645v2TvTmplIpV6toV4MibCountersOutOctets OBJECT-TYPE
   SYNTAX      Counter64
   MAX-ACCESS  read-only
   STATUS      current
   DESCRIPTION
      "Path: tunnels.performance.ipV6toV4.mibCounters.ifOutOctets

       64 bit unsigned wrappable counter."
   ::= {pr1645v2TvTmplIpV6toV4Entry 41091072}

pr1645v2TvTmplIpV6toV4MibCountersOutUcastPkts OBJECT-TYPE
   SYNTAX      Counter64
   MAX-ACCESS  read-only
   STATUS      current
   DESCRIPTION
      "Path: tunnels.performance.ipV6toV4.mibCounters.ifOutUcastPkts

       64 bit unsigned wrappable counter."
   ::= {pr1645v2TvTmplIpV6toV4Entry 41156608}

pr1645v2TvTmplIpV6toV4MibCountersOutNUcastPkts OBJECT-TYPE
   SYNTAX      Counter64
   MAX-ACCESS  read-only
   STATUS      current
   DESCRIPTION
      "Path: tunnels.performance.ipV6toV4.mibCounters.ifOutNUcastPkts

       64 bit unsigned wrappable counter."
   ::= {pr1645v2TvTmplIpV6toV4Entry 41222144}

pr1645v2TvTmplIpV6toV4MibCountersOutBcastPkts OBJECT-TYPE
   SYNTAX      Counter64
   MAX-ACCESS  read-only
   STATUS      current
   DESCRIPTION
      "Path: tunnels.performance.ipV6toV4.mibCounters.ifOutBcastPkts

       64 bit unsigned wrappable counter."
   ::= {pr1645v2TvTmplIpV6toV4Entry 47775744}

pr1645v2TvTmplIpV6toV4MibCountersOutMcastPkts OBJECT-TYPE
   SYNTAX      Counter64
   MAX-ACCESS  read-only
   STATUS      current
   DESCRIPTION
      "Path: tunnels.performance.ipV6toV4.mibCounters.ifOutMcastPkts

       64 bit unsigned wrappable counter."
   ::= {pr1645v2TvTmplIpV6toV4Entry 48431104}

pr1645v2TvTmplIpV6toV4MibCountersOutDiscards OBJECT-TYPE
   SYNTAX      Counter64
   MAX-ACCESS  read-only
   STATUS      current
   DESCRIPTION
      "Path: tunnels.performance.ipV6toV4.mibCounters.ifOutDiscards

       64 bit unsigned wrappable counter."
   ::= {pr1645v2TvTmplIpV6toV4Entry 41287680}

pr1645v2TvTmplIpV6toV4MibCountersOutErrors OBJECT-TYPE
   SYNTAX      Counter64
   MAX-ACCESS  read-only
   STATUS      current
   DESCRIPTION
      "Path: tunnels.performance.ipV6toV4.mibCounters.ifOutErrors

       64 bit unsigned wrappable counter."
   ::= {pr1645v2TvTmplIpV6toV4Entry 41353216}

pr1645v2TvTmplIpV6toV4MibCountersOutQLen OBJECT-TYPE
   SYNTAX      Counter32
   MAX-ACCESS  read-only
   STATUS      current
   DESCRIPTION
      "Path: tunnels.performance.ipV6toV4.mibCounters.ifOutQLen

       32 bit unsigned wrappable counter."
   ::= {pr1645v2TvTmplIpV6toV4Entry 41418752}

pr1645v2TvTmplIpV6toV4MibCountersOutDropEx OBJECT-TYPE
   SYNTAX      Counter64
   MAX-ACCESS  read-only
   STATUS      current
   DESCRIPTION
      "Path: tunnels.performance.ipV6toV4.mibCounters.ifOutDropLevelExceeded

       64 bit unsigned wrappable counter."
   ::= {pr1645v2TvTmplIpV6toV4Entry 41484288}

pr1645v2TvTmplIpV6toV4MibCountersOutDropNoArp OBJECT-TYPE
   SYNTAX      Counter64
   MAX-ACCESS  read-only
   STATUS      current
   DESCRIPTION
      "Path: tunnels.performance.ipV6toV4.mibCounters.ifOutDiscardsNoArp

       64 bit unsigned wrappable counter."
   ::= {pr1645v2TvTmplIpV6toV4Entry 42336256}

pr1645v2TvTmplIpV6toV4MibCountersOutDropFilter OBJECT-TYPE
   SYNTAX      Counter64
   MAX-ACCESS  read-only
   STATUS      current
   DESCRIPTION
      "Path: tunnels.performance.ipV6toV4.mibCounters.ifOutDiscardsFilter

       64 bit unsigned wrappable counter."
   ::= {pr1645v2TvTmplIpV6toV4Entry 42598400}

pr1645v2TvTmplIpV6toV4MibCountersOutBandwidth15sec OBJECT-TYPE
   SYNTAX      Integer32
   MAX-ACCESS  read-only
   STATUS      current
   DESCRIPTION
      "Path: tunnels.performance.ipV6toV4.mibCounters.ifOutBandwidth.15sec

       unit name = bps
       formula = 8 * ; 8 /"
   ::= {pr1645v2TvTmplIpV6toV4Entry 45483264}

pr1645v2TvTmplIpV6toV4MibCountersOutBandwidth30sec OBJECT-TYPE
   SYNTAX      Integer32
   MAX-ACCESS  read-only
   STATUS      current
   DESCRIPTION
      "Path: tunnels.performance.ipV6toV4.mibCounters.ifOutBandwidth.30sec

       unit name = bps
       formula = 8 * ; 8 /"
   ::= {pr1645v2TvTmplIpV6toV4Entry 45484544}

pr1645v2TvTmplIpV6toV4MibCountersOutBandwidth1min OBJECT-TYPE
   SYNTAX      Integer32
   MAX-ACCESS  read-only
   STATUS      current
   DESCRIPTION
      "Path: tunnels.performance.ipV6toV4.mibCounters.ifOutBandwidth.1min

       unit name = bps
       formula = 8 * ; 8 /"
   ::= {pr1645v2TvTmplIpV6toV4Entry 45487104}

pr1645v2TvTmplIpV6toV4MibCountersOutBandwidth2min OBJECT-TYPE
   SYNTAX      Integer32
   MAX-ACCESS  read-only
   STATUS      current
   DESCRIPTION
      "Path: tunnels.performance.ipV6toV4.mibCounters.ifOutBandwidth.2min

       unit name = bps
       formula = 8 * ; 8 /"
   ::= {pr1645v2TvTmplIpV6toV4Entry 45492224}

pr1645v2TvTmplIpV6toV4MibCountersOutBandwidth5min OBJECT-TYPE
   SYNTAX      Integer32
   MAX-ACCESS  read-only
   STATUS      current
   DESCRIPTION
      "Path: tunnels.performance.ipV6toV4.mibCounters.ifOutBandwidth.5min

       unit name = bps
       formula = 8 * ; 8 /"
   ::= {pr1645v2TvTmplIpV6toV4Entry 45507584}

pr1645v2TvTmplIpV6toV4MibCountersH2P OBJECT-TYPE
   SYNTAX      SEQUENCE OF Pr1645v2TvTmplIpV6toV4MibCountersH2PEntry
   MAX-ACCESS  not-accessible
   STATUS      current
   DESCRIPTION
      ""
   ::= {pr1645v2TvTmplIpV6toV4 41549824}

pr1645v2TvTmplIpV6toV4MibCountersH2PEntry OBJECT-TYPE
   SYNTAX      Pr1645v2TvTmplIpV6toV4MibCountersH2PEntry
   MAX-ACCESS  not-accessible
   STATUS      current
   DESCRIPTION
      ""
   INDEX      { pr1645v2TvTmplIpV6toV4TableIx,
                pr1645v2TvTmplIpV6toV4MibCountersH2PTableIx }
   ::= {pr1645v2TvTmplIpV6toV4MibCountersH2P 1}

Pr1645v2TvTmplIpV6toV4MibCountersH2PEntry ::=
   SEQUENCE
      {
      pr1645v2TvTmplIpV6toV4MibCountersH2PTableIx
         TableIndex,
      pr1645v2TvTmplIpV6toV4MibCountersH2PSysUpTime
         TimeTicks,
      pr1645v2TvTmplIpV6toV4MibCountersH2PIfUpTime
         TimeTicks,
      pr1645v2TvTmplIpV6toV4MibCountersH2PIfStatChanges
         Counter32,
      pr1645v2TvTmplIpV6toV4MibCountersH2PIfInOctets
         Counter64,
      pr1645v2TvTmplIpV6toV4MibCountersH2PIfInUCPkts
         Counter64,
      pr1645v2TvTmplIpV6toV4MibCountersH2PIfInNUCPkts
         Counter64,
      pr1645v2TvTmplIpV6toV4MibCountersH2PIfInBCPkts
         Counter64,
      pr1645v2TvTmplIpV6toV4MibCountersH2PIfInMCPkts
         Counter64,
      pr1645v2TvTmplIpV6toV4MibCountersH2PIfInDiscards
         Counter64,
      pr1645v2TvTmplIpV6toV4MibCountersH2PIfInErrors
         Counter64,
      pr1645v2TvTmplIpV6toV4MibCountersH2PIfInUnkwn
         Counter64,
      pr1645v2TvTmplIpV6toV4MibCountersH2PInDropEx
         Counter64,
      pr1645v2TvTmplIpV6toV4MibCountersH2PInDropNoMac
         Counter64,
      pr1645v2TvTmplIpV6toV4MibCountersH2PInDropNUCast
         Counter64,
      pr1645v2TvTmplIpV6toV4MibCountersH2PInDropFilter
         Counter64,
      pr1645v2TvTmplIpV6toV4MibCountersH2PIfInBandwidth
         Integer32,
      pr1645v2TvTmplIpV6toV4MibCountersH2PIfOutOctets
         Counter64,
      pr1645v2TvTmplIpV6toV4MibCountersH2PIfOutUCPkts
         Counter64,
      pr1645v2TvTmplIpV6toV4MibCountersH2PIfOutNUCPkts
         Counter64,
      pr1645v2TvTmplIpV6toV4MibCountersH2PIfOutBCPkts
         Counter64,
      pr1645v2TvTmplIpV6toV4MibCountersH2PIfOutMCPkts
         Counter64,
      pr1645v2TvTmplIpV6toV4MibCountersH2PIfOutDiscards
         Counter64,
      pr1645v2TvTmplIpV6toV4MibCountersH2PIfOutErrors
         Counter64,
      pr1645v2TvTmplIpV6toV4MibCountersH2POutDropEx
         Counter64,
      pr1645v2TvTmplIpV6toV4MibCountersH2POutDropNoArp
         Counter64,
      pr1645v2TvTmplIpV6toV4MibCountersH2POutDropFilter
         Counter64,
      pr1645v2TvTmplIpV6toV4MibCountersH2PIfOutBandwidth
         Integer32,
      pr1645v2TvTmplIpV6toV4MibCountersH2PIfErrSec
         Counter32
      }

pr1645v2TvTmplIpV6toV4MibCountersH2PTableIx OBJECT-TYPE
   SYNTAX      TableIndex
   MAX-ACCESS  not-accessible
   STATUS      current
   DESCRIPTION
      ""
   ::= {pr1645v2TvTmplIpV6toV4MibCountersH2PEntry 11}

pr1645v2TvTmplIpV6toV4MibCountersH2PSysUpTime OBJECT-TYPE
   SYNTAX      TimeTicks
   MAX-ACCESS  read-only
   STATUS      current
   DESCRIPTION
      "Path: tunnels.performance.ipV6toV4.mibCounters.h2Performance.sysUpTime

       Time in centi-second."
   ::= {pr1645v2TvTmplIpV6toV4MibCountersH2PEntry 16777216}

pr1645v2TvTmplIpV6toV4MibCountersH2PIfUpTime OBJECT-TYPE
   SYNTAX      TimeTicks
   MAX-ACCESS  read-only
   STATUS      current
   DESCRIPTION
      "Path: tunnels.performance.ipV6toV4.mibCounters.h2Performance.ifUpTime

       Time in centi-second."
   ::= {pr1645v2TvTmplIpV6toV4MibCountersH2PEntry 33554432}

pr1645v2TvTmplIpV6toV4MibCountersH2PIfStatChanges OBJECT-TYPE
   SYNTAX      Counter32
   MAX-ACCESS  read-only
   STATUS      current
   DESCRIPTION
      "Path: tunnels.performance.ipV6toV4.mibCounters.h2Performance.ifStatusChanges

       32 bit unsigned wrappable counter."
   ::= {pr1645v2TvTmplIpV6toV4MibCountersH2PEntry 50331648}

pr1645v2TvTmplIpV6toV4MibCountersH2PIfInOctets OBJECT-TYPE
   SYNTAX      Counter64
   MAX-ACCESS  read-only
   STATUS      current
   DESCRIPTION
      "Path: tunnels.performance.ipV6toV4.mibCounters.h2Performance.ifInOctets

       64 bit unsigned wrappable counter."
   ::= {pr1645v2TvTmplIpV6toV4MibCountersH2PEntry 67108864}

pr1645v2TvTmplIpV6toV4MibCountersH2PIfInUCPkts OBJECT-TYPE
   SYNTAX      Counter64
   MAX-ACCESS  read-only
   STATUS      current
   DESCRIPTION
      "Path: tunnels.performance.ipV6toV4.mibCounters.h2Performance.ifInUcastPkts

       64 bit unsigned wrappable counter."
   ::= {pr1645v2TvTmplIpV6toV4MibCountersH2PEntry 83886080}

pr1645v2TvTmplIpV6toV4MibCountersH2PIfInNUCPkts OBJECT-TYPE
   SYNTAX      Counter64
   MAX-ACCESS  read-only
   STATUS      current
   DESCRIPTION
      "Path: tunnels.performance.ipV6toV4.mibCounters.h2Performance.ifInNUcastPkts

       64 bit unsigned wrappable counter."
   ::= {pr1645v2TvTmplIpV6toV4MibCountersH2PEntry 100663296}

pr1645v2TvTmplIpV6toV4MibCountersH2PIfInBCPkts OBJECT-TYPE
   SYNTAX      Counter64
   MAX-ACCESS  read-only
   STATUS      current
   DESCRIPTION
      "Path: tunnels.performance.ipV6toV4.mibCounters.h2Performance.ifInBcastPkts

       64 bit unsigned wrappable counter."
   ::= {pr1645v2TvTmplIpV6toV4MibCountersH2PEntry 419430400}

pr1645v2TvTmplIpV6toV4MibCountersH2PIfInMCPkts OBJECT-TYPE
   SYNTAX      Counter64
   MAX-ACCESS  read-only
   STATUS      current
   DESCRIPTION
      "Path: tunnels.performance.ipV6toV4.mibCounters.h2Performance.ifInMcastPkts

       64 bit unsigned wrappable counter."
   ::= {pr1645v2TvTmplIpV6toV4MibCountersH2PEntry 436207616}

pr1645v2TvTmplIpV6toV4MibCountersH2PIfInDiscards OBJECT-TYPE
   SYNTAX      Counter64
   MAX-ACCESS  read-only
   STATUS      current
   DESCRIPTION
      "Path: tunnels.performance.ipV6toV4.mibCounters.h2Performance.ifInDiscards

       64 bit unsigned wrappable counter."
   ::= {pr1645v2TvTmplIpV6toV4MibCountersH2PEntry 117440512}

pr1645v2TvTmplIpV6toV4MibCountersH2PIfInErrors OBJECT-TYPE
   SYNTAX      Counter64
   MAX-ACCESS  read-only
   STATUS      current
   DESCRIPTION
      "Path: tunnels.performance.ipV6toV4.mibCounters.h2Performance.ifInErrors

       64 bit unsigned wrappable counter."
   ::= {pr1645v2TvTmplIpV6toV4MibCountersH2PEntry 134217728}

pr1645v2TvTmplIpV6toV4MibCountersH2PIfInUnkwn OBJECT-TYPE
   SYNTAX      Counter64
   MAX-ACCESS  read-only
   STATUS      current
   DESCRIPTION
      "Path: tunnels.performance.ipV6toV4.mibCounters.h2Performance.ifInUnknownProtos

       64 bit unsigned wrappable counter."
   ::= {pr1645v2TvTmplIpV6toV4MibCountersH2PEntry 150994944}

pr1645v2TvTmplIpV6toV4MibCountersH2PInDropEx OBJECT-TYPE
   SYNTAX      Counter64
   MAX-ACCESS  read-only
   STATUS      current
   DESCRIPTION
      "Path: tunnels.performance.ipV6toV4.mibCounters.h2Performance.ifInDropLevelExceeded

       64 bit unsigned wrappable counter."
   ::= {pr1645v2TvTmplIpV6toV4MibCountersH2PEntry 335544320}

pr1645v2TvTmplIpV6toV4MibCountersH2PInDropNoMac OBJECT-TYPE
   SYNTAX      Counter64
   MAX-ACCESS  read-only
   STATUS      current
   DESCRIPTION
      "Path: tunnels.performance.ipV6toV4.mibCounters.h2Performance.fInDiscardsNoMacFit

       64 bit unsigned wrappable counter."
   ::= {pr1645v2TvTmplIpV6toV4MibCountersH2PEntry 301989888}

pr1645v2TvTmplIpV6toV4MibCountersH2PInDropNUCast OBJECT-TYPE
   SYNTAX      Counter64
   MAX-ACCESS  read-only
   STATUS      current
   DESCRIPTION
      "Path: tunnels.performance.ipV6toV4.mibCounters.h2Performance.fInDiscardsNUCast

       64 bit unsigned wrappable counter."
   ::= {pr1645v2TvTmplIpV6toV4MibCountersH2PEntry 318767104}

pr1645v2TvTmplIpV6toV4MibCountersH2PInDropFilter OBJECT-TYPE
   SYNTAX      Counter64
   MAX-ACCESS  read-only
   STATUS      current
   DESCRIPTION
      "Path: tunnels.performance.ipV6toV4.mibCounters.h2Performance.fInDiscardsFilter

       64 bit unsigned wrappable counter."
   ::= {pr1645v2TvTmplIpV6toV4MibCountersH2PEntry 385875968}

pr1645v2TvTmplIpV6toV4MibCountersH2PIfInBandwidth OBJECT-TYPE
   SYNTAX      Integer32
   MAX-ACCESS  read-only
   STATUS      current
   DESCRIPTION
      "Path: tunnels.performance.ipV6toV4.mibCounters.h2Performance.ifInBandwidth

       unit name = bps
       formula = 8 * ; 8 /"
   ::= {pr1645v2TvTmplIpV6toV4MibCountersH2PEntry 268435456}

pr1645v2TvTmplIpV6toV4MibCountersH2PIfOutOctets OBJECT-TYPE
   SYNTAX      Counter64
   MAX-ACCESS  read-only
   STATUS      current
   DESCRIPTION
      "Path: tunnels.performance.ipV6toV4.mibCounters.h2Performance.ifOutOctets

       64 bit unsigned wrappable counter."
   ::= {pr1645v2TvTmplIpV6toV4MibCountersH2PEntry 167772160}

pr1645v2TvTmplIpV6toV4MibCountersH2PIfOutUCPkts OBJECT-TYPE
   SYNTAX      Counter64
   MAX-ACCESS  read-only
   STATUS      current
   DESCRIPTION
      "Path: tunnels.performance.ipV6toV4.mibCounters.h2Performance.ifOutUcastPkts

       64 bit unsigned wrappable counter."
   ::= {pr1645v2TvTmplIpV6toV4MibCountersH2PEntry 184549376}

pr1645v2TvTmplIpV6toV4MibCountersH2PIfOutNUCPkts OBJECT-TYPE
   SYNTAX      Counter64
   MAX-ACCESS  read-only
   STATUS      current
   DESCRIPTION
      "Path: tunnels.performance.ipV6toV4.mibCounters.h2Performance.ifOutNUcastPkts

       64 bit unsigned wrappable counter."
   ::= {pr1645v2TvTmplIpV6toV4MibCountersH2PEntry 201326592}

pr1645v2TvTmplIpV6toV4MibCountersH2PIfOutBCPkts OBJECT-TYPE
   SYNTAX      Counter64
   MAX-ACCESS  read-only
   STATUS      current
   DESCRIPTION
      "Path: tunnels.performance.ipV6toV4.mibCounters.h2Performance.ifOutBcastPkts

       64 bit unsigned wrappable counter."
   ::= {pr1645v2TvTmplIpV6toV4MibCountersH2PEntry 452984832}

pr1645v2TvTmplIpV6toV4MibCountersH2PIfOutMCPkts OBJECT-TYPE
   SYNTAX      Counter64
   MAX-ACCESS  read-only
   STATUS      current
   DESCRIPTION
      "Path: tunnels.performance.ipV6toV4.mibCounters.h2Performance.ifOutMcastPkts

       64 bit unsigned wrappable counter."
   ::= {pr1645v2TvTmplIpV6toV4MibCountersH2PEntry 469762048}

pr1645v2TvTmplIpV6toV4MibCountersH2PIfOutDiscards OBJECT-TYPE
   SYNTAX      Counter64
   MAX-ACCESS  read-only
   STATUS      current
   DESCRIPTION
      "Path: tunnels.performance.ipV6toV4.mibCounters.h2Performance.ifOutDiscards

       64 bit unsigned wrappable counter."
   ::= {pr1645v2TvTmplIpV6toV4MibCountersH2PEntry 218103808}

pr1645v2TvTmplIpV6toV4MibCountersH2PIfOutErrors OBJECT-TYPE
   SYNTAX      Counter64
   MAX-ACCESS  read-only
   STATUS      current
   DESCRIPTION
      "Path: tunnels.performance.ipV6toV4.mibCounters.h2Performance.ifOutErrors

       64 bit unsigned wrappable counter."
   ::= {pr1645v2TvTmplIpV6toV4MibCountersH2PEntry 234881024}

pr1645v2TvTmplIpV6toV4MibCountersH2POutDropEx OBJECT-TYPE
   SYNTAX      Counter64
   MAX-ACCESS  read-only
   STATUS      current
   DESCRIPTION
      "Path: tunnels.performance.ipV6toV4.mibCounters.h2Performance.ifOutDropLevelExceeded

       64 bit unsigned wrappable counter."
   ::= {pr1645v2TvTmplIpV6toV4MibCountersH2PEntry 352321536}

pr1645v2TvTmplIpV6toV4MibCountersH2POutDropNoArp OBJECT-TYPE
   SYNTAX      Counter64
   MAX-ACCESS  read-only
   STATUS      current
   DESCRIPTION
      "Path: tunnels.performance.ipV6toV4.mibCounters.h2Performance.ifOutDiscardsNoArp

       64 bit unsigned wrappable counter."
   ::= {pr1645v2TvTmplIpV6toV4MibCountersH2PEntry 369098752}

pr1645v2TvTmplIpV6toV4MibCountersH2POutDropFilter OBJECT-TYPE
   SYNTAX      Counter64
   MAX-ACCESS  read-only
   STATUS      current
   DESCRIPTION
      "Path: tunnels.performance.ipV6toV4.mibCounters.h2Performance.ifOutDiscardsFilter

       64 bit unsigned wrappable counter."
   ::= {pr1645v2TvTmplIpV6toV4MibCountersH2PEntry 402653184}

pr1645v2TvTmplIpV6toV4MibCountersH2PIfOutBandwidth OBJECT-TYPE
   SYNTAX      Integer32
   MAX-ACCESS  read-only
   STATUS      current
   DESCRIPTION
      "Path: tunnels.performance.ipV6toV4.mibCounters.h2Performance.ifOutBandwidth

       unit name = bps
       formula = 8 * ; 8 /"
   ::= {pr1645v2TvTmplIpV6toV4MibCountersH2PEntry 285212672}

pr1645v2TvTmplIpV6toV4MibCountersH2PIfErrSec OBJECT-TYPE
   SYNTAX      Counter32
   MAX-ACCESS  read-only
   STATUS      current
   DESCRIPTION
      "Path: tunnels.performance.ipV6toV4.mibCounters.h2Performance.ifErrSec

       32 bit unsigned wrappable counter."
   ::= {pr1645v2TvTmplIpV6toV4MibCountersH2PEntry 251658240}

pr1645v2TvTmplIpV6toV4MibCountersH24P OBJECT-TYPE
   SYNTAX      SEQUENCE OF Pr1645v2TvTmplIpV6toV4MibCountersH24PEntry
   MAX-ACCESS  not-accessible
   STATUS      current
   DESCRIPTION
      ""
   ::= {pr1645v2TvTmplIpV6toV4 41615360}

pr1645v2TvTmplIpV6toV4MibCountersH24PEntry OBJECT-TYPE
   SYNTAX      Pr1645v2TvTmplIpV6toV4MibCountersH24PEntry
   MAX-ACCESS  not-accessible
   STATUS      current
   DESCRIPTION
      ""
   INDEX      { pr1645v2TvTmplIpV6toV4TableIx,
                pr1645v2TvTmplIpV6toV4MibCountersH24PTableIx }
   ::= {pr1645v2TvTmplIpV6toV4MibCountersH24P 1}

Pr1645v2TvTmplIpV6toV4MibCountersH24PEntry ::=
   SEQUENCE
      {
      pr1645v2TvTmplIpV6toV4MibCountersH24PTableIx
         TableIndex,
      pr1645v2TvTmplIpV6toV4MibCountersH24PSysUpTime
         TimeTicks,
      pr1645v2TvTmplIpV6toV4MibCountersH24PIfUpTime
         TimeTicks,
      pr1645v2TvTmplIpV6toV4MibCountersH24PIfStatChanges
         Counter32,
      pr1645v2TvTmplIpV6toV4MibCountersH24PIfInOctets
         Counter64,
      pr1645v2TvTmplIpV6toV4MibCountersH24PIfInUCPkts
         Counter64,
      pr1645v2TvTmplIpV6toV4MibCountersH24PIfInNUCPkts
         Counter64,
      pr1645v2TvTmplIpV6toV4MibCountersH24PIfInBCPkts
         Counter64,
      pr1645v2TvTmplIpV6toV4MibCountersH24PIfInMCPkts
         Counter64,
      pr1645v2TvTmplIpV6toV4MibCountersH24PIfInDiscards
         Counter64,
      pr1645v2TvTmplIpV6toV4MibCountersH24PIfInErrors
         Counter64,
      pr1645v2TvTmplIpV6toV4MibCountersH24PIfInUnkwn
         Counter64,
      pr1645v2TvTmplIpV6toV4MibCountersH24PInDropEx
         Counter64,
      pr1645v2TvTmplIpV6toV4MibCountersH24PInDropNoMac
         Counter64,
      pr1645v2TvTmplIpV6toV4MibCountersH24PInDropNUCast
         Counter64,
      pr1645v2TvTmplIpV6toV4MibCountersH24PInDropFilter
         Counter64,
      pr1645v2TvTmplIpV6toV4MibCountersH24PIfInBandwidth
         Integer32,
      pr1645v2TvTmplIpV6toV4MibCountersH24PIfOutOctets
         Counter64,
      pr1645v2TvTmplIpV6toV4MibCountersH24PIfOutUCPkts
         Counter64,
      pr1645v2TvTmplIpV6toV4MibCountersH24PIfOutNUCPkts
         Counter64,
      pr1645v2TvTmplIpV6toV4MibCountersH24PIfOutBCPkts
         Counter64,
      pr1645v2TvTmplIpV6toV4MibCountersH24PIfOutMCPkts
         Counter64,
      pr1645v2TvTmplIpV6toV4MibCountersH24PIfOutDiscards
         Counter64,
      pr1645v2TvTmplIpV6toV4MibCountersH24PIfOutErrors
         Counter64,
      pr1645v2TvTmplIpV6toV4MibCountersH24POutDropEx
         Counter64,
      pr1645v2TvTmplIpV6toV4MibCountersH24POutDropNoArp
         Counter64,
      pr1645v2TvTmplIpV6toV4MibCountersH24POutDropFilter
         Counter64,
      pr1645v2TvTmplIpV6toV4MibCountersH24PIfOutBandwidth
         Integer32,
      pr1645v2TvTmplIpV6toV4MibCountersH24PIfErrSec
         Counter32
      }

pr1645v2TvTmplIpV6toV4MibCountersH24PTableIx OBJECT-TYPE
   SYNTAX      TableIndex
   MAX-ACCESS  not-accessible
   STATUS      current
   DESCRIPTION
      ""
   ::= {pr1645v2TvTmplIpV6toV4MibCountersH24PEntry 11}

pr1645v2TvTmplIpV6toV4MibCountersH24PSysUpTime OBJECT-TYPE
   SYNTAX      TimeTicks
   MAX-ACCESS  read-only
   STATUS      current
   DESCRIPTION
      "Path: tunnels.performance.ipV6toV4.mibCounters.h24Performance.sysUpTime

       Time in centi-second."
   ::= {pr1645v2TvTmplIpV6toV4MibCountersH24PEntry 16777216}

pr1645v2TvTmplIpV6toV4MibCountersH24PIfUpTime OBJECT-TYPE
   SYNTAX      TimeTicks
   MAX-ACCESS  read-only
   STATUS      current
   DESCRIPTION
      "Path: tunnels.performance.ipV6toV4.mibCounters.h24Performance.ifUpTime

       Time in centi-second."
   ::= {pr1645v2TvTmplIpV6toV4MibCountersH24PEntry 33554432}

pr1645v2TvTmplIpV6toV4MibCountersH24PIfStatChanges OBJECT-TYPE
   SYNTAX      Counter32
   MAX-ACCESS  read-only
   STATUS      current
   DESCRIPTION
      "Path: tunnels.performance.ipV6toV4.mibCounters.h24Performance.ifStatusChanges

       32 bit unsigned wrappable counter."
   ::= {pr1645v2TvTmplIpV6toV4MibCountersH24PEntry 50331648}

pr1645v2TvTmplIpV6toV4MibCountersH24PIfInOctets OBJECT-TYPE
   SYNTAX      Counter64
   MAX-ACCESS  read-only
   STATUS      current
   DESCRIPTION
      "Path: tunnels.performance.ipV6toV4.mibCounters.h24Performance.ifInOctets

       64 bit unsigned wrappable counter."
   ::= {pr1645v2TvTmplIpV6toV4MibCountersH24PEntry 67108864}

pr1645v2TvTmplIpV6toV4MibCountersH24PIfInUCPkts OBJECT-TYPE
   SYNTAX      Counter64
   MAX-ACCESS  read-only
   STATUS      current
   DESCRIPTION
      "Path: tunnels.performance.ipV6toV4.mibCounters.h24Performance.ifInUcastPkts

       64 bit unsigned wrappable counter."
   ::= {pr1645v2TvTmplIpV6toV4MibCountersH24PEntry 83886080}

pr1645v2TvTmplIpV6toV4MibCountersH24PIfInNUCPkts OBJECT-TYPE
   SYNTAX      Counter64
   MAX-ACCESS  read-only
   STATUS      current
   DESCRIPTION
      "Path: tunnels.performance.ipV6toV4.mibCounters.h24Performance.ifInNUcastPkts

       64 bit unsigned wrappable counter."
   ::= {pr1645v2TvTmplIpV6toV4MibCountersH24PEntry 100663296}

pr1645v2TvTmplIpV6toV4MibCountersH24PIfInBCPkts OBJECT-TYPE
   SYNTAX      Counter64
   MAX-ACCESS  read-only
   STATUS      current
   DESCRIPTION
      "Path: tunnels.performance.ipV6toV4.mibCounters.h24Performance.ifInBcastPkts

       64 bit unsigned wrappable counter."
   ::= {pr1645v2TvTmplIpV6toV4MibCountersH24PEntry 419430400}

pr1645v2TvTmplIpV6toV4MibCountersH24PIfInMCPkts OBJECT-TYPE
   SYNTAX      Counter64
   MAX-ACCESS  read-only
   STATUS      current
   DESCRIPTION
      "Path: tunnels.performance.ipV6toV4.mibCounters.h24Performance.ifInMcastPkts

       64 bit unsigned wrappable counter."
   ::= {pr1645v2TvTmplIpV6toV4MibCountersH24PEntry 436207616}

pr1645v2TvTmplIpV6toV4MibCountersH24PIfInDiscards OBJECT-TYPE
   SYNTAX      Counter64
   MAX-ACCESS  read-only
   STATUS      current
   DESCRIPTION
      "Path: tunnels.performance.ipV6toV4.mibCounters.h24Performance.ifInDiscards

       64 bit unsigned wrappable counter."
   ::= {pr1645v2TvTmplIpV6toV4MibCountersH24PEntry 117440512}

pr1645v2TvTmplIpV6toV4MibCountersH24PIfInErrors OBJECT-TYPE
   SYNTAX      Counter64
   MAX-ACCESS  read-only
   STATUS      current
   DESCRIPTION
      "Path: tunnels.performance.ipV6toV4.mibCounters.h24Performance.ifInErrors

       64 bit unsigned wrappable counter."
   ::= {pr1645v2TvTmplIpV6toV4MibCountersH24PEntry 134217728}

pr1645v2TvTmplIpV6toV4MibCountersH24PIfInUnkwn OBJECT-TYPE
   SYNTAX      Counter64
   MAX-ACCESS  read-only
   STATUS      current
   DESCRIPTION
      "Path: tunnels.performance.ipV6toV4.mibCounters.h24Performance.ifInUnknownProtos

       64 bit unsigned wrappable counter."
   ::= {pr1645v2TvTmplIpV6toV4MibCountersH24PEntry 150994944}

pr1645v2TvTmplIpV6toV4MibCountersH24PInDropEx OBJECT-TYPE
   SYNTAX      Counter64
   MAX-ACCESS  read-only
   STATUS      current
   DESCRIPTION
      "Path: tunnels.performance.ipV6toV4.mibCounters.h24Performance.ifInDropLevelExceeded

       64 bit unsigned wrappable counter."
   ::= {pr1645v2TvTmplIpV6toV4MibCountersH24PEntry 335544320}

pr1645v2TvTmplIpV6toV4MibCountersH24PInDropNoMac OBJECT-TYPE
   SYNTAX      Counter64
   MAX-ACCESS  read-only
   STATUS      current
   DESCRIPTION
      "Path: tunnels.performance.ipV6toV4.mibCounters.h24Performance.fInDiscardsNoMacFit

       64 bit unsigned wrappable counter."
   ::= {pr1645v2TvTmplIpV6toV4MibCountersH24PEntry 301989888}

pr1645v2TvTmplIpV6toV4MibCountersH24PInDropNUCast OBJECT-TYPE
   SYNTAX      Counter64
   MAX-ACCESS  read-only
   STATUS      current
   DESCRIPTION
      "Path: tunnels.performance.ipV6toV4.mibCounters.h24Performance.fInDiscardsNUCast

       64 bit unsigned wrappable counter."
   ::= {pr1645v2TvTmplIpV6toV4MibCountersH24PEntry 318767104}

pr1645v2TvTmplIpV6toV4MibCountersH24PInDropFilter OBJECT-TYPE
   SYNTAX      Counter64
   MAX-ACCESS  read-only
   STATUS      current
   DESCRIPTION
      "Path: tunnels.performance.ipV6toV4.mibCounters.h24Performance.fInDiscardsFilter

       64 bit unsigned wrappable counter."
   ::= {pr1645v2TvTmplIpV6toV4MibCountersH24PEntry 385875968}

pr1645v2TvTmplIpV6toV4MibCountersH24PIfInBandwidth OBJECT-TYPE
   SYNTAX      Integer32
   MAX-ACCESS  read-only
   STATUS      current
   DESCRIPTION
      "Path: tunnels.performance.ipV6toV4.mibCounters.h24Performance.ifInBandwidth

       unit name = bps
       formula = 8 * ; 8 /"
   ::= {pr1645v2TvTmplIpV6toV4MibCountersH24PEntry 268435456}

pr1645v2TvTmplIpV6toV4MibCountersH24PIfOutOctets OBJECT-TYPE
   SYNTAX      Counter64
   MAX-ACCESS  read-only
   STATUS      current
   DESCRIPTION
      "Path: tunnels.performance.ipV6toV4.mibCounters.h24Performance.ifOutOctets

       64 bit unsigned wrappable counter."
   ::= {pr1645v2TvTmplIpV6toV4MibCountersH24PEntry 167772160}

pr1645v2TvTmplIpV6toV4MibCountersH24PIfOutUCPkts OBJECT-TYPE
   SYNTAX      Counter64
   MAX-ACCESS  read-only
   STATUS      current
   DESCRIPTION
      "Path: tunnels.performance.ipV6toV4.mibCounters.h24Performance.ifOutUcastPkts

       64 bit unsigned wrappable counter."
   ::= {pr1645v2TvTmplIpV6toV4MibCountersH24PEntry 184549376}

pr1645v2TvTmplIpV6toV4MibCountersH24PIfOutNUCPkts OBJECT-TYPE
   SYNTAX      Counter64
   MAX-ACCESS  read-only
   STATUS      current
   DESCRIPTION
      "Path: tunnels.performance.ipV6toV4.mibCounters.h24Performance.ifOutNUcastPkts

       64 bit unsigned wrappable counter."
   ::= {pr1645v2TvTmplIpV6toV4MibCountersH24PEntry 201326592}

pr1645v2TvTmplIpV6toV4MibCountersH24PIfOutBCPkts OBJECT-TYPE
   SYNTAX      Counter64
   MAX-ACCESS  read-only
   STATUS      current
   DESCRIPTION
      "Path: tunnels.performance.ipV6toV4.mibCounters.h24Performance.ifOutBcastPkts

       64 bit unsigned wrappable counter."
   ::= {pr1645v2TvTmplIpV6toV4MibCountersH24PEntry 452984832}

pr1645v2TvTmplIpV6toV4MibCountersH24PIfOutMCPkts OBJECT-TYPE
   SYNTAX      Counter64
   MAX-ACCESS  read-only
   STATUS      current
   DESCRIPTION
      "Path: tunnels.performance.ipV6toV4.mibCounters.h24Performance.ifOutMcastPkts

       64 bit unsigned wrappable counter."
   ::= {pr1645v2TvTmplIpV6toV4MibCountersH24PEntry 469762048}

pr1645v2TvTmplIpV6toV4MibCountersH24PIfOutDiscards OBJECT-TYPE
   SYNTAX      Counter64
   MAX-ACCESS  read-only
   STATUS      current
   DESCRIPTION
      "Path: tunnels.performance.ipV6toV4.mibCounters.h24Performance.ifOutDiscards

       64 bit unsigned wrappable counter."
   ::= {pr1645v2TvTmplIpV6toV4MibCountersH24PEntry 218103808}

pr1645v2TvTmplIpV6toV4MibCountersH24PIfOutErrors OBJECT-TYPE
   SYNTAX      Counter64
   MAX-ACCESS  read-only
   STATUS      current
   DESCRIPTION
      "Path: tunnels.performance.ipV6toV4.mibCounters.h24Performance.ifOutErrors

       64 bit unsigned wrappable counter."
   ::= {pr1645v2TvTmplIpV6toV4MibCountersH24PEntry 234881024}

pr1645v2TvTmplIpV6toV4MibCountersH24POutDropEx OBJECT-TYPE
   SYNTAX      Counter64
   MAX-ACCESS  read-only
   STATUS      current
   DESCRIPTION
      "Path: tunnels.performance.ipV6toV4.mibCounters.h24Performance.ifOutDropLevelExceeded

       64 bit unsigned wrappable counter."
   ::= {pr1645v2TvTmplIpV6toV4MibCountersH24PEntry 352321536}

pr1645v2TvTmplIpV6toV4MibCountersH24POutDropNoArp OBJECT-TYPE
   SYNTAX      Counter64
   MAX-ACCESS  read-only
   STATUS      current
   DESCRIPTION
      "Path: tunnels.performance.ipV6toV4.mibCounters.h24Performance.ifOutDiscardsNoArp

       64 bit unsigned wrappable counter."
   ::= {pr1645v2TvTmplIpV6toV4MibCountersH24PEntry 369098752}

pr1645v2TvTmplIpV6toV4MibCountersH24POutDropFilter OBJECT-TYPE
   SYNTAX      Counter64
   MAX-ACCESS  read-only
   STATUS      current
   DESCRIPTION
      "Path: tunnels.performance.ipV6toV4.mibCounters.h24Performance.ifOutDiscardsFilter

       64 bit unsigned wrappable counter."
   ::= {pr1645v2TvTmplIpV6toV4MibCountersH24PEntry 402653184}

pr1645v2TvTmplIpV6toV4MibCountersH24PIfOutBandwidth OBJECT-TYPE
   SYNTAX      Integer32
   MAX-ACCESS  read-only
   STATUS      current
   DESCRIPTION
      "Path: tunnels.performance.ipV6toV4.mibCounters.h24Performance.ifOutBandwidth

       unit name = bps
       formula = 8 * ; 8 /"
   ::= {pr1645v2TvTmplIpV6toV4MibCountersH24PEntry 285212672}

pr1645v2TvTmplIpV6toV4MibCountersH24PIfErrSec OBJECT-TYPE
   SYNTAX      Counter32
   MAX-ACCESS  read-only
   STATUS      current
   DESCRIPTION
      "Path: tunnels.performance.ipV6toV4.mibCounters.h24Performance.ifErrSec

       32 bit unsigned wrappable counter."
   ::= {pr1645v2TvTmplIpV6toV4MibCountersH24PEntry 251658240}

pr1645v2TvTmplIpV6toV4MibCountersD7P OBJECT-TYPE
   SYNTAX      SEQUENCE OF Pr1645v2TvTmplIpV6toV4MibCountersD7PEntry
   MAX-ACCESS  not-accessible
   STATUS      current
   DESCRIPTION
      ""
   ::= {pr1645v2TvTmplIpV6toV4 41680896}

pr1645v2TvTmplIpV6toV4MibCountersD7PEntry OBJECT-TYPE
   SYNTAX      Pr1645v2TvTmplIpV6toV4MibCountersD7PEntry
   MAX-ACCESS  not-accessible
   STATUS      current
   DESCRIPTION
      ""
   INDEX      { pr1645v2TvTmplIpV6toV4TableIx,
                pr1645v2TvTmplIpV6toV4MibCountersD7PTableIx }
   ::= {pr1645v2TvTmplIpV6toV4MibCountersD7P 1}

Pr1645v2TvTmplIpV6toV4MibCountersD7PEntry ::=
   SEQUENCE
      {
      pr1645v2TvTmplIpV6toV4MibCountersD7PTableIx
         TableIndex,
      pr1645v2TvTmplIpV6toV4MibCountersD7PSysUpTime
         TimeTicks,
      pr1645v2TvTmplIpV6toV4MibCountersD7PIfUpTime
         TimeTicks,
      pr1645v2TvTmplIpV6toV4MibCountersD7PIfStatChanges
         Counter32,
      pr1645v2TvTmplIpV6toV4MibCountersD7PIfInOctets
         Counter64,
      pr1645v2TvTmplIpV6toV4MibCountersD7PIfInUCPkts
         Counter64,
      pr1645v2TvTmplIpV6toV4MibCountersD7PIfInNUCPkts
         Counter64,
      pr1645v2TvTmplIpV6toV4MibCountersD7PIfInBCPkts
         Counter64,
      pr1645v2TvTmplIpV6toV4MibCountersD7PIfInMCPkts
         Counter64,
      pr1645v2TvTmplIpV6toV4MibCountersD7PIfInDiscards
         Counter64,
      pr1645v2TvTmplIpV6toV4MibCountersD7PIfInErrors
         Counter64,
      pr1645v2TvTmplIpV6toV4MibCountersD7PIfInUnkwn
         Counter64,
      pr1645v2TvTmplIpV6toV4MibCountersD7PInDropEx
         Counter64,
      pr1645v2TvTmplIpV6toV4MibCountersD7PInDropNoMac
         Counter64,
      pr1645v2TvTmplIpV6toV4MibCountersD7PInDropNUCast
         Counter64,
      pr1645v2TvTmplIpV6toV4MibCountersD7PInDropFilter
         Counter64,
      pr1645v2TvTmplIpV6toV4MibCountersD7PIfInBandwidth
         Integer32,
      pr1645v2TvTmplIpV6toV4MibCountersD7PIfOutOctets
         Counter64,
      pr1645v2TvTmplIpV6toV4MibCountersD7PIfOutUCPkts
         Counter64,
      pr1645v2TvTmplIpV6toV4MibCountersD7PIfOutNUCPkts
         Counter64,
      pr1645v2TvTmplIpV6toV4MibCountersD7PIfOutBCPkts
         Counter64,
      pr1645v2TvTmplIpV6toV4MibCountersD7PIfOutMCPkts
         Counter64,
      pr1645v2TvTmplIpV6toV4MibCountersD7PIfOutDiscards
         Counter64,
      pr1645v2TvTmplIpV6toV4MibCountersD7PIfOutErrors
         Counter64,
      pr1645v2TvTmplIpV6toV4MibCountersD7POutDropEx
         Counter64,
      pr1645v2TvTmplIpV6toV4MibCountersD7POutDropNoArp
         Counter64,
      pr1645v2TvTmplIpV6toV4MibCountersD7POutDropFilter
         Counter64,
      pr1645v2TvTmplIpV6toV4MibCountersD7PIfOutBandwidth
         Integer32,
      pr1645v2TvTmplIpV6toV4MibCountersD7PIfErrSec
         Counter32
      }

pr1645v2TvTmplIpV6toV4MibCountersD7PTableIx OBJECT-TYPE
   SYNTAX      TableIndex
   MAX-ACCESS  not-accessible
   STATUS      current
   DESCRIPTION
      ""
   ::= {pr1645v2TvTmplIpV6toV4MibCountersD7PEntry 11}

pr1645v2TvTmplIpV6toV4MibCountersD7PSysUpTime OBJECT-TYPE
   SYNTAX      TimeTicks
   MAX-ACCESS  read-only
   STATUS      current
   DESCRIPTION
      "Path: tunnels.performance.ipV6toV4.mibCounters.d7Performance.sysUpTime

       Time in centi-second."
   ::= {pr1645v2TvTmplIpV6toV4MibCountersD7PEntry 16777216}

pr1645v2TvTmplIpV6toV4MibCountersD7PIfUpTime OBJECT-TYPE
   SYNTAX      TimeTicks
   MAX-ACCESS  read-only
   STATUS      current
   DESCRIPTION
      "Path: tunnels.performance.ipV6toV4.mibCounters.d7Performance.ifUpTime

       Time in centi-second."
   ::= {pr1645v2TvTmplIpV6toV4MibCountersD7PEntry 33554432}

pr1645v2TvTmplIpV6toV4MibCountersD7PIfStatChanges OBJECT-TYPE
   SYNTAX      Counter32
   MAX-ACCESS  read-only
   STATUS      current
   DESCRIPTION
      "Path: tunnels.performance.ipV6toV4.mibCounters.d7Performance.ifStatusChanges

       32 bit unsigned wrappable counter."
   ::= {pr1645v2TvTmplIpV6toV4MibCountersD7PEntry 50331648}

pr1645v2TvTmplIpV6toV4MibCountersD7PIfInOctets OBJECT-TYPE
   SYNTAX      Counter64
   MAX-ACCESS  read-only
   STATUS      current
   DESCRIPTION
      "Path: tunnels.performance.ipV6toV4.mibCounters.d7Performance.ifInOctets

       64 bit unsigned wrappable counter."
   ::= {pr1645v2TvTmplIpV6toV4MibCountersD7PEntry 67108864}

pr1645v2TvTmplIpV6toV4MibCountersD7PIfInUCPkts OBJECT-TYPE
   SYNTAX      Counter64
   MAX-ACCESS  read-only
   STATUS      current
   DESCRIPTION
      "Path: tunnels.performance.ipV6toV4.mibCounters.d7Performance.ifInUcastPkts

       64 bit unsigned wrappable counter."
   ::= {pr1645v2TvTmplIpV6toV4MibCountersD7PEntry 83886080}

pr1645v2TvTmplIpV6toV4MibCountersD7PIfInNUCPkts OBJECT-TYPE
   SYNTAX      Counter64
   MAX-ACCESS  read-only
   STATUS      current
   DESCRIPTION
      "Path: tunnels.performance.ipV6toV4.mibCounters.d7Performance.ifInNUcastPkts

       64 bit unsigned wrappable counter."
   ::= {pr1645v2TvTmplIpV6toV4MibCountersD7PEntry 100663296}

pr1645v2TvTmplIpV6toV4MibCountersD7PIfInBCPkts OBJECT-TYPE
   SYNTAX      Counter64
   MAX-ACCESS  read-only
   STATUS      current
   DESCRIPTION
      "Path: tunnels.performance.ipV6toV4.mibCounters.d7Performance.ifInBcastPkts

       64 bit unsigned wrappable counter."
   ::= {pr1645v2TvTmplIpV6toV4MibCountersD7PEntry 419430400}

pr1645v2TvTmplIpV6toV4MibCountersD7PIfInMCPkts OBJECT-TYPE
   SYNTAX      Counter64
   MAX-ACCESS  read-only
   STATUS      current
   DESCRIPTION
      "Path: tunnels.performance.ipV6toV4.mibCounters.d7Performance.ifInMcastPkts

       64 bit unsigned wrappable counter."
   ::= {pr1645v2TvTmplIpV6toV4MibCountersD7PEntry 436207616}

pr1645v2TvTmplIpV6toV4MibCountersD7PIfInDiscards OBJECT-TYPE
   SYNTAX      Counter64
   MAX-ACCESS  read-only
   STATUS      current
   DESCRIPTION
      "Path: tunnels.performance.ipV6toV4.mibCounters.d7Performance.ifInDiscards

       64 bit unsigned wrappable counter."
   ::= {pr1645v2TvTmplIpV6toV4MibCountersD7PEntry 117440512}

pr1645v2TvTmplIpV6toV4MibCountersD7PIfInErrors OBJECT-TYPE
   SYNTAX      Counter64
   MAX-ACCESS  read-only
   STATUS      current
   DESCRIPTION
      "Path: tunnels.performance.ipV6toV4.mibCounters.d7Performance.ifInErrors

       64 bit unsigned wrappable counter."
   ::= {pr1645v2TvTmplIpV6toV4MibCountersD7PEntry 134217728}

pr1645v2TvTmplIpV6toV4MibCountersD7PIfInUnkwn OBJECT-TYPE
   SYNTAX      Counter64
   MAX-ACCESS  read-only
   STATUS      current
   DESCRIPTION
      "Path: tunnels.performance.ipV6toV4.mibCounters.d7Performance.ifInUnknownProtos

       64 bit unsigned wrappable counter."
   ::= {pr1645v2TvTmplIpV6toV4MibCountersD7PEntry 150994944}

pr1645v2TvTmplIpV6toV4MibCountersD7PInDropEx OBJECT-TYPE
   SYNTAX      Counter64
   MAX-ACCESS  read-only
   STATUS      current
   DESCRIPTION
      "Path: tunnels.performance.ipV6toV4.mibCounters.d7Performance.ifInDropLevelExceeded

       64 bit unsigned wrappable counter."
   ::= {pr1645v2TvTmplIpV6toV4MibCountersD7PEntry 335544320}

pr1645v2TvTmplIpV6toV4MibCountersD7PInDropNoMac OBJECT-TYPE
   SYNTAX      Counter64
   MAX-ACCESS  read-only
   STATUS      current
   DESCRIPTION
      "Path: tunnels.performance.ipV6toV4.mibCounters.d7Performance.fInDiscardsNoMacFit

       64 bit unsigned wrappable counter."
   ::= {pr1645v2TvTmplIpV6toV4MibCountersD7PEntry 301989888}

pr1645v2TvTmplIpV6toV4MibCountersD7PInDropNUCast OBJECT-TYPE
   SYNTAX      Counter64
   MAX-ACCESS  read-only
   STATUS      current
   DESCRIPTION
      "Path: tunnels.performance.ipV6toV4.mibCounters.d7Performance.fInDiscardsNUCast

       64 bit unsigned wrappable counter."
   ::= {pr1645v2TvTmplIpV6toV4MibCountersD7PEntry 318767104}

pr1645v2TvTmplIpV6toV4MibCountersD7PInDropFilter OBJECT-TYPE
   SYNTAX      Counter64
   MAX-ACCESS  read-only
   STATUS      current
   DESCRIPTION
      "Path: tunnels.performance.ipV6toV4.mibCounters.d7Performance.fInDiscardsFilter

       64 bit unsigned wrappable counter."
   ::= {pr1645v2TvTmplIpV6toV4MibCountersD7PEntry 385875968}

pr1645v2TvTmplIpV6toV4MibCountersD7PIfInBandwidth OBJECT-TYPE
   SYNTAX      Integer32
   MAX-ACCESS  read-only
   STATUS      current
   DESCRIPTION
      "Path: tunnels.performance.ipV6toV4.mibCounters.d7Performance.ifInBandwidth

       unit name = bps
       formula = 8 * ; 8 /"
   ::= {pr1645v2TvTmplIpV6toV4MibCountersD7PEntry 268435456}

pr1645v2TvTmplIpV6toV4MibCountersD7PIfOutOctets OBJECT-TYPE
   SYNTAX      Counter64
   MAX-ACCESS  read-only
   STATUS      current
   DESCRIPTION
      "Path: tunnels.performance.ipV6toV4.mibCounters.d7Performance.ifOutOctets

       64 bit unsigned wrappable counter."
   ::= {pr1645v2TvTmplIpV6toV4MibCountersD7PEntry 167772160}

pr1645v2TvTmplIpV6toV4MibCountersD7PIfOutUCPkts OBJECT-TYPE
   SYNTAX      Counter64
   MAX-ACCESS  read-only
   STATUS      current
   DESCRIPTION
      "Path: tunnels.performance.ipV6toV4.mibCounters.d7Performance.ifOutUcastPkts

       64 bit unsigned wrappable counter."
   ::= {pr1645v2TvTmplIpV6toV4MibCountersD7PEntry 184549376}

pr1645v2TvTmplIpV6toV4MibCountersD7PIfOutNUCPkts OBJECT-TYPE
   SYNTAX      Counter64
   MAX-ACCESS  read-only
   STATUS      current
   DESCRIPTION
      "Path: tunnels.performance.ipV6toV4.mibCounters.d7Performance.ifOutNUcastPkts

       64 bit unsigned wrappable counter."
   ::= {pr1645v2TvTmplIpV6toV4MibCountersD7PEntry 201326592}

pr1645v2TvTmplIpV6toV4MibCountersD7PIfOutBCPkts OBJECT-TYPE
   SYNTAX      Counter64
   MAX-ACCESS  read-only
   STATUS      current
   DESCRIPTION
      "Path: tunnels.performance.ipV6toV4.mibCounters.d7Performance.ifOutBcastPkts

       64 bit unsigned wrappable counter."
   ::= {pr1645v2TvTmplIpV6toV4MibCountersD7PEntry 452984832}

pr1645v2TvTmplIpV6toV4MibCountersD7PIfOutMCPkts OBJECT-TYPE
   SYNTAX      Counter64
   MAX-ACCESS  read-only
   STATUS      current
   DESCRIPTION
      "Path: tunnels.performance.ipV6toV4.mibCounters.d7Performance.ifOutMcastPkts

       64 bit unsigned wrappable counter."
   ::= {pr1645v2TvTmplIpV6toV4MibCountersD7PEntry 469762048}

pr1645v2TvTmplIpV6toV4MibCountersD7PIfOutDiscards OBJECT-TYPE
   SYNTAX      Counter64
   MAX-ACCESS  read-only
   STATUS      current
   DESCRIPTION
      "Path: tunnels.performance.ipV6toV4.mibCounters.d7Performance.ifOutDiscards

       64 bit unsigned wrappable counter."
   ::= {pr1645v2TvTmplIpV6toV4MibCountersD7PEntry 218103808}

pr1645v2TvTmplIpV6toV4MibCountersD7PIfOutErrors OBJECT-TYPE
   SYNTAX      Counter64
   MAX-ACCESS  read-only
   STATUS      current
   DESCRIPTION
      "Path: tunnels.performance.ipV6toV4.mibCounters.d7Performance.ifOutErrors

       64 bit unsigned wrappable counter."
   ::= {pr1645v2TvTmplIpV6toV4MibCountersD7PEntry 234881024}

pr1645v2TvTmplIpV6toV4MibCountersD7POutDropEx OBJECT-TYPE
   SYNTAX      Counter64
   MAX-ACCESS  read-only
   STATUS      current
   DESCRIPTION
      "Path: tunnels.performance.ipV6toV4.mibCounters.d7Performance.ifOutDropLevelExceeded

       64 bit unsigned wrappable counter."
   ::= {pr1645v2TvTmplIpV6toV4MibCountersD7PEntry 352321536}

pr1645v2TvTmplIpV6toV4MibCountersD7POutDropNoArp OBJECT-TYPE
   SYNTAX      Counter64
   MAX-ACCESS  read-only
   STATUS      current
   DESCRIPTION
      "Path: tunnels.performance.ipV6toV4.mibCounters.d7Performance.ifOutDiscardsNoArp

       64 bit unsigned wrappable counter."
   ::= {pr1645v2TvTmplIpV6toV4MibCountersD7PEntry 369098752}

pr1645v2TvTmplIpV6toV4MibCountersD7POutDropFilter OBJECT-TYPE
   SYNTAX      Counter64
   MAX-ACCESS  read-only
   STATUS      current
   DESCRIPTION
      "Path: tunnels.performance.ipV6toV4.mibCounters.d7Performance.ifOutDiscardsFilter

       64 bit unsigned wrappable counter."
   ::= {pr1645v2TvTmplIpV6toV4MibCountersD7PEntry 402653184}

pr1645v2TvTmplIpV6toV4MibCountersD7PIfOutBandwidth OBJECT-TYPE
   SYNTAX      Integer32
   MAX-ACCESS  read-only
   STATUS      current
   DESCRIPTION
      "Path: tunnels.performance.ipV6toV4.mibCounters.d7Performance.ifOutBandwidth

       unit name = bps
       formula = 8 * ; 8 /"
   ::= {pr1645v2TvTmplIpV6toV4MibCountersD7PEntry 285212672}

pr1645v2TvTmplIpV6toV4MibCountersD7PIfErrSec OBJECT-TYPE
   SYNTAX      Counter32
   MAX-ACCESS  read-only
   STATUS      current
   DESCRIPTION
      "Path: tunnels.performance.ipV6toV4.mibCounters.d7Performance.ifErrSec

       32 bit unsigned wrappable counter."
   ::= {pr1645v2TvTmplIpV6toV4MibCountersD7PEntry 251658240}


pr1645v2TvTmplVxLanTunnels OBJECT IDENTIFIER ::= {pr1645v2TvTmpl 45}

pr1645v2TvTmplVxLanTunnelsSSCTable OBJECT-TYPE
   SYNTAX      SEQUENCE OF Pr1645v2TvTmplVxLanTunnelsEntry
   MAX-ACCESS  not-accessible
   STATUS      current
   DESCRIPTION
      ""
   ::= {pr1645v2TvTmplVxLanTunnels 1}

pr1645v2TvTmplVxLanTunnelsEntry OBJECT-TYPE
   SYNTAX      Pr1645v2TvTmplVxLanTunnelsEntry
   MAX-ACCESS  not-accessible
   STATUS      current
   DESCRIPTION
      ""
   INDEX      { pr1645v2TvTmplVxLanTunnelsTableIx }
   ::= {pr1645v2TvTmplVxLanTunnelsSSCTable 1}

Pr1645v2TvTmplVxLanTunnelsEntry ::=
   SEQUENCE
      {
      pr1645v2TvTmplVxLanTunnelsTableIx
         TableIndex,
      pr1645v2TvTmplVxLanTunnelsName
         DisplayString,
      pr1645v2TvTmplVxLanTunnelsMCInOctets
         Counter64,
      pr1645v2TvTmplVxLanTunnelsMCInUcast
         Counter64,
      pr1645v2TvTmplVxLanTunnelsMCInNUcastPkts
         Counter64,
      pr1645v2TvTmplVxLanTunnelsMCInBcastPkts
         Counter64,
      pr1645v2TvTmplVxLanTunnelsMCInMcastPkts
         Counter64,
      pr1645v2TvTmplVxLanTunnelsMCInDiscards
         Counter64,
      pr1645v2TvTmplVxLanTunnelsMCInErrors
         Counter64,
      pr1645v2TvTmplVxLanTunnelsMCInUnknownProtos
         Counter64,
      pr1645v2TvTmplVxLanTunnelsMCInDropEx
         Counter64,
      pr1645v2TvTmplVxLanTunnelsMCInDropNoMac
         Counter64,
      pr1645v2TvTmplVxLanTunnelsMCInDropNUCast
         Counter64,
      pr1645v2TvTmplVxLanTunnelsMCInDropFilter
         Counter64,
      pr1645v2TvTmplVxLanTunnelsMCInBandwidth15sec
         Integer32,
      pr1645v2TvTmplVxLanTunnelsMCInBandwidth30sec
         Integer32,
      pr1645v2TvTmplVxLanTunnelsMCInBandwidth1min
         Integer32,
      pr1645v2TvTmplVxLanTunnelsMCInBandwidth2min
         Integer32,
      pr1645v2TvTmplVxLanTunnelsMCInBandwidth5min
         Integer32,
      pr1645v2TvTmplVxLanTunnelsMCOutOctets
         Counter64,
      pr1645v2TvTmplVxLanTunnelsMCOutUcastPkts
         Counter64,
      pr1645v2TvTmplVxLanTunnelsMCOutNUcastPkts
         Counter64,
      pr1645v2TvTmplVxLanTunnelsMCOutBcastPkts
         Counter64,
      pr1645v2TvTmplVxLanTunnelsMCOutMcastPkts
         Counter64,
      pr1645v2TvTmplVxLanTunnelsMCOutDiscards
         Counter64,
      pr1645v2TvTmplVxLanTunnelsMCOutErrors
         Counter64,
      pr1645v2TvTmplVxLanTunnelsMCOutQLen
         Counter32,
      pr1645v2TvTmplVxLanTunnelsMCOutDropEx
         Counter64,
      pr1645v2TvTmplVxLanTunnelsMCOutDropNoArp
         Counter64,
      pr1645v2TvTmplVxLanTunnelsMCOutDropFilter
         Counter64,
      pr1645v2TvTmplVxLanTunnelsMCOutBandwidth15sec
         Integer32,
      pr1645v2TvTmplVxLanTunnelsMCOutBandwidth30sec
         Integer32,
      pr1645v2TvTmplVxLanTunnelsMCOutBandwidth1min
         Integer32,
      pr1645v2TvTmplVxLanTunnelsMCOutBandwidth2min
         Integer32,
      pr1645v2TvTmplVxLanTunnelsMCOutBandwidth5min
         Integer32
      }

pr1645v2TvTmplVxLanTunnelsTableIx OBJECT-TYPE
   SYNTAX      TableIndex
   MAX-ACCESS  not-accessible
   STATUS      current
   DESCRIPTION
      ""
   ::= {pr1645v2TvTmplVxLanTunnelsEntry 11}

pr1645v2TvTmplVxLanTunnelsName OBJECT-TYPE
   SYNTAX      DisplayString
   MAX-ACCESS  read-only
   STATUS      current
   DESCRIPTION
      "Path: tunnels.performance.vxLanTunnels.name"
   ::= {pr1645v2TvTmplVxLanTunnelsEntry 16777216}

pr1645v2TvTmplVxLanTunnelsMCInOctets OBJECT-TYPE
   SYNTAX      Counter64
   MAX-ACCESS  read-only
   STATUS      current
   DESCRIPTION
      "Path: tunnels.performance.vxLanTunnels.mibCounters.ifInOctets

       64 bit unsigned wrappable counter."
   ::= {pr1645v2TvTmplVxLanTunnelsEntry 40697856}

pr1645v2TvTmplVxLanTunnelsMCInUcast OBJECT-TYPE
   SYNTAX      Counter64
   MAX-ACCESS  read-only
   STATUS      current
   DESCRIPTION
      "Path: tunnels.performance.vxLanTunnels.mibCounters.ifInUcastPkts

       64 bit unsigned wrappable counter."
   ::= {pr1645v2TvTmplVxLanTunnelsEntry 40763392}

pr1645v2TvTmplVxLanTunnelsMCInNUcastPkts OBJECT-TYPE
   SYNTAX      Counter64
   MAX-ACCESS  read-only
   STATUS      current
   DESCRIPTION
      "Path: tunnels.performance.vxLanTunnels.mibCounters.ifInNUcastPkts

       64 bit unsigned wrappable counter."
   ::= {pr1645v2TvTmplVxLanTunnelsEntry 40828928}

pr1645v2TvTmplVxLanTunnelsMCInBcastPkts OBJECT-TYPE
   SYNTAX      Counter64
   MAX-ACCESS  read-only
   STATUS      current
   DESCRIPTION
      "Path: tunnels.performance.vxLanTunnels.mibCounters.ifInBcastPkts

       64 bit unsigned wrappable counter."
   ::= {pr1645v2TvTmplVxLanTunnelsEntry 47382528}

pr1645v2TvTmplVxLanTunnelsMCInMcastPkts OBJECT-TYPE
   SYNTAX      Counter64
   MAX-ACCESS  read-only
   STATUS      current
   DESCRIPTION
      "Path: tunnels.performance.vxLanTunnels.mibCounters.ifInMcastPkts

       64 bit unsigned wrappable counter."
   ::= {pr1645v2TvTmplVxLanTunnelsEntry 48037888}

pr1645v2TvTmplVxLanTunnelsMCInDiscards OBJECT-TYPE
   SYNTAX      Counter64
   MAX-ACCESS  read-only
   STATUS      current
   DESCRIPTION
      "Path: tunnels.performance.vxLanTunnels.mibCounters.ifInDiscards

       64 bit unsigned wrappable counter."
   ::= {pr1645v2TvTmplVxLanTunnelsEntry 40894464}

pr1645v2TvTmplVxLanTunnelsMCInErrors OBJECT-TYPE
   SYNTAX      Counter64
   MAX-ACCESS  read-only
   STATUS      current
   DESCRIPTION
      "Path: tunnels.performance.vxLanTunnels.mibCounters.ifInErrors

       64 bit unsigned wrappable counter."
   ::= {pr1645v2TvTmplVxLanTunnelsEntry 40960000}

pr1645v2TvTmplVxLanTunnelsMCInUnknownProtos OBJECT-TYPE
   SYNTAX      Counter64
   MAX-ACCESS  read-only
   STATUS      current
   DESCRIPTION
      "Path: tunnels.performance.vxLanTunnels.mibCounters.ifInUnknownProtos

       64 bit unsigned wrappable counter."
   ::= {pr1645v2TvTmplVxLanTunnelsEntry 41025536}

pr1645v2TvTmplVxLanTunnelsMCInDropEx OBJECT-TYPE
   SYNTAX      Counter64
   MAX-ACCESS  read-only
   STATUS      current
   DESCRIPTION
      "Path: tunnels.performance.vxLanTunnels.mibCounters.ifInDropLevelExceeded

       64 bit unsigned wrappable counter."
   ::= {pr1645v2TvTmplVxLanTunnelsEntry 42074112}

pr1645v2TvTmplVxLanTunnelsMCInDropNoMac OBJECT-TYPE
   SYNTAX      Counter64
   MAX-ACCESS  read-only
   STATUS      current
   DESCRIPTION
      "Path: tunnels.performance.vxLanTunnels.mibCounters.ifInDiscardsNoMacFit

       64 bit unsigned wrappable counter."
   ::= {pr1645v2TvTmplVxLanTunnelsEntry 42270720}

pr1645v2TvTmplVxLanTunnelsMCInDropNUCast OBJECT-TYPE
   SYNTAX      Counter64
   MAX-ACCESS  read-only
   STATUS      current
   DESCRIPTION
      "Path: tunnels.performance.vxLanTunnels.mibCounters.ifInDiscardsNUCast

       64 bit unsigned wrappable counter."
   ::= {pr1645v2TvTmplVxLanTunnelsEntry 42467328}

pr1645v2TvTmplVxLanTunnelsMCInDropFilter OBJECT-TYPE
   SYNTAX      Counter64
   MAX-ACCESS  read-only
   STATUS      current
   DESCRIPTION
      "Path: tunnels.performance.vxLanTunnels.mibCounters.ifInDiscardsFilter

       64 bit unsigned wrappable counter."
   ::= {pr1645v2TvTmplVxLanTunnelsEntry 42532864}

pr1645v2TvTmplVxLanTunnelsMCInBandwidth15sec OBJECT-TYPE
   SYNTAX      Integer32
   MAX-ACCESS  read-only
   STATUS      current
   DESCRIPTION
      "Path: tunnels.performance.vxLanTunnels.mibCounters.ifInBandwidth.15sec

       unit name = bps
       formula = 8 * ; 8 /"
   ::= {pr1645v2TvTmplVxLanTunnelsEntry 45417728}

pr1645v2TvTmplVxLanTunnelsMCInBandwidth30sec OBJECT-TYPE
   SYNTAX      Integer32
   MAX-ACCESS  read-only
   STATUS      current
   DESCRIPTION
      "Path: tunnels.performance.vxLanTunnels.mibCounters.ifInBandwidth.30sec

       unit name = bps
       formula = 8 * ; 8 /"
   ::= {pr1645v2TvTmplVxLanTunnelsEntry 45419008}

pr1645v2TvTmplVxLanTunnelsMCInBandwidth1min OBJECT-TYPE
   SYNTAX      Integer32
   MAX-ACCESS  read-only
   STATUS      current
   DESCRIPTION
      "Path: tunnels.performance.vxLanTunnels.mibCounters.ifInBandwidth.1min

       unit name = bps
       formula = 8 * ; 8 /"
   ::= {pr1645v2TvTmplVxLanTunnelsEntry 45421568}

pr1645v2TvTmplVxLanTunnelsMCInBandwidth2min OBJECT-TYPE
   SYNTAX      Integer32
   MAX-ACCESS  read-only
   STATUS      current
   DESCRIPTION
      "Path: tunnels.performance.vxLanTunnels.mibCounters.ifInBandwidth.2min

       unit name = bps
       formula = 8 * ; 8 /"
   ::= {pr1645v2TvTmplVxLanTunnelsEntry 45426688}

pr1645v2TvTmplVxLanTunnelsMCInBandwidth5min OBJECT-TYPE
   SYNTAX      Integer32
   MAX-ACCESS  read-only
   STATUS      current
   DESCRIPTION
      "Path: tunnels.performance.vxLanTunnels.mibCounters.ifInBandwidth.5min

       unit name = bps
       formula = 8 * ; 8 /"
   ::= {pr1645v2TvTmplVxLanTunnelsEntry 45442048}

pr1645v2TvTmplVxLanTunnelsMCOutOctets OBJECT-TYPE
   SYNTAX      Counter64
   MAX-ACCESS  read-only
   STATUS      current
   DESCRIPTION
      "Path: tunnels.performance.vxLanTunnels.mibCounters.ifOutOctets

       64 bit unsigned wrappable counter."
   ::= {pr1645v2TvTmplVxLanTunnelsEntry 41091072}

pr1645v2TvTmplVxLanTunnelsMCOutUcastPkts OBJECT-TYPE
   SYNTAX      Counter64
   MAX-ACCESS  read-only
   STATUS      current
   DESCRIPTION
      "Path: tunnels.performance.vxLanTunnels.mibCounters.ifOutUcastPkts

       64 bit unsigned wrappable counter."
   ::= {pr1645v2TvTmplVxLanTunnelsEntry 41156608}

pr1645v2TvTmplVxLanTunnelsMCOutNUcastPkts OBJECT-TYPE
   SYNTAX      Counter64
   MAX-ACCESS  read-only
   STATUS      current
   DESCRIPTION
      "Path: tunnels.performance.vxLanTunnels.mibCounters.ifOutNUcastPkts

       64 bit unsigned wrappable counter."
   ::= {pr1645v2TvTmplVxLanTunnelsEntry 41222144}

pr1645v2TvTmplVxLanTunnelsMCOutBcastPkts OBJECT-TYPE
   SYNTAX      Counter64
   MAX-ACCESS  read-only
   STATUS      current
   DESCRIPTION
      "Path: tunnels.performance.vxLanTunnels.mibCounters.ifOutBcastPkts

       64 bit unsigned wrappable counter."
   ::= {pr1645v2TvTmplVxLanTunnelsEntry 47775744}

pr1645v2TvTmplVxLanTunnelsMCOutMcastPkts OBJECT-TYPE
   SYNTAX      Counter64
   MAX-ACCESS  read-only
   STATUS      current
   DESCRIPTION
      "Path: tunnels.performance.vxLanTunnels.mibCounters.ifOutMcastPkts

       64 bit unsigned wrappable counter."
   ::= {pr1645v2TvTmplVxLanTunnelsEntry 48431104}

pr1645v2TvTmplVxLanTunnelsMCOutDiscards OBJECT-TYPE
   SYNTAX      Counter64
   MAX-ACCESS  read-only
   STATUS      current
   DESCRIPTION
      "Path: tunnels.performance.vxLanTunnels.mibCounters.ifOutDiscards

       64 bit unsigned wrappable counter."
   ::= {pr1645v2TvTmplVxLanTunnelsEntry 41287680}

pr1645v2TvTmplVxLanTunnelsMCOutErrors OBJECT-TYPE
   SYNTAX      Counter64
   MAX-ACCESS  read-only
   STATUS      current
   DESCRIPTION
      "Path: tunnels.performance.vxLanTunnels.mibCounters.ifOutErrors

       64 bit unsigned wrappable counter."
   ::= {pr1645v2TvTmplVxLanTunnelsEntry 41353216}

pr1645v2TvTmplVxLanTunnelsMCOutQLen OBJECT-TYPE
   SYNTAX      Counter32
   MAX-ACCESS  read-only
   STATUS      current
   DESCRIPTION
      "Path: tunnels.performance.vxLanTunnels.mibCounters.ifOutQLen

       32 bit unsigned wrappable counter."
   ::= {pr1645v2TvTmplVxLanTunnelsEntry 41418752}

pr1645v2TvTmplVxLanTunnelsMCOutDropEx OBJECT-TYPE
   SYNTAX      Counter64
   MAX-ACCESS  read-only
   STATUS      current
   DESCRIPTION
      "Path: tunnels.performance.vxLanTunnels.mibCounters.ifOutDropLevelExceeded

       64 bit unsigned wrappable counter."
   ::= {pr1645v2TvTmplVxLanTunnelsEntry 41484288}

pr1645v2TvTmplVxLanTunnelsMCOutDropNoArp OBJECT-TYPE
   SYNTAX      Counter64
   MAX-ACCESS  read-only
   STATUS      current
   DESCRIPTION
      "Path: tunnels.performance.vxLanTunnels.mibCounters.ifOutDiscardsNoArp

       64 bit unsigned wrappable counter."
   ::= {pr1645v2TvTmplVxLanTunnelsEntry 42336256}

pr1645v2TvTmplVxLanTunnelsMCOutDropFilter OBJECT-TYPE
   SYNTAX      Counter64
   MAX-ACCESS  read-only
   STATUS      current
   DESCRIPTION
      "Path: tunnels.performance.vxLanTunnels.mibCounters.ifOutDiscardsFilter

       64 bit unsigned wrappable counter."
   ::= {pr1645v2TvTmplVxLanTunnelsEntry 42598400}

pr1645v2TvTmplVxLanTunnelsMCOutBandwidth15sec OBJECT-TYPE
   SYNTAX      Integer32
   MAX-ACCESS  read-only
   STATUS      current
   DESCRIPTION
      "Path: tunnels.performance.vxLanTunnels.mibCounters.ifOutBandwidth.15sec

       unit name = bps
       formula = 8 * ; 8 /"
   ::= {pr1645v2TvTmplVxLanTunnelsEntry 45483264}

pr1645v2TvTmplVxLanTunnelsMCOutBandwidth30sec OBJECT-TYPE
   SYNTAX      Integer32
   MAX-ACCESS  read-only
   STATUS      current
   DESCRIPTION
      "Path: tunnels.performance.vxLanTunnels.mibCounters.ifOutBandwidth.30sec

       unit name = bps
       formula = 8 * ; 8 /"
   ::= {pr1645v2TvTmplVxLanTunnelsEntry 45484544}

pr1645v2TvTmplVxLanTunnelsMCOutBandwidth1min OBJECT-TYPE
   SYNTAX      Integer32
   MAX-ACCESS  read-only
   STATUS      current
   DESCRIPTION
      "Path: tunnels.performance.vxLanTunnels.mibCounters.ifOutBandwidth.1min

       unit name = bps
       formula = 8 * ; 8 /"
   ::= {pr1645v2TvTmplVxLanTunnelsEntry 45487104}

pr1645v2TvTmplVxLanTunnelsMCOutBandwidth2min OBJECT-TYPE
   SYNTAX      Integer32
   MAX-ACCESS  read-only
   STATUS      current
   DESCRIPTION
      "Path: tunnels.performance.vxLanTunnels.mibCounters.ifOutBandwidth.2min

       unit name = bps
       formula = 8 * ; 8 /"
   ::= {pr1645v2TvTmplVxLanTunnelsEntry 45492224}

pr1645v2TvTmplVxLanTunnelsMCOutBandwidth5min OBJECT-TYPE
   SYNTAX      Integer32
   MAX-ACCESS  read-only
   STATUS      current
   DESCRIPTION
      "Path: tunnels.performance.vxLanTunnels.mibCounters.ifOutBandwidth.5min

       unit name = bps
       formula = 8 * ; 8 /"
   ::= {pr1645v2TvTmplVxLanTunnelsEntry 45507584}

pr1645v2TvTmplVxLanTunnelsMCH2P OBJECT-TYPE
   SYNTAX      SEQUENCE OF Pr1645v2TvTmplVxLanTunnelsMCH2PEntry
   MAX-ACCESS  not-accessible
   STATUS      current
   DESCRIPTION
      ""
   ::= {pr1645v2TvTmplVxLanTunnels 41549824}

pr1645v2TvTmplVxLanTunnelsMCH2PEntry OBJECT-TYPE
   SYNTAX      Pr1645v2TvTmplVxLanTunnelsMCH2PEntry
   MAX-ACCESS  not-accessible
   STATUS      current
   DESCRIPTION
      ""
   INDEX      { pr1645v2TvTmplVxLanTunnelsTableIx,
                pr1645v2TvTmplVxLanTunnelsMCH2PTableIx }
   ::= {pr1645v2TvTmplVxLanTunnelsMCH2P 1}

Pr1645v2TvTmplVxLanTunnelsMCH2PEntry ::=
   SEQUENCE
      {
      pr1645v2TvTmplVxLanTunnelsMCH2PTableIx
         TableIndex,
      pr1645v2TvTmplVxLanTunnelsMCH2PSysUpTime
         TimeTicks,
      pr1645v2TvTmplVxLanTunnelsMCH2PIfUpTime
         TimeTicks,
      pr1645v2TvTmplVxLanTunnelsMCH2PIfStatChanges
         Counter32,
      pr1645v2TvTmplVxLanTunnelsMCH2PIfInOctets
         Counter64,
      pr1645v2TvTmplVxLanTunnelsMCH2PIfInUCPkts
         Counter64,
      pr1645v2TvTmplVxLanTunnelsMCH2PIfInNUCPkts
         Counter64,
      pr1645v2TvTmplVxLanTunnelsMCH2PIfInBCPkts
         Counter64,
      pr1645v2TvTmplVxLanTunnelsMCH2PIfInMCPkts
         Counter64,
      pr1645v2TvTmplVxLanTunnelsMCH2PIfInDiscards
         Counter64,
      pr1645v2TvTmplVxLanTunnelsMCH2PIfInErrors
         Counter64,
      pr1645v2TvTmplVxLanTunnelsMCH2PIfInUnkwn
         Counter64,
      pr1645v2TvTmplVxLanTunnelsMCH2PInDropEx
         Counter64,
      pr1645v2TvTmplVxLanTunnelsMCH2PInDropNoMac
         Counter64,
      pr1645v2TvTmplVxLanTunnelsMCH2PInDropNUCast
         Counter64,
      pr1645v2TvTmplVxLanTunnelsMCH2PInDropFilter
         Counter64,
      pr1645v2TvTmplVxLanTunnelsMCH2PIfInBandwidth
         Integer32,
      pr1645v2TvTmplVxLanTunnelsMCH2PIfOutOctets
         Counter64,
      pr1645v2TvTmplVxLanTunnelsMCH2PIfOutUCPkts
         Counter64,
      pr1645v2TvTmplVxLanTunnelsMCH2PIfOutNUCPkts
         Counter64,
      pr1645v2TvTmplVxLanTunnelsMCH2PIfOutBCPkts
         Counter64,
      pr1645v2TvTmplVxLanTunnelsMCH2PIfOutMCPkts
         Counter64,
      pr1645v2TvTmplVxLanTunnelsMCH2PIfOutDiscards
         Counter64,
      pr1645v2TvTmplVxLanTunnelsMCH2PIfOutErrors
         Counter64,
      pr1645v2TvTmplVxLanTunnelsMCH2POutDropEx
         Counter64,
      pr1645v2TvTmplVxLanTunnelsMCH2POutDropNoArp
         Counter64,
      pr1645v2TvTmplVxLanTunnelsMCH2POutDropFilter
         Counter64,
      pr1645v2TvTmplVxLanTunnelsMCH2PIfOutBandwidth
         Integer32,
      pr1645v2TvTmplVxLanTunnelsMCH2PIfErrSec
         Counter32
      }

pr1645v2TvTmplVxLanTunnelsMCH2PTableIx OBJECT-TYPE
   SYNTAX      TableIndex
   MAX-ACCESS  not-accessible
   STATUS      current
   DESCRIPTION
      ""
   ::= {pr1645v2TvTmplVxLanTunnelsMCH2PEntry 11}

pr1645v2TvTmplVxLanTunnelsMCH2PSysUpTime OBJECT-TYPE
   SYNTAX      TimeTicks
   MAX-ACCESS  read-only
   STATUS      current
   DESCRIPTION
      "Path: tunnels.performance.vxLanTunnels.mibCounters.h2Performance.sysUpTime

       Time in centi-second."
   ::= {pr1645v2TvTmplVxLanTunnelsMCH2PEntry 16777216}

pr1645v2TvTmplVxLanTunnelsMCH2PIfUpTime OBJECT-TYPE
   SYNTAX      TimeTicks
   MAX-ACCESS  read-only
   STATUS      current
   DESCRIPTION
      "Path: tunnels.performance.vxLanTunnels.mibCounters.h2Performance.ifUpTime

       Time in centi-second."
   ::= {pr1645v2TvTmplVxLanTunnelsMCH2PEntry 33554432}

pr1645v2TvTmplVxLanTunnelsMCH2PIfStatChanges OBJECT-TYPE
   SYNTAX      Counter32
   MAX-ACCESS  read-only
   STATUS      current
   DESCRIPTION
      "Path: tunnels.performance.vxLanTunnels.mibCounters.h2Performance.ifStatusChanges

       32 bit unsigned wrappable counter."
   ::= {pr1645v2TvTmplVxLanTunnelsMCH2PEntry 50331648}

pr1645v2TvTmplVxLanTunnelsMCH2PIfInOctets OBJECT-TYPE
   SYNTAX      Counter64
   MAX-ACCESS  read-only
   STATUS      current
   DESCRIPTION
      "Path: tunnels.performance.vxLanTunnels.mibCounters.h2Performance.ifInOctets

       64 bit unsigned wrappable counter."
   ::= {pr1645v2TvTmplVxLanTunnelsMCH2PEntry 67108864}

pr1645v2TvTmplVxLanTunnelsMCH2PIfInUCPkts OBJECT-TYPE
   SYNTAX      Counter64
   MAX-ACCESS  read-only
   STATUS      current
   DESCRIPTION
      "Path: tunnels.performance.vxLanTunnels.mibCounters.h2Performance.ifInUcastPkts

       64 bit unsigned wrappable counter."
   ::= {pr1645v2TvTmplVxLanTunnelsMCH2PEntry 83886080}

pr1645v2TvTmplVxLanTunnelsMCH2PIfInNUCPkts OBJECT-TYPE
   SYNTAX      Counter64
   MAX-ACCESS  read-only
   STATUS      current
   DESCRIPTION
      "Path: tunnels.performance.vxLanTunnels.mibCounters.h2Performance.ifInNUcastPkts

       64 bit unsigned wrappable counter."
   ::= {pr1645v2TvTmplVxLanTunnelsMCH2PEntry 100663296}

pr1645v2TvTmplVxLanTunnelsMCH2PIfInBCPkts OBJECT-TYPE
   SYNTAX      Counter64
   MAX-ACCESS  read-only
   STATUS      current
   DESCRIPTION
      "Path: tunnels.performance.vxLanTunnels.mibCounters.h2Performance.ifInBcastPkts

       64 bit unsigned wrappable counter."
   ::= {pr1645v2TvTmplVxLanTunnelsMCH2PEntry 419430400}

pr1645v2TvTmplVxLanTunnelsMCH2PIfInMCPkts OBJECT-TYPE
   SYNTAX      Counter64
   MAX-ACCESS  read-only
   STATUS      current
   DESCRIPTION
      "Path: tunnels.performance.vxLanTunnels.mibCounters.h2Performance.ifInMcastPkts

       64 bit unsigned wrappable counter."
   ::= {pr1645v2TvTmplVxLanTunnelsMCH2PEntry 436207616}

pr1645v2TvTmplVxLanTunnelsMCH2PIfInDiscards OBJECT-TYPE
   SYNTAX      Counter64
   MAX-ACCESS  read-only
   STATUS      current
   DESCRIPTION
      "Path: tunnels.performance.vxLanTunnels.mibCounters.h2Performance.ifInDiscards

       64 bit unsigned wrappable counter."
   ::= {pr1645v2TvTmplVxLanTunnelsMCH2PEntry 117440512}

pr1645v2TvTmplVxLanTunnelsMCH2PIfInErrors OBJECT-TYPE
   SYNTAX      Counter64
   MAX-ACCESS  read-only
   STATUS      current
   DESCRIPTION
      "Path: tunnels.performance.vxLanTunnels.mibCounters.h2Performance.ifInErrors

       64 bit unsigned wrappable counter."
   ::= {pr1645v2TvTmplVxLanTunnelsMCH2PEntry 134217728}

pr1645v2TvTmplVxLanTunnelsMCH2PIfInUnkwn OBJECT-TYPE
   SYNTAX      Counter64
   MAX-ACCESS  read-only
   STATUS      current
   DESCRIPTION
      "Path: tunnels.performance.vxLanTunnels.mibCounters.h2Performance.ifInUnknownProtos

       64 bit unsigned wrappable counter."
   ::= {pr1645v2TvTmplVxLanTunnelsMCH2PEntry 150994944}

pr1645v2TvTmplVxLanTunnelsMCH2PInDropEx OBJECT-TYPE
   SYNTAX      Counter64
   MAX-ACCESS  read-only
   STATUS      current
   DESCRIPTION
      "Path: tunnels.performance.vxLanTunnels.mibCounters.h2Performance.ifInDropLevelExceeded

       64 bit unsigned wrappable counter."
   ::= {pr1645v2TvTmplVxLanTunnelsMCH2PEntry 335544320}

pr1645v2TvTmplVxLanTunnelsMCH2PInDropNoMac OBJECT-TYPE
   SYNTAX      Counter64
   MAX-ACCESS  read-only
   STATUS      current
   DESCRIPTION
      "Path: tunnels.performance.vxLanTunnels.mibCounters.h2Performance.fInDiscardsNoMacFit

       64 bit unsigned wrappable counter."
   ::= {pr1645v2TvTmplVxLanTunnelsMCH2PEntry 301989888}

pr1645v2TvTmplVxLanTunnelsMCH2PInDropNUCast OBJECT-TYPE
   SYNTAX      Counter64
   MAX-ACCESS  read-only
   STATUS      current
   DESCRIPTION
      "Path: tunnels.performance.vxLanTunnels.mibCounters.h2Performance.fInDiscardsNUCast

       64 bit unsigned wrappable counter."
   ::= {pr1645v2TvTmplVxLanTunnelsMCH2PEntry 318767104}

pr1645v2TvTmplVxLanTunnelsMCH2PInDropFilter OBJECT-TYPE
   SYNTAX      Counter64
   MAX-ACCESS  read-only
   STATUS      current
   DESCRIPTION
      "Path: tunnels.performance.vxLanTunnels.mibCounters.h2Performance.fInDiscardsFilter

       64 bit unsigned wrappable counter."
   ::= {pr1645v2TvTmplVxLanTunnelsMCH2PEntry 385875968}

pr1645v2TvTmplVxLanTunnelsMCH2PIfInBandwidth OBJECT-TYPE
   SYNTAX      Integer32
   MAX-ACCESS  read-only
   STATUS      current
   DESCRIPTION
      "Path: tunnels.performance.vxLanTunnels.mibCounters.h2Performance.ifInBandwidth

       unit name = bps
       formula = 8 * ; 8 /"
   ::= {pr1645v2TvTmplVxLanTunnelsMCH2PEntry 268435456}

pr1645v2TvTmplVxLanTunnelsMCH2PIfOutOctets OBJECT-TYPE
   SYNTAX      Counter64
   MAX-ACCESS  read-only
   STATUS      current
   DESCRIPTION
      "Path: tunnels.performance.vxLanTunnels.mibCounters.h2Performance.ifOutOctets

       64 bit unsigned wrappable counter."
   ::= {pr1645v2TvTmplVxLanTunnelsMCH2PEntry 167772160}

pr1645v2TvTmplVxLanTunnelsMCH2PIfOutUCPkts OBJECT-TYPE
   SYNTAX      Counter64
   MAX-ACCESS  read-only
   STATUS      current
   DESCRIPTION
      "Path: tunnels.performance.vxLanTunnels.mibCounters.h2Performance.ifOutUcastPkts

       64 bit unsigned wrappable counter."
   ::= {pr1645v2TvTmplVxLanTunnelsMCH2PEntry 184549376}

pr1645v2TvTmplVxLanTunnelsMCH2PIfOutNUCPkts OBJECT-TYPE
   SYNTAX      Counter64
   MAX-ACCESS  read-only
   STATUS      current
   DESCRIPTION
      "Path: tunnels.performance.vxLanTunnels.mibCounters.h2Performance.ifOutNUcastPkts

       64 bit unsigned wrappable counter."
   ::= {pr1645v2TvTmplVxLanTunnelsMCH2PEntry 201326592}

pr1645v2TvTmplVxLanTunnelsMCH2PIfOutBCPkts OBJECT-TYPE
   SYNTAX      Counter64
   MAX-ACCESS  read-only
   STATUS      current
   DESCRIPTION
      "Path: tunnels.performance.vxLanTunnels.mibCounters.h2Performance.ifOutBcastPkts

       64 bit unsigned wrappable counter."
   ::= {pr1645v2TvTmplVxLanTunnelsMCH2PEntry 452984832}

pr1645v2TvTmplVxLanTunnelsMCH2PIfOutMCPkts OBJECT-TYPE
   SYNTAX      Counter64
   MAX-ACCESS  read-only
   STATUS      current
   DESCRIPTION
      "Path: tunnels.performance.vxLanTunnels.mibCounters.h2Performance.ifOutMcastPkts

       64 bit unsigned wrappable counter."
   ::= {pr1645v2TvTmplVxLanTunnelsMCH2PEntry 469762048}

pr1645v2TvTmplVxLanTunnelsMCH2PIfOutDiscards OBJECT-TYPE
   SYNTAX      Counter64
   MAX-ACCESS  read-only
   STATUS      current
   DESCRIPTION
      "Path: tunnels.performance.vxLanTunnels.mibCounters.h2Performance.ifOutDiscards

       64 bit unsigned wrappable counter."
   ::= {pr1645v2TvTmplVxLanTunnelsMCH2PEntry 218103808}

pr1645v2TvTmplVxLanTunnelsMCH2PIfOutErrors OBJECT-TYPE
   SYNTAX      Counter64
   MAX-ACCESS  read-only
   STATUS      current
   DESCRIPTION
      "Path: tunnels.performance.vxLanTunnels.mibCounters.h2Performance.ifOutErrors

       64 bit unsigned wrappable counter."
   ::= {pr1645v2TvTmplVxLanTunnelsMCH2PEntry 234881024}

pr1645v2TvTmplVxLanTunnelsMCH2POutDropEx OBJECT-TYPE
   SYNTAX      Counter64
   MAX-ACCESS  read-only
   STATUS      current
   DESCRIPTION
      "Path: tunnels.performance.vxLanTunnels.mibCounters.h2Performance.ifOutDropLevelExceeded

       64 bit unsigned wrappable counter."
   ::= {pr1645v2TvTmplVxLanTunnelsMCH2PEntry 352321536}

pr1645v2TvTmplVxLanTunnelsMCH2POutDropNoArp OBJECT-TYPE
   SYNTAX      Counter64
   MAX-ACCESS  read-only
   STATUS      current
   DESCRIPTION
      "Path: tunnels.performance.vxLanTunnels.mibCounters.h2Performance.ifOutDiscardsNoArp

       64 bit unsigned wrappable counter."
   ::= {pr1645v2TvTmplVxLanTunnelsMCH2PEntry 369098752}

pr1645v2TvTmplVxLanTunnelsMCH2POutDropFilter OBJECT-TYPE
   SYNTAX      Counter64
   MAX-ACCESS  read-only
   STATUS      current
   DESCRIPTION
      "Path: tunnels.performance.vxLanTunnels.mibCounters.h2Performance.ifOutDiscardsFilter

       64 bit unsigned wrappable counter."
   ::= {pr1645v2TvTmplVxLanTunnelsMCH2PEntry 402653184}

pr1645v2TvTmplVxLanTunnelsMCH2PIfOutBandwidth OBJECT-TYPE
   SYNTAX      Integer32
   MAX-ACCESS  read-only
   STATUS      current
   DESCRIPTION
      "Path: tunnels.performance.vxLanTunnels.mibCounters.h2Performance.ifOutBandwidth

       unit name = bps
       formula = 8 * ; 8 /"
   ::= {pr1645v2TvTmplVxLanTunnelsMCH2PEntry 285212672}

pr1645v2TvTmplVxLanTunnelsMCH2PIfErrSec OBJECT-TYPE
   SYNTAX      Counter32
   MAX-ACCESS  read-only
   STATUS      current
   DESCRIPTION
      "Path: tunnels.performance.vxLanTunnels.mibCounters.h2Performance.ifErrSec

       32 bit unsigned wrappable counter."
   ::= {pr1645v2TvTmplVxLanTunnelsMCH2PEntry 251658240}

pr1645v2TvTmplVxLanTunnelsMCH24P OBJECT-TYPE
   SYNTAX      SEQUENCE OF Pr1645v2TvTmplVxLanTunnelsMCH24PEntry
   MAX-ACCESS  not-accessible
   STATUS      current
   DESCRIPTION
      ""
   ::= {pr1645v2TvTmplVxLanTunnels 41615360}

pr1645v2TvTmplVxLanTunnelsMCH24PEntry OBJECT-TYPE
   SYNTAX      Pr1645v2TvTmplVxLanTunnelsMCH24PEntry
   MAX-ACCESS  not-accessible
   STATUS      current
   DESCRIPTION
      ""
   INDEX      { pr1645v2TvTmplVxLanTunnelsTableIx,
                pr1645v2TvTmplVxLanTunnelsMCH24PTableIx }
   ::= {pr1645v2TvTmplVxLanTunnelsMCH24P 1}

Pr1645v2TvTmplVxLanTunnelsMCH24PEntry ::=
   SEQUENCE
      {
      pr1645v2TvTmplVxLanTunnelsMCH24PTableIx
         TableIndex,
      pr1645v2TvTmplVxLanTunnelsMCH24PSysUpTime
         TimeTicks,
      pr1645v2TvTmplVxLanTunnelsMCH24PIfUpTime
         TimeTicks,
      pr1645v2TvTmplVxLanTunnelsMCH24PIfStatChanges
         Counter32,
      pr1645v2TvTmplVxLanTunnelsMCH24PIfInOctets
         Counter64,
      pr1645v2TvTmplVxLanTunnelsMCH24PIfInUCPkts
         Counter64,
      pr1645v2TvTmplVxLanTunnelsMCH24PIfInNUCPkts
         Counter64,
      pr1645v2TvTmplVxLanTunnelsMCH24PIfInBCPkts
         Counter64,
      pr1645v2TvTmplVxLanTunnelsMCH24PIfInMCPkts
         Counter64,
      pr1645v2TvTmplVxLanTunnelsMCH24PIfInDiscards
         Counter64,
      pr1645v2TvTmplVxLanTunnelsMCH24PIfInErrors
         Counter64,
      pr1645v2TvTmplVxLanTunnelsMCH24PIfInUnkwn
         Counter64,
      pr1645v2TvTmplVxLanTunnelsMCH24PInDropEx
         Counter64,
      pr1645v2TvTmplVxLanTunnelsMCH24PInDropNoMac
         Counter64,
      pr1645v2TvTmplVxLanTunnelsMCH24PInDropNUCast
         Counter64,
      pr1645v2TvTmplVxLanTunnelsMCH24PInDropFilter
         Counter64,
      pr1645v2TvTmplVxLanTunnelsMCH24PIfInBandwidth
         Integer32,
      pr1645v2TvTmplVxLanTunnelsMCH24PIfOutOctets
         Counter64,
      pr1645v2TvTmplVxLanTunnelsMCH24PIfOutUCPkts
         Counter64,
      pr1645v2TvTmplVxLanTunnelsMCH24PIfOutNUCPkts
         Counter64,
      pr1645v2TvTmplVxLanTunnelsMCH24PIfOutBCPkts
         Counter64,
      pr1645v2TvTmplVxLanTunnelsMCH24PIfOutMCPkts
         Counter64,
      pr1645v2TvTmplVxLanTunnelsMCH24PIfOutDiscards
         Counter64,
      pr1645v2TvTmplVxLanTunnelsMCH24PIfOutErrors
         Counter64,
      pr1645v2TvTmplVxLanTunnelsMCH24POutDropEx
         Counter64,
      pr1645v2TvTmplVxLanTunnelsMCH24POutDropNoArp
         Counter64,
      pr1645v2TvTmplVxLanTunnelsMCH24POutDropFilter
         Counter64,
      pr1645v2TvTmplVxLanTunnelsMCH24PIfOutBandwidth
         Integer32,
      pr1645v2TvTmplVxLanTunnelsMCH24PIfErrSec
         Counter32
      }

pr1645v2TvTmplVxLanTunnelsMCH24PTableIx OBJECT-TYPE
   SYNTAX      TableIndex
   MAX-ACCESS  not-accessible
   STATUS      current
   DESCRIPTION
      ""
   ::= {pr1645v2TvTmplVxLanTunnelsMCH24PEntry 11}

pr1645v2TvTmplVxLanTunnelsMCH24PSysUpTime OBJECT-TYPE
   SYNTAX      TimeTicks
   MAX-ACCESS  read-only
   STATUS      current
   DESCRIPTION
      "Path: tunnels.performance.vxLanTunnels.mibCounters.h24Performance.sysUpTime

       Time in centi-second."
   ::= {pr1645v2TvTmplVxLanTunnelsMCH24PEntry 16777216}

pr1645v2TvTmplVxLanTunnelsMCH24PIfUpTime OBJECT-TYPE
   SYNTAX      TimeTicks
   MAX-ACCESS  read-only
   STATUS      current
   DESCRIPTION
      "Path: tunnels.performance.vxLanTunnels.mibCounters.h24Performance.ifUpTime

       Time in centi-second."
   ::= {pr1645v2TvTmplVxLanTunnelsMCH24PEntry 33554432}

pr1645v2TvTmplVxLanTunnelsMCH24PIfStatChanges OBJECT-TYPE
   SYNTAX      Counter32
   MAX-ACCESS  read-only
   STATUS      current
   DESCRIPTION
      "Path: tunnels.performance.vxLanTunnels.mibCounters.h24Performance.ifStatusChanges

       32 bit unsigned wrappable counter."
   ::= {pr1645v2TvTmplVxLanTunnelsMCH24PEntry 50331648}

pr1645v2TvTmplVxLanTunnelsMCH24PIfInOctets OBJECT-TYPE
   SYNTAX      Counter64
   MAX-ACCESS  read-only
   STATUS      current
   DESCRIPTION
      "Path: tunnels.performance.vxLanTunnels.mibCounters.h24Performance.ifInOctets

       64 bit unsigned wrappable counter."
   ::= {pr1645v2TvTmplVxLanTunnelsMCH24PEntry 67108864}

pr1645v2TvTmplVxLanTunnelsMCH24PIfInUCPkts OBJECT-TYPE
   SYNTAX      Counter64
   MAX-ACCESS  read-only
   STATUS      current
   DESCRIPTION
      "Path: tunnels.performance.vxLanTunnels.mibCounters.h24Performance.ifInUcastPkts

       64 bit unsigned wrappable counter."
   ::= {pr1645v2TvTmplVxLanTunnelsMCH24PEntry 83886080}

pr1645v2TvTmplVxLanTunnelsMCH24PIfInNUCPkts OBJECT-TYPE
   SYNTAX      Counter64
   MAX-ACCESS  read-only
   STATUS      current
   DESCRIPTION
      "Path: tunnels.performance.vxLanTunnels.mibCounters.h24Performance.ifInNUcastPkts

       64 bit unsigned wrappable counter."
   ::= {pr1645v2TvTmplVxLanTunnelsMCH24PEntry 100663296}

pr1645v2TvTmplVxLanTunnelsMCH24PIfInBCPkts OBJECT-TYPE
   SYNTAX      Counter64
   MAX-ACCESS  read-only
   STATUS      current
   DESCRIPTION
      "Path: tunnels.performance.vxLanTunnels.mibCounters.h24Performance.ifInBcastPkts

       64 bit unsigned wrappable counter."
   ::= {pr1645v2TvTmplVxLanTunnelsMCH24PEntry 419430400}

pr1645v2TvTmplVxLanTunnelsMCH24PIfInMCPkts OBJECT-TYPE
   SYNTAX      Counter64
   MAX-ACCESS  read-only
   STATUS      current
   DESCRIPTION
      "Path: tunnels.performance.vxLanTunnels.mibCounters.h24Performance.ifInMcastPkts

       64 bit unsigned wrappable counter."
   ::= {pr1645v2TvTmplVxLanTunnelsMCH24PEntry 436207616}

pr1645v2TvTmplVxLanTunnelsMCH24PIfInDiscards OBJECT-TYPE
   SYNTAX      Counter64
   MAX-ACCESS  read-only
   STATUS      current
   DESCRIPTION
      "Path: tunnels.performance.vxLanTunnels.mibCounters.h24Performance.ifInDiscards

       64 bit unsigned wrappable counter."
   ::= {pr1645v2TvTmplVxLanTunnelsMCH24PEntry 117440512}

pr1645v2TvTmplVxLanTunnelsMCH24PIfInErrors OBJECT-TYPE
   SYNTAX      Counter64
   MAX-ACCESS  read-only
   STATUS      current
   DESCRIPTION
      "Path: tunnels.performance.vxLanTunnels.mibCounters.h24Performance.ifInErrors

       64 bit unsigned wrappable counter."
   ::= {pr1645v2TvTmplVxLanTunnelsMCH24PEntry 134217728}

pr1645v2TvTmplVxLanTunnelsMCH24PIfInUnkwn OBJECT-TYPE
   SYNTAX      Counter64
   MAX-ACCESS  read-only
   STATUS      current
   DESCRIPTION
      "Path: tunnels.performance.vxLanTunnels.mibCounters.h24Performance.ifInUnknownProtos

       64 bit unsigned wrappable counter."
   ::= {pr1645v2TvTmplVxLanTunnelsMCH24PEntry 150994944}

pr1645v2TvTmplVxLanTunnelsMCH24PInDropEx OBJECT-TYPE
   SYNTAX      Counter64
   MAX-ACCESS  read-only
   STATUS      current
   DESCRIPTION
      "Path: tunnels.performance.vxLanTunnels.mibCounters.h24Performance.ifInDropLevelExceeded

       64 bit unsigned wrappable counter."
   ::= {pr1645v2TvTmplVxLanTunnelsMCH24PEntry 335544320}

pr1645v2TvTmplVxLanTunnelsMCH24PInDropNoMac OBJECT-TYPE
   SYNTAX      Counter64
   MAX-ACCESS  read-only
   STATUS      current
   DESCRIPTION
      "Path: tunnels.performance.vxLanTunnels.mibCounters.h24Performance.fInDiscardsNoMacFit

       64 bit unsigned wrappable counter."
   ::= {pr1645v2TvTmplVxLanTunnelsMCH24PEntry 301989888}

pr1645v2TvTmplVxLanTunnelsMCH24PInDropNUCast OBJECT-TYPE
   SYNTAX      Counter64
   MAX-ACCESS  read-only
   STATUS      current
   DESCRIPTION
      "Path: tunnels.performance.vxLanTunnels.mibCounters.h24Performance.fInDiscardsNUCast

       64 bit unsigned wrappable counter."
   ::= {pr1645v2TvTmplVxLanTunnelsMCH24PEntry 318767104}

pr1645v2TvTmplVxLanTunnelsMCH24PInDropFilter OBJECT-TYPE
   SYNTAX      Counter64
   MAX-ACCESS  read-only
   STATUS      current
   DESCRIPTION
      "Path: tunnels.performance.vxLanTunnels.mibCounters.h24Performance.fInDiscardsFilter

       64 bit unsigned wrappable counter."
   ::= {pr1645v2TvTmplVxLanTunnelsMCH24PEntry 385875968}

pr1645v2TvTmplVxLanTunnelsMCH24PIfInBandwidth OBJECT-TYPE
   SYNTAX      Integer32
   MAX-ACCESS  read-only
   STATUS      current
   DESCRIPTION
      "Path: tunnels.performance.vxLanTunnels.mibCounters.h24Performance.ifInBandwidth

       unit name = bps
       formula = 8 * ; 8 /"
   ::= {pr1645v2TvTmplVxLanTunnelsMCH24PEntry 268435456}

pr1645v2TvTmplVxLanTunnelsMCH24PIfOutOctets OBJECT-TYPE
   SYNTAX      Counter64
   MAX-ACCESS  read-only
   STATUS      current
   DESCRIPTION
      "Path: tunnels.performance.vxLanTunnels.mibCounters.h24Performance.ifOutOctets

       64 bit unsigned wrappable counter."
   ::= {pr1645v2TvTmplVxLanTunnelsMCH24PEntry 167772160}

pr1645v2TvTmplVxLanTunnelsMCH24PIfOutUCPkts OBJECT-TYPE
   SYNTAX      Counter64
   MAX-ACCESS  read-only
   STATUS      current
   DESCRIPTION
      "Path: tunnels.performance.vxLanTunnels.mibCounters.h24Performance.ifOutUcastPkts

       64 bit unsigned wrappable counter."
   ::= {pr1645v2TvTmplVxLanTunnelsMCH24PEntry 184549376}

pr1645v2TvTmplVxLanTunnelsMCH24PIfOutNUCPkts OBJECT-TYPE
   SYNTAX      Counter64
   MAX-ACCESS  read-only
   STATUS      current
   DESCRIPTION
      "Path: tunnels.performance.vxLanTunnels.mibCounters.h24Performance.ifOutNUcastPkts

       64 bit unsigned wrappable counter."
   ::= {pr1645v2TvTmplVxLanTunnelsMCH24PEntry 201326592}

pr1645v2TvTmplVxLanTunnelsMCH24PIfOutBCPkts OBJECT-TYPE
   SYNTAX      Counter64
   MAX-ACCESS  read-only
   STATUS      current
   DESCRIPTION
      "Path: tunnels.performance.vxLanTunnels.mibCounters.h24Performance.ifOutBcastPkts

       64 bit unsigned wrappable counter."
   ::= {pr1645v2TvTmplVxLanTunnelsMCH24PEntry 452984832}

pr1645v2TvTmplVxLanTunnelsMCH24PIfOutMCPkts OBJECT-TYPE
   SYNTAX      Counter64
   MAX-ACCESS  read-only
   STATUS      current
   DESCRIPTION
      "Path: tunnels.performance.vxLanTunnels.mibCounters.h24Performance.ifOutMcastPkts

       64 bit unsigned wrappable counter."
   ::= {pr1645v2TvTmplVxLanTunnelsMCH24PEntry 469762048}

pr1645v2TvTmplVxLanTunnelsMCH24PIfOutDiscards OBJECT-TYPE
   SYNTAX      Counter64
   MAX-ACCESS  read-only
   STATUS      current
   DESCRIPTION
      "Path: tunnels.performance.vxLanTunnels.mibCounters.h24Performance.ifOutDiscards

       64 bit unsigned wrappable counter."
   ::= {pr1645v2TvTmplVxLanTunnelsMCH24PEntry 218103808}

pr1645v2TvTmplVxLanTunnelsMCH24PIfOutErrors OBJECT-TYPE
   SYNTAX      Counter64
   MAX-ACCESS  read-only
   STATUS      current
   DESCRIPTION
      "Path: tunnels.performance.vxLanTunnels.mibCounters.h24Performance.ifOutErrors

       64 bit unsigned wrappable counter."
   ::= {pr1645v2TvTmplVxLanTunnelsMCH24PEntry 234881024}

pr1645v2TvTmplVxLanTunnelsMCH24POutDropEx OBJECT-TYPE
   SYNTAX      Counter64
   MAX-ACCESS  read-only
   STATUS      current
   DESCRIPTION
      "Path: tunnels.performance.vxLanTunnels.mibCounters.h24Performance.ifOutDropLevelExceeded

       64 bit unsigned wrappable counter."
   ::= {pr1645v2TvTmplVxLanTunnelsMCH24PEntry 352321536}

pr1645v2TvTmplVxLanTunnelsMCH24POutDropNoArp OBJECT-TYPE
   SYNTAX      Counter64
   MAX-ACCESS  read-only
   STATUS      current
   DESCRIPTION
      "Path: tunnels.performance.vxLanTunnels.mibCounters.h24Performance.ifOutDiscardsNoArp

       64 bit unsigned wrappable counter."
   ::= {pr1645v2TvTmplVxLanTunnelsMCH24PEntry 369098752}

pr1645v2TvTmplVxLanTunnelsMCH24POutDropFilter OBJECT-TYPE
   SYNTAX      Counter64
   MAX-ACCESS  read-only
   STATUS      current
   DESCRIPTION
      "Path: tunnels.performance.vxLanTunnels.mibCounters.h24Performance.ifOutDiscardsFilter

       64 bit unsigned wrappable counter."
   ::= {pr1645v2TvTmplVxLanTunnelsMCH24PEntry 402653184}

pr1645v2TvTmplVxLanTunnelsMCH24PIfOutBandwidth OBJECT-TYPE
   SYNTAX      Integer32
   MAX-ACCESS  read-only
   STATUS      current
   DESCRIPTION
      "Path: tunnels.performance.vxLanTunnels.mibCounters.h24Performance.ifOutBandwidth

       unit name = bps
       formula = 8 * ; 8 /"
   ::= {pr1645v2TvTmplVxLanTunnelsMCH24PEntry 285212672}

pr1645v2TvTmplVxLanTunnelsMCH24PIfErrSec OBJECT-TYPE
   SYNTAX      Counter32
   MAX-ACCESS  read-only
   STATUS      current
   DESCRIPTION
      "Path: tunnels.performance.vxLanTunnels.mibCounters.h24Performance.ifErrSec

       32 bit unsigned wrappable counter."
   ::= {pr1645v2TvTmplVxLanTunnelsMCH24PEntry 251658240}

pr1645v2TvTmplVxLanTunnelsMCD7P OBJECT-TYPE
   SYNTAX      SEQUENCE OF Pr1645v2TvTmplVxLanTunnelsMCD7PEntry
   MAX-ACCESS  not-accessible
   STATUS      current
   DESCRIPTION
      ""
   ::= {pr1645v2TvTmplVxLanTunnels 41680896}

pr1645v2TvTmplVxLanTunnelsMCD7PEntry OBJECT-TYPE
   SYNTAX      Pr1645v2TvTmplVxLanTunnelsMCD7PEntry
   MAX-ACCESS  not-accessible
   STATUS      current
   DESCRIPTION
      ""
   INDEX      { pr1645v2TvTmplVxLanTunnelsTableIx,
                pr1645v2TvTmplVxLanTunnelsMCD7PTableIx }
   ::= {pr1645v2TvTmplVxLanTunnelsMCD7P 1}

Pr1645v2TvTmplVxLanTunnelsMCD7PEntry ::=
   SEQUENCE
      {
      pr1645v2TvTmplVxLanTunnelsMCD7PTableIx
         TableIndex,
      pr1645v2TvTmplVxLanTunnelsMCD7PSysUpTime
         TimeTicks,
      pr1645v2TvTmplVxLanTunnelsMCD7PIfUpTime
         TimeTicks,
      pr1645v2TvTmplVxLanTunnelsMCD7PIfStatChanges
         Counter32,
      pr1645v2TvTmplVxLanTunnelsMCD7PIfInOctets
         Counter64,
      pr1645v2TvTmplVxLanTunnelsMCD7PIfInUCPkts
         Counter64,
      pr1645v2TvTmplVxLanTunnelsMCD7PIfInNUCPkts
         Counter64,
      pr1645v2TvTmplVxLanTunnelsMCD7PIfInBCPkts
         Counter64,
      pr1645v2TvTmplVxLanTunnelsMCD7PIfInMCPkts
         Counter64,
      pr1645v2TvTmplVxLanTunnelsMCD7PIfInDiscards
         Counter64,
      pr1645v2TvTmplVxLanTunnelsMCD7PIfInErrors
         Counter64,
      pr1645v2TvTmplVxLanTunnelsMCD7PIfInUnkwn
         Counter64,
      pr1645v2TvTmplVxLanTunnelsMCD7PInDropEx
         Counter64,
      pr1645v2TvTmplVxLanTunnelsMCD7PInDropNoMac
         Counter64,
      pr1645v2TvTmplVxLanTunnelsMCD7PInDropNUCast
         Counter64,
      pr1645v2TvTmplVxLanTunnelsMCD7PInDropFilter
         Counter64,
      pr1645v2TvTmplVxLanTunnelsMCD7PIfInBandwidth
         Integer32,
      pr1645v2TvTmplVxLanTunnelsMCD7PIfOutOctets
         Counter64,
      pr1645v2TvTmplVxLanTunnelsMCD7PIfOutUCPkts
         Counter64,
      pr1645v2TvTmplVxLanTunnelsMCD7PIfOutNUCPkts
         Counter64,
      pr1645v2TvTmplVxLanTunnelsMCD7PIfOutBCPkts
         Counter64,
      pr1645v2TvTmplVxLanTunnelsMCD7PIfOutMCPkts
         Counter64,
      pr1645v2TvTmplVxLanTunnelsMCD7PIfOutDiscards
         Counter64,
      pr1645v2TvTmplVxLanTunnelsMCD7PIfOutErrors
         Counter64,
      pr1645v2TvTmplVxLanTunnelsMCD7POutDropEx
         Counter64,
      pr1645v2TvTmplVxLanTunnelsMCD7POutDropNoArp
         Counter64,
      pr1645v2TvTmplVxLanTunnelsMCD7POutDropFilter
         Counter64,
      pr1645v2TvTmplVxLanTunnelsMCD7PIfOutBandwidth
         Integer32,
      pr1645v2TvTmplVxLanTunnelsMCD7PIfErrSec
         Counter32
      }

pr1645v2TvTmplVxLanTunnelsMCD7PTableIx OBJECT-TYPE
   SYNTAX      TableIndex
   MAX-ACCESS  not-accessible
   STATUS      current
   DESCRIPTION
      ""
   ::= {pr1645v2TvTmplVxLanTunnelsMCD7PEntry 11}

pr1645v2TvTmplVxLanTunnelsMCD7PSysUpTime OBJECT-TYPE
   SYNTAX      TimeTicks
   MAX-ACCESS  read-only
   STATUS      current
   DESCRIPTION
      "Path: tunnels.performance.vxLanTunnels.mibCounters.d7Performance.sysUpTime

       Time in centi-second."
   ::= {pr1645v2TvTmplVxLanTunnelsMCD7PEntry 16777216}

pr1645v2TvTmplVxLanTunnelsMCD7PIfUpTime OBJECT-TYPE
   SYNTAX      TimeTicks
   MAX-ACCESS  read-only
   STATUS      current
   DESCRIPTION
      "Path: tunnels.performance.vxLanTunnels.mibCounters.d7Performance.ifUpTime

       Time in centi-second."
   ::= {pr1645v2TvTmplVxLanTunnelsMCD7PEntry 33554432}

pr1645v2TvTmplVxLanTunnelsMCD7PIfStatChanges OBJECT-TYPE
   SYNTAX      Counter32
   MAX-ACCESS  read-only
   STATUS      current
   DESCRIPTION
      "Path: tunnels.performance.vxLanTunnels.mibCounters.d7Performance.ifStatusChanges

       32 bit unsigned wrappable counter."
   ::= {pr1645v2TvTmplVxLanTunnelsMCD7PEntry 50331648}

pr1645v2TvTmplVxLanTunnelsMCD7PIfInOctets OBJECT-TYPE
   SYNTAX      Counter64
   MAX-ACCESS  read-only
   STATUS      current
   DESCRIPTION
      "Path: tunnels.performance.vxLanTunnels.mibCounters.d7Performance.ifInOctets

       64 bit unsigned wrappable counter."
   ::= {pr1645v2TvTmplVxLanTunnelsMCD7PEntry 67108864}

pr1645v2TvTmplVxLanTunnelsMCD7PIfInUCPkts OBJECT-TYPE
   SYNTAX      Counter64
   MAX-ACCESS  read-only
   STATUS      current
   DESCRIPTION
      "Path: tunnels.performance.vxLanTunnels.mibCounters.d7Performance.ifInUcastPkts

       64 bit unsigned wrappable counter."
   ::= {pr1645v2TvTmplVxLanTunnelsMCD7PEntry 83886080}

pr1645v2TvTmplVxLanTunnelsMCD7PIfInNUCPkts OBJECT-TYPE
   SYNTAX      Counter64
   MAX-ACCESS  read-only
   STATUS      current
   DESCRIPTION
      "Path: tunnels.performance.vxLanTunnels.mibCounters.d7Performance.ifInNUcastPkts

       64 bit unsigned wrappable counter."
   ::= {pr1645v2TvTmplVxLanTunnelsMCD7PEntry 100663296}

pr1645v2TvTmplVxLanTunnelsMCD7PIfInBCPkts OBJECT-TYPE
   SYNTAX      Counter64
   MAX-ACCESS  read-only
   STATUS      current
   DESCRIPTION
      "Path: tunnels.performance.vxLanTunnels.mibCounters.d7Performance.ifInBcastPkts

       64 bit unsigned wrappable counter."
   ::= {pr1645v2TvTmplVxLanTunnelsMCD7PEntry 419430400}

pr1645v2TvTmplVxLanTunnelsMCD7PIfInMCPkts OBJECT-TYPE
   SYNTAX      Counter64
   MAX-ACCESS  read-only
   STATUS      current
   DESCRIPTION
      "Path: tunnels.performance.vxLanTunnels.mibCounters.d7Performance.ifInMcastPkts

       64 bit unsigned wrappable counter."
   ::= {pr1645v2TvTmplVxLanTunnelsMCD7PEntry 436207616}

pr1645v2TvTmplVxLanTunnelsMCD7PIfInDiscards OBJECT-TYPE
   SYNTAX      Counter64
   MAX-ACCESS  read-only
   STATUS      current
   DESCRIPTION
      "Path: tunnels.performance.vxLanTunnels.mibCounters.d7Performance.ifInDiscards

       64 bit unsigned wrappable counter."
   ::= {pr1645v2TvTmplVxLanTunnelsMCD7PEntry 117440512}

pr1645v2TvTmplVxLanTunnelsMCD7PIfInErrors OBJECT-TYPE
   SYNTAX      Counter64
   MAX-ACCESS  read-only
   STATUS      current
   DESCRIPTION
      "Path: tunnels.performance.vxLanTunnels.mibCounters.d7Performance.ifInErrors

       64 bit unsigned wrappable counter."
   ::= {pr1645v2TvTmplVxLanTunnelsMCD7PEntry 134217728}

pr1645v2TvTmplVxLanTunnelsMCD7PIfInUnkwn OBJECT-TYPE
   SYNTAX      Counter64
   MAX-ACCESS  read-only
   STATUS      current
   DESCRIPTION
      "Path: tunnels.performance.vxLanTunnels.mibCounters.d7Performance.ifInUnknownProtos

       64 bit unsigned wrappable counter."
   ::= {pr1645v2TvTmplVxLanTunnelsMCD7PEntry 150994944}

pr1645v2TvTmplVxLanTunnelsMCD7PInDropEx OBJECT-TYPE
   SYNTAX      Counter64
   MAX-ACCESS  read-only
   STATUS      current
   DESCRIPTION
      "Path: tunnels.performance.vxLanTunnels.mibCounters.d7Performance.ifInDropLevelExceeded

       64 bit unsigned wrappable counter."
   ::= {pr1645v2TvTmplVxLanTunnelsMCD7PEntry 335544320}

pr1645v2TvTmplVxLanTunnelsMCD7PInDropNoMac OBJECT-TYPE
   SYNTAX      Counter64
   MAX-ACCESS  read-only
   STATUS      current
   DESCRIPTION
      "Path: tunnels.performance.vxLanTunnels.mibCounters.d7Performance.fInDiscardsNoMacFit

       64 bit unsigned wrappable counter."
   ::= {pr1645v2TvTmplVxLanTunnelsMCD7PEntry 301989888}

pr1645v2TvTmplVxLanTunnelsMCD7PInDropNUCast OBJECT-TYPE
   SYNTAX      Counter64
   MAX-ACCESS  read-only
   STATUS      current
   DESCRIPTION
      "Path: tunnels.performance.vxLanTunnels.mibCounters.d7Performance.fInDiscardsNUCast

       64 bit unsigned wrappable counter."
   ::= {pr1645v2TvTmplVxLanTunnelsMCD7PEntry 318767104}

pr1645v2TvTmplVxLanTunnelsMCD7PInDropFilter OBJECT-TYPE
   SYNTAX      Counter64
   MAX-ACCESS  read-only
   STATUS      current
   DESCRIPTION
      "Path: tunnels.performance.vxLanTunnels.mibCounters.d7Performance.fInDiscardsFilter

       64 bit unsigned wrappable counter."
   ::= {pr1645v2TvTmplVxLanTunnelsMCD7PEntry 385875968}

pr1645v2TvTmplVxLanTunnelsMCD7PIfInBandwidth OBJECT-TYPE
   SYNTAX      Integer32
   MAX-ACCESS  read-only
   STATUS      current
   DESCRIPTION
      "Path: tunnels.performance.vxLanTunnels.mibCounters.d7Performance.ifInBandwidth

       unit name = bps
       formula = 8 * ; 8 /"
   ::= {pr1645v2TvTmplVxLanTunnelsMCD7PEntry 268435456}

pr1645v2TvTmplVxLanTunnelsMCD7PIfOutOctets OBJECT-TYPE
   SYNTAX      Counter64
   MAX-ACCESS  read-only
   STATUS      current
   DESCRIPTION
      "Path: tunnels.performance.vxLanTunnels.mibCounters.d7Performance.ifOutOctets

       64 bit unsigned wrappable counter."
   ::= {pr1645v2TvTmplVxLanTunnelsMCD7PEntry 167772160}

pr1645v2TvTmplVxLanTunnelsMCD7PIfOutUCPkts OBJECT-TYPE
   SYNTAX      Counter64
   MAX-ACCESS  read-only
   STATUS      current
   DESCRIPTION
      "Path: tunnels.performance.vxLanTunnels.mibCounters.d7Performance.ifOutUcastPkts

       64 bit unsigned wrappable counter."
   ::= {pr1645v2TvTmplVxLanTunnelsMCD7PEntry 184549376}

pr1645v2TvTmplVxLanTunnelsMCD7PIfOutNUCPkts OBJECT-TYPE
   SYNTAX      Counter64
   MAX-ACCESS  read-only
   STATUS      current
   DESCRIPTION
      "Path: tunnels.performance.vxLanTunnels.mibCounters.d7Performance.ifOutNUcastPkts

       64 bit unsigned wrappable counter."
   ::= {pr1645v2TvTmplVxLanTunnelsMCD7PEntry 201326592}

pr1645v2TvTmplVxLanTunnelsMCD7PIfOutBCPkts OBJECT-TYPE
   SYNTAX      Counter64
   MAX-ACCESS  read-only
   STATUS      current
   DESCRIPTION
      "Path: tunnels.performance.vxLanTunnels.mibCounters.d7Performance.ifOutBcastPkts

       64 bit unsigned wrappable counter."
   ::= {pr1645v2TvTmplVxLanTunnelsMCD7PEntry 452984832}

pr1645v2TvTmplVxLanTunnelsMCD7PIfOutMCPkts OBJECT-TYPE
   SYNTAX      Counter64
   MAX-ACCESS  read-only
   STATUS      current
   DESCRIPTION
      "Path: tunnels.performance.vxLanTunnels.mibCounters.d7Performance.ifOutMcastPkts

       64 bit unsigned wrappable counter."
   ::= {pr1645v2TvTmplVxLanTunnelsMCD7PEntry 469762048}

pr1645v2TvTmplVxLanTunnelsMCD7PIfOutDiscards OBJECT-TYPE
   SYNTAX      Counter64
   MAX-ACCESS  read-only
   STATUS      current
   DESCRIPTION
      "Path: tunnels.performance.vxLanTunnels.mibCounters.d7Performance.ifOutDiscards

       64 bit unsigned wrappable counter."
   ::= {pr1645v2TvTmplVxLanTunnelsMCD7PEntry 218103808}

pr1645v2TvTmplVxLanTunnelsMCD7PIfOutErrors OBJECT-TYPE
   SYNTAX      Counter64
   MAX-ACCESS  read-only
   STATUS      current
   DESCRIPTION
      "Path: tunnels.performance.vxLanTunnels.mibCounters.d7Performance.ifOutErrors

       64 bit unsigned wrappable counter."
   ::= {pr1645v2TvTmplVxLanTunnelsMCD7PEntry 234881024}

pr1645v2TvTmplVxLanTunnelsMCD7POutDropEx OBJECT-TYPE
   SYNTAX      Counter64
   MAX-ACCESS  read-only
   STATUS      current
   DESCRIPTION
      "Path: tunnels.performance.vxLanTunnels.mibCounters.d7Performance.ifOutDropLevelExceeded

       64 bit unsigned wrappable counter."
   ::= {pr1645v2TvTmplVxLanTunnelsMCD7PEntry 352321536}

pr1645v2TvTmplVxLanTunnelsMCD7POutDropNoArp OBJECT-TYPE
   SYNTAX      Counter64
   MAX-ACCESS  read-only
   STATUS      current
   DESCRIPTION
      "Path: tunnels.performance.vxLanTunnels.mibCounters.d7Performance.ifOutDiscardsNoArp

       64 bit unsigned wrappable counter."
   ::= {pr1645v2TvTmplVxLanTunnelsMCD7PEntry 369098752}

pr1645v2TvTmplVxLanTunnelsMCD7POutDropFilter OBJECT-TYPE
   SYNTAX      Counter64
   MAX-ACCESS  read-only
   STATUS      current
   DESCRIPTION
      "Path: tunnels.performance.vxLanTunnels.mibCounters.d7Performance.ifOutDiscardsFilter

       64 bit unsigned wrappable counter."
   ::= {pr1645v2TvTmplVxLanTunnelsMCD7PEntry 402653184}

pr1645v2TvTmplVxLanTunnelsMCD7PIfOutBandwidth OBJECT-TYPE
   SYNTAX      Integer32
   MAX-ACCESS  read-only
   STATUS      current
   DESCRIPTION
      "Path: tunnels.performance.vxLanTunnels.mibCounters.d7Performance.ifOutBandwidth

       unit name = bps
       formula = 8 * ; 8 /"
   ::= {pr1645v2TvTmplVxLanTunnelsMCD7PEntry 285212672}

pr1645v2TvTmplVxLanTunnelsMCD7PIfErrSec OBJECT-TYPE
   SYNTAX      Counter32
   MAX-ACCESS  read-only
   STATUS      current
   DESCRIPTION
      "Path: tunnels.performance.vxLanTunnels.mibCounters.d7Performance.ifErrSec

       32 bit unsigned wrappable counter."
   ::= {pr1645v2TvTmplVxLanTunnelsMCD7PEntry 251658240}

pr1645v2TvTmplVxLanTunnelsInPQs OBJECT-TYPE
   SYNTAX      SEQUENCE OF Pr1645v2TvTmplVxLanTunnelsInPQsEntry
   MAX-ACCESS  not-accessible
   STATUS      current
   DESCRIPTION
      ""
   ::= {pr1645v2TvTmplVxLanTunnels 100663296}

pr1645v2TvTmplVxLanTunnelsInPQsEntry OBJECT-TYPE
   SYNTAX      Pr1645v2TvTmplVxLanTunnelsInPQsEntry
   MAX-ACCESS  not-accessible
   STATUS      current
   DESCRIPTION
      ""
   INDEX      { pr1645v2TvTmplVxLanTunnelsTableIx,
                pr1645v2TvTmplVxLanTunnelsInPQsTableIx }
   ::= {pr1645v2TvTmplVxLanTunnelsInPQs 1}

Pr1645v2TvTmplVxLanTunnelsInPQsEntry ::=
   SEQUENCE
      {
      pr1645v2TvTmplVxLanTunnelsInPQsTableIx
         TableIndex,
      pr1645v2TvTmplVxLanTunnelsInPQsName
         INTEGER,
      pr1645v2TvTmplVxLanTunnelsInPQsLength
         Integer32,
      pr1645v2TvTmplVxLanTunnelsInPQsOctetLength
         Integer32,
      pr1645v2TvTmplVxLanTunnelsInPQsRedLength
         Integer32,
      pr1645v2TvTmplVxLanTunnelsInPQsPacketsTotal
         Counter64,
      pr1645v2TvTmplVxLanTunnelsInPQsPacketsDirectTx
         Counter64,
      pr1645v2TvTmplVxLanTunnelsInPQsPacketsQueued
         Counter64,
      pr1645v2TvTmplVxLanTunnelsInPQsPacketsDropped
         Counter64,
      pr1645v2TvTmplVxLanTunnelsInPQsPacketsRedDropped
         Counter64,
      pr1645v2TvTmplVxLanTunnelsInPQsPacketsCirTx
         Counter64,
      pr1645v2TvTmplVxLanTunnelsInPQsPacketsEirTx
         Counter64,
      pr1645v2TvTmplVxLanTunnelsInPQsPacketsViolateTx
         Counter64,
      pr1645v2TvTmplVxLanTunnelsInPQsOctetsTotal
         Counter64,
      pr1645v2TvTmplVxLanTunnelsInPQsOctetsDirectTx
         Counter64,
      pr1645v2TvTmplVxLanTunnelsInPQsOctetsQueued
         Counter64,
      pr1645v2TvTmplVxLanTunnelsInPQsOctetsDropped
         Counter64,
      pr1645v2TvTmplVxLanTunnelsInPQsOctetsRedDropped
         Counter64,
      pr1645v2TvTmplVxLanTunnelsInPQsOctetsCirTx
         Counter64,
      pr1645v2TvTmplVxLanTunnelsInPQsOctetsEirTx
         Counter64,
      pr1645v2TvTmplVxLanTunnelsInPQsOctetsViolateTx
         Counter64,
      pr1645v2TvTmplVxLanTunnelsInPQsOctetsBandwidth15sec
         Integer32,
      pr1645v2TvTmplVxLanTunnelsInPQsOctetsBandwidth30sec
         Integer32,
      pr1645v2TvTmplVxLanTunnelsInPQsOctetsBandwidth1min
         Integer32,
      pr1645v2TvTmplVxLanTunnelsInPQsOctetsBandwidth2min
         Integer32,
      pr1645v2TvTmplVxLanTunnelsInPQsOctetsBandwidth5min
         Integer32
      }

pr1645v2TvTmplVxLanTunnelsInPQsTableIx OBJECT-TYPE
   SYNTAX      TableIndex
   MAX-ACCESS  not-accessible
   STATUS      current
   DESCRIPTION
      ""
   ::= {pr1645v2TvTmplVxLanTunnelsInPQsEntry 11}

pr1645v2TvTmplVxLanTunnelsInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.vxLanTunnels.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplVxLanTunnelsInPQsEntry 16777216}

pr1645v2TvTmplVxLanTunnelsInPQsLength OBJECT-TYPE
   SYNTAX      Integer32
   MAX-ACCESS  read-only
   STATUS      current
   DESCRIPTION
      "Path: tunnels.performance.vxLanTunnels.inPriorityQueues.length"
   ::= {pr1645v2TvTmplVxLanTunnelsInPQsEntry 33554432}

pr1645v2TvTmplVxLanTunnelsInPQsOctetLength OBJECT-TYPE
   SYNTAX      Integer32
   MAX-ACCESS  read-only
   STATUS      current
   DESCRIPTION
      "Path: tunnels.performance.vxLanTunnels.inPriorityQueues.octetLength"
   ::= {pr1645v2TvTmplVxLanTunnelsInPQsEntry 150994944}

pr1645v2TvTmplVxLanTunnelsInPQsRedLength OBJECT-TYPE
   SYNTAX      Integer32
   MAX-ACCESS  read-only
   STATUS      current
   DESCRIPTION
      "Path: tunnels.performance.vxLanTunnels.inPriorityQueues.redLength"
   ::= {pr1645v2TvTmplVxLanTunnelsInPQsEntry 134217728}

pr1645v2TvTmplVxLanTunnelsInPQsPacketsTotal OBJECT-TYPE
   SYNTAX      Counter64
   MAX-ACCESS  read-only
   STATUS      current
   DESCRIPTION
      "Path: tunnels.performance.vxLanTunnels.inPriorityQueues.packets.total

       64 bit unsigned wrappable counter."
   ::= {pr1645v2TvTmplVxLanTunnelsInPQsEntry 50790400}

pr1645v2TvTmplVxLanTunnelsInPQsPacketsDirectTx OBJECT-TYPE
   SYNTAX      Counter64
   MAX-ACCESS  read-only
   STATUS      current
   DESCRIPTION
      "Path: tunnels.performance.vxLanTunnels.inPriorityQueues.packets.directTx

       64 bit unsigned wrappable counter."
   ::= {pr1645v2TvTmplVxLanTunnelsInPQsEntry 50397184}

pr1645v2TvTmplVxLanTunnelsInPQsPacketsQueued OBJECT-TYPE
   SYNTAX      Counter64
   MAX-ACCESS  read-only
   STATUS      current
   DESCRIPTION
      "Path: tunnels.performance.vxLanTunnels.inPriorityQueues.packets.queued

       64 bit unsigned wrappable counter."
   ::= {pr1645v2TvTmplVxLanTunnelsInPQsEntry 50462720}

pr1645v2TvTmplVxLanTunnelsInPQsPacketsDropped OBJECT-TYPE
   SYNTAX      Counter64
   MAX-ACCESS  read-only
   STATUS      current
   DESCRIPTION
      "Path: tunnels.performance.vxLanTunnels.inPriorityQueues.packets.dropped

       64 bit unsigned wrappable counter."
   ::= {pr1645v2TvTmplVxLanTunnelsInPQsEntry 50528256}

pr1645v2TvTmplVxLanTunnelsInPQsPacketsRedDropped OBJECT-TYPE
   SYNTAX      Counter64
   MAX-ACCESS  read-only
   STATUS      current
   DESCRIPTION
      "Path: tunnels.performance.vxLanTunnels.inPriorityQueues.packets.redDropped

       64 bit unsigned wrappable counter."
   ::= {pr1645v2TvTmplVxLanTunnelsInPQsEntry 50724864}

pr1645v2TvTmplVxLanTunnelsInPQsPacketsCirTx OBJECT-TYPE
   SYNTAX      Counter64
   MAX-ACCESS  read-only
   STATUS      current
   DESCRIPTION
      "Path: tunnels.performance.vxLanTunnels.inPriorityQueues.packets.cirTx

       64 bit unsigned wrappable counter."
   ::= {pr1645v2TvTmplVxLanTunnelsInPQsEntry 50593792}

pr1645v2TvTmplVxLanTunnelsInPQsPacketsEirTx OBJECT-TYPE
   SYNTAX      Counter64
   MAX-ACCESS  read-only
   STATUS      current
   DESCRIPTION
      "Path: tunnels.performance.vxLanTunnels.inPriorityQueues.packets.eirTx

       64 bit unsigned wrappable counter."
   ::= {pr1645v2TvTmplVxLanTunnelsInPQsEntry 50659328}

pr1645v2TvTmplVxLanTunnelsInPQsPacketsViolateTx OBJECT-TYPE
   SYNTAX      Counter64
   MAX-ACCESS  read-only
   STATUS      current
   DESCRIPTION
      "Path: tunnels.performance.vxLanTunnels.inPriorityQueues.packets.violateTx

       64 bit unsigned wrappable counter."
   ::= {pr1645v2TvTmplVxLanTunnelsInPQsEntry 50855936}

pr1645v2TvTmplVxLanTunnelsInPQsOctetsTotal OBJECT-TYPE
   SYNTAX      Counter64
   MAX-ACCESS  read-only
   STATUS      current
   DESCRIPTION
      "Path: tunnels.performance.vxLanTunnels.inPriorityQueues.octets.total

       64 bit unsigned wrappable counter."
   ::= {pr1645v2TvTmplVxLanTunnelsInPQsEntry 67567616}

pr1645v2TvTmplVxLanTunnelsInPQsOctetsDirectTx OBJECT-TYPE
   SYNTAX      Counter64
   MAX-ACCESS  read-only
   STATUS      current
   DESCRIPTION
      "Path: tunnels.performance.vxLanTunnels.inPriorityQueues.octets.directTx

       64 bit unsigned wrappable counter."
   ::= {pr1645v2TvTmplVxLanTunnelsInPQsEntry 67174400}

pr1645v2TvTmplVxLanTunnelsInPQsOctetsQueued OBJECT-TYPE
   SYNTAX      Counter64
   MAX-ACCESS  read-only
   STATUS      current
   DESCRIPTION
      "Path: tunnels.performance.vxLanTunnels.inPriorityQueues.octets.queued

       64 bit unsigned wrappable counter."
   ::= {pr1645v2TvTmplVxLanTunnelsInPQsEntry 67239936}

pr1645v2TvTmplVxLanTunnelsInPQsOctetsDropped OBJECT-TYPE
   SYNTAX      Counter64
   MAX-ACCESS  read-only
   STATUS      current
   DESCRIPTION
      "Path: tunnels.performance.vxLanTunnels.inPriorityQueues.octets.dropped

       64 bit unsigned wrappable counter."
   ::= {pr1645v2TvTmplVxLanTunnelsInPQsEntry 67305472}

pr1645v2TvTmplVxLanTunnelsInPQsOctetsRedDropped OBJECT-TYPE
   SYNTAX      Counter64
   MAX-ACCESS  read-only
   STATUS      current
   DESCRIPTION
      "Path: tunnels.performance.vxLanTunnels.inPriorityQueues.octets.redDropped

       64 bit unsigned wrappable counter."
   ::= {pr1645v2TvTmplVxLanTunnelsInPQsEntry 67502080}

pr1645v2TvTmplVxLanTunnelsInPQsOctetsCirTx OBJECT-TYPE
   SYNTAX      Counter64
   MAX-ACCESS  read-only
   STATUS      current
   DESCRIPTION
      "Path: tunnels.performance.vxLanTunnels.inPriorityQueues.octets.cirTx

       64 bit unsigned wrappable counter."
   ::= {pr1645v2TvTmplVxLanTunnelsInPQsEntry 67371008}

pr1645v2TvTmplVxLanTunnelsInPQsOctetsEirTx OBJECT-TYPE
   SYNTAX      Counter64
   MAX-ACCESS  read-only
   STATUS      current
   DESCRIPTION
      "Path: tunnels.performance.vxLanTunnels.inPriorityQueues.octets.eirTx

       64 bit unsigned wrappable counter."
   ::= {pr1645v2TvTmplVxLanTunnelsInPQsEntry 67436544}

pr1645v2TvTmplVxLanTunnelsInPQsOctetsViolateTx OBJECT-TYPE
   SYNTAX      Counter64
   MAX-ACCESS  read-only
   STATUS      current
   DESCRIPTION
      "Path: tunnels.performance.vxLanTunnels.inPriorityQueues.octets.violateTx

       64 bit unsigned wrappable counter."
   ::= {pr1645v2TvTmplVxLanTunnelsInPQsEntry 67633152}

pr1645v2TvTmplVxLanTunnelsInPQsOctetsBandwidth15sec OBJECT-TYPE
   SYNTAX      Integer32
   MAX-ACCESS  read-only
   STATUS      current
   DESCRIPTION
      "Path: tunnels.performance.vxLanTunnels.inPriorityQueues.octets.bandwidth.15sec

       unit name = bps
       formula = 8 * ; 8 /"
   ::= {pr1645v2TvTmplVxLanTunnelsInPQsEntry 70386944}

pr1645v2TvTmplVxLanTunnelsInPQsOctetsBandwidth30sec OBJECT-TYPE
   SYNTAX      Integer32
   MAX-ACCESS  read-only
   STATUS      current
   DESCRIPTION
      "Path: tunnels.performance.vxLanTunnels.inPriorityQueues.octets.bandwidth.30sec

       unit name = bps
       formula = 8 * ; 8 /"
   ::= {pr1645v2TvTmplVxLanTunnelsInPQsEntry 70388224}

pr1645v2TvTmplVxLanTunnelsInPQsOctetsBandwidth1min OBJECT-TYPE
   SYNTAX      Integer32
   MAX-ACCESS  read-only
   STATUS      current
   DESCRIPTION
      "Path: tunnels.performance.vxLanTunnels.inPriorityQueues.octets.bandwidth.1min

       unit name = bps
       formula = 8 * ; 8 /"
   ::= {pr1645v2TvTmplVxLanTunnelsInPQsEntry 70390784}

pr1645v2TvTmplVxLanTunnelsInPQsOctetsBandwidth2min OBJECT-TYPE
   SYNTAX      Integer32
   MAX-ACCESS  read-only
   STATUS      current
   DESCRIPTION
      "Path: tunnels.performance.vxLanTunnels.inPriorityQueues.octets.bandwidth.2min

       unit name = bps
       formula = 8 * ; 8 /"
   ::= {pr1645v2TvTmplVxLanTunnelsInPQsEntry 70395904}

pr1645v2TvTmplVxLanTunnelsInPQsOctetsBandwidth5min OBJECT-TYPE
   SYNTAX      Integer32
   MAX-ACCESS  read-only
   STATUS      current
   DESCRIPTION
      "Path: tunnels.performance.vxLanTunnels.inPriorityQueues.octets.bandwidth.5min

       unit name = bps
       formula = 8 * ; 8 /"
   ::= {pr1645v2TvTmplVxLanTunnelsInPQsEntry 70411264}

pr1645v2TvTmplVxLanTunnelsInPQsH2Performance OBJECT-TYPE
   SYNTAX      SEQUENCE OF Pr1645v2TvTmplVxLanTunnelsInPQsH2PerformanceEntry
   MAX-ACCESS  not-accessible
   STATUS      current
   DESCRIPTION
      ""
   ::= {pr1645v2TvTmplVxLanTunnels 100990976}

pr1645v2TvTmplVxLanTunnelsInPQsH2PerformanceEntry OBJECT-TYPE
   SYNTAX      Pr1645v2TvTmplVxLanTunnelsInPQsH2PerformanceEntry
   MAX-ACCESS  not-accessible
   STATUS      current
   DESCRIPTION
      ""
   INDEX      { pr1645v2TvTmplVxLanTunnelsTableIx,
                pr1645v2TvTmplVxLanTunnelsInPQsTableIx,
                pr1645v2TvTmplVxLanTunnelsInPQsH2PerformanceTableIx }
   ::= {pr1645v2TvTmplVxLanTunnelsInPQsH2Performance 1}

Pr1645v2TvTmplVxLanTunnelsInPQsH2PerformanceEntry ::=
   SEQUENCE
      {
      pr1645v2TvTmplVxLanTunnelsInPQsH2PerformanceTableIx
         TableIndex,
      pr1645v2TvTmplVxLanTunnelsInPQsH2PerformanceSysUpTime
         TimeTicks,
      pr1645v2TvTmplVxLanTunnelsInPQsH2PerformanceTotPkts
         Counter64,
      pr1645v2TvTmplVxLanTunnelsInPQsH2PerformanceDirTxPkts
         Counter64,
      pr1645v2TvTmplVxLanTunnelsInPQsH2PerformanceQdPkts
         Counter64,
      pr1645v2TvTmplVxLanTunnelsInPQsH2PerformanceDropPkts
         Counter64,
      pr1645v2TvTmplVxLanTunnelsInPQsH2PerformanceRDropPkts
         Counter64,
      pr1645v2TvTmplVxLanTunnelsInPQsH2PerformanceCirTxPkts
         Counter64,
      pr1645v2TvTmplVxLanTunnelsInPQsH2PerformanceEirTxPkts
         Counter64,
      pr1645v2TvTmplVxLanTunnelsInPQsH2PerformanceViolTxPkts
         Counter64,
      pr1645v2TvTmplVxLanTunnelsInPQsH2PerformanceTotOcts
         Counter64,
      pr1645v2TvTmplVxLanTunnelsInPQsH2PerformanceDirTxOcts
         Counter64,
      pr1645v2TvTmplVxLanTunnelsInPQsH2PerformanceQdOcts
         Counter64,
      pr1645v2TvTmplVxLanTunnelsInPQsH2PerformanceDropOcts
         Counter64,
      pr1645v2TvTmplVxLanTunnelsInPQsH2PerformanceRDropOcts
         Counter64,
      pr1645v2TvTmplVxLanTunnelsInPQsH2PerformanceCirTxOcts
         Counter64,
      pr1645v2TvTmplVxLanTunnelsInPQsH2PerformanceEirTxOcts
         Counter64,
      pr1645v2TvTmplVxLanTunnelsInPQsH2PerformanceViolTxOcts
         Counter64,
      pr1645v2TvTmplVxLanTunnelsInPQsH2PerformanceBandwidth
         Integer32
      }

pr1645v2TvTmplVxLanTunnelsInPQsH2PerformanceTableIx OBJECT-TYPE
   SYNTAX      TableIndex
   MAX-ACCESS  not-accessible
   STATUS      current
   DESCRIPTION
      ""
   ::= {pr1645v2TvTmplVxLanTunnelsInPQsH2PerformanceEntry 11}

pr1645v2TvTmplVxLanTunnelsInPQsH2PerformanceSysUpTime OBJECT-TYPE
   SYNTAX      TimeTicks
   MAX-ACCESS  read-only
   STATUS      current
   DESCRIPTION
      "Path: tunnels.performance.vxLanTunnels.inPriorityQueues.h2Performance.sysUpTime

       Time in centi-second."
   ::= {pr1645v2TvTmplVxLanTunnelsInPQsH2PerformanceEntry 16777216}

pr1645v2TvTmplVxLanTunnelsInPQsH2PerformanceTotPkts OBJECT-TYPE
   SYNTAX      Counter64
   MAX-ACCESS  read-only
   STATUS      current
   DESCRIPTION
      "Path: tunnels.performance.vxLanTunnels.inPriorityQueues.h2Performance.totalPkts

       64 bit unsigned wrappable counter."
   ::= {pr1645v2TvTmplVxLanTunnelsInPQsH2PerformanceEntry 234881024}

pr1645v2TvTmplVxLanTunnelsInPQsH2PerformanceDirTxPkts OBJECT-TYPE
   SYNTAX      Counter64
   MAX-ACCESS  read-only
   STATUS      current
   DESCRIPTION
      "Path: tunnels.performance.vxLanTunnels.inPriorityQueues.h2Performance.directTxPkts

       64 bit unsigned wrappable counter."
   ::= {pr1645v2TvTmplVxLanTunnelsInPQsH2PerformanceEntry 33554432}

pr1645v2TvTmplVxLanTunnelsInPQsH2PerformanceQdPkts OBJECT-TYPE
   SYNTAX      Counter64
   MAX-ACCESS  read-only
   STATUS      current
   DESCRIPTION
      "Path: tunnels.performance.vxLanTunnels.inPriorityQueues.h2Performance.queuedPkts

       64 bit unsigned wrappable counter."
   ::= {pr1645v2TvTmplVxLanTunnelsInPQsH2PerformanceEntry 50331648}

pr1645v2TvTmplVxLanTunnelsInPQsH2PerformanceDropPkts OBJECT-TYPE
   SYNTAX      Counter64
   MAX-ACCESS  read-only
   STATUS      current
   DESCRIPTION
      "Path: tunnels.performance.vxLanTunnels.inPriorityQueues.h2Performance.droppedPkts

       64 bit unsigned wrappable counter."
   ::= {pr1645v2TvTmplVxLanTunnelsInPQsH2PerformanceEntry 67108864}

pr1645v2TvTmplVxLanTunnelsInPQsH2PerformanceRDropPkts OBJECT-TYPE
   SYNTAX      Counter64
   MAX-ACCESS  read-only
   STATUS      current
   DESCRIPTION
      "Path: tunnels.performance.vxLanTunnels.inPriorityQueues.h2Performance.redDroppedPkts

       64 bit unsigned wrappable counter."
   ::= {pr1645v2TvTmplVxLanTunnelsInPQsH2PerformanceEntry 201326592}

pr1645v2TvTmplVxLanTunnelsInPQsH2PerformanceCirTxPkts OBJECT-TYPE
   SYNTAX      Counter64
   MAX-ACCESS  read-only
   STATUS      current
   DESCRIPTION
      "Path: tunnels.performance.vxLanTunnels.inPriorityQueues.h2Performance.cirTxPkts

       64 bit unsigned wrappable counter."
   ::= {pr1645v2TvTmplVxLanTunnelsInPQsH2PerformanceEntry 83886080}

pr1645v2TvTmplVxLanTunnelsInPQsH2PerformanceEirTxPkts OBJECT-TYPE
   SYNTAX      Counter64
   MAX-ACCESS  read-only
   STATUS      current
   DESCRIPTION
      "Path: tunnels.performance.vxLanTunnels.inPriorityQueues.h2Performance.eirTxPkts

       64 bit unsigned wrappable counter."
   ::= {pr1645v2TvTmplVxLanTunnelsInPQsH2PerformanceEntry 100663296}

pr1645v2TvTmplVxLanTunnelsInPQsH2PerformanceViolTxPkts OBJECT-TYPE
   SYNTAX      Counter64
   MAX-ACCESS  read-only
   STATUS      current
   DESCRIPTION
      "Path: tunnels.performance.vxLanTunnels.inPriorityQueues.h2Performance.violateTxPkts

       64 bit unsigned wrappable counter."
   ::= {pr1645v2TvTmplVxLanTunnelsInPQsH2PerformanceEntry 301989888}

pr1645v2TvTmplVxLanTunnelsInPQsH2PerformanceTotOcts OBJECT-TYPE
   SYNTAX      Counter64
   MAX-ACCESS  read-only
   STATUS      current
   DESCRIPTION
      "Path: tunnels.performance.vxLanTunnels.inPriorityQueues.h2Performance.totalOctets

       64 bit unsigned wrappable counter."
   ::= {pr1645v2TvTmplVxLanTunnelsInPQsH2PerformanceEntry 251658240}

pr1645v2TvTmplVxLanTunnelsInPQsH2PerformanceDirTxOcts OBJECT-TYPE
   SYNTAX      Counter64
   MAX-ACCESS  read-only
   STATUS      current
   DESCRIPTION
      "Path: tunnels.performance.vxLanTunnels.inPriorityQueues.h2Performance.directTxOctets

       64 bit unsigned wrappable counter."
   ::= {pr1645v2TvTmplVxLanTunnelsInPQsH2PerformanceEntry 117440512}

pr1645v2TvTmplVxLanTunnelsInPQsH2PerformanceQdOcts OBJECT-TYPE
   SYNTAX      Counter64
   MAX-ACCESS  read-only
   STATUS      current
   DESCRIPTION
      "Path: tunnels.performance.vxLanTunnels.inPriorityQueues.h2Performance.queuedOctets

       64 bit unsigned wrappable counter."
   ::= {pr1645v2TvTmplVxLanTunnelsInPQsH2PerformanceEntry 134217728}

pr1645v2TvTmplVxLanTunnelsInPQsH2PerformanceDropOcts OBJECT-TYPE
   SYNTAX      Counter64
   MAX-ACCESS  read-only
   STATUS      current
   DESCRIPTION
      "Path: tunnels.performance.vxLanTunnels.inPriorityQueues.h2Performance.droppedOctets

       64 bit unsigned wrappable counter."
   ::= {pr1645v2TvTmplVxLanTunnelsInPQsH2PerformanceEntry 150994944}

pr1645v2TvTmplVxLanTunnelsInPQsH2PerformanceRDropOcts OBJECT-TYPE
   SYNTAX      Counter64
   MAX-ACCESS  read-only
   STATUS      current
   DESCRIPTION
      "Path: tunnels.performance.vxLanTunnels.inPriorityQueues.h2Performance.redDroppedOctets

       64 bit unsigned wrappable counter."
   ::= {pr1645v2TvTmplVxLanTunnelsInPQsH2PerformanceEntry 218103808}

pr1645v2TvTmplVxLanTunnelsInPQsH2PerformanceCirTxOcts OBJECT-TYPE
   SYNTAX      Counter64
   MAX-ACCESS  read-only
   STATUS      current
   DESCRIPTION
      "Path: tunnels.performance.vxLanTunnels.inPriorityQueues.h2Performance.cirTxOctets

       64 bit unsigned wrappable counter."
   ::= {pr1645v2TvTmplVxLanTunnelsInPQsH2PerformanceEntry 167772160}

pr1645v2TvTmplVxLanTunnelsInPQsH2PerformanceEirTxOcts OBJECT-TYPE
   SYNTAX      Counter64
   MAX-ACCESS  read-only
   STATUS      current
   DESCRIPTION
      "Path: tunnels.performance.vxLanTunnels.inPriorityQueues.h2Performance.eirTxOctets

       64 bit unsigned wrappable counter."
   ::= {pr1645v2TvTmplVxLanTunnelsInPQsH2PerformanceEntry 184549376}

pr1645v2TvTmplVxLanTunnelsInPQsH2PerformanceViolTxOcts OBJECT-TYPE
   SYNTAX      Counter64
   MAX-ACCESS  read-only
   STATUS      current
   DESCRIPTION
      "Path: tunnels.performance.vxLanTunnels.inPriorityQueues.h2Performance.violateTxOctets

       64 bit unsigned wrappable counter."
   ::= {pr1645v2TvTmplVxLanTunnelsInPQsH2PerformanceEntry 318767104}

pr1645v2TvTmplVxLanTunnelsInPQsH2PerformanceBandwidth OBJECT-TYPE
   SYNTAX      Integer32
   MAX-ACCESS  read-only
   STATUS      current
   DESCRIPTION
      "Path: tunnels.performance.vxLanTunnels.inPriorityQueues.h2Performance.bandwidth

       unit name = bps
       formula = 8 * ; 8 /"
   ::= {pr1645v2TvTmplVxLanTunnelsInPQsH2PerformanceEntry 268435456}

pr1645v2TvTmplVxLanTunnelsInPQsH24Performance OBJECT-TYPE
   SYNTAX      SEQUENCE OF Pr1645v2TvTmplVxLanTunnelsInPQsH24PerformanceEntry
   MAX-ACCESS  not-accessible
   STATUS      current
   DESCRIPTION
      ""
   ::= {pr1645v2TvTmplVxLanTunnels 101056512}

pr1645v2TvTmplVxLanTunnelsInPQsH24PerformanceEntry OBJECT-TYPE
   SYNTAX      Pr1645v2TvTmplVxLanTunnelsInPQsH24PerformanceEntry
   MAX-ACCESS  not-accessible
   STATUS      current
   DESCRIPTION
      ""
   INDEX      { pr1645v2TvTmplVxLanTunnelsTableIx,
                pr1645v2TvTmplVxLanTunnelsInPQsTableIx,
                pr1645v2TvTmplVxLanTunnelsInPQsH24PerformanceTableIx }
   ::= {pr1645v2TvTmplVxLanTunnelsInPQsH24Performance 1}

Pr1645v2TvTmplVxLanTunnelsInPQsH24PerformanceEntry ::=
   SEQUENCE
      {
      pr1645v2TvTmplVxLanTunnelsInPQsH24PerformanceTableIx
         TableIndex,
      pr1645v2TvTmplVxLanTunnelsInPQsH24PerformanceSysUpTime
         TimeTicks,
      pr1645v2TvTmplVxLanTunnelsInPQsH24PerformanceTotPkts
         Counter64,
      pr1645v2TvTmplVxLanTunnelsInPQsH24PerformanceDirTxPkts
         Counter64,
      pr1645v2TvTmplVxLanTunnelsInPQsH24PerformanceQdPkts
         Counter64,
      pr1645v2TvTmplVxLanTunnelsInPQsH24PerformanceDropPkts
         Counter64,
      pr1645v2TvTmplVxLanTunnelsInPQsH24PerformanceRDropPkts
         Counter64,
      pr1645v2TvTmplVxLanTunnelsInPQsH24PerformanceCirTxPkts
         Counter64,
      pr1645v2TvTmplVxLanTunnelsInPQsH24PerformanceEirTxPkts
         Counter64,
      pr1645v2TvTmplVxLanTunnelsInPQsH24PerformanceViolTxPkts
         Counter64,
      pr1645v2TvTmplVxLanTunnelsInPQsH24PerformanceTotOcts
         Counter64,
      pr1645v2TvTmplVxLanTunnelsInPQsH24PerformanceDirTxOcts
         Counter64,
      pr1645v2TvTmplVxLanTunnelsInPQsH24PerformanceQdOcts
         Counter64,
      pr1645v2TvTmplVxLanTunnelsInPQsH24PerformanceDropOcts
         Counter64,
      pr1645v2TvTmplVxLanTunnelsInPQsH24PerformanceRDropOcts
         Counter64,
      pr1645v2TvTmplVxLanTunnelsInPQsH24PerformanceCirTxOcts
         Counter64,
      pr1645v2TvTmplVxLanTunnelsInPQsH24PerformanceEirTxOcts
         Counter64,
      pr1645v2TvTmplVxLanTunnelsInPQsH24PerformanceViolTxOcts
         Counter64,
      pr1645v2TvTmplVxLanTunnelsInPQsH24PerformanceBandwidth
         Integer32
      }

pr1645v2TvTmplVxLanTunnelsInPQsH24PerformanceTableIx OBJECT-TYPE
   SYNTAX      TableIndex
   MAX-ACCESS  not-accessible
   STATUS      current
   DESCRIPTION
      ""
   ::= {pr1645v2TvTmplVxLanTunnelsInPQsH24PerformanceEntry 11}

pr1645v2TvTmplVxLanTunnelsInPQsH24PerformanceSysUpTime OBJECT-TYPE
   SYNTAX      TimeTicks
   MAX-ACCESS  read-only
   STATUS      current
   DESCRIPTION
      "Path: tunnels.performance.vxLanTunnels.inPriorityQueues.h24Performance.sysUpTime

       Time in centi-second."
   ::= {pr1645v2TvTmplVxLanTunnelsInPQsH24PerformanceEntry 16777216}

pr1645v2TvTmplVxLanTunnelsInPQsH24PerformanceTotPkts OBJECT-TYPE
   SYNTAX      Counter64
   MAX-ACCESS  read-only
   STATUS      current
   DESCRIPTION
      "Path: tunnels.performance.vxLanTunnels.inPriorityQueues.h24Performance.totalPkts

       64 bit unsigned wrappable counter."
   ::= {pr1645v2TvTmplVxLanTunnelsInPQsH24PerformanceEntry 234881024}

pr1645v2TvTmplVxLanTunnelsInPQsH24PerformanceDirTxPkts OBJECT-TYPE
   SYNTAX      Counter64
   MAX-ACCESS  read-only
   STATUS      current
   DESCRIPTION
      "Path: tunnels.performance.vxLanTunnels.inPriorityQueues.h24Performance.directTxPkts

       64 bit unsigned wrappable counter."
   ::= {pr1645v2TvTmplVxLanTunnelsInPQsH24PerformanceEntry 33554432}

pr1645v2TvTmplVxLanTunnelsInPQsH24PerformanceQdPkts OBJECT-TYPE
   SYNTAX      Counter64
   MAX-ACCESS  read-only
   STATUS      current
   DESCRIPTION
      "Path: tunnels.performance.vxLanTunnels.inPriorityQueues.h24Performance.queuedPkts

       64 bit unsigned wrappable counter."
   ::= {pr1645v2TvTmplVxLanTunnelsInPQsH24PerformanceEntry 50331648}

pr1645v2TvTmplVxLanTunnelsInPQsH24PerformanceDropPkts OBJECT-TYPE
   SYNTAX      Counter64
   MAX-ACCESS  read-only
   STATUS      current
   DESCRIPTION
      "Path: tunnels.performance.vxLanTunnels.inPriorityQueues.h24Performance.droppedPkts

       64 bit unsigned wrappable counter."
   ::= {pr1645v2TvTmplVxLanTunnelsInPQsH24PerformanceEntry 67108864}

pr1645v2TvTmplVxLanTunnelsInPQsH24PerformanceRDropPkts OBJECT-TYPE
   SYNTAX      Counter64
   MAX-ACCESS  read-only
   STATUS      current
   DESCRIPTION
      "Path: tunnels.performance.vxLanTunnels.inPriorityQueues.h24Performance.redDroppedPkts

       64 bit unsigned wrappable counter."
   ::= {pr1645v2TvTmplVxLanTunnelsInPQsH24PerformanceEntry 201326592}

pr1645v2TvTmplVxLanTunnelsInPQsH24PerformanceCirTxPkts OBJECT-TYPE
   SYNTAX      Counter64
   MAX-ACCESS  read-only
   STATUS      current
   DESCRIPTION
      "Path: tunnels.performance.vxLanTunnels.inPriorityQueues.h24Performance.cirTxPkts

       64 bit unsigned wrappable counter."
   ::= {pr1645v2TvTmplVxLanTunnelsInPQsH24PerformanceEntry 83886080}

pr1645v2TvTmplVxLanTunnelsInPQsH24PerformanceEirTxPkts OBJECT-TYPE
   SYNTAX      Counter64
   MAX-ACCESS  read-only
   STATUS      current
   DESCRIPTION
      "Path: tunnels.performance.vxLanTunnels.inPriorityQueues.h24Performance.eirTxPkts

       64 bit unsigned wrappable counter."
   ::= {pr1645v2TvTmplVxLanTunnelsInPQsH24PerformanceEntry 100663296}

pr1645v2TvTmplVxLanTunnelsInPQsH24PerformanceViolTxPkts OBJECT-TYPE
   SYNTAX      Counter64
   MAX-ACCESS  read-only
   STATUS      current
   DESCRIPTION
      "Path: tunnels.performance.vxLanTunnels.inPriorityQueues.h24Performance.violateTxPkts

       64 bit unsigned wrappable counter."
   ::= {pr1645v2TvTmplVxLanTunnelsInPQsH24PerformanceEntry 301989888}

pr1645v2TvTmplVxLanTunnelsInPQsH24PerformanceTotOcts OBJECT-TYPE
   SYNTAX      Counter64
   MAX-ACCESS  read-only
   STATUS      current
   DESCRIPTION
      "Path: tunnels.performance.vxLanTunnels.inPriorityQueues.h24Performance.totalOctets

       64 bit unsigned wrappable counter."
   ::= {pr1645v2TvTmplVxLanTunnelsInPQsH24PerformanceEntry 251658240}

pr1645v2TvTmplVxLanTunnelsInPQsH24PerformanceDirTxOcts OBJECT-TYPE
   SYNTAX      Counter64
   MAX-ACCESS  read-only
   STATUS      current
   DESCRIPTION
      "Path: tunnels.performance.vxLanTunnels.inPriorityQueues.h24Performance.directTxOctets

       64 bit unsigned wrappable counter."
   ::= {pr1645v2TvTmplVxLanTunnelsInPQsH24PerformanceEntry 117440512}

pr1645v2TvTmplVxLanTunnelsInPQsH24PerformanceQdOcts OBJECT-TYPE
   SYNTAX      Counter64
   MAX-ACCESS  read-only
   STATUS      current
   DESCRIPTION
      "Path: tunnels.performance.vxLanTunnels.inPriorityQueues.h24Performance.queuedOctets

       64 bit unsigned wrappable counter."
   ::= {pr1645v2TvTmplVxLanTunnelsInPQsH24PerformanceEntry 134217728}

pr1645v2TvTmplVxLanTunnelsInPQsH24PerformanceDropOcts OBJECT-TYPE
   SYNTAX      Counter64
   MAX-ACCESS  read-only
   STATUS      current
   DESCRIPTION
      "Path: tunnels.performance.vxLanTunnels.inPriorityQueues.h24Performance.droppedOctets

       64 bit unsigned wrappable counter."
   ::= {pr1645v2TvTmplVxLanTunnelsInPQsH24PerformanceEntry 150994944}

pr1645v2TvTmplVxLanTunnelsInPQsH24PerformanceRDropOcts OBJECT-TYPE
   SYNTAX      Counter64
   MAX-ACCESS  read-only
   STATUS      current
   DESCRIPTION
      "Path: tunnels.performance.vxLanTunnels.inPriorityQueues.h24Performance.redDroppedOctets

       64 bit unsigned wrappable counter."
   ::= {pr1645v2TvTmplVxLanTunnelsInPQsH24PerformanceEntry 218103808}

pr1645v2TvTmplVxLanTunnelsInPQsH24PerformanceCirTxOcts OBJECT-TYPE
   SYNTAX      Counter64
   MAX-ACCESS  read-only
   STATUS      current
   DESCRIPTION
      "Path: tunnels.performance.vxLanTunnels.inPriorityQueues.h24Performance.cirTxOctets

       64 bit unsigned wrappable counter."
   ::= {pr1645v2TvTmplVxLanTunnelsInPQsH24PerformanceEntry 167772160}

pr1645v2TvTmplVxLanTunnelsInPQsH24PerformanceEirTxOcts OBJECT-TYPE
   SYNTAX      Counter64
   MAX-ACCESS  read-only
   STATUS      current
   DESCRIPTION
      "Path: tunnels.performance.vxLanTunnels.inPriorityQueues.h24Performance.eirTxOctets

       64 bit unsigned wrappable counter."
   ::= {pr1645v2TvTmplVxLanTunnelsInPQsH24PerformanceEntry 184549376}

pr1645v2TvTmplVxLanTunnelsInPQsH24PerformanceViolTxOcts OBJECT-TYPE
   SYNTAX      Counter64
   MAX-ACCESS  read-only
   STATUS      current
   DESCRIPTION
      "Path: tunnels.performance.vxLanTunnels.inPriorityQueues.h24Performance.violateTxOctets

       64 bit unsigned wrappable counter."
   ::= {pr1645v2TvTmplVxLanTunnelsInPQsH24PerformanceEntry 318767104}

pr1645v2TvTmplVxLanTunnelsInPQsH24PerformanceBandwidth OBJECT-TYPE
   SYNTAX      Integer32
   MAX-ACCESS  read-only
   STATUS      current
   DESCRIPTION
      "Path: tunnels.performance.vxLanTunnels.inPriorityQueues.h24Performance.bandwidth

       unit name = bps
       formula = 8 * ; 8 /"
   ::= {pr1645v2TvTmplVxLanTunnelsInPQsH24PerformanceEntry 268435456}

pr1645v2TvTmplVxLanTunnelsInPQsD7Performance OBJECT-TYPE
   SYNTAX      SEQUENCE OF Pr1645v2TvTmplVxLanTunnelsInPQsD7PerformanceEntry
   MAX-ACCESS  not-accessible
   STATUS      current
   DESCRIPTION
      ""
   ::= {pr1645v2TvTmplVxLanTunnels 101122048}

pr1645v2TvTmplVxLanTunnelsInPQsD7PerformanceEntry OBJECT-TYPE
   SYNTAX      Pr1645v2TvTmplVxLanTunnelsInPQsD7PerformanceEntry
   MAX-ACCESS  not-accessible
   STATUS      current
   DESCRIPTION
      ""
   INDEX      { pr1645v2TvTmplVxLanTunnelsTableIx,
                pr1645v2TvTmplVxLanTunnelsInPQsTableIx,
                pr1645v2TvTmplVxLanTunnelsInPQsD7PerformanceTableIx }
   ::= {pr1645v2TvTmplVxLanTunnelsInPQsD7Performance 1}

Pr1645v2TvTmplVxLanTunnelsInPQsD7PerformanceEntry ::=
   SEQUENCE
      {
      pr1645v2TvTmplVxLanTunnelsInPQsD7PerformanceTableIx
         TableIndex,
      pr1645v2TvTmplVxLanTunnelsInPQsD7PerformanceSysUpTime
         TimeTicks,
      pr1645v2TvTmplVxLanTunnelsInPQsD7PerformanceTotPkts
         Counter64,
      pr1645v2TvTmplVxLanTunnelsInPQsD7PerformanceDirTxPkts
         Counter64,
      pr1645v2TvTmplVxLanTunnelsInPQsD7PerformanceQdPkts
         Counter64,
      pr1645v2TvTmplVxLanTunnelsInPQsD7PerformanceDropPkts
         Counter64,
      pr1645v2TvTmplVxLanTunnelsInPQsD7PerformanceRDropPkts
         Counter64,
      pr1645v2TvTmplVxLanTunnelsInPQsD7PerformanceCirTxPkts
         Counter64,
      pr1645v2TvTmplVxLanTunnelsInPQsD7PerformanceEirTxPkts
         Counter64,
      pr1645v2TvTmplVxLanTunnelsInPQsD7PerformanceViolTxPkts
         Counter64,
      pr1645v2TvTmplVxLanTunnelsInPQsD7PerformanceTotOcts
         Counter64,
      pr1645v2TvTmplVxLanTunnelsInPQsD7PerformanceDirTxOcts
         Counter64,
      pr1645v2TvTmplVxLanTunnelsInPQsD7PerformanceQdOcts
         Counter64,
      pr1645v2TvTmplVxLanTunnelsInPQsD7PerformanceDropOcts
         Counter64,
      pr1645v2TvTmplVxLanTunnelsInPQsD7PerformanceRDropOcts
         Counter64,
      pr1645v2TvTmplVxLanTunnelsInPQsD7PerformanceCirTxOcts
         Counter64,
      pr1645v2TvTmplVxLanTunnelsInPQsD7PerformanceEirTxOcts
         Counter64,
      pr1645v2TvTmplVxLanTunnelsInPQsD7PerformanceViolTxOcts
         Counter64,
      pr1645v2TvTmplVxLanTunnelsInPQsD7PerformanceBandwidth
         Integer32
      }

pr1645v2TvTmplVxLanTunnelsInPQsD7PerformanceTableIx OBJECT-TYPE
   SYNTAX      TableIndex
   MAX-ACCESS  not-accessible
   STATUS      current
   DESCRIPTION
      ""
   ::= {pr1645v2TvTmplVxLanTunnelsInPQsD7PerformanceEntry 11}

pr1645v2TvTmplVxLanTunnelsInPQsD7PerformanceSysUpTime OBJECT-TYPE
   SYNTAX      TimeTicks
   MAX-ACCESS  read-only
   STATUS      current
   DESCRIPTION
      "Path: tunnels.performance.vxLanTunnels.inPriorityQueues.d7Performance.sysUpTime

       Time in centi-second."
   ::= {pr1645v2TvTmplVxLanTunnelsInPQsD7PerformanceEntry 16777216}

pr1645v2TvTmplVxLanTunnelsInPQsD7PerformanceTotPkts OBJECT-TYPE
   SYNTAX      Counter64
   MAX-ACCESS  read-only
   STATUS      current
   DESCRIPTION
      "Path: tunnels.performance.vxLanTunnels.inPriorityQueues.d7Performance.totalPkts

       64 bit unsigned wrappable counter."
   ::= {pr1645v2TvTmplVxLanTunnelsInPQsD7PerformanceEntry 234881024}

pr1645v2TvTmplVxLanTunnelsInPQsD7PerformanceDirTxPkts OBJECT-TYPE
   SYNTAX      Counter64
   MAX-ACCESS  read-only
   STATUS      current
   DESCRIPTION
      "Path: tunnels.performance.vxLanTunnels.inPriorityQueues.d7Performance.directTxPkts

       64 bit unsigned wrappable counter."
   ::= {pr1645v2TvTmplVxLanTunnelsInPQsD7PerformanceEntry 33554432}

pr1645v2TvTmplVxLanTunnelsInPQsD7PerformanceQdPkts OBJECT-TYPE
   SYNTAX      Counter64
   MAX-ACCESS  read-only
   STATUS      current
   DESCRIPTION
      "Path: tunnels.performance.vxLanTunnels.inPriorityQueues.d7Performance.queuedPkts

       64 bit unsigned wrappable counter."
   ::= {pr1645v2TvTmplVxLanTunnelsInPQsD7PerformanceEntry 50331648}

pr1645v2TvTmplVxLanTunnelsInPQsD7PerformanceDropPkts OBJECT-TYPE
   SYNTAX      Counter64
   MAX-ACCESS  read-only
   STATUS      current
   DESCRIPTION
      "Path: tunnels.performance.vxLanTunnels.inPriorityQueues.d7Performance.droppedPkts

       64 bit unsigned wrappable counter."
   ::= {pr1645v2TvTmplVxLanTunnelsInPQsD7PerformanceEntry 67108864}

pr1645v2TvTmplVxLanTunnelsInPQsD7PerformanceRDropPkts OBJECT-TYPE
   SYNTAX      Counter64
   MAX-ACCESS  read-only
   STATUS      current
   DESCRIPTION
      "Path: tunnels.performance.vxLanTunnels.inPriorityQueues.d7Performance.redDroppedPkts

       64 bit unsigned wrappable counter."
   ::= {pr1645v2TvTmplVxLanTunnelsInPQsD7PerformanceEntry 201326592}

pr1645v2TvTmplVxLanTunnelsInPQsD7PerformanceCirTxPkts OBJECT-TYPE
   SYNTAX      Counter64
   MAX-ACCESS  read-only
   STATUS      current
   DESCRIPTION
      "Path: tunnels.performance.vxLanTunnels.inPriorityQueues.d7Performance.cirTxPkts

       64 bit unsigned wrappable counter."
   ::= {pr1645v2TvTmplVxLanTunnelsInPQsD7PerformanceEntry 83886080}

pr1645v2TvTmplVxLanTunnelsInPQsD7PerformanceEirTxPkts OBJECT-TYPE
   SYNTAX      Counter64
   MAX-ACCESS  read-only
   STATUS      current
   DESCRIPTION
      "Path: tunnels.performance.vxLanTunnels.inPriorityQueues.d7Performance.eirTxPkts

       64 bit unsigned wrappable counter."
   ::= {pr1645v2TvTmplVxLanTunnelsInPQsD7PerformanceEntry 100663296}

pr1645v2TvTmplVxLanTunnelsInPQsD7PerformanceViolTxPkts OBJECT-TYPE
   SYNTAX      Counter64
   MAX-ACCESS  read-only
   STATUS      current
   DESCRIPTION
      "Path: tunnels.performance.vxLanTunnels.inPriorityQueues.d7Performance.violateTxPkts

       64 bit unsigned wrappable counter."
   ::= {pr1645v2TvTmplVxLanTunnelsInPQsD7PerformanceEntry 301989888}

pr1645v2TvTmplVxLanTunnelsInPQsD7PerformanceTotOcts OBJECT-TYPE
   SYNTAX      Counter64
   MAX-ACCESS  read-only
   STATUS      current
   DESCRIPTION
      "Path: tunnels.performance.vxLanTunnels.inPriorityQueues.d7Performance.totalOctets

       64 bit unsigned wrappable counter."
   ::= {pr1645v2TvTmplVxLanTunnelsInPQsD7PerformanceEntry 251658240}

pr1645v2TvTmplVxLanTunnelsInPQsD7PerformanceDirTxOcts OBJECT-TYPE
   SYNTAX      Counter64
   MAX-ACCESS  read-only
   STATUS      current
   DESCRIPTION
      "Path: tunnels.performance.vxLanTunnels.inPriorityQueues.d7Performance.directTxOctets

       64 bit unsigned wrappable counter."
   ::= {pr1645v2TvTmplVxLanTunnelsInPQsD7PerformanceEntry 117440512}

pr1645v2TvTmplVxLanTunnelsInPQsD7PerformanceQdOcts OBJECT-TYPE
   SYNTAX      Counter64
   MAX-ACCESS  read-only
   STATUS      current
   DESCRIPTION
      "Path: tunnels.performance.vxLanTunnels.inPriorityQueues.d7Performance.queuedOctets

       64 bit unsigned wrappable counter."
   ::= {pr1645v2TvTmplVxLanTunnelsInPQsD7PerformanceEntry 134217728}

pr1645v2TvTmplVxLanTunnelsInPQsD7PerformanceDropOcts OBJECT-TYPE
   SYNTAX      Counter64
   MAX-ACCESS  read-only
   STATUS      current
   DESCRIPTION
      "Path: tunnels.performance.vxLanTunnels.inPriorityQueues.d7Performance.droppedOctets

       64 bit unsigned wrappable counter."
   ::= {pr1645v2TvTmplVxLanTunnelsInPQsD7PerformanceEntry 150994944}

pr1645v2TvTmplVxLanTunnelsInPQsD7PerformanceRDropOcts OBJECT-TYPE
   SYNTAX      Counter64
   MAX-ACCESS  read-only
   STATUS      current
   DESCRIPTION
      "Path: tunnels.performance.vxLanTunnels.inPriorityQueues.d7Performance.redDroppedOctets

       64 bit unsigned wrappable counter."
   ::= {pr1645v2TvTmplVxLanTunnelsInPQsD7PerformanceEntry 218103808}

pr1645v2TvTmplVxLanTunnelsInPQsD7PerformanceCirTxOcts OBJECT-TYPE
   SYNTAX      Counter64
   MAX-ACCESS  read-only
   STATUS      current
   DESCRIPTION
      "Path: tunnels.performance.vxLanTunnels.inPriorityQueues.d7Performance.cirTxOctets

       64 bit unsigned wrappable counter."
   ::= {pr1645v2TvTmplVxLanTunnelsInPQsD7PerformanceEntry 167772160}

pr1645v2TvTmplVxLanTunnelsInPQsD7PerformanceEirTxOcts OBJECT-TYPE
   SYNTAX      Counter64
   MAX-ACCESS  read-only
   STATUS      current
   DESCRIPTION
      "Path: tunnels.performance.vxLanTunnels.inPriorityQueues.d7Performance.eirTxOctets

       64 bit unsigned wrappable counter."
   ::= {pr1645v2TvTmplVxLanTunnelsInPQsD7PerformanceEntry 184549376}

pr1645v2TvTmplVxLanTunnelsInPQsD7PerformanceViolTxOcts OBJECT-TYPE
   SYNTAX      Counter64
   MAX-ACCESS  read-only
   STATUS      current
   DESCRIPTION
      "Path: tunnels.performance.vxLanTunnels.inPriorityQueues.d7Performance.violateTxOctets

       64 bit unsigned wrappable counter."
   ::= {pr1645v2TvTmplVxLanTunnelsInPQsD7PerformanceEntry 318767104}

pr1645v2TvTmplVxLanTunnelsInPQsD7PerformanceBandwidth OBJECT-TYPE
   SYNTAX      Integer32
   MAX-ACCESS  read-only
   STATUS      current
   DESCRIPTION
      "Path: tunnels.performance.vxLanTunnels.inPriorityQueues.d7Performance.bandwidth

       unit name = bps
       formula = 8 * ; 8 /"
   ::= {pr1645v2TvTmplVxLanTunnelsInPQsD7PerformanceEntry 268435456}

pr1645v2TvTmplVxLanTunnelsOutPQs OBJECT-TYPE
   SYNTAX      SEQUENCE OF Pr1645v2TvTmplVxLanTunnelsOutPQsEntry
   MAX-ACCESS  not-accessible
   STATUS      current
   DESCRIPTION
      ""
   ::= {pr1645v2TvTmplVxLanTunnels 83886080}

pr1645v2TvTmplVxLanTunnelsOutPQsEntry OBJECT-TYPE
   SYNTAX      Pr1645v2TvTmplVxLanTunnelsOutPQsEntry
   MAX-ACCESS  not-accessible
   STATUS      current
   DESCRIPTION
      ""
   INDEX      { pr1645v2TvTmplVxLanTunnelsTableIx,
                pr1645v2TvTmplVxLanTunnelsOutPQsTableIx }
   ::= {pr1645v2TvTmplVxLanTunnelsOutPQs 1}

Pr1645v2TvTmplVxLanTunnelsOutPQsEntry ::=
   SEQUENCE
      {
      pr1645v2TvTmplVxLanTunnelsOutPQsTableIx
         TableIndex,
      pr1645v2TvTmplVxLanTunnelsOutPQsName
         INTEGER,
      pr1645v2TvTmplVxLanTunnelsOutPQsLength
         Integer32,
      pr1645v2TvTmplVxLanTunnelsOutPQsOctetLength
         Integer32,
      pr1645v2TvTmplVxLanTunnelsOutPQsRedLength
         Integer32,
      pr1645v2TvTmplVxLanTunnelsOutPQsPacketsTotal
         Counter64,
      pr1645v2TvTmplVxLanTunnelsOutPQsPacketsDirectTx
         Counter64,
      pr1645v2TvTmplVxLanTunnelsOutPQsPacketsQueued
         Counter64,
      pr1645v2TvTmplVxLanTunnelsOutPQsPacketsDropped
         Counter64,
      pr1645v2TvTmplVxLanTunnelsOutPQsPacketsRedDropped
         Counter64,
      pr1645v2TvTmplVxLanTunnelsOutPQsPacketsCirTx
         Counter64,
      pr1645v2TvTmplVxLanTunnelsOutPQsPacketsEirTx
         Counter64,
      pr1645v2TvTmplVxLanTunnelsOutPQsPacketsViolateTx
         Counter64,
      pr1645v2TvTmplVxLanTunnelsOutPQsOctetsTotal
         Counter64,
      pr1645v2TvTmplVxLanTunnelsOutPQsOctetsDirectTx
         Counter64,
      pr1645v2TvTmplVxLanTunnelsOutPQsOctetsQueued
         Counter64,
      pr1645v2TvTmplVxLanTunnelsOutPQsOctetsDropped
         Counter64,
      pr1645v2TvTmplVxLanTunnelsOutPQsOctetsRedDropped
         Counter64,
      pr1645v2TvTmplVxLanTunnelsOutPQsOctetsCirTx
         Counter64,
      pr1645v2TvTmplVxLanTunnelsOutPQsOctetsEirTx
         Counter64,
      pr1645v2TvTmplVxLanTunnelsOutPQsOctetsViolateTx
         Counter64,
      pr1645v2TvTmplVxLanTunnelsOutPQsOctetsBandwidth15sec
         Integer32,
      pr1645v2TvTmplVxLanTunnelsOutPQsOctetsBandwidth30sec
         Integer32,
      pr1645v2TvTmplVxLanTunnelsOutPQsOctetsBandwidth1min
         Integer32,
      pr1645v2TvTmplVxLanTunnelsOutPQsOctetsBandwidth2min
         Integer32,
      pr1645v2TvTmplVxLanTunnelsOutPQsOctetsBandwidth5min
         Integer32
      }

pr1645v2TvTmplVxLanTunnelsOutPQsTableIx OBJECT-TYPE
   SYNTAX      TableIndex
   MAX-ACCESS  not-accessible
   STATUS      current
   DESCRIPTION
      ""
   ::= {pr1645v2TvTmplVxLanTunnelsOutPQsEntry 11}

pr1645v2TvTmplVxLanTunnelsOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: tunnels.performance.vxLanTunnels.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2TvTmplVxLanTunnelsOutPQsEntry 16777216}

pr1645v2TvTmplVxLanTunnelsOutPQsLength OBJECT-TYPE
   SYNTAX      Integer32
   MAX-ACCESS  read-only
   STATUS      current
   DESCRIPTION
      "Path: tunnels.performance.vxLanTunnels.outPriorityQueues.length"
   ::= {pr1645v2TvTmplVxLanTunnelsOutPQsEntry 33554432}

pr1645v2TvTmplVxLanTunnelsOutPQsOctetLength OBJECT-TYPE
   SYNTAX      Integer32
   MAX-ACCESS  read-only
   STATUS      current
   DESCRIPTION
      "Path: tunnels.performance.vxLanTunnels.outPriorityQueues.octetLength"
   ::= {pr1645v2TvTmplVxLanTunnelsOutPQsEntry 150994944}

pr1645v2TvTmplVxLanTunnelsOutPQsRedLength OBJECT-TYPE
   SYNTAX      Integer32
   MAX-ACCESS  read-only
   STATUS      current
   DESCRIPTION
      "Path: tunnels.performance.vxLanTunnels.outPriorityQueues.redLength"
   ::= {pr1645v2TvTmplVxLanTunnelsOutPQsEntry 134217728}

pr1645v2TvTmplVxLanTunnelsOutPQsPacketsTotal OBJECT-TYPE
   SYNTAX      Counter64
   MAX-ACCESS  read-only
   STATUS      current
   DESCRIPTION
      "Path: tunnels.performance.vxLanTunnels.outPriorityQueues.packets.total

       64 bit unsigned wrappable counter."
   ::= {pr1645v2TvTmplVxLanTunnelsOutPQsEntry 50790400}

pr1645v2TvTmplVxLanTunnelsOutPQsPacketsDirectTx OBJECT-TYPE
   SYNTAX      Counter64
   MAX-ACCESS  read-only
   STATUS      current
   DESCRIPTION
      "Path: tunnels.performance.vxLanTunnels.outPriorityQueues.packets.directTx

       64 bit unsigned wrappable counter."
   ::= {pr1645v2TvTmplVxLanTunnelsOutPQsEntry 50397184}

pr1645v2TvTmplVxLanTunnelsOutPQsPacketsQueued OBJECT-TYPE
   SYNTAX      Counter64
   MAX-ACCESS  read-only
   STATUS      current
   DESCRIPTION
      "Path: tunnels.performance.vxLanTunnels.outPriorityQueues.packets.queued

       64 bit unsigned wrappable counter."
   ::= {pr1645v2TvTmplVxLanTunnelsOutPQsEntry 50462720}

pr1645v2TvTmplVxLanTunnelsOutPQsPacketsDropped OBJECT-TYPE
   SYNTAX      Counter64
   MAX-ACCESS  read-only
   STATUS      current
   DESCRIPTION
      "Path: tunnels.performance.vxLanTunnels.outPriorityQueues.packets.dropped

       64 bit unsigned wrappable counter."
   ::= {pr1645v2TvTmplVxLanTunnelsOutPQsEntry 50528256}

pr1645v2TvTmplVxLanTunnelsOutPQsPacketsRedDropped OBJECT-TYPE
   SYNTAX      Counter64
   MAX-ACCESS  read-only
   STATUS      current
   DESCRIPTION
      "Path: tunnels.performance.vxLanTunnels.outPriorityQueues.packets.redDropped

       64 bit unsigned wrappable counter."
   ::= {pr1645v2TvTmplVxLanTunnelsOutPQsEntry 50724864}

pr1645v2TvTmplVxLanTunnelsOutPQsPacketsCirTx OBJECT-TYPE
   SYNTAX      Counter64
   MAX-ACCESS  read-only
   STATUS      current
   DESCRIPTION
      "Path: tunnels.performance.vxLanTunnels.outPriorityQueues.packets.cirTx

       64 bit unsigned wrappable counter."
   ::= {pr1645v2TvTmplVxLanTunnelsOutPQsEntry 50593792}

pr1645v2TvTmplVxLanTunnelsOutPQsPacketsEirTx OBJECT-TYPE
   SYNTAX      Counter64
   MAX-ACCESS  read-only
   STATUS      current
   DESCRIPTION
      "Path: tunnels.performance.vxLanTunnels.outPriorityQueues.packets.eirTx

       64 bit unsigned wrappable counter."
   ::= {pr1645v2TvTmplVxLanTunnelsOutPQsEntry 50659328}

pr1645v2TvTmplVxLanTunnelsOutPQsPacketsViolateTx OBJECT-TYPE
   SYNTAX      Counter64
   MAX-ACCESS  read-only
   STATUS      current
   DESCRIPTION
      "Path: tunnels.performance.vxLanTunnels.outPriorityQueues.packets.violateTx

       64 bit unsigned wrappable counter."
   ::= {pr1645v2TvTmplVxLanTunnelsOutPQsEntry 50855936}

pr1645v2TvTmplVxLanTunnelsOutPQsOctetsTotal OBJECT-TYPE
   SYNTAX      Counter64
   MAX-ACCESS  read-only
   STATUS      current
   DESCRIPTION
      "Path: tunnels.performance.vxLanTunnels.outPriorityQueues.octets.total

       64 bit unsigned wrappable counter."
   ::= {pr1645v2TvTmplVxLanTunnelsOutPQsEntry 67567616}

pr1645v2TvTmplVxLanTunnelsOutPQsOctetsDirectTx OBJECT-TYPE
   SYNTAX      Counter64
   MAX-ACCESS  read-only
   STATUS      current
   DESCRIPTION
      "Path: tunnels.performance.vxLanTunnels.outPriorityQueues.octets.directTx

       64 bit unsigned wrappable counter."
   ::= {pr1645v2TvTmplVxLanTunnelsOutPQsEntry 67174400}

pr1645v2TvTmplVxLanTunnelsOutPQsOctetsQueued OBJECT-TYPE
   SYNTAX      Counter64
   MAX-ACCESS  read-only
   STATUS      current
   DESCRIPTION
      "Path: tunnels.performance.vxLanTunnels.outPriorityQueues.octets.queued

       64 bit unsigned wrappable counter."
   ::= {pr1645v2TvTmplVxLanTunnelsOutPQsEntry 67239936}

pr1645v2TvTmplVxLanTunnelsOutPQsOctetsDropped OBJECT-TYPE
   SYNTAX      Counter64
   MAX-ACCESS  read-only
   STATUS      current
   DESCRIPTION
      "Path: tunnels.performance.vxLanTunnels.outPriorityQueues.octets.dropped

       64 bit unsigned wrappable counter."
   ::= {pr1645v2TvTmplVxLanTunnelsOutPQsEntry 67305472}

pr1645v2TvTmplVxLanTunnelsOutPQsOctetsRedDropped OBJECT-TYPE
   SYNTAX      Counter64
   MAX-ACCESS  read-only
   STATUS      current
   DESCRIPTION
      "Path: tunnels.performance.vxLanTunnels.outPriorityQueues.octets.redDropped

       64 bit unsigned wrappable counter."
   ::= {pr1645v2TvTmplVxLanTunnelsOutPQsEntry 67502080}

pr1645v2TvTmplVxLanTunnelsOutPQsOctetsCirTx OBJECT-TYPE
   SYNTAX      Counter64
   MAX-ACCESS  read-only
   STATUS      current
   DESCRIPTION
      "Path: tunnels.performance.vxLanTunnels.outPriorityQueues.octets.cirTx

       64 bit unsigned wrappable counter."
   ::= {pr1645v2TvTmplVxLanTunnelsOutPQsEntry 67371008}

pr1645v2TvTmplVxLanTunnelsOutPQsOctetsEirTx OBJECT-TYPE
   SYNTAX      Counter64
   MAX-ACCESS  read-only
   STATUS      current
   DESCRIPTION
      "Path: tunnels.performance.vxLanTunnels.outPriorityQueues.octets.eirTx

       64 bit unsigned wrappable counter."
   ::= {pr1645v2TvTmplVxLanTunnelsOutPQsEntry 67436544}

pr1645v2TvTmplVxLanTunnelsOutPQsOctetsViolateTx OBJECT-TYPE
   SYNTAX      Counter64
   MAX-ACCESS  read-only
   STATUS      current
   DESCRIPTION
      "Path: tunnels.performance.vxLanTunnels.outPriorityQueues.octets.violateTx

       64 bit unsigned wrappable counter."
   ::= {pr1645v2TvTmplVxLanTunnelsOutPQsEntry 67633152}

pr1645v2TvTmplVxLanTunnelsOutPQsOctetsBandwidth15sec OBJECT-TYPE
   SYNTAX      Integer32
   MAX-ACCESS  read-only
   STATUS      current
   DESCRIPTION
      "Path: tunnels.performance.vxLanTunnels.outPriorityQueues.octets.bandwidth.15sec

       unit name = bps
       formula = 8 * ; 8 /"
   ::= {pr1645v2TvTmplVxLanTunnelsOutPQsEntry 70386944}

pr1645v2TvTmplVxLanTunnelsOutPQsOctetsBandwidth30sec OBJECT-TYPE
   SYNTAX      Integer32
   MAX-ACCESS  read-only
   STATUS      current
   DESCRIPTION
      "Path: tunnels.performance.vxLanTunnels.outPriorityQueues.octets.bandwidth.30sec

       unit name = bps
       formula = 8 * ; 8 /"
   ::= {pr1645v2TvTmplVxLanTunnelsOutPQsEntry 70388224}

pr1645v2TvTmplVxLanTunnelsOutPQsOctetsBandwidth1min OBJECT-TYPE
   SYNTAX      Integer32
   MAX-ACCESS  read-only
   STATUS      current
   DESCRIPTION
      "Path: tunnels.performance.vxLanTunnels.outPriorityQueues.octets.bandwidth.1min

       unit name = bps
       formula = 8 * ; 8 /"
   ::= {pr1645v2TvTmplVxLanTunnelsOutPQsEntry 70390784}

pr1645v2TvTmplVxLanTunnelsOutPQsOctetsBandwidth2min OBJECT-TYPE
   SYNTAX      Integer32
   MAX-ACCESS  read-only
   STATUS      current
   DESCRIPTION
      "Path: tunnels.performance.vxLanTunnels.outPriorityQueues.octets.bandwidth.2min

       unit name = bps
       formula = 8 * ; 8 /"
   ::= {pr1645v2TvTmplVxLanTunnelsOutPQsEntry 70395904}

pr1645v2TvTmplVxLanTunnelsOutPQsOctetsBandwidth5min OBJECT-TYPE
   SYNTAX      Integer32
   MAX-ACCESS  read-only
   STATUS      current
   DESCRIPTION
      "Path: tunnels.performance.vxLanTunnels.outPriorityQueues.octets.bandwidth.5min

       unit name = bps
       formula = 8 * ; 8 /"
   ::= {pr1645v2TvTmplVxLanTunnelsOutPQsEntry 70411264}

pr1645v2TvTmplVxLanTunnelsOutPQsH2Performance OBJECT-TYPE
   SYNTAX      SEQUENCE OF Pr1645v2TvTmplVxLanTunnelsOutPQsH2PerformanceEntry
   MAX-ACCESS  not-accessible
   STATUS      current
   DESCRIPTION
      ""
   ::= {pr1645v2TvTmplVxLanTunnels 84213760}

pr1645v2TvTmplVxLanTunnelsOutPQsH2PerformanceEntry OBJECT-TYPE
   SYNTAX      Pr1645v2TvTmplVxLanTunnelsOutPQsH2PerformanceEntry
   MAX-ACCESS  not-accessible
   STATUS      current
   DESCRIPTION
      ""
   INDEX      { pr1645v2TvTmplVxLanTunnelsTableIx,
                pr1645v2TvTmplVxLanTunnelsOutPQsTableIx,
                pr1645v2TvTmplVxLanTunnelsOutPQsH2PerformanceTableIx }
   ::= {pr1645v2TvTmplVxLanTunnelsOutPQsH2Performance 1}

Pr1645v2TvTmplVxLanTunnelsOutPQsH2PerformanceEntry ::=
   SEQUENCE
      {
      pr1645v2TvTmplVxLanTunnelsOutPQsH2PerformanceTableIx
         TableIndex,
      pr1645v2TvTmplVxLanTunnelsOutPQsH2PerformanceSysUpTime
         TimeTicks,
      pr1645v2TvTmplVxLanTunnelsOutPQsH2PerformanceTotPkts
         Counter64,
      pr1645v2TvTmplVxLanTunnelsOutPQsH2PerformanceDirTxPkts
         Counter64,
      pr1645v2TvTmplVxLanTunnelsOutPQsH2PerformanceQdPkts
         Counter64,
      pr1645v2TvTmplVxLanTunnelsOutPQsH2PerformanceDropPkts
         Counter64,
      pr1645v2TvTmplVxLanTunnelsOutPQsH2PerformanceRDropPkts
         Counter64,
      pr1645v2TvTmplVxLanTunnelsOutPQsH2PerformanceCirTxPkts
         Counter64,
      pr1645v2TvTmplVxLanTunnelsOutPQsH2PerformanceEirTxPkts
         Counter64,
      pr1645v2TvTmplVxLanTunnelsOutPQsH2PerformanceViolTxPkts
         Counter64,
      pr1645v2TvTmplVxLanTunnelsOutPQsH2PerformanceTotOcts
         Counter64,
      pr1645v2TvTmplVxLanTunnelsOutPQsH2PerformanceDirTxOcts
         Counter64,
      pr1645v2TvTmplVxLanTunnelsOutPQsH2PerformanceQdOcts
         Counter64,
      pr1645v2TvTmplVxLanTunnelsOutPQsH2PerformanceDropOcts
         Counter64,
      pr1645v2TvTmplVxLanTunnelsOutPQsH2PerformanceRDropOcts
         Counter64,
      pr1645v2TvTmplVxLanTunnelsOutPQsH2PerformanceCirTxOcts
         Counter64,
      pr1645v2TvTmplVxLanTunnelsOutPQsH2PerformanceEirTxOcts
         Counter64,
      pr1645v2TvTmplVxLanTunnelsOutPQsH2PerformanceViolTxOcts
         Counter64,
      pr1645v2TvTmplVxLanTunnelsOutPQsH2PerformanceBandwidth
         Integer32
      }

pr1645v2TvTmplVxLanTunnelsOutPQsH2PerformanceTableIx OBJECT-TYPE
   SYNTAX      TableIndex
   MAX-ACCESS  not-accessible
   STATUS      current
   DESCRIPTION
      ""
   ::= {pr1645v2TvTmplVxLanTunnelsOutPQsH2PerformanceEntry 11}

pr1645v2TvTmplVxLanTunnelsOutPQsH2PerformanceSysUpTime OBJECT-TYPE
   SYNTAX      TimeTicks
   MAX-ACCESS  read-only
   STATUS      current
   DESCRIPTION
      "Path: tunnels.performance.vxLanTunnels.outPriorityQueues.h2Performance.sysUpTime

       Time in centi-second."
   ::= {pr1645v2TvTmplVxLanTunnelsOutPQsH2PerformanceEntry 16777216}

pr1645v2TvTmplVxLanTunnelsOutPQsH2PerformanceTotPkts OBJECT-TYPE
   SYNTAX      Counter64
   MAX-ACCESS  read-only
   STATUS      current
   DESCRIPTION
      "Path: tunnels.performance.vxLanTunnels.outPriorityQueues.h2Performance.totalPkts

       64 bit unsigned wrappable counter."
   ::= {pr1645v2TvTmplVxLanTunnelsOutPQsH2PerformanceEntry 234881024}

pr1645v2TvTmplVxLanTunnelsOutPQsH2PerformanceDirTxPkts OBJECT-TYPE
   SYNTAX      Counter64
   MAX-ACCESS  read-only
   STATUS      current
   DESCRIPTION
      "Path: tunnels.performance.vxLanTunnels.outPriorityQueues.h2Performance.directTxPkts

       64 bit unsigned wrappable counter."
   ::= {pr1645v2TvTmplVxLanTunnelsOutPQsH2PerformanceEntry 33554432}

pr1645v2TvTmplVxLanTunnelsOutPQsH2PerformanceQdPkts OBJECT-TYPE
   SYNTAX      Counter64
   MAX-ACCESS  read-only
   STATUS      current
   DESCRIPTION
      "Path: tunnels.performance.vxLanTunnels.outPriorityQueues.h2Performance.queuedPkts

       64 bit unsigned wrappable counter."
   ::= {pr1645v2TvTmplVxLanTunnelsOutPQsH2PerformanceEntry 50331648}

pr1645v2TvTmplVxLanTunnelsOutPQsH2PerformanceDropPkts OBJECT-TYPE
   SYNTAX      Counter64
   MAX-ACCESS  read-only
   STATUS      current
   DESCRIPTION
      "Path: tunnels.performance.vxLanTunnels.outPriorityQueues.h2Performance.droppedPkts

       64 bit unsigned wrappable counter."
   ::= {pr1645v2TvTmplVxLanTunnelsOutPQsH2PerformanceEntry 67108864}

pr1645v2TvTmplVxLanTunnelsOutPQsH2PerformanceRDropPkts OBJECT-TYPE
   SYNTAX      Counter64
   MAX-ACCESS  read-only
   STATUS      current
   DESCRIPTION
      "Path: tunnels.performance.vxLanTunnels.outPriorityQueues.h2Performance.redDroppedPkts

       64 bit unsigned wrappable counter."
   ::= {pr1645v2TvTmplVxLanTunnelsOutPQsH2PerformanceEntry 201326592}

pr1645v2TvTmplVxLanTunnelsOutPQsH2PerformanceCirTxPkts OBJECT-TYPE
   SYNTAX      Counter64
   MAX-ACCESS  read-only
   STATUS      current
   DESCRIPTION
      "Path: tunnels.performance.vxLanTunnels.outPriorityQueues.h2Performance.cirTxPkts

       64 bit unsigned wrappable counter."
   ::= {pr1645v2TvTmplVxLanTunnelsOutPQsH2PerformanceEntry 83886080}

pr1645v2TvTmplVxLanTunnelsOutPQsH2PerformanceEirTxPkts OBJECT-TYPE
   SYNTAX      Counter64
   MAX-ACCESS  read-only
   STATUS      current
   DESCRIPTION
      "Path: tunnels.performance.vxLanTunnels.outPriorityQueues.h2Performance.eirTxPkts

       64 bit unsigned wrappable counter."
   ::= {pr1645v2TvTmplVxLanTunnelsOutPQsH2PerformanceEntry 100663296}

pr1645v2TvTmplVxLanTunnelsOutPQsH2PerformanceViolTxPkts OBJECT-TYPE
   SYNTAX      Counter64
   MAX-ACCESS  read-only
   STATUS      current
   DESCRIPTION
      "Path: tunnels.performance.vxLanTunnels.outPriorityQueues.h2Performance.violateTxPkts

       64 bit unsigned wrappable counter."
   ::= {pr1645v2TvTmplVxLanTunnelsOutPQsH2PerformanceEntry 301989888}

pr1645v2TvTmplVxLanTunnelsOutPQsH2PerformanceTotOcts OBJECT-TYPE
   SYNTAX      Counter64
   MAX-ACCESS  read-only
   STATUS      current
   DESCRIPTION
      "Path: tunnels.performance.vxLanTunnels.outPriorityQueues.h2Performance.totalOctets

       64 bit unsigned wrappable counter."
   ::= {pr1645v2TvTmplVxLanTunnelsOutPQsH2PerformanceEntry 251658240}

pr1645v2TvTmplVxLanTunnelsOutPQsH2PerformanceDirTxOcts OBJECT-TYPE
   SYNTAX      Counter64
   MAX-ACCESS  read-only
   STATUS      current
   DESCRIPTION
      "Path: tunnels.performance.vxLanTunnels.outPriorityQueues.h2Performance.directTxOctets

       64 bit unsigned wrappable counter."
   ::= {pr1645v2TvTmplVxLanTunnelsOutPQsH2PerformanceEntry 117440512}

pr1645v2TvTmplVxLanTunnelsOutPQsH2PerformanceQdOcts OBJECT-TYPE
   SYNTAX      Counter64
   MAX-ACCESS  read-only
   STATUS      current
   DESCRIPTION
      "Path: tunnels.performance.vxLanTunnels.outPriorityQueues.h2Performance.queuedOctets

       64 bit unsigned wrappable counter."
   ::= {pr1645v2TvTmplVxLanTunnelsOutPQsH2PerformanceEntry 134217728}

pr1645v2TvTmplVxLanTunnelsOutPQsH2PerformanceDropOcts OBJECT-TYPE
   SYNTAX      Counter64
   MAX-ACCESS  read-only
   STATUS      current
   DESCRIPTION
      "Path: tunnels.performance.vxLanTunnels.outPriorityQueues.h2Performance.droppedOctets

       64 bit unsigned wrappable counter."
   ::= {pr1645v2TvTmplVxLanTunnelsOutPQsH2PerformanceEntry 150994944}

pr1645v2TvTmplVxLanTunnelsOutPQsH2PerformanceRDropOcts OBJECT-TYPE
   SYNTAX      Counter64
   MAX-ACCESS  read-only
   STATUS      current
   DESCRIPTION
      "Path: tunnels.performance.vxLanTunnels.outPriorityQueues.h2Performance.redDroppedOctets

       64 bit unsigned wrappable counter."
   ::= {pr1645v2TvTmplVxLanTunnelsOutPQsH2PerformanceEntry 218103808}

pr1645v2TvTmplVxLanTunnelsOutPQsH2PerformanceCirTxOcts OBJECT-TYPE
   SYNTAX      Counter64
   MAX-ACCESS  read-only
   STATUS      current
   DESCRIPTION
      "Path: tunnels.performance.vxLanTunnels.outPriorityQueues.h2Performance.cirTxOctets

       64 bit unsigned wrappable counter."
   ::= {pr1645v2TvTmplVxLanTunnelsOutPQsH2PerformanceEntry 167772160}

pr1645v2TvTmplVxLanTunnelsOutPQsH2PerformanceEirTxOcts OBJECT-TYPE
   SYNTAX      Counter64
   MAX-ACCESS  read-only
   STATUS      current
   DESCRIPTION
      "Path: tunnels.performance.vxLanTunnels.outPriorityQueues.h2Performance.eirTxOctets

       64 bit unsigned wrappable counter."
   ::= {pr1645v2TvTmplVxLanTunnelsOutPQsH2PerformanceEntry 184549376}

pr1645v2TvTmplVxLanTunnelsOutPQsH2PerformanceViolTxOcts OBJECT-TYPE
   SYNTAX      Counter64
   MAX-ACCESS  read-only
   STATUS      current
   DESCRIPTION
      "Path: tunnels.performance.vxLanTunnels.outPriorityQueues.h2Performance.violateTxOctets

       64 bit unsigned wrappable counter."
   ::= {pr1645v2TvTmplVxLanTunnelsOutPQsH2PerformanceEntry 318767104}

pr1645v2TvTmplVxLanTunnelsOutPQsH2PerformanceBandwidth OBJECT-TYPE
   SYNTAX      Integer32
   MAX-ACCESS  read-only
   STATUS      current
   DESCRIPTION
      "Path: tunnels.performance.vxLanTunnels.outPriorityQueues.h2Performance.bandwidth

       unit name = bps
       formula = 8 * ; 8 /"
   ::= {pr1645v2TvTmplVxLanTunnelsOutPQsH2PerformanceEntry 268435456}

pr1645v2TvTmplVxLanTunnelsOutPQsH24Performance OBJECT-TYPE
   SYNTAX      SEQUENCE OF Pr1645v2TvTmplVxLanTunnelsOutPQsH24PerformanceEntry
   MAX-ACCESS  not-accessible
   STATUS      current
   DESCRIPTION
      ""
   ::= {pr1645v2TvTmplVxLanTunnels 84279296}

pr1645v2TvTmplVxLanTunnelsOutPQsH24PerformanceEntry OBJECT-TYPE
   SYNTAX      Pr1645v2TvTmplVxLanTunnelsOutPQsH24PerformanceEntry
   MAX-ACCESS  not-accessible
   STATUS      current
   DESCRIPTION
      ""
   INDEX      { pr1645v2TvTmplVxLanTunnelsTableIx,
                pr1645v2TvTmplVxLanTunnelsOutPQsTableIx,
                pr1645v2TvTmplVxLanTunnelsOutPQsH24PerformanceTableIx }
   ::= {pr1645v2TvTmplVxLanTunnelsOutPQsH24Performance 1}

Pr1645v2TvTmplVxLanTunnelsOutPQsH24PerformanceEntry ::=
   SEQUENCE
      {
      pr1645v2TvTmplVxLanTunnelsOutPQsH24PerformanceTableIx
         TableIndex,
      pr1645v2TvTmplVxLanTunnelsOutPQsH24PerformanceSysUpTime
         TimeTicks,
      pr1645v2TvTmplVxLanTunnelsOutPQsH24PerformanceTotPkts
         Counter64,
      pr1645v2TvTmplVxLanTunnelsOutPQsH24PerformanceDirTxPkts
         Counter64,
      pr1645v2TvTmplVxLanTunnelsOutPQsH24PerformanceQdPkts
         Counter64,
      pr1645v2TvTmplVxLanTunnelsOutPQsH24PerformanceDropPkts
         Counter64,
      pr1645v2TvTmplVxLanTunnelsOutPQsH24PerformanceRDropPkts
         Counter64,
      pr1645v2TvTmplVxLanTunnelsOutPQsH24PerformanceCirTxPkts
         Counter64,
      pr1645v2TvTmplVxLanTunnelsOutPQsH24PerformanceEirTxPkts
         Counter64,
      pr1645v2TvTmplVxLanTunnelsOutPQsH24PerformanceViolTxPkts
         Counter64,
      pr1645v2TvTmplVxLanTunnelsOutPQsH24PerformanceTotOcts
         Counter64,
      pr1645v2TvTmplVxLanTunnelsOutPQsH24PerformanceDirTxOcts
         Counter64,
      pr1645v2TvTmplVxLanTunnelsOutPQsH24PerformanceQdOcts
         Counter64,
      pr1645v2TvTmplVxLanTunnelsOutPQsH24PerformanceDropOcts
         Counter64,
      pr1645v2TvTmplVxLanTunnelsOutPQsH24PerformanceRDropOcts
         Counter64,
      pr1645v2TvTmplVxLanTunnelsOutPQsH24PerformanceCirTxOcts
         Counter64,
      pr1645v2TvTmplVxLanTunnelsOutPQsH24PerformanceEirTxOcts
         Counter64,
      pr1645v2TvTmplVxLanTunnelsOutPQsH24PerformanceViolTxOcts
         Counter64,
      pr1645v2TvTmplVxLanTunnelsOutPQsH24PerformanceBandwidth
         Integer32
      }

pr1645v2TvTmplVxLanTunnelsOutPQsH24PerformanceTableIx OBJECT-TYPE
   SYNTAX      TableIndex
   MAX-ACCESS  not-accessible
   STATUS      current
   DESCRIPTION
      ""
   ::= {pr1645v2TvTmplVxLanTunnelsOutPQsH24PerformanceEntry 11}

pr1645v2TvTmplVxLanTunnelsOutPQsH24PerformanceSysUpTime OBJECT-TYPE
   SYNTAX      TimeTicks
   MAX-ACCESS  read-only
   STATUS      current
   DESCRIPTION
      "Path: tunnels.performance.vxLanTunnels.outPriorityQueues.h24Performance.sysUpTime

       Time in centi-second."
   ::= {pr1645v2TvTmplVxLanTunnelsOutPQsH24PerformanceEntry 16777216}

pr1645v2TvTmplVxLanTunnelsOutPQsH24PerformanceTotPkts OBJECT-TYPE
   SYNTAX      Counter64
   MAX-ACCESS  read-only
   STATUS      current
   DESCRIPTION
      "Path: tunnels.performance.vxLanTunnels.outPriorityQueues.h24Performance.totalPkts

       64 bit unsigned wrappable counter."
   ::= {pr1645v2TvTmplVxLanTunnelsOutPQsH24PerformanceEntry 234881024}

pr1645v2TvTmplVxLanTunnelsOutPQsH24PerformanceDirTxPkts OBJECT-TYPE
   SYNTAX      Counter64
   MAX-ACCESS  read-only
   STATUS      current
   DESCRIPTION
      "Path: tunnels.performance.vxLanTunnels.outPriorityQueues.h24Performance.directTxPkts

       64 bit unsigned wrappable counter."
   ::= {pr1645v2TvTmplVxLanTunnelsOutPQsH24PerformanceEntry 33554432}

pr1645v2TvTmplVxLanTunnelsOutPQsH24PerformanceQdPkts OBJECT-TYPE
   SYNTAX      Counter64
   MAX-ACCESS  read-only
   STATUS      current
   DESCRIPTION
      "Path: tunnels.performance.vxLanTunnels.outPriorityQueues.h24Performance.queuedPkts

       64 bit unsigned wrappable counter."
   ::= {pr1645v2TvTmplVxLanTunnelsOutPQsH24PerformanceEntry 50331648}

pr1645v2TvTmplVxLanTunnelsOutPQsH24PerformanceDropPkts OBJECT-TYPE
   SYNTAX      Counter64
   MAX-ACCESS  read-only
   STATUS      current
   DESCRIPTION
      "Path: tunnels.performance.vxLanTunnels.outPriorityQueues.h24Performance.droppedPkts

       64 bit unsigned wrappable counter."
   ::= {pr1645v2TvTmplVxLanTunnelsOutPQsH24PerformanceEntry 67108864}

pr1645v2TvTmplVxLanTunnelsOutPQsH24PerformanceRDropPkts OBJECT-TYPE
   SYNTAX      Counter64
   MAX-ACCESS  read-only
   STATUS      current
   DESCRIPTION
      "Path: tunnels.performance.vxLanTunnels.outPriorityQueues.h24Performance.redDroppedPkts

       64 bit unsigned wrappable counter."
   ::= {pr1645v2TvTmplVxLanTunnelsOutPQsH24PerformanceEntry 201326592}

pr1645v2TvTmplVxLanTunnelsOutPQsH24PerformanceCirTxPkts OBJECT-TYPE
   SYNTAX      Counter64
   MAX-ACCESS  read-only
   STATUS      current
   DESCRIPTION
      "Path: tunnels.performance.vxLanTunnels.outPriorityQueues.h24Performance.cirTxPkts

       64 bit unsigned wrappable counter."
   ::= {pr1645v2TvTmplVxLanTunnelsOutPQsH24PerformanceEntry 83886080}

pr1645v2TvTmplVxLanTunnelsOutPQsH24PerformanceEirTxPkts OBJECT-TYPE
   SYNTAX      Counter64
   MAX-ACCESS  read-only
   STATUS      current
   DESCRIPTION
      "Path: tunnels.performance.vxLanTunnels.outPriorityQueues.h24Performance.eirTxPkts

       64 bit unsigned wrappable counter."
   ::= {pr1645v2TvTmplVxLanTunnelsOutPQsH24PerformanceEntry 100663296}

pr1645v2TvTmplVxLanTunnelsOutPQsH24PerformanceViolTxPkts OBJECT-TYPE
   SYNTAX      Counter64
   MAX-ACCESS  read-only
   STATUS      current
   DESCRIPTION
      "Path: tunnels.performance.vxLanTunnels.outPriorityQueues.h24Performance.violateTxPkts

       64 bit unsigned wrappable counter."
   ::= {pr1645v2TvTmplVxLanTunnelsOutPQsH24PerformanceEntry 301989888}

pr1645v2TvTmplVxLanTunnelsOutPQsH24PerformanceTotOcts OBJECT-TYPE
   SYNTAX      Counter64
   MAX-ACCESS  read-only
   STATUS      current
   DESCRIPTION
      "Path: tunnels.performance.vxLanTunnels.outPriorityQueues.h24Performance.totalOctets

       64 bit unsigned wrappable counter."
   ::= {pr1645v2TvTmplVxLanTunnelsOutPQsH24PerformanceEntry 251658240}

pr1645v2TvTmplVxLanTunnelsOutPQsH24PerformanceDirTxOcts OBJECT-TYPE
   SYNTAX      Counter64
   MAX-ACCESS  read-only
   STATUS      current
   DESCRIPTION
      "Path: tunnels.performance.vxLanTunnels.outPriorityQueues.h24Performance.directTxOctets

       64 bit unsigned wrappable counter."
   ::= {pr1645v2TvTmplVxLanTunnelsOutPQsH24PerformanceEntry 117440512}

pr1645v2TvTmplVxLanTunnelsOutPQsH24PerformanceQdOcts OBJECT-TYPE
   SYNTAX      Counter64
   MAX-ACCESS  read-only
   STATUS      current
   DESCRIPTION
      "Path: tunnels.performance.vxLanTunnels.outPriorityQueues.h24Performance.queuedOctets

       64 bit unsigned wrappable counter."
   ::= {pr1645v2TvTmplVxLanTunnelsOutPQsH24PerformanceEntry 134217728}

pr1645v2TvTmplVxLanTunnelsOutPQsH24PerformanceDropOcts OBJECT-TYPE
   SYNTAX      Counter64
   MAX-ACCESS  read-only
   STATUS      current
   DESCRIPTION
      "Path: tunnels.performance.vxLanTunnels.outPriorityQueues.h24Performance.droppedOctets

       64 bit unsigned wrappable counter."
   ::= {pr1645v2TvTmplVxLanTunnelsOutPQsH24PerformanceEntry 150994944}

pr1645v2TvTmplVxLanTunnelsOutPQsH24PerformanceRDropOcts OBJECT-TYPE
   SYNTAX      Counter64
   MAX-ACCESS  read-only
   STATUS      current
   DESCRIPTION
      "Path: tunnels.performance.vxLanTunnels.outPriorityQueues.h24Performance.redDroppedOctets

       64 bit unsigned wrappable counter."
   ::= {pr1645v2TvTmplVxLanTunnelsOutPQsH24PerformanceEntry 218103808}

pr1645v2TvTmplVxLanTunnelsOutPQsH24PerformanceCirTxOcts OBJECT-TYPE
   SYNTAX      Counter64
   MAX-ACCESS  read-only
   STATUS      current
   DESCRIPTION
      "Path: tunnels.performance.vxLanTunnels.outPriorityQueues.h24Performance.cirTxOctets

       64 bit unsigned wrappable counter."
   ::= {pr1645v2TvTmplVxLanTunnelsOutPQsH24PerformanceEntry 167772160}

pr1645v2TvTmplVxLanTunnelsOutPQsH24PerformanceEirTxOcts OBJECT-TYPE
   SYNTAX      Counter64
   MAX-ACCESS  read-only
   STATUS      current
   DESCRIPTION
      "Path: tunnels.performance.vxLanTunnels.outPriorityQueues.h24Performance.eirTxOctets

       64 bit unsigned wrappable counter."
   ::= {pr1645v2TvTmplVxLanTunnelsOutPQsH24PerformanceEntry 184549376}

pr1645v2TvTmplVxLanTunnelsOutPQsH24PerformanceViolTxOcts OBJECT-TYPE
   SYNTAX      Counter64
   MAX-ACCESS  read-only
   STATUS      current
   DESCRIPTION
      "Path: tunnels.performance.vxLanTunnels.outPriorityQueues.h24Performance.violateTxOctets

       64 bit unsigned wrappable counter."
   ::= {pr1645v2TvTmplVxLanTunnelsOutPQsH24PerformanceEntry 318767104}

pr1645v2TvTmplVxLanTunnelsOutPQsH24PerformanceBandwidth OBJECT-TYPE
   SYNTAX      Integer32
   MAX-ACCESS  read-only
   STATUS      current
   DESCRIPTION
      "Path: tunnels.performance.vxLanTunnels.outPriorityQueues.h24Performance.bandwidth

       unit name = bps
       formula = 8 * ; 8 /"
   ::= {pr1645v2TvTmplVxLanTunnelsOutPQsH24PerformanceEntry 268435456}

pr1645v2TvTmplVxLanTunnelsOutPQsD7Performance OBJECT-TYPE
   SYNTAX      SEQUENCE OF Pr1645v2TvTmplVxLanTunnelsOutPQsD7PerformanceEntry
   MAX-ACCESS  not-accessible
   STATUS      current
   DESCRIPTION
      ""
   ::= {pr1645v2TvTmplVxLanTunnels 84344832}

pr1645v2TvTmplVxLanTunnelsOutPQsD7PerformanceEntry OBJECT-TYPE
   SYNTAX      Pr1645v2TvTmplVxLanTunnelsOutPQsD7PerformanceEntry
   MAX-ACCESS  not-accessible
   STATUS      current
   DESCRIPTION
      ""
   INDEX      { pr1645v2TvTmplVxLanTunnelsTableIx,
                pr1645v2TvTmplVxLanTunnelsOutPQsTableIx,
                pr1645v2TvTmplVxLanTunnelsOutPQsD7PerformanceTableIx }
   ::= {pr1645v2TvTmplVxLanTunnelsOutPQsD7Performance 1}

Pr1645v2TvTmplVxLanTunnelsOutPQsD7PerformanceEntry ::=
   SEQUENCE
      {
      pr1645v2TvTmplVxLanTunnelsOutPQsD7PerformanceTableIx
         TableIndex,
      pr1645v2TvTmplVxLanTunnelsOutPQsD7PerformanceSysUpTime
         TimeTicks,
      pr1645v2TvTmplVxLanTunnelsOutPQsD7PerformanceTotPkts
         Counter64,
      pr1645v2TvTmplVxLanTunnelsOutPQsD7PerformanceDirTxPkts
         Counter64,
      pr1645v2TvTmplVxLanTunnelsOutPQsD7PerformanceQdPkts
         Counter64,
      pr1645v2TvTmplVxLanTunnelsOutPQsD7PerformanceDropPkts
         Counter64,
      pr1645v2TvTmplVxLanTunnelsOutPQsD7PerformanceRDropPkts
         Counter64,
      pr1645v2TvTmplVxLanTunnelsOutPQsD7PerformanceCirTxPkts
         Counter64,
      pr1645v2TvTmplVxLanTunnelsOutPQsD7PerformanceEirTxPkts
         Counter64,
      pr1645v2TvTmplVxLanTunnelsOutPQsD7PerformanceViolTxPkts
         Counter64,
      pr1645v2TvTmplVxLanTunnelsOutPQsD7PerformanceTotOcts
         Counter64,
      pr1645v2TvTmplVxLanTunnelsOutPQsD7PerformanceDirTxOcts
         Counter64,
      pr1645v2TvTmplVxLanTunnelsOutPQsD7PerformanceQdOcts
         Counter64,
      pr1645v2TvTmplVxLanTunnelsOutPQsD7PerformanceDropOcts
         Counter64,
      pr1645v2TvTmplVxLanTunnelsOutPQsD7PerformanceRDropOcts
         Counter64,
      pr1645v2TvTmplVxLanTunnelsOutPQsD7PerformanceCirTxOcts
         Counter64,
      pr1645v2TvTmplVxLanTunnelsOutPQsD7PerformanceEirTxOcts
         Counter64,
      pr1645v2TvTmplVxLanTunnelsOutPQsD7PerformanceViolTxOcts
         Counter64,
      pr1645v2TvTmplVxLanTunnelsOutPQsD7PerformanceBandwidth
         Integer32
      }

pr1645v2TvTmplVxLanTunnelsOutPQsD7PerformanceTableIx OBJECT-TYPE
   SYNTAX      TableIndex
   MAX-ACCESS  not-accessible
   STATUS      current
   DESCRIPTION
      ""
   ::= {pr1645v2TvTmplVxLanTunnelsOutPQsD7PerformanceEntry 11}

pr1645v2TvTmplVxLanTunnelsOutPQsD7PerformanceSysUpTime OBJECT-TYPE
   SYNTAX      TimeTicks
   MAX-ACCESS  read-only
   STATUS      current
   DESCRIPTION
      "Path: tunnels.performance.vxLanTunnels.outPriorityQueues.d7Performance.sysUpTime

       Time in centi-second."
   ::= {pr1645v2TvTmplVxLanTunnelsOutPQsD7PerformanceEntry 16777216}

pr1645v2TvTmplVxLanTunnelsOutPQsD7PerformanceTotPkts OBJECT-TYPE
   SYNTAX      Counter64
   MAX-ACCESS  read-only
   STATUS      current
   DESCRIPTION
      "Path: tunnels.performance.vxLanTunnels.outPriorityQueues.d7Performance.totalPkts

       64 bit unsigned wrappable counter."
   ::= {pr1645v2TvTmplVxLanTunnelsOutPQsD7PerformanceEntry 234881024}

pr1645v2TvTmplVxLanTunnelsOutPQsD7PerformanceDirTxPkts OBJECT-TYPE
   SYNTAX      Counter64
   MAX-ACCESS  read-only
   STATUS      current
   DESCRIPTION
      "Path: tunnels.performance.vxLanTunnels.outPriorityQueues.d7Performance.directTxPkts

       64 bit unsigned wrappable counter."
   ::= {pr1645v2TvTmplVxLanTunnelsOutPQsD7PerformanceEntry 33554432}

pr1645v2TvTmplVxLanTunnelsOutPQsD7PerformanceQdPkts OBJECT-TYPE
   SYNTAX      Counter64
   MAX-ACCESS  read-only
   STATUS      current
   DESCRIPTION
      "Path: tunnels.performance.vxLanTunnels.outPriorityQueues.d7Performance.queuedPkts

       64 bit unsigned wrappable counter."
   ::= {pr1645v2TvTmplVxLanTunnelsOutPQsD7PerformanceEntry 50331648}

pr1645v2TvTmplVxLanTunnelsOutPQsD7PerformanceDropPkts OBJECT-TYPE
   SYNTAX      Counter64
   MAX-ACCESS  read-only
   STATUS      current
   DESCRIPTION
      "Path: tunnels.performance.vxLanTunnels.outPriorityQueues.d7Performance.droppedPkts

       64 bit unsigned wrappable counter."
   ::= {pr1645v2TvTmplVxLanTunnelsOutPQsD7PerformanceEntry 67108864}

pr1645v2TvTmplVxLanTunnelsOutPQsD7PerformanceRDropPkts OBJECT-TYPE
   SYNTAX      Counter64
   MAX-ACCESS  read-only
   STATUS      current
   DESCRIPTION
      "Path: tunnels.performance.vxLanTunnels.outPriorityQueues.d7Performance.redDroppedPkts

       64 bit unsigned wrappable counter."
   ::= {pr1645v2TvTmplVxLanTunnelsOutPQsD7PerformanceEntry 201326592}

pr1645v2TvTmplVxLanTunnelsOutPQsD7PerformanceCirTxPkts OBJECT-TYPE
   SYNTAX      Counter64
   MAX-ACCESS  read-only
   STATUS      current
   DESCRIPTION
      "Path: tunnels.performance.vxLanTunnels.outPriorityQueues.d7Performance.cirTxPkts

       64 bit unsigned wrappable counter."
   ::= {pr1645v2TvTmplVxLanTunnelsOutPQsD7PerformanceEntry 83886080}

pr1645v2TvTmplVxLanTunnelsOutPQsD7PerformanceEirTxPkts OBJECT-TYPE
   SYNTAX      Counter64
   MAX-ACCESS  read-only
   STATUS      current
   DESCRIPTION
      "Path: tunnels.performance.vxLanTunnels.outPriorityQueues.d7Performance.eirTxPkts

       64 bit unsigned wrappable counter."
   ::= {pr1645v2TvTmplVxLanTunnelsOutPQsD7PerformanceEntry 100663296}

pr1645v2TvTmplVxLanTunnelsOutPQsD7PerformanceViolTxPkts OBJECT-TYPE
   SYNTAX      Counter64
   MAX-ACCESS  read-only
   STATUS      current
   DESCRIPTION
      "Path: tunnels.performance.vxLanTunnels.outPriorityQueues.d7Performance.violateTxPkts

       64 bit unsigned wrappable counter."
   ::= {pr1645v2TvTmplVxLanTunnelsOutPQsD7PerformanceEntry 301989888}

pr1645v2TvTmplVxLanTunnelsOutPQsD7PerformanceTotOcts OBJECT-TYPE
   SYNTAX      Counter64
   MAX-ACCESS  read-only
   STATUS      current
   DESCRIPTION
      "Path: tunnels.performance.vxLanTunnels.outPriorityQueues.d7Performance.totalOctets

       64 bit unsigned wrappable counter."
   ::= {pr1645v2TvTmplVxLanTunnelsOutPQsD7PerformanceEntry 251658240}

pr1645v2TvTmplVxLanTunnelsOutPQsD7PerformanceDirTxOcts OBJECT-TYPE
   SYNTAX      Counter64
   MAX-ACCESS  read-only
   STATUS      current
   DESCRIPTION
      "Path: tunnels.performance.vxLanTunnels.outPriorityQueues.d7Performance.directTxOctets

       64 bit unsigned wrappable counter."
   ::= {pr1645v2TvTmplVxLanTunnelsOutPQsD7PerformanceEntry 117440512}

pr1645v2TvTmplVxLanTunnelsOutPQsD7PerformanceQdOcts OBJECT-TYPE
   SYNTAX      Counter64
   MAX-ACCESS  read-only
   STATUS      current
   DESCRIPTION
      "Path: tunnels.performance.vxLanTunnels.outPriorityQueues.d7Performance.queuedOctets

       64 bit unsigned wrappable counter."
   ::= {pr1645v2TvTmplVxLanTunnelsOutPQsD7PerformanceEntry 134217728}

pr1645v2TvTmplVxLanTunnelsOutPQsD7PerformanceDropOcts OBJECT-TYPE
   SYNTAX      Counter64
   MAX-ACCESS  read-only
   STATUS      current
   DESCRIPTION
      "Path: tunnels.performance.vxLanTunnels.outPriorityQueues.d7Performance.droppedOctets

       64 bit unsigned wrappable counter."
   ::= {pr1645v2TvTmplVxLanTunnelsOutPQsD7PerformanceEntry 150994944}

pr1645v2TvTmplVxLanTunnelsOutPQsD7PerformanceRDropOcts OBJECT-TYPE
   SYNTAX      Counter64
   MAX-ACCESS  read-only
   STATUS      current
   DESCRIPTION
      "Path: tunnels.performance.vxLanTunnels.outPriorityQueues.d7Performance.redDroppedOctets

       64 bit unsigned wrappable counter."
   ::= {pr1645v2TvTmplVxLanTunnelsOutPQsD7PerformanceEntry 218103808}

pr1645v2TvTmplVxLanTunnelsOutPQsD7PerformanceCirTxOcts OBJECT-TYPE
   SYNTAX      Counter64
   MAX-ACCESS  read-only
   STATUS      current
   DESCRIPTION
      "Path: tunnels.performance.vxLanTunnels.outPriorityQueues.d7Performance.cirTxOctets

       64 bit unsigned wrappable counter."
   ::= {pr1645v2TvTmplVxLanTunnelsOutPQsD7PerformanceEntry 167772160}

pr1645v2TvTmplVxLanTunnelsOutPQsD7PerformanceEirTxOcts OBJECT-TYPE
   SYNTAX      Counter64
   MAX-ACCESS  read-only
   STATUS      current
   DESCRIPTION
      "Path: tunnels.performance.vxLanTunnels.outPriorityQueues.d7Performance.eirTxOctets

       64 bit unsigned wrappable counter."
   ::= {pr1645v2TvTmplVxLanTunnelsOutPQsD7PerformanceEntry 184549376}

pr1645v2TvTmplVxLanTunnelsOutPQsD7PerformanceViolTxOcts OBJECT-TYPE
   SYNTAX      Counter64
   MAX-ACCESS  read-only
   STATUS      current
   DESCRIPTION
      "Path: tunnels.performance.vxLanTunnels.outPriorityQueues.d7Performance.violateTxOctets

       64 bit unsigned wrappable counter."
   ::= {pr1645v2TvTmplVxLanTunnelsOutPQsD7PerformanceEntry 318767104}

pr1645v2TvTmplVxLanTunnelsOutPQsD7PerformanceBandwidth OBJECT-TYPE
   SYNTAX      Integer32
   MAX-ACCESS  read-only
   STATUS      current
   DESCRIPTION
      "Path: tunnels.performance.vxLanTunnels.outPriorityQueues.d7Performance.bandwidth

       unit name = bps
       formula = 8 * ; 8 /"
   ::= {pr1645v2TvTmplVxLanTunnelsOutPQsD7PerformanceEntry 268435456}



ar1645v2TvTmpl OBJECT IDENTIFIER ::= {r1645v2TvTmpl 16}


ar1645v2TvTmplClearCounters OBJECT-TYPE
   SYNTAX      Integer32
   MAX-ACCESS  read-write
   STATUS      current
   DESCRIPTION
      "Path: tunnels.actions.clearCounters
       Info: reset counters"
   ::= {ar1645v2TvTmpl 263}



fr1645v2TvTmpl OBJECT IDENTIFIER ::= {r1645v2TvTmpl 13}


fr1645v2TvTmplAlarm OBJECT IDENTIFIER ::= {fr1645v2TvTmpl 207}

fr1645v2TvTmplAlarmSSC OBJECT IDENTIFIER ::= {fr1645v2TvTmplAlarm 1}

fr1645v2TvTmplAlarmEntry OBJECT IDENTIFIER ::= {fr1645v2TvTmplAlarmSSC 1}

fr1645v2TvTmplAlarmDiscriminator OBJECT-TYPE
   SYNTAX      Integer32
   MAX-ACCESS  read-only
   STATUS      current
   DESCRIPTION
      "Path: tunnels.alarms.alarmInfo.discriminator"
   ::= {fr1645v2TvTmplAlarmEntry 16777216}

fr1645v2TvTmplAlarmCurrent OBJECT-TYPE
   SYNTAX      Integer32
   MAX-ACCESS  read-only
   STATUS      current
   DESCRIPTION
      "Path: tunnels.alarms.alarmInfo.currentAlarms

       Bit meanings:
               bit 1 = l2tpDown,
               bit 2 = ipsecL2tpDown,
               bit 3 = greDown,
               bit 4 = ipsecGreDown"
   ::= {fr1645v2TvTmplAlarmEntry 33554432}

fr1645v2TvTmplAlarmPrevious OBJECT-TYPE
   SYNTAX      Integer32
   MAX-ACCESS  read-only
   STATUS      current
   DESCRIPTION
      "Path: tunnels.alarms.alarmInfo.previousAlarms

       Bit meanings:
               bit 1 = l2tpDown,
               bit 2 = ipsecL2tpDown,
               bit 3 = greDown,
               bit 4 = ipsecGreDown"
   ::= {fr1645v2TvTmplAlarmEntry 50331648}

fr1645v2TvTmplAlarmMask OBJECT-TYPE
   SYNTAX      Integer32
   MAX-ACCESS  read-only
   STATUS      current
   DESCRIPTION
      "Path: tunnels.alarms.alarmInfo.alarmMask

       Bit meanings:
               bit 1 = l2tpDown,
               bit 2 = ipsecL2tpDown,
               bit 3 = greDown,
               bit 4 = ipsecGreDown"
   ::= {fr1645v2TvTmplAlarmEntry 67108864}

fr1645v2TvTmplAlarmLevL2tpDown OBJECT-TYPE
   SYNTAX      Integer32
   MAX-ACCESS  read-only
   STATUS      current
   DESCRIPTION
      "Path: tunnels.alarms.alarmInfo.alarmLevel.l2tpDown"
   ::= {fr1645v2TvTmplAlarmEntry 84017152}

fr1645v2TvTmplAlarmLevIpsecL2tpDown OBJECT-TYPE
   SYNTAX      Integer32
   MAX-ACCESS  read-only
   STATUS      current
   DESCRIPTION
      "Path: tunnels.alarms.alarmInfo.alarmLevel.ipsecL2tpDown"
   ::= {fr1645v2TvTmplAlarmEntry 84082688}

fr1645v2TvTmplAlarmLevGreDown OBJECT-TYPE
   SYNTAX      Integer32
   MAX-ACCESS  read-only
   STATUS      current
   DESCRIPTION
      "Path: tunnels.alarms.alarmInfo.alarmLevel.greDown"
   ::= {fr1645v2TvTmplAlarmEntry 84148224}

fr1645v2TvTmplAlarmLevIpsecGreDown OBJECT-TYPE
   SYNTAX      Integer32
   MAX-ACCESS  read-only
   STATUS      current
   DESCRIPTION
      "Path: tunnels.alarms.alarmInfo.alarmLevel.ipsecGreDown"
   ::= {fr1645v2TvTmplAlarmEntry 84213760}


fr1645v2TvTmplAlarmE2 OBJECT IDENTIFIER ::= {fr1645v2TvTmplAlarm 2}

fr1645v2TvTmplAlarmE2Entry OBJECT IDENTIFIER ::= {fr1645v2TvTmplAlarmE2 1}

fr1645v2TvTmplAlarmE2L2tpDown OBJECT IDENTIFIER ::= {fr1645v2TvTmplAlarmE2Entry 11}

fr1645v2TvTmplAlarmE2L2tpDownPfx OBJECT IDENTIFIER ::= {fr1645v2TvTmplAlarmE2L2tpDown 0}

fr1645v2TvTmplAlarmE2L2tpDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'l2tpDown'
                representing an alarm condition in the alarm word
                of attribute 'alarmInfo' of managed object 'tunnelsVrf'
                (root='router1645') has changed from the ON to the OFF state."
   ::= {fr1645v2TvTmplAlarmE2L2tpDownPfx 1}

fr1645v2TvTmplAlarmE2L2tpDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'l2tpDown'
                representing an alarm condition in the alarm word
                of attribute 'alarmInfo' of managed object 'tunnelsVrf'
                (root='router1645') has changed from the OFF to the ON state."
   ::= {fr1645v2TvTmplAlarmE2L2tpDownPfx 2}

fr1645v2TvTmplAlarmE2IpsecL2tpDown OBJECT IDENTIFIER ::= {fr1645v2TvTmplAlarmE2Entry 12}

fr1645v2TvTmplAlarmE2IpsecL2tpDownPfx OBJECT IDENTIFIER ::= {fr1645v2TvTmplAlarmE2IpsecL2tpDown 0}

fr1645v2TvTmplAlarmE2IpsecL2tpDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ipsecL2tpDown'
                representing an alarm condition in the alarm word
                of attribute 'alarmInfo' of managed object 'tunnelsVrf'
                (root='router1645') has changed from the ON to the OFF state."
   ::= {fr1645v2TvTmplAlarmE2IpsecL2tpDownPfx 1}

fr1645v2TvTmplAlarmE2IpsecL2tpDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ipsecL2tpDown'
                representing an alarm condition in the alarm word
                of attribute 'alarmInfo' of managed object 'tunnelsVrf'
                (root='router1645') has changed from the OFF to the ON state."
   ::= {fr1645v2TvTmplAlarmE2IpsecL2tpDownPfx 2}

fr1645v2TvTmplAlarmE2GreDown OBJECT IDENTIFIER ::= {fr1645v2TvTmplAlarmE2Entry 13}

fr1645v2TvTmplAlarmE2GreDownPfx OBJECT IDENTIFIER ::= {fr1645v2TvTmplAlarmE2GreDown 0}

fr1645v2TvTmplAlarmE2GreDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'greDown'
                representing an alarm condition in the alarm word
                of attribute 'alarmInfo' of managed object 'tunnelsVrf'
                (root='router1645') has changed from the ON to the OFF state."
   ::= {fr1645v2TvTmplAlarmE2GreDownPfx 1}

fr1645v2TvTmplAlarmE2GreDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'greDown'
                representing an alarm condition in the alarm word
                of attribute 'alarmInfo' of managed object 'tunnelsVrf'
                (root='router1645') has changed from the OFF to the ON state."
   ::= {fr1645v2TvTmplAlarmE2GreDownPfx 2}

fr1645v2TvTmplAlarmE2IpsecGreDown OBJECT IDENTIFIER ::= {fr1645v2TvTmplAlarmE2Entry 14}

fr1645v2TvTmplAlarmE2IpsecGreDownPfx OBJECT IDENTIFIER ::= {fr1645v2TvTmplAlarmE2IpsecGreDown 0}

fr1645v2TvTmplAlarmE2IpsecGreDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ipsecGreDown'
                representing an alarm condition in the alarm word
                of attribute 'alarmInfo' of managed object 'tunnelsVrf'
                (root='router1645') has changed from the ON to the OFF state."
   ::= {fr1645v2TvTmplAlarmE2IpsecGreDownPfx 1}

fr1645v2TvTmplAlarmE2IpsecGreDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'ipsecGreDown'
                representing an alarm condition in the alarm word
                of attribute 'alarmInfo' of managed object 'tunnelsVrf'
                (root='router1645') has changed from the OFF to the ON state."
   ::= {fr1645v2TvTmplAlarmE2IpsecGreDownPfx 2}



END
