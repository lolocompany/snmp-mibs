OneAccess-R1645v2-3131-Zbfw DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Zbfw OBJECT IDENTIFIER ::= {r1645Rootv2 3131}

r1645v2ZbfwMOProp OBJECT-TYPE
   SYNTAX      SEQUENCE OF R1645v2ZbfwMOPropEntry
   MAX-ACCESS  not-accessible
   STATUS      current
   DESCRIPTION
      ""
   ::= {r1645v2Zbfw 1}

r1645v2ZbfwMOPropEntry OBJECT-TYPE
   SYNTAX      R1645v2ZbfwMOPropEntry
   MAX-ACCESS  not-accessible
   STATUS      current
   DESCRIPTION
      ""
   INDEX      { r1645v2ZbfwMOPropGlobalIx }
   ::= {r1645v2ZbfwMOProp 1}

R1645v2ZbfwMOPropEntry ::=
   SEQUENCE
      {
      r1645v2ZbfwMOPropPath
         ContainmentPath,
      r1645v2ZbfwMOPropRev
         ObjectRevision,
      r1645v2ZbfwMOPropGlobalIx
         GlobalIndex
      }

r1645v2ZbfwMOPropPath OBJECT-TYPE
   SYNTAX      ContainmentPath
   MAX-ACCESS  read-only
   STATUS      current
   DESCRIPTION
      "Textual description of the containment tree from the instance of
       the root object down to the instance of the current object."
   ::= {r1645v2ZbfwMOPropEntry 3}

r1645v2ZbfwMOPropRev OBJECT-TYPE
   SYNTAX      ObjectRevision
   MAX-ACCESS  read-only
   STATUS      current
   DESCRIPTION
      "This value corresponds with the revision of the MANAGED OBJECT."
   ::= {r1645v2ZbfwMOPropEntry 4}

r1645v2ZbfwMOPropGlobalIx OBJECT-TYPE
   SYNTAX      GlobalIndex
   MAX-ACCESS  read-only
   STATUS      current
   DESCRIPTION
      "The value of the tlsCntTreeGlobalIndex of the MANAGED OBJECT."
   ::= {r1645v2ZbfwMOPropEntry 10}



er1645v2Zbfw OBJECT IDENTIFIER ::= {r1645v2Zbfw 11}


er1645v2ZbfwInspection OBJECT IDENTIFIER ::= {er1645v2Zbfw 6}

er1645v2ZbfwInspectionTable OBJECT-TYPE
   SYNTAX      SEQUENCE OF Er1645v2ZbfwInspectionEntry
   MAX-ACCESS  not-accessible
   STATUS      current
   DESCRIPTION
      "activate or deactivate inspection"
   ::= {er1645v2ZbfwInspection 1}

er1645v2ZbfwInspectionEntry OBJECT-TYPE
   SYNTAX      Er1645v2ZbfwInspectionEntry
   MAX-ACCESS  not-accessible
   STATUS      current
   DESCRIPTION
      ""
   INDEX      { er1645v2ZbfwInspectionGlobalIx }
   ::= {er1645v2ZbfwInspectionTable 1}

Er1645v2ZbfwInspectionEntry ::=
   SEQUENCE
      {
      er1645v2ZbfwInspectionGlobalIx
         GlobalIndex,
      er1645v2ZbfwInspectionValue
         INTEGER
      }

er1645v2ZbfwInspectionGlobalIx OBJECT-TYPE
   SYNTAX      GlobalIndex
   MAX-ACCESS  not-accessible
   STATUS      current
   DESCRIPTION
      "The value of the tlsCntTreeGlobalIndex of the MANAGED OBJECT."
   ::= {er1645v2ZbfwInspectionEntry 10}

er1645v2ZbfwInspectionValue OBJECT-TYPE
   SYNTAX      INTEGER
               {
               disabled (0),
               enabled (1)
               }
   MAX-ACCESS  read-write
   STATUS      current
   DESCRIPTION
      "Path: zbFirewall.editConf.inspection

       Possibilities:
               disabled   (0)
               enabled   (1)"
   ::= {er1645v2ZbfwInspectionEntry 2147483648}


er1645v2ZbfwNUcastInspection OBJECT IDENTIFIER ::= {er1645v2Zbfw 10}

er1645v2ZbfwNUcastInspectionTable OBJECT-TYPE
   SYNTAX      SEQUENCE OF Er1645v2ZbfwNUcastInspectionEntry
   MAX-ACCESS  not-accessible
   STATUS      current
   DESCRIPTION
      "multicast/broadcast behavior"
   ::= {er1645v2ZbfwNUcastInspection 1}

er1645v2ZbfwNUcastInspectionEntry OBJECT-TYPE
   SYNTAX      Er1645v2ZbfwNUcastInspectionEntry
   MAX-ACCESS  not-accessible
   STATUS      current
   DESCRIPTION
      ""
   INDEX      { er1645v2ZbfwNUcastInspectionGlobalIx }
   ::= {er1645v2ZbfwNUcastInspectionTable 1}

Er1645v2ZbfwNUcastInspectionEntry ::=
   SEQUENCE
      {
      er1645v2ZbfwNUcastInspectionGlobalIx
         GlobalIndex,
      er1645v2ZbfwNUcastInspectionValue
         INTEGER
      }

er1645v2ZbfwNUcastInspectionGlobalIx OBJECT-TYPE
   SYNTAX      GlobalIndex
   MAX-ACCESS  not-accessible
   STATUS      current
   DESCRIPTION
      "The value of the tlsCntTreeGlobalIndex of the MANAGED OBJECT."
   ::= {er1645v2ZbfwNUcastInspectionEntry 10}

er1645v2ZbfwNUcastInspectionValue OBJECT-TYPE
   SYNTAX      INTEGER
               {
               disabled (0),
               enabled (3)
               }
   MAX-ACCESS  read-write
   STATUS      current
   DESCRIPTION
      "Path: zbFirewall.editConf.nUcastInspection

       Possibilities:
               disabled   (0)
               enabled   (3)"
   ::= {er1645v2ZbfwNUcastInspectionEntry 2147483648}


er1645v2ZbfwFlowStatistics OBJECT IDENTIFIER ::= {er1645v2Zbfw 9}

er1645v2ZbfwFlowStatisticsTable OBJECT-TYPE
   SYNTAX      SEQUENCE OF Er1645v2ZbfwFlowStatisticsEntry
   MAX-ACCESS  not-accessible
   STATUS      current
   DESCRIPTION
      "immediate or delayed flow statistics processing"
   ::= {er1645v2ZbfwFlowStatistics 1}

er1645v2ZbfwFlowStatisticsEntry OBJECT-TYPE
   SYNTAX      Er1645v2ZbfwFlowStatisticsEntry
   MAX-ACCESS  not-accessible
   STATUS      current
   DESCRIPTION
      ""
   INDEX      { er1645v2ZbfwFlowStatisticsGlobalIx }
   ::= {er1645v2ZbfwFlowStatisticsTable 1}

Er1645v2ZbfwFlowStatisticsEntry ::=
   SEQUENCE
      {
      er1645v2ZbfwFlowStatisticsGlobalIx
         GlobalIndex,
      er1645v2ZbfwFlowStatisticsValue
         INTEGER
      }

er1645v2ZbfwFlowStatisticsGlobalIx OBJECT-TYPE
   SYNTAX      GlobalIndex
   MAX-ACCESS  not-accessible
   STATUS      current
   DESCRIPTION
      "The value of the tlsCntTreeGlobalIndex of the MANAGED OBJECT."
   ::= {er1645v2ZbfwFlowStatisticsEntry 10}

er1645v2ZbfwFlowStatisticsValue OBJECT-TYPE
   SYNTAX      INTEGER
               {
               immediate (0),
               delayed (1)
               }
   MAX-ACCESS  read-write
   STATUS      current
   DESCRIPTION
      "Path: zbFirewall.editConf.flowStatistics

       Possibilities:
               immediate   (0)
               delayed   (1)"
   ::= {er1645v2ZbfwFlowStatisticsEntry 2147483648}


er1645v2ZbfwMaxConnections OBJECT IDENTIFIER ::= {er1645v2Zbfw 7}

er1645v2ZbfwMaxConnectionsTable OBJECT-TYPE
   SYNTAX      SEQUENCE OF Er1645v2ZbfwMaxConnectionsEntry
   MAX-ACCESS  not-accessible
   STATUS      current
   DESCRIPTION
      "maximum nr of connections"
   ::= {er1645v2ZbfwMaxConnections 1}

er1645v2ZbfwMaxConnectionsEntry OBJECT-TYPE
   SYNTAX      Er1645v2ZbfwMaxConnectionsEntry
   MAX-ACCESS  not-accessible
   STATUS      current
   DESCRIPTION
      ""
   INDEX      { er1645v2ZbfwMaxConnectionsGlobalIx }
   ::= {er1645v2ZbfwMaxConnectionsTable 1}

Er1645v2ZbfwMaxConnectionsEntry ::=
   SEQUENCE
      {
      er1645v2ZbfwMaxConnectionsGlobalIx
         GlobalIndex,
      er1645v2ZbfwMaxConnectionsValue
         Counter32
      }

er1645v2ZbfwMaxConnectionsGlobalIx OBJECT-TYPE
   SYNTAX      GlobalIndex
   MAX-ACCESS  not-accessible
   STATUS      current
   DESCRIPTION
      "The value of the tlsCntTreeGlobalIndex of the MANAGED OBJECT."
   ::= {er1645v2ZbfwMaxConnectionsEntry 10}

er1645v2ZbfwMaxConnectionsValue OBJECT-TYPE
   SYNTAX      Counter32
   MAX-ACCESS  read-write
   STATUS      current
   DESCRIPTION
      "Path: zbFirewall.editConf.maxConnections

       32 bit unsigned wrappable counter."
   ::= {er1645v2ZbfwMaxConnectionsEntry 2147483648}


er1645v2ZbfwZc OBJECT IDENTIFIER ::= {er1645v2Zbfw 1}

er1645v2ZbfwZcSSCTable OBJECT-TYPE
   SYNTAX      SEQUENCE OF Er1645v2ZbfwZcEntry
   MAX-ACCESS  not-accessible
   STATUS      current
   DESCRIPTION
      "zoneTable"
   ::= {er1645v2ZbfwZc 1}

er1645v2ZbfwZcEntry OBJECT-TYPE
   SYNTAX      Er1645v2ZbfwZcEntry
   MAX-ACCESS  not-accessible
   STATUS      current
   DESCRIPTION
      ""
   INDEX      { er1645v2ZbfwZcGlobalIx,
                er1645v2ZbfwZcTableIx }
   ::= {er1645v2ZbfwZcSSCTable 1}

Er1645v2ZbfwZcEntry ::=
   SEQUENCE
      {
      er1645v2ZbfwZcActions
         VariableLengthTableActions,
      er1645v2ZbfwZcGlobalIx
         GlobalIndex,
      er1645v2ZbfwZcTableIx
         TableIndex,
      er1645v2ZbfwZcName
         DisplayString,
      er1645v2ZbfwZcInboundNat
         DisplayString
      }

er1645v2ZbfwZcActions OBJECT-TYPE
   SYNTAX      VariableLengthTableActions
   MAX-ACCESS  read-write
   STATUS      current
   DESCRIPTION
      "By way of this field, some manipulations
       on this table may be performed."
   ::= {er1645v2ZbfwZcEntry 2}

er1645v2ZbfwZcGlobalIx OBJECT-TYPE
   SYNTAX      GlobalIndex
   MAX-ACCESS  not-accessible
   STATUS      current
   DESCRIPTION
      "The value of the tlsCntTreeGlobalIndex of the MANAGED OBJECT."
   ::= {er1645v2ZbfwZcEntry 10}

er1645v2ZbfwZcTableIx OBJECT-TYPE
   SYNTAX      TableIndex
   MAX-ACCESS  not-accessible
   STATUS      current
   DESCRIPTION
      ""
   ::= {er1645v2ZbfwZcEntry 11}

er1645v2ZbfwZcName OBJECT-TYPE
   SYNTAX      DisplayString
   MAX-ACCESS  read-write
   STATUS      current
   DESCRIPTION
      "Path: zbFirewall.editConf.zones.name"
   ::= {er1645v2ZbfwZcEntry 16777216}

er1645v2ZbfwZcInboundNat OBJECT-TYPE
   SYNTAX      DisplayString
   MAX-ACCESS  read-write
   STATUS      current
   DESCRIPTION
      "Path: zbFirewall.editConf.zones.inboundNat"
   ::= {er1645v2ZbfwZcEntry 33554432}


er1645v2ZbfwZpc OBJECT IDENTIFIER ::= {er1645v2Zbfw 2}

er1645v2ZbfwZpcSSCTable OBJECT-TYPE
   SYNTAX      SEQUENCE OF Er1645v2ZbfwZpcEntry
   MAX-ACCESS  not-accessible
   STATUS      current
   DESCRIPTION
      "zonepairTable"
   ::= {er1645v2ZbfwZpc 1}

er1645v2ZbfwZpcEntry OBJECT-TYPE
   SYNTAX      Er1645v2ZbfwZpcEntry
   MAX-ACCESS  not-accessible
   STATUS      current
   DESCRIPTION
      ""
   INDEX      { er1645v2ZbfwZpcGlobalIx,
                er1645v2ZbfwZpcTableIx }
   ::= {er1645v2ZbfwZpcSSCTable 1}

Er1645v2ZbfwZpcEntry ::=
   SEQUENCE
      {
      er1645v2ZbfwZpcActions
         VariableLengthTableActions,
      er1645v2ZbfwZpcGlobalIx
         GlobalIndex,
      er1645v2ZbfwZpcTableIx
         TableIndex,
      er1645v2ZbfwZpcName
         DisplayString,
      er1645v2ZbfwZpcSrcZone
         DisplayString,
      er1645v2ZbfwZpcDstZone
         DisplayString,
      er1645v2ZbfwZpcOutboundNat
         DisplayString,
      er1645v2ZbfwZpcPolicy
         DisplayString
      }

er1645v2ZbfwZpcActions OBJECT-TYPE
   SYNTAX      VariableLengthTableActions
   MAX-ACCESS  read-write
   STATUS      current
   DESCRIPTION
      "By way of this field, some manipulations
       on this table may be performed."
   ::= {er1645v2ZbfwZpcEntry 2}

er1645v2ZbfwZpcGlobalIx OBJECT-TYPE
   SYNTAX      GlobalIndex
   MAX-ACCESS  not-accessible
   STATUS      current
   DESCRIPTION
      "The value of the tlsCntTreeGlobalIndex of the MANAGED OBJECT."
   ::= {er1645v2ZbfwZpcEntry 10}

er1645v2ZbfwZpcTableIx OBJECT-TYPE
   SYNTAX      TableIndex
   MAX-ACCESS  not-accessible
   STATUS      current
   DESCRIPTION
      ""
   ::= {er1645v2ZbfwZpcEntry 11}

er1645v2ZbfwZpcName OBJECT-TYPE
   SYNTAX      DisplayString
   MAX-ACCESS  read-write
   STATUS      current
   DESCRIPTION
      "Path: zbFirewall.editConf.zonePairs.name"
   ::= {er1645v2ZbfwZpcEntry 16777216}

er1645v2ZbfwZpcSrcZone OBJECT-TYPE
   SYNTAX      DisplayString
   MAX-ACCESS  read-write
   STATUS      current
   DESCRIPTION
      "Path: zbFirewall.editConf.zonePairs.srcZone"
   ::= {er1645v2ZbfwZpcEntry 33554432}

er1645v2ZbfwZpcDstZone OBJECT-TYPE
   SYNTAX      DisplayString
   MAX-ACCESS  read-write
   STATUS      current
   DESCRIPTION
      "Path: zbFirewall.editConf.zonePairs.dstZone"
   ::= {er1645v2ZbfwZpcEntry 50331648}

er1645v2ZbfwZpcOutboundNat OBJECT-TYPE
   SYNTAX      DisplayString
   MAX-ACCESS  read-write
   STATUS      current
   DESCRIPTION
      "Path: zbFirewall.editConf.zonePairs.outboundNat"
   ::= {er1645v2ZbfwZpcEntry 67108864}

er1645v2ZbfwZpcPolicy OBJECT-TYPE
   SYNTAX      DisplayString
   MAX-ACCESS  read-write
   STATUS      current
   DESCRIPTION
      "Path: zbFirewall.editConf.zonePairs.policy"
   ::= {er1645v2ZbfwZpcEntry 83886080}


er1645v2ZbfwAc OBJECT IDENTIFIER ::= {er1645v2Zbfw 3}

er1645v2ZbfwAcSSCTable OBJECT-TYPE
   SYNTAX      SEQUENCE OF Er1645v2ZbfwAcEntry
   MAX-ACCESS  not-accessible
   STATUS      current
   DESCRIPTION
      "actionTable"
   ::= {er1645v2ZbfwAc 1}

er1645v2ZbfwAcEntry OBJECT-TYPE
   SYNTAX      Er1645v2ZbfwAcEntry
   MAX-ACCESS  not-accessible
   STATUS      current
   DESCRIPTION
      ""
   INDEX      { er1645v2ZbfwAcGlobalIx,
                er1645v2ZbfwAcTableIx }
   ::= {er1645v2ZbfwAcSSCTable 1}

Er1645v2ZbfwAcEntry ::=
   SEQUENCE
      {
      er1645v2ZbfwAcActions
         VariableLengthTableActions,
      er1645v2ZbfwAcGlobalIx
         GlobalIndex,
      er1645v2ZbfwAcTableIx
         TableIndex,
      er1645v2ZbfwAcName
         DisplayString,
      er1645v2ZbfwAcAction
         INTEGER,
      er1645v2ZbfwAcNatAction
         INTEGER,
      er1645v2ZbfwAcNat
         DisplayString,
      er1645v2ZbfwAcQosTos
         INTEGER
      }

er1645v2ZbfwAcActions OBJECT-TYPE
   SYNTAX      VariableLengthTableActions
   MAX-ACCESS  read-write
   STATUS      current
   DESCRIPTION
      "By way of this field, some manipulations
       on this table may be performed."
   ::= {er1645v2ZbfwAcEntry 2}

er1645v2ZbfwAcGlobalIx OBJECT-TYPE
   SYNTAX      GlobalIndex
   MAX-ACCESS  not-accessible
   STATUS      current
   DESCRIPTION
      "The value of the tlsCntTreeGlobalIndex of the MANAGED OBJECT."
   ::= {er1645v2ZbfwAcEntry 10}

er1645v2ZbfwAcTableIx OBJECT-TYPE
   SYNTAX      TableIndex
   MAX-ACCESS  not-accessible
   STATUS      current
   DESCRIPTION
      ""
   ::= {er1645v2ZbfwAcEntry 11}

er1645v2ZbfwAcName OBJECT-TYPE
   SYNTAX      DisplayString
   MAX-ACCESS  read-write
   STATUS      current
   DESCRIPTION
      "Path: zbFirewall.editConf.actions.name"
   ::= {er1645v2ZbfwAcEntry 16777216}

er1645v2ZbfwAcAction OBJECT-TYPE
   SYNTAX      INTEGER
               {
               pass (0),
               drop (1),
               inspect (2)
               }
   MAX-ACCESS  read-write
   STATUS      current
   DESCRIPTION
      "Path: zbFirewall.editConf.actions.action

       Possibilities:
               pass   (0)
               drop   (1)
               inspect   (2)"
   ::= {er1645v2ZbfwAcEntry 33554432}

er1645v2ZbfwAcNatAction OBJECT-TYPE
   SYNTAX      INTEGER
               {
               none (0),
               bypass (1),
               nat (2)
               }
   MAX-ACCESS  read-write
   STATUS      current
   DESCRIPTION
      "Path: zbFirewall.editConf.actions.natAction

       Possibilities:
               none   (0)
               bypass   (1)
               nat   (2)"
   ::= {er1645v2ZbfwAcEntry 67108864}

er1645v2ZbfwAcNat OBJECT-TYPE
   SYNTAX      DisplayString
   MAX-ACCESS  read-write
   STATUS      current
   DESCRIPTION
      "Path: zbFirewall.editConf.actions.nat"
   ::= {er1645v2ZbfwAcEntry 83886080}

er1645v2ZbfwAcQosTos OBJECT-TYPE
   SYNTAX      INTEGER
               {
               unchanged (65535)
               }
   MAX-ACCESS  read-write
   STATUS      current
   DESCRIPTION
      "Path: zbFirewall.editConf.actions.qos.tos

       Possibilities:
               unchanged   (65535)"
   ::= {er1645v2ZbfwAcEntry 100728832}


er1645v2ZbfwPmc OBJECT IDENTIFIER ::= {er1645v2Zbfw 4}

er1645v2ZbfwPmcSSCTable OBJECT-TYPE
   SYNTAX      SEQUENCE OF Er1645v2ZbfwPmcEntry
   MAX-ACCESS  not-accessible
   STATUS      current
   DESCRIPTION
      "parameters"
   ::= {er1645v2ZbfwPmc 1}

er1645v2ZbfwPmcEntry OBJECT-TYPE
   SYNTAX      Er1645v2ZbfwPmcEntry
   MAX-ACCESS  not-accessible
   STATUS      current
   DESCRIPTION
      ""
   INDEX      { er1645v2ZbfwPmcGlobalIx,
                er1645v2ZbfwPmcTableIx }
   ::= {er1645v2ZbfwPmcSSCTable 1}

Er1645v2ZbfwPmcEntry ::=
   SEQUENCE
      {
      er1645v2ZbfwPmcActions
         VariableLengthTableActions,
      er1645v2ZbfwPmcGlobalIx
         GlobalIndex,
      er1645v2ZbfwPmcTableIx
         TableIndex,
      er1645v2ZbfwPmcName
         DisplayString,
      er1645v2ZbfwPmcMaxConnsPerRule
         Integer32,
      er1645v2ZbfwPmcTimersTimeOut
         TimeTicks,
      er1645v2ZbfwPmcTcpWatchTimeOut
         TimeTicks,
      er1645v2ZbfwPmcTcpFinRstTimeOut
         TimeTicks,
      er1645v2ZbfwPmcTcpConnectionTimeOut
         TimeTicks,
      er1645v2ZbfwPmcTcpMssAdjustFwd
         INTEGER,
      er1645v2ZbfwPmcTcpMssAdjustRev
         INTEGER,
      er1645v2ZbfwPmcUdpWatchTimeOut
         TimeTicks,
      er1645v2ZbfwPmcUdpTimeOut
         TimeTicks,
      er1645v2ZbfwPmcIcmpTimeOut
         TimeTicks,
      er1645v2ZbfwPmcIcmpErrorMessages
         Integer32,
      er1645v2ZbfwPmcDnsTimeOut
         TimeTicks,
      er1645v2ZbfwPmcStealthOnDeny
         INTEGER,
      er1645v2ZbfwPmcStealthOnDrop
         INTEGER,
      er1645v2ZbfwPmcStealthOnTcpError
         INTEGER
      }

er1645v2ZbfwPmcActions OBJECT-TYPE
   SYNTAX      VariableLengthTableActions
   MAX-ACCESS  read-write
   STATUS      current
   DESCRIPTION
      "By way of this field, some manipulations
       on this table may be performed."
   ::= {er1645v2ZbfwPmcEntry 2}

er1645v2ZbfwPmcGlobalIx OBJECT-TYPE
   SYNTAX      GlobalIndex
   MAX-ACCESS  not-accessible
   STATUS      current
   DESCRIPTION
      "The value of the tlsCntTreeGlobalIndex of the MANAGED OBJECT."
   ::= {er1645v2ZbfwPmcEntry 10}

er1645v2ZbfwPmcTableIx OBJECT-TYPE
   SYNTAX      TableIndex
   MAX-ACCESS  not-accessible
   STATUS      current
   DESCRIPTION
      ""
   ::= {er1645v2ZbfwPmcEntry 11}

er1645v2ZbfwPmcName OBJECT-TYPE
   SYNTAX      DisplayString
   MAX-ACCESS  read-write
   STATUS      current
   DESCRIPTION
      "Path: zbFirewall.editConf.parameters.name"
   ::= {er1645v2ZbfwPmcEntry 16777216}

er1645v2ZbfwPmcMaxConnsPerRule OBJECT-TYPE
   SYNTAX      Integer32
   MAX-ACCESS  read-write
   STATUS      current
   DESCRIPTION
      "Path: zbFirewall.editConf.parameters.maxConnsPerRule"
   ::= {er1645v2ZbfwPmcEntry 33554432}

er1645v2ZbfwPmcTimersTimeOut OBJECT-TYPE
   SYNTAX      TimeTicks
   MAX-ACCESS  read-write
   STATUS      current
   DESCRIPTION
      "Path: zbFirewall.editConf.parameters.timers.timeOut

       Time in centi-second."
   ::= {er1645v2ZbfwPmcEntry 50397184}

er1645v2ZbfwPmcTcpWatchTimeOut OBJECT-TYPE
   SYNTAX      TimeTicks
   MAX-ACCESS  read-write
   STATUS      current
   DESCRIPTION
      "Path: zbFirewall.editConf.parameters.tcp.watchTimeOut

       Time in centi-second."
   ::= {er1645v2ZbfwPmcEntry 67174400}

er1645v2ZbfwPmcTcpFinRstTimeOut OBJECT-TYPE
   SYNTAX      TimeTicks
   MAX-ACCESS  read-write
   STATUS      current
   DESCRIPTION
      "Path: zbFirewall.editConf.parameters.tcp.finRstTimeOut

       Time in centi-second."
   ::= {er1645v2ZbfwPmcEntry 67239936}

er1645v2ZbfwPmcTcpConnectionTimeOut OBJECT-TYPE
   SYNTAX      TimeTicks
   MAX-ACCESS  read-write
   STATUS      current
   DESCRIPTION
      "Path: zbFirewall.editConf.parameters.tcp.connectionTimeOut

       Time in centi-second."
   ::= {er1645v2ZbfwPmcEntry 67305472}

er1645v2ZbfwPmcTcpMssAdjustFwd OBJECT-TYPE
   SYNTAX      INTEGER
               {
               disabled (0)
               }
   MAX-ACCESS  read-write
   STATUS      current
   DESCRIPTION
      "Path: zbFirewall.editConf.parameters.tcp.mssAdjustFwd

       Possibilities:
               disabled   (0)"
   ::= {er1645v2ZbfwPmcEntry 67371008}

er1645v2ZbfwPmcTcpMssAdjustRev OBJECT-TYPE
   SYNTAX      INTEGER
               {
               disabled (0)
               }
   MAX-ACCESS  read-write
   STATUS      current
   DESCRIPTION
      "Path: zbFirewall.editConf.parameters.tcp.mssAdjustRev

       Possibilities:
               disabled   (0)"
   ::= {er1645v2ZbfwPmcEntry 67436544}

er1645v2ZbfwPmcUdpWatchTimeOut OBJECT-TYPE
   SYNTAX      TimeTicks
   MAX-ACCESS  read-write
   STATUS      current
   DESCRIPTION
      "Path: zbFirewall.editConf.parameters.udp.watchTimeOut

       Time in centi-second."
   ::= {er1645v2ZbfwPmcEntry 83951616}

er1645v2ZbfwPmcUdpTimeOut OBJECT-TYPE
   SYNTAX      TimeTicks
   MAX-ACCESS  read-write
   STATUS      current
   DESCRIPTION
      "Path: zbFirewall.editConf.parameters.udp.timeOut

       Time in centi-second."
   ::= {er1645v2ZbfwPmcEntry 84017152}

er1645v2ZbfwPmcIcmpTimeOut OBJECT-TYPE
   SYNTAX      TimeTicks
   MAX-ACCESS  read-write
   STATUS      current
   DESCRIPTION
      "Path: zbFirewall.editConf.parameters.icmp.timeOut

       Time in centi-second."
   ::= {er1645v2ZbfwPmcEntry 100728832}

er1645v2ZbfwPmcIcmpErrorMessages OBJECT-TYPE
   SYNTAX      Integer32
   MAX-ACCESS  read-write
   STATUS      current
   DESCRIPTION
      "Path: zbFirewall.editConf.parameters.icmp.errorMessages

       Bit meanings:
               bit 0 = netUnreachable,
               bit 1 = hostUnreachable,
               bit 2 = protocolUnreachable,
               bit 3 = portUnreachable,
               bit 4 = fragNeeded,
               bit 5 = srcRouteFail,
               bit 6 = adminProhibited,
               bit 7 = redirect,
               bit 8 = ttlExceeded,
               bit 9 = paramProblem"
   ::= {er1645v2ZbfwPmcEntry 100794368}

er1645v2ZbfwPmcDnsTimeOut OBJECT-TYPE
   SYNTAX      TimeTicks
   MAX-ACCESS  read-write
   STATUS      current
   DESCRIPTION
      "Path: zbFirewall.editConf.parameters.dns.timeOut

       Time in centi-second."
   ::= {er1645v2ZbfwPmcEntry 117506048}

er1645v2ZbfwPmcStealthOnDeny OBJECT-TYPE
   SYNTAX      INTEGER
               {
               disabled (0),
               enabled (1)
               }
   MAX-ACCESS  read-write
   STATUS      current
   DESCRIPTION
      "Path: zbFirewall.editConf.parameters.stealth.onDeny

       Possibilities:
               disabled   (0)
               enabled   (1)"
   ::= {er1645v2ZbfwPmcEntry 134283264}

er1645v2ZbfwPmcStealthOnDrop OBJECT-TYPE
   SYNTAX      INTEGER
               {
               disabled (0),
               enabled (1)
               }
   MAX-ACCESS  read-write
   STATUS      current
   DESCRIPTION
      "Path: zbFirewall.editConf.parameters.stealth.onDrop

       Possibilities:
               disabled   (0)
               enabled   (1)"
   ::= {er1645v2ZbfwPmcEntry 134348800}

er1645v2ZbfwPmcStealthOnTcpError OBJECT-TYPE
   SYNTAX      INTEGER
               {
               disabled (0),
               enabled (1)
               }
   MAX-ACCESS  read-write
   STATUS      current
   DESCRIPTION
      "Path: zbFirewall.editConf.parameters.stealth.onTcpError

       Possibilities:
               disabled   (0)
               enabled   (1)"
   ::= {er1645v2ZbfwPmcEntry 134414336}


er1645v2ZbfwLogging OBJECT IDENTIFIER ::= {er1645v2Zbfw 5}

er1645v2ZbfwLoggingSSCTable OBJECT-TYPE
   SYNTAX      SEQUENCE OF Er1645v2ZbfwLoggingEntry
   MAX-ACCESS  not-accessible
   STATUS      current
   DESCRIPTION
      "firewall Logging"
   ::= {er1645v2ZbfwLogging 1}

er1645v2ZbfwLoggingEntry OBJECT-TYPE
   SYNTAX      Er1645v2ZbfwLoggingEntry
   MAX-ACCESS  not-accessible
   STATUS      current
   DESCRIPTION
      ""
   INDEX      { er1645v2ZbfwLoggingGlobalIx }
   ::= {er1645v2ZbfwLoggingSSCTable 1}

Er1645v2ZbfwLoggingEntry ::=
   SEQUENCE
      {
      er1645v2ZbfwLoggingGlobalIx
         GlobalIndex,
      er1645v2ZbfwLoggingModulesConfigurationConsole
         INTEGER,
      er1645v2ZbfwLoggingModulesConfigurationBuffered
         INTEGER,
      er1645v2ZbfwLoggingModulesConfigurationSyslog
         INTEGER,
      er1645v2ZbfwLoggingModulesConfigurationElements
         Integer32,
      er1645v2ZbfwLoggingModulesConfigurationFacility
         Integer32,
      er1645v2ZbfwLoggingModulesAttackConsole
         INTEGER,
      er1645v2ZbfwLoggingModulesAttackBuffered
         INTEGER,
      er1645v2ZbfwLoggingModulesAttackSyslog
         INTEGER,
      er1645v2ZbfwLoggingModulesAttackElements
         Integer32,
      er1645v2ZbfwLoggingModulesAttackFacility
         Integer32,
      er1645v2ZbfwLoggingModulesTrafficConsole
         INTEGER,
      er1645v2ZbfwLoggingModulesTrafficBuffered
         INTEGER,
      er1645v2ZbfwLoggingModulesTrafficSyslog
         INTEGER,
      er1645v2ZbfwLoggingModulesTrafficElements
         Integer32,
      er1645v2ZbfwLoggingModulesTrafficFacility
         Integer32,
      er1645v2ZbfwLoggingModulesAlgConsole
         INTEGER,
      er1645v2ZbfwLoggingModulesAlgBuffered
         INTEGER,
      er1645v2ZbfwLoggingModulesAlgSyslog
         INTEGER,
      er1645v2ZbfwLoggingModulesAlgElements
         Integer32,
      er1645v2ZbfwLoggingModulesAlgFacility
         Integer32,
      er1645v2ZbfwLoggingModulesGeneralConsole
         INTEGER,
      er1645v2ZbfwLoggingModulesGeneralBuffered
         INTEGER,
      er1645v2ZbfwLoggingModulesGeneralSyslog
         INTEGER,
      er1645v2ZbfwLoggingModulesGeneralElements
         Integer32,
      er1645v2ZbfwLoggingModulesGeneralFacility
         Integer32,
      er1645v2ZbfwLoggingConsoleMode
         INTEGER,
      er1645v2ZbfwLoggingConsoleRateLimitNrMessages
         Counter32,
      er1645v2ZbfwLoggingConsoleRateLimitInterval
         Integer32,
      er1645v2ZbfwLoggingBufferedMode
         INTEGER,
      er1645v2ZbfwLoggingBufferedMaxMessages
         Integer32,
      er1645v2ZbfwLoggingBufferedRateLimitNrMessages
         Counter32,
      er1645v2ZbfwLoggingBufferedRateLimitInterval
         Integer32,
      er1645v2ZbfwLoggingSyslogMode
         INTEGER,
      er1645v2ZbfwLoggingSyslogRateLimitNrMessages
         Counter32,
      er1645v2ZbfwLoggingSyslogRateLimitInterval
         Integer32,
      er1645v2ZbfwLoggingRateLimitEmergencyNrMessages
         Counter32,
      er1645v2ZbfwLoggingRateLimitEmergencyInterval
         Integer32,
      er1645v2ZbfwLoggingRateLimitAlertNrMessages
         Counter32,
      er1645v2ZbfwLoggingRateLimitAlertInterval
         Integer32,
      er1645v2ZbfwLoggingRateLimitCriticalNrMessages
         Counter32,
      er1645v2ZbfwLoggingRateLimitCriticalInterval
         Integer32,
      er1645v2ZbfwLoggingRateLimitErrorNrMessages
         Counter32,
      er1645v2ZbfwLoggingRateLimitErrorInterval
         Integer32,
      er1645v2ZbfwLoggingRateLimitWarningNrMessages
         Counter32,
      er1645v2ZbfwLoggingRateLimitWarningInterval
         Integer32,
      er1645v2ZbfwLoggingRateLimitNoticeNrMessages
         Counter32,
      er1645v2ZbfwLoggingRateLimitNoticeInterval
         Integer32,
      er1645v2ZbfwLoggingRateLimitInformationalNrMessages
         Counter32,
      er1645v2ZbfwLoggingRateLimitInformationalInterval
         Integer32,
      er1645v2ZbfwLoggingRateLimitDebugNrMessages
         Counter32,
      er1645v2ZbfwLoggingRateLimitDebugInterval
         Integer32
      }

er1645v2ZbfwLoggingGlobalIx OBJECT-TYPE
   SYNTAX      GlobalIndex
   MAX-ACCESS  not-accessible
   STATUS      current
   DESCRIPTION
      "The value of the tlsCntTreeGlobalIndex of the MANAGED OBJECT."
   ::= {er1645v2ZbfwLoggingEntry 10}

er1645v2ZbfwLoggingModulesConfigurationConsole OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.configuration.console

       Possibilities:
               emergency   (0)
               alert   (1)
               critical   (2)
               error   (3)
               warning   (4)
               notice   (5)
               informational   (6)
               debug   (7)"
   ::= {er1645v2ZbfwLoggingEntry 16843008}

er1645v2ZbfwLoggingModulesConfigurationBuffered OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.configuration.buffered

       Possibilities:
               emergency   (0)
               alert   (1)
               critical   (2)
               error   (3)
               warning   (4)
               notice   (5)
               informational   (6)
               debug   (7)"
   ::= {er1645v2ZbfwLoggingEntry 16843264}

er1645v2ZbfwLoggingModulesConfigurationSyslog OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.configuration.syslog

       Possibilities:
               emergency   (0)
               alert   (1)
               critical   (2)
               error   (3)
               warning   (4)
               notice   (5)
               informational   (6)
               debug   (7)"
   ::= {er1645v2ZbfwLoggingEntry 16843520}

er1645v2ZbfwLoggingModulesConfigurationElements OBJECT-TYPE
   SYNTAX      Integer32
   MAX-ACCESS  read-write
   STATUS      current
   DESCRIPTION
      "Path: zbFirewall.editConf.logging.modules.configuration.elements

       Bit meanings:
               bit 0 = reconfiguration,
               bit 1 = configError"
   ::= {er1645v2ZbfwLoggingEntry 16843776}

er1645v2ZbfwLoggingModulesConfigurationFacility OBJECT-TYPE
   SYNTAX      Integer32
   MAX-ACCESS  read-write
   STATUS      current
   DESCRIPTION
      "Path: zbFirewall.editConf.logging.modules.configuration.facility"
   ::= {er1645v2ZbfwLoggingEntry 16844032}

er1645v2ZbfwLoggingModulesAttackConsole OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.attack.console

       Possibilities:
               emergency   (0)
               alert   (1)
               critical   (2)
               error   (3)
               warning   (4)
               notice   (5)
               informational   (6)
               debug   (7)"
   ::= {er1645v2ZbfwLoggingEntry 16908544}

er1645v2ZbfwLoggingModulesAttackBuffered OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.attack.buffered

       Possibilities:
               emergency   (0)
               alert   (1)
               critical   (2)
               error   (3)
               warning   (4)
               notice   (5)
               informational   (6)
               debug   (7)"
   ::= {er1645v2ZbfwLoggingEntry 16908800}

er1645v2ZbfwLoggingModulesAttackSyslog OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.attack.syslog

       Possibilities:
               emergency   (0)
               alert   (1)
               critical   (2)
               error   (3)
               warning   (4)
               notice   (5)
               informational   (6)
               debug   (7)"
   ::= {er1645v2ZbfwLoggingEntry 16909056}

er1645v2ZbfwLoggingModulesAttackElements OBJECT-TYPE
   SYNTAX      Integer32
   MAX-ACCESS  read-write
   STATUS      current
   DESCRIPTION
      "Path: zbFirewall.editConf.logging.modules.attack.elements

       Bit meanings:
               bit 0 = synFlooding,
               bit 1 = pingOfDeath,
               bit 2 = ipSpoofing,
               bit 3 = winNuke,
               bit 4 = ipOption,
               bit 5 = tcpProbe"
   ::= {er1645v2ZbfwLoggingEntry 16909312}

er1645v2ZbfwLoggingModulesAttackFacility OBJECT-TYPE
   SYNTAX      Integer32
   MAX-ACCESS  read-write
   STATUS      current
   DESCRIPTION
      "Path: zbFirewall.editConf.logging.modules.attack.facility"
   ::= {er1645v2ZbfwLoggingEntry 16909568}

er1645v2ZbfwLoggingModulesTrafficConsole OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.traffic.console

       Possibilities:
               emergency   (0)
               alert   (1)
               critical   (2)
               error   (3)
               warning   (4)
               notice   (5)
               informational   (6)
               debug   (7)"
   ::= {er1645v2ZbfwLoggingEntry 16974080}

er1645v2ZbfwLoggingModulesTrafficBuffered OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.traffic.buffered

       Possibilities:
               emergency   (0)
               alert   (1)
               critical   (2)
               error   (3)
               warning   (4)
               notice   (5)
               informational   (6)
               debug   (7)"
   ::= {er1645v2ZbfwLoggingEntry 16974336}

er1645v2ZbfwLoggingModulesTrafficSyslog OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.traffic.syslog

       Possibilities:
               emergency   (0)
               alert   (1)
               critical   (2)
               error   (3)
               warning   (4)
               notice   (5)
               informational   (6)
               debug   (7)"
   ::= {er1645v2ZbfwLoggingEntry 16974592}

er1645v2ZbfwLoggingModulesTrafficElements OBJECT-TYPE
   SYNTAX      Integer32
   MAX-ACCESS  read-write
   STATUS      current
   DESCRIPTION
      "Path: zbFirewall.editConf.logging.modules.traffic.elements

       Bit meanings:
               bit 0 = connection,
               bit 1 = dropPolicy,
               bit 2 = implicitDeny,
               bit 3 = halfOpenConnection"
   ::= {er1645v2ZbfwLoggingEntry 16974848}

er1645v2ZbfwLoggingModulesTrafficFacility OBJECT-TYPE
   SYNTAX      Integer32
   MAX-ACCESS  read-write
   STATUS      current
   DESCRIPTION
      "Path: zbFirewall.editConf.logging.modules.traffic.facility"
   ::= {er1645v2ZbfwLoggingEntry 16975104}

er1645v2ZbfwLoggingModulesAlgConsole OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.alg.console

       Possibilities:
               emergency   (0)
               alert   (1)
               critical   (2)
               error   (3)
               warning   (4)
               notice   (5)
               informational   (6)
               debug   (7)"
   ::= {er1645v2ZbfwLoggingEntry 17039616}

er1645v2ZbfwLoggingModulesAlgBuffered OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.alg.buffered

       Possibilities:
               emergency   (0)
               alert   (1)
               critical   (2)
               error   (3)
               warning   (4)
               notice   (5)
               informational   (6)
               debug   (7)"
   ::= {er1645v2ZbfwLoggingEntry 17039872}

er1645v2ZbfwLoggingModulesAlgSyslog OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.alg.syslog

       Possibilities:
               emergency   (0)
               alert   (1)
               critical   (2)
               error   (3)
               warning   (4)
               notice   (5)
               informational   (6)
               debug   (7)"
   ::= {er1645v2ZbfwLoggingEntry 17040128}

er1645v2ZbfwLoggingModulesAlgElements OBJECT-TYPE
   SYNTAX      Integer32
   MAX-ACCESS  read-write
   STATUS      current
   DESCRIPTION
      "Path: zbFirewall.editConf.logging.modules.alg.elements

       Bit meanings:
               bit 0 = ftp,
               bit 1 = tftp,
               bit 2 = sip,
               bit 3 = h323"
   ::= {er1645v2ZbfwLoggingEntry 17040384}

er1645v2ZbfwLoggingModulesAlgFacility OBJECT-TYPE
   SYNTAX      Integer32
   MAX-ACCESS  read-write
   STATUS      current
   DESCRIPTION
      "Path: zbFirewall.editConf.logging.modules.alg.facility"
   ::= {er1645v2ZbfwLoggingEntry 17040640}

er1645v2ZbfwLoggingModulesGeneralConsole OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.general.console

       Possibilities:
               emergency   (0)
               alert   (1)
               critical   (2)
               error   (3)
               warning   (4)
               notice   (5)
               informational   (6)
               debug   (7)"
   ::= {er1645v2ZbfwLoggingEntry 17105152}

er1645v2ZbfwLoggingModulesGeneralBuffered OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.general.buffered

       Possibilities:
               emergency   (0)
               alert   (1)
               critical   (2)
               error   (3)
               warning   (4)
               notice   (5)
               informational   (6)
               debug   (7)"
   ::= {er1645v2ZbfwLoggingEntry 17105408}

er1645v2ZbfwLoggingModulesGeneralSyslog OBJECT-TYPE
   SYNTAX      INTEGER
               {
               emergency (0),
               alert (1),
               critical (2),
               error (3),
               warning (4),
               notice (5),
               informational (6),
               debug (7)
               }
   MAX-ACCESS  read-write
   STATUS      current
   DESCRIPTION
      "Path: zbFirewall.editConf.logging.modules.general.syslog

       Possibilities:
               emergency   (0)
               alert   (1)
               critical   (2)
               error   (3)
               warning   (4)
               notice   (5)
               informational   (6)
               debug   (7)"
   ::= {er1645v2ZbfwLoggingEntry 17105664}

er1645v2ZbfwLoggingModulesGeneralElements OBJECT-TYPE
   SYNTAX      Integer32
   MAX-ACCESS  read-write
   STATUS      current
   DESCRIPTION
      "Path: zbFirewall.editConf.logging.modules.general.elements

       Bit meanings:
               bit 0 = systemErrors,
               bit 1 = memory"
   ::= {er1645v2ZbfwLoggingEntry 17105920}

er1645v2ZbfwLoggingModulesGeneralFacility OBJECT-TYPE
   SYNTAX      Integer32
   MAX-ACCESS  read-write
   STATUS      current
   DESCRIPTION
      "Path: zbFirewall.editConf.logging.modules.general.facility"
   ::= {er1645v2ZbfwLoggingEntry 17106176}

er1645v2ZbfwLoggingConsoleMode OBJECT-TYPE
   SYNTAX      INTEGER
               {
               disabled (0),
               enabled (1)
               }
   MAX-ACCESS  read-write
   STATUS      current
   DESCRIPTION
      "Path: zbFirewall.editConf.logging.console.mode

       Possibilities:
               disabled   (0)
               enabled   (1)"
   ::= {er1645v2ZbfwLoggingEntry 33619968}

er1645v2ZbfwLoggingConsoleRateLimitNrMessages OBJECT-TYPE
   SYNTAX      Counter32
   MAX-ACCESS  read-write
   STATUS      current
   DESCRIPTION
      "Path: zbFirewall.editConf.logging.console.rateLimit.nrMessages

       32 bit unsigned wrappable counter."
   ::= {er1645v2ZbfwLoggingEntry 33685760}

er1645v2ZbfwLoggingConsoleRateLimitInterval OBJECT-TYPE
   SYNTAX      Integer32
   UNITS       "sec"
   MAX-ACCESS  read-write
   STATUS      current
   DESCRIPTION
      "Path: zbFirewall.editConf.logging.console.rateLimit.interval

       unit name = sec"
   ::= {er1645v2ZbfwLoggingEntry 33686016}

er1645v2ZbfwLoggingBufferedMode OBJECT-TYPE
   SYNTAX      INTEGER
               {
               disabled (0),
               enabled (1)
               }
   MAX-ACCESS  read-write
   STATUS      current
   DESCRIPTION
      "Path: zbFirewall.editConf.logging.buffered.mode

       Possibilities:
               disabled   (0)
               enabled   (1)"
   ::= {er1645v2ZbfwLoggingEntry 50397184}

er1645v2ZbfwLoggingBufferedMaxMessages OBJECT-TYPE
   SYNTAX      Integer32
   MAX-ACCESS  read-write
   STATUS      current
   DESCRIPTION
      "Path: zbFirewall.editConf.logging.buffered.maxMessages"
   ::= {er1645v2ZbfwLoggingEntry 50462720}

er1645v2ZbfwLoggingBufferedRateLimitNrMessages OBJECT-TYPE
   SYNTAX      Counter32
   MAX-ACCESS  read-write
   STATUS      current
   DESCRIPTION
      "Path: zbFirewall.editConf.logging.buffered.rateLimit.nrMessages

       32 bit unsigned wrappable counter."
   ::= {er1645v2ZbfwLoggingEntry 50528512}

er1645v2ZbfwLoggingBufferedRateLimitInterval OBJECT-TYPE
   SYNTAX      Integer32
   UNITS       "sec"
   MAX-ACCESS  read-write
   STATUS      current
   DESCRIPTION
      "Path: zbFirewall.editConf.logging.buffered.rateLimit.interval

       unit name = sec"
   ::= {er1645v2ZbfwLoggingEntry 50528768}

er1645v2ZbfwLoggingSyslogMode OBJECT-TYPE
   SYNTAX      INTEGER
               {
               disabled (0),
               enabled (1)
               }
   MAX-ACCESS  read-write
   STATUS      current
   DESCRIPTION
      "Path: zbFirewall.editConf.logging.syslog.mode

       Possibilities:
               disabled   (0)
               enabled   (1)"
   ::= {er1645v2ZbfwLoggingEntry 67174400}

er1645v2ZbfwLoggingSyslogRateLimitNrMessages OBJECT-TYPE
   SYNTAX      Counter32
   MAX-ACCESS  read-write
   STATUS      current
   DESCRIPTION
      "Path: zbFirewall.editConf.logging.syslog.rateLimit.nrMessages

       32 bit unsigned wrappable counter."
   ::= {er1645v2ZbfwLoggingEntry 67305728}

er1645v2ZbfwLoggingSyslogRateLimitInterval OBJECT-TYPE
   SYNTAX      Integer32
   UNITS       "sec"
   MAX-ACCESS  read-write
   STATUS      current
   DESCRIPTION
      "Path: zbFirewall.editConf.logging.syslog.rateLimit.interval

       unit name = sec"
   ::= {er1645v2ZbfwLoggingEntry 67305984}

er1645v2ZbfwLoggingRateLimitEmergencyNrMessages OBJECT-TYPE
   SYNTAX      Counter32
   MAX-ACCESS  read-write
   STATUS      current
   DESCRIPTION
      "Path: zbFirewall.editConf.logging.rateLimit.emergency.nrMessages

       32 bit unsigned wrappable counter."
   ::= {er1645v2ZbfwLoggingEntry 83951872}

er1645v2ZbfwLoggingRateLimitEmergencyInterval OBJECT-TYPE
   SYNTAX      Integer32
   UNITS       "sec"
   MAX-ACCESS  read-write
   STATUS      current
   DESCRIPTION
      "Path: zbFirewall.editConf.logging.rateLimit.emergency.interval

       unit name = sec"
   ::= {er1645v2ZbfwLoggingEntry 83952128}

er1645v2ZbfwLoggingRateLimitAlertNrMessages OBJECT-TYPE
   SYNTAX      Counter32
   MAX-ACCESS  read-write
   STATUS      current
   DESCRIPTION
      "Path: zbFirewall.editConf.logging.rateLimit.alert.nrMessages

       32 bit unsigned wrappable counter."
   ::= {er1645v2ZbfwLoggingEntry 84017408}

er1645v2ZbfwLoggingRateLimitAlertInterval OBJECT-TYPE
   SYNTAX      Integer32
   UNITS       "sec"
   MAX-ACCESS  read-write
   STATUS      current
   DESCRIPTION
      "Path: zbFirewall.editConf.logging.rateLimit.alert.interval

       unit name = sec"
   ::= {er1645v2ZbfwLoggingEntry 84017664}

er1645v2ZbfwLoggingRateLimitCriticalNrMessages OBJECT-TYPE
   SYNTAX      Counter32
   MAX-ACCESS  read-write
   STATUS      current
   DESCRIPTION
      "Path: zbFirewall.editConf.logging.rateLimit.critical.nrMessages

       32 bit unsigned wrappable counter."
   ::= {er1645v2ZbfwLoggingEntry 84082944}

er1645v2ZbfwLoggingRateLimitCriticalInterval OBJECT-TYPE
   SYNTAX      Integer32
   UNITS       "sec"
   MAX-ACCESS  read-write
   STATUS      current
   DESCRIPTION
      "Path: zbFirewall.editConf.logging.rateLimit.critical.interval

       unit name = sec"
   ::= {er1645v2ZbfwLoggingEntry 84083200}

er1645v2ZbfwLoggingRateLimitErrorNrMessages OBJECT-TYPE
   SYNTAX      Counter32
   MAX-ACCESS  read-write
   STATUS      current
   DESCRIPTION
      "Path: zbFirewall.editConf.logging.rateLimit.error.nrMessages

       32 bit unsigned wrappable counter."
   ::= {er1645v2ZbfwLoggingEntry 84148480}

er1645v2ZbfwLoggingRateLimitErrorInterval OBJECT-TYPE
   SYNTAX      Integer32
   UNITS       "sec"
   MAX-ACCESS  read-write
   STATUS      current
   DESCRIPTION
      "Path: zbFirewall.editConf.logging.rateLimit.error.interval

       unit name = sec"
   ::= {er1645v2ZbfwLoggingEntry 84148736}

er1645v2ZbfwLoggingRateLimitWarningNrMessages OBJECT-TYPE
   SYNTAX      Counter32
   MAX-ACCESS  read-write
   STATUS      current
   DESCRIPTION
      "Path: zbFirewall.editConf.logging.rateLimit.warning.nrMessages

       32 bit unsigned wrappable counter."
   ::= {er1645v2ZbfwLoggingEntry 84214016}

er1645v2ZbfwLoggingRateLimitWarningInterval OBJECT-TYPE
   SYNTAX      Integer32
   UNITS       "sec"
   MAX-ACCESS  read-write
   STATUS      current
   DESCRIPTION
      "Path: zbFirewall.editConf.logging.rateLimit.warning.interval

       unit name = sec"
   ::= {er1645v2ZbfwLoggingEntry 84214272}

er1645v2ZbfwLoggingRateLimitNoticeNrMessages OBJECT-TYPE
   SYNTAX      Counter32
   MAX-ACCESS  read-write
   STATUS      current
   DESCRIPTION
      "Path: zbFirewall.editConf.logging.rateLimit.notice.nrMessages

       32 bit unsigned wrappable counter."
   ::= {er1645v2ZbfwLoggingEntry 84279552}

er1645v2ZbfwLoggingRateLimitNoticeInterval OBJECT-TYPE
   SYNTAX      Integer32
   UNITS       "sec"
   MAX-ACCESS  read-write
   STATUS      current
   DESCRIPTION
      "Path: zbFirewall.editConf.logging.rateLimit.notice.interval

       unit name = sec"
   ::= {er1645v2ZbfwLoggingEntry 84279808}

er1645v2ZbfwLoggingRateLimitInformationalNrMessages OBJECT-TYPE
   SYNTAX      Counter32
   MAX-ACCESS  read-write
   STATUS      current
   DESCRIPTION
      "Path: zbFirewall.editConf.logging.rateLimit.informational.nrMessages

       32 bit unsigned wrappable counter."
   ::= {er1645v2ZbfwLoggingEntry 84345088}

er1645v2ZbfwLoggingRateLimitInformationalInterval OBJECT-TYPE
   SYNTAX      Integer32
   UNITS       "sec"
   MAX-ACCESS  read-write
   STATUS      current
   DESCRIPTION
      "Path: zbFirewall.editConf.logging.rateLimit.informational.interval

       unit name = sec"
   ::= {er1645v2ZbfwLoggingEntry 84345344}

er1645v2ZbfwLoggingRateLimitDebugNrMessages OBJECT-TYPE
   SYNTAX      Counter32
   MAX-ACCESS  read-write
   STATUS      current
   DESCRIPTION
      "Path: zbFirewall.editConf.logging.rateLimit.debug.nrMessages

       32 bit unsigned wrappable counter."
   ::= {er1645v2ZbfwLoggingEntry 84410624}

er1645v2ZbfwLoggingRateLimitDebugInterval OBJECT-TYPE
   SYNTAX      Integer32
   UNITS       "sec"
   MAX-ACCESS  read-write
   STATUS      current
   DESCRIPTION
      "Path: zbFirewall.editConf.logging.rateLimit.debug.interval

       unit name = sec"
   ::= {er1645v2ZbfwLoggingEntry 84410880}

er1645v2ZbfwLoggingSyslogServers OBJECT-TYPE
   SYNTAX      SEQUENCE OF Er1645v2ZbfwLoggingSyslogServersEntry
   MAX-ACCESS  not-accessible
   STATUS      current
   DESCRIPTION
      ""
   ::= {er1645v2ZbfwLogging 67239936}

er1645v2ZbfwLoggingSyslogServersEntry OBJECT-TYPE
   SYNTAX      Er1645v2ZbfwLoggingSyslogServersEntry
   MAX-ACCESS  not-accessible
   STATUS      current
   DESCRIPTION
      ""
   INDEX      { er1645v2ZbfwLoggingSyslogServersGlobalIx,
                er1645v2ZbfwLoggingSyslogServersTableIx }
   ::= {er1645v2ZbfwLoggingSyslogServers 1}

Er1645v2ZbfwLoggingSyslogServersEntry ::=
   SEQUENCE
      {
      er1645v2ZbfwLoggingSyslogServersActions
         VariableLengthTableActions,
      er1645v2ZbfwLoggingSyslogServersGlobalIx
         GlobalIndex,
      er1645v2ZbfwLoggingSyslogServersTableIx
         TableIndex,
      er1645v2ZbfwLoggingSyslogServersVrfRouter
         DisplayString,
      er1645v2ZbfwLoggingSyslogServersAddress
         IpAddress,
      er1645v2ZbfwLoggingSyslogServersSourceIp
         IpAddress,
      er1645v2ZbfwLoggingSyslogServersSeverityLevel
         Integer32
      }

er1645v2ZbfwLoggingSyslogServersActions OBJECT-TYPE
   SYNTAX      VariableLengthTableActions
   MAX-ACCESS  read-write
   STATUS      current
   DESCRIPTION
      "By way of this field, some manipulations
       on this table may be performed."
   ::= {er1645v2ZbfwLoggingSyslogServersEntry 2}

er1645v2ZbfwLoggingSyslogServersGlobalIx OBJECT-TYPE
   SYNTAX      GlobalIndex
   MAX-ACCESS  not-accessible
   STATUS      current
   DESCRIPTION
      "The value of the tlsCntTreeGlobalIndex of the MANAGED OBJECT."
   ::= {er1645v2ZbfwLoggingSyslogServersEntry 10}

er1645v2ZbfwLoggingSyslogServersTableIx OBJECT-TYPE
   SYNTAX      TableIndex
   MAX-ACCESS  not-accessible
   STATUS      current
   DESCRIPTION
      ""
   ::= {er1645v2ZbfwLoggingSyslogServersEntry 11}

er1645v2ZbfwLoggingSyslogServersVrfRouter OBJECT-TYPE
   SYNTAX      DisplayString
   MAX-ACCESS  read-write
   STATUS      current
   DESCRIPTION
      "Path: zbFirewall.editConf.logging.syslog.servers.vrfRouter"
   ::= {er1645v2ZbfwLoggingSyslogServersEntry 16777216}

er1645v2ZbfwLoggingSyslogServersAddress OBJECT-TYPE
   SYNTAX      IpAddress
   MAX-ACCESS  read-write
   STATUS      current
   DESCRIPTION
      "Path: zbFirewall.editConf.logging.syslog.servers.address"
   ::= {er1645v2ZbfwLoggingSyslogServersEntry 33554432}

er1645v2ZbfwLoggingSyslogServersSourceIp OBJECT-TYPE
   SYNTAX      IpAddress
   MAX-ACCESS  read-write
   STATUS      current
   DESCRIPTION
      "Path: zbFirewall.editConf.logging.syslog.servers.sourceIp"
   ::= {er1645v2ZbfwLoggingSyslogServersEntry 50331648}

er1645v2ZbfwLoggingSyslogServersSeverityLevel OBJECT-TYPE
   SYNTAX      Integer32
   MAX-ACCESS  read-write
   STATUS      current
   DESCRIPTION
      "Path: zbFirewall.editConf.logging.syslog.servers.severityLevel"
   ::= {er1645v2ZbfwLoggingSyslogServersEntry 67108864}


er1645v2ZbfwAttacks OBJECT IDENTIFIER ::= {er1645v2Zbfw 8}

er1645v2ZbfwAttacksSSCTable OBJECT-TYPE
   SYNTAX      SEQUENCE OF Er1645v2ZbfwAttacksEntry
   MAX-ACCESS  not-accessible
   STATUS      current
   DESCRIPTION
      "global attack parameters"
   ::= {er1645v2ZbfwAttacks 1}

er1645v2ZbfwAttacksEntry OBJECT-TYPE
   SYNTAX      Er1645v2ZbfwAttacksEntry
   MAX-ACCESS  not-accessible
   STATUS      current
   DESCRIPTION
      ""
   INDEX      { er1645v2ZbfwAttacksGlobalIx }
   ::= {er1645v2ZbfwAttacksSSCTable 1}

Er1645v2ZbfwAttacksEntry ::=
   SEQUENCE
      {
      er1645v2ZbfwAttacksGlobalIx
         GlobalIndex,
      er1645v2ZbfwAttacksTcpMaxIncompleteLow
         Integer32,
      er1645v2ZbfwAttacksTcpMaxIncompleteHigh
         Integer32
      }

er1645v2ZbfwAttacksGlobalIx OBJECT-TYPE
   SYNTAX      GlobalIndex
   MAX-ACCESS  not-accessible
   STATUS      current
   DESCRIPTION
      "The value of the tlsCntTreeGlobalIndex of the MANAGED OBJECT."
   ::= {er1645v2ZbfwAttacksEntry 10}

er1645v2ZbfwAttacksTcpMaxIncompleteLow OBJECT-TYPE
   SYNTAX      Integer32
   MAX-ACCESS  read-write
   STATUS      current
   DESCRIPTION
      "Path: zbFirewall.editConf.attacks.tcp.maxIncompleteLow"
   ::= {er1645v2ZbfwAttacksEntry 16842752}

er1645v2ZbfwAttacksTcpMaxIncompleteHigh OBJECT-TYPE
   SYNTAX      Integer32
   MAX-ACCESS  read-write
   STATUS      current
   DESCRIPTION
      "Path: zbFirewall.editConf.attacks.tcp.maxIncompleteHigh"
   ::= {er1645v2ZbfwAttacksEntry 16908288}


er1645v2ZbfwAlarmMask OBJECT IDENTIFIER ::= {er1645v2Zbfw 135}

er1645v2ZbfwAlarmMaskTable OBJECT-TYPE
   SYNTAX      SEQUENCE OF Er1645v2ZbfwAlarmMaskEntry
   MAX-ACCESS  not-accessible
   STATUS      current
   DESCRIPTION
      "zbfwAlarmMask"
   ::= {er1645v2ZbfwAlarmMask 1}

er1645v2ZbfwAlarmMaskEntry OBJECT-TYPE
   SYNTAX      Er1645v2ZbfwAlarmMaskEntry
   MAX-ACCESS  not-accessible
   STATUS      current
   DESCRIPTION
      ""
   INDEX      { er1645v2ZbfwAlarmMaskGlobalIx }
   ::= {er1645v2ZbfwAlarmMaskTable 1}

Er1645v2ZbfwAlarmMaskEntry ::=
   SEQUENCE
      {
      er1645v2ZbfwAlarmMaskGlobalIx
         GlobalIndex,
      er1645v2ZbfwAlarmMaskValue
         Integer32
      }

er1645v2ZbfwAlarmMaskGlobalIx OBJECT-TYPE
   SYNTAX      GlobalIndex
   MAX-ACCESS  not-accessible
   STATUS      current
   DESCRIPTION
      "The value of the tlsCntTreeGlobalIndex of the MANAGED OBJECT."
   ::= {er1645v2ZbfwAlarmMaskEntry 10}

er1645v2ZbfwAlarmMaskValue OBJECT-TYPE
   SYNTAX      Integer32
   MAX-ACCESS  read-write
   STATUS      current
   DESCRIPTION
      "Path: zbFirewall.editConf.alarmMask

       Bit meanings:
               bit 0 = usedConnectionsHigh,
               bit 1 = usedConnectionsLow,
               bit 2 = synFlooding"
   ::= {er1645v2ZbfwAlarmMaskEntry 2147483648}


er1645v2ZbfwAlarmLev OBJECT IDENTIFIER ::= {er1645v2Zbfw 170}

er1645v2ZbfwAlarmLevSSCTable OBJECT-TYPE
   SYNTAX      SEQUENCE OF Er1645v2ZbfwAlarmLevEntry
   MAX-ACCESS  not-accessible
   STATUS      current
   DESCRIPTION
      "zbfwAlarmLevels"
   ::= {er1645v2ZbfwAlarmLev 1}

er1645v2ZbfwAlarmLevEntry OBJECT-TYPE
   SYNTAX      Er1645v2ZbfwAlarmLevEntry
   MAX-ACCESS  not-accessible
   STATUS      current
   DESCRIPTION
      ""
   INDEX      { er1645v2ZbfwAlarmLevGlobalIx }
   ::= {er1645v2ZbfwAlarmLevSSCTable 1}

Er1645v2ZbfwAlarmLevEntry ::=
   SEQUENCE
      {
      er1645v2ZbfwAlarmLevGlobalIx
         GlobalIndex,
      er1645v2ZbfwAlarmLevUsedConnectionsHigh
         Integer32,
      er1645v2ZbfwAlarmLevUsedConnectionsLow
         Integer32,
      er1645v2ZbfwAlarmLevSynFlooding
         Integer32
      }

er1645v2ZbfwAlarmLevGlobalIx OBJECT-TYPE
   SYNTAX      GlobalIndex
   MAX-ACCESS  not-accessible
   STATUS      current
   DESCRIPTION
      "The value of the tlsCntTreeGlobalIndex of the MANAGED OBJECT."
   ::= {er1645v2ZbfwAlarmLevEntry 10}

er1645v2ZbfwAlarmLevUsedConnectionsHigh OBJECT-TYPE
   SYNTAX      Integer32
   MAX-ACCESS  read-write
   STATUS      current
   DESCRIPTION
      "Path: zbFirewall.editConf.alarmLevel.usedConnectionsHigh"
   ::= {er1645v2ZbfwAlarmLevEntry 16777216}

er1645v2ZbfwAlarmLevUsedConnectionsLow OBJECT-TYPE
   SYNTAX      Integer32
   MAX-ACCESS  read-write
   STATUS      current
   DESCRIPTION
      "Path: zbFirewall.editConf.alarmLevel.usedConnectionsLow"
   ::= {er1645v2ZbfwAlarmLevEntry 33554432}

er1645v2ZbfwAlarmLevSynFlooding OBJECT-TYPE
   SYNTAX      Integer32
   MAX-ACCESS  read-write
   STATUS      current
   DESCRIPTION
      "Path: zbFirewall.editConf.alarmLevel.synFlooding"
   ::= {er1645v2ZbfwAlarmLevEntry 50331648}



sr1645v2Zbfw OBJECT IDENTIFIER ::= {r1645v2Zbfw 14}


sr1645v2ZbfwSnmpIndex OBJECT IDENTIFIER ::= {sr1645v2Zbfw 269}

sr1645v2ZbfwSnmpIndexTable OBJECT-TYPE
   SYNTAX      SEQUENCE OF Sr1645v2ZbfwSnmpIndexEntry
   MAX-ACCESS  not-accessible
   STATUS      current
   DESCRIPTION
      "SNMP index assigned to this object"
   ::= {sr1645v2ZbfwSnmpIndex 1}

sr1645v2ZbfwSnmpIndexEntry OBJECT-TYPE
   SYNTAX      Sr1645v2ZbfwSnmpIndexEntry
   MAX-ACCESS  not-accessible
   STATUS      current
   DESCRIPTION
      ""
   INDEX      { sr1645v2ZbfwSnmpIndexGlobalIx }
   ::= {sr1645v2ZbfwSnmpIndexTable 1}

Sr1645v2ZbfwSnmpIndexEntry ::=
   SEQUENCE
      {
      sr1645v2ZbfwSnmpIndexGlobalIx
         GlobalIndex,
      sr1645v2ZbfwSnmpIndexValue
         Integer32
      }

sr1645v2ZbfwSnmpIndexGlobalIx OBJECT-TYPE
   SYNTAX      GlobalIndex
   MAX-ACCESS  not-accessible
   STATUS      current
   DESCRIPTION
      "The value of the tlsCntTreeGlobalIndex of the MANAGED OBJECT."
   ::= {sr1645v2ZbfwSnmpIndexEntry 10}

sr1645v2ZbfwSnmpIndexValue OBJECT-TYPE
   SYNTAX      Integer32
   MAX-ACCESS  read-only
   STATUS      current
   DESCRIPTION
      "Path: zbFirewall.status.snmpIndex"
   ::= {sr1645v2ZbfwSnmpIndexEntry 2147483648}


sr1645v2ZbfwZones OBJECT IDENTIFIER ::= {sr1645v2Zbfw 21}

sr1645v2ZbfwZonesSSCTable OBJECT-TYPE
   SYNTAX      SEQUENCE OF Sr1645v2ZbfwZonesEntry
   MAX-ACCESS  not-accessible
   STATUS      current
   DESCRIPTION
      "runtime zone table"
   ::= {sr1645v2ZbfwZones 1}

sr1645v2ZbfwZonesEntry OBJECT-TYPE
   SYNTAX      Sr1645v2ZbfwZonesEntry
   MAX-ACCESS  not-accessible
   STATUS      current
   DESCRIPTION
      ""
   INDEX      { sr1645v2ZbfwZonesGlobalIx,
                sr1645v2ZbfwZonesTableIx }
   ::= {sr1645v2ZbfwZonesSSCTable 1}

Sr1645v2ZbfwZonesEntry ::=
   SEQUENCE
      {
      sr1645v2ZbfwZonesGlobalIx
         GlobalIndex,
      sr1645v2ZbfwZonesTableIx
         TableIndex,
      sr1645v2ZbfwZonesName
         DisplayString,
      sr1645v2ZbfwZonesInboundNatName
         DisplayString,
      sr1645v2ZbfwZonesInboundNatGateway
         IpAddress
      }

sr1645v2ZbfwZonesGlobalIx OBJECT-TYPE
   SYNTAX      GlobalIndex
   MAX-ACCESS  not-accessible
   STATUS      current
   DESCRIPTION
      "The value of the tlsCntTreeGlobalIndex of the MANAGED OBJECT."
   ::= {sr1645v2ZbfwZonesEntry 10}

sr1645v2ZbfwZonesTableIx OBJECT-TYPE
   SYNTAX      TableIndex
   MAX-ACCESS  not-accessible
   STATUS      current
   DESCRIPTION
      ""
   ::= {sr1645v2ZbfwZonesEntry 11}

sr1645v2ZbfwZonesName OBJECT-TYPE
   SYNTAX      DisplayString
   MAX-ACCESS  read-only
   STATUS      current
   DESCRIPTION
      "Path: zbFirewall.status.zones.name"
   ::= {sr1645v2ZbfwZonesEntry 16777216}

sr1645v2ZbfwZonesInboundNatName OBJECT-TYPE
   SYNTAX      DisplayString
   MAX-ACCESS  read-only
   STATUS      current
   DESCRIPTION
      "Path: zbFirewall.status.zones.inboundNat.name"
   ::= {sr1645v2ZbfwZonesEntry 33619968}

sr1645v2ZbfwZonesInboundNatGateway OBJECT-TYPE
   SYNTAX      IpAddress
   MAX-ACCESS  read-only
   STATUS      current
   DESCRIPTION
      "Path: zbFirewall.status.zones.inboundNat.gateway"
   ::= {sr1645v2ZbfwZonesEntry 33685504}

sr1645v2ZbfwZonesInboundNatStaticMappings OBJECT-TYPE
   SYNTAX      SEQUENCE OF Sr1645v2ZbfwZonesInboundNatStaticMappingsEntry
   MAX-ACCESS  not-accessible
   STATUS      current
   DESCRIPTION
      ""
   ::= {sr1645v2ZbfwZones 33751040}

sr1645v2ZbfwZonesInboundNatStaticMappingsEntry OBJECT-TYPE
   SYNTAX      Sr1645v2ZbfwZonesInboundNatStaticMappingsEntry
   MAX-ACCESS  not-accessible
   STATUS      current
   DESCRIPTION
      ""
   INDEX      { sr1645v2ZbfwZonesInboundNatStaticMappingsGlobalIx,
                sr1645v2ZbfwZonesTableIx,
                sr1645v2ZbfwZonesInboundNatStaticMappingsTableIx }
   ::= {sr1645v2ZbfwZonesInboundNatStaticMappings 1}

Sr1645v2ZbfwZonesInboundNatStaticMappingsEntry ::=
   SEQUENCE
      {
      sr1645v2ZbfwZonesInboundNatStaticMappingsGlobalIx
         GlobalIndex,
      sr1645v2ZbfwZonesInboundNatStaticMappingsTableIx
         TableIndex,
      sr1645v2ZbfwZonesInboundNatStaticMappingsPublicAddress
         IpAddress,
      sr1645v2ZbfwZonesInboundNatStaticMappingsPublicPort
         INTEGER,
      sr1645v2ZbfwZonesInboundNatStaticMappingsProtocol
         INTEGER,
      sr1645v2ZbfwZonesInboundNatStaticMappingsPrivateAddress
         IpAddress,
      sr1645v2ZbfwZonesInboundNatStaticMappingsPrivatePort
         INTEGER
      }

sr1645v2ZbfwZonesInboundNatStaticMappingsGlobalIx OBJECT-TYPE
   SYNTAX      GlobalIndex
   MAX-ACCESS  not-accessible
   STATUS      current
   DESCRIPTION
      "The value of the tlsCntTreeGlobalIndex of the MANAGED OBJECT."
   ::= {sr1645v2ZbfwZonesInboundNatStaticMappingsEntry 10}

sr1645v2ZbfwZonesInboundNatStaticMappingsTableIx OBJECT-TYPE
   SYNTAX      TableIndex
   MAX-ACCESS  not-accessible
   STATUS      current
   DESCRIPTION
      ""
   ::= {sr1645v2ZbfwZonesInboundNatStaticMappingsEntry 11}

sr1645v2ZbfwZonesInboundNatStaticMappingsPublicAddress OBJECT-TYPE
   SYNTAX      IpAddress
   MAX-ACCESS  read-only
   STATUS      current
   DESCRIPTION
      "Path: zbFirewall.status.zones.inboundNat.staticMappings.publicAddress"
   ::= {sr1645v2ZbfwZonesInboundNatStaticMappingsEntry 16777216}

sr1645v2ZbfwZonesInboundNatStaticMappingsPublicPort OBJECT-TYPE
   SYNTAX      INTEGER
               {
               discard (9),
               bgp (179),
               bootpmdhcpmc (68),
               bootpmdhcpms (67),
               cpudpencap (2746),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               optional (0),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-only
   STATUS      current
   DESCRIPTION
      "Path: zbFirewall.status.zones.inboundNat.staticMappings.publicPort

       Possibilities:
               discard   (9)
               bgp   (179)
               bootp-dhcp-c   (68)
               bootp-dhcp-s   (67)
               cpudpencap   (2746)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               optional   (0)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {sr1645v2ZbfwZonesInboundNatStaticMappingsEntry 33554432}

sr1645v2ZbfwZonesInboundNatStaticMappingsProtocol OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6),
               icmpV6 (58),
               l2tp (115)
               }
   MAX-ACCESS  read-only
   STATUS      current
   DESCRIPTION
      "Path: zbFirewall.status.zones.inboundNat.staticMappings.protocol

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)
               icmpV6   (58)
               l2tp   (115)"
   ::= {sr1645v2ZbfwZonesInboundNatStaticMappingsEntry 50331648}

sr1645v2ZbfwZonesInboundNatStaticMappingsPrivateAddress OBJECT-TYPE
   SYNTAX      IpAddress
   MAX-ACCESS  read-only
   STATUS      current
   DESCRIPTION
      "Path: zbFirewall.status.zones.inboundNat.staticMappings.privateAddress"
   ::= {sr1645v2ZbfwZonesInboundNatStaticMappingsEntry 67108864}

sr1645v2ZbfwZonesInboundNatStaticMappingsPrivatePort OBJECT-TYPE
   SYNTAX      INTEGER
               {
               discard (9),
               bgp (179),
               bootpmdhcpmc (68),
               bootpmdhcpms (67),
               cpudpencap (2746),
               domain (53),
               echo (7),
               ftp (21),
               ftpmdata (20),
               ftps (990),
               ftpsmdata (989),
               httpmalt (8080),
               https (443),
               imap (134),
               imap3 (220),
               imaps (993),
               ipsecmnatmt (4500),
               isakmp (500),
               l2tp (1701),
               ldap (389),
               microsoftmds (445),
               msmwbtmserver (3389),
               msnp (1863),
               nameserver (42),
               netbiosmdgm (138),
               netbiosmns (137),
               netbiosmssn (139),
               nntp (119),
               ntp (123),
               optional (0),
               pop3 (110),
               pop3s (995),
               pptp (1723),
               router (520),
               rtsp (554),
               sip (5060),
               smtp (25),
               smtps (465),
               snmp (161),
               snmptrap (162),
               socks (1080),
               ssdpmuPnP (1900),
               ssh (22),
               syslog (514),
               telindus (1728),
               telnet (23),
               telnets (992),
               tftp (69),
               whip (8700),
               wwwmhttp (80),
               z39d50 (210)
               }
   MAX-ACCESS  read-only
   STATUS      current
   DESCRIPTION
      "Path: zbFirewall.status.zones.inboundNat.staticMappings.privatePort

       Possibilities:
               discard   (9)
               bgp   (179)
               bootp-dhcp-c   (68)
               bootp-dhcp-s   (67)
               cpudpencap   (2746)
               domain   (53)
               echo   (7)
               ftp   (21)
               ftp-data   (20)
               ftps   (990)
               ftps-data   (989)
               http-alt   (8080)
               https   (443)
               imap   (134)
               imap3   (220)
               imaps   (993)
               ipsec-nat-t   (4500)
               isakmp   (500)
               l2tp   (1701)
               ldap   (389)
               microsoft-ds   (445)
               ms-wbt-server   (3389)
               msnp   (1863)
               nameserver   (42)
               netbios-dgm   (138)
               netbios-ns   (137)
               netbios-ssn   (139)
               nntp   (119)
               ntp   (123)
               optional   (0)
               pop3   (110)
               pop3s   (995)
               pptp   (1723)
               router   (520)
               rtsp   (554)
               sip   (5060)
               smtp   (25)
               smtps   (465)
               snmp   (161)
               snmptrap   (162)
               socks   (1080)
               ssdp-uPnP   (1900)
               ssh   (22)
               syslog   (514)
               telindus   (1728)
               telnet   (23)
               telnets   (992)
               tftp   (69)
               whip   (8700)
               www-http   (80)
               z39.50   (210)"
   ::= {sr1645v2ZbfwZonesInboundNatStaticMappingsEntry 83886080}


sr1645v2ZbfwZonePairs OBJECT IDENTIFIER ::= {sr1645v2Zbfw 22}

sr1645v2ZbfwZonePairsSSCTable OBJECT-TYPE
   SYNTAX      SEQUENCE OF Sr1645v2ZbfwZonePairsEntry
   MAX-ACCESS  not-accessible
   STATUS      current
   DESCRIPTION
      "runtime zone pair status table"
   ::= {sr1645v2ZbfwZonePairs 1}

sr1645v2ZbfwZonePairsEntry OBJECT-TYPE
   SYNTAX      Sr1645v2ZbfwZonePairsEntry
   MAX-ACCESS  not-accessible
   STATUS      current
   DESCRIPTION
      ""
   INDEX      { sr1645v2ZbfwZonePairsGlobalIx,
                sr1645v2ZbfwZonePairsTableIx }
   ::= {sr1645v2ZbfwZonePairsSSCTable 1}

Sr1645v2ZbfwZonePairsEntry ::=
   SEQUENCE
      {
      sr1645v2ZbfwZonePairsGlobalIx
         GlobalIndex,
      sr1645v2ZbfwZonePairsTableIx
         TableIndex,
      sr1645v2ZbfwZonePairsName
         DisplayString,
      sr1645v2ZbfwZonePairsSrcZone
         DisplayString,
      sr1645v2ZbfwZonePairsDstZone
         DisplayString,
      sr1645v2ZbfwZonePairsOutboundNat
         DisplayString,
      sr1645v2ZbfwZonePairsPolicy
         DisplayString,
      sr1645v2ZbfwZonePairsCountersProcessed
         Counter32,
      sr1645v2ZbfwZonePairsCountersApplied
         Counter32,
      sr1645v2ZbfwZonePairsCountersConnections
         Counter32,
      sr1645v2ZbfwZonePairsCountersPackets
         Counter32,
      sr1645v2ZbfwZonePairsCountersOctets
         Counter32,
      sr1645v2ZbfwZonePairsCountersReversePackets
         Counter32,
      sr1645v2ZbfwZonePairsCountersReverseOctets
         Counter32
      }

sr1645v2ZbfwZonePairsGlobalIx OBJECT-TYPE
   SYNTAX      GlobalIndex
   MAX-ACCESS  not-accessible
   STATUS      current
   DESCRIPTION
      "The value of the tlsCntTreeGlobalIndex of the MANAGED OBJECT."
   ::= {sr1645v2ZbfwZonePairsEntry 10}

sr1645v2ZbfwZonePairsTableIx OBJECT-TYPE
   SYNTAX      TableIndex
   MAX-ACCESS  not-accessible
   STATUS      current
   DESCRIPTION
      ""
   ::= {sr1645v2ZbfwZonePairsEntry 11}

sr1645v2ZbfwZonePairsName OBJECT-TYPE
   SYNTAX      DisplayString
   MAX-ACCESS  read-only
   STATUS      current
   DESCRIPTION
      "Path: zbFirewall.status.zonePairs.name"
   ::= {sr1645v2ZbfwZonePairsEntry 16777216}

sr1645v2ZbfwZonePairsSrcZone OBJECT-TYPE
   SYNTAX      DisplayString
   MAX-ACCESS  read-only
   STATUS      current
   DESCRIPTION
      "Path: zbFirewall.status.zonePairs.srcZone"
   ::= {sr1645v2ZbfwZonePairsEntry 33554432}

sr1645v2ZbfwZonePairsDstZone OBJECT-TYPE
   SYNTAX      DisplayString
   MAX-ACCESS  read-only
   STATUS      current
   DESCRIPTION
      "Path: zbFirewall.status.zonePairs.dstZone"
   ::= {sr1645v2ZbfwZonePairsEntry 50331648}

sr1645v2ZbfwZonePairsOutboundNat OBJECT-TYPE
   SYNTAX      DisplayString
   MAX-ACCESS  read-only
   STATUS      current
   DESCRIPTION
      "Path: zbFirewall.status.zonePairs.outboundNat"
   ::= {sr1645v2ZbfwZonePairsEntry 67108864}

sr1645v2ZbfwZonePairsPolicy OBJECT-TYPE
   SYNTAX      DisplayString
   MAX-ACCESS  read-only
   STATUS      current
   DESCRIPTION
      "Path: zbFirewall.status.zonePairs.policy"
   ::= {sr1645v2ZbfwZonePairsEntry 83886080}

sr1645v2ZbfwZonePairsCountersProcessed OBJECT-TYPE
   SYNTAX      Counter32
   MAX-ACCESS  read-only
   STATUS      current
   DESCRIPTION
      "Path: zbFirewall.status.zonePairs.counters.processed

       32 bit unsigned wrappable counter."
   ::= {sr1645v2ZbfwZonePairsEntry 100728832}

sr1645v2ZbfwZonePairsCountersApplied OBJECT-TYPE
   SYNTAX      Counter32
   MAX-ACCESS  read-only
   STATUS      current
   DESCRIPTION
      "Path: zbFirewall.status.zonePairs.counters.applied

       32 bit unsigned wrappable counter."
   ::= {sr1645v2ZbfwZonePairsEntry 100794368}

sr1645v2ZbfwZonePairsCountersConnections OBJECT-TYPE
   SYNTAX      Counter32
   MAX-ACCESS  read-only
   STATUS      current
   DESCRIPTION
      "Path: zbFirewall.status.zonePairs.counters.connections

       32 bit unsigned wrappable counter."
   ::= {sr1645v2ZbfwZonePairsEntry 100859904}

sr1645v2ZbfwZonePairsCountersPackets OBJECT-TYPE
   SYNTAX      Counter32
   MAX-ACCESS  read-only
   STATUS      current
   DESCRIPTION
      "Path: zbFirewall.status.zonePairs.counters.packets

       32 bit unsigned wrappable counter."
   ::= {sr1645v2ZbfwZonePairsEntry 100925440}

sr1645v2ZbfwZonePairsCountersOctets OBJECT-TYPE
   SYNTAX      Counter32
   MAX-ACCESS  read-only
   STATUS      current
   DESCRIPTION
      "Path: zbFirewall.status.zonePairs.counters.octets

       32 bit unsigned wrappable counter."
   ::= {sr1645v2ZbfwZonePairsEntry 100990976}

sr1645v2ZbfwZonePairsCountersReversePackets OBJECT-TYPE
   SYNTAX      Counter32
   MAX-ACCESS  read-only
   STATUS      current
   DESCRIPTION
      "Path: zbFirewall.status.zonePairs.counters.reversePackets

       32 bit unsigned wrappable counter."
   ::= {sr1645v2ZbfwZonePairsEntry 101056512}

sr1645v2ZbfwZonePairsCountersReverseOctets OBJECT-TYPE
   SYNTAX      Counter32
   MAX-ACCESS  read-only
   STATUS      current
   DESCRIPTION
      "Path: zbFirewall.status.zonePairs.counters.reverseOctets

       32 bit unsigned wrappable counter."
   ::= {sr1645v2ZbfwZonePairsEntry 101122048}


sr1645v2ZbfwInterfaces OBJECT IDENTIFIER ::= {sr1645v2Zbfw 25}

sr1645v2ZbfwInterfacesSSCTable OBJECT-TYPE
   SYNTAX      SEQUENCE OF Sr1645v2ZbfwInterfacesEntry
   MAX-ACCESS  not-accessible
   STATUS      current
   DESCRIPTION
      "monitored interface status"
   ::= {sr1645v2ZbfwInterfaces 1}

sr1645v2ZbfwInterfacesEntry OBJECT-TYPE
   SYNTAX      Sr1645v2ZbfwInterfacesEntry
   MAX-ACCESS  not-accessible
   STATUS      current
   DESCRIPTION
      ""
   INDEX      { sr1645v2ZbfwInterfacesGlobalIx,
                sr1645v2ZbfwInterfacesTableIx }
   ::= {sr1645v2ZbfwInterfacesSSCTable 1}

Sr1645v2ZbfwInterfacesEntry ::=
   SEQUENCE
      {
      sr1645v2ZbfwInterfacesGlobalIx
         GlobalIndex,
      sr1645v2ZbfwInterfacesTableIx
         TableIndex,
      sr1645v2ZbfwInterfacesName
         DisplayString,
      sr1645v2ZbfwInterfacesZone
         DisplayString
      }

sr1645v2ZbfwInterfacesGlobalIx OBJECT-TYPE
   SYNTAX      GlobalIndex
   MAX-ACCESS  not-accessible
   STATUS      current
   DESCRIPTION
      "The value of the tlsCntTreeGlobalIndex of the MANAGED OBJECT."
   ::= {sr1645v2ZbfwInterfacesEntry 10}

sr1645v2ZbfwInterfacesTableIx OBJECT-TYPE
   SYNTAX      TableIndex
   MAX-ACCESS  not-accessible
   STATUS      current
   DESCRIPTION
      ""
   ::= {sr1645v2ZbfwInterfacesEntry 11}

sr1645v2ZbfwInterfacesName OBJECT-TYPE
   SYNTAX      DisplayString
   MAX-ACCESS  read-only
   STATUS      current
   DESCRIPTION
      "Path: zbFirewall.status.interfaces.name"
   ::= {sr1645v2ZbfwInterfacesEntry 16777216}

sr1645v2ZbfwInterfacesZone OBJECT-TYPE
   SYNTAX      DisplayString
   MAX-ACCESS  read-only
   STATUS      current
   DESCRIPTION
      "Path: zbFirewall.status.interfaces.zone"
   ::= {sr1645v2ZbfwInterfacesEntry 33554432}


sr1645v2ZbfwFlows OBJECT IDENTIFIER ::= {sr1645v2Zbfw 23}

sr1645v2ZbfwFlowsSSCTable OBJECT-TYPE
   SYNTAX      SEQUENCE OF Sr1645v2ZbfwFlowsEntry
   MAX-ACCESS  not-accessible
   STATUS      current
   DESCRIPTION
      "open flow status"
   ::= {sr1645v2ZbfwFlows 1}

sr1645v2ZbfwFlowsEntry OBJECT-TYPE
   SYNTAX      Sr1645v2ZbfwFlowsEntry
   MAX-ACCESS  not-accessible
   STATUS      current
   DESCRIPTION
      ""
   INDEX      { sr1645v2ZbfwFlowsGlobalIx,
                sr1645v2ZbfwFlowsTableIx }
   ::= {sr1645v2ZbfwFlowsSSCTable 1}

Sr1645v2ZbfwFlowsEntry ::=
   SEQUENCE
      {
      sr1645v2ZbfwFlowsGlobalIx
         GlobalIndex,
      sr1645v2ZbfwFlowsTableIx
         TableIndex,
      sr1645v2ZbfwFlowsDir
         INTEGER,
      sr1645v2ZbfwFlowsConnId
         Counter32,
      sr1645v2ZbfwFlowsSrcIntf
         DisplayString,
      sr1645v2ZbfwFlowsSrcZone
         DisplayString,
      sr1645v2ZbfwFlowsDstIntf
         DisplayString,
      sr1645v2ZbfwFlowsDstZone
         DisplayString,
      sr1645v2ZbfwFlowsSrcAddress
         IpAddress,
      sr1645v2ZbfwFlowsDstAddress
         IpAddress,
      sr1645v2ZbfwFlowsNatMode
         INTEGER,
      sr1645v2ZbfwFlowsProt
         INTEGER,
      sr1645v2ZbfwFlowsSrcPort
         INTEGER,
      sr1645v2ZbfwFlowsDstPort
         INTEGER,
      sr1645v2ZbfwFlowsAge
         TimeTicks,
      sr1645v2ZbfwFlowsTimeOut
         TimeTicks,
      sr1645v2ZbfwFlowsInboundNatMode
         INTEGER,
      sr1645v2ZbfwFlowsInboundNatPrivateAddr
         IpAddress,
      sr1645v2ZbfwFlowsInboundNatPrivatePort
         Integer32,
      sr1645v2ZbfwFlowsInboundNatPublicAddr
         IpAddress,
      sr1645v2ZbfwFlowsInboundNatPublicPort
         Integer32,
      sr1645v2ZbfwFlowsOutboundNatMode
         INTEGER,
      sr1645v2ZbfwFlowsOutboundNatPrivateAddr
         IpAddress,
      sr1645v2ZbfwFlowsOutboundNatPrivatePort
         Integer32,
      sr1645v2ZbfwFlowsOutboundNatPublicAddr
         IpAddress,
      sr1645v2ZbfwFlowsOutboundNatPublicPort
         Integer32,
      sr1645v2ZbfwFlowsProtInfoTcpState
         INTEGER,
      sr1645v2ZbfwFlowsProtInfoTcpSeqNr
         Counter32,
      sr1645v2ZbfwFlowsProtInfoTcpAckedNr
         Counter32,
      sr1645v2ZbfwFlowsRulesZonePair
         DisplayString,
      sr1645v2ZbfwFlowsRulesPolicy
         DisplayString,
      sr1645v2ZbfwFlowsRulesPolicyRule
         DisplayString,
      sr1645v2ZbfwFlowsRulesFilter
         DisplayString,
      sr1645v2ZbfwFlowsRulesFilterRule
         DisplayString,
      sr1645v2ZbfwFlowsModeReverse
         INTEGER,
      sr1645v2ZbfwFlowsModeAlg
         INTEGER
      }

sr1645v2ZbfwFlowsGlobalIx OBJECT-TYPE
   SYNTAX      GlobalIndex
   MAX-ACCESS  not-accessible
   STATUS      current
   DESCRIPTION
      "The value of the tlsCntTreeGlobalIndex of the MANAGED OBJECT."
   ::= {sr1645v2ZbfwFlowsEntry 10}

sr1645v2ZbfwFlowsTableIx OBJECT-TYPE
   SYNTAX      TableIndex
   MAX-ACCESS  not-accessible
   STATUS      current
   DESCRIPTION
      ""
   ::= {sr1645v2ZbfwFlowsEntry 11}

sr1645v2ZbfwFlowsDir OBJECT-TYPE
   SYNTAX      INTEGER
               {
               sg (0),
               sl (1)
               }
   MAX-ACCESS  read-only
   STATUS      current
   DESCRIPTION
      "Path: zbFirewall.status.flows.dir

       Possibilities:
               >   (0)
               <   (1)"
   ::= {sr1645v2ZbfwFlowsEntry 838860800}

sr1645v2ZbfwFlowsConnId OBJECT-TYPE
   SYNTAX      Counter32
   MAX-ACCESS  read-only
   STATUS      current
   DESCRIPTION
      "Path: zbFirewall.status.flows.connId

       32 bit unsigned wrappable counter."
   ::= {sr1645v2ZbfwFlowsEntry 285212672}

sr1645v2ZbfwFlowsSrcIntf OBJECT-TYPE
   SYNTAX      DisplayString
   MAX-ACCESS  read-only
   STATUS      current
   DESCRIPTION
      "Path: zbFirewall.status.flows.srcIntf"
   ::= {sr1645v2ZbfwFlowsEntry 16777216}

sr1645v2ZbfwFlowsSrcZone OBJECT-TYPE
   SYNTAX      DisplayString
   MAX-ACCESS  read-only
   STATUS      current
   DESCRIPTION
      "Path: zbFirewall.status.flows.srcZone"
   ::= {sr1645v2ZbfwFlowsEntry 33554432}

sr1645v2ZbfwFlowsDstIntf OBJECT-TYPE
   SYNTAX      DisplayString
   MAX-ACCESS  read-only
   STATUS      current
   DESCRIPTION
      "Path: zbFirewall.status.flows.dstIntf"
   ::= {sr1645v2ZbfwFlowsEntry 50331648}

sr1645v2ZbfwFlowsDstZone OBJECT-TYPE
   SYNTAX      DisplayString
   MAX-ACCESS  read-only
   STATUS      current
   DESCRIPTION
      "Path: zbFirewall.status.flows.dstZone"
   ::= {sr1645v2ZbfwFlowsEntry 67108864}

sr1645v2ZbfwFlowsSrcAddress OBJECT-TYPE
   SYNTAX      IpAddress
   MAX-ACCESS  read-only
   STATUS      current
   DESCRIPTION
      "Path: zbFirewall.status.flows.srcAddress"
   ::= {sr1645v2ZbfwFlowsEntry 83886080}

sr1645v2ZbfwFlowsDstAddress OBJECT-TYPE
   SYNTAX      IpAddress
   MAX-ACCESS  read-only
   STATUS      current
   DESCRIPTION
      "Path: zbFirewall.status.flows.dstAddress"
   ::= {sr1645v2ZbfwFlowsEntry 100663296}

sr1645v2ZbfwFlowsNatMode OBJECT-TYPE
   SYNTAX      INTEGER
               {
               none (0),
               inbound (1),
               outbound (2),
               bidirectional (3)
               }
   MAX-ACCESS  read-only
   STATUS      current
   DESCRIPTION
      "Path: zbFirewall.status.flows.natMode

       Possibilities:
               none   (0)
               inbound   (1)
               outbound   (2)
               bidirectional   (3)"
   ::= {sr1645v2ZbfwFlowsEntry 855638016}

sr1645v2ZbfwFlowsProt OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6),
               icmpV6 (58),
               l2tp (115)
               }
   MAX-ACCESS  read-only
   STATUS      current
   DESCRIPTION
      "Path: zbFirewall.status.flows.prot

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)
               icmpV6   (58)
               l2tp   (115)"
   ::= {sr1645v2ZbfwFlowsEntry 117440512}

sr1645v2ZbfwFlowsSrcPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.status.flows.srcPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1645v2ZbfwFlowsEntry 134217728}

sr1645v2ZbfwFlowsDstPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.status.flows.dstPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1645v2ZbfwFlowsEntry 150994944}

sr1645v2ZbfwFlowsAge OBJECT-TYPE
   SYNTAX      TimeTicks
   MAX-ACCESS  read-only
   STATUS      current
   DESCRIPTION
      "Path: zbFirewall.status.flows.age

       Time in centi-second."
   ::= {sr1645v2ZbfwFlowsEntry 167772160}

sr1645v2ZbfwFlowsTimeOut OBJECT-TYPE
   SYNTAX      TimeTicks
   MAX-ACCESS  read-only
   STATUS      current
   DESCRIPTION
      "Path: zbFirewall.status.flows.timeOut

       Time in centi-second."
   ::= {sr1645v2ZbfwFlowsEntry 184549376}

sr1645v2ZbfwFlowsInboundNatMode OBJECT-TYPE
   SYNTAX      INTEGER
               {
               none (0),
               bypass (1),
               nat (2)
               }
   MAX-ACCESS  read-only
   STATUS      current
   DESCRIPTION
      "Path: zbFirewall.status.flows.inboundNat.mode

       Possibilities:
               none   (0)
               bypass   (1)
               nat   (2)"
   ::= {sr1645v2ZbfwFlowsEntry 201392128}

sr1645v2ZbfwFlowsInboundNatPrivateAddr OBJECT-TYPE
   SYNTAX      IpAddress
   MAX-ACCESS  read-only
   STATUS      current
   DESCRIPTION
      "Path: zbFirewall.status.flows.inboundNat.privateAddr"
   ::= {sr1645v2ZbfwFlowsEntry 201457664}

sr1645v2ZbfwFlowsInboundNatPrivatePort OBJECT-TYPE
   SYNTAX      Integer32
   MAX-ACCESS  read-only
   STATUS      current
   DESCRIPTION
      "Path: zbFirewall.status.flows.inboundNat.privatePort"
   ::= {sr1645v2ZbfwFlowsEntry 201523200}

sr1645v2ZbfwFlowsInboundNatPublicAddr OBJECT-TYPE
   SYNTAX      IpAddress
   MAX-ACCESS  read-only
   STATUS      current
   DESCRIPTION
      "Path: zbFirewall.status.flows.inboundNat.publicAddr"
   ::= {sr1645v2ZbfwFlowsEntry 201588736}

sr1645v2ZbfwFlowsInboundNatPublicPort OBJECT-TYPE
   SYNTAX      Integer32
   MAX-ACCESS  read-only
   STATUS      current
   DESCRIPTION
      "Path: zbFirewall.status.flows.inboundNat.publicPort"
   ::= {sr1645v2ZbfwFlowsEntry 201654272}

sr1645v2ZbfwFlowsOutboundNatMode OBJECT-TYPE
   SYNTAX      INTEGER
               {
               none (0),
               bypass (1),
               nat (2)
               }
   MAX-ACCESS  read-only
   STATUS      current
   DESCRIPTION
      "Path: zbFirewall.status.flows.outboundNat.mode

       Possibilities:
               none   (0)
               bypass   (1)
               nat   (2)"
   ::= {sr1645v2ZbfwFlowsEntry 218169344}

sr1645v2ZbfwFlowsOutboundNatPrivateAddr OBJECT-TYPE
   SYNTAX      IpAddress
   MAX-ACCESS  read-only
   STATUS      current
   DESCRIPTION
      "Path: zbFirewall.status.flows.outboundNat.privateAddr"
   ::= {sr1645v2ZbfwFlowsEntry 218234880}

sr1645v2ZbfwFlowsOutboundNatPrivatePort OBJECT-TYPE
   SYNTAX      Integer32
   MAX-ACCESS  read-only
   STATUS      current
   DESCRIPTION
      "Path: zbFirewall.status.flows.outboundNat.privatePort"
   ::= {sr1645v2ZbfwFlowsEntry 218300416}

sr1645v2ZbfwFlowsOutboundNatPublicAddr OBJECT-TYPE
   SYNTAX      IpAddress
   MAX-ACCESS  read-only
   STATUS      current
   DESCRIPTION
      "Path: zbFirewall.status.flows.outboundNat.publicAddr"
   ::= {sr1645v2ZbfwFlowsEntry 218365952}

sr1645v2ZbfwFlowsOutboundNatPublicPort OBJECT-TYPE
   SYNTAX      Integer32
   MAX-ACCESS  read-only
   STATUS      current
   DESCRIPTION
      "Path: zbFirewall.status.flows.outboundNat.publicPort"
   ::= {sr1645v2ZbfwFlowsEntry 218431488}

sr1645v2ZbfwFlowsProtInfoTcpState OBJECT-TYPE
   SYNTAX      INTEGER
               {
               idle (0),
               listen (1),
               synSent (2),
               synAcked (3),
               established (4),
               finSent (5),
               finAcked (6),
               closed (7),
               reset (8)
               }
   MAX-ACCESS  read-only
   STATUS      current
   DESCRIPTION
      "Path: zbFirewall.status.flows.protInfo.tcp.state

       Possibilities:
               idle   (0)
               listen   (1)
               synSent   (2)
               synAcked   (3)
               established   (4)
               finSent   (5)
               finAcked   (6)
               closed   (7)
               reset   (8)"
   ::= {sr1645v2ZbfwFlowsEntry 234946816}

sr1645v2ZbfwFlowsProtInfoTcpSeqNr OBJECT-TYPE
   SYNTAX      Counter32
   MAX-ACCESS  read-only
   STATUS      current
   DESCRIPTION
      "Path: zbFirewall.status.flows.protInfo.tcp.seqNr

       32 bit unsigned wrappable counter."
   ::= {sr1645v2ZbfwFlowsEntry 234947072}

sr1645v2ZbfwFlowsProtInfoTcpAckedNr OBJECT-TYPE
   SYNTAX      Counter32
   MAX-ACCESS  read-only
   STATUS      current
   DESCRIPTION
      "Path: zbFirewall.status.flows.protInfo.tcp.ackedNr

       32 bit unsigned wrappable counter."
   ::= {sr1645v2ZbfwFlowsEntry 234947328}

sr1645v2ZbfwFlowsRulesZonePair OBJECT-TYPE
   SYNTAX      DisplayString
   MAX-ACCESS  read-only
   STATUS      current
   DESCRIPTION
      "Path: zbFirewall.status.flows.rules.zonePair"
   ::= {sr1645v2ZbfwFlowsEntry 251723776}

sr1645v2ZbfwFlowsRulesPolicy OBJECT-TYPE
   SYNTAX      DisplayString
   MAX-ACCESS  read-only
   STATUS      current
   DESCRIPTION
      "Path: zbFirewall.status.flows.rules.policy"
   ::= {sr1645v2ZbfwFlowsEntry 251789312}

sr1645v2ZbfwFlowsRulesPolicyRule OBJECT-TYPE
   SYNTAX      DisplayString
   MAX-ACCESS  read-only
   STATUS      current
   DESCRIPTION
      "Path: zbFirewall.status.flows.rules.policyRule"
   ::= {sr1645v2ZbfwFlowsEntry 251854848}

sr1645v2ZbfwFlowsRulesFilter OBJECT-TYPE
   SYNTAX      DisplayString
   MAX-ACCESS  read-only
   STATUS      current
   DESCRIPTION
      "Path: zbFirewall.status.flows.rules.filter"
   ::= {sr1645v2ZbfwFlowsEntry 251920384}

sr1645v2ZbfwFlowsRulesFilterRule OBJECT-TYPE
   SYNTAX      DisplayString
   MAX-ACCESS  read-only
   STATUS      current
   DESCRIPTION
      "Path: zbFirewall.status.flows.rules.filterRule"
   ::= {sr1645v2ZbfwFlowsEntry 251985920}

sr1645v2ZbfwFlowsModeReverse OBJECT-TYPE
   SYNTAX      INTEGER
               {
               false (0),
               true (1)
               }
   MAX-ACCESS  read-only
   STATUS      current
   DESCRIPTION
      "Path: zbFirewall.status.flows.mode.reverse

       Possibilities:
               false   (0)
               true   (1)"
   ::= {sr1645v2ZbfwFlowsEntry 268500992}

sr1645v2ZbfwFlowsModeAlg OBJECT-TYPE
   SYNTAX      INTEGER
               {
               false (0),
               true (1)
               }
   MAX-ACCESS  read-only
   STATUS      current
   DESCRIPTION
      "Path: zbFirewall.status.flows.mode.alg

       Possibilities:
               false   (0)
               true   (1)"
   ::= {sr1645v2ZbfwFlowsEntry 268566528}


sr1645v2ZbfwDropFlows OBJECT IDENTIFIER ::= {sr1645v2Zbfw 35}

sr1645v2ZbfwDropFlowsSSCTable OBJECT-TYPE
   SYNTAX      SEQUENCE OF Sr1645v2ZbfwDropFlowsEntry
   MAX-ACCESS  not-accessible
   STATUS      current
   DESCRIPTION
      "open flow status"
   ::= {sr1645v2ZbfwDropFlows 1}

sr1645v2ZbfwDropFlowsEntry OBJECT-TYPE
   SYNTAX      Sr1645v2ZbfwDropFlowsEntry
   MAX-ACCESS  not-accessible
   STATUS      current
   DESCRIPTION
      ""
   INDEX      { sr1645v2ZbfwDropFlowsGlobalIx,
                sr1645v2ZbfwDropFlowsTableIx }
   ::= {sr1645v2ZbfwDropFlowsSSCTable 1}

Sr1645v2ZbfwDropFlowsEntry ::=
   SEQUENCE
      {
      sr1645v2ZbfwDropFlowsGlobalIx
         GlobalIndex,
      sr1645v2ZbfwDropFlowsTableIx
         TableIndex,
      sr1645v2ZbfwDropFlowsDir
         INTEGER,
      sr1645v2ZbfwDropFlowsConnId
         Counter32,
      sr1645v2ZbfwDropFlowsSrcIntf
         DisplayString,
      sr1645v2ZbfwDropFlowsSrcZone
         DisplayString,
      sr1645v2ZbfwDropFlowsDstIntf
         DisplayString,
      sr1645v2ZbfwDropFlowsDstZone
         DisplayString,
      sr1645v2ZbfwDropFlowsSrcAddress
         IpAddress,
      sr1645v2ZbfwDropFlowsDstAddress
         IpAddress,
      sr1645v2ZbfwDropFlowsNatMode
         INTEGER,
      sr1645v2ZbfwDropFlowsProt
         INTEGER,
      sr1645v2ZbfwDropFlowsSrcPort
         INTEGER,
      sr1645v2ZbfwDropFlowsDstPort
         INTEGER,
      sr1645v2ZbfwDropFlowsAge
         TimeTicks,
      sr1645v2ZbfwDropFlowsTimeOut
         TimeTicks,
      sr1645v2ZbfwDropFlowsInboundNatMode
         INTEGER,
      sr1645v2ZbfwDropFlowsInboundNatPrivateAddr
         IpAddress,
      sr1645v2ZbfwDropFlowsInboundNatPrivatePort
         Integer32,
      sr1645v2ZbfwDropFlowsInboundNatPublicAddr
         IpAddress,
      sr1645v2ZbfwDropFlowsInboundNatPublicPort
         Integer32,
      sr1645v2ZbfwDropFlowsOutboundNatMode
         INTEGER,
      sr1645v2ZbfwDropFlowsOutboundNatPrivateAddr
         IpAddress,
      sr1645v2ZbfwDropFlowsOutboundNatPrivatePort
         Integer32,
      sr1645v2ZbfwDropFlowsOutboundNatPublicAddr
         IpAddress,
      sr1645v2ZbfwDropFlowsOutboundNatPublicPort
         Integer32,
      sr1645v2ZbfwDropFlowsProtInfoTcpState
         INTEGER,
      sr1645v2ZbfwDropFlowsProtInfoTcpSeqNr
         Counter32,
      sr1645v2ZbfwDropFlowsProtInfoTcpAckedNr
         Counter32,
      sr1645v2ZbfwDropFlowsRulesZonePair
         DisplayString,
      sr1645v2ZbfwDropFlowsRulesPolicy
         DisplayString,
      sr1645v2ZbfwDropFlowsRulesPolicyRule
         DisplayString,
      sr1645v2ZbfwDropFlowsRulesFilter
         DisplayString,
      sr1645v2ZbfwDropFlowsRulesFilterRule
         DisplayString,
      sr1645v2ZbfwDropFlowsModeReverse
         INTEGER,
      sr1645v2ZbfwDropFlowsModeAlg
         INTEGER
      }

sr1645v2ZbfwDropFlowsGlobalIx OBJECT-TYPE
   SYNTAX      GlobalIndex
   MAX-ACCESS  not-accessible
   STATUS      current
   DESCRIPTION
      "The value of the tlsCntTreeGlobalIndex of the MANAGED OBJECT."
   ::= {sr1645v2ZbfwDropFlowsEntry 10}

sr1645v2ZbfwDropFlowsTableIx OBJECT-TYPE
   SYNTAX      TableIndex
   MAX-ACCESS  not-accessible
   STATUS      current
   DESCRIPTION
      ""
   ::= {sr1645v2ZbfwDropFlowsEntry 11}

sr1645v2ZbfwDropFlowsDir OBJECT-TYPE
   SYNTAX      INTEGER
               {
               sg (0),
               sl (1)
               }
   MAX-ACCESS  read-only
   STATUS      current
   DESCRIPTION
      "Path: zbFirewall.status.dropFlows.dir

       Possibilities:
               >   (0)
               <   (1)"
   ::= {sr1645v2ZbfwDropFlowsEntry 838860800}

sr1645v2ZbfwDropFlowsConnId OBJECT-TYPE
   SYNTAX      Counter32
   MAX-ACCESS  read-only
   STATUS      current
   DESCRIPTION
      "Path: zbFirewall.status.dropFlows.connId

       32 bit unsigned wrappable counter."
   ::= {sr1645v2ZbfwDropFlowsEntry 285212672}

sr1645v2ZbfwDropFlowsSrcIntf OBJECT-TYPE
   SYNTAX      DisplayString
   MAX-ACCESS  read-only
   STATUS      current
   DESCRIPTION
      "Path: zbFirewall.status.dropFlows.srcIntf"
   ::= {sr1645v2ZbfwDropFlowsEntry 16777216}

sr1645v2ZbfwDropFlowsSrcZone OBJECT-TYPE
   SYNTAX      DisplayString
   MAX-ACCESS  read-only
   STATUS      current
   DESCRIPTION
      "Path: zbFirewall.status.dropFlows.srcZone"
   ::= {sr1645v2ZbfwDropFlowsEntry 33554432}

sr1645v2ZbfwDropFlowsDstIntf OBJECT-TYPE
   SYNTAX      DisplayString
   MAX-ACCESS  read-only
   STATUS      current
   DESCRIPTION
      "Path: zbFirewall.status.dropFlows.dstIntf"
   ::= {sr1645v2ZbfwDropFlowsEntry 50331648}

sr1645v2ZbfwDropFlowsDstZone OBJECT-TYPE
   SYNTAX      DisplayString
   MAX-ACCESS  read-only
   STATUS      current
   DESCRIPTION
      "Path: zbFirewall.status.dropFlows.dstZone"
   ::= {sr1645v2ZbfwDropFlowsEntry 67108864}

sr1645v2ZbfwDropFlowsSrcAddress OBJECT-TYPE
   SYNTAX      IpAddress
   MAX-ACCESS  read-only
   STATUS      current
   DESCRIPTION
      "Path: zbFirewall.status.dropFlows.srcAddress"
   ::= {sr1645v2ZbfwDropFlowsEntry 83886080}

sr1645v2ZbfwDropFlowsDstAddress OBJECT-TYPE
   SYNTAX      IpAddress
   MAX-ACCESS  read-only
   STATUS      current
   DESCRIPTION
      "Path: zbFirewall.status.dropFlows.dstAddress"
   ::= {sr1645v2ZbfwDropFlowsEntry 100663296}

sr1645v2ZbfwDropFlowsNatMode OBJECT-TYPE
   SYNTAX      INTEGER
               {
               none (0),
               inbound (1),
               outbound (2),
               bidirectional (3)
               }
   MAX-ACCESS  read-only
   STATUS      current
   DESCRIPTION
      "Path: zbFirewall.status.dropFlows.natMode

       Possibilities:
               none   (0)
               inbound   (1)
               outbound   (2)
               bidirectional   (3)"
   ::= {sr1645v2ZbfwDropFlowsEntry 855638016}

sr1645v2ZbfwDropFlowsProt OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6),
               icmpV6 (58),
               l2tp (115)
               }
   MAX-ACCESS  read-only
   STATUS      current
   DESCRIPTION
      "Path: zbFirewall.status.dropFlows.prot

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)
               icmpV6   (58)
               l2tp   (115)"
   ::= {sr1645v2ZbfwDropFlowsEntry 117440512}

sr1645v2ZbfwDropFlowsSrcPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.status.dropFlows.srcPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1645v2ZbfwDropFlowsEntry 134217728}

sr1645v2ZbfwDropFlowsDstPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.status.dropFlows.dstPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1645v2ZbfwDropFlowsEntry 150994944}

sr1645v2ZbfwDropFlowsAge OBJECT-TYPE
   SYNTAX      TimeTicks
   MAX-ACCESS  read-only
   STATUS      current
   DESCRIPTION
      "Path: zbFirewall.status.dropFlows.age

       Time in centi-second."
   ::= {sr1645v2ZbfwDropFlowsEntry 167772160}

sr1645v2ZbfwDropFlowsTimeOut OBJECT-TYPE
   SYNTAX      TimeTicks
   MAX-ACCESS  read-only
   STATUS      current
   DESCRIPTION
      "Path: zbFirewall.status.dropFlows.timeOut

       Time in centi-second."
   ::= {sr1645v2ZbfwDropFlowsEntry 184549376}

sr1645v2ZbfwDropFlowsInboundNatMode OBJECT-TYPE
   SYNTAX      INTEGER
               {
               none (0),
               bypass (1),
               nat (2)
               }
   MAX-ACCESS  read-only
   STATUS      current
   DESCRIPTION
      "Path: zbFirewall.status.dropFlows.inboundNat.mode

       Possibilities:
               none   (0)
               bypass   (1)
               nat   (2)"
   ::= {sr1645v2ZbfwDropFlowsEntry 201392128}

sr1645v2ZbfwDropFlowsInboundNatPrivateAddr OBJECT-TYPE
   SYNTAX      IpAddress
   MAX-ACCESS  read-only
   STATUS      current
   DESCRIPTION
      "Path: zbFirewall.status.dropFlows.inboundNat.privateAddr"
   ::= {sr1645v2ZbfwDropFlowsEntry 201457664}

sr1645v2ZbfwDropFlowsInboundNatPrivatePort OBJECT-TYPE
   SYNTAX      Integer32
   MAX-ACCESS  read-only
   STATUS      current
   DESCRIPTION
      "Path: zbFirewall.status.dropFlows.inboundNat.privatePort"
   ::= {sr1645v2ZbfwDropFlowsEntry 201523200}

sr1645v2ZbfwDropFlowsInboundNatPublicAddr OBJECT-TYPE
   SYNTAX      IpAddress
   MAX-ACCESS  read-only
   STATUS      current
   DESCRIPTION
      "Path: zbFirewall.status.dropFlows.inboundNat.publicAddr"
   ::= {sr1645v2ZbfwDropFlowsEntry 201588736}

sr1645v2ZbfwDropFlowsInboundNatPublicPort OBJECT-TYPE
   SYNTAX      Integer32
   MAX-ACCESS  read-only
   STATUS      current
   DESCRIPTION
      "Path: zbFirewall.status.dropFlows.inboundNat.publicPort"
   ::= {sr1645v2ZbfwDropFlowsEntry 201654272}

sr1645v2ZbfwDropFlowsOutboundNatMode OBJECT-TYPE
   SYNTAX      INTEGER
               {
               none (0),
               bypass (1),
               nat (2)
               }
   MAX-ACCESS  read-only
   STATUS      current
   DESCRIPTION
      "Path: zbFirewall.status.dropFlows.outboundNat.mode

       Possibilities:
               none   (0)
               bypass   (1)
               nat   (2)"
   ::= {sr1645v2ZbfwDropFlowsEntry 218169344}

sr1645v2ZbfwDropFlowsOutboundNatPrivateAddr OBJECT-TYPE
   SYNTAX      IpAddress
   MAX-ACCESS  read-only
   STATUS      current
   DESCRIPTION
      "Path: zbFirewall.status.dropFlows.outboundNat.privateAddr"
   ::= {sr1645v2ZbfwDropFlowsEntry 218234880}

sr1645v2ZbfwDropFlowsOutboundNatPrivatePort OBJECT-TYPE
   SYNTAX      Integer32
   MAX-ACCESS  read-only
   STATUS      current
   DESCRIPTION
      "Path: zbFirewall.status.dropFlows.outboundNat.privatePort"
   ::= {sr1645v2ZbfwDropFlowsEntry 218300416}

sr1645v2ZbfwDropFlowsOutboundNatPublicAddr OBJECT-TYPE
   SYNTAX      IpAddress
   MAX-ACCESS  read-only
   STATUS      current
   DESCRIPTION
      "Path: zbFirewall.status.dropFlows.outboundNat.publicAddr"
   ::= {sr1645v2ZbfwDropFlowsEntry 218365952}

sr1645v2ZbfwDropFlowsOutboundNatPublicPort OBJECT-TYPE
   SYNTAX      Integer32
   MAX-ACCESS  read-only
   STATUS      current
   DESCRIPTION
      "Path: zbFirewall.status.dropFlows.outboundNat.publicPort"
   ::= {sr1645v2ZbfwDropFlowsEntry 218431488}

sr1645v2ZbfwDropFlowsProtInfoTcpState OBJECT-TYPE
   SYNTAX      INTEGER
               {
               idle (0),
               listen (1),
               synSent (2),
               synAcked (3),
               established (4),
               finSent (5),
               finAcked (6),
               closed (7),
               reset (8)
               }
   MAX-ACCESS  read-only
   STATUS      current
   DESCRIPTION
      "Path: zbFirewall.status.dropFlows.protInfo.tcp.state

       Possibilities:
               idle   (0)
               listen   (1)
               synSent   (2)
               synAcked   (3)
               established   (4)
               finSent   (5)
               finAcked   (6)
               closed   (7)
               reset   (8)"
   ::= {sr1645v2ZbfwDropFlowsEntry 234946816}

sr1645v2ZbfwDropFlowsProtInfoTcpSeqNr OBJECT-TYPE
   SYNTAX      Counter32
   MAX-ACCESS  read-only
   STATUS      current
   DESCRIPTION
      "Path: zbFirewall.status.dropFlows.protInfo.tcp.seqNr

       32 bit unsigned wrappable counter."
   ::= {sr1645v2ZbfwDropFlowsEntry 234947072}

sr1645v2ZbfwDropFlowsProtInfoTcpAckedNr OBJECT-TYPE
   SYNTAX      Counter32
   MAX-ACCESS  read-only
   STATUS      current
   DESCRIPTION
      "Path: zbFirewall.status.dropFlows.protInfo.tcp.ackedNr

       32 bit unsigned wrappable counter."
   ::= {sr1645v2ZbfwDropFlowsEntry 234947328}

sr1645v2ZbfwDropFlowsRulesZonePair OBJECT-TYPE
   SYNTAX      DisplayString
   MAX-ACCESS  read-only
   STATUS      current
   DESCRIPTION
      "Path: zbFirewall.status.dropFlows.rules.zonePair"
   ::= {sr1645v2ZbfwDropFlowsEntry 251723776}

sr1645v2ZbfwDropFlowsRulesPolicy OBJECT-TYPE
   SYNTAX      DisplayString
   MAX-ACCESS  read-only
   STATUS      current
   DESCRIPTION
      "Path: zbFirewall.status.dropFlows.rules.policy"
   ::= {sr1645v2ZbfwDropFlowsEntry 251789312}

sr1645v2ZbfwDropFlowsRulesPolicyRule OBJECT-TYPE
   SYNTAX      DisplayString
   MAX-ACCESS  read-only
   STATUS      current
   DESCRIPTION
      "Path: zbFirewall.status.dropFlows.rules.policyRule"
   ::= {sr1645v2ZbfwDropFlowsEntry 251854848}

sr1645v2ZbfwDropFlowsRulesFilter OBJECT-TYPE
   SYNTAX      DisplayString
   MAX-ACCESS  read-only
   STATUS      current
   DESCRIPTION
      "Path: zbFirewall.status.dropFlows.rules.filter"
   ::= {sr1645v2ZbfwDropFlowsEntry 251920384}

sr1645v2ZbfwDropFlowsRulesFilterRule OBJECT-TYPE
   SYNTAX      DisplayString
   MAX-ACCESS  read-only
   STATUS      current
   DESCRIPTION
      "Path: zbFirewall.status.dropFlows.rules.filterRule"
   ::= {sr1645v2ZbfwDropFlowsEntry 251985920}

sr1645v2ZbfwDropFlowsModeReverse OBJECT-TYPE
   SYNTAX      INTEGER
               {
               false (0),
               true (1)
               }
   MAX-ACCESS  read-only
   STATUS      current
   DESCRIPTION
      "Path: zbFirewall.status.dropFlows.mode.reverse

       Possibilities:
               false   (0)
               true   (1)"
   ::= {sr1645v2ZbfwDropFlowsEntry 268500992}

sr1645v2ZbfwDropFlowsModeAlg OBJECT-TYPE
   SYNTAX      INTEGER
               {
               false (0),
               true (1)
               }
   MAX-ACCESS  read-only
   STATUS      current
   DESCRIPTION
      "Path: zbFirewall.status.dropFlows.mode.alg

       Possibilities:
               false   (0)
               true   (1)"
   ::= {sr1645v2ZbfwDropFlowsEntry 268566528}


sr1645v2ZbfwFtpFlows OBJECT IDENTIFIER ::= {sr1645v2Zbfw 27}

sr1645v2ZbfwFtpFlowsSSCTable OBJECT-TYPE
   SYNTAX      SEQUENCE OF Sr1645v2ZbfwFtpFlowsEntry
   MAX-ACCESS  not-accessible
   STATUS      current
   DESCRIPTION
      "ftp flow status"
   ::= {sr1645v2ZbfwFtpFlows 1}

sr1645v2ZbfwFtpFlowsEntry OBJECT-TYPE
   SYNTAX      Sr1645v2ZbfwFtpFlowsEntry
   MAX-ACCESS  not-accessible
   STATUS      current
   DESCRIPTION
      ""
   INDEX      { sr1645v2ZbfwFtpFlowsGlobalIx,
                sr1645v2ZbfwFtpFlowsTableIx }
   ::= {sr1645v2ZbfwFtpFlowsSSCTable 1}

Sr1645v2ZbfwFtpFlowsEntry ::=
   SEQUENCE
      {
      sr1645v2ZbfwFtpFlowsGlobalIx
         GlobalIndex,
      sr1645v2ZbfwFtpFlowsTableIx
         TableIndex,
      sr1645v2ZbfwFtpFlowsSrcIntf
         DisplayString,
      sr1645v2ZbfwFtpFlowsDstIntf
         DisplayString,
      sr1645v2ZbfwFtpFlowsSrcAddress
         IpAddress,
      sr1645v2ZbfwFtpFlowsDstAddress
         IpAddress,
      sr1645v2ZbfwFtpFlowsSrcPort
         Integer32,
      sr1645v2ZbfwFtpFlowsDstPort
         Integer32,
      sr1645v2ZbfwFtpFlowsTcpState
         INTEGER,
      sr1645v2ZbfwFtpFlowsTcpSeqNr
         Counter32,
      sr1645v2ZbfwFtpFlowsTcpAckedNr
         Counter32,
      sr1645v2ZbfwFtpFlowsFtpState
         INTEGER,
      sr1645v2ZbfwFtpFlowsFtpDataPort
         Integer32
      }

sr1645v2ZbfwFtpFlowsGlobalIx OBJECT-TYPE
   SYNTAX      GlobalIndex
   MAX-ACCESS  not-accessible
   STATUS      current
   DESCRIPTION
      "The value of the tlsCntTreeGlobalIndex of the MANAGED OBJECT."
   ::= {sr1645v2ZbfwFtpFlowsEntry 10}

sr1645v2ZbfwFtpFlowsTableIx OBJECT-TYPE
   SYNTAX      TableIndex
   MAX-ACCESS  not-accessible
   STATUS      current
   DESCRIPTION
      ""
   ::= {sr1645v2ZbfwFtpFlowsEntry 11}

sr1645v2ZbfwFtpFlowsSrcIntf OBJECT-TYPE
   SYNTAX      DisplayString
   MAX-ACCESS  read-only
   STATUS      current
   DESCRIPTION
      "Path: zbFirewall.status.ftpFlows.srcIntf"
   ::= {sr1645v2ZbfwFtpFlowsEntry 16777216}

sr1645v2ZbfwFtpFlowsDstIntf OBJECT-TYPE
   SYNTAX      DisplayString
   MAX-ACCESS  read-only
   STATUS      current
   DESCRIPTION
      "Path: zbFirewall.status.ftpFlows.dstIntf"
   ::= {sr1645v2ZbfwFtpFlowsEntry 33554432}

sr1645v2ZbfwFtpFlowsSrcAddress OBJECT-TYPE
   SYNTAX      IpAddress
   MAX-ACCESS  read-only
   STATUS      current
   DESCRIPTION
      "Path: zbFirewall.status.ftpFlows.srcAddress"
   ::= {sr1645v2ZbfwFtpFlowsEntry 50331648}

sr1645v2ZbfwFtpFlowsDstAddress OBJECT-TYPE
   SYNTAX      IpAddress
   MAX-ACCESS  read-only
   STATUS      current
   DESCRIPTION
      "Path: zbFirewall.status.ftpFlows.dstAddress"
   ::= {sr1645v2ZbfwFtpFlowsEntry 67108864}

sr1645v2ZbfwFtpFlowsSrcPort OBJECT-TYPE
   SYNTAX      Integer32
   MAX-ACCESS  read-only
   STATUS      current
   DESCRIPTION
      "Path: zbFirewall.status.ftpFlows.srcPort"
   ::= {sr1645v2ZbfwFtpFlowsEntry 83886080}

sr1645v2ZbfwFtpFlowsDstPort OBJECT-TYPE
   SYNTAX      Integer32
   MAX-ACCESS  read-only
   STATUS      current
   DESCRIPTION
      "Path: zbFirewall.status.ftpFlows.dstPort"
   ::= {sr1645v2ZbfwFtpFlowsEntry 100663296}

sr1645v2ZbfwFtpFlowsTcpState OBJECT-TYPE
   SYNTAX      INTEGER
               {
               idle (0),
               listen (1),
               synSent (2),
               synAcked (3),
               established (4),
               finSent (5),
               finAcked (6),
               closed (7),
               reset (8)
               }
   MAX-ACCESS  read-only
   STATUS      current
   DESCRIPTION
      "Path: zbFirewall.status.ftpFlows.tcp.state

       Possibilities:
               idle   (0)
               listen   (1)
               synSent   (2)
               synAcked   (3)
               established   (4)
               finSent   (5)
               finAcked   (6)
               closed   (7)
               reset   (8)"
   ::= {sr1645v2ZbfwFtpFlowsEntry 117506048}

sr1645v2ZbfwFtpFlowsTcpSeqNr OBJECT-TYPE
   SYNTAX      Counter32
   MAX-ACCESS  read-only
   STATUS      current
   DESCRIPTION
      "Path: zbFirewall.status.ftpFlows.tcp.seqNr

       32 bit unsigned wrappable counter."
   ::= {sr1645v2ZbfwFtpFlowsEntry 117571584}

sr1645v2ZbfwFtpFlowsTcpAckedNr OBJECT-TYPE
   SYNTAX      Counter32
   MAX-ACCESS  read-only
   STATUS      current
   DESCRIPTION
      "Path: zbFirewall.status.ftpFlows.tcp.ackedNr

       32 bit unsigned wrappable counter."
   ::= {sr1645v2ZbfwFtpFlowsEntry 117637120}

sr1645v2ZbfwFtpFlowsFtpState OBJECT-TYPE
   SYNTAX      INTEGER
               {
               initial (0),
               control (1),
               data (2)
               }
   MAX-ACCESS  read-only
   STATUS      current
   DESCRIPTION
      "Path: zbFirewall.status.ftpFlows.ftp.state

       Possibilities:
               initial   (0)
               control   (1)
               data   (2)"
   ::= {sr1645v2ZbfwFtpFlowsEntry 134283264}

sr1645v2ZbfwFtpFlowsFtpDataPort OBJECT-TYPE
   SYNTAX      Integer32
   MAX-ACCESS  read-only
   STATUS      current
   DESCRIPTION
      "Path: zbFirewall.status.ftpFlows.ftp.dataPort"
   ::= {sr1645v2ZbfwFtpFlowsEntry 134348800}


sr1645v2ZbfwHalfOpenFlows OBJECT IDENTIFIER ::= {sr1645v2Zbfw 28}

sr1645v2ZbfwHalfOpenFlowsSSCTable OBJECT-TYPE
   SYNTAX      SEQUENCE OF Sr1645v2ZbfwHalfOpenFlowsEntry
   MAX-ACCESS  not-accessible
   STATUS      current
   DESCRIPTION
      "open flow status"
   ::= {sr1645v2ZbfwHalfOpenFlows 1}

sr1645v2ZbfwHalfOpenFlowsEntry OBJECT-TYPE
   SYNTAX      Sr1645v2ZbfwHalfOpenFlowsEntry
   MAX-ACCESS  not-accessible
   STATUS      current
   DESCRIPTION
      ""
   INDEX      { sr1645v2ZbfwHalfOpenFlowsGlobalIx,
                sr1645v2ZbfwHalfOpenFlowsTableIx }
   ::= {sr1645v2ZbfwHalfOpenFlowsSSCTable 1}

Sr1645v2ZbfwHalfOpenFlowsEntry ::=
   SEQUENCE
      {
      sr1645v2ZbfwHalfOpenFlowsGlobalIx
         GlobalIndex,
      sr1645v2ZbfwHalfOpenFlowsTableIx
         TableIndex,
      sr1645v2ZbfwHalfOpenFlowsSrcIntf
         DisplayString,
      sr1645v2ZbfwHalfOpenFlowsSrcZone
         DisplayString,
      sr1645v2ZbfwHalfOpenFlowsDstIntf
         DisplayString,
      sr1645v2ZbfwHalfOpenFlowsDstZone
         DisplayString,
      sr1645v2ZbfwHalfOpenFlowsSrcAddress
         IpAddress,
      sr1645v2ZbfwHalfOpenFlowsDstAddress
         IpAddress,
      sr1645v2ZbfwHalfOpenFlowsProt
         INTEGER,
      sr1645v2ZbfwHalfOpenFlowsSrcPort
         Integer32,
      sr1645v2ZbfwHalfOpenFlowsDstPort
         Integer32,
      sr1645v2ZbfwHalfOpenFlowsProtInfoTcpState
         INTEGER,
      sr1645v2ZbfwHalfOpenFlowsProtInfoTcpSeqNr
         Counter32,
      sr1645v2ZbfwHalfOpenFlowsProtInfoTcpAckedNr
         Counter32,
      sr1645v2ZbfwHalfOpenFlowsInboundNatMode
         INTEGER,
      sr1645v2ZbfwHalfOpenFlowsInboundNatPrivateAddr
         IpAddress,
      sr1645v2ZbfwHalfOpenFlowsInboundNatPrivatePort
         Integer32,
      sr1645v2ZbfwHalfOpenFlowsInboundNatPublicAddr
         IpAddress,
      sr1645v2ZbfwHalfOpenFlowsInboundNatPublicPort
         Integer32,
      sr1645v2ZbfwHalfOpenFlowsOutboundNatMode
         INTEGER,
      sr1645v2ZbfwHalfOpenFlowsOutboundNatPrivateAddr
         IpAddress,
      sr1645v2ZbfwHalfOpenFlowsOutboundNatPrivatePort
         Integer32,
      sr1645v2ZbfwHalfOpenFlowsOutboundNatPublicAddr
         IpAddress,
      sr1645v2ZbfwHalfOpenFlowsOutboundNatPublicPort
         Integer32,
      sr1645v2ZbfwHalfOpenFlowsRulesZonePair
         DisplayString,
      sr1645v2ZbfwHalfOpenFlowsRulesPolicy
         DisplayString,
      sr1645v2ZbfwHalfOpenFlowsRulesPolicyRule
         DisplayString,
      sr1645v2ZbfwHalfOpenFlowsRulesFilter
         DisplayString,
      sr1645v2ZbfwHalfOpenFlowsRulesFilterRule
         DisplayString
      }

sr1645v2ZbfwHalfOpenFlowsGlobalIx OBJECT-TYPE
   SYNTAX      GlobalIndex
   MAX-ACCESS  not-accessible
   STATUS      current
   DESCRIPTION
      "The value of the tlsCntTreeGlobalIndex of the MANAGED OBJECT."
   ::= {sr1645v2ZbfwHalfOpenFlowsEntry 10}

sr1645v2ZbfwHalfOpenFlowsTableIx OBJECT-TYPE
   SYNTAX      TableIndex
   MAX-ACCESS  not-accessible
   STATUS      current
   DESCRIPTION
      ""
   ::= {sr1645v2ZbfwHalfOpenFlowsEntry 11}

sr1645v2ZbfwHalfOpenFlowsSrcIntf OBJECT-TYPE
   SYNTAX      DisplayString
   MAX-ACCESS  read-only
   STATUS      current
   DESCRIPTION
      "Path: zbFirewall.status.halfOpenFlows.srcIntf"
   ::= {sr1645v2ZbfwHalfOpenFlowsEntry 16777216}

sr1645v2ZbfwHalfOpenFlowsSrcZone OBJECT-TYPE
   SYNTAX      DisplayString
   MAX-ACCESS  read-only
   STATUS      current
   DESCRIPTION
      "Path: zbFirewall.status.halfOpenFlows.srcZone"
   ::= {sr1645v2ZbfwHalfOpenFlowsEntry 33554432}

sr1645v2ZbfwHalfOpenFlowsDstIntf OBJECT-TYPE
   SYNTAX      DisplayString
   MAX-ACCESS  read-only
   STATUS      current
   DESCRIPTION
      "Path: zbFirewall.status.halfOpenFlows.dstIntf"
   ::= {sr1645v2ZbfwHalfOpenFlowsEntry 50331648}

sr1645v2ZbfwHalfOpenFlowsDstZone OBJECT-TYPE
   SYNTAX      DisplayString
   MAX-ACCESS  read-only
   STATUS      current
   DESCRIPTION
      "Path: zbFirewall.status.halfOpenFlows.dstZone"
   ::= {sr1645v2ZbfwHalfOpenFlowsEntry 67108864}

sr1645v2ZbfwHalfOpenFlowsSrcAddress OBJECT-TYPE
   SYNTAX      IpAddress
   MAX-ACCESS  read-only
   STATUS      current
   DESCRIPTION
      "Path: zbFirewall.status.halfOpenFlows.srcAddress"
   ::= {sr1645v2ZbfwHalfOpenFlowsEntry 83886080}

sr1645v2ZbfwHalfOpenFlowsDstAddress OBJECT-TYPE
   SYNTAX      IpAddress
   MAX-ACCESS  read-only
   STATUS      current
   DESCRIPTION
      "Path: zbFirewall.status.halfOpenFlows.dstAddress"
   ::= {sr1645v2ZbfwHalfOpenFlowsEntry 100663296}

sr1645v2ZbfwHalfOpenFlowsProt OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6),
               icmpV6 (58),
               l2tp (115)
               }
   MAX-ACCESS  read-only
   STATUS      current
   DESCRIPTION
      "Path: zbFirewall.status.halfOpenFlows.prot

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)
               icmpV6   (58)
               l2tp   (115)"
   ::= {sr1645v2ZbfwHalfOpenFlowsEntry 117440512}

sr1645v2ZbfwHalfOpenFlowsSrcPort OBJECT-TYPE
   SYNTAX      Integer32
   MAX-ACCESS  read-only
   STATUS      current
   DESCRIPTION
      "Path: zbFirewall.status.halfOpenFlows.srcPort"
   ::= {sr1645v2ZbfwHalfOpenFlowsEntry 134217728}

sr1645v2ZbfwHalfOpenFlowsDstPort OBJECT-TYPE
   SYNTAX      Integer32
   MAX-ACCESS  read-only
   STATUS      current
   DESCRIPTION
      "Path: zbFirewall.status.halfOpenFlows.dstPort"
   ::= {sr1645v2ZbfwHalfOpenFlowsEntry 150994944}

sr1645v2ZbfwHalfOpenFlowsProtInfoTcpState OBJECT-TYPE
   SYNTAX      INTEGER
               {
               idle (0),
               listen (1),
               synSent (2),
               synAcked (3),
               established (4),
               finSent (5),
               finAcked (6),
               closed (7),
               reset (8)
               }
   MAX-ACCESS  read-only
   STATUS      current
   DESCRIPTION
      "Path: zbFirewall.status.halfOpenFlows.protInfo.tcp.state

       Possibilities:
               idle   (0)
               listen   (1)
               synSent   (2)
               synAcked   (3)
               established   (4)
               finSent   (5)
               finAcked   (6)
               closed   (7)
               reset   (8)"
   ::= {sr1645v2ZbfwHalfOpenFlowsEntry 167837952}

sr1645v2ZbfwHalfOpenFlowsProtInfoTcpSeqNr OBJECT-TYPE
   SYNTAX      Counter32
   MAX-ACCESS  read-only
   STATUS      current
   DESCRIPTION
      "Path: zbFirewall.status.halfOpenFlows.protInfo.tcp.seqNr

       32 bit unsigned wrappable counter."
   ::= {sr1645v2ZbfwHalfOpenFlowsEntry 167838208}

sr1645v2ZbfwHalfOpenFlowsProtInfoTcpAckedNr OBJECT-TYPE
   SYNTAX      Counter32
   MAX-ACCESS  read-only
   STATUS      current
   DESCRIPTION
      "Path: zbFirewall.status.halfOpenFlows.protInfo.tcp.ackedNr

       32 bit unsigned wrappable counter."
   ::= {sr1645v2ZbfwHalfOpenFlowsEntry 167838464}

sr1645v2ZbfwHalfOpenFlowsInboundNatMode OBJECT-TYPE
   SYNTAX      INTEGER
               {
               none (0),
               bypass (1),
               nat (2)
               }
   MAX-ACCESS  read-only
   STATUS      current
   DESCRIPTION
      "Path: zbFirewall.status.halfOpenFlows.inboundNat.mode

       Possibilities:
               none   (0)
               bypass   (1)
               nat   (2)"
   ::= {sr1645v2ZbfwHalfOpenFlowsEntry 184614912}

sr1645v2ZbfwHalfOpenFlowsInboundNatPrivateAddr OBJECT-TYPE
   SYNTAX      IpAddress
   MAX-ACCESS  read-only
   STATUS      current
   DESCRIPTION
      "Path: zbFirewall.status.halfOpenFlows.inboundNat.privateAddr"
   ::= {sr1645v2ZbfwHalfOpenFlowsEntry 184680448}

sr1645v2ZbfwHalfOpenFlowsInboundNatPrivatePort OBJECT-TYPE
   SYNTAX      Integer32
   MAX-ACCESS  read-only
   STATUS      current
   DESCRIPTION
      "Path: zbFirewall.status.halfOpenFlows.inboundNat.privatePort"
   ::= {sr1645v2ZbfwHalfOpenFlowsEntry 184745984}

sr1645v2ZbfwHalfOpenFlowsInboundNatPublicAddr OBJECT-TYPE
   SYNTAX      IpAddress
   MAX-ACCESS  read-only
   STATUS      current
   DESCRIPTION
      "Path: zbFirewall.status.halfOpenFlows.inboundNat.publicAddr"
   ::= {sr1645v2ZbfwHalfOpenFlowsEntry 184811520}

sr1645v2ZbfwHalfOpenFlowsInboundNatPublicPort OBJECT-TYPE
   SYNTAX      Integer32
   MAX-ACCESS  read-only
   STATUS      current
   DESCRIPTION
      "Path: zbFirewall.status.halfOpenFlows.inboundNat.publicPort"
   ::= {sr1645v2ZbfwHalfOpenFlowsEntry 184877056}

sr1645v2ZbfwHalfOpenFlowsOutboundNatMode OBJECT-TYPE
   SYNTAX      INTEGER
               {
               none (0),
               bypass (1),
               nat (2)
               }
   MAX-ACCESS  read-only
   STATUS      current
   DESCRIPTION
      "Path: zbFirewall.status.halfOpenFlows.outboundNat.mode

       Possibilities:
               none   (0)
               bypass   (1)
               nat   (2)"
   ::= {sr1645v2ZbfwHalfOpenFlowsEntry 201392128}

sr1645v2ZbfwHalfOpenFlowsOutboundNatPrivateAddr OBJECT-TYPE
   SYNTAX      IpAddress
   MAX-ACCESS  read-only
   STATUS      current
   DESCRIPTION
      "Path: zbFirewall.status.halfOpenFlows.outboundNat.privateAddr"
   ::= {sr1645v2ZbfwHalfOpenFlowsEntry 201457664}

sr1645v2ZbfwHalfOpenFlowsOutboundNatPrivatePort OBJECT-TYPE
   SYNTAX      Integer32
   MAX-ACCESS  read-only
   STATUS      current
   DESCRIPTION
      "Path: zbFirewall.status.halfOpenFlows.outboundNat.privatePort"
   ::= {sr1645v2ZbfwHalfOpenFlowsEntry 201523200}

sr1645v2ZbfwHalfOpenFlowsOutboundNatPublicAddr OBJECT-TYPE
   SYNTAX      IpAddress
   MAX-ACCESS  read-only
   STATUS      current
   DESCRIPTION
      "Path: zbFirewall.status.halfOpenFlows.outboundNat.publicAddr"
   ::= {sr1645v2ZbfwHalfOpenFlowsEntry 201588736}

sr1645v2ZbfwHalfOpenFlowsOutboundNatPublicPort OBJECT-TYPE
   SYNTAX      Integer32
   MAX-ACCESS  read-only
   STATUS      current
   DESCRIPTION
      "Path: zbFirewall.status.halfOpenFlows.outboundNat.publicPort"
   ::= {sr1645v2ZbfwHalfOpenFlowsEntry 201654272}

sr1645v2ZbfwHalfOpenFlowsRulesZonePair OBJECT-TYPE
   SYNTAX      DisplayString
   MAX-ACCESS  read-only
   STATUS      current
   DESCRIPTION
      "Path: zbFirewall.status.halfOpenFlows.rules.zonePair"
   ::= {sr1645v2ZbfwHalfOpenFlowsEntry 218169344}

sr1645v2ZbfwHalfOpenFlowsRulesPolicy OBJECT-TYPE
   SYNTAX      DisplayString
   MAX-ACCESS  read-only
   STATUS      current
   DESCRIPTION
      "Path: zbFirewall.status.halfOpenFlows.rules.policy"
   ::= {sr1645v2ZbfwHalfOpenFlowsEntry 218234880}

sr1645v2ZbfwHalfOpenFlowsRulesPolicyRule OBJECT-TYPE
   SYNTAX      DisplayString
   MAX-ACCESS  read-only
   STATUS      current
   DESCRIPTION
      "Path: zbFirewall.status.halfOpenFlows.rules.policyRule"
   ::= {sr1645v2ZbfwHalfOpenFlowsEntry 218300416}

sr1645v2ZbfwHalfOpenFlowsRulesFilter OBJECT-TYPE
   SYNTAX      DisplayString
   MAX-ACCESS  read-only
   STATUS      current
   DESCRIPTION
      "Path: zbFirewall.status.halfOpenFlows.rules.filter"
   ::= {sr1645v2ZbfwHalfOpenFlowsEntry 218365952}

sr1645v2ZbfwHalfOpenFlowsRulesFilterRule OBJECT-TYPE
   SYNTAX      DisplayString
   MAX-ACCESS  read-only
   STATUS      current
   DESCRIPTION
      "Path: zbFirewall.status.halfOpenFlows.rules.filterRule"
   ::= {sr1645v2ZbfwHalfOpenFlowsEntry 218431488}


sr1645v2ZbfwBwControl OBJECT IDENTIFIER ::= {sr1645v2Zbfw 29}

sr1645v2ZbfwBwControlSSCTable OBJECT-TYPE
   SYNTAX      SEQUENCE OF Sr1645v2ZbfwBwControlEntry
   MAX-ACCESS  not-accessible
   STATUS      current
   DESCRIPTION
      "bw control status"
   ::= {sr1645v2ZbfwBwControl 1}

sr1645v2ZbfwBwControlEntry OBJECT-TYPE
   SYNTAX      Sr1645v2ZbfwBwControlEntry
   MAX-ACCESS  not-accessible
   STATUS      current
   DESCRIPTION
      ""
   INDEX      { sr1645v2ZbfwBwControlGlobalIx,
                sr1645v2ZbfwBwControlTableIx }
   ::= {sr1645v2ZbfwBwControlSSCTable 1}

Sr1645v2ZbfwBwControlEntry ::=
   SEQUENCE
      {
      sr1645v2ZbfwBwControlGlobalIx
         GlobalIndex,
      sr1645v2ZbfwBwControlTableIx
         TableIndex,
      sr1645v2ZbfwBwControlFlowRefCnt
         Integer32,
      sr1645v2ZbfwBwControlTimeQuotum
         Integer32,
      sr1645v2ZbfwBwControlCirQuotum
         Integer32,
      sr1645v2ZbfwBwControlPktsPassed
         Counter32,
      sr1645v2ZbfwBwControlOctetsPassed
         Counter32,
      sr1645v2ZbfwBwControlPktsDropped
         Counter32,
      sr1645v2ZbfwBwControlOctetsDropped
         Counter32
      }

sr1645v2ZbfwBwControlGlobalIx OBJECT-TYPE
   SYNTAX      GlobalIndex
   MAX-ACCESS  not-accessible
   STATUS      current
   DESCRIPTION
      "The value of the tlsCntTreeGlobalIndex of the MANAGED OBJECT."
   ::= {sr1645v2ZbfwBwControlEntry 10}

sr1645v2ZbfwBwControlTableIx OBJECT-TYPE
   SYNTAX      TableIndex
   MAX-ACCESS  not-accessible
   STATUS      current
   DESCRIPTION
      ""
   ::= {sr1645v2ZbfwBwControlEntry 11}

sr1645v2ZbfwBwControlFlowRefCnt OBJECT-TYPE
   SYNTAX      Integer32
   MAX-ACCESS  read-only
   STATUS      current
   DESCRIPTION
      "Path: zbFirewall.status.bwControl.flowRefCnt"
   ::= {sr1645v2ZbfwBwControlEntry 16777216}

sr1645v2ZbfwBwControlTimeQuotum OBJECT-TYPE
   SYNTAX      Integer32
   MAX-ACCESS  read-only
   STATUS      current
   DESCRIPTION
      "Path: zbFirewall.status.bwControl.timeQuotum"
   ::= {sr1645v2ZbfwBwControlEntry 33554432}

sr1645v2ZbfwBwControlCirQuotum OBJECT-TYPE
   SYNTAX      Integer32
   MAX-ACCESS  read-only
   STATUS      current
   DESCRIPTION
      "Path: zbFirewall.status.bwControl.cirQuotum"
   ::= {sr1645v2ZbfwBwControlEntry 50331648}

sr1645v2ZbfwBwControlPktsPassed OBJECT-TYPE
   SYNTAX      Counter32
   MAX-ACCESS  read-only
   STATUS      current
   DESCRIPTION
      "Path: zbFirewall.status.bwControl.pktsPassed

       32 bit unsigned wrappable counter."
   ::= {sr1645v2ZbfwBwControlEntry 67108864}

sr1645v2ZbfwBwControlOctetsPassed OBJECT-TYPE
   SYNTAX      Counter32
   MAX-ACCESS  read-only
   STATUS      current
   DESCRIPTION
      "Path: zbFirewall.status.bwControl.octetsPassed

       32 bit unsigned wrappable counter."
   ::= {sr1645v2ZbfwBwControlEntry 83886080}

sr1645v2ZbfwBwControlPktsDropped OBJECT-TYPE
   SYNTAX      Counter32
   MAX-ACCESS  read-only
   STATUS      current
   DESCRIPTION
      "Path: zbFirewall.status.bwControl.pktsDropped

       32 bit unsigned wrappable counter."
   ::= {sr1645v2ZbfwBwControlEntry 100663296}

sr1645v2ZbfwBwControlOctetsDropped OBJECT-TYPE
   SYNTAX      Counter32
   MAX-ACCESS  read-only
   STATUS      current
   DESCRIPTION
      "Path: zbFirewall.status.bwControl.octetsDropped

       32 bit unsigned wrappable counter."
   ::= {sr1645v2ZbfwBwControlEntry 117440512}


sr1645v2ZbfwPredefinedServices OBJECT IDENTIFIER ::= {sr1645v2Zbfw 31}

sr1645v2ZbfwPredefinedServicesSSCTable OBJECT-TYPE
   SYNTAX      SEQUENCE OF Sr1645v2ZbfwPredefinedServicesEntry
   MAX-ACCESS  not-accessible
   STATUS      current
   DESCRIPTION
      "predefined service status"
   ::= {sr1645v2ZbfwPredefinedServices 1}

sr1645v2ZbfwPredefinedServicesEntry OBJECT-TYPE
   SYNTAX      Sr1645v2ZbfwPredefinedServicesEntry
   MAX-ACCESS  not-accessible
   STATUS      current
   DESCRIPTION
      ""
   INDEX      { sr1645v2ZbfwPredefinedServicesGlobalIx,
                sr1645v2ZbfwPredefinedServicesTableIx }
   ::= {sr1645v2ZbfwPredefinedServicesSSCTable 1}

Sr1645v2ZbfwPredefinedServicesEntry ::=
   SEQUENCE
      {
      sr1645v2ZbfwPredefinedServicesGlobalIx
         GlobalIndex,
      sr1645v2ZbfwPredefinedServicesTableIx
         TableIndex,
      sr1645v2ZbfwPredefinedServicesName
         DisplayString,
      sr1645v2ZbfwPredefinedServicesProtocol
         INTEGER,
      sr1645v2ZbfwPredefinedServicesPort
         Integer32
      }

sr1645v2ZbfwPredefinedServicesGlobalIx OBJECT-TYPE
   SYNTAX      GlobalIndex
   MAX-ACCESS  not-accessible
   STATUS      current
   DESCRIPTION
      "The value of the tlsCntTreeGlobalIndex of the MANAGED OBJECT."
   ::= {sr1645v2ZbfwPredefinedServicesEntry 10}

sr1645v2ZbfwPredefinedServicesTableIx OBJECT-TYPE
   SYNTAX      TableIndex
   MAX-ACCESS  not-accessible
   STATUS      current
   DESCRIPTION
      ""
   ::= {sr1645v2ZbfwPredefinedServicesEntry 11}

sr1645v2ZbfwPredefinedServicesName OBJECT-TYPE
   SYNTAX      DisplayString
   MAX-ACCESS  read-only
   STATUS      current
   DESCRIPTION
      "Path: zbFirewall.status.predefinedServices.name"
   ::= {sr1645v2ZbfwPredefinedServicesEntry 16777216}

sr1645v2ZbfwPredefinedServicesProtocol OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6),
               icmpV6 (58),
               l2tp (115)
               }
   MAX-ACCESS  read-only
   STATUS      current
   DESCRIPTION
      "Path: zbFirewall.status.predefinedServices.protocol

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)
               icmpV6   (58)
               l2tp   (115)"
   ::= {sr1645v2ZbfwPredefinedServicesEntry 33554432}

sr1645v2ZbfwPredefinedServicesPort OBJECT-TYPE
   SYNTAX      Integer32
   MAX-ACCESS  read-only
   STATUS      current
   DESCRIPTION
      "Path: zbFirewall.status.predefinedServices.port"
   ::= {sr1645v2ZbfwPredefinedServicesEntry 50331648}


sr1645v2ZbfwLogMessages OBJECT IDENTIFIER ::= {sr1645v2Zbfw 24}

sr1645v2ZbfwLogMessagesSSCTable OBJECT-TYPE
   SYNTAX      SEQUENCE OF Sr1645v2ZbfwLogMessagesEntry
   MAX-ACCESS  not-accessible
   STATUS      current
   DESCRIPTION
      "Configuration Messages"
   ::= {sr1645v2ZbfwLogMessages 1}

sr1645v2ZbfwLogMessagesEntry OBJECT-TYPE
   SYNTAX      Sr1645v2ZbfwLogMessagesEntry
   MAX-ACCESS  not-accessible
   STATUS      current
   DESCRIPTION
      ""
   INDEX      { sr1645v2ZbfwLogMessagesGlobalIx,
                sr1645v2ZbfwLogMessagesTableIx }
   ::= {sr1645v2ZbfwLogMessagesSSCTable 1}

Sr1645v2ZbfwLogMessagesEntry ::=
   SEQUENCE
      {
      sr1645v2ZbfwLogMessagesGlobalIx
         GlobalIndex,
      sr1645v2ZbfwLogMessagesTableIx
         TableIndex,
      sr1645v2ZbfwLogMessagesTime
         TimeTicks,
      sr1645v2ZbfwLogMessagesSeqNr
         Integer32,
      sr1645v2ZbfwLogMessagesModule
         INTEGER,
      sr1645v2ZbfwLogMessagesSeverity
         INTEGER,
      sr1645v2ZbfwLogMessagesMsgId
         INTEGER,
      sr1645v2ZbfwLogMessagesMessage
         DisplayString
      }

sr1645v2ZbfwLogMessagesGlobalIx OBJECT-TYPE
   SYNTAX      GlobalIndex
   MAX-ACCESS  not-accessible
   STATUS      current
   DESCRIPTION
      "The value of the tlsCntTreeGlobalIndex of the MANAGED OBJECT."
   ::= {sr1645v2ZbfwLogMessagesEntry 10}

sr1645v2ZbfwLogMessagesTableIx OBJECT-TYPE
   SYNTAX      TableIndex
   MAX-ACCESS  not-accessible
   STATUS      current
   DESCRIPTION
      ""
   ::= {sr1645v2ZbfwLogMessagesEntry 11}

sr1645v2ZbfwLogMessagesTime OBJECT-TYPE
   SYNTAX      TimeTicks
   MAX-ACCESS  read-only
   STATUS      current
   DESCRIPTION
      "Path: zbFirewall.status.logMessages.time

       Time in centi-second."
   ::= {sr1645v2ZbfwLogMessagesEntry 16777216}

sr1645v2ZbfwLogMessagesSeqNr OBJECT-TYPE
   SYNTAX      Integer32
   MAX-ACCESS  read-only
   STATUS      current
   DESCRIPTION
      "Path: zbFirewall.status.logMessages.seqNr"
   ::= {sr1645v2ZbfwLogMessagesEntry 33554432}

sr1645v2ZbfwLogMessagesModule OBJECT-TYPE
   SYNTAX      INTEGER
               {
               config (0),
               attack (1),
               traffic (2),
               alg (3),
               general (4)
               }
   MAX-ACCESS  read-only
   STATUS      current
   DESCRIPTION
      "Path: zbFirewall.status.logMessages.module

       Possibilities:
               config   (0)
               attack   (1)
               traffic   (2)
               alg   (3)
               general   (4)"
   ::= {sr1645v2ZbfwLogMessagesEntry 50331648}

sr1645v2ZbfwLogMessagesSeverity OBJECT-TYPE
   SYNTAX      INTEGER
               {
               emergency (0),
               alert (1),
               critical (2),
               error (3),
               warning (4),
               notice (5),
               informational (6),
               debug (7)
               }
   MAX-ACCESS  read-only
   STATUS      current
   DESCRIPTION
      "Path: zbFirewall.status.logMessages.severity

       Possibilities:
               emergency   (0)
               alert   (1)
               critical   (2)
               error   (3)
               warning   (4)
               notice   (5)
               informational   (6)
               debug   (7)"
   ::= {sr1645v2ZbfwLogMessagesEntry 67108864}

sr1645v2ZbfwLogMessagesMsgId OBJECT-TYPE
   SYNTAX      INTEGER
               {
               incomplZonePair (0),
               incomplPolicy (1),
               incomplPolicyRule (2),
               incomplFilter (3),
               incomplFilterRule (4),
               incomplAction (5),
               incomplNat (6),
               invalidVrf (7),
               connCreate (8),
               connClose (9),
               connTimeOut (10),
               dropPolicy (11),
               noPolicy (12),
               connRefused (13),
               ftpCommandDenied (14),
               synfloodAggrMode (15),
               duplicZonePair (16),
               duplicPolicyRule (17),
               duplicFilterRule (18),
               configModified (19),
               connExceeded (20)
               }
   MAX-ACCESS  read-only
   STATUS      current
   DESCRIPTION
      "Path: zbFirewall.status.logMessages.msgId

       Possibilities:
               incomplZonePair   (0)
               incomplPolicy   (1)
               incomplPolicyRule   (2)
               incomplFilter   (3)
               incomplFilterRule   (4)
               incomplAction   (5)
               incomplNat   (6)
               invalidVrf   (7)
               connCreate   (8)
               connClose   (9)
               connTimeOut   (10)
               dropPolicy   (11)
               noPolicy   (12)
               connRefused   (13)
               ftpCommandDenied   (14)
               synfloodAggrMode   (15)
               duplicZonePair   (16)
               duplicPolicyRule   (17)
               duplicFilterRule   (18)
               configModified   (19)
               connExceeded   (20)"
   ::= {sr1645v2ZbfwLogMessagesEntry 83886080}

sr1645v2ZbfwLogMessagesMessage OBJECT-TYPE
   SYNTAX      DisplayString
   MAX-ACCESS  read-only
   STATUS      current
   DESCRIPTION
      "Path: zbFirewall.status.logMessages.message"
   ::= {sr1645v2ZbfwLogMessagesEntry 100663296}


sr1645v2ZbfwConfigMessages OBJECT IDENTIFIER ::= {sr1645v2Zbfw 26}

sr1645v2ZbfwConfigMessagesSSCTable OBJECT-TYPE
   SYNTAX      SEQUENCE OF Sr1645v2ZbfwConfigMessagesEntry
   MAX-ACCESS  not-accessible
   STATUS      current
   DESCRIPTION
      "Configuration Messages"
   ::= {sr1645v2ZbfwConfigMessages 1}

sr1645v2ZbfwConfigMessagesEntry OBJECT-TYPE
   SYNTAX      Sr1645v2ZbfwConfigMessagesEntry
   MAX-ACCESS  not-accessible
   STATUS      current
   DESCRIPTION
      ""
   INDEX      { sr1645v2ZbfwConfigMessagesGlobalIx,
                sr1645v2ZbfwConfigMessagesTableIx }
   ::= {sr1645v2ZbfwConfigMessagesSSCTable 1}

Sr1645v2ZbfwConfigMessagesEntry ::=
   SEQUENCE
      {
      sr1645v2ZbfwConfigMessagesGlobalIx
         GlobalIndex,
      sr1645v2ZbfwConfigMessagesTableIx
         TableIndex,
      sr1645v2ZbfwConfigMessagesTime
         TimeTicks,
      sr1645v2ZbfwConfigMessagesSeverity
         INTEGER,
      sr1645v2ZbfwConfigMessagesMsgId
         INTEGER,
      sr1645v2ZbfwConfigMessagesMessage
         DisplayString
      }

sr1645v2ZbfwConfigMessagesGlobalIx OBJECT-TYPE
   SYNTAX      GlobalIndex
   MAX-ACCESS  not-accessible
   STATUS      current
   DESCRIPTION
      "The value of the tlsCntTreeGlobalIndex of the MANAGED OBJECT."
   ::= {sr1645v2ZbfwConfigMessagesEntry 10}

sr1645v2ZbfwConfigMessagesTableIx OBJECT-TYPE
   SYNTAX      TableIndex
   MAX-ACCESS  not-accessible
   STATUS      current
   DESCRIPTION
      ""
   ::= {sr1645v2ZbfwConfigMessagesEntry 11}

sr1645v2ZbfwConfigMessagesTime OBJECT-TYPE
   SYNTAX      TimeTicks
   MAX-ACCESS  read-only
   STATUS      current
   DESCRIPTION
      "Path: zbFirewall.status.configMessages.time

       Time in centi-second."
   ::= {sr1645v2ZbfwConfigMessagesEntry 16777216}

sr1645v2ZbfwConfigMessagesSeverity OBJECT-TYPE
   SYNTAX      INTEGER
               {
               emergency (0),
               alert (1),
               critical (2),
               error (3),
               warning (4),
               notice (5),
               informational (6),
               debug (7)
               }
   MAX-ACCESS  read-only
   STATUS      current
   DESCRIPTION
      "Path: zbFirewall.status.configMessages.severity

       Possibilities:
               emergency   (0)
               alert   (1)
               critical   (2)
               error   (3)
               warning   (4)
               notice   (5)
               informational   (6)
               debug   (7)"
   ::= {sr1645v2ZbfwConfigMessagesEntry 33554432}

sr1645v2ZbfwConfigMessagesMsgId OBJECT-TYPE
   SYNTAX      INTEGER
               {
               incomplZonePair (0),
               incomplPolicy (1),
               incomplPolicyRule (2),
               incomplFilter (3),
               incomplFilterRule (4),
               incomplAction (5),
               incomplNat (6),
               invalidVrf (7),
               connCreate (8),
               connClose (9),
               connTimeOut (10),
               dropPolicy (11),
               noPolicy (12),
               connRefused (13),
               ftpCommandDenied (14),
               synfloodAggrMode (15),
               duplicZonePair (16),
               duplicPolicyRule (17),
               duplicFilterRule (18),
               configModified (19),
               connExceeded (20)
               }
   MAX-ACCESS  read-only
   STATUS      current
   DESCRIPTION
      "Path: zbFirewall.status.configMessages.msgId

       Possibilities:
               incomplZonePair   (0)
               incomplPolicy   (1)
               incomplPolicyRule   (2)
               incomplFilter   (3)
               incomplFilterRule   (4)
               incomplAction   (5)
               incomplNat   (6)
               invalidVrf   (7)
               connCreate   (8)
               connClose   (9)
               connTimeOut   (10)
               dropPolicy   (11)
               noPolicy   (12)
               connRefused   (13)
               ftpCommandDenied   (14)
               synfloodAggrMode   (15)
               duplicZonePair   (16)
               duplicPolicyRule   (17)
               duplicFilterRule   (18)
               configModified   (19)
               connExceeded   (20)"
   ::= {sr1645v2ZbfwConfigMessagesEntry 50331648}

sr1645v2ZbfwConfigMessagesMessage OBJECT-TYPE
   SYNTAX      DisplayString
   MAX-ACCESS  read-only
   STATUS      current
   DESCRIPTION
      "Path: zbFirewall.status.configMessages.message"
   ::= {sr1645v2ZbfwConfigMessagesEntry 67108864}


sr1645v2ZbfwAttacks OBJECT IDENTIFIER ::= {sr1645v2Zbfw 32}

sr1645v2ZbfwAttacksSSCTable OBJECT-TYPE
   SYNTAX      SEQUENCE OF Sr1645v2ZbfwAttacksEntry
   MAX-ACCESS  not-accessible
   STATUS      current
   DESCRIPTION
      "firewall Logging"
   ::= {sr1645v2ZbfwAttacks 1}

sr1645v2ZbfwAttacksEntry OBJECT-TYPE
   SYNTAX      Sr1645v2ZbfwAttacksEntry
   MAX-ACCESS  not-accessible
   STATUS      current
   DESCRIPTION
      ""
   INDEX      { sr1645v2ZbfwAttacksGlobalIx }
   ::= {sr1645v2ZbfwAttacksSSCTable 1}

Sr1645v2ZbfwAttacksEntry ::=
   SEQUENCE
      {
      sr1645v2ZbfwAttacksGlobalIx
         GlobalIndex,
      sr1645v2ZbfwAttacksSynFloodingAggressiveMode
         INTEGER,
      sr1645v2ZbfwAttacksSynFloodingMaxIncompleteLow
         Integer32,
      sr1645v2ZbfwAttacksSynFloodingMaxIncompleteHigh
         Integer32,
      sr1645v2ZbfwAttacksSynFloodingIncompleteSessions
         Integer32
      }

sr1645v2ZbfwAttacksGlobalIx OBJECT-TYPE
   SYNTAX      GlobalIndex
   MAX-ACCESS  not-accessible
   STATUS      current
   DESCRIPTION
      "The value of the tlsCntTreeGlobalIndex of the MANAGED OBJECT."
   ::= {sr1645v2ZbfwAttacksEntry 10}

sr1645v2ZbfwAttacksSynFloodingAggressiveMode OBJECT-TYPE
   SYNTAX      INTEGER
               {
               disabled (0),
               enabled (1)
               }
   MAX-ACCESS  read-only
   STATUS      current
   DESCRIPTION
      "Path: zbFirewall.status.attacks.synFlooding.aggressiveMode

       Possibilities:
               disabled   (0)
               enabled   (1)"
   ::= {sr1645v2ZbfwAttacksEntry 16842752}

sr1645v2ZbfwAttacksSynFloodingMaxIncompleteLow OBJECT-TYPE
   SYNTAX      Integer32
   MAX-ACCESS  read-only
   STATUS      current
   DESCRIPTION
      "Path: zbFirewall.status.attacks.synFlooding.maxIncompleteLow"
   ::= {sr1645v2ZbfwAttacksEntry 16973824}

sr1645v2ZbfwAttacksSynFloodingMaxIncompleteHigh OBJECT-TYPE
   SYNTAX      Integer32
   MAX-ACCESS  read-only
   STATUS      current
   DESCRIPTION
      "Path: zbFirewall.status.attacks.synFlooding.maxIncompleteHigh"
   ::= {sr1645v2ZbfwAttacksEntry 17039360}

sr1645v2ZbfwAttacksSynFloodingIncompleteSessions OBJECT-TYPE
   SYNTAX      Integer32
   MAX-ACCESS  read-only
   STATUS      current
   DESCRIPTION
      "Path: zbFirewall.status.attacks.synFlooding.incompleteSessions"
   ::= {sr1645v2ZbfwAttacksEntry 16908288}


sr1645v2ZbfwUsedConnections OBJECT IDENTIFIER ::= {sr1645v2Zbfw 33}

sr1645v2ZbfwUsedConnectionsTable OBJECT-TYPE
   SYNTAX      SEQUENCE OF Sr1645v2ZbfwUsedConnectionsEntry
   MAX-ACCESS  not-accessible
   STATUS      current
   DESCRIPTION
      "nr of used connections"
   ::= {sr1645v2ZbfwUsedConnections 1}

sr1645v2ZbfwUsedConnectionsEntry OBJECT-TYPE
   SYNTAX      Sr1645v2ZbfwUsedConnectionsEntry
   MAX-ACCESS  not-accessible
   STATUS      current
   DESCRIPTION
      ""
   INDEX      { sr1645v2ZbfwUsedConnectionsGlobalIx }
   ::= {sr1645v2ZbfwUsedConnectionsTable 1}

Sr1645v2ZbfwUsedConnectionsEntry ::=
   SEQUENCE
      {
      sr1645v2ZbfwUsedConnectionsGlobalIx
         GlobalIndex,
      sr1645v2ZbfwUsedConnectionsValue
         Counter32
      }

sr1645v2ZbfwUsedConnectionsGlobalIx OBJECT-TYPE
   SYNTAX      GlobalIndex
   MAX-ACCESS  not-accessible
   STATUS      current
   DESCRIPTION
      "The value of the tlsCntTreeGlobalIndex of the MANAGED OBJECT."
   ::= {sr1645v2ZbfwUsedConnectionsEntry 10}

sr1645v2ZbfwUsedConnectionsValue OBJECT-TYPE
   SYNTAX      Counter32
   MAX-ACCESS  read-only
   STATUS      current
   DESCRIPTION
      "Path: zbFirewall.status.usedConnections

       32 bit unsigned wrappable counter."
   ::= {sr1645v2ZbfwUsedConnectionsEntry 2147483648}


sr1645v2ZbfwMaxConnectionsUsed OBJECT IDENTIFIER ::= {sr1645v2Zbfw 34}

sr1645v2ZbfwMaxConnectionsUsedTable OBJECT-TYPE
   SYNTAX      SEQUENCE OF Sr1645v2ZbfwMaxConnectionsUsedEntry
   MAX-ACCESS  not-accessible
   STATUS      current
   DESCRIPTION
      "maximum nr of connections used at the same time"
   ::= {sr1645v2ZbfwMaxConnectionsUsed 1}

sr1645v2ZbfwMaxConnectionsUsedEntry OBJECT-TYPE
   SYNTAX      Sr1645v2ZbfwMaxConnectionsUsedEntry
   MAX-ACCESS  not-accessible
   STATUS      current
   DESCRIPTION
      ""
   INDEX      { sr1645v2ZbfwMaxConnectionsUsedGlobalIx }
   ::= {sr1645v2ZbfwMaxConnectionsUsedTable 1}

Sr1645v2ZbfwMaxConnectionsUsedEntry ::=
   SEQUENCE
      {
      sr1645v2ZbfwMaxConnectionsUsedGlobalIx
         GlobalIndex,
      sr1645v2ZbfwMaxConnectionsUsedValue
         Counter32
      }

sr1645v2ZbfwMaxConnectionsUsedGlobalIx OBJECT-TYPE
   SYNTAX      GlobalIndex
   MAX-ACCESS  not-accessible
   STATUS      current
   DESCRIPTION
      "The value of the tlsCntTreeGlobalIndex of the MANAGED OBJECT."
   ::= {sr1645v2ZbfwMaxConnectionsUsedEntry 10}

sr1645v2ZbfwMaxConnectionsUsedValue OBJECT-TYPE
   SYNTAX      Counter32
   MAX-ACCESS  read-only
   STATUS      current
   DESCRIPTION
      "Path: zbFirewall.status.maxConnectionsUsed

       32 bit unsigned wrappable counter."
   ::= {sr1645v2ZbfwMaxConnectionsUsedEntry 2147483648}



pr1645v2Zbfw OBJECT IDENTIFIER ::= {r1645v2Zbfw 12}


pr1645v2ZbfwRouter OBJECT IDENTIFIER ::= {pr1645v2Zbfw 40}

pr1645v2ZbfwRouterSSCTable OBJECT-TYPE
   SYNTAX      SEQUENCE OF Pr1645v2ZbfwRouterEntry
   MAX-ACCESS  not-accessible
   STATUS      current
   DESCRIPTION
      "router statistics"
   ::= {pr1645v2ZbfwRouter 1}

pr1645v2ZbfwRouterEntry OBJECT-TYPE
   SYNTAX      Pr1645v2ZbfwRouterEntry
   MAX-ACCESS  not-accessible
   STATUS      current
   DESCRIPTION
      ""
   INDEX      { pr1645v2ZbfwRouterGlobalIx }
   ::= {pr1645v2ZbfwRouterSSCTable 1}

Pr1645v2ZbfwRouterEntry ::=
   SEQUENCE
      {
      pr1645v2ZbfwRouterGlobalIx
         GlobalIndex,
      pr1645v2ZbfwRouterConnectionsCreated
         Counter32,
      pr1645v2ZbfwRouterConnectionsClosed
         Counter32,
      pr1645v2ZbfwRouterConnectionsTimedOut
         Counter32
      }

pr1645v2ZbfwRouterGlobalIx OBJECT-TYPE
   SYNTAX      GlobalIndex
   MAX-ACCESS  not-accessible
   STATUS      current
   DESCRIPTION
      "The value of the tlsCntTreeGlobalIndex of the MANAGED OBJECT."
   ::= {pr1645v2ZbfwRouterEntry 10}

pr1645v2ZbfwRouterConnectionsCreated OBJECT-TYPE
   SYNTAX      Counter32
   MAX-ACCESS  read-only
   STATUS      current
   DESCRIPTION
      "Path: zbFirewall.performance.router.connections.created

       32 bit unsigned wrappable counter."
   ::= {pr1645v2ZbfwRouterEntry 16842752}

pr1645v2ZbfwRouterConnectionsClosed OBJECT-TYPE
   SYNTAX      Counter32
   MAX-ACCESS  read-only
   STATUS      current
   DESCRIPTION
      "Path: zbFirewall.performance.router.connections.closed

       32 bit unsigned wrappable counter."
   ::= {pr1645v2ZbfwRouterEntry 16908288}

pr1645v2ZbfwRouterConnectionsTimedOut OBJECT-TYPE
   SYNTAX      Counter32
   MAX-ACCESS  read-only
   STATUS      current
   DESCRIPTION
      "Path: zbFirewall.performance.router.connections.timedOut

       32 bit unsigned wrappable counter."
   ::= {pr1645v2ZbfwRouterEntry 16973824}


pr1645v2ZbfwPackets OBJECT IDENTIFIER ::= {pr1645v2Zbfw 41}

pr1645v2ZbfwPacketsSSCTable OBJECT-TYPE
   SYNTAX      SEQUENCE OF Pr1645v2ZbfwPacketsEntry
   MAX-ACCESS  not-accessible
   STATUS      current
   DESCRIPTION
      "packet statistics"
   ::= {pr1645v2ZbfwPackets 1}

pr1645v2ZbfwPacketsEntry OBJECT-TYPE
   SYNTAX      Pr1645v2ZbfwPacketsEntry
   MAX-ACCESS  not-accessible
   STATUS      current
   DESCRIPTION
      ""
   INDEX      { pr1645v2ZbfwPacketsGlobalIx }
   ::= {pr1645v2ZbfwPacketsSSCTable 1}

Pr1645v2ZbfwPacketsEntry ::=
   SEQUENCE
      {
      pr1645v2ZbfwPacketsGlobalIx
         GlobalIndex,
      pr1645v2ZbfwPacketsProcessed
         Counter32,
      pr1645v2ZbfwPacketsPassed
         Counter32,
      pr1645v2ZbfwPacketsDropped
         Counter32,
      pr1645v2ZbfwPacketsRejected
         Counter32,
      pr1645v2ZbfwPacketsRejectStatsInvalidIntf
         Counter32,
      pr1645v2ZbfwPacketsRejectStatsNoPolicy
         Counter32,
      pr1645v2ZbfwPacketsRejectStatsNoConnSetup
         Counter32,
      pr1645v2ZbfwPacketsRejectStatsConnExceeded
         Counter32,
      pr1645v2ZbfwPacketsRejectStatsProtocol
         Counter32,
      pr1645v2ZbfwPacketsRejectStatsAlg
         Counter32,
      pr1645v2ZbfwPacketsRejectStatsBandwidth
         Counter32
      }

pr1645v2ZbfwPacketsGlobalIx OBJECT-TYPE
   SYNTAX      GlobalIndex
   MAX-ACCESS  not-accessible
   STATUS      current
   DESCRIPTION
      "The value of the tlsCntTreeGlobalIndex of the MANAGED OBJECT."
   ::= {pr1645v2ZbfwPacketsEntry 10}

pr1645v2ZbfwPacketsProcessed OBJECT-TYPE
   SYNTAX      Counter32
   MAX-ACCESS  read-only
   STATUS      current
   DESCRIPTION
      "Path: zbFirewall.performance.packets.processed

       32 bit unsigned wrappable counter."
   ::= {pr1645v2ZbfwPacketsEntry 16777216}

pr1645v2ZbfwPacketsPassed OBJECT-TYPE
   SYNTAX      Counter32
   MAX-ACCESS  read-only
   STATUS      current
   DESCRIPTION
      "Path: zbFirewall.performance.packets.passed

       32 bit unsigned wrappable counter."
   ::= {pr1645v2ZbfwPacketsEntry 33554432}

pr1645v2ZbfwPacketsDropped OBJECT-TYPE
   SYNTAX      Counter32
   MAX-ACCESS  read-only
   STATUS      current
   DESCRIPTION
      "Path: zbFirewall.performance.packets.dropped

       32 bit unsigned wrappable counter."
   ::= {pr1645v2ZbfwPacketsEntry 50331648}

pr1645v2ZbfwPacketsRejected OBJECT-TYPE
   SYNTAX      Counter32
   MAX-ACCESS  read-only
   STATUS      current
   DESCRIPTION
      "Path: zbFirewall.performance.packets.rejected

       32 bit unsigned wrappable counter."
   ::= {pr1645v2ZbfwPacketsEntry 67108864}

pr1645v2ZbfwPacketsRejectStatsInvalidIntf OBJECT-TYPE
   SYNTAX      Counter32
   MAX-ACCESS  read-only
   STATUS      current
   DESCRIPTION
      "Path: zbFirewall.performance.packets.rejectStats.invalidIntf

       32 bit unsigned wrappable counter."
   ::= {pr1645v2ZbfwPacketsEntry 83951616}

pr1645v2ZbfwPacketsRejectStatsNoPolicy OBJECT-TYPE
   SYNTAX      Counter32
   MAX-ACCESS  read-only
   STATUS      current
   DESCRIPTION
      "Path: zbFirewall.performance.packets.rejectStats.noPolicy

       32 bit unsigned wrappable counter."
   ::= {pr1645v2ZbfwPacketsEntry 84017152}

pr1645v2ZbfwPacketsRejectStatsNoConnSetup OBJECT-TYPE
   SYNTAX      Counter32
   MAX-ACCESS  read-only
   STATUS      current
   DESCRIPTION
      "Path: zbFirewall.performance.packets.rejectStats.noConnSetup

       32 bit unsigned wrappable counter."
   ::= {pr1645v2ZbfwPacketsEntry 84082688}

pr1645v2ZbfwPacketsRejectStatsConnExceeded OBJECT-TYPE
   SYNTAX      Counter32
   MAX-ACCESS  read-only
   STATUS      current
   DESCRIPTION
      "Path: zbFirewall.performance.packets.rejectStats.connExceeded

       32 bit unsigned wrappable counter."
   ::= {pr1645v2ZbfwPacketsEntry 84344832}

pr1645v2ZbfwPacketsRejectStatsProtocol OBJECT-TYPE
   SYNTAX      Counter32
   MAX-ACCESS  read-only
   STATUS      current
   DESCRIPTION
      "Path: zbFirewall.performance.packets.rejectStats.protocol

       32 bit unsigned wrappable counter."
   ::= {pr1645v2ZbfwPacketsEntry 84148224}

pr1645v2ZbfwPacketsRejectStatsAlg OBJECT-TYPE
   SYNTAX      Counter32
   MAX-ACCESS  read-only
   STATUS      current
   DESCRIPTION
      "Path: zbFirewall.performance.packets.rejectStats.alg

       32 bit unsigned wrappable counter."
   ::= {pr1645v2ZbfwPacketsEntry 84213760}

pr1645v2ZbfwPacketsRejectStatsBandwidth OBJECT-TYPE
   SYNTAX      Counter32
   MAX-ACCESS  read-only
   STATUS      current
   DESCRIPTION
      "Path: zbFirewall.performance.packets.rejectStats.bandwidth

       32 bit unsigned wrappable counter."
   ::= {pr1645v2ZbfwPacketsEntry 84279296}


pr1645v2ZbfwFragments OBJECT IDENTIFIER ::= {pr1645v2Zbfw 42}

pr1645v2ZbfwFragmentsSSCTable OBJECT-TYPE
   SYNTAX      SEQUENCE OF Pr1645v2ZbfwFragmentsEntry
   MAX-ACCESS  not-accessible
   STATUS      current
   DESCRIPTION
      "fragment statistics"
   ::= {pr1645v2ZbfwFragments 1}

pr1645v2ZbfwFragmentsEntry OBJECT-TYPE
   SYNTAX      Pr1645v2ZbfwFragmentsEntry
   MAX-ACCESS  not-accessible
   STATUS      current
   DESCRIPTION
      ""
   INDEX      { pr1645v2ZbfwFragmentsGlobalIx }
   ::= {pr1645v2ZbfwFragmentsSSCTable 1}

Pr1645v2ZbfwFragmentsEntry ::=
   SEQUENCE
      {
      pr1645v2ZbfwFragmentsGlobalIx
         GlobalIndex,
      pr1645v2ZbfwFragmentsFragPktsRcvd
         Counter32,
      pr1645v2ZbfwFragmentsFragsRcvd
         Counter32,
      pr1645v2ZbfwFragmentsCachedFrags
         Counter32,
      pr1645v2ZbfwFragmentsLostFrags
         Counter32
      }

pr1645v2ZbfwFragmentsGlobalIx OBJECT-TYPE
   SYNTAX      GlobalIndex
   MAX-ACCESS  not-accessible
   STATUS      current
   DESCRIPTION
      "The value of the tlsCntTreeGlobalIndex of the MANAGED OBJECT."
   ::= {pr1645v2ZbfwFragmentsEntry 10}

pr1645v2ZbfwFragmentsFragPktsRcvd OBJECT-TYPE
   SYNTAX      Counter32
   MAX-ACCESS  read-only
   STATUS      current
   DESCRIPTION
      "Path: zbFirewall.performance.fragments.fragPktsRcvd

       32 bit unsigned wrappable counter."
   ::= {pr1645v2ZbfwFragmentsEntry 16777216}

pr1645v2ZbfwFragmentsFragsRcvd OBJECT-TYPE
   SYNTAX      Counter32
   MAX-ACCESS  read-only
   STATUS      current
   DESCRIPTION
      "Path: zbFirewall.performance.fragments.fragsRcvd

       32 bit unsigned wrappable counter."
   ::= {pr1645v2ZbfwFragmentsEntry 33554432}

pr1645v2ZbfwFragmentsCachedFrags OBJECT-TYPE
   SYNTAX      Counter32
   MAX-ACCESS  read-only
   STATUS      current
   DESCRIPTION
      "Path: zbFirewall.performance.fragments.cachedFrags

       32 bit unsigned wrappable counter."
   ::= {pr1645v2ZbfwFragmentsEntry 50331648}

pr1645v2ZbfwFragmentsLostFrags OBJECT-TYPE
   SYNTAX      Counter32
   MAX-ACCESS  read-only
   STATUS      current
   DESCRIPTION
      "Path: zbFirewall.performance.fragments.lostFrags

       32 bit unsigned wrappable counter."
   ::= {pr1645v2ZbfwFragmentsEntry 67108864}


pr1645v2ZbfwAttacks OBJECT IDENTIFIER ::= {pr1645v2Zbfw 43}

pr1645v2ZbfwAttacksSSCTable OBJECT-TYPE
   SYNTAX      SEQUENCE OF Pr1645v2ZbfwAttacksEntry
   MAX-ACCESS  not-accessible
   STATUS      current
   DESCRIPTION
      "attack statistics"
   ::= {pr1645v2ZbfwAttacks 1}

pr1645v2ZbfwAttacksEntry OBJECT-TYPE
   SYNTAX      Pr1645v2ZbfwAttacksEntry
   MAX-ACCESS  not-accessible
   STATUS      current
   DESCRIPTION
      ""
   INDEX      { pr1645v2ZbfwAttacksGlobalIx }
   ::= {pr1645v2ZbfwAttacksSSCTable 1}

Pr1645v2ZbfwAttacksEntry ::=
   SEQUENCE
      {
      pr1645v2ZbfwAttacksGlobalIx
         GlobalIndex,
      pr1645v2ZbfwAttacksSynFloodingNrTcpAggressiveMode
         Counter32,
      pr1645v2ZbfwAttacksSynFloodingNrTcpCleanedUp
         Counter32
      }

pr1645v2ZbfwAttacksGlobalIx OBJECT-TYPE
   SYNTAX      GlobalIndex
   MAX-ACCESS  not-accessible
   STATUS      current
   DESCRIPTION
      "The value of the tlsCntTreeGlobalIndex of the MANAGED OBJECT."
   ::= {pr1645v2ZbfwAttacksEntry 10}

pr1645v2ZbfwAttacksSynFloodingNrTcpAggressiveMode OBJECT-TYPE
   SYNTAX      Counter32
   MAX-ACCESS  read-only
   STATUS      current
   DESCRIPTION
      "Path: zbFirewall.performance.attacks.synFlooding.nrTcpAggressiveMode

       32 bit unsigned wrappable counter."
   ::= {pr1645v2ZbfwAttacksEntry 16842752}

pr1645v2ZbfwAttacksSynFloodingNrTcpCleanedUp OBJECT-TYPE
   SYNTAX      Counter32
   MAX-ACCESS  read-only
   STATUS      current
   DESCRIPTION
      "Path: zbFirewall.performance.attacks.synFlooding.nrTcpCleanedUp

       32 bit unsigned wrappable counter."
   ::= {pr1645v2ZbfwAttacksEntry 16908288}


pr1645v2ZbfwFlows OBJECT IDENTIFIER ::= {pr1645v2Zbfw 44}

pr1645v2ZbfwFlowsSSCTable OBJECT-TYPE
   SYNTAX      SEQUENCE OF Pr1645v2ZbfwFlowsEntry
   MAX-ACCESS  not-accessible
   STATUS      current
   DESCRIPTION
      "open flow stats"
   ::= {pr1645v2ZbfwFlows 1}

pr1645v2ZbfwFlowsEntry OBJECT-TYPE
   SYNTAX      Pr1645v2ZbfwFlowsEntry
   MAX-ACCESS  not-accessible
   STATUS      current
   DESCRIPTION
      ""
   INDEX      { pr1645v2ZbfwFlowsGlobalIx,
                pr1645v2ZbfwFlowsTableIx }
   ::= {pr1645v2ZbfwFlowsSSCTable 1}

Pr1645v2ZbfwFlowsEntry ::=
   SEQUENCE
      {
      pr1645v2ZbfwFlowsGlobalIx
         GlobalIndex,
      pr1645v2ZbfwFlowsTableIx
         TableIndex,
      pr1645v2ZbfwFlowsDir
         INTEGER,
      pr1645v2ZbfwFlowsConnId
         Counter32,
      pr1645v2ZbfwFlowsSrcIntf
         DisplayString,
      pr1645v2ZbfwFlowsSrcZone
         DisplayString,
      pr1645v2ZbfwFlowsDstIntf
         DisplayString,
      pr1645v2ZbfwFlowsDstZone
         DisplayString,
      pr1645v2ZbfwFlowsSrcAddress
         IpAddress,
      pr1645v2ZbfwFlowsDstAddress
         IpAddress,
      pr1645v2ZbfwFlowsNatMode
         INTEGER,
      pr1645v2ZbfwFlowsProt
         INTEGER,
      pr1645v2ZbfwFlowsSrcPort
         INTEGER,
      pr1645v2ZbfwFlowsDstPort
         INTEGER,
      pr1645v2ZbfwFlowsPackets
         Counter32,
      pr1645v2ZbfwFlowsOctets
         Counter32,
      pr1645v2ZbfwFlowsRejected
         Counter32,
      pr1645v2ZbfwFlowsIcmpErrors
         Counter32
      }

pr1645v2ZbfwFlowsGlobalIx OBJECT-TYPE
   SYNTAX      GlobalIndex
   MAX-ACCESS  not-accessible
   STATUS      current
   DESCRIPTION
      "The value of the tlsCntTreeGlobalIndex of the MANAGED OBJECT."
   ::= {pr1645v2ZbfwFlowsEntry 10}

pr1645v2ZbfwFlowsTableIx OBJECT-TYPE
   SYNTAX      TableIndex
   MAX-ACCESS  not-accessible
   STATUS      current
   DESCRIPTION
      ""
   ::= {pr1645v2ZbfwFlowsEntry 11}

pr1645v2ZbfwFlowsDir OBJECT-TYPE
   SYNTAX      INTEGER
               {
               sg (0),
               sl (1)
               }
   MAX-ACCESS  read-only
   STATUS      current
   DESCRIPTION
      "Path: zbFirewall.performance.flows.dir

       Possibilities:
               >   (0)
               <   (1)"
   ::= {pr1645v2ZbfwFlowsEntry 838860800}

pr1645v2ZbfwFlowsConnId OBJECT-TYPE
   SYNTAX      Counter32
   MAX-ACCESS  read-only
   STATUS      current
   DESCRIPTION
      "Path: zbFirewall.performance.flows.connId

       32 bit unsigned wrappable counter."
   ::= {pr1645v2ZbfwFlowsEntry 285212672}

pr1645v2ZbfwFlowsSrcIntf OBJECT-TYPE
   SYNTAX      DisplayString
   MAX-ACCESS  read-only
   STATUS      current
   DESCRIPTION
      "Path: zbFirewall.performance.flows.srcIntf"
   ::= {pr1645v2ZbfwFlowsEntry 16777216}

pr1645v2ZbfwFlowsSrcZone OBJECT-TYPE
   SYNTAX      DisplayString
   MAX-ACCESS  read-only
   STATUS      current
   DESCRIPTION
      "Path: zbFirewall.performance.flows.srcZone"
   ::= {pr1645v2ZbfwFlowsEntry 33554432}

pr1645v2ZbfwFlowsDstIntf OBJECT-TYPE
   SYNTAX      DisplayString
   MAX-ACCESS  read-only
   STATUS      current
   DESCRIPTION
      "Path: zbFirewall.performance.flows.dstIntf"
   ::= {pr1645v2ZbfwFlowsEntry 50331648}

pr1645v2ZbfwFlowsDstZone OBJECT-TYPE
   SYNTAX      DisplayString
   MAX-ACCESS  read-only
   STATUS      current
   DESCRIPTION
      "Path: zbFirewall.performance.flows.dstZone"
   ::= {pr1645v2ZbfwFlowsEntry 67108864}

pr1645v2ZbfwFlowsSrcAddress OBJECT-TYPE
   SYNTAX      IpAddress
   MAX-ACCESS  read-only
   STATUS      current
   DESCRIPTION
      "Path: zbFirewall.performance.flows.srcAddress"
   ::= {pr1645v2ZbfwFlowsEntry 83886080}

pr1645v2ZbfwFlowsDstAddress OBJECT-TYPE
   SYNTAX      IpAddress
   MAX-ACCESS  read-only
   STATUS      current
   DESCRIPTION
      "Path: zbFirewall.performance.flows.dstAddress"
   ::= {pr1645v2ZbfwFlowsEntry 100663296}

pr1645v2ZbfwFlowsNatMode OBJECT-TYPE
   SYNTAX      INTEGER
               {
               none (0),
               inbound (1),
               outbound (2),
               bidirectional (3)
               }
   MAX-ACCESS  read-only
   STATUS      current
   DESCRIPTION
      "Path: zbFirewall.performance.flows.natMode

       Possibilities:
               none   (0)
               inbound   (1)
               outbound   (2)
               bidirectional   (3)"
   ::= {pr1645v2ZbfwFlowsEntry 855638016}

pr1645v2ZbfwFlowsProt OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6),
               icmpV6 (58),
               l2tp (115)
               }
   MAX-ACCESS  read-only
   STATUS      current
   DESCRIPTION
      "Path: zbFirewall.performance.flows.prot

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)
               icmpV6   (58)
               l2tp   (115)"
   ::= {pr1645v2ZbfwFlowsEntry 117440512}

pr1645v2ZbfwFlowsSrcPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.performance.flows.srcPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {pr1645v2ZbfwFlowsEntry 134217728}

pr1645v2ZbfwFlowsDstPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.performance.flows.dstPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {pr1645v2ZbfwFlowsEntry 150994944}

pr1645v2ZbfwFlowsPackets OBJECT-TYPE
   SYNTAX      Counter32
   MAX-ACCESS  read-only
   STATUS      current
   DESCRIPTION
      "Path: zbFirewall.performance.flows.packets

       32 bit unsigned wrappable counter."
   ::= {pr1645v2ZbfwFlowsEntry 301989888}

pr1645v2ZbfwFlowsOctets OBJECT-TYPE
   SYNTAX      Counter32
   MAX-ACCESS  read-only
   STATUS      current
   DESCRIPTION
      "Path: zbFirewall.performance.flows.octets

       32 bit unsigned wrappable counter."
   ::= {pr1645v2ZbfwFlowsEntry 318767104}

pr1645v2ZbfwFlowsRejected OBJECT-TYPE
   SYNTAX      Counter32
   MAX-ACCESS  read-only
   STATUS      current
   DESCRIPTION
      "Path: zbFirewall.performance.flows.rejected

       32 bit unsigned wrappable counter."
   ::= {pr1645v2ZbfwFlowsEntry 335544320}

pr1645v2ZbfwFlowsIcmpErrors OBJECT-TYPE
   SYNTAX      Counter32
   MAX-ACCESS  read-only
   STATUS      current
   DESCRIPTION
      "Path: zbFirewall.performance.flows.icmpErrors

       32 bit unsigned wrappable counter."
   ::= {pr1645v2ZbfwFlowsEntry 872415232}


pr1645v2ZbfwDropFlows OBJECT IDENTIFIER ::= {pr1645v2Zbfw 45}

pr1645v2ZbfwDropFlowsSSCTable OBJECT-TYPE
   SYNTAX      SEQUENCE OF Pr1645v2ZbfwDropFlowsEntry
   MAX-ACCESS  not-accessible
   STATUS      current
   DESCRIPTION
      "open flow stats"
   ::= {pr1645v2ZbfwDropFlows 1}

pr1645v2ZbfwDropFlowsEntry OBJECT-TYPE
   SYNTAX      Pr1645v2ZbfwDropFlowsEntry
   MAX-ACCESS  not-accessible
   STATUS      current
   DESCRIPTION
      ""
   INDEX      { pr1645v2ZbfwDropFlowsGlobalIx,
                pr1645v2ZbfwDropFlowsTableIx }
   ::= {pr1645v2ZbfwDropFlowsSSCTable 1}

Pr1645v2ZbfwDropFlowsEntry ::=
   SEQUENCE
      {
      pr1645v2ZbfwDropFlowsGlobalIx
         GlobalIndex,
      pr1645v2ZbfwDropFlowsTableIx
         TableIndex,
      pr1645v2ZbfwDropFlowsDir
         INTEGER,
      pr1645v2ZbfwDropFlowsConnId
         Counter32,
      pr1645v2ZbfwDropFlowsSrcIntf
         DisplayString,
      pr1645v2ZbfwDropFlowsSrcZone
         DisplayString,
      pr1645v2ZbfwDropFlowsDstIntf
         DisplayString,
      pr1645v2ZbfwDropFlowsDstZone
         DisplayString,
      pr1645v2ZbfwDropFlowsSrcAddress
         IpAddress,
      pr1645v2ZbfwDropFlowsDstAddress
         IpAddress,
      pr1645v2ZbfwDropFlowsNatMode
         INTEGER,
      pr1645v2ZbfwDropFlowsProt
         INTEGER,
      pr1645v2ZbfwDropFlowsSrcPort
         INTEGER,
      pr1645v2ZbfwDropFlowsDstPort
         INTEGER,
      pr1645v2ZbfwDropFlowsPackets
         Counter32,
      pr1645v2ZbfwDropFlowsOctets
         Counter32,
      pr1645v2ZbfwDropFlowsRejected
         Counter32,
      pr1645v2ZbfwDropFlowsIcmpErrors
         Counter32
      }

pr1645v2ZbfwDropFlowsGlobalIx OBJECT-TYPE
   SYNTAX      GlobalIndex
   MAX-ACCESS  not-accessible
   STATUS      current
   DESCRIPTION
      "The value of the tlsCntTreeGlobalIndex of the MANAGED OBJECT."
   ::= {pr1645v2ZbfwDropFlowsEntry 10}

pr1645v2ZbfwDropFlowsTableIx OBJECT-TYPE
   SYNTAX      TableIndex
   MAX-ACCESS  not-accessible
   STATUS      current
   DESCRIPTION
      ""
   ::= {pr1645v2ZbfwDropFlowsEntry 11}

pr1645v2ZbfwDropFlowsDir OBJECT-TYPE
   SYNTAX      INTEGER
               {
               sg (0),
               sl (1)
               }
   MAX-ACCESS  read-only
   STATUS      current
   DESCRIPTION
      "Path: zbFirewall.performance.dropFlows.dir

       Possibilities:
               >   (0)
               <   (1)"
   ::= {pr1645v2ZbfwDropFlowsEntry 838860800}

pr1645v2ZbfwDropFlowsConnId OBJECT-TYPE
   SYNTAX      Counter32
   MAX-ACCESS  read-only
   STATUS      current
   DESCRIPTION
      "Path: zbFirewall.performance.dropFlows.connId

       32 bit unsigned wrappable counter."
   ::= {pr1645v2ZbfwDropFlowsEntry 285212672}

pr1645v2ZbfwDropFlowsSrcIntf OBJECT-TYPE
   SYNTAX      DisplayString
   MAX-ACCESS  read-only
   STATUS      current
   DESCRIPTION
      "Path: zbFirewall.performance.dropFlows.srcIntf"
   ::= {pr1645v2ZbfwDropFlowsEntry 16777216}

pr1645v2ZbfwDropFlowsSrcZone OBJECT-TYPE
   SYNTAX      DisplayString
   MAX-ACCESS  read-only
   STATUS      current
   DESCRIPTION
      "Path: zbFirewall.performance.dropFlows.srcZone"
   ::= {pr1645v2ZbfwDropFlowsEntry 33554432}

pr1645v2ZbfwDropFlowsDstIntf OBJECT-TYPE
   SYNTAX      DisplayString
   MAX-ACCESS  read-only
   STATUS      current
   DESCRIPTION
      "Path: zbFirewall.performance.dropFlows.dstIntf"
   ::= {pr1645v2ZbfwDropFlowsEntry 50331648}

pr1645v2ZbfwDropFlowsDstZone OBJECT-TYPE
   SYNTAX      DisplayString
   MAX-ACCESS  read-only
   STATUS      current
   DESCRIPTION
      "Path: zbFirewall.performance.dropFlows.dstZone"
   ::= {pr1645v2ZbfwDropFlowsEntry 67108864}

pr1645v2ZbfwDropFlowsSrcAddress OBJECT-TYPE
   SYNTAX      IpAddress
   MAX-ACCESS  read-only
   STATUS      current
   DESCRIPTION
      "Path: zbFirewall.performance.dropFlows.srcAddress"
   ::= {pr1645v2ZbfwDropFlowsEntry 83886080}

pr1645v2ZbfwDropFlowsDstAddress OBJECT-TYPE
   SYNTAX      IpAddress
   MAX-ACCESS  read-only
   STATUS      current
   DESCRIPTION
      "Path: zbFirewall.performance.dropFlows.dstAddress"
   ::= {pr1645v2ZbfwDropFlowsEntry 100663296}

pr1645v2ZbfwDropFlowsNatMode OBJECT-TYPE
   SYNTAX      INTEGER
               {
               none (0),
               inbound (1),
               outbound (2),
               bidirectional (3)
               }
   MAX-ACCESS  read-only
   STATUS      current
   DESCRIPTION
      "Path: zbFirewall.performance.dropFlows.natMode

       Possibilities:
               none   (0)
               inbound   (1)
               outbound   (2)
               bidirectional   (3)"
   ::= {pr1645v2ZbfwDropFlowsEntry 855638016}

pr1645v2ZbfwDropFlowsProt OBJECT-TYPE
   SYNTAX      INTEGER
               {
               any (0),
               ah (51),
               egp (8),
               esp (50),
               gre (47),
               icmp (1),
               igp (9),
               igmp (2),
               igrp (88),
               ipInIp (4),
               ospf (89),
               udp (17),
               rsvp (46),
               tcp (6),
               icmpV6 (58),
               l2tp (115)
               }
   MAX-ACCESS  read-only
   STATUS      current
   DESCRIPTION
      "Path: zbFirewall.performance.dropFlows.prot

       Possibilities:
               any   (0)
               ah   (51)
               egp   (8)
               esp   (50)
               gre   (47)
               icmp   (1)
               igp   (9)
               igmp   (2)
               igrp   (88)
               ipInIp   (4)
               ospf   (89)
               udp   (17)
               rsvp   (46)
               tcp   (6)
               icmpV6   (58)
               l2tp   (115)"
   ::= {pr1645v2ZbfwDropFlowsEntry 117440512}

pr1645v2ZbfwDropFlowsSrcPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.performance.dropFlows.srcPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {pr1645v2ZbfwDropFlowsEntry 134217728}

pr1645v2ZbfwDropFlowsDstPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: zbFirewall.performance.dropFlows.dstPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {pr1645v2ZbfwDropFlowsEntry 150994944}

pr1645v2ZbfwDropFlowsPackets OBJECT-TYPE
   SYNTAX      Counter32
   MAX-ACCESS  read-only
   STATUS      current
   DESCRIPTION
      "Path: zbFirewall.performance.dropFlows.packets

       32 bit unsigned wrappable counter."
   ::= {pr1645v2ZbfwDropFlowsEntry 301989888}

pr1645v2ZbfwDropFlowsOctets OBJECT-TYPE
   SYNTAX      Counter32
   MAX-ACCESS  read-only
   STATUS      current
   DESCRIPTION
      "Path: zbFirewall.performance.dropFlows.octets

       32 bit unsigned wrappable counter."
   ::= {pr1645v2ZbfwDropFlowsEntry 318767104}

pr1645v2ZbfwDropFlowsRejected OBJECT-TYPE
   SYNTAX      Counter32
   MAX-ACCESS  read-only
   STATUS      current
   DESCRIPTION
      "Path: zbFirewall.performance.dropFlows.rejected

       32 bit unsigned wrappable counter."
   ::= {pr1645v2ZbfwDropFlowsEntry 335544320}

pr1645v2ZbfwDropFlowsIcmpErrors OBJECT-TYPE
   SYNTAX      Counter32
   MAX-ACCESS  read-only
   STATUS      current
   DESCRIPTION
      "Path: zbFirewall.performance.dropFlows.icmpErrors

       32 bit unsigned wrappable counter."
   ::= {pr1645v2ZbfwDropFlowsEntry 872415232}



fr1645v2Zbfw OBJECT IDENTIFIER ::= {r1645v2Zbfw 13}


fr1645v2ZbfwAlarm OBJECT IDENTIFIER ::= {fr1645v2Zbfw 202}

fr1645v2ZbfwAlarmSSCTable OBJECT-TYPE
   SYNTAX      SEQUENCE OF Fr1645v2ZbfwAlarmEntry
   MAX-ACCESS  not-accessible
   STATUS      current
   DESCRIPTION
      "zbfwAlarmInfo"
   ::= {fr1645v2ZbfwAlarm 1}

fr1645v2ZbfwAlarmEntry OBJECT-TYPE
   SYNTAX      Fr1645v2ZbfwAlarmEntry
   MAX-ACCESS  not-accessible
   STATUS      current
   DESCRIPTION
      ""
   INDEX      { fr1645v2ZbfwAlarmGlobalIx }
   ::= {fr1645v2ZbfwAlarmSSCTable 1}

Fr1645v2ZbfwAlarmEntry ::=
   SEQUENCE
      {
      fr1645v2ZbfwAlarmGlobalIx
         GlobalIndex,
      fr1645v2ZbfwAlarmDiscriminator
         Integer32,
      fr1645v2ZbfwAlarmCurrent
         Integer32,
      fr1645v2ZbfwAlarmPrevious
         Integer32,
      fr1645v2ZbfwAlarmMask
         Integer32,
      fr1645v2ZbfwAlarmLevUsedConnectionsHigh
         Integer32,
      fr1645v2ZbfwAlarmLevUsedConnectionsLow
         Integer32,
      fr1645v2ZbfwAlarmLevSynFlooding
         Integer32
      }

fr1645v2ZbfwAlarmGlobalIx OBJECT-TYPE
   SYNTAX      GlobalIndex
   MAX-ACCESS  not-accessible
   STATUS      current
   DESCRIPTION
      "The value of the tlsCntTreeGlobalIndex of the MANAGED OBJECT."
   ::= {fr1645v2ZbfwAlarmEntry 10}

fr1645v2ZbfwAlarmDiscriminator OBJECT-TYPE
   SYNTAX      Integer32
   MAX-ACCESS  read-only
   STATUS      current
   DESCRIPTION
      "Path: zbFirewall.alarms.alarmInfo.discriminator"
   ::= {fr1645v2ZbfwAlarmEntry 16777216}

fr1645v2ZbfwAlarmCurrent OBJECT-TYPE
   SYNTAX      Integer32
   MAX-ACCESS  read-only
   STATUS      current
   DESCRIPTION
      "Path: zbFirewall.alarms.alarmInfo.currentAlarms

       Bit meanings:
               bit 0 = usedConnectionsHigh,
               bit 1 = usedConnectionsLow,
               bit 2 = synFlooding"
   ::= {fr1645v2ZbfwAlarmEntry 33554432}

fr1645v2ZbfwAlarmPrevious OBJECT-TYPE
   SYNTAX      Integer32
   MAX-ACCESS  read-only
   STATUS      current
   DESCRIPTION
      "Path: zbFirewall.alarms.alarmInfo.previousAlarms

       Bit meanings:
               bit 0 = usedConnectionsHigh,
               bit 1 = usedConnectionsLow,
               bit 2 = synFlooding"
   ::= {fr1645v2ZbfwAlarmEntry 50331648}

fr1645v2ZbfwAlarmMask OBJECT-TYPE
   SYNTAX      Integer32
   MAX-ACCESS  read-only
   STATUS      current
   DESCRIPTION
      "Path: zbFirewall.alarms.alarmInfo.alarmMask

       Bit meanings:
               bit 0 = usedConnectionsHigh,
               bit 1 = usedConnectionsLow,
               bit 2 = synFlooding"
   ::= {fr1645v2ZbfwAlarmEntry 67108864}

fr1645v2ZbfwAlarmLevUsedConnectionsHigh OBJECT-TYPE
   SYNTAX      Integer32
   MAX-ACCESS  read-only
   STATUS      current
   DESCRIPTION
      "Path: zbFirewall.alarms.alarmInfo.alarmLevel.usedConnectionsHigh"
   ::= {fr1645v2ZbfwAlarmEntry 83951616}

fr1645v2ZbfwAlarmLevUsedConnectionsLow OBJECT-TYPE
   SYNTAX      Integer32
   MAX-ACCESS  read-only
   STATUS      current
   DESCRIPTION
      "Path: zbFirewall.alarms.alarmInfo.alarmLevel.usedConnectionsLow"
   ::= {fr1645v2ZbfwAlarmEntry 84017152}

fr1645v2ZbfwAlarmLevSynFlooding OBJECT-TYPE
   SYNTAX      Integer32
   MAX-ACCESS  read-only
   STATUS      current
   DESCRIPTION
      "Path: zbFirewall.alarms.alarmInfo.alarmLevel.synFlooding"
   ::= {fr1645v2ZbfwAlarmEntry 84082688}


fr1645v2ZbfwAlarmE2 OBJECT IDENTIFIER ::= {fr1645v2ZbfwAlarm 2}

fr1645v2ZbfwAlarmE2Entry OBJECT IDENTIFIER ::= {fr1645v2ZbfwAlarmE2 1}

fr1645v2ZbfwAlarmE2UsedConnectionsHigh OBJECT IDENTIFIER ::= {fr1645v2ZbfwAlarmE2Entry 10}

fr1645v2ZbfwAlarmE2UsedConnectionsHighPfx OBJECT IDENTIFIER ::= {fr1645v2ZbfwAlarmE2UsedConnectionsHigh 0}

fr1645v2ZbfwAlarmE2UsedConnectionsHighOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'usedConnectionsHigh'
                representing an alarm condition in the alarm word
                of attribute 'alarmInfo' of managed object 'zbFirewall'
                (root='router1645') has changed from the ON to the OFF state."
   ::= {fr1645v2ZbfwAlarmE2UsedConnectionsHighPfx 1}

fr1645v2ZbfwAlarmE2UsedConnectionsHighOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'usedConnectionsHigh'
                representing an alarm condition in the alarm word
                of attribute 'alarmInfo' of managed object 'zbFirewall'
                (root='router1645') has changed from the OFF to the ON state."
   ::= {fr1645v2ZbfwAlarmE2UsedConnectionsHighPfx 2}

fr1645v2ZbfwAlarmE2UsedConnectionsLow OBJECT IDENTIFIER ::= {fr1645v2ZbfwAlarmE2Entry 11}

fr1645v2ZbfwAlarmE2UsedConnectionsLowPfx OBJECT IDENTIFIER ::= {fr1645v2ZbfwAlarmE2UsedConnectionsLow 0}

fr1645v2ZbfwAlarmE2UsedConnectionsLowOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'usedConnectionsLow'
                representing an alarm condition in the alarm word
                of attribute 'alarmInfo' of managed object 'zbFirewall'
                (root='router1645') has changed from the ON to the OFF state."
   ::= {fr1645v2ZbfwAlarmE2UsedConnectionsLowPfx 1}

fr1645v2ZbfwAlarmE2UsedConnectionsLowOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'usedConnectionsLow'
                representing an alarm condition in the alarm word
                of attribute 'alarmInfo' of managed object 'zbFirewall'
                (root='router1645') has changed from the OFF to the ON state."
   ::= {fr1645v2ZbfwAlarmE2UsedConnectionsLowPfx 2}

fr1645v2ZbfwAlarmE2SynFlooding OBJECT IDENTIFIER ::= {fr1645v2ZbfwAlarmE2Entry 12}

fr1645v2ZbfwAlarmE2SynFloodingPfx OBJECT IDENTIFIER ::= {fr1645v2ZbfwAlarmE2SynFlooding 0}

fr1645v2ZbfwAlarmE2SynFloodingOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'synFlooding'
                representing an alarm condition in the alarm word
                of attribute 'alarmInfo' of managed object 'zbFirewall'
                (root='router1645') has changed from the ON to the OFF state."
   ::= {fr1645v2ZbfwAlarmE2SynFloodingPfx 1}

fr1645v2ZbfwAlarmE2SynFloodingOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'synFlooding'
                representing an alarm condition in the alarm word
                of attribute 'alarmInfo' of managed object 'zbFirewall'
                (root='router1645') has changed from the OFF to the ON state."
   ::= {fr1645v2ZbfwAlarmE2SynFloodingPfx 2}



ar1645v2Zbfw OBJECT IDENTIFIER ::= {r1645v2Zbfw 16}


ar1645v2ZbfwClearCounters OBJECT IDENTIFIER ::= {ar1645v2Zbfw 263}

ar1645v2ZbfwClearCountersTable OBJECT-TYPE
   SYNTAX      SEQUENCE OF Ar1645v2ZbfwClearCountersEntry
   MAX-ACCESS  not-accessible
   STATUS      current
   DESCRIPTION
      "reset counters"
   ::= {ar1645v2ZbfwClearCounters 1}

ar1645v2ZbfwClearCountersEntry OBJECT-TYPE
   SYNTAX      Ar1645v2ZbfwClearCountersEntry
   MAX-ACCESS  not-accessible
   STATUS      current
   DESCRIPTION
      ""
   INDEX      { ar1645v2ZbfwClearCountersGlobalIx }
   ::= {ar1645v2ZbfwClearCountersTable 1}

Ar1645v2ZbfwClearCountersEntry ::=
   SEQUENCE
      {
      ar1645v2ZbfwClearCountersGlobalIx
         GlobalIndex,
      ar1645v2ZbfwClearCountersValue
         Integer32
      }

ar1645v2ZbfwClearCountersGlobalIx OBJECT-TYPE
   SYNTAX      GlobalIndex
   MAX-ACCESS  not-accessible
   STATUS      current
   DESCRIPTION
      "The value of the tlsCntTreeGlobalIndex of the MANAGED OBJECT."
   ::= {ar1645v2ZbfwClearCountersEntry 10}

ar1645v2ZbfwClearCountersValue OBJECT-TYPE
   SYNTAX      Integer32
   MAX-ACCESS  read-write
   STATUS      current
   DESCRIPTION
      "Path: zbFirewall.actions.clearCounters"
   ::= {ar1645v2ZbfwClearCountersEntry 2147483648}


ar1645v2ZbfwClearLogMessages OBJECT IDENTIFIER ::= {ar1645v2Zbfw 87}

ar1645v2ZbfwClearLogMessagesTable OBJECT-TYPE
   SYNTAX      SEQUENCE OF Ar1645v2ZbfwClearLogMessagesEntry
   MAX-ACCESS  not-accessible
   STATUS      current
   DESCRIPTION
      "delete a connection"
   ::= {ar1645v2ZbfwClearLogMessages 1}

ar1645v2ZbfwClearLogMessagesEntry OBJECT-TYPE
   SYNTAX      Ar1645v2ZbfwClearLogMessagesEntry
   MAX-ACCESS  not-accessible
   STATUS      current
   DESCRIPTION
      ""
   INDEX      { ar1645v2ZbfwClearLogMessagesGlobalIx }
   ::= {ar1645v2ZbfwClearLogMessagesTable 1}

Ar1645v2ZbfwClearLogMessagesEntry ::=
   SEQUENCE
      {
      ar1645v2ZbfwClearLogMessagesGlobalIx
         GlobalIndex,
      ar1645v2ZbfwClearLogMessagesValue
         Integer32
      }

ar1645v2ZbfwClearLogMessagesGlobalIx OBJECT-TYPE
   SYNTAX      GlobalIndex
   MAX-ACCESS  not-accessible
   STATUS      current
   DESCRIPTION
      "The value of the tlsCntTreeGlobalIndex of the MANAGED OBJECT."
   ::= {ar1645v2ZbfwClearLogMessagesEntry 10}

ar1645v2ZbfwClearLogMessagesValue OBJECT-TYPE
   SYNTAX      Integer32
   MAX-ACCESS  read-write
   STATUS      current
   DESCRIPTION
      "Path: zbFirewall.actions.clearLogMessages"
   ::= {ar1645v2ZbfwClearLogMessagesEntry 2147483648}


ar1645v2ZbfwDeleteAllConnections OBJECT IDENTIFIER ::= {ar1645v2Zbfw 86}

ar1645v2ZbfwDeleteAllConnectionsTable OBJECT-TYPE
   SYNTAX      SEQUENCE OF Ar1645v2ZbfwDeleteAllConnectionsEntry
   MAX-ACCESS  not-accessible
   STATUS      current
   DESCRIPTION
      "delete all connections"
   ::= {ar1645v2ZbfwDeleteAllConnections 1}

ar1645v2ZbfwDeleteAllConnectionsEntry OBJECT-TYPE
   SYNTAX      Ar1645v2ZbfwDeleteAllConnectionsEntry
   MAX-ACCESS  not-accessible
   STATUS      current
   DESCRIPTION
      ""
   INDEX      { ar1645v2ZbfwDeleteAllConnectionsGlobalIx }
   ::= {ar1645v2ZbfwDeleteAllConnectionsTable 1}

Ar1645v2ZbfwDeleteAllConnectionsEntry ::=
   SEQUENCE
      {
      ar1645v2ZbfwDeleteAllConnectionsGlobalIx
         GlobalIndex,
      ar1645v2ZbfwDeleteAllConnectionsValue
         Integer32
      }

ar1645v2ZbfwDeleteAllConnectionsGlobalIx OBJECT-TYPE
   SYNTAX      GlobalIndex
   MAX-ACCESS  not-accessible
   STATUS      current
   DESCRIPTION
      "The value of the tlsCntTreeGlobalIndex of the MANAGED OBJECT."
   ::= {ar1645v2ZbfwDeleteAllConnectionsEntry 10}

ar1645v2ZbfwDeleteAllConnectionsValue OBJECT-TYPE
   SYNTAX      Integer32
   MAX-ACCESS  read-write
   STATUS      current
   DESCRIPTION
      "Path: zbFirewall.actions.deleteAllConnections"
   ::= {ar1645v2ZbfwDeleteAllConnectionsEntry 2147483648}


ar1645v2ZbfwDeleteConnection OBJECT IDENTIFIER ::= {ar1645v2Zbfw 84}

ar1645v2ZbfwDeleteConnectionTable OBJECT-TYPE
   SYNTAX      SEQUENCE OF Ar1645v2ZbfwDeleteConnectionEntry
   MAX-ACCESS  not-accessible
   STATUS      current
   DESCRIPTION
      "delete a connection"
   ::= {ar1645v2ZbfwDeleteConnection 1}

ar1645v2ZbfwDeleteConnectionEntry OBJECT-TYPE
   SYNTAX      Ar1645v2ZbfwDeleteConnectionEntry
   MAX-ACCESS  not-accessible
   STATUS      current
   DESCRIPTION
      ""
   INDEX      { ar1645v2ZbfwDeleteConnectionGlobalIx }
   ::= {ar1645v2ZbfwDeleteConnectionTable 1}

Ar1645v2ZbfwDeleteConnectionEntry ::=
   SEQUENCE
      {
      ar1645v2ZbfwDeleteConnectionGlobalIx
         GlobalIndex,
      ar1645v2ZbfwDeleteConnectionValue
         Integer32
      }

ar1645v2ZbfwDeleteConnectionGlobalIx OBJECT-TYPE
   SYNTAX      GlobalIndex
   MAX-ACCESS  not-accessible
   STATUS      current
   DESCRIPTION
      "The value of the tlsCntTreeGlobalIndex of the MANAGED OBJECT."
   ::= {ar1645v2ZbfwDeleteConnectionEntry 10}

ar1645v2ZbfwDeleteConnectionValue OBJECT-TYPE
   SYNTAX      Integer32
   MAX-ACCESS  read-write
   STATUS      current
   DESCRIPTION
      "Path: zbFirewall.actions.deleteConnection"
   ::= {ar1645v2ZbfwDeleteConnectionEntry 2147483648}


ar1645v2ZbfwDeleteConnectionParams OBJECT IDENTIFIER ::= {ar1645v2Zbfw 85}

ar1645v2ZbfwDeleteConnectionParamsTable OBJECT-TYPE
   SYNTAX      SEQUENCE OF Ar1645v2ZbfwDeleteConnectionParamsEntry
   MAX-ACCESS  not-accessible
   STATUS      current
   DESCRIPTION
      "Id of the connection to be deleted"
   ::= {ar1645v2ZbfwDeleteConnectionParams 1}

ar1645v2ZbfwDeleteConnectionParamsEntry OBJECT-TYPE
   SYNTAX      Ar1645v2ZbfwDeleteConnectionParamsEntry
   MAX-ACCESS  not-accessible
   STATUS      current
   DESCRIPTION
      ""
   INDEX      { ar1645v2ZbfwDeleteConnectionParamsGlobalIx }
   ::= {ar1645v2ZbfwDeleteConnectionParamsTable 1}

Ar1645v2ZbfwDeleteConnectionParamsEntry ::=
   SEQUENCE
      {
      ar1645v2ZbfwDeleteConnectionParamsGlobalIx
         GlobalIndex,
      ar1645v2ZbfwDeleteConnectionParamsValue
         Integer32
      }

ar1645v2ZbfwDeleteConnectionParamsGlobalIx OBJECT-TYPE
   SYNTAX      GlobalIndex
   MAX-ACCESS  not-accessible
   STATUS      current
   DESCRIPTION
      "The value of the tlsCntTreeGlobalIndex of the MANAGED OBJECT."
   ::= {ar1645v2ZbfwDeleteConnectionParamsEntry 10}

ar1645v2ZbfwDeleteConnectionParamsValue OBJECT-TYPE
   SYNTAX      Integer32
   MAX-ACCESS  read-write
   STATUS      current
   DESCRIPTION
      "Path: zbFirewall.actions.deleteConnectionParams"
   ::= {ar1645v2ZbfwDeleteConnectionParamsEntry 2147483648}


ar1645v2ZbfwSavePolicyDbToFile OBJECT IDENTIFIER ::= {ar1645v2Zbfw 82}

ar1645v2ZbfwSavePolicyDbToFileTable OBJECT-TYPE
   SYNTAX      SEQUENCE OF Ar1645v2ZbfwSavePolicyDbToFileEntry
   MAX-ACCESS  not-accessible
   STATUS      current
   DESCRIPTION
      "save policy database to file"
   ::= {ar1645v2ZbfwSavePolicyDbToFile 1}

ar1645v2ZbfwSavePolicyDbToFileEntry OBJECT-TYPE
   SYNTAX      Ar1645v2ZbfwSavePolicyDbToFileEntry
   MAX-ACCESS  not-accessible
   STATUS      current
   DESCRIPTION
      ""
   INDEX      { ar1645v2ZbfwSavePolicyDbToFileGlobalIx }
   ::= {ar1645v2ZbfwSavePolicyDbToFileTable 1}

Ar1645v2ZbfwSavePolicyDbToFileEntry ::=
   SEQUENCE
      {
      ar1645v2ZbfwSavePolicyDbToFileGlobalIx
         GlobalIndex,
      ar1645v2ZbfwSavePolicyDbToFileValue
         Integer32
      }

ar1645v2ZbfwSavePolicyDbToFileGlobalIx OBJECT-TYPE
   SYNTAX      GlobalIndex
   MAX-ACCESS  not-accessible
   STATUS      current
   DESCRIPTION
      "The value of the tlsCntTreeGlobalIndex of the MANAGED OBJECT."
   ::= {ar1645v2ZbfwSavePolicyDbToFileEntry 10}

ar1645v2ZbfwSavePolicyDbToFileValue OBJECT-TYPE
   SYNTAX      Integer32
   MAX-ACCESS  read-write
   STATUS      current
   DESCRIPTION
      "Path: zbFirewall.actions.savePolicyDbToFile"
   ::= {ar1645v2ZbfwSavePolicyDbToFileEntry 2147483648}


ar1645v2ZbfwSavePolicyDbParams OBJECT IDENTIFIER ::= {ar1645v2Zbfw 83}

ar1645v2ZbfwSavePolicyDbParamsTable OBJECT-TYPE
   SYNTAX      SEQUENCE OF Ar1645v2ZbfwSavePolicyDbParamsEntry
   MAX-ACCESS  not-accessible
   STATUS      current
   DESCRIPTION
      "file in which the policy database will be saved"
   ::= {ar1645v2ZbfwSavePolicyDbParams 1}

ar1645v2ZbfwSavePolicyDbParamsEntry OBJECT-TYPE
   SYNTAX      Ar1645v2ZbfwSavePolicyDbParamsEntry
   MAX-ACCESS  not-accessible
   STATUS      current
   DESCRIPTION
      ""
   INDEX      { ar1645v2ZbfwSavePolicyDbParamsGlobalIx }
   ::= {ar1645v2ZbfwSavePolicyDbParamsTable 1}

Ar1645v2ZbfwSavePolicyDbParamsEntry ::=
   SEQUENCE
      {
      ar1645v2ZbfwSavePolicyDbParamsGlobalIx
         GlobalIndex,
      ar1645v2ZbfwSavePolicyDbParamsValue
         DisplayString
      }

ar1645v2ZbfwSavePolicyDbParamsGlobalIx OBJECT-TYPE
   SYNTAX      GlobalIndex
   MAX-ACCESS  not-accessible
   STATUS      current
   DESCRIPTION
      "The value of the tlsCntTreeGlobalIndex of the MANAGED OBJECT."
   ::= {ar1645v2ZbfwSavePolicyDbParamsEntry 10}

ar1645v2ZbfwSavePolicyDbParamsValue OBJECT-TYPE
   SYNTAX      DisplayString
   MAX-ACCESS  read-write
   STATUS      current
   DESCRIPTION
      "Path: zbFirewall.actions.savePolicyDbParams"
   ::= {ar1645v2ZbfwSavePolicyDbParamsEntry 2147483648}


ar1645v2ZbfwSetReferenceCnt OBJECT IDENTIFIER ::= {ar1645v2Zbfw 80}

ar1645v2ZbfwSetReferenceCntTable OBJECT-TYPE
   SYNTAX      SEQUENCE OF Ar1645v2ZbfwSetReferenceCntEntry
   MAX-ACCESS  not-accessible
   STATUS      current
   DESCRIPTION
      "set reference count"
   ::= {ar1645v2ZbfwSetReferenceCnt 1}

ar1645v2ZbfwSetReferenceCntEntry OBJECT-TYPE
   SYNTAX      Ar1645v2ZbfwSetReferenceCntEntry
   MAX-ACCESS  not-accessible
   STATUS      current
   DESCRIPTION
      ""
   INDEX      { ar1645v2ZbfwSetReferenceCntGlobalIx }
   ::= {ar1645v2ZbfwSetReferenceCntTable 1}

Ar1645v2ZbfwSetReferenceCntEntry ::=
   SEQUENCE
      {
      ar1645v2ZbfwSetReferenceCntGlobalIx
         GlobalIndex,
      ar1645v2ZbfwSetReferenceCntValue
         Integer32
      }

ar1645v2ZbfwSetReferenceCntGlobalIx OBJECT-TYPE
   SYNTAX      GlobalIndex
   MAX-ACCESS  not-accessible
   STATUS      current
   DESCRIPTION
      "The value of the tlsCntTreeGlobalIndex of the MANAGED OBJECT."
   ::= {ar1645v2ZbfwSetReferenceCntEntry 10}

ar1645v2ZbfwSetReferenceCntValue OBJECT-TYPE
   SYNTAX      Integer32
   MAX-ACCESS  read-write
   STATUS      current
   DESCRIPTION
      "Path: zbFirewall.actions.setReferenceCnt"
   ::= {ar1645v2ZbfwSetReferenceCntEntry 2147483648}


ar1645v2ZbfwSetRefCntParams OBJECT IDENTIFIER ::= {ar1645v2Zbfw 81}

ar1645v2ZbfwSetRefCntParamsSSCTable OBJECT-TYPE
   SYNTAX      SEQUENCE OF Ar1645v2ZbfwSetRefCntParamsEntry
   MAX-ACCESS  not-accessible
   STATUS      current
   DESCRIPTION
      "set reference count parameters"
   ::= {ar1645v2ZbfwSetRefCntParams 1}

ar1645v2ZbfwSetRefCntParamsEntry OBJECT-TYPE
   SYNTAX      Ar1645v2ZbfwSetRefCntParamsEntry
   MAX-ACCESS  not-accessible
   STATUS      current
   DESCRIPTION
      ""
   INDEX      { ar1645v2ZbfwSetRefCntParamsGlobalIx }
   ::= {ar1645v2ZbfwSetRefCntParamsSSCTable 1}

Ar1645v2ZbfwSetRefCntParamsEntry ::=
   SEQUENCE
      {
      ar1645v2ZbfwSetRefCntParamsGlobalIx
         GlobalIndex,
      ar1645v2ZbfwSetRefCntParamsPath
         DisplayString,
      ar1645v2ZbfwSetRefCntParamsValue
         Integer32
      }

ar1645v2ZbfwSetRefCntParamsGlobalIx OBJECT-TYPE
   SYNTAX      GlobalIndex
   MAX-ACCESS  not-accessible
   STATUS      current
   DESCRIPTION
      "The value of the tlsCntTreeGlobalIndex of the MANAGED OBJECT."
   ::= {ar1645v2ZbfwSetRefCntParamsEntry 10}

ar1645v2ZbfwSetRefCntParamsPath OBJECT-TYPE
   SYNTAX      DisplayString
   MAX-ACCESS  read-write
   STATUS      current
   DESCRIPTION
      "Path: zbFirewall.actions.setRefCntParams.path"
   ::= {ar1645v2ZbfwSetRefCntParamsEntry 16777216}

ar1645v2ZbfwSetRefCntParamsValue OBJECT-TYPE
   SYNTAX      Integer32
   MAX-ACCESS  read-write
   STATUS      current
   DESCRIPTION
      "Path: zbFirewall.actions.setRefCntParams.value"
   ::= {ar1645v2ZbfwSetRefCntParamsEntry 33554432}



END
