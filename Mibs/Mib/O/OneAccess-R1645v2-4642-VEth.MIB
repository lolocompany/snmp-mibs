OneAccess-R1645v2-4642-VEth DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2VEth OBJECT IDENTIFIER ::= {r1645Rootv2 4642}

r1645v2VEthMOProp OBJECT-TYPE
   SYNTAX      SEQUENCE OF R1645v2VEthMOPropEntry
   MAX-ACCESS  not-accessible
   STATUS      current
   DESCRIPTION
      ""
   ::= {r1645v2VEth 1}

r1645v2VEthMOPropEntry OBJECT-TYPE
   SYNTAX      R1645v2VEthMOPropEntry
   MAX-ACCESS  not-accessible
   STATUS      current
   DESCRIPTION
      ""
   INDEX      { r1645v2VEthMOPropGlobalIx }
   ::= {r1645v2VEthMOProp 1}

R1645v2VEthMOPropEntry ::=
   SEQUENCE
      {
      r1645v2VEthMOPropPath
         ContainmentPath,
      r1645v2VEthMOPropRev
         ObjectRevision,
      r1645v2VEthMOPropGlobalIx
         GlobalIndex
      }

r1645v2VEthMOPropPath OBJECT-TYPE
   SYNTAX      ContainmentPath
   MAX-ACCESS  read-only
   STATUS      current
   DESCRIPTION
      "Textual description of the containment tree from the instance of
       the root object down to the instance of the current object."
   ::= {r1645v2VEthMOPropEntry 3}

r1645v2VEthMOPropRev OBJECT-TYPE
   SYNTAX      ObjectRevision
   MAX-ACCESS  read-only
   STATUS      current
   DESCRIPTION
      "This value corresponds with the revision of the MANAGED OBJECT."
   ::= {r1645v2VEthMOPropEntry 4}

r1645v2VEthMOPropGlobalIx OBJECT-TYPE
   SYNTAX      GlobalIndex
   MAX-ACCESS  read-only
   STATUS      current
   DESCRIPTION
      "The value of the tlsCntTreeGlobalIndex of the MANAGED OBJECT."
   ::= {r1645v2VEthMOPropEntry 10}



er1645v2VEth OBJECT IDENTIFIER ::= {r1645v2VEth 11}


er1645v2VEthRemark OBJECT IDENTIFIER ::= {er1645v2VEth 321}

er1645v2VEthRemarkTable OBJECT-TYPE
   SYNTAX      SEQUENCE OF Er1645v2VEthRemarkEntry
   MAX-ACCESS  not-accessible
   STATUS      current
   DESCRIPTION
      "intfRemark"
   ::= {er1645v2VEthRemark 1}

er1645v2VEthRemarkEntry OBJECT-TYPE
   SYNTAX      Er1645v2VEthRemarkEntry
   MAX-ACCESS  not-accessible
   STATUS      current
   DESCRIPTION
      ""
   INDEX      { er1645v2VEthRemarkGlobalIx }
   ::= {er1645v2VEthRemarkTable 1}

Er1645v2VEthRemarkEntry ::=
   SEQUENCE
      {
      er1645v2VEthRemarkGlobalIx
         GlobalIndex,
      er1645v2VEthRemarkValue
         DisplayString
      }

er1645v2VEthRemarkGlobalIx OBJECT-TYPE
   SYNTAX      GlobalIndex
   MAX-ACCESS  not-accessible
   STATUS      current
   DESCRIPTION
      "The value of the tlsCntTreeGlobalIndex of the MANAGED OBJECT."
   ::= {er1645v2VEthRemarkEntry 10}

er1645v2VEthRemarkValue OBJECT-TYPE
   SYNTAX      DisplayString
   MAX-ACCESS  read-write
   STATUS      current
   DESCRIPTION
      "Path: virtualEthernet.editConf.remark"
   ::= {er1645v2VEthRemarkEntry 2147483648}


er1645v2VEthArp OBJECT IDENTIFIER ::= {er1645v2VEth 19}

er1645v2VEthArpSSCTable OBJECT-TYPE
   SYNTAX      SEQUENCE OF Er1645v2VEthArpEntry
   MAX-ACCESS  not-accessible
   STATUS      current
   DESCRIPTION
      "ethernet related config parameters"
   ::= {er1645v2VEthArp 1}

er1645v2VEthArpEntry OBJECT-TYPE
   SYNTAX      Er1645v2VEthArpEntry
   MAX-ACCESS  not-accessible
   STATUS      current
   DESCRIPTION
      ""
   INDEX      { er1645v2VEthArpGlobalIx }
   ::= {er1645v2VEthArpSSCTable 1}

Er1645v2VEthArpEntry ::=
   SEQUENCE
      {
      er1645v2VEthArpGlobalIx
         GlobalIndex,
      er1645v2VEthArpTimeOut
         TimeTicks,
      er1645v2VEthArpProxyArp
         INTEGER
      }

er1645v2VEthArpGlobalIx OBJECT-TYPE
   SYNTAX      GlobalIndex
   MAX-ACCESS  not-accessible
   STATUS      current
   DESCRIPTION
      "The value of the tlsCntTreeGlobalIndex of the MANAGED OBJECT."
   ::= {er1645v2VEthArpEntry 10}

er1645v2VEthArpTimeOut OBJECT-TYPE
   SYNTAX      TimeTicks
   MAX-ACCESS  read-write
   STATUS      current
   DESCRIPTION
      "Path: virtualEthernet.editConf.arp.timeOut

       Time in centi-second."
   ::= {er1645v2VEthArpEntry 201326592}

er1645v2VEthArpProxyArp OBJECT-TYPE
   SYNTAX      INTEGER
               {
               disabled (0),
               enabled (1)
               }
   MAX-ACCESS  read-write
   STATUS      current
   DESCRIPTION
      "Path: virtualEthernet.editConf.arp.proxyArp

       Possibilities:
               disabled   (0)
               enabled   (1)"
   ::= {er1645v2VEthArpEntry 838860800}

er1645v2VEthArpStaticArp OBJECT-TYPE
   SYNTAX      SEQUENCE OF Er1645v2VEthArpStaticArpEntry
   MAX-ACCESS  not-accessible
   STATUS      current
   DESCRIPTION
      ""
   ::= {er1645v2VEthArp 50331648}

er1645v2VEthArpStaticArpEntry OBJECT-TYPE
   SYNTAX      Er1645v2VEthArpStaticArpEntry
   MAX-ACCESS  not-accessible
   STATUS      current
   DESCRIPTION
      ""
   INDEX      { er1645v2VEthArpStaticArpGlobalIx,
                er1645v2VEthArpStaticArpTableIx }
   ::= {er1645v2VEthArpStaticArp 1}

Er1645v2VEthArpStaticArpEntry ::=
   SEQUENCE
      {
      er1645v2VEthArpStaticArpActions
         VariableLengthTableActions,
      er1645v2VEthArpStaticArpGlobalIx
         GlobalIndex,
      er1645v2VEthArpStaticArpTableIx
         TableIndex,
      er1645v2VEthArpStaticArpMacAddress
         OCTET STRING,
      er1645v2VEthArpStaticArpIpAddress
         IpAddress
      }

er1645v2VEthArpStaticArpActions OBJECT-TYPE
   SYNTAX      VariableLengthTableActions
   MAX-ACCESS  read-write
   STATUS      current
   DESCRIPTION
      "By way of this field, some manipulations
       on this table may be performed."
   ::= {er1645v2VEthArpStaticArpEntry 2}

er1645v2VEthArpStaticArpGlobalIx OBJECT-TYPE
   SYNTAX      GlobalIndex
   MAX-ACCESS  not-accessible
   STATUS      current
   DESCRIPTION
      "The value of the tlsCntTreeGlobalIndex of the MANAGED OBJECT."
   ::= {er1645v2VEthArpStaticArpEntry 10}

er1645v2VEthArpStaticArpTableIx OBJECT-TYPE
   SYNTAX      TableIndex
   MAX-ACCESS  not-accessible
   STATUS      current
   DESCRIPTION
      ""
   ::= {er1645v2VEthArpStaticArpEntry 11}

er1645v2VEthArpStaticArpMacAddress OBJECT-TYPE
   SYNTAX      OCTET STRING
   MAX-ACCESS  read-write
   STATUS      current
   DESCRIPTION
      "Path: virtualEthernet.editConf.arp.staticArp.macAddress

       MAC address."
   ::= {er1645v2VEthArpStaticArpEntry 16777216}

er1645v2VEthArpStaticArpIpAddress OBJECT-TYPE
   SYNTAX      IpAddress
   MAX-ACCESS  read-write
   STATUS      current
   DESCRIPTION
      "Path: virtualEthernet.editConf.arp.staticArp.ipAddress"
   ::= {er1645v2VEthArpStaticArpEntry 33554432}


er1645v2VEthBrC OBJECT IDENTIFIER ::= {er1645v2VEth 27}

er1645v2VEthBrCSSCTable OBJECT-TYPE
   SYNTAX      SEQUENCE OF Er1645v2VEthBrCEntry
   MAX-ACCESS  not-accessible
   STATUS      current
   DESCRIPTION
      "Set bridging parameters"
   ::= {er1645v2VEthBrC 1}

er1645v2VEthBrCEntry OBJECT-TYPE
   SYNTAX      Er1645v2VEthBrCEntry
   MAX-ACCESS  not-accessible
   STATUS      current
   DESCRIPTION
      ""
   INDEX      { er1645v2VEthBrCGlobalIx }
   ::= {er1645v2VEthBrCSSCTable 1}

Er1645v2VEthBrCEntry ::=
   SEQUENCE
      {
      er1645v2VEthBrCGlobalIx
         GlobalIndex,
      er1645v2VEthBrCAccessList
         DisplayString,
      er1645v2VEthBrCInAccessList
         DisplayString,
      er1645v2VEthBrCTp
         DisplayString,
      er1645v2VEthBrCBridgeGroup
         DisplayString,
      er1645v2VEthBrCLimBC
         INTEGER,
      er1645v2VEthBrCPrivateMode
         INTEGER,
      er1645v2VEthBrCLearning
         INTEGER,
      er1645v2VEthBrCMaxCacheSize
         INTEGER,
      er1645v2VEthBrCRelearnDropOnRelearn
         INTEGER,
      er1645v2VEthBrCRelearnShutdownThreshold
         Integer32,
      er1645v2VEthBrCRelearnShutdownTime
         TimeTicks,
      er1645v2VEthBrCRelearnLoopDetection
         INTEGER,
      er1645v2VEthBrCRelearnLoopDetectionInterval
         TimeTicks,
      er1645v2VEthBrCVlanMemberShip
         INTEGER,
      er1645v2VEthBrCDot1adType
         INTEGER,
      er1645v2VEthBrCPriority
         Integer32,
      er1645v2VEthBrCPathCost
         Integer32,
      er1645v2VEthBrCInternalPathCost
         Integer32,
      er1645v2VEthBrCTCD
         INTEGER,
      er1645v2VEthBrCRestrictedRole
         INTEGER,
      er1645v2VEthBrCAdminEdge
         INTEGER,
      er1645v2VEthBrCMgmtInline
         INTEGER,
      er1645v2VEthBrCL2ptMode
         INTEGER,
      er1645v2VEthBrCL2ptProtocols
         Integer32,
      er1645v2VEthBrCL2ptDestMac
         OCTET STRING,
      er1645v2VEthBrCL2ptCos
         INTEGER,
      er1645v2VEthBrCL2ptDropThrStp
         INTEGER,
      er1645v2VEthBrCL2ptDropThrLldp
         INTEGER,
      er1645v2VEthBrCL2ptDropThrOam
         INTEGER,
      er1645v2VEthBrCL2ptDropThrCdp
         INTEGER,
      er1645v2VEthBrCL2ptDropThrVtp
         INTEGER,
      er1645v2VEthBrCL2ptDropThrLacp
         INTEGER,
      er1645v2VEthBrCL2ptDropThrEfmOam
         INTEGER,
      er1645v2VEthBrCL2ptDropThrPvst
         INTEGER,
      er1645v2VEthBrCL2ptDropThrMmrp
         INTEGER,
      er1645v2VEthBrCL2ptDropThrMvrp
         INTEGER,
      er1645v2VEthBrCL2ptDropThrGvrp
         INTEGER,
      er1645v2VEthBrCL2ptDropThrGmrp
         INTEGER,
      er1645v2VEthBrCL2ptDropThrDtp
         INTEGER,
      er1645v2VEthBrCL2ptDropThrPagp
         INTEGER,
      er1645v2VEthBrCL2ptDropThrUdld
         INTEGER
      }

er1645v2VEthBrCGlobalIx OBJECT-TYPE
   SYNTAX      GlobalIndex
   MAX-ACCESS  not-accessible
   STATUS      current
   DESCRIPTION
      "The value of the tlsCntTreeGlobalIndex of the MANAGED OBJECT."
   ::= {er1645v2VEthBrCEntry 10}

er1645v2VEthBrCAccessList OBJECT-TYPE
   SYNTAX      DisplayString
   MAX-ACCESS  read-write
   STATUS      current
   DESCRIPTION
      "Path: virtualEthernet.editConf.bridging.accessList"
   ::= {er1645v2VEthBrCEntry 83886080}

er1645v2VEthBrCInAccessList OBJECT-TYPE
   SYNTAX      DisplayString
   MAX-ACCESS  read-write
   STATUS      current
   DESCRIPTION
      "Path: virtualEthernet.editConf.bridging.inAccessList"
   ::= {er1645v2VEthBrCEntry 251658240}

er1645v2VEthBrCTp OBJECT-TYPE
   SYNTAX      DisplayString
   MAX-ACCESS  read-write
   STATUS      current
   DESCRIPTION
      "Path: virtualEthernet.editConf.bridging.trafficPolicy"
   ::= {er1645v2VEthBrCEntry 100663296}

er1645v2VEthBrCBridgeGroup OBJECT-TYPE
   SYNTAX      DisplayString
   MAX-ACCESS  read-write
   STATUS      current
   DESCRIPTION
      "Path: virtualEthernet.editConf.bridging.bridgeGroup"
   ::= {er1645v2VEthBrCEntry 117440512}

er1645v2VEthBrCLimBC OBJECT-TYPE
   SYNTAX      INTEGER
               {
               disabled (0),
               enabled (1)
               }
   MAX-ACCESS  read-write
   STATUS      current
   DESCRIPTION
      "Path: virtualEthernet.editConf.bridging.limitBroadcasts

       Possibilities:
               disabled   (0)
               enabled   (1)"
   ::= {er1645v2VEthBrCEntry 134217728}

er1645v2VEthBrCPrivateMode OBJECT-TYPE
   SYNTAX      INTEGER
               {
               disabled (0),
               enabled (1)
               }
   MAX-ACCESS  read-write
   STATUS      current
   DESCRIPTION
      "Path: virtualEthernet.editConf.bridging.privateMode

       Possibilities:
               disabled   (0)
               enabled   (1)"
   ::= {er1645v2VEthBrCEntry 419430400}

er1645v2VEthBrCLearning OBJECT-TYPE
   SYNTAX      INTEGER
               {
               disabled (0),
               enabled (1)
               }
   MAX-ACCESS  read-write
   STATUS      current
   DESCRIPTION
      "Path: virtualEthernet.editConf.bridging.learning

       Possibilities:
               disabled   (0)
               enabled   (1)"
   ::= {er1645v2VEthBrCEntry 201326592}

er1645v2VEthBrCMaxCacheSize OBJECT-TYPE
   SYNTAX      INTEGER
               {
               unlimited (0)
               }
   MAX-ACCESS  read-write
   STATUS      current
   DESCRIPTION
      "Path: virtualEthernet.editConf.bridging.maxCacheSize

       Possibilities:
               unlimited   (0)"
   ::= {er1645v2VEthBrCEntry 218103808}

er1645v2VEthBrCRelearnDropOnRelearn OBJECT-TYPE
   SYNTAX      INTEGER
               {
               disabled (0),
               enabled (1)
               }
   MAX-ACCESS  read-write
   STATUS      current
   DESCRIPTION
      "Path: virtualEthernet.editConf.bridging.relearn.dropOnRelearn

       Possibilities:
               disabled   (0)
               enabled   (1)"
   ::= {er1645v2VEthBrCEntry 234946560}

er1645v2VEthBrCRelearnShutdownThreshold OBJECT-TYPE
   SYNTAX      Integer32
   MAX-ACCESS  read-write
   STATUS      current
   DESCRIPTION
      "Path: virtualEthernet.editConf.bridging.relearn.shutdownThreshold"
   ::= {er1645v2VEthBrCEntry 235012096}

er1645v2VEthBrCRelearnShutdownTime OBJECT-TYPE
   SYNTAX      TimeTicks
   MAX-ACCESS  read-write
   STATUS      current
   DESCRIPTION
      "Path: virtualEthernet.editConf.bridging.relearn.shutdownTime

       Time in centi-second."
   ::= {er1645v2VEthBrCEntry 235077632}

er1645v2VEthBrCRelearnLoopDetection OBJECT-TYPE
   SYNTAX      INTEGER
               {
               disabled (0),
               passive (1),
               active (2)
               }
   MAX-ACCESS  read-write
   STATUS      current
   DESCRIPTION
      "Path: virtualEthernet.editConf.bridging.relearn.loopDetection

       Possibilities:
               disabled   (0)
               passive   (1)
               active   (2)"
   ::= {er1645v2VEthBrCEntry 235143168}

er1645v2VEthBrCRelearnLoopDetectionInterval OBJECT-TYPE
   SYNTAX      TimeTicks
   MAX-ACCESS  read-write
   STATUS      current
   DESCRIPTION
      "Path: virtualEthernet.editConf.bridging.relearn.loopDetectionInterval

       Time in centi-second."
   ::= {er1645v2VEthBrCEntry 235208704}

er1645v2VEthBrCVlanMemberShip OBJECT-TYPE
   SYNTAX      INTEGER
               {
               all (0),
               none (1),
               grouped (2)
               }
   MAX-ACCESS  read-write
   STATUS      current
   DESCRIPTION
      "Path: virtualEthernet.editConf.bridging.vlanMemberShip

       Possibilities:
               all   (0)
               none   (1)
               grouped   (2)"
   ::= {er1645v2VEthBrCEntry 318767104}

er1645v2VEthBrCDot1adType OBJECT-TYPE
   SYNTAX      INTEGER
               {
               slOPTg (0),
               cPort (4),
               sPort (1),
               nni (2)
               }
   MAX-ACCESS  read-write
   STATUS      current
   DESCRIPTION
      "Path: virtualEthernet.editConf.bridging.dot1ad.type

       Possibilities:
               <OPT>   (0)
               cPort   (4)
               sPort   (1)
               nni   (2)"
   ::= {er1645v2VEthBrCEntry 503382016}

er1645v2VEthBrCPriority OBJECT-TYPE
   SYNTAX      Integer32
   MAX-ACCESS  read-write
   STATUS      current
   DESCRIPTION
      "Path: virtualEthernet.editConf.bridging.priority"
   ::= {er1645v2VEthBrCEntry 33554432}

er1645v2VEthBrCPathCost OBJECT-TYPE
   SYNTAX      Integer32
   MAX-ACCESS  read-write
   STATUS      current
   DESCRIPTION
      "Path: virtualEthernet.editConf.bridging.pathCost"
   ::= {er1645v2VEthBrCEntry 50331648}

er1645v2VEthBrCInternalPathCost OBJECT-TYPE
   SYNTAX      Integer32
   MAX-ACCESS  read-write
   STATUS      current
   DESCRIPTION
      "Path: virtualEthernet.editConf.bridging.internalPathCost"
   ::= {er1645v2VEthBrCEntry 301989888}

er1645v2VEthBrCTCD OBJECT-TYPE
   SYNTAX      INTEGER
               {
               disabled (0),
               enabled (1)
               }
   MAX-ACCESS  read-write
   STATUS      current
   DESCRIPTION
      "Path: virtualEthernet.editConf.bridging.topologyChangeDetection

       Possibilities:
               disabled   (0)
               enabled   (1)"
   ::= {er1645v2VEthBrCEntry 67108864}

er1645v2VEthBrCRestrictedRole OBJECT-TYPE
   SYNTAX      INTEGER
               {
               disabled (0),
               enabled (1)
               }
   MAX-ACCESS  read-write
   STATUS      current
   DESCRIPTION
      "Path: virtualEthernet.editConf.bridging.restrictedRole

       Possibilities:
               disabled   (0)
               enabled   (1)"
   ::= {er1645v2VEthBrCEntry 335544320}

er1645v2VEthBrCAdminEdge OBJECT-TYPE
   SYNTAX      INTEGER
               {
               disabled (0),
               enabled (1)
               }
   MAX-ACCESS  read-write
   STATUS      current
   DESCRIPTION
      "Path: virtualEthernet.editConf.bridging.adminEdge

       Possibilities:
               disabled   (0)
               enabled   (1)"
   ::= {er1645v2VEthBrCEntry 268435456}

er1645v2VEthBrCMgmtInline OBJECT-TYPE
   SYNTAX      INTEGER
               {
               disabled (0),
               enabled (1)
               }
   MAX-ACCESS  read-write
   STATUS      current
   DESCRIPTION
      "Path: virtualEthernet.editConf.bridging.mgmtInline

       Possibilities:
               disabled   (0)
               enabled   (1)"
   ::= {er1645v2VEthBrCEntry 369098752}

er1645v2VEthBrCL2ptMode OBJECT-TYPE
   SYNTAX      INTEGER
               {
               disabled (0),
               enabled (1)
               }
   MAX-ACCESS  read-write
   STATUS      current
   DESCRIPTION
      "Path: virtualEthernet.editConf.bridging.l2ProtTunnel.mode

       Possibilities:
               disabled   (0)
               enabled   (1)"
   ::= {er1645v2VEthBrCEntry 403701760}

er1645v2VEthBrCL2ptProtocols OBJECT-TYPE
   SYNTAX      Integer32
   MAX-ACCESS  read-write
   STATUS      current
   DESCRIPTION
      "Path: virtualEthernet.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2VEthBrCEntry 404750336}

er1645v2VEthBrCL2ptDestMac OBJECT-TYPE
   SYNTAX      OCTET STRING
   MAX-ACCESS  read-write
   STATUS      current
   DESCRIPTION
      "Path: virtualEthernet.editConf.bridging.l2ProtTunnel.destinationMac

       MAC address."
   ::= {er1645v2VEthBrCEntry 405798912}

er1645v2VEthBrCL2ptCos OBJECT-TYPE
   SYNTAX      INTEGER
               {
               unchanged (255)
               }
   MAX-ACCESS  read-write
   STATUS      current
   DESCRIPTION
      "Path: virtualEthernet.editConf.bridging.l2ProtTunnel.cos

       Possibilities:
               unchanged   (255)"
   ::= {er1645v2VEthBrCEntry 406847488}

er1645v2VEthBrCL2ptDropThrStp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.stp

       unit name = packets/sec

       Possibilities:
               unlimited   (0)"
   ::= {er1645v2VEthBrCEntry 407900160}

er1645v2VEthBrCL2ptDropThrLldp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.lldp

       unit name = packets/sec

       Possibilities:
               unlimited   (0)"
   ::= {er1645v2VEthBrCEntry 407904256}

er1645v2VEthBrCL2ptDropThrOam OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.oam

       unit name = packets/sec

       Possibilities:
               unlimited   (0)"
   ::= {er1645v2VEthBrCEntry 407908352}

er1645v2VEthBrCL2ptDropThrCdp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.cdp

       unit name = packets/sec

       Possibilities:
               unlimited   (0)"
   ::= {er1645v2VEthBrCEntry 407912448}

er1645v2VEthBrCL2ptDropThrVtp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.vtp

       unit name = packets/sec

       Possibilities:
               unlimited   (0)"
   ::= {er1645v2VEthBrCEntry 407916544}

er1645v2VEthBrCL2ptDropThrLacp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.lacp

       unit name = packets/sec

       Possibilities:
               unlimited   (0)"
   ::= {er1645v2VEthBrCEntry 407920640}

er1645v2VEthBrCL2ptDropThrEfmOam OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.efmOam

       unit name = packets/sec

       Possibilities:
               unlimited   (0)"
   ::= {er1645v2VEthBrCEntry 407924736}

er1645v2VEthBrCL2ptDropThrPvst OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.pvst

       unit name = packets/sec

       Possibilities:
               unlimited   (0)"
   ::= {er1645v2VEthBrCEntry 407928832}

er1645v2VEthBrCL2ptDropThrMmrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.mmrp

       unit name = packets/sec

       Possibilities:
               unlimited   (0)"
   ::= {er1645v2VEthBrCEntry 407932928}

er1645v2VEthBrCL2ptDropThrMvrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.mvrp

       unit name = packets/sec

       Possibilities:
               unlimited   (0)"
   ::= {er1645v2VEthBrCEntry 407937024}

er1645v2VEthBrCL2ptDropThrGvrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.gvrp

       unit name = packets/sec

       Possibilities:
               unlimited   (0)"
   ::= {er1645v2VEthBrCEntry 407941120}

er1645v2VEthBrCL2ptDropThrGmrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.gmrp

       unit name = packets/sec

       Possibilities:
               unlimited   (0)"
   ::= {er1645v2VEthBrCEntry 407945216}

er1645v2VEthBrCL2ptDropThrDtp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.dtp

       unit name = packets/sec

       Possibilities:
               unlimited   (0)"
   ::= {er1645v2VEthBrCEntry 407949312}

er1645v2VEthBrCL2ptDropThrPagp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.pagp

       unit name = packets/sec

       Possibilities:
               unlimited   (0)"
   ::= {er1645v2VEthBrCEntry 407953408}

er1645v2VEthBrCL2ptDropThrUdld OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.udld

       unit name = packets/sec

       Possibilities:
               unlimited   (0)"
   ::= {er1645v2VEthBrCEntry 407957504}


er1645v2VEthVlanTagging OBJECT IDENTIFIER ::= {er1645v2VEth 14}

er1645v2VEthVlanTaggingSSCTable OBJECT-TYPE
   SYNTAX      SEQUENCE OF Er1645v2VEthVlanTaggingEntry
   MAX-ACCESS  not-accessible
   STATUS      current
   DESCRIPTION
      "vlan tagging config"
   ::= {er1645v2VEthVlanTagging 1}

er1645v2VEthVlanTaggingEntry OBJECT-TYPE
   SYNTAX      Er1645v2VEthVlanTaggingEntry
   MAX-ACCESS  not-accessible
   STATUS      current
   DESCRIPTION
      ""
   INDEX      { er1645v2VEthVlanTaggingGlobalIx }
   ::= {er1645v2VEthVlanTaggingSSCTable 1}

Er1645v2VEthVlanTaggingEntry ::=
   SEQUENCE
      {
      er1645v2VEthVlanTaggingGlobalIx
         GlobalIndex,
      er1645v2VEthVlanTaggingUntaggedAction
         INTEGER,
      er1645v2VEthVlanTaggingUntaggedTagInfoTpid
         INTEGER,
      er1645v2VEthVlanTaggingUntaggedTagInfoVid
         Integer32,
      er1645v2VEthVlanTaggingUnknownVlansAction
         INTEGER,
      er1645v2VEthVlanTaggingUnknownVlansTagInfoTpid
         INTEGER,
      er1645v2VEthVlanTaggingUnknownVlansTagInfoVid
         Integer32
      }

er1645v2VEthVlanTaggingGlobalIx OBJECT-TYPE
   SYNTAX      GlobalIndex
   MAX-ACCESS  not-accessible
   STATUS      current
   DESCRIPTION
      "The value of the tlsCntTreeGlobalIndex of the MANAGED OBJECT."
   ::= {er1645v2VEthVlanTaggingEntry 10}

er1645v2VEthVlanTaggingUntaggedAction OBJECT-TYPE
   SYNTAX      INTEGER
               {
               discard (0),
               accept (1),
               tag (2)
               }
   MAX-ACCESS  read-write
   STATUS      current
   DESCRIPTION
      "Path: virtualEthernet.editConf.vlanTagging.untagged.action

       Possibilities:
               discard   (0)
               accept   (1)
               tag   (2)"
   ::= {er1645v2VEthVlanTaggingEntry 671088640}

er1645v2VEthVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlanTagging.untagged.tagInfo.tpid

       Possibilities:
               dot1Q   (33024)
               dot1ad   (34984)
               0x9100   (37120)
               0x9200   (37376)
               0x9300   (37632)"
   ::= {er1645v2VEthVlanTaggingEntry 746586112}

er1645v2VEthVlanTaggingUntaggedTagInfoVid OBJECT-TYPE
   SYNTAX      Integer32
   MAX-ACCESS  read-write
   STATUS      current
   DESCRIPTION
      "Path: virtualEthernet.editConf.vlanTagging.untagged.tagInfo.vid"
   ::= {er1645v2VEthVlanTaggingEntry 754974720}

er1645v2VEthVlanTaggingUnknownVlansAction OBJECT-TYPE
   SYNTAX      INTEGER
               {
               discard (0),
               accept (1),
               tag (2)
               }
   MAX-ACCESS  read-write
   STATUS      current
   DESCRIPTION
      "Path: virtualEthernet.editConf.vlanTagging.unknownVlans.action

       Possibilities:
               discard   (0)
               accept   (1)
               tag   (2)"
   ::= {er1645v2VEthVlanTaggingEntry 1744830464}

er1645v2VEthVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlanTagging.unknownVlans.tagInfo.tpid

       Possibilities:
               dot1Q   (33024)
               dot1ad   (34984)
               0x9100   (37120)
               0x9200   (37376)
               0x9300   (37632)"
   ::= {er1645v2VEthVlanTaggingEntry 1820327936}

er1645v2VEthVlanTaggingUnknownVlansTagInfoVid OBJECT-TYPE
   SYNTAX      Integer32
   MAX-ACCESS  read-write
   STATUS      current
   DESCRIPTION
      "Path: virtualEthernet.editConf.vlanTagging.unknownVlans.tagInfo.vid"
   ::= {er1645v2VEthVlanTaggingEntry 1828716544}

er1645v2VEthVlanTaggingVlans OBJECT-TYPE
   SYNTAX      SEQUENCE OF Er1645v2VEthVlanTaggingVlansEntry
   MAX-ACCESS  not-accessible
   STATUS      current
   DESCRIPTION
      ""
   ::= {er1645v2VEthVlanTagging 1073741824}

er1645v2VEthVlanTaggingVlansEntry OBJECT-TYPE
   SYNTAX      Er1645v2VEthVlanTaggingVlansEntry
   MAX-ACCESS  not-accessible
   STATUS      current
   DESCRIPTION
      ""
   INDEX      { er1645v2VEthVlanTaggingVlansGlobalIx,
                er1645v2VEthVlanTaggingVlansTableIx }
   ::= {er1645v2VEthVlanTaggingVlans 1}

Er1645v2VEthVlanTaggingVlansEntry ::=
   SEQUENCE
      {
      er1645v2VEthVlanTaggingVlansActions
         VariableLengthTableActions,
      er1645v2VEthVlanTaggingVlansGlobalIx
         GlobalIndex,
      er1645v2VEthVlanTaggingVlansTableIx
         TableIndex,
      er1645v2VEthVlanTaggingVlansVid
         Integer32,
      er1645v2VEthVlanTaggingVlansEndVid
         Integer32,
      er1645v2VEthVlanTaggingVlansAction
         INTEGER,
      er1645v2VEthVlanTaggingVlansTagInfoTpid
         INTEGER,
      er1645v2VEthVlanTaggingVlansTagInfoVid
         Integer32
      }

er1645v2VEthVlanTaggingVlansActions OBJECT-TYPE
   SYNTAX      VariableLengthTableActions
   MAX-ACCESS  read-write
   STATUS      current
   DESCRIPTION
      "By way of this field, some manipulations
       on this table may be performed."
   ::= {er1645v2VEthVlanTaggingVlansEntry 2}

er1645v2VEthVlanTaggingVlansGlobalIx OBJECT-TYPE
   SYNTAX      GlobalIndex
   MAX-ACCESS  not-accessible
   STATUS      current
   DESCRIPTION
      "The value of the tlsCntTreeGlobalIndex of the MANAGED OBJECT."
   ::= {er1645v2VEthVlanTaggingVlansEntry 10}

er1645v2VEthVlanTaggingVlansTableIx OBJECT-TYPE
   SYNTAX      TableIndex
   MAX-ACCESS  not-accessible
   STATUS      current
   DESCRIPTION
      ""
   ::= {er1645v2VEthVlanTaggingVlansEntry 11}

er1645v2VEthVlanTaggingVlansVid OBJECT-TYPE
   SYNTAX      Integer32
   MAX-ACCESS  read-write
   STATUS      current
   DESCRIPTION
      "Path: virtualEthernet.editConf.vlanTagging.vlans.vid"
   ::= {er1645v2VEthVlanTaggingVlansEntry 536870912}

er1645v2VEthVlanTaggingVlansEndVid OBJECT-TYPE
   SYNTAX      Integer32
   MAX-ACCESS  read-write
   STATUS      current
   DESCRIPTION
      "Path: virtualEthernet.editConf.vlanTagging.vlans.endVid"
   ::= {er1645v2VEthVlanTaggingVlansEntry 2147483648}

er1645v2VEthVlanTaggingVlansAction OBJECT-TYPE
   SYNTAX      INTEGER
               {
               discard (0),
               accept (1),
               tag (2)
               }
   MAX-ACCESS  read-write
   STATUS      current
   DESCRIPTION
      "Path: virtualEthernet.editConf.vlanTagging.vlans.action

       Possibilities:
               discard   (0)
               accept   (1)
               tag   (2)"
   ::= {er1645v2VEthVlanTaggingVlansEntry 1073741824}

er1645v2VEthVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlanTagging.vlans.tagInfo.tpid

       Possibilities:
               dot1Q   (33024)
               dot1ad   (34984)
               0x9100   (37120)
               0x9200   (37376)
               0x9300   (37632)"
   ::= {er1645v2VEthVlanTaggingVlansEntry 1677721600}

er1645v2VEthVlanTaggingVlansTagInfoVid OBJECT-TYPE
   SYNTAX      Integer32
   MAX-ACCESS  read-write
   STATUS      current
   DESCRIPTION
      "Path: virtualEthernet.editConf.vlanTagging.vlans.tagInfo.vid"
   ::= {er1645v2VEthVlanTaggingVlansEntry 1744830464}


er1645v2VEthOam OBJECT IDENTIFIER ::= {er1645v2VEth 900}

er1645v2VEthOamSSCTable OBJECT-TYPE
   SYNTAX      SEQUENCE OF Er1645v2VEthOamEntry
   MAX-ACCESS  not-accessible
   STATUS      current
   DESCRIPTION
      "OAM mode"
   ::= {er1645v2VEthOam 1}

er1645v2VEthOamEntry OBJECT-TYPE
   SYNTAX      Er1645v2VEthOamEntry
   MAX-ACCESS  not-accessible
   STATUS      current
   DESCRIPTION
      ""
   INDEX      { er1645v2VEthOamGlobalIx }
   ::= {er1645v2VEthOamSSCTable 1}

Er1645v2VEthOamEntry ::=
   SEQUENCE
      {
      er1645v2VEthOamGlobalIx
         GlobalIndex,
      er1645v2VEthOamMode
         INTEGER,
      er1645v2VEthOamLpbkLocalParAction
         INTEGER,
      er1645v2VEthOamLpbkSwapMacAddr
         INTEGER,
      er1645v2VEthOamLoopbackIgnoreRx
         INTEGER,
      er1645v2VEthOamEventsErroredSymbolEnabled
         INTEGER,
      er1645v2VEthOamEventsErroredSymbolWindowHi
         INTEGER,
      er1645v2VEthOamEventsErroredSymbolWindowLo
         INTEGER,
      er1645v2VEthOamEventsErroredSymbolThresholdHi
         Integer32,
      er1645v2VEthOamEventsErroredSymbolThresholdLo
         Integer32,
      er1645v2VEthOamEventsErroredFramePeriodEnabled
         INTEGER,
      er1645v2VEthOamEventsErroredFramePeriodWindow
         INTEGER,
      er1645v2VEthOamEventsErroredFramePeriodThreshold
         Integer32,
      er1645v2VEthOamEventsErroredFrameEnabled
         INTEGER,
      er1645v2VEthOamEventsErroredFrameWindow
         Integer32,
      er1645v2VEthOamEventsErroredFrameThreshold
         Integer32,
      er1645v2VEthOamEventsErroredFrameSecondsEnabled
         INTEGER,
      er1645v2VEthOamEventsErroredFrameSecondsWindow
         Integer32,
      er1645v2VEthOamEventsErroredFrameSecondsThreshold
         Integer32,
      er1645v2VEthOamEventsDyingGasp
         INTEGER,
      er1645v2VEthOamEventsCriticalEvent
         INTEGER
      }

er1645v2VEthOamGlobalIx OBJECT-TYPE
   SYNTAX      GlobalIndex
   MAX-ACCESS  not-accessible
   STATUS      current
   DESCRIPTION
      "The value of the tlsCntTreeGlobalIndex of the MANAGED OBJECT."
   ::= {er1645v2VEthOamEntry 10}

er1645v2VEthOamMode OBJECT-TYPE
   SYNTAX      INTEGER
               {
               disabled (0),
               passive (3),
               active (2)
               }
   MAX-ACCESS  read-write
   STATUS      current
   DESCRIPTION
      "Path: virtualEthernet.editConf.oam.mode

       Possibilities:
               disabled   (0)
               passive   (3)
               active   (2)"
   ::= {er1645v2VEthOamEntry 16777216}

er1645v2VEthOamLpbkLocalParAction OBJECT-TYPE
   SYNTAX      INTEGER
               {
               discard (0),
               forward (1)
               }
   MAX-ACCESS  read-write
   STATUS      current
   DESCRIPTION
      "Path: virtualEthernet.editConf.oam.loopbackLocalParserAction

       Possibilities:
               discard   (0)
               forward   (1)"
   ::= {er1645v2VEthOamEntry 33554432}

er1645v2VEthOamLpbkSwapMacAddr OBJECT-TYPE
   SYNTAX      INTEGER
               {
               disabled (0),
               enabled (1)
               }
   MAX-ACCESS  read-write
   STATUS      current
   DESCRIPTION
      "Path: virtualEthernet.editConf.oam.loopbackSwapMacAddresses

       Possibilities:
               disabled   (0)
               enabled   (1)"
   ::= {er1645v2VEthOamEntry 50331648}

er1645v2VEthOamLoopbackIgnoreRx OBJECT-TYPE
   SYNTAX      INTEGER
               {
               no (0),
               yes (1)
               }
   MAX-ACCESS  read-write
   STATUS      current
   DESCRIPTION
      "Path: virtualEthernet.editConf.oam.loopbackIgnoreRx

       Possibilities:
               no   (0)
               yes   (1)"
   ::= {er1645v2VEthOamEntry 67108864}

er1645v2VEthOamEventsErroredSymbolEnabled OBJECT-TYPE
   SYNTAX      INTEGER
               {
               no (0),
               yes (1)
               }
   MAX-ACCESS  read-write
   STATUS      current
   DESCRIPTION
      "Path: virtualEthernet.editConf.oam.events.erroredSymbol.enabled

       Possibilities:
               no   (0)
               yes   (1)"
   ::= {er1645v2VEthOamEntry 83951872}

er1645v2VEthOamEventsErroredSymbolWindowHi OBJECT-TYPE
   SYNTAX      INTEGER
               {
               default (0)
               }
   UNITS       "symbols"
   MAX-ACCESS  read-write
   STATUS      current
   DESCRIPTION
      "Path: virtualEthernet.editConf.oam.events.erroredSymbol.windowHi

       unit name = symbols

       Possibilities:
               default   (0)"
   ::= {er1645v2VEthOamEntry 83952128}

er1645v2VEthOamEventsErroredSymbolWindowLo OBJECT-TYPE
   SYNTAX      INTEGER
               {
               default (0)
               }
   UNITS       "symbols"
   MAX-ACCESS  read-write
   STATUS      current
   DESCRIPTION
      "Path: virtualEthernet.editConf.oam.events.erroredSymbol.windowLo

       unit name = symbols

       Possibilities:
               default   (0)"
   ::= {er1645v2VEthOamEntry 83952384}

er1645v2VEthOamEventsErroredSymbolThresholdHi OBJECT-TYPE
   SYNTAX      Integer32
   UNITS       "symbols"
   MAX-ACCESS  read-write
   STATUS      current
   DESCRIPTION
      "Path: virtualEthernet.editConf.oam.events.erroredSymbol.thresholdHi

       unit name = symbols"
   ::= {er1645v2VEthOamEntry 83952640}

er1645v2VEthOamEventsErroredSymbolThresholdLo OBJECT-TYPE
   SYNTAX      Integer32
   UNITS       "symbols"
   MAX-ACCESS  read-write
   STATUS      current
   DESCRIPTION
      "Path: virtualEthernet.editConf.oam.events.erroredSymbol.thresholdLo

       unit name = symbols"
   ::= {er1645v2VEthOamEntry 83952896}

er1645v2VEthOamEventsErroredFramePeriodEnabled OBJECT-TYPE
   SYNTAX      INTEGER
               {
               no (0),
               yes (1)
               }
   MAX-ACCESS  read-write
   STATUS      current
   DESCRIPTION
      "Path: virtualEthernet.editConf.oam.events.erroredFramePeriod.enabled

       Possibilities:
               no   (0)
               yes   (1)"
   ::= {er1645v2VEthOamEntry 84017408}

er1645v2VEthOamEventsErroredFramePeriodWindow OBJECT-TYPE
   SYNTAX      INTEGER
               {
               default (0)
               }
   UNITS       "frames"
   MAX-ACCESS  read-write
   STATUS      current
   DESCRIPTION
      "Path: virtualEthernet.editConf.oam.events.erroredFramePeriod.window

       unit name = frames

       Possibilities:
               default   (0)"
   ::= {er1645v2VEthOamEntry 84017664}

er1645v2VEthOamEventsErroredFramePeriodThreshold OBJECT-TYPE
   SYNTAX      Integer32
   UNITS       "frames"
   MAX-ACCESS  read-write
   STATUS      current
   DESCRIPTION
      "Path: virtualEthernet.editConf.oam.events.erroredFramePeriod.threshold

       unit name = frames"
   ::= {er1645v2VEthOamEntry 84017920}

er1645v2VEthOamEventsErroredFrameEnabled OBJECT-TYPE
   SYNTAX      INTEGER
               {
               no (0),
               yes (1)
               }
   MAX-ACCESS  read-write
   STATUS      current
   DESCRIPTION
      "Path: virtualEthernet.editConf.oam.events.erroredFrame.enabled

       Possibilities:
               no   (0)
               yes   (1)"
   ::= {er1645v2VEthOamEntry 84082944}

er1645v2VEthOamEventsErroredFrameWindow OBJECT-TYPE
   SYNTAX      Integer32
   UNITS       "100msec"
   MAX-ACCESS  read-write
   STATUS      current
   DESCRIPTION
      "Path: virtualEthernet.editConf.oam.events.erroredFrame.window

       unit name = 100msec"
   ::= {er1645v2VEthOamEntry 84083200}

er1645v2VEthOamEventsErroredFrameThreshold OBJECT-TYPE
   SYNTAX      Integer32
   UNITS       "frames"
   MAX-ACCESS  read-write
   STATUS      current
   DESCRIPTION
      "Path: virtualEthernet.editConf.oam.events.erroredFrame.threshold

       unit name = frames"
   ::= {er1645v2VEthOamEntry 84083456}

er1645v2VEthOamEventsErroredFrameSecondsEnabled OBJECT-TYPE
   SYNTAX      INTEGER
               {
               no (0),
               yes (1)
               }
   MAX-ACCESS  read-write
   STATUS      current
   DESCRIPTION
      "Path: virtualEthernet.editConf.oam.events.erroredFrameSeconds.enabled

       Possibilities:
               no   (0)
               yes   (1)"
   ::= {er1645v2VEthOamEntry 84148480}

er1645v2VEthOamEventsErroredFrameSecondsWindow OBJECT-TYPE
   SYNTAX      Integer32
   UNITS       "100msec"
   MAX-ACCESS  read-write
   STATUS      current
   DESCRIPTION
      "Path: virtualEthernet.editConf.oam.events.erroredFrameSeconds.window

       unit name = 100msec"
   ::= {er1645v2VEthOamEntry 84148736}

er1645v2VEthOamEventsErroredFrameSecondsThreshold OBJECT-TYPE
   SYNTAX      Integer32
   UNITS       "frames"
   MAX-ACCESS  read-write
   STATUS      current
   DESCRIPTION
      "Path: virtualEthernet.editConf.oam.events.erroredFrameSeconds.threshold

       unit name = frames"
   ::= {er1645v2VEthOamEntry 84148992}

er1645v2VEthOamEventsDyingGasp OBJECT-TYPE
   SYNTAX      INTEGER
               {
               disabled (0),
               enabled (1)
               }
   MAX-ACCESS  read-write
   STATUS      current
   DESCRIPTION
      "Path: virtualEthernet.editConf.oam.events.dyingGasp

       Possibilities:
               disabled   (0)
               enabled   (1)"
   ::= {er1645v2VEthOamEntry 84213760}

er1645v2VEthOamEventsCriticalEvent OBJECT-TYPE
   SYNTAX      INTEGER
               {
               disabled (0),
               enabled (1)
               }
   MAX-ACCESS  read-write
   STATUS      current
   DESCRIPTION
      "Path: virtualEthernet.editConf.oam.events.criticalEvent

       Possibilities:
               disabled   (0)
               enabled   (1)"
   ::= {er1645v2VEthOamEntry 84279296}


er1645v2VEthIp OBJECT IDENTIFIER ::= {er1645v2VEth 1}

er1645v2VEthIpSSCTable OBJECT-TYPE
   SYNTAX      SEQUENCE OF Er1645v2VEthIpEntry
   MAX-ACCESS  not-accessible
   STATUS      current
   DESCRIPTION
      "ip interface config parameters"
   ::= {er1645v2VEthIp 1}

er1645v2VEthIpEntry OBJECT-TYPE
   SYNTAX      Er1645v2VEthIpEntry
   MAX-ACCESS  not-accessible
   STATUS      current
   DESCRIPTION
      ""
   INDEX      { er1645v2VEthIpGlobalIx }
   ::= {er1645v2VEthIpSSCTable 1}

Er1645v2VEthIpEntry ::=
   SEQUENCE
      {
      er1645v2VEthIpGlobalIx
         GlobalIndex,
      er1645v2VEthIpVrfRouter
         DisplayString,
      er1645v2VEthIpAdr
         IpAddress,
      er1645v2VEthIpNetm
         IpAddress,
      er1645v2VEthIpSNetName
         INTEGER,
      er1645v2VEthIpSNetCust
         DisplayString,
      er1645v2VEthIpDhcpC
         INTEGER,
      er1645v2VEthIpDhcpGatewayPreference
         Integer32,
      er1645v2VEthIpDhcpRoutePreference
         Integer32,
      er1645v2VEthIpDhcpDnsPreference
         Integer32,
      er1645v2VEthIpMtu
         Integer32,
      er1645v2VEthIpMssAdjust
         INTEGER,
      er1645v2VEthIpRipMetric
         Integer32,
      er1645v2VEthIpRipMetricOut
         Integer32,
      er1645v2VEthIpRipMode
         INTEGER,
      er1645v2VEthIpRipTxVer
         INTEGER,
      er1645v2VEthIpRipRxVer
         INTEGER,
      er1645v2VEthIpRipSplitH
         INTEGER,
      er1645v2VEthIpRipAuth
         INTEGER,
      er1645v2VEthIpRipFilter
         DisplayString,
      er1645v2VEthIpRipFilterIn
         DisplayString,
      er1645v2VEthIpRipClearNextHop
         INTEGER,
      er1645v2VEthIpAccPol
         DisplayString,
      er1645v2VEthIpAB
         DisplayString,
      er1645v2VEthIpMA
         INTEGER,
      er1645v2VEthIpMF
         Integer32,
      er1645v2VEthIpDB
         INTEGER,
      er1645v2VEthIpIR
         INTEGER,
      er1645v2VEthIpIgmp
         INTEGER,
      er1645v2VEthIpNN
         DisplayString,
      er1645v2VEthIpVrrp
         INTEGER,
      er1645v2VEthIpPimMode
         INTEGER,
      er1645v2VEthIpPimDrPriority
         Counter32,
      er1645v2VEthIpPimHelloTime
         TimeTicks,
      er1645v2VEthIpPimPropagationDelay
         TimeTicks,
      er1645v2VEthIpPimOverrideInterval
         TimeTicks,
      er1645v2VEthIpPimBsrBorder
         INTEGER,
      er1645v2VEthIpPimTtlThreshold
         Integer32,
      er1645v2VEthIpIMNetworkUnreachable
         INTEGER,
      er1645v2VEthIpIMHostUnreachable
         INTEGER,
      er1645v2VEthIpIMProtocolUnreachable
         INTEGER,
      er1645v2VEthIpIMPortUnreachable
         INTEGER,
      er1645v2VEthIpIMMtuExceeded
         INTEGER,
      er1645v2VEthIpIMAdminProhibited
         INTEGER,
      er1645v2VEthIpIMTtlExceeded
         INTEGER,
      er1645v2VEthIpIMRedirect
         INTEGER
      }

er1645v2VEthIpGlobalIx OBJECT-TYPE
   SYNTAX      GlobalIndex
   MAX-ACCESS  not-accessible
   STATUS      current
   DESCRIPTION
      "The value of the tlsCntTreeGlobalIndex of the MANAGED OBJECT."
   ::= {er1645v2VEthIpEntry 10}

er1645v2VEthIpVrfRouter OBJECT-TYPE
   SYNTAX      DisplayString
   MAX-ACCESS  read-write
   STATUS      current
   DESCRIPTION
      "Path: virtualEthernet.editConf.ip.vrfRouter"
   ::= {er1645v2VEthIpEntry 738197504}

er1645v2VEthIpAdr OBJECT-TYPE
   SYNTAX      IpAddress
   MAX-ACCESS  read-write
   STATUS      current
   DESCRIPTION
      "Path: virtualEthernet.editConf.ip.address"
   ::= {er1645v2VEthIpEntry 2030043136}

er1645v2VEthIpNetm OBJECT-TYPE
   SYNTAX      IpAddress
   MAX-ACCESS  read-write
   STATUS      current
   DESCRIPTION
      "Path: virtualEthernet.editConf.ip.netMask"
   ::= {er1645v2VEthIpEntry 2063597568}

er1645v2VEthIpSNetName OBJECT-TYPE
   SYNTAX      INTEGER
               {
               slOPTg (0),
               corp (2),
               dmz (3),
               internet (1)
               }
   MAX-ACCESS  read-write
   STATUS      current
   DESCRIPTION
      "Path: virtualEthernet.editConf.ip.sNet.name

       Possibilities:
               <OPT>   (0)
               corp   (2)
               dmz   (3)
               internet   (1)"
   ::= {er1645v2VEthIpEntry 855703552}

er1645v2VEthIpSNetCust OBJECT-TYPE
   SYNTAX      DisplayString
   MAX-ACCESS  read-write
   STATUS      current
   DESCRIPTION
      "Path: virtualEthernet.editConf.ip.sNet.custom"
   ::= {er1645v2VEthIpEntry 855769088}

er1645v2VEthIpDhcpC OBJECT-TYPE
   SYNTAX      INTEGER
               {
               disabled (0),
               enabled (1)
               }
   MAX-ACCESS  read-write
   STATUS      current
   DESCRIPTION
      "Path: virtualEthernet.editConf.ip.dhcpClient

       Possibilities:
               disabled   (0)
               enabled   (1)"
   ::= {er1645v2VEthIpEntry 838860800}

er1645v2VEthIpDhcpGatewayPreference OBJECT-TYPE
   SYNTAX      Integer32
   MAX-ACCESS  read-write
   STATUS      current
   DESCRIPTION
      "Path: virtualEthernet.editConf.ip.dhcp.gatewayPreference"
   ::= {er1645v2VEthIpEntry 872480768}

er1645v2VEthIpDhcpRoutePreference OBJECT-TYPE
   SYNTAX      Integer32
   MAX-ACCESS  read-write
   STATUS      current
   DESCRIPTION
      "Path: virtualEthernet.editConf.ip.dhcp.routePreference"
   ::= {er1645v2VEthIpEntry 872546304}

er1645v2VEthIpDhcpDnsPreference OBJECT-TYPE
   SYNTAX      Integer32
   MAX-ACCESS  read-write
   STATUS      current
   DESCRIPTION
      "Path: virtualEthernet.editConf.ip.dhcp.dnsPreference"
   ::= {er1645v2VEthIpEntry 872611840}

er1645v2VEthIpMtu OBJECT-TYPE
   SYNTAX      Integer32
   MAX-ACCESS  read-write
   STATUS      current
   DESCRIPTION
      "Path: virtualEthernet.editConf.ip.mtu"
   ::= {er1645v2VEthIpEntry 671088640}

er1645v2VEthIpMssAdjust OBJECT-TYPE
   SYNTAX      INTEGER
               {
               disabled (0),
               auto (65536)
               }
   MAX-ACCESS  read-write
   STATUS      current
   DESCRIPTION
      "Path: virtualEthernet.editConf.ip.mssAdjust

       Possibilities:
               disabled   (0)
               auto   (65536)"
   ::= {er1645v2VEthIpEntry 754974720}

er1645v2VEthIpRipMetric OBJECT-TYPE
   SYNTAX      Integer32
   MAX-ACCESS  read-write
   STATUS      current
   DESCRIPTION
      "Path: virtualEthernet.editConf.ip.rip.metric"
   ::= {er1645v2VEthIpEntry 353566720}

er1645v2VEthIpRipMetricOut OBJECT-TYPE
   SYNTAX      Integer32
   MAX-ACCESS  read-write
   STATUS      current
   DESCRIPTION
      "Path: virtualEthernet.editConf.ip.rip.metricOut"
   ::= {er1645v2VEthIpEntry 353632256}

er1645v2VEthIpRipMode OBJECT-TYPE
   SYNTAX      INTEGER
               {
               disabled (0),
               passive (1),
               active (2)
               }
   MAX-ACCESS  read-write
   STATUS      current
   DESCRIPTION
      "Path: virtualEthernet.editConf.ip.rip.mode

       Possibilities:
               disabled   (0)
               passive   (1)
               active   (2)"
   ::= {er1645v2VEthIpEntry 353697792}

er1645v2VEthIpRipTxVer OBJECT-TYPE
   SYNTAX      INTEGER
               {
               rip1 (0),
               rip2 (1),
               rip1mcompatible (2)
               }
   MAX-ACCESS  read-write
   STATUS      current
   DESCRIPTION
      "Path: virtualEthernet.editConf.ip.rip.txVersion

       Possibilities:
               rip1   (0)
               rip2   (1)
               rip1-compatible   (2)"
   ::= {er1645v2VEthIpEntry 354615296}

er1645v2VEthIpRipRxVer OBJECT-TYPE
   SYNTAX      INTEGER
               {
               rip1only (0),
               rip2only (1),
               rip12 (2)
               }
   MAX-ACCESS  read-write
   STATUS      current
   DESCRIPTION
      "Path: virtualEthernet.editConf.ip.rip.rxVersion

       Possibilities:
               rip1only   (0)
               rip2only   (1)
               rip1&2   (2)"
   ::= {er1645v2VEthIpEntry 354680832}

er1645v2VEthIpRipSplitH OBJECT-TYPE
   SYNTAX      INTEGER
               {
               disabled (0),
               enabled (1),
               poisonedReverse (2)
               }
   MAX-ACCESS  read-write
   STATUS      current
   DESCRIPTION
      "Path: virtualEthernet.editConf.ip.rip.splitHorizon

       Possibilities:
               disabled   (0)
               enabled   (1)
               poisonedReverse   (2)"
   ::= {er1645v2VEthIpEntry 353828864}

er1645v2VEthIpRipAuth OBJECT-TYPE
   SYNTAX      INTEGER
               {
               disabled (0),
               texts (1),
               md5 (2)
               }
   MAX-ACCESS  read-write
   STATUS      current
   DESCRIPTION
      "Path: virtualEthernet.editConf.ip.rip.authentication

       Possibilities:
               disabled   (0)
               text    (1)
               md5   (2)"
   ::= {er1645v2VEthIpEntry 353501184}

er1645v2VEthIpRipFilter OBJECT-TYPE
   SYNTAX      DisplayString
   MAX-ACCESS  read-write
   STATUS      current
   DESCRIPTION
      "Path: virtualEthernet.editConf.ip.rip.filter"
   ::= {er1645v2VEthIpEntry 354418688}

er1645v2VEthIpRipFilterIn OBJECT-TYPE
   SYNTAX      DisplayString
   MAX-ACCESS  read-write
   STATUS      current
   DESCRIPTION
      "Path: virtualEthernet.editConf.ip.rip.filterIn"
   ::= {er1645v2VEthIpEntry 354484224}

er1645v2VEthIpRipClearNextHop OBJECT-TYPE
   SYNTAX      INTEGER
               {
               disabled (0),
               enabled (1)
               }
   MAX-ACCESS  read-write
   STATUS      current
   DESCRIPTION
      "Path: virtualEthernet.editConf.ip.rip.clearNextHop

       Possibilities:
               disabled   (0)
               enabled   (1)"
   ::= {er1645v2VEthIpEntry 352452608}

er1645v2VEthIpAccPol OBJECT-TYPE
   SYNTAX      DisplayString
   MAX-ACCESS  read-write
   STATUS      current
   DESCRIPTION
      "Path: virtualEthernet.editConf.ip.accessPolicy"
   ::= {er1645v2VEthIpEntry 704643072}

er1645v2VEthIpAB OBJECT-TYPE
   SYNTAX      DisplayString
   MAX-ACCESS  read-write
   STATUS      current
   DESCRIPTION
      "Path: virtualEthernet.editConf.ip.trafficPolicy"
   ::= {er1645v2VEthIpEntry 234881024}

er1645v2VEthIpMA OBJECT-TYPE
   SYNTAX      INTEGER
               {
               disabled (0),
               enabled (1)
               }
   MAX-ACCESS  read-write
   STATUS      current
   DESCRIPTION
      "Path: virtualEthernet.editConf.ip.mgmtAccess

       Possibilities:
               disabled   (0)
               enabled   (1)"
   ::= {er1645v2VEthIpEntry 268435456}

er1645v2VEthIpMF OBJECT-TYPE
   SYNTAX      Integer32
   MAX-ACCESS  read-write
   STATUS      current
   DESCRIPTION
      "Path: virtualEthernet.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2VEthIpEntry 285212672}

er1645v2VEthIpDB OBJECT-TYPE
   SYNTAX      INTEGER
               {
               disabled (0),
               enabled (1)
               }
   MAX-ACCESS  read-write
   STATUS      current
   DESCRIPTION
      "Path: virtualEthernet.editConf.ip.directedBroadcasts

       Possibilities:
               disabled   (0)
               enabled   (1)"
   ::= {er1645v2VEthIpEntry 369098752}

er1645v2VEthIpIR OBJECT-TYPE
   SYNTAX      INTEGER
               {
               disabled (0),
               enabled (1)
               }
   MAX-ACCESS  read-write
   STATUS      current
   DESCRIPTION
      "Path: virtualEthernet.editConf.ip.icmpRedirects

       Possibilities:
               disabled   (0)
               enabled   (1)"
   ::= {er1645v2VEthIpEntry 436207616}

er1645v2VEthIpIgmp OBJECT-TYPE
   SYNTAX      INTEGER
               {
               disabled (0),
               proxy (1),
               router (2),
               v3Router (5)
               }
   MAX-ACCESS  read-write
   STATUS      current
   DESCRIPTION
      "Path: virtualEthernet.editConf.ip.igmp

       Possibilities:
               disabled   (0)
               proxy   (1)
               router   (2)
               v3Router   (5)"
   ::= {er1645v2VEthIpEntry 536870912}

er1645v2VEthIpNN OBJECT-TYPE
   SYNTAX      DisplayString
   MAX-ACCESS  read-write
   STATUS      current
   DESCRIPTION
      "Path: virtualEthernet.editConf.ip.nat"
   ::= {er1645v2VEthIpEntry 452984832}

er1645v2VEthIpVrrp OBJECT-TYPE
   SYNTAX      INTEGER
               {
               disabled (0),
               enabled (1)
               }
   MAX-ACCESS  read-write
   STATUS      current
   DESCRIPTION
      "Path: virtualEthernet.editConf.ip.vrrp

       Possibilities:
               disabled   (0)
               enabled   (1)"
   ::= {er1645v2VEthIpEntry 721420288}

er1645v2VEthIpPimMode OBJECT-TYPE
   SYNTAX      INTEGER
               {
               disabled (0),
               sparse (1),
               passive (2)
               }
   MAX-ACCESS  read-write
   STATUS      current
   DESCRIPTION
      "Path: virtualEthernet.editConf.ip.pim.mode

       Possibilities:
               disabled   (0)
               sparse   (1)
               passive   (2)"
   ::= {er1645v2VEthIpEntry 771817472}

er1645v2VEthIpPimDrPriority OBJECT-TYPE
   SYNTAX      Counter32
   MAX-ACCESS  read-write
   STATUS      current
   DESCRIPTION
      "Path: virtualEthernet.editConf.ip.pim.drPriority

       32 bit unsigned wrappable counter."
   ::= {er1645v2VEthIpEntry 771883008}

er1645v2VEthIpPimHelloTime OBJECT-TYPE
   SYNTAX      TimeTicks
   MAX-ACCESS  read-write
   STATUS      current
   DESCRIPTION
      "Path: virtualEthernet.editConf.ip.pim.helloTime

       Time in centi-second."
   ::= {er1645v2VEthIpEntry 771948544}

er1645v2VEthIpPimPropagationDelay OBJECT-TYPE
   SYNTAX      TimeTicks
   MAX-ACCESS  read-write
   STATUS      current
   DESCRIPTION
      "Path: virtualEthernet.editConf.ip.pim.propagationDelay

       Time in centi-second."
   ::= {er1645v2VEthIpEntry 772014080}

er1645v2VEthIpPimOverrideInterval OBJECT-TYPE
   SYNTAX      TimeTicks
   MAX-ACCESS  read-write
   STATUS      current
   DESCRIPTION
      "Path: virtualEthernet.editConf.ip.pim.overrideInterval

       Time in centi-second."
   ::= {er1645v2VEthIpEntry 772079616}

er1645v2VEthIpPimBsrBorder OBJECT-TYPE
   SYNTAX      INTEGER
               {
               disabled (0),
               enabled (1)
               }
   MAX-ACCESS  read-write
   STATUS      current
   DESCRIPTION
      "Path: virtualEthernet.editConf.ip.pim.bsrBorder

       Possibilities:
               disabled   (0)
               enabled   (1)"
   ::= {er1645v2VEthIpEntry 772145152}

er1645v2VEthIpPimTtlThreshold OBJECT-TYPE
   SYNTAX      Integer32
   MAX-ACCESS  read-write
   STATUS      current
   DESCRIPTION
      "Path: virtualEthernet.editConf.ip.pim.ttlThreshold"
   ::= {er1645v2VEthIpEntry 772210688}

er1645v2VEthIpIMNetworkUnreachable OBJECT-TYPE
   SYNTAX      INTEGER
               {
               disabled (0),
               enabled (1)
               }
   MAX-ACCESS  read-write
   STATUS      current
   DESCRIPTION
      "Path: virtualEthernet.editConf.ip.icmpMessages.networkUnreachable

       Possibilities:
               disabled   (0)
               enabled   (1)"
   ::= {er1645v2VEthIpEntry 788594688}

er1645v2VEthIpIMHostUnreachable OBJECT-TYPE
   SYNTAX      INTEGER
               {
               disabled (0),
               enabled (1)
               }
   MAX-ACCESS  read-write
   STATUS      current
   DESCRIPTION
      "Path: virtualEthernet.editConf.ip.icmpMessages.hostUnreachable

       Possibilities:
               disabled   (0)
               enabled   (1)"
   ::= {er1645v2VEthIpEntry 788660224}

er1645v2VEthIpIMProtocolUnreachable OBJECT-TYPE
   SYNTAX      INTEGER
               {
               disabled (0),
               enabled (1)
               }
   MAX-ACCESS  read-write
   STATUS      current
   DESCRIPTION
      "Path: virtualEthernet.editConf.ip.icmpMessages.protocolUnreachable

       Possibilities:
               disabled   (0)
               enabled   (1)"
   ::= {er1645v2VEthIpEntry 788725760}

er1645v2VEthIpIMPortUnreachable OBJECT-TYPE
   SYNTAX      INTEGER
               {
               disabled (0),
               enabled (1)
               }
   MAX-ACCESS  read-write
   STATUS      current
   DESCRIPTION
      "Path: virtualEthernet.editConf.ip.icmpMessages.portUnreachable

       Possibilities:
               disabled   (0)
               enabled   (1)"
   ::= {er1645v2VEthIpEntry 788791296}

er1645v2VEthIpIMMtuExceeded OBJECT-TYPE
   SYNTAX      INTEGER
               {
               disabled (0),
               enabled (1)
               }
   MAX-ACCESS  read-write
   STATUS      current
   DESCRIPTION
      "Path: virtualEthernet.editConf.ip.icmpMessages.mtuExceeded

       Possibilities:
               disabled   (0)
               enabled   (1)"
   ::= {er1645v2VEthIpEntry 788856832}

er1645v2VEthIpIMAdminProhibited OBJECT-TYPE
   SYNTAX      INTEGER
               {
               disabled (0),
               enabled (1)
               }
   MAX-ACCESS  read-write
   STATUS      current
   DESCRIPTION
      "Path: virtualEthernet.editConf.ip.icmpMessages.adminProhibited

       Possibilities:
               disabled   (0)
               enabled   (1)"
   ::= {er1645v2VEthIpEntry 788922368}

er1645v2VEthIpIMTtlExceeded OBJECT-TYPE
   SYNTAX      INTEGER
               {
               disabled (0),
               enabled (1)
               }
   MAX-ACCESS  read-write
   STATUS      current
   DESCRIPTION
      "Path: virtualEthernet.editConf.ip.icmpMessages.ttlExceeded

       Possibilities:
               disabled   (0)
               enabled   (1)"
   ::= {er1645v2VEthIpEntry 788987904}

er1645v2VEthIpIMRedirect OBJECT-TYPE
   SYNTAX      INTEGER
               {
               disabled (0),
               enabled (1)
               }
   MAX-ACCESS  read-write
   STATUS      current
   DESCRIPTION
      "Path: virtualEthernet.editConf.ip.icmpMessages.redirect

       Possibilities:
               disabled   (0)
               enabled   (1)"
   ::= {er1645v2VEthIpEntry 789053440}

er1645v2VEthIpSaddr OBJECT-TYPE
   SYNTAX      SEQUENCE OF Er1645v2VEthIpSaddrEntry
   MAX-ACCESS  not-accessible
   STATUS      current
   DESCRIPTION
      ""
   ::= {er1645v2VEthIp 385875968}

er1645v2VEthIpSaddrEntry OBJECT-TYPE
   SYNTAX      Er1645v2VEthIpSaddrEntry
   MAX-ACCESS  not-accessible
   STATUS      current
   DESCRIPTION
      ""
   INDEX      { er1645v2VEthIpSaddrGlobalIx,
                er1645v2VEthIpSaddrTableIx }
   ::= {er1645v2VEthIpSaddr 1}

Er1645v2VEthIpSaddrEntry ::=
   SEQUENCE
      {
      er1645v2VEthIpSaddrActions
         VariableLengthTableActions,
      er1645v2VEthIpSaddrGlobalIx
         GlobalIndex,
      er1645v2VEthIpSaddrTableIx
         TableIndex,
      er1645v2VEthIpSaddrAddress
         IpAddress,
      er1645v2VEthIpSaddrNetMask
         IpAddress
      }

er1645v2VEthIpSaddrActions OBJECT-TYPE
   SYNTAX      VariableLengthTableActions
   MAX-ACCESS  read-write
   STATUS      current
   DESCRIPTION
      "By way of this field, some manipulations
       on this table may be performed."
   ::= {er1645v2VEthIpSaddrEntry 2}

er1645v2VEthIpSaddrGlobalIx OBJECT-TYPE
   SYNTAX      GlobalIndex
   MAX-ACCESS  not-accessible
   STATUS      current
   DESCRIPTION
      "The value of the tlsCntTreeGlobalIndex of the MANAGED OBJECT."
   ::= {er1645v2VEthIpSaddrEntry 10}

er1645v2VEthIpSaddrTableIx OBJECT-TYPE
   SYNTAX      TableIndex
   MAX-ACCESS  not-accessible
   STATUS      current
   DESCRIPTION
      ""
   ::= {er1645v2VEthIpSaddrEntry 11}

er1645v2VEthIpSaddrAddress OBJECT-TYPE
   SYNTAX      IpAddress
   MAX-ACCESS  read-write
   STATUS      current
   DESCRIPTION
      "Path: virtualEthernet.editConf.ip.secondaryIp.address"
   ::= {er1645v2VEthIpSaddrEntry 2030043136}

er1645v2VEthIpSaddrNetMask OBJECT-TYPE
   SYNTAX      IpAddress
   MAX-ACCESS  read-write
   STATUS      current
   DESCRIPTION
      "Path: virtualEthernet.editConf.ip.secondaryIp.netMask"
   ::= {er1645v2VEthIpSaddrEntry 2063597568}

er1645v2VEthIpH OBJECT-TYPE
   SYNTAX      SEQUENCE OF Er1645v2VEthIpHEntry
   MAX-ACCESS  not-accessible
   STATUS      current
   DESCRIPTION
      ""
   ::= {er1645v2VEthIp 251658240}

er1645v2VEthIpHEntry OBJECT-TYPE
   SYNTAX      Er1645v2VEthIpHEntry
   MAX-ACCESS  not-accessible
   STATUS      current
   DESCRIPTION
      ""
   INDEX      { er1645v2VEthIpHGlobalIx,
                er1645v2VEthIpHTableIx }
   ::= {er1645v2VEthIpH 1}

Er1645v2VEthIpHEntry ::=
   SEQUENCE
      {
      er1645v2VEthIpHActions
         VariableLengthTableActions,
      er1645v2VEthIpHGlobalIx
         GlobalIndex,
      er1645v2VEthIpHTableIx
         TableIndex,
      er1645v2VEthIpHAddress
         IpAddress,
      er1645v2VEthIpHDhcpRelayOptionSubscriberId
         DisplayString
      }

er1645v2VEthIpHActions OBJECT-TYPE
   SYNTAX      VariableLengthTableActions
   MAX-ACCESS  read-write
   STATUS      current
   DESCRIPTION
      "By way of this field, some manipulations
       on this table may be performed."
   ::= {er1645v2VEthIpHEntry 2}

er1645v2VEthIpHGlobalIx OBJECT-TYPE
   SYNTAX      GlobalIndex
   MAX-ACCESS  not-accessible
   STATUS      current
   DESCRIPTION
      "The value of the tlsCntTreeGlobalIndex of the MANAGED OBJECT."
   ::= {er1645v2VEthIpHEntry 10}

er1645v2VEthIpHTableIx OBJECT-TYPE
   SYNTAX      TableIndex
   MAX-ACCESS  not-accessible
   STATUS      current
   DESCRIPTION
      ""
   ::= {er1645v2VEthIpHEntry 11}

er1645v2VEthIpHAddress OBJECT-TYPE
   SYNTAX      IpAddress
   MAX-ACCESS  read-write
   STATUS      current
   DESCRIPTION
      "Path: virtualEthernet.editConf.ip.helpers.address"
   ::= {er1645v2VEthIpHEntry 16777216}

er1645v2VEthIpHDhcpRelayOptionSubscriberId OBJECT-TYPE
   SYNTAX      DisplayString
   MAX-ACCESS  read-write
   STATUS      current
   DESCRIPTION
      "Path: virtualEthernet.editConf.ip.helpers.dhcpRelayOption.subscriberId"
   ::= {er1645v2VEthIpHEntry 33947648}


er1645v2VEthVlan OBJECT IDENTIFIER ::= {er1645v2VEth 33}

er1645v2VEthVlanSSCTable OBJECT-TYPE
   SYNTAX      SEQUENCE OF Er1645v2VEthVlanEntry
   MAX-ACCESS  not-accessible
   STATUS      current
   DESCRIPTION
      ""
   ::= {er1645v2VEthVlan 1}

er1645v2VEthVlanEntry OBJECT-TYPE
   SYNTAX      Er1645v2VEthVlanEntry
   MAX-ACCESS  not-accessible
   STATUS      current
   DESCRIPTION
      ""
   INDEX      { er1645v2VEthVlanGlobalIx,
                er1645v2VEthVlanTableIx }
   ::= {er1645v2VEthVlanSSCTable 1}

Er1645v2VEthVlanEntry ::=
   SEQUENCE
      {
      er1645v2VEthVlanActions
         VariableLengthTableActions,
      er1645v2VEthVlanGlobalIx
         GlobalIndex,
      er1645v2VEthVlanTableIx
         TableIndex,
      er1645v2VEthVlanName
         DisplayString,
      er1645v2VEthVlanRemark
         DisplayString,
      er1645v2VEthVlanAdminStatus
         INTEGER,
      er1645v2VEthVlanMode
         INTEGER,
      er1645v2VEthVlanPriorityPolicy
         DisplayString,
      er1645v2VEthVlanIpVrfRouter
         DisplayString,
      er1645v2VEthVlanIpAdr
         IpAddress,
      er1645v2VEthVlanIpNetm
         IpAddress,
      er1645v2VEthVlanIpSNetName
         INTEGER,
      er1645v2VEthVlanIpSNetCust
         DisplayString,
      er1645v2VEthVlanIpDhcpC
         INTEGER,
      er1645v2VEthVlanIpDhcpGatewayPreference
         Integer32,
      er1645v2VEthVlanIpDhcpRoutePreference
         Integer32,
      er1645v2VEthVlanIpDhcpDnsPreference
         Integer32,
      er1645v2VEthVlanIpMtu
         Integer32,
      er1645v2VEthVlanIpMssAdjust
         INTEGER,
      er1645v2VEthVlanIpRipMetric
         Integer32,
      er1645v2VEthVlanIpRipMetricOut
         Integer32,
      er1645v2VEthVlanIpRipMode
         INTEGER,
      er1645v2VEthVlanIpRipTxVer
         INTEGER,
      er1645v2VEthVlanIpRipRxVer
         INTEGER,
      er1645v2VEthVlanIpRipSplitH
         INTEGER,
      er1645v2VEthVlanIpRipAuth
         INTEGER,
      er1645v2VEthVlanIpRipFilter
         DisplayString,
      er1645v2VEthVlanIpRipFilterIn
         DisplayString,
      er1645v2VEthVlanIpRipClearNextHop
         INTEGER,
      er1645v2VEthVlanIpAccPol
         DisplayString,
      er1645v2VEthVlanIpAB
         DisplayString,
      er1645v2VEthVlanIpMA
         INTEGER,
      er1645v2VEthVlanIpMF
         Integer32,
      er1645v2VEthVlanIpDB
         INTEGER,
      er1645v2VEthVlanIpIR
         INTEGER,
      er1645v2VEthVlanIpIgmp
         INTEGER,
      er1645v2VEthVlanIpNN
         DisplayString,
      er1645v2VEthVlanIpVrrp
         INTEGER,
      er1645v2VEthVlanIpPimMode
         INTEGER,
      er1645v2VEthVlanIpPimDrPriority
         Counter32,
      er1645v2VEthVlanIpPimHelloTime
         TimeTicks,
      er1645v2VEthVlanIpPimPropagationDelay
         TimeTicks,
      er1645v2VEthVlanIpPimOverrideInterval
         TimeTicks,
      er1645v2VEthVlanIpPimBsrBorder
         INTEGER,
      er1645v2VEthVlanIpPimTtlThreshold
         Integer32,
      er1645v2VEthVlanIpIMNetworkUnreachable
         INTEGER,
      er1645v2VEthVlanIpIMHostUnreachable
         INTEGER,
      er1645v2VEthVlanIpIMProtocolUnreachable
         INTEGER,
      er1645v2VEthVlanIpIMPortUnreachable
         INTEGER,
      er1645v2VEthVlanIpIMMtuExceeded
         INTEGER,
      er1645v2VEthVlanIpIMAdminProhibited
         INTEGER,
      er1645v2VEthVlanIpIMTtlExceeded
         INTEGER,
      er1645v2VEthVlanIpIMRedirect
         INTEGER,
      er1645v2VEthVlanIpV6VrfRouter
         DisplayString,
      er1645v2VEthVlanIpV6AddrAutoConfigNrDupAddrDetects
         Integer32,
      er1645v2VEthVlanIpV6AddrAutoConfigAcceptRa
         INTEGER,
      er1645v2VEthVlanIpV6AddrAutoConfigAcceptRaRdnss
         INTEGER,
      er1645v2VEthVlanIpV6AddrAutoConfigAcceptRaDnssl
         INTEGER,
      er1645v2VEthVlanIpV6DefaultRoute
         INTEGER,
      er1645v2VEthVlanIpV6RaSend
         INTEGER,
      er1645v2VEthVlanIpV6RaMinInterval
         TimeTicks,
      er1645v2VEthVlanIpV6RaMaxInterval
         TimeTicks,
      er1645v2VEthVlanIpV6RaManagedFlag
         INTEGER,
      er1645v2VEthVlanIpV6RaOtherConfFlag
         INTEGER,
      er1645v2VEthVlanIpV6RaLinkMtu
         Integer32,
      er1645v2VEthVlanIpV6RaReachableTime
         TimeTicks,
      er1645v2VEthVlanIpV6RaRetransmitTime
         TimeTicks,
      er1645v2VEthVlanIpV6RaHopLimit
         Integer32,
      er1645v2VEthVlanIpV6RaDefaultLifeTime
         TimeTicks,
      er1645v2VEthVlanIpV6RaDnsOptionsRdnssLifeTime
         TimeTicks,
      er1645v2VEthVlanIpV6RaDnsOptionsRdnssImportServers
         INTEGER,
      er1645v2VEthVlanIpV6RaDnsOptionsDnsslLifeTime
         TimeTicks,
      er1645v2VEthVlanIpV6RaDnsOptionsDnsslImportDomains
         INTEGER,
      er1645v2VEthVlanIpV6RsSend
         INTEGER,
      er1645v2VEthVlanIpV6RsMaxRandomDelay
         TimeTicks,
      er1645v2VEthVlanIpV6RsInterval
         TimeTicks,
      er1645v2VEthVlanIpV6RsMaxSolicitations
         Integer32,
      er1645v2VEthVlanIpV6TrafficPolicyInbound
         DisplayString,
      er1645v2VEthVlanIpV6TrafficPolicyOutbound
         DisplayString,
      er1645v2VEthVlanIpV6FirewallZone
         DisplayString,
      er1645v2VEthVlanIpV6DhcpClientAddrAC
         INTEGER,
      er1645v2VEthVlanIpV6DhcpClientPrDelMode
         INTEGER,
      er1645v2VEthVlanIpV6DhcpClientPrDelPool
         DisplayString,
      er1645v2VEthVlanIpV6DhcpClientPrDelPdExclOpt
         INTEGER,
      er1645v2VEthVlanIpV6DhcpClientDnsServerPref
         Integer32,
      er1645v2VEthVlanIpV6DhcpClientRapidCommit
         INTEGER,
      er1645v2VEthVlanIpV6DhcpClientTimersSolTimeOut
         TimeTicks,
      er1645v2VEthVlanIpV6DhcpClientTimersSolMaxRt
         TimeTicks,
      er1645v2VEthVlanIpV6DhcpClientTimersInfoRefresh
         TimeTicks,
      er1645v2VEthVlanIpV6DhcpServerMode
         INTEGER,
      er1645v2VEthVlanIpV6DhcpServerPreference
         Integer32,
      er1645v2VEthVlanIpV6DhcpServerPool
         DisplayString,
      er1645v2VEthVlanIpV6DhcpServerRapidCommit
         INTEGER,
      er1645v2VEthVlanIpV6DhcpServerTimersInfoRefresh
         TimeTicks,
      er1645v2VEthVlanIpV6DhcpRelayMode
         INTEGER,
      er1645v2VEthVlanIpV6SendRedirect
         INTEGER,
      er1645v2VEthVlanIpV6LinkMtu
         Integer32,
      er1645v2VEthVlanIpV6InterfaceId
         OCTET STRING,
      er1645v2VEthVlanIpV6MF
         Integer32,
      er1645v2VEthVlanIpV6IcmpMessagesNoRoute
         INTEGER,
      er1645v2VEthVlanIpV6IcmpMessagesBeyondScope
         INTEGER,
      er1645v2VEthVlanIpV6IcmpMessagesAddressUnreachable
         INTEGER,
      er1645v2VEthVlanIpV6IcmpMessagesPortUnreachable
         INTEGER,
      er1645v2VEthVlanIpV6IcmpMessagesPacketTooBig
         INTEGER,
      er1645v2VEthVlanIpV6IcmpMessagesHopLimitExceeded
         INTEGER,
      er1645v2VEthVlanIpV6IcmpMessagesFragTimeExceeded
         INTEGER,
      er1645v2VEthVlanIpV6IcmpMessagesHeaderFieldErr
         INTEGER,
      er1645v2VEthVlanIpV6IcmpMessagesOptionUnrecognized
         INTEGER,
      er1645v2VEthVlanIpV6IcmpMessagesRedirect
         INTEGER,
      er1645v2VEthVlanBridgingAccList
         DisplayString,
      er1645v2VEthVlanBridgingInACL
         DisplayString,
      er1645v2VEthVlanBridgingTp
         DisplayString,
      er1645v2VEthVlanBridgingBrGrp
         DisplayString,
      er1645v2VEthVlanBridgingLimBC
         INTEGER,
      er1645v2VEthVlanBridgingPrivateMode
         INTEGER,
      er1645v2VEthVlanBridgingLearning
         INTEGER,
      er1645v2VEthVlanBridgingMaxCacheSize
         INTEGER,
      er1645v2VEthVlanBridgingRelearnDropOnRelearn
         INTEGER,
      er1645v2VEthVlanBridgingRelearnShutdownThreshold
         Integer32,
      er1645v2VEthVlanBridgingRelearnShutdownTime
         TimeTicks,
      er1645v2VEthVlanBridgingRelearnLoopDetection
         INTEGER,
      er1645v2VEthVlanBridgingRelearnLoopDetectionInterval
         TimeTicks,
      er1645v2VEthVlanBridgingVlanMemberShip
         INTEGER,
      er1645v2VEthVlanBridgingVlTUntaggedAction
         INTEGER,
      er1645v2VEthVlanBridgingVlTUntaggedTagInfoTpid
         INTEGER,
      er1645v2VEthVlanBridgingVlTUntaggedTagInfoVid
         Integer32,
      er1645v2VEthVlanBridgingVlTUnknownVlansAction
         INTEGER,
      er1645v2VEthVlanBridgingVlTUnknownVlansTagInfoTpid
         INTEGER,
      er1645v2VEthVlanBridgingVlTUnknownVlansTagInfoVid
         Integer32,
      er1645v2VEthVlanBridgingDot1adType
         INTEGER,
      er1645v2VEthVlanBridgingPriority
         Integer32,
      er1645v2VEthVlanBridgingPathCost
         Integer32,
      er1645v2VEthVlanBridgingInternalPathCost
         Integer32,
      er1645v2VEthVlanBridgingTCD
         INTEGER,
      er1645v2VEthVlanBridgingRestrictedRole
         INTEGER,
      er1645v2VEthVlanBridgingAdminEdge
         INTEGER,
      er1645v2VEthVlanBridgingOamMacDeviceMac
         DisplayString,
      er1645v2VEthVlanBridgingOamMacUserMac
         OCTET STRING,
      er1645v2VEthVlanBridgingOamMacBridgeMac
         DisplayString,
      er1645v2VEthVlanBridgingMgmtInline
         INTEGER,
      er1645v2VEthVlanBridgingL2ptMode
         INTEGER,
      er1645v2VEthVlanBridgingL2ptProtocols
         Integer32,
      er1645v2VEthVlanBridgingL2ptDestMac
         OCTET STRING,
      er1645v2VEthVlanBridgingL2ptCos
         INTEGER,
      er1645v2VEthVlanBridgingL2ptDropThrStp
         INTEGER,
      er1645v2VEthVlanBridgingL2ptDropThrLldp
         INTEGER,
      er1645v2VEthVlanBridgingL2ptDropThrOam
         INTEGER,
      er1645v2VEthVlanBridgingL2ptDropThrCdp
         INTEGER,
      er1645v2VEthVlanBridgingL2ptDropThrVtp
         INTEGER,
      er1645v2VEthVlanBridgingL2ptDropThrLacp
         INTEGER,
      er1645v2VEthVlanBridgingL2ptDropThrEfmOam
         INTEGER,
      er1645v2VEthVlanBridgingL2ptDropThrPvst
         INTEGER,
      er1645v2VEthVlanBridgingL2ptDropThrMmrp
         INTEGER,
      er1645v2VEthVlanBridgingL2ptDropThrMvrp
         INTEGER,
      er1645v2VEthVlanBridgingL2ptDropThrGvrp
         INTEGER,
      er1645v2VEthVlanBridgingL2ptDropThrGmrp
         INTEGER,
      er1645v2VEthVlanBridgingL2ptDropThrDtp
         INTEGER,
      er1645v2VEthVlanBridgingL2ptDropThrPagp
         INTEGER,
      er1645v2VEthVlanBridgingL2ptDropThrUdld
         INTEGER,
      er1645v2VEthVlanVlanVid
         INTEGER,
      er1645v2VEthVlanVlanVidExtensionSingle
         OCTET STRING,
      er1645v2VEthVlanVlanVidExtensionEndVid
         Integer32,
      er1645v2VEthVlanVlanTpid
         INTEGER,
      er1645v2VEthVlanVlanTagSign
         INTEGER,
      er1645v2VEthVlanVlanChTos
         INTEGER,
      er1645v2VEthVlanVlanCTMapP0
         INTEGER,
      er1645v2VEthVlanVlanCTMapP1
         INTEGER,
      er1645v2VEthVlanVlanCTMapP2
         INTEGER,
      er1645v2VEthVlanVlanCTMapP3
         INTEGER,
      er1645v2VEthVlanVlanCTMapP4
         INTEGER,
      er1645v2VEthVlanVlanCTMapP5
         INTEGER,
      er1645v2VEthVlanVlanCTMapP6
         INTEGER,
      er1645v2VEthVlanVlanCTMapP7
         INTEGER,
      er1645v2VEthVlanVlanTxCos
         INTEGER,
      er1645v2VEthVlanVlanCCMapP0
         Integer32,
      er1645v2VEthVlanVlanCCMapP1
         Integer32,
      er1645v2VEthVlanVlanCCMapP2
         Integer32,
      er1645v2VEthVlanVlanCCMapP3
         Integer32,
      er1645v2VEthVlanVlanCCMapP4
         Integer32,
      er1645v2VEthVlanVlanCCMapP5
         Integer32,
      er1645v2VEthVlanVlanCCMapP6
         Integer32,
      er1645v2VEthVlanVlanCCMapP7
         Integer32,
      er1645v2VEthVlanVlanQCMapQueue1
         Integer32,
      er1645v2VEthVlanVlanQCMapQueue2
         Integer32,
      er1645v2VEthVlanVlanQCMapQueue3
         Integer32,
      er1645v2VEthVlanVlanQCMapQueue4
         Integer32,
      er1645v2VEthVlanVlanQCMapQueue5
         Integer32,
      er1645v2VEthVlanVlanQCMapLowDelayQueue
         Integer32,
      er1645v2VEthVlanVlanQCMapLowDelay2Queue
         Integer32,
      er1645v2VEthVlanVlanQCMapSystemQueue
         Integer32,
      er1645v2VEthVlanVlanQinQSVid
         Integer32,
      er1645v2VEthVlanVlanQinQSTpid
         INTEGER,
      er1645v2VEthVlanVlanArpTimeOut
         TimeTicks,
      er1645v2VEthVlanVlanArpProxyArp
         INTEGER,
      er1645v2VEthVlanBandwidthMode
         INTEGER,
      er1645v2VEthVlanBandwidthCir
         Integer32,
      er1645v2VEthVlanBandwidthEir
         Integer32,
      er1645v2VEthVlanBandwidthUnit
         INTEGER,
      er1645v2VEthVlanBandwidthTc
         INTEGER,
      er1645v2VEthVlanBandwidthTcFactor
         INTEGER,
      er1645v2VEthVlanBandwidthCorrType
         INTEGER,
      er1645v2VEthVlanBandwidthCorrPredefEncapsFrameRelay
         DisplayString,
      er1645v2VEthVlanBandwidthCorrPredefEncapsPpp
         DisplayString,
      er1645v2VEthVlanBandwidthCorrPredefEncapsAtmHl
         INTEGER,
      er1645v2VEthVlanBandwidthCorrPredefEncapsAtmMp
         INTEGER,
      er1645v2VEthVlanBandwidthCorrPredefEncapsHdlc
         DisplayString,
      er1645v2VEthVlanBandwidthCorrPredefEncapsEfmFs
         Integer32,
      er1645v2VEthVlanBandwidthCorrPredefEncapsEfmIb
         Integer32,
      er1645v2VEthVlanBandwidthCorrPredefMode
         INTEGER,
      er1645v2VEthVlanBandwidthCorrManualOverhead
         Integer32,
      er1645v2VEthVlanBandwidthCorrManualFrameData
         Counter32,
      er1645v2VEthVlanBandwidthCorrManualFrameHeader
         Counter32,
      er1645v2VEthVlanBandwidthMaxFifoQLen
         Integer32,
      er1645v2VEthVlanBandwidthDeFlagCir
         INTEGER,
      er1645v2VEthVlanBandwidthDeFlagEir
         INTEGER,
      er1645v2VEthVlanBandwidthDeFlagViolate
         INTEGER,
      er1645v2VEthVlanBandwidthActCirActNone
         OCTET STRING,
      er1645v2VEthVlanBandwidthActCirActEthCos1
         INTEGER,
      er1645v2VEthVlanBandwidthActCirActEthDei1
         INTEGER,
      er1645v2VEthVlanBandwidthActCirActEthCos2
         INTEGER,
      er1645v2VEthVlanBandwidthActCirActEthDei2
         INTEGER,
      er1645v2VEthVlanBandwidthActCirActEthCos3
         INTEGER,
      er1645v2VEthVlanBandwidthActCirActEthDei3
         INTEGER,
      er1645v2VEthVlanBandwidthActCirActEthCos4
         INTEGER,
      er1645v2VEthVlanBandwidthActCirActEthDei4
         INTEGER,
      er1645v2VEthVlanBandwidthActCirActEthCos5
         INTEGER,
      er1645v2VEthVlanBandwidthActCirActEthDei5
         INTEGER,
      er1645v2VEthVlanBandwidthActCirActEthCos6
         INTEGER,
      er1645v2VEthVlanBandwidthActCirActEthDei6
         INTEGER,
      er1645v2VEthVlanBandwidthActCirActEthCos7
         INTEGER,
      er1645v2VEthVlanBandwidthActCirActEthDei7
         INTEGER,
      er1645v2VEthVlanBandwidthActCirActEthCos8
         INTEGER,
      er1645v2VEthVlanBandwidthActCirActEthDei8
         INTEGER,
      er1645v2VEthVlanBandwidthActCirActEthTos
         INTEGER,
      er1645v2VEthVlanBandwidthActCirActEthQueue
         INTEGER,
      er1645v2VEthVlanBandwidthActCirActEthDrpLev
         INTEGER,
      er1645v2VEthVlanBandwidthActCirActEthDeFlag
         INTEGER,
      er1645v2VEthVlanBandwidthActCirActIpTos
         INTEGER,
      er1645v2VEthVlanBandwidthActCirActIpQueue
         INTEGER,
      er1645v2VEthVlanBandwidthActCirActIpDrpLev
         INTEGER,
      er1645v2VEthVlanBandwidthActCirActIpDeFlag
         INTEGER,
      er1645v2VEthVlanBandwidthActEirActNone
         OCTET STRING,
      er1645v2VEthVlanBandwidthActEirActEthCos1
         INTEGER,
      er1645v2VEthVlanBandwidthActEirActEthDei1
         INTEGER,
      er1645v2VEthVlanBandwidthActEirActEthCos2
         INTEGER,
      er1645v2VEthVlanBandwidthActEirActEthDei2
         INTEGER,
      er1645v2VEthVlanBandwidthActEirActEthCos3
         INTEGER,
      er1645v2VEthVlanBandwidthActEirActEthDei3
         INTEGER,
      er1645v2VEthVlanBandwidthActEirActEthCos4
         INTEGER,
      er1645v2VEthVlanBandwidthActEirActEthDei4
         INTEGER,
      er1645v2VEthVlanBandwidthActEirActEthCos5
         INTEGER,
      er1645v2VEthVlanBandwidthActEirActEthDei5
         INTEGER,
      er1645v2VEthVlanBandwidthActEirActEthCos6
         INTEGER,
      er1645v2VEthVlanBandwidthActEirActEthDei6
         INTEGER,
      er1645v2VEthVlanBandwidthActEirActEthCos7
         INTEGER,
      er1645v2VEthVlanBandwidthActEirActEthDei7
         INTEGER,
      er1645v2VEthVlanBandwidthActEirActEthCos8
         INTEGER,
      er1645v2VEthVlanBandwidthActEirActEthDei8
         INTEGER,
      er1645v2VEthVlanBandwidthActEirActEthTos
         INTEGER,
      er1645v2VEthVlanBandwidthActEirActEthQueue
         INTEGER,
      er1645v2VEthVlanBandwidthActEirActEthDrpLev
         INTEGER,
      er1645v2VEthVlanBandwidthActEirActEthDeFlag
         INTEGER,
      er1645v2VEthVlanBandwidthActEirActIpTos
         INTEGER,
      er1645v2VEthVlanBandwidthActEirActIpQueue
         INTEGER,
      er1645v2VEthVlanBandwidthActEirActIpDrpLev
         INTEGER,
      er1645v2VEthVlanBandwidthActEirActIpDeFlag
         INTEGER,
      er1645v2VEthVlanBandwidthActViolActNone
         OCTET STRING,
      er1645v2VEthVlanBandwidthActViolActDrop
         OCTET STRING,
      er1645v2VEthVlanBandwidthActViolActEthCos1
         INTEGER,
      er1645v2VEthVlanBandwidthActViolActEthDei1
         INTEGER,
      er1645v2VEthVlanBandwidthActViolActEthCos2
         INTEGER,
      er1645v2VEthVlanBandwidthActViolActEthDei2
         INTEGER,
      er1645v2VEthVlanBandwidthActViolActEthCos3
         INTEGER,
      er1645v2VEthVlanBandwidthActViolActEthDei3
         INTEGER,
      er1645v2VEthVlanBandwidthActViolActEthCos4
         INTEGER,
      er1645v2VEthVlanBandwidthActViolActEthDei4
         INTEGER,
      er1645v2VEthVlanBandwidthActViolActEthCos5
         INTEGER,
      er1645v2VEthVlanBandwidthActViolActEthDei5
         INTEGER,
      er1645v2VEthVlanBandwidthActViolActEthCos6
         INTEGER,
      er1645v2VEthVlanBandwidthActViolActEthDei6
         INTEGER,
      er1645v2VEthVlanBandwidthActViolActEthCos7
         INTEGER,
      er1645v2VEthVlanBandwidthActViolActEthDei7
         INTEGER,
      er1645v2VEthVlanBandwidthActViolActEthCos8
         INTEGER,
      er1645v2VEthVlanBandwidthActViolActEthDei8
         INTEGER,
      er1645v2VEthVlanBandwidthActViolActEthTos
         INTEGER,
      er1645v2VEthVlanBandwidthActViolActEthQueue
         INTEGER,
      er1645v2VEthVlanBandwidthActViolActEthDrpLev
         INTEGER,
      er1645v2VEthVlanBandwidthActViolActEthDeFlag
         INTEGER,
      er1645v2VEthVlanBandwidthActViolActIpTos
         INTEGER,
      er1645v2VEthVlanBandwidthActViolActIpQueue
         INTEGER,
      er1645v2VEthVlanBandwidthActViolActIpDrpLev
         INTEGER,
      er1645v2VEthVlanBandwidthActViolActIpDeFlag
         INTEGER,
      er1645v2VEthVlanInbBwMode
         INTEGER,
      er1645v2VEthVlanInbBwCir
         Integer32,
      er1645v2VEthVlanInbBwEir
         Integer32,
      er1645v2VEthVlanInbBwUnit
         INTEGER,
      er1645v2VEthVlanInbBwTc
         INTEGER,
      er1645v2VEthVlanInbBwTcFactor
         INTEGER,
      er1645v2VEthVlanInbBwCorrType
         INTEGER,
      er1645v2VEthVlanInbBwCorrPredefEncapsFrameRelay
         DisplayString,
      er1645v2VEthVlanInbBwCorrPredefEncapsPpp
         DisplayString,
      er1645v2VEthVlanInbBwCorrPredefEncapsAtmHl
         INTEGER,
      er1645v2VEthVlanInbBwCorrPredefEncapsAtmMp
         INTEGER,
      er1645v2VEthVlanInbBwCorrPredefEncapsHdlc
         DisplayString,
      er1645v2VEthVlanInbBwCorrPredefEncapsEfmFs
         Integer32,
      er1645v2VEthVlanInbBwCorrPredefEncapsEfmIb
         Integer32,
      er1645v2VEthVlanInbBwCorrPredefMode
         INTEGER,
      er1645v2VEthVlanInbBwCorrManualOverhead
         Integer32,
      er1645v2VEthVlanInbBwCorrManualFrameData
         Counter32,
      er1645v2VEthVlanInbBwCorrManualFrameHeader
         Counter32,
      er1645v2VEthVlanInbBwMaxFifoQLen
         Integer32,
      er1645v2VEthVlanInbBwPriorityPolicy
         DisplayString,
      er1645v2VEthVlanInbBwDeFlagCir
         INTEGER,
      er1645v2VEthVlanInbBwDeFlagEir
         INTEGER,
      er1645v2VEthVlanInbBwDeFlagViolate
         INTEGER,
      er1645v2VEthVlanInbBwActCirActNone
         OCTET STRING,
      er1645v2VEthVlanInbBwActCirActEthCos1
         INTEGER,
      er1645v2VEthVlanInbBwActCirActEthDei1
         INTEGER,
      er1645v2VEthVlanInbBwActCirActEthCos2
         INTEGER,
      er1645v2VEthVlanInbBwActCirActEthDei2
         INTEGER,
      er1645v2VEthVlanInbBwActCirActEthCos3
         INTEGER,
      er1645v2VEthVlanInbBwActCirActEthDei3
         INTEGER,
      er1645v2VEthVlanInbBwActCirActEthCos4
         INTEGER,
      er1645v2VEthVlanInbBwActCirActEthDei4
         INTEGER,
      er1645v2VEthVlanInbBwActCirActEthCos5
         INTEGER,
      er1645v2VEthVlanInbBwActCirActEthDei5
         INTEGER,
      er1645v2VEthVlanInbBwActCirActEthCos6
         INTEGER,
      er1645v2VEthVlanInbBwActCirActEthDei6
         INTEGER,
      er1645v2VEthVlanInbBwActCirActEthCos7
         INTEGER,
      er1645v2VEthVlanInbBwActCirActEthDei7
         INTEGER,
      er1645v2VEthVlanInbBwActCirActEthCos8
         INTEGER,
      er1645v2VEthVlanInbBwActCirActEthDei8
         INTEGER,
      er1645v2VEthVlanInbBwActCirActEthTos
         INTEGER,
      er1645v2VEthVlanInbBwActCirActEthQueue
         INTEGER,
      er1645v2VEthVlanInbBwActCirActEthDrpLev
         INTEGER,
      er1645v2VEthVlanInbBwActCirActEthDeFlag
         INTEGER,
      er1645v2VEthVlanInbBwActCirActIpTos
         INTEGER,
      er1645v2VEthVlanInbBwActCirActIpQueue
         INTEGER,
      er1645v2VEthVlanInbBwActCirActIpDrpLev
         INTEGER,
      er1645v2VEthVlanInbBwActCirActIpDeFlag
         INTEGER,
      er1645v2VEthVlanInbBwActEirActNone
         OCTET STRING,
      er1645v2VEthVlanInbBwActEirActEthCos1
         INTEGER,
      er1645v2VEthVlanInbBwActEirActEthDei1
         INTEGER,
      er1645v2VEthVlanInbBwActEirActEthCos2
         INTEGER,
      er1645v2VEthVlanInbBwActEirActEthDei2
         INTEGER,
      er1645v2VEthVlanInbBwActEirActEthCos3
         INTEGER,
      er1645v2VEthVlanInbBwActEirActEthDei3
         INTEGER,
      er1645v2VEthVlanInbBwActEirActEthCos4
         INTEGER,
      er1645v2VEthVlanInbBwActEirActEthDei4
         INTEGER,
      er1645v2VEthVlanInbBwActEirActEthCos5
         INTEGER,
      er1645v2VEthVlanInbBwActEirActEthDei5
         INTEGER,
      er1645v2VEthVlanInbBwActEirActEthCos6
         INTEGER,
      er1645v2VEthVlanInbBwActEirActEthDei6
         INTEGER,
      er1645v2VEthVlanInbBwActEirActEthCos7
         INTEGER,
      er1645v2VEthVlanInbBwActEirActEthDei7
         INTEGER,
      er1645v2VEthVlanInbBwActEirActEthCos8
         INTEGER,
      er1645v2VEthVlanInbBwActEirActEthDei8
         INTEGER,
      er1645v2VEthVlanInbBwActEirActEthTos
         INTEGER,
      er1645v2VEthVlanInbBwActEirActEthQueue
         INTEGER,
      er1645v2VEthVlanInbBwActEirActEthDrpLev
         INTEGER,
      er1645v2VEthVlanInbBwActEirActEthDeFlag
         INTEGER,
      er1645v2VEthVlanInbBwActEirActIpTos
         INTEGER,
      er1645v2VEthVlanInbBwActEirActIpQueue
         INTEGER,
      er1645v2VEthVlanInbBwActEirActIpDrpLev
         INTEGER,
      er1645v2VEthVlanInbBwActEirActIpDeFlag
         INTEGER,
      er1645v2VEthVlanInbBwActViolActNone
         OCTET STRING,
      er1645v2VEthVlanInbBwActViolActDrop
         OCTET STRING,
      er1645v2VEthVlanInbBwActViolActEthCos1
         INTEGER,
      er1645v2VEthVlanInbBwActViolActEthDei1
         INTEGER,
      er1645v2VEthVlanInbBwActViolActEthCos2
         INTEGER,
      er1645v2VEthVlanInbBwActViolActEthDei2
         INTEGER,
      er1645v2VEthVlanInbBwActViolActEthCos3
         INTEGER,
      er1645v2VEthVlanInbBwActViolActEthDei3
         INTEGER,
      er1645v2VEthVlanInbBwActViolActEthCos4
         INTEGER,
      er1645v2VEthVlanInbBwActViolActEthDei4
         INTEGER,
      er1645v2VEthVlanInbBwActViolActEthCos5
         INTEGER,
      er1645v2VEthVlanInbBwActViolActEthDei5
         INTEGER,
      er1645v2VEthVlanInbBwActViolActEthCos6
         INTEGER,
      er1645v2VEthVlanInbBwActViolActEthDei6
         INTEGER,
      er1645v2VEthVlanInbBwActViolActEthCos7
         INTEGER,
      er1645v2VEthVlanInbBwActViolActEthDei7
         INTEGER,
      er1645v2VEthVlanInbBwActViolActEthCos8
         INTEGER,
      er1645v2VEthVlanInbBwActViolActEthDei8
         INTEGER,
      er1645v2VEthVlanInbBwActViolActEthTos
         INTEGER,
      er1645v2VEthVlanInbBwActViolActEthQueue
         INTEGER,
      er1645v2VEthVlanInbBwActViolActEthDrpLev
         INTEGER,
      er1645v2VEthVlanInbBwActViolActEthDeFlag
         INTEGER,
      er1645v2VEthVlanInbBwActViolActIpTos
         INTEGER,
      er1645v2VEthVlanInbBwActViolActIpQueue
         INTEGER,
      er1645v2VEthVlanInbBwActViolActIpDrpLev
         INTEGER,
      er1645v2VEthVlanInbBwActViolActIpDeFlag
         INTEGER,
      er1645v2VEthVlanPppoE
         INTEGER,
      er1645v2VEthVlanPppLnkMOperation
         INTEGER,
      er1645v2VEthVlanPppLnkMInterval
         TimeTicks,
      er1645v2VEthVlanPppLnkMRepTimeOut
         TimeTicks,
      er1645v2VEthVlanPppLnkMFailsPrmt
         Integer32,
      er1645v2VEthVlanPppAuthentication
         INTEGER,
      er1645v2VEthVlanPppAuthenPeriod
         TimeTicks,
      er1645v2VEthVlanPppSessionName
         DisplayString,
      er1645v2VEthVlanPppSessionSecret
         DisplayString,
      er1645v2VEthVlanPppEncModeSessionSecret
         INTEGER,
      er1645v2VEthVlanPppEncSessionSecret
         DisplayString,
      er1645v2VEthVlanPppServiceName
         DisplayString,
      er1645v2VEthVlanPbbMode
         INTEGER,
      er1645v2VEthVlanPbbTxCos
         Integer32,
      er1645v2VEthVlanPbbIsid
         Integer32,
      er1645v2VEthVlanPbbDestMac
         OCTET STRING,
      er1645v2VEthVlanPbbCustomGroupMac
         OCTET STRING
      }

er1645v2VEthVlanActions OBJECT-TYPE
   SYNTAX      VariableLengthTableActions
   MAX-ACCESS  read-write
   STATUS      current
   DESCRIPTION
      "By way of this field, some manipulations
       on this table may be performed."
   ::= {er1645v2VEthVlanEntry 2}

er1645v2VEthVlanGlobalIx OBJECT-TYPE
   SYNTAX      GlobalIndex
   MAX-ACCESS  not-accessible
   STATUS      current
   DESCRIPTION
      "The value of the tlsCntTreeGlobalIndex of the MANAGED OBJECT."
   ::= {er1645v2VEthVlanEntry 10}

er1645v2VEthVlanTableIx OBJECT-TYPE
   SYNTAX      TableIndex
   MAX-ACCESS  not-accessible
   STATUS      current
   DESCRIPTION
      ""
   ::= {er1645v2VEthVlanEntry 11}

er1645v2VEthVlanName OBJECT-TYPE
   SYNTAX      DisplayString
   MAX-ACCESS  read-write
   STATUS      current
   DESCRIPTION
      "Path: virtualEthernet.editConf.vlan.name"
   ::= {er1645v2VEthVlanEntry 16777216}

er1645v2VEthVlanRemark OBJECT-TYPE
   SYNTAX      DisplayString
   MAX-ACCESS  read-write
   STATUS      current
   DESCRIPTION
      "Path: virtualEthernet.editConf.vlan.remark"
   ::= {er1645v2VEthVlanEntry 1157627904}

er1645v2VEthVlanAdminStatus OBJECT-TYPE
   SYNTAX      INTEGER
               {
               up (1),
               down (2)
               }
   MAX-ACCESS  read-write
   STATUS      current
   DESCRIPTION
      "Path: virtualEthernet.editConf.vlan.adminStatus

       Possibilities:
               up   (1)
               down   (2)"
   ::= {er1645v2VEthVlanEntry 33554432}

er1645v2VEthVlanMode OBJECT-TYPE
   SYNTAX      INTEGER
               {
               routing (1),
               bridging (2),
               ipV6 (16),
               ipV6ipV4 (17),
               multilink (8)
               }
   MAX-ACCESS  read-write
   STATUS      current
   DESCRIPTION
      "Path: virtualEthernet.editConf.vlan.mode

       Possibilities:
               routing   (1)
               bridging   (2)
               ipV6   (16)
               ipV6/ipV4   (17)
               multilink   (8)"
   ::= {er1645v2VEthVlanEntry 67108864}

er1645v2VEthVlanPriorityPolicy OBJECT-TYPE
   SYNTAX      DisplayString
   MAX-ACCESS  read-write
   STATUS      current
   DESCRIPTION
      "Path: virtualEthernet.editConf.vlan.priorityPolicy"
   ::= {er1645v2VEthVlanEntry 83886080}

er1645v2VEthVlanIpVrfRouter OBJECT-TYPE
   SYNTAX      DisplayString
   MAX-ACCESS  read-write
   STATUS      current
   DESCRIPTION
      "Path: virtualEthernet.editConf.vlan.ip.vrfRouter"
   ::= {er1645v2VEthVlanEntry 53215232}

er1645v2VEthVlanIpAdr OBJECT-TYPE
   SYNTAX      IpAddress
   MAX-ACCESS  read-write
   STATUS      current
   DESCRIPTION
      "Path: virtualEthernet.editConf.vlan.ip.address"
   ::= {er1645v2VEthVlanEntry 58261504}

er1645v2VEthVlanIpNetm OBJECT-TYPE
   SYNTAX      IpAddress
   MAX-ACCESS  read-write
   STATUS      current
   DESCRIPTION
      "Path: virtualEthernet.editConf.vlan.ip.netMask"
   ::= {er1645v2VEthVlanEntry 58392576}

er1645v2VEthVlanIpSNetName OBJECT-TYPE
   SYNTAX      INTEGER
               {
               slOPTg (0),
               corp (2),
               dmz (3),
               internet (1)
               }
   MAX-ACCESS  read-write
   STATUS      current
   DESCRIPTION
      "Path: virtualEthernet.editConf.vlan.ip.sNet.name

       Possibilities:
               <OPT>   (0)
               corp   (2)
               dmz   (3)
               internet   (1)"
   ::= {er1645v2VEthVlanEntry 53674240}

er1645v2VEthVlanIpSNetCust OBJECT-TYPE
   SYNTAX      DisplayString
   MAX-ACCESS  read-write
   STATUS      current
   DESCRIPTION
      "Path: virtualEthernet.editConf.vlan.ip.sNet.custom"
   ::= {er1645v2VEthVlanEntry 53674496}

er1645v2VEthVlanIpDhcpC OBJECT-TYPE
   SYNTAX      INTEGER
               {
               disabled (0),
               enabled (1)
               }
   MAX-ACCESS  read-write
   STATUS      current
   DESCRIPTION
      "Path: virtualEthernet.editConf.vlan.ip.dhcpClient

       Possibilities:
               disabled   (0)
               enabled   (1)"
   ::= {er1645v2VEthVlanEntry 53608448}

er1645v2VEthVlanIpDhcpGatewayPreference OBJECT-TYPE
   SYNTAX      Integer32
   MAX-ACCESS  read-write
   STATUS      current
   DESCRIPTION
      "Path: virtualEthernet.editConf.vlan.ip.dhcp.gatewayPreference"
   ::= {er1645v2VEthVlanEntry 53739776}

er1645v2VEthVlanIpDhcpRoutePreference OBJECT-TYPE
   SYNTAX      Integer32
   MAX-ACCESS  read-write
   STATUS      current
   DESCRIPTION
      "Path: virtualEthernet.editConf.vlan.ip.dhcp.routePreference"
   ::= {er1645v2VEthVlanEntry 53740032}

er1645v2VEthVlanIpDhcpDnsPreference OBJECT-TYPE
   SYNTAX      Integer32
   MAX-ACCESS  read-write
   STATUS      current
   DESCRIPTION
      "Path: virtualEthernet.editConf.vlan.ip.dhcp.dnsPreference"
   ::= {er1645v2VEthVlanEntry 53740288}

er1645v2VEthVlanIpMtu OBJECT-TYPE
   SYNTAX      Integer32
   MAX-ACCESS  read-write
   STATUS      current
   DESCRIPTION
      "Path: virtualEthernet.editConf.vlan.ip.mtu"
   ::= {er1645v2VEthVlanEntry 52953088}

er1645v2VEthVlanIpMssAdjust OBJECT-TYPE
   SYNTAX      INTEGER
               {
               disabled (0),
               auto (65536)
               }
   MAX-ACCESS  read-write
   STATUS      current
   DESCRIPTION
      "Path: virtualEthernet.editConf.vlan.ip.mssAdjust

       Possibilities:
               disabled   (0)
               auto   (65536)"
   ::= {er1645v2VEthVlanEntry 53280768}

er1645v2VEthVlanIpRipMetric OBJECT-TYPE
   SYNTAX      Integer32
   MAX-ACCESS  read-write
   STATUS      current
   DESCRIPTION
      "Path: virtualEthernet.editConf.vlan.ip.rip.metric"
   ::= {er1645v2VEthVlanEntry 51712768}

er1645v2VEthVlanIpRipMetricOut OBJECT-TYPE
   SYNTAX      Integer32
   MAX-ACCESS  read-write
   STATUS      current
   DESCRIPTION
      "Path: virtualEthernet.editConf.vlan.ip.rip.metricOut"
   ::= {er1645v2VEthVlanEntry 51713024}

er1645v2VEthVlanIpRipMode OBJECT-TYPE
   SYNTAX      INTEGER
               {
               disabled (0),
               passive (1),
               active (2)
               }
   MAX-ACCESS  read-write
   STATUS      current
   DESCRIPTION
      "Path: virtualEthernet.editConf.vlan.ip.rip.mode

       Possibilities:
               disabled   (0)
               passive   (1)
               active   (2)"
   ::= {er1645v2VEthVlanEntry 51713280}

er1645v2VEthVlanIpRipTxVer OBJECT-TYPE
   SYNTAX      INTEGER
               {
               rip1 (0),
               rip2 (1),
               rip1mcompatible (2)
               }
   MAX-ACCESS  read-write
   STATUS      current
   DESCRIPTION
      "Path: virtualEthernet.editConf.vlan.ip.rip.txVersion

       Possibilities:
               rip1   (0)
               rip2   (1)
               rip1-compatible   (2)"
   ::= {er1645v2VEthVlanEntry 51716864}

er1645v2VEthVlanIpRipRxVer OBJECT-TYPE
   SYNTAX      INTEGER
               {
               rip1only (0),
               rip2only (1),
               rip12 (2)
               }
   MAX-ACCESS  read-write
   STATUS      current
   DESCRIPTION
      "Path: virtualEthernet.editConf.vlan.ip.rip.rxVersion

       Possibilities:
               rip1only   (0)
               rip2only   (1)
               rip1&2   (2)"
   ::= {er1645v2VEthVlanEntry 51717120}

er1645v2VEthVlanIpRipSplitH OBJECT-TYPE
   SYNTAX      INTEGER
               {
               disabled (0),
               enabled (1),
               poisonedReverse (2)
               }
   MAX-ACCESS  read-write
   STATUS      current
   DESCRIPTION
      "Path: virtualEthernet.editConf.vlan.ip.rip.splitHorizon

       Possibilities:
               disabled   (0)
               enabled   (1)
               poisonedReverse   (2)"
   ::= {er1645v2VEthVlanEntry 51713792}

er1645v2VEthVlanIpRipAuth OBJECT-TYPE
   SYNTAX      INTEGER
               {
               disabled (0),
               texts (1),
               md5 (2)
               }
   MAX-ACCESS  read-write
   STATUS      current
   DESCRIPTION
      "Path: virtualEthernet.editConf.vlan.ip.rip.authentication

       Possibilities:
               disabled   (0)
               text    (1)
               md5   (2)"
   ::= {er1645v2VEthVlanEntry 51712512}

er1645v2VEthVlanIpRipFilter OBJECT-TYPE
   SYNTAX      DisplayString
   MAX-ACCESS  read-write
   STATUS      current
   DESCRIPTION
      "Path: virtualEthernet.editConf.vlan.ip.rip.filter"
   ::= {er1645v2VEthVlanEntry 51716096}

er1645v2VEthVlanIpRipFilterIn OBJECT-TYPE
   SYNTAX      DisplayString
   MAX-ACCESS  read-write
   STATUS      current
   DESCRIPTION
      "Path: virtualEthernet.editConf.vlan.ip.rip.filterIn"
   ::= {er1645v2VEthVlanEntry 51716352}

er1645v2VEthVlanIpRipClearNextHop OBJECT-TYPE
   SYNTAX      INTEGER
               {
               disabled (0),
               enabled (1)
               }
   MAX-ACCESS  read-write
   STATUS      current
   DESCRIPTION
      "Path: virtualEthernet.editConf.vlan.ip.rip.clearNextHop

       Possibilities:
               disabled   (0)
               enabled   (1)"
   ::= {er1645v2VEthVlanEntry 51708416}

er1645v2VEthVlanIpAccPol OBJECT-TYPE
   SYNTAX      DisplayString
   MAX-ACCESS  read-write
   STATUS      current
   DESCRIPTION
      "Path: virtualEthernet.editConf.vlan.ip.accessPolicy"
   ::= {er1645v2VEthVlanEntry 53084160}

er1645v2VEthVlanIpAB OBJECT-TYPE
   SYNTAX      DisplayString
   MAX-ACCESS  read-write
   STATUS      current
   DESCRIPTION
      "Path: virtualEthernet.editConf.vlan.ip.trafficPolicy"
   ::= {er1645v2VEthVlanEntry 51249152}

er1645v2VEthVlanIpMA OBJECT-TYPE
   SYNTAX      INTEGER
               {
               disabled (0),
               enabled (1)
               }
   MAX-ACCESS  read-write
   STATUS      current
   DESCRIPTION
      "Path: virtualEthernet.editConf.vlan.ip.mgmtAccess

       Possibilities:
               disabled   (0)
               enabled   (1)"
   ::= {er1645v2VEthVlanEntry 51380224}

er1645v2VEthVlanIpMF OBJECT-TYPE
   SYNTAX      Integer32
   MAX-ACCESS  read-write
   STATUS      current
   DESCRIPTION
      "Path: virtualEthernet.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2VEthVlanEntry 51445760}

er1645v2VEthVlanIpDB OBJECT-TYPE
   SYNTAX      INTEGER
               {
               disabled (0),
               enabled (1)
               }
   MAX-ACCESS  read-write
   STATUS      current
   DESCRIPTION
      "Path: virtualEthernet.editConf.vlan.ip.directedBroadcasts

       Possibilities:
               disabled   (0)
               enabled   (1)"
   ::= {er1645v2VEthVlanEntry 51773440}

er1645v2VEthVlanIpIR OBJECT-TYPE
   SYNTAX      INTEGER
               {
               disabled (0),
               enabled (1)
               }
   MAX-ACCESS  read-write
   STATUS      current
   DESCRIPTION
      "Path: virtualEthernet.editConf.vlan.ip.icmpRedirects

       Possibilities:
               disabled   (0)
               enabled   (1)"
   ::= {er1645v2VEthVlanEntry 52035584}

er1645v2VEthVlanIpIgmp OBJECT-TYPE
   SYNTAX      INTEGER
               {
               disabled (0),
               proxy (1),
               router (2),
               v3Router (5)
               }
   MAX-ACCESS  read-write
   STATUS      current
   DESCRIPTION
      "Path: virtualEthernet.editConf.vlan.ip.igmp

       Possibilities:
               disabled   (0)
               proxy   (1)
               router   (2)
               v3Router   (5)"
   ::= {er1645v2VEthVlanEntry 52428800}

er1645v2VEthVlanIpNN OBJECT-TYPE
   SYNTAX      DisplayString
   MAX-ACCESS  read-write
   STATUS      current
   DESCRIPTION
      "Path: virtualEthernet.editConf.vlan.ip.nat"
   ::= {er1645v2VEthVlanEntry 52101120}

er1645v2VEthVlanIpVrrp OBJECT-TYPE
   SYNTAX      INTEGER
               {
               disabled (0),
               enabled (1)
               }
   MAX-ACCESS  read-write
   STATUS      current
   DESCRIPTION
      "Path: virtualEthernet.editConf.vlan.ip.vrrp

       Possibilities:
               disabled   (0)
               enabled   (1)"
   ::= {er1645v2VEthVlanEntry 53149696}

er1645v2VEthVlanIpPimMode OBJECT-TYPE
   SYNTAX      INTEGER
               {
               disabled (0),
               sparse (1),
               passive (2)
               }
   MAX-ACCESS  read-write
   STATUS      current
   DESCRIPTION
      "Path: virtualEthernet.editConf.vlan.ip.pim.mode

       Possibilities:
               disabled   (0)
               sparse   (1)
               passive   (2)"
   ::= {er1645v2VEthVlanEntry 53346560}

er1645v2VEthVlanIpPimDrPriority OBJECT-TYPE
   SYNTAX      Counter32
   MAX-ACCESS  read-write
   STATUS      current
   DESCRIPTION
      "Path: virtualEthernet.editConf.vlan.ip.pim.drPriority

       32 bit unsigned wrappable counter."
   ::= {er1645v2VEthVlanEntry 53346816}

er1645v2VEthVlanIpPimHelloTime OBJECT-TYPE
   SYNTAX      TimeTicks
   MAX-ACCESS  read-write
   STATUS      current
   DESCRIPTION
      "Path: virtualEthernet.editConf.vlan.ip.pim.helloTime

       Time in centi-second."
   ::= {er1645v2VEthVlanEntry 53347072}

er1645v2VEthVlanIpPimPropagationDelay OBJECT-TYPE
   SYNTAX      TimeTicks
   MAX-ACCESS  read-write
   STATUS      current
   DESCRIPTION
      "Path: virtualEthernet.editConf.vlan.ip.pim.propagationDelay

       Time in centi-second."
   ::= {er1645v2VEthVlanEntry 53347328}

er1645v2VEthVlanIpPimOverrideInterval OBJECT-TYPE
   SYNTAX      TimeTicks
   MAX-ACCESS  read-write
   STATUS      current
   DESCRIPTION
      "Path: virtualEthernet.editConf.vlan.ip.pim.overrideInterval

       Time in centi-second."
   ::= {er1645v2VEthVlanEntry 53347584}

er1645v2VEthVlanIpPimBsrBorder OBJECT-TYPE
   SYNTAX      INTEGER
               {
               disabled (0),
               enabled (1)
               }
   MAX-ACCESS  read-write
   STATUS      current
   DESCRIPTION
      "Path: virtualEthernet.editConf.vlan.ip.pim.bsrBorder

       Possibilities:
               disabled   (0)
               enabled   (1)"
   ::= {er1645v2VEthVlanEntry 53347840}

er1645v2VEthVlanIpPimTtlThreshold OBJECT-TYPE
   SYNTAX      Integer32
   MAX-ACCESS  read-write
   STATUS      current
   DESCRIPTION
      "Path: virtualEthernet.editConf.vlan.ip.pim.ttlThreshold"
   ::= {er1645v2VEthVlanEntry 53348096}

er1645v2VEthVlanIpIMNetworkUnreachable OBJECT-TYPE
   SYNTAX      INTEGER
               {
               disabled (0),
               enabled (1)
               }
   MAX-ACCESS  read-write
   STATUS      current
   DESCRIPTION
      "Path: virtualEthernet.editConf.vlan.ip.icmpMessages.networkUnreachable

       Possibilities:
               disabled   (0)
               enabled   (1)"
   ::= {er1645v2VEthVlanEntry 53412096}

er1645v2VEthVlanIpIMHostUnreachable OBJECT-TYPE
   SYNTAX      INTEGER
               {
               disabled (0),
               enabled (1)
               }
   MAX-ACCESS  read-write
   STATUS      current
   DESCRIPTION
      "Path: virtualEthernet.editConf.vlan.ip.icmpMessages.hostUnreachable

       Possibilities:
               disabled   (0)
               enabled   (1)"
   ::= {er1645v2VEthVlanEntry 53412352}

er1645v2VEthVlanIpIMProtocolUnreachable OBJECT-TYPE
   SYNTAX      INTEGER
               {
               disabled (0),
               enabled (1)
               }
   MAX-ACCESS  read-write
   STATUS      current
   DESCRIPTION
      "Path: virtualEthernet.editConf.vlan.ip.icmpMessages.protocolUnreachable

       Possibilities:
               disabled   (0)
               enabled   (1)"
   ::= {er1645v2VEthVlanEntry 53412608}

er1645v2VEthVlanIpIMPortUnreachable OBJECT-TYPE
   SYNTAX      INTEGER
               {
               disabled (0),
               enabled (1)
               }
   MAX-ACCESS  read-write
   STATUS      current
   DESCRIPTION
      "Path: virtualEthernet.editConf.vlan.ip.icmpMessages.portUnreachable

       Possibilities:
               disabled   (0)
               enabled   (1)"
   ::= {er1645v2VEthVlanEntry 53412864}

er1645v2VEthVlanIpIMMtuExceeded OBJECT-TYPE
   SYNTAX      INTEGER
               {
               disabled (0),
               enabled (1)
               }
   MAX-ACCESS  read-write
   STATUS      current
   DESCRIPTION
      "Path: virtualEthernet.editConf.vlan.ip.icmpMessages.mtuExceeded

       Possibilities:
               disabled   (0)
               enabled   (1)"
   ::= {er1645v2VEthVlanEntry 53413120}

er1645v2VEthVlanIpIMAdminProhibited OBJECT-TYPE
   SYNTAX      INTEGER
               {
               disabled (0),
               enabled (1)
               }
   MAX-ACCESS  read-write
   STATUS      current
   DESCRIPTION
      "Path: virtualEthernet.editConf.vlan.ip.icmpMessages.adminProhibited

       Possibilities:
               disabled   (0)
               enabled   (1)"
   ::= {er1645v2VEthVlanEntry 53413376}

er1645v2VEthVlanIpIMTtlExceeded OBJECT-TYPE
   SYNTAX      INTEGER
               {
               disabled (0),
               enabled (1)
               }
   MAX-ACCESS  read-write
   STATUS      current
   DESCRIPTION
      "Path: virtualEthernet.editConf.vlan.ip.icmpMessages.ttlExceeded

       Possibilities:
               disabled   (0)
               enabled   (1)"
   ::= {er1645v2VEthVlanEntry 53413632}

er1645v2VEthVlanIpIMRedirect OBJECT-TYPE
   SYNTAX      INTEGER
               {
               disabled (0),
               enabled (1)
               }
   MAX-ACCESS  read-write
   STATUS      current
   DESCRIPTION
      "Path: virtualEthernet.editConf.vlan.ip.icmpMessages.redirect

       Possibilities:
               disabled   (0)
               enabled   (1)"
   ::= {er1645v2VEthVlanEntry 53413888}

er1645v2VEthVlanIpV6VrfRouter OBJECT-TYPE
   SYNTAX      DisplayString
   MAX-ACCESS  read-write
   STATUS      current
   DESCRIPTION
      "Path: virtualEthernet.editConf.vlan.ipV6.vrfRouter"
   ::= {er1645v2VEthVlanEntry 704708608}

er1645v2VEthVlanIpV6AddrAutoConfigNrDupAddrDetects OBJECT-TYPE
   SYNTAX      Integer32
   MAX-ACCESS  read-write
   STATUS      current
   DESCRIPTION
      "Path: virtualEthernet.editConf.vlan.ipV6.addrAutoConfig.nrDupAddrDetects"
   ::= {er1645v2VEthVlanEntry 704905472}

er1645v2VEthVlanIpV6AddrAutoConfigAcceptRa OBJECT-TYPE
   SYNTAX      INTEGER
               {
               disabled (0),
               enabled (1)
               }
   MAX-ACCESS  read-write
   STATUS      current
   DESCRIPTION
      "Path: virtualEthernet.editConf.vlan.ipV6.addrAutoConfig.acceptRa

       Possibilities:
               disabled   (0)
               enabled   (1)"
   ::= {er1645v2VEthVlanEntry 704905728}

er1645v2VEthVlanIpV6AddrAutoConfigAcceptRaRdnss OBJECT-TYPE
   SYNTAX      INTEGER
               {
               disabled (0),
               enabled (1)
               }
   MAX-ACCESS  read-write
   STATUS      current
   DESCRIPTION
      "Path: virtualEthernet.editConf.vlan.ipV6.addrAutoConfig.acceptRaRdnss

       Possibilities:
               disabled   (0)
               enabled   (1)"
   ::= {er1645v2VEthVlanEntry 704905984}

er1645v2VEthVlanIpV6AddrAutoConfigAcceptRaDnssl OBJECT-TYPE
   SYNTAX      INTEGER
               {
               disabled (0),
               enabled (1)
               }
   MAX-ACCESS  read-write
   STATUS      current
   DESCRIPTION
      "Path: virtualEthernet.editConf.vlan.ipV6.addrAutoConfig.acceptRaDnssl

       Possibilities:
               disabled   (0)
               enabled   (1)"
   ::= {er1645v2VEthVlanEntry 704906240}

er1645v2VEthVlanIpV6DefaultRoute OBJECT-TYPE
   SYNTAX      INTEGER
               {
               disabled (0),
               enabled (1)
               }
   MAX-ACCESS  read-write
   STATUS      current
   DESCRIPTION
      "Path: virtualEthernet.editConf.vlan.ipV6.defaultRoute

       Possibilities:
               disabled   (0)
               enabled   (1)"
   ::= {er1645v2VEthVlanEntry 704970752}

er1645v2VEthVlanIpV6RaSend OBJECT-TYPE
   SYNTAX      INTEGER
               {
               disabled (0),
               enabled (1)
               }
   MAX-ACCESS  read-write
   STATUS      current
   DESCRIPTION
      "Path: virtualEthernet.editConf.vlan.ipV6.ra.send

       Possibilities:
               disabled   (0)
               enabled   (1)"
   ::= {er1645v2VEthVlanEntry 705036544}

er1645v2VEthVlanIpV6RaMinInterval OBJECT-TYPE
   SYNTAX      TimeTicks
   MAX-ACCESS  read-write
   STATUS      current
   DESCRIPTION
      "Path: virtualEthernet.editConf.vlan.ipV6.ra.minInterval

       Time in centi-second."
   ::= {er1645v2VEthVlanEntry 705036800}

er1645v2VEthVlanIpV6RaMaxInterval OBJECT-TYPE
   SYNTAX      TimeTicks
   MAX-ACCESS  read-write
   STATUS      current
   DESCRIPTION
      "Path: virtualEthernet.editConf.vlan.ipV6.ra.maxInterval

       Time in centi-second."
   ::= {er1645v2VEthVlanEntry 705037056}

er1645v2VEthVlanIpV6RaManagedFlag OBJECT-TYPE
   SYNTAX      INTEGER
               {
               disabled (0),
               enabled (1)
               }
   MAX-ACCESS  read-write
   STATUS      current
   DESCRIPTION
      "Path: virtualEthernet.editConf.vlan.ipV6.ra.managedFlag

       Possibilities:
               disabled   (0)
               enabled   (1)"
   ::= {er1645v2VEthVlanEntry 705037312}

er1645v2VEthVlanIpV6RaOtherConfFlag OBJECT-TYPE
   SYNTAX      INTEGER
               {
               disabled (0),
               enabled (1)
               }
   MAX-ACCESS  read-write
   STATUS      current
   DESCRIPTION
      "Path: virtualEthernet.editConf.vlan.ipV6.ra.otherConfFlag

       Possibilities:
               disabled   (0)
               enabled   (1)"
   ::= {er1645v2VEthVlanEntry 705037568}

er1645v2VEthVlanIpV6RaLinkMtu OBJECT-TYPE
   SYNTAX      Integer32
   MAX-ACCESS  read-write
   STATUS      current
   DESCRIPTION
      "Path: virtualEthernet.editConf.vlan.ipV6.ra.linkMtu"
   ::= {er1645v2VEthVlanEntry 705037824}

er1645v2VEthVlanIpV6RaReachableTime OBJECT-TYPE
   SYNTAX      TimeTicks
   MAX-ACCESS  read-write
   STATUS      current
   DESCRIPTION
      "Path: virtualEthernet.editConf.vlan.ipV6.ra.reachableTime

       Time in centi-second."
   ::= {er1645v2VEthVlanEntry 705038080}

er1645v2VEthVlanIpV6RaRetransmitTime OBJECT-TYPE
   SYNTAX      TimeTicks
   MAX-ACCESS  read-write
   STATUS      current
   DESCRIPTION
      "Path: virtualEthernet.editConf.vlan.ipV6.ra.retransmitTime

       Time in centi-second."
   ::= {er1645v2VEthVlanEntry 705038336}

er1645v2VEthVlanIpV6RaHopLimit OBJECT-TYPE
   SYNTAX      Integer32
   MAX-ACCESS  read-write
   STATUS      current
   DESCRIPTION
      "Path: virtualEthernet.editConf.vlan.ipV6.ra.hopLimit"
   ::= {er1645v2VEthVlanEntry 705038592}

er1645v2VEthVlanIpV6RaDefaultLifeTime OBJECT-TYPE
   SYNTAX      TimeTicks
   MAX-ACCESS  read-write
   STATUS      current
   DESCRIPTION
      "Path: virtualEthernet.editConf.vlan.ipV6.ra.defaultLifeTime

       Time in centi-second."
   ::= {er1645v2VEthVlanEntry 705038848}

er1645v2VEthVlanIpV6RaDnsOptionsRdnssLifeTime OBJECT-TYPE
   SYNTAX      TimeTicks
   MAX-ACCESS  read-write
   STATUS      current
   DESCRIPTION
      "Path: virtualEthernet.editConf.vlan.ipV6.ra.dnsOptions.rdnss.lifeTime

       Time in centi-second."
   ::= {er1645v2VEthVlanEntry 705039140}

er1645v2VEthVlanIpV6RaDnsOptionsRdnssImportServers OBJECT-TYPE
   SYNTAX      INTEGER
               {
               disabled (0),
               enabled (1)
               }
   MAX-ACCESS  read-write
   STATUS      current
   DESCRIPTION
      "Path: virtualEthernet.editConf.vlan.ipV6.ra.dnsOptions.rdnss.importServers

       Possibilities:
               disabled   (0)
               enabled   (1)"
   ::= {er1645v2VEthVlanEntry 705039148}

er1645v2VEthVlanIpV6RaDnsOptionsDnsslLifeTime OBJECT-TYPE
   SYNTAX      TimeTicks
   MAX-ACCESS  read-write
   STATUS      current
   DESCRIPTION
      "Path: virtualEthernet.editConf.vlan.ipV6.ra.dnsOptions.dnssl.lifeTime

       Time in centi-second."
   ::= {er1645v2VEthVlanEntry 705039172}

er1645v2VEthVlanIpV6RaDnsOptionsDnsslImportDomains OBJECT-TYPE
   SYNTAX      INTEGER
               {
               disabled (0),
               enabled (1)
               }
   MAX-ACCESS  read-write
   STATUS      current
   DESCRIPTION
      "Path: virtualEthernet.editConf.vlan.ipV6.ra.dnsOptions.dnssl.importDomains

       Possibilities:
               disabled   (0)
               enabled   (1)"
   ::= {er1645v2VEthVlanEntry 705039180}

er1645v2VEthVlanIpV6RsSend OBJECT-TYPE
   SYNTAX      INTEGER
               {
               disabled (0),
               enabled (1)
               }
   MAX-ACCESS  read-write
   STATUS      current
   DESCRIPTION
      "Path: virtualEthernet.editConf.vlan.ipV6.rs.send

       Possibilities:
               disabled   (0)
               enabled   (1)"
   ::= {er1645v2VEthVlanEntry 705954048}

er1645v2VEthVlanIpV6RsMaxRandomDelay OBJECT-TYPE
   SYNTAX      TimeTicks
   MAX-ACCESS  read-write
   STATUS      current
   DESCRIPTION
      "Path: virtualEthernet.editConf.vlan.ipV6.rs.maxRandomDelay

       Time in centi-second."
   ::= {er1645v2VEthVlanEntry 705954304}

er1645v2VEthVlanIpV6RsInterval OBJECT-TYPE
   SYNTAX      TimeTicks
   MAX-ACCESS  read-write
   STATUS      current
   DESCRIPTION
      "Path: virtualEthernet.editConf.vlan.ipV6.rs.interval

       Time in centi-second."
   ::= {er1645v2VEthVlanEntry 705954560}

er1645v2VEthVlanIpV6RsMaxSolicitations OBJECT-TYPE
   SYNTAX      Integer32
   MAX-ACCESS  read-write
   STATUS      current
   DESCRIPTION
      "Path: virtualEthernet.editConf.vlan.ipV6.rs.maxSolicitations"
   ::= {er1645v2VEthVlanEntry 705954816}

er1645v2VEthVlanIpV6TrafficPolicyInbound OBJECT-TYPE
   SYNTAX      DisplayString
   MAX-ACCESS  read-write
   STATUS      current
   DESCRIPTION
      "Path: virtualEthernet.editConf.vlan.ipV6.trafficPolicy.inbound"
   ::= {er1645v2VEthVlanEntry 705364224}

er1645v2VEthVlanIpV6TrafficPolicyOutbound OBJECT-TYPE
   SYNTAX      DisplayString
   MAX-ACCESS  read-write
   STATUS      current
   DESCRIPTION
      "Path: virtualEthernet.editConf.vlan.ipV6.trafficPolicy.outbound"
   ::= {er1645v2VEthVlanEntry 705364480}

er1645v2VEthVlanIpV6FirewallZone OBJECT-TYPE
   SYNTAX      DisplayString
   MAX-ACCESS  read-write
   STATUS      current
   DESCRIPTION
      "Path: virtualEthernet.editConf.vlan.ipV6.firewall.zone"
   ::= {er1645v2VEthVlanEntry 705429760}

er1645v2VEthVlanIpV6DhcpClientAddrAC OBJECT-TYPE
   SYNTAX      INTEGER
               {
               disabled (0),
               enabled (1)
               }
   MAX-ACCESS  read-write
   STATUS      current
   DESCRIPTION
      "Path: virtualEthernet.editConf.vlan.ipV6.dhcp.client.addrAutoConfig

       Possibilities:
               disabled   (0)
               enabled   (1)"
   ::= {er1645v2VEthVlanEntry 705307648}

er1645v2VEthVlanIpV6DhcpClientPrDelMode OBJECT-TYPE
   SYNTAX      INTEGER
               {
               disabled (0),
               enabled (1)
               }
   MAX-ACCESS  read-write
   STATUS      current
   DESCRIPTION
      "Path: virtualEthernet.editConf.vlan.ipV6.dhcp.client.pd.mode

       Possibilities:
               disabled   (0)
               enabled   (1)"
   ::= {er1645v2VEthVlanEntry 705308676}

er1645v2VEthVlanIpV6DhcpClientPrDelPool OBJECT-TYPE
   SYNTAX      DisplayString
   MAX-ACCESS  read-write
   STATUS      current
   DESCRIPTION
      "Path: virtualEthernet.editConf.vlan.ipV6.dhcp.client.pd.pool"
   ::= {er1645v2VEthVlanEntry 705308680}

er1645v2VEthVlanIpV6DhcpClientPrDelPdExclOpt OBJECT-TYPE
   SYNTAX      INTEGER
               {
               disabled (0),
               enabled (1)
               }
   MAX-ACCESS  read-write
   STATUS      current
   DESCRIPTION
      "Path: virtualEthernet.editConf.vlan.ipV6.dhcp.client.pd.pdExclOpt

       Possibilities:
               disabled   (0)
               enabled   (1)"
   ::= {er1645v2VEthVlanEntry 705308684}

er1645v2VEthVlanIpV6DhcpClientDnsServerPref OBJECT-TYPE
   SYNTAX      Integer32
   MAX-ACCESS  read-write
   STATUS      current
   DESCRIPTION
      "Path: virtualEthernet.editConf.vlan.ipV6.dhcp.client.dns.serverPref"
   ::= {er1645v2VEthVlanEntry 705310724}

er1645v2VEthVlanIpV6DhcpClientRapidCommit OBJECT-TYPE
   SYNTAX      INTEGER
               {
               disabled (0),
               enabled (1)
               }
   MAX-ACCESS  read-write
   STATUS      current
   DESCRIPTION
      "Path: virtualEthernet.editConf.vlan.ipV6.dhcp.client.rapidCommit

       Possibilities:
               disabled   (0)
               enabled   (1)"
   ::= {er1645v2VEthVlanEntry 705309696}

er1645v2VEthVlanIpV6DhcpClientTimersSolTimeOut OBJECT-TYPE
   SYNTAX      TimeTicks
   MAX-ACCESS  read-write
   STATUS      current
   DESCRIPTION
      "Path: virtualEthernet.editConf.vlan.ipV6.dhcp.client.timers.solTimeOut

       Time in centi-second."
   ::= {er1645v2VEthVlanEntry 705311748}

er1645v2VEthVlanIpV6DhcpClientTimersSolMaxRt OBJECT-TYPE
   SYNTAX      TimeTicks
   MAX-ACCESS  read-write
   STATUS      current
   DESCRIPTION
      "Path: virtualEthernet.editConf.vlan.ipV6.dhcp.client.timers.solMaxRt

       Time in centi-second."
   ::= {er1645v2VEthVlanEntry 705311752}

er1645v2VEthVlanIpV6DhcpClientTimersInfoRefresh OBJECT-TYPE
   SYNTAX      TimeTicks
   MAX-ACCESS  read-write
   STATUS      current
   DESCRIPTION
      "Path: virtualEthernet.editConf.vlan.ipV6.dhcp.client.timers.infoRefresh

       Time in centi-second."
   ::= {er1645v2VEthVlanEntry 705311756}

er1645v2VEthVlanIpV6DhcpServerMode OBJECT-TYPE
   SYNTAX      INTEGER
               {
               disabled (0),
               enabled (1)
               }
   MAX-ACCESS  read-write
   STATUS      current
   DESCRIPTION
      "Path: virtualEthernet.editConf.vlan.ipV6.dhcp.server.mode

       Possibilities:
               disabled   (0)
               enabled   (1)"
   ::= {er1645v2VEthVlanEntry 705315840}

er1645v2VEthVlanIpV6DhcpServerPreference OBJECT-TYPE
   SYNTAX      Integer32
   MAX-ACCESS  read-write
   STATUS      current
   DESCRIPTION
      "Path: virtualEthernet.editConf.vlan.ipV6.dhcp.server.preference"
   ::= {er1645v2VEthVlanEntry 705316864}

er1645v2VEthVlanIpV6DhcpServerPool OBJECT-TYPE
   SYNTAX      DisplayString
   MAX-ACCESS  read-write
   STATUS      current
   DESCRIPTION
      "Path: virtualEthernet.editConf.vlan.ipV6.dhcp.server.pool"
   ::= {er1645v2VEthVlanEntry 705317888}

er1645v2VEthVlanIpV6DhcpServerRapidCommit OBJECT-TYPE
   SYNTAX      INTEGER
               {
               disabled (0),
               enabled (1)
               }
   MAX-ACCESS  read-write
   STATUS      current
   DESCRIPTION
      "Path: virtualEthernet.editConf.vlan.ipV6.dhcp.server.rapidCommit

       Possibilities:
               disabled   (0)
               enabled   (1)"
   ::= {er1645v2VEthVlanEntry 705318912}

er1645v2VEthVlanIpV6DhcpServerTimersInfoRefresh OBJECT-TYPE
   SYNTAX      TimeTicks
   MAX-ACCESS  read-write
   STATUS      current
   DESCRIPTION
      "Path: virtualEthernet.editConf.vlan.ipV6.dhcp.server.timers.infoRefresh

       Time in centi-second."
   ::= {er1645v2VEthVlanEntry 705319940}

er1645v2VEthVlanIpV6DhcpRelayMode OBJECT-TYPE
   SYNTAX      INTEGER
               {
               disabled (0),
               enabled (1)
               }
   MAX-ACCESS  read-write
   STATUS      current
   DESCRIPTION
      "Path: virtualEthernet.editConf.vlan.ipV6.dhcp.relay.mode

       Possibilities:
               disabled   (0)
               enabled   (1)"
   ::= {er1645v2VEthVlanEntry 705323040}

er1645v2VEthVlanIpV6SendRedirect OBJECT-TYPE
   SYNTAX      INTEGER
               {
               disabled (0),
               enabled (1)
               }
   MAX-ACCESS  read-write
   STATUS      current
   DESCRIPTION
      "Path: virtualEthernet.editConf.vlan.ipV6.sendRedirect

       Possibilities:
               disabled   (0)
               enabled   (1)"
   ::= {er1645v2VEthVlanEntry 705101824}

er1645v2VEthVlanIpV6LinkMtu OBJECT-TYPE
   SYNTAX      Integer32
   MAX-ACCESS  read-write
   STATUS      current
   DESCRIPTION
      "Path: virtualEthernet.editConf.vlan.ipV6.linkMtu"
   ::= {er1645v2VEthVlanEntry 705167360}

er1645v2VEthVlanIpV6InterfaceId OBJECT-TYPE
   SYNTAX      OCTET STRING
   MAX-ACCESS  read-write
   STATUS      current
   DESCRIPTION
      "Path: virtualEthernet.editConf.vlan.ipV6.interfaceId"
   ::= {er1645v2VEthVlanEntry 705232896}

er1645v2VEthVlanIpV6MF OBJECT-TYPE
   SYNTAX      Integer32
   MAX-ACCESS  read-write
   STATUS      current
   DESCRIPTION
      "Path: virtualEthernet.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2VEthVlanEntry 705757184}

er1645v2VEthVlanIpV6IcmpMessagesNoRoute OBJECT-TYPE
   SYNTAX      INTEGER
               {
               disabled (0),
               enabled (1)
               }
   MAX-ACCESS  read-write
   STATUS      current
   DESCRIPTION
      "Path: virtualEthernet.editConf.vlan.ipV6.icmpMessages.noRoute

       Possibilities:
               disabled   (0)
               enabled   (1)"
   ::= {er1645v2VEthVlanEntry 705822976}

er1645v2VEthVlanIpV6IcmpMessagesBeyondScope OBJECT-TYPE
   SYNTAX      INTEGER
               {
               disabled (0),
               enabled (1)
               }
   MAX-ACCESS  read-write
   STATUS      current
   DESCRIPTION
      "Path: virtualEthernet.editConf.vlan.ipV6.icmpMessages.beyondScope

       Possibilities:
               disabled   (0)
               enabled   (1)"
   ::= {er1645v2VEthVlanEntry 705823488}

er1645v2VEthVlanIpV6IcmpMessagesAddressUnreachable OBJECT-TYPE
   SYNTAX      INTEGER
               {
               disabled (0),
               enabled (1)
               }
   MAX-ACCESS  read-write
   STATUS      current
   DESCRIPTION
      "Path: virtualEthernet.editConf.vlan.ipV6.icmpMessages.addressUnreachable

       Possibilities:
               disabled   (0)
               enabled   (1)"
   ::= {er1645v2VEthVlanEntry 705823744}

er1645v2VEthVlanIpV6IcmpMessagesPortUnreachable OBJECT-TYPE
   SYNTAX      INTEGER
               {
               disabled (0),
               enabled (1)
               }
   MAX-ACCESS  read-write
   STATUS      current
   DESCRIPTION
      "Path: virtualEthernet.editConf.vlan.ipV6.icmpMessages.portUnreachable

       Possibilities:
               disabled   (0)
               enabled   (1)"
   ::= {er1645v2VEthVlanEntry 705824000}

er1645v2VEthVlanIpV6IcmpMessagesPacketTooBig OBJECT-TYPE
   SYNTAX      INTEGER
               {
               disabled (0),
               enabled (1)
               }
   MAX-ACCESS  read-write
   STATUS      current
   DESCRIPTION
      "Path: virtualEthernet.editConf.vlan.ipV6.icmpMessages.packetTooBig

       Possibilities:
               disabled   (0)
               enabled   (1)"
   ::= {er1645v2VEthVlanEntry 705825280}

er1645v2VEthVlanIpV6IcmpMessagesHopLimitExceeded OBJECT-TYPE
   SYNTAX      INTEGER
               {
               disabled (0),
               enabled (1)
               }
   MAX-ACCESS  read-write
   STATUS      current
   DESCRIPTION
      "Path: virtualEthernet.editConf.vlan.ipV6.icmpMessages.hopLimitExceeded

       Possibilities:
               disabled   (0)
               enabled   (1)"
   ::= {er1645v2VEthVlanEntry 705827840}

er1645v2VEthVlanIpV6IcmpMessagesFragTimeExceeded OBJECT-TYPE
   SYNTAX      INTEGER
               {
               disabled (0),
               enabled (1)
               }
   MAX-ACCESS  read-write
   STATUS      current
   DESCRIPTION
      "Path: virtualEthernet.editConf.vlan.ipV6.icmpMessages.fragTimeExceeded

       Possibilities:
               disabled   (0)
               enabled   (1)"
   ::= {er1645v2VEthVlanEntry 705828096}

er1645v2VEthVlanIpV6IcmpMessagesHeaderFieldErr OBJECT-TYPE
   SYNTAX      INTEGER
               {
               disabled (0),
               enabled (1)
               }
   MAX-ACCESS  read-write
   STATUS      current
   DESCRIPTION
      "Path: virtualEthernet.editConf.vlan.ipV6.icmpMessages.headerFieldErr

       Possibilities:
               disabled   (0)
               enabled   (1)"
   ::= {er1645v2VEthVlanEntry 705830400}

er1645v2VEthVlanIpV6IcmpMessagesOptionUnrecognized OBJECT-TYPE
   SYNTAX      INTEGER
               {
               disabled (0),
               enabled (1)
               }
   MAX-ACCESS  read-write
   STATUS      current
   DESCRIPTION
      "Path: virtualEthernet.editConf.vlan.ipV6.icmpMessages.optionUnrecognized

       Possibilities:
               disabled   (0)
               enabled   (1)"
   ::= {er1645v2VEthVlanEntry 705830912}

er1645v2VEthVlanIpV6IcmpMessagesRedirect OBJECT-TYPE
   SYNTAX      INTEGER
               {
               disabled (0),
               enabled (1)
               }
   MAX-ACCESS  read-write
   STATUS      current
   DESCRIPTION
      "Path: virtualEthernet.editConf.vlan.ipV6.icmpMessages.redirect

       Possibilities:
               disabled   (0)
               enabled   (1)"
   ::= {er1645v2VEthVlanEntry 705832960}

er1645v2VEthVlanBridgingAccList OBJECT-TYPE
   SYNTAX      DisplayString
   MAX-ACCESS  read-write
   STATUS      current
   DESCRIPTION
      "Path: virtualEthernet.editConf.vlan.bridging.accessList"
   ::= {er1645v2VEthVlanEntry 453246976}

er1645v2VEthVlanBridgingInACL OBJECT-TYPE
   SYNTAX      DisplayString
   MAX-ACCESS  read-write
   STATUS      current
   DESCRIPTION
      "Path: virtualEthernet.editConf.vlan.bridging.inAccessList"
   ::= {er1645v2VEthVlanEntry 456916992}

er1645v2VEthVlanBridgingTp OBJECT-TYPE
   SYNTAX      DisplayString
   MAX-ACCESS  read-write
   STATUS      current
   DESCRIPTION
      "Path: virtualEthernet.editConf.vlan.bridging.trafficPolicy"
   ::= {er1645v2VEthVlanEntry 454295552}

er1645v2VEthVlanBridgingBrGrp OBJECT-TYPE
   SYNTAX      DisplayString
   MAX-ACCESS  read-write
   STATUS      current
   DESCRIPTION
      "Path: virtualEthernet.editConf.vlan.bridging.bridgeGroup"
   ::= {er1645v2VEthVlanEntry 454819840}

er1645v2VEthVlanBridgingLimBC OBJECT-TYPE
   SYNTAX      INTEGER
               {
               disabled (0),
               enabled (1)
               }
   MAX-ACCESS  read-write
   STATUS      current
   DESCRIPTION
      "Path: virtualEthernet.editConf.vlan.bridging.limitBroadcasts

       Possibilities:
               disabled   (0)
               enabled   (1)"
   ::= {er1645v2VEthVlanEntry 455081984}

er1645v2VEthVlanBridgingPrivateMode OBJECT-TYPE
   SYNTAX      INTEGER
               {
               disabled (0),
               enabled (1)
               }
   MAX-ACCESS  read-write
   STATUS      current
   DESCRIPTION
      "Path: virtualEthernet.editConf.vlan.bridging.privateMode

       Possibilities:
               disabled   (0)
               enabled   (1)"
   ::= {er1645v2VEthVlanEntry 459538432}

er1645v2VEthVlanBridgingLearning OBJECT-TYPE
   SYNTAX      INTEGER
               {
               disabled (0),
               enabled (1)
               }
   MAX-ACCESS  read-write
   STATUS      current
   DESCRIPTION
      "Path: virtualEthernet.editConf.vlan.bridging.learning

       Possibilities:
               disabled   (0)
               enabled   (1)"
   ::= {er1645v2VEthVlanEntry 456130560}

er1645v2VEthVlanBridgingMaxCacheSize OBJECT-TYPE
   SYNTAX      INTEGER
               {
               unlimited (0)
               }
   MAX-ACCESS  read-write
   STATUS      current
   DESCRIPTION
      "Path: virtualEthernet.editConf.vlan.bridging.maxCacheSize

       Possibilities:
               unlimited   (0)"
   ::= {er1645v2VEthVlanEntry 456392704}

er1645v2VEthVlanBridgingRelearnDropOnRelearn OBJECT-TYPE
   SYNTAX      INTEGER
               {
               disabled (0),
               enabled (1)
               }
   MAX-ACCESS  read-write
   STATUS      current
   DESCRIPTION
      "Path: virtualEthernet.editConf.vlan.bridging.relearn.dropOnRelearn

       Possibilities:
               disabled   (0)
               enabled   (1)"
   ::= {er1645v2VEthVlanEntry 456655872}

er1645v2VEthVlanBridgingRelearnShutdownThreshold OBJECT-TYPE
   SYNTAX      Integer32
   MAX-ACCESS  read-write
   STATUS      current
   DESCRIPTION
      "Path: virtualEthernet.editConf.vlan.bridging.relearn.shutdownThreshold"
   ::= {er1645v2VEthVlanEntry 456656896}

er1645v2VEthVlanBridgingRelearnShutdownTime OBJECT-TYPE
   SYNTAX      TimeTicks
   MAX-ACCESS  read-write
   STATUS      current
   DESCRIPTION
      "Path: virtualEthernet.editConf.vlan.bridging.relearn.shutdownTime

       Time in centi-second."
   ::= {er1645v2VEthVlanEntry 456657920}

er1645v2VEthVlanBridgingRelearnLoopDetection OBJECT-TYPE
   SYNTAX      INTEGER
               {
               disabled (0),
               passive (1),
               active (2)
               }
   MAX-ACCESS  read-write
   STATUS      current
   DESCRIPTION
      "Path: virtualEthernet.editConf.vlan.bridging.relearn.loopDetection

       Possibilities:
               disabled   (0)
               passive   (1)
               active   (2)"
   ::= {er1645v2VEthVlanEntry 456658944}

er1645v2VEthVlanBridgingRelearnLoopDetectionInterval OBJECT-TYPE
   SYNTAX      TimeTicks
   MAX-ACCESS  read-write
   STATUS      current
   DESCRIPTION
      "Path: virtualEthernet.editConf.vlan.bridging.relearn.loopDetectionInterval

       Time in centi-second."
   ::= {er1645v2VEthVlanEntry 456659968}

er1645v2VEthVlanBridgingVlanMemberShip OBJECT-TYPE
   SYNTAX      INTEGER
               {
               all (0),
               none (1),
               grouped (2)
               }
   MAX-ACCESS  read-write
   STATUS      current
   DESCRIPTION
      "Path: virtualEthernet.editConf.vlan.bridging.vlanMemberShip

       Possibilities:
               all   (0)
               none   (1)
               grouped   (2)"
   ::= {er1645v2VEthVlanEntry 457965568}

er1645v2VEthVlanBridgingVlTUntaggedAction OBJECT-TYPE
   SYNTAX      INTEGER
               {
               discard (0),
               accept (1),
               tag (2)
               }
   MAX-ACCESS  read-write
   STATUS      current
   DESCRIPTION
      "Path: virtualEthernet.editConf.vlan.bridging.vlanTagging.untagged.action

       Possibilities:
               discard   (0)
               accept   (1)
               tag   (2)"
   ::= {er1645v2VEthVlanEntry 459055104}

er1645v2VEthVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.bridging.vlanTagging.untagged.tagInfo.tpid

       Possibilities:
               dot1Q   (33024)
               dot1ad   (34984)
               0x9100   (37120)
               0x9200   (37376)
               0x9300   (37632)"
   ::= {er1645v2VEthVlanEntry 459059712}

er1645v2VEthVlanBridgingVlTUntaggedTagInfoVid OBJECT-TYPE
   SYNTAX      Integer32
   MAX-ACCESS  read-write
   STATUS      current
   DESCRIPTION
      "Path: virtualEthernet.editConf.vlan.bridging.vlanTagging.untagged.tagInfo.vid"
   ::= {er1645v2VEthVlanEntry 459060224}

er1645v2VEthVlanBridgingVlTUnknownVlansAction OBJECT-TYPE
   SYNTAX      INTEGER
               {
               discard (0),
               accept (1),
               tag (2)
               }
   MAX-ACCESS  read-write
   STATUS      current
   DESCRIPTION
      "Path: virtualEthernet.editConf.vlan.bridging.vlanTagging.unknownVlans.action

       Possibilities:
               discard   (0)
               accept   (1)
               tag   (2)"
   ::= {er1645v2VEthVlanEntry 459120640}

er1645v2VEthVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.bridging.vlanTagging.unknownVlans.tagInfo.tpid

       Possibilities:
               dot1Q   (33024)
               dot1ad   (34984)
               0x9100   (37120)
               0x9200   (37376)
               0x9300   (37632)"
   ::= {er1645v2VEthVlanEntry 459125248}

er1645v2VEthVlanBridgingVlTUnknownVlansTagInfoVid OBJECT-TYPE
   SYNTAX      Integer32
   MAX-ACCESS  read-write
   STATUS      current
   DESCRIPTION
      "Path: virtualEthernet.editConf.vlan.bridging.vlanTagging.unknownVlans.tagInfo.vid"
   ::= {er1645v2VEthVlanEntry 459125760}

er1645v2VEthVlanBridgingDot1adType OBJECT-TYPE
   SYNTAX      INTEGER
               {
               slOPTg (0),
               cPort (4),
               sPort (1),
               nni (2)
               }
   MAX-ACCESS  read-write
   STATUS      current
   DESCRIPTION
      "Path: virtualEthernet.editConf.vlan.bridging.dot1ad.type

       Possibilities:
               <OPT>   (0)
               cPort   (4)
               sPort   (1)
               nni   (2)"
   ::= {er1645v2VEthVlanEntry 460850176}

er1645v2VEthVlanBridgingPriority OBJECT-TYPE
   SYNTAX      Integer32
   MAX-ACCESS  read-write
   STATUS      current
   DESCRIPTION
      "Path: virtualEthernet.editConf.vlan.bridging.priority"
   ::= {er1645v2VEthVlanEntry 453509120}

er1645v2VEthVlanBridgingPathCost OBJECT-TYPE
   SYNTAX      Integer32
   MAX-ACCESS  read-write
   STATUS      current
   DESCRIPTION
      "Path: virtualEthernet.editConf.vlan.bridging.pathCost"
   ::= {er1645v2VEthVlanEntry 453771264}

er1645v2VEthVlanBridgingInternalPathCost OBJECT-TYPE
   SYNTAX      Integer32
   MAX-ACCESS  read-write
   STATUS      current
   DESCRIPTION
      "Path: virtualEthernet.editConf.vlan.bridging.internalPathCost"
   ::= {er1645v2VEthVlanEntry 457703424}

er1645v2VEthVlanBridgingTCD OBJECT-TYPE
   SYNTAX      INTEGER
               {
               disabled (0),
               enabled (1)
               }
   MAX-ACCESS  read-write
   STATUS      current
   DESCRIPTION
      "Path: virtualEthernet.editConf.vlan.bridging.topologyChangeDetection

       Possibilities:
               disabled   (0)
               enabled   (1)"
   ::= {er1645v2VEthVlanEntry 454033408}

er1645v2VEthVlanBridgingRestrictedRole OBJECT-TYPE
   SYNTAX      INTEGER
               {
               disabled (0),
               enabled (1)
               }
   MAX-ACCESS  read-write
   STATUS      current
   DESCRIPTION
      "Path: virtualEthernet.editConf.vlan.bridging.restrictedRole

       Possibilities:
               disabled   (0)
               enabled   (1)"
   ::= {er1645v2VEthVlanEntry 458227712}

er1645v2VEthVlanBridgingAdminEdge OBJECT-TYPE
   SYNTAX      INTEGER
               {
               disabled (0),
               enabled (1)
               }
   MAX-ACCESS  read-write
   STATUS      current
   DESCRIPTION
      "Path: virtualEthernet.editConf.vlan.bridging.adminEdge

       Possibilities:
               disabled   (0)
               enabled   (1)"
   ::= {er1645v2VEthVlanEntry 457179136}

er1645v2VEthVlanBridgingOamMacDeviceMac OBJECT-TYPE
   SYNTAX      DisplayString
   MAX-ACCESS  read-write
   STATUS      current
   DESCRIPTION
      "Path: virtualEthernet.editConf.vlan.bridging.ethOam.macAddress.deviceMac"
   ::= {er1645v2VEthVlanEntry 458506496}

er1645v2VEthVlanBridgingOamMacUserMac OBJECT-TYPE
   SYNTAX      OCTET STRING
   MAX-ACCESS  read-write
   STATUS      current
   DESCRIPTION
      "Path: virtualEthernet.editConf.vlan.bridging.ethOam.macAddress.userMac

       MAC address."
   ::= {er1645v2VEthVlanEntry 458506368}

er1645v2VEthVlanBridgingOamMacBridgeMac OBJECT-TYPE
   SYNTAX      DisplayString
   MAX-ACCESS  read-write
   STATUS      current
   DESCRIPTION
      "Path: virtualEthernet.editConf.vlan.bridging.ethOam.macAddress.bridgeMac"
   ::= {er1645v2VEthVlanEntry 458506432}

er1645v2VEthVlanBridgingMgmtInline OBJECT-TYPE
   SYNTAX      INTEGER
               {
               disabled (0),
               enabled (1)
               }
   MAX-ACCESS  read-write
   STATUS      current
   DESCRIPTION
      "Path: virtualEthernet.editConf.vlan.bridging.mgmtInline

       Possibilities:
               disabled   (0)
               enabled   (1)"
   ::= {er1645v2VEthVlanEntry 458752000}

er1645v2VEthVlanBridgingL2ptMode OBJECT-TYPE
   SYNTAX      INTEGER
               {
               disabled (0),
               enabled (1)
               }
   MAX-ACCESS  read-write
   STATUS      current
   DESCRIPTION
      "Path: virtualEthernet.editConf.vlan.bridging.l2ProtTunnel.mode

       Possibilities:
               disabled   (0)
               enabled   (1)"
   ::= {er1645v2VEthVlanEntry 459292672}

er1645v2VEthVlanBridgingL2ptProtocols OBJECT-TYPE
   SYNTAX      Integer32
   MAX-ACCESS  read-write
   STATUS      current
   DESCRIPTION
      "Path: virtualEthernet.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2VEthVlanEntry 459309056}

er1645v2VEthVlanBridgingL2ptDestMac OBJECT-TYPE
   SYNTAX      OCTET STRING
   MAX-ACCESS  read-write
   STATUS      current
   DESCRIPTION
      "Path: virtualEthernet.editConf.vlan.bridging.l2ProtTunnel.destinationMac

       MAC address."
   ::= {er1645v2VEthVlanEntry 459325440}

er1645v2VEthVlanBridgingL2ptCos OBJECT-TYPE
   SYNTAX      INTEGER
               {
               unchanged (255)
               }
   MAX-ACCESS  read-write
   STATUS      current
   DESCRIPTION
      "Path: virtualEthernet.editConf.vlan.bridging.l2ProtTunnel.cos

       Possibilities:
               unchanged   (255)"
   ::= {er1645v2VEthVlanEntry 459341824}

er1645v2VEthVlanBridgingL2ptDropThrStp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.stp

       unit name = packets/sec

       Possibilities:
               unlimited   (0)"
   ::= {er1645v2VEthVlanEntry 459358272}

er1645v2VEthVlanBridgingL2ptDropThrLldp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.lldp

       unit name = packets/sec

       Possibilities:
               unlimited   (0)"
   ::= {er1645v2VEthVlanEntry 459358336}

er1645v2VEthVlanBridgingL2ptDropThrOam OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.oam

       unit name = packets/sec

       Possibilities:
               unlimited   (0)"
   ::= {er1645v2VEthVlanEntry 459358400}

er1645v2VEthVlanBridgingL2ptDropThrCdp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.cdp

       unit name = packets/sec

       Possibilities:
               unlimited   (0)"
   ::= {er1645v2VEthVlanEntry 459358464}

er1645v2VEthVlanBridgingL2ptDropThrVtp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.vtp

       unit name = packets/sec

       Possibilities:
               unlimited   (0)"
   ::= {er1645v2VEthVlanEntry 459358528}

er1645v2VEthVlanBridgingL2ptDropThrLacp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.lacp

       unit name = packets/sec

       Possibilities:
               unlimited   (0)"
   ::= {er1645v2VEthVlanEntry 459358592}

er1645v2VEthVlanBridgingL2ptDropThrEfmOam OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.efmOam

       unit name = packets/sec

       Possibilities:
               unlimited   (0)"
   ::= {er1645v2VEthVlanEntry 459358656}

er1645v2VEthVlanBridgingL2ptDropThrPvst OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.pvst

       unit name = packets/sec

       Possibilities:
               unlimited   (0)"
   ::= {er1645v2VEthVlanEntry 459358720}

er1645v2VEthVlanBridgingL2ptDropThrMmrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.mmrp

       unit name = packets/sec

       Possibilities:
               unlimited   (0)"
   ::= {er1645v2VEthVlanEntry 459358784}

er1645v2VEthVlanBridgingL2ptDropThrMvrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.mvrp

       unit name = packets/sec

       Possibilities:
               unlimited   (0)"
   ::= {er1645v2VEthVlanEntry 459358848}

er1645v2VEthVlanBridgingL2ptDropThrGvrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.gvrp

       unit name = packets/sec

       Possibilities:
               unlimited   (0)"
   ::= {er1645v2VEthVlanEntry 459358912}

er1645v2VEthVlanBridgingL2ptDropThrGmrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.gmrp

       unit name = packets/sec

       Possibilities:
               unlimited   (0)"
   ::= {er1645v2VEthVlanEntry 459358976}

er1645v2VEthVlanBridgingL2ptDropThrDtp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.dtp

       unit name = packets/sec

       Possibilities:
               unlimited   (0)"
   ::= {er1645v2VEthVlanEntry 459359040}

er1645v2VEthVlanBridgingL2ptDropThrPagp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.pagp

       unit name = packets/sec

       Possibilities:
               unlimited   (0)"
   ::= {er1645v2VEthVlanEntry 459359104}

er1645v2VEthVlanBridgingL2ptDropThrUdld OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.udld

       unit name = packets/sec

       Possibilities:
               unlimited   (0)"
   ::= {er1645v2VEthVlanEntry 459359168}

er1645v2VEthVlanVlanVid OBJECT-TYPE
   SYNTAX      INTEGER
               {
               untagged (0),
               prioTagged (4096),
               notUsed (4097)
               }
   MAX-ACCESS  read-write
   STATUS      current
   DESCRIPTION
      "Path: virtualEthernet.editConf.vlan.vlan.vid

       Possibilities:
               untagged   (0)
               prioTagged   (4096)
               notUsed   (4097)"
   ::= {er1645v2VEthVlanEntry 234946560}

er1645v2VEthVlanVlanVidExtensionSingle OBJECT-TYPE
   SYNTAX      OCTET STRING
   MAX-ACCESS  read-write
   STATUS      current
   DESCRIPTION
      "Path: virtualEthernet.editConf.vlan.vlan.vidExtension.single"
   ::= {er1645v2VEthVlanEntry 235340032}

er1645v2VEthVlanVlanVidExtensionEndVid OBJECT-TYPE
   SYNTAX      Integer32
   MAX-ACCESS  read-write
   STATUS      current
   DESCRIPTION
      "Path: virtualEthernet.editConf.vlan.vlan.vidExtension.endVid"
   ::= {er1645v2VEthVlanEntry 235340288}

er1645v2VEthVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.vlan.tpid

       Possibilities:
               dot1Q   (33024)
               dot1ad   (34984)
               0x9100   (37120)
               0x9200   (37376)
               0x9300   (37632)"
   ::= {er1645v2VEthVlanEntry 241238016}

er1645v2VEthVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: virtualEthernet.editConf.vlan.vlan.tagSignificance

       Possibilities:
               global   (0)
               local   (1)
               sVlan   (2)
               sVlanGlobal   (6)
               cVlan   (3)
               scVlan   (5)
               cVlanLocal   (4)"
   ::= {er1645v2VEthVlanEntry 235012096}

er1645v2VEthVlanVlanChTos OBJECT-TYPE
   SYNTAX      INTEGER
               {
               disabled (0),
               enabled (1)
               }
   MAX-ACCESS  read-write
   STATUS      current
   DESCRIPTION
      "Path: virtualEthernet.editConf.vlan.vlan.changeTos

       Possibilities:
               disabled   (0)
               enabled   (1)"
   ::= {er1645v2VEthVlanEntry 235208704}

er1645v2VEthVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235143424}

er1645v2VEthVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235143680}

er1645v2VEthVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235143936}

er1645v2VEthVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235144192}

er1645v2VEthVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235144448}

er1645v2VEthVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235144704}

er1645v2VEthVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235144960}

er1645v2VEthVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2VEthVlanEntry 235145216}

er1645v2VEthVlanVlanTxCos OBJECT-TYPE
   SYNTAX      INTEGER
               {
               tosCosMap (8),
               queueCosMap (16)
               }
   MAX-ACCESS  read-write
   STATUS      current
   DESCRIPTION
      "Path: virtualEthernet.editConf.vlan.vlan.txCos

       Possibilities:
               tosCosMap   (8)
               queueCosMap   (16)"
   ::= {er1645v2VEthVlanEntry 235077632}

er1645v2VEthVlanVlanCCMapP0 OBJECT-TYPE
   SYNTAX      Integer32
   MAX-ACCESS  read-write
   STATUS      current
   DESCRIPTION
      "Path: virtualEthernet.editConf.vlan.vlan.cosCosMap.p0"
   ::= {er1645v2VEthVlanEntry 241303808}

er1645v2VEthVlanVlanCCMapP1 OBJECT-TYPE
   SYNTAX      Integer32
   MAX-ACCESS  read-write
   STATUS      current
   DESCRIPTION
      "Path: virtualEthernet.editConf.vlan.vlan.cosCosMap.p1"
   ::= {er1645v2VEthVlanEntry 241304064}

er1645v2VEthVlanVlanCCMapP2 OBJECT-TYPE
   SYNTAX      Integer32
   MAX-ACCESS  read-write
   STATUS      current
   DESCRIPTION
      "Path: virtualEthernet.editConf.vlan.vlan.cosCosMap.p2"
   ::= {er1645v2VEthVlanEntry 241304320}

er1645v2VEthVlanVlanCCMapP3 OBJECT-TYPE
   SYNTAX      Integer32
   MAX-ACCESS  read-write
   STATUS      current
   DESCRIPTION
      "Path: virtualEthernet.editConf.vlan.vlan.cosCosMap.p3"
   ::= {er1645v2VEthVlanEntry 241304576}

er1645v2VEthVlanVlanCCMapP4 OBJECT-TYPE
   SYNTAX      Integer32
   MAX-ACCESS  read-write
   STATUS      current
   DESCRIPTION
      "Path: virtualEthernet.editConf.vlan.vlan.cosCosMap.p4"
   ::= {er1645v2VEthVlanEntry 241304832}

er1645v2VEthVlanVlanCCMapP5 OBJECT-TYPE
   SYNTAX      Integer32
   MAX-ACCESS  read-write
   STATUS      current
   DESCRIPTION
      "Path: virtualEthernet.editConf.vlan.vlan.cosCosMap.p5"
   ::= {er1645v2VEthVlanEntry 241305088}

er1645v2VEthVlanVlanCCMapP6 OBJECT-TYPE
   SYNTAX      Integer32
   MAX-ACCESS  read-write
   STATUS      current
   DESCRIPTION
      "Path: virtualEthernet.editConf.vlan.vlan.cosCosMap.p6"
   ::= {er1645v2VEthVlanEntry 241305344}

er1645v2VEthVlanVlanCCMapP7 OBJECT-TYPE
   SYNTAX      Integer32
   MAX-ACCESS  read-write
   STATUS      current
   DESCRIPTION
      "Path: virtualEthernet.editConf.vlan.vlan.cosCosMap.p7"
   ::= {er1645v2VEthVlanEntry 241305600}

er1645v2VEthVlanVlanQCMapQueue1 OBJECT-TYPE
   SYNTAX      Integer32
   MAX-ACCESS  read-write
   STATUS      current
   DESCRIPTION
      "Path: virtualEthernet.editConf.vlan.vlan.queueCosMap.queue1"
   ::= {er1645v2VEthVlanEntry 241434880}

er1645v2VEthVlanVlanQCMapQueue2 OBJECT-TYPE
   SYNTAX      Integer32
   MAX-ACCESS  read-write
   STATUS      current
   DESCRIPTION
      "Path: virtualEthernet.editConf.vlan.vlan.queueCosMap.queue2"
   ::= {er1645v2VEthVlanEntry 241435136}

er1645v2VEthVlanVlanQCMapQueue3 OBJECT-TYPE
   SYNTAX      Integer32
   MAX-ACCESS  read-write
   STATUS      current
   DESCRIPTION
      "Path: virtualEthernet.editConf.vlan.vlan.queueCosMap.queue3"
   ::= {er1645v2VEthVlanEntry 241435392}

er1645v2VEthVlanVlanQCMapQueue4 OBJECT-TYPE
   SYNTAX      Integer32
   MAX-ACCESS  read-write
   STATUS      current
   DESCRIPTION
      "Path: virtualEthernet.editConf.vlan.vlan.queueCosMap.queue4"
   ::= {er1645v2VEthVlanEntry 241435648}

er1645v2VEthVlanVlanQCMapQueue5 OBJECT-TYPE
   SYNTAX      Integer32
   MAX-ACCESS  read-write
   STATUS      current
   DESCRIPTION
      "Path: virtualEthernet.editConf.vlan.vlan.queueCosMap.queue5"
   ::= {er1645v2VEthVlanEntry 241435904}

er1645v2VEthVlanVlanQCMapLowDelayQueue OBJECT-TYPE
   SYNTAX      Integer32
   MAX-ACCESS  read-write
   STATUS      current
   DESCRIPTION
      "Path: virtualEthernet.editConf.vlan.vlan.queueCosMap.lowDelayQueue"
   ::= {er1645v2VEthVlanEntry 241436160}

er1645v2VEthVlanVlanQCMapLowDelay2Queue OBJECT-TYPE
   SYNTAX      Integer32
   MAX-ACCESS  read-write
   STATUS      current
   DESCRIPTION
      "Path: virtualEthernet.editConf.vlan.vlan.queueCosMap.lowDelay2Queue"
   ::= {er1645v2VEthVlanEntry 241436416}

er1645v2VEthVlanVlanQCMapSystemQueue OBJECT-TYPE
   SYNTAX      Integer32
   MAX-ACCESS  read-write
   STATUS      current
   DESCRIPTION
      "Path: virtualEthernet.editConf.vlan.vlan.queueCosMap.systemQueue"
   ::= {er1645v2VEthVlanEntry 241436672}

er1645v2VEthVlanVlanQinQSVid OBJECT-TYPE
   SYNTAX      Integer32
   MAX-ACCESS  read-write
   STATUS      current
   DESCRIPTION
      "Path: virtualEthernet.editConf.vlan.vlan.tunnel.sVid"
   ::= {er1645v2VEthVlanEntry 241172736}

er1645v2VEthVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.vlan.tunnel.sTpid

       Possibilities:
               dot1Q   (33024)
               dot1ad   (34984)
               0x9100   (37120)
               0x9200   (37376)
               0x9300   (37632)"
   ::= {er1645v2VEthVlanEntry 241172992}

er1645v2VEthVlanVlanArpTimeOut OBJECT-TYPE
   SYNTAX      TimeTicks
   MAX-ACCESS  read-write
   STATUS      current
   DESCRIPTION
      "Path: virtualEthernet.editConf.vlan.vlan.arp.timeOut

       Time in centi-second."
   ::= {er1645v2VEthVlanEntry 235277312}

er1645v2VEthVlanVlanArpProxyArp OBJECT-TYPE
   SYNTAX      INTEGER
               {
               disabled (0),
               enabled (1)
               }
   MAX-ACCESS  read-write
   STATUS      current
   DESCRIPTION
      "Path: virtualEthernet.editConf.vlan.vlan.arp.proxyArp

       Possibilities:
               disabled   (0)
               enabled   (1)"
   ::= {er1645v2VEthVlanEntry 235287040}

er1645v2VEthVlanBandwidthMode OBJECT-TYPE
   SYNTAX      INTEGER
               {
               reshaping (1),
               policing (2),
               policingReshape (3)
               }
   MAX-ACCESS  read-write
   STATUS      current
   DESCRIPTION
      "Path: virtualEthernet.editConf.vlan.bandwidth.mode

       Possibilities:
               reshaping   (1)
               policing   (2)
               policingReshape   (3)"
   ::= {er1645v2VEthVlanEntry 148897792}

er1645v2VEthVlanBandwidthCir OBJECT-TYPE
   SYNTAX      Integer32
   MAX-ACCESS  read-write
   STATUS      current
   DESCRIPTION
      "Path: virtualEthernet.editConf.vlan.bandwidth.cir"
   ::= {er1645v2VEthVlanEntry 135266304}

er1645v2VEthVlanBandwidthEir OBJECT-TYPE
   SYNTAX      Integer32
   MAX-ACCESS  read-write
   STATUS      current
   DESCRIPTION
      "Path: virtualEthernet.editConf.vlan.bandwidth.eir"
   ::= {er1645v2VEthVlanEntry 141557760}

er1645v2VEthVlanBandwidthUnit OBJECT-TYPE
   SYNTAX      INTEGER
               {
               bitssec (1),
               percent (2)
               }
   MAX-ACCESS  read-write
   STATUS      current
   DESCRIPTION
      "Path: virtualEthernet.editConf.vlan.bandwidth.unit

       Possibilities:
               bits/sec   (1)
               percent   (2)"
   ::= {er1645v2VEthVlanEntry 139460608}

er1645v2VEthVlanBandwidthTc OBJECT-TYPE
   SYNTAX      INTEGER
               {
               auto (0)
               }
   MAX-ACCESS  read-write
   STATUS      current
   DESCRIPTION
      "Path: virtualEthernet.editConf.vlan.bandwidth.tc

       Possibilities:
               auto   (0)"
   ::= {er1645v2VEthVlanEntry 140509184}

er1645v2VEthVlanBandwidthTcFactor OBJECT-TYPE
   SYNTAX      INTEGER
               {
               ms (10),
               s100us (1)
               }
   MAX-ACCESS  read-write
   STATUS      current
   DESCRIPTION
      "Path: virtualEthernet.editConf.vlan.bandwidth.tcFactor

       Possibilities:
               ms   (10)
               *100us   (1)"
   ::= {er1645v2VEthVlanEntry 142606336}

er1645v2VEthVlanBandwidthCorrType OBJECT-TYPE
   SYNTAX      INTEGER
               {
               noCorrection (0),
               predefined (1),
               manual (2)
               }
   MAX-ACCESS  read-write
   STATUS      current
   DESCRIPTION
      "Path: virtualEthernet.editConf.vlan.bandwidth.correction.type

       Possibilities:
               noCorrection   (0)
               predefined   (1)
               manual   (2)"
   ::= {er1645v2VEthVlanEntry 136445952}

er1645v2VEthVlanBandwidthCorrPredefEncapsFrameRelay OBJECT-TYPE
   SYNTAX      DisplayString
   MAX-ACCESS  read-write
   STATUS      current
   DESCRIPTION
      "Path: virtualEthernet.editConf.vlan.bandwidth.correction.predefined.encapsulation.frameRelay"
   ::= {er1645v2VEthVlanEntry 136594432}

er1645v2VEthVlanBandwidthCorrPredefEncapsPpp OBJECT-TYPE
   SYNTAX      DisplayString
   MAX-ACCESS  read-write
   STATUS      current
   DESCRIPTION
      "Path: virtualEthernet.editConf.vlan.bandwidth.correction.predefined.encapsulation.ppp"
   ::= {er1645v2VEthVlanEntry 136595456}

er1645v2VEthVlanBandwidthCorrPredefEncapsAtmHl OBJECT-TYPE
   SYNTAX      INTEGER
               {
               rfc2684 (0),
               ppp (1),
               pppOverEthernet (2)
               }
   MAX-ACCESS  read-write
   STATUS      current
   DESCRIPTION
      "Path: virtualEthernet.editConf.vlan.bandwidth.correction.predefined.encapsulation.atm.higherLayer

       Possibilities:
               rfc2684   (0)
               ppp   (1)
               pppOverEthernet   (2)"
   ::= {er1645v2VEthVlanEntry 136596608}

er1645v2VEthVlanBandwidthCorrPredefEncapsAtmMp OBJECT-TYPE
   SYNTAX      INTEGER
               {
               llcEncapsulation (0),
               vcMultiplexing (1)
               }
   MAX-ACCESS  read-write
   STATUS      current
   DESCRIPTION
      "Path: virtualEthernet.editConf.vlan.bandwidth.correction.predefined.encapsulation.atm.multiProtocol

       Possibilities:
               llcEncapsulation   (0)
               vcMultiplexing   (1)"
   ::= {er1645v2VEthVlanEntry 136596736}

er1645v2VEthVlanBandwidthCorrPredefEncapsHdlc OBJECT-TYPE
   SYNTAX      DisplayString
   MAX-ACCESS  read-write
   STATUS      current
   DESCRIPTION
      "Path: virtualEthernet.editConf.vlan.bandwidth.correction.predefined.encapsulation.hdlc"
   ::= {er1645v2VEthVlanEntry 136597504}

er1645v2VEthVlanBandwidthCorrPredefEncapsEfmFs OBJECT-TYPE
   SYNTAX      Integer32
   MAX-ACCESS  read-write
   STATUS      current
   DESCRIPTION
      "Path: virtualEthernet.editConf.vlan.bandwidth.correction.predefined.encapsulation.efm.fragmentSize"
   ::= {er1645v2VEthVlanEntry 136598656}

er1645v2VEthVlanBandwidthCorrPredefEncapsEfmIb OBJECT-TYPE
   SYNTAX      Integer32
   MAX-ACCESS  read-write
   STATUS      current
   DESCRIPTION
      "Path: virtualEthernet.editConf.vlan.bandwidth.correction.predefined.encapsulation.efm.idleBytes"
   ::= {er1645v2VEthVlanEntry 136598784}

er1645v2VEthVlanBandwidthCorrPredefMode OBJECT-TYPE
   SYNTAX      INTEGER
               {
               routing (0),
               bridging (1)
               }
   MAX-ACCESS  read-write
   STATUS      current
   DESCRIPTION
      "Path: virtualEthernet.editConf.vlan.bandwidth.correction.predefined.mode

       Possibilities:
               routing   (0)
               bridging   (1)"
   ::= {er1645v2VEthVlanEntry 136609792}

er1645v2VEthVlanBandwidthCorrManualOverhead OBJECT-TYPE
   SYNTAX      Integer32
   MAX-ACCESS  read-write
   STATUS      current
   DESCRIPTION
      "Path: virtualEthernet.editConf.vlan.bandwidth.correction.manual.overhead"
   ::= {er1645v2VEthVlanEntry 136708608}

er1645v2VEthVlanBandwidthCorrManualFrameData OBJECT-TYPE
   SYNTAX      Counter32
   MAX-ACCESS  read-write
   STATUS      current
   DESCRIPTION
      "Path: virtualEthernet.editConf.vlan.bandwidth.correction.manual.frameData

       32 bit unsigned wrappable counter."
   ::= {er1645v2VEthVlanEntry 136709120}

er1645v2VEthVlanBandwidthCorrManualFrameHeader OBJECT-TYPE
   SYNTAX      Counter32
   MAX-ACCESS  read-write
   STATUS      current
   DESCRIPTION
      "Path: virtualEthernet.editConf.vlan.bandwidth.correction.manual.frameHeader

       32 bit unsigned wrappable counter."
   ::= {er1645v2VEthVlanEntry 136709632}

er1645v2VEthVlanBandwidthMaxFifoQLen OBJECT-TYPE
   SYNTAX      Integer32
   MAX-ACCESS  read-write
   STATUS      current
   DESCRIPTION
      "Path: virtualEthernet.editConf.vlan.bandwidth.maxFifoQLen"
   ::= {er1645v2VEthVlanEntry 137363456}

er1645v2VEthVlanBandwidthDeFlagCir OBJECT-TYPE
   SYNTAX      INTEGER
               {
               allowed (1),
               notAllowed (2)
               }
   MAX-ACCESS  read-write
   STATUS      current
   DESCRIPTION
      "Path: virtualEthernet.editConf.vlan.bandwidth.deFlag.cir

       Possibilities:
               allowed   (1)
               notAllowed   (2)"
   ::= {er1645v2VEthVlanEntry 147853312}

er1645v2VEthVlanBandwidthDeFlagEir OBJECT-TYPE
   SYNTAX      INTEGER
               {
               allowed (1),
               notAllowed (2)
               }
   MAX-ACCESS  read-write
   STATUS      current
   DESCRIPTION
      "Path: virtualEthernet.editConf.vlan.bandwidth.deFlag.eir

       Possibilities:
               allowed   (1)
               notAllowed   (2)"
   ::= {er1645v2VEthVlanEntry 147857408}

er1645v2VEthVlanBandwidthDeFlagViolate OBJECT-TYPE
   SYNTAX      INTEGER
               {
               allowed (1),
               notAllowed (2)
               }
   MAX-ACCESS  read-write
   STATUS      current
   DESCRIPTION
      "Path: virtualEthernet.editConf.vlan.bandwidth.deFlag.violate

       Possibilities:
               allowed   (1)
               notAllowed   (2)"
   ::= {er1645v2VEthVlanEntry 147861504}

er1645v2VEthVlanBandwidthActCirActNone OBJECT-TYPE
   SYNTAX      OCTET STRING
   MAX-ACCESS  read-write
   STATUS      current
   DESCRIPTION
      "Path: virtualEthernet.editConf.vlan.bandwidth.action.cirAction.none"
   ::= {er1645v2VEthVlanEntry 150085632}

er1645v2VEthVlanBandwidthActCirActEthCos1 OBJECT-TYPE
   SYNTAX      INTEGER
               {
               unchanged (256)
               }
   MAX-ACCESS  read-write
   STATUS      current
   DESCRIPTION
      "Path: virtualEthernet.editConf.vlan.bandwidth.action.cirAction.ethernet.cosDepth1

       Possibilities:
               unchanged   (256)"
   ::= {er1645v2VEthVlanEntry 150094080}

er1645v2VEthVlanBandwidthActCirActEthDei1 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth1

       Possibilities:
               unchanged   (255)
               clear   (0)
               set   (1)"
   ::= {er1645v2VEthVlanEntry 150099200}

er1645v2VEthVlanBandwidthActCirActEthCos2 OBJECT-TYPE
   SYNTAX      INTEGER
               {
               unchanged (256)
               }
   MAX-ACCESS  read-write
   STATUS      current
   DESCRIPTION
      "Path: virtualEthernet.editConf.vlan.bandwidth.action.cirAction.ethernet.cosDepth2

       Possibilities:
               unchanged   (256)"
   ::= {er1645v2VEthVlanEntry 150094336}

er1645v2VEthVlanBandwidthActCirActEthDei2 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth2

       Possibilities:
               unchanged   (255)
               clear   (0)
               set   (1)"
   ::= {er1645v2VEthVlanEntry 150099456}

er1645v2VEthVlanBandwidthActCirActEthCos3 OBJECT-TYPE
   SYNTAX      INTEGER
               {
               unchanged (256)
               }
   MAX-ACCESS  read-write
   STATUS      current
   DESCRIPTION
      "Path: virtualEthernet.editConf.vlan.bandwidth.action.cirAction.ethernet.cosDepth3

       Possibilities:
               unchanged   (256)"
   ::= {er1645v2VEthVlanEntry 150094592}

er1645v2VEthVlanBandwidthActCirActEthDei3 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth3

       Possibilities:
               unchanged   (255)
               clear   (0)
               set   (1)"
   ::= {er1645v2VEthVlanEntry 150099712}

er1645v2VEthVlanBandwidthActCirActEthCos4 OBJECT-TYPE
   SYNTAX      INTEGER
               {
               unchanged (256)
               }
   MAX-ACCESS  read-write
   STATUS      current
   DESCRIPTION
      "Path: virtualEthernet.editConf.vlan.bandwidth.action.cirAction.ethernet.cosDepth4

       Possibilities:
               unchanged   (256)"
   ::= {er1645v2VEthVlanEntry 150094848}

er1645v2VEthVlanBandwidthActCirActEthDei4 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth4

       Possibilities:
               unchanged   (255)
               clear   (0)
               set   (1)"
   ::= {er1645v2VEthVlanEntry 150099968}

er1645v2VEthVlanBandwidthActCirActEthCos5 OBJECT-TYPE
   SYNTAX      INTEGER
               {
               unchanged (256)
               }
   MAX-ACCESS  read-write
   STATUS      current
   DESCRIPTION
      "Path: virtualEthernet.editConf.vlan.bandwidth.action.cirAction.ethernet.cosDepth5

       Possibilities:
               unchanged   (256)"
   ::= {er1645v2VEthVlanEntry 150095104}

er1645v2VEthVlanBandwidthActCirActEthDei5 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth5

       Possibilities:
               unchanged   (255)
               clear   (0)
               set   (1)"
   ::= {er1645v2VEthVlanEntry 150100224}

er1645v2VEthVlanBandwidthActCirActEthCos6 OBJECT-TYPE
   SYNTAX      INTEGER
               {
               unchanged (256)
               }
   MAX-ACCESS  read-write
   STATUS      current
   DESCRIPTION
      "Path: virtualEthernet.editConf.vlan.bandwidth.action.cirAction.ethernet.cosDepth6

       Possibilities:
               unchanged   (256)"
   ::= {er1645v2VEthVlanEntry 150095360}

er1645v2VEthVlanBandwidthActCirActEthDei6 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth6

       Possibilities:
               unchanged   (255)
               clear   (0)
               set   (1)"
   ::= {er1645v2VEthVlanEntry 150100480}

er1645v2VEthVlanBandwidthActCirActEthCos7 OBJECT-TYPE
   SYNTAX      INTEGER
               {
               unchanged (256)
               }
   MAX-ACCESS  read-write
   STATUS      current
   DESCRIPTION
      "Path: virtualEthernet.editConf.vlan.bandwidth.action.cirAction.ethernet.cosDepth7

       Possibilities:
               unchanged   (256)"
   ::= {er1645v2VEthVlanEntry 150095616}

er1645v2VEthVlanBandwidthActCirActEthDei7 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth7

       Possibilities:
               unchanged   (255)
               clear   (0)
               set   (1)"
   ::= {er1645v2VEthVlanEntry 150100736}

er1645v2VEthVlanBandwidthActCirActEthCos8 OBJECT-TYPE
   SYNTAX      INTEGER
               {
               unchanged (256)
               }
   MAX-ACCESS  read-write
   STATUS      current
   DESCRIPTION
      "Path: virtualEthernet.editConf.vlan.bandwidth.action.cirAction.ethernet.cosDepth8

       Possibilities:
               unchanged   (256)"
   ::= {er1645v2VEthVlanEntry 150095872}

er1645v2VEthVlanBandwidthActCirActEthDei8 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth8

       Possibilities:
               unchanged   (255)
               clear   (0)
               set   (1)"
   ::= {er1645v2VEthVlanEntry 150100992}

er1645v2VEthVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 150096128}

er1645v2VEthVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 150096384}

er1645v2VEthVlanBandwidthActCirActEthDrpLev OBJECT-TYPE
   SYNTAX      INTEGER
               {
               unchanged (0)
               }
   MAX-ACCESS  read-write
   STATUS      current
   DESCRIPTION
      "Path: virtualEthernet.editConf.vlan.bandwidth.action.cirAction.ethernet.dropLevel

       Possibilities:
               unchanged   (0)"
   ::= {er1645v2VEthVlanEntry 150096640}

er1645v2VEthVlanBandwidthActCirActEthDeFlag OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deFlag

       Possibilities:
               unchanged   (255)
               clear   (0)
               set   (1)"
   ::= {er1645v2VEthVlanEntry 150097408}

er1645v2VEthVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 150120704}

er1645v2VEthVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 150120960}

er1645v2VEthVlanBandwidthActCirActIpDrpLev OBJECT-TYPE
   SYNTAX      INTEGER
               {
               unchanged (0)
               }
   MAX-ACCESS  read-write
   STATUS      current
   DESCRIPTION
      "Path: virtualEthernet.editConf.vlan.bandwidth.action.cirAction.ip.dropLevel

       Possibilities:
               unchanged   (0)"
   ::= {er1645v2VEthVlanEntry 150121216}

er1645v2VEthVlanBandwidthActCirActIpDeFlag OBJECT-TYPE
   SYNTAX      INTEGER
               {
               unchanged (255),
               clear (0),
               set (1)
               }
   MAX-ACCESS  read-write
   STATUS      current
   DESCRIPTION
      "Path: virtualEthernet.editConf.vlan.bandwidth.action.cirAction.ip.deFlag

       Possibilities:
               unchanged   (255)
               clear   (0)
               set   (1)"
   ::= {er1645v2VEthVlanEntry 150121984}

er1645v2VEthVlanBandwidthActEirActNone OBJECT-TYPE
   SYNTAX      OCTET STRING
   MAX-ACCESS  read-write
   STATUS      current
   DESCRIPTION
      "Path: virtualEthernet.editConf.vlan.bandwidth.action.eirAction.none"
   ::= {er1645v2VEthVlanEntry 150216704}

er1645v2VEthVlanBandwidthActEirActEthCos1 OBJECT-TYPE
   SYNTAX      INTEGER
               {
               unchanged (256)
               }
   MAX-ACCESS  read-write
   STATUS      current
   DESCRIPTION
      "Path: virtualEthernet.editConf.vlan.bandwidth.action.eirAction.ethernet.cosDepth1

       Possibilities:
               unchanged   (256)"
   ::= {er1645v2VEthVlanEntry 150225152}

er1645v2VEthVlanBandwidthActEirActEthDei1 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth1

       Possibilities:
               unchanged   (255)
               clear   (0)
               set   (1)"
   ::= {er1645v2VEthVlanEntry 150230272}

er1645v2VEthVlanBandwidthActEirActEthCos2 OBJECT-TYPE
   SYNTAX      INTEGER
               {
               unchanged (256)
               }
   MAX-ACCESS  read-write
   STATUS      current
   DESCRIPTION
      "Path: virtualEthernet.editConf.vlan.bandwidth.action.eirAction.ethernet.cosDepth2

       Possibilities:
               unchanged   (256)"
   ::= {er1645v2VEthVlanEntry 150225408}

er1645v2VEthVlanBandwidthActEirActEthDei2 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth2

       Possibilities:
               unchanged   (255)
               clear   (0)
               set   (1)"
   ::= {er1645v2VEthVlanEntry 150230528}

er1645v2VEthVlanBandwidthActEirActEthCos3 OBJECT-TYPE
   SYNTAX      INTEGER
               {
               unchanged (256)
               }
   MAX-ACCESS  read-write
   STATUS      current
   DESCRIPTION
      "Path: virtualEthernet.editConf.vlan.bandwidth.action.eirAction.ethernet.cosDepth3

       Possibilities:
               unchanged   (256)"
   ::= {er1645v2VEthVlanEntry 150225664}

er1645v2VEthVlanBandwidthActEirActEthDei3 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth3

       Possibilities:
               unchanged   (255)
               clear   (0)
               set   (1)"
   ::= {er1645v2VEthVlanEntry 150230784}

er1645v2VEthVlanBandwidthActEirActEthCos4 OBJECT-TYPE
   SYNTAX      INTEGER
               {
               unchanged (256)
               }
   MAX-ACCESS  read-write
   STATUS      current
   DESCRIPTION
      "Path: virtualEthernet.editConf.vlan.bandwidth.action.eirAction.ethernet.cosDepth4

       Possibilities:
               unchanged   (256)"
   ::= {er1645v2VEthVlanEntry 150225920}

er1645v2VEthVlanBandwidthActEirActEthDei4 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth4

       Possibilities:
               unchanged   (255)
               clear   (0)
               set   (1)"
   ::= {er1645v2VEthVlanEntry 150231040}

er1645v2VEthVlanBandwidthActEirActEthCos5 OBJECT-TYPE
   SYNTAX      INTEGER
               {
               unchanged (256)
               }
   MAX-ACCESS  read-write
   STATUS      current
   DESCRIPTION
      "Path: virtualEthernet.editConf.vlan.bandwidth.action.eirAction.ethernet.cosDepth5

       Possibilities:
               unchanged   (256)"
   ::= {er1645v2VEthVlanEntry 150226176}

er1645v2VEthVlanBandwidthActEirActEthDei5 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth5

       Possibilities:
               unchanged   (255)
               clear   (0)
               set   (1)"
   ::= {er1645v2VEthVlanEntry 150231296}

er1645v2VEthVlanBandwidthActEirActEthCos6 OBJECT-TYPE
   SYNTAX      INTEGER
               {
               unchanged (256)
               }
   MAX-ACCESS  read-write
   STATUS      current
   DESCRIPTION
      "Path: virtualEthernet.editConf.vlan.bandwidth.action.eirAction.ethernet.cosDepth6

       Possibilities:
               unchanged   (256)"
   ::= {er1645v2VEthVlanEntry 150226432}

er1645v2VEthVlanBandwidthActEirActEthDei6 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth6

       Possibilities:
               unchanged   (255)
               clear   (0)
               set   (1)"
   ::= {er1645v2VEthVlanEntry 150231552}

er1645v2VEthVlanBandwidthActEirActEthCos7 OBJECT-TYPE
   SYNTAX      INTEGER
               {
               unchanged (256)
               }
   MAX-ACCESS  read-write
   STATUS      current
   DESCRIPTION
      "Path: virtualEthernet.editConf.vlan.bandwidth.action.eirAction.ethernet.cosDepth7

       Possibilities:
               unchanged   (256)"
   ::= {er1645v2VEthVlanEntry 150226688}

er1645v2VEthVlanBandwidthActEirActEthDei7 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth7

       Possibilities:
               unchanged   (255)
               clear   (0)
               set   (1)"
   ::= {er1645v2VEthVlanEntry 150231808}

er1645v2VEthVlanBandwidthActEirActEthCos8 OBJECT-TYPE
   SYNTAX      INTEGER
               {
               unchanged (256)
               }
   MAX-ACCESS  read-write
   STATUS      current
   DESCRIPTION
      "Path: virtualEthernet.editConf.vlan.bandwidth.action.eirAction.ethernet.cosDepth8

       Possibilities:
               unchanged   (256)"
   ::= {er1645v2VEthVlanEntry 150226944}

er1645v2VEthVlanBandwidthActEirActEthDei8 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth8

       Possibilities:
               unchanged   (255)
               clear   (0)
               set   (1)"
   ::= {er1645v2VEthVlanEntry 150232064}

er1645v2VEthVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 150227200}

er1645v2VEthVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 150227456}

er1645v2VEthVlanBandwidthActEirActEthDrpLev OBJECT-TYPE
   SYNTAX      INTEGER
               {
               unchanged (0)
               }
   MAX-ACCESS  read-write
   STATUS      current
   DESCRIPTION
      "Path: virtualEthernet.editConf.vlan.bandwidth.action.eirAction.ethernet.dropLevel

       Possibilities:
               unchanged   (0)"
   ::= {er1645v2VEthVlanEntry 150227712}

er1645v2VEthVlanBandwidthActEirActEthDeFlag OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deFlag

       Possibilities:
               unchanged   (255)
               clear   (0)
               set   (1)"
   ::= {er1645v2VEthVlanEntry 150228480}

er1645v2VEthVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 150251776}

er1645v2VEthVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 150252032}

er1645v2VEthVlanBandwidthActEirActIpDrpLev OBJECT-TYPE
   SYNTAX      INTEGER
               {
               unchanged (0)
               }
   MAX-ACCESS  read-write
   STATUS      current
   DESCRIPTION
      "Path: virtualEthernet.editConf.vlan.bandwidth.action.eirAction.ip.dropLevel

       Possibilities:
               unchanged   (0)"
   ::= {er1645v2VEthVlanEntry 150252288}

er1645v2VEthVlanBandwidthActEirActIpDeFlag OBJECT-TYPE
   SYNTAX      INTEGER
               {
               unchanged (255),
               clear (0),
               set (1)
               }
   MAX-ACCESS  read-write
   STATUS      current
   DESCRIPTION
      "Path: virtualEthernet.editConf.vlan.bandwidth.action.eirAction.ip.deFlag

       Possibilities:
               unchanged   (255)
               clear   (0)
               set   (1)"
   ::= {er1645v2VEthVlanEntry 150253056}

er1645v2VEthVlanBandwidthActViolActNone OBJECT-TYPE
   SYNTAX      OCTET STRING
   MAX-ACCESS  read-write
   STATUS      current
   DESCRIPTION
      "Path: virtualEthernet.editConf.vlan.bandwidth.action.violateAction.none"
   ::= {er1645v2VEthVlanEntry 150347776}

er1645v2VEthVlanBandwidthActViolActDrop OBJECT-TYPE
   SYNTAX      OCTET STRING
   MAX-ACCESS  read-write
   STATUS      current
   DESCRIPTION
      "Path: virtualEthernet.editConf.vlan.bandwidth.action.violateAction.drop"
   ::= {er1645v2VEthVlanEntry 150364160}

er1645v2VEthVlanBandwidthActViolActEthCos1 OBJECT-TYPE
   SYNTAX      INTEGER
               {
               unchanged (256)
               }
   MAX-ACCESS  read-write
   STATUS      current
   DESCRIPTION
      "Path: virtualEthernet.editConf.vlan.bandwidth.action.violateAction.ethernet.cosDepth1

       Possibilities:
               unchanged   (256)"
   ::= {er1645v2VEthVlanEntry 150356224}

er1645v2VEthVlanBandwidthActViolActEthDei1 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth1

       Possibilities:
               unchanged   (255)
               clear   (0)
               set   (1)"
   ::= {er1645v2VEthVlanEntry 150361344}

er1645v2VEthVlanBandwidthActViolActEthCos2 OBJECT-TYPE
   SYNTAX      INTEGER
               {
               unchanged (256)
               }
   MAX-ACCESS  read-write
   STATUS      current
   DESCRIPTION
      "Path: virtualEthernet.editConf.vlan.bandwidth.action.violateAction.ethernet.cosDepth2

       Possibilities:
               unchanged   (256)"
   ::= {er1645v2VEthVlanEntry 150356480}

er1645v2VEthVlanBandwidthActViolActEthDei2 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth2

       Possibilities:
               unchanged   (255)
               clear   (0)
               set   (1)"
   ::= {er1645v2VEthVlanEntry 150361600}

er1645v2VEthVlanBandwidthActViolActEthCos3 OBJECT-TYPE
   SYNTAX      INTEGER
               {
               unchanged (256)
               }
   MAX-ACCESS  read-write
   STATUS      current
   DESCRIPTION
      "Path: virtualEthernet.editConf.vlan.bandwidth.action.violateAction.ethernet.cosDepth3

       Possibilities:
               unchanged   (256)"
   ::= {er1645v2VEthVlanEntry 150356736}

er1645v2VEthVlanBandwidthActViolActEthDei3 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth3

       Possibilities:
               unchanged   (255)
               clear   (0)
               set   (1)"
   ::= {er1645v2VEthVlanEntry 150361856}

er1645v2VEthVlanBandwidthActViolActEthCos4 OBJECT-TYPE
   SYNTAX      INTEGER
               {
               unchanged (256)
               }
   MAX-ACCESS  read-write
   STATUS      current
   DESCRIPTION
      "Path: virtualEthernet.editConf.vlan.bandwidth.action.violateAction.ethernet.cosDepth4

       Possibilities:
               unchanged   (256)"
   ::= {er1645v2VEthVlanEntry 150356992}

er1645v2VEthVlanBandwidthActViolActEthDei4 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth4

       Possibilities:
               unchanged   (255)
               clear   (0)
               set   (1)"
   ::= {er1645v2VEthVlanEntry 150362112}

er1645v2VEthVlanBandwidthActViolActEthCos5 OBJECT-TYPE
   SYNTAX      INTEGER
               {
               unchanged (256)
               }
   MAX-ACCESS  read-write
   STATUS      current
   DESCRIPTION
      "Path: virtualEthernet.editConf.vlan.bandwidth.action.violateAction.ethernet.cosDepth5

       Possibilities:
               unchanged   (256)"
   ::= {er1645v2VEthVlanEntry 150357248}

er1645v2VEthVlanBandwidthActViolActEthDei5 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth5

       Possibilities:
               unchanged   (255)
               clear   (0)
               set   (1)"
   ::= {er1645v2VEthVlanEntry 150362368}

er1645v2VEthVlanBandwidthActViolActEthCos6 OBJECT-TYPE
   SYNTAX      INTEGER
               {
               unchanged (256)
               }
   MAX-ACCESS  read-write
   STATUS      current
   DESCRIPTION
      "Path: virtualEthernet.editConf.vlan.bandwidth.action.violateAction.ethernet.cosDepth6

       Possibilities:
               unchanged   (256)"
   ::= {er1645v2VEthVlanEntry 150357504}

er1645v2VEthVlanBandwidthActViolActEthDei6 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth6

       Possibilities:
               unchanged   (255)
               clear   (0)
               set   (1)"
   ::= {er1645v2VEthVlanEntry 150362624}

er1645v2VEthVlanBandwidthActViolActEthCos7 OBJECT-TYPE
   SYNTAX      INTEGER
               {
               unchanged (256)
               }
   MAX-ACCESS  read-write
   STATUS      current
   DESCRIPTION
      "Path: virtualEthernet.editConf.vlan.bandwidth.action.violateAction.ethernet.cosDepth7

       Possibilities:
               unchanged   (256)"
   ::= {er1645v2VEthVlanEntry 150357760}

er1645v2VEthVlanBandwidthActViolActEthDei7 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth7

       Possibilities:
               unchanged   (255)
               clear   (0)
               set   (1)"
   ::= {er1645v2VEthVlanEntry 150362880}

er1645v2VEthVlanBandwidthActViolActEthCos8 OBJECT-TYPE
   SYNTAX      INTEGER
               {
               unchanged (256)
               }
   MAX-ACCESS  read-write
   STATUS      current
   DESCRIPTION
      "Path: virtualEthernet.editConf.vlan.bandwidth.action.violateAction.ethernet.cosDepth8

       Possibilities:
               unchanged   (256)"
   ::= {er1645v2VEthVlanEntry 150358016}

er1645v2VEthVlanBandwidthActViolActEthDei8 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth8

       Possibilities:
               unchanged   (255)
               clear   (0)
               set   (1)"
   ::= {er1645v2VEthVlanEntry 150363136}

er1645v2VEthVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 150358272}

er1645v2VEthVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 150358528}

er1645v2VEthVlanBandwidthActViolActEthDrpLev OBJECT-TYPE
   SYNTAX      INTEGER
               {
               unchanged (0)
               }
   MAX-ACCESS  read-write
   STATUS      current
   DESCRIPTION
      "Path: virtualEthernet.editConf.vlan.bandwidth.action.violateAction.ethernet.dropLevel

       Possibilities:
               unchanged   (0)"
   ::= {er1645v2VEthVlanEntry 150358784}

er1645v2VEthVlanBandwidthActViolActEthDeFlag OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deFlag

       Possibilities:
               unchanged   (255)
               clear   (0)
               set   (1)"
   ::= {er1645v2VEthVlanEntry 150359552}

er1645v2VEthVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 150382848}

er1645v2VEthVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 150383104}

er1645v2VEthVlanBandwidthActViolActIpDrpLev OBJECT-TYPE
   SYNTAX      INTEGER
               {
               unchanged (0)
               }
   MAX-ACCESS  read-write
   STATUS      current
   DESCRIPTION
      "Path: virtualEthernet.editConf.vlan.bandwidth.action.violateAction.ip.dropLevel

       Possibilities:
               unchanged   (0)"
   ::= {er1645v2VEthVlanEntry 150383360}

er1645v2VEthVlanBandwidthActViolActIpDeFlag OBJECT-TYPE
   SYNTAX      INTEGER
               {
               unchanged (255),
               clear (0),
               set (1)
               }
   MAX-ACCESS  read-write
   STATUS      current
   DESCRIPTION
      "Path: virtualEthernet.editConf.vlan.bandwidth.action.violateAction.ip.deFlag

       Possibilities:
               unchanged   (255)
               clear   (0)
               set   (1)"
   ::= {er1645v2VEthVlanEntry 150384128}

er1645v2VEthVlanInbBwMode OBJECT-TYPE
   SYNTAX      INTEGER
               {
               reshaping (1),
               policing (2)
               }
   MAX-ACCESS  read-write
   STATUS      current
   DESCRIPTION
      "Path: virtualEthernet.editConf.vlan.inboundBandwidth.mode

       Possibilities:
               reshaping   (1)
               policing   (2)"
   ::= {er1645v2VEthVlanEntry 132120576}

er1645v2VEthVlanInbBwCir OBJECT-TYPE
   SYNTAX      Integer32
   MAX-ACCESS  read-write
   STATUS      current
   DESCRIPTION
      "Path: virtualEthernet.editConf.vlan.inboundBandwidth.cir"
   ::= {er1645v2VEthVlanEntry 118489088}

er1645v2VEthVlanInbBwEir OBJECT-TYPE
   SYNTAX      Integer32
   MAX-ACCESS  read-write
   STATUS      current
   DESCRIPTION
      "Path: virtualEthernet.editConf.vlan.inboundBandwidth.eir"
   ::= {er1645v2VEthVlanEntry 124780544}

er1645v2VEthVlanInbBwUnit OBJECT-TYPE
   SYNTAX      INTEGER
               {
               bitssec (1),
               percent (2)
               }
   MAX-ACCESS  read-write
   STATUS      current
   DESCRIPTION
      "Path: virtualEthernet.editConf.vlan.inboundBandwidth.unit

       Possibilities:
               bits/sec   (1)
               percent   (2)"
   ::= {er1645v2VEthVlanEntry 122683392}

er1645v2VEthVlanInbBwTc OBJECT-TYPE
   SYNTAX      INTEGER
               {
               auto (0)
               }
   MAX-ACCESS  read-write
   STATUS      current
   DESCRIPTION
      "Path: virtualEthernet.editConf.vlan.inboundBandwidth.tc

       Possibilities:
               auto   (0)"
   ::= {er1645v2VEthVlanEntry 123731968}

er1645v2VEthVlanInbBwTcFactor OBJECT-TYPE
   SYNTAX      INTEGER
               {
               ms (10),
               s100us (1)
               }
   MAX-ACCESS  read-write
   STATUS      current
   DESCRIPTION
      "Path: virtualEthernet.editConf.vlan.inboundBandwidth.tcFactor

       Possibilities:
               ms   (10)
               *100us   (1)"
   ::= {er1645v2VEthVlanEntry 125829120}

er1645v2VEthVlanInbBwCorrType OBJECT-TYPE
   SYNTAX      INTEGER
               {
               noCorrection (0),
               predefined (1),
               manual (2)
               }
   MAX-ACCESS  read-write
   STATUS      current
   DESCRIPTION
      "Path: virtualEthernet.editConf.vlan.inboundBandwidth.correction.type

       Possibilities:
               noCorrection   (0)
               predefined   (1)
               manual   (2)"
   ::= {er1645v2VEthVlanEntry 119668736}

er1645v2VEthVlanInbBwCorrPredefEncapsFrameRelay OBJECT-TYPE
   SYNTAX      DisplayString
   MAX-ACCESS  read-write
   STATUS      current
   DESCRIPTION
      "Path: virtualEthernet.editConf.vlan.inboundBandwidth.correction.predefined.encapsulation.frameRelay"
   ::= {er1645v2VEthVlanEntry 119817216}

er1645v2VEthVlanInbBwCorrPredefEncapsPpp OBJECT-TYPE
   SYNTAX      DisplayString
   MAX-ACCESS  read-write
   STATUS      current
   DESCRIPTION
      "Path: virtualEthernet.editConf.vlan.inboundBandwidth.correction.predefined.encapsulation.ppp"
   ::= {er1645v2VEthVlanEntry 119818240}

er1645v2VEthVlanInbBwCorrPredefEncapsAtmHl OBJECT-TYPE
   SYNTAX      INTEGER
               {
               rfc2684 (0),
               ppp (1),
               pppOverEthernet (2)
               }
   MAX-ACCESS  read-write
   STATUS      current
   DESCRIPTION
      "Path: virtualEthernet.editConf.vlan.inboundBandwidth.correction.predefined.encapsulation.atm.higherLayer

       Possibilities:
               rfc2684   (0)
               ppp   (1)
               pppOverEthernet   (2)"
   ::= {er1645v2VEthVlanEntry 119819392}

er1645v2VEthVlanInbBwCorrPredefEncapsAtmMp OBJECT-TYPE
   SYNTAX      INTEGER
               {
               llcEncapsulation (0),
               vcMultiplexing (1)
               }
   MAX-ACCESS  read-write
   STATUS      current
   DESCRIPTION
      "Path: virtualEthernet.editConf.vlan.inboundBandwidth.correction.predefined.encapsulation.atm.multiProtocol

       Possibilities:
               llcEncapsulation   (0)
               vcMultiplexing   (1)"
   ::= {er1645v2VEthVlanEntry 119819520}

er1645v2VEthVlanInbBwCorrPredefEncapsHdlc OBJECT-TYPE
   SYNTAX      DisplayString
   MAX-ACCESS  read-write
   STATUS      current
   DESCRIPTION
      "Path: virtualEthernet.editConf.vlan.inboundBandwidth.correction.predefined.encapsulation.hdlc"
   ::= {er1645v2VEthVlanEntry 119820288}

er1645v2VEthVlanInbBwCorrPredefEncapsEfmFs OBJECT-TYPE
   SYNTAX      Integer32
   MAX-ACCESS  read-write
   STATUS      current
   DESCRIPTION
      "Path: virtualEthernet.editConf.vlan.inboundBandwidth.correction.predefined.encapsulation.efm.fragmentSize"
   ::= {er1645v2VEthVlanEntry 119821440}

er1645v2VEthVlanInbBwCorrPredefEncapsEfmIb OBJECT-TYPE
   SYNTAX      Integer32
   MAX-ACCESS  read-write
   STATUS      current
   DESCRIPTION
      "Path: virtualEthernet.editConf.vlan.inboundBandwidth.correction.predefined.encapsulation.efm.idleBytes"
   ::= {er1645v2VEthVlanEntry 119821568}

er1645v2VEthVlanInbBwCorrPredefMode OBJECT-TYPE
   SYNTAX      INTEGER
               {
               routing (0),
               bridging (1)
               }
   MAX-ACCESS  read-write
   STATUS      current
   DESCRIPTION
      "Path: virtualEthernet.editConf.vlan.inboundBandwidth.correction.predefined.mode

       Possibilities:
               routing   (0)
               bridging   (1)"
   ::= {er1645v2VEthVlanEntry 119832576}

er1645v2VEthVlanInbBwCorrManualOverhead OBJECT-TYPE
   SYNTAX      Integer32
   MAX-ACCESS  read-write
   STATUS      current
   DESCRIPTION
      "Path: virtualEthernet.editConf.vlan.inboundBandwidth.correction.manual.overhead"
   ::= {er1645v2VEthVlanEntry 119931392}

er1645v2VEthVlanInbBwCorrManualFrameData OBJECT-TYPE
   SYNTAX      Counter32
   MAX-ACCESS  read-write
   STATUS      current
   DESCRIPTION
      "Path: virtualEthernet.editConf.vlan.inboundBandwidth.correction.manual.frameData

       32 bit unsigned wrappable counter."
   ::= {er1645v2VEthVlanEntry 119931904}

er1645v2VEthVlanInbBwCorrManualFrameHeader OBJECT-TYPE
   SYNTAX      Counter32
   MAX-ACCESS  read-write
   STATUS      current
   DESCRIPTION
      "Path: virtualEthernet.editConf.vlan.inboundBandwidth.correction.manual.frameHeader

       32 bit unsigned wrappable counter."
   ::= {er1645v2VEthVlanEntry 119932416}

er1645v2VEthVlanInbBwMaxFifoQLen OBJECT-TYPE
   SYNTAX      Integer32
   MAX-ACCESS  read-write
   STATUS      current
   DESCRIPTION
      "Path: virtualEthernet.editConf.vlan.inboundBandwidth.maxFifoQLen"
   ::= {er1645v2VEthVlanEntry 120586240}

er1645v2VEthVlanInbBwPriorityPolicy OBJECT-TYPE
   SYNTAX      DisplayString
   MAX-ACCESS  read-write
   STATUS      current
   DESCRIPTION
      "Path: virtualEthernet.editConf.vlan.inboundBandwidth.priorityPolicy"
   ::= {er1645v2VEthVlanEntry 121634816}

er1645v2VEthVlanInbBwDeFlagCir OBJECT-TYPE
   SYNTAX      INTEGER
               {
               allowed (1),
               notAllowed (2)
               }
   MAX-ACCESS  read-write
   STATUS      current
   DESCRIPTION
      "Path: virtualEthernet.editConf.vlan.inboundBandwidth.deFlag.cir

       Possibilities:
               allowed   (1)
               notAllowed   (2)"
   ::= {er1645v2VEthVlanEntry 131076096}

er1645v2VEthVlanInbBwDeFlagEir OBJECT-TYPE
   SYNTAX      INTEGER
               {
               allowed (1),
               notAllowed (2)
               }
   MAX-ACCESS  read-write
   STATUS      current
   DESCRIPTION
      "Path: virtualEthernet.editConf.vlan.inboundBandwidth.deFlag.eir

       Possibilities:
               allowed   (1)
               notAllowed   (2)"
   ::= {er1645v2VEthVlanEntry 131080192}

er1645v2VEthVlanInbBwDeFlagViolate OBJECT-TYPE
   SYNTAX      INTEGER
               {
               allowed (1),
               notAllowed (2)
               }
   MAX-ACCESS  read-write
   STATUS      current
   DESCRIPTION
      "Path: virtualEthernet.editConf.vlan.inboundBandwidth.deFlag.violate

       Possibilities:
               allowed   (1)
               notAllowed   (2)"
   ::= {er1645v2VEthVlanEntry 131084288}

er1645v2VEthVlanInbBwActCirActNone OBJECT-TYPE
   SYNTAX      OCTET STRING
   MAX-ACCESS  read-write
   STATUS      current
   DESCRIPTION
      "Path: virtualEthernet.editConf.vlan.inboundBandwidth.action.cirAction.none"
   ::= {er1645v2VEthVlanEntry 133308416}

er1645v2VEthVlanInbBwActCirActEthCos1 OBJECT-TYPE
   SYNTAX      INTEGER
               {
               unchanged (256)
               }
   MAX-ACCESS  read-write
   STATUS      current
   DESCRIPTION
      "Path: virtualEthernet.editConf.vlan.inboundBandwidth.action.cirAction.ethernet.cosDepth1

       Possibilities:
               unchanged   (256)"
   ::= {er1645v2VEthVlanEntry 133316864}

er1645v2VEthVlanInbBwActCirActEthDei1 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth1

       Possibilities:
               unchanged   (255)
               clear   (0)
               set   (1)"
   ::= {er1645v2VEthVlanEntry 133321984}

er1645v2VEthVlanInbBwActCirActEthCos2 OBJECT-TYPE
   SYNTAX      INTEGER
               {
               unchanged (256)
               }
   MAX-ACCESS  read-write
   STATUS      current
   DESCRIPTION
      "Path: virtualEthernet.editConf.vlan.inboundBandwidth.action.cirAction.ethernet.cosDepth2

       Possibilities:
               unchanged   (256)"
   ::= {er1645v2VEthVlanEntry 133317120}

er1645v2VEthVlanInbBwActCirActEthDei2 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth2

       Possibilities:
               unchanged   (255)
               clear   (0)
               set   (1)"
   ::= {er1645v2VEthVlanEntry 133322240}

er1645v2VEthVlanInbBwActCirActEthCos3 OBJECT-TYPE
   SYNTAX      INTEGER
               {
               unchanged (256)
               }
   MAX-ACCESS  read-write
   STATUS      current
   DESCRIPTION
      "Path: virtualEthernet.editConf.vlan.inboundBandwidth.action.cirAction.ethernet.cosDepth3

       Possibilities:
               unchanged   (256)"
   ::= {er1645v2VEthVlanEntry 133317376}

er1645v2VEthVlanInbBwActCirActEthDei3 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth3

       Possibilities:
               unchanged   (255)
               clear   (0)
               set   (1)"
   ::= {er1645v2VEthVlanEntry 133322496}

er1645v2VEthVlanInbBwActCirActEthCos4 OBJECT-TYPE
   SYNTAX      INTEGER
               {
               unchanged (256)
               }
   MAX-ACCESS  read-write
   STATUS      current
   DESCRIPTION
      "Path: virtualEthernet.editConf.vlan.inboundBandwidth.action.cirAction.ethernet.cosDepth4

       Possibilities:
               unchanged   (256)"
   ::= {er1645v2VEthVlanEntry 133317632}

er1645v2VEthVlanInbBwActCirActEthDei4 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth4

       Possibilities:
               unchanged   (255)
               clear   (0)
               set   (1)"
   ::= {er1645v2VEthVlanEntry 133322752}

er1645v2VEthVlanInbBwActCirActEthCos5 OBJECT-TYPE
   SYNTAX      INTEGER
               {
               unchanged (256)
               }
   MAX-ACCESS  read-write
   STATUS      current
   DESCRIPTION
      "Path: virtualEthernet.editConf.vlan.inboundBandwidth.action.cirAction.ethernet.cosDepth5

       Possibilities:
               unchanged   (256)"
   ::= {er1645v2VEthVlanEntry 133317888}

er1645v2VEthVlanInbBwActCirActEthDei5 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth5

       Possibilities:
               unchanged   (255)
               clear   (0)
               set   (1)"
   ::= {er1645v2VEthVlanEntry 133323008}

er1645v2VEthVlanInbBwActCirActEthCos6 OBJECT-TYPE
   SYNTAX      INTEGER
               {
               unchanged (256)
               }
   MAX-ACCESS  read-write
   STATUS      current
   DESCRIPTION
      "Path: virtualEthernet.editConf.vlan.inboundBandwidth.action.cirAction.ethernet.cosDepth6

       Possibilities:
               unchanged   (256)"
   ::= {er1645v2VEthVlanEntry 133318144}

er1645v2VEthVlanInbBwActCirActEthDei6 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth6

       Possibilities:
               unchanged   (255)
               clear   (0)
               set   (1)"
   ::= {er1645v2VEthVlanEntry 133323264}

er1645v2VEthVlanInbBwActCirActEthCos7 OBJECT-TYPE
   SYNTAX      INTEGER
               {
               unchanged (256)
               }
   MAX-ACCESS  read-write
   STATUS      current
   DESCRIPTION
      "Path: virtualEthernet.editConf.vlan.inboundBandwidth.action.cirAction.ethernet.cosDepth7

       Possibilities:
               unchanged   (256)"
   ::= {er1645v2VEthVlanEntry 133318400}

er1645v2VEthVlanInbBwActCirActEthDei7 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth7

       Possibilities:
               unchanged   (255)
               clear   (0)
               set   (1)"
   ::= {er1645v2VEthVlanEntry 133323520}

er1645v2VEthVlanInbBwActCirActEthCos8 OBJECT-TYPE
   SYNTAX      INTEGER
               {
               unchanged (256)
               }
   MAX-ACCESS  read-write
   STATUS      current
   DESCRIPTION
      "Path: virtualEthernet.editConf.vlan.inboundBandwidth.action.cirAction.ethernet.cosDepth8

       Possibilities:
               unchanged   (256)"
   ::= {er1645v2VEthVlanEntry 133318656}

er1645v2VEthVlanInbBwActCirActEthDei8 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth8

       Possibilities:
               unchanged   (255)
               clear   (0)
               set   (1)"
   ::= {er1645v2VEthVlanEntry 133323776}

er1645v2VEthVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 133318912}

er1645v2VEthVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 133319168}

er1645v2VEthVlanInbBwActCirActEthDrpLev OBJECT-TYPE
   SYNTAX      INTEGER
               {
               unchanged (0)
               }
   MAX-ACCESS  read-write
   STATUS      current
   DESCRIPTION
      "Path: virtualEthernet.editConf.vlan.inboundBandwidth.action.cirAction.ethernet.dropLevel

       Possibilities:
               unchanged   (0)"
   ::= {er1645v2VEthVlanEntry 133319424}

er1645v2VEthVlanInbBwActCirActEthDeFlag OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deFlag

       Possibilities:
               unchanged   (255)
               clear   (0)
               set   (1)"
   ::= {er1645v2VEthVlanEntry 133320192}

er1645v2VEthVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 133343488}

er1645v2VEthVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 133343744}

er1645v2VEthVlanInbBwActCirActIpDrpLev OBJECT-TYPE
   SYNTAX      INTEGER
               {
               unchanged (0)
               }
   MAX-ACCESS  read-write
   STATUS      current
   DESCRIPTION
      "Path: virtualEthernet.editConf.vlan.inboundBandwidth.action.cirAction.ip.dropLevel

       Possibilities:
               unchanged   (0)"
   ::= {er1645v2VEthVlanEntry 133344000}

er1645v2VEthVlanInbBwActCirActIpDeFlag OBJECT-TYPE
   SYNTAX      INTEGER
               {
               unchanged (255),
               clear (0),
               set (1)
               }
   MAX-ACCESS  read-write
   STATUS      current
   DESCRIPTION
      "Path: virtualEthernet.editConf.vlan.inboundBandwidth.action.cirAction.ip.deFlag

       Possibilities:
               unchanged   (255)
               clear   (0)
               set   (1)"
   ::= {er1645v2VEthVlanEntry 133344768}

er1645v2VEthVlanInbBwActEirActNone OBJECT-TYPE
   SYNTAX      OCTET STRING
   MAX-ACCESS  read-write
   STATUS      current
   DESCRIPTION
      "Path: virtualEthernet.editConf.vlan.inboundBandwidth.action.eirAction.none"
   ::= {er1645v2VEthVlanEntry 133439488}

er1645v2VEthVlanInbBwActEirActEthCos1 OBJECT-TYPE
   SYNTAX      INTEGER
               {
               unchanged (256)
               }
   MAX-ACCESS  read-write
   STATUS      current
   DESCRIPTION
      "Path: virtualEthernet.editConf.vlan.inboundBandwidth.action.eirAction.ethernet.cosDepth1

       Possibilities:
               unchanged   (256)"
   ::= {er1645v2VEthVlanEntry 133447936}

er1645v2VEthVlanInbBwActEirActEthDei1 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth1

       Possibilities:
               unchanged   (255)
               clear   (0)
               set   (1)"
   ::= {er1645v2VEthVlanEntry 133453056}

er1645v2VEthVlanInbBwActEirActEthCos2 OBJECT-TYPE
   SYNTAX      INTEGER
               {
               unchanged (256)
               }
   MAX-ACCESS  read-write
   STATUS      current
   DESCRIPTION
      "Path: virtualEthernet.editConf.vlan.inboundBandwidth.action.eirAction.ethernet.cosDepth2

       Possibilities:
               unchanged   (256)"
   ::= {er1645v2VEthVlanEntry 133448192}

er1645v2VEthVlanInbBwActEirActEthDei2 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth2

       Possibilities:
               unchanged   (255)
               clear   (0)
               set   (1)"
   ::= {er1645v2VEthVlanEntry 133453312}

er1645v2VEthVlanInbBwActEirActEthCos3 OBJECT-TYPE
   SYNTAX      INTEGER
               {
               unchanged (256)
               }
   MAX-ACCESS  read-write
   STATUS      current
   DESCRIPTION
      "Path: virtualEthernet.editConf.vlan.inboundBandwidth.action.eirAction.ethernet.cosDepth3

       Possibilities:
               unchanged   (256)"
   ::= {er1645v2VEthVlanEntry 133448448}

er1645v2VEthVlanInbBwActEirActEthDei3 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth3

       Possibilities:
               unchanged   (255)
               clear   (0)
               set   (1)"
   ::= {er1645v2VEthVlanEntry 133453568}

er1645v2VEthVlanInbBwActEirActEthCos4 OBJECT-TYPE
   SYNTAX      INTEGER
               {
               unchanged (256)
               }
   MAX-ACCESS  read-write
   STATUS      current
   DESCRIPTION
      "Path: virtualEthernet.editConf.vlan.inboundBandwidth.action.eirAction.ethernet.cosDepth4

       Possibilities:
               unchanged   (256)"
   ::= {er1645v2VEthVlanEntry 133448704}

er1645v2VEthVlanInbBwActEirActEthDei4 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth4

       Possibilities:
               unchanged   (255)
               clear   (0)
               set   (1)"
   ::= {er1645v2VEthVlanEntry 133453824}

er1645v2VEthVlanInbBwActEirActEthCos5 OBJECT-TYPE
   SYNTAX      INTEGER
               {
               unchanged (256)
               }
   MAX-ACCESS  read-write
   STATUS      current
   DESCRIPTION
      "Path: virtualEthernet.editConf.vlan.inboundBandwidth.action.eirAction.ethernet.cosDepth5

       Possibilities:
               unchanged   (256)"
   ::= {er1645v2VEthVlanEntry 133448960}

er1645v2VEthVlanInbBwActEirActEthDei5 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth5

       Possibilities:
               unchanged   (255)
               clear   (0)
               set   (1)"
   ::= {er1645v2VEthVlanEntry 133454080}

er1645v2VEthVlanInbBwActEirActEthCos6 OBJECT-TYPE
   SYNTAX      INTEGER
               {
               unchanged (256)
               }
   MAX-ACCESS  read-write
   STATUS      current
   DESCRIPTION
      "Path: virtualEthernet.editConf.vlan.inboundBandwidth.action.eirAction.ethernet.cosDepth6

       Possibilities:
               unchanged   (256)"
   ::= {er1645v2VEthVlanEntry 133449216}

er1645v2VEthVlanInbBwActEirActEthDei6 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth6

       Possibilities:
               unchanged   (255)
               clear   (0)
               set   (1)"
   ::= {er1645v2VEthVlanEntry 133454336}

er1645v2VEthVlanInbBwActEirActEthCos7 OBJECT-TYPE
   SYNTAX      INTEGER
               {
               unchanged (256)
               }
   MAX-ACCESS  read-write
   STATUS      current
   DESCRIPTION
      "Path: virtualEthernet.editConf.vlan.inboundBandwidth.action.eirAction.ethernet.cosDepth7

       Possibilities:
               unchanged   (256)"
   ::= {er1645v2VEthVlanEntry 133449472}

er1645v2VEthVlanInbBwActEirActEthDei7 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth7

       Possibilities:
               unchanged   (255)
               clear   (0)
               set   (1)"
   ::= {er1645v2VEthVlanEntry 133454592}

er1645v2VEthVlanInbBwActEirActEthCos8 OBJECT-TYPE
   SYNTAX      INTEGER
               {
               unchanged (256)
               }
   MAX-ACCESS  read-write
   STATUS      current
   DESCRIPTION
      "Path: virtualEthernet.editConf.vlan.inboundBandwidth.action.eirAction.ethernet.cosDepth8

       Possibilities:
               unchanged   (256)"
   ::= {er1645v2VEthVlanEntry 133449728}

er1645v2VEthVlanInbBwActEirActEthDei8 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth8

       Possibilities:
               unchanged   (255)
               clear   (0)
               set   (1)"
   ::= {er1645v2VEthVlanEntry 133454848}

er1645v2VEthVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 133449984}

er1645v2VEthVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 133450240}

er1645v2VEthVlanInbBwActEirActEthDrpLev OBJECT-TYPE
   SYNTAX      INTEGER
               {
               unchanged (0)
               }
   MAX-ACCESS  read-write
   STATUS      current
   DESCRIPTION
      "Path: virtualEthernet.editConf.vlan.inboundBandwidth.action.eirAction.ethernet.dropLevel

       Possibilities:
               unchanged   (0)"
   ::= {er1645v2VEthVlanEntry 133450496}

er1645v2VEthVlanInbBwActEirActEthDeFlag OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deFlag

       Possibilities:
               unchanged   (255)
               clear   (0)
               set   (1)"
   ::= {er1645v2VEthVlanEntry 133451264}

er1645v2VEthVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 133474560}

er1645v2VEthVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 133474816}

er1645v2VEthVlanInbBwActEirActIpDrpLev OBJECT-TYPE
   SYNTAX      INTEGER
               {
               unchanged (0)
               }
   MAX-ACCESS  read-write
   STATUS      current
   DESCRIPTION
      "Path: virtualEthernet.editConf.vlan.inboundBandwidth.action.eirAction.ip.dropLevel

       Possibilities:
               unchanged   (0)"
   ::= {er1645v2VEthVlanEntry 133475072}

er1645v2VEthVlanInbBwActEirActIpDeFlag OBJECT-TYPE
   SYNTAX      INTEGER
               {
               unchanged (255),
               clear (0),
               set (1)
               }
   MAX-ACCESS  read-write
   STATUS      current
   DESCRIPTION
      "Path: virtualEthernet.editConf.vlan.inboundBandwidth.action.eirAction.ip.deFlag

       Possibilities:
               unchanged   (255)
               clear   (0)
               set   (1)"
   ::= {er1645v2VEthVlanEntry 133475840}

er1645v2VEthVlanInbBwActViolActNone OBJECT-TYPE
   SYNTAX      OCTET STRING
   MAX-ACCESS  read-write
   STATUS      current
   DESCRIPTION
      "Path: virtualEthernet.editConf.vlan.inboundBandwidth.action.violateAction.none"
   ::= {er1645v2VEthVlanEntry 133570560}

er1645v2VEthVlanInbBwActViolActDrop OBJECT-TYPE
   SYNTAX      OCTET STRING
   MAX-ACCESS  read-write
   STATUS      current
   DESCRIPTION
      "Path: virtualEthernet.editConf.vlan.inboundBandwidth.action.violateAction.drop"
   ::= {er1645v2VEthVlanEntry 133586944}

er1645v2VEthVlanInbBwActViolActEthCos1 OBJECT-TYPE
   SYNTAX      INTEGER
               {
               unchanged (256)
               }
   MAX-ACCESS  read-write
   STATUS      current
   DESCRIPTION
      "Path: virtualEthernet.editConf.vlan.inboundBandwidth.action.violateAction.ethernet.cosDepth1

       Possibilities:
               unchanged   (256)"
   ::= {er1645v2VEthVlanEntry 133579008}

er1645v2VEthVlanInbBwActViolActEthDei1 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth1

       Possibilities:
               unchanged   (255)
               clear   (0)
               set   (1)"
   ::= {er1645v2VEthVlanEntry 133584128}

er1645v2VEthVlanInbBwActViolActEthCos2 OBJECT-TYPE
   SYNTAX      INTEGER
               {
               unchanged (256)
               }
   MAX-ACCESS  read-write
   STATUS      current
   DESCRIPTION
      "Path: virtualEthernet.editConf.vlan.inboundBandwidth.action.violateAction.ethernet.cosDepth2

       Possibilities:
               unchanged   (256)"
   ::= {er1645v2VEthVlanEntry 133579264}

er1645v2VEthVlanInbBwActViolActEthDei2 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth2

       Possibilities:
               unchanged   (255)
               clear   (0)
               set   (1)"
   ::= {er1645v2VEthVlanEntry 133584384}

er1645v2VEthVlanInbBwActViolActEthCos3 OBJECT-TYPE
   SYNTAX      INTEGER
               {
               unchanged (256)
               }
   MAX-ACCESS  read-write
   STATUS      current
   DESCRIPTION
      "Path: virtualEthernet.editConf.vlan.inboundBandwidth.action.violateAction.ethernet.cosDepth3

       Possibilities:
               unchanged   (256)"
   ::= {er1645v2VEthVlanEntry 133579520}

er1645v2VEthVlanInbBwActViolActEthDei3 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth3

       Possibilities:
               unchanged   (255)
               clear   (0)
               set   (1)"
   ::= {er1645v2VEthVlanEntry 133584640}

er1645v2VEthVlanInbBwActViolActEthCos4 OBJECT-TYPE
   SYNTAX      INTEGER
               {
               unchanged (256)
               }
   MAX-ACCESS  read-write
   STATUS      current
   DESCRIPTION
      "Path: virtualEthernet.editConf.vlan.inboundBandwidth.action.violateAction.ethernet.cosDepth4

       Possibilities:
               unchanged   (256)"
   ::= {er1645v2VEthVlanEntry 133579776}

er1645v2VEthVlanInbBwActViolActEthDei4 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth4

       Possibilities:
               unchanged   (255)
               clear   (0)
               set   (1)"
   ::= {er1645v2VEthVlanEntry 133584896}

er1645v2VEthVlanInbBwActViolActEthCos5 OBJECT-TYPE
   SYNTAX      INTEGER
               {
               unchanged (256)
               }
   MAX-ACCESS  read-write
   STATUS      current
   DESCRIPTION
      "Path: virtualEthernet.editConf.vlan.inboundBandwidth.action.violateAction.ethernet.cosDepth5

       Possibilities:
               unchanged   (256)"
   ::= {er1645v2VEthVlanEntry 133580032}

er1645v2VEthVlanInbBwActViolActEthDei5 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth5

       Possibilities:
               unchanged   (255)
               clear   (0)
               set   (1)"
   ::= {er1645v2VEthVlanEntry 133585152}

er1645v2VEthVlanInbBwActViolActEthCos6 OBJECT-TYPE
   SYNTAX      INTEGER
               {
               unchanged (256)
               }
   MAX-ACCESS  read-write
   STATUS      current
   DESCRIPTION
      "Path: virtualEthernet.editConf.vlan.inboundBandwidth.action.violateAction.ethernet.cosDepth6

       Possibilities:
               unchanged   (256)"
   ::= {er1645v2VEthVlanEntry 133580288}

er1645v2VEthVlanInbBwActViolActEthDei6 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth6

       Possibilities:
               unchanged   (255)
               clear   (0)
               set   (1)"
   ::= {er1645v2VEthVlanEntry 133585408}

er1645v2VEthVlanInbBwActViolActEthCos7 OBJECT-TYPE
   SYNTAX      INTEGER
               {
               unchanged (256)
               }
   MAX-ACCESS  read-write
   STATUS      current
   DESCRIPTION
      "Path: virtualEthernet.editConf.vlan.inboundBandwidth.action.violateAction.ethernet.cosDepth7

       Possibilities:
               unchanged   (256)"
   ::= {er1645v2VEthVlanEntry 133580544}

er1645v2VEthVlanInbBwActViolActEthDei7 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth7

       Possibilities:
               unchanged   (255)
               clear   (0)
               set   (1)"
   ::= {er1645v2VEthVlanEntry 133585664}

er1645v2VEthVlanInbBwActViolActEthCos8 OBJECT-TYPE
   SYNTAX      INTEGER
               {
               unchanged (256)
               }
   MAX-ACCESS  read-write
   STATUS      current
   DESCRIPTION
      "Path: virtualEthernet.editConf.vlan.inboundBandwidth.action.violateAction.ethernet.cosDepth8

       Possibilities:
               unchanged   (256)"
   ::= {er1645v2VEthVlanEntry 133580800}

er1645v2VEthVlanInbBwActViolActEthDei8 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth8

       Possibilities:
               unchanged   (255)
               clear   (0)
               set   (1)"
   ::= {er1645v2VEthVlanEntry 133585920}

er1645v2VEthVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 133581056}

er1645v2VEthVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 133581312}

er1645v2VEthVlanInbBwActViolActEthDrpLev OBJECT-TYPE
   SYNTAX      INTEGER
               {
               unchanged (0)
               }
   MAX-ACCESS  read-write
   STATUS      current
   DESCRIPTION
      "Path: virtualEthernet.editConf.vlan.inboundBandwidth.action.violateAction.ethernet.dropLevel

       Possibilities:
               unchanged   (0)"
   ::= {er1645v2VEthVlanEntry 133581568}

er1645v2VEthVlanInbBwActViolActEthDeFlag OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deFlag

       Possibilities:
               unchanged   (255)
               clear   (0)
               set   (1)"
   ::= {er1645v2VEthVlanEntry 133582336}

er1645v2VEthVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanEntry 133605632}

er1645v2VEthVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanEntry 133605888}

er1645v2VEthVlanInbBwActViolActIpDrpLev OBJECT-TYPE
   SYNTAX      INTEGER
               {
               unchanged (0)
               }
   MAX-ACCESS  read-write
   STATUS      current
   DESCRIPTION
      "Path: virtualEthernet.editConf.vlan.inboundBandwidth.action.violateAction.ip.dropLevel

       Possibilities:
               unchanged   (0)"
   ::= {er1645v2VEthVlanEntry 133606144}

er1645v2VEthVlanInbBwActViolActIpDeFlag OBJECT-TYPE
   SYNTAX      INTEGER
               {
               unchanged (255),
               clear (0),
               set (1)
               }
   MAX-ACCESS  read-write
   STATUS      current
   DESCRIPTION
      "Path: virtualEthernet.editConf.vlan.inboundBandwidth.action.violateAction.ip.deFlag

       Possibilities:
               unchanged   (255)
               clear   (0)
               set   (1)"
   ::= {er1645v2VEthVlanEntry 133606912}

er1645v2VEthVlanPppoE OBJECT-TYPE
   SYNTAX      INTEGER
               {
               disabled (0),
               enabled (1)
               }
   MAX-ACCESS  read-write
   STATUS      current
   DESCRIPTION
      "Path: virtualEthernet.editConf.vlan.pppoE

       Possibilities:
               disabled   (0)
               enabled   (1)"
   ::= {er1645v2VEthVlanEntry 838860800}

er1645v2VEthVlanPppLnkMOperation OBJECT-TYPE
   SYNTAX      INTEGER
               {
               disabled (0),
               enabled (1)
               }
   MAX-ACCESS  read-write
   STATUS      current
   DESCRIPTION
      "Path: virtualEthernet.editConf.vlan.ppp.linkMonitoring.operation

       Possibilities:
               disabled   (0)
               enabled   (1)"
   ::= {er1645v2VEthVlanEntry 251724032}

er1645v2VEthVlanPppLnkMInterval OBJECT-TYPE
   SYNTAX      TimeTicks
   MAX-ACCESS  read-write
   STATUS      current
   DESCRIPTION
      "Path: virtualEthernet.editConf.vlan.ppp.linkMonitoring.interval

       Time in centi-second."
   ::= {er1645v2VEthVlanEntry 251724288}

er1645v2VEthVlanPppLnkMRepTimeOut OBJECT-TYPE
   SYNTAX      TimeTicks
   MAX-ACCESS  read-write
   STATUS      current
   DESCRIPTION
      "Path: virtualEthernet.editConf.vlan.ppp.linkMonitoring.replyTimeOut

       Time in centi-second."
   ::= {er1645v2VEthVlanEntry 251724544}

er1645v2VEthVlanPppLnkMFailsPrmt OBJECT-TYPE
   SYNTAX      Integer32
   MAX-ACCESS  read-write
   STATUS      current
   DESCRIPTION
      "Path: virtualEthernet.editConf.vlan.ppp.linkMonitoring.failsPermitted"
   ::= {er1645v2VEthVlanEntry 251724800}

er1645v2VEthVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: virtualEthernet.editConf.vlan.ppp.authentication

       Possibilities:
               disabled   (0)
               chap   (1)
               pap   (2)
               chapOrPap   (3)
               msChap   (4)
               msChapV2   (5)"
   ::= {er1645v2VEthVlanEntry 251789312}

er1645v2VEthVlanPppAuthenPeriod OBJECT-TYPE
   SYNTAX      TimeTicks
   MAX-ACCESS  read-write
   STATUS      current
   DESCRIPTION
      "Path: virtualEthernet.editConf.vlan.ppp.authenPeriod

       Time in centi-second."
   ::= {er1645v2VEthVlanEntry 251854848}

er1645v2VEthVlanPppSessionName OBJECT-TYPE
   SYNTAX      DisplayString
   MAX-ACCESS  read-write
   STATUS      current
   DESCRIPTION
      "Path: virtualEthernet.editConf.vlan.ppp.sessionName"
   ::= {er1645v2VEthVlanEntry 251985920}

er1645v2VEthVlanPppSessionSecret OBJECT-TYPE
   SYNTAX      DisplayString
   MAX-ACCESS  read-write
   STATUS      current
   DESCRIPTION
      "Path: virtualEthernet.editConf.vlan.ppp.sessionSecret"
   ::= {er1645v2VEthVlanEntry 252051456}

er1645v2VEthVlanPppEncModeSessionSecret OBJECT-TYPE
   SYNTAX      INTEGER
               {
               none (1),
               encrypt (2),
               encType1 (3),
               invalid (128)
               }
   MAX-ACCESS  read-write
   STATUS      current
   DESCRIPTION
      "Path: virtualEthernet.editConf.vlan.ppp.encModeSessionSecret

       Possibilities:
               none   (1)
               encrypt   (2)
               encType1   (3)
               invalid   (128)"
   ::= {er1645v2VEthVlanEntry 252182528}

er1645v2VEthVlanPppEncSessionSecret OBJECT-TYPE
   SYNTAX      DisplayString
   MAX-ACCESS  read-write
   STATUS      current
   DESCRIPTION
      "Path: virtualEthernet.editConf.vlan.ppp.encSessionSecret"
   ::= {er1645v2VEthVlanEntry 252248064}

er1645v2VEthVlanPppServiceName OBJECT-TYPE
   SYNTAX      DisplayString
   MAX-ACCESS  read-write
   STATUS      current
   DESCRIPTION
      "Path: virtualEthernet.editConf.vlan.ppp.serviceName"
   ::= {er1645v2VEthVlanEntry 252116992}

er1645v2VEthVlanPbbMode OBJECT-TYPE
   SYNTAX      INTEGER
               {
               disabled (0),
               static (1),
               dynamicPtp (2),
               dynamicPtmp (3)
               }
   MAX-ACCESS  read-write
   STATUS      current
   DESCRIPTION
      "Path: virtualEthernet.editConf.vlan.pbb.mode

       Possibilities:
               disabled   (0)
               static   (1)
               dynamicPtp   (2)
               dynamicPtmp   (3)"
   ::= {er1645v2VEthVlanEntry 1174667264}

er1645v2VEthVlanPbbTxCos OBJECT-TYPE
   SYNTAX      Integer32
   MAX-ACCESS  read-write
   STATUS      current
   DESCRIPTION
      "Path: virtualEthernet.editConf.vlan.pbb.txCos"
   ::= {er1645v2VEthVlanEntry 1175191552}

er1645v2VEthVlanPbbIsid OBJECT-TYPE
   SYNTAX      Integer32
   MAX-ACCESS  read-write
   STATUS      current
   DESCRIPTION
      "Path: virtualEthernet.editConf.vlan.pbb.isid"
   ::= {er1645v2VEthVlanEntry 1175453696}

er1645v2VEthVlanPbbDestMac OBJECT-TYPE
   SYNTAX      OCTET STRING
   MAX-ACCESS  read-write
   STATUS      current
   DESCRIPTION
      "Path: virtualEthernet.editConf.vlan.pbb.destMac

       MAC address."
   ::= {er1645v2VEthVlanEntry 1175715840}

er1645v2VEthVlanPbbCustomGroupMac OBJECT-TYPE
   SYNTAX      OCTET STRING
   MAX-ACCESS  read-write
   STATUS      current
   DESCRIPTION
      "Path: virtualEthernet.editConf.vlan.pbb.customGroupMac

       MAC address."
   ::= {er1645v2VEthVlanEntry 1175977984}

er1645v2VEthVlanIpSaddr OBJECT-TYPE
   SYNTAX      SEQUENCE OF Er1645v2VEthVlanIpSaddrEntry
   MAX-ACCESS  not-accessible
   STATUS      current
   DESCRIPTION
      ""
   ::= {er1645v2VEthVlan 51838976}

er1645v2VEthVlanIpSaddrEntry OBJECT-TYPE
   SYNTAX      Er1645v2VEthVlanIpSaddrEntry
   MAX-ACCESS  not-accessible
   STATUS      current
   DESCRIPTION
      ""
   INDEX      { er1645v2VEthVlanIpSaddrGlobalIx,
                er1645v2VEthVlanTableIx,
                er1645v2VEthVlanIpSaddrTableIx }
   ::= {er1645v2VEthVlanIpSaddr 1}

Er1645v2VEthVlanIpSaddrEntry ::=
   SEQUENCE
      {
      er1645v2VEthVlanIpSaddrActions
         VariableLengthTableActions,
      er1645v2VEthVlanIpSaddrGlobalIx
         GlobalIndex,
      er1645v2VEthVlanIpSaddrTableIx
         TableIndex,
      er1645v2VEthVlanIpSaddrAddress
         IpAddress,
      er1645v2VEthVlanIpSaddrNetMask
         IpAddress
      }

er1645v2VEthVlanIpSaddrActions OBJECT-TYPE
   SYNTAX      VariableLengthTableActions
   MAX-ACCESS  read-write
   STATUS      current
   DESCRIPTION
      "By way of this field, some manipulations
       on this table may be performed."
   ::= {er1645v2VEthVlanIpSaddrEntry 2}

er1645v2VEthVlanIpSaddrGlobalIx OBJECT-TYPE
   SYNTAX      GlobalIndex
   MAX-ACCESS  not-accessible
   STATUS      current
   DESCRIPTION
      "The value of the tlsCntTreeGlobalIndex of the MANAGED OBJECT."
   ::= {er1645v2VEthVlanIpSaddrEntry 10}

er1645v2VEthVlanIpSaddrTableIx OBJECT-TYPE
   SYNTAX      TableIndex
   MAX-ACCESS  not-accessible
   STATUS      current
   DESCRIPTION
      ""
   ::= {er1645v2VEthVlanIpSaddrEntry 11}

er1645v2VEthVlanIpSaddrAddress OBJECT-TYPE
   SYNTAX      IpAddress
   MAX-ACCESS  read-write
   STATUS      current
   DESCRIPTION
      "Path: virtualEthernet.editConf.vlan.ip.secondaryIp.address"
   ::= {er1645v2VEthVlanIpSaddrEntry 2030043136}

er1645v2VEthVlanIpSaddrNetMask OBJECT-TYPE
   SYNTAX      IpAddress
   MAX-ACCESS  read-write
   STATUS      current
   DESCRIPTION
      "Path: virtualEthernet.editConf.vlan.ip.secondaryIp.netMask"
   ::= {er1645v2VEthVlanIpSaddrEntry 2063597568}

er1645v2VEthVlanIpH OBJECT-TYPE
   SYNTAX      SEQUENCE OF Er1645v2VEthVlanIpHEntry
   MAX-ACCESS  not-accessible
   STATUS      current
   DESCRIPTION
      ""
   ::= {er1645v2VEthVlan 51314688}

er1645v2VEthVlanIpHEntry OBJECT-TYPE
   SYNTAX      Er1645v2VEthVlanIpHEntry
   MAX-ACCESS  not-accessible
   STATUS      current
   DESCRIPTION
      ""
   INDEX      { er1645v2VEthVlanIpHGlobalIx,
                er1645v2VEthVlanTableIx,
                er1645v2VEthVlanIpHTableIx }
   ::= {er1645v2VEthVlanIpH 1}

Er1645v2VEthVlanIpHEntry ::=
   SEQUENCE
      {
      er1645v2VEthVlanIpHActions
         VariableLengthTableActions,
      er1645v2VEthVlanIpHGlobalIx
         GlobalIndex,
      er1645v2VEthVlanIpHTableIx
         TableIndex,
      er1645v2VEthVlanIpHAddress
         IpAddress,
      er1645v2VEthVlanIpHDhcpRelayOptionSubscriberId
         DisplayString
      }

er1645v2VEthVlanIpHActions OBJECT-TYPE
   SYNTAX      VariableLengthTableActions
   MAX-ACCESS  read-write
   STATUS      current
   DESCRIPTION
      "By way of this field, some manipulations
       on this table may be performed."
   ::= {er1645v2VEthVlanIpHEntry 2}

er1645v2VEthVlanIpHGlobalIx OBJECT-TYPE
   SYNTAX      GlobalIndex
   MAX-ACCESS  not-accessible
   STATUS      current
   DESCRIPTION
      "The value of the tlsCntTreeGlobalIndex of the MANAGED OBJECT."
   ::= {er1645v2VEthVlanIpHEntry 10}

er1645v2VEthVlanIpHTableIx OBJECT-TYPE
   SYNTAX      TableIndex
   MAX-ACCESS  not-accessible
   STATUS      current
   DESCRIPTION
      ""
   ::= {er1645v2VEthVlanIpHEntry 11}

er1645v2VEthVlanIpHAddress OBJECT-TYPE
   SYNTAX      IpAddress
   MAX-ACCESS  read-write
   STATUS      current
   DESCRIPTION
      "Path: virtualEthernet.editConf.vlan.ip.helpers.address"
   ::= {er1645v2VEthVlanIpHEntry 16777216}

er1645v2VEthVlanIpHDhcpRelayOptionSubscriberId OBJECT-TYPE
   SYNTAX      DisplayString
   MAX-ACCESS  read-write
   STATUS      current
   DESCRIPTION
      "Path: virtualEthernet.editConf.vlan.ip.helpers.dhcpRelayOption.subscriberId"
   ::= {er1645v2VEthVlanIpHEntry 33947648}

er1645v2VEthVlanIpV6Addresses OBJECT-TYPE
   SYNTAX      SEQUENCE OF Er1645v2VEthVlanIpV6AddressesEntry
   MAX-ACCESS  not-accessible
   STATUS      current
   DESCRIPTION
      ""
   ::= {er1645v2VEthVlan 704839680}

er1645v2VEthVlanIpV6AddressesEntry OBJECT-TYPE
   SYNTAX      Er1645v2VEthVlanIpV6AddressesEntry
   MAX-ACCESS  not-accessible
   STATUS      current
   DESCRIPTION
      ""
   INDEX      { er1645v2VEthVlanIpV6AddressesGlobalIx,
                er1645v2VEthVlanTableIx,
                er1645v2VEthVlanIpV6AddressesTableIx }
   ::= {er1645v2VEthVlanIpV6Addresses 1}

Er1645v2VEthVlanIpV6AddressesEntry ::=
   SEQUENCE
      {
      er1645v2VEthVlanIpV6AddressesActions
         VariableLengthTableActions,
      er1645v2VEthVlanIpV6AddressesGlobalIx
         GlobalIndex,
      er1645v2VEthVlanIpV6AddressesTableIx
         TableIndex,
      er1645v2VEthVlanIpV6AddressesType
         INTEGER,
      er1645v2VEthVlanIpV6AddressesAddress
         Ipv6Address,
      er1645v2VEthVlanIpV6AddressesPrefixLength
         Integer32,
      er1645v2VEthVlanIpV6AddressesGeneralPrefix
         DisplayString,
      er1645v2VEthVlanIpV6AddressesRaSend
         INTEGER,
      er1645v2VEthVlanIpV6AddressesRaOnLinkFlag
         INTEGER,
      er1645v2VEthVlanIpV6AddressesRaAutoFlag
         INTEGER,
      er1645v2VEthVlanIpV6AddressesRaValidLifeTime
         TimeTicks,
      er1645v2VEthVlanIpV6AddressesRaValidLTMode
         INTEGER,
      er1645v2VEthVlanIpV6AddressesRaPrefLifeTime
         TimeTicks,
      er1645v2VEthVlanIpV6AddressesRaPrefLTMode
         INTEGER
      }

er1645v2VEthVlanIpV6AddressesActions OBJECT-TYPE
   SYNTAX      VariableLengthTableActions
   MAX-ACCESS  read-write
   STATUS      current
   DESCRIPTION
      "By way of this field, some manipulations
       on this table may be performed."
   ::= {er1645v2VEthVlanIpV6AddressesEntry 2}

er1645v2VEthVlanIpV6AddressesGlobalIx OBJECT-TYPE
   SYNTAX      GlobalIndex
   MAX-ACCESS  not-accessible
   STATUS      current
   DESCRIPTION
      "The value of the tlsCntTreeGlobalIndex of the MANAGED OBJECT."
   ::= {er1645v2VEthVlanIpV6AddressesEntry 10}

er1645v2VEthVlanIpV6AddressesTableIx OBJECT-TYPE
   SYNTAX      TableIndex
   MAX-ACCESS  not-accessible
   STATUS      current
   DESCRIPTION
      ""
   ::= {er1645v2VEthVlanIpV6AddressesEntry 11}

er1645v2VEthVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: virtualEthernet.editConf.vlan.ipV6.addresses.type

       Possibilities:
               unicast   (0)
               eui64   (1)
               anycast   (2)
               linkLocal   (3)
               generalPrefix   (4)"
   ::= {er1645v2VEthVlanIpV6AddressesEntry 50331648}

er1645v2VEthVlanIpV6AddressesAddress OBJECT-TYPE
   SYNTAX      Ipv6Address
   MAX-ACCESS  read-write
   STATUS      current
   DESCRIPTION
      "Path: virtualEthernet.editConf.vlan.ipV6.addresses.address

       ipv6 address"
   ::= {er1645v2VEthVlanIpV6AddressesEntry 16777216}

er1645v2VEthVlanIpV6AddressesPrefixLength OBJECT-TYPE
   SYNTAX      Integer32
   MAX-ACCESS  read-write
   STATUS      current
   DESCRIPTION
      "Path: virtualEthernet.editConf.vlan.ipV6.addresses.prefixLength"
   ::= {er1645v2VEthVlanIpV6AddressesEntry 33554432}

er1645v2VEthVlanIpV6AddressesGeneralPrefix OBJECT-TYPE
   SYNTAX      DisplayString
   MAX-ACCESS  read-write
   STATUS      current
   DESCRIPTION
      "Path: virtualEthernet.editConf.vlan.ipV6.addresses.generalPrefix"
   ::= {er1645v2VEthVlanIpV6AddressesEntry 83886080}

er1645v2VEthVlanIpV6AddressesRaSend OBJECT-TYPE
   SYNTAX      INTEGER
               {
               disabled (0),
               enabled (1)
               }
   MAX-ACCESS  read-write
   STATUS      current
   DESCRIPTION
      "Path: virtualEthernet.editConf.vlan.ipV6.addresses.ra.send

       Possibilities:
               disabled   (0)
               enabled   (1)"
   ::= {er1645v2VEthVlanIpV6AddressesEntry 67174400}

er1645v2VEthVlanIpV6AddressesRaOnLinkFlag OBJECT-TYPE
   SYNTAX      INTEGER
               {
               disabled (0),
               enabled (1)
               }
   MAX-ACCESS  read-write
   STATUS      current
   DESCRIPTION
      "Path: virtualEthernet.editConf.vlan.ipV6.addresses.ra.onLinkFlag

       Possibilities:
               disabled   (0)
               enabled   (1)"
   ::= {er1645v2VEthVlanIpV6AddressesEntry 67371008}

er1645v2VEthVlanIpV6AddressesRaAutoFlag OBJECT-TYPE
   SYNTAX      INTEGER
               {
               disabled (0),
               enabled (1)
               }
   MAX-ACCESS  read-write
   STATUS      current
   DESCRIPTION
      "Path: virtualEthernet.editConf.vlan.ipV6.addresses.ra.autonomousFlag

       Possibilities:
               disabled   (0)
               enabled   (1)"
   ::= {er1645v2VEthVlanIpV6AddressesEntry 67567616}

er1645v2VEthVlanIpV6AddressesRaValidLifeTime OBJECT-TYPE
   SYNTAX      TimeTicks
   MAX-ACCESS  read-write
   STATUS      current
   DESCRIPTION
      "Path: virtualEthernet.editConf.vlan.ipV6.addresses.ra.validLifeTime

       Time in centi-second."
   ::= {er1645v2VEthVlanIpV6AddressesEntry 67239936}

er1645v2VEthVlanIpV6AddressesRaValidLTMode OBJECT-TYPE
   SYNTAX      INTEGER
               {
               fixed (0),
               infinite (2)
               }
   MAX-ACCESS  read-write
   STATUS      current
   DESCRIPTION
      "Path: virtualEthernet.editConf.vlan.ipV6.addresses.ra.validLifeTimeMode

       Possibilities:
               fixed   (0)
               infinite   (2)"
   ::= {er1645v2VEthVlanIpV6AddressesEntry 67305472}

er1645v2VEthVlanIpV6AddressesRaPrefLifeTime OBJECT-TYPE
   SYNTAX      TimeTicks
   MAX-ACCESS  read-write
   STATUS      current
   DESCRIPTION
      "Path: virtualEthernet.editConf.vlan.ipV6.addresses.ra.prefLifeTime

       Time in centi-second."
   ::= {er1645v2VEthVlanIpV6AddressesEntry 67436544}

er1645v2VEthVlanIpV6AddressesRaPrefLTMode OBJECT-TYPE
   SYNTAX      INTEGER
               {
               fixed (0),
               infinite (2)
               }
   MAX-ACCESS  read-write
   STATUS      current
   DESCRIPTION
      "Path: virtualEthernet.editConf.vlan.ipV6.addresses.ra.prefLifeTimeMode

       Possibilities:
               fixed   (0)
               infinite   (2)"
   ::= {er1645v2VEthVlanIpV6AddressesEntry 67502080}

er1645v2VEthVlanIpV6RaDnsOptionsRdnssServers OBJECT-TYPE
   SYNTAX      SEQUENCE OF Er1645v2VEthVlanIpV6RaDnsOptionsRdnssServersEntry
   MAX-ACCESS  not-accessible
   STATUS      current
   DESCRIPTION
      ""
   ::= {er1645v2VEthVlan 705039144}

er1645v2VEthVlanIpV6RaDnsOptionsRdnssServersEntry OBJECT-TYPE
   SYNTAX      Er1645v2VEthVlanIpV6RaDnsOptionsRdnssServersEntry
   MAX-ACCESS  not-accessible
   STATUS      current
   DESCRIPTION
      ""
   INDEX      { er1645v2VEthVlanIpV6RaDnsOptionsRdnssServersGlobalIx,
                er1645v2VEthVlanTableIx,
                er1645v2VEthVlanIpV6RaDnsOptionsRdnssServersTableIx }
   ::= {er1645v2VEthVlanIpV6RaDnsOptionsRdnssServers 1}

Er1645v2VEthVlanIpV6RaDnsOptionsRdnssServersEntry ::=
   SEQUENCE
      {
      er1645v2VEthVlanIpV6RaDnsOptionsRdnssServersActions
         VariableLengthTableActions,
      er1645v2VEthVlanIpV6RaDnsOptionsRdnssServersGlobalIx
         GlobalIndex,
      er1645v2VEthVlanIpV6RaDnsOptionsRdnssServersTableIx
         TableIndex,
      er1645v2VEthVlanIpV6RaDnsOptionsRdnssServersAddress
         Ipv6Address
      }

er1645v2VEthVlanIpV6RaDnsOptionsRdnssServersActions OBJECT-TYPE
   SYNTAX      VariableLengthTableActions
   MAX-ACCESS  read-write
   STATUS      current
   DESCRIPTION
      "By way of this field, some manipulations
       on this table may be performed."
   ::= {er1645v2VEthVlanIpV6RaDnsOptionsRdnssServersEntry 2}

er1645v2VEthVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2VEthVlanIpV6RaDnsOptionsRdnssServersEntry 10}

er1645v2VEthVlanIpV6RaDnsOptionsRdnssServersTableIx OBJECT-TYPE
   SYNTAX      TableIndex
   MAX-ACCESS  not-accessible
   STATUS      current
   DESCRIPTION
      ""
   ::= {er1645v2VEthVlanIpV6RaDnsOptionsRdnssServersEntry 11}

er1645v2VEthVlanIpV6RaDnsOptionsRdnssServersAddress OBJECT-TYPE
   SYNTAX      Ipv6Address
   MAX-ACCESS  read-write
   STATUS      current
   DESCRIPTION
      "Path: virtualEthernet.editConf.vlan.ipV6.ra.dnsOptions.rdnss.servers.address

       ipv6 address"
   ::= {er1645v2VEthVlanIpV6RaDnsOptionsRdnssServersEntry 16777216}

er1645v2VEthVlanIpV6RaDnsOptionsDnsslDomains OBJECT-TYPE
   SYNTAX      SEQUENCE OF Er1645v2VEthVlanIpV6RaDnsOptionsDnsslDomainsEntry
   MAX-ACCESS  not-accessible
   STATUS      current
   DESCRIPTION
      ""
   ::= {er1645v2VEthVlan 705039176}

er1645v2VEthVlanIpV6RaDnsOptionsDnsslDomainsEntry OBJECT-TYPE
   SYNTAX      Er1645v2VEthVlanIpV6RaDnsOptionsDnsslDomainsEntry
   MAX-ACCESS  not-accessible
   STATUS      current
   DESCRIPTION
      ""
   INDEX      { er1645v2VEthVlanIpV6RaDnsOptionsDnsslDomainsGlobalIx,
                er1645v2VEthVlanTableIx,
                er1645v2VEthVlanIpV6RaDnsOptionsDnsslDomainsTableIx }
   ::= {er1645v2VEthVlanIpV6RaDnsOptionsDnsslDomains 1}

Er1645v2VEthVlanIpV6RaDnsOptionsDnsslDomainsEntry ::=
   SEQUENCE
      {
      er1645v2VEthVlanIpV6RaDnsOptionsDnsslDomainsActions
         VariableLengthTableActions,
      er1645v2VEthVlanIpV6RaDnsOptionsDnsslDomainsGlobalIx
         GlobalIndex,
      er1645v2VEthVlanIpV6RaDnsOptionsDnsslDomainsTableIx
         TableIndex,
      er1645v2VEthVlanIpV6RaDnsOptionsDnsslDomainsName
         DisplayString
      }

er1645v2VEthVlanIpV6RaDnsOptionsDnsslDomainsActions OBJECT-TYPE
   SYNTAX      VariableLengthTableActions
   MAX-ACCESS  read-write
   STATUS      current
   DESCRIPTION
      "By way of this field, some manipulations
       on this table may be performed."
   ::= {er1645v2VEthVlanIpV6RaDnsOptionsDnsslDomainsEntry 2}

er1645v2VEthVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2VEthVlanIpV6RaDnsOptionsDnsslDomainsEntry 10}

er1645v2VEthVlanIpV6RaDnsOptionsDnsslDomainsTableIx OBJECT-TYPE
   SYNTAX      TableIndex
   MAX-ACCESS  not-accessible
   STATUS      current
   DESCRIPTION
      ""
   ::= {er1645v2VEthVlanIpV6RaDnsOptionsDnsslDomainsEntry 11}

er1645v2VEthVlanIpV6RaDnsOptionsDnsslDomainsName OBJECT-TYPE
   SYNTAX      DisplayString
   MAX-ACCESS  read-write
   STATUS      current
   DESCRIPTION
      "Path: virtualEthernet.editConf.vlan.ipV6.ra.dnsOptions.dnssl.domains.name"
   ::= {er1645v2VEthVlanIpV6RaDnsOptionsDnsslDomainsEntry 16777216}

er1645v2VEthVlanIpV6DhcpClientUserClassOpt OBJECT-TYPE
   SYNTAX      SEQUENCE OF Er1645v2VEthVlanIpV6DhcpClientUserClassOptEntry
   MAX-ACCESS  not-accessible
   STATUS      current
   DESCRIPTION
      ""
   ::= {er1645v2VEthVlan 705312768}

er1645v2VEthVlanIpV6DhcpClientUserClassOptEntry OBJECT-TYPE
   SYNTAX      Er1645v2VEthVlanIpV6DhcpClientUserClassOptEntry
   MAX-ACCESS  not-accessible
   STATUS      current
   DESCRIPTION
      ""
   INDEX      { er1645v2VEthVlanIpV6DhcpClientUserClassOptGlobalIx,
                er1645v2VEthVlanTableIx,
                er1645v2VEthVlanIpV6DhcpClientUserClassOptTableIx }
   ::= {er1645v2VEthVlanIpV6DhcpClientUserClassOpt 1}

Er1645v2VEthVlanIpV6DhcpClientUserClassOptEntry ::=
   SEQUENCE
      {
      er1645v2VEthVlanIpV6DhcpClientUserClassOptActions
         VariableLengthTableActions,
      er1645v2VEthVlanIpV6DhcpClientUserClassOptGlobalIx
         GlobalIndex,
      er1645v2VEthVlanIpV6DhcpClientUserClassOptTableIx
         TableIndex,
      er1645v2VEthVlanIpV6DhcpClientUserClassOptValueAscii
         DisplayString,
      er1645v2VEthVlanIpV6DhcpClientUserClassOptValueDecimal
         Integer32,
      er1645v2VEthVlanIpV6DhcpClientUserClassOptValueHexData
         OCTET STRING
      }

er1645v2VEthVlanIpV6DhcpClientUserClassOptActions OBJECT-TYPE
   SYNTAX      VariableLengthTableActions
   MAX-ACCESS  read-write
   STATUS      current
   DESCRIPTION
      "By way of this field, some manipulations
       on this table may be performed."
   ::= {er1645v2VEthVlanIpV6DhcpClientUserClassOptEntry 2}

er1645v2VEthVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2VEthVlanIpV6DhcpClientUserClassOptEntry 10}

er1645v2VEthVlanIpV6DhcpClientUserClassOptTableIx OBJECT-TYPE
   SYNTAX      TableIndex
   MAX-ACCESS  not-accessible
   STATUS      current
   DESCRIPTION
      ""
   ::= {er1645v2VEthVlanIpV6DhcpClientUserClassOptEntry 11}

er1645v2VEthVlanIpV6DhcpClientUserClassOptValueAscii OBJECT-TYPE
   SYNTAX      DisplayString
   MAX-ACCESS  read-write
   STATUS      current
   DESCRIPTION
      "Path: virtualEthernet.editConf.vlan.ipV6.dhcp.client.userClassOpt.value.ascii"
   ::= {er1645v2VEthVlanIpV6DhcpClientUserClassOptEntry 16842752}

er1645v2VEthVlanIpV6DhcpClientUserClassOptValueDecimal OBJECT-TYPE
   SYNTAX      Integer32
   MAX-ACCESS  read-write
   STATUS      current
   DESCRIPTION
      "Path: virtualEthernet.editConf.vlan.ipV6.dhcp.client.userClassOpt.value.decimal"
   ::= {er1645v2VEthVlanIpV6DhcpClientUserClassOptEntry 16908288}

er1645v2VEthVlanIpV6DhcpClientUserClassOptValueHexData OBJECT-TYPE
   SYNTAX      OCTET STRING
   MAX-ACCESS  read-write
   STATUS      current
   DESCRIPTION
      "Path: virtualEthernet.editConf.vlan.ipV6.dhcp.client.userClassOpt.value.hexData"
   ::= {er1645v2VEthVlanIpV6DhcpClientUserClassOptEntry 16973824}

er1645v2VEthVlanIpV6DhcpClientVendorCl OBJECT-TYPE
   SYNTAX      SEQUENCE OF Er1645v2VEthVlanIpV6DhcpClientVendorClEntry
   MAX-ACCESS  not-accessible
   STATUS      current
   DESCRIPTION
      ""
   ::= {er1645v2VEthVlan 705313792}

er1645v2VEthVlanIpV6DhcpClientVendorClEntry OBJECT-TYPE
   SYNTAX      Er1645v2VEthVlanIpV6DhcpClientVendorClEntry
   MAX-ACCESS  not-accessible
   STATUS      current
   DESCRIPTION
      ""
   INDEX      { er1645v2VEthVlanIpV6DhcpClientVendorClGlobalIx,
                er1645v2VEthVlanTableIx,
                er1645v2VEthVlanIpV6DhcpClientVendorClTableIx }
   ::= {er1645v2VEthVlanIpV6DhcpClientVendorCl 1}

Er1645v2VEthVlanIpV6DhcpClientVendorClEntry ::=
   SEQUENCE
      {
      er1645v2VEthVlanIpV6DhcpClientVendorClActions
         VariableLengthTableActions,
      er1645v2VEthVlanIpV6DhcpClientVendorClGlobalIx
         GlobalIndex,
      er1645v2VEthVlanIpV6DhcpClientVendorClTableIx
         TableIndex,
      er1645v2VEthVlanIpV6DhcpClientVendorClValueAscii
         DisplayString,
      er1645v2VEthVlanIpV6DhcpClientVendorClValueDecimal
         Integer32,
      er1645v2VEthVlanIpV6DhcpClientVendorClValueHexData
         OCTET STRING
      }

er1645v2VEthVlanIpV6DhcpClientVendorClActions OBJECT-TYPE
   SYNTAX      VariableLengthTableActions
   MAX-ACCESS  read-write
   STATUS      current
   DESCRIPTION
      "By way of this field, some manipulations
       on this table may be performed."
   ::= {er1645v2VEthVlanIpV6DhcpClientVendorClEntry 2}

er1645v2VEthVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2VEthVlanIpV6DhcpClientVendorClEntry 10}

er1645v2VEthVlanIpV6DhcpClientVendorClTableIx OBJECT-TYPE
   SYNTAX      TableIndex
   MAX-ACCESS  not-accessible
   STATUS      current
   DESCRIPTION
      ""
   ::= {er1645v2VEthVlanIpV6DhcpClientVendorClEntry 11}

er1645v2VEthVlanIpV6DhcpClientVendorClValueAscii OBJECT-TYPE
   SYNTAX      DisplayString
   MAX-ACCESS  read-write
   STATUS      current
   DESCRIPTION
      "Path: virtualEthernet.editConf.vlan.ipV6.dhcp.client.vendorClassOpt.value.ascii"
   ::= {er1645v2VEthVlanIpV6DhcpClientVendorClEntry 16842752}

er1645v2VEthVlanIpV6DhcpClientVendorClValueDecimal OBJECT-TYPE
   SYNTAX      Integer32
   MAX-ACCESS  read-write
   STATUS      current
   DESCRIPTION
      "Path: virtualEthernet.editConf.vlan.ipV6.dhcp.client.vendorClassOpt.value.decimal"
   ::= {er1645v2VEthVlanIpV6DhcpClientVendorClEntry 16908288}

er1645v2VEthVlanIpV6DhcpClientVendorClValueHexData OBJECT-TYPE
   SYNTAX      OCTET STRING
   MAX-ACCESS  read-write
   STATUS      current
   DESCRIPTION
      "Path: virtualEthernet.editConf.vlan.ipV6.dhcp.client.vendorClassOpt.value.hexData"
   ::= {er1645v2VEthVlanIpV6DhcpClientVendorClEntry 16973824}

er1645v2VEthVlanIpV6DhcpRelayDestinations OBJECT-TYPE
   SYNTAX      SEQUENCE OF Er1645v2VEthVlanIpV6DhcpRelayDestinationsEntry
   MAX-ACCESS  not-accessible
   STATUS      current
   DESCRIPTION
      ""
   ::= {er1645v2VEthVlan 705323072}

er1645v2VEthVlanIpV6DhcpRelayDestinationsEntry OBJECT-TYPE
   SYNTAX      Er1645v2VEthVlanIpV6DhcpRelayDestinationsEntry
   MAX-ACCESS  not-accessible
   STATUS      current
   DESCRIPTION
      ""
   INDEX      { er1645v2VEthVlanIpV6DhcpRelayDestinationsGlobalIx,
                er1645v2VEthVlanTableIx,
                er1645v2VEthVlanIpV6DhcpRelayDestinationsTableIx }
   ::= {er1645v2VEthVlanIpV6DhcpRelayDestinations 1}

Er1645v2VEthVlanIpV6DhcpRelayDestinationsEntry ::=
   SEQUENCE
      {
      er1645v2VEthVlanIpV6DhcpRelayDestinationsActions
         VariableLengthTableActions,
      er1645v2VEthVlanIpV6DhcpRelayDestinationsGlobalIx
         GlobalIndex,
      er1645v2VEthVlanIpV6DhcpRelayDestinationsTableIx
         TableIndex,
      er1645v2VEthVlanIpV6DhcpRelayDestinationsAddress
         Ipv6Address,
      er1645v2VEthVlanIpV6DhcpRelayDestinationsInterface
         DisplayString
      }

er1645v2VEthVlanIpV6DhcpRelayDestinationsActions OBJECT-TYPE
   SYNTAX      VariableLengthTableActions
   MAX-ACCESS  read-write
   STATUS      current
   DESCRIPTION
      "By way of this field, some manipulations
       on this table may be performed."
   ::= {er1645v2VEthVlanIpV6DhcpRelayDestinationsEntry 2}

er1645v2VEthVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2VEthVlanIpV6DhcpRelayDestinationsEntry 10}

er1645v2VEthVlanIpV6DhcpRelayDestinationsTableIx OBJECT-TYPE
   SYNTAX      TableIndex
   MAX-ACCESS  not-accessible
   STATUS      current
   DESCRIPTION
      ""
   ::= {er1645v2VEthVlanIpV6DhcpRelayDestinationsEntry 11}

er1645v2VEthVlanIpV6DhcpRelayDestinationsAddress OBJECT-TYPE
   SYNTAX      Ipv6Address
   MAX-ACCESS  read-write
   STATUS      current
   DESCRIPTION
      "Path: virtualEthernet.editConf.vlan.ipV6.dhcp.relay.destinations.address

       ipv6 address"
   ::= {er1645v2VEthVlanIpV6DhcpRelayDestinationsEntry 16777216}

er1645v2VEthVlanIpV6DhcpRelayDestinationsInterface OBJECT-TYPE
   SYNTAX      DisplayString
   MAX-ACCESS  read-write
   STATUS      current
   DESCRIPTION
      "Path: virtualEthernet.editConf.vlan.ipV6.dhcp.relay.destinations.interface"
   ::= {er1645v2VEthVlanIpV6DhcpRelayDestinationsEntry 33554432}

er1645v2VEthVlanBridgingVlTVlans OBJECT-TYPE
   SYNTAX      SEQUENCE OF Er1645v2VEthVlanBridgingVlTVlansEntry
   MAX-ACCESS  not-accessible
   STATUS      current
   DESCRIPTION
      ""
   ::= {er1645v2VEthVlan 459079680}

er1645v2VEthVlanBridgingVlTVlansEntry OBJECT-TYPE
   SYNTAX      Er1645v2VEthVlanBridgingVlTVlansEntry
   MAX-ACCESS  not-accessible
   STATUS      current
   DESCRIPTION
      ""
   INDEX      { er1645v2VEthVlanBridgingVlTVlansGlobalIx,
                er1645v2VEthVlanTableIx,
                er1645v2VEthVlanBridgingVlTVlansTableIx }
   ::= {er1645v2VEthVlanBridgingVlTVlans 1}

Er1645v2VEthVlanBridgingVlTVlansEntry ::=
   SEQUENCE
      {
      er1645v2VEthVlanBridgingVlTVlansActions
         VariableLengthTableActions,
      er1645v2VEthVlanBridgingVlTVlansGlobalIx
         GlobalIndex,
      er1645v2VEthVlanBridgingVlTVlansTableIx
         TableIndex,
      er1645v2VEthVlanBridgingVlTVlansVid
         Integer32,
      er1645v2VEthVlanBridgingVlTVlansEndVid
         Integer32,
      er1645v2VEthVlanBridgingVlTVlansAction
         INTEGER,
      er1645v2VEthVlanBridgingVlTVlansTagInfoTpid
         INTEGER,
      er1645v2VEthVlanBridgingVlTVlansTagInfoVid
         Integer32
      }

er1645v2VEthVlanBridgingVlTVlansActions OBJECT-TYPE
   SYNTAX      VariableLengthTableActions
   MAX-ACCESS  read-write
   STATUS      current
   DESCRIPTION
      "By way of this field, some manipulations
       on this table may be performed."
   ::= {er1645v2VEthVlanBridgingVlTVlansEntry 2}

er1645v2VEthVlanBridgingVlTVlansGlobalIx OBJECT-TYPE
   SYNTAX      GlobalIndex
   MAX-ACCESS  not-accessible
   STATUS      current
   DESCRIPTION
      "The value of the tlsCntTreeGlobalIndex of the MANAGED OBJECT."
   ::= {er1645v2VEthVlanBridgingVlTVlansEntry 10}

er1645v2VEthVlanBridgingVlTVlansTableIx OBJECT-TYPE
   SYNTAX      TableIndex
   MAX-ACCESS  not-accessible
   STATUS      current
   DESCRIPTION
      ""
   ::= {er1645v2VEthVlanBridgingVlTVlansEntry 11}

er1645v2VEthVlanBridgingVlTVlansVid OBJECT-TYPE
   SYNTAX      Integer32
   MAX-ACCESS  read-write
   STATUS      current
   DESCRIPTION
      "Path: virtualEthernet.editConf.vlan.bridging.vlanTagging.vlans.vid"
   ::= {er1645v2VEthVlanBridgingVlTVlansEntry 536870912}

er1645v2VEthVlanBridgingVlTVlansEndVid OBJECT-TYPE
   SYNTAX      Integer32
   MAX-ACCESS  read-write
   STATUS      current
   DESCRIPTION
      "Path: virtualEthernet.editConf.vlan.bridging.vlanTagging.vlans.endVid"
   ::= {er1645v2VEthVlanBridgingVlTVlansEntry 2147483648}

er1645v2VEthVlanBridgingVlTVlansAction OBJECT-TYPE
   SYNTAX      INTEGER
               {
               discard (0),
               accept (1),
               tag (2)
               }
   MAX-ACCESS  read-write
   STATUS      current
   DESCRIPTION
      "Path: virtualEthernet.editConf.vlan.bridging.vlanTagging.vlans.action

       Possibilities:
               discard   (0)
               accept   (1)
               tag   (2)"
   ::= {er1645v2VEthVlanBridgingVlTVlansEntry 1073741824}

er1645v2VEthVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.bridging.vlanTagging.vlans.tagInfo.tpid

       Possibilities:
               dot1Q   (33024)
               dot1ad   (34984)
               0x9100   (37120)
               0x9200   (37376)
               0x9300   (37632)"
   ::= {er1645v2VEthVlanBridgingVlTVlansEntry 1677721600}

er1645v2VEthVlanBridgingVlTVlansTagInfoVid OBJECT-TYPE
   SYNTAX      Integer32
   MAX-ACCESS  read-write
   STATUS      current
   DESCRIPTION
      "Path: virtualEthernet.editConf.vlan.bridging.vlanTagging.vlans.tagInfo.vid"
   ::= {er1645v2VEthVlanBridgingVlTVlansEntry 1744830464}

er1645v2VEthVlanVlanVidExtensionTable OBJECT-TYPE
   SYNTAX      SEQUENCE OF Er1645v2VEthVlanVlanVidExtensionTableEntry
   MAX-ACCESS  not-accessible
   STATUS      current
   DESCRIPTION
      ""
   ::= {er1645v2VEthVlan 235340544}

er1645v2VEthVlanVlanVidExtensionTableEntry OBJECT-TYPE
   SYNTAX      Er1645v2VEthVlanVlanVidExtensionTableEntry
   MAX-ACCESS  not-accessible
   STATUS      current
   DESCRIPTION
      ""
   INDEX      { er1645v2VEthVlanVlanVidExtensionTableGlobalIx,
                er1645v2VEthVlanTableIx,
                er1645v2VEthVlanVlanVidExtensionTableTableIx }
   ::= {er1645v2VEthVlanVlanVidExtensionTable 1}

Er1645v2VEthVlanVlanVidExtensionTableEntry ::=
   SEQUENCE
      {
      er1645v2VEthVlanVlanVidExtensionTableActions
         VariableLengthTableActions,
      er1645v2VEthVlanVlanVidExtensionTableGlobalIx
         GlobalIndex,
      er1645v2VEthVlanVlanVidExtensionTableTableIx
         TableIndex,
      er1645v2VEthVlanVlanVidExtensionTableTpid
         INTEGER,
      er1645v2VEthVlanVlanVidExtensionTableVid
         Integer32,
      er1645v2VEthVlanVlanVidExtensionTableEndVid
         Integer32
      }

er1645v2VEthVlanVlanVidExtensionTableActions OBJECT-TYPE
   SYNTAX      VariableLengthTableActions
   MAX-ACCESS  read-write
   STATUS      current
   DESCRIPTION
      "By way of this field, some manipulations
       on this table may be performed."
   ::= {er1645v2VEthVlanVlanVidExtensionTableEntry 2}

er1645v2VEthVlanVlanVidExtensionTableGlobalIx OBJECT-TYPE
   SYNTAX      GlobalIndex
   MAX-ACCESS  not-accessible
   STATUS      current
   DESCRIPTION
      "The value of the tlsCntTreeGlobalIndex of the MANAGED OBJECT."
   ::= {er1645v2VEthVlanVlanVidExtensionTableEntry 10}

er1645v2VEthVlanVlanVidExtensionTableTableIx OBJECT-TYPE
   SYNTAX      TableIndex
   MAX-ACCESS  not-accessible
   STATUS      current
   DESCRIPTION
      ""
   ::= {er1645v2VEthVlanVlanVidExtensionTableEntry 11}

er1645v2VEthVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.vlan.vidExtension.table.tpid

       Possibilities:
               dot1Q   (33024)
               dot1ad   (34984)
               0x9100   (37120)
               0x9200   (37376)
               0x9300   (37632)"
   ::= {er1645v2VEthVlanVlanVidExtensionTableEntry 16777216}

er1645v2VEthVlanVlanVidExtensionTableVid OBJECT-TYPE
   SYNTAX      Integer32
   MAX-ACCESS  read-write
   STATUS      current
   DESCRIPTION
      "Path: virtualEthernet.editConf.vlan.vlan.vidExtension.table.vid"
   ::= {er1645v2VEthVlanVlanVidExtensionTableEntry 33554432}

er1645v2VEthVlanVlanVidExtensionTableEndVid OBJECT-TYPE
   SYNTAX      Integer32
   MAX-ACCESS  read-write
   STATUS      current
   DESCRIPTION
      "Path: virtualEthernet.editConf.vlan.vlan.vidExtension.table.endVid"
   ::= {er1645v2VEthVlanVlanVidExtensionTableEntry 50331648}

er1645v2VEthVlanVlanCSMap OBJECT-TYPE
   SYNTAX      SEQUENCE OF Er1645v2VEthVlanVlanCSMapEntry
   MAX-ACCESS  not-accessible
   STATUS      current
   DESCRIPTION
      ""
   ::= {er1645v2VEthVlan 235405312}

er1645v2VEthVlanVlanCSMapEntry OBJECT-TYPE
   SYNTAX      Er1645v2VEthVlanVlanCSMapEntry
   MAX-ACCESS  not-accessible
   STATUS      current
   DESCRIPTION
      ""
   INDEX      { er1645v2VEthVlanVlanCSMapGlobalIx,
                er1645v2VEthVlanTableIx,
                er1645v2VEthVlanVlanCSMapTableIx }
   ::= {er1645v2VEthVlanVlanCSMap 1}

Er1645v2VEthVlanVlanCSMapEntry ::=
   SEQUENCE
      {
      er1645v2VEthVlanVlanCSMapActions
         VariableLengthTableActions,
      er1645v2VEthVlanVlanCSMapGlobalIx
         GlobalIndex,
      er1645v2VEthVlanVlanCSMapTableIx
         TableIndex,
      er1645v2VEthVlanVlanCSMapCos
         INTEGER,
      er1645v2VEthVlanVlanCSMapDei
         INTEGER,
      er1645v2VEthVlanVlanCSMapTos
         INTEGER,
      er1645v2VEthVlanVlanCSMapQueue
         INTEGER,
      er1645v2VEthVlanVlanCSMapDropLevel
         INTEGER,
      er1645v2VEthVlanVlanCSMapDeFlag
         INTEGER
      }

er1645v2VEthVlanVlanCSMapActions OBJECT-TYPE
   SYNTAX      VariableLengthTableActions
   MAX-ACCESS  read-write
   STATUS      current
   DESCRIPTION
      "By way of this field, some manipulations
       on this table may be performed."
   ::= {er1645v2VEthVlanVlanCSMapEntry 2}

er1645v2VEthVlanVlanCSMapGlobalIx OBJECT-TYPE
   SYNTAX      GlobalIndex
   MAX-ACCESS  not-accessible
   STATUS      current
   DESCRIPTION
      "The value of the tlsCntTreeGlobalIndex of the MANAGED OBJECT."
   ::= {er1645v2VEthVlanVlanCSMapEntry 10}

er1645v2VEthVlanVlanCSMapTableIx OBJECT-TYPE
   SYNTAX      TableIndex
   MAX-ACCESS  not-accessible
   STATUS      current
   DESCRIPTION
      ""
   ::= {er1645v2VEthVlanVlanCSMapEntry 11}

er1645v2VEthVlanVlanCSMapCos OBJECT-TYPE
   SYNTAX      INTEGER
               {
               any (8)
               }
   MAX-ACCESS  read-write
   STATUS      current
   DESCRIPTION
      "Path: virtualEthernet.editConf.vlan.vlan.cosMap.cos

       Possibilities:
               any   (8)"
   ::= {er1645v2VEthVlanVlanCSMapEntry 16777216}

er1645v2VEthVlanVlanCSMapDei OBJECT-TYPE
   SYNTAX      INTEGER
               {
               clear (0),
               set (1),
               any (2)
               }
   MAX-ACCESS  read-write
   STATUS      current
   DESCRIPTION
      "Path: virtualEthernet.editConf.vlan.vlan.cosMap.dei

       Possibilities:
               clear   (0)
               set   (1)
               any   (2)"
   ::= {er1645v2VEthVlanVlanCSMapEntry 33554432}

er1645v2VEthVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2VEthVlanVlanCSMapEntry 50331648}

er1645v2VEthVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2VEthVlanVlanCSMapEntry 67108864}

er1645v2VEthVlanVlanCSMapDropLevel OBJECT-TYPE
   SYNTAX      INTEGER
               {
               unchanged (-1),
               dropOnQueue (0)
               }
   MAX-ACCESS  read-write
   STATUS      current
   DESCRIPTION
      "Path: virtualEthernet.editConf.vlan.vlan.cosMap.dropLevel

       Possibilities:
               unchanged   (-1)
               dropOnQueue   (0)"
   ::= {er1645v2VEthVlanVlanCSMapEntry 83886080}

er1645v2VEthVlanVlanCSMapDeFlag OBJECT-TYPE
   SYNTAX      INTEGER
               {
               unchanged (255),
               clear (0),
               set (1)
               }
   MAX-ACCESS  read-write
   STATUS      current
   DESCRIPTION
      "Path: virtualEthernet.editConf.vlan.vlan.cosMap.deFlag

       Possibilities:
               unchanged   (255)
               clear   (0)
               set   (1)"
   ::= {er1645v2VEthVlanVlanCSMapEntry 117440512}

er1645v2VEthVlanVlanTCMap OBJECT-TYPE
   SYNTAX      SEQUENCE OF Er1645v2VEthVlanVlanTCMapEntry
   MAX-ACCESS  not-accessible
   STATUS      current
   DESCRIPTION
      ""
   ::= {er1645v2VEthVlan 241369088}

er1645v2VEthVlanVlanTCMapEntry OBJECT-TYPE
   SYNTAX      Er1645v2VEthVlanVlanTCMapEntry
   MAX-ACCESS  not-accessible
   STATUS      current
   DESCRIPTION
      ""
   INDEX      { er1645v2VEthVlanVlanTCMapGlobalIx,
                er1645v2VEthVlanTableIx,
                er1645v2VEthVlanVlanTCMapTableIx }
   ::= {er1645v2VEthVlanVlanTCMap 1}

Er1645v2VEthVlanVlanTCMapEntry ::=
   SEQUENCE
      {
      er1645v2VEthVlanVlanTCMapActions
         VariableLengthTableActions,
      er1645v2VEthVlanVlanTCMapGlobalIx
         GlobalIndex,
      er1645v2VEthVlanVlanTCMapTableIx
         TableIndex,
      er1645v2VEthVlanVlanTCMapStartTos
         INTEGER,
      er1645v2VEthVlanVlanTCMapEndTos
         INTEGER,
      er1645v2VEthVlanVlanTCMapCos
         INTEGER
      }

er1645v2VEthVlanVlanTCMapActions OBJECT-TYPE
   SYNTAX      VariableLengthTableActions
   MAX-ACCESS  read-write
   STATUS      current
   DESCRIPTION
      "By way of this field, some manipulations
       on this table may be performed."
   ::= {er1645v2VEthVlanVlanTCMapEntry 2}

er1645v2VEthVlanVlanTCMapGlobalIx OBJECT-TYPE
   SYNTAX      GlobalIndex
   MAX-ACCESS  not-accessible
   STATUS      current
   DESCRIPTION
      "The value of the tlsCntTreeGlobalIndex of the MANAGED OBJECT."
   ::= {er1645v2VEthVlanVlanTCMapEntry 10}

er1645v2VEthVlanVlanTCMapTableIx OBJECT-TYPE
   SYNTAX      TableIndex
   MAX-ACCESS  not-accessible
   STATUS      current
   DESCRIPTION
      ""
   ::= {er1645v2VEthVlanVlanTCMapEntry 11}

er1645v2VEthVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: virtualEthernet.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2VEthVlanVlanTCMapEntry 16777216}

er1645v2VEthVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: virtualEthernet.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2VEthVlanVlanTCMapEntry 33554432}

er1645v2VEthVlanVlanTCMapCos OBJECT-TYPE
   SYNTAX      INTEGER
               {
               queueCosMap (8)
               }
   MAX-ACCESS  read-write
   STATUS      current
   DESCRIPTION
      "Path: virtualEthernet.editConf.vlan.vlan.tosCosMap.cos

       Possibilities:
               queueCosMap   (8)"
   ::= {er1645v2VEthVlanVlanTCMapEntry 50331648}

er1645v2VEthVlanVlanArpStaticArp OBJECT-TYPE
   SYNTAX      SEQUENCE OF Er1645v2VEthVlanVlanArpStaticArpEntry
   MAX-ACCESS  not-accessible
   STATUS      current
   DESCRIPTION
      ""
   ::= {er1645v2VEthVlan 235275008}

er1645v2VEthVlanVlanArpStaticArpEntry OBJECT-TYPE
   SYNTAX      Er1645v2VEthVlanVlanArpStaticArpEntry
   MAX-ACCESS  not-accessible
   STATUS      current
   DESCRIPTION
      ""
   INDEX      { er1645v2VEthVlanVlanArpStaticArpGlobalIx,
                er1645v2VEthVlanTableIx,
                er1645v2VEthVlanVlanArpStaticArpTableIx }
   ::= {er1645v2VEthVlanVlanArpStaticArp 1}

Er1645v2VEthVlanVlanArpStaticArpEntry ::=
   SEQUENCE
      {
      er1645v2VEthVlanVlanArpStaticArpActions
         VariableLengthTableActions,
      er1645v2VEthVlanVlanArpStaticArpGlobalIx
         GlobalIndex,
      er1645v2VEthVlanVlanArpStaticArpTableIx
         TableIndex,
      er1645v2VEthVlanVlanArpStaticArpMacAddress
         OCTET STRING,
      er1645v2VEthVlanVlanArpStaticArpIpAddress
         IpAddress
      }

er1645v2VEthVlanVlanArpStaticArpActions OBJECT-TYPE
   SYNTAX      VariableLengthTableActions
   MAX-ACCESS  read-write
   STATUS      current
   DESCRIPTION
      "By way of this field, some manipulations
       on this table may be performed."
   ::= {er1645v2VEthVlanVlanArpStaticArpEntry 2}

er1645v2VEthVlanVlanArpStaticArpGlobalIx OBJECT-TYPE
   SYNTAX      GlobalIndex
   MAX-ACCESS  not-accessible
   STATUS      current
   DESCRIPTION
      "The value of the tlsCntTreeGlobalIndex of the MANAGED OBJECT."
   ::= {er1645v2VEthVlanVlanArpStaticArpEntry 10}

er1645v2VEthVlanVlanArpStaticArpTableIx OBJECT-TYPE
   SYNTAX      TableIndex
   MAX-ACCESS  not-accessible
   STATUS      current
   DESCRIPTION
      ""
   ::= {er1645v2VEthVlanVlanArpStaticArpEntry 11}

er1645v2VEthVlanVlanArpStaticArpMacAddress OBJECT-TYPE
   SYNTAX      OCTET STRING
   MAX-ACCESS  read-write
   STATUS      current
   DESCRIPTION
      "Path: virtualEthernet.editConf.vlan.vlan.arp.staticArp.macAddress

       MAC address."
   ::= {er1645v2VEthVlanVlanArpStaticArpEntry 16777216}

er1645v2VEthVlanVlanArpStaticArpIpAddress OBJECT-TYPE
   SYNTAX      IpAddress
   MAX-ACCESS  read-write
   STATUS      current
   DESCRIPTION
      "Path: virtualEthernet.editConf.vlan.vlan.arp.staticArp.ipAddress"
   ::= {er1645v2VEthVlanVlanArpStaticArpEntry 33554432}


er1645v2VEthPppOE OBJECT IDENTIFIER ::= {er1645v2VEth 35}

er1645v2VEthPppOESSCTable OBJECT-TYPE
   SYNTAX      SEQUENCE OF Er1645v2VEthPppOEEntry
   MAX-ACCESS  not-accessible
   STATUS      current
   DESCRIPTION
      ""
   ::= {er1645v2VEthPppOE 1}

er1645v2VEthPppOEEntry OBJECT-TYPE
   SYNTAX      Er1645v2VEthPppOEEntry
   MAX-ACCESS  not-accessible
   STATUS      current
   DESCRIPTION
      ""
   INDEX      { er1645v2VEthPppOEGlobalIx,
                er1645v2VEthPppOETableIx }
   ::= {er1645v2VEthPppOESSCTable 1}

Er1645v2VEthPppOEEntry ::=
   SEQUENCE
      {
      er1645v2VEthPppOEActions
         VariableLengthTableActions,
      er1645v2VEthPppOEGlobalIx
         GlobalIndex,
      er1645v2VEthPppOETableIx
         TableIndex,
      er1645v2VEthPppOEName
         DisplayString,
      er1645v2VEthPppOERemark
         DisplayString,
      er1645v2VEthPppOEAdminStatus
         INTEGER,
      er1645v2VEthPppOEMode
         INTEGER,
      er1645v2VEthPppOEIpVrfRouter
         DisplayString,
      er1645v2VEthPppOEIpAdr
         IpAddress,
      er1645v2VEthPppOEIpNetm
         IpAddress,
      er1645v2VEthPppOEIpSNetName
         INTEGER,
      er1645v2VEthPppOEIpSNetCust
         DisplayString,
      er1645v2VEthPppOEIpRem
         IpAddress,
      er1645v2VEthPppOEIpUnnumbered
         DisplayString,
      er1645v2VEthPppOEIpGwPref
         Integer32,
      er1645v2VEthPppOEIpRsn
         INTEGER,
      er1645v2VEthPppOEIpMtu
         Integer32,
      er1645v2VEthPppOEIpMssAdjust
         INTEGER,
      er1645v2VEthPppOEIpRipMetric
         Integer32,
      er1645v2VEthPppOEIpRipMetricOut
         Integer32,
      er1645v2VEthPppOEIpRipMode
         INTEGER,
      er1645v2VEthPppOEIpRipTxVer
         INTEGER,
      er1645v2VEthPppOEIpRipRxVer
         INTEGER,
      er1645v2VEthPppOEIpRipSplitH
         INTEGER,
      er1645v2VEthPppOEIpRipAuth
         INTEGER,
      er1645v2VEthPppOEIpRipFilter
         DisplayString,
      er1645v2VEthPppOEIpRipFilterIn
         DisplayString,
      er1645v2VEthPppOEIpRipClearNextHop
         INTEGER,
      er1645v2VEthPppOEIpAccPol
         DisplayString,
      er1645v2VEthPppOEIpAB
         DisplayString,
      er1645v2VEthPppOEIpMA
         INTEGER,
      er1645v2VEthPppOEIpMF
         Integer32,
      er1645v2VEthPppOEIpDB
         INTEGER,
      er1645v2VEthPppOEIpIR
         INTEGER,
      er1645v2VEthPppOEIpIgmp
         INTEGER,
      er1645v2VEthPppOEIpNN
         DisplayString,
      er1645v2VEthPppOEIpPimMode
         INTEGER,
      er1645v2VEthPppOEIpPimDrPriority
         Counter32,
      er1645v2VEthPppOEIpPimHelloTime
         TimeTicks,
      er1645v2VEthPppOEIpPimPropagationDelay
         TimeTicks,
      er1645v2VEthPppOEIpPimOverrideInterval
         TimeTicks,
      er1645v2VEthPppOEIpPimBsrBorder
         INTEGER,
      er1645v2VEthPppOEIpPimTtlThreshold
         Integer32,
      er1645v2VEthPppOEIpIMNetworkUnreachable
         INTEGER,
      er1645v2VEthPppOEIpIMHostUnreachable
         INTEGER,
      er1645v2VEthPppOEIpIMProtocolUnreachable
         INTEGER,
      er1645v2VEthPppOEIpIMPortUnreachable
         INTEGER,
      er1645v2VEthPppOEIpIMMtuExceeded
         INTEGER,
      er1645v2VEthPppOEIpIMAdminProhibited
         INTEGER,
      er1645v2VEthPppOEIpIMTtlExceeded
         INTEGER,
      er1645v2VEthPppOEIpIMRedirect
         INTEGER,
      er1645v2VEthPppOEIpV6VrfRouter
         DisplayString,
      er1645v2VEthPppOEIpV6AddrAutoConfigNrDupAddrDetects
         Integer32,
      er1645v2VEthPppOEIpV6AddrAutoConfigAcceptRa
         INTEGER,
      er1645v2VEthPppOEIpV6AddrAutoConfigAcceptRaRdnss
         INTEGER,
      er1645v2VEthPppOEIpV6AddrAutoConfigAcceptRaDnssl
         INTEGER,
      er1645v2VEthPppOEIpV6DefaultRoute
         INTEGER,
      er1645v2VEthPppOEIpV6RaSend
         INTEGER,
      er1645v2VEthPppOEIpV6RaMinInterval
         TimeTicks,
      er1645v2VEthPppOEIpV6RaMaxInterval
         TimeTicks,
      er1645v2VEthPppOEIpV6RaManagedFlag
         INTEGER,
      er1645v2VEthPppOEIpV6RaOtherConfFlag
         INTEGER,
      er1645v2VEthPppOEIpV6RaLinkMtu
         Integer32,
      er1645v2VEthPppOEIpV6RaReachableTime
         TimeTicks,
      er1645v2VEthPppOEIpV6RaRetransmitTime
         TimeTicks,
      er1645v2VEthPppOEIpV6RaHopLimit
         Integer32,
      er1645v2VEthPppOEIpV6RaDefaultLifeTime
         TimeTicks,
      er1645v2VEthPppOEIpV6RaDnsOptionsRdnssLifeTime
         TimeTicks,
      er1645v2VEthPppOEIpV6RaDnsOptionsRdnssImportServers
         INTEGER,
      er1645v2VEthPppOEIpV6RaDnsOptionsDnsslLifeTime
         TimeTicks,
      er1645v2VEthPppOEIpV6RaDnsOptionsDnsslImportDomains
         INTEGER,
      er1645v2VEthPppOEIpV6RsSend
         INTEGER,
      er1645v2VEthPppOEIpV6RsMaxRandomDelay
         TimeTicks,
      er1645v2VEthPppOEIpV6RsInterval
         TimeTicks,
      er1645v2VEthPppOEIpV6RsMaxSolicitations
         Integer32,
      er1645v2VEthPppOEIpV6TrafficPolicyInbound
         DisplayString,
      er1645v2VEthPppOEIpV6TrafficPolicyOutbound
         DisplayString,
      er1645v2VEthPppOEIpV6FirewallZone
         DisplayString,
      er1645v2VEthPppOEIpV6DhcpClientAddrAC
         INTEGER,
      er1645v2VEthPppOEIpV6DhcpClientPrDelMode
         INTEGER,
      er1645v2VEthPppOEIpV6DhcpClientPrDelPool
         DisplayString,
      er1645v2VEthPppOEIpV6DhcpClientPrDelPdExclOpt
         INTEGER,
      er1645v2VEthPppOEIpV6DhcpClientDnsServerPref
         Integer32,
      er1645v2VEthPppOEIpV6DhcpClientRapidCommit
         INTEGER,
      er1645v2VEthPppOEIpV6DhcpClientTimersSolTimeOut
         TimeTicks,
      er1645v2VEthPppOEIpV6DhcpClientTimersSolMaxRt
         TimeTicks,
      er1645v2VEthPppOEIpV6DhcpClientTimersInfoRefresh
         TimeTicks,
      er1645v2VEthPppOEIpV6DhcpServerMode
         INTEGER,
      er1645v2VEthPppOEIpV6DhcpServerPreference
         Integer32,
      er1645v2VEthPppOEIpV6DhcpServerPool
         DisplayString,
      er1645v2VEthPppOEIpV6DhcpServerRapidCommit
         INTEGER,
      er1645v2VEthPppOEIpV6DhcpServerTimersInfoRefresh
         TimeTicks,
      er1645v2VEthPppOEIpV6DhcpRelayMode
         INTEGER,
      er1645v2VEthPppOEIpV6SendRedirect
         INTEGER,
      er1645v2VEthPppOEIpV6LinkMtu
         Integer32,
      er1645v2VEthPppOEIpV6InterfaceId
         OCTET STRING,
      er1645v2VEthPppOEIpV6MF
         Integer32,
      er1645v2VEthPppOEIpV6IcmpMessagesNoRoute
         INTEGER,
      er1645v2VEthPppOEIpV6IcmpMessagesBeyondScope
         INTEGER,
      er1645v2VEthPppOEIpV6IcmpMessagesAddressUnreachable
         INTEGER,
      er1645v2VEthPppOEIpV6IcmpMessagesPortUnreachable
         INTEGER,
      er1645v2VEthPppOEIpV6IcmpMessagesPacketTooBig
         INTEGER,
      er1645v2VEthPppOEIpV6IcmpMessagesHopLimitExceeded
         INTEGER,
      er1645v2VEthPppOEIpV6IcmpMessagesFragTimeExceeded
         INTEGER,
      er1645v2VEthPppOEIpV6IcmpMessagesHeaderFieldErr
         INTEGER,
      er1645v2VEthPppOEIpV6IcmpMessagesOptionUnrecognized
         INTEGER,
      er1645v2VEthPppOEIpV6IcmpMessagesRedirect
         INTEGER,
      er1645v2VEthPppOEPppLnkMOperation
         INTEGER,
      er1645v2VEthPppOEPppLnkMInterval
         TimeTicks,
      er1645v2VEthPppOEPppLnkMRepTimeOut
         TimeTicks,
      er1645v2VEthPppOEPppLnkMFailsPrmt
         Integer32,
      er1645v2VEthPppOEPppAuthentication
         INTEGER,
      er1645v2VEthPppOEPppAuthenPeriod
         TimeTicks,
      er1645v2VEthPppOEPppSessionName
         DisplayString,
      er1645v2VEthPppOEPppSessionSecret
         DisplayString,
      er1645v2VEthPppOEPppEncModeSessionSecret
         INTEGER,
      er1645v2VEthPppOEPppEncSessionSecret
         DisplayString,
      er1645v2VEthPppOEPppServiceName
         DisplayString
      }

er1645v2VEthPppOEActions OBJECT-TYPE
   SYNTAX      VariableLengthTableActions
   MAX-ACCESS  read-write
   STATUS      current
   DESCRIPTION
      "By way of this field, some manipulations
       on this table may be performed."
   ::= {er1645v2VEthPppOEEntry 2}

er1645v2VEthPppOEGlobalIx OBJECT-TYPE
   SYNTAX      GlobalIndex
   MAX-ACCESS  not-accessible
   STATUS      current
   DESCRIPTION
      "The value of the tlsCntTreeGlobalIndex of the MANAGED OBJECT."
   ::= {er1645v2VEthPppOEEntry 10}

er1645v2VEthPppOETableIx OBJECT-TYPE
   SYNTAX      TableIndex
   MAX-ACCESS  not-accessible
   STATUS      current
   DESCRIPTION
      ""
   ::= {er1645v2VEthPppOEEntry 11}

er1645v2VEthPppOEName OBJECT-TYPE
   SYNTAX      DisplayString
   MAX-ACCESS  read-write
   STATUS      current
   DESCRIPTION
      "Path: virtualEthernet.editConf.pppoEClient.name"
   ::= {er1645v2VEthPppOEEntry 16777216}

er1645v2VEthPppOERemark OBJECT-TYPE
   SYNTAX      DisplayString
   MAX-ACCESS  read-write
   STATUS      current
   DESCRIPTION
      "Path: virtualEthernet.editConf.pppoEClient.remark"
   ::= {er1645v2VEthPppOEEntry 1157627904}

er1645v2VEthPppOEAdminStatus OBJECT-TYPE
   SYNTAX      INTEGER
               {
               up (1),
               down (2)
               }
   MAX-ACCESS  read-write
   STATUS      current
   DESCRIPTION
      "Path: virtualEthernet.editConf.pppoEClient.adminStatus

       Possibilities:
               up   (1)
               down   (2)"
   ::= {er1645v2VEthPppOEEntry 33554432}

er1645v2VEthPppOEMode OBJECT-TYPE
   SYNTAX      INTEGER
               {
               routing (1),
               multilink (8),
               ipV6 (16),
               ipV6ipV4 (17)
               }
   MAX-ACCESS  read-write
   STATUS      current
   DESCRIPTION
      "Path: virtualEthernet.editConf.pppoEClient.mode

       Possibilities:
               routing   (1)
               multilink   (8)
               ipV6   (16)
               ipV6/ipV4   (17)"
   ::= {er1645v2VEthPppOEEntry 67108864}

er1645v2VEthPppOEIpVrfRouter OBJECT-TYPE
   SYNTAX      DisplayString
   MAX-ACCESS  read-write
   STATUS      current
   DESCRIPTION
      "Path: virtualEthernet.editConf.pppoEClient.ip.vrfRouter"
   ::= {er1645v2VEthPppOEEntry 53215232}

er1645v2VEthPppOEIpAdr OBJECT-TYPE
   SYNTAX      IpAddress
   MAX-ACCESS  read-write
   STATUS      current
   DESCRIPTION
      "Path: virtualEthernet.editConf.pppoEClient.ip.address"
   ::= {er1645v2VEthPppOEEntry 58261504}

er1645v2VEthPppOEIpNetm OBJECT-TYPE
   SYNTAX      IpAddress
   MAX-ACCESS  read-write
   STATUS      current
   DESCRIPTION
      "Path: virtualEthernet.editConf.pppoEClient.ip.netMask"
   ::= {er1645v2VEthPppOEEntry 58392576}

er1645v2VEthPppOEIpSNetName OBJECT-TYPE
   SYNTAX      INTEGER
               {
               slOPTg (0),
               corp (2),
               dmz (3),
               internet (1)
               }
   MAX-ACCESS  read-write
   STATUS      current
   DESCRIPTION
      "Path: virtualEthernet.editConf.pppoEClient.ip.sNet.name

       Possibilities:
               <OPT>   (0)
               corp   (2)
               dmz   (3)
               internet   (1)"
   ::= {er1645v2VEthPppOEEntry 53674240}

er1645v2VEthPppOEIpSNetCust OBJECT-TYPE
   SYNTAX      DisplayString
   MAX-ACCESS  read-write
   STATUS      current
   DESCRIPTION
      "Path: virtualEthernet.editConf.pppoEClient.ip.sNet.custom"
   ::= {er1645v2VEthPppOEEntry 53674496}

er1645v2VEthPppOEIpRem OBJECT-TYPE
   SYNTAX      IpAddress
   MAX-ACCESS  read-write
   STATUS      current
   DESCRIPTION
      "Path: virtualEthernet.editConf.pppoEClient.ip.remote"
   ::= {er1645v2VEthPppOEEntry 58458112}

er1645v2VEthPppOEIpUnnumbered OBJECT-TYPE
   SYNTAX      DisplayString
   MAX-ACCESS  read-write
   STATUS      current
   DESCRIPTION
      "Path: virtualEthernet.editConf.pppoEClient.ip.unnumbered"
   ::= {er1645v2VEthPppOEEntry 52625408}

er1645v2VEthPppOEIpGwPref OBJECT-TYPE
   SYNTAX      Integer32
   MAX-ACCESS  read-write
   STATUS      current
   DESCRIPTION
      "Path: virtualEthernet.editConf.pppoEClient.ip.gatewayPreference"
   ::= {er1645v2VEthPppOEEntry 52690944}

er1645v2VEthPppOEIpRsn OBJECT-TYPE
   SYNTAX      INTEGER
               {
               disabled (0),
               enabled (1)
               }
   MAX-ACCESS  read-write
   STATUS      current
   DESCRIPTION
      "Path: virtualEthernet.editConf.pppoEClient.ip.requestSubnet

       Possibilities:
               disabled   (0)
               enabled   (1)"
   ::= {er1645v2VEthPppOEEntry 56688640}

er1645v2VEthPppOEIpMtu OBJECT-TYPE
   SYNTAX      Integer32
   MAX-ACCESS  read-write
   STATUS      current
   DESCRIPTION
      "Path: virtualEthernet.editConf.pppoEClient.ip.mtu"
   ::= {er1645v2VEthPppOEEntry 52953088}

er1645v2VEthPppOEIpMssAdjust OBJECT-TYPE
   SYNTAX      INTEGER
               {
               disabled (0),
               auto (65536)
               }
   MAX-ACCESS  read-write
   STATUS      current
   DESCRIPTION
      "Path: virtualEthernet.editConf.pppoEClient.ip.mssAdjust

       Possibilities:
               disabled   (0)
               auto   (65536)"
   ::= {er1645v2VEthPppOEEntry 53280768}

er1645v2VEthPppOEIpRipMetric OBJECT-TYPE
   SYNTAX      Integer32
   MAX-ACCESS  read-write
   STATUS      current
   DESCRIPTION
      "Path: virtualEthernet.editConf.pppoEClient.ip.rip.metric"
   ::= {er1645v2VEthPppOEEntry 51712768}

er1645v2VEthPppOEIpRipMetricOut OBJECT-TYPE
   SYNTAX      Integer32
   MAX-ACCESS  read-write
   STATUS      current
   DESCRIPTION
      "Path: virtualEthernet.editConf.pppoEClient.ip.rip.metricOut"
   ::= {er1645v2VEthPppOEEntry 51713024}

er1645v2VEthPppOEIpRipMode OBJECT-TYPE
   SYNTAX      INTEGER
               {
               disabled (0),
               passive (1),
               active (2)
               }
   MAX-ACCESS  read-write
   STATUS      current
   DESCRIPTION
      "Path: virtualEthernet.editConf.pppoEClient.ip.rip.mode

       Possibilities:
               disabled   (0)
               passive   (1)
               active   (2)"
   ::= {er1645v2VEthPppOEEntry 51713280}

er1645v2VEthPppOEIpRipTxVer OBJECT-TYPE
   SYNTAX      INTEGER
               {
               rip1 (0),
               rip2 (1),
               rip1mcompatible (2)
               }
   MAX-ACCESS  read-write
   STATUS      current
   DESCRIPTION
      "Path: virtualEthernet.editConf.pppoEClient.ip.rip.txVersion

       Possibilities:
               rip1   (0)
               rip2   (1)
               rip1-compatible   (2)"
   ::= {er1645v2VEthPppOEEntry 51716864}

er1645v2VEthPppOEIpRipRxVer OBJECT-TYPE
   SYNTAX      INTEGER
               {
               rip1only (0),
               rip2only (1),
               rip12 (2)
               }
   MAX-ACCESS  read-write
   STATUS      current
   DESCRIPTION
      "Path: virtualEthernet.editConf.pppoEClient.ip.rip.rxVersion

       Possibilities:
               rip1only   (0)
               rip2only   (1)
               rip1&2   (2)"
   ::= {er1645v2VEthPppOEEntry 51717120}

er1645v2VEthPppOEIpRipSplitH OBJECT-TYPE
   SYNTAX      INTEGER
               {
               disabled (0),
               enabled (1),
               poisonedReverse (2)
               }
   MAX-ACCESS  read-write
   STATUS      current
   DESCRIPTION
      "Path: virtualEthernet.editConf.pppoEClient.ip.rip.splitHorizon

       Possibilities:
               disabled   (0)
               enabled   (1)
               poisonedReverse   (2)"
   ::= {er1645v2VEthPppOEEntry 51713792}

er1645v2VEthPppOEIpRipAuth OBJECT-TYPE
   SYNTAX      INTEGER
               {
               disabled (0),
               texts (1),
               md5 (2)
               }
   MAX-ACCESS  read-write
   STATUS      current
   DESCRIPTION
      "Path: virtualEthernet.editConf.pppoEClient.ip.rip.authentication

       Possibilities:
               disabled   (0)
               text    (1)
               md5   (2)"
   ::= {er1645v2VEthPppOEEntry 51712512}

er1645v2VEthPppOEIpRipFilter OBJECT-TYPE
   SYNTAX      DisplayString
   MAX-ACCESS  read-write
   STATUS      current
   DESCRIPTION
      "Path: virtualEthernet.editConf.pppoEClient.ip.rip.filter"
   ::= {er1645v2VEthPppOEEntry 51716096}

er1645v2VEthPppOEIpRipFilterIn OBJECT-TYPE
   SYNTAX      DisplayString
   MAX-ACCESS  read-write
   STATUS      current
   DESCRIPTION
      "Path: virtualEthernet.editConf.pppoEClient.ip.rip.filterIn"
   ::= {er1645v2VEthPppOEEntry 51716352}

er1645v2VEthPppOEIpRipClearNextHop OBJECT-TYPE
   SYNTAX      INTEGER
               {
               disabled (0),
               enabled (1)
               }
   MAX-ACCESS  read-write
   STATUS      current
   DESCRIPTION
      "Path: virtualEthernet.editConf.pppoEClient.ip.rip.clearNextHop

       Possibilities:
               disabled   (0)
               enabled   (1)"
   ::= {er1645v2VEthPppOEEntry 51708416}

er1645v2VEthPppOEIpAccPol OBJECT-TYPE
   SYNTAX      DisplayString
   MAX-ACCESS  read-write
   STATUS      current
   DESCRIPTION
      "Path: virtualEthernet.editConf.pppoEClient.ip.accessPolicy"
   ::= {er1645v2VEthPppOEEntry 53084160}

er1645v2VEthPppOEIpAB OBJECT-TYPE
   SYNTAX      DisplayString
   MAX-ACCESS  read-write
   STATUS      current
   DESCRIPTION
      "Path: virtualEthernet.editConf.pppoEClient.ip.trafficPolicy"
   ::= {er1645v2VEthPppOEEntry 51249152}

er1645v2VEthPppOEIpMA OBJECT-TYPE
   SYNTAX      INTEGER
               {
               disabled (0),
               enabled (1)
               }
   MAX-ACCESS  read-write
   STATUS      current
   DESCRIPTION
      "Path: virtualEthernet.editConf.pppoEClient.ip.mgmtAccess

       Possibilities:
               disabled   (0)
               enabled   (1)"
   ::= {er1645v2VEthPppOEEntry 51380224}

er1645v2VEthPppOEIpMF OBJECT-TYPE
   SYNTAX      Integer32
   MAX-ACCESS  read-write
   STATUS      current
   DESCRIPTION
      "Path: virtualEthernet.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2VEthPppOEEntry 51445760}

er1645v2VEthPppOEIpDB OBJECT-TYPE
   SYNTAX      INTEGER
               {
               disabled (0),
               enabled (1)
               }
   MAX-ACCESS  read-write
   STATUS      current
   DESCRIPTION
      "Path: virtualEthernet.editConf.pppoEClient.ip.directedBroadcasts

       Possibilities:
               disabled   (0)
               enabled   (1)"
   ::= {er1645v2VEthPppOEEntry 51773440}

er1645v2VEthPppOEIpIR OBJECT-TYPE
   SYNTAX      INTEGER
               {
               disabled (0),
               enabled (1)
               }
   MAX-ACCESS  read-write
   STATUS      current
   DESCRIPTION
      "Path: virtualEthernet.editConf.pppoEClient.ip.icmpRedirects

       Possibilities:
               disabled   (0)
               enabled   (1)"
   ::= {er1645v2VEthPppOEEntry 52035584}

er1645v2VEthPppOEIpIgmp OBJECT-TYPE
   SYNTAX      INTEGER
               {
               disabled (0),
               proxy (1),
               router (2),
               v3Router (5)
               }
   MAX-ACCESS  read-write
   STATUS      current
   DESCRIPTION
      "Path: virtualEthernet.editConf.pppoEClient.ip.igmp

       Possibilities:
               disabled   (0)
               proxy   (1)
               router   (2)
               v3Router   (5)"
   ::= {er1645v2VEthPppOEEntry 52428800}

er1645v2VEthPppOEIpNN OBJECT-TYPE
   SYNTAX      DisplayString
   MAX-ACCESS  read-write
   STATUS      current
   DESCRIPTION
      "Path: virtualEthernet.editConf.pppoEClient.ip.nat"
   ::= {er1645v2VEthPppOEEntry 52101120}

er1645v2VEthPppOEIpPimMode OBJECT-TYPE
   SYNTAX      INTEGER
               {
               disabled (0),
               sparse (1),
               passive (2)
               }
   MAX-ACCESS  read-write
   STATUS      current
   DESCRIPTION
      "Path: virtualEthernet.editConf.pppoEClient.ip.pim.mode

       Possibilities:
               disabled   (0)
               sparse   (1)
               passive   (2)"
   ::= {er1645v2VEthPppOEEntry 53346560}

er1645v2VEthPppOEIpPimDrPriority OBJECT-TYPE
   SYNTAX      Counter32
   MAX-ACCESS  read-write
   STATUS      current
   DESCRIPTION
      "Path: virtualEthernet.editConf.pppoEClient.ip.pim.drPriority

       32 bit unsigned wrappable counter."
   ::= {er1645v2VEthPppOEEntry 53346816}

er1645v2VEthPppOEIpPimHelloTime OBJECT-TYPE
   SYNTAX      TimeTicks
   MAX-ACCESS  read-write
   STATUS      current
   DESCRIPTION
      "Path: virtualEthernet.editConf.pppoEClient.ip.pim.helloTime

       Time in centi-second."
   ::= {er1645v2VEthPppOEEntry 53347072}

er1645v2VEthPppOEIpPimPropagationDelay OBJECT-TYPE
   SYNTAX      TimeTicks
   MAX-ACCESS  read-write
   STATUS      current
   DESCRIPTION
      "Path: virtualEthernet.editConf.pppoEClient.ip.pim.propagationDelay

       Time in centi-second."
   ::= {er1645v2VEthPppOEEntry 53347328}

er1645v2VEthPppOEIpPimOverrideInterval OBJECT-TYPE
   SYNTAX      TimeTicks
   MAX-ACCESS  read-write
   STATUS      current
   DESCRIPTION
      "Path: virtualEthernet.editConf.pppoEClient.ip.pim.overrideInterval

       Time in centi-second."
   ::= {er1645v2VEthPppOEEntry 53347584}

er1645v2VEthPppOEIpPimBsrBorder OBJECT-TYPE
   SYNTAX      INTEGER
               {
               disabled (0),
               enabled (1)
               }
   MAX-ACCESS  read-write
   STATUS      current
   DESCRIPTION
      "Path: virtualEthernet.editConf.pppoEClient.ip.pim.bsrBorder

       Possibilities:
               disabled   (0)
               enabled   (1)"
   ::= {er1645v2VEthPppOEEntry 53347840}

er1645v2VEthPppOEIpPimTtlThreshold OBJECT-TYPE
   SYNTAX      Integer32
   MAX-ACCESS  read-write
   STATUS      current
   DESCRIPTION
      "Path: virtualEthernet.editConf.pppoEClient.ip.pim.ttlThreshold"
   ::= {er1645v2VEthPppOEEntry 53348096}

er1645v2VEthPppOEIpIMNetworkUnreachable OBJECT-TYPE
   SYNTAX      INTEGER
               {
               disabled (0),
               enabled (1)
               }
   MAX-ACCESS  read-write
   STATUS      current
   DESCRIPTION
      "Path: virtualEthernet.editConf.pppoEClient.ip.icmpMessages.networkUnreachable

       Possibilities:
               disabled   (0)
               enabled   (1)"
   ::= {er1645v2VEthPppOEEntry 53412096}

er1645v2VEthPppOEIpIMHostUnreachable OBJECT-TYPE
   SYNTAX      INTEGER
               {
               disabled (0),
               enabled (1)
               }
   MAX-ACCESS  read-write
   STATUS      current
   DESCRIPTION
      "Path: virtualEthernet.editConf.pppoEClient.ip.icmpMessages.hostUnreachable

       Possibilities:
               disabled   (0)
               enabled   (1)"
   ::= {er1645v2VEthPppOEEntry 53412352}

er1645v2VEthPppOEIpIMProtocolUnreachable OBJECT-TYPE
   SYNTAX      INTEGER
               {
               disabled (0),
               enabled (1)
               }
   MAX-ACCESS  read-write
   STATUS      current
   DESCRIPTION
      "Path: virtualEthernet.editConf.pppoEClient.ip.icmpMessages.protocolUnreachable

       Possibilities:
               disabled   (0)
               enabled   (1)"
   ::= {er1645v2VEthPppOEEntry 53412608}

er1645v2VEthPppOEIpIMPortUnreachable OBJECT-TYPE
   SYNTAX      INTEGER
               {
               disabled (0),
               enabled (1)
               }
   MAX-ACCESS  read-write
   STATUS      current
   DESCRIPTION
      "Path: virtualEthernet.editConf.pppoEClient.ip.icmpMessages.portUnreachable

       Possibilities:
               disabled   (0)
               enabled   (1)"
   ::= {er1645v2VEthPppOEEntry 53412864}

er1645v2VEthPppOEIpIMMtuExceeded OBJECT-TYPE
   SYNTAX      INTEGER
               {
               disabled (0),
               enabled (1)
               }
   MAX-ACCESS  read-write
   STATUS      current
   DESCRIPTION
      "Path: virtualEthernet.editConf.pppoEClient.ip.icmpMessages.mtuExceeded

       Possibilities:
               disabled   (0)
               enabled   (1)"
   ::= {er1645v2VEthPppOEEntry 53413120}

er1645v2VEthPppOEIpIMAdminProhibited OBJECT-TYPE
   SYNTAX      INTEGER
               {
               disabled (0),
               enabled (1)
               }
   MAX-ACCESS  read-write
   STATUS      current
   DESCRIPTION
      "Path: virtualEthernet.editConf.pppoEClient.ip.icmpMessages.adminProhibited

       Possibilities:
               disabled   (0)
               enabled   (1)"
   ::= {er1645v2VEthPppOEEntry 53413376}

er1645v2VEthPppOEIpIMTtlExceeded OBJECT-TYPE
   SYNTAX      INTEGER
               {
               disabled (0),
               enabled (1)
               }
   MAX-ACCESS  read-write
   STATUS      current
   DESCRIPTION
      "Path: virtualEthernet.editConf.pppoEClient.ip.icmpMessages.ttlExceeded

       Possibilities:
               disabled   (0)
               enabled   (1)"
   ::= {er1645v2VEthPppOEEntry 53413632}

er1645v2VEthPppOEIpIMRedirect OBJECT-TYPE
   SYNTAX      INTEGER
               {
               disabled (0),
               enabled (1)
               }
   MAX-ACCESS  read-write
   STATUS      current
   DESCRIPTION
      "Path: virtualEthernet.editConf.pppoEClient.ip.icmpMessages.redirect

       Possibilities:
               disabled   (0)
               enabled   (1)"
   ::= {er1645v2VEthPppOEEntry 53413888}

er1645v2VEthPppOEIpV6VrfRouter OBJECT-TYPE
   SYNTAX      DisplayString
   MAX-ACCESS  read-write
   STATUS      current
   DESCRIPTION
      "Path: virtualEthernet.editConf.pppoEClient.ipV6.vrfRouter"
   ::= {er1645v2VEthPppOEEntry 704708608}

er1645v2VEthPppOEIpV6AddrAutoConfigNrDupAddrDetects OBJECT-TYPE
   SYNTAX      Integer32
   MAX-ACCESS  read-write
   STATUS      current
   DESCRIPTION
      "Path: virtualEthernet.editConf.pppoEClient.ipV6.addrAutoConfig.nrDupAddrDetects"
   ::= {er1645v2VEthPppOEEntry 704905472}

er1645v2VEthPppOEIpV6AddrAutoConfigAcceptRa OBJECT-TYPE
   SYNTAX      INTEGER
               {
               disabled (0),
               enabled (1)
               }
   MAX-ACCESS  read-write
   STATUS      current
   DESCRIPTION
      "Path: virtualEthernet.editConf.pppoEClient.ipV6.addrAutoConfig.acceptRa

       Possibilities:
               disabled   (0)
               enabled   (1)"
   ::= {er1645v2VEthPppOEEntry 704905728}

er1645v2VEthPppOEIpV6AddrAutoConfigAcceptRaRdnss OBJECT-TYPE
   SYNTAX      INTEGER
               {
               disabled (0),
               enabled (1)
               }
   MAX-ACCESS  read-write
   STATUS      current
   DESCRIPTION
      "Path: virtualEthernet.editConf.pppoEClient.ipV6.addrAutoConfig.acceptRaRdnss

       Possibilities:
               disabled   (0)
               enabled   (1)"
   ::= {er1645v2VEthPppOEEntry 704905984}

er1645v2VEthPppOEIpV6AddrAutoConfigAcceptRaDnssl OBJECT-TYPE
   SYNTAX      INTEGER
               {
               disabled (0),
               enabled (1)
               }
   MAX-ACCESS  read-write
   STATUS      current
   DESCRIPTION
      "Path: virtualEthernet.editConf.pppoEClient.ipV6.addrAutoConfig.acceptRaDnssl

       Possibilities:
               disabled   (0)
               enabled   (1)"
   ::= {er1645v2VEthPppOEEntry 704906240}

er1645v2VEthPppOEIpV6DefaultRoute OBJECT-TYPE
   SYNTAX      INTEGER
               {
               disabled (0),
               enabled (1)
               }
   MAX-ACCESS  read-write
   STATUS      current
   DESCRIPTION
      "Path: virtualEthernet.editConf.pppoEClient.ipV6.defaultRoute

       Possibilities:
               disabled   (0)
               enabled   (1)"
   ::= {er1645v2VEthPppOEEntry 704970752}

er1645v2VEthPppOEIpV6RaSend OBJECT-TYPE
   SYNTAX      INTEGER
               {
               disabled (0),
               enabled (1)
               }
   MAX-ACCESS  read-write
   STATUS      current
   DESCRIPTION
      "Path: virtualEthernet.editConf.pppoEClient.ipV6.ra.send

       Possibilities:
               disabled   (0)
               enabled   (1)"
   ::= {er1645v2VEthPppOEEntry 705036544}

er1645v2VEthPppOEIpV6RaMinInterval OBJECT-TYPE
   SYNTAX      TimeTicks
   MAX-ACCESS  read-write
   STATUS      current
   DESCRIPTION
      "Path: virtualEthernet.editConf.pppoEClient.ipV6.ra.minInterval

       Time in centi-second."
   ::= {er1645v2VEthPppOEEntry 705036800}

er1645v2VEthPppOEIpV6RaMaxInterval OBJECT-TYPE
   SYNTAX      TimeTicks
   MAX-ACCESS  read-write
   STATUS      current
   DESCRIPTION
      "Path: virtualEthernet.editConf.pppoEClient.ipV6.ra.maxInterval

       Time in centi-second."
   ::= {er1645v2VEthPppOEEntry 705037056}

er1645v2VEthPppOEIpV6RaManagedFlag OBJECT-TYPE
   SYNTAX      INTEGER
               {
               disabled (0),
               enabled (1)
               }
   MAX-ACCESS  read-write
   STATUS      current
   DESCRIPTION
      "Path: virtualEthernet.editConf.pppoEClient.ipV6.ra.managedFlag

       Possibilities:
               disabled   (0)
               enabled   (1)"
   ::= {er1645v2VEthPppOEEntry 705037312}

er1645v2VEthPppOEIpV6RaOtherConfFlag OBJECT-TYPE
   SYNTAX      INTEGER
               {
               disabled (0),
               enabled (1)
               }
   MAX-ACCESS  read-write
   STATUS      current
   DESCRIPTION
      "Path: virtualEthernet.editConf.pppoEClient.ipV6.ra.otherConfFlag

       Possibilities:
               disabled   (0)
               enabled   (1)"
   ::= {er1645v2VEthPppOEEntry 705037568}

er1645v2VEthPppOEIpV6RaLinkMtu OBJECT-TYPE
   SYNTAX      Integer32
   MAX-ACCESS  read-write
   STATUS      current
   DESCRIPTION
      "Path: virtualEthernet.editConf.pppoEClient.ipV6.ra.linkMtu"
   ::= {er1645v2VEthPppOEEntry 705037824}

er1645v2VEthPppOEIpV6RaReachableTime OBJECT-TYPE
   SYNTAX      TimeTicks
   MAX-ACCESS  read-write
   STATUS      current
   DESCRIPTION
      "Path: virtualEthernet.editConf.pppoEClient.ipV6.ra.reachableTime

       Time in centi-second."
   ::= {er1645v2VEthPppOEEntry 705038080}

er1645v2VEthPppOEIpV6RaRetransmitTime OBJECT-TYPE
   SYNTAX      TimeTicks
   MAX-ACCESS  read-write
   STATUS      current
   DESCRIPTION
      "Path: virtualEthernet.editConf.pppoEClient.ipV6.ra.retransmitTime

       Time in centi-second."
   ::= {er1645v2VEthPppOEEntry 705038336}

er1645v2VEthPppOEIpV6RaHopLimit OBJECT-TYPE
   SYNTAX      Integer32
   MAX-ACCESS  read-write
   STATUS      current
   DESCRIPTION
      "Path: virtualEthernet.editConf.pppoEClient.ipV6.ra.hopLimit"
   ::= {er1645v2VEthPppOEEntry 705038592}

er1645v2VEthPppOEIpV6RaDefaultLifeTime OBJECT-TYPE
   SYNTAX      TimeTicks
   MAX-ACCESS  read-write
   STATUS      current
   DESCRIPTION
      "Path: virtualEthernet.editConf.pppoEClient.ipV6.ra.defaultLifeTime

       Time in centi-second."
   ::= {er1645v2VEthPppOEEntry 705038848}

er1645v2VEthPppOEIpV6RaDnsOptionsRdnssLifeTime OBJECT-TYPE
   SYNTAX      TimeTicks
   MAX-ACCESS  read-write
   STATUS      current
   DESCRIPTION
      "Path: virtualEthernet.editConf.pppoEClient.ipV6.ra.dnsOptions.rdnss.lifeTime

       Time in centi-second."
   ::= {er1645v2VEthPppOEEntry 705039140}

er1645v2VEthPppOEIpV6RaDnsOptionsRdnssImportServers OBJECT-TYPE
   SYNTAX      INTEGER
               {
               disabled (0),
               enabled (1)
               }
   MAX-ACCESS  read-write
   STATUS      current
   DESCRIPTION
      "Path: virtualEthernet.editConf.pppoEClient.ipV6.ra.dnsOptions.rdnss.importServers

       Possibilities:
               disabled   (0)
               enabled   (1)"
   ::= {er1645v2VEthPppOEEntry 705039148}

er1645v2VEthPppOEIpV6RaDnsOptionsDnsslLifeTime OBJECT-TYPE
   SYNTAX      TimeTicks
   MAX-ACCESS  read-write
   STATUS      current
   DESCRIPTION
      "Path: virtualEthernet.editConf.pppoEClient.ipV6.ra.dnsOptions.dnssl.lifeTime

       Time in centi-second."
   ::= {er1645v2VEthPppOEEntry 705039172}

er1645v2VEthPppOEIpV6RaDnsOptionsDnsslImportDomains OBJECT-TYPE
   SYNTAX      INTEGER
               {
               disabled (0),
               enabled (1)
               }
   MAX-ACCESS  read-write
   STATUS      current
   DESCRIPTION
      "Path: virtualEthernet.editConf.pppoEClient.ipV6.ra.dnsOptions.dnssl.importDomains

       Possibilities:
               disabled   (0)
               enabled   (1)"
   ::= {er1645v2VEthPppOEEntry 705039180}

er1645v2VEthPppOEIpV6RsSend OBJECT-TYPE
   SYNTAX      INTEGER
               {
               disabled (0),
               enabled (1)
               }
   MAX-ACCESS  read-write
   STATUS      current
   DESCRIPTION
      "Path: virtualEthernet.editConf.pppoEClient.ipV6.rs.send

       Possibilities:
               disabled   (0)
               enabled   (1)"
   ::= {er1645v2VEthPppOEEntry 705954048}

er1645v2VEthPppOEIpV6RsMaxRandomDelay OBJECT-TYPE
   SYNTAX      TimeTicks
   MAX-ACCESS  read-write
   STATUS      current
   DESCRIPTION
      "Path: virtualEthernet.editConf.pppoEClient.ipV6.rs.maxRandomDelay

       Time in centi-second."
   ::= {er1645v2VEthPppOEEntry 705954304}

er1645v2VEthPppOEIpV6RsInterval OBJECT-TYPE
   SYNTAX      TimeTicks
   MAX-ACCESS  read-write
   STATUS      current
   DESCRIPTION
      "Path: virtualEthernet.editConf.pppoEClient.ipV6.rs.interval

       Time in centi-second."
   ::= {er1645v2VEthPppOEEntry 705954560}

er1645v2VEthPppOEIpV6RsMaxSolicitations OBJECT-TYPE
   SYNTAX      Integer32
   MAX-ACCESS  read-write
   STATUS      current
   DESCRIPTION
      "Path: virtualEthernet.editConf.pppoEClient.ipV6.rs.maxSolicitations"
   ::= {er1645v2VEthPppOEEntry 705954816}

er1645v2VEthPppOEIpV6TrafficPolicyInbound OBJECT-TYPE
   SYNTAX      DisplayString
   MAX-ACCESS  read-write
   STATUS      current
   DESCRIPTION
      "Path: virtualEthernet.editConf.pppoEClient.ipV6.trafficPolicy.inbound"
   ::= {er1645v2VEthPppOEEntry 705364224}

er1645v2VEthPppOEIpV6TrafficPolicyOutbound OBJECT-TYPE
   SYNTAX      DisplayString
   MAX-ACCESS  read-write
   STATUS      current
   DESCRIPTION
      "Path: virtualEthernet.editConf.pppoEClient.ipV6.trafficPolicy.outbound"
   ::= {er1645v2VEthPppOEEntry 705364480}

er1645v2VEthPppOEIpV6FirewallZone OBJECT-TYPE
   SYNTAX      DisplayString
   MAX-ACCESS  read-write
   STATUS      current
   DESCRIPTION
      "Path: virtualEthernet.editConf.pppoEClient.ipV6.firewall.zone"
   ::= {er1645v2VEthPppOEEntry 705429760}

er1645v2VEthPppOEIpV6DhcpClientAddrAC OBJECT-TYPE
   SYNTAX      INTEGER
               {
               disabled (0),
               enabled (1)
               }
   MAX-ACCESS  read-write
   STATUS      current
   DESCRIPTION
      "Path: virtualEthernet.editConf.pppoEClient.ipV6.dhcp.client.addrAutoConfig

       Possibilities:
               disabled   (0)
               enabled   (1)"
   ::= {er1645v2VEthPppOEEntry 705307648}

er1645v2VEthPppOEIpV6DhcpClientPrDelMode OBJECT-TYPE
   SYNTAX      INTEGER
               {
               disabled (0),
               enabled (1)
               }
   MAX-ACCESS  read-write
   STATUS      current
   DESCRIPTION
      "Path: virtualEthernet.editConf.pppoEClient.ipV6.dhcp.client.pd.mode

       Possibilities:
               disabled   (0)
               enabled   (1)"
   ::= {er1645v2VEthPppOEEntry 705308676}

er1645v2VEthPppOEIpV6DhcpClientPrDelPool OBJECT-TYPE
   SYNTAX      DisplayString
   MAX-ACCESS  read-write
   STATUS      current
   DESCRIPTION
      "Path: virtualEthernet.editConf.pppoEClient.ipV6.dhcp.client.pd.pool"
   ::= {er1645v2VEthPppOEEntry 705308680}

er1645v2VEthPppOEIpV6DhcpClientPrDelPdExclOpt OBJECT-TYPE
   SYNTAX      INTEGER
               {
               disabled (0),
               enabled (1)
               }
   MAX-ACCESS  read-write
   STATUS      current
   DESCRIPTION
      "Path: virtualEthernet.editConf.pppoEClient.ipV6.dhcp.client.pd.pdExclOpt

       Possibilities:
               disabled   (0)
               enabled   (1)"
   ::= {er1645v2VEthPppOEEntry 705308684}

er1645v2VEthPppOEIpV6DhcpClientDnsServerPref OBJECT-TYPE
   SYNTAX      Integer32
   MAX-ACCESS  read-write
   STATUS      current
   DESCRIPTION
      "Path: virtualEthernet.editConf.pppoEClient.ipV6.dhcp.client.dns.serverPref"
   ::= {er1645v2VEthPppOEEntry 705310724}

er1645v2VEthPppOEIpV6DhcpClientRapidCommit OBJECT-TYPE
   SYNTAX      INTEGER
               {
               disabled (0),
               enabled (1)
               }
   MAX-ACCESS  read-write
   STATUS      current
   DESCRIPTION
      "Path: virtualEthernet.editConf.pppoEClient.ipV6.dhcp.client.rapidCommit

       Possibilities:
               disabled   (0)
               enabled   (1)"
   ::= {er1645v2VEthPppOEEntry 705309696}

er1645v2VEthPppOEIpV6DhcpClientTimersSolTimeOut OBJECT-TYPE
   SYNTAX      TimeTicks
   MAX-ACCESS  read-write
   STATUS      current
   DESCRIPTION
      "Path: virtualEthernet.editConf.pppoEClient.ipV6.dhcp.client.timers.solTimeOut

       Time in centi-second."
   ::= {er1645v2VEthPppOEEntry 705311748}

er1645v2VEthPppOEIpV6DhcpClientTimersSolMaxRt OBJECT-TYPE
   SYNTAX      TimeTicks
   MAX-ACCESS  read-write
   STATUS      current
   DESCRIPTION
      "Path: virtualEthernet.editConf.pppoEClient.ipV6.dhcp.client.timers.solMaxRt

       Time in centi-second."
   ::= {er1645v2VEthPppOEEntry 705311752}

er1645v2VEthPppOEIpV6DhcpClientTimersInfoRefresh OBJECT-TYPE
   SYNTAX      TimeTicks
   MAX-ACCESS  read-write
   STATUS      current
   DESCRIPTION
      "Path: virtualEthernet.editConf.pppoEClient.ipV6.dhcp.client.timers.infoRefresh

       Time in centi-second."
   ::= {er1645v2VEthPppOEEntry 705311756}

er1645v2VEthPppOEIpV6DhcpServerMode OBJECT-TYPE
   SYNTAX      INTEGER
               {
               disabled (0),
               enabled (1)
               }
   MAX-ACCESS  read-write
   STATUS      current
   DESCRIPTION
      "Path: virtualEthernet.editConf.pppoEClient.ipV6.dhcp.server.mode

       Possibilities:
               disabled   (0)
               enabled   (1)"
   ::= {er1645v2VEthPppOEEntry 705315840}

er1645v2VEthPppOEIpV6DhcpServerPreference OBJECT-TYPE
   SYNTAX      Integer32
   MAX-ACCESS  read-write
   STATUS      current
   DESCRIPTION
      "Path: virtualEthernet.editConf.pppoEClient.ipV6.dhcp.server.preference"
   ::= {er1645v2VEthPppOEEntry 705316864}

er1645v2VEthPppOEIpV6DhcpServerPool OBJECT-TYPE
   SYNTAX      DisplayString
   MAX-ACCESS  read-write
   STATUS      current
   DESCRIPTION
      "Path: virtualEthernet.editConf.pppoEClient.ipV6.dhcp.server.pool"
   ::= {er1645v2VEthPppOEEntry 705317888}

er1645v2VEthPppOEIpV6DhcpServerRapidCommit OBJECT-TYPE
   SYNTAX      INTEGER
               {
               disabled (0),
               enabled (1)
               }
   MAX-ACCESS  read-write
   STATUS      current
   DESCRIPTION
      "Path: virtualEthernet.editConf.pppoEClient.ipV6.dhcp.server.rapidCommit

       Possibilities:
               disabled   (0)
               enabled   (1)"
   ::= {er1645v2VEthPppOEEntry 705318912}

er1645v2VEthPppOEIpV6DhcpServerTimersInfoRefresh OBJECT-TYPE
   SYNTAX      TimeTicks
   MAX-ACCESS  read-write
   STATUS      current
   DESCRIPTION
      "Path: virtualEthernet.editConf.pppoEClient.ipV6.dhcp.server.timers.infoRefresh

       Time in centi-second."
   ::= {er1645v2VEthPppOEEntry 705319940}

er1645v2VEthPppOEIpV6DhcpRelayMode OBJECT-TYPE
   SYNTAX      INTEGER
               {
               disabled (0),
               enabled (1)
               }
   MAX-ACCESS  read-write
   STATUS      current
   DESCRIPTION
      "Path: virtualEthernet.editConf.pppoEClient.ipV6.dhcp.relay.mode

       Possibilities:
               disabled   (0)
               enabled   (1)"
   ::= {er1645v2VEthPppOEEntry 705323040}

er1645v2VEthPppOEIpV6SendRedirect OBJECT-TYPE
   SYNTAX      INTEGER
               {
               disabled (0),
               enabled (1)
               }
   MAX-ACCESS  read-write
   STATUS      current
   DESCRIPTION
      "Path: virtualEthernet.editConf.pppoEClient.ipV6.sendRedirect

       Possibilities:
               disabled   (0)
               enabled   (1)"
   ::= {er1645v2VEthPppOEEntry 705101824}

er1645v2VEthPppOEIpV6LinkMtu OBJECT-TYPE
   SYNTAX      Integer32
   MAX-ACCESS  read-write
   STATUS      current
   DESCRIPTION
      "Path: virtualEthernet.editConf.pppoEClient.ipV6.linkMtu"
   ::= {er1645v2VEthPppOEEntry 705167360}

er1645v2VEthPppOEIpV6InterfaceId OBJECT-TYPE
   SYNTAX      OCTET STRING
   MAX-ACCESS  read-write
   STATUS      current
   DESCRIPTION
      "Path: virtualEthernet.editConf.pppoEClient.ipV6.interfaceId"
   ::= {er1645v2VEthPppOEEntry 705232896}

er1645v2VEthPppOEIpV6MF OBJECT-TYPE
   SYNTAX      Integer32
   MAX-ACCESS  read-write
   STATUS      current
   DESCRIPTION
      "Path: virtualEthernet.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2VEthPppOEEntry 705757184}

er1645v2VEthPppOEIpV6IcmpMessagesNoRoute OBJECT-TYPE
   SYNTAX      INTEGER
               {
               disabled (0),
               enabled (1)
               }
   MAX-ACCESS  read-write
   STATUS      current
   DESCRIPTION
      "Path: virtualEthernet.editConf.pppoEClient.ipV6.icmpMessages.noRoute

       Possibilities:
               disabled   (0)
               enabled   (1)"
   ::= {er1645v2VEthPppOEEntry 705822976}

er1645v2VEthPppOEIpV6IcmpMessagesBeyondScope OBJECT-TYPE
   SYNTAX      INTEGER
               {
               disabled (0),
               enabled (1)
               }
   MAX-ACCESS  read-write
   STATUS      current
   DESCRIPTION
      "Path: virtualEthernet.editConf.pppoEClient.ipV6.icmpMessages.beyondScope

       Possibilities:
               disabled   (0)
               enabled   (1)"
   ::= {er1645v2VEthPppOEEntry 705823488}

er1645v2VEthPppOEIpV6IcmpMessagesAddressUnreachable OBJECT-TYPE
   SYNTAX      INTEGER
               {
               disabled (0),
               enabled (1)
               }
   MAX-ACCESS  read-write
   STATUS      current
   DESCRIPTION
      "Path: virtualEthernet.editConf.pppoEClient.ipV6.icmpMessages.addressUnreachable

       Possibilities:
               disabled   (0)
               enabled   (1)"
   ::= {er1645v2VEthPppOEEntry 705823744}

er1645v2VEthPppOEIpV6IcmpMessagesPortUnreachable OBJECT-TYPE
   SYNTAX      INTEGER
               {
               disabled (0),
               enabled (1)
               }
   MAX-ACCESS  read-write
   STATUS      current
   DESCRIPTION
      "Path: virtualEthernet.editConf.pppoEClient.ipV6.icmpMessages.portUnreachable

       Possibilities:
               disabled   (0)
               enabled   (1)"
   ::= {er1645v2VEthPppOEEntry 705824000}

er1645v2VEthPppOEIpV6IcmpMessagesPacketTooBig OBJECT-TYPE
   SYNTAX      INTEGER
               {
               disabled (0),
               enabled (1)
               }
   MAX-ACCESS  read-write
   STATUS      current
   DESCRIPTION
      "Path: virtualEthernet.editConf.pppoEClient.ipV6.icmpMessages.packetTooBig

       Possibilities:
               disabled   (0)
               enabled   (1)"
   ::= {er1645v2VEthPppOEEntry 705825280}

er1645v2VEthPppOEIpV6IcmpMessagesHopLimitExceeded OBJECT-TYPE
   SYNTAX      INTEGER
               {
               disabled (0),
               enabled (1)
               }
   MAX-ACCESS  read-write
   STATUS      current
   DESCRIPTION
      "Path: virtualEthernet.editConf.pppoEClient.ipV6.icmpMessages.hopLimitExceeded

       Possibilities:
               disabled   (0)
               enabled   (1)"
   ::= {er1645v2VEthPppOEEntry 705827840}

er1645v2VEthPppOEIpV6IcmpMessagesFragTimeExceeded OBJECT-TYPE
   SYNTAX      INTEGER
               {
               disabled (0),
               enabled (1)
               }
   MAX-ACCESS  read-write
   STATUS      current
   DESCRIPTION
      "Path: virtualEthernet.editConf.pppoEClient.ipV6.icmpMessages.fragTimeExceeded

       Possibilities:
               disabled   (0)
               enabled   (1)"
   ::= {er1645v2VEthPppOEEntry 705828096}

er1645v2VEthPppOEIpV6IcmpMessagesHeaderFieldErr OBJECT-TYPE
   SYNTAX      INTEGER
               {
               disabled (0),
               enabled (1)
               }
   MAX-ACCESS  read-write
   STATUS      current
   DESCRIPTION
      "Path: virtualEthernet.editConf.pppoEClient.ipV6.icmpMessages.headerFieldErr

       Possibilities:
               disabled   (0)
               enabled   (1)"
   ::= {er1645v2VEthPppOEEntry 705830400}

er1645v2VEthPppOEIpV6IcmpMessagesOptionUnrecognized OBJECT-TYPE
   SYNTAX      INTEGER
               {
               disabled (0),
               enabled (1)
               }
   MAX-ACCESS  read-write
   STATUS      current
   DESCRIPTION
      "Path: virtualEthernet.editConf.pppoEClient.ipV6.icmpMessages.optionUnrecognized

       Possibilities:
               disabled   (0)
               enabled   (1)"
   ::= {er1645v2VEthPppOEEntry 705830912}

er1645v2VEthPppOEIpV6IcmpMessagesRedirect OBJECT-TYPE
   SYNTAX      INTEGER
               {
               disabled (0),
               enabled (1)
               }
   MAX-ACCESS  read-write
   STATUS      current
   DESCRIPTION
      "Path: virtualEthernet.editConf.pppoEClient.ipV6.icmpMessages.redirect

       Possibilities:
               disabled   (0)
               enabled   (1)"
   ::= {er1645v2VEthPppOEEntry 705832960}

er1645v2VEthPppOEPppLnkMOperation OBJECT-TYPE
   SYNTAX      INTEGER
               {
               disabled (0),
               enabled (1)
               }
   MAX-ACCESS  read-write
   STATUS      current
   DESCRIPTION
      "Path: virtualEthernet.editConf.pppoEClient.ppp.linkMonitoring.operation

       Possibilities:
               disabled   (0)
               enabled   (1)"
   ::= {er1645v2VEthPppOEEntry 251724032}

er1645v2VEthPppOEPppLnkMInterval OBJECT-TYPE
   SYNTAX      TimeTicks
   MAX-ACCESS  read-write
   STATUS      current
   DESCRIPTION
      "Path: virtualEthernet.editConf.pppoEClient.ppp.linkMonitoring.interval

       Time in centi-second."
   ::= {er1645v2VEthPppOEEntry 251724288}

er1645v2VEthPppOEPppLnkMRepTimeOut OBJECT-TYPE
   SYNTAX      TimeTicks
   MAX-ACCESS  read-write
   STATUS      current
   DESCRIPTION
      "Path: virtualEthernet.editConf.pppoEClient.ppp.linkMonitoring.replyTimeOut

       Time in centi-second."
   ::= {er1645v2VEthPppOEEntry 251724544}

er1645v2VEthPppOEPppLnkMFailsPrmt OBJECT-TYPE
   SYNTAX      Integer32
   MAX-ACCESS  read-write
   STATUS      current
   DESCRIPTION
      "Path: virtualEthernet.editConf.pppoEClient.ppp.linkMonitoring.failsPermitted"
   ::= {er1645v2VEthPppOEEntry 251724800}

er1645v2VEthPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: virtualEthernet.editConf.pppoEClient.ppp.authentication

       Possibilities:
               disabled   (0)
               chap   (1)
               pap   (2)
               chapOrPap   (3)
               msChap   (4)
               msChapV2   (5)"
   ::= {er1645v2VEthPppOEEntry 251789312}

er1645v2VEthPppOEPppAuthenPeriod OBJECT-TYPE
   SYNTAX      TimeTicks
   MAX-ACCESS  read-write
   STATUS      current
   DESCRIPTION
      "Path: virtualEthernet.editConf.pppoEClient.ppp.authenPeriod

       Time in centi-second."
   ::= {er1645v2VEthPppOEEntry 251854848}

er1645v2VEthPppOEPppSessionName OBJECT-TYPE
   SYNTAX      DisplayString
   MAX-ACCESS  read-write
   STATUS      current
   DESCRIPTION
      "Path: virtualEthernet.editConf.pppoEClient.ppp.sessionName"
   ::= {er1645v2VEthPppOEEntry 251985920}

er1645v2VEthPppOEPppSessionSecret OBJECT-TYPE
   SYNTAX      DisplayString
   MAX-ACCESS  read-write
   STATUS      current
   DESCRIPTION
      "Path: virtualEthernet.editConf.pppoEClient.ppp.sessionSecret"
   ::= {er1645v2VEthPppOEEntry 252051456}

er1645v2VEthPppOEPppEncModeSessionSecret OBJECT-TYPE
   SYNTAX      INTEGER
               {
               none (1),
               encrypt (2),
               encType1 (3),
               invalid (128)
               }
   MAX-ACCESS  read-write
   STATUS      current
   DESCRIPTION
      "Path: virtualEthernet.editConf.pppoEClient.ppp.encModeSessionSecret

       Possibilities:
               none   (1)
               encrypt   (2)
               encType1   (3)
               invalid   (128)"
   ::= {er1645v2VEthPppOEEntry 252182528}

er1645v2VEthPppOEPppEncSessionSecret OBJECT-TYPE
   SYNTAX      DisplayString
   MAX-ACCESS  read-write
   STATUS      current
   DESCRIPTION
      "Path: virtualEthernet.editConf.pppoEClient.ppp.encSessionSecret"
   ::= {er1645v2VEthPppOEEntry 252248064}

er1645v2VEthPppOEPppServiceName OBJECT-TYPE
   SYNTAX      DisplayString
   MAX-ACCESS  read-write
   STATUS      current
   DESCRIPTION
      "Path: virtualEthernet.editConf.pppoEClient.ppp.serviceName"
   ::= {er1645v2VEthPppOEEntry 252116992}

er1645v2VEthPppOEIpH OBJECT-TYPE
   SYNTAX      SEQUENCE OF Er1645v2VEthPppOEIpHEntry
   MAX-ACCESS  not-accessible
   STATUS      current
   DESCRIPTION
      ""
   ::= {er1645v2VEthPppOE 51314688}

er1645v2VEthPppOEIpHEntry OBJECT-TYPE
   SYNTAX      Er1645v2VEthPppOEIpHEntry
   MAX-ACCESS  not-accessible
   STATUS      current
   DESCRIPTION
      ""
   INDEX      { er1645v2VEthPppOEIpHGlobalIx,
                er1645v2VEthPppOETableIx,
                er1645v2VEthPppOEIpHTableIx }
   ::= {er1645v2VEthPppOEIpH 1}

Er1645v2VEthPppOEIpHEntry ::=
   SEQUENCE
      {
      er1645v2VEthPppOEIpHActions
         VariableLengthTableActions,
      er1645v2VEthPppOEIpHGlobalIx
         GlobalIndex,
      er1645v2VEthPppOEIpHTableIx
         TableIndex,
      er1645v2VEthPppOEIpHAddress
         IpAddress,
      er1645v2VEthPppOEIpHDhcpRelayOptionSubscriberId
         DisplayString
      }

er1645v2VEthPppOEIpHActions OBJECT-TYPE
   SYNTAX      VariableLengthTableActions
   MAX-ACCESS  read-write
   STATUS      current
   DESCRIPTION
      "By way of this field, some manipulations
       on this table may be performed."
   ::= {er1645v2VEthPppOEIpHEntry 2}

er1645v2VEthPppOEIpHGlobalIx OBJECT-TYPE
   SYNTAX      GlobalIndex
   MAX-ACCESS  not-accessible
   STATUS      current
   DESCRIPTION
      "The value of the tlsCntTreeGlobalIndex of the MANAGED OBJECT."
   ::= {er1645v2VEthPppOEIpHEntry 10}

er1645v2VEthPppOEIpHTableIx OBJECT-TYPE
   SYNTAX      TableIndex
   MAX-ACCESS  not-accessible
   STATUS      current
   DESCRIPTION
      ""
   ::= {er1645v2VEthPppOEIpHEntry 11}

er1645v2VEthPppOEIpHAddress OBJECT-TYPE
   SYNTAX      IpAddress
   MAX-ACCESS  read-write
   STATUS      current
   DESCRIPTION
      "Path: virtualEthernet.editConf.pppoEClient.ip.helpers.address"
   ::= {er1645v2VEthPppOEIpHEntry 16777216}

er1645v2VEthPppOEIpHDhcpRelayOptionSubscriberId OBJECT-TYPE
   SYNTAX      DisplayString
   MAX-ACCESS  read-write
   STATUS      current
   DESCRIPTION
      "Path: virtualEthernet.editConf.pppoEClient.ip.helpers.dhcpRelayOption.subscriberId"
   ::= {er1645v2VEthPppOEIpHEntry 33947648}

er1645v2VEthPppOEIpV6Addresses OBJECT-TYPE
   SYNTAX      SEQUENCE OF Er1645v2VEthPppOEIpV6AddressesEntry
   MAX-ACCESS  not-accessible
   STATUS      current
   DESCRIPTION
      ""
   ::= {er1645v2VEthPppOE 704839680}

er1645v2VEthPppOEIpV6AddressesEntry OBJECT-TYPE
   SYNTAX      Er1645v2VEthPppOEIpV6AddressesEntry
   MAX-ACCESS  not-accessible
   STATUS      current
   DESCRIPTION
      ""
   INDEX      { er1645v2VEthPppOEIpV6AddressesGlobalIx,
                er1645v2VEthPppOETableIx,
                er1645v2VEthPppOEIpV6AddressesTableIx }
   ::= {er1645v2VEthPppOEIpV6Addresses 1}

Er1645v2VEthPppOEIpV6AddressesEntry ::=
   SEQUENCE
      {
      er1645v2VEthPppOEIpV6AddressesActions
         VariableLengthTableActions,
      er1645v2VEthPppOEIpV6AddressesGlobalIx
         GlobalIndex,
      er1645v2VEthPppOEIpV6AddressesTableIx
         TableIndex,
      er1645v2VEthPppOEIpV6AddressesType
         INTEGER,
      er1645v2VEthPppOEIpV6AddressesAddress
         Ipv6Address,
      er1645v2VEthPppOEIpV6AddressesPrefixLength
         Integer32,
      er1645v2VEthPppOEIpV6AddressesGeneralPrefix
         DisplayString,
      er1645v2VEthPppOEIpV6AddressesRaSend
         INTEGER,
      er1645v2VEthPppOEIpV6AddressesRaOnLinkFlag
         INTEGER,
      er1645v2VEthPppOEIpV6AddressesRaAutoFlag
         INTEGER,
      er1645v2VEthPppOEIpV6AddressesRaValidLifeTime
         TimeTicks,
      er1645v2VEthPppOEIpV6AddressesRaValidLTMode
         INTEGER,
      er1645v2VEthPppOEIpV6AddressesRaPrefLifeTime
         TimeTicks,
      er1645v2VEthPppOEIpV6AddressesRaPrefLTMode
         INTEGER
      }

er1645v2VEthPppOEIpV6AddressesActions OBJECT-TYPE
   SYNTAX      VariableLengthTableActions
   MAX-ACCESS  read-write
   STATUS      current
   DESCRIPTION
      "By way of this field, some manipulations
       on this table may be performed."
   ::= {er1645v2VEthPppOEIpV6AddressesEntry 2}

er1645v2VEthPppOEIpV6AddressesGlobalIx OBJECT-TYPE
   SYNTAX      GlobalIndex
   MAX-ACCESS  not-accessible
   STATUS      current
   DESCRIPTION
      "The value of the tlsCntTreeGlobalIndex of the MANAGED OBJECT."
   ::= {er1645v2VEthPppOEIpV6AddressesEntry 10}

er1645v2VEthPppOEIpV6AddressesTableIx OBJECT-TYPE
   SYNTAX      TableIndex
   MAX-ACCESS  not-accessible
   STATUS      current
   DESCRIPTION
      ""
   ::= {er1645v2VEthPppOEIpV6AddressesEntry 11}

er1645v2VEthPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: virtualEthernet.editConf.pppoEClient.ipV6.addresses.type

       Possibilities:
               unicast   (0)
               eui64   (1)
               anycast   (2)
               linkLocal   (3)
               generalPrefix   (4)"
   ::= {er1645v2VEthPppOEIpV6AddressesEntry 50331648}

er1645v2VEthPppOEIpV6AddressesAddress OBJECT-TYPE
   SYNTAX      Ipv6Address
   MAX-ACCESS  read-write
   STATUS      current
   DESCRIPTION
      "Path: virtualEthernet.editConf.pppoEClient.ipV6.addresses.address

       ipv6 address"
   ::= {er1645v2VEthPppOEIpV6AddressesEntry 16777216}

er1645v2VEthPppOEIpV6AddressesPrefixLength OBJECT-TYPE
   SYNTAX      Integer32
   MAX-ACCESS  read-write
   STATUS      current
   DESCRIPTION
      "Path: virtualEthernet.editConf.pppoEClient.ipV6.addresses.prefixLength"
   ::= {er1645v2VEthPppOEIpV6AddressesEntry 33554432}

er1645v2VEthPppOEIpV6AddressesGeneralPrefix OBJECT-TYPE
   SYNTAX      DisplayString
   MAX-ACCESS  read-write
   STATUS      current
   DESCRIPTION
      "Path: virtualEthernet.editConf.pppoEClient.ipV6.addresses.generalPrefix"
   ::= {er1645v2VEthPppOEIpV6AddressesEntry 83886080}

er1645v2VEthPppOEIpV6AddressesRaSend OBJECT-TYPE
   SYNTAX      INTEGER
               {
               disabled (0),
               enabled (1)
               }
   MAX-ACCESS  read-write
   STATUS      current
   DESCRIPTION
      "Path: virtualEthernet.editConf.pppoEClient.ipV6.addresses.ra.send

       Possibilities:
               disabled   (0)
               enabled   (1)"
   ::= {er1645v2VEthPppOEIpV6AddressesEntry 67174400}

er1645v2VEthPppOEIpV6AddressesRaOnLinkFlag OBJECT-TYPE
   SYNTAX      INTEGER
               {
               disabled (0),
               enabled (1)
               }
   MAX-ACCESS  read-write
   STATUS      current
   DESCRIPTION
      "Path: virtualEthernet.editConf.pppoEClient.ipV6.addresses.ra.onLinkFlag

       Possibilities:
               disabled   (0)
               enabled   (1)"
   ::= {er1645v2VEthPppOEIpV6AddressesEntry 67371008}

er1645v2VEthPppOEIpV6AddressesRaAutoFlag OBJECT-TYPE
   SYNTAX      INTEGER
               {
               disabled (0),
               enabled (1)
               }
   MAX-ACCESS  read-write
   STATUS      current
   DESCRIPTION
      "Path: virtualEthernet.editConf.pppoEClient.ipV6.addresses.ra.autonomousFlag

       Possibilities:
               disabled   (0)
               enabled   (1)"
   ::= {er1645v2VEthPppOEIpV6AddressesEntry 67567616}

er1645v2VEthPppOEIpV6AddressesRaValidLifeTime OBJECT-TYPE
   SYNTAX      TimeTicks
   MAX-ACCESS  read-write
   STATUS      current
   DESCRIPTION
      "Path: virtualEthernet.editConf.pppoEClient.ipV6.addresses.ra.validLifeTime

       Time in centi-second."
   ::= {er1645v2VEthPppOEIpV6AddressesEntry 67239936}

er1645v2VEthPppOEIpV6AddressesRaValidLTMode OBJECT-TYPE
   SYNTAX      INTEGER
               {
               fixed (0),
               infinite (2)
               }
   MAX-ACCESS  read-write
   STATUS      current
   DESCRIPTION
      "Path: virtualEthernet.editConf.pppoEClient.ipV6.addresses.ra.validLifeTimeMode

       Possibilities:
               fixed   (0)
               infinite   (2)"
   ::= {er1645v2VEthPppOEIpV6AddressesEntry 67305472}

er1645v2VEthPppOEIpV6AddressesRaPrefLifeTime OBJECT-TYPE
   SYNTAX      TimeTicks
   MAX-ACCESS  read-write
   STATUS      current
   DESCRIPTION
      "Path: virtualEthernet.editConf.pppoEClient.ipV6.addresses.ra.prefLifeTime

       Time in centi-second."
   ::= {er1645v2VEthPppOEIpV6AddressesEntry 67436544}

er1645v2VEthPppOEIpV6AddressesRaPrefLTMode OBJECT-TYPE
   SYNTAX      INTEGER
               {
               fixed (0),
               infinite (2)
               }
   MAX-ACCESS  read-write
   STATUS      current
   DESCRIPTION
      "Path: virtualEthernet.editConf.pppoEClient.ipV6.addresses.ra.prefLifeTimeMode

       Possibilities:
               fixed   (0)
               infinite   (2)"
   ::= {er1645v2VEthPppOEIpV6AddressesEntry 67502080}

er1645v2VEthPppOEIpV6RaDnsOptionsRdnssServers OBJECT-TYPE
   SYNTAX      SEQUENCE OF Er1645v2VEthPppOEIpV6RaDnsOptionsRdnssServersEntry
   MAX-ACCESS  not-accessible
   STATUS      current
   DESCRIPTION
      ""
   ::= {er1645v2VEthPppOE 705039144}

er1645v2VEthPppOEIpV6RaDnsOptionsRdnssServersEntry OBJECT-TYPE
   SYNTAX      Er1645v2VEthPppOEIpV6RaDnsOptionsRdnssServersEntry
   MAX-ACCESS  not-accessible
   STATUS      current
   DESCRIPTION
      ""
   INDEX      { er1645v2VEthPppOEIpV6RaDnsOptionsRdnssServersGlobalIx,
                er1645v2VEthPppOETableIx,
                er1645v2VEthPppOEIpV6RaDnsOptionsRdnssServersTableIx }
   ::= {er1645v2VEthPppOEIpV6RaDnsOptionsRdnssServers 1}

Er1645v2VEthPppOEIpV6RaDnsOptionsRdnssServersEntry ::=
   SEQUENCE
      {
      er1645v2VEthPppOEIpV6RaDnsOptionsRdnssServersActions
         VariableLengthTableActions,
      er1645v2VEthPppOEIpV6RaDnsOptionsRdnssServersGlobalIx
         GlobalIndex,
      er1645v2VEthPppOEIpV6RaDnsOptionsRdnssServersTableIx
         TableIndex,
      er1645v2VEthPppOEIpV6RaDnsOptionsRdnssServersAddress
         Ipv6Address
      }

er1645v2VEthPppOEIpV6RaDnsOptionsRdnssServersActions OBJECT-TYPE
   SYNTAX      VariableLengthTableActions
   MAX-ACCESS  read-write
   STATUS      current
   DESCRIPTION
      "By way of this field, some manipulations
       on this table may be performed."
   ::= {er1645v2VEthPppOEIpV6RaDnsOptionsRdnssServersEntry 2}

er1645v2VEthPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2VEthPppOEIpV6RaDnsOptionsRdnssServersEntry 10}

er1645v2VEthPppOEIpV6RaDnsOptionsRdnssServersTableIx OBJECT-TYPE
   SYNTAX      TableIndex
   MAX-ACCESS  not-accessible
   STATUS      current
   DESCRIPTION
      ""
   ::= {er1645v2VEthPppOEIpV6RaDnsOptionsRdnssServersEntry 11}

er1645v2VEthPppOEIpV6RaDnsOptionsRdnssServersAddress OBJECT-TYPE
   SYNTAX      Ipv6Address
   MAX-ACCESS  read-write
   STATUS      current
   DESCRIPTION
      "Path: virtualEthernet.editConf.pppoEClient.ipV6.ra.dnsOptions.rdnss.servers.address

       ipv6 address"
   ::= {er1645v2VEthPppOEIpV6RaDnsOptionsRdnssServersEntry 16777216}

er1645v2VEthPppOEIpV6RaDnsOptionsDnsslDomains OBJECT-TYPE
   SYNTAX      SEQUENCE OF Er1645v2VEthPppOEIpV6RaDnsOptionsDnsslDomainsEntry
   MAX-ACCESS  not-accessible
   STATUS      current
   DESCRIPTION
      ""
   ::= {er1645v2VEthPppOE 705039176}

er1645v2VEthPppOEIpV6RaDnsOptionsDnsslDomainsEntry OBJECT-TYPE
   SYNTAX      Er1645v2VEthPppOEIpV6RaDnsOptionsDnsslDomainsEntry
   MAX-ACCESS  not-accessible
   STATUS      current
   DESCRIPTION
      ""
   INDEX      { er1645v2VEthPppOEIpV6RaDnsOptionsDnsslDomainsGlobalIx,
                er1645v2VEthPppOETableIx,
                er1645v2VEthPppOEIpV6RaDnsOptionsDnsslDomainsTableIx }
   ::= {er1645v2VEthPppOEIpV6RaDnsOptionsDnsslDomains 1}

Er1645v2VEthPppOEIpV6RaDnsOptionsDnsslDomainsEntry ::=
   SEQUENCE
      {
      er1645v2VEthPppOEIpV6RaDnsOptionsDnsslDomainsActions
         VariableLengthTableActions,
      er1645v2VEthPppOEIpV6RaDnsOptionsDnsslDomainsGlobalIx
         GlobalIndex,
      er1645v2VEthPppOEIpV6RaDnsOptionsDnsslDomainsTableIx
         TableIndex,
      er1645v2VEthPppOEIpV6RaDnsOptionsDnsslDomainsName
         DisplayString
      }

er1645v2VEthPppOEIpV6RaDnsOptionsDnsslDomainsActions OBJECT-TYPE
   SYNTAX      VariableLengthTableActions
   MAX-ACCESS  read-write
   STATUS      current
   DESCRIPTION
      "By way of this field, some manipulations
       on this table may be performed."
   ::= {er1645v2VEthPppOEIpV6RaDnsOptionsDnsslDomainsEntry 2}

er1645v2VEthPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2VEthPppOEIpV6RaDnsOptionsDnsslDomainsEntry 10}

er1645v2VEthPppOEIpV6RaDnsOptionsDnsslDomainsTableIx OBJECT-TYPE
   SYNTAX      TableIndex
   MAX-ACCESS  not-accessible
   STATUS      current
   DESCRIPTION
      ""
   ::= {er1645v2VEthPppOEIpV6RaDnsOptionsDnsslDomainsEntry 11}

er1645v2VEthPppOEIpV6RaDnsOptionsDnsslDomainsName OBJECT-TYPE
   SYNTAX      DisplayString
   MAX-ACCESS  read-write
   STATUS      current
   DESCRIPTION
      "Path: virtualEthernet.editConf.pppoEClient.ipV6.ra.dnsOptions.dnssl.domains.name"
   ::= {er1645v2VEthPppOEIpV6RaDnsOptionsDnsslDomainsEntry 16777216}

er1645v2VEthPppOEIpV6DhcpClientUserClassOpt OBJECT-TYPE
   SYNTAX      SEQUENCE OF Er1645v2VEthPppOEIpV6DhcpClientUserClassOptEntry
   MAX-ACCESS  not-accessible
   STATUS      current
   DESCRIPTION
      ""
   ::= {er1645v2VEthPppOE 705312768}

er1645v2VEthPppOEIpV6DhcpClientUserClassOptEntry OBJECT-TYPE
   SYNTAX      Er1645v2VEthPppOEIpV6DhcpClientUserClassOptEntry
   MAX-ACCESS  not-accessible
   STATUS      current
   DESCRIPTION
      ""
   INDEX      { er1645v2VEthPppOEIpV6DhcpClientUserClassOptGlobalIx,
                er1645v2VEthPppOETableIx,
                er1645v2VEthPppOEIpV6DhcpClientUserClassOptTableIx }
   ::= {er1645v2VEthPppOEIpV6DhcpClientUserClassOpt 1}

Er1645v2VEthPppOEIpV6DhcpClientUserClassOptEntry ::=
   SEQUENCE
      {
      er1645v2VEthPppOEIpV6DhcpClientUserClassOptActions
         VariableLengthTableActions,
      er1645v2VEthPppOEIpV6DhcpClientUserClassOptGlobalIx
         GlobalIndex,
      er1645v2VEthPppOEIpV6DhcpClientUserClassOptTableIx
         TableIndex,
      er1645v2VEthPppOEIpV6DhcpClientUserClassOptValueAscii
         DisplayString,
      er1645v2VEthPppOEIpV6DhcpClientUserClassOptValueDecimal
         Integer32,
      er1645v2VEthPppOEIpV6DhcpClientUserClassOptValueHexData
         OCTET STRING
      }

er1645v2VEthPppOEIpV6DhcpClientUserClassOptActions OBJECT-TYPE
   SYNTAX      VariableLengthTableActions
   MAX-ACCESS  read-write
   STATUS      current
   DESCRIPTION
      "By way of this field, some manipulations
       on this table may be performed."
   ::= {er1645v2VEthPppOEIpV6DhcpClientUserClassOptEntry 2}

er1645v2VEthPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2VEthPppOEIpV6DhcpClientUserClassOptEntry 10}

er1645v2VEthPppOEIpV6DhcpClientUserClassOptTableIx OBJECT-TYPE
   SYNTAX      TableIndex
   MAX-ACCESS  not-accessible
   STATUS      current
   DESCRIPTION
      ""
   ::= {er1645v2VEthPppOEIpV6DhcpClientUserClassOptEntry 11}

er1645v2VEthPppOEIpV6DhcpClientUserClassOptValueAscii OBJECT-TYPE
   SYNTAX      DisplayString
   MAX-ACCESS  read-write
   STATUS      current
   DESCRIPTION
      "Path: virtualEthernet.editConf.pppoEClient.ipV6.dhcp.client.userClassOpt.value.ascii"
   ::= {er1645v2VEthPppOEIpV6DhcpClientUserClassOptEntry 16842752}

er1645v2VEthPppOEIpV6DhcpClientUserClassOptValueDecimal OBJECT-TYPE
   SYNTAX      Integer32
   MAX-ACCESS  read-write
   STATUS      current
   DESCRIPTION
      "Path: virtualEthernet.editConf.pppoEClient.ipV6.dhcp.client.userClassOpt.value.decimal"
   ::= {er1645v2VEthPppOEIpV6DhcpClientUserClassOptEntry 16908288}

er1645v2VEthPppOEIpV6DhcpClientUserClassOptValueHexData OBJECT-TYPE
   SYNTAX      OCTET STRING
   MAX-ACCESS  read-write
   STATUS      current
   DESCRIPTION
      "Path: virtualEthernet.editConf.pppoEClient.ipV6.dhcp.client.userClassOpt.value.hexData"
   ::= {er1645v2VEthPppOEIpV6DhcpClientUserClassOptEntry 16973824}

er1645v2VEthPppOEIpV6DhcpClientVendorCl OBJECT-TYPE
   SYNTAX      SEQUENCE OF Er1645v2VEthPppOEIpV6DhcpClientVendorClEntry
   MAX-ACCESS  not-accessible
   STATUS      current
   DESCRIPTION
      ""
   ::= {er1645v2VEthPppOE 705313792}

er1645v2VEthPppOEIpV6DhcpClientVendorClEntry OBJECT-TYPE
   SYNTAX      Er1645v2VEthPppOEIpV6DhcpClientVendorClEntry
   MAX-ACCESS  not-accessible
   STATUS      current
   DESCRIPTION
      ""
   INDEX      { er1645v2VEthPppOEIpV6DhcpClientVendorClGlobalIx,
                er1645v2VEthPppOETableIx,
                er1645v2VEthPppOEIpV6DhcpClientVendorClTableIx }
   ::= {er1645v2VEthPppOEIpV6DhcpClientVendorCl 1}

Er1645v2VEthPppOEIpV6DhcpClientVendorClEntry ::=
   SEQUENCE
      {
      er1645v2VEthPppOEIpV6DhcpClientVendorClActions
         VariableLengthTableActions,
      er1645v2VEthPppOEIpV6DhcpClientVendorClGlobalIx
         GlobalIndex,
      er1645v2VEthPppOEIpV6DhcpClientVendorClTableIx
         TableIndex,
      er1645v2VEthPppOEIpV6DhcpClientVendorClValueAscii
         DisplayString,
      er1645v2VEthPppOEIpV6DhcpClientVendorClValueDecimal
         Integer32,
      er1645v2VEthPppOEIpV6DhcpClientVendorClValueHexData
         OCTET STRING
      }

er1645v2VEthPppOEIpV6DhcpClientVendorClActions OBJECT-TYPE
   SYNTAX      VariableLengthTableActions
   MAX-ACCESS  read-write
   STATUS      current
   DESCRIPTION
      "By way of this field, some manipulations
       on this table may be performed."
   ::= {er1645v2VEthPppOEIpV6DhcpClientVendorClEntry 2}

er1645v2VEthPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2VEthPppOEIpV6DhcpClientVendorClEntry 10}

er1645v2VEthPppOEIpV6DhcpClientVendorClTableIx OBJECT-TYPE
   SYNTAX      TableIndex
   MAX-ACCESS  not-accessible
   STATUS      current
   DESCRIPTION
      ""
   ::= {er1645v2VEthPppOEIpV6DhcpClientVendorClEntry 11}

er1645v2VEthPppOEIpV6DhcpClientVendorClValueAscii OBJECT-TYPE
   SYNTAX      DisplayString
   MAX-ACCESS  read-write
   STATUS      current
   DESCRIPTION
      "Path: virtualEthernet.editConf.pppoEClient.ipV6.dhcp.client.vendorClassOpt.value.ascii"
   ::= {er1645v2VEthPppOEIpV6DhcpClientVendorClEntry 16842752}

er1645v2VEthPppOEIpV6DhcpClientVendorClValueDecimal OBJECT-TYPE
   SYNTAX      Integer32
   MAX-ACCESS  read-write
   STATUS      current
   DESCRIPTION
      "Path: virtualEthernet.editConf.pppoEClient.ipV6.dhcp.client.vendorClassOpt.value.decimal"
   ::= {er1645v2VEthPppOEIpV6DhcpClientVendorClEntry 16908288}

er1645v2VEthPppOEIpV6DhcpClientVendorClValueHexData OBJECT-TYPE
   SYNTAX      OCTET STRING
   MAX-ACCESS  read-write
   STATUS      current
   DESCRIPTION
      "Path: virtualEthernet.editConf.pppoEClient.ipV6.dhcp.client.vendorClassOpt.value.hexData"
   ::= {er1645v2VEthPppOEIpV6DhcpClientVendorClEntry 16973824}

er1645v2VEthPppOEIpV6DhcpRelayDestinations OBJECT-TYPE
   SYNTAX      SEQUENCE OF Er1645v2VEthPppOEIpV6DhcpRelayDestinationsEntry
   MAX-ACCESS  not-accessible
   STATUS      current
   DESCRIPTION
      ""
   ::= {er1645v2VEthPppOE 705323072}

er1645v2VEthPppOEIpV6DhcpRelayDestinationsEntry OBJECT-TYPE
   SYNTAX      Er1645v2VEthPppOEIpV6DhcpRelayDestinationsEntry
   MAX-ACCESS  not-accessible
   STATUS      current
   DESCRIPTION
      ""
   INDEX      { er1645v2VEthPppOEIpV6DhcpRelayDestinationsGlobalIx,
                er1645v2VEthPppOETableIx,
                er1645v2VEthPppOEIpV6DhcpRelayDestinationsTableIx }
   ::= {er1645v2VEthPppOEIpV6DhcpRelayDestinations 1}

Er1645v2VEthPppOEIpV6DhcpRelayDestinationsEntry ::=
   SEQUENCE
      {
      er1645v2VEthPppOEIpV6DhcpRelayDestinationsActions
         VariableLengthTableActions,
      er1645v2VEthPppOEIpV6DhcpRelayDestinationsGlobalIx
         GlobalIndex,
      er1645v2VEthPppOEIpV6DhcpRelayDestinationsTableIx
         TableIndex,
      er1645v2VEthPppOEIpV6DhcpRelayDestinationsAddress
         Ipv6Address,
      er1645v2VEthPppOEIpV6DhcpRelayDestinationsInterface
         DisplayString
      }

er1645v2VEthPppOEIpV6DhcpRelayDestinationsActions OBJECT-TYPE
   SYNTAX      VariableLengthTableActions
   MAX-ACCESS  read-write
   STATUS      current
   DESCRIPTION
      "By way of this field, some manipulations
       on this table may be performed."
   ::= {er1645v2VEthPppOEIpV6DhcpRelayDestinationsEntry 2}

er1645v2VEthPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2VEthPppOEIpV6DhcpRelayDestinationsEntry 10}

er1645v2VEthPppOEIpV6DhcpRelayDestinationsTableIx OBJECT-TYPE
   SYNTAX      TableIndex
   MAX-ACCESS  not-accessible
   STATUS      current
   DESCRIPTION
      ""
   ::= {er1645v2VEthPppOEIpV6DhcpRelayDestinationsEntry 11}

er1645v2VEthPppOEIpV6DhcpRelayDestinationsAddress OBJECT-TYPE
   SYNTAX      Ipv6Address
   MAX-ACCESS  read-write
   STATUS      current
   DESCRIPTION
      "Path: virtualEthernet.editConf.pppoEClient.ipV6.dhcp.relay.destinations.address

       ipv6 address"
   ::= {er1645v2VEthPppOEIpV6DhcpRelayDestinationsEntry 16777216}

er1645v2VEthPppOEIpV6DhcpRelayDestinationsInterface OBJECT-TYPE
   SYNTAX      DisplayString
   MAX-ACCESS  read-write
   STATUS      current
   DESCRIPTION
      "Path: virtualEthernet.editConf.pppoEClient.ipV6.dhcp.relay.destinations.interface"
   ::= {er1645v2VEthPppOEIpV6DhcpRelayDestinationsEntry 33554432}


er1645v2VEthDot1x OBJECT IDENTIFIER ::= {er1645v2VEth 191}

er1645v2VEthDot1xSSCTable OBJECT-TYPE
   SYNTAX      SEQUENCE OF Er1645v2VEthDot1xEntry
   MAX-ACCESS  not-accessible
   STATUS      current
   DESCRIPTION
      "ppp server name on interface"
   ::= {er1645v2VEthDot1x 1}

er1645v2VEthDot1xEntry OBJECT-TYPE
   SYNTAX      Er1645v2VEthDot1xEntry
   MAX-ACCESS  not-accessible
   STATUS      current
   DESCRIPTION
      ""
   INDEX      { er1645v2VEthDot1xGlobalIx }
   ::= {er1645v2VEthDot1xSSCTable 1}

Er1645v2VEthDot1xEntry ::=
   SEQUENCE
      {
      er1645v2VEthDot1xGlobalIx
         GlobalIndex,
      er1645v2VEthDot1xMode
         INTEGER,
      er1645v2VEthDot1xMaxHosts
         Integer32,
      er1645v2VEthDot1xReAuthentication
         INTEGER,
      er1645v2VEthDot1xReAuthPeriod
         TimeTicks,
      er1645v2VEthDot1xQuietPeriod
         TimeTicks,
      er1645v2VEthDot1xSupplTimeout
         TimeTicks,
      er1645v2VEthDot1xServerTimeout
         TimeTicks,
      er1645v2VEthDot1xMaxReqCount
         Integer32
      }

er1645v2VEthDot1xGlobalIx OBJECT-TYPE
   SYNTAX      GlobalIndex
   MAX-ACCESS  not-accessible
   STATUS      current
   DESCRIPTION
      "The value of the tlsCntTreeGlobalIndex of the MANAGED OBJECT."
   ::= {er1645v2VEthDot1xEntry 10}

er1645v2VEthDot1xMode OBJECT-TYPE
   SYNTAX      INTEGER
               {
               inactive (0),
               auto (1)
               }
   MAX-ACCESS  read-write
   STATUS      current
   DESCRIPTION
      "Path: virtualEthernet.editConf.dot1x.mode

       Possibilities:
               inactive   (0)
               auto   (1)"
   ::= {er1645v2VEthDot1xEntry 16777216}

er1645v2VEthDot1xMaxHosts OBJECT-TYPE
   SYNTAX      Integer32
   MAX-ACCESS  read-write
   STATUS      current
   DESCRIPTION
      "Path: virtualEthernet.editConf.dot1x.maxHosts"
   ::= {er1645v2VEthDot1xEntry 33554432}

er1645v2VEthDot1xReAuthentication OBJECT-TYPE
   SYNTAX      INTEGER
               {
               disabled (0),
               enabled (1)
               }
   MAX-ACCESS  read-write
   STATUS      current
   DESCRIPTION
      "Path: virtualEthernet.editConf.dot1x.reAuthentication

       Possibilities:
               disabled   (0)
               enabled   (1)"
   ::= {er1645v2VEthDot1xEntry 50331648}

er1645v2VEthDot1xReAuthPeriod OBJECT-TYPE
   SYNTAX      TimeTicks
   MAX-ACCESS  read-write
   STATUS      current
   DESCRIPTION
      "Path: virtualEthernet.editConf.dot1x.reAuthPeriod

       Time in centi-second."
   ::= {er1645v2VEthDot1xEntry 67108864}

er1645v2VEthDot1xQuietPeriod OBJECT-TYPE
   SYNTAX      TimeTicks
   MAX-ACCESS  read-write
   STATUS      current
   DESCRIPTION
      "Path: virtualEthernet.editConf.dot1x.quietPeriod

       Time in centi-second."
   ::= {er1645v2VEthDot1xEntry 83886080}

er1645v2VEthDot1xSupplTimeout OBJECT-TYPE
   SYNTAX      TimeTicks
   MAX-ACCESS  read-write
   STATUS      current
   DESCRIPTION
      "Path: virtualEthernet.editConf.dot1x.supplTimeout

       Time in centi-second."
   ::= {er1645v2VEthDot1xEntry 100663296}

er1645v2VEthDot1xServerTimeout OBJECT-TYPE
   SYNTAX      TimeTicks
   MAX-ACCESS  read-write
   STATUS      current
   DESCRIPTION
      "Path: virtualEthernet.editConf.dot1x.serverTimeout

       Time in centi-second."
   ::= {er1645v2VEthDot1xEntry 117440512}

er1645v2VEthDot1xMaxReqCount OBJECT-TYPE
   SYNTAX      Integer32
   MAX-ACCESS  read-write
   STATUS      current
   DESCRIPTION
      "Path: virtualEthernet.editConf.dot1x.maxReqCount"
   ::= {er1645v2VEthDot1xEntry 134217728}


er1645v2VEthMode OBJECT IDENTIFIER ::= {er1645v2VEth 29}

er1645v2VEthModeTable OBJECT-TYPE
   SYNTAX      SEQUENCE OF Er1645v2VEthModeEntry
   MAX-ACCESS  not-accessible
   STATUS      current
   DESCRIPTION
      "routing and/or bridging or ipV6 selection"
   ::= {er1645v2VEthMode 1}

er1645v2VEthModeEntry OBJECT-TYPE
   SYNTAX      Er1645v2VEthModeEntry
   MAX-ACCESS  not-accessible
   STATUS      current
   DESCRIPTION
      ""
   INDEX      { er1645v2VEthModeGlobalIx }
   ::= {er1645v2VEthModeTable 1}

Er1645v2VEthModeEntry ::=
   SEQUENCE
      {
      er1645v2VEthModeGlobalIx
         GlobalIndex,
      er1645v2VEthModeValue
         INTEGER
      }

er1645v2VEthModeGlobalIx OBJECT-TYPE
   SYNTAX      GlobalIndex
   MAX-ACCESS  not-accessible
   STATUS      current
   DESCRIPTION
      "The value of the tlsCntTreeGlobalIndex of the MANAGED OBJECT."
   ::= {er1645v2VEthModeEntry 10}

er1645v2VEthModeValue OBJECT-TYPE
   SYNTAX      INTEGER
               {
               bridging (0),
               routing (1),
               routingAndBridging (2),
               ipV6 (3),
               ipV6ipV4 (4)
               }
   MAX-ACCESS  read-write
   STATUS      current
   DESCRIPTION
      "Path: virtualEthernet.editConf.mode

       Possibilities:
               bridging   (0)
               routing   (1)
               routingAndBridging   (2)
               ipV6   (3)
               ipV6/ipV4   (4)"
   ::= {er1645v2VEthModeEntry 2147483648}


er1645v2VEthIpV6 OBJECT IDENTIFIER ::= {er1645v2VEth 15}

er1645v2VEthIpV6SSCTable OBJECT-TYPE
   SYNTAX      SEQUENCE OF Er1645v2VEthIpV6Entry
   MAX-ACCESS  not-accessible
   STATUS      current
   DESCRIPTION
      "IPv6 interface config parameters"
   ::= {er1645v2VEthIpV6 1}

er1645v2VEthIpV6Entry OBJECT-TYPE
   SYNTAX      Er1645v2VEthIpV6Entry
   MAX-ACCESS  not-accessible
   STATUS      current
   DESCRIPTION
      ""
   INDEX      { er1645v2VEthIpV6GlobalIx }
   ::= {er1645v2VEthIpV6SSCTable 1}

Er1645v2VEthIpV6Entry ::=
   SEQUENCE
      {
      er1645v2VEthIpV6GlobalIx
         GlobalIndex,
      er1645v2VEthIpV6VrfRouter
         DisplayString,
      er1645v2VEthIpV6AddrAutoConfigNrDupAddrDetects
         Integer32,
      er1645v2VEthIpV6AddrAutoConfigAcceptRa
         INTEGER,
      er1645v2VEthIpV6AddrAutoConfigAcceptRaRdnss
         INTEGER,
      er1645v2VEthIpV6AddrAutoConfigAcceptRaDnssl
         INTEGER,
      er1645v2VEthIpV6DefaultRoute
         INTEGER,
      er1645v2VEthIpV6RaSend
         INTEGER,
      er1645v2VEthIpV6RaMinInterval
         TimeTicks,
      er1645v2VEthIpV6RaMaxInterval
         TimeTicks,
      er1645v2VEthIpV6RaManagedFlag
         INTEGER,
      er1645v2VEthIpV6RaOtherConfFlag
         INTEGER,
      er1645v2VEthIpV6RaLinkMtu
         Integer32,
      er1645v2VEthIpV6RaReachableTime
         TimeTicks,
      er1645v2VEthIpV6RaRetransmitTime
         TimeTicks,
      er1645v2VEthIpV6RaHopLimit
         Integer32,
      er1645v2VEthIpV6RaDefaultLifeTime
         TimeTicks,
      er1645v2VEthIpV6RaDnsOptionsRdnssLifeTime
         TimeTicks,
      er1645v2VEthIpV6RaDnsOptionsRdnssImportServers
         INTEGER,
      er1645v2VEthIpV6RaDnsOptionsDnsslLifeTime
         TimeTicks,
      er1645v2VEthIpV6RaDnsOptionsDnsslImportDomains
         INTEGER,
      er1645v2VEthIpV6RsSend
         INTEGER,
      er1645v2VEthIpV6RsMaxRandomDelay
         TimeTicks,
      er1645v2VEthIpV6RsInterval
         TimeTicks,
      er1645v2VEthIpV6RsMaxSolicitations
         Integer32,
      er1645v2VEthIpV6TrafficPolicyInbound
         DisplayString,
      er1645v2VEthIpV6TrafficPolicyOutbound
         DisplayString,
      er1645v2VEthIpV6FirewallZone
         DisplayString,
      er1645v2VEthIpV6DhcpClientAddrAC
         INTEGER,
      er1645v2VEthIpV6DhcpClientPrDelMode
         INTEGER,
      er1645v2VEthIpV6DhcpClientPrDelPool
         DisplayString,
      er1645v2VEthIpV6DhcpClientPrDelPdExclOpt
         INTEGER,
      er1645v2VEthIpV6DhcpClientDnsServerPref
         Integer32,
      er1645v2VEthIpV6DhcpClientRapidCommit
         INTEGER,
      er1645v2VEthIpV6DhcpClientTimersSolTimeOut
         TimeTicks,
      er1645v2VEthIpV6DhcpClientTimersSolMaxRt
         TimeTicks,
      er1645v2VEthIpV6DhcpClientTimersInfoRefresh
         TimeTicks,
      er1645v2VEthIpV6DhcpServerMode
         INTEGER,
      er1645v2VEthIpV6DhcpServerPreference
         Integer32,
      er1645v2VEthIpV6DhcpServerPool
         DisplayString,
      er1645v2VEthIpV6DhcpServerRapidCommit
         INTEGER,
      er1645v2VEthIpV6DhcpServerTimersInfoRefresh
         TimeTicks,
      er1645v2VEthIpV6DhcpRelayMode
         INTEGER,
      er1645v2VEthIpV6SendRedirect
         INTEGER,
      er1645v2VEthIpV6LinkMtu
         Integer32,
      er1645v2VEthIpV6InterfaceId
         OCTET STRING,
      er1645v2VEthIpV6MF
         Integer32,
      er1645v2VEthIpV6IcmpMessagesNoRoute
         INTEGER,
      er1645v2VEthIpV6IcmpMessagesBeyondScope
         INTEGER,
      er1645v2VEthIpV6IcmpMessagesAddressUnreachable
         INTEGER,
      er1645v2VEthIpV6IcmpMessagesPortUnreachable
         INTEGER,
      er1645v2VEthIpV6IcmpMessagesPacketTooBig
         INTEGER,
      er1645v2VEthIpV6IcmpMessagesHopLimitExceeded
         INTEGER,
      er1645v2VEthIpV6IcmpMessagesFragTimeExceeded
         INTEGER,
      er1645v2VEthIpV6IcmpMessagesHeaderFieldErr
         INTEGER,
      er1645v2VEthIpV6IcmpMessagesOptionUnrecognized
         INTEGER,
      er1645v2VEthIpV6IcmpMessagesRedirect
         INTEGER
      }

er1645v2VEthIpV6GlobalIx OBJECT-TYPE
   SYNTAX      GlobalIndex
   MAX-ACCESS  not-accessible
   STATUS      current
   DESCRIPTION
      "The value of the tlsCntTreeGlobalIndex of the MANAGED OBJECT."
   ::= {er1645v2VEthIpV6Entry 10}

er1645v2VEthIpV6VrfRouter OBJECT-TYPE
   SYNTAX      DisplayString
   MAX-ACCESS  read-write
   STATUS      current
   DESCRIPTION
      "Path: virtualEthernet.editConf.ipV6.vrfRouter"
   ::= {er1645v2VEthIpV6Entry 16777216}

er1645v2VEthIpV6AddrAutoConfigNrDupAddrDetects OBJECT-TYPE
   SYNTAX      Integer32
   MAX-ACCESS  read-write
   STATUS      current
   DESCRIPTION
      "Path: virtualEthernet.editConf.ipV6.addrAutoConfig.nrDupAddrDetects"
   ::= {er1645v2VEthIpV6Entry 67174400}

er1645v2VEthIpV6AddrAutoConfigAcceptRa OBJECT-TYPE
   SYNTAX      INTEGER
               {
               disabled (0),
               enabled (1)
               }
   MAX-ACCESS  read-write
   STATUS      current
   DESCRIPTION
      "Path: virtualEthernet.editConf.ipV6.addrAutoConfig.acceptRa

       Possibilities:
               disabled   (0)
               enabled   (1)"
   ::= {er1645v2VEthIpV6Entry 67239936}

er1645v2VEthIpV6AddrAutoConfigAcceptRaRdnss OBJECT-TYPE
   SYNTAX      INTEGER
               {
               disabled (0),
               enabled (1)
               }
   MAX-ACCESS  read-write
   STATUS      current
   DESCRIPTION
      "Path: virtualEthernet.editConf.ipV6.addrAutoConfig.acceptRaRdnss

       Possibilities:
               disabled   (0)
               enabled   (1)"
   ::= {er1645v2VEthIpV6Entry 67305472}

er1645v2VEthIpV6AddrAutoConfigAcceptRaDnssl OBJECT-TYPE
   SYNTAX      INTEGER
               {
               disabled (0),
               enabled (1)
               }
   MAX-ACCESS  read-write
   STATUS      current
   DESCRIPTION
      "Path: virtualEthernet.editConf.ipV6.addrAutoConfig.acceptRaDnssl

       Possibilities:
               disabled   (0)
               enabled   (1)"
   ::= {er1645v2VEthIpV6Entry 67371008}

er1645v2VEthIpV6DefaultRoute OBJECT-TYPE
   SYNTAX      INTEGER
               {
               disabled (0),
               enabled (1)
               }
   MAX-ACCESS  read-write
   STATUS      current
   DESCRIPTION
      "Path: virtualEthernet.editConf.ipV6.defaultRoute

       Possibilities:
               disabled   (0)
               enabled   (1)"
   ::= {er1645v2VEthIpV6Entry 83886080}

er1645v2VEthIpV6RaSend OBJECT-TYPE
   SYNTAX      INTEGER
               {
               disabled (0),
               enabled (1)
               }
   MAX-ACCESS  read-write
   STATUS      current
   DESCRIPTION
      "Path: virtualEthernet.editConf.ipV6.ra.send

       Possibilities:
               disabled   (0)
               enabled   (1)"
   ::= {er1645v2VEthIpV6Entry 100728832}

er1645v2VEthIpV6RaMinInterval OBJECT-TYPE
   SYNTAX      TimeTicks
   MAX-ACCESS  read-write
   STATUS      current
   DESCRIPTION
      "Path: virtualEthernet.editConf.ipV6.ra.minInterval

       Time in centi-second."
   ::= {er1645v2VEthIpV6Entry 100794368}

er1645v2VEthIpV6RaMaxInterval OBJECT-TYPE
   SYNTAX      TimeTicks
   MAX-ACCESS  read-write
   STATUS      current
   DESCRIPTION
      "Path: virtualEthernet.editConf.ipV6.ra.maxInterval

       Time in centi-second."
   ::= {er1645v2VEthIpV6Entry 100859904}

er1645v2VEthIpV6RaManagedFlag OBJECT-TYPE
   SYNTAX      INTEGER
               {
               disabled (0),
               enabled (1)
               }
   MAX-ACCESS  read-write
   STATUS      current
   DESCRIPTION
      "Path: virtualEthernet.editConf.ipV6.ra.managedFlag

       Possibilities:
               disabled   (0)
               enabled   (1)"
   ::= {er1645v2VEthIpV6Entry 100925440}

er1645v2VEthIpV6RaOtherConfFlag OBJECT-TYPE
   SYNTAX      INTEGER
               {
               disabled (0),
               enabled (1)
               }
   MAX-ACCESS  read-write
   STATUS      current
   DESCRIPTION
      "Path: virtualEthernet.editConf.ipV6.ra.otherConfFlag

       Possibilities:
               disabled   (0)
               enabled   (1)"
   ::= {er1645v2VEthIpV6Entry 100990976}

er1645v2VEthIpV6RaLinkMtu OBJECT-TYPE
   SYNTAX      Integer32
   MAX-ACCESS  read-write
   STATUS      current
   DESCRIPTION
      "Path: virtualEthernet.editConf.ipV6.ra.linkMtu"
   ::= {er1645v2VEthIpV6Entry 101056512}

er1645v2VEthIpV6RaReachableTime OBJECT-TYPE
   SYNTAX      TimeTicks
   MAX-ACCESS  read-write
   STATUS      current
   DESCRIPTION
      "Path: virtualEthernet.editConf.ipV6.ra.reachableTime

       Time in centi-second."
   ::= {er1645v2VEthIpV6Entry 101122048}

er1645v2VEthIpV6RaRetransmitTime OBJECT-TYPE
   SYNTAX      TimeTicks
   MAX-ACCESS  read-write
   STATUS      current
   DESCRIPTION
      "Path: virtualEthernet.editConf.ipV6.ra.retransmitTime

       Time in centi-second."
   ::= {er1645v2VEthIpV6Entry 101187584}

er1645v2VEthIpV6RaHopLimit OBJECT-TYPE
   SYNTAX      Integer32
   MAX-ACCESS  read-write
   STATUS      current
   DESCRIPTION
      "Path: virtualEthernet.editConf.ipV6.ra.hopLimit"
   ::= {er1645v2VEthIpV6Entry 101253120}

er1645v2VEthIpV6RaDefaultLifeTime OBJECT-TYPE
   SYNTAX      TimeTicks
   MAX-ACCESS  read-write
   STATUS      current
   DESCRIPTION
      "Path: virtualEthernet.editConf.ipV6.ra.defaultLifeTime

       Time in centi-second."
   ::= {er1645v2VEthIpV6Entry 101318656}

er1645v2VEthIpV6RaDnsOptionsRdnssLifeTime OBJECT-TYPE
   SYNTAX      TimeTicks
   MAX-ACCESS  read-write
   STATUS      current
   DESCRIPTION
      "Path: virtualEthernet.editConf.ipV6.ra.dnsOptions.rdnss.lifeTime

       Time in centi-second."
   ::= {er1645v2VEthIpV6Entry 101393408}

er1645v2VEthIpV6RaDnsOptionsRdnssImportServers OBJECT-TYPE
   SYNTAX      INTEGER
               {
               disabled (0),
               enabled (1)
               }
   MAX-ACCESS  read-write
   STATUS      current
   DESCRIPTION
      "Path: virtualEthernet.editConf.ipV6.ra.dnsOptions.rdnss.importServers

       Possibilities:
               disabled   (0)
               enabled   (1)"
   ::= {er1645v2VEthIpV6Entry 101395456}

er1645v2VEthIpV6RaDnsOptionsDnsslLifeTime OBJECT-TYPE
   SYNTAX      TimeTicks
   MAX-ACCESS  read-write
   STATUS      current
   DESCRIPTION
      "Path: virtualEthernet.editConf.ipV6.ra.dnsOptions.dnssl.lifeTime

       Time in centi-second."
   ::= {er1645v2VEthIpV6Entry 101401600}

er1645v2VEthIpV6RaDnsOptionsDnsslImportDomains OBJECT-TYPE
   SYNTAX      INTEGER
               {
               disabled (0),
               enabled (1)
               }
   MAX-ACCESS  read-write
   STATUS      current
   DESCRIPTION
      "Path: virtualEthernet.editConf.ipV6.ra.dnsOptions.dnssl.importDomains

       Possibilities:
               disabled   (0)
               enabled   (1)"
   ::= {er1645v2VEthIpV6Entry 101403648}

er1645v2VEthIpV6RsSend OBJECT-TYPE
   SYNTAX      INTEGER
               {
               disabled (0),
               enabled (1)
               }
   MAX-ACCESS  read-write
   STATUS      current
   DESCRIPTION
      "Path: virtualEthernet.editConf.ipV6.rs.send

       Possibilities:
               disabled   (0)
               enabled   (1)"
   ::= {er1645v2VEthIpV6Entry 335609856}

er1645v2VEthIpV6RsMaxRandomDelay OBJECT-TYPE
   SYNTAX      TimeTicks
   MAX-ACCESS  read-write
   STATUS      current
   DESCRIPTION
      "Path: virtualEthernet.editConf.ipV6.rs.maxRandomDelay

       Time in centi-second."
   ::= {er1645v2VEthIpV6Entry 335675392}

er1645v2VEthIpV6RsInterval OBJECT-TYPE
   SYNTAX      TimeTicks
   MAX-ACCESS  read-write
   STATUS      current
   DESCRIPTION
      "Path: virtualEthernet.editConf.ipV6.rs.interval

       Time in centi-second."
   ::= {er1645v2VEthIpV6Entry 335740928}

er1645v2VEthIpV6RsMaxSolicitations OBJECT-TYPE
   SYNTAX      Integer32
   MAX-ACCESS  read-write
   STATUS      current
   DESCRIPTION
      "Path: virtualEthernet.editConf.ipV6.rs.maxSolicitations"
   ::= {er1645v2VEthIpV6Entry 335806464}

er1645v2VEthIpV6TrafficPolicyInbound OBJECT-TYPE
   SYNTAX      DisplayString
   MAX-ACCESS  read-write
   STATUS      current
   DESCRIPTION
      "Path: virtualEthernet.editConf.ipV6.trafficPolicy.inbound"
   ::= {er1645v2VEthIpV6Entry 184614912}

er1645v2VEthIpV6TrafficPolicyOutbound OBJECT-TYPE
   SYNTAX      DisplayString
   MAX-ACCESS  read-write
   STATUS      current
   DESCRIPTION
      "Path: virtualEthernet.editConf.ipV6.trafficPolicy.outbound"
   ::= {er1645v2VEthIpV6Entry 184680448}

er1645v2VEthIpV6FirewallZone OBJECT-TYPE
   SYNTAX      DisplayString
   MAX-ACCESS  read-write
   STATUS      current
   DESCRIPTION
      "Path: virtualEthernet.editConf.ipV6.firewall.zone"
   ::= {er1645v2VEthIpV6Entry 201392128}

er1645v2VEthIpV6DhcpClientAddrAC OBJECT-TYPE
   SYNTAX      INTEGER
               {
               disabled (0),
               enabled (1)
               }
   MAX-ACCESS  read-write
   STATUS      current
   DESCRIPTION
      "Path: virtualEthernet.editConf.ipV6.dhcp.client.addrAutoConfig

       Possibilities:
               disabled   (0)
               enabled   (1)"
   ::= {er1645v2VEthIpV6Entry 170131456}

er1645v2VEthIpV6DhcpClientPrDelMode OBJECT-TYPE
   SYNTAX      INTEGER
               {
               disabled (0),
               enabled (1)
               }
   MAX-ACCESS  read-write
   STATUS      current
   DESCRIPTION
      "Path: virtualEthernet.editConf.ipV6.dhcp.client.pd.mode

       Possibilities:
               disabled   (0)
               enabled   (1)"
   ::= {er1645v2VEthIpV6Entry 170394624}

er1645v2VEthIpV6DhcpClientPrDelPool OBJECT-TYPE
   SYNTAX      DisplayString
   MAX-ACCESS  read-write
   STATUS      current
   DESCRIPTION
      "Path: virtualEthernet.editConf.ipV6.dhcp.client.pd.pool"
   ::= {er1645v2VEthIpV6Entry 170395648}

er1645v2VEthIpV6DhcpClientPrDelPdExclOpt OBJECT-TYPE
   SYNTAX      INTEGER
               {
               disabled (0),
               enabled (1)
               }
   MAX-ACCESS  read-write
   STATUS      current
   DESCRIPTION
      "Path: virtualEthernet.editConf.ipV6.dhcp.client.pd.pdExclOpt

       Possibilities:
               disabled   (0)
               enabled   (1)"
   ::= {er1645v2VEthIpV6Entry 170396672}

er1645v2VEthIpV6DhcpClientDnsServerPref OBJECT-TYPE
   SYNTAX      Integer32
   MAX-ACCESS  read-write
   STATUS      current
   DESCRIPTION
      "Path: virtualEthernet.editConf.ipV6.dhcp.client.dns.serverPref"
   ::= {er1645v2VEthIpV6Entry 170918912}

er1645v2VEthIpV6DhcpClientRapidCommit OBJECT-TYPE
   SYNTAX      INTEGER
               {
               disabled (0),
               enabled (1)
               }
   MAX-ACCESS  read-write
   STATUS      current
   DESCRIPTION
      "Path: virtualEthernet.editConf.ipV6.dhcp.client.rapidCommit

       Possibilities:
               disabled   (0)
               enabled   (1)"
   ::= {er1645v2VEthIpV6Entry 170655744}

er1645v2VEthIpV6DhcpClientTimersSolTimeOut OBJECT-TYPE
   SYNTAX      TimeTicks
   MAX-ACCESS  read-write
   STATUS      current
   DESCRIPTION
      "Path: virtualEthernet.editConf.ipV6.dhcp.client.timers.solTimeOut

       Time in centi-second."
   ::= {er1645v2VEthIpV6Entry 171181056}

er1645v2VEthIpV6DhcpClientTimersSolMaxRt OBJECT-TYPE
   SYNTAX      TimeTicks
   MAX-ACCESS  read-write
   STATUS      current
   DESCRIPTION
      "Path: virtualEthernet.editConf.ipV6.dhcp.client.timers.solMaxRt

       Time in centi-second."
   ::= {er1645v2VEthIpV6Entry 171182080}

er1645v2VEthIpV6DhcpClientTimersInfoRefresh OBJECT-TYPE
   SYNTAX      TimeTicks
   MAX-ACCESS  read-write
   STATUS      current
   DESCRIPTION
      "Path: virtualEthernet.editConf.ipV6.dhcp.client.timers.infoRefresh

       Time in centi-second."
   ::= {er1645v2VEthIpV6Entry 171183104}

er1645v2VEthIpV6DhcpServerMode OBJECT-TYPE
   SYNTAX      INTEGER
               {
               disabled (0),
               enabled (1)
               }
   MAX-ACCESS  read-write
   STATUS      current
   DESCRIPTION
      "Path: virtualEthernet.editConf.ipV6.dhcp.server.mode

       Possibilities:
               disabled   (0)
               enabled   (1)"
   ::= {er1645v2VEthIpV6Entry 172228608}

er1645v2VEthIpV6DhcpServerPreference OBJECT-TYPE
   SYNTAX      Integer32
   MAX-ACCESS  read-write
   STATUS      current
   DESCRIPTION
      "Path: virtualEthernet.editConf.ipV6.dhcp.server.preference"
   ::= {er1645v2VEthIpV6Entry 172490752}

er1645v2VEthIpV6DhcpServerPool OBJECT-TYPE
   SYNTAX      DisplayString
   MAX-ACCESS  read-write
   STATUS      current
   DESCRIPTION
      "Path: virtualEthernet.editConf.ipV6.dhcp.server.pool"
   ::= {er1645v2VEthIpV6Entry 172752896}

er1645v2VEthIpV6DhcpServerRapidCommit OBJECT-TYPE
   SYNTAX      INTEGER
               {
               disabled (0),
               enabled (1)
               }
   MAX-ACCESS  read-write
   STATUS      current
   DESCRIPTION
      "Path: virtualEthernet.editConf.ipV6.dhcp.server.rapidCommit

       Possibilities:
               disabled   (0)
               enabled   (1)"
   ::= {er1645v2VEthIpV6Entry 173015040}

er1645v2VEthIpV6DhcpServerTimersInfoRefresh OBJECT-TYPE
   SYNTAX      TimeTicks
   MAX-ACCESS  read-write
   STATUS      current
   DESCRIPTION
      "Path: virtualEthernet.editConf.ipV6.dhcp.server.timers.infoRefresh

       Time in centi-second."
   ::= {er1645v2VEthIpV6Entry 173278208}

er1645v2VEthIpV6DhcpRelayMode OBJECT-TYPE
   SYNTAX      INTEGER
               {
               disabled (0),
               enabled (1)
               }
   MAX-ACCESS  read-write
   STATUS      current
   DESCRIPTION
      "Path: virtualEthernet.editConf.ipV6.dhcp.relay.mode

       Possibilities:
               disabled   (0)
               enabled   (1)"
   ::= {er1645v2VEthIpV6Entry 174071808}

er1645v2VEthIpV6SendRedirect OBJECT-TYPE
   SYNTAX      INTEGER
               {
               disabled (0),
               enabled (1)
               }
   MAX-ACCESS  read-write
   STATUS      current
   DESCRIPTION
      "Path: virtualEthernet.editConf.ipV6.sendRedirect

       Possibilities:
               disabled   (0)
               enabled   (1)"
   ::= {er1645v2VEthIpV6Entry 117440512}

er1645v2VEthIpV6LinkMtu OBJECT-TYPE
   SYNTAX      Integer32
   MAX-ACCESS  read-write
   STATUS      current
   DESCRIPTION
      "Path: virtualEthernet.editConf.ipV6.linkMtu"
   ::= {er1645v2VEthIpV6Entry 134217728}

er1645v2VEthIpV6InterfaceId OBJECT-TYPE
   SYNTAX      OCTET STRING
   MAX-ACCESS  read-write
   STATUS      current
   DESCRIPTION
      "Path: virtualEthernet.editConf.ipV6.interfaceId"
   ::= {er1645v2VEthIpV6Entry 150994944}

er1645v2VEthIpV6MF OBJECT-TYPE
   SYNTAX      Integer32
   MAX-ACCESS  read-write
   STATUS      current
   DESCRIPTION
      "Path: virtualEthernet.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2VEthIpV6Entry 285212672}

er1645v2VEthIpV6IcmpMessagesNoRoute OBJECT-TYPE
   SYNTAX      INTEGER
               {
               disabled (0),
               enabled (1)
               }
   MAX-ACCESS  read-write
   STATUS      current
   DESCRIPTION
      "Path: virtualEthernet.editConf.ipV6.icmpMessages.noRoute

       Possibilities:
               disabled   (0)
               enabled   (1)"
   ::= {er1645v2VEthIpV6Entry 302055424}

er1645v2VEthIpV6IcmpMessagesBeyondScope OBJECT-TYPE
   SYNTAX      INTEGER
               {
               disabled (0),
               enabled (1)
               }
   MAX-ACCESS  read-write
   STATUS      current
   DESCRIPTION
      "Path: virtualEthernet.editConf.ipV6.icmpMessages.beyondScope

       Possibilities:
               disabled   (0)
               enabled   (1)"
   ::= {er1645v2VEthIpV6Entry 302186496}

er1645v2VEthIpV6IcmpMessagesAddressUnreachable OBJECT-TYPE
   SYNTAX      INTEGER
               {
               disabled (0),
               enabled (1)
               }
   MAX-ACCESS  read-write
   STATUS      current
   DESCRIPTION
      "Path: virtualEthernet.editConf.ipV6.icmpMessages.addressUnreachable

       Possibilities:
               disabled   (0)
               enabled   (1)"
   ::= {er1645v2VEthIpV6Entry 302252032}

er1645v2VEthIpV6IcmpMessagesPortUnreachable OBJECT-TYPE
   SYNTAX      INTEGER
               {
               disabled (0),
               enabled (1)
               }
   MAX-ACCESS  read-write
   STATUS      current
   DESCRIPTION
      "Path: virtualEthernet.editConf.ipV6.icmpMessages.portUnreachable

       Possibilities:
               disabled   (0)
               enabled   (1)"
   ::= {er1645v2VEthIpV6Entry 302317568}

er1645v2VEthIpV6IcmpMessagesPacketTooBig OBJECT-TYPE
   SYNTAX      INTEGER
               {
               disabled (0),
               enabled (1)
               }
   MAX-ACCESS  read-write
   STATUS      current
   DESCRIPTION
      "Path: virtualEthernet.editConf.ipV6.icmpMessages.packetTooBig

       Possibilities:
               disabled   (0)
               enabled   (1)"
   ::= {er1645v2VEthIpV6Entry 302645248}

er1645v2VEthIpV6IcmpMessagesHopLimitExceeded OBJECT-TYPE
   SYNTAX      INTEGER
               {
               disabled (0),
               enabled (1)
               }
   MAX-ACCESS  read-write
   STATUS      current
   DESCRIPTION
      "Path: virtualEthernet.editConf.ipV6.icmpMessages.hopLimitExceeded

       Possibilities:
               disabled   (0)
               enabled   (1)"
   ::= {er1645v2VEthIpV6Entry 303300608}

er1645v2VEthIpV6IcmpMessagesFragTimeExceeded OBJECT-TYPE
   SYNTAX      INTEGER
               {
               disabled (0),
               enabled (1)
               }
   MAX-ACCESS  read-write
   STATUS      current
   DESCRIPTION
      "Path: virtualEthernet.editConf.ipV6.icmpMessages.fragTimeExceeded

       Possibilities:
               disabled   (0)
               enabled   (1)"
   ::= {er1645v2VEthIpV6Entry 303366144}

er1645v2VEthIpV6IcmpMessagesHeaderFieldErr OBJECT-TYPE
   SYNTAX      INTEGER
               {
               disabled (0),
               enabled (1)
               }
   MAX-ACCESS  read-write
   STATUS      current
   DESCRIPTION
      "Path: virtualEthernet.editConf.ipV6.icmpMessages.headerFieldErr

       Possibilities:
               disabled   (0)
               enabled   (1)"
   ::= {er1645v2VEthIpV6Entry 303955968}

er1645v2VEthIpV6IcmpMessagesOptionUnrecognized OBJECT-TYPE
   SYNTAX      INTEGER
               {
               disabled (0),
               enabled (1)
               }
   MAX-ACCESS  read-write
   STATUS      current
   DESCRIPTION
      "Path: virtualEthernet.editConf.ipV6.icmpMessages.optionUnrecognized

       Possibilities:
               disabled   (0)
               enabled   (1)"
   ::= {er1645v2VEthIpV6Entry 304087040}

er1645v2VEthIpV6IcmpMessagesRedirect OBJECT-TYPE
   SYNTAX      INTEGER
               {
               disabled (0),
               enabled (1)
               }
   MAX-ACCESS  read-write
   STATUS      current
   DESCRIPTION
      "Path: virtualEthernet.editConf.ipV6.icmpMessages.redirect

       Possibilities:
               disabled   (0)
               enabled   (1)"
   ::= {er1645v2VEthIpV6Entry 304611328}

er1645v2VEthIpV6Addresses OBJECT-TYPE
   SYNTAX      SEQUENCE OF Er1645v2VEthIpV6AddressesEntry
   MAX-ACCESS  not-accessible
   STATUS      current
   DESCRIPTION
      ""
   ::= {er1645v2VEthIpV6 50331648}

er1645v2VEthIpV6AddressesEntry OBJECT-TYPE
   SYNTAX      Er1645v2VEthIpV6AddressesEntry
   MAX-ACCESS  not-accessible
   STATUS      current
   DESCRIPTION
      ""
   INDEX      { er1645v2VEthIpV6AddressesGlobalIx,
                er1645v2VEthIpV6AddressesTableIx }
   ::= {er1645v2VEthIpV6Addresses 1}

Er1645v2VEthIpV6AddressesEntry ::=
   SEQUENCE
      {
      er1645v2VEthIpV6AddressesActions
         VariableLengthTableActions,
      er1645v2VEthIpV6AddressesGlobalIx
         GlobalIndex,
      er1645v2VEthIpV6AddressesTableIx
         TableIndex,
      er1645v2VEthIpV6AddressesType
         INTEGER,
      er1645v2VEthIpV6AddressesAddress
         Ipv6Address,
      er1645v2VEthIpV6AddressesPrefixLength
         Integer32,
      er1645v2VEthIpV6AddressesGeneralPrefix
         DisplayString,
      er1645v2VEthIpV6AddressesRaSend
         INTEGER,
      er1645v2VEthIpV6AddressesRaOnLinkFlag
         INTEGER,
      er1645v2VEthIpV6AddressesRaAutoFlag
         INTEGER,
      er1645v2VEthIpV6AddressesRaValidLifeTime
         TimeTicks,
      er1645v2VEthIpV6AddressesRaValidLTMode
         INTEGER,
      er1645v2VEthIpV6AddressesRaPrefLifeTime
         TimeTicks,
      er1645v2VEthIpV6AddressesRaPrefLTMode
         INTEGER
      }

er1645v2VEthIpV6AddressesActions OBJECT-TYPE
   SYNTAX      VariableLengthTableActions
   MAX-ACCESS  read-write
   STATUS      current
   DESCRIPTION
      "By way of this field, some manipulations
       on this table may be performed."
   ::= {er1645v2VEthIpV6AddressesEntry 2}

er1645v2VEthIpV6AddressesGlobalIx OBJECT-TYPE
   SYNTAX      GlobalIndex
   MAX-ACCESS  not-accessible
   STATUS      current
   DESCRIPTION
      "The value of the tlsCntTreeGlobalIndex of the MANAGED OBJECT."
   ::= {er1645v2VEthIpV6AddressesEntry 10}

er1645v2VEthIpV6AddressesTableIx OBJECT-TYPE
   SYNTAX      TableIndex
   MAX-ACCESS  not-accessible
   STATUS      current
   DESCRIPTION
      ""
   ::= {er1645v2VEthIpV6AddressesEntry 11}

er1645v2VEthIpV6AddressesType OBJECT-TYPE
   SYNTAX      INTEGER
               {
               unicast (0),
               eui64 (1),
               anycast (2),
               linkLocal (3),
               generalPrefix (4)
               }
   MAX-ACCESS  read-write
   STATUS      current
   DESCRIPTION
      "Path: virtualEthernet.editConf.ipV6.addresses.type

       Possibilities:
               unicast   (0)
               eui64   (1)
               anycast   (2)
               linkLocal   (3)
               generalPrefix   (4)"
   ::= {er1645v2VEthIpV6AddressesEntry 50331648}

er1645v2VEthIpV6AddressesAddress OBJECT-TYPE
   SYNTAX      Ipv6Address
   MAX-ACCESS  read-write
   STATUS      current
   DESCRIPTION
      "Path: virtualEthernet.editConf.ipV6.addresses.address

       ipv6 address"
   ::= {er1645v2VEthIpV6AddressesEntry 16777216}

er1645v2VEthIpV6AddressesPrefixLength OBJECT-TYPE
   SYNTAX      Integer32
   MAX-ACCESS  read-write
   STATUS      current
   DESCRIPTION
      "Path: virtualEthernet.editConf.ipV6.addresses.prefixLength"
   ::= {er1645v2VEthIpV6AddressesEntry 33554432}

er1645v2VEthIpV6AddressesGeneralPrefix OBJECT-TYPE
   SYNTAX      DisplayString
   MAX-ACCESS  read-write
   STATUS      current
   DESCRIPTION
      "Path: virtualEthernet.editConf.ipV6.addresses.generalPrefix"
   ::= {er1645v2VEthIpV6AddressesEntry 83886080}

er1645v2VEthIpV6AddressesRaSend OBJECT-TYPE
   SYNTAX      INTEGER
               {
               disabled (0),
               enabled (1)
               }
   MAX-ACCESS  read-write
   STATUS      current
   DESCRIPTION
      "Path: virtualEthernet.editConf.ipV6.addresses.ra.send

       Possibilities:
               disabled   (0)
               enabled   (1)"
   ::= {er1645v2VEthIpV6AddressesEntry 67174400}

er1645v2VEthIpV6AddressesRaOnLinkFlag OBJECT-TYPE
   SYNTAX      INTEGER
               {
               disabled (0),
               enabled (1)
               }
   MAX-ACCESS  read-write
   STATUS      current
   DESCRIPTION
      "Path: virtualEthernet.editConf.ipV6.addresses.ra.onLinkFlag

       Possibilities:
               disabled   (0)
               enabled   (1)"
   ::= {er1645v2VEthIpV6AddressesEntry 67371008}

er1645v2VEthIpV6AddressesRaAutoFlag OBJECT-TYPE
   SYNTAX      INTEGER
               {
               disabled (0),
               enabled (1)
               }
   MAX-ACCESS  read-write
   STATUS      current
   DESCRIPTION
      "Path: virtualEthernet.editConf.ipV6.addresses.ra.autonomousFlag

       Possibilities:
               disabled   (0)
               enabled   (1)"
   ::= {er1645v2VEthIpV6AddressesEntry 67567616}

er1645v2VEthIpV6AddressesRaValidLifeTime OBJECT-TYPE
   SYNTAX      TimeTicks
   MAX-ACCESS  read-write
   STATUS      current
   DESCRIPTION
      "Path: virtualEthernet.editConf.ipV6.addresses.ra.validLifeTime

       Time in centi-second."
   ::= {er1645v2VEthIpV6AddressesEntry 67239936}

er1645v2VEthIpV6AddressesRaValidLTMode OBJECT-TYPE
   SYNTAX      INTEGER
               {
               fixed (0),
               infinite (2)
               }
   MAX-ACCESS  read-write
   STATUS      current
   DESCRIPTION
      "Path: virtualEthernet.editConf.ipV6.addresses.ra.validLifeTimeMode

       Possibilities:
               fixed   (0)
               infinite   (2)"
   ::= {er1645v2VEthIpV6AddressesEntry 67305472}

er1645v2VEthIpV6AddressesRaPrefLifeTime OBJECT-TYPE
   SYNTAX      TimeTicks
   MAX-ACCESS  read-write
   STATUS      current
   DESCRIPTION
      "Path: virtualEthernet.editConf.ipV6.addresses.ra.prefLifeTime

       Time in centi-second."
   ::= {er1645v2VEthIpV6AddressesEntry 67436544}

er1645v2VEthIpV6AddressesRaPrefLTMode OBJECT-TYPE
   SYNTAX      INTEGER
               {
               fixed (0),
               infinite (2)
               }
   MAX-ACCESS  read-write
   STATUS      current
   DESCRIPTION
      "Path: virtualEthernet.editConf.ipV6.addresses.ra.prefLifeTimeMode

       Possibilities:
               fixed   (0)
               infinite   (2)"
   ::= {er1645v2VEthIpV6AddressesEntry 67502080}

er1645v2VEthIpV6RaDnsOptionsRdnssServers OBJECT-TYPE
   SYNTAX      SEQUENCE OF Er1645v2VEthIpV6RaDnsOptionsRdnssServersEntry
   MAX-ACCESS  not-accessible
   STATUS      current
   DESCRIPTION
      ""
   ::= {er1645v2VEthIpV6 101394432}

er1645v2VEthIpV6RaDnsOptionsRdnssServersEntry OBJECT-TYPE
   SYNTAX      Er1645v2VEthIpV6RaDnsOptionsRdnssServersEntry
   MAX-ACCESS  not-accessible
   STATUS      current
   DESCRIPTION
      ""
   INDEX      { er1645v2VEthIpV6RaDnsOptionsRdnssServersGlobalIx,
                er1645v2VEthIpV6RaDnsOptionsRdnssServersTableIx }
   ::= {er1645v2VEthIpV6RaDnsOptionsRdnssServers 1}

Er1645v2VEthIpV6RaDnsOptionsRdnssServersEntry ::=
   SEQUENCE
      {
      er1645v2VEthIpV6RaDnsOptionsRdnssServersActions
         VariableLengthTableActions,
      er1645v2VEthIpV6RaDnsOptionsRdnssServersGlobalIx
         GlobalIndex,
      er1645v2VEthIpV6RaDnsOptionsRdnssServersTableIx
         TableIndex,
      er1645v2VEthIpV6RaDnsOptionsRdnssServersAddress
         Ipv6Address
      }

er1645v2VEthIpV6RaDnsOptionsRdnssServersActions OBJECT-TYPE
   SYNTAX      VariableLengthTableActions
   MAX-ACCESS  read-write
   STATUS      current
   DESCRIPTION
      "By way of this field, some manipulations
       on this table may be performed."
   ::= {er1645v2VEthIpV6RaDnsOptionsRdnssServersEntry 2}

er1645v2VEthIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2VEthIpV6RaDnsOptionsRdnssServersEntry 10}

er1645v2VEthIpV6RaDnsOptionsRdnssServersTableIx OBJECT-TYPE
   SYNTAX      TableIndex
   MAX-ACCESS  not-accessible
   STATUS      current
   DESCRIPTION
      ""
   ::= {er1645v2VEthIpV6RaDnsOptionsRdnssServersEntry 11}

er1645v2VEthIpV6RaDnsOptionsRdnssServersAddress OBJECT-TYPE
   SYNTAX      Ipv6Address
   MAX-ACCESS  read-write
   STATUS      current
   DESCRIPTION
      "Path: virtualEthernet.editConf.ipV6.ra.dnsOptions.rdnss.servers.address

       ipv6 address"
   ::= {er1645v2VEthIpV6RaDnsOptionsRdnssServersEntry 16777216}

er1645v2VEthIpV6RaDnsOptionsDnsslDomains OBJECT-TYPE
   SYNTAX      SEQUENCE OF Er1645v2VEthIpV6RaDnsOptionsDnsslDomainsEntry
   MAX-ACCESS  not-accessible
   STATUS      current
   DESCRIPTION
      ""
   ::= {er1645v2VEthIpV6 101402624}

er1645v2VEthIpV6RaDnsOptionsDnsslDomainsEntry OBJECT-TYPE
   SYNTAX      Er1645v2VEthIpV6RaDnsOptionsDnsslDomainsEntry
   MAX-ACCESS  not-accessible
   STATUS      current
   DESCRIPTION
      ""
   INDEX      { er1645v2VEthIpV6RaDnsOptionsDnsslDomainsGlobalIx,
                er1645v2VEthIpV6RaDnsOptionsDnsslDomainsTableIx }
   ::= {er1645v2VEthIpV6RaDnsOptionsDnsslDomains 1}

Er1645v2VEthIpV6RaDnsOptionsDnsslDomainsEntry ::=
   SEQUENCE
      {
      er1645v2VEthIpV6RaDnsOptionsDnsslDomainsActions
         VariableLengthTableActions,
      er1645v2VEthIpV6RaDnsOptionsDnsslDomainsGlobalIx
         GlobalIndex,
      er1645v2VEthIpV6RaDnsOptionsDnsslDomainsTableIx
         TableIndex,
      er1645v2VEthIpV6RaDnsOptionsDnsslDomainsName
         DisplayString
      }

er1645v2VEthIpV6RaDnsOptionsDnsslDomainsActions OBJECT-TYPE
   SYNTAX      VariableLengthTableActions
   MAX-ACCESS  read-write
   STATUS      current
   DESCRIPTION
      "By way of this field, some manipulations
       on this table may be performed."
   ::= {er1645v2VEthIpV6RaDnsOptionsDnsslDomainsEntry 2}

er1645v2VEthIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2VEthIpV6RaDnsOptionsDnsslDomainsEntry 10}

er1645v2VEthIpV6RaDnsOptionsDnsslDomainsTableIx OBJECT-TYPE
   SYNTAX      TableIndex
   MAX-ACCESS  not-accessible
   STATUS      current
   DESCRIPTION
      ""
   ::= {er1645v2VEthIpV6RaDnsOptionsDnsslDomainsEntry 11}

er1645v2VEthIpV6RaDnsOptionsDnsslDomainsName OBJECT-TYPE
   SYNTAX      DisplayString
   MAX-ACCESS  read-write
   STATUS      current
   DESCRIPTION
      "Path: virtualEthernet.editConf.ipV6.ra.dnsOptions.dnssl.domains.name"
   ::= {er1645v2VEthIpV6RaDnsOptionsDnsslDomainsEntry 16777216}

er1645v2VEthIpV6DhcpClientUserClassOpt OBJECT-TYPE
   SYNTAX      SEQUENCE OF Er1645v2VEthIpV6DhcpClientUserClassOptEntry
   MAX-ACCESS  not-accessible
   STATUS      current
   DESCRIPTION
      ""
   ::= {er1645v2VEthIpV6 171442176}

er1645v2VEthIpV6DhcpClientUserClassOptEntry OBJECT-TYPE
   SYNTAX      Er1645v2VEthIpV6DhcpClientUserClassOptEntry
   MAX-ACCESS  not-accessible
   STATUS      current
   DESCRIPTION
      ""
   INDEX      { er1645v2VEthIpV6DhcpClientUserClassOptGlobalIx,
                er1645v2VEthIpV6DhcpClientUserClassOptTableIx }
   ::= {er1645v2VEthIpV6DhcpClientUserClassOpt 1}

Er1645v2VEthIpV6DhcpClientUserClassOptEntry ::=
   SEQUENCE
      {
      er1645v2VEthIpV6DhcpClientUserClassOptActions
         VariableLengthTableActions,
      er1645v2VEthIpV6DhcpClientUserClassOptGlobalIx
         GlobalIndex,
      er1645v2VEthIpV6DhcpClientUserClassOptTableIx
         TableIndex,
      er1645v2VEthIpV6DhcpClientUserClassOptValueAscii
         DisplayString,
      er1645v2VEthIpV6DhcpClientUserClassOptValueDecimal
         Integer32,
      er1645v2VEthIpV6DhcpClientUserClassOptValueHexData
         OCTET STRING
      }

er1645v2VEthIpV6DhcpClientUserClassOptActions OBJECT-TYPE
   SYNTAX      VariableLengthTableActions
   MAX-ACCESS  read-write
   STATUS      current
   DESCRIPTION
      "By way of this field, some manipulations
       on this table may be performed."
   ::= {er1645v2VEthIpV6DhcpClientUserClassOptEntry 2}

er1645v2VEthIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2VEthIpV6DhcpClientUserClassOptEntry 10}

er1645v2VEthIpV6DhcpClientUserClassOptTableIx OBJECT-TYPE
   SYNTAX      TableIndex
   MAX-ACCESS  not-accessible
   STATUS      current
   DESCRIPTION
      ""
   ::= {er1645v2VEthIpV6DhcpClientUserClassOptEntry 11}

er1645v2VEthIpV6DhcpClientUserClassOptValueAscii OBJECT-TYPE
   SYNTAX      DisplayString
   MAX-ACCESS  read-write
   STATUS      current
   DESCRIPTION
      "Path: virtualEthernet.editConf.ipV6.dhcp.client.userClassOpt.value.ascii"
   ::= {er1645v2VEthIpV6DhcpClientUserClassOptEntry 16842752}

er1645v2VEthIpV6DhcpClientUserClassOptValueDecimal OBJECT-TYPE
   SYNTAX      Integer32
   MAX-ACCESS  read-write
   STATUS      current
   DESCRIPTION
      "Path: virtualEthernet.editConf.ipV6.dhcp.client.userClassOpt.value.decimal"
   ::= {er1645v2VEthIpV6DhcpClientUserClassOptEntry 16908288}

er1645v2VEthIpV6DhcpClientUserClassOptValueHexData OBJECT-TYPE
   SYNTAX      OCTET STRING
   MAX-ACCESS  read-write
   STATUS      current
   DESCRIPTION
      "Path: virtualEthernet.editConf.ipV6.dhcp.client.userClassOpt.value.hexData"
   ::= {er1645v2VEthIpV6DhcpClientUserClassOptEntry 16973824}

er1645v2VEthIpV6DhcpClientVendorCl OBJECT-TYPE
   SYNTAX      SEQUENCE OF Er1645v2VEthIpV6DhcpClientVendorClEntry
   MAX-ACCESS  not-accessible
   STATUS      current
   DESCRIPTION
      ""
   ::= {er1645v2VEthIpV6 171704320}

er1645v2VEthIpV6DhcpClientVendorClEntry OBJECT-TYPE
   SYNTAX      Er1645v2VEthIpV6DhcpClientVendorClEntry
   MAX-ACCESS  not-accessible
   STATUS      current
   DESCRIPTION
      ""
   INDEX      { er1645v2VEthIpV6DhcpClientVendorClGlobalIx,
                er1645v2VEthIpV6DhcpClientVendorClTableIx }
   ::= {er1645v2VEthIpV6DhcpClientVendorCl 1}

Er1645v2VEthIpV6DhcpClientVendorClEntry ::=
   SEQUENCE
      {
      er1645v2VEthIpV6DhcpClientVendorClActions
         VariableLengthTableActions,
      er1645v2VEthIpV6DhcpClientVendorClGlobalIx
         GlobalIndex,
      er1645v2VEthIpV6DhcpClientVendorClTableIx
         TableIndex,
      er1645v2VEthIpV6DhcpClientVendorClValueAscii
         DisplayString,
      er1645v2VEthIpV6DhcpClientVendorClValueDecimal
         Integer32,
      er1645v2VEthIpV6DhcpClientVendorClValueHexData
         OCTET STRING
      }

er1645v2VEthIpV6DhcpClientVendorClActions OBJECT-TYPE
   SYNTAX      VariableLengthTableActions
   MAX-ACCESS  read-write
   STATUS      current
   DESCRIPTION
      "By way of this field, some manipulations
       on this table may be performed."
   ::= {er1645v2VEthIpV6DhcpClientVendorClEntry 2}

er1645v2VEthIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2VEthIpV6DhcpClientVendorClEntry 10}

er1645v2VEthIpV6DhcpClientVendorClTableIx OBJECT-TYPE
   SYNTAX      TableIndex
   MAX-ACCESS  not-accessible
   STATUS      current
   DESCRIPTION
      ""
   ::= {er1645v2VEthIpV6DhcpClientVendorClEntry 11}

er1645v2VEthIpV6DhcpClientVendorClValueAscii OBJECT-TYPE
   SYNTAX      DisplayString
   MAX-ACCESS  read-write
   STATUS      current
   DESCRIPTION
      "Path: virtualEthernet.editConf.ipV6.dhcp.client.vendorClassOpt.value.ascii"
   ::= {er1645v2VEthIpV6DhcpClientVendorClEntry 16842752}

er1645v2VEthIpV6DhcpClientVendorClValueDecimal OBJECT-TYPE
   SYNTAX      Integer32
   MAX-ACCESS  read-write
   STATUS      current
   DESCRIPTION
      "Path: virtualEthernet.editConf.ipV6.dhcp.client.vendorClassOpt.value.decimal"
   ::= {er1645v2VEthIpV6DhcpClientVendorClEntry 16908288}

er1645v2VEthIpV6DhcpClientVendorClValueHexData OBJECT-TYPE
   SYNTAX      OCTET STRING
   MAX-ACCESS  read-write
   STATUS      current
   DESCRIPTION
      "Path: virtualEthernet.editConf.ipV6.dhcp.client.vendorClassOpt.value.hexData"
   ::= {er1645v2VEthIpV6DhcpClientVendorClEntry 16973824}

er1645v2VEthIpV6DhcpRelayDestinations OBJECT-TYPE
   SYNTAX      SEQUENCE OF Er1645v2VEthIpV6DhcpRelayDestinationsEntry
   MAX-ACCESS  not-accessible
   STATUS      current
   DESCRIPTION
      ""
   ::= {er1645v2VEthIpV6 174080000}

er1645v2VEthIpV6DhcpRelayDestinationsEntry OBJECT-TYPE
   SYNTAX      Er1645v2VEthIpV6DhcpRelayDestinationsEntry
   MAX-ACCESS  not-accessible
   STATUS      current
   DESCRIPTION
      ""
   INDEX      { er1645v2VEthIpV6DhcpRelayDestinationsGlobalIx,
                er1645v2VEthIpV6DhcpRelayDestinationsTableIx }
   ::= {er1645v2VEthIpV6DhcpRelayDestinations 1}

Er1645v2VEthIpV6DhcpRelayDestinationsEntry ::=
   SEQUENCE
      {
      er1645v2VEthIpV6DhcpRelayDestinationsActions
         VariableLengthTableActions,
      er1645v2VEthIpV6DhcpRelayDestinationsGlobalIx
         GlobalIndex,
      er1645v2VEthIpV6DhcpRelayDestinationsTableIx
         TableIndex,
      er1645v2VEthIpV6DhcpRelayDestinationsAddress
         Ipv6Address,
      er1645v2VEthIpV6DhcpRelayDestinationsInterface
         DisplayString
      }

er1645v2VEthIpV6DhcpRelayDestinationsActions OBJECT-TYPE
   SYNTAX      VariableLengthTableActions
   MAX-ACCESS  read-write
   STATUS      current
   DESCRIPTION
      "By way of this field, some manipulations
       on this table may be performed."
   ::= {er1645v2VEthIpV6DhcpRelayDestinationsEntry 2}

er1645v2VEthIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2VEthIpV6DhcpRelayDestinationsEntry 10}

er1645v2VEthIpV6DhcpRelayDestinationsTableIx OBJECT-TYPE
   SYNTAX      TableIndex
   MAX-ACCESS  not-accessible
   STATUS      current
   DESCRIPTION
      ""
   ::= {er1645v2VEthIpV6DhcpRelayDestinationsEntry 11}

er1645v2VEthIpV6DhcpRelayDestinationsAddress OBJECT-TYPE
   SYNTAX      Ipv6Address
   MAX-ACCESS  read-write
   STATUS      current
   DESCRIPTION
      "Path: virtualEthernet.editConf.ipV6.dhcp.relay.destinations.address

       ipv6 address"
   ::= {er1645v2VEthIpV6DhcpRelayDestinationsEntry 16777216}

er1645v2VEthIpV6DhcpRelayDestinationsInterface OBJECT-TYPE
   SYNTAX      DisplayString
   MAX-ACCESS  read-write
   STATUS      current
   DESCRIPTION
      "Path: virtualEthernet.editConf.ipV6.dhcp.relay.destinations.interface"
   ::= {er1645v2VEthIpV6DhcpRelayDestinationsEntry 33554432}


er1645v2VEthMacAddress OBJECT IDENTIFIER ::= {er1645v2VEth 201}

er1645v2VEthMacAddressSSCTable OBJECT-TYPE
   SYNTAX      SEQUENCE OF Er1645v2VEthMacAddressEntry
   MAX-ACCESS  not-accessible
   STATUS      current
   DESCRIPTION
      "Configurable MAC address of a Virtual Ethernet"
   ::= {er1645v2VEthMacAddress 1}

er1645v2VEthMacAddressEntry OBJECT-TYPE
   SYNTAX      Er1645v2VEthMacAddressEntry
   MAX-ACCESS  not-accessible
   STATUS      current
   DESCRIPTION
      ""
   INDEX      { er1645v2VEthMacAddressGlobalIx }
   ::= {er1645v2VEthMacAddressSSCTable 1}

Er1645v2VEthMacAddressEntry ::=
   SEQUENCE
      {
      er1645v2VEthMacAddressGlobalIx
         GlobalIndex,
      er1645v2VEthMacAddressUserMac
         OCTET STRING,
      er1645v2VEthMacAddressRandomMac
         Integer32
      }

er1645v2VEthMacAddressGlobalIx OBJECT-TYPE
   SYNTAX      GlobalIndex
   MAX-ACCESS  not-accessible
   STATUS      current
   DESCRIPTION
      "The value of the tlsCntTreeGlobalIndex of the MANAGED OBJECT."
   ::= {er1645v2VEthMacAddressEntry 10}

er1645v2VEthMacAddressUserMac OBJECT-TYPE
   SYNTAX      OCTET STRING
   MAX-ACCESS  read-write
   STATUS      current
   DESCRIPTION
      "Path: virtualEthernet.editConf.macAddress.userMac

       MAC address."
   ::= {er1645v2VEthMacAddressEntry 33554432}

er1645v2VEthMacAddressRandomMac OBJECT-TYPE
   SYNTAX      Integer32
   MAX-ACCESS  read-write
   STATUS      current
   DESCRIPTION
      "Path: virtualEthernet.editConf.macAddress.randomMac"
   ::= {er1645v2VEthMacAddressEntry 67108864}


er1645v2VEthSnmpIndexOffset OBJECT IDENTIFIER ::= {er1645v2VEth 268}

er1645v2VEthSnmpIndexOffsetTable OBJECT-TYPE
   SYNTAX      SEQUENCE OF Er1645v2VEthSnmpIndexOffsetEntry
   MAX-ACCESS  not-accessible
   STATUS      current
   DESCRIPTION
      "Preferred offset in the range of SNMP indices for this SWinst, 0 means automatic"
   ::= {er1645v2VEthSnmpIndexOffset 1}

er1645v2VEthSnmpIndexOffsetEntry OBJECT-TYPE
   SYNTAX      Er1645v2VEthSnmpIndexOffsetEntry
   MAX-ACCESS  not-accessible
   STATUS      current
   DESCRIPTION
      ""
   INDEX      { er1645v2VEthSnmpIndexOffsetGlobalIx }
   ::= {er1645v2VEthSnmpIndexOffsetTable 1}

Er1645v2VEthSnmpIndexOffsetEntry ::=
   SEQUENCE
      {
      er1645v2VEthSnmpIndexOffsetGlobalIx
         GlobalIndex,
      er1645v2VEthSnmpIndexOffsetValue
         Integer32
      }

er1645v2VEthSnmpIndexOffsetGlobalIx OBJECT-TYPE
   SYNTAX      GlobalIndex
   MAX-ACCESS  not-accessible
   STATUS      current
   DESCRIPTION
      "The value of the tlsCntTreeGlobalIndex of the MANAGED OBJECT."
   ::= {er1645v2VEthSnmpIndexOffsetEntry 10}

er1645v2VEthSnmpIndexOffsetValue OBJECT-TYPE
   SYNTAX      Integer32
   MAX-ACCESS  read-write
   STATUS      current
   DESCRIPTION
      "Path: virtualEthernet.editConf.snmpIndexOffset"
   ::= {er1645v2VEthSnmpIndexOffsetEntry 2147483648}


er1645v2VEthAlarmMask OBJECT IDENTIFIER ::= {er1645v2VEth 135}

er1645v2VEthAlarmMaskTable OBJECT-TYPE
   SYNTAX      SEQUENCE OF Er1645v2VEthAlarmMaskEntry
   MAX-ACCESS  not-accessible
   STATUS      current
   DESCRIPTION
      "ifAlarmMask"
   ::= {er1645v2VEthAlarmMask 1}

er1645v2VEthAlarmMaskEntry OBJECT-TYPE
   SYNTAX      Er1645v2VEthAlarmMaskEntry
   MAX-ACCESS  not-accessible
   STATUS      current
   DESCRIPTION
      ""
   INDEX      { er1645v2VEthAlarmMaskGlobalIx }
   ::= {er1645v2VEthAlarmMaskTable 1}

Er1645v2VEthAlarmMaskEntry ::=
   SEQUENCE
      {
      er1645v2VEthAlarmMaskGlobalIx
         GlobalIndex,
      er1645v2VEthAlarmMaskValue
         Integer32
      }

er1645v2VEthAlarmMaskGlobalIx OBJECT-TYPE
   SYNTAX      GlobalIndex
   MAX-ACCESS  not-accessible
   STATUS      current
   DESCRIPTION
      "The value of the tlsCntTreeGlobalIndex of the MANAGED OBJECT."
   ::= {er1645v2VEthAlarmMaskEntry 10}

er1645v2VEthAlarmMaskValue OBJECT-TYPE
   SYNTAX      Integer32
   MAX-ACCESS  read-write
   STATUS      current
   DESCRIPTION
      "Path: virtualEthernet.editConf.alarmMask

       Bit meanings:
               bit 0 = linkDown,
               bit 9 = pppoEDown"
   ::= {er1645v2VEthAlarmMaskEntry 2147483648}


er1645v2VEthAlarmLev OBJECT IDENTIFIER ::= {er1645v2VEth 170}

er1645v2VEthAlarmLevSSCTable OBJECT-TYPE
   SYNTAX      SEQUENCE OF Er1645v2VEthAlarmLevEntry
   MAX-ACCESS  not-accessible
   STATUS      current
   DESCRIPTION
      "IfAlarmLevels"
   ::= {er1645v2VEthAlarmLev 1}

er1645v2VEthAlarmLevEntry OBJECT-TYPE
   SYNTAX      Er1645v2VEthAlarmLevEntry
   MAX-ACCESS  not-accessible
   STATUS      current
   DESCRIPTION
      ""
   INDEX      { er1645v2VEthAlarmLevGlobalIx }
   ::= {er1645v2VEthAlarmLevSSCTable 1}

Er1645v2VEthAlarmLevEntry ::=
   SEQUENCE
      {
      er1645v2VEthAlarmLevGlobalIx
         GlobalIndex,
      er1645v2VEthAlarmLevLinkDown
         Integer32,
      er1645v2VEthAlarmLevPppoEDown
         Integer32
      }

er1645v2VEthAlarmLevGlobalIx OBJECT-TYPE
   SYNTAX      GlobalIndex
   MAX-ACCESS  not-accessible
   STATUS      current
   DESCRIPTION
      "The value of the tlsCntTreeGlobalIndex of the MANAGED OBJECT."
   ::= {er1645v2VEthAlarmLevEntry 10}

er1645v2VEthAlarmLevLinkDown OBJECT-TYPE
   SYNTAX      Integer32
   MAX-ACCESS  read-write
   STATUS      current
   DESCRIPTION
      "Path: virtualEthernet.editConf.alarmLevel.linkDown"
   ::= {er1645v2VEthAlarmLevEntry 16777216}

er1645v2VEthAlarmLevPppoEDown OBJECT-TYPE
   SYNTAX      Integer32
   MAX-ACCESS  read-write
   STATUS      current
   DESCRIPTION
      "Path: virtualEthernet.editConf.alarmLevel.pppoEDown"
   ::= {er1645v2VEthAlarmLevEntry 167772160}



sr1645v2VEth OBJECT IDENTIFIER ::= {r1645v2VEth 14}


sr1645v2VEthDescr OBJECT IDENTIFIER ::= {sr1645v2VEth 101}

sr1645v2VEthDescrTable OBJECT-TYPE
   SYNTAX      SEQUENCE OF Sr1645v2VEthDescrEntry
   MAX-ACCESS  not-accessible
   STATUS      current
   DESCRIPTION
      "ifDescr"
   ::= {sr1645v2VEthDescr 1}

sr1645v2VEthDescrEntry OBJECT-TYPE
   SYNTAX      Sr1645v2VEthDescrEntry
   MAX-ACCESS  not-accessible
   STATUS      current
   DESCRIPTION
      ""
   INDEX      { sr1645v2VEthDescrGlobalIx }
   ::= {sr1645v2VEthDescrTable 1}

Sr1645v2VEthDescrEntry ::=
   SEQUENCE
      {
      sr1645v2VEthDescrGlobalIx
         GlobalIndex,
      sr1645v2VEthDescrValue
         DisplayString
      }

sr1645v2VEthDescrGlobalIx OBJECT-TYPE
   SYNTAX      GlobalIndex
   MAX-ACCESS  not-accessible
   STATUS      current
   DESCRIPTION
      "The value of the tlsCntTreeGlobalIndex of the MANAGED OBJECT."
   ::= {sr1645v2VEthDescrEntry 10}

sr1645v2VEthDescrValue OBJECT-TYPE
   SYNTAX      DisplayString
   MAX-ACCESS  read-only
   STATUS      current
   DESCRIPTION
      "Path: virtualEthernet.status.ifDescr"
   ::= {sr1645v2VEthDescrEntry 2147483648}


sr1645v2VEthType OBJECT IDENTIFIER ::= {sr1645v2VEth 102}

sr1645v2VEthTypeTable OBJECT-TYPE
   SYNTAX      SEQUENCE OF Sr1645v2VEthTypeEntry
   MAX-ACCESS  not-accessible
   STATUS      current
   DESCRIPTION
      "ifType"
   ::= {sr1645v2VEthType 1}

sr1645v2VEthTypeEntry OBJECT-TYPE
   SYNTAX      Sr1645v2VEthTypeEntry
   MAX-ACCESS  not-accessible
   STATUS      current
   DESCRIPTION
      ""
   INDEX      { sr1645v2VEthTypeGlobalIx }
   ::= {sr1645v2VEthTypeTable 1}

Sr1645v2VEthTypeEntry ::=
   SEQUENCE
      {
      sr1645v2VEthTypeGlobalIx
         GlobalIndex,
      sr1645v2VEthTypeValue
         INTEGER
      }

sr1645v2VEthTypeGlobalIx OBJECT-TYPE
   SYNTAX      GlobalIndex
   MAX-ACCESS  not-accessible
   STATUS      current
   DESCRIPTION
      "The value of the tlsCntTreeGlobalIndex of the MANAGED OBJECT."
   ::= {sr1645v2VEthTypeEntry 10}

sr1645v2VEthTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: virtualEthernet.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2VEthTypeEntry 2147483648}


sr1645v2VEthMtu OBJECT IDENTIFIER ::= {sr1645v2VEth 103}

sr1645v2VEthMtuTable OBJECT-TYPE
   SYNTAX      SEQUENCE OF Sr1645v2VEthMtuEntry
   MAX-ACCESS  not-accessible
   STATUS      current
   DESCRIPTION
      "ifMtu"
   ::= {sr1645v2VEthMtu 1}

sr1645v2VEthMtuEntry OBJECT-TYPE
   SYNTAX      Sr1645v2VEthMtuEntry
   MAX-ACCESS  not-accessible
   STATUS      current
   DESCRIPTION
      ""
   INDEX      { sr1645v2VEthMtuGlobalIx }
   ::= {sr1645v2VEthMtuTable 1}

Sr1645v2VEthMtuEntry ::=
   SEQUENCE
      {
      sr1645v2VEthMtuGlobalIx
         GlobalIndex,
      sr1645v2VEthMtuValue
         Integer32
      }

sr1645v2VEthMtuGlobalIx OBJECT-TYPE
   SYNTAX      GlobalIndex
   MAX-ACCESS  not-accessible
   STATUS      current
   DESCRIPTION
      "The value of the tlsCntTreeGlobalIndex of the MANAGED OBJECT."
   ::= {sr1645v2VEthMtuEntry 10}

sr1645v2VEthMtuValue OBJECT-TYPE
   SYNTAX      Integer32
   MAX-ACCESS  read-only
   STATUS      current
   DESCRIPTION
      "Path: virtualEthernet.status.ifMtu"
   ::= {sr1645v2VEthMtuEntry 2147483648}


sr1645v2VEthOperStatus OBJECT IDENTIFIER ::= {sr1645v2VEth 107}

sr1645v2VEthOperStatusTable OBJECT-TYPE
   SYNTAX      SEQUENCE OF Sr1645v2VEthOperStatusEntry
   MAX-ACCESS  not-accessible
   STATUS      current
   DESCRIPTION
      "ifOperStatus"
   ::= {sr1645v2VEthOperStatus 1}

sr1645v2VEthOperStatusEntry OBJECT-TYPE
   SYNTAX      Sr1645v2VEthOperStatusEntry
   MAX-ACCESS  not-accessible
   STATUS      current
   DESCRIPTION
      ""
   INDEX      { sr1645v2VEthOperStatusGlobalIx }
   ::= {sr1645v2VEthOperStatusTable 1}

Sr1645v2VEthOperStatusEntry ::=
   SEQUENCE
      {
      sr1645v2VEthOperStatusGlobalIx
         GlobalIndex,
      sr1645v2VEthOperStatusValue
         INTEGER
      }

sr1645v2VEthOperStatusGlobalIx OBJECT-TYPE
   SYNTAX      GlobalIndex
   MAX-ACCESS  not-accessible
   STATUS      current
   DESCRIPTION
      "The value of the tlsCntTreeGlobalIndex of the MANAGED OBJECT."
   ::= {sr1645v2VEthOperStatusEntry 10}

sr1645v2VEthOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.ifOperStatus

       Possibilities:
               up   (1)
               down   (2)
               testing   (3)
               unknown   (4)
               dormant   (5)
               notPresent   (6)
               lowerLayerDown   (7)"
   ::= {sr1645v2VEthOperStatusEntry 2147483648}


sr1645v2VEthLastChange OBJECT IDENTIFIER ::= {sr1645v2VEth 108}

sr1645v2VEthLastChangeTable OBJECT-TYPE
   SYNTAX      SEQUENCE OF Sr1645v2VEthLastChangeEntry
   MAX-ACCESS  not-accessible
   STATUS      current
   DESCRIPTION
      "ifLastChange"
   ::= {sr1645v2VEthLastChange 1}

sr1645v2VEthLastChangeEntry OBJECT-TYPE
   SYNTAX      Sr1645v2VEthLastChangeEntry
   MAX-ACCESS  not-accessible
   STATUS      current
   DESCRIPTION
      ""
   INDEX      { sr1645v2VEthLastChangeGlobalIx }
   ::= {sr1645v2VEthLastChangeTable 1}

Sr1645v2VEthLastChangeEntry ::=
   SEQUENCE
      {
      sr1645v2VEthLastChangeGlobalIx
         GlobalIndex,
      sr1645v2VEthLastChangeValue
         TimeTicks
      }

sr1645v2VEthLastChangeGlobalIx OBJECT-TYPE
   SYNTAX      GlobalIndex
   MAX-ACCESS  not-accessible
   STATUS      current
   DESCRIPTION
      "The value of the tlsCntTreeGlobalIndex of the MANAGED OBJECT."
   ::= {sr1645v2VEthLastChangeEntry 10}

sr1645v2VEthLastChangeValue OBJECT-TYPE
   SYNTAX      TimeTicks
   MAX-ACCESS  read-only
   STATUS      current
   DESCRIPTION
      "Path: virtualEthernet.status.ifLastChange

       Time in centi-second."
   ::= {sr1645v2VEthLastChangeEntry 2147483648}


sr1645v2VEthLastChangeD OBJECT IDENTIFIER ::= {sr1645v2VEth 183}

sr1645v2VEthLastChangeDTable OBJECT-TYPE
   SYNTAX      SEQUENCE OF Sr1645v2VEthLastChangeDEntry
   MAX-ACCESS  not-accessible
   STATUS      current
   DESCRIPTION
      "ifLastChangeDate"
   ::= {sr1645v2VEthLastChangeD 1}

sr1645v2VEthLastChangeDEntry OBJECT-TYPE
   SYNTAX      Sr1645v2VEthLastChangeDEntry
   MAX-ACCESS  not-accessible
   STATUS      current
   DESCRIPTION
      ""
   INDEX      { sr1645v2VEthLastChangeDGlobalIx }
   ::= {sr1645v2VEthLastChangeDTable 1}

Sr1645v2VEthLastChangeDEntry ::=
   SEQUENCE
      {
      sr1645v2VEthLastChangeDGlobalIx
         GlobalIndex,
      sr1645v2VEthLastChangeDValue
         DisplayString
      }

sr1645v2VEthLastChangeDGlobalIx OBJECT-TYPE
   SYNTAX      GlobalIndex
   MAX-ACCESS  not-accessible
   STATUS      current
   DESCRIPTION
      "The value of the tlsCntTreeGlobalIndex of the MANAGED OBJECT."
   ::= {sr1645v2VEthLastChangeDEntry 10}

sr1645v2VEthLastChangeDValue OBJECT-TYPE
   SYNTAX      DisplayString
   MAX-ACCESS  read-only
   STATUS      current
   DESCRIPTION
      "Path: virtualEthernet.status.ifLastChangeDate"
   ::= {sr1645v2VEthLastChangeDEntry 2147483648}


sr1645v2VEthSpeed OBJECT IDENTIFIER ::= {sr1645v2VEth 104}

sr1645v2VEthSpeedTable OBJECT-TYPE
   SYNTAX      SEQUENCE OF Sr1645v2VEthSpeedEntry
   MAX-ACCESS  not-accessible
   STATUS      current
   DESCRIPTION
      "ifSpeed"
   ::= {sr1645v2VEthSpeed 1}

sr1645v2VEthSpeedEntry OBJECT-TYPE
   SYNTAX      Sr1645v2VEthSpeedEntry
   MAX-ACCESS  not-accessible
   STATUS      current
   DESCRIPTION
      ""
   INDEX      { sr1645v2VEthSpeedGlobalIx }
   ::= {sr1645v2VEthSpeedTable 1}

Sr1645v2VEthSpeedEntry ::=
   SEQUENCE
      {
      sr1645v2VEthSpeedGlobalIx
         GlobalIndex,
      sr1645v2VEthSpeedValue
         Gauge32
      }

sr1645v2VEthSpeedGlobalIx OBJECT-TYPE
   SYNTAX      GlobalIndex
   MAX-ACCESS  not-accessible
   STATUS      current
   DESCRIPTION
      "The value of the tlsCntTreeGlobalIndex of the MANAGED OBJECT."
   ::= {sr1645v2VEthSpeedEntry 10}

sr1645v2VEthSpeedValue OBJECT-TYPE
   SYNTAX      Gauge32
   MAX-ACCESS  read-only
   STATUS      current
   DESCRIPTION
      "Path: virtualEthernet.status.ifSpeed

       32 bit unsigned gauge value."
   ::= {sr1645v2VEthSpeedEntry 2147483648}


sr1645v2VEthIp OBJECT IDENTIFIER ::= {sr1645v2VEth 16}

sr1645v2VEthIpSSCTable OBJECT-TYPE
   SYNTAX      SEQUENCE OF Sr1645v2VEthIpEntry
   MAX-ACCESS  not-accessible
   STATUS      current
   DESCRIPTION
      "ip interface status parameters"
   ::= {sr1645v2VEthIp 1}

sr1645v2VEthIpEntry OBJECT-TYPE
   SYNTAX      Sr1645v2VEthIpEntry
   MAX-ACCESS  not-accessible
   STATUS      current
   DESCRIPTION
      ""
   INDEX      { sr1645v2VEthIpGlobalIx }
   ::= {sr1645v2VEthIpSSCTable 1}

Sr1645v2VEthIpEntry ::=
   SEQUENCE
      {
      sr1645v2VEthIpGlobalIx
         GlobalIndex,
      sr1645v2VEthIpStatus
         INTEGER,
      sr1645v2VEthIpAddress
         IpAddress,
      sr1645v2VEthIpNetMask
         IpAddress,
      sr1645v2VEthIpDhcpStatus
         INTEGER,
      sr1645v2VEthIpDhcpLeaseTime
         TimeTicks
      }

sr1645v2VEthIpGlobalIx OBJECT-TYPE
   SYNTAX      GlobalIndex
   MAX-ACCESS  not-accessible
   STATUS      current
   DESCRIPTION
      "The value of the tlsCntTreeGlobalIndex of the MANAGED OBJECT."
   ::= {sr1645v2VEthIpEntry 10}

sr1645v2VEthIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.ip.status

       Possibilities:
               up   (1)
               down   (2)
               testing   (3)
               unknown   (4)
               dormant   (5)
               notPresent   (6)
               lowerLayerDown   (7)"
   ::= {sr1645v2VEthIpEntry 1795162112}

sr1645v2VEthIpAddress OBJECT-TYPE
   SYNTAX      IpAddress
   MAX-ACCESS  read-only
   STATUS      current
   DESCRIPTION
      "Path: virtualEthernet.status.ip.address"
   ::= {sr1645v2VEthIpEntry 2030043136}

sr1645v2VEthIpNetMask OBJECT-TYPE
   SYNTAX      IpAddress
   MAX-ACCESS  read-only
   STATUS      current
   DESCRIPTION
      "Path: virtualEthernet.status.ip.netMask"
   ::= {sr1645v2VEthIpEntry 2063597568}

sr1645v2VEthIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: virtualEthernet.status.ip.dhcp.status

       Possibilities:
               none   (0)
               selecting   (1)
               requesting   (2)
               rebinding   (3)
               bound   (4)
               renewing   (5)
               rebooting   (6)
               initreboot   (7)"
   ::= {sr1645v2VEthIpEntry 402718720}

sr1645v2VEthIpDhcpLeaseTime OBJECT-TYPE
   SYNTAX      TimeTicks
   MAX-ACCESS  read-only
   STATUS      current
   DESCRIPTION
      "Path: virtualEthernet.status.ip.dhcp.leaseTime

       Time in centi-second."
   ::= {sr1645v2VEthIpEntry 402784256}

sr1645v2VEthIpSecondaryIp OBJECT-TYPE
   SYNTAX      SEQUENCE OF Sr1645v2VEthIpSecondaryIpEntry
   MAX-ACCESS  not-accessible
   STATUS      current
   DESCRIPTION
      ""
   ::= {sr1645v2VEthIp 385875968}

sr1645v2VEthIpSecondaryIpEntry OBJECT-TYPE
   SYNTAX      Sr1645v2VEthIpSecondaryIpEntry
   MAX-ACCESS  not-accessible
   STATUS      current
   DESCRIPTION
      ""
   INDEX      { sr1645v2VEthIpSecondaryIpGlobalIx,
                sr1645v2VEthIpSecondaryIpTableIx }
   ::= {sr1645v2VEthIpSecondaryIp 1}

Sr1645v2VEthIpSecondaryIpEntry ::=
   SEQUENCE
      {
      sr1645v2VEthIpSecondaryIpGlobalIx
         GlobalIndex,
      sr1645v2VEthIpSecondaryIpTableIx
         TableIndex,
      sr1645v2VEthIpSecondaryIpAddress
         IpAddress,
      sr1645v2VEthIpSecondaryIpNetMask
         IpAddress
      }

sr1645v2VEthIpSecondaryIpGlobalIx OBJECT-TYPE
   SYNTAX      GlobalIndex
   MAX-ACCESS  not-accessible
   STATUS      current
   DESCRIPTION
      "The value of the tlsCntTreeGlobalIndex of the MANAGED OBJECT."
   ::= {sr1645v2VEthIpSecondaryIpEntry 10}

sr1645v2VEthIpSecondaryIpTableIx OBJECT-TYPE
   SYNTAX      TableIndex
   MAX-ACCESS  not-accessible
   STATUS      current
   DESCRIPTION
      ""
   ::= {sr1645v2VEthIpSecondaryIpEntry 11}

sr1645v2VEthIpSecondaryIpAddress OBJECT-TYPE
   SYNTAX      IpAddress
   MAX-ACCESS  read-only
   STATUS      current
   DESCRIPTION
      "Path: virtualEthernet.status.ip.secondaryIp.address"
   ::= {sr1645v2VEthIpSecondaryIpEntry 2030043136}

sr1645v2VEthIpSecondaryIpNetMask OBJECT-TYPE
   SYNTAX      IpAddress
   MAX-ACCESS  read-only
   STATUS      current
   DESCRIPTION
      "Path: virtualEthernet.status.ip.secondaryIp.netMask"
   ::= {sr1645v2VEthIpSecondaryIpEntry 2063597568}


sr1645v2VEthArpCache OBJECT IDENTIFIER ::= {sr1645v2VEth 11}

sr1645v2VEthArpCacheSSCTable OBJECT-TYPE
   SYNTAX      SEQUENCE OF Sr1645v2VEthArpCacheEntry
   MAX-ACCESS  not-accessible
   STATUS      current
   DESCRIPTION
      "arp cache of ethernet interface"
   ::= {sr1645v2VEthArpCache 1}

sr1645v2VEthArpCacheEntry OBJECT-TYPE
   SYNTAX      Sr1645v2VEthArpCacheEntry
   MAX-ACCESS  not-accessible
   STATUS      current
   DESCRIPTION
      ""
   INDEX      { sr1645v2VEthArpCacheGlobalIx,
                sr1645v2VEthArpCacheTableIx }
   ::= {sr1645v2VEthArpCacheSSCTable 1}

Sr1645v2VEthArpCacheEntry ::=
   SEQUENCE
      {
      sr1645v2VEthArpCacheGlobalIx
         GlobalIndex,
      sr1645v2VEthArpCacheTableIx
         TableIndex,
      sr1645v2VEthArpCacheMacAddress
         OCTET STRING,
      sr1645v2VEthArpCacheIpAddress
         IpAddress,
      sr1645v2VEthArpCacheType
         INTEGER,
      sr1645v2VEthArpCacheTimeOut
         TimeTicks
      }

sr1645v2VEthArpCacheGlobalIx OBJECT-TYPE
   SYNTAX      GlobalIndex
   MAX-ACCESS  not-accessible
   STATUS      current
   DESCRIPTION
      "The value of the tlsCntTreeGlobalIndex of the MANAGED OBJECT."
   ::= {sr1645v2VEthArpCacheEntry 10}

sr1645v2VEthArpCacheTableIx OBJECT-TYPE
   SYNTAX      TableIndex
   MAX-ACCESS  not-accessible
   STATUS      current
   DESCRIPTION
      ""
   ::= {sr1645v2VEthArpCacheEntry 11}

sr1645v2VEthArpCacheMacAddress OBJECT-TYPE
   SYNTAX      OCTET STRING
   MAX-ACCESS  read-only
   STATUS      current
   DESCRIPTION
      "Path: virtualEthernet.status.arpCache.macAddress

       MAC address."
   ::= {sr1645v2VEthArpCacheEntry 16777216}

sr1645v2VEthArpCacheIpAddress OBJECT-TYPE
   SYNTAX      IpAddress
   MAX-ACCESS  read-only
   STATUS      current
   DESCRIPTION
      "Path: virtualEthernet.status.arpCache.ipAddress"
   ::= {sr1645v2VEthArpCacheEntry 33554432}

sr1645v2VEthArpCacheType OBJECT-TYPE
   SYNTAX      INTEGER
               {
               static (0),
               dynamic (1)
               }
   MAX-ACCESS  read-only
   STATUS      current
   DESCRIPTION
      "Path: virtualEthernet.status.arpCache.type

       Possibilities:
               static   (0)
               dynamic   (1)"
   ::= {sr1645v2VEthArpCacheEntry 50331648}

sr1645v2VEthArpCacheTimeOut OBJECT-TYPE
   SYNTAX      TimeTicks
   MAX-ACCESS  read-only
   STATUS      current
   DESCRIPTION
      "Path: virtualEthernet.status.arpCache.timeOut

       Time in centi-second."
   ::= {sr1645v2VEthArpCacheEntry 67108864}


sr1645v2VEthBrS OBJECT IDENTIFIER ::= {sr1645v2VEth 28}

sr1645v2VEthBrSSSCTable OBJECT-TYPE
   SYNTAX      SEQUENCE OF Sr1645v2VEthBrSEntry
   MAX-ACCESS  not-accessible
   STATUS      current
   DESCRIPTION
      "spanning tree status ethernet interface"
   ::= {sr1645v2VEthBrS 1}

sr1645v2VEthBrSEntry OBJECT-TYPE
   SYNTAX      Sr1645v2VEthBrSEntry
   MAX-ACCESS  not-accessible
   STATUS      current
   DESCRIPTION
      ""
   INDEX      { sr1645v2VEthBrSGlobalIx }
   ::= {sr1645v2VEthBrSSSCTable 1}

Sr1645v2VEthBrSEntry ::=
   SEQUENCE
      {
      sr1645v2VEthBrSGlobalIx
         GlobalIndex,
      sr1645v2VEthBrSStatus
         INTEGER,
      sr1645v2VEthBrSStPortRole
         INTEGER,
      sr1645v2VEthBrSStPortId
         Integer32,
      sr1645v2VEthBrSStPpCostExtPathCost
         Integer32,
      sr1645v2VEthBrSStPpCostIntPathCost
         Integer32,
      sr1645v2VEthBrSStExtRpCost
         Integer32,
      sr1645v2VEthBrSStIntRpCost
         Integer32,
      sr1645v2VEthBrSStDesBrIdPriority
         Integer32,
      sr1645v2VEthBrSStDesBrIdMacAddress
         OCTET STRING,
      sr1645v2VEthBrSStDesPrtId
         Integer32,
      sr1645v2VEthBrSStDesInt
         INTEGER,
      sr1645v2VEthBrSStEdgeDetection
         INTEGER
      }

sr1645v2VEthBrSGlobalIx OBJECT-TYPE
   SYNTAX      GlobalIndex
   MAX-ACCESS  not-accessible
   STATUS      current
   DESCRIPTION
      "The value of the tlsCntTreeGlobalIndex of the MANAGED OBJECT."
   ::= {sr1645v2VEthBrSEntry 10}

sr1645v2VEthBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: virtualEthernet.status.bridging.status

       Possibilities:
               disabled   (0)
               discarding   (1)
               learning   (2)
               forwarding   (3)
               backupBlockedIntfDown   (256)
               backupBlockedIntfUp   (259)
               shutdown   (255)"
   ::= {sr1645v2VEthBrSEntry 16777216}

sr1645v2VEthBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: virtualEthernet.status.bridging.spanningTree.portRole

       Possibilities:
               none   (0)
               root   (1)
               designated   (2)
               alternate   (3)
               backup   (4)
               disabled   (5)
               master   (6)"
   ::= {sr1645v2VEthBrSEntry 33619968}

sr1645v2VEthBrSStPortId OBJECT-TYPE
   SYNTAX      Integer32
   MAX-ACCESS  read-only
   STATUS      current
   DESCRIPTION
      "Path: virtualEthernet.status.bridging.spanningTree.portId"
   ::= {sr1645v2VEthBrSEntry 33685504}

sr1645v2VEthBrSStPpCostExtPathCost OBJECT-TYPE
   SYNTAX      Integer32
   MAX-ACCESS  read-only
   STATUS      current
   DESCRIPTION
      "Path: virtualEthernet.status.bridging.spanningTree.portPathCosts.extPathCost"
   ::= {sr1645v2VEthBrSEntry 33751296}

sr1645v2VEthBrSStPpCostIntPathCost OBJECT-TYPE
   SYNTAX      Integer32
   MAX-ACCESS  read-only
   STATUS      current
   DESCRIPTION
      "Path: virtualEthernet.status.bridging.spanningTree.portPathCosts.intPathCost"
   ::= {sr1645v2VEthBrSEntry 33751552}

sr1645v2VEthBrSStExtRpCost OBJECT-TYPE
   SYNTAX      Integer32
   MAX-ACCESS  read-only
   STATUS      current
   DESCRIPTION
      "Path: virtualEthernet.status.bridging.spanningTree.extRootPathCost"
   ::= {sr1645v2VEthBrSEntry 33816576}

sr1645v2VEthBrSStIntRpCost OBJECT-TYPE
   SYNTAX      Integer32
   MAX-ACCESS  read-only
   STATUS      current
   DESCRIPTION
      "Path: virtualEthernet.status.bridging.spanningTree.intRootPathCost"
   ::= {sr1645v2VEthBrSEntry 33882112}

sr1645v2VEthBrSStDesBrIdPriority OBJECT-TYPE
   SYNTAX      Integer32
   MAX-ACCESS  read-only
   STATUS      current
   DESCRIPTION
      "Path: virtualEthernet.status.bridging.spanningTree.designatedBridgeId.priority"
   ::= {sr1645v2VEthBrSEntry 33947904}

sr1645v2VEthBrSStDesBrIdMacAddress OBJECT-TYPE
   SYNTAX      OCTET STRING
   MAX-ACCESS  read-only
   STATUS      current
   DESCRIPTION
      "Path: virtualEthernet.status.bridging.spanningTree.designatedBridgeId.macAddress

       MAC address."
   ::= {sr1645v2VEthBrSEntry 33948160}

sr1645v2VEthBrSStDesPrtId OBJECT-TYPE
   SYNTAX      Integer32
   MAX-ACCESS  read-only
   STATUS      current
   DESCRIPTION
      "Path: virtualEthernet.status.bridging.spanningTree.designatedPortId"
   ::= {sr1645v2VEthBrSEntry 34013184}

sr1645v2VEthBrSStDesInt OBJECT-TYPE
   SYNTAX      INTEGER
               {
               no (0),
               yes (1)
               }
   MAX-ACCESS  read-only
   STATUS      current
   DESCRIPTION
      "Path: virtualEthernet.status.bridging.spanningTree.designatedOrInternal

       Possibilities:
               no   (0)
               yes   (1)"
   ::= {sr1645v2VEthBrSEntry 34078720}

sr1645v2VEthBrSStEdgeDetection OBJECT-TYPE
   SYNTAX      INTEGER
               {
               none (0),
               edge (1),
               notEdge (2)
               }
   MAX-ACCESS  read-only
   STATUS      current
   DESCRIPTION
      "Path: virtualEthernet.status.bridging.spanningTree.edgeDetection

       Possibilities:
               none   (0)
               edge   (1)
               notEdge   (2)"
   ::= {sr1645v2VEthBrSEntry 34144256}


sr1645v2VEthMacAddress OBJECT IDENTIFIER ::= {sr1645v2VEth 105}

sr1645v2VEthMacAddressTable OBJECT-TYPE
   SYNTAX      SEQUENCE OF Sr1645v2VEthMacAddressEntry
   MAX-ACCESS  not-accessible
   STATUS      current
   DESCRIPTION
      "ifPhysAddress"
   ::= {sr1645v2VEthMacAddress 1}

sr1645v2VEthMacAddressEntry OBJECT-TYPE
   SYNTAX      Sr1645v2VEthMacAddressEntry
   MAX-ACCESS  not-accessible
   STATUS      current
   DESCRIPTION
      ""
   INDEX      { sr1645v2VEthMacAddressGlobalIx }
   ::= {sr1645v2VEthMacAddressTable 1}

Sr1645v2VEthMacAddressEntry ::=
   SEQUENCE
      {
      sr1645v2VEthMacAddressGlobalIx
         GlobalIndex,
      sr1645v2VEthMacAddressValue
         OCTET STRING
      }

sr1645v2VEthMacAddressGlobalIx OBJECT-TYPE
   SYNTAX      GlobalIndex
   MAX-ACCESS  not-accessible
   STATUS      current
   DESCRIPTION
      "The value of the tlsCntTreeGlobalIndex of the MANAGED OBJECT."
   ::= {sr1645v2VEthMacAddressEntry 10}

sr1645v2VEthMacAddressValue OBJECT-TYPE
   SYNTAX      OCTET STRING
   MAX-ACCESS  read-only
   STATUS      current
   DESCRIPTION
      "Path: virtualEthernet.status.macAddress

       MAC address."
   ::= {sr1645v2VEthMacAddressEntry 2147483648}


sr1645v2VEthIpAdEntBcastAddr OBJECT IDENTIFIER ::= {sr1645v2VEth 124}

sr1645v2VEthIpAdEntBcastAddrTable OBJECT-TYPE
   SYNTAX      SEQUENCE OF Sr1645v2VEthIpAdEntBcastAddrEntry
   MAX-ACCESS  not-accessible
   STATUS      current
   DESCRIPTION
      "ipAdEntBcastAddr"
   ::= {sr1645v2VEthIpAdEntBcastAddr 1}

sr1645v2VEthIpAdEntBcastAddrEntry OBJECT-TYPE
   SYNTAX      Sr1645v2VEthIpAdEntBcastAddrEntry
   MAX-ACCESS  not-accessible
   STATUS      current
   DESCRIPTION
      ""
   INDEX      { sr1645v2VEthIpAdEntBcastAddrGlobalIx }
   ::= {sr1645v2VEthIpAdEntBcastAddrTable 1}

Sr1645v2VEthIpAdEntBcastAddrEntry ::=
   SEQUENCE
      {
      sr1645v2VEthIpAdEntBcastAddrGlobalIx
         GlobalIndex,
      sr1645v2VEthIpAdEntBcastAddrValue
         Integer32
      }

sr1645v2VEthIpAdEntBcastAddrGlobalIx OBJECT-TYPE
   SYNTAX      GlobalIndex
   MAX-ACCESS  not-accessible
   STATUS      current
   DESCRIPTION
      "The value of the tlsCntTreeGlobalIndex of the MANAGED OBJECT."
   ::= {sr1645v2VEthIpAdEntBcastAddrEntry 10}

sr1645v2VEthIpAdEntBcastAddrValue OBJECT-TYPE
   SYNTAX      Integer32
   MAX-ACCESS  read-only
   STATUS      current
   DESCRIPTION
      "Path: virtualEthernet.status.ipAdEntBcastAddr"
   ::= {sr1645v2VEthIpAdEntBcastAddrEntry 2147483648}


sr1645v2VEthIpAdEntReasmMaxSize OBJECT IDENTIFIER ::= {sr1645v2VEth 125}

sr1645v2VEthIpAdEntReasmMaxSizeTable OBJECT-TYPE
   SYNTAX      SEQUENCE OF Sr1645v2VEthIpAdEntReasmMaxSizeEntry
   MAX-ACCESS  not-accessible
   STATUS      current
   DESCRIPTION
      "ipAdEntReasmMaxSize"
   ::= {sr1645v2VEthIpAdEntReasmMaxSize 1}

sr1645v2VEthIpAdEntReasmMaxSizeEntry OBJECT-TYPE
   SYNTAX      Sr1645v2VEthIpAdEntReasmMaxSizeEntry
   MAX-ACCESS  not-accessible
   STATUS      current
   DESCRIPTION
      ""
   INDEX      { sr1645v2VEthIpAdEntReasmMaxSizeGlobalIx }
   ::= {sr1645v2VEthIpAdEntReasmMaxSizeTable 1}

Sr1645v2VEthIpAdEntReasmMaxSizeEntry ::=
   SEQUENCE
      {
      sr1645v2VEthIpAdEntReasmMaxSizeGlobalIx
         GlobalIndex,
      sr1645v2VEthIpAdEntReasmMaxSizeValue
         Integer32
      }

sr1645v2VEthIpAdEntReasmMaxSizeGlobalIx OBJECT-TYPE
   SYNTAX      GlobalIndex
   MAX-ACCESS  not-accessible
   STATUS      current
   DESCRIPTION
      "The value of the tlsCntTreeGlobalIndex of the MANAGED OBJECT."
   ::= {sr1645v2VEthIpAdEntReasmMaxSizeEntry 10}

sr1645v2VEthIpAdEntReasmMaxSizeValue OBJECT-TYPE
   SYNTAX      Integer32
   MAX-ACCESS  read-only
   STATUS      current
   DESCRIPTION
      "Path: virtualEthernet.status.ipAdEntReasmMaxSize"
   ::= {sr1645v2VEthIpAdEntReasmMaxSizeEntry 2147483648}


sr1645v2VEthOam OBJECT IDENTIFIER ::= {sr1645v2VEth 901}

sr1645v2VEthOamSSCTable OBJECT-TYPE
   SYNTAX      SEQUENCE OF Sr1645v2VEthOamEntry
   MAX-ACCESS  not-accessible
   STATUS      current
   DESCRIPTION
      "OAM discovery state"
   ::= {sr1645v2VEthOam 1}

sr1645v2VEthOamEntry OBJECT-TYPE
   SYNTAX      Sr1645v2VEthOamEntry
   MAX-ACCESS  not-accessible
   STATUS      current
   DESCRIPTION
      ""
   INDEX      { sr1645v2VEthOamGlobalIx }
   ::= {sr1645v2VEthOamSSCTable 1}

Sr1645v2VEthOamEntry ::=
   SEQUENCE
      {
      sr1645v2VEthOamGlobalIx
         GlobalIndex,
      sr1645v2VEthOamDiscovery
         INTEGER,
      sr1645v2VEthOamLoopback
         INTEGER,
      sr1645v2VEthOamLocalInfoVersion
         Integer32,
      sr1645v2VEthOamLocalInfoRevision
         Integer32,
      sr1645v2VEthOamLocalInfoStateMuxAction
         INTEGER,
      sr1645v2VEthOamLocalInfoStateParserAction
         INTEGER,
      sr1645v2VEthOamLocalInfoOui
         OCTET STRING,
      sr1645v2VEthOamLocalInfoVendorInfo
         OCTET STRING,
      sr1645v2VEthOamLocalInfoVarRetrieval
         INTEGER,
      sr1645v2VEthOamLocalInfoLinkEvents
         INTEGER,
      sr1645v2VEthOamLocalInfoLoopback
         INTEGER,
      sr1645v2VEthOamLocalInfoUnidirectional
         INTEGER,
      sr1645v2VEthOamLocalInfoMode
         INTEGER,
      sr1645v2VEthOamLocalInfoMaxPduSize
         Integer32,
      sr1645v2VEthOamRemoteInfoVersion
         Integer32,
      sr1645v2VEthOamRemoteInfoRevision
         Integer32,
      sr1645v2VEthOamRemoteInfoStateMuxAction
         INTEGER,
      sr1645v2VEthOamRemoteInfoStateParserAction
         INTEGER,
      sr1645v2VEthOamRemoteInfoOui
         OCTET STRING,
      sr1645v2VEthOamRemoteInfoVendorInfo
         OCTET STRING,
      sr1645v2VEthOamRemoteInfoVarRetrieval
         INTEGER,
      sr1645v2VEthOamRemoteInfoLinkEvents
         INTEGER,
      sr1645v2VEthOamRemoteInfoLoopback
         INTEGER,
      sr1645v2VEthOamRemoteInfoUnidirectional
         INTEGER,
      sr1645v2VEthOamRemoteInfoMode
         INTEGER,
      sr1645v2VEthOamRemoteInfoMaxPduSize
         Integer32,
      sr1645v2VEthOamEventsErroredSymbolWindow
         Integer32,
      sr1645v2VEthOamEventsErroredSymbolThreshold
         OCTET STRING,
      sr1645v2VEthOamEventsErroredFramePeriodWindow
         INTEGER,
      sr1645v2VEthOamEventsErroredFramePeriodThreshold
         Integer32,
      sr1645v2VEthOamEventsErroredFrameWindow
         Integer32,
      sr1645v2VEthOamEventsErroredFrameThreshold
         Integer32,
      sr1645v2VEthOamEventsErroredFrameSecondsWindow
         Integer32,
      sr1645v2VEthOamEventsErroredFrameSecondsThreshold
         Integer32
      }

sr1645v2VEthOamGlobalIx OBJECT-TYPE
   SYNTAX      GlobalIndex
   MAX-ACCESS  not-accessible
   STATUS      current
   DESCRIPTION
      "The value of the tlsCntTreeGlobalIndex of the MANAGED OBJECT."
   ::= {sr1645v2VEthOamEntry 10}

sr1645v2VEthOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: virtualEthernet.status.oam.discovery

       Possibilities:
               fault   (0)
               sendLocal   (1)
               passiveWait   (2)
               sendLocalRemote   (3)
               sendLocalRemoteOk   (4)
               sendAny   (5)"
   ::= {sr1645v2VEthOamEntry 16777216}

sr1645v2VEthOamLoopback OBJECT-TYPE
   SYNTAX      INTEGER
               {
               idle (0),
               waiting (1),
               localRunning (2),
               remoteRunning (3)
               }
   MAX-ACCESS  read-only
   STATUS      current
   DESCRIPTION
      "Path: virtualEthernet.status.oam.loopback

       Possibilities:
               idle   (0)
               waiting   (1)
               localRunning   (2)
               remoteRunning   (3)"
   ::= {sr1645v2VEthOamEntry 33554432}

sr1645v2VEthOamLocalInfoVersion OBJECT-TYPE
   SYNTAX      Integer32
   MAX-ACCESS  read-only
   STATUS      current
   DESCRIPTION
      "Path: virtualEthernet.status.oam.localInfo.version"
   ::= {sr1645v2VEthOamEntry 50397184}

sr1645v2VEthOamLocalInfoRevision OBJECT-TYPE
   SYNTAX      Integer32
   MAX-ACCESS  read-only
   STATUS      current
   DESCRIPTION
      "Path: virtualEthernet.status.oam.localInfo.revision"
   ::= {sr1645v2VEthOamEntry 50462720}

sr1645v2VEthOamLocalInfoStateMuxAction OBJECT-TYPE
   SYNTAX      INTEGER
               {
               forwarding (0),
               discarding (1)
               }
   MAX-ACCESS  read-only
   STATUS      current
   DESCRIPTION
      "Path: virtualEthernet.status.oam.localInfo.state.muxAction

       Possibilities:
               forwarding   (0)
               discarding   (1)"
   ::= {sr1645v2VEthOamEntry 50528512}

sr1645v2VEthOamLocalInfoStateParserAction OBJECT-TYPE
   SYNTAX      INTEGER
               {
               forwarding (0),
               loopback (1),
               discarding (2),
               reserved (3)
               }
   MAX-ACCESS  read-only
   STATUS      current
   DESCRIPTION
      "Path: virtualEthernet.status.oam.localInfo.state.parserAction

       Possibilities:
               forwarding   (0)
               loopback   (1)
               discarding   (2)
               reserved   (3)"
   ::= {sr1645v2VEthOamEntry 50528768}

sr1645v2VEthOamLocalInfoOui OBJECT-TYPE
   SYNTAX      OCTET STRING
   MAX-ACCESS  read-only
   STATUS      current
   DESCRIPTION
      "Path: virtualEthernet.status.oam.localInfo.oui"
   ::= {sr1645v2VEthOamEntry 50593792}

sr1645v2VEthOamLocalInfoVendorInfo OBJECT-TYPE
   SYNTAX      OCTET STRING
   MAX-ACCESS  read-only
   STATUS      current
   DESCRIPTION
      "Path: virtualEthernet.status.oam.localInfo.vendorInfo"
   ::= {sr1645v2VEthOamEntry 50659328}

sr1645v2VEthOamLocalInfoVarRetrieval OBJECT-TYPE
   SYNTAX      INTEGER
               {
               notSupported (0),
               supported (1)
               }
   MAX-ACCESS  read-only
   STATUS      current
   DESCRIPTION
      "Path: virtualEthernet.status.oam.localInfo.varRetrieval

       Possibilities:
               notSupported   (0)
               supported   (1)"
   ::= {sr1645v2VEthOamEntry 50724864}

sr1645v2VEthOamLocalInfoLinkEvents OBJECT-TYPE
   SYNTAX      INTEGER
               {
               ignored (0),
               interpreted (1)
               }
   MAX-ACCESS  read-only
   STATUS      current
   DESCRIPTION
      "Path: virtualEthernet.status.oam.localInfo.linkEvents

       Possibilities:
               ignored   (0)
               interpreted   (1)"
   ::= {sr1645v2VEthOamEntry 50790400}

sr1645v2VEthOamLocalInfoLoopback OBJECT-TYPE
   SYNTAX      INTEGER
               {
               notSupported (0),
               supported (1)
               }
   MAX-ACCESS  read-only
   STATUS      current
   DESCRIPTION
      "Path: virtualEthernet.status.oam.localInfo.loopback

       Possibilities:
               notSupported   (0)
               supported   (1)"
   ::= {sr1645v2VEthOamEntry 50855936}

sr1645v2VEthOamLocalInfoUnidirectional OBJECT-TYPE
   SYNTAX      INTEGER
               {
               notSupported (0),
               supported (1)
               }
   MAX-ACCESS  read-only
   STATUS      current
   DESCRIPTION
      "Path: virtualEthernet.status.oam.localInfo.unidirectional

       Possibilities:
               notSupported   (0)
               supported   (1)"
   ::= {sr1645v2VEthOamEntry 50921472}

sr1645v2VEthOamLocalInfoMode OBJECT-TYPE
   SYNTAX      INTEGER
               {
               passive (0),
               active (1)
               }
   MAX-ACCESS  read-only
   STATUS      current
   DESCRIPTION
      "Path: virtualEthernet.status.oam.localInfo.mode

       Possibilities:
               passive   (0)
               active   (1)"
   ::= {sr1645v2VEthOamEntry 50987008}

sr1645v2VEthOamLocalInfoMaxPduSize OBJECT-TYPE
   SYNTAX      Integer32
   MAX-ACCESS  read-only
   STATUS      current
   DESCRIPTION
      "Path: virtualEthernet.status.oam.localInfo.maxPduSize"
   ::= {sr1645v2VEthOamEntry 51052544}

sr1645v2VEthOamRemoteInfoVersion OBJECT-TYPE
   SYNTAX      Integer32
   MAX-ACCESS  read-only
   STATUS      current
   DESCRIPTION
      "Path: virtualEthernet.status.oam.remoteInfo.version"
   ::= {sr1645v2VEthOamEntry 67174400}

sr1645v2VEthOamRemoteInfoRevision OBJECT-TYPE
   SYNTAX      Integer32
   MAX-ACCESS  read-only
   STATUS      current
   DESCRIPTION
      "Path: virtualEthernet.status.oam.remoteInfo.revision"
   ::= {sr1645v2VEthOamEntry 67239936}

sr1645v2VEthOamRemoteInfoStateMuxAction OBJECT-TYPE
   SYNTAX      INTEGER
               {
               forwarding (0),
               discarding (1)
               }
   MAX-ACCESS  read-only
   STATUS      current
   DESCRIPTION
      "Path: virtualEthernet.status.oam.remoteInfo.state.muxAction

       Possibilities:
               forwarding   (0)
               discarding   (1)"
   ::= {sr1645v2VEthOamEntry 67305728}

sr1645v2VEthOamRemoteInfoStateParserAction OBJECT-TYPE
   SYNTAX      INTEGER
               {
               forwarding (0),
               loopback (1),
               discarding (2),
               reserved (3)
               }
   MAX-ACCESS  read-only
   STATUS      current
   DESCRIPTION
      "Path: virtualEthernet.status.oam.remoteInfo.state.parserAction

       Possibilities:
               forwarding   (0)
               loopback   (1)
               discarding   (2)
               reserved   (3)"
   ::= {sr1645v2VEthOamEntry 67305984}

sr1645v2VEthOamRemoteInfoOui OBJECT-TYPE
   SYNTAX      OCTET STRING
   MAX-ACCESS  read-only
   STATUS      current
   DESCRIPTION
      "Path: virtualEthernet.status.oam.remoteInfo.oui"
   ::= {sr1645v2VEthOamEntry 67371008}

sr1645v2VEthOamRemoteInfoVendorInfo OBJECT-TYPE
   SYNTAX      OCTET STRING
   MAX-ACCESS  read-only
   STATUS      current
   DESCRIPTION
      "Path: virtualEthernet.status.oam.remoteInfo.vendorInfo"
   ::= {sr1645v2VEthOamEntry 67436544}

sr1645v2VEthOamRemoteInfoVarRetrieval OBJECT-TYPE
   SYNTAX      INTEGER
               {
               notSupported (0),
               supported (1)
               }
   MAX-ACCESS  read-only
   STATUS      current
   DESCRIPTION
      "Path: virtualEthernet.status.oam.remoteInfo.varRetrieval

       Possibilities:
               notSupported   (0)
               supported   (1)"
   ::= {sr1645v2VEthOamEntry 67502080}

sr1645v2VEthOamRemoteInfoLinkEvents OBJECT-TYPE
   SYNTAX      INTEGER
               {
               ignored (0),
               interpreted (1)
               }
   MAX-ACCESS  read-only
   STATUS      current
   DESCRIPTION
      "Path: virtualEthernet.status.oam.remoteInfo.linkEvents

       Possibilities:
               ignored   (0)
               interpreted   (1)"
   ::= {sr1645v2VEthOamEntry 67567616}

sr1645v2VEthOamRemoteInfoLoopback OBJECT-TYPE
   SYNTAX      INTEGER
               {
               notSupported (0),
               supported (1)
               }
   MAX-ACCESS  read-only
   STATUS      current
   DESCRIPTION
      "Path: virtualEthernet.status.oam.remoteInfo.loopback

       Possibilities:
               notSupported   (0)
               supported   (1)"
   ::= {sr1645v2VEthOamEntry 67633152}

sr1645v2VEthOamRemoteInfoUnidirectional OBJECT-TYPE
   SYNTAX      INTEGER
               {
               notSupported (0),
               supported (1)
               }
   MAX-ACCESS  read-only
   STATUS      current
   DESCRIPTION
      "Path: virtualEthernet.status.oam.remoteInfo.unidirectional

       Possibilities:
               notSupported   (0)
               supported   (1)"
   ::= {sr1645v2VEthOamEntry 67698688}

sr1645v2VEthOamRemoteInfoMode OBJECT-TYPE
   SYNTAX      INTEGER
               {
               passive (0),
               active (1)
               }
   MAX-ACCESS  read-only
   STATUS      current
   DESCRIPTION
      "Path: virtualEthernet.status.oam.remoteInfo.mode

       Possibilities:
               passive   (0)
               active   (1)"
   ::= {sr1645v2VEthOamEntry 67764224}

sr1645v2VEthOamRemoteInfoMaxPduSize OBJECT-TYPE
   SYNTAX      Integer32
   MAX-ACCESS  read-only
   STATUS      current
   DESCRIPTION
      "Path: virtualEthernet.status.oam.remoteInfo.maxPduSize"
   ::= {sr1645v2VEthOamEntry 67829760}

sr1645v2VEthOamEventsErroredSymbolWindow OBJECT-TYPE
   SYNTAX      Integer32
   UNITS       "symbols"
   MAX-ACCESS  read-only
   STATUS      current
   DESCRIPTION
      "Path: virtualEthernet.status.oam.events.erroredSymbol.window

       unit name = symbols"
   ::= {sr1645v2VEthOamEntry 83951872}

sr1645v2VEthOamEventsErroredSymbolThreshold OBJECT-TYPE
   SYNTAX      OCTET STRING
   UNITS       "symbols"
   MAX-ACCESS  read-only
   STATUS      current
   DESCRIPTION
      "Path: virtualEthernet.status.oam.events.erroredSymbol.threshold

       unit name = symbols"
   ::= {sr1645v2VEthOamEntry 83952128}

sr1645v2VEthOamEventsErroredFramePeriodWindow OBJECT-TYPE
   SYNTAX      INTEGER
               {
               default (0)
               }
   UNITS       "frames"
   MAX-ACCESS  read-only
   STATUS      current
   DESCRIPTION
      "Path: virtualEthernet.status.oam.events.erroredFramePeriod.window

       unit name = frames

       Possibilities:
               default   (0)"
   ::= {sr1645v2VEthOamEntry 84017408}

sr1645v2VEthOamEventsErroredFramePeriodThreshold OBJECT-TYPE
   SYNTAX      Integer32
   UNITS       "frames"
   MAX-ACCESS  read-only
   STATUS      current
   DESCRIPTION
      "Path: virtualEthernet.status.oam.events.erroredFramePeriod.threshold

       unit name = frames"
   ::= {sr1645v2VEthOamEntry 84017664}

sr1645v2VEthOamEventsErroredFrameWindow OBJECT-TYPE
   SYNTAX      Integer32
   UNITS       "100msec"
   MAX-ACCESS  read-only
   STATUS      current
   DESCRIPTION
      "Path: virtualEthernet.status.oam.events.erroredFrame.window

       unit name = 100msec"
   ::= {sr1645v2VEthOamEntry 84082944}

sr1645v2VEthOamEventsErroredFrameThreshold OBJECT-TYPE
   SYNTAX      Integer32
   UNITS       "frames"
   MAX-ACCESS  read-only
   STATUS      current
   DESCRIPTION
      "Path: virtualEthernet.status.oam.events.erroredFrame.threshold

       unit name = frames"
   ::= {sr1645v2VEthOamEntry 84083200}

sr1645v2VEthOamEventsErroredFrameSecondsWindow OBJECT-TYPE
   SYNTAX      Integer32
   UNITS       "100msec"
   MAX-ACCESS  read-only
   STATUS      current
   DESCRIPTION
      "Path: virtualEthernet.status.oam.events.erroredFrameSeconds.window

       unit name = 100msec"
   ::= {sr1645v2VEthOamEntry 84148480}

sr1645v2VEthOamEventsErroredFrameSecondsThreshold OBJECT-TYPE
   SYNTAX      Integer32
   UNITS       "frames"
   MAX-ACCESS  read-only
   STATUS      current
   DESCRIPTION
      "Path: virtualEthernet.status.oam.events.erroredFrameSeconds.threshold

       unit name = frames"
   ::= {sr1645v2VEthOamEntry 84148736}


sr1645v2VEthOamEventLog OBJECT IDENTIFIER ::= {sr1645v2VEth 911}

sr1645v2VEthOamEventLogSSCTable OBJECT-TYPE
   SYNTAX      SEQUENCE OF Sr1645v2VEthOamEventLogEntry
   MAX-ACCESS  not-accessible
   STATUS      current
   DESCRIPTION
      "OAM event log"
   ::= {sr1645v2VEthOamEventLog 1}

sr1645v2VEthOamEventLogEntry OBJECT-TYPE
   SYNTAX      Sr1645v2VEthOamEventLogEntry
   MAX-ACCESS  not-accessible
   STATUS      current
   DESCRIPTION
      ""
   INDEX      { sr1645v2VEthOamEventLogGlobalIx,
                sr1645v2VEthOamEventLogTableIx }
   ::= {sr1645v2VEthOamEventLogSSCTable 1}

Sr1645v2VEthOamEventLogEntry ::=
   SEQUENCE
      {
      sr1645v2VEthOamEventLogGlobalIx
         GlobalIndex,
      sr1645v2VEthOamEventLogTableIx
         TableIndex,
      sr1645v2VEthOamEventLogSysUpTime
         TimeTicks,
      sr1645v2VEthOamEventLogLocation
         INTEGER,
      sr1645v2VEthOamEventLogType
         INTEGER,
      sr1645v2VEthOamEventLogOui
         OCTET STRING,
      sr1645v2VEthOamEventLogWindow
         Counter64,
      sr1645v2VEthOamEventLogThreshold
         Counter64,
      sr1645v2VEthOamEventLogTotal
         Counter32,
      sr1645v2VEthOamEventLogValue
         Counter64,
      sr1645v2VEthOamEventLogRunningTotal
         Counter64
      }

sr1645v2VEthOamEventLogGlobalIx OBJECT-TYPE
   SYNTAX      GlobalIndex
   MAX-ACCESS  not-accessible
   STATUS      current
   DESCRIPTION
      "The value of the tlsCntTreeGlobalIndex of the MANAGED OBJECT."
   ::= {sr1645v2VEthOamEventLogEntry 10}

sr1645v2VEthOamEventLogTableIx OBJECT-TYPE
   SYNTAX      TableIndex
   MAX-ACCESS  not-accessible
   STATUS      current
   DESCRIPTION
      ""
   ::= {sr1645v2VEthOamEventLogEntry 11}

sr1645v2VEthOamEventLogSysUpTime OBJECT-TYPE
   SYNTAX      TimeTicks
   MAX-ACCESS  read-only
   STATUS      current
   DESCRIPTION
      "Path: virtualEthernet.status.oamEventLog.sysUpTime

       Time in centi-second."
   ::= {sr1645v2VEthOamEventLogEntry 16777216}

sr1645v2VEthOamEventLogLocation OBJECT-TYPE
   SYNTAX      INTEGER
               {
               local (1),
               remote (2)
               }
   MAX-ACCESS  read-only
   STATUS      current
   DESCRIPTION
      "Path: virtualEthernet.status.oamEventLog.location

       Possibilities:
               local   (1)
               remote   (2)"
   ::= {sr1645v2VEthOamEventLogEntry 33554432}

sr1645v2VEthOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: virtualEthernet.status.oamEventLog.type

       Possibilities:
               erroredSymbols   (1)
               erroredFramePeriod   (2)
               erroredFrame   (3)
               erroredFrameSeconds   (4)
               linkFault   (256)
               dyingGasp   (257)
               criticalLink   (258)"
   ::= {sr1645v2VEthOamEventLogEntry 50331648}

sr1645v2VEthOamEventLogOui OBJECT-TYPE
   SYNTAX      OCTET STRING
   MAX-ACCESS  read-only
   STATUS      current
   DESCRIPTION
      "Path: virtualEthernet.status.oamEventLog.oui"
   ::= {sr1645v2VEthOamEventLogEntry 67108864}

sr1645v2VEthOamEventLogWindow OBJECT-TYPE
   SYNTAX      Counter64
   MAX-ACCESS  read-only
   STATUS      current
   DESCRIPTION
      "Path: virtualEthernet.status.oamEventLog.window

       64 bit unsigned wrappable counter."
   ::= {sr1645v2VEthOamEventLogEntry 83886080}

sr1645v2VEthOamEventLogThreshold OBJECT-TYPE
   SYNTAX      Counter64
   MAX-ACCESS  read-only
   STATUS      current
   DESCRIPTION
      "Path: virtualEthernet.status.oamEventLog.threshold

       64 bit unsigned wrappable counter."
   ::= {sr1645v2VEthOamEventLogEntry 100663296}

sr1645v2VEthOamEventLogTotal OBJECT-TYPE
   SYNTAX      Counter32
   MAX-ACCESS  read-only
   STATUS      current
   DESCRIPTION
      "Path: virtualEthernet.status.oamEventLog.total

       32 bit unsigned wrappable counter."
   ::= {sr1645v2VEthOamEventLogEntry 117440512}

sr1645v2VEthOamEventLogValue OBJECT-TYPE
   SYNTAX      Counter64
   MAX-ACCESS  read-only
   STATUS      current
   DESCRIPTION
      "Path: virtualEthernet.status.oamEventLog.value

       64 bit unsigned wrappable counter."
   ::= {sr1645v2VEthOamEventLogEntry 134217728}

sr1645v2VEthOamEventLogRunningTotal OBJECT-TYPE
   SYNTAX      Counter64
   MAX-ACCESS  read-only
   STATUS      current
   DESCRIPTION
      "Path: virtualEthernet.status.oamEventLog.runningTotal

       64 bit unsigned wrappable counter."
   ::= {sr1645v2VEthOamEventLogEntry 150994944}


sr1645v2VEthVlan OBJECT IDENTIFIER ::= {sr1645v2VEth 34}

sr1645v2VEthVlanSSCTable OBJECT-TYPE
   SYNTAX      SEQUENCE OF Sr1645v2VEthVlanEntry
   MAX-ACCESS  not-accessible
   STATUS      current
   DESCRIPTION
      ""
   ::= {sr1645v2VEthVlan 1}

sr1645v2VEthVlanEntry OBJECT-TYPE
   SYNTAX      Sr1645v2VEthVlanEntry
   MAX-ACCESS  not-accessible
   STATUS      current
   DESCRIPTION
      ""
   INDEX      { sr1645v2VEthVlanGlobalIx,
                sr1645v2VEthVlanTableIx }
   ::= {sr1645v2VEthVlanSSCTable 1}

Sr1645v2VEthVlanEntry ::=
   SEQUENCE
      {
      sr1645v2VEthVlanGlobalIx
         GlobalIndex,
      sr1645v2VEthVlanTableIx
         TableIndex,
      sr1645v2VEthVlanName
         DisplayString,
      sr1645v2VEthVlanMode
         INTEGER,
      sr1645v2VEthVlanIfOperStatus
         INTEGER,
      sr1645v2VEthVlanIfLastChange
         TimeTicks,
      sr1645v2VEthVlanIfLastChangeDate
         DisplayString,
      sr1645v2VEthVlanIpAddress
         IpAddress,
      sr1645v2VEthVlanIpNetMask
         IpAddress,
      sr1645v2VEthVlanIpRemote
         IpAddress,
      sr1645v2VEthVlanIpDhcpStatus
         INTEGER,
      sr1645v2VEthVlanIpDhcpLeaseTime
         TimeTicks,
      sr1645v2VEthVlanIpV6State
         INTEGER,
      sr1645v2VEthVlanIpV6InterfaceId
         OCTET STRING,
      sr1645v2VEthVlanIpV6LinkMtu
         Integer32,
      sr1645v2VEthVlanIpV6HopLimit
         Integer32,
      sr1645v2VEthVlanIpV6DhcpIaid
         Counter32,
      sr1645v2VEthVlanIpV6RaRcvOption
         Integer32,
      sr1645v2VEthVlanBridgingStatus
         INTEGER,
      sr1645v2VEthVlanBridgingSpanningTreePortRole
         INTEGER,
      sr1645v2VEthVlanBridgingSpanningTreePortId
         Integer32,
      sr1645v2VEthVlanBridgingSpanningTreePpCostExtPathCost
         Integer32,
      sr1645v2VEthVlanBridgingSpanningTreePpCostIntPathCost
         Integer32,
      sr1645v2VEthVlanBridgingSpanningTreeExtRpCost
         Integer32,
      sr1645v2VEthVlanBridgingSpanningTreeIntRpCost
         Integer32,
      sr1645v2VEthVlanBridgingSpanningTreeDesBrIdPriority
         Integer32,
      sr1645v2VEthVlanBridgingSpanningTreeDesBrIdMacAddress
         OCTET STRING,
      sr1645v2VEthVlanBridgingSpanningTreeDesPrtId
         Integer32,
      sr1645v2VEthVlanBridgingSpanningTreeDesInt
         INTEGER,
      sr1645v2VEthVlanBridgingSpanningTreeEdgeDetection
         INTEGER,
      sr1645v2VEthVlanVlanVid
         Integer32,
      sr1645v2VEthVlanPppOEthDiscState
         INTEGER,
      sr1645v2VEthVlanPppOEthPeerMac
         OCTET STRING,
      sr1645v2VEthVlanPppOEthServiceName
         DisplayString,
      sr1645v2VEthVlanPppLcpState
         INTEGER,
      sr1645v2VEthVlanPppIpcpState
         INTEGER,
      sr1645v2VEthVlanPppIp6cpState
         INTEGER,
      sr1645v2VEthVlanPppMyAutSt
         INTEGER,
      sr1645v2VEthVlanPppHisAutSt
         INTEGER,
      sr1645v2VEthVlanPppMru
         Integer32
      }

sr1645v2VEthVlanGlobalIx OBJECT-TYPE
   SYNTAX      GlobalIndex
   MAX-ACCESS  not-accessible
   STATUS      current
   DESCRIPTION
      "The value of the tlsCntTreeGlobalIndex of the MANAGED OBJECT."
   ::= {sr1645v2VEthVlanEntry 10}

sr1645v2VEthVlanTableIx OBJECT-TYPE
   SYNTAX      TableIndex
   MAX-ACCESS  not-accessible
   STATUS      current
   DESCRIPTION
      ""
   ::= {sr1645v2VEthVlanEntry 11}

sr1645v2VEthVlanName OBJECT-TYPE
   SYNTAX      DisplayString
   MAX-ACCESS  read-only
   STATUS      current
   DESCRIPTION
      "Path: virtualEthernet.status.vlan.name"
   ::= {sr1645v2VEthVlanEntry 16777216}

sr1645v2VEthVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: virtualEthernet.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2VEthVlanEntry 335544320}

sr1645v2VEthVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.vlan.ifOperStatus

       Possibilities:
               up   (1)
               down   (2)
               testing   (3)
               unknown   (4)
               dormant   (5)
               notPresent   (6)
               lowerLayerDown   (7)"
   ::= {sr1645v2VEthVlanEntry 1795162112}

sr1645v2VEthVlanIfLastChange OBJECT-TYPE
   SYNTAX      TimeTicks
   MAX-ACCESS  read-only
   STATUS      current
   DESCRIPTION
      "Path: virtualEthernet.status.vlan.ifLastChange

       Time in centi-second."
   ::= {sr1645v2VEthVlanEntry 1811939328}

sr1645v2VEthVlanIfLastChangeDate OBJECT-TYPE
   SYNTAX      DisplayString
   MAX-ACCESS  read-only
   STATUS      current
   DESCRIPTION
      "Path: virtualEthernet.status.vlan.ifLastChangeDate"
   ::= {sr1645v2VEthVlanEntry 3070230528}

sr1645v2VEthVlanIpAddress OBJECT-TYPE
   SYNTAX      IpAddress
   MAX-ACCESS  read-only
   STATUS      current
   DESCRIPTION
      "Path: virtualEthernet.status.vlan.ip.address"
   ::= {sr1645v2VEthVlanEntry 51380224}

sr1645v2VEthVlanIpNetMask OBJECT-TYPE
   SYNTAX      IpAddress
   MAX-ACCESS  read-only
   STATUS      current
   DESCRIPTION
      "Path: virtualEthernet.status.vlan.ip.netMask"
   ::= {sr1645v2VEthVlanEntry 51445760}

sr1645v2VEthVlanIpRemote OBJECT-TYPE
   SYNTAX      IpAddress
   MAX-ACCESS  read-only
   STATUS      current
   DESCRIPTION
      "Path: virtualEthernet.status.vlan.ip.remote"
   ::= {sr1645v2VEthVlanEntry 51511296}

sr1645v2VEthVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: virtualEthernet.status.vlan.ip.dhcp.status

       Possibilities:
               none   (0)
               selecting   (1)
               requesting   (2)
               rebinding   (3)
               bound   (4)
               renewing   (5)
               rebooting   (6)
               initreboot   (7)"
   ::= {sr1645v2VEthVlanEntry 51904768}

sr1645v2VEthVlanIpDhcpLeaseTime OBJECT-TYPE
   SYNTAX      TimeTicks
   MAX-ACCESS  read-only
   STATUS      current
   DESCRIPTION
      "Path: virtualEthernet.status.vlan.ip.dhcp.leaseTime

       Time in centi-second."
   ::= {sr1645v2VEthVlanEntry 51905024}

sr1645v2VEthVlanIpV6State OBJECT-TYPE
   SYNTAX      INTEGER
               {
               disabled (0),
               enabled (1)
               }
   MAX-ACCESS  read-only
   STATUS      current
   DESCRIPTION
      "Path: virtualEthernet.status.vlan.ipV6.state

       Possibilities:
               disabled   (0)
               enabled   (1)"
   ::= {sr1645v2VEthVlanEntry 100728832}

sr1645v2VEthVlanIpV6InterfaceId OBJECT-TYPE
   SYNTAX      OCTET STRING
   MAX-ACCESS  read-only
   STATUS      current
   DESCRIPTION
      "Path: virtualEthernet.status.vlan.ipV6.interfaceId"
   ::= {sr1645v2VEthVlanEntry 100794368}

sr1645v2VEthVlanIpV6LinkMtu OBJECT-TYPE
   SYNTAX      Integer32
   MAX-ACCESS  read-only
   STATUS      current
   DESCRIPTION
      "Path: virtualEthernet.status.vlan.ipV6.linkMtu"
   ::= {sr1645v2VEthVlanEntry 100925440}

sr1645v2VEthVlanIpV6HopLimit OBJECT-TYPE
   SYNTAX      Integer32
   MAX-ACCESS  read-only
   STATUS      current
   DESCRIPTION
      "Path: virtualEthernet.status.vlan.ipV6.hopLimit"
   ::= {sr1645v2VEthVlanEntry 100990976}

sr1645v2VEthVlanIpV6DhcpIaid OBJECT-TYPE
   SYNTAX      Counter32
   MAX-ACCESS  read-only
   STATUS      current
   DESCRIPTION
      "Path: virtualEthernet.status.vlan.ipV6.dhcp.iaid

       32 bit unsigned wrappable counter."
   ::= {sr1645v2VEthVlanEntry 101056768}

sr1645v2VEthVlanIpV6RaRcvOption OBJECT-TYPE
   SYNTAX      Integer32
   MAX-ACCESS  read-only
   STATUS      current
   DESCRIPTION
      "Path: virtualEthernet.status.vlan.ipV6.raRcvOption

       Bit meanings:
               bit 0 = linkMtu,
               bit 1 = srcLinkLayer,
               bit 2 = prefixInfo,
               bit 3 = rdnss,
               bit 4 = dnssl"
   ::= {sr1645v2VEthVlanEntry 101122048}

sr1645v2VEthVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: virtualEthernet.status.vlan.bridging.status

       Possibilities:
               disabled   (0)
               discarding   (1)
               learning   (2)
               forwarding   (3)
               backupBlockedIntfDown   (256)
               backupBlockedIntfUp   (259)
               shutdown   (255)"
   ::= {sr1645v2VEthVlanEntry 453050368}

sr1645v2VEthVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: virtualEthernet.status.vlan.bridging.spanningTree.portRole

       Possibilities:
               none   (0)
               root   (1)
               designated   (2)
               alternate   (3)
               backup   (4)
               disabled   (5)
               master   (6)"
   ::= {sr1645v2VEthVlanEntry 453116160}

sr1645v2VEthVlanBridgingSpanningTreePortId OBJECT-TYPE
   SYNTAX      Integer32
   MAX-ACCESS  read-only
   STATUS      current
   DESCRIPTION
      "Path: virtualEthernet.status.vlan.bridging.spanningTree.portId"
   ::= {sr1645v2VEthVlanEntry 453116416}

sr1645v2VEthVlanBridgingSpanningTreePpCostExtPathCost OBJECT-TYPE
   SYNTAX      Integer32
   MAX-ACCESS  read-only
   STATUS      current
   DESCRIPTION
      "Path: virtualEthernet.status.vlan.bridging.spanningTree.portPathCosts.extPathCost"
   ::= {sr1645v2VEthVlanEntry 453116673}

sr1645v2VEthVlanBridgingSpanningTreePpCostIntPathCost OBJECT-TYPE
   SYNTAX      Integer32
   MAX-ACCESS  read-only
   STATUS      current
   DESCRIPTION
      "Path: virtualEthernet.status.vlan.bridging.spanningTree.portPathCosts.intPathCost"
   ::= {sr1645v2VEthVlanEntry 453116674}

sr1645v2VEthVlanBridgingSpanningTreeExtRpCost OBJECT-TYPE
   SYNTAX      Integer32
   MAX-ACCESS  read-only
   STATUS      current
   DESCRIPTION
      "Path: virtualEthernet.status.vlan.bridging.spanningTree.extRootPathCost"
   ::= {sr1645v2VEthVlanEntry 453116928}

sr1645v2VEthVlanBridgingSpanningTreeIntRpCost OBJECT-TYPE
   SYNTAX      Integer32
   MAX-ACCESS  read-only
   STATUS      current
   DESCRIPTION
      "Path: virtualEthernet.status.vlan.bridging.spanningTree.intRootPathCost"
   ::= {sr1645v2VEthVlanEntry 453117184}

sr1645v2VEthVlanBridgingSpanningTreeDesBrIdPriority OBJECT-TYPE
   SYNTAX      Integer32
   MAX-ACCESS  read-only
   STATUS      current
   DESCRIPTION
      "Path: virtualEthernet.status.vlan.bridging.spanningTree.designatedBridgeId.priority"
   ::= {sr1645v2VEthVlanEntry 453117441}

sr1645v2VEthVlanBridgingSpanningTreeDesBrIdMacAddress OBJECT-TYPE
   SYNTAX      OCTET STRING
   MAX-ACCESS  read-only
   STATUS      current
   DESCRIPTION
      "Path: virtualEthernet.status.vlan.bridging.spanningTree.designatedBridgeId.macAddress

       MAC address."
   ::= {sr1645v2VEthVlanEntry 453117442}

sr1645v2VEthVlanBridgingSpanningTreeDesPrtId OBJECT-TYPE
   SYNTAX      Integer32
   MAX-ACCESS  read-only
   STATUS      current
   DESCRIPTION
      "Path: virtualEthernet.status.vlan.bridging.spanningTree.designatedPortId"
   ::= {sr1645v2VEthVlanEntry 453117696}

sr1645v2VEthVlanBridgingSpanningTreeDesInt OBJECT-TYPE
   SYNTAX      INTEGER
               {
               no (0),
               yes (1)
               }
   MAX-ACCESS  read-only
   STATUS      current
   DESCRIPTION
      "Path: virtualEthernet.status.vlan.bridging.spanningTree.designatedOrInternal

       Possibilities:
               no   (0)
               yes   (1)"
   ::= {sr1645v2VEthVlanEntry 453117952}

sr1645v2VEthVlanBridgingSpanningTreeEdgeDetection OBJECT-TYPE
   SYNTAX      INTEGER
               {
               none (0),
               edge (1),
               notEdge (2)
               }
   MAX-ACCESS  read-only
   STATUS      current
   DESCRIPTION
      "Path: virtualEthernet.status.vlan.bridging.spanningTree.edgeDetection

       Possibilities:
               none   (0)
               edge   (1)
               notEdge   (2)"
   ::= {sr1645v2VEthVlanEntry 453118208}

sr1645v2VEthVlanVlanVid OBJECT-TYPE
   SYNTAX      Integer32
   MAX-ACCESS  read-only
   STATUS      current
   DESCRIPTION
      "Path: virtualEthernet.status.vlan.vlan.vid"
   ::= {sr1645v2VEthVlanEntry 234946560}

sr1645v2VEthVlanPppOEthDiscState OBJECT-TYPE
   SYNTAX      INTEGER
               {
               idle (0),
               waitForPADO (1),
               waitForPADS (2),
               established (3)
               }
   MAX-ACCESS  read-only
   STATUS      current
   DESCRIPTION
      "Path: virtualEthernet.status.vlan.pppOverEth.discState

       Possibilities:
               idle   (0)
               waitForPADO   (1)
               waitForPADS   (2)
               established   (3)"
   ::= {sr1645v2VEthVlanEntry 67174400}

sr1645v2VEthVlanPppOEthPeerMac OBJECT-TYPE
   SYNTAX      OCTET STRING
   MAX-ACCESS  read-only
   STATUS      current
   DESCRIPTION
      "Path: virtualEthernet.status.vlan.pppOverEth.remoteMacAddress

       MAC address."
   ::= {sr1645v2VEthVlanEntry 67239936}

sr1645v2VEthVlanPppOEthServiceName OBJECT-TYPE
   SYNTAX      DisplayString
   MAX-ACCESS  read-only
   STATUS      current
   DESCRIPTION
      "Path: virtualEthernet.status.vlan.pppOverEth.serviceName"
   ::= {sr1645v2VEthVlanEntry 67305472}

sr1645v2VEthVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2VEthVlanEntry 83951616}

sr1645v2VEthVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2VEthVlanEntry 84017152}

sr1645v2VEthVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2VEthVlanEntry 84869120}

sr1645v2VEthVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: virtualEthernet.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2VEthVlanEntry 84541440}

sr1645v2VEthVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: virtualEthernet.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2VEthVlanEntry 84606976}

sr1645v2VEthVlanPppMru OBJECT-TYPE
   SYNTAX      Integer32
   MAX-ACCESS  read-only
   STATUS      current
   DESCRIPTION
      "Path: virtualEthernet.status.vlan.ppp.mru"
   ::= {sr1645v2VEthVlanEntry 84934656}

sr1645v2VEthVlanIpSecondaryIp OBJECT-TYPE
   SYNTAX      SEQUENCE OF Sr1645v2VEthVlanIpSecondaryIpEntry
   MAX-ACCESS  not-accessible
   STATUS      current
   DESCRIPTION
      ""
   ::= {sr1645v2VEthVlan 51838976}

sr1645v2VEthVlanIpSecondaryIpEntry OBJECT-TYPE
   SYNTAX      Sr1645v2VEthVlanIpSecondaryIpEntry
   MAX-ACCESS  not-accessible
   STATUS      current
   DESCRIPTION
      ""
   INDEX      { sr1645v2VEthVlanIpSecondaryIpGlobalIx,
                sr1645v2VEthVlanTableIx,
                sr1645v2VEthVlanIpSecondaryIpTableIx }
   ::= {sr1645v2VEthVlanIpSecondaryIp 1}

Sr1645v2VEthVlanIpSecondaryIpEntry ::=
   SEQUENCE
      {
      sr1645v2VEthVlanIpSecondaryIpGlobalIx
         GlobalIndex,
      sr1645v2VEthVlanIpSecondaryIpTableIx
         TableIndex,
      sr1645v2VEthVlanIpSecondaryIpAddress
         IpAddress,
      sr1645v2VEthVlanIpSecondaryIpNetMask
         IpAddress
      }

sr1645v2VEthVlanIpSecondaryIpGlobalIx OBJECT-TYPE
   SYNTAX      GlobalIndex
   MAX-ACCESS  not-accessible
   STATUS      current
   DESCRIPTION
      "The value of the tlsCntTreeGlobalIndex of the MANAGED OBJECT."
   ::= {sr1645v2VEthVlanIpSecondaryIpEntry 10}

sr1645v2VEthVlanIpSecondaryIpTableIx OBJECT-TYPE
   SYNTAX      TableIndex
   MAX-ACCESS  not-accessible
   STATUS      current
   DESCRIPTION
      ""
   ::= {sr1645v2VEthVlanIpSecondaryIpEntry 11}

sr1645v2VEthVlanIpSecondaryIpAddress OBJECT-TYPE
   SYNTAX      IpAddress
   MAX-ACCESS  read-only
   STATUS      current
   DESCRIPTION
      "Path: virtualEthernet.status.vlan.ip.secondaryIp.address"
   ::= {sr1645v2VEthVlanIpSecondaryIpEntry 2030043136}

sr1645v2VEthVlanIpSecondaryIpNetMask OBJECT-TYPE
   SYNTAX      IpAddress
   MAX-ACCESS  read-only
   STATUS      current
   DESCRIPTION
      "Path: virtualEthernet.status.vlan.ip.secondaryIp.netMask"
   ::= {sr1645v2VEthVlanIpSecondaryIpEntry 2063597568}

sr1645v2VEthVlanIpV6Addresses OBJECT-TYPE
   SYNTAX      SEQUENCE OF Sr1645v2VEthVlanIpV6AddressesEntry
   MAX-ACCESS  not-accessible
   STATUS      current
   DESCRIPTION
      ""
   ::= {sr1645v2VEthVlan 100859904}

sr1645v2VEthVlanIpV6AddressesEntry OBJECT-TYPE
   SYNTAX      Sr1645v2VEthVlanIpV6AddressesEntry
   MAX-ACCESS  not-accessible
   STATUS      current
   DESCRIPTION
      ""
   INDEX      { sr1645v2VEthVlanIpV6AddressesGlobalIx,
                sr1645v2VEthVlanTableIx,
                sr1645v2VEthVlanIpV6AddressesTableIx }
   ::= {sr1645v2VEthVlanIpV6Addresses 1}

Sr1645v2VEthVlanIpV6AddressesEntry ::=
   SEQUENCE
      {
      sr1645v2VEthVlanIpV6AddressesGlobalIx
         GlobalIndex,
      sr1645v2VEthVlanIpV6AddressesTableIx
         TableIndex,
      sr1645v2VEthVlanIpV6AddressesAddress
         Ipv6Address,
      sr1645v2VEthVlanIpV6AddressesPrefixLength
         Integer32,
      sr1645v2VEthVlanIpV6AddressesStatus
         INTEGER,
      sr1645v2VEthVlanIpV6AddressesOrigin
         INTEGER,
      sr1645v2VEthVlanIpV6AddressesFlagsInterfaceId
         INTEGER,
      sr1645v2VEthVlanIpV6AddressesFlagsAnycast
         INTEGER,
      sr1645v2VEthVlanIpV6AddressesTimersValidLifeTime
         TimeTicks,
      sr1645v2VEthVlanIpV6AddressesTimersPrefLifeTime
         TimeTicks
      }

sr1645v2VEthVlanIpV6AddressesGlobalIx OBJECT-TYPE
   SYNTAX      GlobalIndex
   MAX-ACCESS  not-accessible
   STATUS      current
   DESCRIPTION
      "The value of the tlsCntTreeGlobalIndex of the MANAGED OBJECT."
   ::= {sr1645v2VEthVlanIpV6AddressesEntry 10}

sr1645v2VEthVlanIpV6AddressesTableIx OBJECT-TYPE
   SYNTAX      TableIndex
   MAX-ACCESS  not-accessible
   STATUS      current
   DESCRIPTION
      ""
   ::= {sr1645v2VEthVlanIpV6AddressesEntry 11}

sr1645v2VEthVlanIpV6AddressesAddress OBJECT-TYPE
   SYNTAX      Ipv6Address
   MAX-ACCESS  read-only
   STATUS      current
   DESCRIPTION
      "Path: virtualEthernet.status.vlan.ipV6.addresses.address

       ipv6 address"
   ::= {sr1645v2VEthVlanIpV6AddressesEntry 16777216}

sr1645v2VEthVlanIpV6AddressesPrefixLength OBJECT-TYPE
   SYNTAX      Integer32
   MAX-ACCESS  read-only
   STATUS      current
   DESCRIPTION
      "Path: virtualEthernet.status.vlan.ipV6.addresses.prefixLength"
   ::= {sr1645v2VEthVlanIpV6AddressesEntry 33554432}

sr1645v2VEthVlanIpV6AddressesStatus OBJECT-TYPE
   SYNTAX      INTEGER
               {
               invalid (0),
               tentative (1),
               deprecated (2),
               preferred (3)
               }
   MAX-ACCESS  read-only
   STATUS      current
   DESCRIPTION
      "Path: virtualEthernet.status.vlan.ipV6.addresses.status

       Possibilities:
               invalid   (0)
               tentative   (1)
               deprecated   (2)
               preferred   (3)"
   ::= {sr1645v2VEthVlanIpV6AddressesEntry 50331648}

sr1645v2VEthVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: virtualEthernet.status.vlan.ipV6.addresses.origin

       Possibilities:
               unknown   (0)
               manual   (1)
               generalPrefix   (2)
               statelessAuto   (3)
               statefullAuto   (4)"
   ::= {sr1645v2VEthVlanIpV6AddressesEntry 67108864}

sr1645v2VEthVlanIpV6AddressesFlagsInterfaceId OBJECT-TYPE
   SYNTAX      INTEGER
               {
               no (0),
               yes (1)
               }
   MAX-ACCESS  read-only
   STATUS      current
   DESCRIPTION
      "Path: virtualEthernet.status.vlan.ipV6.addresses.flags.interfaceId

       Possibilities:
               no   (0)
               yes   (1)"
   ::= {sr1645v2VEthVlanIpV6AddressesEntry 83951616}

sr1645v2VEthVlanIpV6AddressesFlagsAnycast OBJECT-TYPE
   SYNTAX      INTEGER
               {
               no (0),
               yes (1)
               }
   MAX-ACCESS  read-only
   STATUS      current
   DESCRIPTION
      "Path: virtualEthernet.status.vlan.ipV6.addresses.flags.anycast

       Possibilities:
               no   (0)
               yes   (1)"
   ::= {sr1645v2VEthVlanIpV6AddressesEntry 84017152}

sr1645v2VEthVlanIpV6AddressesTimersValidLifeTime OBJECT-TYPE
   SYNTAX      TimeTicks
   MAX-ACCESS  read-only
   STATUS      current
   DESCRIPTION
      "Path: virtualEthernet.status.vlan.ipV6.addresses.timers.validLifeTime

       Time in centi-second."
   ::= {sr1645v2VEthVlanIpV6AddressesEntry 100794368}

sr1645v2VEthVlanIpV6AddressesTimersPrefLifeTime OBJECT-TYPE
   SYNTAX      TimeTicks
   MAX-ACCESS  read-only
   STATUS      current
   DESCRIPTION
      "Path: virtualEthernet.status.vlan.ipV6.addresses.timers.prefLifeTime

       Time in centi-second."
   ::= {sr1645v2VEthVlanIpV6AddressesEntry 100728832}

sr1645v2VEthVlanVlanArpCache OBJECT-TYPE
   SYNTAX      SEQUENCE OF Sr1645v2VEthVlanVlanArpCacheEntry
   MAX-ACCESS  not-accessible
   STATUS      current
   DESCRIPTION
      ""
   ::= {sr1645v2VEthVlan 235601920}

sr1645v2VEthVlanVlanArpCacheEntry OBJECT-TYPE
   SYNTAX      Sr1645v2VEthVlanVlanArpCacheEntry
   MAX-ACCESS  not-accessible
   STATUS      current
   DESCRIPTION
      ""
   INDEX      { sr1645v2VEthVlanVlanArpCacheGlobalIx,
                sr1645v2VEthVlanTableIx,
                sr1645v2VEthVlanVlanArpCacheTableIx }
   ::= {sr1645v2VEthVlanVlanArpCache 1}

Sr1645v2VEthVlanVlanArpCacheEntry ::=
   SEQUENCE
      {
      sr1645v2VEthVlanVlanArpCacheGlobalIx
         GlobalIndex,
      sr1645v2VEthVlanVlanArpCacheTableIx
         TableIndex,
      sr1645v2VEthVlanVlanArpCacheMacAddress
         OCTET STRING,
      sr1645v2VEthVlanVlanArpCacheIpAddress
         IpAddress,
      sr1645v2VEthVlanVlanArpCacheType
         INTEGER,
      sr1645v2VEthVlanVlanArpCacheTimeOut
         TimeTicks
      }

sr1645v2VEthVlanVlanArpCacheGlobalIx OBJECT-TYPE
   SYNTAX      GlobalIndex
   MAX-ACCESS  not-accessible
   STATUS      current
   DESCRIPTION
      "The value of the tlsCntTreeGlobalIndex of the MANAGED OBJECT."
   ::= {sr1645v2VEthVlanVlanArpCacheEntry 10}

sr1645v2VEthVlanVlanArpCacheTableIx OBJECT-TYPE
   SYNTAX      TableIndex
   MAX-ACCESS  not-accessible
   STATUS      current
   DESCRIPTION
      ""
   ::= {sr1645v2VEthVlanVlanArpCacheEntry 11}

sr1645v2VEthVlanVlanArpCacheMacAddress OBJECT-TYPE
   SYNTAX      OCTET STRING
   MAX-ACCESS  read-only
   STATUS      current
   DESCRIPTION
      "Path: virtualEthernet.status.vlan.vlan.arpCache.macAddress

       MAC address."
   ::= {sr1645v2VEthVlanVlanArpCacheEntry 16777216}

sr1645v2VEthVlanVlanArpCacheIpAddress OBJECT-TYPE
   SYNTAX      IpAddress
   MAX-ACCESS  read-only
   STATUS      current
   DESCRIPTION
      "Path: virtualEthernet.status.vlan.vlan.arpCache.ipAddress"
   ::= {sr1645v2VEthVlanVlanArpCacheEntry 33554432}

sr1645v2VEthVlanVlanArpCacheType OBJECT-TYPE
   SYNTAX      INTEGER
               {
               static (0),
               dynamic (1)
               }
   MAX-ACCESS  read-only
   STATUS      current
   DESCRIPTION
      "Path: virtualEthernet.status.vlan.vlan.arpCache.type

       Possibilities:
               static   (0)
               dynamic   (1)"
   ::= {sr1645v2VEthVlanVlanArpCacheEntry 50331648}

sr1645v2VEthVlanVlanArpCacheTimeOut OBJECT-TYPE
   SYNTAX      TimeTicks
   MAX-ACCESS  read-only
   STATUS      current
   DESCRIPTION
      "Path: virtualEthernet.status.vlan.vlan.arpCache.timeOut

       Time in centi-second."
   ::= {sr1645v2VEthVlanVlanArpCacheEntry 67108864}


sr1645v2VEthPppOE OBJECT IDENTIFIER ::= {sr1645v2VEth 36}

sr1645v2VEthPppOESSCTable OBJECT-TYPE
   SYNTAX      SEQUENCE OF Sr1645v2VEthPppOEEntry
   MAX-ACCESS  not-accessible
   STATUS      current
   DESCRIPTION
      ""
   ::= {sr1645v2VEthPppOE 1}

sr1645v2VEthPppOEEntry OBJECT-TYPE
   SYNTAX      Sr1645v2VEthPppOEEntry
   MAX-ACCESS  not-accessible
   STATUS      current
   DESCRIPTION
      ""
   INDEX      { sr1645v2VEthPppOEGlobalIx,
                sr1645v2VEthPppOETableIx }
   ::= {sr1645v2VEthPppOESSCTable 1}

Sr1645v2VEthPppOEEntry ::=
   SEQUENCE
      {
      sr1645v2VEthPppOEGlobalIx
         GlobalIndex,
      sr1645v2VEthPppOETableIx
         TableIndex,
      sr1645v2VEthPppOEName
         DisplayString,
      sr1645v2VEthPppOEMode
         INTEGER,
      sr1645v2VEthPppOEIfOperStatus
         INTEGER,
      sr1645v2VEthPppOEIfLastChange
         TimeTicks,
      sr1645v2VEthPppOEIfLastChangeDate
         DisplayString,
      sr1645v2VEthPppOEIpAddress
         IpAddress,
      sr1645v2VEthPppOEIpNetMask
         IpAddress,
      sr1645v2VEthPppOEIpRemote
         IpAddress,
      sr1645v2VEthPppOEPppOEthDiscState
         INTEGER,
      sr1645v2VEthPppOEPppOEthPeerMac
         OCTET STRING,
      sr1645v2VEthPppOEPppOEthServiceName
         DisplayString,
      sr1645v2VEthPppOEPppLcpState
         INTEGER,
      sr1645v2VEthPppOEPppIpcpState
         INTEGER,
      sr1645v2VEthPppOEPppIp6cpState
         INTEGER,
      sr1645v2VEthPppOEPppMyAutSt
         INTEGER,
      sr1645v2VEthPppOEPppHisAutSt
         INTEGER,
      sr1645v2VEthPppOEPppMru
         Integer32,
      sr1645v2VEthPppOEIpV6State
         INTEGER,
      sr1645v2VEthPppOEIpV6InterfaceId
         OCTET STRING,
      sr1645v2VEthPppOEIpV6LinkMtu
         Integer32,
      sr1645v2VEthPppOEIpV6HopLimit
         Integer32,
      sr1645v2VEthPppOEIpV6DhcpIaid
         Counter32,
      sr1645v2VEthPppOEIpV6RaRcvOption
         Integer32
      }

sr1645v2VEthPppOEGlobalIx OBJECT-TYPE
   SYNTAX      GlobalIndex
   MAX-ACCESS  not-accessible
   STATUS      current
   DESCRIPTION
      "The value of the tlsCntTreeGlobalIndex of the MANAGED OBJECT."
   ::= {sr1645v2VEthPppOEEntry 10}

sr1645v2VEthPppOETableIx OBJECT-TYPE
   SYNTAX      TableIndex
   MAX-ACCESS  not-accessible
   STATUS      current
   DESCRIPTION
      ""
   ::= {sr1645v2VEthPppOEEntry 11}

sr1645v2VEthPppOEName OBJECT-TYPE
   SYNTAX      DisplayString
   MAX-ACCESS  read-only
   STATUS      current
   DESCRIPTION
      "Path: virtualEthernet.status.pppoEClient.name"
   ::= {sr1645v2VEthPppOEEntry 16777216}

sr1645v2VEthPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: virtualEthernet.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2VEthPppOEEntry 335544320}

sr1645v2VEthPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.pppoEClient.ifOperStatus

       Possibilities:
               up   (1)
               down   (2)
               testing   (3)
               unknown   (4)
               dormant   (5)
               notPresent   (6)
               lowerLayerDown   (7)"
   ::= {sr1645v2VEthPppOEEntry 1795162112}

sr1645v2VEthPppOEIfLastChange OBJECT-TYPE
   SYNTAX      TimeTicks
   MAX-ACCESS  read-only
   STATUS      current
   DESCRIPTION
      "Path: virtualEthernet.status.pppoEClient.ifLastChange

       Time in centi-second."
   ::= {sr1645v2VEthPppOEEntry 1811939328}

sr1645v2VEthPppOEIfLastChangeDate OBJECT-TYPE
   SYNTAX      DisplayString
   MAX-ACCESS  read-only
   STATUS      current
   DESCRIPTION
      "Path: virtualEthernet.status.pppoEClient.ifLastChangeDate"
   ::= {sr1645v2VEthPppOEEntry 3070230528}

sr1645v2VEthPppOEIpAddress OBJECT-TYPE
   SYNTAX      IpAddress
   MAX-ACCESS  read-only
   STATUS      current
   DESCRIPTION
      "Path: virtualEthernet.status.pppoEClient.ip.address"
   ::= {sr1645v2VEthPppOEEntry 51380224}

sr1645v2VEthPppOEIpNetMask OBJECT-TYPE
   SYNTAX      IpAddress
   MAX-ACCESS  read-only
   STATUS      current
   DESCRIPTION
      "Path: virtualEthernet.status.pppoEClient.ip.netMask"
   ::= {sr1645v2VEthPppOEEntry 51445760}

sr1645v2VEthPppOEIpRemote OBJECT-TYPE
   SYNTAX      IpAddress
   MAX-ACCESS  read-only
   STATUS      current
   DESCRIPTION
      "Path: virtualEthernet.status.pppoEClient.ip.remote"
   ::= {sr1645v2VEthPppOEEntry 51511296}

sr1645v2VEthPppOEPppOEthDiscState OBJECT-TYPE
   SYNTAX      INTEGER
               {
               idle (0),
               waitForPADO (1),
               waitForPADS (2),
               established (3)
               }
   MAX-ACCESS  read-only
   STATUS      current
   DESCRIPTION
      "Path: virtualEthernet.status.pppoEClient.pppOverEth.discState

       Possibilities:
               idle   (0)
               waitForPADO   (1)
               waitForPADS   (2)
               established   (3)"
   ::= {sr1645v2VEthPppOEEntry 67174400}

sr1645v2VEthPppOEPppOEthPeerMac OBJECT-TYPE
   SYNTAX      OCTET STRING
   MAX-ACCESS  read-only
   STATUS      current
   DESCRIPTION
      "Path: virtualEthernet.status.pppoEClient.pppOverEth.remoteMacAddress

       MAC address."
   ::= {sr1645v2VEthPppOEEntry 67239936}

sr1645v2VEthPppOEPppOEthServiceName OBJECT-TYPE
   SYNTAX      DisplayString
   MAX-ACCESS  read-only
   STATUS      current
   DESCRIPTION
      "Path: virtualEthernet.status.pppoEClient.pppOverEth.serviceName"
   ::= {sr1645v2VEthPppOEEntry 67305472}

sr1645v2VEthPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2VEthPppOEEntry 83951616}

sr1645v2VEthPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2VEthPppOEEntry 84017152}

sr1645v2VEthPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2VEthPppOEEntry 84869120}

sr1645v2VEthPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: virtualEthernet.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2VEthPppOEEntry 84541440}

sr1645v2VEthPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: virtualEthernet.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2VEthPppOEEntry 84606976}

sr1645v2VEthPppOEPppMru OBJECT-TYPE
   SYNTAX      Integer32
   MAX-ACCESS  read-only
   STATUS      current
   DESCRIPTION
      "Path: virtualEthernet.status.pppoEClient.ppp.mru"
   ::= {sr1645v2VEthPppOEEntry 84934656}

sr1645v2VEthPppOEIpV6State OBJECT-TYPE
   SYNTAX      INTEGER
               {
               disabled (0),
               enabled (1)
               }
   MAX-ACCESS  read-only
   STATUS      current
   DESCRIPTION
      "Path: virtualEthernet.status.pppoEClient.ipV6.state

       Possibilities:
               disabled   (0)
               enabled   (1)"
   ::= {sr1645v2VEthPppOEEntry 100728832}

sr1645v2VEthPppOEIpV6InterfaceId OBJECT-TYPE
   SYNTAX      OCTET STRING
   MAX-ACCESS  read-only
   STATUS      current
   DESCRIPTION
      "Path: virtualEthernet.status.pppoEClient.ipV6.interfaceId"
   ::= {sr1645v2VEthPppOEEntry 100794368}

sr1645v2VEthPppOEIpV6LinkMtu OBJECT-TYPE
   SYNTAX      Integer32
   MAX-ACCESS  read-only
   STATUS      current
   DESCRIPTION
      "Path: virtualEthernet.status.pppoEClient.ipV6.linkMtu"
   ::= {sr1645v2VEthPppOEEntry 100925440}

sr1645v2VEthPppOEIpV6HopLimit OBJECT-TYPE
   SYNTAX      Integer32
   MAX-ACCESS  read-only
   STATUS      current
   DESCRIPTION
      "Path: virtualEthernet.status.pppoEClient.ipV6.hopLimit"
   ::= {sr1645v2VEthPppOEEntry 100990976}

sr1645v2VEthPppOEIpV6DhcpIaid OBJECT-TYPE
   SYNTAX      Counter32
   MAX-ACCESS  read-only
   STATUS      current
   DESCRIPTION
      "Path: virtualEthernet.status.pppoEClient.ipV6.dhcp.iaid

       32 bit unsigned wrappable counter."
   ::= {sr1645v2VEthPppOEEntry 101056768}

sr1645v2VEthPppOEIpV6RaRcvOption OBJECT-TYPE
   SYNTAX      Integer32
   MAX-ACCESS  read-only
   STATUS      current
   DESCRIPTION
      "Path: virtualEthernet.status.pppoEClient.ipV6.raRcvOption

       Bit meanings:
               bit 0 = linkMtu,
               bit 1 = srcLinkLayer,
               bit 2 = prefixInfo,
               bit 3 = rdnss,
               bit 4 = dnssl"
   ::= {sr1645v2VEthPppOEEntry 101122048}

sr1645v2VEthPppOEIpV6Addresses OBJECT-TYPE
   SYNTAX      SEQUENCE OF Sr1645v2VEthPppOEIpV6AddressesEntry
   MAX-ACCESS  not-accessible
   STATUS      current
   DESCRIPTION
      ""
   ::= {sr1645v2VEthPppOE 100859904}

sr1645v2VEthPppOEIpV6AddressesEntry OBJECT-TYPE
   SYNTAX      Sr1645v2VEthPppOEIpV6AddressesEntry
   MAX-ACCESS  not-accessible
   STATUS      current
   DESCRIPTION
      ""
   INDEX      { sr1645v2VEthPppOEIpV6AddressesGlobalIx,
                sr1645v2VEthPppOETableIx,
                sr1645v2VEthPppOEIpV6AddressesTableIx }
   ::= {sr1645v2VEthPppOEIpV6Addresses 1}

Sr1645v2VEthPppOEIpV6AddressesEntry ::=
   SEQUENCE
      {
      sr1645v2VEthPppOEIpV6AddressesGlobalIx
         GlobalIndex,
      sr1645v2VEthPppOEIpV6AddressesTableIx
         TableIndex,
      sr1645v2VEthPppOEIpV6AddressesAddress
         Ipv6Address,
      sr1645v2VEthPppOEIpV6AddressesPrefixLength
         Integer32,
      sr1645v2VEthPppOEIpV6AddressesStatus
         INTEGER,
      sr1645v2VEthPppOEIpV6AddressesOrigin
         INTEGER,
      sr1645v2VEthPppOEIpV6AddressesFlagsInterfaceId
         INTEGER,
      sr1645v2VEthPppOEIpV6AddressesFlagsAnycast
         INTEGER,
      sr1645v2VEthPppOEIpV6AddressesTimersValidLifeTime
         TimeTicks,
      sr1645v2VEthPppOEIpV6AddressesTimersPrefLifeTime
         TimeTicks
      }

sr1645v2VEthPppOEIpV6AddressesGlobalIx OBJECT-TYPE
   SYNTAX      GlobalIndex
   MAX-ACCESS  not-accessible
   STATUS      current
   DESCRIPTION
      "The value of the tlsCntTreeGlobalIndex of the MANAGED OBJECT."
   ::= {sr1645v2VEthPppOEIpV6AddressesEntry 10}

sr1645v2VEthPppOEIpV6AddressesTableIx OBJECT-TYPE
   SYNTAX      TableIndex
   MAX-ACCESS  not-accessible
   STATUS      current
   DESCRIPTION
      ""
   ::= {sr1645v2VEthPppOEIpV6AddressesEntry 11}

sr1645v2VEthPppOEIpV6AddressesAddress OBJECT-TYPE
   SYNTAX      Ipv6Address
   MAX-ACCESS  read-only
   STATUS      current
   DESCRIPTION
      "Path: virtualEthernet.status.pppoEClient.ipV6.addresses.address

       ipv6 address"
   ::= {sr1645v2VEthPppOEIpV6AddressesEntry 16777216}

sr1645v2VEthPppOEIpV6AddressesPrefixLength OBJECT-TYPE
   SYNTAX      Integer32
   MAX-ACCESS  read-only
   STATUS      current
   DESCRIPTION
      "Path: virtualEthernet.status.pppoEClient.ipV6.addresses.prefixLength"
   ::= {sr1645v2VEthPppOEIpV6AddressesEntry 33554432}

sr1645v2VEthPppOEIpV6AddressesStatus OBJECT-TYPE
   SYNTAX      INTEGER
               {
               invalid (0),
               tentative (1),
               deprecated (2),
               preferred (3)
               }
   MAX-ACCESS  read-only
   STATUS      current
   DESCRIPTION
      "Path: virtualEthernet.status.pppoEClient.ipV6.addresses.status

       Possibilities:
               invalid   (0)
               tentative   (1)
               deprecated   (2)
               preferred   (3)"
   ::= {sr1645v2VEthPppOEIpV6AddressesEntry 50331648}

sr1645v2VEthPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: virtualEthernet.status.pppoEClient.ipV6.addresses.origin

       Possibilities:
               unknown   (0)
               manual   (1)
               generalPrefix   (2)
               statelessAuto   (3)
               statefullAuto   (4)"
   ::= {sr1645v2VEthPppOEIpV6AddressesEntry 67108864}

sr1645v2VEthPppOEIpV6AddressesFlagsInterfaceId OBJECT-TYPE
   SYNTAX      INTEGER
               {
               no (0),
               yes (1)
               }
   MAX-ACCESS  read-only
   STATUS      current
   DESCRIPTION
      "Path: virtualEthernet.status.pppoEClient.ipV6.addresses.flags.interfaceId

       Possibilities:
               no   (0)
               yes   (1)"
   ::= {sr1645v2VEthPppOEIpV6AddressesEntry 83951616}

sr1645v2VEthPppOEIpV6AddressesFlagsAnycast OBJECT-TYPE
   SYNTAX      INTEGER
               {
               no (0),
               yes (1)
               }
   MAX-ACCESS  read-only
   STATUS      current
   DESCRIPTION
      "Path: virtualEthernet.status.pppoEClient.ipV6.addresses.flags.anycast

       Possibilities:
               no   (0)
               yes   (1)"
   ::= {sr1645v2VEthPppOEIpV6AddressesEntry 84017152}

sr1645v2VEthPppOEIpV6AddressesTimersValidLifeTime OBJECT-TYPE
   SYNTAX      TimeTicks
   MAX-ACCESS  read-only
   STATUS      current
   DESCRIPTION
      "Path: virtualEthernet.status.pppoEClient.ipV6.addresses.timers.validLifeTime

       Time in centi-second."
   ::= {sr1645v2VEthPppOEIpV6AddressesEntry 100794368}

sr1645v2VEthPppOEIpV6AddressesTimersPrefLifeTime OBJECT-TYPE
   SYNTAX      TimeTicks
   MAX-ACCESS  read-only
   STATUS      current
   DESCRIPTION
      "Path: virtualEthernet.status.pppoEClient.ipV6.addresses.timers.prefLifeTime

       Time in centi-second."
   ::= {sr1645v2VEthPppOEIpV6AddressesEntry 100728832}


sr1645v2VEthDot1x OBJECT IDENTIFIER ::= {sr1645v2VEth 190}

sr1645v2VEthDot1xSSCTable OBJECT-TYPE
   SYNTAX      SEQUENCE OF Sr1645v2VEthDot1xEntry
   MAX-ACCESS  not-accessible
   STATUS      current
   DESCRIPTION
      "Ethernet Switch VLAN Table"
   ::= {sr1645v2VEthDot1x 1}

sr1645v2VEthDot1xEntry OBJECT-TYPE
   SYNTAX      Sr1645v2VEthDot1xEntry
   MAX-ACCESS  not-accessible
   STATUS      current
   DESCRIPTION
      ""
   INDEX      { sr1645v2VEthDot1xGlobalIx,
                sr1645v2VEthDot1xTableIx }
   ::= {sr1645v2VEthDot1xSSCTable 1}

Sr1645v2VEthDot1xEntry ::=
   SEQUENCE
      {
      sr1645v2VEthDot1xGlobalIx
         GlobalIndex,
      sr1645v2VEthDot1xTableIx
         TableIndex,
      sr1645v2VEthDot1xRemote
         OCTET STRING,
      sr1645v2VEthDot1xAuthorized
         INTEGER,
      sr1645v2VEthDot1xAuthenticator
         INTEGER,
      sr1645v2VEthDot1xBackEnd
         INTEGER,
      sr1645v2VEthDot1xRetries
         Integer32,
      sr1645v2VEthDot1xReAuthTime
         TimeTicks,
      sr1645v2VEthDot1xHoldTime
         TimeTicks
      }

sr1645v2VEthDot1xGlobalIx OBJECT-TYPE
   SYNTAX      GlobalIndex
   MAX-ACCESS  not-accessible
   STATUS      current
   DESCRIPTION
      "The value of the tlsCntTreeGlobalIndex of the MANAGED OBJECT."
   ::= {sr1645v2VEthDot1xEntry 10}

sr1645v2VEthDot1xTableIx OBJECT-TYPE
   SYNTAX      TableIndex
   MAX-ACCESS  not-accessible
   STATUS      current
   DESCRIPTION
      ""
   ::= {sr1645v2VEthDot1xEntry 11}

sr1645v2VEthDot1xRemote OBJECT-TYPE
   SYNTAX      OCTET STRING
   MAX-ACCESS  read-only
   STATUS      current
   DESCRIPTION
      "Path: virtualEthernet.status.dot1x.remote

       MAC address."
   ::= {sr1645v2VEthDot1xEntry 16777216}

sr1645v2VEthDot1xAuthorized OBJECT-TYPE
   SYNTAX      INTEGER
               {
               no (0),
               yes (1)
               }
   MAX-ACCESS  read-only
   STATUS      current
   DESCRIPTION
      "Path: virtualEthernet.status.dot1x.authorized

       Possibilities:
               no   (0)
               yes   (1)"
   ::= {sr1645v2VEthDot1xEntry 33554432}

sr1645v2VEthDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: virtualEthernet.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2VEthDot1xEntry 50331648}

sr1645v2VEthDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: virtualEthernet.status.dot1x.backEnd

       Possibilities:
               preInit   (0)
               initialize   (1)
               idle   (2)
               request   (3)
               response   (4)
               success   (5)
               failure   (6)
               radiusTimeout   (7)
               timeout   (8)"
   ::= {sr1645v2VEthDot1xEntry 67108864}

sr1645v2VEthDot1xRetries OBJECT-TYPE
   SYNTAX      Integer32
   MAX-ACCESS  read-only
   STATUS      current
   DESCRIPTION
      "Path: virtualEthernet.status.dot1x.retries"
   ::= {sr1645v2VEthDot1xEntry 83886080}

sr1645v2VEthDot1xReAuthTime OBJECT-TYPE
   SYNTAX      TimeTicks
   MAX-ACCESS  read-only
   STATUS      current
   DESCRIPTION
      "Path: virtualEthernet.status.dot1x.reAuthTime

       Time in centi-second."
   ::= {sr1645v2VEthDot1xEntry 100663296}

sr1645v2VEthDot1xHoldTime OBJECT-TYPE
   SYNTAX      TimeTicks
   MAX-ACCESS  read-only
   STATUS      current
   DESCRIPTION
      "Path: virtualEthernet.status.dot1x.holdTime

       Time in centi-second."
   ::= {sr1645v2VEthDot1xEntry 117440512}


sr1645v2VEthIpV6 OBJECT IDENTIFIER ::= {sr1645v2VEth 17}

sr1645v2VEthIpV6SSCTable OBJECT-TYPE
   SYNTAX      SEQUENCE OF Sr1645v2VEthIpV6Entry
   MAX-ACCESS  not-accessible
   STATUS      current
   DESCRIPTION
      "IPv6 interface config parameters"
   ::= {sr1645v2VEthIpV6 1}

sr1645v2VEthIpV6Entry OBJECT-TYPE
   SYNTAX      Sr1645v2VEthIpV6Entry
   MAX-ACCESS  not-accessible
   STATUS      current
   DESCRIPTION
      ""
   INDEX      { sr1645v2VEthIpV6GlobalIx }
   ::= {sr1645v2VEthIpV6SSCTable 1}

Sr1645v2VEthIpV6Entry ::=
   SEQUENCE
      {
      sr1645v2VEthIpV6GlobalIx
         GlobalIndex,
      sr1645v2VEthIpV6State
         INTEGER,
      sr1645v2VEthIpV6InterfaceId
         OCTET STRING,
      sr1645v2VEthIpV6LinkMtu
         Integer32,
      sr1645v2VEthIpV6HopLimit
         Integer32,
      sr1645v2VEthIpV6DhcpIaid
         Counter32,
      sr1645v2VEthIpV6RaRcvOption
         Integer32
      }

sr1645v2VEthIpV6GlobalIx OBJECT-TYPE
   SYNTAX      GlobalIndex
   MAX-ACCESS  not-accessible
   STATUS      current
   DESCRIPTION
      "The value of the tlsCntTreeGlobalIndex of the MANAGED OBJECT."
   ::= {sr1645v2VEthIpV6Entry 10}

sr1645v2VEthIpV6State OBJECT-TYPE
   SYNTAX      INTEGER
               {
               disabled (0),
               enabled (1)
               }
   MAX-ACCESS  read-only
   STATUS      current
   DESCRIPTION
      "Path: virtualEthernet.status.ipV6.state

       Possibilities:
               disabled   (0)
               enabled   (1)"
   ::= {sr1645v2VEthIpV6Entry 16777216}

sr1645v2VEthIpV6InterfaceId OBJECT-TYPE
   SYNTAX      OCTET STRING
   MAX-ACCESS  read-only
   STATUS      current
   DESCRIPTION
      "Path: virtualEthernet.status.ipV6.interfaceId"
   ::= {sr1645v2VEthIpV6Entry 33554432}

sr1645v2VEthIpV6LinkMtu OBJECT-TYPE
   SYNTAX      Integer32
   MAX-ACCESS  read-only
   STATUS      current
   DESCRIPTION
      "Path: virtualEthernet.status.ipV6.linkMtu"
   ::= {sr1645v2VEthIpV6Entry 67108864}

sr1645v2VEthIpV6HopLimit OBJECT-TYPE
   SYNTAX      Integer32
   MAX-ACCESS  read-only
   STATUS      current
   DESCRIPTION
      "Path: virtualEthernet.status.ipV6.hopLimit"
   ::= {sr1645v2VEthIpV6Entry 83886080}

sr1645v2VEthIpV6DhcpIaid OBJECT-TYPE
   SYNTAX      Counter32
   MAX-ACCESS  read-only
   STATUS      current
   DESCRIPTION
      "Path: virtualEthernet.status.ipV6.dhcp.iaid

       32 bit unsigned wrappable counter."
   ::= {sr1645v2VEthIpV6Entry 100728832}

sr1645v2VEthIpV6RaRcvOption OBJECT-TYPE
   SYNTAX      Integer32
   MAX-ACCESS  read-only
   STATUS      current
   DESCRIPTION
      "Path: virtualEthernet.status.ipV6.raRcvOption

       Bit meanings:
               bit 0 = linkMtu,
               bit 1 = srcLinkLayer,
               bit 2 = prefixInfo,
               bit 3 = rdnss,
               bit 4 = dnssl"
   ::= {sr1645v2VEthIpV6Entry 117440512}

sr1645v2VEthIpV6Addresses OBJECT-TYPE
   SYNTAX      SEQUENCE OF Sr1645v2VEthIpV6AddressesEntry
   MAX-ACCESS  not-accessible
   STATUS      current
   DESCRIPTION
      ""
   ::= {sr1645v2VEthIpV6 50331648}

sr1645v2VEthIpV6AddressesEntry OBJECT-TYPE
   SYNTAX      Sr1645v2VEthIpV6AddressesEntry
   MAX-ACCESS  not-accessible
   STATUS      current
   DESCRIPTION
      ""
   INDEX      { sr1645v2VEthIpV6AddressesGlobalIx,
                sr1645v2VEthIpV6AddressesTableIx }
   ::= {sr1645v2VEthIpV6Addresses 1}

Sr1645v2VEthIpV6AddressesEntry ::=
   SEQUENCE
      {
      sr1645v2VEthIpV6AddressesGlobalIx
         GlobalIndex,
      sr1645v2VEthIpV6AddressesTableIx
         TableIndex,
      sr1645v2VEthIpV6AddressesAddress
         Ipv6Address,
      sr1645v2VEthIpV6AddressesPrefixLength
         Integer32,
      sr1645v2VEthIpV6AddressesStatus
         INTEGER,
      sr1645v2VEthIpV6AddressesOrigin
         INTEGER,
      sr1645v2VEthIpV6AddressesFlagsInterfaceId
         INTEGER,
      sr1645v2VEthIpV6AddressesFlagsAnycast
         INTEGER,
      sr1645v2VEthIpV6AddressesTimersValidLifeTime
         TimeTicks,
      sr1645v2VEthIpV6AddressesTimersPrefLifeTime
         TimeTicks
      }

sr1645v2VEthIpV6AddressesGlobalIx OBJECT-TYPE
   SYNTAX      GlobalIndex
   MAX-ACCESS  not-accessible
   STATUS      current
   DESCRIPTION
      "The value of the tlsCntTreeGlobalIndex of the MANAGED OBJECT."
   ::= {sr1645v2VEthIpV6AddressesEntry 10}

sr1645v2VEthIpV6AddressesTableIx OBJECT-TYPE
   SYNTAX      TableIndex
   MAX-ACCESS  not-accessible
   STATUS      current
   DESCRIPTION
      ""
   ::= {sr1645v2VEthIpV6AddressesEntry 11}

sr1645v2VEthIpV6AddressesAddress OBJECT-TYPE
   SYNTAX      Ipv6Address
   MAX-ACCESS  read-only
   STATUS      current
   DESCRIPTION
      "Path: virtualEthernet.status.ipV6.addresses.address

       ipv6 address"
   ::= {sr1645v2VEthIpV6AddressesEntry 16777216}

sr1645v2VEthIpV6AddressesPrefixLength OBJECT-TYPE
   SYNTAX      Integer32
   MAX-ACCESS  read-only
   STATUS      current
   DESCRIPTION
      "Path: virtualEthernet.status.ipV6.addresses.prefixLength"
   ::= {sr1645v2VEthIpV6AddressesEntry 33554432}

sr1645v2VEthIpV6AddressesStatus OBJECT-TYPE
   SYNTAX      INTEGER
               {
               invalid (0),
               tentative (1),
               deprecated (2),
               preferred (3)
               }
   MAX-ACCESS  read-only
   STATUS      current
   DESCRIPTION
      "Path: virtualEthernet.status.ipV6.addresses.status

       Possibilities:
               invalid   (0)
               tentative   (1)
               deprecated   (2)
               preferred   (3)"
   ::= {sr1645v2VEthIpV6AddressesEntry 50331648}

sr1645v2VEthIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: virtualEthernet.status.ipV6.addresses.origin

       Possibilities:
               unknown   (0)
               manual   (1)
               generalPrefix   (2)
               statelessAuto   (3)
               statefullAuto   (4)"
   ::= {sr1645v2VEthIpV6AddressesEntry 67108864}

sr1645v2VEthIpV6AddressesFlagsInterfaceId OBJECT-TYPE
   SYNTAX      INTEGER
               {
               no (0),
               yes (1)
               }
   MAX-ACCESS  read-only
   STATUS      current
   DESCRIPTION
      "Path: virtualEthernet.status.ipV6.addresses.flags.interfaceId

       Possibilities:
               no   (0)
               yes   (1)"
   ::= {sr1645v2VEthIpV6AddressesEntry 83951616}

sr1645v2VEthIpV6AddressesFlagsAnycast OBJECT-TYPE
   SYNTAX      INTEGER
               {
               no (0),
               yes (1)
               }
   MAX-ACCESS  read-only
   STATUS      current
   DESCRIPTION
      "Path: virtualEthernet.status.ipV6.addresses.flags.anycast

       Possibilities:
               no   (0)
               yes   (1)"
   ::= {sr1645v2VEthIpV6AddressesEntry 84017152}

sr1645v2VEthIpV6AddressesTimersValidLifeTime OBJECT-TYPE
   SYNTAX      TimeTicks
   MAX-ACCESS  read-only
   STATUS      current
   DESCRIPTION
      "Path: virtualEthernet.status.ipV6.addresses.timers.validLifeTime

       Time in centi-second."
   ::= {sr1645v2VEthIpV6AddressesEntry 100794368}

sr1645v2VEthIpV6AddressesTimersPrefLifeTime OBJECT-TYPE
   SYNTAX      TimeTicks
   MAX-ACCESS  read-only
   STATUS      current
   DESCRIPTION
      "Path: virtualEthernet.status.ipV6.addresses.timers.prefLifeTime

       Time in centi-second."
   ::= {sr1645v2VEthIpV6AddressesEntry 100728832}


sr1645v2VEthSnmpIndex OBJECT IDENTIFIER ::= {sr1645v2VEth 269}

sr1645v2VEthSnmpIndexTable OBJECT-TYPE
   SYNTAX      SEQUENCE OF Sr1645v2VEthSnmpIndexEntry
   MAX-ACCESS  not-accessible
   STATUS      current
   DESCRIPTION
      "SNMP index assigned to this object"
   ::= {sr1645v2VEthSnmpIndex 1}

sr1645v2VEthSnmpIndexEntry OBJECT-TYPE
   SYNTAX      Sr1645v2VEthSnmpIndexEntry
   MAX-ACCESS  not-accessible
   STATUS      current
   DESCRIPTION
      ""
   INDEX      { sr1645v2VEthSnmpIndexGlobalIx }
   ::= {sr1645v2VEthSnmpIndexTable 1}

Sr1645v2VEthSnmpIndexEntry ::=
   SEQUENCE
      {
      sr1645v2VEthSnmpIndexGlobalIx
         GlobalIndex,
      sr1645v2VEthSnmpIndexValue
         Integer32
      }

sr1645v2VEthSnmpIndexGlobalIx OBJECT-TYPE
   SYNTAX      GlobalIndex
   MAX-ACCESS  not-accessible
   STATUS      current
   DESCRIPTION
      "The value of the tlsCntTreeGlobalIndex of the MANAGED OBJECT."
   ::= {sr1645v2VEthSnmpIndexEntry 10}

sr1645v2VEthSnmpIndexValue OBJECT-TYPE
   SYNTAX      Integer32
   MAX-ACCESS  read-only
   STATUS      current
   DESCRIPTION
      "Path: virtualEthernet.status.snmpIndex"
   ::= {sr1645v2VEthSnmpIndexEntry 2147483648}



pr1645v2VEth OBJECT IDENTIFIER ::= {r1645v2VEth 12}


pr1645v2VEthInOctets OBJECT IDENTIFIER ::= {pr1645v2VEth 109}

pr1645v2VEthInOctetsTable OBJECT-TYPE
   SYNTAX      SEQUENCE OF Pr1645v2VEthInOctetsEntry
   MAX-ACCESS  not-accessible
   STATUS      current
   DESCRIPTION
      "ifInOctets"
   ::= {pr1645v2VEthInOctets 1}

pr1645v2VEthInOctetsEntry OBJECT-TYPE
   SYNTAX      Pr1645v2VEthInOctetsEntry
   MAX-ACCESS  not-accessible
   STATUS      current
   DESCRIPTION
      ""
   INDEX      { pr1645v2VEthInOctetsGlobalIx }
   ::= {pr1645v2VEthInOctetsTable 1}

Pr1645v2VEthInOctetsEntry ::=
   SEQUENCE
      {
      pr1645v2VEthInOctetsGlobalIx
         GlobalIndex,
      pr1645v2VEthInOctetsValue
         Counter64
      }

pr1645v2VEthInOctetsGlobalIx OBJECT-TYPE
   SYNTAX      GlobalIndex
   MAX-ACCESS  not-accessible
   STATUS      current
   DESCRIPTION
      "The value of the tlsCntTreeGlobalIndex of the MANAGED OBJECT."
   ::= {pr1645v2VEthInOctetsEntry 10}

pr1645v2VEthInOctetsValue OBJECT-TYPE
   SYNTAX      Counter64
   MAX-ACCESS  read-only
   STATUS      current
   DESCRIPTION
      "Path: virtualEthernet.performance.ifInOctets

       64 bit unsigned wrappable counter."
   ::= {pr1645v2VEthInOctetsEntry 2147483648}


pr1645v2VEthInUcast OBJECT IDENTIFIER ::= {pr1645v2VEth 110}

pr1645v2VEthInUcastTable OBJECT-TYPE
   SYNTAX      SEQUENCE OF Pr1645v2VEthInUcastEntry
   MAX-ACCESS  not-accessible
   STATUS      current
   DESCRIPTION
      "ifInUcastPkts"
   ::= {pr1645v2VEthInUcast 1}

pr1645v2VEthInUcastEntry OBJECT-TYPE
   SYNTAX      Pr1645v2VEthInUcastEntry
   MAX-ACCESS  not-accessible
   STATUS      current
   DESCRIPTION
      ""
   INDEX      { pr1645v2VEthInUcastGlobalIx }
   ::= {pr1645v2VEthInUcastTable 1}

Pr1645v2VEthInUcastEntry ::=
   SEQUENCE
      {
      pr1645v2VEthInUcastGlobalIx
         GlobalIndex,
      pr1645v2VEthInUcastValue
         Counter64
      }

pr1645v2VEthInUcastGlobalIx OBJECT-TYPE
   SYNTAX      GlobalIndex
   MAX-ACCESS  not-accessible
   STATUS      current
   DESCRIPTION
      "The value of the tlsCntTreeGlobalIndex of the MANAGED OBJECT."
   ::= {pr1645v2VEthInUcastEntry 10}

pr1645v2VEthInUcastValue OBJECT-TYPE
   SYNTAX      Counter64
   MAX-ACCESS  read-only
   STATUS      current
   DESCRIPTION
      "Path: virtualEthernet.performance.ifInUcastPkts

       64 bit unsigned wrappable counter."
   ::= {pr1645v2VEthInUcastEntry 2147483648}


pr1645v2VEthInNUcastPkts OBJECT IDENTIFIER ::= {pr1645v2VEth 111}

pr1645v2VEthInNUcastPktsTable OBJECT-TYPE
   SYNTAX      SEQUENCE OF Pr1645v2VEthInNUcastPktsEntry
   MAX-ACCESS  not-accessible
   STATUS      current
   DESCRIPTION
      "ifInNUcastPkts"
   ::= {pr1645v2VEthInNUcastPkts 1}

pr1645v2VEthInNUcastPktsEntry OBJECT-TYPE
   SYNTAX      Pr1645v2VEthInNUcastPktsEntry
   MAX-ACCESS  not-accessible
   STATUS      current
   DESCRIPTION
      ""
   INDEX      { pr1645v2VEthInNUcastPktsGlobalIx }
   ::= {pr1645v2VEthInNUcastPktsTable 1}

Pr1645v2VEthInNUcastPktsEntry ::=
   SEQUENCE
      {
      pr1645v2VEthInNUcastPktsGlobalIx
         GlobalIndex,
      pr1645v2VEthInNUcastPktsValue
         Counter64
      }

pr1645v2VEthInNUcastPktsGlobalIx OBJECT-TYPE
   SYNTAX      GlobalIndex
   MAX-ACCESS  not-accessible
   STATUS      current
   DESCRIPTION
      "The value of the tlsCntTreeGlobalIndex of the MANAGED OBJECT."
   ::= {pr1645v2VEthInNUcastPktsEntry 10}

pr1645v2VEthInNUcastPktsValue OBJECT-TYPE
   SYNTAX      Counter64
   MAX-ACCESS  read-only
   STATUS      current
   DESCRIPTION
      "Path: virtualEthernet.performance.ifInNUcastPkts

       64 bit unsigned wrappable counter."
   ::= {pr1645v2VEthInNUcastPktsEntry 2147483648}


pr1645v2VEthInBcastPkts OBJECT IDENTIFIER ::= {pr1645v2VEth 211}

pr1645v2VEthInBcastPktsTable OBJECT-TYPE
   SYNTAX      SEQUENCE OF Pr1645v2VEthInBcastPktsEntry
   MAX-ACCESS  not-accessible
   STATUS      current
   DESCRIPTION
      "ifInBcastPkts"
   ::= {pr1645v2VEthInBcastPkts 1}

pr1645v2VEthInBcastPktsEntry OBJECT-TYPE
   SYNTAX      Pr1645v2VEthInBcastPktsEntry
   MAX-ACCESS  not-accessible
   STATUS      current
   DESCRIPTION
      ""
   INDEX      { pr1645v2VEthInBcastPktsGlobalIx }
   ::= {pr1645v2VEthInBcastPktsTable 1}

Pr1645v2VEthInBcastPktsEntry ::=
   SEQUENCE
      {
      pr1645v2VEthInBcastPktsGlobalIx
         GlobalIndex,
      pr1645v2VEthInBcastPktsValue
         Counter64
      }

pr1645v2VEthInBcastPktsGlobalIx OBJECT-TYPE
   SYNTAX      GlobalIndex
   MAX-ACCESS  not-accessible
   STATUS      current
   DESCRIPTION
      "The value of the tlsCntTreeGlobalIndex of the MANAGED OBJECT."
   ::= {pr1645v2VEthInBcastPktsEntry 10}

pr1645v2VEthInBcastPktsValue OBJECT-TYPE
   SYNTAX      Counter64
   MAX-ACCESS  read-only
   STATUS      current
   DESCRIPTION
      "Path: virtualEthernet.performance.ifInBcastPkts

       64 bit unsigned wrappable counter."
   ::= {pr1645v2VEthInBcastPktsEntry 2147483648}


pr1645v2VEthInMcastPkts OBJECT IDENTIFIER ::= {pr1645v2VEth 221}

pr1645v2VEthInMcastPktsTable OBJECT-TYPE
   SYNTAX      SEQUENCE OF Pr1645v2VEthInMcastPktsEntry
   MAX-ACCESS  not-accessible
   STATUS      current
   DESCRIPTION
      "ifInNUcastPkts"
   ::= {pr1645v2VEthInMcastPkts 1}

pr1645v2VEthInMcastPktsEntry OBJECT-TYPE
   SYNTAX      Pr1645v2VEthInMcastPktsEntry
   MAX-ACCESS  not-accessible
   STATUS      current
   DESCRIPTION
      ""
   INDEX      { pr1645v2VEthInMcastPktsGlobalIx }
   ::= {pr1645v2VEthInMcastPktsTable 1}

Pr1645v2VEthInMcastPktsEntry ::=
   SEQUENCE
      {
      pr1645v2VEthInMcastPktsGlobalIx
         GlobalIndex,
      pr1645v2VEthInMcastPktsValue
         Counter64
      }

pr1645v2VEthInMcastPktsGlobalIx OBJECT-TYPE
   SYNTAX      GlobalIndex
   MAX-ACCESS  not-accessible
   STATUS      current
   DESCRIPTION
      "The value of the tlsCntTreeGlobalIndex of the MANAGED OBJECT."
   ::= {pr1645v2VEthInMcastPktsEntry 10}

pr1645v2VEthInMcastPktsValue OBJECT-TYPE
   SYNTAX      Counter64
   MAX-ACCESS  read-only
   STATUS      current
   DESCRIPTION
      "Path: virtualEthernet.performance.ifInMcastPkts

       64 bit unsigned wrappable counter."
   ::= {pr1645v2VEthInMcastPktsEntry 2147483648}


pr1645v2VEthInDiscards OBJECT IDENTIFIER ::= {pr1645v2VEth 112}

pr1645v2VEthInDiscardsTable OBJECT-TYPE
   SYNTAX      SEQUENCE OF Pr1645v2VEthInDiscardsEntry
   MAX-ACCESS  not-accessible
   STATUS      current
   DESCRIPTION
      "ifInDiscards"
   ::= {pr1645v2VEthInDiscards 1}

pr1645v2VEthInDiscardsEntry OBJECT-TYPE
   SYNTAX      Pr1645v2VEthInDiscardsEntry
   MAX-ACCESS  not-accessible
   STATUS      current
   DESCRIPTION
      ""
   INDEX      { pr1645v2VEthInDiscardsGlobalIx }
   ::= {pr1645v2VEthInDiscardsTable 1}

Pr1645v2VEthInDiscardsEntry ::=
   SEQUENCE
      {
      pr1645v2VEthInDiscardsGlobalIx
         GlobalIndex,
      pr1645v2VEthInDiscardsValue
         Counter64
      }

pr1645v2VEthInDiscardsGlobalIx OBJECT-TYPE
   SYNTAX      GlobalIndex
   MAX-ACCESS  not-accessible
   STATUS      current
   DESCRIPTION
      "The value of the tlsCntTreeGlobalIndex of the MANAGED OBJECT."
   ::= {pr1645v2VEthInDiscardsEntry 10}

pr1645v2VEthInDiscardsValue OBJECT-TYPE
   SYNTAX      Counter64
   MAX-ACCESS  read-only
   STATUS      current
   DESCRIPTION
      "Path: virtualEthernet.performance.ifInDiscards

       64 bit unsigned wrappable counter."
   ::= {pr1645v2VEthInDiscardsEntry 2147483648}


pr1645v2VEthInErrors OBJECT IDENTIFIER ::= {pr1645v2VEth 113}

pr1645v2VEthInErrorsTable OBJECT-TYPE
   SYNTAX      SEQUENCE OF Pr1645v2VEthInErrorsEntry
   MAX-ACCESS  not-accessible
   STATUS      current
   DESCRIPTION
      "ifInErrors"
   ::= {pr1645v2VEthInErrors 1}

pr1645v2VEthInErrorsEntry OBJECT-TYPE
   SYNTAX      Pr1645v2VEthInErrorsEntry
   MAX-ACCESS  not-accessible
   STATUS      current
   DESCRIPTION
      ""
   INDEX      { pr1645v2VEthInErrorsGlobalIx }
   ::= {pr1645v2VEthInErrorsTable 1}

Pr1645v2VEthInErrorsEntry ::=
   SEQUENCE
      {
      pr1645v2VEthInErrorsGlobalIx
         GlobalIndex,
      pr1645v2VEthInErrorsValue
         Counter64
      }

pr1645v2VEthInErrorsGlobalIx OBJECT-TYPE
   SYNTAX      GlobalIndex
   MAX-ACCESS  not-accessible
   STATUS      current
   DESCRIPTION
      "The value of the tlsCntTreeGlobalIndex of the MANAGED OBJECT."
   ::= {pr1645v2VEthInErrorsEntry 10}

pr1645v2VEthInErrorsValue OBJECT-TYPE
   SYNTAX      Counter64
   MAX-ACCESS  read-only
   STATUS      current
   DESCRIPTION
      "Path: virtualEthernet.performance.ifInErrors

       64 bit unsigned wrappable counter."
   ::= {pr1645v2VEthInErrorsEntry 2147483648}


pr1645v2VEthInUnknownProtos OBJECT IDENTIFIER ::= {pr1645v2VEth 114}

pr1645v2VEthInUnknownProtosTable OBJECT-TYPE
   SYNTAX      SEQUENCE OF Pr1645v2VEthInUnknownProtosEntry
   MAX-ACCESS  not-accessible
   STATUS      current
   DESCRIPTION
      "ifInUnknownprotos"
   ::= {pr1645v2VEthInUnknownProtos 1}

pr1645v2VEthInUnknownProtosEntry OBJECT-TYPE
   SYNTAX      Pr1645v2VEthInUnknownProtosEntry
   MAX-ACCESS  not-accessible
   STATUS      current
   DESCRIPTION
      ""
   INDEX      { pr1645v2VEthInUnknownProtosGlobalIx }
   ::= {pr1645v2VEthInUnknownProtosTable 1}

Pr1645v2VEthInUnknownProtosEntry ::=
   SEQUENCE
      {
      pr1645v2VEthInUnknownProtosGlobalIx
         GlobalIndex,
      pr1645v2VEthInUnknownProtosValue
         Counter64
      }

pr1645v2VEthInUnknownProtosGlobalIx OBJECT-TYPE
   SYNTAX      GlobalIndex
   MAX-ACCESS  not-accessible
   STATUS      current
   DESCRIPTION
      "The value of the tlsCntTreeGlobalIndex of the MANAGED OBJECT."
   ::= {pr1645v2VEthInUnknownProtosEntry 10}

pr1645v2VEthInUnknownProtosValue OBJECT-TYPE
   SYNTAX      Counter64
   MAX-ACCESS  read-only
   STATUS      current
   DESCRIPTION
      "Path: virtualEthernet.performance.ifInUnknownProtos

       64 bit unsigned wrappable counter."
   ::= {pr1645v2VEthInUnknownProtosEntry 2147483648}


pr1645v2VEthInQLen OBJECT IDENTIFIER ::= {pr1645v2VEth 128}

pr1645v2VEthInQLenTable OBJECT-TYPE
   SYNTAX      SEQUENCE OF Pr1645v2VEthInQLenEntry
   MAX-ACCESS  not-accessible
   STATUS      current
   DESCRIPTION
      "ifInQLen"
   ::= {pr1645v2VEthInQLen 1}

pr1645v2VEthInQLenEntry OBJECT-TYPE
   SYNTAX      Pr1645v2VEthInQLenEntry
   MAX-ACCESS  not-accessible
   STATUS      current
   DESCRIPTION
      ""
   INDEX      { pr1645v2VEthInQLenGlobalIx }
   ::= {pr1645v2VEthInQLenTable 1}

Pr1645v2VEthInQLenEntry ::=
   SEQUENCE
      {
      pr1645v2VEthInQLenGlobalIx
         GlobalIndex,
      pr1645v2VEthInQLenValue
         Gauge32
      }

pr1645v2VEthInQLenGlobalIx OBJECT-TYPE
   SYNTAX      GlobalIndex
   MAX-ACCESS  not-accessible
   STATUS      current
   DESCRIPTION
      "The value of the tlsCntTreeGlobalIndex of the MANAGED OBJECT."
   ::= {pr1645v2VEthInQLenEntry 10}

pr1645v2VEthInQLenValue OBJECT-TYPE
   SYNTAX      Gauge32
   MAX-ACCESS  read-only
   STATUS      current
   DESCRIPTION
      "Path: virtualEthernet.performance.ifInQLen

       32 bit unsigned gauge value."
   ::= {pr1645v2VEthInQLenEntry 2147483648}


pr1645v2VEthInDropEx OBJECT IDENTIFIER ::= {pr1645v2VEth 130}

pr1645v2VEthInDropExTable OBJECT-TYPE
   SYNTAX      SEQUENCE OF Pr1645v2VEthInDropExEntry
   MAX-ACCESS  not-accessible
   STATUS      current
   DESCRIPTION
      "ifInDiscards"
   ::= {pr1645v2VEthInDropEx 1}

pr1645v2VEthInDropExEntry OBJECT-TYPE
   SYNTAX      Pr1645v2VEthInDropExEntry
   MAX-ACCESS  not-accessible
   STATUS      current
   DESCRIPTION
      ""
   INDEX      { pr1645v2VEthInDropExGlobalIx }
   ::= {pr1645v2VEthInDropExTable 1}

Pr1645v2VEthInDropExEntry ::=
   SEQUENCE
      {
      pr1645v2VEthInDropExGlobalIx
         GlobalIndex,
      pr1645v2VEthInDropExValue
         Counter64
      }

pr1645v2VEthInDropExGlobalIx OBJECT-TYPE
   SYNTAX      GlobalIndex
   MAX-ACCESS  not-accessible
   STATUS      current
   DESCRIPTION
      "The value of the tlsCntTreeGlobalIndex of the MANAGED OBJECT."
   ::= {pr1645v2VEthInDropExEntry 10}

pr1645v2VEthInDropExValue OBJECT-TYPE
   SYNTAX      Counter64
   MAX-ACCESS  read-only
   STATUS      current
   DESCRIPTION
      "Path: virtualEthernet.performance.ifInDropLevelExceeded

       64 bit unsigned wrappable counter."
   ::= {pr1645v2VEthInDropExEntry 2147483648}


pr1645v2VEthInDropNoMac OBJECT IDENTIFIER ::= {pr1645v2VEth 133}

pr1645v2VEthInDropNoMacTable OBJECT-TYPE
   SYNTAX      SEQUENCE OF Pr1645v2VEthInDropNoMacEntry
   MAX-ACCESS  not-accessible
   STATUS      current
   DESCRIPTION
      "ifInDiscards"
   ::= {pr1645v2VEthInDropNoMac 1}

pr1645v2VEthInDropNoMacEntry OBJECT-TYPE
   SYNTAX      Pr1645v2VEthInDropNoMacEntry
   MAX-ACCESS  not-accessible
   STATUS      current
   DESCRIPTION
      ""
   INDEX      { pr1645v2VEthInDropNoMacGlobalIx }
   ::= {pr1645v2VEthInDropNoMacTable 1}

Pr1645v2VEthInDropNoMacEntry ::=
   SEQUENCE
      {
      pr1645v2VEthInDropNoMacGlobalIx
         GlobalIndex,
      pr1645v2VEthInDropNoMacValue
         Counter64
      }

pr1645v2VEthInDropNoMacGlobalIx OBJECT-TYPE
   SYNTAX      GlobalIndex
   MAX-ACCESS  not-accessible
   STATUS      current
   DESCRIPTION
      "The value of the tlsCntTreeGlobalIndex of the MANAGED OBJECT."
   ::= {pr1645v2VEthInDropNoMacEntry 10}

pr1645v2VEthInDropNoMacValue OBJECT-TYPE
   SYNTAX      Counter64
   MAX-ACCESS  read-only
   STATUS      current
   DESCRIPTION
      "Path: virtualEthernet.performance.ifInDiscardsNoMacFit

       64 bit unsigned wrappable counter."
   ::= {pr1645v2VEthInDropNoMacEntry 2147483648}


pr1645v2VEthInDropNUCast OBJECT IDENTIFIER ::= {pr1645v2VEth 136}

pr1645v2VEthInDropNUCastTable OBJECT-TYPE
   SYNTAX      SEQUENCE OF Pr1645v2VEthInDropNUCastEntry
   MAX-ACCESS  not-accessible
   STATUS      current
   DESCRIPTION
      "ifInDiscards"
   ::= {pr1645v2VEthInDropNUCast 1}

pr1645v2VEthInDropNUCastEntry OBJECT-TYPE
   SYNTAX      Pr1645v2VEthInDropNUCastEntry
   MAX-ACCESS  not-accessible
   STATUS      current
   DESCRIPTION
      ""
   INDEX      { pr1645v2VEthInDropNUCastGlobalIx }
   ::= {pr1645v2VEthInDropNUCastTable 1}

Pr1645v2VEthInDropNUCastEntry ::=
   SEQUENCE
      {
      pr1645v2VEthInDropNUCastGlobalIx
         GlobalIndex,
      pr1645v2VEthInDropNUCastValue
         Counter64
      }

pr1645v2VEthInDropNUCastGlobalIx OBJECT-TYPE
   SYNTAX      GlobalIndex
   MAX-ACCESS  not-accessible
   STATUS      current
   DESCRIPTION
      "The value of the tlsCntTreeGlobalIndex of the MANAGED OBJECT."
   ::= {pr1645v2VEthInDropNUCastEntry 10}

pr1645v2VEthInDropNUCastValue OBJECT-TYPE
   SYNTAX      Counter64
   MAX-ACCESS  read-only
   STATUS      current
   DESCRIPTION
      "Path: virtualEthernet.performance.ifInDiscardsNUCast

       64 bit unsigned wrappable counter."
   ::= {pr1645v2VEthInDropNUCastEntry 2147483648}


pr1645v2VEthInDropFilter OBJECT IDENTIFIER ::= {pr1645v2VEth 137}

pr1645v2VEthInDropFilterTable OBJECT-TYPE
   SYNTAX      SEQUENCE OF Pr1645v2VEthInDropFilterEntry
   MAX-ACCESS  not-accessible
   STATUS      current
   DESCRIPTION
      "ifInDiscards"
   ::= {pr1645v2VEthInDropFilter 1}

pr1645v2VEthInDropFilterEntry OBJECT-TYPE
   SYNTAX      Pr1645v2VEthInDropFilterEntry
   MAX-ACCESS  not-accessible
   STATUS      current
   DESCRIPTION
      ""
   INDEX      { pr1645v2VEthInDropFilterGlobalIx }
   ::= {pr1645v2VEthInDropFilterTable 1}

Pr1645v2VEthInDropFilterEntry ::=
   SEQUENCE
      {
      pr1645v2VEthInDropFilterGlobalIx
         GlobalIndex,
      pr1645v2VEthInDropFilterValue
         Counter64
      }

pr1645v2VEthInDropFilterGlobalIx OBJECT-TYPE
   SYNTAX      GlobalIndex
   MAX-ACCESS  not-accessible
   STATUS      current
   DESCRIPTION
      "The value of the tlsCntTreeGlobalIndex of the MANAGED OBJECT."
   ::= {pr1645v2VEthInDropFilterEntry 10}

pr1645v2VEthInDropFilterValue OBJECT-TYPE
   SYNTAX      Counter64
   MAX-ACCESS  read-only
   STATUS      current
   DESCRIPTION
      "Path: virtualEthernet.performance.ifInDiscardsFilter

       64 bit unsigned wrappable counter."
   ::= {pr1645v2VEthInDropFilterEntry 2147483648}


pr1645v2VEthInQueues OBJECT IDENTIFIER ::= {pr1645v2VEth 131}

pr1645v2VEthInQueuesSSCTable OBJECT-TYPE
   SYNTAX      SEQUENCE OF Pr1645v2VEthInQueuesEntry
   MAX-ACCESS  not-accessible
   STATUS      current
   DESCRIPTION
      "Queue Lengths"
   ::= {pr1645v2VEthInQueues 1}

pr1645v2VEthInQueuesEntry OBJECT-TYPE
   SYNTAX      Pr1645v2VEthInQueuesEntry
   MAX-ACCESS  not-accessible
   STATUS      current
   DESCRIPTION
      ""
   INDEX      { pr1645v2VEthInQueuesGlobalIx,
                pr1645v2VEthInQueuesTableIx }
   ::= {pr1645v2VEthInQueuesSSCTable 1}

Pr1645v2VEthInQueuesEntry ::=
   SEQUENCE
      {
      pr1645v2VEthInQueuesGlobalIx
         GlobalIndex,
      pr1645v2VEthInQueuesTableIx
         TableIndex,
      pr1645v2VEthInQueuesName
         INTEGER,
      pr1645v2VEthInQueuesLength
         Integer32,
      pr1645v2VEthInQueuesOctetLength
         Integer32,
      pr1645v2VEthInQueuesRedLength
         Integer32,
      pr1645v2VEthInQueuesPacketsTotal
         Counter64,
      pr1645v2VEthInQueuesPacketsDirectTx
         Counter64,
      pr1645v2VEthInQueuesPacketsQueued
         Counter64,
      pr1645v2VEthInQueuesPacketsDropped
         Counter64,
      pr1645v2VEthInQueuesPacketsRedDropped
         Counter64,
      pr1645v2VEthInQueuesPacketsCirTx
         Counter64,
      pr1645v2VEthInQueuesPacketsEirTx
         Counter64,
      pr1645v2VEthInQueuesPacketsViolateTx
         Counter64,
      pr1645v2VEthInQueuesOctetsTotal
         Counter64,
      pr1645v2VEthInQueuesOctetsDirectTx
         Counter64,
      pr1645v2VEthInQueuesOctetsQueued
         Counter64,
      pr1645v2VEthInQueuesOctetsDropped
         Counter64,
      pr1645v2VEthInQueuesOctetsRedDropped
         Counter64,
      pr1645v2VEthInQueuesOctetsCirTx
         Counter64,
      pr1645v2VEthInQueuesOctetsEirTx
         Counter64,
      pr1645v2VEthInQueuesOctetsViolateTx
         Counter64,
      pr1645v2VEthInQueuesOctetsBandwidth15sec
         Integer32,
      pr1645v2VEthInQueuesOctetsBandwidth30sec
         Integer32,
      pr1645v2VEthInQueuesOctetsBandwidth1min
         Integer32,
      pr1645v2VEthInQueuesOctetsBandwidth2min
         Integer32,
      pr1645v2VEthInQueuesOctetsBandwidth5min
         Integer32
      }

pr1645v2VEthInQueuesGlobalIx OBJECT-TYPE
   SYNTAX      GlobalIndex
   MAX-ACCESS  not-accessible
   STATUS      current
   DESCRIPTION
      "The value of the tlsCntTreeGlobalIndex of the MANAGED OBJECT."
   ::= {pr1645v2VEthInQueuesEntry 10}

pr1645v2VEthInQueuesTableIx OBJECT-TYPE
   SYNTAX      TableIndex
   MAX-ACCESS  not-accessible
   STATUS      current
   DESCRIPTION
      ""
   ::= {pr1645v2VEthInQueuesEntry 11}

pr1645v2VEthInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2VEthInQueuesEntry 16777216}

pr1645v2VEthInQueuesLength OBJECT-TYPE
   SYNTAX      Integer32
   MAX-ACCESS  read-only
   STATUS      current
   DESCRIPTION
      "Path: virtualEthernet.performance.ifInPriorityQueues.length"
   ::= {pr1645v2VEthInQueuesEntry 33554432}

pr1645v2VEthInQueuesOctetLength OBJECT-TYPE
   SYNTAX      Integer32
   MAX-ACCESS  read-only
   STATUS      current
   DESCRIPTION
      "Path: virtualEthernet.performance.ifInPriorityQueues.octetLength"
   ::= {pr1645v2VEthInQueuesEntry 150994944}

pr1645v2VEthInQueuesRedLength OBJECT-TYPE
   SYNTAX      Integer32
   MAX-ACCESS  read-only
   STATUS      current
   DESCRIPTION
      "Path: virtualEthernet.performance.ifInPriorityQueues.redLength"
   ::= {pr1645v2VEthInQueuesEntry 134217728}

pr1645v2VEthInQueuesPacketsTotal OBJECT-TYPE
   SYNTAX      Counter64
   MAX-ACCESS  read-only
   STATUS      current
   DESCRIPTION
      "Path: virtualEthernet.performance.ifInPriorityQueues.packets.total

       64 bit unsigned wrappable counter."
   ::= {pr1645v2VEthInQueuesEntry 50790400}

pr1645v2VEthInQueuesPacketsDirectTx OBJECT-TYPE
   SYNTAX      Counter64
   MAX-ACCESS  read-only
   STATUS      current
   DESCRIPTION
      "Path: virtualEthernet.performance.ifInPriorityQueues.packets.directTx

       64 bit unsigned wrappable counter."
   ::= {pr1645v2VEthInQueuesEntry 50397184}

pr1645v2VEthInQueuesPacketsQueued OBJECT-TYPE
   SYNTAX      Counter64
   MAX-ACCESS  read-only
   STATUS      current
   DESCRIPTION
      "Path: virtualEthernet.performance.ifInPriorityQueues.packets.queued

       64 bit unsigned wrappable counter."
   ::= {pr1645v2VEthInQueuesEntry 50462720}

pr1645v2VEthInQueuesPacketsDropped OBJECT-TYPE
   SYNTAX      Counter64
   MAX-ACCESS  read-only
   STATUS      current
   DESCRIPTION
      "Path: virtualEthernet.performance.ifInPriorityQueues.packets.dropped

       64 bit unsigned wrappable counter."
   ::= {pr1645v2VEthInQueuesEntry 50528256}

pr1645v2VEthInQueuesPacketsRedDropped OBJECT-TYPE
   SYNTAX      Counter64
   MAX-ACCESS  read-only
   STATUS      current
   DESCRIPTION
      "Path: virtualEthernet.performance.ifInPriorityQueues.packets.redDropped

       64 bit unsigned wrappable counter."
   ::= {pr1645v2VEthInQueuesEntry 50724864}

pr1645v2VEthInQueuesPacketsCirTx OBJECT-TYPE
   SYNTAX      Counter64
   MAX-ACCESS  read-only
   STATUS      current
   DESCRIPTION
      "Path: virtualEthernet.performance.ifInPriorityQueues.packets.cirTx

       64 bit unsigned wrappable counter."
   ::= {pr1645v2VEthInQueuesEntry 50593792}

pr1645v2VEthInQueuesPacketsEirTx OBJECT-TYPE
   SYNTAX      Counter64
   MAX-ACCESS  read-only
   STATUS      current
   DESCRIPTION
      "Path: virtualEthernet.performance.ifInPriorityQueues.packets.eirTx

       64 bit unsigned wrappable counter."
   ::= {pr1645v2VEthInQueuesEntry 50659328}

pr1645v2VEthInQueuesPacketsViolateTx OBJECT-TYPE
   SYNTAX      Counter64
   MAX-ACCESS  read-only
   STATUS      current
   DESCRIPTION
      "Path: virtualEthernet.performance.ifInPriorityQueues.packets.violateTx

       64 bit unsigned wrappable counter."
   ::= {pr1645v2VEthInQueuesEntry 50855936}

pr1645v2VEthInQueuesOctetsTotal OBJECT-TYPE
   SYNTAX      Counter64
   MAX-ACCESS  read-only
   STATUS      current
   DESCRIPTION
      "Path: virtualEthernet.performance.ifInPriorityQueues.octets.total

       64 bit unsigned wrappable counter."
   ::= {pr1645v2VEthInQueuesEntry 67567616}

pr1645v2VEthInQueuesOctetsDirectTx OBJECT-TYPE
   SYNTAX      Counter64
   MAX-ACCESS  read-only
   STATUS      current
   DESCRIPTION
      "Path: virtualEthernet.performance.ifInPriorityQueues.octets.directTx

       64 bit unsigned wrappable counter."
   ::= {pr1645v2VEthInQueuesEntry 67174400}

pr1645v2VEthInQueuesOctetsQueued OBJECT-TYPE
   SYNTAX      Counter64
   MAX-ACCESS  read-only
   STATUS      current
   DESCRIPTION
      "Path: virtualEthernet.performance.ifInPriorityQueues.octets.queued

       64 bit unsigned wrappable counter."
   ::= {pr1645v2VEthInQueuesEntry 67239936}

pr1645v2VEthInQueuesOctetsDropped OBJECT-TYPE
   SYNTAX      Counter64
   MAX-ACCESS  read-only
   STATUS      current
   DESCRIPTION
      "Path: virtualEthernet.performance.ifInPriorityQueues.octets.dropped

       64 bit unsigned wrappable counter."
   ::= {pr1645v2VEthInQueuesEntry 67305472}

pr1645v2VEthInQueuesOctetsRedDropped OBJECT-TYPE
   SYNTAX      Counter64
   MAX-ACCESS  read-only
   STATUS      current
   DESCRIPTION
      "Path: virtualEthernet.performance.ifInPriorityQueues.octets.redDropped

       64 bit unsigned wrappable counter."
   ::= {pr1645v2VEthInQueuesEntry 67502080}

pr1645v2VEthInQueuesOctetsCirTx OBJECT-TYPE
   SYNTAX      Counter64
   MAX-ACCESS  read-only
   STATUS      current
   DESCRIPTION
      "Path: virtualEthernet.performance.ifInPriorityQueues.octets.cirTx

       64 bit unsigned wrappable counter."
   ::= {pr1645v2VEthInQueuesEntry 67371008}

pr1645v2VEthInQueuesOctetsEirTx OBJECT-TYPE
   SYNTAX      Counter64
   MAX-ACCESS  read-only
   STATUS      current
   DESCRIPTION
      "Path: virtualEthernet.performance.ifInPriorityQueues.octets.eirTx

       64 bit unsigned wrappable counter."
   ::= {pr1645v2VEthInQueuesEntry 67436544}

pr1645v2VEthInQueuesOctetsViolateTx OBJECT-TYPE
   SYNTAX      Counter64
   MAX-ACCESS  read-only
   STATUS      current
   DESCRIPTION
      "Path: virtualEthernet.performance.ifInPriorityQueues.octets.violateTx

       64 bit unsigned wrappable counter."
   ::= {pr1645v2VEthInQueuesEntry 67633152}

pr1645v2VEthInQueuesOctetsBandwidth15sec OBJECT-TYPE
   SYNTAX      Integer32
   MAX-ACCESS  read-only
   STATUS      current
   DESCRIPTION
      "Path: virtualEthernet.performance.ifInPriorityQueues.octets.bandwidth.15sec

       unit name = bps
       formula = 8 * ; 8 /"
   ::= {pr1645v2VEthInQueuesEntry 70386944}

pr1645v2VEthInQueuesOctetsBandwidth30sec OBJECT-TYPE
   SYNTAX      Integer32
   MAX-ACCESS  read-only
   STATUS      current
   DESCRIPTION
      "Path: virtualEthernet.performance.ifInPriorityQueues.octets.bandwidth.30sec

       unit name = bps
       formula = 8 * ; 8 /"
   ::= {pr1645v2VEthInQueuesEntry 70388224}

pr1645v2VEthInQueuesOctetsBandwidth1min OBJECT-TYPE
   SYNTAX      Integer32
   MAX-ACCESS  read-only
   STATUS      current
   DESCRIPTION
      "Path: virtualEthernet.performance.ifInPriorityQueues.octets.bandwidth.1min

       unit name = bps
       formula = 8 * ; 8 /"
   ::= {pr1645v2VEthInQueuesEntry 70390784}

pr1645v2VEthInQueuesOctetsBandwidth2min OBJECT-TYPE
   SYNTAX      Integer32
   MAX-ACCESS  read-only
   STATUS      current
   DESCRIPTION
      "Path: virtualEthernet.performance.ifInPriorityQueues.octets.bandwidth.2min

       unit name = bps
       formula = 8 * ; 8 /"
   ::= {pr1645v2VEthInQueuesEntry 70395904}

pr1645v2VEthInQueuesOctetsBandwidth5min OBJECT-TYPE
   SYNTAX      Integer32
   MAX-ACCESS  read-only
   STATUS      current
   DESCRIPTION
      "Path: virtualEthernet.performance.ifInPriorityQueues.octets.bandwidth.5min

       unit name = bps
       formula = 8 * ; 8 /"
   ::= {pr1645v2VEthInQueuesEntry 70411264}

pr1645v2VEthInQueuesH2Performance OBJECT-TYPE
   SYNTAX      SEQUENCE OF Pr1645v2VEthInQueuesH2PerformanceEntry
   MAX-ACCESS  not-accessible
   STATUS      current
   DESCRIPTION
      ""
   ::= {pr1645v2VEthInQueues 83886080}

pr1645v2VEthInQueuesH2PerformanceEntry OBJECT-TYPE
   SYNTAX      Pr1645v2VEthInQueuesH2PerformanceEntry
   MAX-ACCESS  not-accessible
   STATUS      current
   DESCRIPTION
      ""
   INDEX      { pr1645v2VEthInQueuesH2PerformanceGlobalIx,
                pr1645v2VEthInQueuesTableIx,
                pr1645v2VEthInQueuesH2PerformanceTableIx }
   ::= {pr1645v2VEthInQueuesH2Performance 1}

Pr1645v2VEthInQueuesH2PerformanceEntry ::=
   SEQUENCE
      {
      pr1645v2VEthInQueuesH2PerformanceGlobalIx
         GlobalIndex,
      pr1645v2VEthInQueuesH2PerformanceTableIx
         TableIndex,
      pr1645v2VEthInQueuesH2PerformanceSysUpTime
         TimeTicks,
      pr1645v2VEthInQueuesH2PerformanceTotPkts
         Counter64,
      pr1645v2VEthInQueuesH2PerformanceDirTxPkts
         Counter64,
      pr1645v2VEthInQueuesH2PerformanceQdPkts
         Counter64,
      pr1645v2VEthInQueuesH2PerformanceDropPkts
         Counter64,
      pr1645v2VEthInQueuesH2PerformanceRDropPkts
         Counter64,
      pr1645v2VEthInQueuesH2PerformanceCirTxPkts
         Counter64,
      pr1645v2VEthInQueuesH2PerformanceEirTxPkts
         Counter64,
      pr1645v2VEthInQueuesH2PerformanceViolTxPkts
         Counter64,
      pr1645v2VEthInQueuesH2PerformanceTotOcts
         Counter64,
      pr1645v2VEthInQueuesH2PerformanceDirTxOcts
         Counter64,
      pr1645v2VEthInQueuesH2PerformanceQdOcts
         Counter64,
      pr1645v2VEthInQueuesH2PerformanceDropOcts
         Counter64,
      pr1645v2VEthInQueuesH2PerformanceRDropOcts
         Counter64,
      pr1645v2VEthInQueuesH2PerformanceCirTxOcts
         Counter64,
      pr1645v2VEthInQueuesH2PerformanceEirTxOcts
         Counter64,
      pr1645v2VEthInQueuesH2PerformanceViolTxOcts
         Counter64,
      pr1645v2VEthInQueuesH2PerformanceBandwidth
         Integer32
      }

pr1645v2VEthInQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2VEthInQueuesH2PerformanceEntry 10}

pr1645v2VEthInQueuesH2PerformanceTableIx OBJECT-TYPE
   SYNTAX      TableIndex
   MAX-ACCESS  not-accessible
   STATUS      current
   DESCRIPTION
      ""
   ::= {pr1645v2VEthInQueuesH2PerformanceEntry 11}

pr1645v2VEthInQueuesH2PerformanceSysUpTime OBJECT-TYPE
   SYNTAX      TimeTicks
   MAX-ACCESS  read-only
   STATUS      current
   DESCRIPTION
      "Path: virtualEthernet.performance.ifInPriorityQueues.h2Performance.sysUpTime

       Time in centi-second."
   ::= {pr1645v2VEthInQueuesH2PerformanceEntry 16777216}

pr1645v2VEthInQueuesH2PerformanceTotPkts OBJECT-TYPE
   SYNTAX      Counter64
   MAX-ACCESS  read-only
   STATUS      current
   DESCRIPTION
      "Path: virtualEthernet.performance.ifInPriorityQueues.h2Performance.totalPkts

       64 bit unsigned wrappable counter."
   ::= {pr1645v2VEthInQueuesH2PerformanceEntry 234881024}

pr1645v2VEthInQueuesH2PerformanceDirTxPkts OBJECT-TYPE
   SYNTAX      Counter64
   MAX-ACCESS  read-only
   STATUS      current
   DESCRIPTION
      "Path: virtualEthernet.performance.ifInPriorityQueues.h2Performance.directTxPkts

       64 bit unsigned wrappable counter."
   ::= {pr1645v2VEthInQueuesH2PerformanceEntry 33554432}

pr1645v2VEthInQueuesH2PerformanceQdPkts OBJECT-TYPE
   SYNTAX      Counter64
   MAX-ACCESS  read-only
   STATUS      current
   DESCRIPTION
      "Path: virtualEthernet.performance.ifInPriorityQueues.h2Performance.queuedPkts

       64 bit unsigned wrappable counter."
   ::= {pr1645v2VEthInQueuesH2PerformanceEntry 50331648}

pr1645v2VEthInQueuesH2PerformanceDropPkts OBJECT-TYPE
   SYNTAX      Counter64
   MAX-ACCESS  read-only
   STATUS      current
   DESCRIPTION
      "Path: virtualEthernet.performance.ifInPriorityQueues.h2Performance.droppedPkts

       64 bit unsigned wrappable counter."
   ::= {pr1645v2VEthInQueuesH2PerformanceEntry 67108864}

pr1645v2VEthInQueuesH2PerformanceRDropPkts OBJECT-TYPE
   SYNTAX      Counter64
   MAX-ACCESS  read-only
   STATUS      current
   DESCRIPTION
      "Path: virtualEthernet.performance.ifInPriorityQueues.h2Performance.redDroppedPkts

       64 bit unsigned wrappable counter."
   ::= {pr1645v2VEthInQueuesH2PerformanceEntry 201326592}

pr1645v2VEthInQueuesH2PerformanceCirTxPkts OBJECT-TYPE
   SYNTAX      Counter64
   MAX-ACCESS  read-only
   STATUS      current
   DESCRIPTION
      "Path: virtualEthernet.performance.ifInPriorityQueues.h2Performance.cirTxPkts

       64 bit unsigned wrappable counter."
   ::= {pr1645v2VEthInQueuesH2PerformanceEntry 83886080}

pr1645v2VEthInQueuesH2PerformanceEirTxPkts OBJECT-TYPE
   SYNTAX      Counter64
   MAX-ACCESS  read-only
   STATUS      current
   DESCRIPTION
      "Path: virtualEthernet.performance.ifInPriorityQueues.h2Performance.eirTxPkts

       64 bit unsigned wrappable counter."
   ::= {pr1645v2VEthInQueuesH2PerformanceEntry 100663296}

pr1645v2VEthInQueuesH2PerformanceViolTxPkts OBJECT-TYPE
   SYNTAX      Counter64
   MAX-ACCESS  read-only
   STATUS      current
   DESCRIPTION
      "Path: virtualEthernet.performance.ifInPriorityQueues.h2Performance.violateTxPkts

       64 bit unsigned wrappable counter."
   ::= {pr1645v2VEthInQueuesH2PerformanceEntry 301989888}

pr1645v2VEthInQueuesH2PerformanceTotOcts OBJECT-TYPE
   SYNTAX      Counter64
   MAX-ACCESS  read-only
   STATUS      current
   DESCRIPTION
      "Path: virtualEthernet.performance.ifInPriorityQueues.h2Performance.totalOctets

       64 bit unsigned wrappable counter."
   ::= {pr1645v2VEthInQueuesH2PerformanceEntry 251658240}

pr1645v2VEthInQueuesH2PerformanceDirTxOcts OBJECT-TYPE
   SYNTAX      Counter64
   MAX-ACCESS  read-only
   STATUS      current
   DESCRIPTION
      "Path: virtualEthernet.performance.ifInPriorityQueues.h2Performance.directTxOctets

       64 bit unsigned wrappable counter."
   ::= {pr1645v2VEthInQueuesH2PerformanceEntry 117440512}

pr1645v2VEthInQueuesH2PerformanceQdOcts OBJECT-TYPE
   SYNTAX      Counter64
   MAX-ACCESS  read-only
   STATUS      current
   DESCRIPTION
      "Path: virtualEthernet.performance.ifInPriorityQueues.h2Performance.queuedOctets

       64 bit unsigned wrappable counter."
   ::= {pr1645v2VEthInQueuesH2PerformanceEntry 134217728}

pr1645v2VEthInQueuesH2PerformanceDropOcts OBJECT-TYPE
   SYNTAX      Counter64
   MAX-ACCESS  read-only
   STATUS      current
   DESCRIPTION
      "Path: virtualEthernet.performance.ifInPriorityQueues.h2Performance.droppedOctets

       64 bit unsigned wrappable counter."
   ::= {pr1645v2VEthInQueuesH2PerformanceEntry 150994944}

pr1645v2VEthInQueuesH2PerformanceRDropOcts OBJECT-TYPE
   SYNTAX      Counter64
   MAX-ACCESS  read-only
   STATUS      current
   DESCRIPTION
      "Path: virtualEthernet.performance.ifInPriorityQueues.h2Performance.redDroppedOctets

       64 bit unsigned wrappable counter."
   ::= {pr1645v2VEthInQueuesH2PerformanceEntry 218103808}

pr1645v2VEthInQueuesH2PerformanceCirTxOcts OBJECT-TYPE
   SYNTAX      Counter64
   MAX-ACCESS  read-only
   STATUS      current
   DESCRIPTION
      "Path: virtualEthernet.performance.ifInPriorityQueues.h2Performance.cirTxOctets

       64 bit unsigned wrappable counter."
   ::= {pr1645v2VEthInQueuesH2PerformanceEntry 167772160}

pr1645v2VEthInQueuesH2PerformanceEirTxOcts OBJECT-TYPE
   SYNTAX      Counter64
   MAX-ACCESS  read-only
   STATUS      current
   DESCRIPTION
      "Path: virtualEthernet.performance.ifInPriorityQueues.h2Performance.eirTxOctets

       64 bit unsigned wrappable counter."
   ::= {pr1645v2VEthInQueuesH2PerformanceEntry 184549376}

pr1645v2VEthInQueuesH2PerformanceViolTxOcts OBJECT-TYPE
   SYNTAX      Counter64
   MAX-ACCESS  read-only
   STATUS      current
   DESCRIPTION
      "Path: virtualEthernet.performance.ifInPriorityQueues.h2Performance.violateTxOctets

       64 bit unsigned wrappable counter."
   ::= {pr1645v2VEthInQueuesH2PerformanceEntry 318767104}

pr1645v2VEthInQueuesH2PerformanceBandwidth OBJECT-TYPE
   SYNTAX      Integer32
   MAX-ACCESS  read-only
   STATUS      current
   DESCRIPTION
      "Path: virtualEthernet.performance.ifInPriorityQueues.h2Performance.bandwidth

       unit name = bps
       formula = 8 * ; 8 /"
   ::= {pr1645v2VEthInQueuesH2PerformanceEntry 268435456}

pr1645v2VEthInQueuesH24Performance OBJECT-TYPE
   SYNTAX      SEQUENCE OF Pr1645v2VEthInQueuesH24PerformanceEntry
   MAX-ACCESS  not-accessible
   STATUS      current
   DESCRIPTION
      ""
   ::= {pr1645v2VEthInQueues 100663296}

pr1645v2VEthInQueuesH24PerformanceEntry OBJECT-TYPE
   SYNTAX      Pr1645v2VEthInQueuesH24PerformanceEntry
   MAX-ACCESS  not-accessible
   STATUS      current
   DESCRIPTION
      ""
   INDEX      { pr1645v2VEthInQueuesH24PerformanceGlobalIx,
                pr1645v2VEthInQueuesTableIx,
                pr1645v2VEthInQueuesH24PerformanceTableIx }
   ::= {pr1645v2VEthInQueuesH24Performance 1}

Pr1645v2VEthInQueuesH24PerformanceEntry ::=
   SEQUENCE
      {
      pr1645v2VEthInQueuesH24PerformanceGlobalIx
         GlobalIndex,
      pr1645v2VEthInQueuesH24PerformanceTableIx
         TableIndex,
      pr1645v2VEthInQueuesH24PerformanceSysUpTime
         TimeTicks,
      pr1645v2VEthInQueuesH24PerformanceTotPkts
         Counter64,
      pr1645v2VEthInQueuesH24PerformanceDirTxPkts
         Counter64,
      pr1645v2VEthInQueuesH24PerformanceQdPkts
         Counter64,
      pr1645v2VEthInQueuesH24PerformanceDropPkts
         Counter64,
      pr1645v2VEthInQueuesH24PerformanceRDropPkts
         Counter64,
      pr1645v2VEthInQueuesH24PerformanceCirTxPkts
         Counter64,
      pr1645v2VEthInQueuesH24PerformanceEirTxPkts
         Counter64,
      pr1645v2VEthInQueuesH24PerformanceViolTxPkts
         Counter64,
      pr1645v2VEthInQueuesH24PerformanceTotOcts
         Counter64,
      pr1645v2VEthInQueuesH24PerformanceDirTxOcts
         Counter64,
      pr1645v2VEthInQueuesH24PerformanceQdOcts
         Counter64,
      pr1645v2VEthInQueuesH24PerformanceDropOcts
         Counter64,
      pr1645v2VEthInQueuesH24PerformanceRDropOcts
         Counter64,
      pr1645v2VEthInQueuesH24PerformanceCirTxOcts
         Counter64,
      pr1645v2VEthInQueuesH24PerformanceEirTxOcts
         Counter64,
      pr1645v2VEthInQueuesH24PerformanceViolTxOcts
         Counter64,
      pr1645v2VEthInQueuesH24PerformanceBandwidth
         Integer32
      }

pr1645v2VEthInQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2VEthInQueuesH24PerformanceEntry 10}

pr1645v2VEthInQueuesH24PerformanceTableIx OBJECT-TYPE
   SYNTAX      TableIndex
   MAX-ACCESS  not-accessible
   STATUS      current
   DESCRIPTION
      ""
   ::= {pr1645v2VEthInQueuesH24PerformanceEntry 11}

pr1645v2VEthInQueuesH24PerformanceSysUpTime OBJECT-TYPE
   SYNTAX      TimeTicks
   MAX-ACCESS  read-only
   STATUS      current
   DESCRIPTION
      "Path: virtualEthernet.performance.ifInPriorityQueues.h24Performance.sysUpTime

       Time in centi-second."
   ::= {pr1645v2VEthInQueuesH24PerformanceEntry 16777216}

pr1645v2VEthInQueuesH24PerformanceTotPkts OBJECT-TYPE
   SYNTAX      Counter64
   MAX-ACCESS  read-only
   STATUS      current
   DESCRIPTION
      "Path: virtualEthernet.performance.ifInPriorityQueues.h24Performance.totalPkts

       64 bit unsigned wrappable counter."
   ::= {pr1645v2VEthInQueuesH24PerformanceEntry 234881024}

pr1645v2VEthInQueuesH24PerformanceDirTxPkts OBJECT-TYPE
   SYNTAX      Counter64
   MAX-ACCESS  read-only
   STATUS      current
   DESCRIPTION
      "Path: virtualEthernet.performance.ifInPriorityQueues.h24Performance.directTxPkts

       64 bit unsigned wrappable counter."
   ::= {pr1645v2VEthInQueuesH24PerformanceEntry 33554432}

pr1645v2VEthInQueuesH24PerformanceQdPkts OBJECT-TYPE
   SYNTAX      Counter64
   MAX-ACCESS  read-only
   STATUS      current
   DESCRIPTION
      "Path: virtualEthernet.performance.ifInPriorityQueues.h24Performance.queuedPkts

       64 bit unsigned wrappable counter."
   ::= {pr1645v2VEthInQueuesH24PerformanceEntry 50331648}

pr1645v2VEthInQueuesH24PerformanceDropPkts OBJECT-TYPE
   SYNTAX      Counter64
   MAX-ACCESS  read-only
   STATUS      current
   DESCRIPTION
      "Path: virtualEthernet.performance.ifInPriorityQueues.h24Performance.droppedPkts

       64 bit unsigned wrappable counter."
   ::= {pr1645v2VEthInQueuesH24PerformanceEntry 67108864}

pr1645v2VEthInQueuesH24PerformanceRDropPkts OBJECT-TYPE
   SYNTAX      Counter64
   MAX-ACCESS  read-only
   STATUS      current
   DESCRIPTION
      "Path: virtualEthernet.performance.ifInPriorityQueues.h24Performance.redDroppedPkts

       64 bit unsigned wrappable counter."
   ::= {pr1645v2VEthInQueuesH24PerformanceEntry 201326592}

pr1645v2VEthInQueuesH24PerformanceCirTxPkts OBJECT-TYPE
   SYNTAX      Counter64
   MAX-ACCESS  read-only
   STATUS      current
   DESCRIPTION
      "Path: virtualEthernet.performance.ifInPriorityQueues.h24Performance.cirTxPkts

       64 bit unsigned wrappable counter."
   ::= {pr1645v2VEthInQueuesH24PerformanceEntry 83886080}

pr1645v2VEthInQueuesH24PerformanceEirTxPkts OBJECT-TYPE
   SYNTAX      Counter64
   MAX-ACCESS  read-only
   STATUS      current
   DESCRIPTION
      "Path: virtualEthernet.performance.ifInPriorityQueues.h24Performance.eirTxPkts

       64 bit unsigned wrappable counter."
   ::= {pr1645v2VEthInQueuesH24PerformanceEntry 100663296}

pr1645v2VEthInQueuesH24PerformanceViolTxPkts OBJECT-TYPE
   SYNTAX      Counter64
   MAX-ACCESS  read-only
   STATUS      current
   DESCRIPTION
      "Path: virtualEthernet.performance.ifInPriorityQueues.h24Performance.violateTxPkts

       64 bit unsigned wrappable counter."
   ::= {pr1645v2VEthInQueuesH24PerformanceEntry 301989888}

pr1645v2VEthInQueuesH24PerformanceTotOcts OBJECT-TYPE
   SYNTAX      Counter64
   MAX-ACCESS  read-only
   STATUS      current
   DESCRIPTION
      "Path: virtualEthernet.performance.ifInPriorityQueues.h24Performance.totalOctets

       64 bit unsigned wrappable counter."
   ::= {pr1645v2VEthInQueuesH24PerformanceEntry 251658240}

pr1645v2VEthInQueuesH24PerformanceDirTxOcts OBJECT-TYPE
   SYNTAX      Counter64
   MAX-ACCESS  read-only
   STATUS      current
   DESCRIPTION
      "Path: virtualEthernet.performance.ifInPriorityQueues.h24Performance.directTxOctets

       64 bit unsigned wrappable counter."
   ::= {pr1645v2VEthInQueuesH24PerformanceEntry 117440512}

pr1645v2VEthInQueuesH24PerformanceQdOcts OBJECT-TYPE
   SYNTAX      Counter64
   MAX-ACCESS  read-only
   STATUS      current
   DESCRIPTION
      "Path: virtualEthernet.performance.ifInPriorityQueues.h24Performance.queuedOctets

       64 bit unsigned wrappable counter."
   ::= {pr1645v2VEthInQueuesH24PerformanceEntry 134217728}

pr1645v2VEthInQueuesH24PerformanceDropOcts OBJECT-TYPE
   SYNTAX      Counter64
   MAX-ACCESS  read-only
   STATUS      current
   DESCRIPTION
      "Path: virtualEthernet.performance.ifInPriorityQueues.h24Performance.droppedOctets

       64 bit unsigned wrappable counter."
   ::= {pr1645v2VEthInQueuesH24PerformanceEntry 150994944}

pr1645v2VEthInQueuesH24PerformanceRDropOcts OBJECT-TYPE
   SYNTAX      Counter64
   MAX-ACCESS  read-only
   STATUS      current
   DESCRIPTION
      "Path: virtualEthernet.performance.ifInPriorityQueues.h24Performance.redDroppedOctets

       64 bit unsigned wrappable counter."
   ::= {pr1645v2VEthInQueuesH24PerformanceEntry 218103808}

pr1645v2VEthInQueuesH24PerformanceCirTxOcts OBJECT-TYPE
   SYNTAX      Counter64
   MAX-ACCESS  read-only
   STATUS      current
   DESCRIPTION
      "Path: virtualEthernet.performance.ifInPriorityQueues.h24Performance.cirTxOctets

       64 bit unsigned wrappable counter."
   ::= {pr1645v2VEthInQueuesH24PerformanceEntry 167772160}

pr1645v2VEthInQueuesH24PerformanceEirTxOcts OBJECT-TYPE
   SYNTAX      Counter64
   MAX-ACCESS  read-only
   STATUS      current
   DESCRIPTION
      "Path: virtualEthernet.performance.ifInPriorityQueues.h24Performance.eirTxOctets

       64 bit unsigned wrappable counter."
   ::= {pr1645v2VEthInQueuesH24PerformanceEntry 184549376}

pr1645v2VEthInQueuesH24PerformanceViolTxOcts OBJECT-TYPE
   SYNTAX      Counter64
   MAX-ACCESS  read-only
   STATUS      current
   DESCRIPTION
      "Path: virtualEthernet.performance.ifInPriorityQueues.h24Performance.violateTxOctets

       64 bit unsigned wrappable counter."
   ::= {pr1645v2VEthInQueuesH24PerformanceEntry 318767104}

pr1645v2VEthInQueuesH24PerformanceBandwidth OBJECT-TYPE
   SYNTAX      Integer32
   MAX-ACCESS  read-only
   STATUS      current
   DESCRIPTION
      "Path: virtualEthernet.performance.ifInPriorityQueues.h24Performance.bandwidth

       unit name = bps
       formula = 8 * ; 8 /"
   ::= {pr1645v2VEthInQueuesH24PerformanceEntry 268435456}

pr1645v2VEthInQueuesD7Performance OBJECT-TYPE
   SYNTAX      SEQUENCE OF Pr1645v2VEthInQueuesD7PerformanceEntry
   MAX-ACCESS  not-accessible
   STATUS      current
   DESCRIPTION
      ""
   ::= {pr1645v2VEthInQueues 117440512}

pr1645v2VEthInQueuesD7PerformanceEntry OBJECT-TYPE
   SYNTAX      Pr1645v2VEthInQueuesD7PerformanceEntry
   MAX-ACCESS  not-accessible
   STATUS      current
   DESCRIPTION
      ""
   INDEX      { pr1645v2VEthInQueuesD7PerformanceGlobalIx,
                pr1645v2VEthInQueuesTableIx,
                pr1645v2VEthInQueuesD7PerformanceTableIx }
   ::= {pr1645v2VEthInQueuesD7Performance 1}

Pr1645v2VEthInQueuesD7PerformanceEntry ::=
   SEQUENCE
      {
      pr1645v2VEthInQueuesD7PerformanceGlobalIx
         GlobalIndex,
      pr1645v2VEthInQueuesD7PerformanceTableIx
         TableIndex,
      pr1645v2VEthInQueuesD7PerformanceSysUpTime
         TimeTicks,
      pr1645v2VEthInQueuesD7PerformanceTotPkts
         Counter64,
      pr1645v2VEthInQueuesD7PerformanceDirTxPkts
         Counter64,
      pr1645v2VEthInQueuesD7PerformanceQdPkts
         Counter64,
      pr1645v2VEthInQueuesD7PerformanceDropPkts
         Counter64,
      pr1645v2VEthInQueuesD7PerformanceRDropPkts
         Counter64,
      pr1645v2VEthInQueuesD7PerformanceCirTxPkts
         Counter64,
      pr1645v2VEthInQueuesD7PerformanceEirTxPkts
         Counter64,
      pr1645v2VEthInQueuesD7PerformanceViolTxPkts
         Counter64,
      pr1645v2VEthInQueuesD7PerformanceTotOcts
         Counter64,
      pr1645v2VEthInQueuesD7PerformanceDirTxOcts
         Counter64,
      pr1645v2VEthInQueuesD7PerformanceQdOcts
         Counter64,
      pr1645v2VEthInQueuesD7PerformanceDropOcts
         Counter64,
      pr1645v2VEthInQueuesD7PerformanceRDropOcts
         Counter64,
      pr1645v2VEthInQueuesD7PerformanceCirTxOcts
         Counter64,
      pr1645v2VEthInQueuesD7PerformanceEirTxOcts
         Counter64,
      pr1645v2VEthInQueuesD7PerformanceViolTxOcts
         Counter64,
      pr1645v2VEthInQueuesD7PerformanceBandwidth
         Integer32
      }

pr1645v2VEthInQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2VEthInQueuesD7PerformanceEntry 10}

pr1645v2VEthInQueuesD7PerformanceTableIx OBJECT-TYPE
   SYNTAX      TableIndex
   MAX-ACCESS  not-accessible
   STATUS      current
   DESCRIPTION
      ""
   ::= {pr1645v2VEthInQueuesD7PerformanceEntry 11}

pr1645v2VEthInQueuesD7PerformanceSysUpTime OBJECT-TYPE
   SYNTAX      TimeTicks
   MAX-ACCESS  read-only
   STATUS      current
   DESCRIPTION
      "Path: virtualEthernet.performance.ifInPriorityQueues.d7Performance.sysUpTime

       Time in centi-second."
   ::= {pr1645v2VEthInQueuesD7PerformanceEntry 16777216}

pr1645v2VEthInQueuesD7PerformanceTotPkts OBJECT-TYPE
   SYNTAX      Counter64
   MAX-ACCESS  read-only
   STATUS      current
   DESCRIPTION
      "Path: virtualEthernet.performance.ifInPriorityQueues.d7Performance.totalPkts

       64 bit unsigned wrappable counter."
   ::= {pr1645v2VEthInQueuesD7PerformanceEntry 234881024}

pr1645v2VEthInQueuesD7PerformanceDirTxPkts OBJECT-TYPE
   SYNTAX      Counter64
   MAX-ACCESS  read-only
   STATUS      current
   DESCRIPTION
      "Path: virtualEthernet.performance.ifInPriorityQueues.d7Performance.directTxPkts

       64 bit unsigned wrappable counter."
   ::= {pr1645v2VEthInQueuesD7PerformanceEntry 33554432}

pr1645v2VEthInQueuesD7PerformanceQdPkts OBJECT-TYPE
   SYNTAX      Counter64
   MAX-ACCESS  read-only
   STATUS      current
   DESCRIPTION
      "Path: virtualEthernet.performance.ifInPriorityQueues.d7Performance.queuedPkts

       64 bit unsigned wrappable counter."
   ::= {pr1645v2VEthInQueuesD7PerformanceEntry 50331648}

pr1645v2VEthInQueuesD7PerformanceDropPkts OBJECT-TYPE
   SYNTAX      Counter64
   MAX-ACCESS  read-only
   STATUS      current
   DESCRIPTION
      "Path: virtualEthernet.performance.ifInPriorityQueues.d7Performance.droppedPkts

       64 bit unsigned wrappable counter."
   ::= {pr1645v2VEthInQueuesD7PerformanceEntry 67108864}

pr1645v2VEthInQueuesD7PerformanceRDropPkts OBJECT-TYPE
   SYNTAX      Counter64
   MAX-ACCESS  read-only
   STATUS      current
   DESCRIPTION
      "Path: virtualEthernet.performance.ifInPriorityQueues.d7Performance.redDroppedPkts

       64 bit unsigned wrappable counter."
   ::= {pr1645v2VEthInQueuesD7PerformanceEntry 201326592}

pr1645v2VEthInQueuesD7PerformanceCirTxPkts OBJECT-TYPE
   SYNTAX      Counter64
   MAX-ACCESS  read-only
   STATUS      current
   DESCRIPTION
      "Path: virtualEthernet.performance.ifInPriorityQueues.d7Performance.cirTxPkts

       64 bit unsigned wrappable counter."
   ::= {pr1645v2VEthInQueuesD7PerformanceEntry 83886080}

pr1645v2VEthInQueuesD7PerformanceEirTxPkts OBJECT-TYPE
   SYNTAX      Counter64
   MAX-ACCESS  read-only
   STATUS      current
   DESCRIPTION
      "Path: virtualEthernet.performance.ifInPriorityQueues.d7Performance.eirTxPkts

       64 bit unsigned wrappable counter."
   ::= {pr1645v2VEthInQueuesD7PerformanceEntry 100663296}

pr1645v2VEthInQueuesD7PerformanceViolTxPkts OBJECT-TYPE
   SYNTAX      Counter64
   MAX-ACCESS  read-only
   STATUS      current
   DESCRIPTION
      "Path: virtualEthernet.performance.ifInPriorityQueues.d7Performance.violateTxPkts

       64 bit unsigned wrappable counter."
   ::= {pr1645v2VEthInQueuesD7PerformanceEntry 301989888}

pr1645v2VEthInQueuesD7PerformanceTotOcts OBJECT-TYPE
   SYNTAX      Counter64
   MAX-ACCESS  read-only
   STATUS      current
   DESCRIPTION
      "Path: virtualEthernet.performance.ifInPriorityQueues.d7Performance.totalOctets

       64 bit unsigned wrappable counter."
   ::= {pr1645v2VEthInQueuesD7PerformanceEntry 251658240}

pr1645v2VEthInQueuesD7PerformanceDirTxOcts OBJECT-TYPE
   SYNTAX      Counter64
   MAX-ACCESS  read-only
   STATUS      current
   DESCRIPTION
      "Path: virtualEthernet.performance.ifInPriorityQueues.d7Performance.directTxOctets

       64 bit unsigned wrappable counter."
   ::= {pr1645v2VEthInQueuesD7PerformanceEntry 117440512}

pr1645v2VEthInQueuesD7PerformanceQdOcts OBJECT-TYPE
   SYNTAX      Counter64
   MAX-ACCESS  read-only
   STATUS      current
   DESCRIPTION
      "Path: virtualEthernet.performance.ifInPriorityQueues.d7Performance.queuedOctets

       64 bit unsigned wrappable counter."
   ::= {pr1645v2VEthInQueuesD7PerformanceEntry 134217728}

pr1645v2VEthInQueuesD7PerformanceDropOcts OBJECT-TYPE
   SYNTAX      Counter64
   MAX-ACCESS  read-only
   STATUS      current
   DESCRIPTION
      "Path: virtualEthernet.performance.ifInPriorityQueues.d7Performance.droppedOctets

       64 bit unsigned wrappable counter."
   ::= {pr1645v2VEthInQueuesD7PerformanceEntry 150994944}

pr1645v2VEthInQueuesD7PerformanceRDropOcts OBJECT-TYPE
   SYNTAX      Counter64
   MAX-ACCESS  read-only
   STATUS      current
   DESCRIPTION
      "Path: virtualEthernet.performance.ifInPriorityQueues.d7Performance.redDroppedOctets

       64 bit unsigned wrappable counter."
   ::= {pr1645v2VEthInQueuesD7PerformanceEntry 218103808}

pr1645v2VEthInQueuesD7PerformanceCirTxOcts OBJECT-TYPE
   SYNTAX      Counter64
   MAX-ACCESS  read-only
   STATUS      current
   DESCRIPTION
      "Path: virtualEthernet.performance.ifInPriorityQueues.d7Performance.cirTxOctets

       64 bit unsigned wrappable counter."
   ::= {pr1645v2VEthInQueuesD7PerformanceEntry 167772160}

pr1645v2VEthInQueuesD7PerformanceEirTxOcts OBJECT-TYPE
   SYNTAX      Counter64
   MAX-ACCESS  read-only
   STATUS      current
   DESCRIPTION
      "Path: virtualEthernet.performance.ifInPriorityQueues.d7Performance.eirTxOctets

       64 bit unsigned wrappable counter."
   ::= {pr1645v2VEthInQueuesD7PerformanceEntry 184549376}

pr1645v2VEthInQueuesD7PerformanceViolTxOcts OBJECT-TYPE
   SYNTAX      Counter64
   MAX-ACCESS  read-only
   STATUS      current
   DESCRIPTION
      "Path: virtualEthernet.performance.ifInPriorityQueues.d7Performance.violateTxOctets

       64 bit unsigned wrappable counter."
   ::= {pr1645v2VEthInQueuesD7PerformanceEntry 318767104}

pr1645v2VEthInQueuesD7PerformanceBandwidth OBJECT-TYPE
   SYNTAX      Integer32
   MAX-ACCESS  read-only
   STATUS      current
   DESCRIPTION
      "Path: virtualEthernet.performance.ifInPriorityQueues.d7Performance.bandwidth

       unit name = bps
       formula = 8 * ; 8 /"
   ::= {pr1645v2VEthInQueuesD7PerformanceEntry 268435456}


pr1645v2VEthInBandwidth OBJECT IDENTIFIER ::= {pr1645v2VEth 181}

pr1645v2VEthInBandwidthSSCTable OBJECT-TYPE
   SYNTAX      SEQUENCE OF Pr1645v2VEthInBandwidthEntry
   MAX-ACCESS  not-accessible
   STATUS      current
   DESCRIPTION
      "bandwidth"
   ::= {pr1645v2VEthInBandwidth 1}

pr1645v2VEthInBandwidthEntry OBJECT-TYPE
   SYNTAX      Pr1645v2VEthInBandwidthEntry
   MAX-ACCESS  not-accessible
   STATUS      current
   DESCRIPTION
      ""
   INDEX      { pr1645v2VEthInBandwidthGlobalIx }
   ::= {pr1645v2VEthInBandwidthSSCTable 1}

Pr1645v2VEthInBandwidthEntry ::=
   SEQUENCE
      {
      pr1645v2VEthInBandwidthGlobalIx
         GlobalIndex,
      pr1645v2VEthInBandwidth15sec
         Integer32,
      pr1645v2VEthInBandwidth30sec
         Integer32,
      pr1645v2VEthInBandwidth1min
         Integer32,
      pr1645v2VEthInBandwidth2min
         Integer32,
      pr1645v2VEthInBandwidth5min
         Integer32
      }

pr1645v2VEthInBandwidthGlobalIx OBJECT-TYPE
   SYNTAX      GlobalIndex
   MAX-ACCESS  not-accessible
   STATUS      current
   DESCRIPTION
      "The value of the tlsCntTreeGlobalIndex of the MANAGED OBJECT."
   ::= {pr1645v2VEthInBandwidthEntry 10}

pr1645v2VEthInBandwidth15sec OBJECT-TYPE
   SYNTAX      Integer32
   MAX-ACCESS  read-only
   STATUS      current
   DESCRIPTION
      "Path: virtualEthernet.performance.ifInBandwidth.15sec

       unit name = bps
       formula = 8 * ; 8 /"
   ::= {pr1645v2VEthInBandwidthEntry 83886080}

pr1645v2VEthInBandwidth30sec OBJECT-TYPE
   SYNTAX      Integer32
   MAX-ACCESS  read-only
   STATUS      current
   DESCRIPTION
      "Path: virtualEthernet.performance.ifInBandwidth.30sec

       unit name = bps
       formula = 8 * ; 8 /"
   ::= {pr1645v2VEthInBandwidthEntry 167772160}

pr1645v2VEthInBandwidth1min OBJECT-TYPE
   SYNTAX      Integer32
   MAX-ACCESS  read-only
   STATUS      current
   DESCRIPTION
      "Path: virtualEthernet.performance.ifInBandwidth.1min

       unit name = bps
       formula = 8 * ; 8 /"
   ::= {pr1645v2VEthInBandwidthEntry 335544320}

pr1645v2VEthInBandwidth2min OBJECT-TYPE
   SYNTAX      Integer32
   MAX-ACCESS  read-only
   STATUS      current
   DESCRIPTION
      "Path: virtualEthernet.performance.ifInBandwidth.2min

       unit name = bps
       formula = 8 * ; 8 /"
   ::= {pr1645v2VEthInBandwidthEntry 671088640}

pr1645v2VEthInBandwidth5min OBJECT-TYPE
   SYNTAX      Integer32
   MAX-ACCESS  read-only
   STATUS      current
   DESCRIPTION
      "Path: virtualEthernet.performance.ifInBandwidth.5min

       unit name = bps
       formula = 8 * ; 8 /"
   ::= {pr1645v2VEthInBandwidthEntry 1677721600}


pr1645v2VEthOutOctets OBJECT IDENTIFIER ::= {pr1645v2VEth 115}

pr1645v2VEthOutOctetsTable OBJECT-TYPE
   SYNTAX      SEQUENCE OF Pr1645v2VEthOutOctetsEntry
   MAX-ACCESS  not-accessible
   STATUS      current
   DESCRIPTION
      "ifOutOctets"
   ::= {pr1645v2VEthOutOctets 1}

pr1645v2VEthOutOctetsEntry OBJECT-TYPE
   SYNTAX      Pr1645v2VEthOutOctetsEntry
   MAX-ACCESS  not-accessible
   STATUS      current
   DESCRIPTION
      ""
   INDEX      { pr1645v2VEthOutOctetsGlobalIx }
   ::= {pr1645v2VEthOutOctetsTable 1}

Pr1645v2VEthOutOctetsEntry ::=
   SEQUENCE
      {
      pr1645v2VEthOutOctetsGlobalIx
         GlobalIndex,
      pr1645v2VEthOutOctetsValue
         Counter64
      }

pr1645v2VEthOutOctetsGlobalIx OBJECT-TYPE
   SYNTAX      GlobalIndex
   MAX-ACCESS  not-accessible
   STATUS      current
   DESCRIPTION
      "The value of the tlsCntTreeGlobalIndex of the MANAGED OBJECT."
   ::= {pr1645v2VEthOutOctetsEntry 10}

pr1645v2VEthOutOctetsValue OBJECT-TYPE
   SYNTAX      Counter64
   MAX-ACCESS  read-only
   STATUS      current
   DESCRIPTION
      "Path: virtualEthernet.performance.ifOutOctets

       64 bit unsigned wrappable counter."
   ::= {pr1645v2VEthOutOctetsEntry 2147483648}


pr1645v2VEthOutUcastPkts OBJECT IDENTIFIER ::= {pr1645v2VEth 116}

pr1645v2VEthOutUcastPktsTable OBJECT-TYPE
   SYNTAX      SEQUENCE OF Pr1645v2VEthOutUcastPktsEntry
   MAX-ACCESS  not-accessible
   STATUS      current
   DESCRIPTION
      "ifOutUcastPkts"
   ::= {pr1645v2VEthOutUcastPkts 1}

pr1645v2VEthOutUcastPktsEntry OBJECT-TYPE
   SYNTAX      Pr1645v2VEthOutUcastPktsEntry
   MAX-ACCESS  not-accessible
   STATUS      current
   DESCRIPTION
      ""
   INDEX      { pr1645v2VEthOutUcastPktsGlobalIx }
   ::= {pr1645v2VEthOutUcastPktsTable 1}

Pr1645v2VEthOutUcastPktsEntry ::=
   SEQUENCE
      {
      pr1645v2VEthOutUcastPktsGlobalIx
         GlobalIndex,
      pr1645v2VEthOutUcastPktsValue
         Counter64
      }

pr1645v2VEthOutUcastPktsGlobalIx OBJECT-TYPE
   SYNTAX      GlobalIndex
   MAX-ACCESS  not-accessible
   STATUS      current
   DESCRIPTION
      "The value of the tlsCntTreeGlobalIndex of the MANAGED OBJECT."
   ::= {pr1645v2VEthOutUcastPktsEntry 10}

pr1645v2VEthOutUcastPktsValue OBJECT-TYPE
   SYNTAX      Counter64
   MAX-ACCESS  read-only
   STATUS      current
   DESCRIPTION
      "Path: virtualEthernet.performance.ifOutUcastPkts

       64 bit unsigned wrappable counter."
   ::= {pr1645v2VEthOutUcastPktsEntry 2147483648}


pr1645v2VEthOutNUcastPkts OBJECT IDENTIFIER ::= {pr1645v2VEth 117}

pr1645v2VEthOutNUcastPktsTable OBJECT-TYPE
   SYNTAX      SEQUENCE OF Pr1645v2VEthOutNUcastPktsEntry
   MAX-ACCESS  not-accessible
   STATUS      current
   DESCRIPTION
      "ifOutNUcastPkts"
   ::= {pr1645v2VEthOutNUcastPkts 1}

pr1645v2VEthOutNUcastPktsEntry OBJECT-TYPE
   SYNTAX      Pr1645v2VEthOutNUcastPktsEntry
   MAX-ACCESS  not-accessible
   STATUS      current
   DESCRIPTION
      ""
   INDEX      { pr1645v2VEthOutNUcastPktsGlobalIx }
   ::= {pr1645v2VEthOutNUcastPktsTable 1}

Pr1645v2VEthOutNUcastPktsEntry ::=
   SEQUENCE
      {
      pr1645v2VEthOutNUcastPktsGlobalIx
         GlobalIndex,
      pr1645v2VEthOutNUcastPktsValue
         Counter64
      }

pr1645v2VEthOutNUcastPktsGlobalIx OBJECT-TYPE
   SYNTAX      GlobalIndex
   MAX-ACCESS  not-accessible
   STATUS      current
   DESCRIPTION
      "The value of the tlsCntTreeGlobalIndex of the MANAGED OBJECT."
   ::= {pr1645v2VEthOutNUcastPktsEntry 10}

pr1645v2VEthOutNUcastPktsValue OBJECT-TYPE
   SYNTAX      Counter64
   MAX-ACCESS  read-only
   STATUS      current
   DESCRIPTION
      "Path: virtualEthernet.performance.ifOutNUcastPkts

       64 bit unsigned wrappable counter."
   ::= {pr1645v2VEthOutNUcastPktsEntry 2147483648}


pr1645v2VEthOutBcastPkts OBJECT IDENTIFIER ::= {pr1645v2VEth 217}

pr1645v2VEthOutBcastPktsTable OBJECT-TYPE
   SYNTAX      SEQUENCE OF Pr1645v2VEthOutBcastPktsEntry
   MAX-ACCESS  not-accessible
   STATUS      current
   DESCRIPTION
      "ifOutBcastPkts"
   ::= {pr1645v2VEthOutBcastPkts 1}

pr1645v2VEthOutBcastPktsEntry OBJECT-TYPE
   SYNTAX      Pr1645v2VEthOutBcastPktsEntry
   MAX-ACCESS  not-accessible
   STATUS      current
   DESCRIPTION
      ""
   INDEX      { pr1645v2VEthOutBcastPktsGlobalIx }
   ::= {pr1645v2VEthOutBcastPktsTable 1}

Pr1645v2VEthOutBcastPktsEntry ::=
   SEQUENCE
      {
      pr1645v2VEthOutBcastPktsGlobalIx
         GlobalIndex,
      pr1645v2VEthOutBcastPktsValue
         Counter64
      }

pr1645v2VEthOutBcastPktsGlobalIx OBJECT-TYPE
   SYNTAX      GlobalIndex
   MAX-ACCESS  not-accessible
   STATUS      current
   DESCRIPTION
      "The value of the tlsCntTreeGlobalIndex of the MANAGED OBJECT."
   ::= {pr1645v2VEthOutBcastPktsEntry 10}

pr1645v2VEthOutBcastPktsValue OBJECT-TYPE
   SYNTAX      Counter64
   MAX-ACCESS  read-only
   STATUS      current
   DESCRIPTION
      "Path: virtualEthernet.performance.ifOutBcastPkts

       64 bit unsigned wrappable counter."
   ::= {pr1645v2VEthOutBcastPktsEntry 2147483648}


pr1645v2VEthOutMcastPkts OBJECT IDENTIFIER ::= {pr1645v2VEth 227}

pr1645v2VEthOutMcastPktsTable OBJECT-TYPE
   SYNTAX      SEQUENCE OF Pr1645v2VEthOutMcastPktsEntry
   MAX-ACCESS  not-accessible
   STATUS      current
   DESCRIPTION
      "ifOutMcastPkts"
   ::= {pr1645v2VEthOutMcastPkts 1}

pr1645v2VEthOutMcastPktsEntry OBJECT-TYPE
   SYNTAX      Pr1645v2VEthOutMcastPktsEntry
   MAX-ACCESS  not-accessible
   STATUS      current
   DESCRIPTION
      ""
   INDEX      { pr1645v2VEthOutMcastPktsGlobalIx }
   ::= {pr1645v2VEthOutMcastPktsTable 1}

Pr1645v2VEthOutMcastPktsEntry ::=
   SEQUENCE
      {
      pr1645v2VEthOutMcastPktsGlobalIx
         GlobalIndex,
      pr1645v2VEthOutMcastPktsValue
         Counter64
      }

pr1645v2VEthOutMcastPktsGlobalIx OBJECT-TYPE
   SYNTAX      GlobalIndex
   MAX-ACCESS  not-accessible
   STATUS      current
   DESCRIPTION
      "The value of the tlsCntTreeGlobalIndex of the MANAGED OBJECT."
   ::= {pr1645v2VEthOutMcastPktsEntry 10}

pr1645v2VEthOutMcastPktsValue OBJECT-TYPE
   SYNTAX      Counter64
   MAX-ACCESS  read-only
   STATUS      current
   DESCRIPTION
      "Path: virtualEthernet.performance.ifOutMcastPkts

       64 bit unsigned wrappable counter."
   ::= {pr1645v2VEthOutMcastPktsEntry 2147483648}


pr1645v2VEthOutDiscards OBJECT IDENTIFIER ::= {pr1645v2VEth 118}

pr1645v2VEthOutDiscardsTable OBJECT-TYPE
   SYNTAX      SEQUENCE OF Pr1645v2VEthOutDiscardsEntry
   MAX-ACCESS  not-accessible
   STATUS      current
   DESCRIPTION
      "ifOutDiscards"
   ::= {pr1645v2VEthOutDiscards 1}

pr1645v2VEthOutDiscardsEntry OBJECT-TYPE
   SYNTAX      Pr1645v2VEthOutDiscardsEntry
   MAX-ACCESS  not-accessible
   STATUS      current
   DESCRIPTION
      ""
   INDEX      { pr1645v2VEthOutDiscardsGlobalIx }
   ::= {pr1645v2VEthOutDiscardsTable 1}

Pr1645v2VEthOutDiscardsEntry ::=
   SEQUENCE
      {
      pr1645v2VEthOutDiscardsGlobalIx
         GlobalIndex,
      pr1645v2VEthOutDiscardsValue
         Counter64
      }

pr1645v2VEthOutDiscardsGlobalIx OBJECT-TYPE
   SYNTAX      GlobalIndex
   MAX-ACCESS  not-accessible
   STATUS      current
   DESCRIPTION
      "The value of the tlsCntTreeGlobalIndex of the MANAGED OBJECT."
   ::= {pr1645v2VEthOutDiscardsEntry 10}

pr1645v2VEthOutDiscardsValue OBJECT-TYPE
   SYNTAX      Counter64
   MAX-ACCESS  read-only
   STATUS      current
   DESCRIPTION
      "Path: virtualEthernet.performance.ifOutDiscards

       64 bit unsigned wrappable counter."
   ::= {pr1645v2VEthOutDiscardsEntry 2147483648}


pr1645v2VEthOutErrors OBJECT IDENTIFIER ::= {pr1645v2VEth 119}

pr1645v2VEthOutErrorsTable OBJECT-TYPE
   SYNTAX      SEQUENCE OF Pr1645v2VEthOutErrorsEntry
   MAX-ACCESS  not-accessible
   STATUS      current
   DESCRIPTION
      "ifOutErrors"
   ::= {pr1645v2VEthOutErrors 1}

pr1645v2VEthOutErrorsEntry OBJECT-TYPE
   SYNTAX      Pr1645v2VEthOutErrorsEntry
   MAX-ACCESS  not-accessible
   STATUS      current
   DESCRIPTION
      ""
   INDEX      { pr1645v2VEthOutErrorsGlobalIx }
   ::= {pr1645v2VEthOutErrorsTable 1}

Pr1645v2VEthOutErrorsEntry ::=
   SEQUENCE
      {
      pr1645v2VEthOutErrorsGlobalIx
         GlobalIndex,
      pr1645v2VEthOutErrorsValue
         Counter64
      }

pr1645v2VEthOutErrorsGlobalIx OBJECT-TYPE
   SYNTAX      GlobalIndex
   MAX-ACCESS  not-accessible
   STATUS      current
   DESCRIPTION
      "The value of the tlsCntTreeGlobalIndex of the MANAGED OBJECT."
   ::= {pr1645v2VEthOutErrorsEntry 10}

pr1645v2VEthOutErrorsValue OBJECT-TYPE
   SYNTAX      Counter64
   MAX-ACCESS  read-only
   STATUS      current
   DESCRIPTION
      "Path: virtualEthernet.performance.ifOutErrors

       64 bit unsigned wrappable counter."
   ::= {pr1645v2VEthOutErrorsEntry 2147483648}


pr1645v2VEthOutQLen OBJECT IDENTIFIER ::= {pr1645v2VEth 120}

pr1645v2VEthOutQLenTable OBJECT-TYPE
   SYNTAX      SEQUENCE OF Pr1645v2VEthOutQLenEntry
   MAX-ACCESS  not-accessible
   STATUS      current
   DESCRIPTION
      "ifOutQLen"
   ::= {pr1645v2VEthOutQLen 1}

pr1645v2VEthOutQLenEntry OBJECT-TYPE
   SYNTAX      Pr1645v2VEthOutQLenEntry
   MAX-ACCESS  not-accessible
   STATUS      current
   DESCRIPTION
      ""
   INDEX      { pr1645v2VEthOutQLenGlobalIx }
   ::= {pr1645v2VEthOutQLenTable 1}

Pr1645v2VEthOutQLenEntry ::=
   SEQUENCE
      {
      pr1645v2VEthOutQLenGlobalIx
         GlobalIndex,
      pr1645v2VEthOutQLenValue
         Gauge32
      }

pr1645v2VEthOutQLenGlobalIx OBJECT-TYPE
   SYNTAX      GlobalIndex
   MAX-ACCESS  not-accessible
   STATUS      current
   DESCRIPTION
      "The value of the tlsCntTreeGlobalIndex of the MANAGED OBJECT."
   ::= {pr1645v2VEthOutQLenEntry 10}

pr1645v2VEthOutQLenValue OBJECT-TYPE
   SYNTAX      Gauge32
   MAX-ACCESS  read-only
   STATUS      current
   DESCRIPTION
      "Path: virtualEthernet.performance.ifOutQLen

       32 bit unsigned gauge value."
   ::= {pr1645v2VEthOutQLenEntry 2147483648}


pr1645v2VEthOutDropEx OBJECT IDENTIFIER ::= {pr1645v2VEth 127}

pr1645v2VEthOutDropExTable OBJECT-TYPE
   SYNTAX      SEQUENCE OF Pr1645v2VEthOutDropExEntry
   MAX-ACCESS  not-accessible
   STATUS      current
   DESCRIPTION
      "ifOutDiscards"
   ::= {pr1645v2VEthOutDropEx 1}

pr1645v2VEthOutDropExEntry OBJECT-TYPE
   SYNTAX      Pr1645v2VEthOutDropExEntry
   MAX-ACCESS  not-accessible
   STATUS      current
   DESCRIPTION
      ""
   INDEX      { pr1645v2VEthOutDropExGlobalIx }
   ::= {pr1645v2VEthOutDropExTable 1}

Pr1645v2VEthOutDropExEntry ::=
   SEQUENCE
      {
      pr1645v2VEthOutDropExGlobalIx
         GlobalIndex,
      pr1645v2VEthOutDropExValue
         Counter64
      }

pr1645v2VEthOutDropExGlobalIx OBJECT-TYPE
   SYNTAX      GlobalIndex
   MAX-ACCESS  not-accessible
   STATUS      current
   DESCRIPTION
      "The value of the tlsCntTreeGlobalIndex of the MANAGED OBJECT."
   ::= {pr1645v2VEthOutDropExEntry 10}

pr1645v2VEthOutDropExValue OBJECT-TYPE
   SYNTAX      Counter64
   MAX-ACCESS  read-only
   STATUS      current
   DESCRIPTION
      "Path: virtualEthernet.performance.ifOutDropLevelExceeded

       64 bit unsigned wrappable counter."
   ::= {pr1645v2VEthOutDropExEntry 2147483648}


pr1645v2VEthOutDropNoArp OBJECT IDENTIFIER ::= {pr1645v2VEth 134}

pr1645v2VEthOutDropNoArpTable OBJECT-TYPE
   SYNTAX      SEQUENCE OF Pr1645v2VEthOutDropNoArpEntry
   MAX-ACCESS  not-accessible
   STATUS      current
   DESCRIPTION
      "ifOutDiscards"
   ::= {pr1645v2VEthOutDropNoArp 1}

pr1645v2VEthOutDropNoArpEntry OBJECT-TYPE
   SYNTAX      Pr1645v2VEthOutDropNoArpEntry
   MAX-ACCESS  not-accessible
   STATUS      current
   DESCRIPTION
      ""
   INDEX      { pr1645v2VEthOutDropNoArpGlobalIx }
   ::= {pr1645v2VEthOutDropNoArpTable 1}

Pr1645v2VEthOutDropNoArpEntry ::=
   SEQUENCE
      {
      pr1645v2VEthOutDropNoArpGlobalIx
         GlobalIndex,
      pr1645v2VEthOutDropNoArpValue
         Counter64
      }

pr1645v2VEthOutDropNoArpGlobalIx OBJECT-TYPE
   SYNTAX      GlobalIndex
   MAX-ACCESS  not-accessible
   STATUS      current
   DESCRIPTION
      "The value of the tlsCntTreeGlobalIndex of the MANAGED OBJECT."
   ::= {pr1645v2VEthOutDropNoArpEntry 10}

pr1645v2VEthOutDropNoArpValue OBJECT-TYPE
   SYNTAX      Counter64
   MAX-ACCESS  read-only
   STATUS      current
   DESCRIPTION
      "Path: virtualEthernet.performance.ifOutDiscardsNoArp

       64 bit unsigned wrappable counter."
   ::= {pr1645v2VEthOutDropNoArpEntry 2147483648}


pr1645v2VEthOutDropFilter OBJECT IDENTIFIER ::= {pr1645v2VEth 138}

pr1645v2VEthOutDropFilterTable OBJECT-TYPE
   SYNTAX      SEQUENCE OF Pr1645v2VEthOutDropFilterEntry
   MAX-ACCESS  not-accessible
   STATUS      current
   DESCRIPTION
      "ifOutDiscards"
   ::= {pr1645v2VEthOutDropFilter 1}

pr1645v2VEthOutDropFilterEntry OBJECT-TYPE
   SYNTAX      Pr1645v2VEthOutDropFilterEntry
   MAX-ACCESS  not-accessible
   STATUS      current
   DESCRIPTION
      ""
   INDEX      { pr1645v2VEthOutDropFilterGlobalIx }
   ::= {pr1645v2VEthOutDropFilterTable 1}

Pr1645v2VEthOutDropFilterEntry ::=
   SEQUENCE
      {
      pr1645v2VEthOutDropFilterGlobalIx
         GlobalIndex,
      pr1645v2VEthOutDropFilterValue
         Counter64
      }

pr1645v2VEthOutDropFilterGlobalIx OBJECT-TYPE
   SYNTAX      GlobalIndex
   MAX-ACCESS  not-accessible
   STATUS      current
   DESCRIPTION
      "The value of the tlsCntTreeGlobalIndex of the MANAGED OBJECT."
   ::= {pr1645v2VEthOutDropFilterEntry 10}

pr1645v2VEthOutDropFilterValue OBJECT-TYPE
   SYNTAX      Counter64
   MAX-ACCESS  read-only
   STATUS      current
   DESCRIPTION
      "Path: virtualEthernet.performance.ifOutDiscardsFilter

       64 bit unsigned wrappable counter."
   ::= {pr1645v2VEthOutDropFilterEntry 2147483648}


pr1645v2VEthOutQueues OBJECT IDENTIFIER ::= {pr1645v2VEth 129}

pr1645v2VEthOutQueuesSSCTable OBJECT-TYPE
   SYNTAX      SEQUENCE OF Pr1645v2VEthOutQueuesEntry
   MAX-ACCESS  not-accessible
   STATUS      current
   DESCRIPTION
      "Queue Lengths"
   ::= {pr1645v2VEthOutQueues 1}

pr1645v2VEthOutQueuesEntry OBJECT-TYPE
   SYNTAX      Pr1645v2VEthOutQueuesEntry
   MAX-ACCESS  not-accessible
   STATUS      current
   DESCRIPTION
      ""
   INDEX      { pr1645v2VEthOutQueuesGlobalIx,
                pr1645v2VEthOutQueuesTableIx }
   ::= {pr1645v2VEthOutQueuesSSCTable 1}

Pr1645v2VEthOutQueuesEntry ::=
   SEQUENCE
      {
      pr1645v2VEthOutQueuesGlobalIx
         GlobalIndex,
      pr1645v2VEthOutQueuesTableIx
         TableIndex,
      pr1645v2VEthOutQueuesName
         INTEGER,
      pr1645v2VEthOutQueuesLength
         Integer32,
      pr1645v2VEthOutQueuesOctetLength
         Integer32,
      pr1645v2VEthOutQueuesRedLength
         Integer32,
      pr1645v2VEthOutQueuesPacketsTotal
         Counter64,
      pr1645v2VEthOutQueuesPacketsDirectTx
         Counter64,
      pr1645v2VEthOutQueuesPacketsQueued
         Counter64,
      pr1645v2VEthOutQueuesPacketsDropped
         Counter64,
      pr1645v2VEthOutQueuesPacketsRedDropped
         Counter64,
      pr1645v2VEthOutQueuesPacketsCirTx
         Counter64,
      pr1645v2VEthOutQueuesPacketsEirTx
         Counter64,
      pr1645v2VEthOutQueuesPacketsViolateTx
         Counter64,
      pr1645v2VEthOutQueuesOctetsTotal
         Counter64,
      pr1645v2VEthOutQueuesOctetsDirectTx
         Counter64,
      pr1645v2VEthOutQueuesOctetsQueued
         Counter64,
      pr1645v2VEthOutQueuesOctetsDropped
         Counter64,
      pr1645v2VEthOutQueuesOctetsRedDropped
         Counter64,
      pr1645v2VEthOutQueuesOctetsCirTx
         Counter64,
      pr1645v2VEthOutQueuesOctetsEirTx
         Counter64,
      pr1645v2VEthOutQueuesOctetsViolateTx
         Counter64,
      pr1645v2VEthOutQueuesOctetsBandwidth15sec
         Integer32,
      pr1645v2VEthOutQueuesOctetsBandwidth30sec
         Integer32,
      pr1645v2VEthOutQueuesOctetsBandwidth1min
         Integer32,
      pr1645v2VEthOutQueuesOctetsBandwidth2min
         Integer32,
      pr1645v2VEthOutQueuesOctetsBandwidth5min
         Integer32
      }

pr1645v2VEthOutQueuesGlobalIx OBJECT-TYPE
   SYNTAX      GlobalIndex
   MAX-ACCESS  not-accessible
   STATUS      current
   DESCRIPTION
      "The value of the tlsCntTreeGlobalIndex of the MANAGED OBJECT."
   ::= {pr1645v2VEthOutQueuesEntry 10}

pr1645v2VEthOutQueuesTableIx OBJECT-TYPE
   SYNTAX      TableIndex
   MAX-ACCESS  not-accessible
   STATUS      current
   DESCRIPTION
      ""
   ::= {pr1645v2VEthOutQueuesEntry 11}

pr1645v2VEthOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2VEthOutQueuesEntry 16777216}

pr1645v2VEthOutQueuesLength OBJECT-TYPE
   SYNTAX      Integer32
   MAX-ACCESS  read-only
   STATUS      current
   DESCRIPTION
      "Path: virtualEthernet.performance.ifOutPriorityQueues.length"
   ::= {pr1645v2VEthOutQueuesEntry 33554432}

pr1645v2VEthOutQueuesOctetLength OBJECT-TYPE
   SYNTAX      Integer32
   MAX-ACCESS  read-only
   STATUS      current
   DESCRIPTION
      "Path: virtualEthernet.performance.ifOutPriorityQueues.octetLength"
   ::= {pr1645v2VEthOutQueuesEntry 150994944}

pr1645v2VEthOutQueuesRedLength OBJECT-TYPE
   SYNTAX      Integer32
   MAX-ACCESS  read-only
   STATUS      current
   DESCRIPTION
      "Path: virtualEthernet.performance.ifOutPriorityQueues.redLength"
   ::= {pr1645v2VEthOutQueuesEntry 134217728}

pr1645v2VEthOutQueuesPacketsTotal OBJECT-TYPE
   SYNTAX      Counter64
   MAX-ACCESS  read-only
   STATUS      current
   DESCRIPTION
      "Path: virtualEthernet.performance.ifOutPriorityQueues.packets.total

       64 bit unsigned wrappable counter."
   ::= {pr1645v2VEthOutQueuesEntry 50790400}

pr1645v2VEthOutQueuesPacketsDirectTx OBJECT-TYPE
   SYNTAX      Counter64
   MAX-ACCESS  read-only
   STATUS      current
   DESCRIPTION
      "Path: virtualEthernet.performance.ifOutPriorityQueues.packets.directTx

       64 bit unsigned wrappable counter."
   ::= {pr1645v2VEthOutQueuesEntry 50397184}

pr1645v2VEthOutQueuesPacketsQueued OBJECT-TYPE
   SYNTAX      Counter64
   MAX-ACCESS  read-only
   STATUS      current
   DESCRIPTION
      "Path: virtualEthernet.performance.ifOutPriorityQueues.packets.queued

       64 bit unsigned wrappable counter."
   ::= {pr1645v2VEthOutQueuesEntry 50462720}

pr1645v2VEthOutQueuesPacketsDropped OBJECT-TYPE
   SYNTAX      Counter64
   MAX-ACCESS  read-only
   STATUS      current
   DESCRIPTION
      "Path: virtualEthernet.performance.ifOutPriorityQueues.packets.dropped

       64 bit unsigned wrappable counter."
   ::= {pr1645v2VEthOutQueuesEntry 50528256}

pr1645v2VEthOutQueuesPacketsRedDropped OBJECT-TYPE
   SYNTAX      Counter64
   MAX-ACCESS  read-only
   STATUS      current
   DESCRIPTION
      "Path: virtualEthernet.performance.ifOutPriorityQueues.packets.redDropped

       64 bit unsigned wrappable counter."
   ::= {pr1645v2VEthOutQueuesEntry 50724864}

pr1645v2VEthOutQueuesPacketsCirTx OBJECT-TYPE
   SYNTAX      Counter64
   MAX-ACCESS  read-only
   STATUS      current
   DESCRIPTION
      "Path: virtualEthernet.performance.ifOutPriorityQueues.packets.cirTx

       64 bit unsigned wrappable counter."
   ::= {pr1645v2VEthOutQueuesEntry 50593792}

pr1645v2VEthOutQueuesPacketsEirTx OBJECT-TYPE
   SYNTAX      Counter64
   MAX-ACCESS  read-only
   STATUS      current
   DESCRIPTION
      "Path: virtualEthernet.performance.ifOutPriorityQueues.packets.eirTx

       64 bit unsigned wrappable counter."
   ::= {pr1645v2VEthOutQueuesEntry 50659328}

pr1645v2VEthOutQueuesPacketsViolateTx OBJECT-TYPE
   SYNTAX      Counter64
   MAX-ACCESS  read-only
   STATUS      current
   DESCRIPTION
      "Path: virtualEthernet.performance.ifOutPriorityQueues.packets.violateTx

       64 bit unsigned wrappable counter."
   ::= {pr1645v2VEthOutQueuesEntry 50855936}

pr1645v2VEthOutQueuesOctetsTotal OBJECT-TYPE
   SYNTAX      Counter64
   MAX-ACCESS  read-only
   STATUS      current
   DESCRIPTION
      "Path: virtualEthernet.performance.ifOutPriorityQueues.octets.total

       64 bit unsigned wrappable counter."
   ::= {pr1645v2VEthOutQueuesEntry 67567616}

pr1645v2VEthOutQueuesOctetsDirectTx OBJECT-TYPE
   SYNTAX      Counter64
   MAX-ACCESS  read-only
   STATUS      current
   DESCRIPTION
      "Path: virtualEthernet.performance.ifOutPriorityQueues.octets.directTx

       64 bit unsigned wrappable counter."
   ::= {pr1645v2VEthOutQueuesEntry 67174400}

pr1645v2VEthOutQueuesOctetsQueued OBJECT-TYPE
   SYNTAX      Counter64
   MAX-ACCESS  read-only
   STATUS      current
   DESCRIPTION
      "Path: virtualEthernet.performance.ifOutPriorityQueues.octets.queued

       64 bit unsigned wrappable counter."
   ::= {pr1645v2VEthOutQueuesEntry 67239936}

pr1645v2VEthOutQueuesOctetsDropped OBJECT-TYPE
   SYNTAX      Counter64
   MAX-ACCESS  read-only
   STATUS      current
   DESCRIPTION
      "Path: virtualEthernet.performance.ifOutPriorityQueues.octets.dropped

       64 bit unsigned wrappable counter."
   ::= {pr1645v2VEthOutQueuesEntry 67305472}

pr1645v2VEthOutQueuesOctetsRedDropped OBJECT-TYPE
   SYNTAX      Counter64
   MAX-ACCESS  read-only
   STATUS      current
   DESCRIPTION
      "Path: virtualEthernet.performance.ifOutPriorityQueues.octets.redDropped

       64 bit unsigned wrappable counter."
   ::= {pr1645v2VEthOutQueuesEntry 67502080}

pr1645v2VEthOutQueuesOctetsCirTx OBJECT-TYPE
   SYNTAX      Counter64
   MAX-ACCESS  read-only
   STATUS      current
   DESCRIPTION
      "Path: virtualEthernet.performance.ifOutPriorityQueues.octets.cirTx

       64 bit unsigned wrappable counter."
   ::= {pr1645v2VEthOutQueuesEntry 67371008}

pr1645v2VEthOutQueuesOctetsEirTx OBJECT-TYPE
   SYNTAX      Counter64
   MAX-ACCESS  read-only
   STATUS      current
   DESCRIPTION
      "Path: virtualEthernet.performance.ifOutPriorityQueues.octets.eirTx

       64 bit unsigned wrappable counter."
   ::= {pr1645v2VEthOutQueuesEntry 67436544}

pr1645v2VEthOutQueuesOctetsViolateTx OBJECT-TYPE
   SYNTAX      Counter64
   MAX-ACCESS  read-only
   STATUS      current
   DESCRIPTION
      "Path: virtualEthernet.performance.ifOutPriorityQueues.octets.violateTx

       64 bit unsigned wrappable counter."
   ::= {pr1645v2VEthOutQueuesEntry 67633152}

pr1645v2VEthOutQueuesOctetsBandwidth15sec OBJECT-TYPE
   SYNTAX      Integer32
   MAX-ACCESS  read-only
   STATUS      current
   DESCRIPTION
      "Path: virtualEthernet.performance.ifOutPriorityQueues.octets.bandwidth.15sec

       unit name = bps
       formula = 8 * ; 8 /"
   ::= {pr1645v2VEthOutQueuesEntry 70386944}

pr1645v2VEthOutQueuesOctetsBandwidth30sec OBJECT-TYPE
   SYNTAX      Integer32
   MAX-ACCESS  read-only
   STATUS      current
   DESCRIPTION
      "Path: virtualEthernet.performance.ifOutPriorityQueues.octets.bandwidth.30sec

       unit name = bps
       formula = 8 * ; 8 /"
   ::= {pr1645v2VEthOutQueuesEntry 70388224}

pr1645v2VEthOutQueuesOctetsBandwidth1min OBJECT-TYPE
   SYNTAX      Integer32
   MAX-ACCESS  read-only
   STATUS      current
   DESCRIPTION
      "Path: virtualEthernet.performance.ifOutPriorityQueues.octets.bandwidth.1min

       unit name = bps
       formula = 8 * ; 8 /"
   ::= {pr1645v2VEthOutQueuesEntry 70390784}

pr1645v2VEthOutQueuesOctetsBandwidth2min OBJECT-TYPE
   SYNTAX      Integer32
   MAX-ACCESS  read-only
   STATUS      current
   DESCRIPTION
      "Path: virtualEthernet.performance.ifOutPriorityQueues.octets.bandwidth.2min

       unit name = bps
       formula = 8 * ; 8 /"
   ::= {pr1645v2VEthOutQueuesEntry 70395904}

pr1645v2VEthOutQueuesOctetsBandwidth5min OBJECT-TYPE
   SYNTAX      Integer32
   MAX-ACCESS  read-only
   STATUS      current
   DESCRIPTION
      "Path: virtualEthernet.performance.ifOutPriorityQueues.octets.bandwidth.5min

       unit name = bps
       formula = 8 * ; 8 /"
   ::= {pr1645v2VEthOutQueuesEntry 70411264}

pr1645v2VEthOutQueuesH2Performance OBJECT-TYPE
   SYNTAX      SEQUENCE OF Pr1645v2VEthOutQueuesH2PerformanceEntry
   MAX-ACCESS  not-accessible
   STATUS      current
   DESCRIPTION
      ""
   ::= {pr1645v2VEthOutQueues 83886080}

pr1645v2VEthOutQueuesH2PerformanceEntry OBJECT-TYPE
   SYNTAX      Pr1645v2VEthOutQueuesH2PerformanceEntry
   MAX-ACCESS  not-accessible
   STATUS      current
   DESCRIPTION
      ""
   INDEX      { pr1645v2VEthOutQueuesH2PerformanceGlobalIx,
                pr1645v2VEthOutQueuesTableIx,
                pr1645v2VEthOutQueuesH2PerformanceTableIx }
   ::= {pr1645v2VEthOutQueuesH2Performance 1}

Pr1645v2VEthOutQueuesH2PerformanceEntry ::=
   SEQUENCE
      {
      pr1645v2VEthOutQueuesH2PerformanceGlobalIx
         GlobalIndex,
      pr1645v2VEthOutQueuesH2PerformanceTableIx
         TableIndex,
      pr1645v2VEthOutQueuesH2PerformanceSysUpTime
         TimeTicks,
      pr1645v2VEthOutQueuesH2PerformanceTotPkts
         Counter64,
      pr1645v2VEthOutQueuesH2PerformanceDirTxPkts
         Counter64,
      pr1645v2VEthOutQueuesH2PerformanceQdPkts
         Counter64,
      pr1645v2VEthOutQueuesH2PerformanceDropPkts
         Counter64,
      pr1645v2VEthOutQueuesH2PerformanceRDropPkts
         Counter64,
      pr1645v2VEthOutQueuesH2PerformanceCirTxPkts
         Counter64,
      pr1645v2VEthOutQueuesH2PerformanceEirTxPkts
         Counter64,
      pr1645v2VEthOutQueuesH2PerformanceViolTxPkts
         Counter64,
      pr1645v2VEthOutQueuesH2PerformanceTotOcts
         Counter64,
      pr1645v2VEthOutQueuesH2PerformanceDirTxOcts
         Counter64,
      pr1645v2VEthOutQueuesH2PerformanceQdOcts
         Counter64,
      pr1645v2VEthOutQueuesH2PerformanceDropOcts
         Counter64,
      pr1645v2VEthOutQueuesH2PerformanceRDropOcts
         Counter64,
      pr1645v2VEthOutQueuesH2PerformanceCirTxOcts
         Counter64,
      pr1645v2VEthOutQueuesH2PerformanceEirTxOcts
         Counter64,
      pr1645v2VEthOutQueuesH2PerformanceViolTxOcts
         Counter64,
      pr1645v2VEthOutQueuesH2PerformanceBandwidth
         Integer32
      }

pr1645v2VEthOutQueuesH2PerformanceGlobalIx OBJECT-TYPE
   SYNTAX      GlobalIndex
   MAX-ACCESS  not-accessible
   STATUS      current
   DESCRIPTION
      "The value of the tlsCntTreeGlobalIndex of the MANAGED OBJECT."
   ::= {pr1645v2VEthOutQueuesH2PerformanceEntry 10}

pr1645v2VEthOutQueuesH2PerformanceTableIx OBJECT-TYPE
   SYNTAX      TableIndex
   MAX-ACCESS  not-accessible
   STATUS      current
   DESCRIPTION
      ""
   ::= {pr1645v2VEthOutQueuesH2PerformanceEntry 11}

pr1645v2VEthOutQueuesH2PerformanceSysUpTime OBJECT-TYPE
   SYNTAX      TimeTicks
   MAX-ACCESS  read-only
   STATUS      current
   DESCRIPTION
      "Path: virtualEthernet.performance.ifOutPriorityQueues.h2Performance.sysUpTime

       Time in centi-second."
   ::= {pr1645v2VEthOutQueuesH2PerformanceEntry 16777216}

pr1645v2VEthOutQueuesH2PerformanceTotPkts OBJECT-TYPE
   SYNTAX      Counter64
   MAX-ACCESS  read-only
   STATUS      current
   DESCRIPTION
      "Path: virtualEthernet.performance.ifOutPriorityQueues.h2Performance.totalPkts

       64 bit unsigned wrappable counter."
   ::= {pr1645v2VEthOutQueuesH2PerformanceEntry 234881024}

pr1645v2VEthOutQueuesH2PerformanceDirTxPkts OBJECT-TYPE
   SYNTAX      Counter64
   MAX-ACCESS  read-only
   STATUS      current
   DESCRIPTION
      "Path: virtualEthernet.performance.ifOutPriorityQueues.h2Performance.directTxPkts

       64 bit unsigned wrappable counter."
   ::= {pr1645v2VEthOutQueuesH2PerformanceEntry 33554432}

pr1645v2VEthOutQueuesH2PerformanceQdPkts OBJECT-TYPE
   SYNTAX      Counter64
   MAX-ACCESS  read-only
   STATUS      current
   DESCRIPTION
      "Path: virtualEthernet.performance.ifOutPriorityQueues.h2Performance.queuedPkts

       64 bit unsigned wrappable counter."
   ::= {pr1645v2VEthOutQueuesH2PerformanceEntry 50331648}

pr1645v2VEthOutQueuesH2PerformanceDropPkts OBJECT-TYPE
   SYNTAX      Counter64
   MAX-ACCESS  read-only
   STATUS      current
   DESCRIPTION
      "Path: virtualEthernet.performance.ifOutPriorityQueues.h2Performance.droppedPkts

       64 bit unsigned wrappable counter."
   ::= {pr1645v2VEthOutQueuesH2PerformanceEntry 67108864}

pr1645v2VEthOutQueuesH2PerformanceRDropPkts OBJECT-TYPE
   SYNTAX      Counter64
   MAX-ACCESS  read-only
   STATUS      current
   DESCRIPTION
      "Path: virtualEthernet.performance.ifOutPriorityQueues.h2Performance.redDroppedPkts

       64 bit unsigned wrappable counter."
   ::= {pr1645v2VEthOutQueuesH2PerformanceEntry 201326592}

pr1645v2VEthOutQueuesH2PerformanceCirTxPkts OBJECT-TYPE
   SYNTAX      Counter64
   MAX-ACCESS  read-only
   STATUS      current
   DESCRIPTION
      "Path: virtualEthernet.performance.ifOutPriorityQueues.h2Performance.cirTxPkts

       64 bit unsigned wrappable counter."
   ::= {pr1645v2VEthOutQueuesH2PerformanceEntry 83886080}

pr1645v2VEthOutQueuesH2PerformanceEirTxPkts OBJECT-TYPE
   SYNTAX      Counter64
   MAX-ACCESS  read-only
   STATUS      current
   DESCRIPTION
      "Path: virtualEthernet.performance.ifOutPriorityQueues.h2Performance.eirTxPkts

       64 bit unsigned wrappable counter."
   ::= {pr1645v2VEthOutQueuesH2PerformanceEntry 100663296}

pr1645v2VEthOutQueuesH2PerformanceViolTxPkts OBJECT-TYPE
   SYNTAX      Counter64
   MAX-ACCESS  read-only
   STATUS      current
   DESCRIPTION
      "Path: virtualEthernet.performance.ifOutPriorityQueues.h2Performance.violateTxPkts

       64 bit unsigned wrappable counter."
   ::= {pr1645v2VEthOutQueuesH2PerformanceEntry 301989888}

pr1645v2VEthOutQueuesH2PerformanceTotOcts OBJECT-TYPE
   SYNTAX      Counter64
   MAX-ACCESS  read-only
   STATUS      current
   DESCRIPTION
      "Path: virtualEthernet.performance.ifOutPriorityQueues.h2Performance.totalOctets

       64 bit unsigned wrappable counter."
   ::= {pr1645v2VEthOutQueuesH2PerformanceEntry 251658240}

pr1645v2VEthOutQueuesH2PerformanceDirTxOcts OBJECT-TYPE
   SYNTAX      Counter64
   MAX-ACCESS  read-only
   STATUS      current
   DESCRIPTION
      "Path: virtualEthernet.performance.ifOutPriorityQueues.h2Performance.directTxOctets

       64 bit unsigned wrappable counter."
   ::= {pr1645v2VEthOutQueuesH2PerformanceEntry 117440512}

pr1645v2VEthOutQueuesH2PerformanceQdOcts OBJECT-TYPE
   SYNTAX      Counter64
   MAX-ACCESS  read-only
   STATUS      current
   DESCRIPTION
      "Path: virtualEthernet.performance.ifOutPriorityQueues.h2Performance.queuedOctets

       64 bit unsigned wrappable counter."
   ::= {pr1645v2VEthOutQueuesH2PerformanceEntry 134217728}

pr1645v2VEthOutQueuesH2PerformanceDropOcts OBJECT-TYPE
   SYNTAX      Counter64
   MAX-ACCESS  read-only
   STATUS      current
   DESCRIPTION
      "Path: virtualEthernet.performance.ifOutPriorityQueues.h2Performance.droppedOctets

       64 bit unsigned wrappable counter."
   ::= {pr1645v2VEthOutQueuesH2PerformanceEntry 150994944}

pr1645v2VEthOutQueuesH2PerformanceRDropOcts OBJECT-TYPE
   SYNTAX      Counter64
   MAX-ACCESS  read-only
   STATUS      current
   DESCRIPTION
      "Path: virtualEthernet.performance.ifOutPriorityQueues.h2Performance.redDroppedOctets

       64 bit unsigned wrappable counter."
   ::= {pr1645v2VEthOutQueuesH2PerformanceEntry 218103808}

pr1645v2VEthOutQueuesH2PerformanceCirTxOcts OBJECT-TYPE
   SYNTAX      Counter64
   MAX-ACCESS  read-only
   STATUS      current
   DESCRIPTION
      "Path: virtualEthernet.performance.ifOutPriorityQueues.h2Performance.cirTxOctets

       64 bit unsigned wrappable counter."
   ::= {pr1645v2VEthOutQueuesH2PerformanceEntry 167772160}

pr1645v2VEthOutQueuesH2PerformanceEirTxOcts OBJECT-TYPE
   SYNTAX      Counter64
   MAX-ACCESS  read-only
   STATUS      current
   DESCRIPTION
      "Path: virtualEthernet.performance.ifOutPriorityQueues.h2Performance.eirTxOctets

       64 bit unsigned wrappable counter."
   ::= {pr1645v2VEthOutQueuesH2PerformanceEntry 184549376}

pr1645v2VEthOutQueuesH2PerformanceViolTxOcts OBJECT-TYPE
   SYNTAX      Counter64
   MAX-ACCESS  read-only
   STATUS      current
   DESCRIPTION
      "Path: virtualEthernet.performance.ifOutPriorityQueues.h2Performance.violateTxOctets

       64 bit unsigned wrappable counter."
   ::= {pr1645v2VEthOutQueuesH2PerformanceEntry 318767104}

pr1645v2VEthOutQueuesH2PerformanceBandwidth OBJECT-TYPE
   SYNTAX      Integer32
   MAX-ACCESS  read-only
   STATUS      current
   DESCRIPTION
      "Path: virtualEthernet.performance.ifOutPriorityQueues.h2Performance.bandwidth

       unit name = bps
       formula = 8 * ; 8 /"
   ::= {pr1645v2VEthOutQueuesH2PerformanceEntry 268435456}

pr1645v2VEthOutQueuesH24Performance OBJECT-TYPE
   SYNTAX      SEQUENCE OF Pr1645v2VEthOutQueuesH24PerformanceEntry
   MAX-ACCESS  not-accessible
   STATUS      current
   DESCRIPTION
      ""
   ::= {pr1645v2VEthOutQueues 100663296}

pr1645v2VEthOutQueuesH24PerformanceEntry OBJECT-TYPE
   SYNTAX      Pr1645v2VEthOutQueuesH24PerformanceEntry
   MAX-ACCESS  not-accessible
   STATUS      current
   DESCRIPTION
      ""
   INDEX      { pr1645v2VEthOutQueuesH24PerformanceGlobalIx,
                pr1645v2VEthOutQueuesTableIx,
                pr1645v2VEthOutQueuesH24PerformanceTableIx }
   ::= {pr1645v2VEthOutQueuesH24Performance 1}

Pr1645v2VEthOutQueuesH24PerformanceEntry ::=
   SEQUENCE
      {
      pr1645v2VEthOutQueuesH24PerformanceGlobalIx
         GlobalIndex,
      pr1645v2VEthOutQueuesH24PerformanceTableIx
         TableIndex,
      pr1645v2VEthOutQueuesH24PerformanceSysUpTime
         TimeTicks,
      pr1645v2VEthOutQueuesH24PerformanceTotPkts
         Counter64,
      pr1645v2VEthOutQueuesH24PerformanceDirTxPkts
         Counter64,
      pr1645v2VEthOutQueuesH24PerformanceQdPkts
         Counter64,
      pr1645v2VEthOutQueuesH24PerformanceDropPkts
         Counter64,
      pr1645v2VEthOutQueuesH24PerformanceRDropPkts
         Counter64,
      pr1645v2VEthOutQueuesH24PerformanceCirTxPkts
         Counter64,
      pr1645v2VEthOutQueuesH24PerformanceEirTxPkts
         Counter64,
      pr1645v2VEthOutQueuesH24PerformanceViolTxPkts
         Counter64,
      pr1645v2VEthOutQueuesH24PerformanceTotOcts
         Counter64,
      pr1645v2VEthOutQueuesH24PerformanceDirTxOcts
         Counter64,
      pr1645v2VEthOutQueuesH24PerformanceQdOcts
         Counter64,
      pr1645v2VEthOutQueuesH24PerformanceDropOcts
         Counter64,
      pr1645v2VEthOutQueuesH24PerformanceRDropOcts
         Counter64,
      pr1645v2VEthOutQueuesH24PerformanceCirTxOcts
         Counter64,
      pr1645v2VEthOutQueuesH24PerformanceEirTxOcts
         Counter64,
      pr1645v2VEthOutQueuesH24PerformanceViolTxOcts
         Counter64,
      pr1645v2VEthOutQueuesH24PerformanceBandwidth
         Integer32
      }

pr1645v2VEthOutQueuesH24PerformanceGlobalIx OBJECT-TYPE
   SYNTAX      GlobalIndex
   MAX-ACCESS  not-accessible
   STATUS      current
   DESCRIPTION
      "The value of the tlsCntTreeGlobalIndex of the MANAGED OBJECT."
   ::= {pr1645v2VEthOutQueuesH24PerformanceEntry 10}

pr1645v2VEthOutQueuesH24PerformanceTableIx OBJECT-TYPE
   SYNTAX      TableIndex
   MAX-ACCESS  not-accessible
   STATUS      current
   DESCRIPTION
      ""
   ::= {pr1645v2VEthOutQueuesH24PerformanceEntry 11}

pr1645v2VEthOutQueuesH24PerformanceSysUpTime OBJECT-TYPE
   SYNTAX      TimeTicks
   MAX-ACCESS  read-only
   STATUS      current
   DESCRIPTION
      "Path: virtualEthernet.performance.ifOutPriorityQueues.h24Performance.sysUpTime

       Time in centi-second."
   ::= {pr1645v2VEthOutQueuesH24PerformanceEntry 16777216}

pr1645v2VEthOutQueuesH24PerformanceTotPkts OBJECT-TYPE
   SYNTAX      Counter64
   MAX-ACCESS  read-only
   STATUS      current
   DESCRIPTION
      "Path: virtualEthernet.performance.ifOutPriorityQueues.h24Performance.totalPkts

       64 bit unsigned wrappable counter."
   ::= {pr1645v2VEthOutQueuesH24PerformanceEntry 234881024}

pr1645v2VEthOutQueuesH24PerformanceDirTxPkts OBJECT-TYPE
   SYNTAX      Counter64
   MAX-ACCESS  read-only
   STATUS      current
   DESCRIPTION
      "Path: virtualEthernet.performance.ifOutPriorityQueues.h24Performance.directTxPkts

       64 bit unsigned wrappable counter."
   ::= {pr1645v2VEthOutQueuesH24PerformanceEntry 33554432}

pr1645v2VEthOutQueuesH24PerformanceQdPkts OBJECT-TYPE
   SYNTAX      Counter64
   MAX-ACCESS  read-only
   STATUS      current
   DESCRIPTION
      "Path: virtualEthernet.performance.ifOutPriorityQueues.h24Performance.queuedPkts

       64 bit unsigned wrappable counter."
   ::= {pr1645v2VEthOutQueuesH24PerformanceEntry 50331648}

pr1645v2VEthOutQueuesH24PerformanceDropPkts OBJECT-TYPE
   SYNTAX      Counter64
   MAX-ACCESS  read-only
   STATUS      current
   DESCRIPTION
      "Path: virtualEthernet.performance.ifOutPriorityQueues.h24Performance.droppedPkts

       64 bit unsigned wrappable counter."
   ::= {pr1645v2VEthOutQueuesH24PerformanceEntry 67108864}

pr1645v2VEthOutQueuesH24PerformanceRDropPkts OBJECT-TYPE
   SYNTAX      Counter64
   MAX-ACCESS  read-only
   STATUS      current
   DESCRIPTION
      "Path: virtualEthernet.performance.ifOutPriorityQueues.h24Performance.redDroppedPkts

       64 bit unsigned wrappable counter."
   ::= {pr1645v2VEthOutQueuesH24PerformanceEntry 201326592}

pr1645v2VEthOutQueuesH24PerformanceCirTxPkts OBJECT-TYPE
   SYNTAX      Counter64
   MAX-ACCESS  read-only
   STATUS      current
   DESCRIPTION
      "Path: virtualEthernet.performance.ifOutPriorityQueues.h24Performance.cirTxPkts

       64 bit unsigned wrappable counter."
   ::= {pr1645v2VEthOutQueuesH24PerformanceEntry 83886080}

pr1645v2VEthOutQueuesH24PerformanceEirTxPkts OBJECT-TYPE
   SYNTAX      Counter64
   MAX-ACCESS  read-only
   STATUS      current
   DESCRIPTION
      "Path: virtualEthernet.performance.ifOutPriorityQueues.h24Performance.eirTxPkts

       64 bit unsigned wrappable counter."
   ::= {pr1645v2VEthOutQueuesH24PerformanceEntry 100663296}

pr1645v2VEthOutQueuesH24PerformanceViolTxPkts OBJECT-TYPE
   SYNTAX      Counter64
   MAX-ACCESS  read-only
   STATUS      current
   DESCRIPTION
      "Path: virtualEthernet.performance.ifOutPriorityQueues.h24Performance.violateTxPkts

       64 bit unsigned wrappable counter."
   ::= {pr1645v2VEthOutQueuesH24PerformanceEntry 301989888}

pr1645v2VEthOutQueuesH24PerformanceTotOcts OBJECT-TYPE
   SYNTAX      Counter64
   MAX-ACCESS  read-only
   STATUS      current
   DESCRIPTION
      "Path: virtualEthernet.performance.ifOutPriorityQueues.h24Performance.totalOctets

       64 bit unsigned wrappable counter."
   ::= {pr1645v2VEthOutQueuesH24PerformanceEntry 251658240}

pr1645v2VEthOutQueuesH24PerformanceDirTxOcts OBJECT-TYPE
   SYNTAX      Counter64
   MAX-ACCESS  read-only
   STATUS      current
   DESCRIPTION
      "Path: virtualEthernet.performance.ifOutPriorityQueues.h24Performance.directTxOctets

       64 bit unsigned wrappable counter."
   ::= {pr1645v2VEthOutQueuesH24PerformanceEntry 117440512}

pr1645v2VEthOutQueuesH24PerformanceQdOcts OBJECT-TYPE
   SYNTAX      Counter64
   MAX-ACCESS  read-only
   STATUS      current
   DESCRIPTION
      "Path: virtualEthernet.performance.ifOutPriorityQueues.h24Performance.queuedOctets

       64 bit unsigned wrappable counter."
   ::= {pr1645v2VEthOutQueuesH24PerformanceEntry 134217728}

pr1645v2VEthOutQueuesH24PerformanceDropOcts OBJECT-TYPE
   SYNTAX      Counter64
   MAX-ACCESS  read-only
   STATUS      current
   DESCRIPTION
      "Path: virtualEthernet.performance.ifOutPriorityQueues.h24Performance.droppedOctets

       64 bit unsigned wrappable counter."
   ::= {pr1645v2VEthOutQueuesH24PerformanceEntry 150994944}

pr1645v2VEthOutQueuesH24PerformanceRDropOcts OBJECT-TYPE
   SYNTAX      Counter64
   MAX-ACCESS  read-only
   STATUS      current
   DESCRIPTION
      "Path: virtualEthernet.performance.ifOutPriorityQueues.h24Performance.redDroppedOctets

       64 bit unsigned wrappable counter."
   ::= {pr1645v2VEthOutQueuesH24PerformanceEntry 218103808}

pr1645v2VEthOutQueuesH24PerformanceCirTxOcts OBJECT-TYPE
   SYNTAX      Counter64
   MAX-ACCESS  read-only
   STATUS      current
   DESCRIPTION
      "Path: virtualEthernet.performance.ifOutPriorityQueues.h24Performance.cirTxOctets

       64 bit unsigned wrappable counter."
   ::= {pr1645v2VEthOutQueuesH24PerformanceEntry 167772160}

pr1645v2VEthOutQueuesH24PerformanceEirTxOcts OBJECT-TYPE
   SYNTAX      Counter64
   MAX-ACCESS  read-only
   STATUS      current
   DESCRIPTION
      "Path: virtualEthernet.performance.ifOutPriorityQueues.h24Performance.eirTxOctets

       64 bit unsigned wrappable counter."
   ::= {pr1645v2VEthOutQueuesH24PerformanceEntry 184549376}

pr1645v2VEthOutQueuesH24PerformanceViolTxOcts OBJECT-TYPE
   SYNTAX      Counter64
   MAX-ACCESS  read-only
   STATUS      current
   DESCRIPTION
      "Path: virtualEthernet.performance.ifOutPriorityQueues.h24Performance.violateTxOctets

       64 bit unsigned wrappable counter."
   ::= {pr1645v2VEthOutQueuesH24PerformanceEntry 318767104}

pr1645v2VEthOutQueuesH24PerformanceBandwidth OBJECT-TYPE
   SYNTAX      Integer32
   MAX-ACCESS  read-only
   STATUS      current
   DESCRIPTION
      "Path: virtualEthernet.performance.ifOutPriorityQueues.h24Performance.bandwidth

       unit name = bps
       formula = 8 * ; 8 /"
   ::= {pr1645v2VEthOutQueuesH24PerformanceEntry 268435456}

pr1645v2VEthOutQueuesD7Performance OBJECT-TYPE
   SYNTAX      SEQUENCE OF Pr1645v2VEthOutQueuesD7PerformanceEntry
   MAX-ACCESS  not-accessible
   STATUS      current
   DESCRIPTION
      ""
   ::= {pr1645v2VEthOutQueues 117440512}

pr1645v2VEthOutQueuesD7PerformanceEntry OBJECT-TYPE
   SYNTAX      Pr1645v2VEthOutQueuesD7PerformanceEntry
   MAX-ACCESS  not-accessible
   STATUS      current
   DESCRIPTION
      ""
   INDEX      { pr1645v2VEthOutQueuesD7PerformanceGlobalIx,
                pr1645v2VEthOutQueuesTableIx,
                pr1645v2VEthOutQueuesD7PerformanceTableIx }
   ::= {pr1645v2VEthOutQueuesD7Performance 1}

Pr1645v2VEthOutQueuesD7PerformanceEntry ::=
   SEQUENCE
      {
      pr1645v2VEthOutQueuesD7PerformanceGlobalIx
         GlobalIndex,
      pr1645v2VEthOutQueuesD7PerformanceTableIx
         TableIndex,
      pr1645v2VEthOutQueuesD7PerformanceSysUpTime
         TimeTicks,
      pr1645v2VEthOutQueuesD7PerformanceTotPkts
         Counter64,
      pr1645v2VEthOutQueuesD7PerformanceDirTxPkts
         Counter64,
      pr1645v2VEthOutQueuesD7PerformanceQdPkts
         Counter64,
      pr1645v2VEthOutQueuesD7PerformanceDropPkts
         Counter64,
      pr1645v2VEthOutQueuesD7PerformanceRDropPkts
         Counter64,
      pr1645v2VEthOutQueuesD7PerformanceCirTxPkts
         Counter64,
      pr1645v2VEthOutQueuesD7PerformanceEirTxPkts
         Counter64,
      pr1645v2VEthOutQueuesD7PerformanceViolTxPkts
         Counter64,
      pr1645v2VEthOutQueuesD7PerformanceTotOcts
         Counter64,
      pr1645v2VEthOutQueuesD7PerformanceDirTxOcts
         Counter64,
      pr1645v2VEthOutQueuesD7PerformanceQdOcts
         Counter64,
      pr1645v2VEthOutQueuesD7PerformanceDropOcts
         Counter64,
      pr1645v2VEthOutQueuesD7PerformanceRDropOcts
         Counter64,
      pr1645v2VEthOutQueuesD7PerformanceCirTxOcts
         Counter64,
      pr1645v2VEthOutQueuesD7PerformanceEirTxOcts
         Counter64,
      pr1645v2VEthOutQueuesD7PerformanceViolTxOcts
         Counter64,
      pr1645v2VEthOutQueuesD7PerformanceBandwidth
         Integer32
      }

pr1645v2VEthOutQueuesD7PerformanceGlobalIx OBJECT-TYPE
   SYNTAX      GlobalIndex
   MAX-ACCESS  not-accessible
   STATUS      current
   DESCRIPTION
      "The value of the tlsCntTreeGlobalIndex of the MANAGED OBJECT."
   ::= {pr1645v2VEthOutQueuesD7PerformanceEntry 10}

pr1645v2VEthOutQueuesD7PerformanceTableIx OBJECT-TYPE
   SYNTAX      TableIndex
   MAX-ACCESS  not-accessible
   STATUS      current
   DESCRIPTION
      ""
   ::= {pr1645v2VEthOutQueuesD7PerformanceEntry 11}

pr1645v2VEthOutQueuesD7PerformanceSysUpTime OBJECT-TYPE
   SYNTAX      TimeTicks
   MAX-ACCESS  read-only
   STATUS      current
   DESCRIPTION
      "Path: virtualEthernet.performance.ifOutPriorityQueues.d7Performance.sysUpTime

       Time in centi-second."
   ::= {pr1645v2VEthOutQueuesD7PerformanceEntry 16777216}

pr1645v2VEthOutQueuesD7PerformanceTotPkts OBJECT-TYPE
   SYNTAX      Counter64
   MAX-ACCESS  read-only
   STATUS      current
   DESCRIPTION
      "Path: virtualEthernet.performance.ifOutPriorityQueues.d7Performance.totalPkts

       64 bit unsigned wrappable counter."
   ::= {pr1645v2VEthOutQueuesD7PerformanceEntry 234881024}

pr1645v2VEthOutQueuesD7PerformanceDirTxPkts OBJECT-TYPE
   SYNTAX      Counter64
   MAX-ACCESS  read-only
   STATUS      current
   DESCRIPTION
      "Path: virtualEthernet.performance.ifOutPriorityQueues.d7Performance.directTxPkts

       64 bit unsigned wrappable counter."
   ::= {pr1645v2VEthOutQueuesD7PerformanceEntry 33554432}

pr1645v2VEthOutQueuesD7PerformanceQdPkts OBJECT-TYPE
   SYNTAX      Counter64
   MAX-ACCESS  read-only
   STATUS      current
   DESCRIPTION
      "Path: virtualEthernet.performance.ifOutPriorityQueues.d7Performance.queuedPkts

       64 bit unsigned wrappable counter."
   ::= {pr1645v2VEthOutQueuesD7PerformanceEntry 50331648}

pr1645v2VEthOutQueuesD7PerformanceDropPkts OBJECT-TYPE
   SYNTAX      Counter64
   MAX-ACCESS  read-only
   STATUS      current
   DESCRIPTION
      "Path: virtualEthernet.performance.ifOutPriorityQueues.d7Performance.droppedPkts

       64 bit unsigned wrappable counter."
   ::= {pr1645v2VEthOutQueuesD7PerformanceEntry 67108864}

pr1645v2VEthOutQueuesD7PerformanceRDropPkts OBJECT-TYPE
   SYNTAX      Counter64
   MAX-ACCESS  read-only
   STATUS      current
   DESCRIPTION
      "Path: virtualEthernet.performance.ifOutPriorityQueues.d7Performance.redDroppedPkts

       64 bit unsigned wrappable counter."
   ::= {pr1645v2VEthOutQueuesD7PerformanceEntry 201326592}

pr1645v2VEthOutQueuesD7PerformanceCirTxPkts OBJECT-TYPE
   SYNTAX      Counter64
   MAX-ACCESS  read-only
   STATUS      current
   DESCRIPTION
      "Path: virtualEthernet.performance.ifOutPriorityQueues.d7Performance.cirTxPkts

       64 bit unsigned wrappable counter."
   ::= {pr1645v2VEthOutQueuesD7PerformanceEntry 83886080}

pr1645v2VEthOutQueuesD7PerformanceEirTxPkts OBJECT-TYPE
   SYNTAX      Counter64
   MAX-ACCESS  read-only
   STATUS      current
   DESCRIPTION
      "Path: virtualEthernet.performance.ifOutPriorityQueues.d7Performance.eirTxPkts

       64 bit unsigned wrappable counter."
   ::= {pr1645v2VEthOutQueuesD7PerformanceEntry 100663296}

pr1645v2VEthOutQueuesD7PerformanceViolTxPkts OBJECT-TYPE
   SYNTAX      Counter64
   MAX-ACCESS  read-only
   STATUS      current
   DESCRIPTION
      "Path: virtualEthernet.performance.ifOutPriorityQueues.d7Performance.violateTxPkts

       64 bit unsigned wrappable counter."
   ::= {pr1645v2VEthOutQueuesD7PerformanceEntry 301989888}

pr1645v2VEthOutQueuesD7PerformanceTotOcts OBJECT-TYPE
   SYNTAX      Counter64
   MAX-ACCESS  read-only
   STATUS      current
   DESCRIPTION
      "Path: virtualEthernet.performance.ifOutPriorityQueues.d7Performance.totalOctets

       64 bit unsigned wrappable counter."
   ::= {pr1645v2VEthOutQueuesD7PerformanceEntry 251658240}

pr1645v2VEthOutQueuesD7PerformanceDirTxOcts OBJECT-TYPE
   SYNTAX      Counter64
   MAX-ACCESS  read-only
   STATUS      current
   DESCRIPTION
      "Path: virtualEthernet.performance.ifOutPriorityQueues.d7Performance.directTxOctets

       64 bit unsigned wrappable counter."
   ::= {pr1645v2VEthOutQueuesD7PerformanceEntry 117440512}

pr1645v2VEthOutQueuesD7PerformanceQdOcts OBJECT-TYPE
   SYNTAX      Counter64
   MAX-ACCESS  read-only
   STATUS      current
   DESCRIPTION
      "Path: virtualEthernet.performance.ifOutPriorityQueues.d7Performance.queuedOctets

       64 bit unsigned wrappable counter."
   ::= {pr1645v2VEthOutQueuesD7PerformanceEntry 134217728}

pr1645v2VEthOutQueuesD7PerformanceDropOcts OBJECT-TYPE
   SYNTAX      Counter64
   MAX-ACCESS  read-only
   STATUS      current
   DESCRIPTION
      "Path: virtualEthernet.performance.ifOutPriorityQueues.d7Performance.droppedOctets

       64 bit unsigned wrappable counter."
   ::= {pr1645v2VEthOutQueuesD7PerformanceEntry 150994944}

pr1645v2VEthOutQueuesD7PerformanceRDropOcts OBJECT-TYPE
   SYNTAX      Counter64
   MAX-ACCESS  read-only
   STATUS      current
   DESCRIPTION
      "Path: virtualEthernet.performance.ifOutPriorityQueues.d7Performance.redDroppedOctets

       64 bit unsigned wrappable counter."
   ::= {pr1645v2VEthOutQueuesD7PerformanceEntry 218103808}

pr1645v2VEthOutQueuesD7PerformanceCirTxOcts OBJECT-TYPE
   SYNTAX      Counter64
   MAX-ACCESS  read-only
   STATUS      current
   DESCRIPTION
      "Path: virtualEthernet.performance.ifOutPriorityQueues.d7Performance.cirTxOctets

       64 bit unsigned wrappable counter."
   ::= {pr1645v2VEthOutQueuesD7PerformanceEntry 167772160}

pr1645v2VEthOutQueuesD7PerformanceEirTxOcts OBJECT-TYPE
   SYNTAX      Counter64
   MAX-ACCESS  read-only
   STATUS      current
   DESCRIPTION
      "Path: virtualEthernet.performance.ifOutPriorityQueues.d7Performance.eirTxOctets

       64 bit unsigned wrappable counter."
   ::= {pr1645v2VEthOutQueuesD7PerformanceEntry 184549376}

pr1645v2VEthOutQueuesD7PerformanceViolTxOcts OBJECT-TYPE
   SYNTAX      Counter64
   MAX-ACCESS  read-only
   STATUS      current
   DESCRIPTION
      "Path: virtualEthernet.performance.ifOutPriorityQueues.d7Performance.violateTxOctets

       64 bit unsigned wrappable counter."
   ::= {pr1645v2VEthOutQueuesD7PerformanceEntry 318767104}

pr1645v2VEthOutQueuesD7PerformanceBandwidth OBJECT-TYPE
   SYNTAX      Integer32
   MAX-ACCESS  read-only
   STATUS      current
   DESCRIPTION
      "Path: virtualEthernet.performance.ifOutPriorityQueues.d7Performance.bandwidth

       unit name = bps
       formula = 8 * ; 8 /"
   ::= {pr1645v2VEthOutQueuesD7PerformanceEntry 268435456}


pr1645v2VEthOutBandwidth OBJECT IDENTIFIER ::= {pr1645v2VEth 182}

pr1645v2VEthOutBandwidthSSCTable OBJECT-TYPE
   SYNTAX      SEQUENCE OF Pr1645v2VEthOutBandwidthEntry
   MAX-ACCESS  not-accessible
   STATUS      current
   DESCRIPTION
      "bandwidth"
   ::= {pr1645v2VEthOutBandwidth 1}

pr1645v2VEthOutBandwidthEntry OBJECT-TYPE
   SYNTAX      Pr1645v2VEthOutBandwidthEntry
   MAX-ACCESS  not-accessible
   STATUS      current
   DESCRIPTION
      ""
   INDEX      { pr1645v2VEthOutBandwidthGlobalIx }
   ::= {pr1645v2VEthOutBandwidthSSCTable 1}

Pr1645v2VEthOutBandwidthEntry ::=
   SEQUENCE
      {
      pr1645v2VEthOutBandwidthGlobalIx
         GlobalIndex,
      pr1645v2VEthOutBandwidth15sec
         Integer32,
      pr1645v2VEthOutBandwidth30sec
         Integer32,
      pr1645v2VEthOutBandwidth1min
         Integer32,
      pr1645v2VEthOutBandwidth2min
         Integer32,
      pr1645v2VEthOutBandwidth5min
         Integer32
      }

pr1645v2VEthOutBandwidthGlobalIx OBJECT-TYPE
   SYNTAX      GlobalIndex
   MAX-ACCESS  not-accessible
   STATUS      current
   DESCRIPTION
      "The value of the tlsCntTreeGlobalIndex of the MANAGED OBJECT."
   ::= {pr1645v2VEthOutBandwidthEntry 10}

pr1645v2VEthOutBandwidth15sec OBJECT-TYPE
   SYNTAX      Integer32
   MAX-ACCESS  read-only
   STATUS      current
   DESCRIPTION
      "Path: virtualEthernet.performance.ifOutBandwidth.15sec

       unit name = bps
       formula = 8 * ; 8 /"
   ::= {pr1645v2VEthOutBandwidthEntry 83886080}

pr1645v2VEthOutBandwidth30sec OBJECT-TYPE
   SYNTAX      Integer32
   MAX-ACCESS  read-only
   STATUS      current
   DESCRIPTION
      "Path: virtualEthernet.performance.ifOutBandwidth.30sec

       unit name = bps
       formula = 8 * ; 8 /"
   ::= {pr1645v2VEthOutBandwidthEntry 167772160}

pr1645v2VEthOutBandwidth1min OBJECT-TYPE
   SYNTAX      Integer32
   MAX-ACCESS  read-only
   STATUS      current
   DESCRIPTION
      "Path: virtualEthernet.performance.ifOutBandwidth.1min

       unit name = bps
       formula = 8 * ; 8 /"
   ::= {pr1645v2VEthOutBandwidthEntry 335544320}

pr1645v2VEthOutBandwidth2min OBJECT-TYPE
   SYNTAX      Integer32
   MAX-ACCESS  read-only
   STATUS      current
   DESCRIPTION
      "Path: virtualEthernet.performance.ifOutBandwidth.2min

       unit name = bps
       formula = 8 * ; 8 /"
   ::= {pr1645v2VEthOutBandwidthEntry 671088640}

pr1645v2VEthOutBandwidth5min OBJECT-TYPE
   SYNTAX      Integer32
   MAX-ACCESS  read-only
   STATUS      current
   DESCRIPTION
      "Path: virtualEthernet.performance.ifOutBandwidth.5min

       unit name = bps
       formula = 8 * ; 8 /"
   ::= {pr1645v2VEthOutBandwidthEntry 1677721600}


pr1645v2VEthInP OBJECT IDENTIFIER ::= {pr1645v2VEth 307}

pr1645v2VEthInPSSCTable OBJECT-TYPE
   SYNTAX      SEQUENCE OF Pr1645v2VEthInPEntry
   MAX-ACCESS  not-accessible
   STATUS      current
   DESCRIPTION
      "h2IfInPerformance"
   ::= {pr1645v2VEthInP 1}

pr1645v2VEthInPEntry OBJECT-TYPE
   SYNTAX      Pr1645v2VEthInPEntry
   MAX-ACCESS  not-accessible
   STATUS      current
   DESCRIPTION
      ""
   INDEX      { pr1645v2VEthInPGlobalIx,
                pr1645v2VEthInPTableIx }
   ::= {pr1645v2VEthInPSSCTable 1}

Pr1645v2VEthInPEntry ::=
   SEQUENCE
      {
      pr1645v2VEthInPGlobalIx
         GlobalIndex,
      pr1645v2VEthInPTableIx
         TableIndex,
      pr1645v2VEthInPSysUpTime
         TimeTicks,
      pr1645v2VEthInPIfUpTime
         TimeTicks,
      pr1645v2VEthInPIfStatChanges
         Counter32,
      pr1645v2VEthInPIfInOctets
         Counter64,
      pr1645v2VEthInPIfInUCPkts
         Counter64,
      pr1645v2VEthInPIfInNUCPkts
         Counter64,
      pr1645v2VEthInPIfInBCPkts
         Counter64,
      pr1645v2VEthInPIfInMCPkts
         Counter64,
      pr1645v2VEthInPIfInDiscards
         Counter64,
      pr1645v2VEthInPIfInErrors
         Counter64,
      pr1645v2VEthInPIfInUnkwn
         Counter64,
      pr1645v2VEthInPInDropEx
         Counter64,
      pr1645v2VEthInPInDropNoMac
         Counter64,
      pr1645v2VEthInPInDropNUCast
         Counter64,
      pr1645v2VEthInPInDropFilter
         Counter64,
      pr1645v2VEthInPIfInBandwidth
         Integer32,
      pr1645v2VEthInPIfOutOctets
         Counter64,
      pr1645v2VEthInPIfOutUCPkts
         Counter64,
      pr1645v2VEthInPIfOutNUCPkts
         Counter64,
      pr1645v2VEthInPIfOutBCPkts
         Counter64,
      pr1645v2VEthInPIfOutMCPkts
         Counter64,
      pr1645v2VEthInPIfOutDiscards
         Counter64,
      pr1645v2VEthInPIfOutErrors
         Counter64,
      pr1645v2VEthInPOutDropEx
         Counter64,
      pr1645v2VEthInPOutDropNoArp
         Counter64,
      pr1645v2VEthInPOutDropFilter
         Counter64,
      pr1645v2VEthInPIfOutBandwidth
         Integer32,
      pr1645v2VEthInPIfErrSec
         Counter32
      }

pr1645v2VEthInPGlobalIx OBJECT-TYPE
   SYNTAX      GlobalIndex
   MAX-ACCESS  not-accessible
   STATUS      current
   DESCRIPTION
      "The value of the tlsCntTreeGlobalIndex of the MANAGED OBJECT."
   ::= {pr1645v2VEthInPEntry 10}

pr1645v2VEthInPTableIx OBJECT-TYPE
   SYNTAX      TableIndex
   MAX-ACCESS  not-accessible
   STATUS      current
   DESCRIPTION
      ""
   ::= {pr1645v2VEthInPEntry 11}

pr1645v2VEthInPSysUpTime OBJECT-TYPE
   SYNTAX      TimeTicks
   MAX-ACCESS  read-only
   STATUS      current
   DESCRIPTION
      "Path: virtualEthernet.performance.h2Performance.sysUpTime

       Time in centi-second."
   ::= {pr1645v2VEthInPEntry 16777216}

pr1645v2VEthInPIfUpTime OBJECT-TYPE
   SYNTAX      TimeTicks
   MAX-ACCESS  read-only
   STATUS      current
   DESCRIPTION
      "Path: virtualEthernet.performance.h2Performance.ifUpTime

       Time in centi-second."
   ::= {pr1645v2VEthInPEntry 33554432}

pr1645v2VEthInPIfStatChanges OBJECT-TYPE
   SYNTAX      Counter32
   MAX-ACCESS  read-only
   STATUS      current
   DESCRIPTION
      "Path: virtualEthernet.performance.h2Performance.ifStatusChanges

       32 bit unsigned wrappable counter."
   ::= {pr1645v2VEthInPEntry 50331648}

pr1645v2VEthInPIfInOctets OBJECT-TYPE
   SYNTAX      Counter64
   MAX-ACCESS  read-only
   STATUS      current
   DESCRIPTION
      "Path: virtualEthernet.performance.h2Performance.ifInOctets

       64 bit unsigned wrappable counter."
   ::= {pr1645v2VEthInPEntry 67108864}

pr1645v2VEthInPIfInUCPkts OBJECT-TYPE
   SYNTAX      Counter64
   MAX-ACCESS  read-only
   STATUS      current
   DESCRIPTION
      "Path: virtualEthernet.performance.h2Performance.ifInUcastPkts

       64 bit unsigned wrappable counter."
   ::= {pr1645v2VEthInPEntry 83886080}

pr1645v2VEthInPIfInNUCPkts OBJECT-TYPE
   SYNTAX      Counter64
   MAX-ACCESS  read-only
   STATUS      current
   DESCRIPTION
      "Path: virtualEthernet.performance.h2Performance.ifInNUcastPkts

       64 bit unsigned wrappable counter."
   ::= {pr1645v2VEthInPEntry 100663296}

pr1645v2VEthInPIfInBCPkts OBJECT-TYPE
   SYNTAX      Counter64
   MAX-ACCESS  read-only
   STATUS      current
   DESCRIPTION
      "Path: virtualEthernet.performance.h2Performance.ifInBcastPkts

       64 bit unsigned wrappable counter."
   ::= {pr1645v2VEthInPEntry 419430400}

pr1645v2VEthInPIfInMCPkts OBJECT-TYPE
   SYNTAX      Counter64
   MAX-ACCESS  read-only
   STATUS      current
   DESCRIPTION
      "Path: virtualEthernet.performance.h2Performance.ifInMcastPkts

       64 bit unsigned wrappable counter."
   ::= {pr1645v2VEthInPEntry 436207616}

pr1645v2VEthInPIfInDiscards OBJECT-TYPE
   SYNTAX      Counter64
   MAX-ACCESS  read-only
   STATUS      current
   DESCRIPTION
      "Path: virtualEthernet.performance.h2Performance.ifInDiscards

       64 bit unsigned wrappable counter."
   ::= {pr1645v2VEthInPEntry 117440512}

pr1645v2VEthInPIfInErrors OBJECT-TYPE
   SYNTAX      Counter64
   MAX-ACCESS  read-only
   STATUS      current
   DESCRIPTION
      "Path: virtualEthernet.performance.h2Performance.ifInErrors

       64 bit unsigned wrappable counter."
   ::= {pr1645v2VEthInPEntry 134217728}

pr1645v2VEthInPIfInUnkwn OBJECT-TYPE
   SYNTAX      Counter64
   MAX-ACCESS  read-only
   STATUS      current
   DESCRIPTION
      "Path: virtualEthernet.performance.h2Performance.ifInUnknownProtos

       64 bit unsigned wrappable counter."
   ::= {pr1645v2VEthInPEntry 150994944}

pr1645v2VEthInPInDropEx OBJECT-TYPE
   SYNTAX      Counter64
   MAX-ACCESS  read-only
   STATUS      current
   DESCRIPTION
      "Path: virtualEthernet.performance.h2Performance.ifInDropLevelExceeded

       64 bit unsigned wrappable counter."
   ::= {pr1645v2VEthInPEntry 335544320}

pr1645v2VEthInPInDropNoMac OBJECT-TYPE
   SYNTAX      Counter64
   MAX-ACCESS  read-only
   STATUS      current
   DESCRIPTION
      "Path: virtualEthernet.performance.h2Performance.fInDiscardsNoMacFit

       64 bit unsigned wrappable counter."
   ::= {pr1645v2VEthInPEntry 301989888}

pr1645v2VEthInPInDropNUCast OBJECT-TYPE
   SYNTAX      Counter64
   MAX-ACCESS  read-only
   STATUS      current
   DESCRIPTION
      "Path: virtualEthernet.performance.h2Performance.fInDiscardsNUCast

       64 bit unsigned wrappable counter."
   ::= {pr1645v2VEthInPEntry 318767104}

pr1645v2VEthInPInDropFilter OBJECT-TYPE
   SYNTAX      Counter64
   MAX-ACCESS  read-only
   STATUS      current
   DESCRIPTION
      "Path: virtualEthernet.performance.h2Performance.fInDiscardsFilter

       64 bit unsigned wrappable counter."
   ::= {pr1645v2VEthInPEntry 385875968}

pr1645v2VEthInPIfInBandwidth OBJECT-TYPE
   SYNTAX      Integer32
   MAX-ACCESS  read-only
   STATUS      current
   DESCRIPTION
      "Path: virtualEthernet.performance.h2Performance.ifInBandwidth

       unit name = bps
       formula = 8 * ; 8 /"
   ::= {pr1645v2VEthInPEntry 268435456}

pr1645v2VEthInPIfOutOctets OBJECT-TYPE
   SYNTAX      Counter64
   MAX-ACCESS  read-only
   STATUS      current
   DESCRIPTION
      "Path: virtualEthernet.performance.h2Performance.ifOutOctets

       64 bit unsigned wrappable counter."
   ::= {pr1645v2VEthInPEntry 167772160}

pr1645v2VEthInPIfOutUCPkts OBJECT-TYPE
   SYNTAX      Counter64
   MAX-ACCESS  read-only
   STATUS      current
   DESCRIPTION
      "Path: virtualEthernet.performance.h2Performance.ifOutUcastPkts

       64 bit unsigned wrappable counter."
   ::= {pr1645v2VEthInPEntry 184549376}

pr1645v2VEthInPIfOutNUCPkts OBJECT-TYPE
   SYNTAX      Counter64
   MAX-ACCESS  read-only
   STATUS      current
   DESCRIPTION
      "Path: virtualEthernet.performance.h2Performance.ifOutNUcastPkts

       64 bit unsigned wrappable counter."
   ::= {pr1645v2VEthInPEntry 201326592}

pr1645v2VEthInPIfOutBCPkts OBJECT-TYPE
   SYNTAX      Counter64
   MAX-ACCESS  read-only
   STATUS      current
   DESCRIPTION
      "Path: virtualEthernet.performance.h2Performance.ifOutBcastPkts

       64 bit unsigned wrappable counter."
   ::= {pr1645v2VEthInPEntry 452984832}

pr1645v2VEthInPIfOutMCPkts OBJECT-TYPE
   SYNTAX      Counter64
   MAX-ACCESS  read-only
   STATUS      current
   DESCRIPTION
      "Path: virtualEthernet.performance.h2Performance.ifOutMcastPkts

       64 bit unsigned wrappable counter."
   ::= {pr1645v2VEthInPEntry 469762048}

pr1645v2VEthInPIfOutDiscards OBJECT-TYPE
   SYNTAX      Counter64
   MAX-ACCESS  read-only
   STATUS      current
   DESCRIPTION
      "Path: virtualEthernet.performance.h2Performance.ifOutDiscards

       64 bit unsigned wrappable counter."
   ::= {pr1645v2VEthInPEntry 218103808}

pr1645v2VEthInPIfOutErrors OBJECT-TYPE
   SYNTAX      Counter64
   MAX-ACCESS  read-only
   STATUS      current
   DESCRIPTION
      "Path: virtualEthernet.performance.h2Performance.ifOutErrors

       64 bit unsigned wrappable counter."
   ::= {pr1645v2VEthInPEntry 234881024}

pr1645v2VEthInPOutDropEx OBJECT-TYPE
   SYNTAX      Counter64
   MAX-ACCESS  read-only
   STATUS      current
   DESCRIPTION
      "Path: virtualEthernet.performance.h2Performance.ifOutDropLevelExceeded

       64 bit unsigned wrappable counter."
   ::= {pr1645v2VEthInPEntry 352321536}

pr1645v2VEthInPOutDropNoArp OBJECT-TYPE
   SYNTAX      Counter64
   MAX-ACCESS  read-only
   STATUS      current
   DESCRIPTION
      "Path: virtualEthernet.performance.h2Performance.ifOutDiscardsNoArp

       64 bit unsigned wrappable counter."
   ::= {pr1645v2VEthInPEntry 369098752}

pr1645v2VEthInPOutDropFilter OBJECT-TYPE
   SYNTAX      Counter64
   MAX-ACCESS  read-only
   STATUS      current
   DESCRIPTION
      "Path: virtualEthernet.performance.h2Performance.ifOutDiscardsFilter

       64 bit unsigned wrappable counter."
   ::= {pr1645v2VEthInPEntry 402653184}

pr1645v2VEthInPIfOutBandwidth OBJECT-TYPE
   SYNTAX      Integer32
   MAX-ACCESS  read-only
   STATUS      current
   DESCRIPTION
      "Path: virtualEthernet.performance.h2Performance.ifOutBandwidth

       unit name = bps
       formula = 8 * ; 8 /"
   ::= {pr1645v2VEthInPEntry 285212672}

pr1645v2VEthInPIfErrSec OBJECT-TYPE
   SYNTAX      Counter32
   MAX-ACCESS  read-only
   STATUS      current
   DESCRIPTION
      "Path: virtualEthernet.performance.h2Performance.ifErrSec

       32 bit unsigned wrappable counter."
   ::= {pr1645v2VEthInPEntry 251658240}


pr1645v2VEthH24InP OBJECT IDENTIFIER ::= {pr1645v2VEth 308}

pr1645v2VEthH24InPSSCTable OBJECT-TYPE
   SYNTAX      SEQUENCE OF Pr1645v2VEthH24InPEntry
   MAX-ACCESS  not-accessible
   STATUS      current
   DESCRIPTION
      "h24IfInPerformance"
   ::= {pr1645v2VEthH24InP 1}

pr1645v2VEthH24InPEntry OBJECT-TYPE
   SYNTAX      Pr1645v2VEthH24InPEntry
   MAX-ACCESS  not-accessible
   STATUS      current
   DESCRIPTION
      ""
   INDEX      { pr1645v2VEthH24InPGlobalIx,
                pr1645v2VEthH24InPTableIx }
   ::= {pr1645v2VEthH24InPSSCTable 1}

Pr1645v2VEthH24InPEntry ::=
   SEQUENCE
      {
      pr1645v2VEthH24InPGlobalIx
         GlobalIndex,
      pr1645v2VEthH24InPTableIx
         TableIndex,
      pr1645v2VEthH24InPSysUpTime
         TimeTicks,
      pr1645v2VEthH24InPIfUpTime
         TimeTicks,
      pr1645v2VEthH24InPIfStatChanges
         Counter32,
      pr1645v2VEthH24InPIfInOctets
         Counter64,
      pr1645v2VEthH24InPIfInUCPkts
         Counter64,
      pr1645v2VEthH24InPIfInNUCPkts
         Counter64,
      pr1645v2VEthH24InPIfInBCPkts
         Counter64,
      pr1645v2VEthH24InPIfInMCPkts
         Counter64,
      pr1645v2VEthH24InPIfInDiscards
         Counter64,
      pr1645v2VEthH24InPIfInErrors
         Counter64,
      pr1645v2VEthH24InPIfInUnkwn
         Counter64,
      pr1645v2VEthH24InPInDropEx
         Counter64,
      pr1645v2VEthH24InPInDropNoMac
         Counter64,
      pr1645v2VEthH24InPInDropNUCast
         Counter64,
      pr1645v2VEthH24InPInDropFilter
         Counter64,
      pr1645v2VEthH24InPIfInBandwidth
         Integer32,
      pr1645v2VEthH24InPIfOutOctets
         Counter64,
      pr1645v2VEthH24InPIfOutUCPkts
         Counter64,
      pr1645v2VEthH24InPIfOutNUCPkts
         Counter64,
      pr1645v2VEthH24InPIfOutBCPkts
         Counter64,
      pr1645v2VEthH24InPIfOutMCPkts
         Counter64,
      pr1645v2VEthH24InPIfOutDiscards
         Counter64,
      pr1645v2VEthH24InPIfOutErrors
         Counter64,
      pr1645v2VEthH24InPOutDropEx
         Counter64,
      pr1645v2VEthH24InPOutDropNoArp
         Counter64,
      pr1645v2VEthH24InPOutDropFilter
         Counter64,
      pr1645v2VEthH24InPIfOutBandwidth
         Integer32,
      pr1645v2VEthH24InPIfErrSec
         Counter32
      }

pr1645v2VEthH24InPGlobalIx OBJECT-TYPE
   SYNTAX      GlobalIndex
   MAX-ACCESS  not-accessible
   STATUS      current
   DESCRIPTION
      "The value of the tlsCntTreeGlobalIndex of the MANAGED OBJECT."
   ::= {pr1645v2VEthH24InPEntry 10}

pr1645v2VEthH24InPTableIx OBJECT-TYPE
   SYNTAX      TableIndex
   MAX-ACCESS  not-accessible
   STATUS      current
   DESCRIPTION
      ""
   ::= {pr1645v2VEthH24InPEntry 11}

pr1645v2VEthH24InPSysUpTime OBJECT-TYPE
   SYNTAX      TimeTicks
   MAX-ACCESS  read-only
   STATUS      current
   DESCRIPTION
      "Path: virtualEthernet.performance.h24Performance.sysUpTime

       Time in centi-second."
   ::= {pr1645v2VEthH24InPEntry 16777216}

pr1645v2VEthH24InPIfUpTime OBJECT-TYPE
   SYNTAX      TimeTicks
   MAX-ACCESS  read-only
   STATUS      current
   DESCRIPTION
      "Path: virtualEthernet.performance.h24Performance.ifUpTime

       Time in centi-second."
   ::= {pr1645v2VEthH24InPEntry 33554432}

pr1645v2VEthH24InPIfStatChanges OBJECT-TYPE
   SYNTAX      Counter32
   MAX-ACCESS  read-only
   STATUS      current
   DESCRIPTION
      "Path: virtualEthernet.performance.h24Performance.ifStatusChanges

       32 bit unsigned wrappable counter."
   ::= {pr1645v2VEthH24InPEntry 50331648}

pr1645v2VEthH24InPIfInOctets OBJECT-TYPE
   SYNTAX      Counter64
   MAX-ACCESS  read-only
   STATUS      current
   DESCRIPTION
      "Path: virtualEthernet.performance.h24Performance.ifInOctets

       64 bit unsigned wrappable counter."
   ::= {pr1645v2VEthH24InPEntry 67108864}

pr1645v2VEthH24InPIfInUCPkts OBJECT-TYPE
   SYNTAX      Counter64
   MAX-ACCESS  read-only
   STATUS      current
   DESCRIPTION
      "Path: virtualEthernet.performance.h24Performance.ifInUcastPkts

       64 bit unsigned wrappable counter."
   ::= {pr1645v2VEthH24InPEntry 83886080}

pr1645v2VEthH24InPIfInNUCPkts OBJECT-TYPE
   SYNTAX      Counter64
   MAX-ACCESS  read-only
   STATUS      current
   DESCRIPTION
      "Path: virtualEthernet.performance.h24Performance.ifInNUcastPkts

       64 bit unsigned wrappable counter."
   ::= {pr1645v2VEthH24InPEntry 100663296}

pr1645v2VEthH24InPIfInBCPkts OBJECT-TYPE
   SYNTAX      Counter64
   MAX-ACCESS  read-only
   STATUS      current
   DESCRIPTION
      "Path: virtualEthernet.performance.h24Performance.ifInBcastPkts

       64 bit unsigned wrappable counter."
   ::= {pr1645v2VEthH24InPEntry 419430400}

pr1645v2VEthH24InPIfInMCPkts OBJECT-TYPE
   SYNTAX      Counter64
   MAX-ACCESS  read-only
   STATUS      current
   DESCRIPTION
      "Path: virtualEthernet.performance.h24Performance.ifInMcastPkts

       64 bit unsigned wrappable counter."
   ::= {pr1645v2VEthH24InPEntry 436207616}

pr1645v2VEthH24InPIfInDiscards OBJECT-TYPE
   SYNTAX      Counter64
   MAX-ACCESS  read-only
   STATUS      current
   DESCRIPTION
      "Path: virtualEthernet.performance.h24Performance.ifInDiscards

       64 bit unsigned wrappable counter."
   ::= {pr1645v2VEthH24InPEntry 117440512}

pr1645v2VEthH24InPIfInErrors OBJECT-TYPE
   SYNTAX      Counter64
   MAX-ACCESS  read-only
   STATUS      current
   DESCRIPTION
      "Path: virtualEthernet.performance.h24Performance.ifInErrors

       64 bit unsigned wrappable counter."
   ::= {pr1645v2VEthH24InPEntry 134217728}

pr1645v2VEthH24InPIfInUnkwn OBJECT-TYPE
   SYNTAX      Counter64
   MAX-ACCESS  read-only
   STATUS      current
   DESCRIPTION
      "Path: virtualEthernet.performance.h24Performance.ifInUnknownProtos

       64 bit unsigned wrappable counter."
   ::= {pr1645v2VEthH24InPEntry 150994944}

pr1645v2VEthH24InPInDropEx OBJECT-TYPE
   SYNTAX      Counter64
   MAX-ACCESS  read-only
   STATUS      current
   DESCRIPTION
      "Path: virtualEthernet.performance.h24Performance.ifInDropLevelExceeded

       64 bit unsigned wrappable counter."
   ::= {pr1645v2VEthH24InPEntry 335544320}

pr1645v2VEthH24InPInDropNoMac OBJECT-TYPE
   SYNTAX      Counter64
   MAX-ACCESS  read-only
   STATUS      current
   DESCRIPTION
      "Path: virtualEthernet.performance.h24Performance.fInDiscardsNoMacFit

       64 bit unsigned wrappable counter."
   ::= {pr1645v2VEthH24InPEntry 301989888}

pr1645v2VEthH24InPInDropNUCast OBJECT-TYPE
   SYNTAX      Counter64
   MAX-ACCESS  read-only
   STATUS      current
   DESCRIPTION
      "Path: virtualEthernet.performance.h24Performance.fInDiscardsNUCast

       64 bit unsigned wrappable counter."
   ::= {pr1645v2VEthH24InPEntry 318767104}

pr1645v2VEthH24InPInDropFilter OBJECT-TYPE
   SYNTAX      Counter64
   MAX-ACCESS  read-only
   STATUS      current
   DESCRIPTION
      "Path: virtualEthernet.performance.h24Performance.fInDiscardsFilter

       64 bit unsigned wrappable counter."
   ::= {pr1645v2VEthH24InPEntry 385875968}

pr1645v2VEthH24InPIfInBandwidth OBJECT-TYPE
   SYNTAX      Integer32
   MAX-ACCESS  read-only
   STATUS      current
   DESCRIPTION
      "Path: virtualEthernet.performance.h24Performance.ifInBandwidth

       unit name = bps
       formula = 8 * ; 8 /"
   ::= {pr1645v2VEthH24InPEntry 268435456}

pr1645v2VEthH24InPIfOutOctets OBJECT-TYPE
   SYNTAX      Counter64
   MAX-ACCESS  read-only
   STATUS      current
   DESCRIPTION
      "Path: virtualEthernet.performance.h24Performance.ifOutOctets

       64 bit unsigned wrappable counter."
   ::= {pr1645v2VEthH24InPEntry 167772160}

pr1645v2VEthH24InPIfOutUCPkts OBJECT-TYPE
   SYNTAX      Counter64
   MAX-ACCESS  read-only
   STATUS      current
   DESCRIPTION
      "Path: virtualEthernet.performance.h24Performance.ifOutUcastPkts

       64 bit unsigned wrappable counter."
   ::= {pr1645v2VEthH24InPEntry 184549376}

pr1645v2VEthH24InPIfOutNUCPkts OBJECT-TYPE
   SYNTAX      Counter64
   MAX-ACCESS  read-only
   STATUS      current
   DESCRIPTION
      "Path: virtualEthernet.performance.h24Performance.ifOutNUcastPkts

       64 bit unsigned wrappable counter."
   ::= {pr1645v2VEthH24InPEntry 201326592}

pr1645v2VEthH24InPIfOutBCPkts OBJECT-TYPE
   SYNTAX      Counter64
   MAX-ACCESS  read-only
   STATUS      current
   DESCRIPTION
      "Path: virtualEthernet.performance.h24Performance.ifOutBcastPkts

       64 bit unsigned wrappable counter."
   ::= {pr1645v2VEthH24InPEntry 452984832}

pr1645v2VEthH24InPIfOutMCPkts OBJECT-TYPE
   SYNTAX      Counter64
   MAX-ACCESS  read-only
   STATUS      current
   DESCRIPTION
      "Path: virtualEthernet.performance.h24Performance.ifOutMcastPkts

       64 bit unsigned wrappable counter."
   ::= {pr1645v2VEthH24InPEntry 469762048}

pr1645v2VEthH24InPIfOutDiscards OBJECT-TYPE
   SYNTAX      Counter64
   MAX-ACCESS  read-only
   STATUS      current
   DESCRIPTION
      "Path: virtualEthernet.performance.h24Performance.ifOutDiscards

       64 bit unsigned wrappable counter."
   ::= {pr1645v2VEthH24InPEntry 218103808}

pr1645v2VEthH24InPIfOutErrors OBJECT-TYPE
   SYNTAX      Counter64
   MAX-ACCESS  read-only
   STATUS      current
   DESCRIPTION
      "Path: virtualEthernet.performance.h24Performance.ifOutErrors

       64 bit unsigned wrappable counter."
   ::= {pr1645v2VEthH24InPEntry 234881024}

pr1645v2VEthH24InPOutDropEx OBJECT-TYPE
   SYNTAX      Counter64
   MAX-ACCESS  read-only
   STATUS      current
   DESCRIPTION
      "Path: virtualEthernet.performance.h24Performance.ifOutDropLevelExceeded

       64 bit unsigned wrappable counter."
   ::= {pr1645v2VEthH24InPEntry 352321536}

pr1645v2VEthH24InPOutDropNoArp OBJECT-TYPE
   SYNTAX      Counter64
   MAX-ACCESS  read-only
   STATUS      current
   DESCRIPTION
      "Path: virtualEthernet.performance.h24Performance.ifOutDiscardsNoArp

       64 bit unsigned wrappable counter."
   ::= {pr1645v2VEthH24InPEntry 369098752}

pr1645v2VEthH24InPOutDropFilter OBJECT-TYPE
   SYNTAX      Counter64
   MAX-ACCESS  read-only
   STATUS      current
   DESCRIPTION
      "Path: virtualEthernet.performance.h24Performance.ifOutDiscardsFilter

       64 bit unsigned wrappable counter."
   ::= {pr1645v2VEthH24InPEntry 402653184}

pr1645v2VEthH24InPIfOutBandwidth OBJECT-TYPE
   SYNTAX      Integer32
   MAX-ACCESS  read-only
   STATUS      current
   DESCRIPTION
      "Path: virtualEthernet.performance.h24Performance.ifOutBandwidth

       unit name = bps
       formula = 8 * ; 8 /"
   ::= {pr1645v2VEthH24InPEntry 285212672}

pr1645v2VEthH24InPIfErrSec OBJECT-TYPE
   SYNTAX      Counter32
   MAX-ACCESS  read-only
   STATUS      current
   DESCRIPTION
      "Path: virtualEthernet.performance.h24Performance.ifErrSec

       32 bit unsigned wrappable counter."
   ::= {pr1645v2VEthH24InPEntry 251658240}


pr1645v2VEthD7InP OBJECT IDENTIFIER ::= {pr1645v2VEth 309}

pr1645v2VEthD7InPSSCTable OBJECT-TYPE
   SYNTAX      SEQUENCE OF Pr1645v2VEthD7InPEntry
   MAX-ACCESS  not-accessible
   STATUS      current
   DESCRIPTION
      "d7IfInPerformance"
   ::= {pr1645v2VEthD7InP 1}

pr1645v2VEthD7InPEntry OBJECT-TYPE
   SYNTAX      Pr1645v2VEthD7InPEntry
   MAX-ACCESS  not-accessible
   STATUS      current
   DESCRIPTION
      ""
   INDEX      { pr1645v2VEthD7InPGlobalIx,
                pr1645v2VEthD7InPTableIx }
   ::= {pr1645v2VEthD7InPSSCTable 1}

Pr1645v2VEthD7InPEntry ::=
   SEQUENCE
      {
      pr1645v2VEthD7InPGlobalIx
         GlobalIndex,
      pr1645v2VEthD7InPTableIx
         TableIndex,
      pr1645v2VEthD7InPSysUpTime
         TimeTicks,
      pr1645v2VEthD7InPIfUpTime
         TimeTicks,
      pr1645v2VEthD7InPIfStatChanges
         Counter32,
      pr1645v2VEthD7InPIfInOctets
         Counter64,
      pr1645v2VEthD7InPIfInUCPkts
         Counter64,
      pr1645v2VEthD7InPIfInNUCPkts
         Counter64,
      pr1645v2VEthD7InPIfInBCPkts
         Counter64,
      pr1645v2VEthD7InPIfInMCPkts
         Counter64,
      pr1645v2VEthD7InPIfInDiscards
         Counter64,
      pr1645v2VEthD7InPIfInErrors
         Counter64,
      pr1645v2VEthD7InPIfInUnkwn
         Counter64,
      pr1645v2VEthD7InPInDropEx
         Counter64,
      pr1645v2VEthD7InPInDropNoMac
         Counter64,
      pr1645v2VEthD7InPInDropNUCast
         Counter64,
      pr1645v2VEthD7InPInDropFilter
         Counter64,
      pr1645v2VEthD7InPIfInBandwidth
         Integer32,
      pr1645v2VEthD7InPIfOutOctets
         Counter64,
      pr1645v2VEthD7InPIfOutUCPkts
         Counter64,
      pr1645v2VEthD7InPIfOutNUCPkts
         Counter64,
      pr1645v2VEthD7InPIfOutBCPkts
         Counter64,
      pr1645v2VEthD7InPIfOutMCPkts
         Counter64,
      pr1645v2VEthD7InPIfOutDiscards
         Counter64,
      pr1645v2VEthD7InPIfOutErrors
         Counter64,
      pr1645v2VEthD7InPOutDropEx
         Counter64,
      pr1645v2VEthD7InPOutDropNoArp
         Counter64,
      pr1645v2VEthD7InPOutDropFilter
         Counter64,
      pr1645v2VEthD7InPIfOutBandwidth
         Integer32,
      pr1645v2VEthD7InPIfErrSec
         Counter32
      }

pr1645v2VEthD7InPGlobalIx OBJECT-TYPE
   SYNTAX      GlobalIndex
   MAX-ACCESS  not-accessible
   STATUS      current
   DESCRIPTION
      "The value of the tlsCntTreeGlobalIndex of the MANAGED OBJECT."
   ::= {pr1645v2VEthD7InPEntry 10}

pr1645v2VEthD7InPTableIx OBJECT-TYPE
   SYNTAX      TableIndex
   MAX-ACCESS  not-accessible
   STATUS      current
   DESCRIPTION
      ""
   ::= {pr1645v2VEthD7InPEntry 11}

pr1645v2VEthD7InPSysUpTime OBJECT-TYPE
   SYNTAX      TimeTicks
   MAX-ACCESS  read-only
   STATUS      current
   DESCRIPTION
      "Path: virtualEthernet.performance.d7Performance.sysUpTime

       Time in centi-second."
   ::= {pr1645v2VEthD7InPEntry 16777216}

pr1645v2VEthD7InPIfUpTime OBJECT-TYPE
   SYNTAX      TimeTicks
   MAX-ACCESS  read-only
   STATUS      current
   DESCRIPTION
      "Path: virtualEthernet.performance.d7Performance.ifUpTime

       Time in centi-second."
   ::= {pr1645v2VEthD7InPEntry 33554432}

pr1645v2VEthD7InPIfStatChanges OBJECT-TYPE
   SYNTAX      Counter32
   MAX-ACCESS  read-only
   STATUS      current
   DESCRIPTION
      "Path: virtualEthernet.performance.d7Performance.ifStatusChanges

       32 bit unsigned wrappable counter."
   ::= {pr1645v2VEthD7InPEntry 50331648}

pr1645v2VEthD7InPIfInOctets OBJECT-TYPE
   SYNTAX      Counter64
   MAX-ACCESS  read-only
   STATUS      current
   DESCRIPTION
      "Path: virtualEthernet.performance.d7Performance.ifInOctets

       64 bit unsigned wrappable counter."
   ::= {pr1645v2VEthD7InPEntry 67108864}

pr1645v2VEthD7InPIfInUCPkts OBJECT-TYPE
   SYNTAX      Counter64
   MAX-ACCESS  read-only
   STATUS      current
   DESCRIPTION
      "Path: virtualEthernet.performance.d7Performance.ifInUcastPkts

       64 bit unsigned wrappable counter."
   ::= {pr1645v2VEthD7InPEntry 83886080}

pr1645v2VEthD7InPIfInNUCPkts OBJECT-TYPE
   SYNTAX      Counter64
   MAX-ACCESS  read-only
   STATUS      current
   DESCRIPTION
      "Path: virtualEthernet.performance.d7Performance.ifInNUcastPkts

       64 bit unsigned wrappable counter."
   ::= {pr1645v2VEthD7InPEntry 100663296}

pr1645v2VEthD7InPIfInBCPkts OBJECT-TYPE
   SYNTAX      Counter64
   MAX-ACCESS  read-only
   STATUS      current
   DESCRIPTION
      "Path: virtualEthernet.performance.d7Performance.ifInBcastPkts

       64 bit unsigned wrappable counter."
   ::= {pr1645v2VEthD7InPEntry 419430400}

pr1645v2VEthD7InPIfInMCPkts OBJECT-TYPE
   SYNTAX      Counter64
   MAX-ACCESS  read-only
   STATUS      current
   DESCRIPTION
      "Path: virtualEthernet.performance.d7Performance.ifInMcastPkts

       64 bit unsigned wrappable counter."
   ::= {pr1645v2VEthD7InPEntry 436207616}

pr1645v2VEthD7InPIfInDiscards OBJECT-TYPE
   SYNTAX      Counter64
   MAX-ACCESS  read-only
   STATUS      current
   DESCRIPTION
      "Path: virtualEthernet.performance.d7Performance.ifInDiscards

       64 bit unsigned wrappable counter."
   ::= {pr1645v2VEthD7InPEntry 117440512}

pr1645v2VEthD7InPIfInErrors OBJECT-TYPE
   SYNTAX      Counter64
   MAX-ACCESS  read-only
   STATUS      current
   DESCRIPTION
      "Path: virtualEthernet.performance.d7Performance.ifInErrors

       64 bit unsigned wrappable counter."
   ::= {pr1645v2VEthD7InPEntry 134217728}

pr1645v2VEthD7InPIfInUnkwn OBJECT-TYPE
   SYNTAX      Counter64
   MAX-ACCESS  read-only
   STATUS      current
   DESCRIPTION
      "Path: virtualEthernet.performance.d7Performance.ifInUnknownProtos

       64 bit unsigned wrappable counter."
   ::= {pr1645v2VEthD7InPEntry 150994944}

pr1645v2VEthD7InPInDropEx OBJECT-TYPE
   SYNTAX      Counter64
   MAX-ACCESS  read-only
   STATUS      current
   DESCRIPTION
      "Path: virtualEthernet.performance.d7Performance.ifInDropLevelExceeded

       64 bit unsigned wrappable counter."
   ::= {pr1645v2VEthD7InPEntry 335544320}

pr1645v2VEthD7InPInDropNoMac OBJECT-TYPE
   SYNTAX      Counter64
   MAX-ACCESS  read-only
   STATUS      current
   DESCRIPTION
      "Path: virtualEthernet.performance.d7Performance.fInDiscardsNoMacFit

       64 bit unsigned wrappable counter."
   ::= {pr1645v2VEthD7InPEntry 301989888}

pr1645v2VEthD7InPInDropNUCast OBJECT-TYPE
   SYNTAX      Counter64
   MAX-ACCESS  read-only
   STATUS      current
   DESCRIPTION
      "Path: virtualEthernet.performance.d7Performance.fInDiscardsNUCast

       64 bit unsigned wrappable counter."
   ::= {pr1645v2VEthD7InPEntry 318767104}

pr1645v2VEthD7InPInDropFilter OBJECT-TYPE
   SYNTAX      Counter64
   MAX-ACCESS  read-only
   STATUS      current
   DESCRIPTION
      "Path: virtualEthernet.performance.d7Performance.fInDiscardsFilter

       64 bit unsigned wrappable counter."
   ::= {pr1645v2VEthD7InPEntry 385875968}

pr1645v2VEthD7InPIfInBandwidth OBJECT-TYPE
   SYNTAX      Integer32
   MAX-ACCESS  read-only
   STATUS      current
   DESCRIPTION
      "Path: virtualEthernet.performance.d7Performance.ifInBandwidth

       unit name = bps
       formula = 8 * ; 8 /"
   ::= {pr1645v2VEthD7InPEntry 268435456}

pr1645v2VEthD7InPIfOutOctets OBJECT-TYPE
   SYNTAX      Counter64
   MAX-ACCESS  read-only
   STATUS      current
   DESCRIPTION
      "Path: virtualEthernet.performance.d7Performance.ifOutOctets

       64 bit unsigned wrappable counter."
   ::= {pr1645v2VEthD7InPEntry 167772160}

pr1645v2VEthD7InPIfOutUCPkts OBJECT-TYPE
   SYNTAX      Counter64
   MAX-ACCESS  read-only
   STATUS      current
   DESCRIPTION
      "Path: virtualEthernet.performance.d7Performance.ifOutUcastPkts

       64 bit unsigned wrappable counter."
   ::= {pr1645v2VEthD7InPEntry 184549376}

pr1645v2VEthD7InPIfOutNUCPkts OBJECT-TYPE
   SYNTAX      Counter64
   MAX-ACCESS  read-only
   STATUS      current
   DESCRIPTION
      "Path: virtualEthernet.performance.d7Performance.ifOutNUcastPkts

       64 bit unsigned wrappable counter."
   ::= {pr1645v2VEthD7InPEntry 201326592}

pr1645v2VEthD7InPIfOutBCPkts OBJECT-TYPE
   SYNTAX      Counter64
   MAX-ACCESS  read-only
   STATUS      current
   DESCRIPTION
      "Path: virtualEthernet.performance.d7Performance.ifOutBcastPkts

       64 bit unsigned wrappable counter."
   ::= {pr1645v2VEthD7InPEntry 452984832}

pr1645v2VEthD7InPIfOutMCPkts OBJECT-TYPE
   SYNTAX      Counter64
   MAX-ACCESS  read-only
   STATUS      current
   DESCRIPTION
      "Path: virtualEthernet.performance.d7Performance.ifOutMcastPkts

       64 bit unsigned wrappable counter."
   ::= {pr1645v2VEthD7InPEntry 469762048}

pr1645v2VEthD7InPIfOutDiscards OBJECT-TYPE
   SYNTAX      Counter64
   MAX-ACCESS  read-only
   STATUS      current
   DESCRIPTION
      "Path: virtualEthernet.performance.d7Performance.ifOutDiscards

       64 bit unsigned wrappable counter."
   ::= {pr1645v2VEthD7InPEntry 218103808}

pr1645v2VEthD7InPIfOutErrors OBJECT-TYPE
   SYNTAX      Counter64
   MAX-ACCESS  read-only
   STATUS      current
   DESCRIPTION
      "Path: virtualEthernet.performance.d7Performance.ifOutErrors

       64 bit unsigned wrappable counter."
   ::= {pr1645v2VEthD7InPEntry 234881024}

pr1645v2VEthD7InPOutDropEx OBJECT-TYPE
   SYNTAX      Counter64
   MAX-ACCESS  read-only
   STATUS      current
   DESCRIPTION
      "Path: virtualEthernet.performance.d7Performance.ifOutDropLevelExceeded

       64 bit unsigned wrappable counter."
   ::= {pr1645v2VEthD7InPEntry 352321536}

pr1645v2VEthD7InPOutDropNoArp OBJECT-TYPE
   SYNTAX      Counter64
   MAX-ACCESS  read-only
   STATUS      current
   DESCRIPTION
      "Path: virtualEthernet.performance.d7Performance.ifOutDiscardsNoArp

       64 bit unsigned wrappable counter."
   ::= {pr1645v2VEthD7InPEntry 369098752}

pr1645v2VEthD7InPOutDropFilter OBJECT-TYPE
   SYNTAX      Counter64
   MAX-ACCESS  read-only
   STATUS      current
   DESCRIPTION
      "Path: virtualEthernet.performance.d7Performance.ifOutDiscardsFilter

       64 bit unsigned wrappable counter."
   ::= {pr1645v2VEthD7InPEntry 402653184}

pr1645v2VEthD7InPIfOutBandwidth OBJECT-TYPE
   SYNTAX      Integer32
   MAX-ACCESS  read-only
   STATUS      current
   DESCRIPTION
      "Path: virtualEthernet.performance.d7Performance.ifOutBandwidth

       unit name = bps
       formula = 8 * ; 8 /"
   ::= {pr1645v2VEthD7InPEntry 285212672}

pr1645v2VEthD7InPIfErrSec OBJECT-TYPE
   SYNTAX      Counter32
   MAX-ACCESS  read-only
   STATUS      current
   DESCRIPTION
      "Path: virtualEthernet.performance.d7Performance.ifErrSec

       32 bit unsigned wrappable counter."
   ::= {pr1645v2VEthD7InPEntry 251658240}


pr1645v2VEthOam OBJECT IDENTIFIER ::= {pr1645v2VEth 910}

pr1645v2VEthOamSSCTable OBJECT-TYPE
   SYNTAX      SEQUENCE OF Pr1645v2VEthOamEntry
   MAX-ACCESS  not-accessible
   STATUS      current
   DESCRIPTION
      "OAM statistics"
   ::= {pr1645v2VEthOam 1}

pr1645v2VEthOamEntry OBJECT-TYPE
   SYNTAX      Pr1645v2VEthOamEntry
   MAX-ACCESS  not-accessible
   STATUS      current
   DESCRIPTION
      ""
   INDEX      { pr1645v2VEthOamGlobalIx }
   ::= {pr1645v2VEthOamSSCTable 1}

Pr1645v2VEthOamEntry ::=
   SEQUENCE
      {
      pr1645v2VEthOamGlobalIx
         GlobalIndex,
      pr1645v2VEthOamInformationTx
         Counter32,
      pr1645v2VEthOamInformationRx
         Counter32,
      pr1645v2VEthOamUniqueEventNotifTx
         Counter32,
      pr1645v2VEthOamUniqueEventNotifRx
         Counter32,
      pr1645v2VEthOamLoopbackCtrlTx
         Counter32,
      pr1645v2VEthOamLoopbackCtrlRx
         Counter32,
      pr1645v2VEthOamVarReqTx
         Counter32,
      pr1645v2VEthOamVarReqRx
         Counter32,
      pr1645v2VEthOamVarRespTx
         Counter32,
      pr1645v2VEthOamVarRespRx
         Counter32,
      pr1645v2VEthOamOrgSpecificTx
         Counter32,
      pr1645v2VEthOamOrgSpecificRx
         Counter32,
      pr1645v2VEthOamUnsupportedCodesTx
         Counter32,
      pr1645v2VEthOamUnsupportedCodesRx
         Counter32,
      pr1645v2VEthOamPduDiscardRx
         Counter32,
      pr1645v2VEthOamDataDiscardTx
         Counter32,
      pr1645v2VEthOamDataDiscardRx
         Counter32
      }

pr1645v2VEthOamGlobalIx OBJECT-TYPE
   SYNTAX      GlobalIndex
   MAX-ACCESS  not-accessible
   STATUS      current
   DESCRIPTION
      "The value of the tlsCntTreeGlobalIndex of the MANAGED OBJECT."
   ::= {pr1645v2VEthOamEntry 10}

pr1645v2VEthOamInformationTx OBJECT-TYPE
   SYNTAX      Counter32
   MAX-ACCESS  read-only
   STATUS      current
   DESCRIPTION
      "Path: virtualEthernet.performance.oam.informationTx

       32 bit unsigned wrappable counter."
   ::= {pr1645v2VEthOamEntry 16777216}

pr1645v2VEthOamInformationRx OBJECT-TYPE
   SYNTAX      Counter32
   MAX-ACCESS  read-only
   STATUS      current
   DESCRIPTION
      "Path: virtualEthernet.performance.oam.informationRx

       32 bit unsigned wrappable counter."
   ::= {pr1645v2VEthOamEntry 33554432}

pr1645v2VEthOamUniqueEventNotifTx OBJECT-TYPE
   SYNTAX      Counter32
   MAX-ACCESS  read-only
   STATUS      current
   DESCRIPTION
      "Path: virtualEthernet.performance.oam.uniqueEventNotifTx

       32 bit unsigned wrappable counter."
   ::= {pr1645v2VEthOamEntry 50331648}

pr1645v2VEthOamUniqueEventNotifRx OBJECT-TYPE
   SYNTAX      Counter32
   MAX-ACCESS  read-only
   STATUS      current
   DESCRIPTION
      "Path: virtualEthernet.performance.oam.uniqueEventNotifRx

       32 bit unsigned wrappable counter."
   ::= {pr1645v2VEthOamEntry 67108864}

pr1645v2VEthOamLoopbackCtrlTx OBJECT-TYPE
   SYNTAX      Counter32
   MAX-ACCESS  read-only
   STATUS      current
   DESCRIPTION
      "Path: virtualEthernet.performance.oam.loopbackCtrlTx

       32 bit unsigned wrappable counter."
   ::= {pr1645v2VEthOamEntry 117440512}

pr1645v2VEthOamLoopbackCtrlRx OBJECT-TYPE
   SYNTAX      Counter32
   MAX-ACCESS  read-only
   STATUS      current
   DESCRIPTION
      "Path: virtualEthernet.performance.oam.loopbackCtrlRx

       32 bit unsigned wrappable counter."
   ::= {pr1645v2VEthOamEntry 134217728}

pr1645v2VEthOamVarReqTx OBJECT-TYPE
   SYNTAX      Counter32
   MAX-ACCESS  read-only
   STATUS      current
   DESCRIPTION
      "Path: virtualEthernet.performance.oam.varReqTx

       32 bit unsigned wrappable counter."
   ::= {pr1645v2VEthOamEntry 150994944}

pr1645v2VEthOamVarReqRx OBJECT-TYPE
   SYNTAX      Counter32
   MAX-ACCESS  read-only
   STATUS      current
   DESCRIPTION
      "Path: virtualEthernet.performance.oam.varReqRx

       32 bit unsigned wrappable counter."
   ::= {pr1645v2VEthOamEntry 167772160}

pr1645v2VEthOamVarRespTx OBJECT-TYPE
   SYNTAX      Counter32
   MAX-ACCESS  read-only
   STATUS      current
   DESCRIPTION
      "Path: virtualEthernet.performance.oam.varRespTx

       32 bit unsigned wrappable counter."
   ::= {pr1645v2VEthOamEntry 184549376}

pr1645v2VEthOamVarRespRx OBJECT-TYPE
   SYNTAX      Counter32
   MAX-ACCESS  read-only
   STATUS      current
   DESCRIPTION
      "Path: virtualEthernet.performance.oam.varRespRx

       32 bit unsigned wrappable counter."
   ::= {pr1645v2VEthOamEntry 201326592}

pr1645v2VEthOamOrgSpecificTx OBJECT-TYPE
   SYNTAX      Counter32
   MAX-ACCESS  read-only
   STATUS      current
   DESCRIPTION
      "Path: virtualEthernet.performance.oam.orgSpecificTx

       32 bit unsigned wrappable counter."
   ::= {pr1645v2VEthOamEntry 218103808}

pr1645v2VEthOamOrgSpecificRx OBJECT-TYPE
   SYNTAX      Counter32
   MAX-ACCESS  read-only
   STATUS      current
   DESCRIPTION
      "Path: virtualEthernet.performance.oam.orgSpecificRx

       32 bit unsigned wrappable counter."
   ::= {pr1645v2VEthOamEntry 234881024}

pr1645v2VEthOamUnsupportedCodesTx OBJECT-TYPE
   SYNTAX      Counter32
   MAX-ACCESS  read-only
   STATUS      current
   DESCRIPTION
      "Path: virtualEthernet.performance.oam.unsupportedCodesTx

       32 bit unsigned wrappable counter."
   ::= {pr1645v2VEthOamEntry 251658240}

pr1645v2VEthOamUnsupportedCodesRx OBJECT-TYPE
   SYNTAX      Counter32
   MAX-ACCESS  read-only
   STATUS      current
   DESCRIPTION
      "Path: virtualEthernet.performance.oam.unsupportedCodesRx

       32 bit unsigned wrappable counter."
   ::= {pr1645v2VEthOamEntry 268435456}

pr1645v2VEthOamPduDiscardRx OBJECT-TYPE
   SYNTAX      Counter32
   MAX-ACCESS  read-only
   STATUS      current
   DESCRIPTION
      "Path: virtualEthernet.performance.oam.pduDiscardRx

       32 bit unsigned wrappable counter."
   ::= {pr1645v2VEthOamEntry 1694498816}

pr1645v2VEthOamDataDiscardTx OBJECT-TYPE
   SYNTAX      Counter32
   MAX-ACCESS  read-only
   STATUS      current
   DESCRIPTION
      "Path: virtualEthernet.performance.oam.dataDiscardTx

       32 bit unsigned wrappable counter."
   ::= {pr1645v2VEthOamEntry 1711276032}

pr1645v2VEthOamDataDiscardRx OBJECT-TYPE
   SYNTAX      Counter32
   MAX-ACCESS  read-only
   STATUS      current
   DESCRIPTION
      "Path: virtualEthernet.performance.oam.dataDiscardRx

       32 bit unsigned wrappable counter."
   ::= {pr1645v2VEthOamEntry 1728053248}


pr1645v2VEthVlan OBJECT IDENTIFIER ::= {pr1645v2VEth 310}

pr1645v2VEthVlanSSCTable OBJECT-TYPE
   SYNTAX      SEQUENCE OF Pr1645v2VEthVlanEntry
   MAX-ACCESS  not-accessible
   STATUS      current
   DESCRIPTION
      ""
   ::= {pr1645v2VEthVlan 1}

pr1645v2VEthVlanEntry OBJECT-TYPE
   SYNTAX      Pr1645v2VEthVlanEntry
   MAX-ACCESS  not-accessible
   STATUS      current
   DESCRIPTION
      ""
   INDEX      { pr1645v2VEthVlanGlobalIx,
                pr1645v2VEthVlanTableIx }
   ::= {pr1645v2VEthVlanSSCTable 1}

Pr1645v2VEthVlanEntry ::=
   SEQUENCE
      {
      pr1645v2VEthVlanGlobalIx
         GlobalIndex,
      pr1645v2VEthVlanTableIx
         TableIndex,
      pr1645v2VEthVlanName
         DisplayString,
      pr1645v2VEthVlanMCInOctets
         Counter64,
      pr1645v2VEthVlanMCInUcast
         Counter64,
      pr1645v2VEthVlanMCInNUcastPkts
         Counter64,
      pr1645v2VEthVlanMCInBcastPkts
         Counter64,
      pr1645v2VEthVlanMCInMcastPkts
         Counter64,
      pr1645v2VEthVlanMCInDiscards
         Counter64,
      pr1645v2VEthVlanMCInErrors
         Counter64,
      pr1645v2VEthVlanMCInUnknownProtos
         Counter64,
      pr1645v2VEthVlanMCInDropEx
         Counter64,
      pr1645v2VEthVlanMCInDropNoMac
         Counter64,
      pr1645v2VEthVlanMCInDropNUCast
         Counter64,
      pr1645v2VEthVlanMCInDropFilter
         Counter64,
      pr1645v2VEthVlanMCInBandwidth15sec
         Integer32,
      pr1645v2VEthVlanMCInBandwidth30sec
         Integer32,
      pr1645v2VEthVlanMCInBandwidth1min
         Integer32,
      pr1645v2VEthVlanMCInBandwidth2min
         Integer32,
      pr1645v2VEthVlanMCInBandwidth5min
         Integer32,
      pr1645v2VEthVlanMCOutOctets
         Counter64,
      pr1645v2VEthVlanMCOutUcastPkts
         Counter64,
      pr1645v2VEthVlanMCOutNUcastPkts
         Counter64,
      pr1645v2VEthVlanMCOutBcastPkts
         Counter64,
      pr1645v2VEthVlanMCOutMcastPkts
         Counter64,
      pr1645v2VEthVlanMCOutDiscards
         Counter64,
      pr1645v2VEthVlanMCOutErrors
         Counter64,
      pr1645v2VEthVlanMCOutQLen
         Counter32,
      pr1645v2VEthVlanMCOutDropEx
         Counter64,
      pr1645v2VEthVlanMCOutDropNoArp
         Counter64,
      pr1645v2VEthVlanMCOutDropFilter
         Counter64,
      pr1645v2VEthVlanMCOutBandwidth15sec
         Integer32,
      pr1645v2VEthVlanMCOutBandwidth30sec
         Integer32,
      pr1645v2VEthVlanMCOutBandwidth1min
         Integer32,
      pr1645v2VEthVlanMCOutBandwidth2min
         Integer32,
      pr1645v2VEthVlanMCOutBandwidth5min
         Integer32,
      pr1645v2VEthVlanVlanVid
         Integer32,
      pr1645v2VEthVlanPppLinkMonitoringRequestsSent
         Gauge32,
      pr1645v2VEthVlanPppLinkMonitoringRepliesRcvd
         Gauge32,
      pr1645v2VEthVlanPppLinkMonitoringRequestsRcvd
         Gauge32,
      pr1645v2VEthVlanPppLinkMonitoringRepliesSent
         Gauge32
      }

pr1645v2VEthVlanGlobalIx OBJECT-TYPE
   SYNTAX      GlobalIndex
   MAX-ACCESS  not-accessible
   STATUS      current
   DESCRIPTION
      "The value of the tlsCntTreeGlobalIndex of the MANAGED OBJECT."
   ::= {pr1645v2VEthVlanEntry 10}

pr1645v2VEthVlanTableIx OBJECT-TYPE
   SYNTAX      TableIndex
   MAX-ACCESS  not-accessible
   STATUS      current
   DESCRIPTION
      ""
   ::= {pr1645v2VEthVlanEntry 11}

pr1645v2VEthVlanName OBJECT-TYPE
   SYNTAX      DisplayString
   MAX-ACCESS  read-only
   STATUS      current
   DESCRIPTION
      "Path: virtualEthernet.performance.vlan.name"
   ::= {pr1645v2VEthVlanEntry 16777216}

pr1645v2VEthVlanMCInOctets OBJECT-TYPE
   SYNTAX      Counter64
   MAX-ACCESS  read-only
   STATUS      current
   DESCRIPTION
      "Path: virtualEthernet.performance.vlan.mibCounters.ifInOctets

       64 bit unsigned wrappable counter."
   ::= {pr1645v2VEthVlanEntry 40697856}

pr1645v2VEthVlanMCInUcast OBJECT-TYPE
   SYNTAX      Counter64
   MAX-ACCESS  read-only
   STATUS      current
   DESCRIPTION
      "Path: virtualEthernet.performance.vlan.mibCounters.ifInUcastPkts

       64 bit unsigned wrappable counter."
   ::= {pr1645v2VEthVlanEntry 40763392}

pr1645v2VEthVlanMCInNUcastPkts OBJECT-TYPE
   SYNTAX      Counter64
   MAX-ACCESS  read-only
   STATUS      current
   DESCRIPTION
      "Path: virtualEthernet.performance.vlan.mibCounters.ifInNUcastPkts

       64 bit unsigned wrappable counter."
   ::= {pr1645v2VEthVlanEntry 40828928}

pr1645v2VEthVlanMCInBcastPkts OBJECT-TYPE
   SYNTAX      Counter64
   MAX-ACCESS  read-only
   STATUS      current
   DESCRIPTION
      "Path: virtualEthernet.performance.vlan.mibCounters.ifInBcastPkts

       64 bit unsigned wrappable counter."
   ::= {pr1645v2VEthVlanEntry 47382528}

pr1645v2VEthVlanMCInMcastPkts OBJECT-TYPE
   SYNTAX      Counter64
   MAX-ACCESS  read-only
   STATUS      current
   DESCRIPTION
      "Path: virtualEthernet.performance.vlan.mibCounters.ifInMcastPkts

       64 bit unsigned wrappable counter."
   ::= {pr1645v2VEthVlanEntry 48037888}

pr1645v2VEthVlanMCInDiscards OBJECT-TYPE
   SYNTAX      Counter64
   MAX-ACCESS  read-only
   STATUS      current
   DESCRIPTION
      "Path: virtualEthernet.performance.vlan.mibCounters.ifInDiscards

       64 bit unsigned wrappable counter."
   ::= {pr1645v2VEthVlanEntry 40894464}

pr1645v2VEthVlanMCInErrors OBJECT-TYPE
   SYNTAX      Counter64
   MAX-ACCESS  read-only
   STATUS      current
   DESCRIPTION
      "Path: virtualEthernet.performance.vlan.mibCounters.ifInErrors

       64 bit unsigned wrappable counter."
   ::= {pr1645v2VEthVlanEntry 40960000}

pr1645v2VEthVlanMCInUnknownProtos OBJECT-TYPE
   SYNTAX      Counter64
   MAX-ACCESS  read-only
   STATUS      current
   DESCRIPTION
      "Path: virtualEthernet.performance.vlan.mibCounters.ifInUnknownProtos

       64 bit unsigned wrappable counter."
   ::= {pr1645v2VEthVlanEntry 41025536}

pr1645v2VEthVlanMCInDropEx OBJECT-TYPE
   SYNTAX      Counter64
   MAX-ACCESS  read-only
   STATUS      current
   DESCRIPTION
      "Path: virtualEthernet.performance.vlan.mibCounters.ifInDropLevelExceeded

       64 bit unsigned wrappable counter."
   ::= {pr1645v2VEthVlanEntry 42074112}

pr1645v2VEthVlanMCInDropNoMac OBJECT-TYPE
   SYNTAX      Counter64
   MAX-ACCESS  read-only
   STATUS      current
   DESCRIPTION
      "Path: virtualEthernet.performance.vlan.mibCounters.ifInDiscardsNoMacFit

       64 bit unsigned wrappable counter."
   ::= {pr1645v2VEthVlanEntry 42270720}

pr1645v2VEthVlanMCInDropNUCast OBJECT-TYPE
   SYNTAX      Counter64
   MAX-ACCESS  read-only
   STATUS      current
   DESCRIPTION
      "Path: virtualEthernet.performance.vlan.mibCounters.ifInDiscardsNUCast

       64 bit unsigned wrappable counter."
   ::= {pr1645v2VEthVlanEntry 42467328}

pr1645v2VEthVlanMCInDropFilter OBJECT-TYPE
   SYNTAX      Counter64
   MAX-ACCESS  read-only
   STATUS      current
   DESCRIPTION
      "Path: virtualEthernet.performance.vlan.mibCounters.ifInDiscardsFilter

       64 bit unsigned wrappable counter."
   ::= {pr1645v2VEthVlanEntry 42532864}

pr1645v2VEthVlanMCInBandwidth15sec OBJECT-TYPE
   SYNTAX      Integer32
   MAX-ACCESS  read-only
   STATUS      current
   DESCRIPTION
      "Path: virtualEthernet.performance.vlan.mibCounters.ifInBandwidth.15sec

       unit name = bps
       formula = 8 * ; 8 /"
   ::= {pr1645v2VEthVlanEntry 45417728}

pr1645v2VEthVlanMCInBandwidth30sec OBJECT-TYPE
   SYNTAX      Integer32
   MAX-ACCESS  read-only
   STATUS      current
   DESCRIPTION
      "Path: virtualEthernet.performance.vlan.mibCounters.ifInBandwidth.30sec

       unit name = bps
       formula = 8 * ; 8 /"
   ::= {pr1645v2VEthVlanEntry 45419008}

pr1645v2VEthVlanMCInBandwidth1min OBJECT-TYPE
   SYNTAX      Integer32
   MAX-ACCESS  read-only
   STATUS      current
   DESCRIPTION
      "Path: virtualEthernet.performance.vlan.mibCounters.ifInBandwidth.1min

       unit name = bps
       formula = 8 * ; 8 /"
   ::= {pr1645v2VEthVlanEntry 45421568}

pr1645v2VEthVlanMCInBandwidth2min OBJECT-TYPE
   SYNTAX      Integer32
   MAX-ACCESS  read-only
   STATUS      current
   DESCRIPTION
      "Path: virtualEthernet.performance.vlan.mibCounters.ifInBandwidth.2min

       unit name = bps
       formula = 8 * ; 8 /"
   ::= {pr1645v2VEthVlanEntry 45426688}

pr1645v2VEthVlanMCInBandwidth5min OBJECT-TYPE
   SYNTAX      Integer32
   MAX-ACCESS  read-only
   STATUS      current
   DESCRIPTION
      "Path: virtualEthernet.performance.vlan.mibCounters.ifInBandwidth.5min

       unit name = bps
       formula = 8 * ; 8 /"
   ::= {pr1645v2VEthVlanEntry 45442048}

pr1645v2VEthVlanMCOutOctets OBJECT-TYPE
   SYNTAX      Counter64
   MAX-ACCESS  read-only
   STATUS      current
   DESCRIPTION
      "Path: virtualEthernet.performance.vlan.mibCounters.ifOutOctets

       64 bit unsigned wrappable counter."
   ::= {pr1645v2VEthVlanEntry 41091072}

pr1645v2VEthVlanMCOutUcastPkts OBJECT-TYPE
   SYNTAX      Counter64
   MAX-ACCESS  read-only
   STATUS      current
   DESCRIPTION
      "Path: virtualEthernet.performance.vlan.mibCounters.ifOutUcastPkts

       64 bit unsigned wrappable counter."
   ::= {pr1645v2VEthVlanEntry 41156608}

pr1645v2VEthVlanMCOutNUcastPkts OBJECT-TYPE
   SYNTAX      Counter64
   MAX-ACCESS  read-only
   STATUS      current
   DESCRIPTION
      "Path: virtualEthernet.performance.vlan.mibCounters.ifOutNUcastPkts

       64 bit unsigned wrappable counter."
   ::= {pr1645v2VEthVlanEntry 41222144}

pr1645v2VEthVlanMCOutBcastPkts OBJECT-TYPE
   SYNTAX      Counter64
   MAX-ACCESS  read-only
   STATUS      current
   DESCRIPTION
      "Path: virtualEthernet.performance.vlan.mibCounters.ifOutBcastPkts

       64 bit unsigned wrappable counter."
   ::= {pr1645v2VEthVlanEntry 47775744}

pr1645v2VEthVlanMCOutMcastPkts OBJECT-TYPE
   SYNTAX      Counter64
   MAX-ACCESS  read-only
   STATUS      current
   DESCRIPTION
      "Path: virtualEthernet.performance.vlan.mibCounters.ifOutMcastPkts

       64 bit unsigned wrappable counter."
   ::= {pr1645v2VEthVlanEntry 48431104}

pr1645v2VEthVlanMCOutDiscards OBJECT-TYPE
   SYNTAX      Counter64
   MAX-ACCESS  read-only
   STATUS      current
   DESCRIPTION
      "Path: virtualEthernet.performance.vlan.mibCounters.ifOutDiscards

       64 bit unsigned wrappable counter."
   ::= {pr1645v2VEthVlanEntry 41287680}

pr1645v2VEthVlanMCOutErrors OBJECT-TYPE
   SYNTAX      Counter64
   MAX-ACCESS  read-only
   STATUS      current
   DESCRIPTION
      "Path: virtualEthernet.performance.vlan.mibCounters.ifOutErrors

       64 bit unsigned wrappable counter."
   ::= {pr1645v2VEthVlanEntry 41353216}

pr1645v2VEthVlanMCOutQLen OBJECT-TYPE
   SYNTAX      Counter32
   MAX-ACCESS  read-only
   STATUS      current
   DESCRIPTION
      "Path: virtualEthernet.performance.vlan.mibCounters.ifOutQLen

       32 bit unsigned wrappable counter."
   ::= {pr1645v2VEthVlanEntry 41418752}

pr1645v2VEthVlanMCOutDropEx OBJECT-TYPE
   SYNTAX      Counter64
   MAX-ACCESS  read-only
   STATUS      current
   DESCRIPTION
      "Path: virtualEthernet.performance.vlan.mibCounters.ifOutDropLevelExceeded

       64 bit unsigned wrappable counter."
   ::= {pr1645v2VEthVlanEntry 41484288}

pr1645v2VEthVlanMCOutDropNoArp OBJECT-TYPE
   SYNTAX      Counter64
   MAX-ACCESS  read-only
   STATUS      current
   DESCRIPTION
      "Path: virtualEthernet.performance.vlan.mibCounters.ifOutDiscardsNoArp

       64 bit unsigned wrappable counter."
   ::= {pr1645v2VEthVlanEntry 42336256}

pr1645v2VEthVlanMCOutDropFilter OBJECT-TYPE
   SYNTAX      Counter64
   MAX-ACCESS  read-only
   STATUS      current
   DESCRIPTION
      "Path: virtualEthernet.performance.vlan.mibCounters.ifOutDiscardsFilter

       64 bit unsigned wrappable counter."
   ::= {pr1645v2VEthVlanEntry 42598400}

pr1645v2VEthVlanMCOutBandwidth15sec OBJECT-TYPE
   SYNTAX      Integer32
   MAX-ACCESS  read-only
   STATUS      current
   DESCRIPTION
      "Path: virtualEthernet.performance.vlan.mibCounters.ifOutBandwidth.15sec

       unit name = bps
       formula = 8 * ; 8 /"
   ::= {pr1645v2VEthVlanEntry 45483264}

pr1645v2VEthVlanMCOutBandwidth30sec OBJECT-TYPE
   SYNTAX      Integer32
   MAX-ACCESS  read-only
   STATUS      current
   DESCRIPTION
      "Path: virtualEthernet.performance.vlan.mibCounters.ifOutBandwidth.30sec

       unit name = bps
       formula = 8 * ; 8 /"
   ::= {pr1645v2VEthVlanEntry 45484544}

pr1645v2VEthVlanMCOutBandwidth1min OBJECT-TYPE
   SYNTAX      Integer32
   MAX-ACCESS  read-only
   STATUS      current
   DESCRIPTION
      "Path: virtualEthernet.performance.vlan.mibCounters.ifOutBandwidth.1min

       unit name = bps
       formula = 8 * ; 8 /"
   ::= {pr1645v2VEthVlanEntry 45487104}

pr1645v2VEthVlanMCOutBandwidth2min OBJECT-TYPE
   SYNTAX      Integer32
   MAX-ACCESS  read-only
   STATUS      current
   DESCRIPTION
      "Path: virtualEthernet.performance.vlan.mibCounters.ifOutBandwidth.2min

       unit name = bps
       formula = 8 * ; 8 /"
   ::= {pr1645v2VEthVlanEntry 45492224}

pr1645v2VEthVlanMCOutBandwidth5min OBJECT-TYPE
   SYNTAX      Integer32
   MAX-ACCESS  read-only
   STATUS      current
   DESCRIPTION
      "Path: virtualEthernet.performance.vlan.mibCounters.ifOutBandwidth.5min

       unit name = bps
       formula = 8 * ; 8 /"
   ::= {pr1645v2VEthVlanEntry 45507584}

pr1645v2VEthVlanVlanVid OBJECT-TYPE
   SYNTAX      Integer32
   MAX-ACCESS  read-only
   STATUS      current
   DESCRIPTION
      "Path: virtualEthernet.performance.vlan.vlan.vid"
   ::= {pr1645v2VEthVlanEntry 234946560}

pr1645v2VEthVlanPppLinkMonitoringRequestsSent OBJECT-TYPE
   SYNTAX      Gauge32
   MAX-ACCESS  read-only
   STATUS      current
   DESCRIPTION
      "Path: virtualEthernet.performance.vlan.ppp.linkMonitoring.requestsSent

       32 bit unsigned gauge value."
   ::= {pr1645v2VEthVlanEntry 50397440}

pr1645v2VEthVlanPppLinkMonitoringRepliesRcvd OBJECT-TYPE
   SYNTAX      Gauge32
   MAX-ACCESS  read-only
   STATUS      current
   DESCRIPTION
      "Path: virtualEthernet.performance.vlan.ppp.linkMonitoring.repliesRcvd

       32 bit unsigned gauge value."
   ::= {pr1645v2VEthVlanEntry 50397696}

pr1645v2VEthVlanPppLinkMonitoringRequestsRcvd OBJECT-TYPE
   SYNTAX      Gauge32
   MAX-ACCESS  read-only
   STATUS      current
   DESCRIPTION
      "Path: virtualEthernet.performance.vlan.ppp.linkMonitoring.requestsRcvd

       32 bit unsigned gauge value."
   ::= {pr1645v2VEthVlanEntry 50397952}

pr1645v2VEthVlanPppLinkMonitoringRepliesSent OBJECT-TYPE
   SYNTAX      Gauge32
   MAX-ACCESS  read-only
   STATUS      current
   DESCRIPTION
      "Path: virtualEthernet.performance.vlan.ppp.linkMonitoring.repliesSent

       32 bit unsigned gauge value."
   ::= {pr1645v2VEthVlanEntry 50398208}

pr1645v2VEthVlanMCH2P OBJECT-TYPE
   SYNTAX      SEQUENCE OF Pr1645v2VEthVlanMCH2PEntry
   MAX-ACCESS  not-accessible
   STATUS      current
   DESCRIPTION
      ""
   ::= {pr1645v2VEthVlan 41549824}

pr1645v2VEthVlanMCH2PEntry OBJECT-TYPE
   SYNTAX      Pr1645v2VEthVlanMCH2PEntry
   MAX-ACCESS  not-accessible
   STATUS      current
   DESCRIPTION
      ""
   INDEX      { pr1645v2VEthVlanMCH2PGlobalIx,
                pr1645v2VEthVlanTableIx,
                pr1645v2VEthVlanMCH2PTableIx }
   ::= {pr1645v2VEthVlanMCH2P 1}

Pr1645v2VEthVlanMCH2PEntry ::=
   SEQUENCE
      {
      pr1645v2VEthVlanMCH2PGlobalIx
         GlobalIndex,
      pr1645v2VEthVlanMCH2PTableIx
         TableIndex,
      pr1645v2VEthVlanMCH2PSysUpTime
         TimeTicks,
      pr1645v2VEthVlanMCH2PIfUpTime
         TimeTicks,
      pr1645v2VEthVlanMCH2PIfStatChanges
         Counter32,
      pr1645v2VEthVlanMCH2PIfInOctets
         Counter64,
      pr1645v2VEthVlanMCH2PIfInUCPkts
         Counter64,
      pr1645v2VEthVlanMCH2PIfInNUCPkts
         Counter64,
      pr1645v2VEthVlanMCH2PIfInBCPkts
         Counter64,
      pr1645v2VEthVlanMCH2PIfInMCPkts
         Counter64,
      pr1645v2VEthVlanMCH2PIfInDiscards
         Counter64,
      pr1645v2VEthVlanMCH2PIfInErrors
         Counter64,
      pr1645v2VEthVlanMCH2PIfInUnkwn
         Counter64,
      pr1645v2VEthVlanMCH2PInDropEx
         Counter64,
      pr1645v2VEthVlanMCH2PInDropNoMac
         Counter64,
      pr1645v2VEthVlanMCH2PInDropNUCast
         Counter64,
      pr1645v2VEthVlanMCH2PInDropFilter
         Counter64,
      pr1645v2VEthVlanMCH2PIfInBandwidth
         Integer32,
      pr1645v2VEthVlanMCH2PIfOutOctets
         Counter64,
      pr1645v2VEthVlanMCH2PIfOutUCPkts
         Counter64,
      pr1645v2VEthVlanMCH2PIfOutNUCPkts
         Counter64,
      pr1645v2VEthVlanMCH2PIfOutBCPkts
         Counter64,
      pr1645v2VEthVlanMCH2PIfOutMCPkts
         Counter64,
      pr1645v2VEthVlanMCH2PIfOutDiscards
         Counter64,
      pr1645v2VEthVlanMCH2PIfOutErrors
         Counter64,
      pr1645v2VEthVlanMCH2POutDropEx
         Counter64,
      pr1645v2VEthVlanMCH2POutDropNoArp
         Counter64,
      pr1645v2VEthVlanMCH2POutDropFilter
         Counter64,
      pr1645v2VEthVlanMCH2PIfOutBandwidth
         Integer32,
      pr1645v2VEthVlanMCH2PIfErrSec
         Counter32
      }

pr1645v2VEthVlanMCH2PGlobalIx OBJECT-TYPE
   SYNTAX      GlobalIndex
   MAX-ACCESS  not-accessible
   STATUS      current
   DESCRIPTION
      "The value of the tlsCntTreeGlobalIndex of the MANAGED OBJECT."
   ::= {pr1645v2VEthVlanMCH2PEntry 10}

pr1645v2VEthVlanMCH2PTableIx OBJECT-TYPE
   SYNTAX      TableIndex
   MAX-ACCESS  not-accessible
   STATUS      current
   DESCRIPTION
      ""
   ::= {pr1645v2VEthVlanMCH2PEntry 11}

pr1645v2VEthVlanMCH2PSysUpTime OBJECT-TYPE
   SYNTAX      TimeTicks
   MAX-ACCESS  read-only
   STATUS      current
   DESCRIPTION
      "Path: virtualEthernet.performance.vlan.mibCounters.h2Performance.sysUpTime

       Time in centi-second."
   ::= {pr1645v2VEthVlanMCH2PEntry 16777216}

pr1645v2VEthVlanMCH2PIfUpTime OBJECT-TYPE
   SYNTAX      TimeTicks
   MAX-ACCESS  read-only
   STATUS      current
   DESCRIPTION
      "Path: virtualEthernet.performance.vlan.mibCounters.h2Performance.ifUpTime

       Time in centi-second."
   ::= {pr1645v2VEthVlanMCH2PEntry 33554432}

pr1645v2VEthVlanMCH2PIfStatChanges OBJECT-TYPE
   SYNTAX      Counter32
   MAX-ACCESS  read-only
   STATUS      current
   DESCRIPTION
      "Path: virtualEthernet.performance.vlan.mibCounters.h2Performance.ifStatusChanges

       32 bit unsigned wrappable counter."
   ::= {pr1645v2VEthVlanMCH2PEntry 50331648}

pr1645v2VEthVlanMCH2PIfInOctets OBJECT-TYPE
   SYNTAX      Counter64
   MAX-ACCESS  read-only
   STATUS      current
   DESCRIPTION
      "Path: virtualEthernet.performance.vlan.mibCounters.h2Performance.ifInOctets

       64 bit unsigned wrappable counter."
   ::= {pr1645v2VEthVlanMCH2PEntry 67108864}

pr1645v2VEthVlanMCH2PIfInUCPkts OBJECT-TYPE
   SYNTAX      Counter64
   MAX-ACCESS  read-only
   STATUS      current
   DESCRIPTION
      "Path: virtualEthernet.performance.vlan.mibCounters.h2Performance.ifInUcastPkts

       64 bit unsigned wrappable counter."
   ::= {pr1645v2VEthVlanMCH2PEntry 83886080}

pr1645v2VEthVlanMCH2PIfInNUCPkts OBJECT-TYPE
   SYNTAX      Counter64
   MAX-ACCESS  read-only
   STATUS      current
   DESCRIPTION
      "Path: virtualEthernet.performance.vlan.mibCounters.h2Performance.ifInNUcastPkts

       64 bit unsigned wrappable counter."
   ::= {pr1645v2VEthVlanMCH2PEntry 100663296}

pr1645v2VEthVlanMCH2PIfInBCPkts OBJECT-TYPE
   SYNTAX      Counter64
   MAX-ACCESS  read-only
   STATUS      current
   DESCRIPTION
      "Path: virtualEthernet.performance.vlan.mibCounters.h2Performance.ifInBcastPkts

       64 bit unsigned wrappable counter."
   ::= {pr1645v2VEthVlanMCH2PEntry 419430400}

pr1645v2VEthVlanMCH2PIfInMCPkts OBJECT-TYPE
   SYNTAX      Counter64
   MAX-ACCESS  read-only
   STATUS      current
   DESCRIPTION
      "Path: virtualEthernet.performance.vlan.mibCounters.h2Performance.ifInMcastPkts

       64 bit unsigned wrappable counter."
   ::= {pr1645v2VEthVlanMCH2PEntry 436207616}

pr1645v2VEthVlanMCH2PIfInDiscards OBJECT-TYPE
   SYNTAX      Counter64
   MAX-ACCESS  read-only
   STATUS      current
   DESCRIPTION
      "Path: virtualEthernet.performance.vlan.mibCounters.h2Performance.ifInDiscards

       64 bit unsigned wrappable counter."
   ::= {pr1645v2VEthVlanMCH2PEntry 117440512}

pr1645v2VEthVlanMCH2PIfInErrors OBJECT-TYPE
   SYNTAX      Counter64
   MAX-ACCESS  read-only
   STATUS      current
   DESCRIPTION
      "Path: virtualEthernet.performance.vlan.mibCounters.h2Performance.ifInErrors

       64 bit unsigned wrappable counter."
   ::= {pr1645v2VEthVlanMCH2PEntry 134217728}

pr1645v2VEthVlanMCH2PIfInUnkwn OBJECT-TYPE
   SYNTAX      Counter64
   MAX-ACCESS  read-only
   STATUS      current
   DESCRIPTION
      "Path: virtualEthernet.performance.vlan.mibCounters.h2Performance.ifInUnknownProtos

       64 bit unsigned wrappable counter."
   ::= {pr1645v2VEthVlanMCH2PEntry 150994944}

pr1645v2VEthVlanMCH2PInDropEx OBJECT-TYPE
   SYNTAX      Counter64
   MAX-ACCESS  read-only
   STATUS      current
   DESCRIPTION
      "Path: virtualEthernet.performance.vlan.mibCounters.h2Performance.ifInDropLevelExceeded

       64 bit unsigned wrappable counter."
   ::= {pr1645v2VEthVlanMCH2PEntry 335544320}

pr1645v2VEthVlanMCH2PInDropNoMac OBJECT-TYPE
   SYNTAX      Counter64
   MAX-ACCESS  read-only
   STATUS      current
   DESCRIPTION
      "Path: virtualEthernet.performance.vlan.mibCounters.h2Performance.fInDiscardsNoMacFit

       64 bit unsigned wrappable counter."
   ::= {pr1645v2VEthVlanMCH2PEntry 301989888}

pr1645v2VEthVlanMCH2PInDropNUCast OBJECT-TYPE
   SYNTAX      Counter64
   MAX-ACCESS  read-only
   STATUS      current
   DESCRIPTION
      "Path: virtualEthernet.performance.vlan.mibCounters.h2Performance.fInDiscardsNUCast

       64 bit unsigned wrappable counter."
   ::= {pr1645v2VEthVlanMCH2PEntry 318767104}

pr1645v2VEthVlanMCH2PInDropFilter OBJECT-TYPE
   SYNTAX      Counter64
   MAX-ACCESS  read-only
   STATUS      current
   DESCRIPTION
      "Path: virtualEthernet.performance.vlan.mibCounters.h2Performance.fInDiscardsFilter

       64 bit unsigned wrappable counter."
   ::= {pr1645v2VEthVlanMCH2PEntry 385875968}

pr1645v2VEthVlanMCH2PIfInBandwidth OBJECT-TYPE
   SYNTAX      Integer32
   MAX-ACCESS  read-only
   STATUS      current
   DESCRIPTION
      "Path: virtualEthernet.performance.vlan.mibCounters.h2Performance.ifInBandwidth

       unit name = bps
       formula = 8 * ; 8 /"
   ::= {pr1645v2VEthVlanMCH2PEntry 268435456}

pr1645v2VEthVlanMCH2PIfOutOctets OBJECT-TYPE
   SYNTAX      Counter64
   MAX-ACCESS  read-only
   STATUS      current
   DESCRIPTION
      "Path: virtualEthernet.performance.vlan.mibCounters.h2Performance.ifOutOctets

       64 bit unsigned wrappable counter."
   ::= {pr1645v2VEthVlanMCH2PEntry 167772160}

pr1645v2VEthVlanMCH2PIfOutUCPkts OBJECT-TYPE
   SYNTAX      Counter64
   MAX-ACCESS  read-only
   STATUS      current
   DESCRIPTION
      "Path: virtualEthernet.performance.vlan.mibCounters.h2Performance.ifOutUcastPkts

       64 bit unsigned wrappable counter."
   ::= {pr1645v2VEthVlanMCH2PEntry 184549376}

pr1645v2VEthVlanMCH2PIfOutNUCPkts OBJECT-TYPE
   SYNTAX      Counter64
   MAX-ACCESS  read-only
   STATUS      current
   DESCRIPTION
      "Path: virtualEthernet.performance.vlan.mibCounters.h2Performance.ifOutNUcastPkts

       64 bit unsigned wrappable counter."
   ::= {pr1645v2VEthVlanMCH2PEntry 201326592}

pr1645v2VEthVlanMCH2PIfOutBCPkts OBJECT-TYPE
   SYNTAX      Counter64
   MAX-ACCESS  read-only
   STATUS      current
   DESCRIPTION
      "Path: virtualEthernet.performance.vlan.mibCounters.h2Performance.ifOutBcastPkts

       64 bit unsigned wrappable counter."
   ::= {pr1645v2VEthVlanMCH2PEntry 452984832}

pr1645v2VEthVlanMCH2PIfOutMCPkts OBJECT-TYPE
   SYNTAX      Counter64
   MAX-ACCESS  read-only
   STATUS      current
   DESCRIPTION
      "Path: virtualEthernet.performance.vlan.mibCounters.h2Performance.ifOutMcastPkts

       64 bit unsigned wrappable counter."
   ::= {pr1645v2VEthVlanMCH2PEntry 469762048}

pr1645v2VEthVlanMCH2PIfOutDiscards OBJECT-TYPE
   SYNTAX      Counter64
   MAX-ACCESS  read-only
   STATUS      current
   DESCRIPTION
      "Path: virtualEthernet.performance.vlan.mibCounters.h2Performance.ifOutDiscards

       64 bit unsigned wrappable counter."
   ::= {pr1645v2VEthVlanMCH2PEntry 218103808}

pr1645v2VEthVlanMCH2PIfOutErrors OBJECT-TYPE
   SYNTAX      Counter64
   MAX-ACCESS  read-only
   STATUS      current
   DESCRIPTION
      "Path: virtualEthernet.performance.vlan.mibCounters.h2Performance.ifOutErrors

       64 bit unsigned wrappable counter."
   ::= {pr1645v2VEthVlanMCH2PEntry 234881024}

pr1645v2VEthVlanMCH2POutDropEx OBJECT-TYPE
   SYNTAX      Counter64
   MAX-ACCESS  read-only
   STATUS      current
   DESCRIPTION
      "Path: virtualEthernet.performance.vlan.mibCounters.h2Performance.ifOutDropLevelExceeded

       64 bit unsigned wrappable counter."
   ::= {pr1645v2VEthVlanMCH2PEntry 352321536}

pr1645v2VEthVlanMCH2POutDropNoArp OBJECT-TYPE
   SYNTAX      Counter64
   MAX-ACCESS  read-only
   STATUS      current
   DESCRIPTION
      "Path: virtualEthernet.performance.vlan.mibCounters.h2Performance.ifOutDiscardsNoArp

       64 bit unsigned wrappable counter."
   ::= {pr1645v2VEthVlanMCH2PEntry 369098752}

pr1645v2VEthVlanMCH2POutDropFilter OBJECT-TYPE
   SYNTAX      Counter64
   MAX-ACCESS  read-only
   STATUS      current
   DESCRIPTION
      "Path: virtualEthernet.performance.vlan.mibCounters.h2Performance.ifOutDiscardsFilter

       64 bit unsigned wrappable counter."
   ::= {pr1645v2VEthVlanMCH2PEntry 402653184}

pr1645v2VEthVlanMCH2PIfOutBandwidth OBJECT-TYPE
   SYNTAX      Integer32
   MAX-ACCESS  read-only
   STATUS      current
   DESCRIPTION
      "Path: virtualEthernet.performance.vlan.mibCounters.h2Performance.ifOutBandwidth

       unit name = bps
       formula = 8 * ; 8 /"
   ::= {pr1645v2VEthVlanMCH2PEntry 285212672}

pr1645v2VEthVlanMCH2PIfErrSec OBJECT-TYPE
   SYNTAX      Counter32
   MAX-ACCESS  read-only
   STATUS      current
   DESCRIPTION
      "Path: virtualEthernet.performance.vlan.mibCounters.h2Performance.ifErrSec

       32 bit unsigned wrappable counter."
   ::= {pr1645v2VEthVlanMCH2PEntry 251658240}

pr1645v2VEthVlanMCH24P OBJECT-TYPE
   SYNTAX      SEQUENCE OF Pr1645v2VEthVlanMCH24PEntry
   MAX-ACCESS  not-accessible
   STATUS      current
   DESCRIPTION
      ""
   ::= {pr1645v2VEthVlan 41615360}

pr1645v2VEthVlanMCH24PEntry OBJECT-TYPE
   SYNTAX      Pr1645v2VEthVlanMCH24PEntry
   MAX-ACCESS  not-accessible
   STATUS      current
   DESCRIPTION
      ""
   INDEX      { pr1645v2VEthVlanMCH24PGlobalIx,
                pr1645v2VEthVlanTableIx,
                pr1645v2VEthVlanMCH24PTableIx }
   ::= {pr1645v2VEthVlanMCH24P 1}

Pr1645v2VEthVlanMCH24PEntry ::=
   SEQUENCE
      {
      pr1645v2VEthVlanMCH24PGlobalIx
         GlobalIndex,
      pr1645v2VEthVlanMCH24PTableIx
         TableIndex,
      pr1645v2VEthVlanMCH24PSysUpTime
         TimeTicks,
      pr1645v2VEthVlanMCH24PIfUpTime
         TimeTicks,
      pr1645v2VEthVlanMCH24PIfStatChanges
         Counter32,
      pr1645v2VEthVlanMCH24PIfInOctets
         Counter64,
      pr1645v2VEthVlanMCH24PIfInUCPkts
         Counter64,
      pr1645v2VEthVlanMCH24PIfInNUCPkts
         Counter64,
      pr1645v2VEthVlanMCH24PIfInBCPkts
         Counter64,
      pr1645v2VEthVlanMCH24PIfInMCPkts
         Counter64,
      pr1645v2VEthVlanMCH24PIfInDiscards
         Counter64,
      pr1645v2VEthVlanMCH24PIfInErrors
         Counter64,
      pr1645v2VEthVlanMCH24PIfInUnkwn
         Counter64,
      pr1645v2VEthVlanMCH24PInDropEx
         Counter64,
      pr1645v2VEthVlanMCH24PInDropNoMac
         Counter64,
      pr1645v2VEthVlanMCH24PInDropNUCast
         Counter64,
      pr1645v2VEthVlanMCH24PInDropFilter
         Counter64,
      pr1645v2VEthVlanMCH24PIfInBandwidth
         Integer32,
      pr1645v2VEthVlanMCH24PIfOutOctets
         Counter64,
      pr1645v2VEthVlanMCH24PIfOutUCPkts
         Counter64,
      pr1645v2VEthVlanMCH24PIfOutNUCPkts
         Counter64,
      pr1645v2VEthVlanMCH24PIfOutBCPkts
         Counter64,
      pr1645v2VEthVlanMCH24PIfOutMCPkts
         Counter64,
      pr1645v2VEthVlanMCH24PIfOutDiscards
         Counter64,
      pr1645v2VEthVlanMCH24PIfOutErrors
         Counter64,
      pr1645v2VEthVlanMCH24POutDropEx
         Counter64,
      pr1645v2VEthVlanMCH24POutDropNoArp
         Counter64,
      pr1645v2VEthVlanMCH24POutDropFilter
         Counter64,
      pr1645v2VEthVlanMCH24PIfOutBandwidth
         Integer32,
      pr1645v2VEthVlanMCH24PIfErrSec
         Counter32
      }

pr1645v2VEthVlanMCH24PGlobalIx OBJECT-TYPE
   SYNTAX      GlobalIndex
   MAX-ACCESS  not-accessible
   STATUS      current
   DESCRIPTION
      "The value of the tlsCntTreeGlobalIndex of the MANAGED OBJECT."
   ::= {pr1645v2VEthVlanMCH24PEntry 10}

pr1645v2VEthVlanMCH24PTableIx OBJECT-TYPE
   SYNTAX      TableIndex
   MAX-ACCESS  not-accessible
   STATUS      current
   DESCRIPTION
      ""
   ::= {pr1645v2VEthVlanMCH24PEntry 11}

pr1645v2VEthVlanMCH24PSysUpTime OBJECT-TYPE
   SYNTAX      TimeTicks
   MAX-ACCESS  read-only
   STATUS      current
   DESCRIPTION
      "Path: virtualEthernet.performance.vlan.mibCounters.h24Performance.sysUpTime

       Time in centi-second."
   ::= {pr1645v2VEthVlanMCH24PEntry 16777216}

pr1645v2VEthVlanMCH24PIfUpTime OBJECT-TYPE
   SYNTAX      TimeTicks
   MAX-ACCESS  read-only
   STATUS      current
   DESCRIPTION
      "Path: virtualEthernet.performance.vlan.mibCounters.h24Performance.ifUpTime

       Time in centi-second."
   ::= {pr1645v2VEthVlanMCH24PEntry 33554432}

pr1645v2VEthVlanMCH24PIfStatChanges OBJECT-TYPE
   SYNTAX      Counter32
   MAX-ACCESS  read-only
   STATUS      current
   DESCRIPTION
      "Path: virtualEthernet.performance.vlan.mibCounters.h24Performance.ifStatusChanges

       32 bit unsigned wrappable counter."
   ::= {pr1645v2VEthVlanMCH24PEntry 50331648}

pr1645v2VEthVlanMCH24PIfInOctets OBJECT-TYPE
   SYNTAX      Counter64
   MAX-ACCESS  read-only
   STATUS      current
   DESCRIPTION
      "Path: virtualEthernet.performance.vlan.mibCounters.h24Performance.ifInOctets

       64 bit unsigned wrappable counter."
   ::= {pr1645v2VEthVlanMCH24PEntry 67108864}

pr1645v2VEthVlanMCH24PIfInUCPkts OBJECT-TYPE
   SYNTAX      Counter64
   MAX-ACCESS  read-only
   STATUS      current
   DESCRIPTION
      "Path: virtualEthernet.performance.vlan.mibCounters.h24Performance.ifInUcastPkts

       64 bit unsigned wrappable counter."
   ::= {pr1645v2VEthVlanMCH24PEntry 83886080}

pr1645v2VEthVlanMCH24PIfInNUCPkts OBJECT-TYPE
   SYNTAX      Counter64
   MAX-ACCESS  read-only
   STATUS      current
   DESCRIPTION
      "Path: virtualEthernet.performance.vlan.mibCounters.h24Performance.ifInNUcastPkts

       64 bit unsigned wrappable counter."
   ::= {pr1645v2VEthVlanMCH24PEntry 100663296}

pr1645v2VEthVlanMCH24PIfInBCPkts OBJECT-TYPE
   SYNTAX      Counter64
   MAX-ACCESS  read-only
   STATUS      current
   DESCRIPTION
      "Path: virtualEthernet.performance.vlan.mibCounters.h24Performance.ifInBcastPkts

       64 bit unsigned wrappable counter."
   ::= {pr1645v2VEthVlanMCH24PEntry 419430400}

pr1645v2VEthVlanMCH24PIfInMCPkts OBJECT-TYPE
   SYNTAX      Counter64
   MAX-ACCESS  read-only
   STATUS      current
   DESCRIPTION
      "Path: virtualEthernet.performance.vlan.mibCounters.h24Performance.ifInMcastPkts

       64 bit unsigned wrappable counter."
   ::= {pr1645v2VEthVlanMCH24PEntry 436207616}

pr1645v2VEthVlanMCH24PIfInDiscards OBJECT-TYPE
   SYNTAX      Counter64
   MAX-ACCESS  read-only
   STATUS      current
   DESCRIPTION
      "Path: virtualEthernet.performance.vlan.mibCounters.h24Performance.ifInDiscards

       64 bit unsigned wrappable counter."
   ::= {pr1645v2VEthVlanMCH24PEntry 117440512}

pr1645v2VEthVlanMCH24PIfInErrors OBJECT-TYPE
   SYNTAX      Counter64
   MAX-ACCESS  read-only
   STATUS      current
   DESCRIPTION
      "Path: virtualEthernet.performance.vlan.mibCounters.h24Performance.ifInErrors

       64 bit unsigned wrappable counter."
   ::= {pr1645v2VEthVlanMCH24PEntry 134217728}

pr1645v2VEthVlanMCH24PIfInUnkwn OBJECT-TYPE
   SYNTAX      Counter64
   MAX-ACCESS  read-only
   STATUS      current
   DESCRIPTION
      "Path: virtualEthernet.performance.vlan.mibCounters.h24Performance.ifInUnknownProtos

       64 bit unsigned wrappable counter."
   ::= {pr1645v2VEthVlanMCH24PEntry 150994944}

pr1645v2VEthVlanMCH24PInDropEx OBJECT-TYPE
   SYNTAX      Counter64
   MAX-ACCESS  read-only
   STATUS      current
   DESCRIPTION
      "Path: virtualEthernet.performance.vlan.mibCounters.h24Performance.ifInDropLevelExceeded

       64 bit unsigned wrappable counter."
   ::= {pr1645v2VEthVlanMCH24PEntry 335544320}

pr1645v2VEthVlanMCH24PInDropNoMac OBJECT-TYPE
   SYNTAX      Counter64
   MAX-ACCESS  read-only
   STATUS      current
   DESCRIPTION
      "Path: virtualEthernet.performance.vlan.mibCounters.h24Performance.fInDiscardsNoMacFit

       64 bit unsigned wrappable counter."
   ::= {pr1645v2VEthVlanMCH24PEntry 301989888}

pr1645v2VEthVlanMCH24PInDropNUCast OBJECT-TYPE
   SYNTAX      Counter64
   MAX-ACCESS  read-only
   STATUS      current
   DESCRIPTION
      "Path: virtualEthernet.performance.vlan.mibCounters.h24Performance.fInDiscardsNUCast

       64 bit unsigned wrappable counter."
   ::= {pr1645v2VEthVlanMCH24PEntry 318767104}

pr1645v2VEthVlanMCH24PInDropFilter OBJECT-TYPE
   SYNTAX      Counter64
   MAX-ACCESS  read-only
   STATUS      current
   DESCRIPTION
      "Path: virtualEthernet.performance.vlan.mibCounters.h24Performance.fInDiscardsFilter

       64 bit unsigned wrappable counter."
   ::= {pr1645v2VEthVlanMCH24PEntry 385875968}

pr1645v2VEthVlanMCH24PIfInBandwidth OBJECT-TYPE
   SYNTAX      Integer32
   MAX-ACCESS  read-only
   STATUS      current
   DESCRIPTION
      "Path: virtualEthernet.performance.vlan.mibCounters.h24Performance.ifInBandwidth

       unit name = bps
       formula = 8 * ; 8 /"
   ::= {pr1645v2VEthVlanMCH24PEntry 268435456}

pr1645v2VEthVlanMCH24PIfOutOctets OBJECT-TYPE
   SYNTAX      Counter64
   MAX-ACCESS  read-only
   STATUS      current
   DESCRIPTION
      "Path: virtualEthernet.performance.vlan.mibCounters.h24Performance.ifOutOctets

       64 bit unsigned wrappable counter."
   ::= {pr1645v2VEthVlanMCH24PEntry 167772160}

pr1645v2VEthVlanMCH24PIfOutUCPkts OBJECT-TYPE
   SYNTAX      Counter64
   MAX-ACCESS  read-only
   STATUS      current
   DESCRIPTION
      "Path: virtualEthernet.performance.vlan.mibCounters.h24Performance.ifOutUcastPkts

       64 bit unsigned wrappable counter."
   ::= {pr1645v2VEthVlanMCH24PEntry 184549376}

pr1645v2VEthVlanMCH24PIfOutNUCPkts OBJECT-TYPE
   SYNTAX      Counter64
   MAX-ACCESS  read-only
   STATUS      current
   DESCRIPTION
      "Path: virtualEthernet.performance.vlan.mibCounters.h24Performance.ifOutNUcastPkts

       64 bit unsigned wrappable counter."
   ::= {pr1645v2VEthVlanMCH24PEntry 201326592}

pr1645v2VEthVlanMCH24PIfOutBCPkts OBJECT-TYPE
   SYNTAX      Counter64
   MAX-ACCESS  read-only
   STATUS      current
   DESCRIPTION
      "Path: virtualEthernet.performance.vlan.mibCounters.h24Performance.ifOutBcastPkts

       64 bit unsigned wrappable counter."
   ::= {pr1645v2VEthVlanMCH24PEntry 452984832}

pr1645v2VEthVlanMCH24PIfOutMCPkts OBJECT-TYPE
   SYNTAX      Counter64
   MAX-ACCESS  read-only
   STATUS      current
   DESCRIPTION
      "Path: virtualEthernet.performance.vlan.mibCounters.h24Performance.ifOutMcastPkts

       64 bit unsigned wrappable counter."
   ::= {pr1645v2VEthVlanMCH24PEntry 469762048}

pr1645v2VEthVlanMCH24PIfOutDiscards OBJECT-TYPE
   SYNTAX      Counter64
   MAX-ACCESS  read-only
   STATUS      current
   DESCRIPTION
      "Path: virtualEthernet.performance.vlan.mibCounters.h24Performance.ifOutDiscards

       64 bit unsigned wrappable counter."
   ::= {pr1645v2VEthVlanMCH24PEntry 218103808}

pr1645v2VEthVlanMCH24PIfOutErrors OBJECT-TYPE
   SYNTAX      Counter64
   MAX-ACCESS  read-only
   STATUS      current
   DESCRIPTION
      "Path: virtualEthernet.performance.vlan.mibCounters.h24Performance.ifOutErrors

       64 bit unsigned wrappable counter."
   ::= {pr1645v2VEthVlanMCH24PEntry 234881024}

pr1645v2VEthVlanMCH24POutDropEx OBJECT-TYPE
   SYNTAX      Counter64
   MAX-ACCESS  read-only
   STATUS      current
   DESCRIPTION
      "Path: virtualEthernet.performance.vlan.mibCounters.h24Performance.ifOutDropLevelExceeded

       64 bit unsigned wrappable counter."
   ::= {pr1645v2VEthVlanMCH24PEntry 352321536}

pr1645v2VEthVlanMCH24POutDropNoArp OBJECT-TYPE
   SYNTAX      Counter64
   MAX-ACCESS  read-only
   STATUS      current
   DESCRIPTION
      "Path: virtualEthernet.performance.vlan.mibCounters.h24Performance.ifOutDiscardsNoArp

       64 bit unsigned wrappable counter."
   ::= {pr1645v2VEthVlanMCH24PEntry 369098752}

pr1645v2VEthVlanMCH24POutDropFilter OBJECT-TYPE
   SYNTAX      Counter64
   MAX-ACCESS  read-only
   STATUS      current
   DESCRIPTION
      "Path: virtualEthernet.performance.vlan.mibCounters.h24Performance.ifOutDiscardsFilter

       64 bit unsigned wrappable counter."
   ::= {pr1645v2VEthVlanMCH24PEntry 402653184}

pr1645v2VEthVlanMCH24PIfOutBandwidth OBJECT-TYPE
   SYNTAX      Integer32
   MAX-ACCESS  read-only
   STATUS      current
   DESCRIPTION
      "Path: virtualEthernet.performance.vlan.mibCounters.h24Performance.ifOutBandwidth

       unit name = bps
       formula = 8 * ; 8 /"
   ::= {pr1645v2VEthVlanMCH24PEntry 285212672}

pr1645v2VEthVlanMCH24PIfErrSec OBJECT-TYPE
   SYNTAX      Counter32
   MAX-ACCESS  read-only
   STATUS      current
   DESCRIPTION
      "Path: virtualEthernet.performance.vlan.mibCounters.h24Performance.ifErrSec

       32 bit unsigned wrappable counter."
   ::= {pr1645v2VEthVlanMCH24PEntry 251658240}

pr1645v2VEthVlanMCD7P OBJECT-TYPE
   SYNTAX      SEQUENCE OF Pr1645v2VEthVlanMCD7PEntry
   MAX-ACCESS  not-accessible
   STATUS      current
   DESCRIPTION
      ""
   ::= {pr1645v2VEthVlan 41680896}

pr1645v2VEthVlanMCD7PEntry OBJECT-TYPE
   SYNTAX      Pr1645v2VEthVlanMCD7PEntry
   MAX-ACCESS  not-accessible
   STATUS      current
   DESCRIPTION
      ""
   INDEX      { pr1645v2VEthVlanMCD7PGlobalIx,
                pr1645v2VEthVlanTableIx,
                pr1645v2VEthVlanMCD7PTableIx }
   ::= {pr1645v2VEthVlanMCD7P 1}

Pr1645v2VEthVlanMCD7PEntry ::=
   SEQUENCE
      {
      pr1645v2VEthVlanMCD7PGlobalIx
         GlobalIndex,
      pr1645v2VEthVlanMCD7PTableIx
         TableIndex,
      pr1645v2VEthVlanMCD7PSysUpTime
         TimeTicks,
      pr1645v2VEthVlanMCD7PIfUpTime
         TimeTicks,
      pr1645v2VEthVlanMCD7PIfStatChanges
         Counter32,
      pr1645v2VEthVlanMCD7PIfInOctets
         Counter64,
      pr1645v2VEthVlanMCD7PIfInUCPkts
         Counter64,
      pr1645v2VEthVlanMCD7PIfInNUCPkts
         Counter64,
      pr1645v2VEthVlanMCD7PIfInBCPkts
         Counter64,
      pr1645v2VEthVlanMCD7PIfInMCPkts
         Counter64,
      pr1645v2VEthVlanMCD7PIfInDiscards
         Counter64,
      pr1645v2VEthVlanMCD7PIfInErrors
         Counter64,
      pr1645v2VEthVlanMCD7PIfInUnkwn
         Counter64,
      pr1645v2VEthVlanMCD7PInDropEx
         Counter64,
      pr1645v2VEthVlanMCD7PInDropNoMac
         Counter64,
      pr1645v2VEthVlanMCD7PInDropNUCast
         Counter64,
      pr1645v2VEthVlanMCD7PInDropFilter
         Counter64,
      pr1645v2VEthVlanMCD7PIfInBandwidth
         Integer32,
      pr1645v2VEthVlanMCD7PIfOutOctets
         Counter64,
      pr1645v2VEthVlanMCD7PIfOutUCPkts
         Counter64,
      pr1645v2VEthVlanMCD7PIfOutNUCPkts
         Counter64,
      pr1645v2VEthVlanMCD7PIfOutBCPkts
         Counter64,
      pr1645v2VEthVlanMCD7PIfOutMCPkts
         Counter64,
      pr1645v2VEthVlanMCD7PIfOutDiscards
         Counter64,
      pr1645v2VEthVlanMCD7PIfOutErrors
         Counter64,
      pr1645v2VEthVlanMCD7POutDropEx
         Counter64,
      pr1645v2VEthVlanMCD7POutDropNoArp
         Counter64,
      pr1645v2VEthVlanMCD7POutDropFilter
         Counter64,
      pr1645v2VEthVlanMCD7PIfOutBandwidth
         Integer32,
      pr1645v2VEthVlanMCD7PIfErrSec
         Counter32
      }

pr1645v2VEthVlanMCD7PGlobalIx OBJECT-TYPE
   SYNTAX      GlobalIndex
   MAX-ACCESS  not-accessible
   STATUS      current
   DESCRIPTION
      "The value of the tlsCntTreeGlobalIndex of the MANAGED OBJECT."
   ::= {pr1645v2VEthVlanMCD7PEntry 10}

pr1645v2VEthVlanMCD7PTableIx OBJECT-TYPE
   SYNTAX      TableIndex
   MAX-ACCESS  not-accessible
   STATUS      current
   DESCRIPTION
      ""
   ::= {pr1645v2VEthVlanMCD7PEntry 11}

pr1645v2VEthVlanMCD7PSysUpTime OBJECT-TYPE
   SYNTAX      TimeTicks
   MAX-ACCESS  read-only
   STATUS      current
   DESCRIPTION
      "Path: virtualEthernet.performance.vlan.mibCounters.d7Performance.sysUpTime

       Time in centi-second."
   ::= {pr1645v2VEthVlanMCD7PEntry 16777216}

pr1645v2VEthVlanMCD7PIfUpTime OBJECT-TYPE
   SYNTAX      TimeTicks
   MAX-ACCESS  read-only
   STATUS      current
   DESCRIPTION
      "Path: virtualEthernet.performance.vlan.mibCounters.d7Performance.ifUpTime

       Time in centi-second."
   ::= {pr1645v2VEthVlanMCD7PEntry 33554432}

pr1645v2VEthVlanMCD7PIfStatChanges OBJECT-TYPE
   SYNTAX      Counter32
   MAX-ACCESS  read-only
   STATUS      current
   DESCRIPTION
      "Path: virtualEthernet.performance.vlan.mibCounters.d7Performance.ifStatusChanges

       32 bit unsigned wrappable counter."
   ::= {pr1645v2VEthVlanMCD7PEntry 50331648}

pr1645v2VEthVlanMCD7PIfInOctets OBJECT-TYPE
   SYNTAX      Counter64
   MAX-ACCESS  read-only
   STATUS      current
   DESCRIPTION
      "Path: virtualEthernet.performance.vlan.mibCounters.d7Performance.ifInOctets

       64 bit unsigned wrappable counter."
   ::= {pr1645v2VEthVlanMCD7PEntry 67108864}

pr1645v2VEthVlanMCD7PIfInUCPkts OBJECT-TYPE
   SYNTAX      Counter64
   MAX-ACCESS  read-only
   STATUS      current
   DESCRIPTION
      "Path: virtualEthernet.performance.vlan.mibCounters.d7Performance.ifInUcastPkts

       64 bit unsigned wrappable counter."
   ::= {pr1645v2VEthVlanMCD7PEntry 83886080}

pr1645v2VEthVlanMCD7PIfInNUCPkts OBJECT-TYPE
   SYNTAX      Counter64
   MAX-ACCESS  read-only
   STATUS      current
   DESCRIPTION
      "Path: virtualEthernet.performance.vlan.mibCounters.d7Performance.ifInNUcastPkts

       64 bit unsigned wrappable counter."
   ::= {pr1645v2VEthVlanMCD7PEntry 100663296}

pr1645v2VEthVlanMCD7PIfInBCPkts OBJECT-TYPE
   SYNTAX      Counter64
   MAX-ACCESS  read-only
   STATUS      current
   DESCRIPTION
      "Path: virtualEthernet.performance.vlan.mibCounters.d7Performance.ifInBcastPkts

       64 bit unsigned wrappable counter."
   ::= {pr1645v2VEthVlanMCD7PEntry 419430400}

pr1645v2VEthVlanMCD7PIfInMCPkts OBJECT-TYPE
   SYNTAX      Counter64
   MAX-ACCESS  read-only
   STATUS      current
   DESCRIPTION
      "Path: virtualEthernet.performance.vlan.mibCounters.d7Performance.ifInMcastPkts

       64 bit unsigned wrappable counter."
   ::= {pr1645v2VEthVlanMCD7PEntry 436207616}

pr1645v2VEthVlanMCD7PIfInDiscards OBJECT-TYPE
   SYNTAX      Counter64
   MAX-ACCESS  read-only
   STATUS      current
   DESCRIPTION
      "Path: virtualEthernet.performance.vlan.mibCounters.d7Performance.ifInDiscards

       64 bit unsigned wrappable counter."
   ::= {pr1645v2VEthVlanMCD7PEntry 117440512}

pr1645v2VEthVlanMCD7PIfInErrors OBJECT-TYPE
   SYNTAX      Counter64
   MAX-ACCESS  read-only
   STATUS      current
   DESCRIPTION
      "Path: virtualEthernet.performance.vlan.mibCounters.d7Performance.ifInErrors

       64 bit unsigned wrappable counter."
   ::= {pr1645v2VEthVlanMCD7PEntry 134217728}

pr1645v2VEthVlanMCD7PIfInUnkwn OBJECT-TYPE
   SYNTAX      Counter64
   MAX-ACCESS  read-only
   STATUS      current
   DESCRIPTION
      "Path: virtualEthernet.performance.vlan.mibCounters.d7Performance.ifInUnknownProtos

       64 bit unsigned wrappable counter."
   ::= {pr1645v2VEthVlanMCD7PEntry 150994944}

pr1645v2VEthVlanMCD7PInDropEx OBJECT-TYPE
   SYNTAX      Counter64
   MAX-ACCESS  read-only
   STATUS      current
   DESCRIPTION
      "Path: virtualEthernet.performance.vlan.mibCounters.d7Performance.ifInDropLevelExceeded

       64 bit unsigned wrappable counter."
   ::= {pr1645v2VEthVlanMCD7PEntry 335544320}

pr1645v2VEthVlanMCD7PInDropNoMac OBJECT-TYPE
   SYNTAX      Counter64
   MAX-ACCESS  read-only
   STATUS      current
   DESCRIPTION
      "Path: virtualEthernet.performance.vlan.mibCounters.d7Performance.fInDiscardsNoMacFit

       64 bit unsigned wrappable counter."
   ::= {pr1645v2VEthVlanMCD7PEntry 301989888}

pr1645v2VEthVlanMCD7PInDropNUCast OBJECT-TYPE
   SYNTAX      Counter64
   MAX-ACCESS  read-only
   STATUS      current
   DESCRIPTION
      "Path: virtualEthernet.performance.vlan.mibCounters.d7Performance.fInDiscardsNUCast

       64 bit unsigned wrappable counter."
   ::= {pr1645v2VEthVlanMCD7PEntry 318767104}

pr1645v2VEthVlanMCD7PInDropFilter OBJECT-TYPE
   SYNTAX      Counter64
   MAX-ACCESS  read-only
   STATUS      current
   DESCRIPTION
      "Path: virtualEthernet.performance.vlan.mibCounters.d7Performance.fInDiscardsFilter

       64 bit unsigned wrappable counter."
   ::= {pr1645v2VEthVlanMCD7PEntry 385875968}

pr1645v2VEthVlanMCD7PIfInBandwidth OBJECT-TYPE
   SYNTAX      Integer32
   MAX-ACCESS  read-only
   STATUS      current
   DESCRIPTION
      "Path: virtualEthernet.performance.vlan.mibCounters.d7Performance.ifInBandwidth

       unit name = bps
       formula = 8 * ; 8 /"
   ::= {pr1645v2VEthVlanMCD7PEntry 268435456}

pr1645v2VEthVlanMCD7PIfOutOctets OBJECT-TYPE
   SYNTAX      Counter64
   MAX-ACCESS  read-only
   STATUS      current
   DESCRIPTION
      "Path: virtualEthernet.performance.vlan.mibCounters.d7Performance.ifOutOctets

       64 bit unsigned wrappable counter."
   ::= {pr1645v2VEthVlanMCD7PEntry 167772160}

pr1645v2VEthVlanMCD7PIfOutUCPkts OBJECT-TYPE
   SYNTAX      Counter64
   MAX-ACCESS  read-only
   STATUS      current
   DESCRIPTION
      "Path: virtualEthernet.performance.vlan.mibCounters.d7Performance.ifOutUcastPkts

       64 bit unsigned wrappable counter."
   ::= {pr1645v2VEthVlanMCD7PEntry 184549376}

pr1645v2VEthVlanMCD7PIfOutNUCPkts OBJECT-TYPE
   SYNTAX      Counter64
   MAX-ACCESS  read-only
   STATUS      current
   DESCRIPTION
      "Path: virtualEthernet.performance.vlan.mibCounters.d7Performance.ifOutNUcastPkts

       64 bit unsigned wrappable counter."
   ::= {pr1645v2VEthVlanMCD7PEntry 201326592}

pr1645v2VEthVlanMCD7PIfOutBCPkts OBJECT-TYPE
   SYNTAX      Counter64
   MAX-ACCESS  read-only
   STATUS      current
   DESCRIPTION
      "Path: virtualEthernet.performance.vlan.mibCounters.d7Performance.ifOutBcastPkts

       64 bit unsigned wrappable counter."
   ::= {pr1645v2VEthVlanMCD7PEntry 452984832}

pr1645v2VEthVlanMCD7PIfOutMCPkts OBJECT-TYPE
   SYNTAX      Counter64
   MAX-ACCESS  read-only
   STATUS      current
   DESCRIPTION
      "Path: virtualEthernet.performance.vlan.mibCounters.d7Performance.ifOutMcastPkts

       64 bit unsigned wrappable counter."
   ::= {pr1645v2VEthVlanMCD7PEntry 469762048}

pr1645v2VEthVlanMCD7PIfOutDiscards OBJECT-TYPE
   SYNTAX      Counter64
   MAX-ACCESS  read-only
   STATUS      current
   DESCRIPTION
      "Path: virtualEthernet.performance.vlan.mibCounters.d7Performance.ifOutDiscards

       64 bit unsigned wrappable counter."
   ::= {pr1645v2VEthVlanMCD7PEntry 218103808}

pr1645v2VEthVlanMCD7PIfOutErrors OBJECT-TYPE
   SYNTAX      Counter64
   MAX-ACCESS  read-only
   STATUS      current
   DESCRIPTION
      "Path: virtualEthernet.performance.vlan.mibCounters.d7Performance.ifOutErrors

       64 bit unsigned wrappable counter."
   ::= {pr1645v2VEthVlanMCD7PEntry 234881024}

pr1645v2VEthVlanMCD7POutDropEx OBJECT-TYPE
   SYNTAX      Counter64
   MAX-ACCESS  read-only
   STATUS      current
   DESCRIPTION
      "Path: virtualEthernet.performance.vlan.mibCounters.d7Performance.ifOutDropLevelExceeded

       64 bit unsigned wrappable counter."
   ::= {pr1645v2VEthVlanMCD7PEntry 352321536}

pr1645v2VEthVlanMCD7POutDropNoArp OBJECT-TYPE
   SYNTAX      Counter64
   MAX-ACCESS  read-only
   STATUS      current
   DESCRIPTION
      "Path: virtualEthernet.performance.vlan.mibCounters.d7Performance.ifOutDiscardsNoArp

       64 bit unsigned wrappable counter."
   ::= {pr1645v2VEthVlanMCD7PEntry 369098752}

pr1645v2VEthVlanMCD7POutDropFilter OBJECT-TYPE
   SYNTAX      Counter64
   MAX-ACCESS  read-only
   STATUS      current
   DESCRIPTION
      "Path: virtualEthernet.performance.vlan.mibCounters.d7Performance.ifOutDiscardsFilter

       64 bit unsigned wrappable counter."
   ::= {pr1645v2VEthVlanMCD7PEntry 402653184}

pr1645v2VEthVlanMCD7PIfOutBandwidth OBJECT-TYPE
   SYNTAX      Integer32
   MAX-ACCESS  read-only
   STATUS      current
   DESCRIPTION
      "Path: virtualEthernet.performance.vlan.mibCounters.d7Performance.ifOutBandwidth

       unit name = bps
       formula = 8 * ; 8 /"
   ::= {pr1645v2VEthVlanMCD7PEntry 285212672}

pr1645v2VEthVlanMCD7PIfErrSec OBJECT-TYPE
   SYNTAX      Counter32
   MAX-ACCESS  read-only
   STATUS      current
   DESCRIPTION
      "Path: virtualEthernet.performance.vlan.mibCounters.d7Performance.ifErrSec

       32 bit unsigned wrappable counter."
   ::= {pr1645v2VEthVlanMCD7PEntry 251658240}

pr1645v2VEthVlanInPQs OBJECT-TYPE
   SYNTAX      SEQUENCE OF Pr1645v2VEthVlanInPQsEntry
   MAX-ACCESS  not-accessible
   STATUS      current
   DESCRIPTION
      ""
   ::= {pr1645v2VEthVlan 100663296}

pr1645v2VEthVlanInPQsEntry OBJECT-TYPE
   SYNTAX      Pr1645v2VEthVlanInPQsEntry
   MAX-ACCESS  not-accessible
   STATUS      current
   DESCRIPTION
      ""
   INDEX      { pr1645v2VEthVlanInPQsGlobalIx,
                pr1645v2VEthVlanTableIx,
                pr1645v2VEthVlanInPQsTableIx }
   ::= {pr1645v2VEthVlanInPQs 1}

Pr1645v2VEthVlanInPQsEntry ::=
   SEQUENCE
      {
      pr1645v2VEthVlanInPQsGlobalIx
         GlobalIndex,
      pr1645v2VEthVlanInPQsTableIx
         TableIndex,
      pr1645v2VEthVlanInPQsName
         INTEGER,
      pr1645v2VEthVlanInPQsLength
         Integer32,
      pr1645v2VEthVlanInPQsOctetLength
         Integer32,
      pr1645v2VEthVlanInPQsRedLength
         Integer32,
      pr1645v2VEthVlanInPQsPacketsTotal
         Counter64,
      pr1645v2VEthVlanInPQsPacketsDirectTx
         Counter64,
      pr1645v2VEthVlanInPQsPacketsQueued
         Counter64,
      pr1645v2VEthVlanInPQsPacketsDropped
         Counter64,
      pr1645v2VEthVlanInPQsPacketsRedDropped
         Counter64,
      pr1645v2VEthVlanInPQsPacketsCirTx
         Counter64,
      pr1645v2VEthVlanInPQsPacketsEirTx
         Counter64,
      pr1645v2VEthVlanInPQsPacketsViolateTx
         Counter64,
      pr1645v2VEthVlanInPQsOctetsTotal
         Counter64,
      pr1645v2VEthVlanInPQsOctetsDirectTx
         Counter64,
      pr1645v2VEthVlanInPQsOctetsQueued
         Counter64,
      pr1645v2VEthVlanInPQsOctetsDropped
         Counter64,
      pr1645v2VEthVlanInPQsOctetsRedDropped
         Counter64,
      pr1645v2VEthVlanInPQsOctetsCirTx
         Counter64,
      pr1645v2VEthVlanInPQsOctetsEirTx
         Counter64,
      pr1645v2VEthVlanInPQsOctetsViolateTx
         Counter64,
      pr1645v2VEthVlanInPQsOctetsBandwidth15sec
         Integer32,
      pr1645v2VEthVlanInPQsOctetsBandwidth30sec
         Integer32,
      pr1645v2VEthVlanInPQsOctetsBandwidth1min
         Integer32,
      pr1645v2VEthVlanInPQsOctetsBandwidth2min
         Integer32,
      pr1645v2VEthVlanInPQsOctetsBandwidth5min
         Integer32
      }

pr1645v2VEthVlanInPQsGlobalIx OBJECT-TYPE
   SYNTAX      GlobalIndex
   MAX-ACCESS  not-accessible
   STATUS      current
   DESCRIPTION
      "The value of the tlsCntTreeGlobalIndex of the MANAGED OBJECT."
   ::= {pr1645v2VEthVlanInPQsEntry 10}

pr1645v2VEthVlanInPQsTableIx OBJECT-TYPE
   SYNTAX      TableIndex
   MAX-ACCESS  not-accessible
   STATUS      current
   DESCRIPTION
      ""
   ::= {pr1645v2VEthVlanInPQsEntry 11}

pr1645v2VEthVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2VEthVlanInPQsEntry 16777216}

pr1645v2VEthVlanInPQsLength OBJECT-TYPE
   SYNTAX      Integer32
   MAX-ACCESS  read-only
   STATUS      current
   DESCRIPTION
      "Path: virtualEthernet.performance.vlan.inPriorityQueues.length"
   ::= {pr1645v2VEthVlanInPQsEntry 33554432}

pr1645v2VEthVlanInPQsOctetLength OBJECT-TYPE
   SYNTAX      Integer32
   MAX-ACCESS  read-only
   STATUS      current
   DESCRIPTION
      "Path: virtualEthernet.performance.vlan.inPriorityQueues.octetLength"
   ::= {pr1645v2VEthVlanInPQsEntry 150994944}

pr1645v2VEthVlanInPQsRedLength OBJECT-TYPE
   SYNTAX      Integer32
   MAX-ACCESS  read-only
   STATUS      current
   DESCRIPTION
      "Path: virtualEthernet.performance.vlan.inPriorityQueues.redLength"
   ::= {pr1645v2VEthVlanInPQsEntry 134217728}

pr1645v2VEthVlanInPQsPacketsTotal OBJECT-TYPE
   SYNTAX      Counter64
   MAX-ACCESS  read-only
   STATUS      current
   DESCRIPTION
      "Path: virtualEthernet.performance.vlan.inPriorityQueues.packets.total

       64 bit unsigned wrappable counter."
   ::= {pr1645v2VEthVlanInPQsEntry 50790400}

pr1645v2VEthVlanInPQsPacketsDirectTx OBJECT-TYPE
   SYNTAX      Counter64
   MAX-ACCESS  read-only
   STATUS      current
   DESCRIPTION
      "Path: virtualEthernet.performance.vlan.inPriorityQueues.packets.directTx

       64 bit unsigned wrappable counter."
   ::= {pr1645v2VEthVlanInPQsEntry 50397184}

pr1645v2VEthVlanInPQsPacketsQueued OBJECT-TYPE
   SYNTAX      Counter64
   MAX-ACCESS  read-only
   STATUS      current
   DESCRIPTION
      "Path: virtualEthernet.performance.vlan.inPriorityQueues.packets.queued

       64 bit unsigned wrappable counter."
   ::= {pr1645v2VEthVlanInPQsEntry 50462720}

pr1645v2VEthVlanInPQsPacketsDropped OBJECT-TYPE
   SYNTAX      Counter64
   MAX-ACCESS  read-only
   STATUS      current
   DESCRIPTION
      "Path: virtualEthernet.performance.vlan.inPriorityQueues.packets.dropped

       64 bit unsigned wrappable counter."
   ::= {pr1645v2VEthVlanInPQsEntry 50528256}

pr1645v2VEthVlanInPQsPacketsRedDropped OBJECT-TYPE
   SYNTAX      Counter64
   MAX-ACCESS  read-only
   STATUS      current
   DESCRIPTION
      "Path: virtualEthernet.performance.vlan.inPriorityQueues.packets.redDropped

       64 bit unsigned wrappable counter."
   ::= {pr1645v2VEthVlanInPQsEntry 50724864}

pr1645v2VEthVlanInPQsPacketsCirTx OBJECT-TYPE
   SYNTAX      Counter64
   MAX-ACCESS  read-only
   STATUS      current
   DESCRIPTION
      "Path: virtualEthernet.performance.vlan.inPriorityQueues.packets.cirTx

       64 bit unsigned wrappable counter."
   ::= {pr1645v2VEthVlanInPQsEntry 50593792}

pr1645v2VEthVlanInPQsPacketsEirTx OBJECT-TYPE
   SYNTAX      Counter64
   MAX-ACCESS  read-only
   STATUS      current
   DESCRIPTION
      "Path: virtualEthernet.performance.vlan.inPriorityQueues.packets.eirTx

       64 bit unsigned wrappable counter."
   ::= {pr1645v2VEthVlanInPQsEntry 50659328}

pr1645v2VEthVlanInPQsPacketsViolateTx OBJECT-TYPE
   SYNTAX      Counter64
   MAX-ACCESS  read-only
   STATUS      current
   DESCRIPTION
      "Path: virtualEthernet.performance.vlan.inPriorityQueues.packets.violateTx

       64 bit unsigned wrappable counter."
   ::= {pr1645v2VEthVlanInPQsEntry 50855936}

pr1645v2VEthVlanInPQsOctetsTotal OBJECT-TYPE
   SYNTAX      Counter64
   MAX-ACCESS  read-only
   STATUS      current
   DESCRIPTION
      "Path: virtualEthernet.performance.vlan.inPriorityQueues.octets.total

       64 bit unsigned wrappable counter."
   ::= {pr1645v2VEthVlanInPQsEntry 67567616}

pr1645v2VEthVlanInPQsOctetsDirectTx OBJECT-TYPE
   SYNTAX      Counter64
   MAX-ACCESS  read-only
   STATUS      current
   DESCRIPTION
      "Path: virtualEthernet.performance.vlan.inPriorityQueues.octets.directTx

       64 bit unsigned wrappable counter."
   ::= {pr1645v2VEthVlanInPQsEntry 67174400}

pr1645v2VEthVlanInPQsOctetsQueued OBJECT-TYPE
   SYNTAX      Counter64
   MAX-ACCESS  read-only
   STATUS      current
   DESCRIPTION
      "Path: virtualEthernet.performance.vlan.inPriorityQueues.octets.queued

       64 bit unsigned wrappable counter."
   ::= {pr1645v2VEthVlanInPQsEntry 67239936}

pr1645v2VEthVlanInPQsOctetsDropped OBJECT-TYPE
   SYNTAX      Counter64
   MAX-ACCESS  read-only
   STATUS      current
   DESCRIPTION
      "Path: virtualEthernet.performance.vlan.inPriorityQueues.octets.dropped

       64 bit unsigned wrappable counter."
   ::= {pr1645v2VEthVlanInPQsEntry 67305472}

pr1645v2VEthVlanInPQsOctetsRedDropped OBJECT-TYPE
   SYNTAX      Counter64
   MAX-ACCESS  read-only
   STATUS      current
   DESCRIPTION
      "Path: virtualEthernet.performance.vlan.inPriorityQueues.octets.redDropped

       64 bit unsigned wrappable counter."
   ::= {pr1645v2VEthVlanInPQsEntry 67502080}

pr1645v2VEthVlanInPQsOctetsCirTx OBJECT-TYPE
   SYNTAX      Counter64
   MAX-ACCESS  read-only
   STATUS      current
   DESCRIPTION
      "Path: virtualEthernet.performance.vlan.inPriorityQueues.octets.cirTx

       64 bit unsigned wrappable counter."
   ::= {pr1645v2VEthVlanInPQsEntry 67371008}

pr1645v2VEthVlanInPQsOctetsEirTx OBJECT-TYPE
   SYNTAX      Counter64
   MAX-ACCESS  read-only
   STATUS      current
   DESCRIPTION
      "Path: virtualEthernet.performance.vlan.inPriorityQueues.octets.eirTx

       64 bit unsigned wrappable counter."
   ::= {pr1645v2VEthVlanInPQsEntry 67436544}

pr1645v2VEthVlanInPQsOctetsViolateTx OBJECT-TYPE
   SYNTAX      Counter64
   MAX-ACCESS  read-only
   STATUS      current
   DESCRIPTION
      "Path: virtualEthernet.performance.vlan.inPriorityQueues.octets.violateTx

       64 bit unsigned wrappable counter."
   ::= {pr1645v2VEthVlanInPQsEntry 67633152}

pr1645v2VEthVlanInPQsOctetsBandwidth15sec OBJECT-TYPE
   SYNTAX      Integer32
   MAX-ACCESS  read-only
   STATUS      current
   DESCRIPTION
      "Path: virtualEthernet.performance.vlan.inPriorityQueues.octets.bandwidth.15sec

       unit name = bps
       formula = 8 * ; 8 /"
   ::= {pr1645v2VEthVlanInPQsEntry 70386944}

pr1645v2VEthVlanInPQsOctetsBandwidth30sec OBJECT-TYPE
   SYNTAX      Integer32
   MAX-ACCESS  read-only
   STATUS      current
   DESCRIPTION
      "Path: virtualEthernet.performance.vlan.inPriorityQueues.octets.bandwidth.30sec

       unit name = bps
       formula = 8 * ; 8 /"
   ::= {pr1645v2VEthVlanInPQsEntry 70388224}

pr1645v2VEthVlanInPQsOctetsBandwidth1min OBJECT-TYPE
   SYNTAX      Integer32
   MAX-ACCESS  read-only
   STATUS      current
   DESCRIPTION
      "Path: virtualEthernet.performance.vlan.inPriorityQueues.octets.bandwidth.1min

       unit name = bps
       formula = 8 * ; 8 /"
   ::= {pr1645v2VEthVlanInPQsEntry 70390784}

pr1645v2VEthVlanInPQsOctetsBandwidth2min OBJECT-TYPE
   SYNTAX      Integer32
   MAX-ACCESS  read-only
   STATUS      current
   DESCRIPTION
      "Path: virtualEthernet.performance.vlan.inPriorityQueues.octets.bandwidth.2min

       unit name = bps
       formula = 8 * ; 8 /"
   ::= {pr1645v2VEthVlanInPQsEntry 70395904}

pr1645v2VEthVlanInPQsOctetsBandwidth5min OBJECT-TYPE
   SYNTAX      Integer32
   MAX-ACCESS  read-only
   STATUS      current
   DESCRIPTION
      "Path: virtualEthernet.performance.vlan.inPriorityQueues.octets.bandwidth.5min

       unit name = bps
       formula = 8 * ; 8 /"
   ::= {pr1645v2VEthVlanInPQsEntry 70411264}

pr1645v2VEthVlanInPQsH2Performance OBJECT-TYPE
   SYNTAX      SEQUENCE OF Pr1645v2VEthVlanInPQsH2PerformanceEntry
   MAX-ACCESS  not-accessible
   STATUS      current
   DESCRIPTION
      ""
   ::= {pr1645v2VEthVlan 100990976}

pr1645v2VEthVlanInPQsH2PerformanceEntry OBJECT-TYPE
   SYNTAX      Pr1645v2VEthVlanInPQsH2PerformanceEntry
   MAX-ACCESS  not-accessible
   STATUS      current
   DESCRIPTION
      ""
   INDEX      { pr1645v2VEthVlanInPQsH2PerformanceGlobalIx,
                pr1645v2VEthVlanTableIx,
                pr1645v2VEthVlanInPQsTableIx,
                pr1645v2VEthVlanInPQsH2PerformanceTableIx }
   ::= {pr1645v2VEthVlanInPQsH2Performance 1}

Pr1645v2VEthVlanInPQsH2PerformanceEntry ::=
   SEQUENCE
      {
      pr1645v2VEthVlanInPQsH2PerformanceGlobalIx
         GlobalIndex,
      pr1645v2VEthVlanInPQsH2PerformanceTableIx
         TableIndex,
      pr1645v2VEthVlanInPQsH2PerformanceSysUpTime
         TimeTicks,
      pr1645v2VEthVlanInPQsH2PerformanceTotPkts
         Counter64,
      pr1645v2VEthVlanInPQsH2PerformanceDirTxPkts
         Counter64,
      pr1645v2VEthVlanInPQsH2PerformanceQdPkts
         Counter64,
      pr1645v2VEthVlanInPQsH2PerformanceDropPkts
         Counter64,
      pr1645v2VEthVlanInPQsH2PerformanceRDropPkts
         Counter64,
      pr1645v2VEthVlanInPQsH2PerformanceCirTxPkts
         Counter64,
      pr1645v2VEthVlanInPQsH2PerformanceEirTxPkts
         Counter64,
      pr1645v2VEthVlanInPQsH2PerformanceViolTxPkts
         Counter64,
      pr1645v2VEthVlanInPQsH2PerformanceTotOcts
         Counter64,
      pr1645v2VEthVlanInPQsH2PerformanceDirTxOcts
         Counter64,
      pr1645v2VEthVlanInPQsH2PerformanceQdOcts
         Counter64,
      pr1645v2VEthVlanInPQsH2PerformanceDropOcts
         Counter64,
      pr1645v2VEthVlanInPQsH2PerformanceRDropOcts
         Counter64,
      pr1645v2VEthVlanInPQsH2PerformanceCirTxOcts
         Counter64,
      pr1645v2VEthVlanInPQsH2PerformanceEirTxOcts
         Counter64,
      pr1645v2VEthVlanInPQsH2PerformanceViolTxOcts
         Counter64,
      pr1645v2VEthVlanInPQsH2PerformanceBandwidth
         Integer32
      }

pr1645v2VEthVlanInPQsH2PerformanceGlobalIx OBJECT-TYPE
   SYNTAX      GlobalIndex
   MAX-ACCESS  not-accessible
   STATUS      current
   DESCRIPTION
      "The value of the tlsCntTreeGlobalIndex of the MANAGED OBJECT."
   ::= {pr1645v2VEthVlanInPQsH2PerformanceEntry 10}

pr1645v2VEthVlanInPQsH2PerformanceTableIx OBJECT-TYPE
   SYNTAX      TableIndex
   MAX-ACCESS  not-accessible
   STATUS      current
   DESCRIPTION
      ""
   ::= {pr1645v2VEthVlanInPQsH2PerformanceEntry 11}

pr1645v2VEthVlanInPQsH2PerformanceSysUpTime OBJECT-TYPE
   SYNTAX      TimeTicks
   MAX-ACCESS  read-only
   STATUS      current
   DESCRIPTION
      "Path: virtualEthernet.performance.vlan.inPriorityQueues.h2Performance.sysUpTime

       Time in centi-second."
   ::= {pr1645v2VEthVlanInPQsH2PerformanceEntry 16777216}

pr1645v2VEthVlanInPQsH2PerformanceTotPkts OBJECT-TYPE
   SYNTAX      Counter64
   MAX-ACCESS  read-only
   STATUS      current
   DESCRIPTION
      "Path: virtualEthernet.performance.vlan.inPriorityQueues.h2Performance.totalPkts

       64 bit unsigned wrappable counter."
   ::= {pr1645v2VEthVlanInPQsH2PerformanceEntry 234881024}

pr1645v2VEthVlanInPQsH2PerformanceDirTxPkts OBJECT-TYPE
   SYNTAX      Counter64
   MAX-ACCESS  read-only
   STATUS      current
   DESCRIPTION
      "Path: virtualEthernet.performance.vlan.inPriorityQueues.h2Performance.directTxPkts

       64 bit unsigned wrappable counter."
   ::= {pr1645v2VEthVlanInPQsH2PerformanceEntry 33554432}

pr1645v2VEthVlanInPQsH2PerformanceQdPkts OBJECT-TYPE
   SYNTAX      Counter64
   MAX-ACCESS  read-only
   STATUS      current
   DESCRIPTION
      "Path: virtualEthernet.performance.vlan.inPriorityQueues.h2Performance.queuedPkts

       64 bit unsigned wrappable counter."
   ::= {pr1645v2VEthVlanInPQsH2PerformanceEntry 50331648}

pr1645v2VEthVlanInPQsH2PerformanceDropPkts OBJECT-TYPE
   SYNTAX      Counter64
   MAX-ACCESS  read-only
   STATUS      current
   DESCRIPTION
      "Path: virtualEthernet.performance.vlan.inPriorityQueues.h2Performance.droppedPkts

       64 bit unsigned wrappable counter."
   ::= {pr1645v2VEthVlanInPQsH2PerformanceEntry 67108864}

pr1645v2VEthVlanInPQsH2PerformanceRDropPkts OBJECT-TYPE
   SYNTAX      Counter64
   MAX-ACCESS  read-only
   STATUS      current
   DESCRIPTION
      "Path: virtualEthernet.performance.vlan.inPriorityQueues.h2Performance.redDroppedPkts

       64 bit unsigned wrappable counter."
   ::= {pr1645v2VEthVlanInPQsH2PerformanceEntry 201326592}

pr1645v2VEthVlanInPQsH2PerformanceCirTxPkts OBJECT-TYPE
   SYNTAX      Counter64
   MAX-ACCESS  read-only
   STATUS      current
   DESCRIPTION
      "Path: virtualEthernet.performance.vlan.inPriorityQueues.h2Performance.cirTxPkts

       64 bit unsigned wrappable counter."
   ::= {pr1645v2VEthVlanInPQsH2PerformanceEntry 83886080}

pr1645v2VEthVlanInPQsH2PerformanceEirTxPkts OBJECT-TYPE
   SYNTAX      Counter64
   MAX-ACCESS  read-only
   STATUS      current
   DESCRIPTION
      "Path: virtualEthernet.performance.vlan.inPriorityQueues.h2Performance.eirTxPkts

       64 bit unsigned wrappable counter."
   ::= {pr1645v2VEthVlanInPQsH2PerformanceEntry 100663296}

pr1645v2VEthVlanInPQsH2PerformanceViolTxPkts OBJECT-TYPE
   SYNTAX      Counter64
   MAX-ACCESS  read-only
   STATUS      current
   DESCRIPTION
      "Path: virtualEthernet.performance.vlan.inPriorityQueues.h2Performance.violateTxPkts

       64 bit unsigned wrappable counter."
   ::= {pr1645v2VEthVlanInPQsH2PerformanceEntry 301989888}

pr1645v2VEthVlanInPQsH2PerformanceTotOcts OBJECT-TYPE
   SYNTAX      Counter64
   MAX-ACCESS  read-only
   STATUS      current
   DESCRIPTION
      "Path: virtualEthernet.performance.vlan.inPriorityQueues.h2Performance.totalOctets

       64 bit unsigned wrappable counter."
   ::= {pr1645v2VEthVlanInPQsH2PerformanceEntry 251658240}

pr1645v2VEthVlanInPQsH2PerformanceDirTxOcts OBJECT-TYPE
   SYNTAX      Counter64
   MAX-ACCESS  read-only
   STATUS      current
   DESCRIPTION
      "Path: virtualEthernet.performance.vlan.inPriorityQueues.h2Performance.directTxOctets

       64 bit unsigned wrappable counter."
   ::= {pr1645v2VEthVlanInPQsH2PerformanceEntry 117440512}

pr1645v2VEthVlanInPQsH2PerformanceQdOcts OBJECT-TYPE
   SYNTAX      Counter64
   MAX-ACCESS  read-only
   STATUS      current
   DESCRIPTION
      "Path: virtualEthernet.performance.vlan.inPriorityQueues.h2Performance.queuedOctets

       64 bit unsigned wrappable counter."
   ::= {pr1645v2VEthVlanInPQsH2PerformanceEntry 134217728}

pr1645v2VEthVlanInPQsH2PerformanceDropOcts OBJECT-TYPE
   SYNTAX      Counter64
   MAX-ACCESS  read-only
   STATUS      current
   DESCRIPTION
      "Path: virtualEthernet.performance.vlan.inPriorityQueues.h2Performance.droppedOctets

       64 bit unsigned wrappable counter."
   ::= {pr1645v2VEthVlanInPQsH2PerformanceEntry 150994944}

pr1645v2VEthVlanInPQsH2PerformanceRDropOcts OBJECT-TYPE
   SYNTAX      Counter64
   MAX-ACCESS  read-only
   STATUS      current
   DESCRIPTION
      "Path: virtualEthernet.performance.vlan.inPriorityQueues.h2Performance.redDroppedOctets

       64 bit unsigned wrappable counter."
   ::= {pr1645v2VEthVlanInPQsH2PerformanceEntry 218103808}

pr1645v2VEthVlanInPQsH2PerformanceCirTxOcts OBJECT-TYPE
   SYNTAX      Counter64
   MAX-ACCESS  read-only
   STATUS      current
   DESCRIPTION
      "Path: virtualEthernet.performance.vlan.inPriorityQueues.h2Performance.cirTxOctets

       64 bit unsigned wrappable counter."
   ::= {pr1645v2VEthVlanInPQsH2PerformanceEntry 167772160}

pr1645v2VEthVlanInPQsH2PerformanceEirTxOcts OBJECT-TYPE
   SYNTAX      Counter64
   MAX-ACCESS  read-only
   STATUS      current
   DESCRIPTION
      "Path: virtualEthernet.performance.vlan.inPriorityQueues.h2Performance.eirTxOctets

       64 bit unsigned wrappable counter."
   ::= {pr1645v2VEthVlanInPQsH2PerformanceEntry 184549376}

pr1645v2VEthVlanInPQsH2PerformanceViolTxOcts OBJECT-TYPE
   SYNTAX      Counter64
   MAX-ACCESS  read-only
   STATUS      current
   DESCRIPTION
      "Path: virtualEthernet.performance.vlan.inPriorityQueues.h2Performance.violateTxOctets

       64 bit unsigned wrappable counter."
   ::= {pr1645v2VEthVlanInPQsH2PerformanceEntry 318767104}

pr1645v2VEthVlanInPQsH2PerformanceBandwidth OBJECT-TYPE
   SYNTAX      Integer32
   MAX-ACCESS  read-only
   STATUS      current
   DESCRIPTION
      "Path: virtualEthernet.performance.vlan.inPriorityQueues.h2Performance.bandwidth

       unit name = bps
       formula = 8 * ; 8 /"
   ::= {pr1645v2VEthVlanInPQsH2PerformanceEntry 268435456}

pr1645v2VEthVlanInPQsH24Performance OBJECT-TYPE
   SYNTAX      SEQUENCE OF Pr1645v2VEthVlanInPQsH24PerformanceEntry
   MAX-ACCESS  not-accessible
   STATUS      current
   DESCRIPTION
      ""
   ::= {pr1645v2VEthVlan 101056512}

pr1645v2VEthVlanInPQsH24PerformanceEntry OBJECT-TYPE
   SYNTAX      Pr1645v2VEthVlanInPQsH24PerformanceEntry
   MAX-ACCESS  not-accessible
   STATUS      current
   DESCRIPTION
      ""
   INDEX      { pr1645v2VEthVlanInPQsH24PerformanceGlobalIx,
                pr1645v2VEthVlanTableIx,
                pr1645v2VEthVlanInPQsTableIx,
                pr1645v2VEthVlanInPQsH24PerformanceTableIx }
   ::= {pr1645v2VEthVlanInPQsH24Performance 1}

Pr1645v2VEthVlanInPQsH24PerformanceEntry ::=
   SEQUENCE
      {
      pr1645v2VEthVlanInPQsH24PerformanceGlobalIx
         GlobalIndex,
      pr1645v2VEthVlanInPQsH24PerformanceTableIx
         TableIndex,
      pr1645v2VEthVlanInPQsH24PerformanceSysUpTime
         TimeTicks,
      pr1645v2VEthVlanInPQsH24PerformanceTotPkts
         Counter64,
      pr1645v2VEthVlanInPQsH24PerformanceDirTxPkts
         Counter64,
      pr1645v2VEthVlanInPQsH24PerformanceQdPkts
         Counter64,
      pr1645v2VEthVlanInPQsH24PerformanceDropPkts
         Counter64,
      pr1645v2VEthVlanInPQsH24PerformanceRDropPkts
         Counter64,
      pr1645v2VEthVlanInPQsH24PerformanceCirTxPkts
         Counter64,
      pr1645v2VEthVlanInPQsH24PerformanceEirTxPkts
         Counter64,
      pr1645v2VEthVlanInPQsH24PerformanceViolTxPkts
         Counter64,
      pr1645v2VEthVlanInPQsH24PerformanceTotOcts
         Counter64,
      pr1645v2VEthVlanInPQsH24PerformanceDirTxOcts
         Counter64,
      pr1645v2VEthVlanInPQsH24PerformanceQdOcts
         Counter64,
      pr1645v2VEthVlanInPQsH24PerformanceDropOcts
         Counter64,
      pr1645v2VEthVlanInPQsH24PerformanceRDropOcts
         Counter64,
      pr1645v2VEthVlanInPQsH24PerformanceCirTxOcts
         Counter64,
      pr1645v2VEthVlanInPQsH24PerformanceEirTxOcts
         Counter64,
      pr1645v2VEthVlanInPQsH24PerformanceViolTxOcts
         Counter64,
      pr1645v2VEthVlanInPQsH24PerformanceBandwidth
         Integer32
      }

pr1645v2VEthVlanInPQsH24PerformanceGlobalIx OBJECT-TYPE
   SYNTAX      GlobalIndex
   MAX-ACCESS  not-accessible
   STATUS      current
   DESCRIPTION
      "The value of the tlsCntTreeGlobalIndex of the MANAGED OBJECT."
   ::= {pr1645v2VEthVlanInPQsH24PerformanceEntry 10}

pr1645v2VEthVlanInPQsH24PerformanceTableIx OBJECT-TYPE
   SYNTAX      TableIndex
   MAX-ACCESS  not-accessible
   STATUS      current
   DESCRIPTION
      ""
   ::= {pr1645v2VEthVlanInPQsH24PerformanceEntry 11}

pr1645v2VEthVlanInPQsH24PerformanceSysUpTime OBJECT-TYPE
   SYNTAX      TimeTicks
   MAX-ACCESS  read-only
   STATUS      current
   DESCRIPTION
      "Path: virtualEthernet.performance.vlan.inPriorityQueues.h24Performance.sysUpTime

       Time in centi-second."
   ::= {pr1645v2VEthVlanInPQsH24PerformanceEntry 16777216}

pr1645v2VEthVlanInPQsH24PerformanceTotPkts OBJECT-TYPE
   SYNTAX      Counter64
   MAX-ACCESS  read-only
   STATUS      current
   DESCRIPTION
      "Path: virtualEthernet.performance.vlan.inPriorityQueues.h24Performance.totalPkts

       64 bit unsigned wrappable counter."
   ::= {pr1645v2VEthVlanInPQsH24PerformanceEntry 234881024}

pr1645v2VEthVlanInPQsH24PerformanceDirTxPkts OBJECT-TYPE
   SYNTAX      Counter64
   MAX-ACCESS  read-only
   STATUS      current
   DESCRIPTION
      "Path: virtualEthernet.performance.vlan.inPriorityQueues.h24Performance.directTxPkts

       64 bit unsigned wrappable counter."
   ::= {pr1645v2VEthVlanInPQsH24PerformanceEntry 33554432}

pr1645v2VEthVlanInPQsH24PerformanceQdPkts OBJECT-TYPE
   SYNTAX      Counter64
   MAX-ACCESS  read-only
   STATUS      current
   DESCRIPTION
      "Path: virtualEthernet.performance.vlan.inPriorityQueues.h24Performance.queuedPkts

       64 bit unsigned wrappable counter."
   ::= {pr1645v2VEthVlanInPQsH24PerformanceEntry 50331648}

pr1645v2VEthVlanInPQsH24PerformanceDropPkts OBJECT-TYPE
   SYNTAX      Counter64
   MAX-ACCESS  read-only
   STATUS      current
   DESCRIPTION
      "Path: virtualEthernet.performance.vlan.inPriorityQueues.h24Performance.droppedPkts

       64 bit unsigned wrappable counter."
   ::= {pr1645v2VEthVlanInPQsH24PerformanceEntry 67108864}

pr1645v2VEthVlanInPQsH24PerformanceRDropPkts OBJECT-TYPE
   SYNTAX      Counter64
   MAX-ACCESS  read-only
   STATUS      current
   DESCRIPTION
      "Path: virtualEthernet.performance.vlan.inPriorityQueues.h24Performance.redDroppedPkts

       64 bit unsigned wrappable counter."
   ::= {pr1645v2VEthVlanInPQsH24PerformanceEntry 201326592}

pr1645v2VEthVlanInPQsH24PerformanceCirTxPkts OBJECT-TYPE
   SYNTAX      Counter64
   MAX-ACCESS  read-only
   STATUS      current
   DESCRIPTION
      "Path: virtualEthernet.performance.vlan.inPriorityQueues.h24Performance.cirTxPkts

       64 bit unsigned wrappable counter."
   ::= {pr1645v2VEthVlanInPQsH24PerformanceEntry 83886080}

pr1645v2VEthVlanInPQsH24PerformanceEirTxPkts OBJECT-TYPE
   SYNTAX      Counter64
   MAX-ACCESS  read-only
   STATUS      current
   DESCRIPTION
      "Path: virtualEthernet.performance.vlan.inPriorityQueues.h24Performance.eirTxPkts

       64 bit unsigned wrappable counter."
   ::= {pr1645v2VEthVlanInPQsH24PerformanceEntry 100663296}

pr1645v2VEthVlanInPQsH24PerformanceViolTxPkts OBJECT-TYPE
   SYNTAX      Counter64
   MAX-ACCESS  read-only
   STATUS      current
   DESCRIPTION
      "Path: virtualEthernet.performance.vlan.inPriorityQueues.h24Performance.violateTxPkts

       64 bit unsigned wrappable counter."
   ::= {pr1645v2VEthVlanInPQsH24PerformanceEntry 301989888}

pr1645v2VEthVlanInPQsH24PerformanceTotOcts OBJECT-TYPE
   SYNTAX      Counter64
   MAX-ACCESS  read-only
   STATUS      current
   DESCRIPTION
      "Path: virtualEthernet.performance.vlan.inPriorityQueues.h24Performance.totalOctets

       64 bit unsigned wrappable counter."
   ::= {pr1645v2VEthVlanInPQsH24PerformanceEntry 251658240}

pr1645v2VEthVlanInPQsH24PerformanceDirTxOcts OBJECT-TYPE
   SYNTAX      Counter64
   MAX-ACCESS  read-only
   STATUS      current
   DESCRIPTION
      "Path: virtualEthernet.performance.vlan.inPriorityQueues.h24Performance.directTxOctets

       64 bit unsigned wrappable counter."
   ::= {pr1645v2VEthVlanInPQsH24PerformanceEntry 117440512}

pr1645v2VEthVlanInPQsH24PerformanceQdOcts OBJECT-TYPE
   SYNTAX      Counter64
   MAX-ACCESS  read-only
   STATUS      current
   DESCRIPTION
      "Path: virtualEthernet.performance.vlan.inPriorityQueues.h24Performance.queuedOctets

       64 bit unsigned wrappable counter."
   ::= {pr1645v2VEthVlanInPQsH24PerformanceEntry 134217728}

pr1645v2VEthVlanInPQsH24PerformanceDropOcts OBJECT-TYPE
   SYNTAX      Counter64
   MAX-ACCESS  read-only
   STATUS      current
   DESCRIPTION
      "Path: virtualEthernet.performance.vlan.inPriorityQueues.h24Performance.droppedOctets

       64 bit unsigned wrappable counter."
   ::= {pr1645v2VEthVlanInPQsH24PerformanceEntry 150994944}

pr1645v2VEthVlanInPQsH24PerformanceRDropOcts OBJECT-TYPE
   SYNTAX      Counter64
   MAX-ACCESS  read-only
   STATUS      current
   DESCRIPTION
      "Path: virtualEthernet.performance.vlan.inPriorityQueues.h24Performance.redDroppedOctets

       64 bit unsigned wrappable counter."
   ::= {pr1645v2VEthVlanInPQsH24PerformanceEntry 218103808}

pr1645v2VEthVlanInPQsH24PerformanceCirTxOcts OBJECT-TYPE
   SYNTAX      Counter64
   MAX-ACCESS  read-only
   STATUS      current
   DESCRIPTION
      "Path: virtualEthernet.performance.vlan.inPriorityQueues.h24Performance.cirTxOctets

       64 bit unsigned wrappable counter."
   ::= {pr1645v2VEthVlanInPQsH24PerformanceEntry 167772160}

pr1645v2VEthVlanInPQsH24PerformanceEirTxOcts OBJECT-TYPE
   SYNTAX      Counter64
   MAX-ACCESS  read-only
   STATUS      current
   DESCRIPTION
      "Path: virtualEthernet.performance.vlan.inPriorityQueues.h24Performance.eirTxOctets

       64 bit unsigned wrappable counter."
   ::= {pr1645v2VEthVlanInPQsH24PerformanceEntry 184549376}

pr1645v2VEthVlanInPQsH24PerformanceViolTxOcts OBJECT-TYPE
   SYNTAX      Counter64
   MAX-ACCESS  read-only
   STATUS      current
   DESCRIPTION
      "Path: virtualEthernet.performance.vlan.inPriorityQueues.h24Performance.violateTxOctets

       64 bit unsigned wrappable counter."
   ::= {pr1645v2VEthVlanInPQsH24PerformanceEntry 318767104}

pr1645v2VEthVlanInPQsH24PerformanceBandwidth OBJECT-TYPE
   SYNTAX      Integer32
   MAX-ACCESS  read-only
   STATUS      current
   DESCRIPTION
      "Path: virtualEthernet.performance.vlan.inPriorityQueues.h24Performance.bandwidth

       unit name = bps
       formula = 8 * ; 8 /"
   ::= {pr1645v2VEthVlanInPQsH24PerformanceEntry 268435456}

pr1645v2VEthVlanInPQsD7Performance OBJECT-TYPE
   SYNTAX      SEQUENCE OF Pr1645v2VEthVlanInPQsD7PerformanceEntry
   MAX-ACCESS  not-accessible
   STATUS      current
   DESCRIPTION
      ""
   ::= {pr1645v2VEthVlan 101122048}

pr1645v2VEthVlanInPQsD7PerformanceEntry OBJECT-TYPE
   SYNTAX      Pr1645v2VEthVlanInPQsD7PerformanceEntry
   MAX-ACCESS  not-accessible
   STATUS      current
   DESCRIPTION
      ""
   INDEX      { pr1645v2VEthVlanInPQsD7PerformanceGlobalIx,
                pr1645v2VEthVlanTableIx,
                pr1645v2VEthVlanInPQsTableIx,
                pr1645v2VEthVlanInPQsD7PerformanceTableIx }
   ::= {pr1645v2VEthVlanInPQsD7Performance 1}

Pr1645v2VEthVlanInPQsD7PerformanceEntry ::=
   SEQUENCE
      {
      pr1645v2VEthVlanInPQsD7PerformanceGlobalIx
         GlobalIndex,
      pr1645v2VEthVlanInPQsD7PerformanceTableIx
         TableIndex,
      pr1645v2VEthVlanInPQsD7PerformanceSysUpTime
         TimeTicks,
      pr1645v2VEthVlanInPQsD7PerformanceTotPkts
         Counter64,
      pr1645v2VEthVlanInPQsD7PerformanceDirTxPkts
         Counter64,
      pr1645v2VEthVlanInPQsD7PerformanceQdPkts
         Counter64,
      pr1645v2VEthVlanInPQsD7PerformanceDropPkts
         Counter64,
      pr1645v2VEthVlanInPQsD7PerformanceRDropPkts
         Counter64,
      pr1645v2VEthVlanInPQsD7PerformanceCirTxPkts
         Counter64,
      pr1645v2VEthVlanInPQsD7PerformanceEirTxPkts
         Counter64,
      pr1645v2VEthVlanInPQsD7PerformanceViolTxPkts
         Counter64,
      pr1645v2VEthVlanInPQsD7PerformanceTotOcts
         Counter64,
      pr1645v2VEthVlanInPQsD7PerformanceDirTxOcts
         Counter64,
      pr1645v2VEthVlanInPQsD7PerformanceQdOcts
         Counter64,
      pr1645v2VEthVlanInPQsD7PerformanceDropOcts
         Counter64,
      pr1645v2VEthVlanInPQsD7PerformanceRDropOcts
         Counter64,
      pr1645v2VEthVlanInPQsD7PerformanceCirTxOcts
         Counter64,
      pr1645v2VEthVlanInPQsD7PerformanceEirTxOcts
         Counter64,
      pr1645v2VEthVlanInPQsD7PerformanceViolTxOcts
         Counter64,
      pr1645v2VEthVlanInPQsD7PerformanceBandwidth
         Integer32
      }

pr1645v2VEthVlanInPQsD7PerformanceGlobalIx OBJECT-TYPE
   SYNTAX      GlobalIndex
   MAX-ACCESS  not-accessible
   STATUS      current
   DESCRIPTION
      "The value of the tlsCntTreeGlobalIndex of the MANAGED OBJECT."
   ::= {pr1645v2VEthVlanInPQsD7PerformanceEntry 10}

pr1645v2VEthVlanInPQsD7PerformanceTableIx OBJECT-TYPE
   SYNTAX      TableIndex
   MAX-ACCESS  not-accessible
   STATUS      current
   DESCRIPTION
      ""
   ::= {pr1645v2VEthVlanInPQsD7PerformanceEntry 11}

pr1645v2VEthVlanInPQsD7PerformanceSysUpTime OBJECT-TYPE
   SYNTAX      TimeTicks
   MAX-ACCESS  read-only
   STATUS      current
   DESCRIPTION
      "Path: virtualEthernet.performance.vlan.inPriorityQueues.d7Performance.sysUpTime

       Time in centi-second."
   ::= {pr1645v2VEthVlanInPQsD7PerformanceEntry 16777216}

pr1645v2VEthVlanInPQsD7PerformanceTotPkts OBJECT-TYPE
   SYNTAX      Counter64
   MAX-ACCESS  read-only
   STATUS      current
   DESCRIPTION
      "Path: virtualEthernet.performance.vlan.inPriorityQueues.d7Performance.totalPkts

       64 bit unsigned wrappable counter."
   ::= {pr1645v2VEthVlanInPQsD7PerformanceEntry 234881024}

pr1645v2VEthVlanInPQsD7PerformanceDirTxPkts OBJECT-TYPE
   SYNTAX      Counter64
   MAX-ACCESS  read-only
   STATUS      current
   DESCRIPTION
      "Path: virtualEthernet.performance.vlan.inPriorityQueues.d7Performance.directTxPkts

       64 bit unsigned wrappable counter."
   ::= {pr1645v2VEthVlanInPQsD7PerformanceEntry 33554432}

pr1645v2VEthVlanInPQsD7PerformanceQdPkts OBJECT-TYPE
   SYNTAX      Counter64
   MAX-ACCESS  read-only
   STATUS      current
   DESCRIPTION
      "Path: virtualEthernet.performance.vlan.inPriorityQueues.d7Performance.queuedPkts

       64 bit unsigned wrappable counter."
   ::= {pr1645v2VEthVlanInPQsD7PerformanceEntry 50331648}

pr1645v2VEthVlanInPQsD7PerformanceDropPkts OBJECT-TYPE
   SYNTAX      Counter64
   MAX-ACCESS  read-only
   STATUS      current
   DESCRIPTION
      "Path: virtualEthernet.performance.vlan.inPriorityQueues.d7Performance.droppedPkts

       64 bit unsigned wrappable counter."
   ::= {pr1645v2VEthVlanInPQsD7PerformanceEntry 67108864}

pr1645v2VEthVlanInPQsD7PerformanceRDropPkts OBJECT-TYPE
   SYNTAX      Counter64
   MAX-ACCESS  read-only
   STATUS      current
   DESCRIPTION
      "Path: virtualEthernet.performance.vlan.inPriorityQueues.d7Performance.redDroppedPkts

       64 bit unsigned wrappable counter."
   ::= {pr1645v2VEthVlanInPQsD7PerformanceEntry 201326592}

pr1645v2VEthVlanInPQsD7PerformanceCirTxPkts OBJECT-TYPE
   SYNTAX      Counter64
   MAX-ACCESS  read-only
   STATUS      current
   DESCRIPTION
      "Path: virtualEthernet.performance.vlan.inPriorityQueues.d7Performance.cirTxPkts

       64 bit unsigned wrappable counter."
   ::= {pr1645v2VEthVlanInPQsD7PerformanceEntry 83886080}

pr1645v2VEthVlanInPQsD7PerformanceEirTxPkts OBJECT-TYPE
   SYNTAX      Counter64
   MAX-ACCESS  read-only
   STATUS      current
   DESCRIPTION
      "Path: virtualEthernet.performance.vlan.inPriorityQueues.d7Performance.eirTxPkts

       64 bit unsigned wrappable counter."
   ::= {pr1645v2VEthVlanInPQsD7PerformanceEntry 100663296}

pr1645v2VEthVlanInPQsD7PerformanceViolTxPkts OBJECT-TYPE
   SYNTAX      Counter64
   MAX-ACCESS  read-only
   STATUS      current
   DESCRIPTION
      "Path: virtualEthernet.performance.vlan.inPriorityQueues.d7Performance.violateTxPkts

       64 bit unsigned wrappable counter."
   ::= {pr1645v2VEthVlanInPQsD7PerformanceEntry 301989888}

pr1645v2VEthVlanInPQsD7PerformanceTotOcts OBJECT-TYPE
   SYNTAX      Counter64
   MAX-ACCESS  read-only
   STATUS      current
   DESCRIPTION
      "Path: virtualEthernet.performance.vlan.inPriorityQueues.d7Performance.totalOctets

       64 bit unsigned wrappable counter."
   ::= {pr1645v2VEthVlanInPQsD7PerformanceEntry 251658240}

pr1645v2VEthVlanInPQsD7PerformanceDirTxOcts OBJECT-TYPE
   SYNTAX      Counter64
   MAX-ACCESS  read-only
   STATUS      current
   DESCRIPTION
      "Path: virtualEthernet.performance.vlan.inPriorityQueues.d7Performance.directTxOctets

       64 bit unsigned wrappable counter."
   ::= {pr1645v2VEthVlanInPQsD7PerformanceEntry 117440512}

pr1645v2VEthVlanInPQsD7PerformanceQdOcts OBJECT-TYPE
   SYNTAX      Counter64
   MAX-ACCESS  read-only
   STATUS      current
   DESCRIPTION
      "Path: virtualEthernet.performance.vlan.inPriorityQueues.d7Performance.queuedOctets

       64 bit unsigned wrappable counter."
   ::= {pr1645v2VEthVlanInPQsD7PerformanceEntry 134217728}

pr1645v2VEthVlanInPQsD7PerformanceDropOcts OBJECT-TYPE
   SYNTAX      Counter64
   MAX-ACCESS  read-only
   STATUS      current
   DESCRIPTION
      "Path: virtualEthernet.performance.vlan.inPriorityQueues.d7Performance.droppedOctets

       64 bit unsigned wrappable counter."
   ::= {pr1645v2VEthVlanInPQsD7PerformanceEntry 150994944}

pr1645v2VEthVlanInPQsD7PerformanceRDropOcts OBJECT-TYPE
   SYNTAX      Counter64
   MAX-ACCESS  read-only
   STATUS      current
   DESCRIPTION
      "Path: virtualEthernet.performance.vlan.inPriorityQueues.d7Performance.redDroppedOctets

       64 bit unsigned wrappable counter."
   ::= {pr1645v2VEthVlanInPQsD7PerformanceEntry 218103808}

pr1645v2VEthVlanInPQsD7PerformanceCirTxOcts OBJECT-TYPE
   SYNTAX      Counter64
   MAX-ACCESS  read-only
   STATUS      current
   DESCRIPTION
      "Path: virtualEthernet.performance.vlan.inPriorityQueues.d7Performance.cirTxOctets

       64 bit unsigned wrappable counter."
   ::= {pr1645v2VEthVlanInPQsD7PerformanceEntry 167772160}

pr1645v2VEthVlanInPQsD7PerformanceEirTxOcts OBJECT-TYPE
   SYNTAX      Counter64
   MAX-ACCESS  read-only
   STATUS      current
   DESCRIPTION
      "Path: virtualEthernet.performance.vlan.inPriorityQueues.d7Performance.eirTxOctets

       64 bit unsigned wrappable counter."
   ::= {pr1645v2VEthVlanInPQsD7PerformanceEntry 184549376}

pr1645v2VEthVlanInPQsD7PerformanceViolTxOcts OBJECT-TYPE
   SYNTAX      Counter64
   MAX-ACCESS  read-only
   STATUS      current
   DESCRIPTION
      "Path: virtualEthernet.performance.vlan.inPriorityQueues.d7Performance.violateTxOctets

       64 bit unsigned wrappable counter."
   ::= {pr1645v2VEthVlanInPQsD7PerformanceEntry 318767104}

pr1645v2VEthVlanInPQsD7PerformanceBandwidth OBJECT-TYPE
   SYNTAX      Integer32
   MAX-ACCESS  read-only
   STATUS      current
   DESCRIPTION
      "Path: virtualEthernet.performance.vlan.inPriorityQueues.d7Performance.bandwidth

       unit name = bps
       formula = 8 * ; 8 /"
   ::= {pr1645v2VEthVlanInPQsD7PerformanceEntry 268435456}

pr1645v2VEthVlanOutPQs OBJECT-TYPE
   SYNTAX      SEQUENCE OF Pr1645v2VEthVlanOutPQsEntry
   MAX-ACCESS  not-accessible
   STATUS      current
   DESCRIPTION
      ""
   ::= {pr1645v2VEthVlan 83886080}

pr1645v2VEthVlanOutPQsEntry OBJECT-TYPE
   SYNTAX      Pr1645v2VEthVlanOutPQsEntry
   MAX-ACCESS  not-accessible
   STATUS      current
   DESCRIPTION
      ""
   INDEX      { pr1645v2VEthVlanOutPQsGlobalIx,
                pr1645v2VEthVlanTableIx,
                pr1645v2VEthVlanOutPQsTableIx }
   ::= {pr1645v2VEthVlanOutPQs 1}

Pr1645v2VEthVlanOutPQsEntry ::=
   SEQUENCE
      {
      pr1645v2VEthVlanOutPQsGlobalIx
         GlobalIndex,
      pr1645v2VEthVlanOutPQsTableIx
         TableIndex,
      pr1645v2VEthVlanOutPQsName
         INTEGER,
      pr1645v2VEthVlanOutPQsLength
         Integer32,
      pr1645v2VEthVlanOutPQsOctetLength
         Integer32,
      pr1645v2VEthVlanOutPQsRedLength
         Integer32,
      pr1645v2VEthVlanOutPQsPacketsTotal
         Counter64,
      pr1645v2VEthVlanOutPQsPacketsDirectTx
         Counter64,
      pr1645v2VEthVlanOutPQsPacketsQueued
         Counter64,
      pr1645v2VEthVlanOutPQsPacketsDropped
         Counter64,
      pr1645v2VEthVlanOutPQsPacketsRedDropped
         Counter64,
      pr1645v2VEthVlanOutPQsPacketsCirTx
         Counter64,
      pr1645v2VEthVlanOutPQsPacketsEirTx
         Counter64,
      pr1645v2VEthVlanOutPQsPacketsViolateTx
         Counter64,
      pr1645v2VEthVlanOutPQsOctetsTotal
         Counter64,
      pr1645v2VEthVlanOutPQsOctetsDirectTx
         Counter64,
      pr1645v2VEthVlanOutPQsOctetsQueued
         Counter64,
      pr1645v2VEthVlanOutPQsOctetsDropped
         Counter64,
      pr1645v2VEthVlanOutPQsOctetsRedDropped
         Counter64,
      pr1645v2VEthVlanOutPQsOctetsCirTx
         Counter64,
      pr1645v2VEthVlanOutPQsOctetsEirTx
         Counter64,
      pr1645v2VEthVlanOutPQsOctetsViolateTx
         Counter64,
      pr1645v2VEthVlanOutPQsOctetsBandwidth15sec
         Integer32,
      pr1645v2VEthVlanOutPQsOctetsBandwidth30sec
         Integer32,
      pr1645v2VEthVlanOutPQsOctetsBandwidth1min
         Integer32,
      pr1645v2VEthVlanOutPQsOctetsBandwidth2min
         Integer32,
      pr1645v2VEthVlanOutPQsOctetsBandwidth5min
         Integer32
      }

pr1645v2VEthVlanOutPQsGlobalIx OBJECT-TYPE
   SYNTAX      GlobalIndex
   MAX-ACCESS  not-accessible
   STATUS      current
   DESCRIPTION
      "The value of the tlsCntTreeGlobalIndex of the MANAGED OBJECT."
   ::= {pr1645v2VEthVlanOutPQsEntry 10}

pr1645v2VEthVlanOutPQsTableIx OBJECT-TYPE
   SYNTAX      TableIndex
   MAX-ACCESS  not-accessible
   STATUS      current
   DESCRIPTION
      ""
   ::= {pr1645v2VEthVlanOutPQsEntry 11}

pr1645v2VEthVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2VEthVlanOutPQsEntry 16777216}

pr1645v2VEthVlanOutPQsLength OBJECT-TYPE
   SYNTAX      Integer32
   MAX-ACCESS  read-only
   STATUS      current
   DESCRIPTION
      "Path: virtualEthernet.performance.vlan.outPriorityQueues.length"
   ::= {pr1645v2VEthVlanOutPQsEntry 33554432}

pr1645v2VEthVlanOutPQsOctetLength OBJECT-TYPE
   SYNTAX      Integer32
   MAX-ACCESS  read-only
   STATUS      current
   DESCRIPTION
      "Path: virtualEthernet.performance.vlan.outPriorityQueues.octetLength"
   ::= {pr1645v2VEthVlanOutPQsEntry 150994944}

pr1645v2VEthVlanOutPQsRedLength OBJECT-TYPE
   SYNTAX      Integer32
   MAX-ACCESS  read-only
   STATUS      current
   DESCRIPTION
      "Path: virtualEthernet.performance.vlan.outPriorityQueues.redLength"
   ::= {pr1645v2VEthVlanOutPQsEntry 134217728}

pr1645v2VEthVlanOutPQsPacketsTotal OBJECT-TYPE
   SYNTAX      Counter64
   MAX-ACCESS  read-only
   STATUS      current
   DESCRIPTION
      "Path: virtualEthernet.performance.vlan.outPriorityQueues.packets.total

       64 bit unsigned wrappable counter."
   ::= {pr1645v2VEthVlanOutPQsEntry 50790400}

pr1645v2VEthVlanOutPQsPacketsDirectTx OBJECT-TYPE
   SYNTAX      Counter64
   MAX-ACCESS  read-only
   STATUS      current
   DESCRIPTION
      "Path: virtualEthernet.performance.vlan.outPriorityQueues.packets.directTx

       64 bit unsigned wrappable counter."
   ::= {pr1645v2VEthVlanOutPQsEntry 50397184}

pr1645v2VEthVlanOutPQsPacketsQueued OBJECT-TYPE
   SYNTAX      Counter64
   MAX-ACCESS  read-only
   STATUS      current
   DESCRIPTION
      "Path: virtualEthernet.performance.vlan.outPriorityQueues.packets.queued

       64 bit unsigned wrappable counter."
   ::= {pr1645v2VEthVlanOutPQsEntry 50462720}

pr1645v2VEthVlanOutPQsPacketsDropped OBJECT-TYPE
   SYNTAX      Counter64
   MAX-ACCESS  read-only
   STATUS      current
   DESCRIPTION
      "Path: virtualEthernet.performance.vlan.outPriorityQueues.packets.dropped

       64 bit unsigned wrappable counter."
   ::= {pr1645v2VEthVlanOutPQsEntry 50528256}

pr1645v2VEthVlanOutPQsPacketsRedDropped OBJECT-TYPE
   SYNTAX      Counter64
   MAX-ACCESS  read-only
   STATUS      current
   DESCRIPTION
      "Path: virtualEthernet.performance.vlan.outPriorityQueues.packets.redDropped

       64 bit unsigned wrappable counter."
   ::= {pr1645v2VEthVlanOutPQsEntry 50724864}

pr1645v2VEthVlanOutPQsPacketsCirTx OBJECT-TYPE
   SYNTAX      Counter64
   MAX-ACCESS  read-only
   STATUS      current
   DESCRIPTION
      "Path: virtualEthernet.performance.vlan.outPriorityQueues.packets.cirTx

       64 bit unsigned wrappable counter."
   ::= {pr1645v2VEthVlanOutPQsEntry 50593792}

pr1645v2VEthVlanOutPQsPacketsEirTx OBJECT-TYPE
   SYNTAX      Counter64
   MAX-ACCESS  read-only
   STATUS      current
   DESCRIPTION
      "Path: virtualEthernet.performance.vlan.outPriorityQueues.packets.eirTx

       64 bit unsigned wrappable counter."
   ::= {pr1645v2VEthVlanOutPQsEntry 50659328}

pr1645v2VEthVlanOutPQsPacketsViolateTx OBJECT-TYPE
   SYNTAX      Counter64
   MAX-ACCESS  read-only
   STATUS      current
   DESCRIPTION
      "Path: virtualEthernet.performance.vlan.outPriorityQueues.packets.violateTx

       64 bit unsigned wrappable counter."
   ::= {pr1645v2VEthVlanOutPQsEntry 50855936}

pr1645v2VEthVlanOutPQsOctetsTotal OBJECT-TYPE
   SYNTAX      Counter64
   MAX-ACCESS  read-only
   STATUS      current
   DESCRIPTION
      "Path: virtualEthernet.performance.vlan.outPriorityQueues.octets.total

       64 bit unsigned wrappable counter."
   ::= {pr1645v2VEthVlanOutPQsEntry 67567616}

pr1645v2VEthVlanOutPQsOctetsDirectTx OBJECT-TYPE
   SYNTAX      Counter64
   MAX-ACCESS  read-only
   STATUS      current
   DESCRIPTION
      "Path: virtualEthernet.performance.vlan.outPriorityQueues.octets.directTx

       64 bit unsigned wrappable counter."
   ::= {pr1645v2VEthVlanOutPQsEntry 67174400}

pr1645v2VEthVlanOutPQsOctetsQueued OBJECT-TYPE
   SYNTAX      Counter64
   MAX-ACCESS  read-only
   STATUS      current
   DESCRIPTION
      "Path: virtualEthernet.performance.vlan.outPriorityQueues.octets.queued

       64 bit unsigned wrappable counter."
   ::= {pr1645v2VEthVlanOutPQsEntry 67239936}

pr1645v2VEthVlanOutPQsOctetsDropped OBJECT-TYPE
   SYNTAX      Counter64
   MAX-ACCESS  read-only
   STATUS      current
   DESCRIPTION
      "Path: virtualEthernet.performance.vlan.outPriorityQueues.octets.dropped

       64 bit unsigned wrappable counter."
   ::= {pr1645v2VEthVlanOutPQsEntry 67305472}

pr1645v2VEthVlanOutPQsOctetsRedDropped OBJECT-TYPE
   SYNTAX      Counter64
   MAX-ACCESS  read-only
   STATUS      current
   DESCRIPTION
      "Path: virtualEthernet.performance.vlan.outPriorityQueues.octets.redDropped

       64 bit unsigned wrappable counter."
   ::= {pr1645v2VEthVlanOutPQsEntry 67502080}

pr1645v2VEthVlanOutPQsOctetsCirTx OBJECT-TYPE
   SYNTAX      Counter64
   MAX-ACCESS  read-only
   STATUS      current
   DESCRIPTION
      "Path: virtualEthernet.performance.vlan.outPriorityQueues.octets.cirTx

       64 bit unsigned wrappable counter."
   ::= {pr1645v2VEthVlanOutPQsEntry 67371008}

pr1645v2VEthVlanOutPQsOctetsEirTx OBJECT-TYPE
   SYNTAX      Counter64
   MAX-ACCESS  read-only
   STATUS      current
   DESCRIPTION
      "Path: virtualEthernet.performance.vlan.outPriorityQueues.octets.eirTx

       64 bit unsigned wrappable counter."
   ::= {pr1645v2VEthVlanOutPQsEntry 67436544}

pr1645v2VEthVlanOutPQsOctetsViolateTx OBJECT-TYPE
   SYNTAX      Counter64
   MAX-ACCESS  read-only
   STATUS      current
   DESCRIPTION
      "Path: virtualEthernet.performance.vlan.outPriorityQueues.octets.violateTx

       64 bit unsigned wrappable counter."
   ::= {pr1645v2VEthVlanOutPQsEntry 67633152}

pr1645v2VEthVlanOutPQsOctetsBandwidth15sec OBJECT-TYPE
   SYNTAX      Integer32
   MAX-ACCESS  read-only
   STATUS      current
   DESCRIPTION
      "Path: virtualEthernet.performance.vlan.outPriorityQueues.octets.bandwidth.15sec

       unit name = bps
       formula = 8 * ; 8 /"
   ::= {pr1645v2VEthVlanOutPQsEntry 70386944}

pr1645v2VEthVlanOutPQsOctetsBandwidth30sec OBJECT-TYPE
   SYNTAX      Integer32
   MAX-ACCESS  read-only
   STATUS      current
   DESCRIPTION
      "Path: virtualEthernet.performance.vlan.outPriorityQueues.octets.bandwidth.30sec

       unit name = bps
       formula = 8 * ; 8 /"
   ::= {pr1645v2VEthVlanOutPQsEntry 70388224}

pr1645v2VEthVlanOutPQsOctetsBandwidth1min OBJECT-TYPE
   SYNTAX      Integer32
   MAX-ACCESS  read-only
   STATUS      current
   DESCRIPTION
      "Path: virtualEthernet.performance.vlan.outPriorityQueues.octets.bandwidth.1min

       unit name = bps
       formula = 8 * ; 8 /"
   ::= {pr1645v2VEthVlanOutPQsEntry 70390784}

pr1645v2VEthVlanOutPQsOctetsBandwidth2min OBJECT-TYPE
   SYNTAX      Integer32
   MAX-ACCESS  read-only
   STATUS      current
   DESCRIPTION
      "Path: virtualEthernet.performance.vlan.outPriorityQueues.octets.bandwidth.2min

       unit name = bps
       formula = 8 * ; 8 /"
   ::= {pr1645v2VEthVlanOutPQsEntry 70395904}

pr1645v2VEthVlanOutPQsOctetsBandwidth5min OBJECT-TYPE
   SYNTAX      Integer32
   MAX-ACCESS  read-only
   STATUS      current
   DESCRIPTION
      "Path: virtualEthernet.performance.vlan.outPriorityQueues.octets.bandwidth.5min

       unit name = bps
       formula = 8 * ; 8 /"
   ::= {pr1645v2VEthVlanOutPQsEntry 70411264}

pr1645v2VEthVlanOutPQsH2Performance OBJECT-TYPE
   SYNTAX      SEQUENCE OF Pr1645v2VEthVlanOutPQsH2PerformanceEntry
   MAX-ACCESS  not-accessible
   STATUS      current
   DESCRIPTION
      ""
   ::= {pr1645v2VEthVlan 84213760}

pr1645v2VEthVlanOutPQsH2PerformanceEntry OBJECT-TYPE
   SYNTAX      Pr1645v2VEthVlanOutPQsH2PerformanceEntry
   MAX-ACCESS  not-accessible
   STATUS      current
   DESCRIPTION
      ""
   INDEX      { pr1645v2VEthVlanOutPQsH2PerformanceGlobalIx,
                pr1645v2VEthVlanTableIx,
                pr1645v2VEthVlanOutPQsTableIx,
                pr1645v2VEthVlanOutPQsH2PerformanceTableIx }
   ::= {pr1645v2VEthVlanOutPQsH2Performance 1}

Pr1645v2VEthVlanOutPQsH2PerformanceEntry ::=
   SEQUENCE
      {
      pr1645v2VEthVlanOutPQsH2PerformanceGlobalIx
         GlobalIndex,
      pr1645v2VEthVlanOutPQsH2PerformanceTableIx
         TableIndex,
      pr1645v2VEthVlanOutPQsH2PerformanceSysUpTime
         TimeTicks,
      pr1645v2VEthVlanOutPQsH2PerformanceTotPkts
         Counter64,
      pr1645v2VEthVlanOutPQsH2PerformanceDirTxPkts
         Counter64,
      pr1645v2VEthVlanOutPQsH2PerformanceQdPkts
         Counter64,
      pr1645v2VEthVlanOutPQsH2PerformanceDropPkts
         Counter64,
      pr1645v2VEthVlanOutPQsH2PerformanceRDropPkts
         Counter64,
      pr1645v2VEthVlanOutPQsH2PerformanceCirTxPkts
         Counter64,
      pr1645v2VEthVlanOutPQsH2PerformanceEirTxPkts
         Counter64,
      pr1645v2VEthVlanOutPQsH2PerformanceViolTxPkts
         Counter64,
      pr1645v2VEthVlanOutPQsH2PerformanceTotOcts
         Counter64,
      pr1645v2VEthVlanOutPQsH2PerformanceDirTxOcts
         Counter64,
      pr1645v2VEthVlanOutPQsH2PerformanceQdOcts
         Counter64,
      pr1645v2VEthVlanOutPQsH2PerformanceDropOcts
         Counter64,
      pr1645v2VEthVlanOutPQsH2PerformanceRDropOcts
         Counter64,
      pr1645v2VEthVlanOutPQsH2PerformanceCirTxOcts
         Counter64,
      pr1645v2VEthVlanOutPQsH2PerformanceEirTxOcts
         Counter64,
      pr1645v2VEthVlanOutPQsH2PerformanceViolTxOcts
         Counter64,
      pr1645v2VEthVlanOutPQsH2PerformanceBandwidth
         Integer32
      }

pr1645v2VEthVlanOutPQsH2PerformanceGlobalIx OBJECT-TYPE
   SYNTAX      GlobalIndex
   MAX-ACCESS  not-accessible
   STATUS      current
   DESCRIPTION
      "The value of the tlsCntTreeGlobalIndex of the MANAGED OBJECT."
   ::= {pr1645v2VEthVlanOutPQsH2PerformanceEntry 10}

pr1645v2VEthVlanOutPQsH2PerformanceTableIx OBJECT-TYPE
   SYNTAX      TableIndex
   MAX-ACCESS  not-accessible
   STATUS      current
   DESCRIPTION
      ""
   ::= {pr1645v2VEthVlanOutPQsH2PerformanceEntry 11}

pr1645v2VEthVlanOutPQsH2PerformanceSysUpTime OBJECT-TYPE
   SYNTAX      TimeTicks
   MAX-ACCESS  read-only
   STATUS      current
   DESCRIPTION
      "Path: virtualEthernet.performance.vlan.outPriorityQueues.h2Performance.sysUpTime

       Time in centi-second."
   ::= {pr1645v2VEthVlanOutPQsH2PerformanceEntry 16777216}

pr1645v2VEthVlanOutPQsH2PerformanceTotPkts OBJECT-TYPE
   SYNTAX      Counter64
   MAX-ACCESS  read-only
   STATUS      current
   DESCRIPTION
      "Path: virtualEthernet.performance.vlan.outPriorityQueues.h2Performance.totalPkts

       64 bit unsigned wrappable counter."
   ::= {pr1645v2VEthVlanOutPQsH2PerformanceEntry 234881024}

pr1645v2VEthVlanOutPQsH2PerformanceDirTxPkts OBJECT-TYPE
   SYNTAX      Counter64
   MAX-ACCESS  read-only
   STATUS      current
   DESCRIPTION
      "Path: virtualEthernet.performance.vlan.outPriorityQueues.h2Performance.directTxPkts

       64 bit unsigned wrappable counter."
   ::= {pr1645v2VEthVlanOutPQsH2PerformanceEntry 33554432}

pr1645v2VEthVlanOutPQsH2PerformanceQdPkts OBJECT-TYPE
   SYNTAX      Counter64
   MAX-ACCESS  read-only
   STATUS      current
   DESCRIPTION
      "Path: virtualEthernet.performance.vlan.outPriorityQueues.h2Performance.queuedPkts

       64 bit unsigned wrappable counter."
   ::= {pr1645v2VEthVlanOutPQsH2PerformanceEntry 50331648}

pr1645v2VEthVlanOutPQsH2PerformanceDropPkts OBJECT-TYPE
   SYNTAX      Counter64
   MAX-ACCESS  read-only
   STATUS      current
   DESCRIPTION
      "Path: virtualEthernet.performance.vlan.outPriorityQueues.h2Performance.droppedPkts

       64 bit unsigned wrappable counter."
   ::= {pr1645v2VEthVlanOutPQsH2PerformanceEntry 67108864}

pr1645v2VEthVlanOutPQsH2PerformanceRDropPkts OBJECT-TYPE
   SYNTAX      Counter64
   MAX-ACCESS  read-only
   STATUS      current
   DESCRIPTION
      "Path: virtualEthernet.performance.vlan.outPriorityQueues.h2Performance.redDroppedPkts

       64 bit unsigned wrappable counter."
   ::= {pr1645v2VEthVlanOutPQsH2PerformanceEntry 201326592}

pr1645v2VEthVlanOutPQsH2PerformanceCirTxPkts OBJECT-TYPE
   SYNTAX      Counter64
   MAX-ACCESS  read-only
   STATUS      current
   DESCRIPTION
      "Path: virtualEthernet.performance.vlan.outPriorityQueues.h2Performance.cirTxPkts

       64 bit unsigned wrappable counter."
   ::= {pr1645v2VEthVlanOutPQsH2PerformanceEntry 83886080}

pr1645v2VEthVlanOutPQsH2PerformanceEirTxPkts OBJECT-TYPE
   SYNTAX      Counter64
   MAX-ACCESS  read-only
   STATUS      current
   DESCRIPTION
      "Path: virtualEthernet.performance.vlan.outPriorityQueues.h2Performance.eirTxPkts

       64 bit unsigned wrappable counter."
   ::= {pr1645v2VEthVlanOutPQsH2PerformanceEntry 100663296}

pr1645v2VEthVlanOutPQsH2PerformanceViolTxPkts OBJECT-TYPE
   SYNTAX      Counter64
   MAX-ACCESS  read-only
   STATUS      current
   DESCRIPTION
      "Path: virtualEthernet.performance.vlan.outPriorityQueues.h2Performance.violateTxPkts

       64 bit unsigned wrappable counter."
   ::= {pr1645v2VEthVlanOutPQsH2PerformanceEntry 301989888}

pr1645v2VEthVlanOutPQsH2PerformanceTotOcts OBJECT-TYPE
   SYNTAX      Counter64
   MAX-ACCESS  read-only
   STATUS      current
   DESCRIPTION
      "Path: virtualEthernet.performance.vlan.outPriorityQueues.h2Performance.totalOctets

       64 bit unsigned wrappable counter."
   ::= {pr1645v2VEthVlanOutPQsH2PerformanceEntry 251658240}

pr1645v2VEthVlanOutPQsH2PerformanceDirTxOcts OBJECT-TYPE
   SYNTAX      Counter64
   MAX-ACCESS  read-only
   STATUS      current
   DESCRIPTION
      "Path: virtualEthernet.performance.vlan.outPriorityQueues.h2Performance.directTxOctets

       64 bit unsigned wrappable counter."
   ::= {pr1645v2VEthVlanOutPQsH2PerformanceEntry 117440512}

pr1645v2VEthVlanOutPQsH2PerformanceQdOcts OBJECT-TYPE
   SYNTAX      Counter64
   MAX-ACCESS  read-only
   STATUS      current
   DESCRIPTION
      "Path: virtualEthernet.performance.vlan.outPriorityQueues.h2Performance.queuedOctets

       64 bit unsigned wrappable counter."
   ::= {pr1645v2VEthVlanOutPQsH2PerformanceEntry 134217728}

pr1645v2VEthVlanOutPQsH2PerformanceDropOcts OBJECT-TYPE
   SYNTAX      Counter64
   MAX-ACCESS  read-only
   STATUS      current
   DESCRIPTION
      "Path: virtualEthernet.performance.vlan.outPriorityQueues.h2Performance.droppedOctets

       64 bit unsigned wrappable counter."
   ::= {pr1645v2VEthVlanOutPQsH2PerformanceEntry 150994944}

pr1645v2VEthVlanOutPQsH2PerformanceRDropOcts OBJECT-TYPE
   SYNTAX      Counter64
   MAX-ACCESS  read-only
   STATUS      current
   DESCRIPTION
      "Path: virtualEthernet.performance.vlan.outPriorityQueues.h2Performance.redDroppedOctets

       64 bit unsigned wrappable counter."
   ::= {pr1645v2VEthVlanOutPQsH2PerformanceEntry 218103808}

pr1645v2VEthVlanOutPQsH2PerformanceCirTxOcts OBJECT-TYPE
   SYNTAX      Counter64
   MAX-ACCESS  read-only
   STATUS      current
   DESCRIPTION
      "Path: virtualEthernet.performance.vlan.outPriorityQueues.h2Performance.cirTxOctets

       64 bit unsigned wrappable counter."
   ::= {pr1645v2VEthVlanOutPQsH2PerformanceEntry 167772160}

pr1645v2VEthVlanOutPQsH2PerformanceEirTxOcts OBJECT-TYPE
   SYNTAX      Counter64
   MAX-ACCESS  read-only
   STATUS      current
   DESCRIPTION
      "Path: virtualEthernet.performance.vlan.outPriorityQueues.h2Performance.eirTxOctets

       64 bit unsigned wrappable counter."
   ::= {pr1645v2VEthVlanOutPQsH2PerformanceEntry 184549376}

pr1645v2VEthVlanOutPQsH2PerformanceViolTxOcts OBJECT-TYPE
   SYNTAX      Counter64
   MAX-ACCESS  read-only
   STATUS      current
   DESCRIPTION
      "Path: virtualEthernet.performance.vlan.outPriorityQueues.h2Performance.violateTxOctets

       64 bit unsigned wrappable counter."
   ::= {pr1645v2VEthVlanOutPQsH2PerformanceEntry 318767104}

pr1645v2VEthVlanOutPQsH2PerformanceBandwidth OBJECT-TYPE
   SYNTAX      Integer32
   MAX-ACCESS  read-only
   STATUS      current
   DESCRIPTION
      "Path: virtualEthernet.performance.vlan.outPriorityQueues.h2Performance.bandwidth

       unit name = bps
       formula = 8 * ; 8 /"
   ::= {pr1645v2VEthVlanOutPQsH2PerformanceEntry 268435456}

pr1645v2VEthVlanOutPQsH24Performance OBJECT-TYPE
   SYNTAX      SEQUENCE OF Pr1645v2VEthVlanOutPQsH24PerformanceEntry
   MAX-ACCESS  not-accessible
   STATUS      current
   DESCRIPTION
      ""
   ::= {pr1645v2VEthVlan 84279296}

pr1645v2VEthVlanOutPQsH24PerformanceEntry OBJECT-TYPE
   SYNTAX      Pr1645v2VEthVlanOutPQsH24PerformanceEntry
   MAX-ACCESS  not-accessible
   STATUS      current
   DESCRIPTION
      ""
   INDEX      { pr1645v2VEthVlanOutPQsH24PerformanceGlobalIx,
                pr1645v2VEthVlanTableIx,
                pr1645v2VEthVlanOutPQsTableIx,
                pr1645v2VEthVlanOutPQsH24PerformanceTableIx }
   ::= {pr1645v2VEthVlanOutPQsH24Performance 1}

Pr1645v2VEthVlanOutPQsH24PerformanceEntry ::=
   SEQUENCE
      {
      pr1645v2VEthVlanOutPQsH24PerformanceGlobalIx
         GlobalIndex,
      pr1645v2VEthVlanOutPQsH24PerformanceTableIx
         TableIndex,
      pr1645v2VEthVlanOutPQsH24PerformanceSysUpTime
         TimeTicks,
      pr1645v2VEthVlanOutPQsH24PerformanceTotPkts
         Counter64,
      pr1645v2VEthVlanOutPQsH24PerformanceDirTxPkts
         Counter64,
      pr1645v2VEthVlanOutPQsH24PerformanceQdPkts
         Counter64,
      pr1645v2VEthVlanOutPQsH24PerformanceDropPkts
         Counter64,
      pr1645v2VEthVlanOutPQsH24PerformanceRDropPkts
         Counter64,
      pr1645v2VEthVlanOutPQsH24PerformanceCirTxPkts
         Counter64,
      pr1645v2VEthVlanOutPQsH24PerformanceEirTxPkts
         Counter64,
      pr1645v2VEthVlanOutPQsH24PerformanceViolTxPkts
         Counter64,
      pr1645v2VEthVlanOutPQsH24PerformanceTotOcts
         Counter64,
      pr1645v2VEthVlanOutPQsH24PerformanceDirTxOcts
         Counter64,
      pr1645v2VEthVlanOutPQsH24PerformanceQdOcts
         Counter64,
      pr1645v2VEthVlanOutPQsH24PerformanceDropOcts
         Counter64,
      pr1645v2VEthVlanOutPQsH24PerformanceRDropOcts
         Counter64,
      pr1645v2VEthVlanOutPQsH24PerformanceCirTxOcts
         Counter64,
      pr1645v2VEthVlanOutPQsH24PerformanceEirTxOcts
         Counter64,
      pr1645v2VEthVlanOutPQsH24PerformanceViolTxOcts
         Counter64,
      pr1645v2VEthVlanOutPQsH24PerformanceBandwidth
         Integer32
      }

pr1645v2VEthVlanOutPQsH24PerformanceGlobalIx OBJECT-TYPE
   SYNTAX      GlobalIndex
   MAX-ACCESS  not-accessible
   STATUS      current
   DESCRIPTION
      "The value of the tlsCntTreeGlobalIndex of the MANAGED OBJECT."
   ::= {pr1645v2VEthVlanOutPQsH24PerformanceEntry 10}

pr1645v2VEthVlanOutPQsH24PerformanceTableIx OBJECT-TYPE
   SYNTAX      TableIndex
   MAX-ACCESS  not-accessible
   STATUS      current
   DESCRIPTION
      ""
   ::= {pr1645v2VEthVlanOutPQsH24PerformanceEntry 11}

pr1645v2VEthVlanOutPQsH24PerformanceSysUpTime OBJECT-TYPE
   SYNTAX      TimeTicks
   MAX-ACCESS  read-only
   STATUS      current
   DESCRIPTION
      "Path: virtualEthernet.performance.vlan.outPriorityQueues.h24Performance.sysUpTime

       Time in centi-second."
   ::= {pr1645v2VEthVlanOutPQsH24PerformanceEntry 16777216}

pr1645v2VEthVlanOutPQsH24PerformanceTotPkts OBJECT-TYPE
   SYNTAX      Counter64
   MAX-ACCESS  read-only
   STATUS      current
   DESCRIPTION
      "Path: virtualEthernet.performance.vlan.outPriorityQueues.h24Performance.totalPkts

       64 bit unsigned wrappable counter."
   ::= {pr1645v2VEthVlanOutPQsH24PerformanceEntry 234881024}

pr1645v2VEthVlanOutPQsH24PerformanceDirTxPkts OBJECT-TYPE
   SYNTAX      Counter64
   MAX-ACCESS  read-only
   STATUS      current
   DESCRIPTION
      "Path: virtualEthernet.performance.vlan.outPriorityQueues.h24Performance.directTxPkts

       64 bit unsigned wrappable counter."
   ::= {pr1645v2VEthVlanOutPQsH24PerformanceEntry 33554432}

pr1645v2VEthVlanOutPQsH24PerformanceQdPkts OBJECT-TYPE
   SYNTAX      Counter64
   MAX-ACCESS  read-only
   STATUS      current
   DESCRIPTION
      "Path: virtualEthernet.performance.vlan.outPriorityQueues.h24Performance.queuedPkts

       64 bit unsigned wrappable counter."
   ::= {pr1645v2VEthVlanOutPQsH24PerformanceEntry 50331648}

pr1645v2VEthVlanOutPQsH24PerformanceDropPkts OBJECT-TYPE
   SYNTAX      Counter64
   MAX-ACCESS  read-only
   STATUS      current
   DESCRIPTION
      "Path: virtualEthernet.performance.vlan.outPriorityQueues.h24Performance.droppedPkts

       64 bit unsigned wrappable counter."
   ::= {pr1645v2VEthVlanOutPQsH24PerformanceEntry 67108864}

pr1645v2VEthVlanOutPQsH24PerformanceRDropPkts OBJECT-TYPE
   SYNTAX      Counter64
   MAX-ACCESS  read-only
   STATUS      current
   DESCRIPTION
      "Path: virtualEthernet.performance.vlan.outPriorityQueues.h24Performance.redDroppedPkts

       64 bit unsigned wrappable counter."
   ::= {pr1645v2VEthVlanOutPQsH24PerformanceEntry 201326592}

pr1645v2VEthVlanOutPQsH24PerformanceCirTxPkts OBJECT-TYPE
   SYNTAX      Counter64
   MAX-ACCESS  read-only
   STATUS      current
   DESCRIPTION
      "Path: virtualEthernet.performance.vlan.outPriorityQueues.h24Performance.cirTxPkts

       64 bit unsigned wrappable counter."
   ::= {pr1645v2VEthVlanOutPQsH24PerformanceEntry 83886080}

pr1645v2VEthVlanOutPQsH24PerformanceEirTxPkts OBJECT-TYPE
   SYNTAX      Counter64
   MAX-ACCESS  read-only
   STATUS      current
   DESCRIPTION
      "Path: virtualEthernet.performance.vlan.outPriorityQueues.h24Performance.eirTxPkts

       64 bit unsigned wrappable counter."
   ::= {pr1645v2VEthVlanOutPQsH24PerformanceEntry 100663296}

pr1645v2VEthVlanOutPQsH24PerformanceViolTxPkts OBJECT-TYPE
   SYNTAX      Counter64
   MAX-ACCESS  read-only
   STATUS      current
   DESCRIPTION
      "Path: virtualEthernet.performance.vlan.outPriorityQueues.h24Performance.violateTxPkts

       64 bit unsigned wrappable counter."
   ::= {pr1645v2VEthVlanOutPQsH24PerformanceEntry 301989888}

pr1645v2VEthVlanOutPQsH24PerformanceTotOcts OBJECT-TYPE
   SYNTAX      Counter64
   MAX-ACCESS  read-only
   STATUS      current
   DESCRIPTION
      "Path: virtualEthernet.performance.vlan.outPriorityQueues.h24Performance.totalOctets

       64 bit unsigned wrappable counter."
   ::= {pr1645v2VEthVlanOutPQsH24PerformanceEntry 251658240}

pr1645v2VEthVlanOutPQsH24PerformanceDirTxOcts OBJECT-TYPE
   SYNTAX      Counter64
   MAX-ACCESS  read-only
   STATUS      current
   DESCRIPTION
      "Path: virtualEthernet.performance.vlan.outPriorityQueues.h24Performance.directTxOctets

       64 bit unsigned wrappable counter."
   ::= {pr1645v2VEthVlanOutPQsH24PerformanceEntry 117440512}

pr1645v2VEthVlanOutPQsH24PerformanceQdOcts OBJECT-TYPE
   SYNTAX      Counter64
   MAX-ACCESS  read-only
   STATUS      current
   DESCRIPTION
      "Path: virtualEthernet.performance.vlan.outPriorityQueues.h24Performance.queuedOctets

       64 bit unsigned wrappable counter."
   ::= {pr1645v2VEthVlanOutPQsH24PerformanceEntry 134217728}

pr1645v2VEthVlanOutPQsH24PerformanceDropOcts OBJECT-TYPE
   SYNTAX      Counter64
   MAX-ACCESS  read-only
   STATUS      current
   DESCRIPTION
      "Path: virtualEthernet.performance.vlan.outPriorityQueues.h24Performance.droppedOctets

       64 bit unsigned wrappable counter."
   ::= {pr1645v2VEthVlanOutPQsH24PerformanceEntry 150994944}

pr1645v2VEthVlanOutPQsH24PerformanceRDropOcts OBJECT-TYPE
   SYNTAX      Counter64
   MAX-ACCESS  read-only
   STATUS      current
   DESCRIPTION
      "Path: virtualEthernet.performance.vlan.outPriorityQueues.h24Performance.redDroppedOctets

       64 bit unsigned wrappable counter."
   ::= {pr1645v2VEthVlanOutPQsH24PerformanceEntry 218103808}

pr1645v2VEthVlanOutPQsH24PerformanceCirTxOcts OBJECT-TYPE
   SYNTAX      Counter64
   MAX-ACCESS  read-only
   STATUS      current
   DESCRIPTION
      "Path: virtualEthernet.performance.vlan.outPriorityQueues.h24Performance.cirTxOctets

       64 bit unsigned wrappable counter."
   ::= {pr1645v2VEthVlanOutPQsH24PerformanceEntry 167772160}

pr1645v2VEthVlanOutPQsH24PerformanceEirTxOcts OBJECT-TYPE
   SYNTAX      Counter64
   MAX-ACCESS  read-only
   STATUS      current
   DESCRIPTION
      "Path: virtualEthernet.performance.vlan.outPriorityQueues.h24Performance.eirTxOctets

       64 bit unsigned wrappable counter."
   ::= {pr1645v2VEthVlanOutPQsH24PerformanceEntry 184549376}

pr1645v2VEthVlanOutPQsH24PerformanceViolTxOcts OBJECT-TYPE
   SYNTAX      Counter64
   MAX-ACCESS  read-only
   STATUS      current
   DESCRIPTION
      "Path: virtualEthernet.performance.vlan.outPriorityQueues.h24Performance.violateTxOctets

       64 bit unsigned wrappable counter."
   ::= {pr1645v2VEthVlanOutPQsH24PerformanceEntry 318767104}

pr1645v2VEthVlanOutPQsH24PerformanceBandwidth OBJECT-TYPE
   SYNTAX      Integer32
   MAX-ACCESS  read-only
   STATUS      current
   DESCRIPTION
      "Path: virtualEthernet.performance.vlan.outPriorityQueues.h24Performance.bandwidth

       unit name = bps
       formula = 8 * ; 8 /"
   ::= {pr1645v2VEthVlanOutPQsH24PerformanceEntry 268435456}

pr1645v2VEthVlanOutPQsD7Performance OBJECT-TYPE
   SYNTAX      SEQUENCE OF Pr1645v2VEthVlanOutPQsD7PerformanceEntry
   MAX-ACCESS  not-accessible
   STATUS      current
   DESCRIPTION
      ""
   ::= {pr1645v2VEthVlan 84344832}

pr1645v2VEthVlanOutPQsD7PerformanceEntry OBJECT-TYPE
   SYNTAX      Pr1645v2VEthVlanOutPQsD7PerformanceEntry
   MAX-ACCESS  not-accessible
   STATUS      current
   DESCRIPTION
      ""
   INDEX      { pr1645v2VEthVlanOutPQsD7PerformanceGlobalIx,
                pr1645v2VEthVlanTableIx,
                pr1645v2VEthVlanOutPQsTableIx,
                pr1645v2VEthVlanOutPQsD7PerformanceTableIx }
   ::= {pr1645v2VEthVlanOutPQsD7Performance 1}

Pr1645v2VEthVlanOutPQsD7PerformanceEntry ::=
   SEQUENCE
      {
      pr1645v2VEthVlanOutPQsD7PerformanceGlobalIx
         GlobalIndex,
      pr1645v2VEthVlanOutPQsD7PerformanceTableIx
         TableIndex,
      pr1645v2VEthVlanOutPQsD7PerformanceSysUpTime
         TimeTicks,
      pr1645v2VEthVlanOutPQsD7PerformanceTotPkts
         Counter64,
      pr1645v2VEthVlanOutPQsD7PerformanceDirTxPkts
         Counter64,
      pr1645v2VEthVlanOutPQsD7PerformanceQdPkts
         Counter64,
      pr1645v2VEthVlanOutPQsD7PerformanceDropPkts
         Counter64,
      pr1645v2VEthVlanOutPQsD7PerformanceRDropPkts
         Counter64,
      pr1645v2VEthVlanOutPQsD7PerformanceCirTxPkts
         Counter64,
      pr1645v2VEthVlanOutPQsD7PerformanceEirTxPkts
         Counter64,
      pr1645v2VEthVlanOutPQsD7PerformanceViolTxPkts
         Counter64,
      pr1645v2VEthVlanOutPQsD7PerformanceTotOcts
         Counter64,
      pr1645v2VEthVlanOutPQsD7PerformanceDirTxOcts
         Counter64,
      pr1645v2VEthVlanOutPQsD7PerformanceQdOcts
         Counter64,
      pr1645v2VEthVlanOutPQsD7PerformanceDropOcts
         Counter64,
      pr1645v2VEthVlanOutPQsD7PerformanceRDropOcts
         Counter64,
      pr1645v2VEthVlanOutPQsD7PerformanceCirTxOcts
         Counter64,
      pr1645v2VEthVlanOutPQsD7PerformanceEirTxOcts
         Counter64,
      pr1645v2VEthVlanOutPQsD7PerformanceViolTxOcts
         Counter64,
      pr1645v2VEthVlanOutPQsD7PerformanceBandwidth
         Integer32
      }

pr1645v2VEthVlanOutPQsD7PerformanceGlobalIx OBJECT-TYPE
   SYNTAX      GlobalIndex
   MAX-ACCESS  not-accessible
   STATUS      current
   DESCRIPTION
      "The value of the tlsCntTreeGlobalIndex of the MANAGED OBJECT."
   ::= {pr1645v2VEthVlanOutPQsD7PerformanceEntry 10}

pr1645v2VEthVlanOutPQsD7PerformanceTableIx OBJECT-TYPE
   SYNTAX      TableIndex
   MAX-ACCESS  not-accessible
   STATUS      current
   DESCRIPTION
      ""
   ::= {pr1645v2VEthVlanOutPQsD7PerformanceEntry 11}

pr1645v2VEthVlanOutPQsD7PerformanceSysUpTime OBJECT-TYPE
   SYNTAX      TimeTicks
   MAX-ACCESS  read-only
   STATUS      current
   DESCRIPTION
      "Path: virtualEthernet.performance.vlan.outPriorityQueues.d7Performance.sysUpTime

       Time in centi-second."
   ::= {pr1645v2VEthVlanOutPQsD7PerformanceEntry 16777216}

pr1645v2VEthVlanOutPQsD7PerformanceTotPkts OBJECT-TYPE
   SYNTAX      Counter64
   MAX-ACCESS  read-only
   STATUS      current
   DESCRIPTION
      "Path: virtualEthernet.performance.vlan.outPriorityQueues.d7Performance.totalPkts

       64 bit unsigned wrappable counter."
   ::= {pr1645v2VEthVlanOutPQsD7PerformanceEntry 234881024}

pr1645v2VEthVlanOutPQsD7PerformanceDirTxPkts OBJECT-TYPE
   SYNTAX      Counter64
   MAX-ACCESS  read-only
   STATUS      current
   DESCRIPTION
      "Path: virtualEthernet.performance.vlan.outPriorityQueues.d7Performance.directTxPkts

       64 bit unsigned wrappable counter."
   ::= {pr1645v2VEthVlanOutPQsD7PerformanceEntry 33554432}

pr1645v2VEthVlanOutPQsD7PerformanceQdPkts OBJECT-TYPE
   SYNTAX      Counter64
   MAX-ACCESS  read-only
   STATUS      current
   DESCRIPTION
      "Path: virtualEthernet.performance.vlan.outPriorityQueues.d7Performance.queuedPkts

       64 bit unsigned wrappable counter."
   ::= {pr1645v2VEthVlanOutPQsD7PerformanceEntry 50331648}

pr1645v2VEthVlanOutPQsD7PerformanceDropPkts OBJECT-TYPE
   SYNTAX      Counter64
   MAX-ACCESS  read-only
   STATUS      current
   DESCRIPTION
      "Path: virtualEthernet.performance.vlan.outPriorityQueues.d7Performance.droppedPkts

       64 bit unsigned wrappable counter."
   ::= {pr1645v2VEthVlanOutPQsD7PerformanceEntry 67108864}

pr1645v2VEthVlanOutPQsD7PerformanceRDropPkts OBJECT-TYPE
   SYNTAX      Counter64
   MAX-ACCESS  read-only
   STATUS      current
   DESCRIPTION
      "Path: virtualEthernet.performance.vlan.outPriorityQueues.d7Performance.redDroppedPkts

       64 bit unsigned wrappable counter."
   ::= {pr1645v2VEthVlanOutPQsD7PerformanceEntry 201326592}

pr1645v2VEthVlanOutPQsD7PerformanceCirTxPkts OBJECT-TYPE
   SYNTAX      Counter64
   MAX-ACCESS  read-only
   STATUS      current
   DESCRIPTION
      "Path: virtualEthernet.performance.vlan.outPriorityQueues.d7Performance.cirTxPkts

       64 bit unsigned wrappable counter."
   ::= {pr1645v2VEthVlanOutPQsD7PerformanceEntry 83886080}

pr1645v2VEthVlanOutPQsD7PerformanceEirTxPkts OBJECT-TYPE
   SYNTAX      Counter64
   MAX-ACCESS  read-only
   STATUS      current
   DESCRIPTION
      "Path: virtualEthernet.performance.vlan.outPriorityQueues.d7Performance.eirTxPkts

       64 bit unsigned wrappable counter."
   ::= {pr1645v2VEthVlanOutPQsD7PerformanceEntry 100663296}

pr1645v2VEthVlanOutPQsD7PerformanceViolTxPkts OBJECT-TYPE
   SYNTAX      Counter64
   MAX-ACCESS  read-only
   STATUS      current
   DESCRIPTION
      "Path: virtualEthernet.performance.vlan.outPriorityQueues.d7Performance.violateTxPkts

       64 bit unsigned wrappable counter."
   ::= {pr1645v2VEthVlanOutPQsD7PerformanceEntry 301989888}

pr1645v2VEthVlanOutPQsD7PerformanceTotOcts OBJECT-TYPE
   SYNTAX      Counter64
   MAX-ACCESS  read-only
   STATUS      current
   DESCRIPTION
      "Path: virtualEthernet.performance.vlan.outPriorityQueues.d7Performance.totalOctets

       64 bit unsigned wrappable counter."
   ::= {pr1645v2VEthVlanOutPQsD7PerformanceEntry 251658240}

pr1645v2VEthVlanOutPQsD7PerformanceDirTxOcts OBJECT-TYPE
   SYNTAX      Counter64
   MAX-ACCESS  read-only
   STATUS      current
   DESCRIPTION
      "Path: virtualEthernet.performance.vlan.outPriorityQueues.d7Performance.directTxOctets

       64 bit unsigned wrappable counter."
   ::= {pr1645v2VEthVlanOutPQsD7PerformanceEntry 117440512}

pr1645v2VEthVlanOutPQsD7PerformanceQdOcts OBJECT-TYPE
   SYNTAX      Counter64
   MAX-ACCESS  read-only
   STATUS      current
   DESCRIPTION
      "Path: virtualEthernet.performance.vlan.outPriorityQueues.d7Performance.queuedOctets

       64 bit unsigned wrappable counter."
   ::= {pr1645v2VEthVlanOutPQsD7PerformanceEntry 134217728}

pr1645v2VEthVlanOutPQsD7PerformanceDropOcts OBJECT-TYPE
   SYNTAX      Counter64
   MAX-ACCESS  read-only
   STATUS      current
   DESCRIPTION
      "Path: virtualEthernet.performance.vlan.outPriorityQueues.d7Performance.droppedOctets

       64 bit unsigned wrappable counter."
   ::= {pr1645v2VEthVlanOutPQsD7PerformanceEntry 150994944}

pr1645v2VEthVlanOutPQsD7PerformanceRDropOcts OBJECT-TYPE
   SYNTAX      Counter64
   MAX-ACCESS  read-only
   STATUS      current
   DESCRIPTION
      "Path: virtualEthernet.performance.vlan.outPriorityQueues.d7Performance.redDroppedOctets

       64 bit unsigned wrappable counter."
   ::= {pr1645v2VEthVlanOutPQsD7PerformanceEntry 218103808}

pr1645v2VEthVlanOutPQsD7PerformanceCirTxOcts OBJECT-TYPE
   SYNTAX      Counter64
   MAX-ACCESS  read-only
   STATUS      current
   DESCRIPTION
      "Path: virtualEthernet.performance.vlan.outPriorityQueues.d7Performance.cirTxOctets

       64 bit unsigned wrappable counter."
   ::= {pr1645v2VEthVlanOutPQsD7PerformanceEntry 167772160}

pr1645v2VEthVlanOutPQsD7PerformanceEirTxOcts OBJECT-TYPE
   SYNTAX      Counter64
   MAX-ACCESS  read-only
   STATUS      current
   DESCRIPTION
      "Path: virtualEthernet.performance.vlan.outPriorityQueues.d7Performance.eirTxOctets

       64 bit unsigned wrappable counter."
   ::= {pr1645v2VEthVlanOutPQsD7PerformanceEntry 184549376}

pr1645v2VEthVlanOutPQsD7PerformanceViolTxOcts OBJECT-TYPE
   SYNTAX      Counter64
   MAX-ACCESS  read-only
   STATUS      current
   DESCRIPTION
      "Path: virtualEthernet.performance.vlan.outPriorityQueues.d7Performance.violateTxOctets

       64 bit unsigned wrappable counter."
   ::= {pr1645v2VEthVlanOutPQsD7PerformanceEntry 318767104}

pr1645v2VEthVlanOutPQsD7PerformanceBandwidth OBJECT-TYPE
   SYNTAX      Integer32
   MAX-ACCESS  read-only
   STATUS      current
   DESCRIPTION
      "Path: virtualEthernet.performance.vlan.outPriorityQueues.d7Performance.bandwidth

       unit name = bps
       formula = 8 * ; 8 /"
   ::= {pr1645v2VEthVlanOutPQsD7PerformanceEntry 268435456}


pr1645v2VEthPPPoE OBJECT IDENTIFIER ::= {pr1645v2VEth 53}

pr1645v2VEthPPPoESSCTable OBJECT-TYPE
   SYNTAX      SEQUENCE OF Pr1645v2VEthPPPoEEntry
   MAX-ACCESS  not-accessible
   STATUS      current
   DESCRIPTION
      ""
   ::= {pr1645v2VEthPPPoE 1}

pr1645v2VEthPPPoEEntry OBJECT-TYPE
   SYNTAX      Pr1645v2VEthPPPoEEntry
   MAX-ACCESS  not-accessible
   STATUS      current
   DESCRIPTION
      ""
   INDEX      { pr1645v2VEthPPPoEGlobalIx,
                pr1645v2VEthPPPoETableIx }
   ::= {pr1645v2VEthPPPoESSCTable 1}

Pr1645v2VEthPPPoEEntry ::=
   SEQUENCE
      {
      pr1645v2VEthPPPoEGlobalIx
         GlobalIndex,
      pr1645v2VEthPPPoETableIx
         TableIndex,
      pr1645v2VEthPPPoEName
         DisplayString,
      pr1645v2VEthPPPoEMCInOctets
         Counter64,
      pr1645v2VEthPPPoEMCInUcast
         Counter64,
      pr1645v2VEthPPPoEMCInNUcastPkts
         Counter64,
      pr1645v2VEthPPPoEMCInBcastPkts
         Counter64,
      pr1645v2VEthPPPoEMCInMcastPkts
         Counter64,
      pr1645v2VEthPPPoEMCInDiscards
         Counter64,
      pr1645v2VEthPPPoEMCInErrors
         Counter64,
      pr1645v2VEthPPPoEMCInUnknownProtos
         Counter64,
      pr1645v2VEthPPPoEMCInDropEx
         Counter64,
      pr1645v2VEthPPPoEMCInDropNoMac
         Counter64,
      pr1645v2VEthPPPoEMCInDropNUCast
         Counter64,
      pr1645v2VEthPPPoEMCInDropFilter
         Counter64,
      pr1645v2VEthPPPoEMCInBandwidth15sec
         Integer32,
      pr1645v2VEthPPPoEMCInBandwidth30sec
         Integer32,
      pr1645v2VEthPPPoEMCInBandwidth1min
         Integer32,
      pr1645v2VEthPPPoEMCInBandwidth2min
         Integer32,
      pr1645v2VEthPPPoEMCInBandwidth5min
         Integer32,
      pr1645v2VEthPPPoEMCOutOctets
         Counter64,
      pr1645v2VEthPPPoEMCOutUcastPkts
         Counter64,
      pr1645v2VEthPPPoEMCOutNUcastPkts
         Counter64,
      pr1645v2VEthPPPoEMCOutBcastPkts
         Counter64,
      pr1645v2VEthPPPoEMCOutMcastPkts
         Counter64,
      pr1645v2VEthPPPoEMCOutDiscards
         Counter64,
      pr1645v2VEthPPPoEMCOutErrors
         Counter64,
      pr1645v2VEthPPPoEMCOutQLen
         Counter32,
      pr1645v2VEthPPPoEMCOutDropEx
         Counter64,
      pr1645v2VEthPPPoEMCOutDropNoArp
         Counter64,
      pr1645v2VEthPPPoEMCOutDropFilter
         Counter64,
      pr1645v2VEthPPPoEMCOutBandwidth15sec
         Integer32,
      pr1645v2VEthPPPoEMCOutBandwidth30sec
         Integer32,
      pr1645v2VEthPPPoEMCOutBandwidth1min
         Integer32,
      pr1645v2VEthPPPoEMCOutBandwidth2min
         Integer32,
      pr1645v2VEthPPPoEMCOutBandwidth5min
         Integer32,
      pr1645v2VEthPPPoEPppLinkMonitoringRequestsSent
         Gauge32,
      pr1645v2VEthPPPoEPppLinkMonitoringRepliesRcvd
         Gauge32,
      pr1645v2VEthPPPoEPppLinkMonitoringRequestsRcvd
         Gauge32,
      pr1645v2VEthPPPoEPppLinkMonitoringRepliesSent
         Gauge32
      }

pr1645v2VEthPPPoEGlobalIx OBJECT-TYPE
   SYNTAX      GlobalIndex
   MAX-ACCESS  not-accessible
   STATUS      current
   DESCRIPTION
      "The value of the tlsCntTreeGlobalIndex of the MANAGED OBJECT."
   ::= {pr1645v2VEthPPPoEEntry 10}

pr1645v2VEthPPPoETableIx OBJECT-TYPE
   SYNTAX      TableIndex
   MAX-ACCESS  not-accessible
   STATUS      current
   DESCRIPTION
      ""
   ::= {pr1645v2VEthPPPoEEntry 11}

pr1645v2VEthPPPoEName OBJECT-TYPE
   SYNTAX      DisplayString
   MAX-ACCESS  read-only
   STATUS      current
   DESCRIPTION
      "Path: virtualEthernet.performance.pppoEClient.name"
   ::= {pr1645v2VEthPPPoEEntry 16777216}

pr1645v2VEthPPPoEMCInOctets OBJECT-TYPE
   SYNTAX      Counter64
   MAX-ACCESS  read-only
   STATUS      current
   DESCRIPTION
      "Path: virtualEthernet.performance.pppoEClient.mibCounters.ifInOctets

       64 bit unsigned wrappable counter."
   ::= {pr1645v2VEthPPPoEEntry 40697856}

pr1645v2VEthPPPoEMCInUcast OBJECT-TYPE
   SYNTAX      Counter64
   MAX-ACCESS  read-only
   STATUS      current
   DESCRIPTION
      "Path: virtualEthernet.performance.pppoEClient.mibCounters.ifInUcastPkts

       64 bit unsigned wrappable counter."
   ::= {pr1645v2VEthPPPoEEntry 40763392}

pr1645v2VEthPPPoEMCInNUcastPkts OBJECT-TYPE
   SYNTAX      Counter64
   MAX-ACCESS  read-only
   STATUS      current
   DESCRIPTION
      "Path: virtualEthernet.performance.pppoEClient.mibCounters.ifInNUcastPkts

       64 bit unsigned wrappable counter."
   ::= {pr1645v2VEthPPPoEEntry 40828928}

pr1645v2VEthPPPoEMCInBcastPkts OBJECT-TYPE
   SYNTAX      Counter64
   MAX-ACCESS  read-only
   STATUS      current
   DESCRIPTION
      "Path: virtualEthernet.performance.pppoEClient.mibCounters.ifInBcastPkts

       64 bit unsigned wrappable counter."
   ::= {pr1645v2VEthPPPoEEntry 47382528}

pr1645v2VEthPPPoEMCInMcastPkts OBJECT-TYPE
   SYNTAX      Counter64
   MAX-ACCESS  read-only
   STATUS      current
   DESCRIPTION
      "Path: virtualEthernet.performance.pppoEClient.mibCounters.ifInMcastPkts

       64 bit unsigned wrappable counter."
   ::= {pr1645v2VEthPPPoEEntry 48037888}

pr1645v2VEthPPPoEMCInDiscards OBJECT-TYPE
   SYNTAX      Counter64
   MAX-ACCESS  read-only
   STATUS      current
   DESCRIPTION
      "Path: virtualEthernet.performance.pppoEClient.mibCounters.ifInDiscards

       64 bit unsigned wrappable counter."
   ::= {pr1645v2VEthPPPoEEntry 40894464}

pr1645v2VEthPPPoEMCInErrors OBJECT-TYPE
   SYNTAX      Counter64
   MAX-ACCESS  read-only
   STATUS      current
   DESCRIPTION
      "Path: virtualEthernet.performance.pppoEClient.mibCounters.ifInErrors

       64 bit unsigned wrappable counter."
   ::= {pr1645v2VEthPPPoEEntry 40960000}

pr1645v2VEthPPPoEMCInUnknownProtos OBJECT-TYPE
   SYNTAX      Counter64
   MAX-ACCESS  read-only
   STATUS      current
   DESCRIPTION
      "Path: virtualEthernet.performance.pppoEClient.mibCounters.ifInUnknownProtos

       64 bit unsigned wrappable counter."
   ::= {pr1645v2VEthPPPoEEntry 41025536}

pr1645v2VEthPPPoEMCInDropEx OBJECT-TYPE
   SYNTAX      Counter64
   MAX-ACCESS  read-only
   STATUS      current
   DESCRIPTION
      "Path: virtualEthernet.performance.pppoEClient.mibCounters.ifInDropLevelExceeded

       64 bit unsigned wrappable counter."
   ::= {pr1645v2VEthPPPoEEntry 42074112}

pr1645v2VEthPPPoEMCInDropNoMac OBJECT-TYPE
   SYNTAX      Counter64
   MAX-ACCESS  read-only
   STATUS      current
   DESCRIPTION
      "Path: virtualEthernet.performance.pppoEClient.mibCounters.ifInDiscardsNoMacFit

       64 bit unsigned wrappable counter."
   ::= {pr1645v2VEthPPPoEEntry 42270720}

pr1645v2VEthPPPoEMCInDropNUCast OBJECT-TYPE
   SYNTAX      Counter64
   MAX-ACCESS  read-only
   STATUS      current
   DESCRIPTION
      "Path: virtualEthernet.performance.pppoEClient.mibCounters.ifInDiscardsNUCast

       64 bit unsigned wrappable counter."
   ::= {pr1645v2VEthPPPoEEntry 42467328}

pr1645v2VEthPPPoEMCInDropFilter OBJECT-TYPE
   SYNTAX      Counter64
   MAX-ACCESS  read-only
   STATUS      current
   DESCRIPTION
      "Path: virtualEthernet.performance.pppoEClient.mibCounters.ifInDiscardsFilter

       64 bit unsigned wrappable counter."
   ::= {pr1645v2VEthPPPoEEntry 42532864}

pr1645v2VEthPPPoEMCInBandwidth15sec OBJECT-TYPE
   SYNTAX      Integer32
   MAX-ACCESS  read-only
   STATUS      current
   DESCRIPTION
      "Path: virtualEthernet.performance.pppoEClient.mibCounters.ifInBandwidth.15sec

       unit name = bps
       formula = 8 * ; 8 /"
   ::= {pr1645v2VEthPPPoEEntry 45417728}

pr1645v2VEthPPPoEMCInBandwidth30sec OBJECT-TYPE
   SYNTAX      Integer32
   MAX-ACCESS  read-only
   STATUS      current
   DESCRIPTION
      "Path: virtualEthernet.performance.pppoEClient.mibCounters.ifInBandwidth.30sec

       unit name = bps
       formula = 8 * ; 8 /"
   ::= {pr1645v2VEthPPPoEEntry 45419008}

pr1645v2VEthPPPoEMCInBandwidth1min OBJECT-TYPE
   SYNTAX      Integer32
   MAX-ACCESS  read-only
   STATUS      current
   DESCRIPTION
      "Path: virtualEthernet.performance.pppoEClient.mibCounters.ifInBandwidth.1min

       unit name = bps
       formula = 8 * ; 8 /"
   ::= {pr1645v2VEthPPPoEEntry 45421568}

pr1645v2VEthPPPoEMCInBandwidth2min OBJECT-TYPE
   SYNTAX      Integer32
   MAX-ACCESS  read-only
   STATUS      current
   DESCRIPTION
      "Path: virtualEthernet.performance.pppoEClient.mibCounters.ifInBandwidth.2min

       unit name = bps
       formula = 8 * ; 8 /"
   ::= {pr1645v2VEthPPPoEEntry 45426688}

pr1645v2VEthPPPoEMCInBandwidth5min OBJECT-TYPE
   SYNTAX      Integer32
   MAX-ACCESS  read-only
   STATUS      current
   DESCRIPTION
      "Path: virtualEthernet.performance.pppoEClient.mibCounters.ifInBandwidth.5min

       unit name = bps
       formula = 8 * ; 8 /"
   ::= {pr1645v2VEthPPPoEEntry 45442048}

pr1645v2VEthPPPoEMCOutOctets OBJECT-TYPE
   SYNTAX      Counter64
   MAX-ACCESS  read-only
   STATUS      current
   DESCRIPTION
      "Path: virtualEthernet.performance.pppoEClient.mibCounters.ifOutOctets

       64 bit unsigned wrappable counter."
   ::= {pr1645v2VEthPPPoEEntry 41091072}

pr1645v2VEthPPPoEMCOutUcastPkts OBJECT-TYPE
   SYNTAX      Counter64
   MAX-ACCESS  read-only
   STATUS      current
   DESCRIPTION
      "Path: virtualEthernet.performance.pppoEClient.mibCounters.ifOutUcastPkts

       64 bit unsigned wrappable counter."
   ::= {pr1645v2VEthPPPoEEntry 41156608}

pr1645v2VEthPPPoEMCOutNUcastPkts OBJECT-TYPE
   SYNTAX      Counter64
   MAX-ACCESS  read-only
   STATUS      current
   DESCRIPTION
      "Path: virtualEthernet.performance.pppoEClient.mibCounters.ifOutNUcastPkts

       64 bit unsigned wrappable counter."
   ::= {pr1645v2VEthPPPoEEntry 41222144}

pr1645v2VEthPPPoEMCOutBcastPkts OBJECT-TYPE
   SYNTAX      Counter64
   MAX-ACCESS  read-only
   STATUS      current
   DESCRIPTION
      "Path: virtualEthernet.performance.pppoEClient.mibCounters.ifOutBcastPkts

       64 bit unsigned wrappable counter."
   ::= {pr1645v2VEthPPPoEEntry 47775744}

pr1645v2VEthPPPoEMCOutMcastPkts OBJECT-TYPE
   SYNTAX      Counter64
   MAX-ACCESS  read-only
   STATUS      current
   DESCRIPTION
      "Path: virtualEthernet.performance.pppoEClient.mibCounters.ifOutMcastPkts

       64 bit unsigned wrappable counter."
   ::= {pr1645v2VEthPPPoEEntry 48431104}

pr1645v2VEthPPPoEMCOutDiscards OBJECT-TYPE
   SYNTAX      Counter64
   MAX-ACCESS  read-only
   STATUS      current
   DESCRIPTION
      "Path: virtualEthernet.performance.pppoEClient.mibCounters.ifOutDiscards

       64 bit unsigned wrappable counter."
   ::= {pr1645v2VEthPPPoEEntry 41287680}

pr1645v2VEthPPPoEMCOutErrors OBJECT-TYPE
   SYNTAX      Counter64
   MAX-ACCESS  read-only
   STATUS      current
   DESCRIPTION
      "Path: virtualEthernet.performance.pppoEClient.mibCounters.ifOutErrors

       64 bit unsigned wrappable counter."
   ::= {pr1645v2VEthPPPoEEntry 41353216}

pr1645v2VEthPPPoEMCOutQLen OBJECT-TYPE
   SYNTAX      Counter32
   MAX-ACCESS  read-only
   STATUS      current
   DESCRIPTION
      "Path: virtualEthernet.performance.pppoEClient.mibCounters.ifOutQLen

       32 bit unsigned wrappable counter."
   ::= {pr1645v2VEthPPPoEEntry 41418752}

pr1645v2VEthPPPoEMCOutDropEx OBJECT-TYPE
   SYNTAX      Counter64
   MAX-ACCESS  read-only
   STATUS      current
   DESCRIPTION
      "Path: virtualEthernet.performance.pppoEClient.mibCounters.ifOutDropLevelExceeded

       64 bit unsigned wrappable counter."
   ::= {pr1645v2VEthPPPoEEntry 41484288}

pr1645v2VEthPPPoEMCOutDropNoArp OBJECT-TYPE
   SYNTAX      Counter64
   MAX-ACCESS  read-only
   STATUS      current
   DESCRIPTION
      "Path: virtualEthernet.performance.pppoEClient.mibCounters.ifOutDiscardsNoArp

       64 bit unsigned wrappable counter."
   ::= {pr1645v2VEthPPPoEEntry 42336256}

pr1645v2VEthPPPoEMCOutDropFilter OBJECT-TYPE
   SYNTAX      Counter64
   MAX-ACCESS  read-only
   STATUS      current
   DESCRIPTION
      "Path: virtualEthernet.performance.pppoEClient.mibCounters.ifOutDiscardsFilter

       64 bit unsigned wrappable counter."
   ::= {pr1645v2VEthPPPoEEntry 42598400}

pr1645v2VEthPPPoEMCOutBandwidth15sec OBJECT-TYPE
   SYNTAX      Integer32
   MAX-ACCESS  read-only
   STATUS      current
   DESCRIPTION
      "Path: virtualEthernet.performance.pppoEClient.mibCounters.ifOutBandwidth.15sec

       unit name = bps
       formula = 8 * ; 8 /"
   ::= {pr1645v2VEthPPPoEEntry 45483264}

pr1645v2VEthPPPoEMCOutBandwidth30sec OBJECT-TYPE
   SYNTAX      Integer32
   MAX-ACCESS  read-only
   STATUS      current
   DESCRIPTION
      "Path: virtualEthernet.performance.pppoEClient.mibCounters.ifOutBandwidth.30sec

       unit name = bps
       formula = 8 * ; 8 /"
   ::= {pr1645v2VEthPPPoEEntry 45484544}

pr1645v2VEthPPPoEMCOutBandwidth1min OBJECT-TYPE
   SYNTAX      Integer32
   MAX-ACCESS  read-only
   STATUS      current
   DESCRIPTION
      "Path: virtualEthernet.performance.pppoEClient.mibCounters.ifOutBandwidth.1min

       unit name = bps
       formula = 8 * ; 8 /"
   ::= {pr1645v2VEthPPPoEEntry 45487104}

pr1645v2VEthPPPoEMCOutBandwidth2min OBJECT-TYPE
   SYNTAX      Integer32
   MAX-ACCESS  read-only
   STATUS      current
   DESCRIPTION
      "Path: virtualEthernet.performance.pppoEClient.mibCounters.ifOutBandwidth.2min

       unit name = bps
       formula = 8 * ; 8 /"
   ::= {pr1645v2VEthPPPoEEntry 45492224}

pr1645v2VEthPPPoEMCOutBandwidth5min OBJECT-TYPE
   SYNTAX      Integer32
   MAX-ACCESS  read-only
   STATUS      current
   DESCRIPTION
      "Path: virtualEthernet.performance.pppoEClient.mibCounters.ifOutBandwidth.5min

       unit name = bps
       formula = 8 * ; 8 /"
   ::= {pr1645v2VEthPPPoEEntry 45507584}

pr1645v2VEthPPPoEPppLinkMonitoringRequestsSent OBJECT-TYPE
   SYNTAX      Gauge32
   MAX-ACCESS  read-only
   STATUS      current
   DESCRIPTION
      "Path: virtualEthernet.performance.pppoEClient.ppp.linkMonitoring.requestsSent

       32 bit unsigned gauge value."
   ::= {pr1645v2VEthPPPoEEntry 50397440}

pr1645v2VEthPPPoEPppLinkMonitoringRepliesRcvd OBJECT-TYPE
   SYNTAX      Gauge32
   MAX-ACCESS  read-only
   STATUS      current
   DESCRIPTION
      "Path: virtualEthernet.performance.pppoEClient.ppp.linkMonitoring.repliesRcvd

       32 bit unsigned gauge value."
   ::= {pr1645v2VEthPPPoEEntry 50397696}

pr1645v2VEthPPPoEPppLinkMonitoringRequestsRcvd OBJECT-TYPE
   SYNTAX      Gauge32
   MAX-ACCESS  read-only
   STATUS      current
   DESCRIPTION
      "Path: virtualEthernet.performance.pppoEClient.ppp.linkMonitoring.requestsRcvd

       32 bit unsigned gauge value."
   ::= {pr1645v2VEthPPPoEEntry 50397952}

pr1645v2VEthPPPoEPppLinkMonitoringRepliesSent OBJECT-TYPE
   SYNTAX      Gauge32
   MAX-ACCESS  read-only
   STATUS      current
   DESCRIPTION
      "Path: virtualEthernet.performance.pppoEClient.ppp.linkMonitoring.repliesSent

       32 bit unsigned gauge value."
   ::= {pr1645v2VEthPPPoEEntry 50398208}

pr1645v2VEthPPPoEMCH2P OBJECT-TYPE
   SYNTAX      SEQUENCE OF Pr1645v2VEthPPPoEMCH2PEntry
   MAX-ACCESS  not-accessible
   STATUS      current
   DESCRIPTION
      ""
   ::= {pr1645v2VEthPPPoE 41549824}

pr1645v2VEthPPPoEMCH2PEntry OBJECT-TYPE
   SYNTAX      Pr1645v2VEthPPPoEMCH2PEntry
   MAX-ACCESS  not-accessible
   STATUS      current
   DESCRIPTION
      ""
   INDEX      { pr1645v2VEthPPPoEMCH2PGlobalIx,
                pr1645v2VEthPPPoETableIx,
                pr1645v2VEthPPPoEMCH2PTableIx }
   ::= {pr1645v2VEthPPPoEMCH2P 1}

Pr1645v2VEthPPPoEMCH2PEntry ::=
   SEQUENCE
      {
      pr1645v2VEthPPPoEMCH2PGlobalIx
         GlobalIndex,
      pr1645v2VEthPPPoEMCH2PTableIx
         TableIndex,
      pr1645v2VEthPPPoEMCH2PSysUpTime
         TimeTicks,
      pr1645v2VEthPPPoEMCH2PIfUpTime
         TimeTicks,
      pr1645v2VEthPPPoEMCH2PIfStatChanges
         Counter32,
      pr1645v2VEthPPPoEMCH2PIfInOctets
         Counter64,
      pr1645v2VEthPPPoEMCH2PIfInUCPkts
         Counter64,
      pr1645v2VEthPPPoEMCH2PIfInNUCPkts
         Counter64,
      pr1645v2VEthPPPoEMCH2PIfInBCPkts
         Counter64,
      pr1645v2VEthPPPoEMCH2PIfInMCPkts
         Counter64,
      pr1645v2VEthPPPoEMCH2PIfInDiscards
         Counter64,
      pr1645v2VEthPPPoEMCH2PIfInErrors
         Counter64,
      pr1645v2VEthPPPoEMCH2PIfInUnkwn
         Counter64,
      pr1645v2VEthPPPoEMCH2PInDropEx
         Counter64,
      pr1645v2VEthPPPoEMCH2PInDropNoMac
         Counter64,
      pr1645v2VEthPPPoEMCH2PInDropNUCast
         Counter64,
      pr1645v2VEthPPPoEMCH2PInDropFilter
         Counter64,
      pr1645v2VEthPPPoEMCH2PIfInBandwidth
         Integer32,
      pr1645v2VEthPPPoEMCH2PIfOutOctets
         Counter64,
      pr1645v2VEthPPPoEMCH2PIfOutUCPkts
         Counter64,
      pr1645v2VEthPPPoEMCH2PIfOutNUCPkts
         Counter64,
      pr1645v2VEthPPPoEMCH2PIfOutBCPkts
         Counter64,
      pr1645v2VEthPPPoEMCH2PIfOutMCPkts
         Counter64,
      pr1645v2VEthPPPoEMCH2PIfOutDiscards
         Counter64,
      pr1645v2VEthPPPoEMCH2PIfOutErrors
         Counter64,
      pr1645v2VEthPPPoEMCH2POutDropEx
         Counter64,
      pr1645v2VEthPPPoEMCH2POutDropNoArp
         Counter64,
      pr1645v2VEthPPPoEMCH2POutDropFilter
         Counter64,
      pr1645v2VEthPPPoEMCH2PIfOutBandwidth
         Integer32,
      pr1645v2VEthPPPoEMCH2PIfErrSec
         Counter32
      }

pr1645v2VEthPPPoEMCH2PGlobalIx OBJECT-TYPE
   SYNTAX      GlobalIndex
   MAX-ACCESS  not-accessible
   STATUS      current
   DESCRIPTION
      "The value of the tlsCntTreeGlobalIndex of the MANAGED OBJECT."
   ::= {pr1645v2VEthPPPoEMCH2PEntry 10}

pr1645v2VEthPPPoEMCH2PTableIx OBJECT-TYPE
   SYNTAX      TableIndex
   MAX-ACCESS  not-accessible
   STATUS      current
   DESCRIPTION
      ""
   ::= {pr1645v2VEthPPPoEMCH2PEntry 11}

pr1645v2VEthPPPoEMCH2PSysUpTime OBJECT-TYPE
   SYNTAX      TimeTicks
   MAX-ACCESS  read-only
   STATUS      current
   DESCRIPTION
      "Path: virtualEthernet.performance.pppoEClient.mibCounters.h2Performance.sysUpTime

       Time in centi-second."
   ::= {pr1645v2VEthPPPoEMCH2PEntry 16777216}

pr1645v2VEthPPPoEMCH2PIfUpTime OBJECT-TYPE
   SYNTAX      TimeTicks
   MAX-ACCESS  read-only
   STATUS      current
   DESCRIPTION
      "Path: virtualEthernet.performance.pppoEClient.mibCounters.h2Performance.ifUpTime

       Time in centi-second."
   ::= {pr1645v2VEthPPPoEMCH2PEntry 33554432}

pr1645v2VEthPPPoEMCH2PIfStatChanges OBJECT-TYPE
   SYNTAX      Counter32
   MAX-ACCESS  read-only
   STATUS      current
   DESCRIPTION
      "Path: virtualEthernet.performance.pppoEClient.mibCounters.h2Performance.ifStatusChanges

       32 bit unsigned wrappable counter."
   ::= {pr1645v2VEthPPPoEMCH2PEntry 50331648}

pr1645v2VEthPPPoEMCH2PIfInOctets OBJECT-TYPE
   SYNTAX      Counter64
   MAX-ACCESS  read-only
   STATUS      current
   DESCRIPTION
      "Path: virtualEthernet.performance.pppoEClient.mibCounters.h2Performance.ifInOctets

       64 bit unsigned wrappable counter."
   ::= {pr1645v2VEthPPPoEMCH2PEntry 67108864}

pr1645v2VEthPPPoEMCH2PIfInUCPkts OBJECT-TYPE
   SYNTAX      Counter64
   MAX-ACCESS  read-only
   STATUS      current
   DESCRIPTION
      "Path: virtualEthernet.performance.pppoEClient.mibCounters.h2Performance.ifInUcastPkts

       64 bit unsigned wrappable counter."
   ::= {pr1645v2VEthPPPoEMCH2PEntry 83886080}

pr1645v2VEthPPPoEMCH2PIfInNUCPkts OBJECT-TYPE
   SYNTAX      Counter64
   MAX-ACCESS  read-only
   STATUS      current
   DESCRIPTION
      "Path: virtualEthernet.performance.pppoEClient.mibCounters.h2Performance.ifInNUcastPkts

       64 bit unsigned wrappable counter."
   ::= {pr1645v2VEthPPPoEMCH2PEntry 100663296}

pr1645v2VEthPPPoEMCH2PIfInBCPkts OBJECT-TYPE
   SYNTAX      Counter64
   MAX-ACCESS  read-only
   STATUS      current
   DESCRIPTION
      "Path: virtualEthernet.performance.pppoEClient.mibCounters.h2Performance.ifInBcastPkts

       64 bit unsigned wrappable counter."
   ::= {pr1645v2VEthPPPoEMCH2PEntry 419430400}

pr1645v2VEthPPPoEMCH2PIfInMCPkts OBJECT-TYPE
   SYNTAX      Counter64
   MAX-ACCESS  read-only
   STATUS      current
   DESCRIPTION
      "Path: virtualEthernet.performance.pppoEClient.mibCounters.h2Performance.ifInMcastPkts

       64 bit unsigned wrappable counter."
   ::= {pr1645v2VEthPPPoEMCH2PEntry 436207616}

pr1645v2VEthPPPoEMCH2PIfInDiscards OBJECT-TYPE
   SYNTAX      Counter64
   MAX-ACCESS  read-only
   STATUS      current
   DESCRIPTION
      "Path: virtualEthernet.performance.pppoEClient.mibCounters.h2Performance.ifInDiscards

       64 bit unsigned wrappable counter."
   ::= {pr1645v2VEthPPPoEMCH2PEntry 117440512}

pr1645v2VEthPPPoEMCH2PIfInErrors OBJECT-TYPE
   SYNTAX      Counter64
   MAX-ACCESS  read-only
   STATUS      current
   DESCRIPTION
      "Path: virtualEthernet.performance.pppoEClient.mibCounters.h2Performance.ifInErrors

       64 bit unsigned wrappable counter."
   ::= {pr1645v2VEthPPPoEMCH2PEntry 134217728}

pr1645v2VEthPPPoEMCH2PIfInUnkwn OBJECT-TYPE
   SYNTAX      Counter64
   MAX-ACCESS  read-only
   STATUS      current
   DESCRIPTION
      "Path: virtualEthernet.performance.pppoEClient.mibCounters.h2Performance.ifInUnknownProtos

       64 bit unsigned wrappable counter."
   ::= {pr1645v2VEthPPPoEMCH2PEntry 150994944}

pr1645v2VEthPPPoEMCH2PInDropEx OBJECT-TYPE
   SYNTAX      Counter64
   MAX-ACCESS  read-only
   STATUS      current
   DESCRIPTION
      "Path: virtualEthernet.performance.pppoEClient.mibCounters.h2Performance.ifInDropLevelExceeded

       64 bit unsigned wrappable counter."
   ::= {pr1645v2VEthPPPoEMCH2PEntry 335544320}

pr1645v2VEthPPPoEMCH2PInDropNoMac OBJECT-TYPE
   SYNTAX      Counter64
   MAX-ACCESS  read-only
   STATUS      current
   DESCRIPTION
      "Path: virtualEthernet.performance.pppoEClient.mibCounters.h2Performance.fInDiscardsNoMacFit

       64 bit unsigned wrappable counter."
   ::= {pr1645v2VEthPPPoEMCH2PEntry 301989888}

pr1645v2VEthPPPoEMCH2PInDropNUCast OBJECT-TYPE
   SYNTAX      Counter64
   MAX-ACCESS  read-only
   STATUS      current
   DESCRIPTION
      "Path: virtualEthernet.performance.pppoEClient.mibCounters.h2Performance.fInDiscardsNUCast

       64 bit unsigned wrappable counter."
   ::= {pr1645v2VEthPPPoEMCH2PEntry 318767104}

pr1645v2VEthPPPoEMCH2PInDropFilter OBJECT-TYPE
   SYNTAX      Counter64
   MAX-ACCESS  read-only
   STATUS      current
   DESCRIPTION
      "Path: virtualEthernet.performance.pppoEClient.mibCounters.h2Performance.fInDiscardsFilter

       64 bit unsigned wrappable counter."
   ::= {pr1645v2VEthPPPoEMCH2PEntry 385875968}

pr1645v2VEthPPPoEMCH2PIfInBandwidth OBJECT-TYPE
   SYNTAX      Integer32
   MAX-ACCESS  read-only
   STATUS      current
   DESCRIPTION
      "Path: virtualEthernet.performance.pppoEClient.mibCounters.h2Performance.ifInBandwidth

       unit name = bps
       formula = 8 * ; 8 /"
   ::= {pr1645v2VEthPPPoEMCH2PEntry 268435456}

pr1645v2VEthPPPoEMCH2PIfOutOctets OBJECT-TYPE
   SYNTAX      Counter64
   MAX-ACCESS  read-only
   STATUS      current
   DESCRIPTION
      "Path: virtualEthernet.performance.pppoEClient.mibCounters.h2Performance.ifOutOctets

       64 bit unsigned wrappable counter."
   ::= {pr1645v2VEthPPPoEMCH2PEntry 167772160}

pr1645v2VEthPPPoEMCH2PIfOutUCPkts OBJECT-TYPE
   SYNTAX      Counter64
   MAX-ACCESS  read-only
   STATUS      current
   DESCRIPTION
      "Path: virtualEthernet.performance.pppoEClient.mibCounters.h2Performance.ifOutUcastPkts

       64 bit unsigned wrappable counter."
   ::= {pr1645v2VEthPPPoEMCH2PEntry 184549376}

pr1645v2VEthPPPoEMCH2PIfOutNUCPkts OBJECT-TYPE
   SYNTAX      Counter64
   MAX-ACCESS  read-only
   STATUS      current
   DESCRIPTION
      "Path: virtualEthernet.performance.pppoEClient.mibCounters.h2Performance.ifOutNUcastPkts

       64 bit unsigned wrappable counter."
   ::= {pr1645v2VEthPPPoEMCH2PEntry 201326592}

pr1645v2VEthPPPoEMCH2PIfOutBCPkts OBJECT-TYPE
   SYNTAX      Counter64
   MAX-ACCESS  read-only
   STATUS      current
   DESCRIPTION
      "Path: virtualEthernet.performance.pppoEClient.mibCounters.h2Performance.ifOutBcastPkts

       64 bit unsigned wrappable counter."
   ::= {pr1645v2VEthPPPoEMCH2PEntry 452984832}

pr1645v2VEthPPPoEMCH2PIfOutMCPkts OBJECT-TYPE
   SYNTAX      Counter64
   MAX-ACCESS  read-only
   STATUS      current
   DESCRIPTION
      "Path: virtualEthernet.performance.pppoEClient.mibCounters.h2Performance.ifOutMcastPkts

       64 bit unsigned wrappable counter."
   ::= {pr1645v2VEthPPPoEMCH2PEntry 469762048}

pr1645v2VEthPPPoEMCH2PIfOutDiscards OBJECT-TYPE
   SYNTAX      Counter64
   MAX-ACCESS  read-only
   STATUS      current
   DESCRIPTION
      "Path: virtualEthernet.performance.pppoEClient.mibCounters.h2Performance.ifOutDiscards

       64 bit unsigned wrappable counter."
   ::= {pr1645v2VEthPPPoEMCH2PEntry 218103808}

pr1645v2VEthPPPoEMCH2PIfOutErrors OBJECT-TYPE
   SYNTAX      Counter64
   MAX-ACCESS  read-only
   STATUS      current
   DESCRIPTION
      "Path: virtualEthernet.performance.pppoEClient.mibCounters.h2Performance.ifOutErrors

       64 bit unsigned wrappable counter."
   ::= {pr1645v2VEthPPPoEMCH2PEntry 234881024}

pr1645v2VEthPPPoEMCH2POutDropEx OBJECT-TYPE
   SYNTAX      Counter64
   MAX-ACCESS  read-only
   STATUS      current
   DESCRIPTION
      "Path: virtualEthernet.performance.pppoEClient.mibCounters.h2Performance.ifOutDropLevelExceeded

       64 bit unsigned wrappable counter."
   ::= {pr1645v2VEthPPPoEMCH2PEntry 352321536}

pr1645v2VEthPPPoEMCH2POutDropNoArp OBJECT-TYPE
   SYNTAX      Counter64
   MAX-ACCESS  read-only
   STATUS      current
   DESCRIPTION
      "Path: virtualEthernet.performance.pppoEClient.mibCounters.h2Performance.ifOutDiscardsNoArp

       64 bit unsigned wrappable counter."
   ::= {pr1645v2VEthPPPoEMCH2PEntry 369098752}

pr1645v2VEthPPPoEMCH2POutDropFilter OBJECT-TYPE
   SYNTAX      Counter64
   MAX-ACCESS  read-only
   STATUS      current
   DESCRIPTION
      "Path: virtualEthernet.performance.pppoEClient.mibCounters.h2Performance.ifOutDiscardsFilter

       64 bit unsigned wrappable counter."
   ::= {pr1645v2VEthPPPoEMCH2PEntry 402653184}

pr1645v2VEthPPPoEMCH2PIfOutBandwidth OBJECT-TYPE
   SYNTAX      Integer32
   MAX-ACCESS  read-only
   STATUS      current
   DESCRIPTION
      "Path: virtualEthernet.performance.pppoEClient.mibCounters.h2Performance.ifOutBandwidth

       unit name = bps
       formula = 8 * ; 8 /"
   ::= {pr1645v2VEthPPPoEMCH2PEntry 285212672}

pr1645v2VEthPPPoEMCH2PIfErrSec OBJECT-TYPE
   SYNTAX      Counter32
   MAX-ACCESS  read-only
   STATUS      current
   DESCRIPTION
      "Path: virtualEthernet.performance.pppoEClient.mibCounters.h2Performance.ifErrSec

       32 bit unsigned wrappable counter."
   ::= {pr1645v2VEthPPPoEMCH2PEntry 251658240}

pr1645v2VEthPPPoEMCH24P OBJECT-TYPE
   SYNTAX      SEQUENCE OF Pr1645v2VEthPPPoEMCH24PEntry
   MAX-ACCESS  not-accessible
   STATUS      current
   DESCRIPTION
      ""
   ::= {pr1645v2VEthPPPoE 41615360}

pr1645v2VEthPPPoEMCH24PEntry OBJECT-TYPE
   SYNTAX      Pr1645v2VEthPPPoEMCH24PEntry
   MAX-ACCESS  not-accessible
   STATUS      current
   DESCRIPTION
      ""
   INDEX      { pr1645v2VEthPPPoEMCH24PGlobalIx,
                pr1645v2VEthPPPoETableIx,
                pr1645v2VEthPPPoEMCH24PTableIx }
   ::= {pr1645v2VEthPPPoEMCH24P 1}

Pr1645v2VEthPPPoEMCH24PEntry ::=
   SEQUENCE
      {
      pr1645v2VEthPPPoEMCH24PGlobalIx
         GlobalIndex,
      pr1645v2VEthPPPoEMCH24PTableIx
         TableIndex,
      pr1645v2VEthPPPoEMCH24PSysUpTime
         TimeTicks,
      pr1645v2VEthPPPoEMCH24PIfUpTime
         TimeTicks,
      pr1645v2VEthPPPoEMCH24PIfStatChanges
         Counter32,
      pr1645v2VEthPPPoEMCH24PIfInOctets
         Counter64,
      pr1645v2VEthPPPoEMCH24PIfInUCPkts
         Counter64,
      pr1645v2VEthPPPoEMCH24PIfInNUCPkts
         Counter64,
      pr1645v2VEthPPPoEMCH24PIfInBCPkts
         Counter64,
      pr1645v2VEthPPPoEMCH24PIfInMCPkts
         Counter64,
      pr1645v2VEthPPPoEMCH24PIfInDiscards
         Counter64,
      pr1645v2VEthPPPoEMCH24PIfInErrors
         Counter64,
      pr1645v2VEthPPPoEMCH24PIfInUnkwn
         Counter64,
      pr1645v2VEthPPPoEMCH24PInDropEx
         Counter64,
      pr1645v2VEthPPPoEMCH24PInDropNoMac
         Counter64,
      pr1645v2VEthPPPoEMCH24PInDropNUCast
         Counter64,
      pr1645v2VEthPPPoEMCH24PInDropFilter
         Counter64,
      pr1645v2VEthPPPoEMCH24PIfInBandwidth
         Integer32,
      pr1645v2VEthPPPoEMCH24PIfOutOctets
         Counter64,
      pr1645v2VEthPPPoEMCH24PIfOutUCPkts
         Counter64,
      pr1645v2VEthPPPoEMCH24PIfOutNUCPkts
         Counter64,
      pr1645v2VEthPPPoEMCH24PIfOutBCPkts
         Counter64,
      pr1645v2VEthPPPoEMCH24PIfOutMCPkts
         Counter64,
      pr1645v2VEthPPPoEMCH24PIfOutDiscards
         Counter64,
      pr1645v2VEthPPPoEMCH24PIfOutErrors
         Counter64,
      pr1645v2VEthPPPoEMCH24POutDropEx
         Counter64,
      pr1645v2VEthPPPoEMCH24POutDropNoArp
         Counter64,
      pr1645v2VEthPPPoEMCH24POutDropFilter
         Counter64,
      pr1645v2VEthPPPoEMCH24PIfOutBandwidth
         Integer32,
      pr1645v2VEthPPPoEMCH24PIfErrSec
         Counter32
      }

pr1645v2VEthPPPoEMCH24PGlobalIx OBJECT-TYPE
   SYNTAX      GlobalIndex
   MAX-ACCESS  not-accessible
   STATUS      current
   DESCRIPTION
      "The value of the tlsCntTreeGlobalIndex of the MANAGED OBJECT."
   ::= {pr1645v2VEthPPPoEMCH24PEntry 10}

pr1645v2VEthPPPoEMCH24PTableIx OBJECT-TYPE
   SYNTAX      TableIndex
   MAX-ACCESS  not-accessible
   STATUS      current
   DESCRIPTION
      ""
   ::= {pr1645v2VEthPPPoEMCH24PEntry 11}

pr1645v2VEthPPPoEMCH24PSysUpTime OBJECT-TYPE
   SYNTAX      TimeTicks
   MAX-ACCESS  read-only
   STATUS      current
   DESCRIPTION
      "Path: virtualEthernet.performance.pppoEClient.mibCounters.h24Performance.sysUpTime

       Time in centi-second."
   ::= {pr1645v2VEthPPPoEMCH24PEntry 16777216}

pr1645v2VEthPPPoEMCH24PIfUpTime OBJECT-TYPE
   SYNTAX      TimeTicks
   MAX-ACCESS  read-only
   STATUS      current
   DESCRIPTION
      "Path: virtualEthernet.performance.pppoEClient.mibCounters.h24Performance.ifUpTime

       Time in centi-second."
   ::= {pr1645v2VEthPPPoEMCH24PEntry 33554432}

pr1645v2VEthPPPoEMCH24PIfStatChanges OBJECT-TYPE
   SYNTAX      Counter32
   MAX-ACCESS  read-only
   STATUS      current
   DESCRIPTION
      "Path: virtualEthernet.performance.pppoEClient.mibCounters.h24Performance.ifStatusChanges

       32 bit unsigned wrappable counter."
   ::= {pr1645v2VEthPPPoEMCH24PEntry 50331648}

pr1645v2VEthPPPoEMCH24PIfInOctets OBJECT-TYPE
   SYNTAX      Counter64
   MAX-ACCESS  read-only
   STATUS      current
   DESCRIPTION
      "Path: virtualEthernet.performance.pppoEClient.mibCounters.h24Performance.ifInOctets

       64 bit unsigned wrappable counter."
   ::= {pr1645v2VEthPPPoEMCH24PEntry 67108864}

pr1645v2VEthPPPoEMCH24PIfInUCPkts OBJECT-TYPE
   SYNTAX      Counter64
   MAX-ACCESS  read-only
   STATUS      current
   DESCRIPTION
      "Path: virtualEthernet.performance.pppoEClient.mibCounters.h24Performance.ifInUcastPkts

       64 bit unsigned wrappable counter."
   ::= {pr1645v2VEthPPPoEMCH24PEntry 83886080}

pr1645v2VEthPPPoEMCH24PIfInNUCPkts OBJECT-TYPE
   SYNTAX      Counter64
   MAX-ACCESS  read-only
   STATUS      current
   DESCRIPTION
      "Path: virtualEthernet.performance.pppoEClient.mibCounters.h24Performance.ifInNUcastPkts

       64 bit unsigned wrappable counter."
   ::= {pr1645v2VEthPPPoEMCH24PEntry 100663296}

pr1645v2VEthPPPoEMCH24PIfInBCPkts OBJECT-TYPE
   SYNTAX      Counter64
   MAX-ACCESS  read-only
   STATUS      current
   DESCRIPTION
      "Path: virtualEthernet.performance.pppoEClient.mibCounters.h24Performance.ifInBcastPkts

       64 bit unsigned wrappable counter."
   ::= {pr1645v2VEthPPPoEMCH24PEntry 419430400}

pr1645v2VEthPPPoEMCH24PIfInMCPkts OBJECT-TYPE
   SYNTAX      Counter64
   MAX-ACCESS  read-only
   STATUS      current
   DESCRIPTION
      "Path: virtualEthernet.performance.pppoEClient.mibCounters.h24Performance.ifInMcastPkts

       64 bit unsigned wrappable counter."
   ::= {pr1645v2VEthPPPoEMCH24PEntry 436207616}

pr1645v2VEthPPPoEMCH24PIfInDiscards OBJECT-TYPE
   SYNTAX      Counter64
   MAX-ACCESS  read-only
   STATUS      current
   DESCRIPTION
      "Path: virtualEthernet.performance.pppoEClient.mibCounters.h24Performance.ifInDiscards

       64 bit unsigned wrappable counter."
   ::= {pr1645v2VEthPPPoEMCH24PEntry 117440512}

pr1645v2VEthPPPoEMCH24PIfInErrors OBJECT-TYPE
   SYNTAX      Counter64
   MAX-ACCESS  read-only
   STATUS      current
   DESCRIPTION
      "Path: virtualEthernet.performance.pppoEClient.mibCounters.h24Performance.ifInErrors

       64 bit unsigned wrappable counter."
   ::= {pr1645v2VEthPPPoEMCH24PEntry 134217728}

pr1645v2VEthPPPoEMCH24PIfInUnkwn OBJECT-TYPE
   SYNTAX      Counter64
   MAX-ACCESS  read-only
   STATUS      current
   DESCRIPTION
      "Path: virtualEthernet.performance.pppoEClient.mibCounters.h24Performance.ifInUnknownProtos

       64 bit unsigned wrappable counter."
   ::= {pr1645v2VEthPPPoEMCH24PEntry 150994944}

pr1645v2VEthPPPoEMCH24PInDropEx OBJECT-TYPE
   SYNTAX      Counter64
   MAX-ACCESS  read-only
   STATUS      current
   DESCRIPTION
      "Path: virtualEthernet.performance.pppoEClient.mibCounters.h24Performance.ifInDropLevelExceeded

       64 bit unsigned wrappable counter."
   ::= {pr1645v2VEthPPPoEMCH24PEntry 335544320}

pr1645v2VEthPPPoEMCH24PInDropNoMac OBJECT-TYPE
   SYNTAX      Counter64
   MAX-ACCESS  read-only
   STATUS      current
   DESCRIPTION
      "Path: virtualEthernet.performance.pppoEClient.mibCounters.h24Performance.fInDiscardsNoMacFit

       64 bit unsigned wrappable counter."
   ::= {pr1645v2VEthPPPoEMCH24PEntry 301989888}

pr1645v2VEthPPPoEMCH24PInDropNUCast OBJECT-TYPE
   SYNTAX      Counter64
   MAX-ACCESS  read-only
   STATUS      current
   DESCRIPTION
      "Path: virtualEthernet.performance.pppoEClient.mibCounters.h24Performance.fInDiscardsNUCast

       64 bit unsigned wrappable counter."
   ::= {pr1645v2VEthPPPoEMCH24PEntry 318767104}

pr1645v2VEthPPPoEMCH24PInDropFilter OBJECT-TYPE
   SYNTAX      Counter64
   MAX-ACCESS  read-only
   STATUS      current
   DESCRIPTION
      "Path: virtualEthernet.performance.pppoEClient.mibCounters.h24Performance.fInDiscardsFilter

       64 bit unsigned wrappable counter."
   ::= {pr1645v2VEthPPPoEMCH24PEntry 385875968}

pr1645v2VEthPPPoEMCH24PIfInBandwidth OBJECT-TYPE
   SYNTAX      Integer32
   MAX-ACCESS  read-only
   STATUS      current
   DESCRIPTION
      "Path: virtualEthernet.performance.pppoEClient.mibCounters.h24Performance.ifInBandwidth

       unit name = bps
       formula = 8 * ; 8 /"
   ::= {pr1645v2VEthPPPoEMCH24PEntry 268435456}

pr1645v2VEthPPPoEMCH24PIfOutOctets OBJECT-TYPE
   SYNTAX      Counter64
   MAX-ACCESS  read-only
   STATUS      current
   DESCRIPTION
      "Path: virtualEthernet.performance.pppoEClient.mibCounters.h24Performance.ifOutOctets

       64 bit unsigned wrappable counter."
   ::= {pr1645v2VEthPPPoEMCH24PEntry 167772160}

pr1645v2VEthPPPoEMCH24PIfOutUCPkts OBJECT-TYPE
   SYNTAX      Counter64
   MAX-ACCESS  read-only
   STATUS      current
   DESCRIPTION
      "Path: virtualEthernet.performance.pppoEClient.mibCounters.h24Performance.ifOutUcastPkts

       64 bit unsigned wrappable counter."
   ::= {pr1645v2VEthPPPoEMCH24PEntry 184549376}

pr1645v2VEthPPPoEMCH24PIfOutNUCPkts OBJECT-TYPE
   SYNTAX      Counter64
   MAX-ACCESS  read-only
   STATUS      current
   DESCRIPTION
      "Path: virtualEthernet.performance.pppoEClient.mibCounters.h24Performance.ifOutNUcastPkts

       64 bit unsigned wrappable counter."
   ::= {pr1645v2VEthPPPoEMCH24PEntry 201326592}

pr1645v2VEthPPPoEMCH24PIfOutBCPkts OBJECT-TYPE
   SYNTAX      Counter64
   MAX-ACCESS  read-only
   STATUS      current
   DESCRIPTION
      "Path: virtualEthernet.performance.pppoEClient.mibCounters.h24Performance.ifOutBcastPkts

       64 bit unsigned wrappable counter."
   ::= {pr1645v2VEthPPPoEMCH24PEntry 452984832}

pr1645v2VEthPPPoEMCH24PIfOutMCPkts OBJECT-TYPE
   SYNTAX      Counter64
   MAX-ACCESS  read-only
   STATUS      current
   DESCRIPTION
      "Path: virtualEthernet.performance.pppoEClient.mibCounters.h24Performance.ifOutMcastPkts

       64 bit unsigned wrappable counter."
   ::= {pr1645v2VEthPPPoEMCH24PEntry 469762048}

pr1645v2VEthPPPoEMCH24PIfOutDiscards OBJECT-TYPE
   SYNTAX      Counter64
   MAX-ACCESS  read-only
   STATUS      current
   DESCRIPTION
      "Path: virtualEthernet.performance.pppoEClient.mibCounters.h24Performance.ifOutDiscards

       64 bit unsigned wrappable counter."
   ::= {pr1645v2VEthPPPoEMCH24PEntry 218103808}

pr1645v2VEthPPPoEMCH24PIfOutErrors OBJECT-TYPE
   SYNTAX      Counter64
   MAX-ACCESS  read-only
   STATUS      current
   DESCRIPTION
      "Path: virtualEthernet.performance.pppoEClient.mibCounters.h24Performance.ifOutErrors

       64 bit unsigned wrappable counter."
   ::= {pr1645v2VEthPPPoEMCH24PEntry 234881024}

pr1645v2VEthPPPoEMCH24POutDropEx OBJECT-TYPE
   SYNTAX      Counter64
   MAX-ACCESS  read-only
   STATUS      current
   DESCRIPTION
      "Path: virtualEthernet.performance.pppoEClient.mibCounters.h24Performance.ifOutDropLevelExceeded

       64 bit unsigned wrappable counter."
   ::= {pr1645v2VEthPPPoEMCH24PEntry 352321536}

pr1645v2VEthPPPoEMCH24POutDropNoArp OBJECT-TYPE
   SYNTAX      Counter64
   MAX-ACCESS  read-only
   STATUS      current
   DESCRIPTION
      "Path: virtualEthernet.performance.pppoEClient.mibCounters.h24Performance.ifOutDiscardsNoArp

       64 bit unsigned wrappable counter."
   ::= {pr1645v2VEthPPPoEMCH24PEntry 369098752}

pr1645v2VEthPPPoEMCH24POutDropFilter OBJECT-TYPE
   SYNTAX      Counter64
   MAX-ACCESS  read-only
   STATUS      current
   DESCRIPTION
      "Path: virtualEthernet.performance.pppoEClient.mibCounters.h24Performance.ifOutDiscardsFilter

       64 bit unsigned wrappable counter."
   ::= {pr1645v2VEthPPPoEMCH24PEntry 402653184}

pr1645v2VEthPPPoEMCH24PIfOutBandwidth OBJECT-TYPE
   SYNTAX      Integer32
   MAX-ACCESS  read-only
   STATUS      current
   DESCRIPTION
      "Path: virtualEthernet.performance.pppoEClient.mibCounters.h24Performance.ifOutBandwidth

       unit name = bps
       formula = 8 * ; 8 /"
   ::= {pr1645v2VEthPPPoEMCH24PEntry 285212672}

pr1645v2VEthPPPoEMCH24PIfErrSec OBJECT-TYPE
   SYNTAX      Counter32
   MAX-ACCESS  read-only
   STATUS      current
   DESCRIPTION
      "Path: virtualEthernet.performance.pppoEClient.mibCounters.h24Performance.ifErrSec

       32 bit unsigned wrappable counter."
   ::= {pr1645v2VEthPPPoEMCH24PEntry 251658240}

pr1645v2VEthPPPoEMCD7P OBJECT-TYPE
   SYNTAX      SEQUENCE OF Pr1645v2VEthPPPoEMCD7PEntry
   MAX-ACCESS  not-accessible
   STATUS      current
   DESCRIPTION
      ""
   ::= {pr1645v2VEthPPPoE 41680896}

pr1645v2VEthPPPoEMCD7PEntry OBJECT-TYPE
   SYNTAX      Pr1645v2VEthPPPoEMCD7PEntry
   MAX-ACCESS  not-accessible
   STATUS      current
   DESCRIPTION
      ""
   INDEX      { pr1645v2VEthPPPoEMCD7PGlobalIx,
                pr1645v2VEthPPPoETableIx,
                pr1645v2VEthPPPoEMCD7PTableIx }
   ::= {pr1645v2VEthPPPoEMCD7P 1}

Pr1645v2VEthPPPoEMCD7PEntry ::=
   SEQUENCE
      {
      pr1645v2VEthPPPoEMCD7PGlobalIx
         GlobalIndex,
      pr1645v2VEthPPPoEMCD7PTableIx
         TableIndex,
      pr1645v2VEthPPPoEMCD7PSysUpTime
         TimeTicks,
      pr1645v2VEthPPPoEMCD7PIfUpTime
         TimeTicks,
      pr1645v2VEthPPPoEMCD7PIfStatChanges
         Counter32,
      pr1645v2VEthPPPoEMCD7PIfInOctets
         Counter64,
      pr1645v2VEthPPPoEMCD7PIfInUCPkts
         Counter64,
      pr1645v2VEthPPPoEMCD7PIfInNUCPkts
         Counter64,
      pr1645v2VEthPPPoEMCD7PIfInBCPkts
         Counter64,
      pr1645v2VEthPPPoEMCD7PIfInMCPkts
         Counter64,
      pr1645v2VEthPPPoEMCD7PIfInDiscards
         Counter64,
      pr1645v2VEthPPPoEMCD7PIfInErrors
         Counter64,
      pr1645v2VEthPPPoEMCD7PIfInUnkwn
         Counter64,
      pr1645v2VEthPPPoEMCD7PInDropEx
         Counter64,
      pr1645v2VEthPPPoEMCD7PInDropNoMac
         Counter64,
      pr1645v2VEthPPPoEMCD7PInDropNUCast
         Counter64,
      pr1645v2VEthPPPoEMCD7PInDropFilter
         Counter64,
      pr1645v2VEthPPPoEMCD7PIfInBandwidth
         Integer32,
      pr1645v2VEthPPPoEMCD7PIfOutOctets
         Counter64,
      pr1645v2VEthPPPoEMCD7PIfOutUCPkts
         Counter64,
      pr1645v2VEthPPPoEMCD7PIfOutNUCPkts
         Counter64,
      pr1645v2VEthPPPoEMCD7PIfOutBCPkts
         Counter64,
      pr1645v2VEthPPPoEMCD7PIfOutMCPkts
         Counter64,
      pr1645v2VEthPPPoEMCD7PIfOutDiscards
         Counter64,
      pr1645v2VEthPPPoEMCD7PIfOutErrors
         Counter64,
      pr1645v2VEthPPPoEMCD7POutDropEx
         Counter64,
      pr1645v2VEthPPPoEMCD7POutDropNoArp
         Counter64,
      pr1645v2VEthPPPoEMCD7POutDropFilter
         Counter64,
      pr1645v2VEthPPPoEMCD7PIfOutBandwidth
         Integer32,
      pr1645v2VEthPPPoEMCD7PIfErrSec
         Counter32
      }

pr1645v2VEthPPPoEMCD7PGlobalIx OBJECT-TYPE
   SYNTAX      GlobalIndex
   MAX-ACCESS  not-accessible
   STATUS      current
   DESCRIPTION
      "The value of the tlsCntTreeGlobalIndex of the MANAGED OBJECT."
   ::= {pr1645v2VEthPPPoEMCD7PEntry 10}

pr1645v2VEthPPPoEMCD7PTableIx OBJECT-TYPE
   SYNTAX      TableIndex
   MAX-ACCESS  not-accessible
   STATUS      current
   DESCRIPTION
      ""
   ::= {pr1645v2VEthPPPoEMCD7PEntry 11}

pr1645v2VEthPPPoEMCD7PSysUpTime OBJECT-TYPE
   SYNTAX      TimeTicks
   MAX-ACCESS  read-only
   STATUS      current
   DESCRIPTION
      "Path: virtualEthernet.performance.pppoEClient.mibCounters.d7Performance.sysUpTime

       Time in centi-second."
   ::= {pr1645v2VEthPPPoEMCD7PEntry 16777216}

pr1645v2VEthPPPoEMCD7PIfUpTime OBJECT-TYPE
   SYNTAX      TimeTicks
   MAX-ACCESS  read-only
   STATUS      current
   DESCRIPTION
      "Path: virtualEthernet.performance.pppoEClient.mibCounters.d7Performance.ifUpTime

       Time in centi-second."
   ::= {pr1645v2VEthPPPoEMCD7PEntry 33554432}

pr1645v2VEthPPPoEMCD7PIfStatChanges OBJECT-TYPE
   SYNTAX      Counter32
   MAX-ACCESS  read-only
   STATUS      current
   DESCRIPTION
      "Path: virtualEthernet.performance.pppoEClient.mibCounters.d7Performance.ifStatusChanges

       32 bit unsigned wrappable counter."
   ::= {pr1645v2VEthPPPoEMCD7PEntry 50331648}

pr1645v2VEthPPPoEMCD7PIfInOctets OBJECT-TYPE
   SYNTAX      Counter64
   MAX-ACCESS  read-only
   STATUS      current
   DESCRIPTION
      "Path: virtualEthernet.performance.pppoEClient.mibCounters.d7Performance.ifInOctets

       64 bit unsigned wrappable counter."
   ::= {pr1645v2VEthPPPoEMCD7PEntry 67108864}

pr1645v2VEthPPPoEMCD7PIfInUCPkts OBJECT-TYPE
   SYNTAX      Counter64
   MAX-ACCESS  read-only
   STATUS      current
   DESCRIPTION
      "Path: virtualEthernet.performance.pppoEClient.mibCounters.d7Performance.ifInUcastPkts

       64 bit unsigned wrappable counter."
   ::= {pr1645v2VEthPPPoEMCD7PEntry 83886080}

pr1645v2VEthPPPoEMCD7PIfInNUCPkts OBJECT-TYPE
   SYNTAX      Counter64
   MAX-ACCESS  read-only
   STATUS      current
   DESCRIPTION
      "Path: virtualEthernet.performance.pppoEClient.mibCounters.d7Performance.ifInNUcastPkts

       64 bit unsigned wrappable counter."
   ::= {pr1645v2VEthPPPoEMCD7PEntry 100663296}

pr1645v2VEthPPPoEMCD7PIfInBCPkts OBJECT-TYPE
   SYNTAX      Counter64
   MAX-ACCESS  read-only
   STATUS      current
   DESCRIPTION
      "Path: virtualEthernet.performance.pppoEClient.mibCounters.d7Performance.ifInBcastPkts

       64 bit unsigned wrappable counter."
   ::= {pr1645v2VEthPPPoEMCD7PEntry 419430400}

pr1645v2VEthPPPoEMCD7PIfInMCPkts OBJECT-TYPE
   SYNTAX      Counter64
   MAX-ACCESS  read-only
   STATUS      current
   DESCRIPTION
      "Path: virtualEthernet.performance.pppoEClient.mibCounters.d7Performance.ifInMcastPkts

       64 bit unsigned wrappable counter."
   ::= {pr1645v2VEthPPPoEMCD7PEntry 436207616}

pr1645v2VEthPPPoEMCD7PIfInDiscards OBJECT-TYPE
   SYNTAX      Counter64
   MAX-ACCESS  read-only
   STATUS      current
   DESCRIPTION
      "Path: virtualEthernet.performance.pppoEClient.mibCounters.d7Performance.ifInDiscards

       64 bit unsigned wrappable counter."
   ::= {pr1645v2VEthPPPoEMCD7PEntry 117440512}

pr1645v2VEthPPPoEMCD7PIfInErrors OBJECT-TYPE
   SYNTAX      Counter64
   MAX-ACCESS  read-only
   STATUS      current
   DESCRIPTION
      "Path: virtualEthernet.performance.pppoEClient.mibCounters.d7Performance.ifInErrors

       64 bit unsigned wrappable counter."
   ::= {pr1645v2VEthPPPoEMCD7PEntry 134217728}

pr1645v2VEthPPPoEMCD7PIfInUnkwn OBJECT-TYPE
   SYNTAX      Counter64
   MAX-ACCESS  read-only
   STATUS      current
   DESCRIPTION
      "Path: virtualEthernet.performance.pppoEClient.mibCounters.d7Performance.ifInUnknownProtos

       64 bit unsigned wrappable counter."
   ::= {pr1645v2VEthPPPoEMCD7PEntry 150994944}

pr1645v2VEthPPPoEMCD7PInDropEx OBJECT-TYPE
   SYNTAX      Counter64
   MAX-ACCESS  read-only
   STATUS      current
   DESCRIPTION
      "Path: virtualEthernet.performance.pppoEClient.mibCounters.d7Performance.ifInDropLevelExceeded

       64 bit unsigned wrappable counter."
   ::= {pr1645v2VEthPPPoEMCD7PEntry 335544320}

pr1645v2VEthPPPoEMCD7PInDropNoMac OBJECT-TYPE
   SYNTAX      Counter64
   MAX-ACCESS  read-only
   STATUS      current
   DESCRIPTION
      "Path: virtualEthernet.performance.pppoEClient.mibCounters.d7Performance.fInDiscardsNoMacFit

       64 bit unsigned wrappable counter."
   ::= {pr1645v2VEthPPPoEMCD7PEntry 301989888}

pr1645v2VEthPPPoEMCD7PInDropNUCast OBJECT-TYPE
   SYNTAX      Counter64
   MAX-ACCESS  read-only
   STATUS      current
   DESCRIPTION
      "Path: virtualEthernet.performance.pppoEClient.mibCounters.d7Performance.fInDiscardsNUCast

       64 bit unsigned wrappable counter."
   ::= {pr1645v2VEthPPPoEMCD7PEntry 318767104}

pr1645v2VEthPPPoEMCD7PInDropFilter OBJECT-TYPE
   SYNTAX      Counter64
   MAX-ACCESS  read-only
   STATUS      current
   DESCRIPTION
      "Path: virtualEthernet.performance.pppoEClient.mibCounters.d7Performance.fInDiscardsFilter

       64 bit unsigned wrappable counter."
   ::= {pr1645v2VEthPPPoEMCD7PEntry 385875968}

pr1645v2VEthPPPoEMCD7PIfInBandwidth OBJECT-TYPE
   SYNTAX      Integer32
   MAX-ACCESS  read-only
   STATUS      current
   DESCRIPTION
      "Path: virtualEthernet.performance.pppoEClient.mibCounters.d7Performance.ifInBandwidth

       unit name = bps
       formula = 8 * ; 8 /"
   ::= {pr1645v2VEthPPPoEMCD7PEntry 268435456}

pr1645v2VEthPPPoEMCD7PIfOutOctets OBJECT-TYPE
   SYNTAX      Counter64
   MAX-ACCESS  read-only
   STATUS      current
   DESCRIPTION
      "Path: virtualEthernet.performance.pppoEClient.mibCounters.d7Performance.ifOutOctets

       64 bit unsigned wrappable counter."
   ::= {pr1645v2VEthPPPoEMCD7PEntry 167772160}

pr1645v2VEthPPPoEMCD7PIfOutUCPkts OBJECT-TYPE
   SYNTAX      Counter64
   MAX-ACCESS  read-only
   STATUS      current
   DESCRIPTION
      "Path: virtualEthernet.performance.pppoEClient.mibCounters.d7Performance.ifOutUcastPkts

       64 bit unsigned wrappable counter."
   ::= {pr1645v2VEthPPPoEMCD7PEntry 184549376}

pr1645v2VEthPPPoEMCD7PIfOutNUCPkts OBJECT-TYPE
   SYNTAX      Counter64
   MAX-ACCESS  read-only
   STATUS      current
   DESCRIPTION
      "Path: virtualEthernet.performance.pppoEClient.mibCounters.d7Performance.ifOutNUcastPkts

       64 bit unsigned wrappable counter."
   ::= {pr1645v2VEthPPPoEMCD7PEntry 201326592}

pr1645v2VEthPPPoEMCD7PIfOutBCPkts OBJECT-TYPE
   SYNTAX      Counter64
   MAX-ACCESS  read-only
   STATUS      current
   DESCRIPTION
      "Path: virtualEthernet.performance.pppoEClient.mibCounters.d7Performance.ifOutBcastPkts

       64 bit unsigned wrappable counter."
   ::= {pr1645v2VEthPPPoEMCD7PEntry 452984832}

pr1645v2VEthPPPoEMCD7PIfOutMCPkts OBJECT-TYPE
   SYNTAX      Counter64
   MAX-ACCESS  read-only
   STATUS      current
   DESCRIPTION
      "Path: virtualEthernet.performance.pppoEClient.mibCounters.d7Performance.ifOutMcastPkts

       64 bit unsigned wrappable counter."
   ::= {pr1645v2VEthPPPoEMCD7PEntry 469762048}

pr1645v2VEthPPPoEMCD7PIfOutDiscards OBJECT-TYPE
   SYNTAX      Counter64
   MAX-ACCESS  read-only
   STATUS      current
   DESCRIPTION
      "Path: virtualEthernet.performance.pppoEClient.mibCounters.d7Performance.ifOutDiscards

       64 bit unsigned wrappable counter."
   ::= {pr1645v2VEthPPPoEMCD7PEntry 218103808}

pr1645v2VEthPPPoEMCD7PIfOutErrors OBJECT-TYPE
   SYNTAX      Counter64
   MAX-ACCESS  read-only
   STATUS      current
   DESCRIPTION
      "Path: virtualEthernet.performance.pppoEClient.mibCounters.d7Performance.ifOutErrors

       64 bit unsigned wrappable counter."
   ::= {pr1645v2VEthPPPoEMCD7PEntry 234881024}

pr1645v2VEthPPPoEMCD7POutDropEx OBJECT-TYPE
   SYNTAX      Counter64
   MAX-ACCESS  read-only
   STATUS      current
   DESCRIPTION
      "Path: virtualEthernet.performance.pppoEClient.mibCounters.d7Performance.ifOutDropLevelExceeded

       64 bit unsigned wrappable counter."
   ::= {pr1645v2VEthPPPoEMCD7PEntry 352321536}

pr1645v2VEthPPPoEMCD7POutDropNoArp OBJECT-TYPE
   SYNTAX      Counter64
   MAX-ACCESS  read-only
   STATUS      current
   DESCRIPTION
      "Path: virtualEthernet.performance.pppoEClient.mibCounters.d7Performance.ifOutDiscardsNoArp

       64 bit unsigned wrappable counter."
   ::= {pr1645v2VEthPPPoEMCD7PEntry 369098752}

pr1645v2VEthPPPoEMCD7POutDropFilter OBJECT-TYPE
   SYNTAX      Counter64
   MAX-ACCESS  read-only
   STATUS      current
   DESCRIPTION
      "Path: virtualEthernet.performance.pppoEClient.mibCounters.d7Performance.ifOutDiscardsFilter

       64 bit unsigned wrappable counter."
   ::= {pr1645v2VEthPPPoEMCD7PEntry 402653184}

pr1645v2VEthPPPoEMCD7PIfOutBandwidth OBJECT-TYPE
   SYNTAX      Integer32
   MAX-ACCESS  read-only
   STATUS      current
   DESCRIPTION
      "Path: virtualEthernet.performance.pppoEClient.mibCounters.d7Performance.ifOutBandwidth

       unit name = bps
       formula = 8 * ; 8 /"
   ::= {pr1645v2VEthPPPoEMCD7PEntry 285212672}

pr1645v2VEthPPPoEMCD7PIfErrSec OBJECT-TYPE
   SYNTAX      Counter32
   MAX-ACCESS  read-only
   STATUS      current
   DESCRIPTION
      "Path: virtualEthernet.performance.pppoEClient.mibCounters.d7Performance.ifErrSec

       32 bit unsigned wrappable counter."
   ::= {pr1645v2VEthPPPoEMCD7PEntry 251658240}



ar1645v2VEth OBJECT IDENTIFIER ::= {r1645v2VEth 16}


ar1645v2VEthClearCounters OBJECT IDENTIFIER ::= {ar1645v2VEth 263}

ar1645v2VEthClearCountersTable OBJECT-TYPE
   SYNTAX      SEQUENCE OF Ar1645v2VEthClearCountersEntry
   MAX-ACCESS  not-accessible
   STATUS      current
   DESCRIPTION
      "reset counters"
   ::= {ar1645v2VEthClearCounters 1}

ar1645v2VEthClearCountersEntry OBJECT-TYPE
   SYNTAX      Ar1645v2VEthClearCountersEntry
   MAX-ACCESS  not-accessible
   STATUS      current
   DESCRIPTION
      ""
   INDEX      { ar1645v2VEthClearCountersGlobalIx }
   ::= {ar1645v2VEthClearCountersTable 1}

Ar1645v2VEthClearCountersEntry ::=
   SEQUENCE
      {
      ar1645v2VEthClearCountersGlobalIx
         GlobalIndex,
      ar1645v2VEthClearCountersValue
         Integer32
      }

ar1645v2VEthClearCountersGlobalIx OBJECT-TYPE
   SYNTAX      GlobalIndex
   MAX-ACCESS  not-accessible
   STATUS      current
   DESCRIPTION
      "The value of the tlsCntTreeGlobalIndex of the MANAGED OBJECT."
   ::= {ar1645v2VEthClearCountersEntry 10}

ar1645v2VEthClearCountersValue OBJECT-TYPE
   SYNTAX      Integer32
   MAX-ACCESS  read-write
   STATUS      current
   DESCRIPTION
      "Path: virtualEthernet.actions.clearCounters"
   ::= {ar1645v2VEthClearCountersEntry 2147483648}


ar1645v2VEthRestartIntf OBJECT IDENTIFIER ::= {ar1645v2VEth 67}

ar1645v2VEthRestartIntfTable OBJECT-TYPE
   SYNTAX      SEQUENCE OF Ar1645v2VEthRestartIntfEntry
   MAX-ACCESS  not-accessible
   STATUS      current
   DESCRIPTION
      "action in the debug group"
   ::= {ar1645v2VEthRestartIntf 1}

ar1645v2VEthRestartIntfEntry OBJECT-TYPE
   SYNTAX      Ar1645v2VEthRestartIntfEntry
   MAX-ACCESS  not-accessible
   STATUS      current
   DESCRIPTION
      ""
   INDEX      { ar1645v2VEthRestartIntfGlobalIx }
   ::= {ar1645v2VEthRestartIntfTable 1}

Ar1645v2VEthRestartIntfEntry ::=
   SEQUENCE
      {
      ar1645v2VEthRestartIntfGlobalIx
         GlobalIndex,
      ar1645v2VEthRestartIntfValue
         Integer32
      }

ar1645v2VEthRestartIntfGlobalIx OBJECT-TYPE
   SYNTAX      GlobalIndex
   MAX-ACCESS  not-accessible
   STATUS      current
   DESCRIPTION
      "The value of the tlsCntTreeGlobalIndex of the MANAGED OBJECT."
   ::= {ar1645v2VEthRestartIntfEntry 10}

ar1645v2VEthRestartIntfValue OBJECT-TYPE
   SYNTAX      Integer32
   MAX-ACCESS  read-write
   STATUS      current
   DESCRIPTION
      "Path: virtualEthernet.actions.restartIntf"
   ::= {ar1645v2VEthRestartIntfEntry 2147483648}


ar1645v2VEthClearOamEventLog OBJECT IDENTIFIER ::= {ar1645v2VEth 916}

ar1645v2VEthClearOamEventLogTable OBJECT-TYPE
   SYNTAX      SEQUENCE OF Ar1645v2VEthClearOamEventLogEntry
   MAX-ACCESS  not-accessible
   STATUS      current
   DESCRIPTION
      "clear the OAM event log"
   ::= {ar1645v2VEthClearOamEventLog 1}

ar1645v2VEthClearOamEventLogEntry OBJECT-TYPE
   SYNTAX      Ar1645v2VEthClearOamEventLogEntry
   MAX-ACCESS  not-accessible
   STATUS      current
   DESCRIPTION
      ""
   INDEX      { ar1645v2VEthClearOamEventLogGlobalIx }
   ::= {ar1645v2VEthClearOamEventLogTable 1}

Ar1645v2VEthClearOamEventLogEntry ::=
   SEQUENCE
      {
      ar1645v2VEthClearOamEventLogGlobalIx
         GlobalIndex,
      ar1645v2VEthClearOamEventLogValue
         Integer32
      }

ar1645v2VEthClearOamEventLogGlobalIx OBJECT-TYPE
   SYNTAX      GlobalIndex
   MAX-ACCESS  not-accessible
   STATUS      current
   DESCRIPTION
      "The value of the tlsCntTreeGlobalIndex of the MANAGED OBJECT."
   ::= {ar1645v2VEthClearOamEventLogEntry 10}

ar1645v2VEthClearOamEventLogValue OBJECT-TYPE
   SYNTAX      Integer32
   MAX-ACCESS  read-write
   STATUS      current
   DESCRIPTION
      "Path: virtualEthernet.actions.clearOamEventLog"
   ::= {ar1645v2VEthClearOamEventLogEntry 2147483648}


ar1645v2VEthLoopback OBJECT IDENTIFIER ::= {ar1645v2VEth 914}

ar1645v2VEthLoopbackTable OBJECT-TYPE
   SYNTAX      SEQUENCE OF Ar1645v2VEthLoopbackEntry
   MAX-ACCESS  not-accessible
   STATUS      current
   DESCRIPTION
      "ethernet loopback"
   ::= {ar1645v2VEthLoopback 1}

ar1645v2VEthLoopbackEntry OBJECT-TYPE
   SYNTAX      Ar1645v2VEthLoopbackEntry
   MAX-ACCESS  not-accessible
   STATUS      current
   DESCRIPTION
      ""
   INDEX      { ar1645v2VEthLoopbackGlobalIx }
   ::= {ar1645v2VEthLoopbackTable 1}

Ar1645v2VEthLoopbackEntry ::=
   SEQUENCE
      {
      ar1645v2VEthLoopbackGlobalIx
         GlobalIndex,
      ar1645v2VEthLoopbackValue
         Integer32
      }

ar1645v2VEthLoopbackGlobalIx OBJECT-TYPE
   SYNTAX      GlobalIndex
   MAX-ACCESS  not-accessible
   STATUS      current
   DESCRIPTION
      "The value of the tlsCntTreeGlobalIndex of the MANAGED OBJECT."
   ::= {ar1645v2VEthLoopbackEntry 10}

ar1645v2VEthLoopbackValue OBJECT-TYPE
   SYNTAX      Integer32
   MAX-ACCESS  read-write
   STATUS      current
   DESCRIPTION
      "Path: virtualEthernet.actions.loopback"
   ::= {ar1645v2VEthLoopbackEntry 2147483648}


ar1645v2VEthLoop OBJECT IDENTIFIER ::= {ar1645v2VEth 915}

ar1645v2VEthLoopSSCTable OBJECT-TYPE
   SYNTAX      SEQUENCE OF Ar1645v2VEthLoopEntry
   MAX-ACCESS  not-accessible
   STATUS      current
   DESCRIPTION
      "ethernet loopback type"
   ::= {ar1645v2VEthLoop 1}

ar1645v2VEthLoopEntry OBJECT-TYPE
   SYNTAX      Ar1645v2VEthLoopEntry
   MAX-ACCESS  not-accessible
   STATUS      current
   DESCRIPTION
      ""
   INDEX      { ar1645v2VEthLoopGlobalIx }
   ::= {ar1645v2VEthLoopSSCTable 1}

Ar1645v2VEthLoopEntry ::=
   SEQUENCE
      {
      ar1645v2VEthLoopGlobalIx
         GlobalIndex,
      ar1645v2VEthLoopAction
         INTEGER,
      ar1645v2VEthLoopTime
         TimeTicks,
      ar1645v2VEthLoopIntfName
         DisplayString
      }

ar1645v2VEthLoopGlobalIx OBJECT-TYPE
   SYNTAX      GlobalIndex
   MAX-ACCESS  not-accessible
   STATUS      current
   DESCRIPTION
      "The value of the tlsCntTreeGlobalIndex of the MANAGED OBJECT."
   ::= {ar1645v2VEthLoopEntry 10}

ar1645v2VEthLoopAction OBJECT-TYPE
   SYNTAX      INTEGER
               {
               start (1),
               stop (2)
               }
   MAX-ACCESS  read-write
   STATUS      current
   DESCRIPTION
      "Path: virtualEthernet.actions.loop.action

       Possibilities:
               start   (1)
               stop   (2)"
   ::= {ar1645v2VEthLoopEntry 16777216}

ar1645v2VEthLoopTime OBJECT-TYPE
   SYNTAX      TimeTicks
   MAX-ACCESS  read-write
   STATUS      current
   DESCRIPTION
      "Path: virtualEthernet.actions.loop.time

       Time in centi-second."
   ::= {ar1645v2VEthLoopEntry 50331648}

ar1645v2VEthLoopIntfName OBJECT-TYPE
   SYNTAX      DisplayString
   MAX-ACCESS  read-write
   STATUS      current
   DESCRIPTION
      "Path: virtualEthernet.actions.loop.intfName"
   ::= {ar1645v2VEthLoopEntry 67108864}


ar1645v2VEthOamRemLoopback OBJECT IDENTIFIER ::= {ar1645v2VEth 912}

ar1645v2VEthOamRemLoopbackTable OBJECT-TYPE
   SYNTAX      SEQUENCE OF Ar1645v2VEthOamRemLoopbackEntry
   MAX-ACCESS  not-accessible
   STATUS      current
   DESCRIPTION
      "OAM Remote Loopback"
   ::= {ar1645v2VEthOamRemLoopback 1}

ar1645v2VEthOamRemLoopbackEntry OBJECT-TYPE
   SYNTAX      Ar1645v2VEthOamRemLoopbackEntry
   MAX-ACCESS  not-accessible
   STATUS      current
   DESCRIPTION
      ""
   INDEX      { ar1645v2VEthOamRemLoopbackGlobalIx }
   ::= {ar1645v2VEthOamRemLoopbackTable 1}

Ar1645v2VEthOamRemLoopbackEntry ::=
   SEQUENCE
      {
      ar1645v2VEthOamRemLoopbackGlobalIx
         GlobalIndex,
      ar1645v2VEthOamRemLoopbackValue
         Integer32
      }

ar1645v2VEthOamRemLoopbackGlobalIx OBJECT-TYPE
   SYNTAX      GlobalIndex
   MAX-ACCESS  not-accessible
   STATUS      current
   DESCRIPTION
      "The value of the tlsCntTreeGlobalIndex of the MANAGED OBJECT."
   ::= {ar1645v2VEthOamRemLoopbackEntry 10}

ar1645v2VEthOamRemLoopbackValue OBJECT-TYPE
   SYNTAX      Integer32
   MAX-ACCESS  read-write
   STATUS      current
   DESCRIPTION
      "Path: virtualEthernet.actions.oamRemLoopback"
   ::= {ar1645v2VEthOamRemLoopbackEntry 2147483648}


ar1645v2VEthType OBJECT IDENTIFIER ::= {ar1645v2VEth 913}

ar1645v2VEthTypeTable OBJECT-TYPE
   SYNTAX      SEQUENCE OF Ar1645v2VEthTypeEntry
   MAX-ACCESS  not-accessible
   STATUS      current
   DESCRIPTION
      "OAM Remote Loopback type"
   ::= {ar1645v2VEthType 1}

ar1645v2VEthTypeEntry OBJECT-TYPE
   SYNTAX      Ar1645v2VEthTypeEntry
   MAX-ACCESS  not-accessible
   STATUS      current
   DESCRIPTION
      ""
   INDEX      { ar1645v2VEthTypeGlobalIx }
   ::= {ar1645v2VEthTypeTable 1}

Ar1645v2VEthTypeEntry ::=
   SEQUENCE
      {
      ar1645v2VEthTypeGlobalIx
         GlobalIndex,
      ar1645v2VEthTypeValue
         INTEGER
      }

ar1645v2VEthTypeGlobalIx OBJECT-TYPE
   SYNTAX      GlobalIndex
   MAX-ACCESS  not-accessible
   STATUS      current
   DESCRIPTION
      "The value of the tlsCntTreeGlobalIndex of the MANAGED OBJECT."
   ::= {ar1645v2VEthTypeEntry 10}

ar1645v2VEthTypeValue OBJECT-TYPE
   SYNTAX      INTEGER
               {
               start (0),
               stop (1)
               }
   MAX-ACCESS  read-write
   STATUS      current
   DESCRIPTION
      "Path: virtualEthernet.actions.type

       Possibilities:
               start   (0)
               stop   (1)"
   ::= {ar1645v2VEthTypeEntry 2147483648}


ar1645v2VEthSendWOL OBJECT IDENTIFIER ::= {ar1645v2VEth 333}

ar1645v2VEthSendWOLTable OBJECT-TYPE
   SYNTAX      SEQUENCE OF Ar1645v2VEthSendWOLEntry
   MAX-ACCESS  not-accessible
   STATUS      current
   DESCRIPTION
      "send a WakeOnLan message on this interface"
   ::= {ar1645v2VEthSendWOL 1}

ar1645v2VEthSendWOLEntry OBJECT-TYPE
   SYNTAX      Ar1645v2VEthSendWOLEntry
   MAX-ACCESS  not-accessible
   STATUS      current
   DESCRIPTION
      ""
   INDEX      { ar1645v2VEthSendWOLGlobalIx }
   ::= {ar1645v2VEthSendWOLTable 1}

Ar1645v2VEthSendWOLEntry ::=
   SEQUENCE
      {
      ar1645v2VEthSendWOLGlobalIx
         GlobalIndex,
      ar1645v2VEthSendWOLValue
         Integer32
      }

ar1645v2VEthSendWOLGlobalIx OBJECT-TYPE
   SYNTAX      GlobalIndex
   MAX-ACCESS  not-accessible
   STATUS      current
   DESCRIPTION
      "The value of the tlsCntTreeGlobalIndex of the MANAGED OBJECT."
   ::= {ar1645v2VEthSendWOLEntry 10}

ar1645v2VEthSendWOLValue OBJECT-TYPE
   SYNTAX      Integer32
   MAX-ACCESS  read-write
   STATUS      current
   DESCRIPTION
      "Path: virtualEthernet.actions.sendWOL"
   ::= {ar1645v2VEthSendWOLEntry 2147483648}


ar1645v2VEthWolInfo OBJECT IDENTIFIER ::= {ar1645v2VEth 332}

ar1645v2VEthWolInfoSSCTable OBJECT-TYPE
   SYNTAX      SEQUENCE OF Ar1645v2VEthWolInfoEntry
   MAX-ACCESS  not-accessible
   STATUS      current
   DESCRIPTION
      "content of a WakeOnLan message"
   ::= {ar1645v2VEthWolInfo 1}

ar1645v2VEthWolInfoEntry OBJECT-TYPE
   SYNTAX      Ar1645v2VEthWolInfoEntry
   MAX-ACCESS  not-accessible
   STATUS      current
   DESCRIPTION
      ""
   INDEX      { ar1645v2VEthWolInfoGlobalIx }
   ::= {ar1645v2VEthWolInfoSSCTable 1}

Ar1645v2VEthWolInfoEntry ::=
   SEQUENCE
      {
      ar1645v2VEthWolInfoGlobalIx
         GlobalIndex,
      ar1645v2VEthWolInfoTargetMAC
         OCTET STRING,
      ar1645v2VEthWolInfoPassword
         OCTET STRING
      }

ar1645v2VEthWolInfoGlobalIx OBJECT-TYPE
   SYNTAX      GlobalIndex
   MAX-ACCESS  not-accessible
   STATUS      current
   DESCRIPTION
      "The value of the tlsCntTreeGlobalIndex of the MANAGED OBJECT."
   ::= {ar1645v2VEthWolInfoEntry 10}

ar1645v2VEthWolInfoTargetMAC OBJECT-TYPE
   SYNTAX      OCTET STRING
   MAX-ACCESS  read-write
   STATUS      current
   DESCRIPTION
      "Path: virtualEthernet.actions.wolInfo.targetMAC

       MAC address."
   ::= {ar1645v2VEthWolInfoEntry 16777216}

ar1645v2VEthWolInfoPassword OBJECT-TYPE
   SYNTAX      OCTET STRING
   MAX-ACCESS  read-write
   STATUS      current
   DESCRIPTION
      "Path: virtualEthernet.actions.wolInfo.password"
   ::= {ar1645v2VEthWolInfoEntry 33554432}


ar1645v2VEthClearArpCache OBJECT IDENTIFIER ::= {ar1645v2VEth 25}

ar1645v2VEthClearArpCacheTable OBJECT-TYPE
   SYNTAX      SEQUENCE OF Ar1645v2VEthClearArpCacheEntry
   MAX-ACCESS  not-accessible
   STATUS      current
   DESCRIPTION
      "clear all dynamic enties in ARP cache table"
   ::= {ar1645v2VEthClearArpCache 1}

ar1645v2VEthClearArpCacheEntry OBJECT-TYPE
   SYNTAX      Ar1645v2VEthClearArpCacheEntry
   MAX-ACCESS  not-accessible
   STATUS      current
   DESCRIPTION
      ""
   INDEX      { ar1645v2VEthClearArpCacheGlobalIx }
   ::= {ar1645v2VEthClearArpCacheTable 1}

Ar1645v2VEthClearArpCacheEntry ::=
   SEQUENCE
      {
      ar1645v2VEthClearArpCacheGlobalIx
         GlobalIndex,
      ar1645v2VEthClearArpCacheValue
         Integer32
      }

ar1645v2VEthClearArpCacheGlobalIx OBJECT-TYPE
   SYNTAX      GlobalIndex
   MAX-ACCESS  not-accessible
   STATUS      current
   DESCRIPTION
      "The value of the tlsCntTreeGlobalIndex of the MANAGED OBJECT."
   ::= {ar1645v2VEthClearArpCacheEntry 10}

ar1645v2VEthClearArpCacheValue OBJECT-TYPE
   SYNTAX      Integer32
   MAX-ACCESS  read-write
   STATUS      current
   DESCRIPTION
      "Path: virtualEthernet.actions.clearArpCache"
   ::= {ar1645v2VEthClearArpCacheEntry 2147483648}



fr1645v2VEth OBJECT IDENTIFIER ::= {r1645v2VEth 13}


fr1645v2VEthAlarm OBJECT IDENTIFIER ::= {fr1645v2VEth 207}

fr1645v2VEthAlarmSSCTable OBJECT-TYPE
   SYNTAX      SEQUENCE OF Fr1645v2VEthAlarmEntry
   MAX-ACCESS  not-accessible
   STATUS      current
   DESCRIPTION
      "IfAlarmInfo"
   ::= {fr1645v2VEthAlarm 1}

fr1645v2VEthAlarmEntry OBJECT-TYPE
   SYNTAX      Fr1645v2VEthAlarmEntry
   MAX-ACCESS  not-accessible
   STATUS      current
   DESCRIPTION
      ""
   INDEX      { fr1645v2VEthAlarmGlobalIx }
   ::= {fr1645v2VEthAlarmSSCTable 1}

Fr1645v2VEthAlarmEntry ::=
   SEQUENCE
      {
      fr1645v2VEthAlarmGlobalIx
         GlobalIndex,
      fr1645v2VEthAlarmDiscriminator
         Integer32,
      fr1645v2VEthAlarmCurrent
         Integer32,
      fr1645v2VEthAlarmPrevious
         Integer32,
      fr1645v2VEthAlarmMask
         Integer32,
      fr1645v2VEthAlarmLevLinkDown
         Integer32,
      fr1645v2VEthAlarmLevPppoEDown
         Integer32
      }

fr1645v2VEthAlarmGlobalIx OBJECT-TYPE
   SYNTAX      GlobalIndex
   MAX-ACCESS  not-accessible
   STATUS      current
   DESCRIPTION
      "The value of the tlsCntTreeGlobalIndex of the MANAGED OBJECT."
   ::= {fr1645v2VEthAlarmEntry 10}

fr1645v2VEthAlarmDiscriminator OBJECT-TYPE
   SYNTAX      Integer32
   MAX-ACCESS  read-only
   STATUS      current
   DESCRIPTION
      "Path: virtualEthernet.alarms.alarmInfo.discriminator"
   ::= {fr1645v2VEthAlarmEntry 16777216}

fr1645v2VEthAlarmCurrent OBJECT-TYPE
   SYNTAX      Integer32
   MAX-ACCESS  read-only
   STATUS      current
   DESCRIPTION
      "Path: virtualEthernet.alarms.alarmInfo.currentAlarms

       Bit meanings:
               bit 0 = linkDown,
               bit 9 = pppoEDown"
   ::= {fr1645v2VEthAlarmEntry 33554432}

fr1645v2VEthAlarmPrevious OBJECT-TYPE
   SYNTAX      Integer32
   MAX-ACCESS  read-only
   STATUS      current
   DESCRIPTION
      "Path: virtualEthernet.alarms.alarmInfo.previousAlarms

       Bit meanings:
               bit 0 = linkDown,
               bit 9 = pppoEDown"
   ::= {fr1645v2VEthAlarmEntry 50331648}

fr1645v2VEthAlarmMask OBJECT-TYPE
   SYNTAX      Integer32
   MAX-ACCESS  read-only
   STATUS      current
   DESCRIPTION
      "Path: virtualEthernet.alarms.alarmInfo.alarmMask

       Bit meanings:
               bit 0 = linkDown,
               bit 9 = pppoEDown"
   ::= {fr1645v2VEthAlarmEntry 67108864}

fr1645v2VEthAlarmLevLinkDown OBJECT-TYPE
   SYNTAX      Integer32
   MAX-ACCESS  read-only
   STATUS      current
   DESCRIPTION
      "Path: virtualEthernet.alarms.alarmInfo.alarmLevel.linkDown"
   ::= {fr1645v2VEthAlarmEntry 83951616}

fr1645v2VEthAlarmLevPppoEDown OBJECT-TYPE
   SYNTAX      Integer32
   MAX-ACCESS  read-only
   STATUS      current
   DESCRIPTION
      "Path: virtualEthernet.alarms.alarmInfo.alarmLevel.pppoEDown"
   ::= {fr1645v2VEthAlarmEntry 84541440}


fr1645v2VEthAlarmE2 OBJECT IDENTIFIER ::= {fr1645v2VEthAlarm 2}

fr1645v2VEthAlarmE2Entry OBJECT IDENTIFIER ::= {fr1645v2VEthAlarmE2 1}

fr1645v2VEthAlarmE2LinkDown OBJECT IDENTIFIER ::= {fr1645v2VEthAlarmE2Entry 10}

fr1645v2VEthAlarmE2LinkDownPfx OBJECT IDENTIFIER ::= {fr1645v2VEthAlarmE2LinkDown 0}

fr1645v2VEthAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'virtualEthernet'
                (root='router1645') has changed from the ON to the OFF state."
   ::= {fr1645v2VEthAlarmE2LinkDownPfx 1}

fr1645v2VEthAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'virtualEthernet'
                (root='router1645') has changed from the OFF to the ON state."
   ::= {fr1645v2VEthAlarmE2LinkDownPfx 2}

fr1645v2VEthAlarmE2PppoEDown OBJECT IDENTIFIER ::= {fr1645v2VEthAlarmE2Entry 19}

fr1645v2VEthAlarmE2PppoEDownPfx OBJECT IDENTIFIER ::= {fr1645v2VEthAlarmE2PppoEDown 0}

fr1645v2VEthAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'virtualEthernet'
                (root='router1645') has changed from the ON to the OFF state."
   ::= {fr1645v2VEthAlarmE2PppoEDownPfx 1}

fr1645v2VEthAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'virtualEthernet'
                (root='router1645') has changed from the OFF to the ON state."
   ::= {fr1645v2VEthAlarmE2PppoEDownPfx 2}



END
