OneAccess-R1646v2-4642-VEth DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1646Rootv2 MODULE-IDENTITY
   LAST-UPDATED "202107151728Z"
   ORGANIZATION "OneAccess"
   CONTACT-INFO "http://www.oneaccess-net.com/telindus/"
   DESCRIPTION
      "..."
   ::= {telindus 1132}




r1646v2VEth OBJECT IDENTIFIER ::= {r1646Rootv2 4642}

r1646v2VEthMOProp OBJECT-TYPE
   SYNTAX      SEQUENCE OF R1646v2VEthMOPropEntry
   MAX-ACCESS  not-accessible
   STATUS      current
   DESCRIPTION
      ""
   ::= {r1646v2VEth 1}

r1646v2VEthMOPropEntry OBJECT-TYPE
   SYNTAX      R1646v2VEthMOPropEntry
   MAX-ACCESS  not-accessible
   STATUS      current
   DESCRIPTION
      ""
   INDEX      { r1646v2VEthMOPropGlobalIx }
   ::= {r1646v2VEthMOProp 1}

R1646v2VEthMOPropEntry ::=
   SEQUENCE
      {
      r1646v2VEthMOPropPath
         ContainmentPath,
      r1646v2VEthMOPropRev
         ObjectRevision,
      r1646v2VEthMOPropGlobalIx
         GlobalIndex
      }

r1646v2VEthMOPropPath OBJECT-TYPE
   SYNTAX      ContainmentPath
   MAX-ACCESS  read-only
   STATUS      current
   DESCRIPTION
      "Textual description of the containment tree from the instance of
       the root object down to the instance of the current object."
   ::= {r1646v2VEthMOPropEntry 3}

r1646v2VEthMOPropRev OBJECT-TYPE
   SYNTAX      ObjectRevision
   MAX-ACCESS  read-only
   STATUS      current
   DESCRIPTION
      "This value corresponds with the revision of the MANAGED OBJECT."
   ::= {r1646v2VEthMOPropEntry 4}

r1646v2VEthMOPropGlobalIx OBJECT-TYPE
   SYNTAX      GlobalIndex
   MAX-ACCESS  read-only
   STATUS      current
   DESCRIPTION
      "The value of the tlsCntTreeGlobalIndex of the MANAGED OBJECT."
   ::= {r1646v2VEthMOPropEntry 10}



er1646v2VEth OBJECT IDENTIFIER ::= {r1646v2VEth 11}


er1646v2VEthRemark OBJECT IDENTIFIER ::= {er1646v2VEth 321}

er1646v2VEthRemarkTable OBJECT-TYPE
   SYNTAX      SEQUENCE OF Er1646v2VEthRemarkEntry
   MAX-ACCESS  not-accessible
   STATUS      current
   DESCRIPTION
      "intfRemark"
   ::= {er1646v2VEthRemark 1}

er1646v2VEthRemarkEntry OBJECT-TYPE
   SYNTAX      Er1646v2VEthRemarkEntry
   MAX-ACCESS  not-accessible
   STATUS      current
   DESCRIPTION
      ""
   INDEX      { er1646v2VEthRemarkGlobalIx }
   ::= {er1646v2VEthRemarkTable 1}

Er1646v2VEthRemarkEntry ::=
   SEQUENCE
      {
      er1646v2VEthRemarkGlobalIx
         GlobalIndex,
      er1646v2VEthRemarkValue
         DisplayString
      }

er1646v2VEthRemarkGlobalIx OBJECT-TYPE
   SYNTAX      GlobalIndex
   MAX-ACCESS  not-accessible
   STATUS      current
   DESCRIPTION
      "The value of the tlsCntTreeGlobalIndex of the MANAGED OBJECT."
   ::= {er1646v2VEthRemarkEntry 10}

er1646v2VEthRemarkValue OBJECT-TYPE
   SYNTAX      DisplayString
   MAX-ACCESS  read-write
   STATUS      current
   DESCRIPTION
      "Path: virtualEthernet.editConf.remark"
   ::= {er1646v2VEthRemarkEntry 2147483648}


er1646v2VEthArp OBJECT IDENTIFIER ::= {er1646v2VEth 19}

er1646v2VEthArpSSCTable OBJECT-TYPE
   SYNTAX      SEQUENCE OF Er1646v2VEthArpEntry
   MAX-ACCESS  not-accessible
   STATUS      current
   DESCRIPTION
      "ethernet related config parameters"
   ::= {er1646v2VEthArp 1}

er1646v2VEthArpEntry OBJECT-TYPE
   SYNTAX      Er1646v2VEthArpEntry
   MAX-ACCESS  not-accessible
   STATUS      current
   DESCRIPTION
      ""
   INDEX      { er1646v2VEthArpGlobalIx }
   ::= {er1646v2VEthArpSSCTable 1}

Er1646v2VEthArpEntry ::=
   SEQUENCE
      {
      er1646v2VEthArpGlobalIx
         GlobalIndex,
      er1646v2VEthArpTimeOut
         TimeTicks,
      er1646v2VEthArpProxyArp
         INTEGER
      }

er1646v2VEthArpGlobalIx OBJECT-TYPE
   SYNTAX      GlobalIndex
   MAX-ACCESS  not-accessible
   STATUS      current
   DESCRIPTION
      "The value of the tlsCntTreeGlobalIndex of the MANAGED OBJECT."
   ::= {er1646v2VEthArpEntry 10}

er1646v2VEthArpTimeOut OBJECT-TYPE
   SYNTAX      TimeTicks
   MAX-ACCESS  read-write
   STATUS      current
   DESCRIPTION
      "Path: virtualEthernet.editConf.arp.timeOut

       Time in centi-second."
   ::= {er1646v2VEthArpEntry 201326592}

er1646v2VEthArpProxyArp OBJECT-TYPE
   SYNTAX      INTEGER
               {
               disabled (0),
               enabled (1)
               }
   MAX-ACCESS  read-write
   STATUS      current
   DESCRIPTION
      "Path: virtualEthernet.editConf.arp.proxyArp

       Possibilities:
               disabled   (0)
               enabled   (1)"
   ::= {er1646v2VEthArpEntry 838860800}

er1646v2VEthArpStaticArp OBJECT-TYPE
   SYNTAX      SEQUENCE OF Er1646v2VEthArpStaticArpEntry
   MAX-ACCESS  not-accessible
   STATUS      current
   DESCRIPTION
      ""
   ::= {er1646v2VEthArp 50331648}

er1646v2VEthArpStaticArpEntry OBJECT-TYPE
   SYNTAX      Er1646v2VEthArpStaticArpEntry
   MAX-ACCESS  not-accessible
   STATUS      current
   DESCRIPTION
      ""
   INDEX      { er1646v2VEthArpStaticArpGlobalIx,
                er1646v2VEthArpStaticArpTableIx }
   ::= {er1646v2VEthArpStaticArp 1}

Er1646v2VEthArpStaticArpEntry ::=
   SEQUENCE
      {
      er1646v2VEthArpStaticArpActions
         VariableLengthTableActions,
      er1646v2VEthArpStaticArpGlobalIx
         GlobalIndex,
      er1646v2VEthArpStaticArpTableIx
         TableIndex,
      er1646v2VEthArpStaticArpMacAddress
         OCTET STRING,
      er1646v2VEthArpStaticArpIpAddress
         IpAddress
      }

er1646v2VEthArpStaticArpActions OBJECT-TYPE
   SYNTAX      VariableLengthTableActions
   MAX-ACCESS  read-write
   STATUS      current
   DESCRIPTION
      "By way of this field, some manipulations
       on this table may be performed."
   ::= {er1646v2VEthArpStaticArpEntry 2}

er1646v2VEthArpStaticArpGlobalIx OBJECT-TYPE
   SYNTAX      GlobalIndex
   MAX-ACCESS  not-accessible
   STATUS      current
   DESCRIPTION
      "The value of the tlsCntTreeGlobalIndex of the MANAGED OBJECT."
   ::= {er1646v2VEthArpStaticArpEntry 10}

er1646v2VEthArpStaticArpTableIx OBJECT-TYPE
   SYNTAX      TableIndex
   MAX-ACCESS  not-accessible
   STATUS      current
   DESCRIPTION
      ""
   ::= {er1646v2VEthArpStaticArpEntry 11}

er1646v2VEthArpStaticArpMacAddress OBJECT-TYPE
   SYNTAX      OCTET STRING
   MAX-ACCESS  read-write
   STATUS      current
   DESCRIPTION
      "Path: virtualEthernet.editConf.arp.staticArp.macAddress

       MAC address."
   ::= {er1646v2VEthArpStaticArpEntry 16777216}

er1646v2VEthArpStaticArpIpAddress OBJECT-TYPE
   SYNTAX      IpAddress
   MAX-ACCESS  read-write
   STATUS      current
   DESCRIPTION
      "Path: virtualEthernet.editConf.arp.staticArp.ipAddress"
   ::= {er1646v2VEthArpStaticArpEntry 33554432}


er1646v2VEthBrC OBJECT IDENTIFIER ::= {er1646v2VEth 27}

er1646v2VEthBrCSSCTable OBJECT-TYPE
   SYNTAX      SEQUENCE OF Er1646v2VEthBrCEntry
   MAX-ACCESS  not-accessible
   STATUS      current
   DESCRIPTION
      "Set bridging parameters"
   ::= {er1646v2VEthBrC 1}

er1646v2VEthBrCEntry OBJECT-TYPE
   SYNTAX      Er1646v2VEthBrCEntry
   MAX-ACCESS  not-accessible
   STATUS      current
   DESCRIPTION
      ""
   INDEX      { er1646v2VEthBrCGlobalIx }
   ::= {er1646v2VEthBrCSSCTable 1}

Er1646v2VEthBrCEntry ::=
   SEQUENCE
      {
      er1646v2VEthBrCGlobalIx
         GlobalIndex,
      er1646v2VEthBrCAccessList
         DisplayString,
      er1646v2VEthBrCInAccessList
         DisplayString,
      er1646v2VEthBrCTp
         DisplayString,
      er1646v2VEthBrCBridgeGroup
         DisplayString,
      er1646v2VEthBrCLimBC
         INTEGER,
      er1646v2VEthBrCPrivateMode
         INTEGER,
      er1646v2VEthBrCLearning
         INTEGER,
      er1646v2VEthBrCMaxCacheSize
         INTEGER,
      er1646v2VEthBrCRelearnDropOnRelearn
         INTEGER,
      er1646v2VEthBrCRelearnShutdownThreshold
         Integer32,
      er1646v2VEthBrCRelearnShutdownTime
         TimeTicks,
      er1646v2VEthBrCRelearnLoopDetection
         INTEGER,
      er1646v2VEthBrCRelearnLoopDetectionInterval
         TimeTicks,
      er1646v2VEthBrCVlanMemberShip
         INTEGER,
      er1646v2VEthBrCDot1adType
         INTEGER,
      er1646v2VEthBrCPriority
         Integer32,
      er1646v2VEthBrCPathCost
         Integer32,
      er1646v2VEthBrCInternalPathCost
         Integer32,
      er1646v2VEthBrCTCD
         INTEGER,
      er1646v2VEthBrCRestrictedRole
         INTEGER,
      er1646v2VEthBrCAdminEdge
         INTEGER,
      er1646v2VEthBrCMgmtInline
         INTEGER,
      er1646v2VEthBrCL2ptMode
         INTEGER,
      er1646v2VEthBrCL2ptProtocols
         Integer32,
      er1646v2VEthBrCL2ptDestMac
         OCTET STRING,
      er1646v2VEthBrCL2ptCos
         INTEGER,
      er1646v2VEthBrCL2ptDropThrStp
         INTEGER,
      er1646v2VEthBrCL2ptDropThrLldp
         INTEGER,
      er1646v2VEthBrCL2ptDropThrOam
         INTEGER,
      er1646v2VEthBrCL2ptDropThrCdp
         INTEGER,
      er1646v2VEthBrCL2ptDropThrVtp
         INTEGER,
      er1646v2VEthBrCL2ptDropThrLacp
         INTEGER,
      er1646v2VEthBrCL2ptDropThrEfmOam
         INTEGER,
      er1646v2VEthBrCL2ptDropThrPvst
         INTEGER,
      er1646v2VEthBrCL2ptDropThrMmrp
         INTEGER,
      er1646v2VEthBrCL2ptDropThrMvrp
         INTEGER,
      er1646v2VEthBrCL2ptDropThrGvrp
         INTEGER,
      er1646v2VEthBrCL2ptDropThrGmrp
         INTEGER,
      er1646v2VEthBrCL2ptDropThrDtp
         INTEGER,
      er1646v2VEthBrCL2ptDropThrPagp
         INTEGER,
      er1646v2VEthBrCL2ptDropThrUdld
         INTEGER
      }

er1646v2VEthBrCGlobalIx OBJECT-TYPE
   SYNTAX      GlobalIndex
   MAX-ACCESS  not-accessible
   STATUS      current
   DESCRIPTION
      "The value of the tlsCntTreeGlobalIndex of the MANAGED OBJECT."
   ::= {er1646v2VEthBrCEntry 10}

er1646v2VEthBrCAccessList OBJECT-TYPE
   SYNTAX      DisplayString
   MAX-ACCESS  read-write
   STATUS      current
   DESCRIPTION
      "Path: virtualEthernet.editConf.bridging.accessList"
   ::= {er1646v2VEthBrCEntry 83886080}

er1646v2VEthBrCInAccessList OBJECT-TYPE
   SYNTAX      DisplayString
   MAX-ACCESS  read-write
   STATUS      current
   DESCRIPTION
      "Path: virtualEthernet.editConf.bridging.inAccessList"
   ::= {er1646v2VEthBrCEntry 251658240}

er1646v2VEthBrCTp OBJECT-TYPE
   SYNTAX      DisplayString
   MAX-ACCESS  read-write
   STATUS      current
   DESCRIPTION
      "Path: virtualEthernet.editConf.bridging.trafficPolicy"
   ::= {er1646v2VEthBrCEntry 100663296}

er1646v2VEthBrCBridgeGroup OBJECT-TYPE
   SYNTAX      DisplayString
   MAX-ACCESS  read-write
   STATUS      current
   DESCRIPTION
      "Path: virtualEthernet.editConf.bridging.bridgeGroup"
   ::= {er1646v2VEthBrCEntry 117440512}

er1646v2VEthBrCLimBC OBJECT-TYPE
   SYNTAX      INTEGER
               {
               disabled (0),
               enabled (1)
               }
   MAX-ACCESS  read-write
   STATUS      current
   DESCRIPTION
      "Path: virtualEthernet.editConf.bridging.limitBroadcasts

       Possibilities:
               disabled   (0)
               enabled   (1)"
   ::= {er1646v2VEthBrCEntry 134217728}

er1646v2VEthBrCPrivateMode OBJECT-TYPE
   SYNTAX      INTEGER
               {
               disabled (0),
               enabled (1)
               }
   MAX-ACCESS  read-write
   STATUS      current
   DESCRIPTION
      "Path: virtualEthernet.editConf.bridging.privateMode

       Possibilities:
               disabled   (0)
               enabled   (1)"
   ::= {er1646v2VEthBrCEntry 419430400}

er1646v2VEthBrCLearning OBJECT-TYPE
   SYNTAX      INTEGER
               {
               disabled (0),
               enabled (1)
               }
   MAX-ACCESS  read-write
   STATUS      current
   DESCRIPTION
      "Path: virtualEthernet.editConf.bridging.learning

       Possibilities:
               disabled   (0)
               enabled   (1)"
   ::= {er1646v2VEthBrCEntry 201326592}

er1646v2VEthBrCMaxCacheSize OBJECT-TYPE
   SYNTAX      INTEGER
               {
               unlimited (0)
               }
   MAX-ACCESS  read-write
   STATUS      current
   DESCRIPTION
      "Path: virtualEthernet.editConf.bridging.maxCacheSize

       Possibilities:
               unlimited   (0)"
   ::= {er1646v2VEthBrCEntry 218103808}

er1646v2VEthBrCRelearnDropOnRelearn OBJECT-TYPE
   SYNTAX      INTEGER
               {
               disabled (0),
               enabled (1)
               }
   MAX-ACCESS  read-write
   STATUS      current
   DESCRIPTION
      "Path: virtualEthernet.editConf.bridging.relearn.dropOnRelearn

       Possibilities:
               disabled   (0)
               enabled   (1)"
   ::= {er1646v2VEthBrCEntry 234946560}

er1646v2VEthBrCRelearnShutdownThreshold OBJECT-TYPE
   SYNTAX      Integer32
   MAX-ACCESS  read-write
   STATUS      current
   DESCRIPTION
      "Path: virtualEthernet.editConf.bridging.relearn.shutdownThreshold"
   ::= {er1646v2VEthBrCEntry 235012096}

er1646v2VEthBrCRelearnShutdownTime OBJECT-TYPE
   SYNTAX      TimeTicks
   MAX-ACCESS  read-write
   STATUS      current
   DESCRIPTION
      "Path: virtualEthernet.editConf.bridging.relearn.shutdownTime

       Time in centi-second."
   ::= {er1646v2VEthBrCEntry 235077632}

er1646v2VEthBrCRelearnLoopDetection OBJECT-TYPE
   SYNTAX      INTEGER
               {
               disabled (0),
               passive (1),
               active (2)
               }
   MAX-ACCESS  read-write
   STATUS      current
   DESCRIPTION
      "Path: virtualEthernet.editConf.bridging.relearn.loopDetection

       Possibilities:
               disabled   (0)
               passive   (1)
               active   (2)"
   ::= {er1646v2VEthBrCEntry 235143168}

er1646v2VEthBrCRelearnLoopDetectionInterval OBJECT-TYPE
   SYNTAX      TimeTicks
   MAX-ACCESS  read-write
   STATUS      current
   DESCRIPTION
      "Path: virtualEthernet.editConf.bridging.relearn.loopDetectionInterval

       Time in centi-second."
   ::= {er1646v2VEthBrCEntry 235208704}

er1646v2VEthBrCVlanMemberShip OBJECT-TYPE
   SYNTAX      INTEGER
               {
               all (0),
               none (1),
               grouped (2)
               }
   MAX-ACCESS  read-write
   STATUS      current
   DESCRIPTION
      "Path: virtualEthernet.editConf.bridging.vlanMemberShip

       Possibilities:
               all   (0)
               none   (1)
               grouped   (2)"
   ::= {er1646v2VEthBrCEntry 318767104}

er1646v2VEthBrCDot1adType OBJECT-TYPE
   SYNTAX      INTEGER
               {
               slOPTg (0),
               cPort (4),
               sPort (1),
               nni (2)
               }
   MAX-ACCESS  read-write
   STATUS      current
   DESCRIPTION
      "Path: virtualEthernet.editConf.bridging.dot1ad.type

       Possibilities:
               <OPT>   (0)
               cPort   (4)
               sPort   (1)
               nni   (2)"
   ::= {er1646v2VEthBrCEntry 503382016}

er1646v2VEthBrCPriority OBJECT-TYPE
   SYNTAX      Integer32
   MAX-ACCESS  read-write
   STATUS      current
   DESCRIPTION
      "Path: virtualEthernet.editConf.bridging.priority"
   ::= {er1646v2VEthBrCEntry 33554432}

er1646v2VEthBrCPathCost OBJECT-TYPE
   SYNTAX      Integer32
   MAX-ACCESS  read-write
   STATUS      current
   DESCRIPTION
      "Path: virtualEthernet.editConf.bridging.pathCost"
   ::= {er1646v2VEthBrCEntry 50331648}

er1646v2VEthBrCInternalPathCost OBJECT-TYPE
   SYNTAX      Integer32
   MAX-ACCESS  read-write
   STATUS      current
   DESCRIPTION
      "Path: virtualEthernet.editConf.bridging.internalPathCost"
   ::= {er1646v2VEthBrCEntry 301989888}

er1646v2VEthBrCTCD OBJECT-TYPE
   SYNTAX      INTEGER
               {
               disabled (0),
               enabled (1)
               }
   MAX-ACCESS  read-write
   STATUS      current
   DESCRIPTION
      "Path: virtualEthernet.editConf.bridging.topologyChangeDetection

       Possibilities:
               disabled   (0)
               enabled   (1)"
   ::= {er1646v2VEthBrCEntry 67108864}

er1646v2VEthBrCRestrictedRole OBJECT-TYPE
   SYNTAX      INTEGER
               {
               disabled (0),
               enabled (1)
               }
   MAX-ACCESS  read-write
   STATUS      current
   DESCRIPTION
      "Path: virtualEthernet.editConf.bridging.restrictedRole

       Possibilities:
               disabled   (0)
               enabled   (1)"
   ::= {er1646v2VEthBrCEntry 335544320}

er1646v2VEthBrCAdminEdge OBJECT-TYPE
   SYNTAX      INTEGER
               {
               disabled (0),
               enabled (1)
               }
   MAX-ACCESS  read-write
   STATUS      current
   DESCRIPTION
      "Path: virtualEthernet.editConf.bridging.adminEdge

       Possibilities:
               disabled   (0)
               enabled   (1)"
   ::= {er1646v2VEthBrCEntry 268435456}

er1646v2VEthBrCMgmtInline OBJECT-TYPE
   SYNTAX      INTEGER
               {
               disabled (0),
               enabled (1)
               }
   MAX-ACCESS  read-write
   STATUS      current
   DESCRIPTION
      "Path: virtualEthernet.editConf.bridging.mgmtInline

       Possibilities:
               disabled   (0)
               enabled   (1)"
   ::= {er1646v2VEthBrCEntry 369098752}

er1646v2VEthBrCL2ptMode OBJECT-TYPE
   SYNTAX      INTEGER
               {
               disabled (0),
               enabled (1)
               }
   MAX-ACCESS  read-write
   STATUS      current
   DESCRIPTION
      "Path: virtualEthernet.editConf.bridging.l2ProtTunnel.mode

       Possibilities:
               disabled   (0)
               enabled   (1)"
   ::= {er1646v2VEthBrCEntry 403701760}

er1646v2VEthBrCL2ptProtocols OBJECT-TYPE
   SYNTAX      Integer32
   MAX-ACCESS  read-write
   STATUS      current
   DESCRIPTION
      "Path: virtualEthernet.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2VEthBrCEntry 404750336}

er1646v2VEthBrCL2ptDestMac OBJECT-TYPE
   SYNTAX      OCTET STRING
   MAX-ACCESS  read-write
   STATUS      current
   DESCRIPTION
      "Path: virtualEthernet.editConf.bridging.l2ProtTunnel.destinationMac

       MAC address."
   ::= {er1646v2VEthBrCEntry 405798912}

er1646v2VEthBrCL2ptCos OBJECT-TYPE
   SYNTAX      INTEGER
               {
               unchanged (255)
               }
   MAX-ACCESS  read-write
   STATUS      current
   DESCRIPTION
      "Path: virtualEthernet.editConf.bridging.l2ProtTunnel.cos

       Possibilities:
               unchanged   (255)"
   ::= {er1646v2VEthBrCEntry 406847488}

er1646v2VEthBrCL2ptDropThrStp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.stp

       unit name = packets/sec

       Possibilities:
               unlimited   (0)"
   ::= {er1646v2VEthBrCEntry 407900160}

er1646v2VEthBrCL2ptDropThrLldp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.lldp

       unit name = packets/sec

       Possibilities:
               unlimited   (0)"
   ::= {er1646v2VEthBrCEntry 407904256}

er1646v2VEthBrCL2ptDropThrOam OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.oam

       unit name = packets/sec

       Possibilities:
               unlimited   (0)"
   ::= {er1646v2VEthBrCEntry 407908352}

er1646v2VEthBrCL2ptDropThrCdp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.cdp

       unit name = packets/sec

       Possibilities:
               unlimited   (0)"
   ::= {er1646v2VEthBrCEntry 407912448}

er1646v2VEthBrCL2ptDropThrVtp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.vtp

       unit name = packets/sec

       Possibilities:
               unlimited   (0)"
   ::= {er1646v2VEthBrCEntry 407916544}

er1646v2VEthBrCL2ptDropThrLacp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.lacp

       unit name = packets/sec

       Possibilities:
               unlimited   (0)"
   ::= {er1646v2VEthBrCEntry 407920640}

er1646v2VEthBrCL2ptDropThrEfmOam OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.efmOam

       unit name = packets/sec

       Possibilities:
               unlimited   (0)"
   ::= {er1646v2VEthBrCEntry 407924736}

er1646v2VEthBrCL2ptDropThrPvst OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.pvst

       unit name = packets/sec

       Possibilities:
               unlimited   (0)"
   ::= {er1646v2VEthBrCEntry 407928832}

er1646v2VEthBrCL2ptDropThrMmrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.mmrp

       unit name = packets/sec

       Possibilities:
               unlimited   (0)"
   ::= {er1646v2VEthBrCEntry 407932928}

er1646v2VEthBrCL2ptDropThrMvrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.mvrp

       unit name = packets/sec

       Possibilities:
               unlimited   (0)"
   ::= {er1646v2VEthBrCEntry 407937024}

er1646v2VEthBrCL2ptDropThrGvrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.gvrp

       unit name = packets/sec

       Possibilities:
               unlimited   (0)"
   ::= {er1646v2VEthBrCEntry 407941120}

er1646v2VEthBrCL2ptDropThrGmrp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.gmrp

       unit name = packets/sec

       Possibilities:
               unlimited   (0)"
   ::= {er1646v2VEthBrCEntry 407945216}

er1646v2VEthBrCL2ptDropThrDtp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.dtp

       unit name = packets/sec

       Possibilities:
               unlimited   (0)"
   ::= {er1646v2VEthBrCEntry 407949312}

er1646v2VEthBrCL2ptDropThrPagp OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.pagp

       unit name = packets/sec

       Possibilities:
               unlimited   (0)"
   ::= {er1646v2VEthBrCEntry 407953408}

er1646v2VEthBrCL2ptDropThrUdld OBJECT-TYPE
   SYNTAX      INTEGER
               {
               unlimited (0)
               }
   UNITS       "packets/sec"
   MAX-ACCESS  read-write
   STATUS      current
   DESCRIPTION
      "Path: virtualEthernet.editConf.bridging.l2ProtTunnel.dropThresholds.udld

       unit name = packets/sec

       Possibilities:
               unlimited   (0)"
   ::= {er1646v2VEthBrCEntry 407957504}


er1646v2VEthVlanTagging OBJECT IDENTIFIER ::= {er1646v2VEth 14}

er1646v2VEthVlanTaggingSSCTable OBJECT-TYPE
   SYNTAX      SEQUENCE OF Er1646v2VEthVlanTaggingEntry
   MAX-ACCESS  not-accessible
   STATUS      current
   DESCRIPTION
      "vlan tagging config"
   ::= {er1646v2VEthVlanTagging 1}

er1646v2VEthVlanTaggingEntry OBJECT-TYPE
   SYNTAX      Er1646v2VEthVlanTaggingEntry
   MAX-ACCESS  not-accessible
   STATUS      current
   DESCRIPTION
      ""
   INDEX      { er1646v2VEthVlanTaggingGlobalIx }
   ::= {er1646v2VEthVlanTaggingSSCTable 1}

Er1646v2VEthVlanTaggingEntry ::=
   SEQUENCE
      {
      er1646v2VEthVlanTaggingGlobalIx
         GlobalIndex,
      er1646v2VEthVlanTaggingUntaggedAction
         INTEGER,
      er1646v2VEthVlanTaggingUntaggedTagInfoTpid
         INTEGER,
      er1646v2VEthVlanTaggingUntaggedTagInfoVid
         Integer32,
      er1646v2VEthVlanTaggingUnknownVlansAction
         INTEGER,
      er1646v2VEthVlanTaggingUnknownVlansTagInfoTpid
         INTEGER,
      er1646v2VEthVlanTaggingUnknownVlansTagInfoVid
         Integer32
      }

er1646v2VEthVlanTaggingGlobalIx OBJECT-TYPE
   SYNTAX      GlobalIndex
   MAX-ACCESS  not-accessible
   STATUS      current
   DESCRIPTION
      "The value of the tlsCntTreeGlobalIndex of the MANAGED OBJECT."
   ::= {er1646v2VEthVlanTaggingEntry 10}

er1646v2VEthVlanTaggingUntaggedAction OBJECT-TYPE
   SYNTAX      INTEGER
               {
               discard (0),
               accept (1),
               tag (2)
               }
   MAX-ACCESS  read-write
   STATUS      current
   DESCRIPTION
      "Path: virtualEthernet.editConf.vlanTagging.untagged.action

       Possibilities:
               discard   (0)
               accept   (1)
               tag   (2)"
   ::= {er1646v2VEthVlanTaggingEntry 671088640}

er1646v2VEthVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlanTagging.untagged.tagInfo.tpid

       Possibilities:
               dot1Q   (33024)
               dot1ad   (34984)
               0x9100   (37120)
               0x9200   (37376)
               0x9300   (37632)"
   ::= {er1646v2VEthVlanTaggingEntry 746586112}

er1646v2VEthVlanTaggingUntaggedTagInfoVid OBJECT-TYPE
   SYNTAX      Integer32
   MAX-ACCESS  read-write
   STATUS      current
   DESCRIPTION
      "Path: virtualEthernet.editConf.vlanTagging.untagged.tagInfo.vid"
   ::= {er1646v2VEthVlanTaggingEntry 754974720}

er1646v2VEthVlanTaggingUnknownVlansAction OBJECT-TYPE
   SYNTAX      INTEGER
               {
               discard (0),
               accept (1),
               tag (2)
               }
   MAX-ACCESS  read-write
   STATUS      current
   DESCRIPTION
      "Path: virtualEthernet.editConf.vlanTagging.unknownVlans.action

       Possibilities:
               discard   (0)
               accept   (1)
               tag   (2)"
   ::= {er1646v2VEthVlanTaggingEntry 1744830464}

er1646v2VEthVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlanTagging.unknownVlans.tagInfo.tpid

       Possibilities:
               dot1Q   (33024)
               dot1ad   (34984)
               0x9100   (37120)
               0x9200   (37376)
               0x9300   (37632)"
   ::= {er1646v2VEthVlanTaggingEntry 1820327936}

er1646v2VEthVlanTaggingUnknownVlansTagInfoVid OBJECT-TYPE
   SYNTAX      Integer32
   MAX-ACCESS  read-write
   STATUS      current
   DESCRIPTION
      "Path: virtualEthernet.editConf.vlanTagging.unknownVlans.tagInfo.vid"
   ::= {er1646v2VEthVlanTaggingEntry 1828716544}

er1646v2VEthVlanTaggingVlans OBJECT-TYPE
   SYNTAX      SEQUENCE OF Er1646v2VEthVlanTaggingVlansEntry
   MAX-ACCESS  not-accessible
   STATUS      current
   DESCRIPTION
      ""
   ::= {er1646v2VEthVlanTagging 1073741824}

er1646v2VEthVlanTaggingVlansEntry OBJECT-TYPE
   SYNTAX      Er1646v2VEthVlanTaggingVlansEntry
   MAX-ACCESS  not-accessible
   STATUS      current
   DESCRIPTION
      ""
   INDEX      { er1646v2VEthVlanTaggingVlansGlobalIx,
                er1646v2VEthVlanTaggingVlansTableIx }
   ::= {er1646v2VEthVlanTaggingVlans 1}

Er1646v2VEthVlanTaggingVlansEntry ::=
   SEQUENCE
      {
      er1646v2VEthVlanTaggingVlansActions
         VariableLengthTableActions,
      er1646v2VEthVlanTaggingVlansGlobalIx
         GlobalIndex,
      er1646v2VEthVlanTaggingVlansTableIx
         TableIndex,
      er1646v2VEthVlanTaggingVlansVid
         Integer32,
      er1646v2VEthVlanTaggingVlansEndVid
         Integer32,
      er1646v2VEthVlanTaggingVlansAction
         INTEGER,
      er1646v2VEthVlanTaggingVlansTagInfoTpid
         INTEGER,
      er1646v2VEthVlanTaggingVlansTagInfoVid
         Integer32
      }

er1646v2VEthVlanTaggingVlansActions OBJECT-TYPE
   SYNTAX      VariableLengthTableActions
   MAX-ACCESS  read-write
   STATUS      current
   DESCRIPTION
      "By way of this field, some manipulations
       on this table may be performed."
   ::= {er1646v2VEthVlanTaggingVlansEntry 2}

er1646v2VEthVlanTaggingVlansGlobalIx OBJECT-TYPE
   SYNTAX      GlobalIndex
   MAX-ACCESS  not-accessible
   STATUS      current
   DESCRIPTION
      "The value of the tlsCntTreeGlobalIndex of the MANAGED OBJECT."
   ::= {er1646v2VEthVlanTaggingVlansEntry 10}

er1646v2VEthVlanTaggingVlansTableIx OBJECT-TYPE
   SYNTAX      TableIndex
   MAX-ACCESS  not-accessible
   STATUS      current
   DESCRIPTION
      ""
   ::= {er1646v2VEthVlanTaggingVlansEntry 11}

er1646v2VEthVlanTaggingVlansVid OBJECT-TYPE
   SYNTAX      Integer32
   MAX-ACCESS  read-write
   STATUS      current
   DESCRIPTION
      "Path: virtualEthernet.editConf.vlanTagging.vlans.vid"
   ::= {er1646v2VEthVlanTaggingVlansEntry 536870912}

er1646v2VEthVlanTaggingVlansEndVid OBJECT-TYPE
   SYNTAX      Integer32
   MAX-ACCESS  read-write
   STATUS      current
   DESCRIPTION
      "Path: virtualEthernet.editConf.vlanTagging.vlans.endVid"
   ::= {er1646v2VEthVlanTaggingVlansEntry 2147483648}

er1646v2VEthVlanTaggingVlansAction OBJECT-TYPE
   SYNTAX      INTEGER
               {
               discard (0),
               accept (1),
               tag (2)
               }
   MAX-ACCESS  read-write
   STATUS      current
   DESCRIPTION
      "Path: virtualEthernet.editConf.vlanTagging.vlans.action

       Possibilities:
               discard   (0)
               accept   (1)
               tag   (2)"
   ::= {er1646v2VEthVlanTaggingVlansEntry 1073741824}

er1646v2VEthVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlanTagging.vlans.tagInfo.tpid

       Possibilities:
               dot1Q   (33024)
               dot1ad   (34984)
               0x9100   (37120)
               0x9200   (37376)
               0x9300   (37632)"
   ::= {er1646v2VEthVlanTaggingVlansEntry 1677721600}

er1646v2VEthVlanTaggingVlansTagInfoVid OBJECT-TYPE
   SYNTAX      Integer32
   MAX-ACCESS  read-write
   STATUS      current
   DESCRIPTION
      "Path: virtualEthernet.editConf.vlanTagging.vlans.tagInfo.vid"
   ::= {er1646v2VEthVlanTaggingVlansEntry 1744830464}


er1646v2VEthOam OBJECT IDENTIFIER ::= {er1646v2VEth 900}

er1646v2VEthOamSSCTable OBJECT-TYPE
   SYNTAX      SEQUENCE OF Er1646v2VEthOamEntry
   MAX-ACCESS  not-accessible
   STATUS      current
   DESCRIPTION
      "OAM mode"
   ::= {er1646v2VEthOam 1}

er1646v2VEthOamEntry OBJECT-TYPE
   SYNTAX      Er1646v2VEthOamEntry
   MAX-ACCESS  not-accessible
   STATUS      current
   DESCRIPTION
      ""
   INDEX      { er1646v2VEthOamGlobalIx }
   ::= {er1646v2VEthOamSSCTable 1}

Er1646v2VEthOamEntry ::=
   SEQUENCE
      {
      er1646v2VEthOamGlobalIx
         GlobalIndex,
      er1646v2VEthOamMode
         INTEGER,
      er1646v2VEthOamLpbkLocalParAction
         INTEGER,
      er1646v2VEthOamLpbkSwapMacAddr
         INTEGER,
      er1646v2VEthOamLoopbackIgnoreRx
         INTEGER,
      er1646v2VEthOamEventsErroredSymbolEnabled
         INTEGER,
      er1646v2VEthOamEventsErroredSymbolWindowHi
         INTEGER,
      er1646v2VEthOamEventsErroredSymbolWindowLo
         INTEGER,
      er1646v2VEthOamEventsErroredSymbolThresholdHi
         Integer32,
      er1646v2VEthOamEventsErroredSymbolThresholdLo
         Integer32,
      er1646v2VEthOamEventsErroredFramePeriodEnabled
         INTEGER,
      er1646v2VEthOamEventsErroredFramePeriodWindow
         INTEGER,
      er1646v2VEthOamEventsErroredFramePeriodThreshold
         Integer32,
      er1646v2VEthOamEventsErroredFrameEnabled
         INTEGER,
      er1646v2VEthOamEventsErroredFrameWindow
         Integer32,
      er1646v2VEthOamEventsErroredFrameThreshold
         Integer32,
      er1646v2VEthOamEventsErroredFrameSecondsEnabled
         INTEGER,
      er1646v2VEthOamEventsErroredFrameSecondsWindow
         Integer32,
      er1646v2VEthOamEventsErroredFrameSecondsThreshold
         Integer32,
      er1646v2VEthOamEventsDyingGasp
         INTEGER,
      er1646v2VEthOamEventsCriticalEvent
         INTEGER
      }

er1646v2VEthOamGlobalIx OBJECT-TYPE
   SYNTAX      GlobalIndex
   MAX-ACCESS  not-accessible
   STATUS      current
   DESCRIPTION
      "The value of the tlsCntTreeGlobalIndex of the MANAGED OBJECT."
   ::= {er1646v2VEthOamEntry 10}

er1646v2VEthOamMode OBJECT-TYPE
   SYNTAX      INTEGER
               {
               disabled (0),
               passive (3),
               active (2)
               }
   MAX-ACCESS  read-write
   STATUS      current
   DESCRIPTION
      "Path: virtualEthernet.editConf.oam.mode

       Possibilities:
               disabled   (0)
               passive   (3)
               active   (2)"
   ::= {er1646v2VEthOamEntry 16777216}

er1646v2VEthOamLpbkLocalParAction OBJECT-TYPE
   SYNTAX      INTEGER
               {
               discard (0),
               forward (1)
               }
   MAX-ACCESS  read-write
   STATUS      current
   DESCRIPTION
      "Path: virtualEthernet.editConf.oam.loopbackLocalParserAction

       Possibilities:
               discard   (0)
               forward   (1)"
   ::= {er1646v2VEthOamEntry 33554432}

er1646v2VEthOamLpbkSwapMacAddr OBJECT-TYPE
   SYNTAX      INTEGER
               {
               disabled (0),
               enabled (1)
               }
   MAX-ACCESS  read-write
   STATUS      current
   DESCRIPTION
      "Path: virtualEthernet.editConf.oam.loopbackSwapMacAddresses

       Possibilities:
               disabled   (0)
               enabled   (1)"
   ::= {er1646v2VEthOamEntry 50331648}

er1646v2VEthOamLoopbackIgnoreRx OBJECT-TYPE
   SYNTAX      INTEGER
               {
               no (0),
               yes (1)
               }
   MAX-ACCESS  read-write
   STATUS      current
   DESCRIPTION
      "Path: virtualEthernet.editConf.oam.loopbackIgnoreRx

       Possibilities:
               no   (0)
               yes   (1)"
   ::= {er1646v2VEthOamEntry 67108864}

er1646v2VEthOamEventsErroredSymbolEnabled OBJECT-TYPE
   SYNTAX      INTEGER
               {
               no (0),
               yes (1)
               }
   MAX-ACCESS  read-write
   STATUS      current
   DESCRIPTION
      "Path: virtualEthernet.editConf.oam.events.erroredSymbol.enabled

       Possibilities:
               no   (0)
               yes   (1)"
   ::= {er1646v2VEthOamEntry 83951872}

er1646v2VEthOamEventsErroredSymbolWindowHi OBJECT-TYPE
   SYNTAX      INTEGER
               {
               default (0)
               }
   UNITS       "symbols"
   MAX-ACCESS  read-write
   STATUS      current
   DESCRIPTION
      "Path: virtualEthernet.editConf.oam.events.erroredSymbol.windowHi

       unit name = symbols

       Possibilities:
               default   (0)"
   ::= {er1646v2VEthOamEntry 83952128}

er1646v2VEthOamEventsErroredSymbolWindowLo OBJECT-TYPE
   SYNTAX      INTEGER
               {
               default (0)
               }
   UNITS       "symbols"
   MAX-ACCESS  read-write
   STATUS      current
   DESCRIPTION
      "Path: virtualEthernet.editConf.oam.events.erroredSymbol.windowLo

       unit name = symbols

       Possibilities:
               default   (0)"
   ::= {er1646v2VEthOamEntry 83952384}

er1646v2VEthOamEventsErroredSymbolThresholdHi OBJECT-TYPE
   SYNTAX      Integer32
   UNITS       "symbols"
   MAX-ACCESS  read-write
   STATUS      current
   DESCRIPTION
      "Path: virtualEthernet.editConf.oam.events.erroredSymbol.thresholdHi

       unit name = symbols"
   ::= {er1646v2VEthOamEntry 83952640}

er1646v2VEthOamEventsErroredSymbolThresholdLo OBJECT-TYPE
   SYNTAX      Integer32
   UNITS       "symbols"
   MAX-ACCESS  read-write
   STATUS      current
   DESCRIPTION
      "Path: virtualEthernet.editConf.oam.events.erroredSymbol.thresholdLo

       unit name = symbols"
   ::= {er1646v2VEthOamEntry 83952896}

er1646v2VEthOamEventsErroredFramePeriodEnabled OBJECT-TYPE
   SYNTAX      INTEGER
               {
               no (0),
               yes (1)
               }
   MAX-ACCESS  read-write
   STATUS      current
   DESCRIPTION
      "Path: virtualEthernet.editConf.oam.events.erroredFramePeriod.enabled

       Possibilities:
               no   (0)
               yes   (1)"
   ::= {er1646v2VEthOamEntry 84017408}

er1646v2VEthOamEventsErroredFramePeriodWindow OBJECT-TYPE
   SYNTAX      INTEGER
               {
               default (0)
               }
   UNITS       "frames"
   MAX-ACCESS  read-write
   STATUS      current
   DESCRIPTION
      "Path: virtualEthernet.editConf.oam.events.erroredFramePeriod.window

       unit name = frames

       Possibilities:
               default   (0)"
   ::= {er1646v2VEthOamEntry 84017664}

er1646v2VEthOamEventsErroredFramePeriodThreshold OBJECT-TYPE
   SYNTAX      Integer32
   UNITS       "frames"
   MAX-ACCESS  read-write
   STATUS      current
   DESCRIPTION
      "Path: virtualEthernet.editConf.oam.events.erroredFramePeriod.threshold

       unit name = frames"
   ::= {er1646v2VEthOamEntry 84017920}

er1646v2VEthOamEventsErroredFrameEnabled OBJECT-TYPE
   SYNTAX      INTEGER
               {
               no (0),
               yes (1)
               }
   MAX-ACCESS  read-write
   STATUS      current
   DESCRIPTION
      "Path: virtualEthernet.editConf.oam.events.erroredFrame.enabled

       Possibilities:
               no   (0)
               yes   (1)"
   ::= {er1646v2VEthOamEntry 84082944}

er1646v2VEthOamEventsErroredFrameWindow OBJECT-TYPE
   SYNTAX      Integer32
   UNITS       "100msec"
   MAX-ACCESS  read-write
   STATUS      current
   DESCRIPTION
      "Path: virtualEthernet.editConf.oam.events.erroredFrame.window

       unit name = 100msec"
   ::= {er1646v2VEthOamEntry 84083200}

er1646v2VEthOamEventsErroredFrameThreshold OBJECT-TYPE
   SYNTAX      Integer32
   UNITS       "frames"
   MAX-ACCESS  read-write
   STATUS      current
   DESCRIPTION
      "Path: virtualEthernet.editConf.oam.events.erroredFrame.threshold

       unit name = frames"
   ::= {er1646v2VEthOamEntry 84083456}

er1646v2VEthOamEventsErroredFrameSecondsEnabled OBJECT-TYPE
   SYNTAX      INTEGER
               {
               no (0),
               yes (1)
               }
   MAX-ACCESS  read-write
   STATUS      current
   DESCRIPTION
      "Path: virtualEthernet.editConf.oam.events.erroredFrameSeconds.enabled

       Possibilities:
               no   (0)
               yes   (1)"
   ::= {er1646v2VEthOamEntry 84148480}

er1646v2VEthOamEventsErroredFrameSecondsWindow OBJECT-TYPE
   SYNTAX      Integer32
   UNITS       "100msec"
   MAX-ACCESS  read-write
   STATUS      current
   DESCRIPTION
      "Path: virtualEthernet.editConf.oam.events.erroredFrameSeconds.window

       unit name = 100msec"
   ::= {er1646v2VEthOamEntry 84148736}

er1646v2VEthOamEventsErroredFrameSecondsThreshold OBJECT-TYPE
   SYNTAX      Integer32
   UNITS       "frames"
   MAX-ACCESS  read-write
   STATUS      current
   DESCRIPTION
      "Path: virtualEthernet.editConf.oam.events.erroredFrameSeconds.threshold

       unit name = frames"
   ::= {er1646v2VEthOamEntry 84148992}

er1646v2VEthOamEventsDyingGasp OBJECT-TYPE
   SYNTAX      INTEGER
               {
               disabled (0),
               enabled (1)
               }
   MAX-ACCESS  read-write
   STATUS      current
   DESCRIPTION
      "Path: virtualEthernet.editConf.oam.events.dyingGasp

       Possibilities:
               disabled   (0)
               enabled   (1)"
   ::= {er1646v2VEthOamEntry 84213760}

er1646v2VEthOamEventsCriticalEvent OBJECT-TYPE
   SYNTAX      INTEGER
               {
               disabled (0),
               enabled (1)
               }
   MAX-ACCESS  read-write
   STATUS      current
   DESCRIPTION
      "Path: virtualEthernet.editConf.oam.events.criticalEvent

       Possibilities:
               disabled   (0)
               enabled   (1)"
   ::= {er1646v2VEthOamEntry 84279296}


er1646v2VEthIp OBJECT IDENTIFIER ::= {er1646v2VEth 1}

er1646v2VEthIpSSCTable OBJECT-TYPE
   SYNTAX      SEQUENCE OF Er1646v2VEthIpEntry
   MAX-ACCESS  not-accessible
   STATUS      current
   DESCRIPTION
      "ip interface config parameters"
   ::= {er1646v2VEthIp 1}

er1646v2VEthIpEntry OBJECT-TYPE
   SYNTAX      Er1646v2VEthIpEntry
   MAX-ACCESS  not-accessible
   STATUS      current
   DESCRIPTION
      ""
   INDEX      { er1646v2VEthIpGlobalIx }
   ::= {er1646v2VEthIpSSCTable 1}

Er1646v2VEthIpEntry ::=
   SEQUENCE
      {
      er1646v2VEthIpGlobalIx
         GlobalIndex,
      er1646v2VEthIpVrfRouter
         DisplayString,
      er1646v2VEthIpAdr
         IpAddress,
      er1646v2VEthIpNetm
         IpAddress,
      er1646v2VEthIpSNetName
         INTEGER,
      er1646v2VEthIpSNetCust
         DisplayString,
      er1646v2VEthIpDhcpC
         INTEGER,
      er1646v2VEthIpDhcpGatewayPreference
         Integer32,
      er1646v2VEthIpDhcpRoutePreference
         Integer32,
      er1646v2VEthIpDhcpDnsPreference
         Integer32,
      er1646v2VEthIpMtu
         Integer32,
      er1646v2VEthIpMssAdjust
         INTEGER,
      er1646v2VEthIpRipMetric
         Integer32,
      er1646v2VEthIpRipMetricOut
         Integer32,
      er1646v2VEthIpRipMode
         INTEGER,
      er1646v2VEthIpRipTxVer
         INTEGER,
      er1646v2VEthIpRipRxVer
         INTEGER,
      er1646v2VEthIpRipSplitH
         INTEGER,
      er1646v2VEthIpRipAuth
         INTEGER,
      er1646v2VEthIpRipFilter
         DisplayString,
      er1646v2VEthIpRipFilterIn
         DisplayString,
      er1646v2VEthIpRipClearNextHop
         INTEGER,
      er1646v2VEthIpAccPol
         DisplayString,
      er1646v2VEthIpAB
         DisplayString,
      er1646v2VEthIpMA
         INTEGER,
      er1646v2VEthIpMF
         Integer32,
      er1646v2VEthIpDB
         INTEGER,
      er1646v2VEthIpIR
         INTEGER,
      er1646v2VEthIpIgmp
         INTEGER,
      er1646v2VEthIpNN
         DisplayString,
      er1646v2VEthIpVrrp
         INTEGER,
      er1646v2VEthIpPimMode
         INTEGER,
      er1646v2VEthIpPimDrPriority
         Counter32,
      er1646v2VEthIpPimHelloTime
         TimeTicks,
      er1646v2VEthIpPimPropagationDelay
         TimeTicks,
      er1646v2VEthIpPimOverrideInterval
         TimeTicks,
      er1646v2VEthIpPimBsrBorder
         INTEGER,
      er1646v2VEthIpPimTtlThreshold
         Integer32,
      er1646v2VEthIpIMNetworkUnreachable
         INTEGER,
      er1646v2VEthIpIMHostUnreachable
         INTEGER,
      er1646v2VEthIpIMProtocolUnreachable
         INTEGER,
      er1646v2VEthIpIMPortUnreachable
         INTEGER,
      er1646v2VEthIpIMMtuExceeded
         INTEGER,
      er1646v2VEthIpIMAdminProhibited
         INTEGER,
      er1646v2VEthIpIMTtlExceeded
         INTEGER,
      er1646v2VEthIpIMRedirect
         INTEGER
      }

er1646v2VEthIpGlobalIx OBJECT-TYPE
   SYNTAX      GlobalIndex
   MAX-ACCESS  not-accessible
   STATUS      current
   DESCRIPTION
      "The value of the tlsCntTreeGlobalIndex of the MANAGED OBJECT."
   ::= {er1646v2VEthIpEntry 10}

er1646v2VEthIpVrfRouter OBJECT-TYPE
   SYNTAX      DisplayString
   MAX-ACCESS  read-write
   STATUS      current
   DESCRIPTION
      "Path: virtualEthernet.editConf.ip.vrfRouter"
   ::= {er1646v2VEthIpEntry 738197504}

er1646v2VEthIpAdr OBJECT-TYPE
   SYNTAX      IpAddress
   MAX-ACCESS  read-write
   STATUS      current
   DESCRIPTION
      "Path: virtualEthernet.editConf.ip.address"
   ::= {er1646v2VEthIpEntry 2030043136}

er1646v2VEthIpNetm OBJECT-TYPE
   SYNTAX      IpAddress
   MAX-ACCESS  read-write
   STATUS      current
   DESCRIPTION
      "Path: virtualEthernet.editConf.ip.netMask"
   ::= {er1646v2VEthIpEntry 2063597568}

er1646v2VEthIpSNetName OBJECT-TYPE
   SYNTAX      INTEGER
               {
               slOPTg (0),
               corp (2),
               dmz (3),
               internet (1)
               }
   MAX-ACCESS  read-write
   STATUS      current
   DESCRIPTION
      "Path: virtualEthernet.editConf.ip.sNet.name

       Possibilities:
               <OPT>   (0)
               corp   (2)
               dmz   (3)
               internet   (1)"
   ::= {er1646v2VEthIpEntry 855703552}

er1646v2VEthIpSNetCust OBJECT-TYPE
   SYNTAX      DisplayString
   MAX-ACCESS  read-write
   STATUS      current
   DESCRIPTION
      "Path: virtualEthernet.editConf.ip.sNet.custom"
   ::= {er1646v2VEthIpEntry 855769088}

er1646v2VEthIpDhcpC OBJECT-TYPE
   SYNTAX      INTEGER
               {
               disabled (0),
               enabled (1)
               }
   MAX-ACCESS  read-write
   STATUS      current
   DESCRIPTION
      "Path: virtualEthernet.editConf.ip.dhcpClient

       Possibilities:
               disabled   (0)
               enabled   (1)"
   ::= {er1646v2VEthIpEntry 838860800}

er1646v2VEthIpDhcpGatewayPreference OBJECT-TYPE
   SYNTAX      Integer32
   MAX-ACCESS  read-write
   STATUS      current
   DESCRIPTION
      "Path: virtualEthernet.editConf.ip.dhcp.gatewayPreference"
   ::= {er1646v2VEthIpEntry 872480768}

er1646v2VEthIpDhcpRoutePreference OBJECT-TYPE
   SYNTAX      Integer32
   MAX-ACCESS  read-write
   STATUS      current
   DESCRIPTION
      "Path: virtualEthernet.editConf.ip.dhcp.routePreference"
   ::= {er1646v2VEthIpEntry 872546304}

er1646v2VEthIpDhcpDnsPreference OBJECT-TYPE
   SYNTAX      Integer32
   MAX-ACCESS  read-write
   STATUS      current
   DESCRIPTION
      "Path: virtualEthernet.editConf.ip.dhcp.dnsPreference"
   ::= {er1646v2VEthIpEntry 872611840}

er1646v2VEthIpMtu OBJECT-TYPE
   SYNTAX      Integer32
   MAX-ACCESS  read-write
   STATUS      current
   DESCRIPTION
      "Path: virtualEthernet.editConf.ip.mtu"
   ::= {er1646v2VEthIpEntry 671088640}

er1646v2VEthIpMssAdjust OBJECT-TYPE
   SYNTAX      INTEGER
               {
               disabled (0),
               auto (65536)
               }
   MAX-ACCESS  read-write
   STATUS      current
   DESCRIPTION
      "Path: virtualEthernet.editConf.ip.mssAdjust

       Possibilities:
               disabled   (0)
               auto   (65536)"
   ::= {er1646v2VEthIpEntry 754974720}

er1646v2VEthIpRipMetric OBJECT-TYPE
   SYNTAX      Integer32
   MAX-ACCESS  read-write
   STATUS      current
   DESCRIPTION
      "Path: virtualEthernet.editConf.ip.rip.metric"
   ::= {er1646v2VEthIpEntry 353566720}

er1646v2VEthIpRipMetricOut OBJECT-TYPE
   SYNTAX      Integer32
   MAX-ACCESS  read-write
   STATUS      current
   DESCRIPTION
      "Path: virtualEthernet.editConf.ip.rip.metricOut"
   ::= {er1646v2VEthIpEntry 353632256}

er1646v2VEthIpRipMode OBJECT-TYPE
   SYNTAX      INTEGER
               {
               disabled (0),
               passive (1),
               active (2)
               }
   MAX-ACCESS  read-write
   STATUS      current
   DESCRIPTION
      "Path: virtualEthernet.editConf.ip.rip.mode

       Possibilities:
               disabled   (0)
               passive   (1)
               active   (2)"
   ::= {er1646v2VEthIpEntry 353697792}

er1646v2VEthIpRipTxVer OBJECT-TYPE
   SYNTAX      INTEGER
               {
               rip1 (0),
               rip2 (1),
               rip1mcompatible (2)
               }
   MAX-ACCESS  read-write
   STATUS      current
   DESCRIPTION
      "Path: virtualEthernet.editConf.ip.rip.txVersion

       Possibilities:
               rip1   (0)
               rip2   (1)
               rip1-compatible   (2)"
   ::= {er1646v2VEthIpEntry 354615296}

er1646v2VEthIpRipRxVer OBJECT-TYPE
   SYNTAX      INTEGER
               {
               rip1only (0),
               rip2only (1),
               rip12 (2)
               }
   MAX-ACCESS  read-write
   STATUS      current
   DESCRIPTION
      "Path: virtualEthernet.editConf.ip.rip.rxVersion

       Possibilities:
               rip1only   (0)
               rip2only   (1)
               rip1&2   (2)"
   ::= {er1646v2VEthIpEntry 354680832}

er1646v2VEthIpRipSplitH OBJECT-TYPE
   SYNTAX      INTEGER
               {
               disabled (0),
               enabled (1),
               poisonedReverse (2)
               }
   MAX-ACCESS  read-write
   STATUS      current
   DESCRIPTION
      "Path: virtualEthernet.editConf.ip.rip.splitHorizon

       Possibilities:
               disabled   (0)
               enabled   (1)
               poisonedReverse   (2)"
   ::= {er1646v2VEthIpEntry 353828864}

er1646v2VEthIpRipAuth OBJECT-TYPE
   SYNTAX      INTEGER
               {
               disabled (0),
               texts (1),
               md5 (2)
               }
   MAX-ACCESS  read-write
   STATUS      current
   DESCRIPTION
      "Path: virtualEthernet.editConf.ip.rip.authentication

       Possibilities:
               disabled   (0)
               text    (1)
               md5   (2)"
   ::= {er1646v2VEthIpEntry 353501184}

er1646v2VEthIpRipFilter OBJECT-TYPE
   SYNTAX      DisplayString
   MAX-ACCESS  read-write
   STATUS      current
   DESCRIPTION
      "Path: virtualEthernet.editConf.ip.rip.filter"
   ::= {er1646v2VEthIpEntry 354418688}

er1646v2VEthIpRipFilterIn OBJECT-TYPE
   SYNTAX      DisplayString
   MAX-ACCESS  read-write
   STATUS      current
   DESCRIPTION
      "Path: virtualEthernet.editConf.ip.rip.filterIn"
   ::= {er1646v2VEthIpEntry 354484224}

er1646v2VEthIpRipClearNextHop OBJECT-TYPE
   SYNTAX      INTEGER
               {
               disabled (0),
               enabled (1)
               }
   MAX-ACCESS  read-write
   STATUS      current
   DESCRIPTION
      "Path: virtualEthernet.editConf.ip.rip.clearNextHop

       Possibilities:
               disabled   (0)
               enabled   (1)"
   ::= {er1646v2VEthIpEntry 352452608}

er1646v2VEthIpAccPol OBJECT-TYPE
   SYNTAX      DisplayString
   MAX-ACCESS  read-write
   STATUS      current
   DESCRIPTION
      "Path: virtualEthernet.editConf.ip.accessPolicy"
   ::= {er1646v2VEthIpEntry 704643072}

er1646v2VEthIpAB OBJECT-TYPE
   SYNTAX      DisplayString
   MAX-ACCESS  read-write
   STATUS      current
   DESCRIPTION
      "Path: virtualEthernet.editConf.ip.trafficPolicy"
   ::= {er1646v2VEthIpEntry 234881024}

er1646v2VEthIpMA OBJECT-TYPE
   SYNTAX      INTEGER
               {
               disabled (0),
               enabled (1)
               }
   MAX-ACCESS  read-write
   STATUS      current
   DESCRIPTION
      "Path: virtualEthernet.editConf.ip.mgmtAccess

       Possibilities:
               disabled   (0)
               enabled   (1)"
   ::= {er1646v2VEthIpEntry 268435456}

er1646v2VEthIpMF OBJECT-TYPE
   SYNTAX      Integer32
   MAX-ACCESS  read-write
   STATUS      current
   DESCRIPTION
      "Path: virtualEthernet.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2VEthIpEntry 285212672}

er1646v2VEthIpDB OBJECT-TYPE
   SYNTAX      INTEGER
               {
               disabled (0),
               enabled (1)
               }
   MAX-ACCESS  read-write
   STATUS      current
   DESCRIPTION
      "Path: virtualEthernet.editConf.ip.directedBroadcasts

       Possibilities:
               disabled   (0)
               enabled   (1)"
   ::= {er1646v2VEthIpEntry 369098752}

er1646v2VEthIpIR OBJECT-TYPE
   SYNTAX      INTEGER
               {
               disabled (0),
               enabled (1)
               }
   MAX-ACCESS  read-write
   STATUS      current
   DESCRIPTION
      "Path: virtualEthernet.editConf.ip.icmpRedirects

       Possibilities:
               disabled   (0)
               enabled   (1)"
   ::= {er1646v2VEthIpEntry 436207616}

er1646v2VEthIpIgmp OBJECT-TYPE
   SYNTAX      INTEGER
               {
               disabled (0),
               proxy (1),
               router (2),
               v3Router (5)
               }
   MAX-ACCESS  read-write
   STATUS      current
   DESCRIPTION
      "Path: virtualEthernet.editConf.ip.igmp

       Possibilities:
               disabled   (0)
               proxy   (1)
               router   (2)
               v3Router   (5)"
   ::= {er1646v2VEthIpEntry 536870912}

er1646v2VEthIpNN OBJECT-TYPE
   SYNTAX      DisplayString
   MAX-ACCESS  read-write
   STATUS      current
   DESCRIPTION
      "Path: virtualEthernet.editConf.ip.nat"
   ::= {er1646v2VEthIpEntry 452984832}

er1646v2VEthIpVrrp OBJECT-TYPE
   SYNTAX      INTEGER
               {
               disabled (0),
               enabled (1)
               }
   MAX-ACCESS  read-write
   STATUS      current
   DESCRIPTION
      "Path: virtualEthernet.editConf.ip.vrrp

       Possibilities:
               disabled   (0)
               enabled   (1)"
   ::= {er1646v2VEthIpEntry 721420288}

er1646v2VEthIpPimMode OBJECT-TYPE
   SYNTAX      INTEGER
               {
               disabled (0),
               sparse (1),
               passive (2)
               }
   MAX-ACCESS  read-write
   STATUS      current
   DESCRIPTION
      "Path: virtualEthernet.editConf.ip.pim.mode

       Possibilities:
               disabled   (0)
               sparse   (1)
               passive   (2)"
   ::= {er1646v2VEthIpEntry 771817472}

er1646v2VEthIpPimDrPriority OBJECT-TYPE
   SYNTAX      Counter32
   MAX-ACCESS  read-write
   STATUS      current
   DESCRIPTION
      "Path: virtualEthernet.editConf.ip.pim.drPriority

       32 bit unsigned wrappable counter."
   ::= {er1646v2VEthIpEntry 771883008}

er1646v2VEthIpPimHelloTime OBJECT-TYPE
   SYNTAX      TimeTicks
   MAX-ACCESS  read-write
   STATUS      current
   DESCRIPTION
      "Path: virtualEthernet.editConf.ip.pim.helloTime

       Time in centi-second."
   ::= {er1646v2VEthIpEntry 771948544}

er1646v2VEthIpPimPropagationDelay OBJECT-TYPE
   SYNTAX      TimeTicks
   MAX-ACCESS  read-write
   STATUS      current
   DESCRIPTION
      "Path: virtualEthernet.editConf.ip.pim.propagationDelay

       Time in centi-second."
   ::= {er1646v2VEthIpEntry 772014080}

er1646v2VEthIpPimOverrideInterval OBJECT-TYPE
   SYNTAX      TimeTicks
   MAX-ACCESS  read-write
   STATUS      current
   DESCRIPTION
      "Path: virtualEthernet.editConf.ip.pim.overrideInterval

       Time in centi-second."
   ::= {er1646v2VEthIpEntry 772079616}

er1646v2VEthIpPimBsrBorder OBJECT-TYPE
   SYNTAX      INTEGER
               {
               disabled (0),
               enabled (1)
               }
   MAX-ACCESS  read-write
   STATUS      current
   DESCRIPTION
      "Path: virtualEthernet.editConf.ip.pim.bsrBorder

       Possibilities:
               disabled   (0)
               enabled   (1)"
   ::= {er1646v2VEthIpEntry 772145152}

er1646v2VEthIpPimTtlThreshold OBJECT-TYPE
   SYNTAX      Integer32
   MAX-ACCESS  read-write
   STATUS      current
   DESCRIPTION
      "Path: virtualEthernet.editConf.ip.pim.ttlThreshold"
   ::= {er1646v2VEthIpEntry 772210688}

er1646v2VEthIpIMNetworkUnreachable OBJECT-TYPE
   SYNTAX      INTEGER
               {
               disabled (0),
               enabled (1)
               }
   MAX-ACCESS  read-write
   STATUS      current
   DESCRIPTION
      "Path: virtualEthernet.editConf.ip.icmpMessages.networkUnreachable

       Possibilities:
               disabled   (0)
               enabled   (1)"
   ::= {er1646v2VEthIpEntry 788594688}

er1646v2VEthIpIMHostUnreachable OBJECT-TYPE
   SYNTAX      INTEGER
               {
               disabled (0),
               enabled (1)
               }
   MAX-ACCESS  read-write
   STATUS      current
   DESCRIPTION
      "Path: virtualEthernet.editConf.ip.icmpMessages.hostUnreachable

       Possibilities:
               disabled   (0)
               enabled   (1)"
   ::= {er1646v2VEthIpEntry 788660224}

er1646v2VEthIpIMProtocolUnreachable OBJECT-TYPE
   SYNTAX      INTEGER
               {
               disabled (0),
               enabled (1)
               }
   MAX-ACCESS  read-write
   STATUS      current
   DESCRIPTION
      "Path: virtualEthernet.editConf.ip.icmpMessages.protocolUnreachable

       Possibilities:
               disabled   (0)
               enabled   (1)"
   ::= {er1646v2VEthIpEntry 788725760}

er1646v2VEthIpIMPortUnreachable OBJECT-TYPE
   SYNTAX      INTEGER
               {
               disabled (0),
               enabled (1)
               }
   MAX-ACCESS  read-write
   STATUS      current
   DESCRIPTION
      "Path: virtualEthernet.editConf.ip.icmpMessages.portUnreachable

       Possibilities:
               disabled   (0)
               enabled   (1)"
   ::= {er1646v2VEthIpEntry 788791296}

er1646v2VEthIpIMMtuExceeded OBJECT-TYPE
   SYNTAX      INTEGER
               {
               disabled (0),
               enabled (1)
               }
   MAX-ACCESS  read-write
   STATUS      current
   DESCRIPTION
      "Path: virtualEthernet.editConf.ip.icmpMessages.mtuExceeded

       Possibilities:
               disabled   (0)
               enabled   (1)"
   ::= {er1646v2VEthIpEntry 788856832}

er1646v2VEthIpIMAdminProhibited OBJECT-TYPE
   SYNTAX      INTEGER
               {
               disabled (0),
               enabled (1)
               }
   MAX-ACCESS  read-write
   STATUS      current
   DESCRIPTION
      "Path: virtualEthernet.editConf.ip.icmpMessages.adminProhibited

       Possibilities:
               disabled   (0)
               enabled   (1)"
   ::= {er1646v2VEthIpEntry 788922368}

er1646v2VEthIpIMTtlExceeded OBJECT-TYPE
   SYNTAX      INTEGER
               {
               disabled (0),
               enabled (1)
               }
   MAX-ACCESS  read-write
   STATUS      current
   DESCRIPTION
      "Path: virtualEthernet.editConf.ip.icmpMessages.ttlExceeded

       Possibilities:
               disabled   (0)
               enabled   (1)"
   ::= {er1646v2VEthIpEntry 788987904}

er1646v2VEthIpIMRedirect OBJECT-TYPE
   SYNTAX      INTEGER
               {
               disabled (0),
               enabled (1)
               }
   MAX-ACCESS  read-write
   STATUS      current
   DESCRIPTION
      "Path: virtualEthernet.editConf.ip.icmpMessages.redirect

       Possibilities:
               disabled   (0)
               enabled   (1)"
   ::= {er1646v2VEthIpEntry 789053440}

er1646v2VEthIpSaddr OBJECT-TYPE
   SYNTAX      SEQUENCE OF Er1646v2VEthIpSaddrEntry
   MAX-ACCESS  not-accessible
   STATUS      current
   DESCRIPTION
      ""
   ::= {er1646v2VEthIp 385875968}

er1646v2VEthIpSaddrEntry OBJECT-TYPE
   SYNTAX      Er1646v2VEthIpSaddrEntry
   MAX-ACCESS  not-accessible
   STATUS      current
   DESCRIPTION
      ""
   INDEX      { er1646v2VEthIpSaddrGlobalIx,
                er1646v2VEthIpSaddrTableIx }
   ::= {er1646v2VEthIpSaddr 1}

Er1646v2VEthIpSaddrEntry ::=
   SEQUENCE
      {
      er1646v2VEthIpSaddrActions
         VariableLengthTableActions,
      er1646v2VEthIpSaddrGlobalIx
         GlobalIndex,
      er1646v2VEthIpSaddrTableIx
         TableIndex,
      er1646v2VEthIpSaddrAddress
         IpAddress,
      er1646v2VEthIpSaddrNetMask
         IpAddress
      }

er1646v2VEthIpSaddrActions OBJECT-TYPE
   SYNTAX      VariableLengthTableActions
   MAX-ACCESS  read-write
   STATUS      current
   DESCRIPTION
      "By way of this field, some manipulations
       on this table may be performed."
   ::= {er1646v2VEthIpSaddrEntry 2}

er1646v2VEthIpSaddrGlobalIx OBJECT-TYPE
   SYNTAX      GlobalIndex
   MAX-ACCESS  not-accessible
   STATUS      current
   DESCRIPTION
      "The value of the tlsCntTreeGlobalIndex of the MANAGED OBJECT."
   ::= {er1646v2VEthIpSaddrEntry 10}

er1646v2VEthIpSaddrTableIx OBJECT-TYPE
   SYNTAX      TableIndex
   MAX-ACCESS  not-accessible
   STATUS      current
   DESCRIPTION
      ""
   ::= {er1646v2VEthIpSaddrEntry 11}

er1646v2VEthIpSaddrAddress OBJECT-TYPE
   SYNTAX      IpAddress
   MAX-ACCESS  read-write
   STATUS      current
   DESCRIPTION
      "Path: virtualEthernet.editConf.ip.secondaryIp.address"
   ::= {er1646v2VEthIpSaddrEntry 2030043136}

er1646v2VEthIpSaddrNetMask OBJECT-TYPE
   SYNTAX      IpAddress
   MAX-ACCESS  read-write
   STATUS      current
   DESCRIPTION
      "Path: virtualEthernet.editConf.ip.secondaryIp.netMask"
   ::= {er1646v2VEthIpSaddrEntry 2063597568}

er1646v2VEthIpH OBJECT-TYPE
   SYNTAX      SEQUENCE OF Er1646v2VEthIpHEntry
   MAX-ACCESS  not-accessible
   STATUS      current
   DESCRIPTION
      ""
   ::= {er1646v2VEthIp 251658240}

er1646v2VEthIpHEntry OBJECT-TYPE
   SYNTAX      Er1646v2VEthIpHEntry
   MAX-ACCESS  not-accessible
   STATUS      current
   DESCRIPTION
      ""
   INDEX      { er1646v2VEthIpHGlobalIx,
                er1646v2VEthIpHTableIx }
   ::= {er1646v2VEthIpH 1}

Er1646v2VEthIpHEntry ::=
   SEQUENCE
      {
      er1646v2VEthIpHActions
         VariableLengthTableActions,
      er1646v2VEthIpHGlobalIx
         GlobalIndex,
      er1646v2VEthIpHTableIx
         TableIndex,
      er1646v2VEthIpHAddress
         IpAddress,
      er1646v2VEthIpHDhcpRelayOptionSubscriberId
         DisplayString
      }

er1646v2VEthIpHActions OBJECT-TYPE
   SYNTAX      VariableLengthTableActions
   MAX-ACCESS  read-write
   STATUS      current
   DESCRIPTION
      "By way of this field, some manipulations
       on this table may be performed."
   ::= {er1646v2VEthIpHEntry 2}

er1646v2VEthIpHGlobalIx OBJECT-TYPE
   SYNTAX      GlobalIndex
   MAX-ACCESS  not-accessible
   STATUS      current
   DESCRIPTION
      "The value of the tlsCntTreeGlobalIndex of the MANAGED OBJECT."
   ::= {er1646v2VEthIpHEntry 10}

er1646v2VEthIpHTableIx OBJECT-TYPE
   SYNTAX      TableIndex
   MAX-ACCESS  not-accessible
   STATUS      current
   DESCRIPTION
      ""
   ::= {er1646v2VEthIpHEntry 11}

er1646v2VEthIpHAddress OBJECT-TYPE
   SYNTAX      IpAddress
   MAX-ACCESS  read-write
   STATUS      current
   DESCRIPTION
      "Path: virtualEthernet.editConf.ip.helpers.address"
   ::= {er1646v2VEthIpHEntry 16777216}

er1646v2VEthIpHDhcpRelayOptionSubscriberId OBJECT-TYPE
   SYNTAX      DisplayString
   MAX-ACCESS  read-write
   STATUS      current
   DESCRIPTION
      "Path: virtualEthernet.editConf.ip.helpers.dhcpRelayOption.subscriberId"
   ::= {er1646v2VEthIpHEntry 33947648}


er1646v2VEthVlan OBJECT IDENTIFIER ::= {er1646v2VEth 33}

er1646v2VEthVlanSSCTable OBJECT-TYPE
   SYNTAX      SEQUENCE OF Er1646v2VEthVlanEntry
   MAX-ACCESS  not-accessible
   STATUS      current
   DESCRIPTION
      ""
   ::= {er1646v2VEthVlan 1}

er1646v2VEthVlanEntry OBJECT-TYPE
   SYNTAX      Er1646v2VEthVlanEntry
   MAX-ACCESS  not-accessible
   STATUS      current
   DESCRIPTION
      ""
   INDEX      { er1646v2VEthVlanGlobalIx,
                er1646v2VEthVlanTableIx }
   ::= {er1646v2VEthVlanSSCTable 1}

Er1646v2VEthVlanEntry ::=
   SEQUENCE
      {
      er1646v2VEthVlanActions
         VariableLengthTableActions,
      er1646v2VEthVlanGlobalIx
         GlobalIndex,
      er1646v2VEthVlanTableIx
         TableIndex,
      er1646v2VEthVlanName
         DisplayString,
      er1646v2VEthVlanRemark
         DisplayString,
      er1646v2VEthVlanAdminStatus
         INTEGER,
      er1646v2VEthVlanMode
         INTEGER,
      er1646v2VEthVlanPriorityPolicy
         DisplayString,
      er1646v2VEthVlanIpVrfRouter
         DisplayString,
      er1646v2VEthVlanIpAdr
         IpAddress,
      er1646v2VEthVlanIpNetm
         IpAddress,
      er1646v2VEthVlanIpSNetName
         INTEGER,
      er1646v2VEthVlanIpSNetCust
         DisplayString,
      er1646v2VEthVlanIpDhcpC
         INTEGER,
      er1646v2VEthVlanIpDhcpGatewayPreference
         Integer32,
      er1646v2VEthVlanIpDhcpRoutePreference
         Integer32,
      er1646v2VEthVlanIpDhcpDnsPreference
         Integer32,
      er1646v2VEthVlanIpMtu
         Integer32,
      er1646v2VEthVlanIpMssAdjust
         INTEGER,
      er1646v2VEthVlanIpRipMetric
         Integer32,
      er1646v2VEthVlanIpRipMetricOut
         Integer32,
      er1646v2VEthVlanIpRipMode
         INTEGER,
      er1646v2VEthVlanIpRipTxVer
         INTEGER,
      er1646v2VEthVlanIpRipRxVer
         INTEGER,
      er1646v2VEthVlanIpRipSplitH
         INTEGER,
      er1646v2VEthVlanIpRipAuth
         INTEGER,
      er1646v2VEthVlanIpRipFilter
         DisplayString,
      er1646v2VEthVlanIpRipFilterIn
         DisplayString,
      er1646v2VEthVlanIpRipClearNextHop
         INTEGER,
      er1646v2VEthVlanIpAccPol
         DisplayString,
      er1646v2VEthVlanIpAB
         DisplayString,
      er1646v2VEthVlanIpMA
         INTEGER,
      er1646v2VEthVlanIpMF
         Integer32,
      er1646v2VEthVlanIpDB
         INTEGER,
      er1646v2VEthVlanIpIR
         INTEGER,
      er1646v2VEthVlanIpIgmp
         INTEGER,
      er1646v2VEthVlanIpNN
         DisplayString,
      er1646v2VEthVlanIpVrrp
         INTEGER,
      er1646v2VEthVlanIpPimMode
         INTEGER,
      er1646v2VEthVlanIpPimDrPriority
         Counter32,
      er1646v2VEthVlanIpPimHelloTime
         TimeTicks,
      er1646v2VEthVlanIpPimPropagationDelay
         TimeTicks,
      er1646v2VEthVlanIpPimOverrideInterval
         TimeTicks,
      er1646v2VEthVlanIpPimBsrBorder
         INTEGER,
      er1646v2VEthVlanIpPimTtlThreshold
         Integer32,
      er1646v2VEthVlanIpIMNetworkUnreachable
         INTEGER,
      er1646v2VEthVlanIpIMHostUnreachable
         INTEGER,
      er1646v2VEthVlanIpIMProtocolUnreachable
         INTEGER,
      er1646v2VEthVlanIpIMPortUnreachable
         INTEGER,
      er1646v2VEthVlanIpIMMtuExceeded
         INTEGER,
      er1646v2VEthVlanIpIMAdminProhibited
         INTEGER,
      er1646v2VEthVlanIpIMTtlExceeded
         INTEGER,
      er1646v2VEthVlanIpIMRedirect
         INTEGER,
      er1646v2VEthVlanIpV6VrfRouter
         DisplayString,
      er1646v2VEthVlanIpV6AddrAutoConfigNrDupAddrDetects
         Integer32,
      er1646v2VEthVlanIpV6AddrAutoConfigAcceptRa
         INTEGER,
      er1646v2VEthVlanIpV6AddrAutoConfigAcceptRaRdnss
         INTEGER,
      er1646v2VEthVlanIpV6AddrAutoConfigAcceptRaDnssl
         INTEGER,
      er1646v2VEthVlanIpV6DefaultRoute
         INTEGER,
      er1646v2VEthVlanIpV6RaSend
         INTEGER,
      er1646v2VEthVlanIpV6RaMinInterval
         TimeTicks,
      er1646v2VEthVlanIpV6RaMaxInterval
         TimeTicks,
      er1646v2VEthVlanIpV6RaManagedFlag
         INTEGER,
      er1646v2VEthVlanIpV6RaOtherConfFlag
         INTEGER,
      er1646v2VEthVlanIpV6RaLinkMtu
         Integer32,
      er1646v2VEthVlanIpV6RaReachableTime
         TimeTicks,
      er1646v2VEthVlanIpV6RaRetransmitTime
         TimeTicks,
      er1646v2VEthVlanIpV6RaHopLimit
         Integer32,
      er1646v2VEthVlanIpV6RaDefaultLifeTime
         TimeTicks,
      er1646v2VEthVlanIpV6RaDnsOptionsRdnssLifeTime
         TimeTicks,
      er1646v2VEthVlanIpV6RaDnsOptionsRdnssImportServers
         INTEGER,
      er1646v2VEthVlanIpV6RaDnsOptionsDnsslLifeTime
         TimeTicks,
      er1646v2VEthVlanIpV6RaDnsOptionsDnsslImportDomains
         INTEGER,
      er1646v2VEthVlanIpV6RsSend
         INTEGER,
      er1646v2VEthVlanIpV6RsMaxRandomDelay
         TimeTicks,
      er1646v2VEthVlanIpV6RsInterval
         TimeTicks,
      er1646v2VEthVlanIpV6RsMaxSolicitations
         Integer32,
      er1646v2VEthVlanIpV6TrafficPolicyInbound
         DisplayString,
      er1646v2VEthVlanIpV6TrafficPolicyOutbound
         DisplayString,
      er1646v2VEthVlanIpV6FirewallZone
         DisplayString,
      er1646v2VEthVlanIpV6DhcpClientAddrAC
         INTEGER,
      er1646v2VEthVlanIpV6DhcpClientPrDelMode
         INTEGER,
      er1646v2VEthVlanIpV6DhcpClientPrDelPool
         DisplayString,
      er1646v2VEthVlanIpV6DhcpClientPrDelPdExclOpt
         INTEGER,
      er1646v2VEthVlanIpV6DhcpClientDnsServerPref
         Integer32,
      er1646v2VEthVlanIpV6DhcpClientRapidCommit
         INTEGER,
      er1646v2VEthVlanIpV6DhcpClientTimersSolTimeOut
         TimeTicks,
      er1646v2VEthVlanIpV6DhcpClientTimersSolMaxRt
         TimeTicks,
      er1646v2VEthVlanIpV6DhcpClientTimersInfoRefresh
         TimeTicks,
      er1646v2VEthVlanIpV6DhcpServerMode
         INTEGER,
      er1646v2VEthVlanIpV6DhcpServerPreference
         Integer32,
      er1646v2VEthVlanIpV6DhcpServerPool
         DisplayString,
      er1646v2VEthVlanIpV6DhcpServerRapidCommit
         INTEGER,
      er1646v2VEthVlanIpV6DhcpServerTimersInfoRefresh
         TimeTicks,
      er1646v2VEthVlanIpV6DhcpRelayMode
         INTEGER,
      er1646v2VEthVlanIpV6SendRedirect
         INTEGER,
      er1646v2VEthVlanIpV6LinkMtu
         Integer32,
      er1646v2VEthVlanIpV6InterfaceId
         OCTET STRING,
      er1646v2VEthVlanIpV6MF
         Integer32,
      er1646v2VEthVlanIpV6IcmpMessagesNoRoute
         INTEGER,
      er1646v2VEthVlanIpV6IcmpMessagesBeyondScope
         INTEGER,
      er1646v2VEthVlanIpV6IcmpMessagesAddressUnreachable
         INTEGER,
      er1646v2VEthVlanIpV6IcmpMessagesPortUnreachable
         INTEGER,
      er1646v2VEthVlanIpV6IcmpMessagesPacketTooBig
         INTEGER,
      er1646v2VEthVlanIpV6IcmpMessagesHopLimitExceeded
         INTEGER,
      er1646v2VEthVlanIpV6IcmpMessagesFragTimeExceeded
         INTEGER,
      er1646v2VEthVlanIpV6IcmpMessagesHeaderFieldErr
         INTEGER,
      er1646v2VEthVlanIpV6IcmpMessagesOptionUnrecognized
         INTEGER,
      er1646v2VEthVlanIpV6IcmpMessagesRedirect
         INTEGER,
      er1646v2VEthVlanBridgingAccList
         DisplayString,
      er1646v2VEthVlanBridgingInACL
         DisplayString,
      er1646v2VEthVlanBridgingTp
         DisplayString,
      er1646v2VEthVlanBridgingBrGrp
         DisplayString,
      er1646v2VEthVlanBridgingLimBC
         INTEGER,
      er1646v2VEthVlanBridgingPrivateMode
         INTEGER,
      er1646v2VEthVlanBridgingLearning
         INTEGER,
      er1646v2VEthVlanBridgingMaxCacheSize
         INTEGER,
      er1646v2VEthVlanBridgingRelearnDropOnRelearn
         INTEGER,
      er1646v2VEthVlanBridgingRelearnShutdownThreshold
         Integer32,
      er1646v2VEthVlanBridgingRelearnShutdownTime
         TimeTicks,
      er1646v2VEthVlanBridgingRelearnLoopDetection
         INTEGER,
      er1646v2VEthVlanBridgingRelearnLoopDetectionInterval
         TimeTicks,
      er1646v2VEthVlanBridgingVlanMemberShip
         INTEGER,
      er1646v2VEthVlanBridgingVlTUntaggedAction
         INTEGER,
      er1646v2VEthVlanBridgingVlTUntaggedTagInfoTpid
         INTEGER,
      er1646v2VEthVlanBridgingVlTUntaggedTagInfoVid
         Integer32,
      er1646v2VEthVlanBridgingVlTUnknownVlansAction
         INTEGER,
      er1646v2VEthVlanBridgingVlTUnknownVlansTagInfoTpid
         INTEGER,
      er1646v2VEthVlanBridgingVlTUnknownVlansTagInfoVid
         Integer32,
      er1646v2VEthVlanBridgingDot1adType
         INTEGER,
      er1646v2VEthVlanBridgingPriority
         Integer32,
      er1646v2VEthVlanBridgingPathCost
         Integer32,
      er1646v2VEthVlanBridgingInternalPathCost
         Integer32,
      er1646v2VEthVlanBridgingTCD
         INTEGER,
      er1646v2VEthVlanBridgingRestrictedRole
         INTEGER,
      er1646v2VEthVlanBridgingAdminEdge
         INTEGER,
      er1646v2VEthVlanBridgingOamMacDeviceMac
         DisplayString,
      er1646v2VEthVlanBridgingOamMacUserMac
         OCTET STRING,
      er1646v2VEthVlanBridgingOamMacBridgeMac
         DisplayString,
      er1646v2VEthVlanBridgingMgmtInline
         INTEGER,
      er1646v2VEthVlanBridgingL2ptMode
         INTEGER,
      er1646v2VEthVlanBridgingL2ptProtocols
         Integer32,
      er1646v2VEthVlanBridgingL2ptDestMac
         OCTET STRING,
      er1646v2VEthVlanBridgingL2ptCos
         INTEGER,
      er1646v2VEthVlanBridgingL2ptDropThrStp
         INTEGER,
      er1646v2VEthVlanBridgingL2ptDropThrLldp
         INTEGER,
      er1646v2VEthVlanBridgingL2ptDropThrOam
         INTEGER,
      er1646v2VEthVlanBridgingL2ptDropThrCdp
         INTEGER,
      er1646v2VEthVlanBridgingL2ptDropThrVtp
         INTEGER,
      er1646v2VEthVlanBridgingL2ptDropThrLacp
         INTEGER,
      er1646v2VEthVlanBridgingL2ptDropThrEfmOam
         INTEGER,
      er1646v2VEthVlanBridgingL2ptDropThrPvst
         INTEGER,
      er1646v2VEthVlanBridgingL2ptDropThrMmrp
         INTEGER,
      er1646v2VEthVlanBridgingL2ptDropThrMvrp
         INTEGER,
      er1646v2VEthVlanBridgingL2ptDropThrGvrp
         INTEGER,
      er1646v2VEthVlanBridgingL2ptDropThrGmrp
         INTEGER,
      er1646v2VEthVlanBridgingL2ptDropThrDtp
         INTEGER,
      er1646v2VEthVlanBridgingL2ptDropThrPagp
         INTEGER,
      er1646v2VEthVlanBridgingL2ptDropThrUdld
         INTEGER,
      er1646v2VEthVlanVlanVid
         INTEGER,
      er1646v2VEthVlanVlanVidExtensionSingle
         OCTET STRING,
      er1646v2VEthVlanVlanVidExtensionEndVid
         Integer32,
      er1646v2VEthVlanVlanTpid
         INTEGER,
      er1646v2VEthVlanVlanTagSign
         INTEGER,
      er1646v2VEthVlanVlanChTos
         INTEGER,
      er1646v2VEthVlanVlanCTMapP0
         INTEGER,
      er1646v2VEthVlanVlanCTMapP1
         INTEGER,
      er1646v2VEthVlanVlanCTMapP2
         INTEGER,
      er1646v2VEthVlanVlanCTMapP3
         INTEGER,
      er1646v2VEthVlanVlanCTMapP4
         INTEGER,
      er1646v2VEthVlanVlanCTMapP5
         INTEGER,
      er1646v2VEthVlanVlanCTMapP6
         INTEGER,
      er1646v2VEthVlanVlanCTMapP7
         INTEGER,
      er1646v2VEthVlanVlanTxCos
         INTEGER,
      er1646v2VEthVlanVlanCCMapP0
         Integer32,
      er1646v2VEthVlanVlanCCMapP1
         Integer32,
      er1646v2VEthVlanVlanCCMapP2
         Integer32,
      er1646v2VEthVlanVlanCCMapP3
         Integer32,
      er1646v2VEthVlanVlanCCMapP4
         Integer32,
      er1646v2VEthVlanVlanCCMapP5
         Integer32,
      er1646v2VEthVlanVlanCCMapP6
         Integer32,
      er1646v2VEthVlanVlanCCMapP7
         Integer32,
      er1646v2VEthVlanVlanQCMapQueue1
         Integer32,
      er1646v2VEthVlanVlanQCMapQueue2
         Integer32,
      er1646v2VEthVlanVlanQCMapQueue3
         Integer32,
      er1646v2VEthVlanVlanQCMapQueue4
         Integer32,
      er1646v2VEthVlanVlanQCMapQueue5
         Integer32,
      er1646v2VEthVlanVlanQCMapLowDelayQueue
         Integer32,
      er1646v2VEthVlanVlanQCMapLowDelay2Queue
         Integer32,
      er1646v2VEthVlanVlanQCMapSystemQueue
         Integer32,
      er1646v2VEthVlanVlanQinQSVid
         Integer32,
      er1646v2VEthVlanVlanQinQSTpid
         INTEGER,
      er1646v2VEthVlanVlanArpTimeOut
         TimeTicks,
      er1646v2VEthVlanVlanArpProxyArp
         INTEGER,
      er1646v2VEthVlanBandwidthMode
         INTEGER,
      er1646v2VEthVlanBandwidthCir
         Integer32,
      er1646v2VEthVlanBandwidthEir
         Integer32,
      er1646v2VEthVlanBandwidthUnit
         INTEGER,
      er1646v2VEthVlanBandwidthTc
         INTEGER,
      er1646v2VEthVlanBandwidthTcFactor
         INTEGER,
      er1646v2VEthVlanBandwidthCorrType
         INTEGER,
      er1646v2VEthVlanBandwidthCorrPredefEncapsFrameRelay
         DisplayString,
      er1646v2VEthVlanBandwidthCorrPredefEncapsPpp
         DisplayString,
      er1646v2VEthVlanBandwidthCorrPredefEncapsAtmHl
         INTEGER,
      er1646v2VEthVlanBandwidthCorrPredefEncapsAtmMp
         INTEGER,
      er1646v2VEthVlanBandwidthCorrPredefEncapsHdlc
         DisplayString,
      er1646v2VEthVlanBandwidthCorrPredefEncapsEfmFs
         Integer32,
      er1646v2VEthVlanBandwidthCorrPredefEncapsEfmIb
         Integer32,
      er1646v2VEthVlanBandwidthCorrPredefMode
         INTEGER,
      er1646v2VEthVlanBandwidthCorrManualOverhead
         Integer32,
      er1646v2VEthVlanBandwidthCorrManualFrameData
         Counter32,
      er1646v2VEthVlanBandwidthCorrManualFrameHeader
         Counter32,
      er1646v2VEthVlanBandwidthMaxFifoQLen
         Integer32,
      er1646v2VEthVlanBandwidthDeFlagCir
         INTEGER,
      er1646v2VEthVlanBandwidthDeFlagEir
         INTEGER,
      er1646v2VEthVlanBandwidthDeFlagViolate
         INTEGER,
      er1646v2VEthVlanBandwidthActCirActNone
         OCTET STRING,
      er1646v2VEthVlanBandwidthActCirActEthCos1
         INTEGER,
      er1646v2VEthVlanBandwidthActCirActEthDei1
         INTEGER,
      er1646v2VEthVlanBandwidthActCirActEthCos2
         INTEGER,
      er1646v2VEthVlanBandwidthActCirActEthDei2
         INTEGER,
      er1646v2VEthVlanBandwidthActCirActEthCos3
         INTEGER,
      er1646v2VEthVlanBandwidthActCirActEthDei3
         INTEGER,
      er1646v2VEthVlanBandwidthActCirActEthCos4
         INTEGER,
      er1646v2VEthVlanBandwidthActCirActEthDei4
         INTEGER,
      er1646v2VEthVlanBandwidthActCirActEthCos5
         INTEGER,
      er1646v2VEthVlanBandwidthActCirActEthDei5
         INTEGER,
      er1646v2VEthVlanBandwidthActCirActEthCos6
         INTEGER,
      er1646v2VEthVlanBandwidthActCirActEthDei6
         INTEGER,
      er1646v2VEthVlanBandwidthActCirActEthCos7
         INTEGER,
      er1646v2VEthVlanBandwidthActCirActEthDei7
         INTEGER,
      er1646v2VEthVlanBandwidthActCirActEthCos8
         INTEGER,
      er1646v2VEthVlanBandwidthActCirActEthDei8
         INTEGER,
      er1646v2VEthVlanBandwidthActCirActEthTos
         INTEGER,
      er1646v2VEthVlanBandwidthActCirActEthQueue
         INTEGER,
      er1646v2VEthVlanBandwidthActCirActEthDrpLev
         INTEGER,
      er1646v2VEthVlanBandwidthActCirActEthDeFlag
         INTEGER,
      er1646v2VEthVlanBandwidthActCirActIpTos
         INTEGER,
      er1646v2VEthVlanBandwidthActCirActIpQueue
         INTEGER,
      er1646v2VEthVlanBandwidthActCirActIpDrpLev
         INTEGER,
      er1646v2VEthVlanBandwidthActCirActIpDeFlag
         INTEGER,
      er1646v2VEthVlanBandwidthActEirActNone
         OCTET STRING,
      er1646v2VEthVlanBandwidthActEirActEthCos1
         INTEGER,
      er1646v2VEthVlanBandwidthActEirActEthDei1
         INTEGER,
      er1646v2VEthVlanBandwidthActEirActEthCos2
         INTEGER,
      er1646v2VEthVlanBandwidthActEirActEthDei2
         INTEGER,
      er1646v2VEthVlanBandwidthActEirActEthCos3
         INTEGER,
      er1646v2VEthVlanBandwidthActEirActEthDei3
         INTEGER,
      er1646v2VEthVlanBandwidthActEirActEthCos4
         INTEGER,
      er1646v2VEthVlanBandwidthActEirActEthDei4
         INTEGER,
      er1646v2VEthVlanBandwidthActEirActEthCos5
         INTEGER,
      er1646v2VEthVlanBandwidthActEirActEthDei5
         INTEGER,
      er1646v2VEthVlanBandwidthActEirActEthCos6
         INTEGER,
      er1646v2VEthVlanBandwidthActEirActEthDei6
         INTEGER,
      er1646v2VEthVlanBandwidthActEirActEthCos7
         INTEGER,
      er1646v2VEthVlanBandwidthActEirActEthDei7
         INTEGER,
      er1646v2VEthVlanBandwidthActEirActEthCos8
         INTEGER,
      er1646v2VEthVlanBandwidthActEirActEthDei8
         INTEGER,
      er1646v2VEthVlanBandwidthActEirActEthTos
         INTEGER,
      er1646v2VEthVlanBandwidthActEirActEthQueue
         INTEGER,
      er1646v2VEthVlanBandwidthActEirActEthDrpLev
         INTEGER,
      er1646v2VEthVlanBandwidthActEirActEthDeFlag
         INTEGER,
      er1646v2VEthVlanBandwidthActEirActIpTos
         INTEGER,
      er1646v2VEthVlanBandwidthActEirActIpQueue
         INTEGER,
      er1646v2VEthVlanBandwidthActEirActIpDrpLev
         INTEGER,
      er1646v2VEthVlanBandwidthActEirActIpDeFlag
         INTEGER,
      er1646v2VEthVlanBandwidthActViolActNone
         OCTET STRING,
      er1646v2VEthVlanBandwidthActViolActDrop
         OCTET STRING,
      er1646v2VEthVlanBandwidthActViolActEthCos1
         INTEGER,
      er1646v2VEthVlanBandwidthActViolActEthDei1
         INTEGER,
      er1646v2VEthVlanBandwidthActViolActEthCos2
         INTEGER,
      er1646v2VEthVlanBandwidthActViolActEthDei2
         INTEGER,
      er1646v2VEthVlanBandwidthActViolActEthCos3
         INTEGER,
      er1646v2VEthVlanBandwidthActViolActEthDei3
         INTEGER,
      er1646v2VEthVlanBandwidthActViolActEthCos4
         INTEGER,
      er1646v2VEthVlanBandwidthActViolActEthDei4
         INTEGER,
      er1646v2VEthVlanBandwidthActViolActEthCos5
         INTEGER,
      er1646v2VEthVlanBandwidthActViolActEthDei5
         INTEGER,
      er1646v2VEthVlanBandwidthActViolActEthCos6
         INTEGER,
      er1646v2VEthVlanBandwidthActViolActEthDei6
         INTEGER,
      er1646v2VEthVlanBandwidthActViolActEthCos7
         INTEGER,
      er1646v2VEthVlanBandwidthActViolActEthDei7
         INTEGER,
      er1646v2VEthVlanBandwidthActViolActEthCos8
         INTEGER,
      er1646v2VEthVlanBandwidthActViolActEthDei8
         INTEGER,
      er1646v2VEthVlanBandwidthActViolActEthTos
         INTEGER,
      er1646v2VEthVlanBandwidthActViolActEthQueue
         INTEGER,
      er1646v2VEthVlanBandwidthActViolActEthDrpLev
         INTEGER,
      er1646v2VEthVlanBandwidthActViolActEthDeFlag
         INTEGER,
      er1646v2VEthVlanBandwidthActViolActIpTos
         INTEGER,
      er1646v2VEthVlanBandwidthActViolActIpQueue
         INTEGER,
      er1646v2VEthVlanBandwidthActViolActIpDrpLev
         INTEGER,
      er1646v2VEthVlanBandwidthActViolActIpDeFlag
         INTEGER,
      er1646v2VEthVlanInbBwMode
         INTEGER,
      er1646v2VEthVlanInbBwCir
         Integer32,
      er1646v2VEthVlanInbBwEir
         Integer32,
      er1646v2VEthVlanInbBwUnit
         INTEGER,
      er1646v2VEthVlanInbBwTc
         INTEGER,
      er1646v2VEthVlanInbBwTcFactor
         INTEGER,
      er1646v2VEthVlanInbBwCorrType
         INTEGER,
      er1646v2VEthVlanInbBwCorrPredefEncapsFrameRelay
         DisplayString,
      er1646v2VEthVlanInbBwCorrPredefEncapsPpp
         DisplayString,
      er1646v2VEthVlanInbBwCorrPredefEncapsAtmHl
         INTEGER,
      er1646v2VEthVlanInbBwCorrPredefEncapsAtmMp
         INTEGER,
      er1646v2VEthVlanInbBwCorrPredefEncapsHdlc
         DisplayString,
      er1646v2VEthVlanInbBwCorrPredefEncapsEfmFs
         Integer32,
      er1646v2VEthVlanInbBwCorrPredefEncapsEfmIb
         Integer32,
      er1646v2VEthVlanInbBwCorrPredefMode
         INTEGER,
      er1646v2VEthVlanInbBwCorrManualOverhead
         Integer32,
      er1646v2VEthVlanInbBwCorrManualFrameData
         Counter32,
      er1646v2VEthVlanInbBwCorrManualFrameHeader
         Counter32,
      er1646v2VEthVlanInbBwMaxFifoQLen
         Integer32,
      er1646v2VEthVlanInbBwPriorityPolicy
         DisplayString,
      er1646v2VEthVlanInbBwDeFlagCir
         INTEGER,
      er1646v2VEthVlanInbBwDeFlagEir
         INTEGER,
      er1646v2VEthVlanInbBwDeFlagViolate
         INTEGER,
      er1646v2VEthVlanInbBwActCirActNone
         OCTET STRING,
      er1646v2VEthVlanInbBwActCirActEthCos1
         INTEGER,
      er1646v2VEthVlanInbBwActCirActEthDei1
         INTEGER,
      er1646v2VEthVlanInbBwActCirActEthCos2
         INTEGER,
      er1646v2VEthVlanInbBwActCirActEthDei2
         INTEGER,
      er1646v2VEthVlanInbBwActCirActEthCos3
         INTEGER,
      er1646v2VEthVlanInbBwActCirActEthDei3
         INTEGER,
      er1646v2VEthVlanInbBwActCirActEthCos4
         INTEGER,
      er1646v2VEthVlanInbBwActCirActEthDei4
         INTEGER,
      er1646v2VEthVlanInbBwActCirActEthCos5
         INTEGER,
      er1646v2VEthVlanInbBwActCirActEthDei5
         INTEGER,
      er1646v2VEthVlanInbBwActCirActEthCos6
         INTEGER,
      er1646v2VEthVlanInbBwActCirActEthDei6
         INTEGER,
      er1646v2VEthVlanInbBwActCirActEthCos7
         INTEGER,
      er1646v2VEthVlanInbBwActCirActEthDei7
         INTEGER,
      er1646v2VEthVlanInbBwActCirActEthCos8
         INTEGER,
      er1646v2VEthVlanInbBwActCirActEthDei8
         INTEGER,
      er1646v2VEthVlanInbBwActCirActEthTos
         INTEGER,
      er1646v2VEthVlanInbBwActCirActEthQueue
         INTEGER,
      er1646v2VEthVlanInbBwActCirActEthDrpLev
         INTEGER,
      er1646v2VEthVlanInbBwActCirActEthDeFlag
         INTEGER,
      er1646v2VEthVlanInbBwActCirActIpTos
         INTEGER,
      er1646v2VEthVlanInbBwActCirActIpQueue
         INTEGER,
      er1646v2VEthVlanInbBwActCirActIpDrpLev
         INTEGER,
      er1646v2VEthVlanInbBwActCirActIpDeFlag
         INTEGER,
      er1646v2VEthVlanInbBwActEirActNone
         OCTET STRING,
      er1646v2VEthVlanInbBwActEirActEthCos1
         INTEGER,
      er1646v2VEthVlanInbBwActEirActEthDei1
         INTEGER,
      er1646v2VEthVlanInbBwActEirActEthCos2
         INTEGER,
      er1646v2VEthVlanInbBwActEirActEthDei2
         INTEGER,
      er1646v2VEthVlanInbBwActEirActEthCos3
         INTEGER,
      er1646v2VEthVlanInbBwActEirActEthDei3
         INTEGER,
      er1646v2VEthVlanInbBwActEirActEthCos4
         INTEGER,
      er1646v2VEthVlanInbBwActEirActEthDei4
         INTEGER,
      er1646v2VEthVlanInbBwActEirActEthCos5
         INTEGER,
      er1646v2VEthVlanInbBwActEirActEthDei5
         INTEGER,
      er1646v2VEthVlanInbBwActEirActEthCos6
         INTEGER,
      er1646v2VEthVlanInbBwActEirActEthDei6
         INTEGER,
      er1646v2VEthVlanInbBwActEirActEthCos7
         INTEGER,
      er1646v2VEthVlanInbBwActEirActEthDei7
         INTEGER,
      er1646v2VEthVlanInbBwActEirActEthCos8
         INTEGER,
      er1646v2VEthVlanInbBwActEirActEthDei8
         INTEGER,
      er1646v2VEthVlanInbBwActEirActEthTos
         INTEGER,
      er1646v2VEthVlanInbBwActEirActEthQueue
         INTEGER,
      er1646v2VEthVlanInbBwActEirActEthDrpLev
         INTEGER,
      er1646v2VEthVlanInbBwActEirActEthDeFlag
         INTEGER,
      er1646v2VEthVlanInbBwActEirActIpTos
         INTEGER,
      er1646v2VEthVlanInbBwActEirActIpQueue
         INTEGER,
      er1646v2VEthVlanInbBwActEirActIpDrpLev
         INTEGER,
      er1646v2VEthVlanInbBwActEirActIpDeFlag
         INTEGER,
      er1646v2VEthVlanInbBwActViolActNone
         OCTET STRING,
      er1646v2VEthVlanInbBwActViolActDrop
         OCTET STRING,
      er1646v2VEthVlanInbBwActViolActEthCos1
         INTEGER,
      er1646v2VEthVlanInbBwActViolActEthDei1
         INTEGER,
      er1646v2VEthVlanInbBwActViolActEthCos2
         INTEGER,
      er1646v2VEthVlanInbBwActViolActEthDei2
         INTEGER,
      er1646v2VEthVlanInbBwActViolActEthCos3
         INTEGER,
      er1646v2VEthVlanInbBwActViolActEthDei3
         INTEGER,
      er1646v2VEthVlanInbBwActViolActEthCos4
         INTEGER,
      er1646v2VEthVlanInbBwActViolActEthDei4
         INTEGER,
      er1646v2VEthVlanInbBwActViolActEthCos5
         INTEGER,
      er1646v2VEthVlanInbBwActViolActEthDei5
         INTEGER,
      er1646v2VEthVlanInbBwActViolActEthCos6
         INTEGER,
      er1646v2VEthVlanInbBwActViolActEthDei6
         INTEGER,
      er1646v2VEthVlanInbBwActViolActEthCos7
         INTEGER,
      er1646v2VEthVlanInbBwActViolActEthDei7
         INTEGER,
      er1646v2VEthVlanInbBwActViolActEthCos8
         INTEGER,
      er1646v2VEthVlanInbBwActViolActEthDei8
         INTEGER,
      er1646v2VEthVlanInbBwActViolActEthTos
         INTEGER,
      er1646v2VEthVlanInbBwActViolActEthQueue
         INTEGER,
      er1646v2VEthVlanInbBwActViolActEthDrpLev
         INTEGER,
      er1646v2VEthVlanInbBwActViolActEthDeFlag
         INTEGER,
      er1646v2VEthVlanInbBwActViolActIpTos
         INTEGER,
      er1646v2VEthVlanInbBwActViolActIpQueue
         INTEGER,
      er1646v2VEthVlanInbBwActViolActIpDrpLev
         INTEGER,
      er1646v2VEthVlanInbBwActViolActIpDeFlag
         INTEGER,
      er1646v2VEthVlanPppoE
         INTEGER,
      er1646v2VEthVlanPppLnkMOperation
         INTEGER,
      er1646v2VEthVlanPppLnkMInterval
         TimeTicks,
      er1646v2VEthVlanPppLnkMRepTimeOut
         TimeTicks,
      er1646v2VEthVlanPppLnkMFailsPrmt
         Integer32,
      er1646v2VEthVlanPppAuthentication
         INTEGER,
      er1646v2VEthVlanPppAuthenPeriod
         TimeTicks,
      er1646v2VEthVlanPppSessionName
         DisplayString,
      er1646v2VEthVlanPppSessionSecret
         DisplayString,
      er1646v2VEthVlanPppEncModeSessionSecret
         INTEGER,
      er1646v2VEthVlanPppEncSessionSecret
         DisplayString,
      er1646v2VEthVlanPppServiceName
         DisplayString,
      er1646v2VEthVlanPbbMode
         INTEGER,
      er1646v2VEthVlanPbbTxCos
         Integer32,
      er1646v2VEthVlanPbbIsid
         Integer32,
      er1646v2VEthVlanPbbDestMac
         OCTET STRING,
      er1646v2VEthVlanPbbCustomGroupMac
         OCTET STRING
      }

er1646v2VEthVlanActions OBJECT-TYPE
   SYNTAX      VariableLengthTableActions
   MAX-ACCESS  read-write
   STATUS      current
   DESCRIPTION
      "By way of this field, some manipulations
       on this table may be performed."
   ::= {er1646v2VEthVlanEntry 2}

er1646v2VEthVlanGlobalIx OBJECT-TYPE
   SYNTAX      GlobalIndex
   MAX-ACCESS  not-accessible
   STATUS      current
   DESCRIPTION
      "The value of the tlsCntTreeGlobalIndex of the MANAGED OBJECT."
   ::= {er1646v2VEthVlanEntry 10}

er1646v2VEthVlanTableIx OBJECT-TYPE
   SYNTAX      TableIndex
   MAX-ACCESS  not-accessible
   STATUS      current
   DESCRIPTION
      ""
   ::= {er1646v2VEthVlanEntry 11}

er1646v2VEthVlanName OBJECT-TYPE
   SYNTAX      DisplayString
   MAX-ACCESS  read-write
   STATUS      current
   DESCRIPTION
      "Path: virtualEthernet.editConf.vlan.name"
   ::= {er1646v2VEthVlanEntry 16777216}

er1646v2VEthVlanRemark OBJECT-TYPE
   SYNTAX      DisplayString
   MAX-ACCESS  read-write
   STATUS      current
   DESCRIPTION
      "Path: virtualEthernet.editConf.vlan.remark"
   ::= {er1646v2VEthVlanEntry 1157627904}

er1646v2VEthVlanAdminStatus OBJECT-TYPE
   SYNTAX      INTEGER
               {
               up (1),
               down (2)
               }
   MAX-ACCESS  read-write
   STATUS      current
   DESCRIPTION
      "Path: virtualEthernet.editConf.vlan.adminStatus

       Possibilities:
               up   (1)
               down   (2)"
   ::= {er1646v2VEthVlanEntry 33554432}

er1646v2VEthVlanMode OBJECT-TYPE
   SYNTAX      INTEGER
               {
               routing (1),
               bridging (2),
               ipV6 (16),
               ipV6ipV4 (17),
               multilink (8)
               }
   MAX-ACCESS  read-write
   STATUS      current
   DESCRIPTION
      "Path: virtualEthernet.editConf.vlan.mode

       Possibilities:
               routing   (1)
               bridging   (2)
               ipV6   (16)
               ipV6/ipV4   (17)
               multilink   (8)"
   ::= {er1646v2VEthVlanEntry 67108864}

er1646v2VEthVlanPriorityPolicy OBJECT-TYPE
   SYNTAX      DisplayString
   MAX-ACCESS  read-write
   STATUS      current
   DESCRIPTION
      "Path: virtualEthernet.editConf.vlan.priorityPolicy"
   ::= {er1646v2VEthVlanEntry 83886080}

er1646v2VEthVlanIpVrfRouter OBJECT-TYPE
   SYNTAX      DisplayString
   MAX-ACCESS  read-write
   STATUS      current
   DESCRIPTION
      "Path: virtualEthernet.editConf.vlan.ip.vrfRouter"
   ::= {er1646v2VEthVlanEntry 53215232}

er1646v2VEthVlanIpAdr OBJECT-TYPE
   SYNTAX      IpAddress
   MAX-ACCESS  read-write
   STATUS      current
   DESCRIPTION
      "Path: virtualEthernet.editConf.vlan.ip.address"
   ::= {er1646v2VEthVlanEntry 58261504}

er1646v2VEthVlanIpNetm OBJECT-TYPE
   SYNTAX      IpAddress
   MAX-ACCESS  read-write
   STATUS      current
   DESCRIPTION
      "Path: virtualEthernet.editConf.vlan.ip.netMask"
   ::= {er1646v2VEthVlanEntry 58392576}

er1646v2VEthVlanIpSNetName OBJECT-TYPE
   SYNTAX      INTEGER
               {
               slOPTg (0),
               corp (2),
               dmz (3),
               internet (1)
               }
   MAX-ACCESS  read-write
   STATUS      current
   DESCRIPTION
      "Path: virtualEthernet.editConf.vlan.ip.sNet.name

       Possibilities:
               <OPT>   (0)
               corp   (2)
               dmz   (3)
               internet   (1)"
   ::= {er1646v2VEthVlanEntry 53674240}

er1646v2VEthVlanIpSNetCust OBJECT-TYPE
   SYNTAX      DisplayString
   MAX-ACCESS  read-write
   STATUS      current
   DESCRIPTION
      "Path: virtualEthernet.editConf.vlan.ip.sNet.custom"
   ::= {er1646v2VEthVlanEntry 53674496}

er1646v2VEthVlanIpDhcpC OBJECT-TYPE
   SYNTAX      INTEGER
               {
               disabled (0),
               enabled (1)
               }
   MAX-ACCESS  read-write
   STATUS      current
   DESCRIPTION
      "Path: virtualEthernet.editConf.vlan.ip.dhcpClient

       Possibilities:
               disabled   (0)
               enabled   (1)"
   ::= {er1646v2VEthVlanEntry 53608448}

er1646v2VEthVlanIpDhcpGatewayPreference OBJECT-TYPE
   SYNTAX      Integer32
   MAX-ACCESS  read-write
   STATUS      current
   DESCRIPTION
      "Path: virtualEthernet.editConf.vlan.ip.dhcp.gatewayPreference"
   ::= {er1646v2VEthVlanEntry 53739776}

er1646v2VEthVlanIpDhcpRoutePreference OBJECT-TYPE
   SYNTAX      Integer32
   MAX-ACCESS  read-write
   STATUS      current
   DESCRIPTION
      "Path: virtualEthernet.editConf.vlan.ip.dhcp.routePreference"
   ::= {er1646v2VEthVlanEntry 53740032}

er1646v2VEthVlanIpDhcpDnsPreference OBJECT-TYPE
   SYNTAX      Integer32
   MAX-ACCESS  read-write
   STATUS      current
   DESCRIPTION
      "Path: virtualEthernet.editConf.vlan.ip.dhcp.dnsPreference"
   ::= {er1646v2VEthVlanEntry 53740288}

er1646v2VEthVlanIpMtu OBJECT-TYPE
   SYNTAX      Integer32
   MAX-ACCESS  read-write
   STATUS      current
   DESCRIPTION
      "Path: virtualEthernet.editConf.vlan.ip.mtu"
   ::= {er1646v2VEthVlanEntry 52953088}

er1646v2VEthVlanIpMssAdjust OBJECT-TYPE
   SYNTAX      INTEGER
               {
               disabled (0),
               auto (65536)
               }
   MAX-ACCESS  read-write
   STATUS      current
   DESCRIPTION
      "Path: virtualEthernet.editConf.vlan.ip.mssAdjust

       Possibilities:
               disabled   (0)
               auto   (65536)"
   ::= {er1646v2VEthVlanEntry 53280768}

er1646v2VEthVlanIpRipMetric OBJECT-TYPE
   SYNTAX      Integer32
   MAX-ACCESS  read-write
   STATUS      current
   DESCRIPTION
      "Path: virtualEthernet.editConf.vlan.ip.rip.metric"
   ::= {er1646v2VEthVlanEntry 51712768}

er1646v2VEthVlanIpRipMetricOut OBJECT-TYPE
   SYNTAX      Integer32
   MAX-ACCESS  read-write
   STATUS      current
   DESCRIPTION
      "Path: virtualEthernet.editConf.vlan.ip.rip.metricOut"
   ::= {er1646v2VEthVlanEntry 51713024}

er1646v2VEthVlanIpRipMode OBJECT-TYPE
   SYNTAX      INTEGER
               {
               disabled (0),
               passive (1),
               active (2)
               }
   MAX-ACCESS  read-write
   STATUS      current
   DESCRIPTION
      "Path: virtualEthernet.editConf.vlan.ip.rip.mode

       Possibilities:
               disabled   (0)
               passive   (1)
               active   (2)"
   ::= {er1646v2VEthVlanEntry 51713280}

er1646v2VEthVlanIpRipTxVer OBJECT-TYPE
   SYNTAX      INTEGER
               {
               rip1 (0),
               rip2 (1),
               rip1mcompatible (2)
               }
   MAX-ACCESS  read-write
   STATUS      current
   DESCRIPTION
      "Path: virtualEthernet.editConf.vlan.ip.rip.txVersion

       Possibilities:
               rip1   (0)
               rip2   (1)
               rip1-compatible   (2)"
   ::= {er1646v2VEthVlanEntry 51716864}

er1646v2VEthVlanIpRipRxVer OBJECT-TYPE
   SYNTAX      INTEGER
               {
               rip1only (0),
               rip2only (1),
               rip12 (2)
               }
   MAX-ACCESS  read-write
   STATUS      current
   DESCRIPTION
      "Path: virtualEthernet.editConf.vlan.ip.rip.rxVersion

       Possibilities:
               rip1only   (0)
               rip2only   (1)
               rip1&2   (2)"
   ::= {er1646v2VEthVlanEntry 51717120}

er1646v2VEthVlanIpRipSplitH OBJECT-TYPE
   SYNTAX      INTEGER
               {
               disabled (0),
               enabled (1),
               poisonedReverse (2)
               }
   MAX-ACCESS  read-write
   STATUS      current
   DESCRIPTION
      "Path: virtualEthernet.editConf.vlan.ip.rip.splitHorizon

       Possibilities:
               disabled   (0)
               enabled   (1)
               poisonedReverse   (2)"
   ::= {er1646v2VEthVlanEntry 51713792}

er1646v2VEthVlanIpRipAuth OBJECT-TYPE
   SYNTAX      INTEGER
               {
               disabled (0),
               texts (1),
               md5 (2)
               }
   MAX-ACCESS  read-write
   STATUS      current
   DESCRIPTION
      "Path: virtualEthernet.editConf.vlan.ip.rip.authentication

       Possibilities:
               disabled   (0)
               text    (1)
               md5   (2)"
   ::= {er1646v2VEthVlanEntry 51712512}

er1646v2VEthVlanIpRipFilter OBJECT-TYPE
   SYNTAX      DisplayString
   MAX-ACCESS  read-write
   STATUS      current
   DESCRIPTION
      "Path: virtualEthernet.editConf.vlan.ip.rip.filter"
   ::= {er1646v2VEthVlanEntry 51716096}

er1646v2VEthVlanIpRipFilterIn OBJECT-TYPE
   SYNTAX      DisplayString
   MAX-ACCESS  read-write
   STATUS      current
   DESCRIPTION
      "Path: virtualEthernet.editConf.vlan.ip.rip.filterIn"
   ::= {er1646v2VEthVlanEntry 51716352}

er1646v2VEthVlanIpRipClearNextHop OBJECT-TYPE
   SYNTAX      INTEGER
               {
               disabled (0),
               enabled (1)
               }
   MAX-ACCESS  read-write
   STATUS      current
   DESCRIPTION
      "Path: virtualEthernet.editConf.vlan.ip.rip.clearNextHop

       Possibilities:
               disabled   (0)
               enabled   (1)"
   ::= {er1646v2VEthVlanEntry 51708416}

er1646v2VEthVlanIpAccPol OBJECT-TYPE
   SYNTAX      DisplayString
   MAX-ACCESS  read-write
   STATUS      current
   DESCRIPTION
      "Path: virtualEthernet.editConf.vlan.ip.accessPolicy"
   ::= {er1646v2VEthVlanEntry 53084160}

er1646v2VEthVlanIpAB OBJECT-TYPE
   SYNTAX      DisplayString
   MAX-ACCESS  read-write
   STATUS      current
   DESCRIPTION
      "Path: virtualEthernet.editConf.vlan.ip.trafficPolicy"
   ::= {er1646v2VEthVlanEntry 51249152}

er1646v2VEthVlanIpMA OBJECT-TYPE
   SYNTAX      INTEGER
               {
               disabled (0),
               enabled (1)
               }
   MAX-ACCESS  read-write
   STATUS      current
   DESCRIPTION
      "Path: virtualEthernet.editConf.vlan.ip.mgmtAccess

       Possibilities:
               disabled   (0)
               enabled   (1)"
   ::= {er1646v2VEthVlanEntry 51380224}

er1646v2VEthVlanIpMF OBJECT-TYPE
   SYNTAX      Integer32
   MAX-ACCESS  read-write
   STATUS      current
   DESCRIPTION
      "Path: virtualEthernet.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2VEthVlanEntry 51445760}

er1646v2VEthVlanIpDB OBJECT-TYPE
   SYNTAX      INTEGER
               {
               disabled (0),
               enabled (1)
               }
   MAX-ACCESS  read-write
   STATUS      current
   DESCRIPTION
      "Path: virtualEthernet.editConf.vlan.ip.directedBroadcasts

       Possibilities:
               disabled   (0)
               enabled   (1)"
   ::= {er1646v2VEthVlanEntry 51773440}

er1646v2VEthVlanIpIR OBJECT-TYPE
   SYNTAX      INTEGER
               {
               disabled (0),
               enabled (1)
               }
   MAX-ACCESS  read-write
   STATUS      current
   DESCRIPTION
      "Path: virtualEthernet.editConf.vlan.ip.icmpRedirects

       Possibilities:
               disabled   (0)
               enabled   (1)"
   ::= {er1646v2VEthVlanEntry 52035584}

er1646v2VEthVlanIpIgmp OBJECT-TYPE
   SYNTAX      INTEGER
               {
               disabled (0),
               proxy (1),
               router (2),
               v3Router (5)
               }
   MAX-ACCESS  read-write
   STATUS      current
   DESCRIPTION
      "Path: virtualEthernet.editConf.vlan.ip.igmp

       Possibilities:
               disabled   (0)
               proxy   (1)
               router   (2)
               v3Router   (5)"
   ::= {er1646v2VEthVlanEntry 52428800}

er1646v2VEthVlanIpNN OBJECT-TYPE
   SYNTAX      DisplayString
   MAX-ACCESS  read-write
   STATUS      current
   DESCRIPTION
      "Path: virtualEthernet.editConf.vlan.ip.nat"
   ::= {er1646v2VEthVlanEntry 52101120}

er1646v2VEthVlanIpVrrp OBJECT-TYPE
   SYNTAX      INTEGER
               {
               disabled (0),
               enabled (1)
               }
   MAX-ACCESS  read-write
   STATUS      current
   DESCRIPTION
      "Path: virtualEthernet.editConf.vlan.ip.vrrp

       Possibilities:
               disabled   (0)
               enabled   (1)"
   ::= {er1646v2VEthVlanEntry 53149696}

er1646v2VEthVlanIpPimMode OBJECT-TYPE
   SYNTAX      INTEGER
               {
               disabled (0),
               sparse (1),
               passive (2)
               }
   MAX-ACCESS  read-write
   STATUS      current
   DESCRIPTION
      "Path: virtualEthernet.editConf.vlan.ip.pim.mode

       Possibilities:
               disabled   (0)
               sparse   (1)
               passive   (2)"
   ::= {er1646v2VEthVlanEntry 53346560}

er1646v2VEthVlanIpPimDrPriority OBJECT-TYPE
   SYNTAX      Counter32
   MAX-ACCESS  read-write
   STATUS      current
   DESCRIPTION
      "Path: virtualEthernet.editConf.vlan.ip.pim.drPriority

       32 bit unsigned wrappable counter."
   ::= {er1646v2VEthVlanEntry 53346816}

er1646v2VEthVlanIpPimHelloTime OBJECT-TYPE
   SYNTAX      TimeTicks
   MAX-ACCESS  read-write
   STATUS      current
   DESCRIPTION
      "Path: virtualEthernet.editConf.vlan.ip.pim.helloTime

       Time in centi-second."
   ::= {er1646v2VEthVlanEntry 53347072}

er1646v2VEthVlanIpPimPropagationDelay OBJECT-TYPE
   SYNTAX      TimeTicks
   MAX-ACCESS  read-write
   STATUS      current
   DESCRIPTION
      "Path: virtualEthernet.editConf.vlan.ip.pim.propagationDelay

       Time in centi-second."
   ::= {er1646v2VEthVlanEntry 53347328}

er1646v2VEthVlanIpPimOverrideInterval OBJECT-TYPE
   SYNTAX      TimeTicks
   MAX-ACCESS  read-write
   STATUS      current
   DESCRIPTION
      "Path: virtualEthernet.editConf.vlan.ip.pim.overrideInterval

       Time in centi-second."
   ::= {er1646v2VEthVlanEntry 53347584}

er1646v2VEthVlanIpPimBsrBorder OBJECT-TYPE
   SYNTAX      INTEGER
               {
               disabled (0),
               enabled (1)
               }
   MAX-ACCESS  read-write
   STATUS      current
   DESCRIPTION
      "Path: virtualEthernet.editConf.vlan.ip.pim.bsrBorder

       Possibilities:
               disabled   (0)
               enabled   (1)"
   ::= {er1646v2VEthVlanEntry 53347840}

er1646v2VEthVlanIpPimTtlThreshold OBJECT-TYPE
   SYNTAX      Integer32
   MAX-ACCESS  read-write
   STATUS      current
   DESCRIPTION
      "Path: virtualEthernet.editConf.vlan.ip.pim.ttlThreshold"
   ::= {er1646v2VEthVlanEntry 53348096}

er1646v2VEthVlanIpIMNetworkUnreachable OBJECT-TYPE
   SYNTAX      INTEGER
               {
               disabled (0),
               enabled (1)
               }
   MAX-ACCESS  read-write
   STATUS      current
   DESCRIPTION
      "Path: virtualEthernet.editConf.vlan.ip.icmpMessages.networkUnreachable

       Possibilities:
               disabled   (0)
               enabled   (1)"
   ::= {er1646v2VEthVlanEntry 53412096}

er1646v2VEthVlanIpIMHostUnreachable OBJECT-TYPE
   SYNTAX      INTEGER
               {
               disabled (0),
               enabled (1)
               }
   MAX-ACCESS  read-write
   STATUS      current
   DESCRIPTION
      "Path: virtualEthernet.editConf.vlan.ip.icmpMessages.hostUnreachable

       Possibilities:
               disabled   (0)
               enabled   (1)"
   ::= {er1646v2VEthVlanEntry 53412352}

er1646v2VEthVlanIpIMProtocolUnreachable OBJECT-TYPE
   SYNTAX      INTEGER
               {
               disabled (0),
               enabled (1)
               }
   MAX-ACCESS  read-write
   STATUS      current
   DESCRIPTION
      "Path: virtualEthernet.editConf.vlan.ip.icmpMessages.protocolUnreachable

       Possibilities:
               disabled   (0)
               enabled   (1)"
   ::= {er1646v2VEthVlanEntry 53412608}

er1646v2VEthVlanIpIMPortUnreachable OBJECT-TYPE
   SYNTAX      INTEGER
               {
               disabled (0),
               enabled (1)
               }
   MAX-ACCESS  read-write
   STATUS      current
   DESCRIPTION
      "Path: virtualEthernet.editConf.vlan.ip.icmpMessages.portUnreachable

       Possibilities:
               disabled   (0)
               enabled   (1)"
   ::= {er1646v2VEthVlanEntry 53412864}

er1646v2VEthVlanIpIMMtuExceeded OBJECT-TYPE
   SYNTAX      INTEGER
               {
               disabled (0),
               enabled (1)
               }
   MAX-ACCESS  read-write
   STATUS      current
   DESCRIPTION
      "Path: virtualEthernet.editConf.vlan.ip.icmpMessages.mtuExceeded

       Possibilities:
               disabled   (0)
               enabled   (1)"
   ::= {er1646v2VEthVlanEntry 53413120}

er1646v2VEthVlanIpIMAdminProhibited OBJECT-TYPE
   SYNTAX      INTEGER
               {
               disabled (0),
               enabled (1)
               }
   MAX-ACCESS  read-write
   STATUS      current
   DESCRIPTION
      "Path: virtualEthernet.editConf.vlan.ip.icmpMessages.adminProhibited

       Possibilities:
               disabled   (0)
               enabled   (1)"
   ::= {er1646v2VEthVlanEntry 53413376}

er1646v2VEthVlanIpIMTtlExceeded OBJECT-TYPE
   SYNTAX      INTEGER
               {
               disabled (0),
               enabled (1)
               }
   MAX-ACCESS  read-write
   STATUS      current
   DESCRIPTION
      "Path: virtualEthernet.editConf.vlan.ip.icmpMessages.ttlExceeded

       Possibilities:
               disabled   (0)
               enabled   (1)"
   ::= {er1646v2VEthVlanEntry 53413632}

er1646v2VEthVlanIpIMRedirect OBJECT-TYPE
   SYNTAX      INTEGER
               {
               disabled (0),
               enabled (1)
               }
   MAX-ACCESS  read-write
   STATUS      current
   DESCRIPTION
      "Path: virtualEthernet.editConf.vlan.ip.icmpMessages.redirect

       Possibilities:
               disabled   (0)
               enabled   (1)"
   ::= {er1646v2VEthVlanEntry 53413888}

er1646v2VEthVlanIpV6VrfRouter OBJECT-TYPE
   SYNTAX      DisplayString
   MAX-ACCESS  read-write
   STATUS      current
   DESCRIPTION
      "Path: virtualEthernet.editConf.vlan.ipV6.vrfRouter"
   ::= {er1646v2VEthVlanEntry 704708608}

er1646v2VEthVlanIpV6AddrAutoConfigNrDupAddrDetects OBJECT-TYPE
   SYNTAX      Integer32
   MAX-ACCESS  read-write
   STATUS      current
   DESCRIPTION
      "Path: virtualEthernet.editConf.vlan.ipV6.addrAutoConfig.nrDupAddrDetects"
   ::= {er1646v2VEthVlanEntry 704905472}

er1646v2VEthVlanIpV6AddrAutoConfigAcceptRa OBJECT-TYPE
   SYNTAX      INTEGER
               {
               disabled (0),
               enabled (1)
               }
   MAX-ACCESS  read-write
   STATUS      current
   DESCRIPTION
      "Path: virtualEthernet.editConf.vlan.ipV6.addrAutoConfig.acceptRa

       Possibilities:
               disabled   (0)
               enabled   (1)"
   ::= {er1646v2VEthVlanEntry 704905728}

er1646v2VEthVlanIpV6AddrAutoConfigAcceptRaRdnss OBJECT-TYPE
   SYNTAX      INTEGER
               {
               disabled (0),
               enabled (1)
               }
   MAX-ACCESS  read-write
   STATUS      current
   DESCRIPTION
      "Path: virtualEthernet.editConf.vlan.ipV6.addrAutoConfig.acceptRaRdnss

       Possibilities:
               disabled   (0)
               enabled   (1)"
   ::= {er1646v2VEthVlanEntry 704905984}

er1646v2VEthVlanIpV6AddrAutoConfigAcceptRaDnssl OBJECT-TYPE
   SYNTAX      INTEGER
               {
               disabled (0),
               enabled (1)
               }
   MAX-ACCESS  read-write
   STATUS      current
   DESCRIPTION
      "Path: virtualEthernet.editConf.vlan.ipV6.addrAutoConfig.acceptRaDnssl

       Possibilities:
               disabled   (0)
               enabled   (1)"
   ::= {er1646v2VEthVlanEntry 704906240}

er1646v2VEthVlanIpV6DefaultRoute OBJECT-TYPE
   SYNTAX      INTEGER
               {
               disabled (0),
               enabled (1)
               }
   MAX-ACCESS  read-write
   STATUS      current
   DESCRIPTION
      "Path: virtualEthernet.editConf.vlan.ipV6.defaultRoute

       Possibilities:
               disabled   (0)
               enabled   (1)"
   ::= {er1646v2VEthVlanEntry 704970752}

er1646v2VEthVlanIpV6RaSend OBJECT-TYPE
   SYNTAX      INTEGER
               {
               disabled (0),
               enabled (1)
               }
   MAX-ACCESS  read-write
   STATUS      current
   DESCRIPTION
      "Path: virtualEthernet.editConf.vlan.ipV6.ra.send

       Possibilities:
               disabled   (0)
               enabled   (1)"
   ::= {er1646v2VEthVlanEntry 705036544}

er1646v2VEthVlanIpV6RaMinInterval OBJECT-TYPE
   SYNTAX      TimeTicks
   MAX-ACCESS  read-write
   STATUS      current
   DESCRIPTION
      "Path: virtualEthernet.editConf.vlan.ipV6.ra.minInterval

       Time in centi-second."
   ::= {er1646v2VEthVlanEntry 705036800}

er1646v2VEthVlanIpV6RaMaxInterval OBJECT-TYPE
   SYNTAX      TimeTicks
   MAX-ACCESS  read-write
   STATUS      current
   DESCRIPTION
      "Path: virtualEthernet.editConf.vlan.ipV6.ra.maxInterval

       Time in centi-second."
   ::= {er1646v2VEthVlanEntry 705037056}

er1646v2VEthVlanIpV6RaManagedFlag OBJECT-TYPE
   SYNTAX      INTEGER
               {
               disabled (0),
               enabled (1)
               }
   MAX-ACCESS  read-write
   STATUS      current
   DESCRIPTION
      "Path: virtualEthernet.editConf.vlan.ipV6.ra.managedFlag

       Possibilities:
               disabled   (0)
               enabled   (1)"
   ::= {er1646v2VEthVlanEntry 705037312}

er1646v2VEthVlanIpV6RaOtherConfFlag OBJECT-TYPE
   SYNTAX      INTEGER
               {
               disabled (0),
               enabled (1)
               }
   MAX-ACCESS  read-write
   STATUS      current
   DESCRIPTION
      "Path: virtualEthernet.editConf.vlan.ipV6.ra.otherConfFlag

       Possibilities:
               disabled   (0)
               enabled   (1)"
   ::= {er1646v2VEthVlanEntry 705037568}

er1646v2VEthVlanIpV6RaLinkMtu OBJECT-TYPE
   SYNTAX      Integer32
   MAX-ACCESS  read-write
   STATUS      current
   DESCRIPTION
      "Path: virtualEthernet.editConf.vlan.ipV6.ra.linkMtu"
   ::= {er1646v2VEthVlanEntry 705037824}

er1646v2VEthVlanIpV6RaReachableTime OBJECT-TYPE
   SYNTAX      TimeTicks
   MAX-ACCESS  read-write
   STATUS      current
   DESCRIPTION
      "Path: virtualEthernet.editConf.vlan.ipV6.ra.reachableTime

       Time in centi-second."
   ::= {er1646v2VEthVlanEntry 705038080}

er1646v2VEthVlanIpV6RaRetransmitTime OBJECT-TYPE
   SYNTAX      TimeTicks
   MAX-ACCESS  read-write
   STATUS      current
   DESCRIPTION
      "Path: virtualEthernet.editConf.vlan.ipV6.ra.retransmitTime

       Time in centi-second."
   ::= {er1646v2VEthVlanEntry 705038336}

er1646v2VEthVlanIpV6RaHopLimit OBJECT-TYPE
   SYNTAX      Integer32
   MAX-ACCESS  read-write
   STATUS      current
   DESCRIPTION
      "Path: virtualEthernet.editConf.vlan.ipV6.ra.hopLimit"
   ::= {er1646v2VEthVlanEntry 705038592}

er1646v2VEthVlanIpV6RaDefaultLifeTime OBJECT-TYPE
   SYNTAX      TimeTicks
   MAX-ACCESS  read-write
   STATUS      current
   DESCRIPTION
      "Path: virtualEthernet.editConf.vlan.ipV6.ra.defaultLifeTime

       Time in centi-second."
   ::= {er1646v2VEthVlanEntry 705038848}

er1646v2VEthVlanIpV6RaDnsOptionsRdnssLifeTime OBJECT-TYPE
   SYNTAX      TimeTicks
   MAX-ACCESS  read-write
   STATUS      current
   DESCRIPTION
      "Path: virtualEthernet.editConf.vlan.ipV6.ra.dnsOptions.rdnss.lifeTime

       Time in centi-second."
   ::= {er1646v2VEthVlanEntry 705039140}

er1646v2VEthVlanIpV6RaDnsOptionsRdnssImportServers OBJECT-TYPE
   SYNTAX      INTEGER
               {
               disabled (0),
               enabled (1)
               }
   MAX-ACCESS  read-write
   STATUS      current
   DESCRIPTION
      "Path: virtualEthernet.editConf.vlan.ipV6.ra.dnsOptions.rdnss.importServers

       Possibilities:
               disabled   (0)
               enabled   (1)"
   ::= {er1646v2VEthVlanEntry 705039148}

er1646v2VEthVlanIpV6RaDnsOptionsDnsslLifeTime OBJECT-TYPE
   SYNTAX      TimeTicks
   MAX-ACCESS  read-write
   STATUS      current
   DESCRIPTION
      "Path: virtualEthernet.editConf.vlan.ipV6.ra.dnsOptions.dnssl.lifeTime

       Time in centi-second."
   ::= {er1646v2VEthVlanEntry 705039172}

er1646v2VEthVlanIpV6RaDnsOptionsDnsslImportDomains OBJECT-TYPE
   SYNTAX      INTEGER
               {
               disabled (0),
               enabled (1)
               }
   MAX-ACCESS  read-write
   STATUS      current
   DESCRIPTION
      "Path: virtualEthernet.editConf.vlan.ipV6.ra.dnsOptions.dnssl.importDomains

       Possibilities:
               disabled   (0)
               enabled   (1)"
   ::= {er1646v2VEthVlanEntry 705039180}

er1646v2VEthVlanIpV6RsSend OBJECT-TYPE
   SYNTAX      INTEGER
               {
               disabled (0),
               enabled (1)
               }
   MAX-ACCESS  read-write
   STATUS      current
   DESCRIPTION
      "Path: virtualEthernet.editConf.vlan.ipV6.rs.send

       Possibilities:
               disabled   (0)
               enabled   (1)"
   ::= {er1646v2VEthVlanEntry 705954048}

er1646v2VEthVlanIpV6RsMaxRandomDelay OBJECT-TYPE
   SYNTAX      TimeTicks
   MAX-ACCESS  read-write
   STATUS      current
   DESCRIPTION
      "Path: virtualEthernet.editConf.vlan.ipV6.rs.maxRandomDelay

       Time in centi-second."
   ::= {er1646v2VEthVlanEntry 705954304}

er1646v2VEthVlanIpV6RsInterval OBJECT-TYPE
   SYNTAX      TimeTicks
   MAX-ACCESS  read-write
   STATUS      current
   DESCRIPTION
      "Path: virtualEthernet.editConf.vlan.ipV6.rs.interval

       Time in centi-second."
   ::= {er1646v2VEthVlanEntry 705954560}

er1646v2VEthVlanIpV6RsMaxSolicitations OBJECT-TYPE
   SYNTAX      Integer32
   MAX-ACCESS  read-write
   STATUS      current
   DESCRIPTION
      "Path: virtualEthernet.editConf.vlan.ipV6.rs.maxSolicitations"
   ::= {er1646v2VEthVlanEntry 705954816}

er1646v2VEthVlanIpV6TrafficPolicyInbound OBJECT-TYPE
   SYNTAX      DisplayString
   MAX-ACCESS  read-write
   STATUS      current
   DESCRIPTION
      "Path: virtualEthernet.editConf.vlan.ipV6.trafficPolicy.inbound"
   ::= {er1646v2VEthVlanEntry 705364224}

er1646v2VEthVlanIpV6TrafficPolicyOutbound OBJECT-TYPE
   SYNTAX      DisplayString
   MAX-ACCESS  read-write
   STATUS      current
   DESCRIPTION
      "Path: virtualEthernet.editConf.vlan.ipV6.trafficPolicy.outbound"
   ::= {er1646v2VEthVlanEntry 705364480}

er1646v2VEthVlanIpV6FirewallZone OBJECT-TYPE
   SYNTAX      DisplayString
   MAX-ACCESS  read-write
   STATUS      current
   DESCRIPTION
      "Path: virtualEthernet.editConf.vlan.ipV6.firewall.zone"
   ::= {er1646v2VEthVlanEntry 705429760}

er1646v2VEthVlanIpV6DhcpClientAddrAC OBJECT-TYPE
   SYNTAX      INTEGER
               {
               disabled (0),
               enabled (1)
               }
   MAX-ACCESS  read-write
   STATUS      current
   DESCRIPTION
      "Path: virtualEthernet.editConf.vlan.ipV6.dhcp.client.addrAutoConfig

       Possibilities:
               disabled   (0)
               enabled   (1)"
   ::= {er1646v2VEthVlanEntry 705307648}

er1646v2VEthVlanIpV6DhcpClientPrDelMode OBJECT-TYPE
   SYNTAX      INTEGER
               {
               disabled (0),
               enabled (1)
               }
   MAX-ACCESS  read-write
   STATUS      current
   DESCRIPTION
      "Path: virtualEthernet.editConf.vlan.ipV6.dhcp.client.pd.mode

       Possibilities:
               disabled   (0)
               enabled   (1)"
   ::= {er1646v2VEthVlanEntry 705308676}

er1646v2VEthVlanIpV6DhcpClientPrDelPool OBJECT-TYPE
   SYNTAX      DisplayString
   MAX-ACCESS  read-write
   STATUS      current
   DESCRIPTION
      "Path: virtualEthernet.editConf.vlan.ipV6.dhcp.client.pd.pool"
   ::= {er1646v2VEthVlanEntry 705308680}

er1646v2VEthVlanIpV6DhcpClientPrDelPdExclOpt OBJECT-TYPE
   SYNTAX      INTEGER
               {
               disabled (0),
               enabled (1)
               }
   MAX-ACCESS  read-write
   STATUS      current
   DESCRIPTION
      "Path: virtualEthernet.editConf.vlan.ipV6.dhcp.client.pd.pdExclOpt

       Possibilities:
               disabled   (0)
               enabled   (1)"
   ::= {er1646v2VEthVlanEntry 705308684}

er1646v2VEthVlanIpV6DhcpClientDnsServerPref OBJECT-TYPE
   SYNTAX      Integer32
   MAX-ACCESS  read-write
   STATUS      current
   DESCRIPTION
      "Path: virtualEthernet.editConf.vlan.ipV6.dhcp.client.dns.serverPref"
   ::= {er1646v2VEthVlanEntry 705310724}

er1646v2VEthVlanIpV6DhcpClientRapidCommit OBJECT-TYPE
   SYNTAX      INTEGER
               {
               disabled (0),
               enabled (1)
               }
   MAX-ACCESS  read-write
   STATUS      current
   DESCRIPTION
      "Path: virtualEthernet.editConf.vlan.ipV6.dhcp.client.rapidCommit

       Possibilities:
               disabled   (0)
               enabled   (1)"
   ::= {er1646v2VEthVlanEntry 705309696}

er1646v2VEthVlanIpV6DhcpClientTimersSolTimeOut OBJECT-TYPE
   SYNTAX      TimeTicks
   MAX-ACCESS  read-write
   STATUS      current
   DESCRIPTION
      "Path: virtualEthernet.editConf.vlan.ipV6.dhcp.client.timers.solTimeOut

       Time in centi-second."
   ::= {er1646v2VEthVlanEntry 705311748}

er1646v2VEthVlanIpV6DhcpClientTimersSolMaxRt OBJECT-TYPE
   SYNTAX      TimeTicks
   MAX-ACCESS  read-write
   STATUS      current
   DESCRIPTION
      "Path: virtualEthernet.editConf.vlan.ipV6.dhcp.client.timers.solMaxRt

       Time in centi-second."
   ::= {er1646v2VEthVlanEntry 705311752}

er1646v2VEthVlanIpV6DhcpClientTimersInfoRefresh OBJECT-TYPE
   SYNTAX      TimeTicks
   MAX-ACCESS  read-write
   STATUS      current
   DESCRIPTION
      "Path: virtualEthernet.editConf.vlan.ipV6.dhcp.client.timers.infoRefresh

       Time in centi-second."
   ::= {er1646v2VEthVlanEntry 705311756}

er1646v2VEthVlanIpV6DhcpServerMode OBJECT-TYPE
   SYNTAX      INTEGER
               {
               disabled (0),
               enabled (1)
               }
   MAX-ACCESS  read-write
   STATUS      current
   DESCRIPTION
      "Path: virtualEthernet.editConf.vlan.ipV6.dhcp.server.mode

       Possibilities:
               disabled   (0)
               enabled   (1)"
   ::= {er1646v2VEthVlanEntry 705315840}

er1646v2VEthVlanIpV6DhcpServerPreference OBJECT-TYPE
   SYNTAX      Integer32
   MAX-ACCESS  read-write
   STATUS      current
   DESCRIPTION
      "Path: virtualEthernet.editConf.vlan.ipV6.dhcp.server.preference"
   ::= {er1646v2VEthVlanEntry 705316864}

er1646v2VEthVlanIpV6DhcpServerPool OBJECT-TYPE
   SYNTAX      DisplayString
   MAX-ACCESS  read-write
   STATUS      current
   DESCRIPTION
      "Path: virtualEthernet.editConf.vlan.ipV6.dhcp.server.pool"
   ::= {er1646v2VEthVlanEntry 705317888}

er1646v2VEthVlanIpV6DhcpServerRapidCommit OBJECT-TYPE
   SYNTAX      INTEGER
               {
               disabled (0),
               enabled (1)
               }
   MAX-ACCESS  read-write
   STATUS      current
   DESCRIPTION
      "Path: virtualEthernet.editConf.vlan.ipV6.dhcp.server.rapidCommit

       Possibilities:
               disabled   (0)
               enabled   (1)"
   ::= {er1646v2VEthVlanEntry 705318912}

er1646v2VEthVlanIpV6DhcpServerTimersInfoRefresh OBJECT-TYPE
   SYNTAX      TimeTicks
   MAX-ACCESS  read-write
   STATUS      current
   DESCRIPTION
      "Path: virtualEthernet.editConf.vlan.ipV6.dhcp.server.timers.infoRefresh

       Time in centi-second."
   ::= {er1646v2VEthVlanEntry 705319940}

er1646v2VEthVlanIpV6DhcpRelayMode OBJECT-TYPE
   SYNTAX      INTEGER
               {
               disabled (0),
               enabled (1)
               }
   MAX-ACCESS  read-write
   STATUS      current
   DESCRIPTION
      "Path: virtualEthernet.editConf.vlan.ipV6.dhcp.relay.mode

       Possibilities:
               disabled   (0)
               enabled   (1)"
   ::= {er1646v2VEthVlanEntry 705323040}

er1646v2VEthVlanIpV6SendRedirect OBJECT-TYPE
   SYNTAX      INTEGER
               {
               disabled (0),
               enabled (1)
               }
   MAX-ACCESS  read-write
   STATUS      current
   DESCRIPTION
      "Path: virtualEthernet.editConf.vlan.ipV6.sendRedirect

       Possibilities:
               disabled   (0)
               enabled   (1)"
   ::= {er1646v2VEthVlanEntry 705101824}

er1646v2VEthVlanIpV6LinkMtu OBJECT-TYPE
   SYNTAX      Integer32
   MAX-ACCESS  read-write
   STATUS      current
   DESCRIPTION
      "Path: virtualEthernet.editConf.vlan.ipV6.linkMtu"
   ::= {er1646v2VEthVlanEntry 705167360}

er1646v2VEthVlanIpV6InterfaceId OBJECT-TYPE
   SYNTAX      OCTET STRING
   MAX-ACCESS  read-write
   STATUS      current
   DESCRIPTION
      "Path: virtualEthernet.editConf.vlan.ipV6.interfaceId"
   ::= {er1646v2VEthVlanEntry 705232896}

er1646v2VEthVlanIpV6MF OBJECT-TYPE
   SYNTAX      Integer32
   MAX-ACCESS  read-write
   STATUS      current
   DESCRIPTION
      "Path: virtualEthernet.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2VEthVlanEntry 705757184}

er1646v2VEthVlanIpV6IcmpMessagesNoRoute OBJECT-TYPE
   SYNTAX      INTEGER
               {
               disabled (0),
               enabled (1)
               }
   MAX-ACCESS  read-write
   STATUS      current
   DESCRIPTION
      "Path: virtualEthernet.editConf.vlan.ipV6.icmpMessages.noRoute

       Possibilities:
               disabled   (0)
               enabled   (1)"
   ::= {er1646v2VEthVlanEntry 705822976}

er1646v2VEthVlanIpV6IcmpMessagesBeyondScope OBJECT-TYPE
   SYNTAX      INTEGER
               {
               disabled (0),
               enabled (1)
               }
   MAX-ACCESS  read-write
   STATUS      current
   DESCRIPTION
      "Path: virtualEthernet.editConf.vlan.ipV6.icmpMessages.beyondScope

       Possibilities:
               disabled   (0)
               enabled   (1)"
   ::= {er1646v2VEthVlanEntry 705823488}

er1646v2VEthVlanIpV6IcmpMessagesAddressUnreachable OBJECT-TYPE
   SYNTAX      INTEGER
               {
               disabled (0),
               enabled (1)
               }
   MAX-ACCESS  read-write
   STATUS      current
   DESCRIPTION
      "Path: virtualEthernet.editConf.vlan.ipV6.icmpMessages.addressUnreachable

       Possibilities:
               disabled   (0)
               enabled   (1)"
   ::= {er1646v2VEthVlanEntry 705823744}

er1646v2VEthVlanIpV6IcmpMessagesPortUnreachable OBJECT-TYPE
   SYNTAX      INTEGER
               {
               disabled (0),
               enabled (1)
               }
   MAX-ACCESS  read-write
   STATUS      current
   DESCRIPTION
      "Path: virtualEthernet.editConf.vlan.ipV6.icmpMessages.portUnreachable

       Possibilities:
               disabled   (0)
               enabled   (1)"
   ::= {er1646v2VEthVlanEntry 705824000}

er1646v2VEthVlanIpV6IcmpMessagesPacketTooBig OBJECT-TYPE
   SYNTAX      INTEGER
               {
               disabled (0),
               enabled (1)
               }
   MAX-ACCESS  read-write
   STATUS      current
   DESCRIPTION
      "Path: virtualEthernet.editConf.vlan.ipV6.icmpMessages.packetTooBig

       Possibilities:
               disabled   (0)
               enabled   (1)"
   ::= {er1646v2VEthVlanEntry 705825280}

er1646v2VEthVlanIpV6IcmpMessagesHopLimitExceeded OBJECT-TYPE
   SYNTAX      INTEGER
               {
               disabled (0),
               enabled (1)
               }
   MAX-ACCESS  read-write
   STATUS      current
   DESCRIPTION
      "Path: virtualEthernet.editConf.vlan.ipV6.icmpMessages.hopLimitExceeded

       Possibilities:
               disabled   (0)
               enabled   (1)"
   ::= {er1646v2VEthVlanEntry 705827840}

er1646v2VEthVlanIpV6IcmpMessagesFragTimeExceeded OBJECT-TYPE
   SYNTAX      INTEGER
               {
               disabled (0),
               enabled (1)
               }
   MAX-ACCESS  read-write
   STATUS      current
   DESCRIPTION
      "Path: virtualEthernet.editConf.vlan.ipV6.icmpMessages.fragTimeExceeded

       Possibilities:
               disabled   (0)
               enabled   (1)"
   ::= {er1646v2VEthVlanEntry 705828096}

er1646v2VEthVlanIpV6IcmpMessagesHeaderFieldErr OBJECT-TYPE
   SYNTAX      INTEGER
               {
               disabled (0),
               enabled (1)
               }
   MAX-ACCESS  read-write
   STATUS      current
   DESCRIPTION
      "Path: virtualEthernet.editConf.vlan.ipV6.icmpMessages.headerFieldErr

       Possibilities:
               disabled   (0)
               enabled   (1)"
   ::= {er1646v2VEthVlanEntry 705830400}

er1646v2VEthVlanIpV6IcmpMessagesOptionUnrecognized OBJECT-TYPE
   SYNTAX      INTEGER
               {
               disabled (0),
               enabled (1)
               }
   MAX-ACCESS  read-write
   STATUS      current
   DESCRIPTION
      "Path: virtualEthernet.editConf.vlan.ipV6.icmpMessages.optionUnrecognized

       Possibilities:
               disabled   (0)
               enabled   (1)"
   ::= {er1646v2VEthVlanEntry 705830912}

er1646v2VEthVlanIpV6IcmpMessagesRedirect OBJECT-TYPE
   SYNTAX      INTEGER
               {
               disabled (0),
               enabled (1)
               }
   MAX-ACCESS  read-write
   STATUS      current
   DESCRIPTION
      "Path: virtualEthernet.editConf.vlan.ipV6.icmpMessages.redirect

       Possibilities:
               disabled   (0)
               enabled   (1)"
   ::= {er1646v2VEthVlanEntry 705832960}

er1646v2VEthVlanBridgingAccList OBJECT-TYPE
   SYNTAX      DisplayString
   MAX-ACCESS  read-write
   STATUS      current
   DESCRIPTION
      "Path: virtualEthernet.editConf.vlan.bridging.accessList"
   ::= {er1646v2VEthVlanEntry 453246976}

er1646v2VEthVlanBridgingInACL OBJECT-TYPE
   SYNTAX      DisplayString
   MAX-ACCESS  read-write
   STATUS      current
   DESCRIPTION
      "Path: virtualEthernet.editConf.vlan.bridging.inAccessList"
   ::= {er1646v2VEthVlanEntry 456916992}

er1646v2VEthVlanBridgingTp OBJECT-TYPE
   SYNTAX      DisplayString
   MAX-ACCESS  read-write
   STATUS      current
   DESCRIPTION
      "Path: virtualEthernet.editConf.vlan.bridging.trafficPolicy"
   ::= {er1646v2VEthVlanEntry 454295552}

er1646v2VEthVlanBridgingBrGrp OBJECT-TYPE
   SYNTAX      DisplayString
   MAX-ACCESS  read-write
   STATUS      current
   DESCRIPTION
      "Path: virtualEthernet.editConf.vlan.bridging.bridgeGroup"
   ::= {er1646v2VEthVlanEntry 454819840}

er1646v2VEthVlanBridgingLimBC OBJECT-TYPE
   SYNTAX      INTEGER
               {
               disabled (0),
               enabled (1)
               }
   MAX-ACCESS  read-write
   STATUS      current
   DESCRIPTION
      "Path: virtualEthernet.editConf.vlan.bridging.limitBroadcasts

       Possibilities:
               disabled   (0)
               enabled   (1)"
   ::= {er1646v2VEthVlanEntry 455081984}

er1646v2VEthVlanBridgingPrivateMode OBJECT-TYPE
   SYNTAX      INTEGER
               {
               disabled (0),
               enabled (1)
               }
   MAX-ACCESS  read-write
   STATUS      current
   DESCRIPTION
      "Path: virtualEthernet.editConf.vlan.bridging.privateMode

       Possibilities:
               disabled   (0)
               enabled   (1)"
   ::= {er1646v2VEthVlanEntry 459538432}

er1646v2VEthVlanBridgingLearning OBJECT-TYPE
   SYNTAX      INTEGER
               {
               disabled (0),
               enabled (1)
               }
   MAX-ACCESS  read-write
   STATUS      current
   DESCRIPTION
      "Path: virtualEthernet.editConf.vlan.bridging.learning

       Possibilities:
               disabled   (0)
               enabled   (1)"
   ::= {er1646v2VEthVlanEntry 456130560}

er1646v2VEthVlanBridgingMaxCacheSize OBJECT-TYPE
   SYNTAX      INTEGER
               {
               unlimited (0)
               }
   MAX-ACCESS  read-write
   STATUS      current
   DESCRIPTION
      "Path: virtualEthernet.editConf.vlan.bridging.maxCacheSize

       Possibilities:
               unlimited   (0)"
   ::= {er1646v2VEthVlanEntry 456392704}

er1646v2VEthVlanBridgingRelearnDropOnRelearn OBJECT-TYPE
   SYNTAX      INTEGER
               {
               disabled (0),
               enabled (1)
               }
   MAX-ACCESS  read-write
   STATUS      current
   DESCRIPTION
      "Path: virtualEthernet.editConf.vlan.bridging.relearn.dropOnRelearn

       Possibilities:
               disabled   (0)
               enabled   (1)"
   ::= {er1646v2VEthVlanEntry 456655872}

er1646v2VEthVlanBridgingRelearnShutdownThreshold OBJECT-TYPE
   SYNTAX      Integer32
   MAX-ACCESS  read-write
   STATUS      current
   DESCRIPTION
      "Path: virtualEthernet.editConf.vlan.bridging.relearn.shutdownThreshold"
   ::= {er1646v2VEthVlanEntry 456656896}

er1646v2VEthVlanBridgingRelearnShutdownTime OBJECT-TYPE
   SYNTAX      TimeTicks
   MAX-ACCESS  read-write
   STATUS      current
   DESCRIPTION
      "Path: virtualEthernet.editConf.vlan.bridging.relearn.shutdownTime

       Time in centi-second."
   ::= {er1646v2VEthVlanEntry 456657920}

er1646v2VEthVlanBridgingRelearnLoopDetection OBJECT-TYPE
   SYNTAX      INTEGER
               {
               disabled (0),
               passive (1),
               active (2)
               }
   MAX-ACCESS  read-write
   STATUS      current
   DESCRIPTION
      "Path: virtualEthernet.editConf.vlan.bridging.relearn.loopDetection

       Possibilities:
               disabled   (0)
               passive   (1)
               active   (2)"
   ::= {er1646v2VEthVlanEntry 456658944}

er1646v2VEthVlanBridgingRelearnLoopDetectionInterval OBJECT-TYPE
   SYNTAX      TimeTicks
   MAX-ACCESS  read-write
   STATUS      current
   DESCRIPTION
      "Path: virtualEthernet.editConf.vlan.bridging.relearn.loopDetectionInterval

       Time in centi-second."
   ::= {er1646v2VEthVlanEntry 456659968}

er1646v2VEthVlanBridgingVlanMemberShip OBJECT-TYPE
   SYNTAX      INTEGER
               {
               all (0),
               none (1),
               grouped (2)
               }
   MAX-ACCESS  read-write
   STATUS      current
   DESCRIPTION
      "Path: virtualEthernet.editConf.vlan.bridging.vlanMemberShip

       Possibilities:
               all   (0)
               none   (1)
               grouped   (2)"
   ::= {er1646v2VEthVlanEntry 457965568}

er1646v2VEthVlanBridgingVlTUntaggedAction OBJECT-TYPE
   SYNTAX      INTEGER
               {
               discard (0),
               accept (1),
               tag (2)
               }
   MAX-ACCESS  read-write
   STATUS      current
   DESCRIPTION
      "Path: virtualEthernet.editConf.vlan.bridging.vlanTagging.untagged.action

       Possibilities:
               discard   (0)
               accept   (1)
               tag   (2)"
   ::= {er1646v2VEthVlanEntry 459055104}

er1646v2VEthVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.bridging.vlanTagging.untagged.tagInfo.tpid

       Possibilities:
               dot1Q   (33024)
               dot1ad   (34984)
               0x9100   (37120)
               0x9200   (37376)
               0x9300   (37632)"
   ::= {er1646v2VEthVlanEntry 459059712}

er1646v2VEthVlanBridgingVlTUntaggedTagInfoVid OBJECT-TYPE
   SYNTAX      Integer32
   MAX-ACCESS  read-write
   STATUS      current
   DESCRIPTION
      "Path: virtualEthernet.editConf.vlan.bridging.vlanTagging.untagged.tagInfo.vid"
   ::= {er1646v2VEthVlanEntry 459060224}

er1646v2VEthVlanBridgingVlTUnknownVlansAction OBJECT-TYPE
   SYNTAX      INTEGER
               {
               discard (0),
               accept (1),
               tag (2)
               }
   MAX-ACCESS  read-write
   STATUS      current
   DESCRIPTION
      "Path: virtualEthernet.editConf.vlan.bridging.vlanTagging.unknownVlans.action

       Possibilities:
               discard   (0)
               accept   (1)
               tag   (2)"
   ::= {er1646v2VEthVlanEntry 459120640}

er1646v2VEthVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.bridging.vlanTagging.unknownVlans.tagInfo.tpid

       Possibilities:
               dot1Q   (33024)
               dot1ad   (34984)
               0x9100   (37120)
               0x9200   (37376)
               0x9300   (37632)"
   ::= {er1646v2VEthVlanEntry 459125248}

er1646v2VEthVlanBridgingVlTUnknownVlansTagInfoVid OBJECT-TYPE
   SYNTAX      Integer32
   MAX-ACCESS  read-write
   STATUS      current
   DESCRIPTION
      "Path: virtualEthernet.editConf.vlan.bridging.vlanTagging.unknownVlans.tagInfo.vid"
   ::= {er1646v2VEthVlanEntry 459125760}

er1646v2VEthVlanBridgingDot1adType OBJECT-TYPE
   SYNTAX      INTEGER
               {
               slOPTg (0),
               cPort (4),
               sPort (1),
               nni (2)
               }
   MAX-ACCESS  read-write
   STATUS      current
   DESCRIPTION
      "Path: virtualEthernet.editConf.vlan.bridging.dot1ad.type

       Possibilities:
               <OPT>   (0)
               cPort   (4)
               sPort   (1)
               nni   (2)"
   ::= {er1646v2VEthVlanEntry 460850176}

er1646v2VEthVlanBridgingPriority OBJECT-TYPE
   SYNTAX      Integer32
   MAX-ACCESS  read-write
   STATUS      current
   DESCRIPTION
      "Path: virtualEthernet.editConf.vlan.bridging.priority"
   ::= {er1646v2VEthVlanEntry 453509120}

er1646v2VEthVlanBridgingPathCost OBJECT-TYPE
   SYNTAX      Integer32
   MAX-ACCESS  read-write
   STATUS      current
   DESCRIPTION
      "Path: virtualEthernet.editConf.vlan.bridging.pathCost"
   ::= {er1646v2VEthVlanEntry 453771264}

er1646v2VEthVlanBridgingInternalPathCost OBJECT-TYPE
   SYNTAX      Integer32
   MAX-ACCESS  read-write
   STATUS      current
   DESCRIPTION
      "Path: virtualEthernet.editConf.vlan.bridging.internalPathCost"
   ::= {er1646v2VEthVlanEntry 457703424}

er1646v2VEthVlanBridgingTCD OBJECT-TYPE
   SYNTAX      INTEGER
               {
               disabled (0),
               enabled (1)
               }
   MAX-ACCESS  read-write
   STATUS      current
   DESCRIPTION
      "Path: virtualEthernet.editConf.vlan.bridging.topologyChangeDetection

       Possibilities:
               disabled   (0)
               enabled   (1)"
   ::= {er1646v2VEthVlanEntry 454033408}

er1646v2VEthVlanBridgingRestrictedRole OBJECT-TYPE
   SYNTAX      INTEGER
               {
               disabled (0),
               enabled (1)
               }
   MAX-ACCESS  read-write
   STATUS      current
   DESCRIPTION
      "Path: virtualEthernet.editConf.vlan.bridging.restrictedRole

       Possibilities:
               disabled   (0)
               enabled   (1)"
   ::= {er1646v2VEthVlanEntry 458227712}

er1646v2VEthVlanBridgingAdminEdge OBJECT-TYPE
   SYNTAX      INTEGER
               {
               disabled (0),
               enabled (1)
               }
   MAX-ACCESS  read-write
   STATUS      current
   DESCRIPTION
      "Path: virtualEthernet.editConf.vlan.bridging.adminEdge

       Possibilities:
               disabled   (0)
               enabled   (1)"
   ::= {er1646v2VEthVlanEntry 457179136}

er1646v2VEthVlanBridgingOamMacDeviceMac OBJECT-TYPE
   SYNTAX      DisplayString
   MAX-ACCESS  read-write
   STATUS      current
   DESCRIPTION
      "Path: virtualEthernet.editConf.vlan.bridging.ethOam.macAddress.deviceMac"
   ::= {er1646v2VEthVlanEntry 458506496}

er1646v2VEthVlanBridgingOamMacUserMac OBJECT-TYPE
   SYNTAX      OCTET STRING
   MAX-ACCESS  read-write
   STATUS      current
   DESCRIPTION
      "Path: virtualEthernet.editConf.vlan.bridging.ethOam.macAddress.userMac

       MAC address."
   ::= {er1646v2VEthVlanEntry 458506368}

er1646v2VEthVlanBridgingOamMacBridgeMac OBJECT-TYPE
   SYNTAX      DisplayString
   MAX-ACCESS  read-write
   STATUS      current
   DESCRIPTION
      "Path: virtualEthernet.editConf.vlan.bridging.ethOam.macAddress.bridgeMac"
   ::= {er1646v2VEthVlanEntry 458506432}

er1646v2VEthVlanBridgingMgmtInline OBJECT-TYPE
   SYNTAX      INTEGER
               {
               disabled (0),
               enabled (1)
               }
   MAX-ACCESS  read-write
   STATUS      current
   DESCRIPTION
      "Path: virtualEthernet.editConf.vlan.bridging.mgmtInline

       Possibilities:
               disabled   (0)
               enabled   (1)"
   ::= {er1646v2VEthVlanEntry 458752000}

er1646v2VEthVlanBridgingL2ptMode OBJECT-TYPE
   SYNTAX      INTEGER
               {
               disabled (0),
               enabled (1)
               }
   MAX-ACCESS  read-write
   STATUS      current
   DESCRIPTION
      "Path: virtualEthernet.editConf.vlan.bridging.l2ProtTunnel.mode

       Possibilities:
               disabled   (0)
               enabled   (1)"
   ::= {er1646v2VEthVlanEntry 459292672}

er1646v2VEthVlanBridgingL2ptProtocols OBJECT-TYPE
   SYNTAX      Integer32
   MAX-ACCESS  read-write
   STATUS      current
   DESCRIPTION
      "Path: virtualEthernet.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1646v2VEthVlanEntry 459309056}

er1646v2VEthVlanBridgingL2ptDestMac OBJECT-TYPE
   SYNTAX      OCTET STRING
   MAX-ACCESS  read-write
   STATUS      current
   DESCRIPTION
      "Path: virtualEthernet.editConf.vlan.bridging.l2ProtTunnel.destinationMac

       MAC address."
   ::= {er1646v2VEthVlanEntry 459325440}

er1646v2VEthVlanBridgingL2ptCos OBJECT-TYPE
   SYNTAX      INTEGER
               {
               unchanged (255)
               }
   MAX-ACCESS  read-write
   STATUS      current
   DESCRIPTION
      "Path: virtualEthernet.editConf.vlan.bridging.l2ProtTunnel.cos

       Possibilities:
               unchanged   (255)"
   ::= {er1646v2VEthVlanEntry 459341824}

er1646v2VEthVlanBridgingL2ptDropThrStp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.stp

       unit name = packets/sec

       Possibilities:
               unlimited   (0)"
   ::= {er1646v2VEthVlanEntry 459358272}

er1646v2VEthVlanBridgingL2ptDropThrLldp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.lldp

       unit name = packets/sec

       Possibilities:
               unlimited   (0)"
   ::= {er1646v2VEthVlanEntry 459358336}

er1646v2VEthVlanBridgingL2ptDropThrOam OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.oam

       unit name = packets/sec

       Possibilities:
               unlimited   (0)"
   ::= {er1646v2VEthVlanEntry 459358400}

er1646v2VEthVlanBridgingL2ptDropThrCdp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.cdp

       unit name = packets/sec

       Possibilities:
               unlimited   (0)"
   ::= {er1646v2VEthVlanEntry 459358464}

er1646v2VEthVlanBridgingL2ptDropThrVtp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.vtp

       unit name = packets/sec

       Possibilities:
               unlimited   (0)"
   ::= {er1646v2VEthVlanEntry 459358528}

er1646v2VEthVlanBridgingL2ptDropThrLacp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.lacp

       unit name = packets/sec

       Possibilities:
               unlimited   (0)"
   ::= {er1646v2VEthVlanEntry 459358592}

er1646v2VEthVlanBridgingL2ptDropThrEfmOam OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.efmOam

       unit name = packets/sec

       Possibilities:
               unlimited   (0)"
   ::= {er1646v2VEthVlanEntry 459358656}

er1646v2VEthVlanBridgingL2ptDropThrPvst OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.pvst

       unit name = packets/sec

       Possibilities:
               unlimited   (0)"
   ::= {er1646v2VEthVlanEntry 459358720}

er1646v2VEthVlanBridgingL2ptDropThrMmrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.mmrp

       unit name = packets/sec

       Possibilities:
               unlimited   (0)"
   ::= {er1646v2VEthVlanEntry 459358784}

er1646v2VEthVlanBridgingL2ptDropThrMvrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.mvrp

       unit name = packets/sec

       Possibilities:
               unlimited   (0)"
   ::= {er1646v2VEthVlanEntry 459358848}

er1646v2VEthVlanBridgingL2ptDropThrGvrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.gvrp

       unit name = packets/sec

       Possibilities:
               unlimited   (0)"
   ::= {er1646v2VEthVlanEntry 459358912}

er1646v2VEthVlanBridgingL2ptDropThrGmrp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.gmrp

       unit name = packets/sec

       Possibilities:
               unlimited   (0)"
   ::= {er1646v2VEthVlanEntry 459358976}

er1646v2VEthVlanBridgingL2ptDropThrDtp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.dtp

       unit name = packets/sec

       Possibilities:
               unlimited   (0)"
   ::= {er1646v2VEthVlanEntry 459359040}

er1646v2VEthVlanBridgingL2ptDropThrPagp OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.pagp

       unit name = packets/sec

       Possibilities:
               unlimited   (0)"
   ::= {er1646v2VEthVlanEntry 459359104}

er1646v2VEthVlanBridgingL2ptDropThrUdld OBJECT-TYPE
   SYNTAX      INTEGER
               {
               unlimited (0)
               }
   UNITS       "packets/sec"
   MAX-ACCESS  read-write
   STATUS      current
   DESCRIPTION
      "Path: virtualEthernet.editConf.vlan.bridging.l2ProtTunnel.dropThresholds.udld

       unit name = packets/sec

       Possibilities:
               unlimited   (0)"
   ::= {er1646v2VEthVlanEntry 459359168}

er1646v2VEthVlanVlanVid OBJECT-TYPE
   SYNTAX      INTEGER
               {
               untagged (0),
               prioTagged (4096),
               notUsed (4097)
               }
   MAX-ACCESS  read-write
   STATUS      current
   DESCRIPTION
      "Path: virtualEthernet.editConf.vlan.vlan.vid

       Possibilities:
               untagged   (0)
               prioTagged   (4096)
               notUsed   (4097)"
   ::= {er1646v2VEthVlanEntry 234946560}

er1646v2VEthVlanVlanVidExtensionSingle OBJECT-TYPE
   SYNTAX      OCTET STRING
   MAX-ACCESS  read-write
   STATUS      current
   DESCRIPTION
      "Path: virtualEthernet.editConf.vlan.vlan.vidExtension.single"
   ::= {er1646v2VEthVlanEntry 235340032}

er1646v2VEthVlanVlanVidExtensionEndVid OBJECT-TYPE
   SYNTAX      Integer32
   MAX-ACCESS  read-write
   STATUS      current
   DESCRIPTION
      "Path: virtualEthernet.editConf.vlan.vlan.vidExtension.endVid"
   ::= {er1646v2VEthVlanEntry 235340288}

er1646v2VEthVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.vlan.tpid

       Possibilities:
               dot1Q   (33024)
               dot1ad   (34984)
               0x9100   (37120)
               0x9200   (37376)
               0x9300   (37632)"
   ::= {er1646v2VEthVlanEntry 241238016}

er1646v2VEthVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: virtualEthernet.editConf.vlan.vlan.tagSignificance

       Possibilities:
               global   (0)
               local   (1)
               sVlan   (2)
               sVlanGlobal   (6)
               cVlan   (3)
               scVlan   (5)
               cVlanLocal   (4)"
   ::= {er1646v2VEthVlanEntry 235012096}

er1646v2VEthVlanVlanChTos OBJECT-TYPE
   SYNTAX      INTEGER
               {
               disabled (0),
               enabled (1)
               }
   MAX-ACCESS  read-write
   STATUS      current
   DESCRIPTION
      "Path: virtualEthernet.editConf.vlan.vlan.changeTos

       Possibilities:
               disabled   (0)
               enabled   (1)"
   ::= {er1646v2VEthVlanEntry 235208704}

er1646v2VEthVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235143424}

er1646v2VEthVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235143680}

er1646v2VEthVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235143936}

er1646v2VEthVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235144192}

er1646v2VEthVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235144448}

er1646v2VEthVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235144704}

er1646v2VEthVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235144960}

er1646v2VEthVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: virtualEthernet.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1646v2VEthVlanEntry 235145216}

er1646v2VEthVlanVlanTxCos OBJECT-TYPE
   SYNTAX      INTEGER
               {
               tosCosMap (8),
               queueCosMap (16)
               }
   MAX-ACCESS  read-write
   STATUS      current
   DESCRIPTION
      "Path: virtualEthernet.editConf.vlan.vlan.txCos

       Possibilities:
               tosCosMap   (8)
               queueCosMap   (16)"
   ::= {er1646v2VEthVlanEntry 235077632}

er1646v2VEthVlanVlanCCMapP0 OBJECT-TYPE
   SYNTAX      Integer32
   MAX-ACCESS  read-write
   STATUS      current
   DESCRIPTION
      "Path: virtualEthernet.editConf.vlan.vlan.cosCosMap.p0"
   ::= {er1646v2VEthVlanEntry 241303808}

er1646v2VEthVlanVlanCCMapP1 OBJECT-TYPE
   SYNTAX      Integer32
   MAX-ACCESS  read-write
   STATUS      current
   DESCRIPTION
      "Path: virtualEthernet.editConf.vlan.vlan.cosCosMap.p1"
   ::= {er1646v2VEthVlanEntry 241304064}

er1646v2VEthVlanVlanCCMapP2 OBJECT-TYPE
   SYNTAX      Integer32
   MAX-ACCESS  read-write
   STATUS      current
   DESCRIPTION
      "Path: virtualEthernet.editConf.vlan.vlan.cosCosMap.p2"
   ::= {er1646v2VEthVlanEntry 241304320}

er1646v2VEthVlanVlanCCMapP3 OBJECT-TYPE
   SYNTAX      Integer32
   MAX-ACCESS  read-write
   STATUS      current
   DESCRIPTION
      "Path: virtualEthernet.editConf.vlan.vlan.cosCosMap.p3"
   ::= {er1646v2VEthVlanEntry 241304576}

er1646v2VEthVlanVlanCCMapP4 OBJECT-TYPE
   SYNTAX      Integer32
   MAX-ACCESS  read-write
   STATUS      current
   DESCRIPTION
      "Path: virtualEthernet.editConf.vlan.vlan.cosCosMap.p4"
   ::= {er1646v2VEthVlanEntry 241304832}

er1646v2VEthVlanVlanCCMapP5 OBJECT-TYPE
   SYNTAX      Integer32
   MAX-ACCESS  read-write
   STATUS      current
   DESCRIPTION
      "Path: virtualEthernet.editConf.vlan.vlan.cosCosMap.p5"
   ::= {er1646v2VEthVlanEntry 241305088}

er1646v2VEthVlanVlanCCMapP6 OBJECT-TYPE
   SYNTAX      Integer32
   MAX-ACCESS  read-write
   STATUS      current
   DESCRIPTION
      "Path: virtualEthernet.editConf.vlan.vlan.cosCosMap.p6"
   ::= {er1646v2VEthVlanEntry 241305344}

er1646v2VEthVlanVlanCCMapP7 OBJECT-TYPE
   SYNTAX      Integer32
   MAX-ACCESS  read-write
   STATUS      current
   DESCRIPTION
      "Path: virtualEthernet.editConf.vlan.vlan.cosCosMap.p7"
   ::= {er1646v2VEthVlanEntry 241305600}

er1646v2VEthVlanVlanQCMapQueue1 OBJECT-TYPE
   SYNTAX      Integer32
   MAX-ACCESS  read-write
   STATUS      current
   DESCRIPTION
      "Path: virtualEthernet.editConf.vlan.vlan.queueCosMap.queue1"
   ::= {er1646v2VEthVlanEntry 241434880}

er1646v2VEthVlanVlanQCMapQueue2 OBJECT-TYPE
   SYNTAX      Integer32
   MAX-ACCESS  read-write
   STATUS      current
   DESCRIPTION
      "Path: virtualEthernet.editConf.vlan.vlan.queueCosMap.queue2"
   ::= {er1646v2VEthVlanEntry 241435136}

er1646v2VEthVlanVlanQCMapQueue3 OBJECT-TYPE
   SYNTAX      Integer32
   MAX-ACCESS  read-write
   STATUS      current
   DESCRIPTION
      "Path: virtualEthernet.editConf.vlan.vlan.queueCosMap.queue3"
   ::= {er1646v2VEthVlanEntry 241435392}

er1646v2VEthVlanVlanQCMapQueue4 OBJECT-TYPE
   SYNTAX      Integer32
   MAX-ACCESS  read-write
   STATUS      current
   DESCRIPTION
      "Path: virtualEthernet.editConf.vlan.vlan.queueCosMap.queue4"
   ::= {er1646v2VEthVlanEntry 241435648}

er1646v2VEthVlanVlanQCMapQueue5 OBJECT-TYPE
   SYNTAX      Integer32
   MAX-ACCESS  read-write
   STATUS      current
   DESCRIPTION
      "Path: virtualEthernet.editConf.vlan.vlan.queueCosMap.queue5"
   ::= {er1646v2VEthVlanEntry 241435904}

er1646v2VEthVlanVlanQCMapLowDelayQueue OBJECT-TYPE
   SYNTAX      Integer32
   MAX-ACCESS  read-write
   STATUS      current
   DESCRIPTION
      "Path: virtualEthernet.editConf.vlan.vlan.queueCosMap.lowDelayQueue"
   ::= {er1646v2VEthVlanEntry 241436160}

er1646v2VEthVlanVlanQCMapLowDelay2Queue OBJECT-TYPE
   SYNTAX      Integer32
   MAX-ACCESS  read-write
   STATUS      current
   DESCRIPTION
      "Path: virtualEthernet.editConf.vlan.vlan.queueCosMap.lowDelay2Queue"
   ::= {er1646v2VEthVlanEntry 241436416}

er1646v2VEthVlanVlanQCMapSystemQueue OBJECT-TYPE
   SYNTAX      Integer32
   MAX-ACCESS  read-write
   STATUS      current
   DESCRIPTION
      "Path: virtualEthernet.editConf.vlan.vlan.queueCosMap.systemQueue"
   ::= {er1646v2VEthVlanEntry 241436672}

er1646v2VEthVlanVlanQinQSVid OBJECT-TYPE
   SYNTAX      Integer32
   MAX-ACCESS  read-write
   STATUS      current
   DESCRIPTION
      "Path: virtualEthernet.editConf.vlan.vlan.tunnel.sVid"
   ::= {er1646v2VEthVlanEntry 241172736}

er1646v2VEthVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.vlan.tunnel.sTpid

       Possibilities:
               dot1Q   (33024)
               dot1ad   (34984)
               0x9100   (37120)
               0x9200   (37376)
               0x9300   (37632)"
   ::= {er1646v2VEthVlanEntry 241172992}

er1646v2VEthVlanVlanArpTimeOut OBJECT-TYPE
   SYNTAX      TimeTicks
   MAX-ACCESS  read-write
   STATUS      current
   DESCRIPTION
      "Path: virtualEthernet.editConf.vlan.vlan.arp.timeOut

       Time in centi-second."
   ::= {er1646v2VEthVlanEntry 235277312}

er1646v2VEthVlanVlanArpProxyArp OBJECT-TYPE
   SYNTAX      INTEGER
               {
               disabled (0),
               enabled (1)
               }
   MAX-ACCESS  read-write
   STATUS      current
   DESCRIPTION
      "Path: virtualEthernet.editConf.vlan.vlan.arp.proxyArp

       Possibilities:
               disabled   (0)
               enabled   (1)"
   ::= {er1646v2VEthVlanEntry 235287040}

er1646v2VEthVlanBandwidthMode OBJECT-TYPE
   SYNTAX      INTEGER
               {
               reshaping (1),
               policing (2),
               policingReshape (3)
               }
   MAX-ACCESS  read-write
   STATUS      current
   DESCRIPTION
      "Path: virtualEthernet.editConf.vlan.bandwidth.mode

       Possibilities:
               reshaping   (1)
               policing   (2)
               policingReshape   (3)"
   ::= {er1646v2VEthVlanEntry 148897792}

er1646v2VEthVlanBandwidthCir OBJECT-TYPE
   SYNTAX      Integer32
   MAX-ACCESS  read-write
   STATUS      current
   DESCRIPTION
      "Path: virtualEthernet.editConf.vlan.bandwidth.cir"
   ::= {er1646v2VEthVlanEntry 135266304}

er1646v2VEthVlanBandwidthEir OBJECT-TYPE
   SYNTAX      Integer32
   MAX-ACCESS  read-write
   STATUS      current
   DESCRIPTION
      "Path: virtualEthernet.editConf.vlan.bandwidth.eir"
   ::= {er1646v2VEthVlanEntry 141557760}

er1646v2VEthVlanBandwidthUnit OBJECT-TYPE
   SYNTAX      INTEGER
               {
               bitssec (1),
               percent (2)
               }
   MAX-ACCESS  read-write
   STATUS      current
   DESCRIPTION
      "Path: virtualEthernet.editConf.vlan.bandwidth.unit

       Possibilities:
               bits/sec   (1)
               percent   (2)"
   ::= {er1646v2VEthVlanEntry 139460608}

er1646v2VEthVlanBandwidthTc OBJECT-TYPE
   SYNTAX      INTEGER
               {
               auto (0)
               }
   MAX-ACCESS  read-write
   STATUS      current
   DESCRIPTION
      "Path: virtualEthernet.editConf.vlan.bandwidth.tc

       Possibilities:
               auto   (0)"
   ::= {er1646v2VEthVlanEntry 140509184}

er1646v2VEthVlanBandwidthTcFactor OBJECT-TYPE
   SYNTAX      INTEGER
               {
               ms (10),
               s100us (1)
               }
   MAX-ACCESS  read-write
   STATUS      current
   DESCRIPTION
      "Path: virtualEthernet.editConf.vlan.bandwidth.tcFactor

       Possibilities:
               ms   (10)
               *100us   (1)"
   ::= {er1646v2VEthVlanEntry 142606336}

er1646v2VEthVlanBandwidthCorrType OBJECT-TYPE
   SYNTAX      INTEGER
               {
               noCorrection (0),
               predefined (1),
               manual (2)
               }
   MAX-ACCESS  read-write
   STATUS      current
   DESCRIPTION
      "Path: virtualEthernet.editConf.vlan.bandwidth.correction.type

       Possibilities:
               noCorrection   (0)
               predefined   (1)
               manual   (2)"
   ::= {er1646v2VEthVlanEntry 136445952}

er1646v2VEthVlanBandwidthCorrPredefEncapsFrameRelay OBJECT-TYPE
   SYNTAX      DisplayString
   MAX-ACCESS  read-write
   STATUS      current
   DESCRIPTION
      "Path: virtualEthernet.editConf.vlan.bandwidth.correction.predefined.encapsulation.frameRelay"
   ::= {er1646v2VEthVlanEntry 136594432}

er1646v2VEthVlanBandwidthCorrPredefEncapsPpp OBJECT-TYPE
   SYNTAX      DisplayString
   MAX-ACCESS  read-write
   STATUS      current
   DESCRIPTION
      "Path: virtualEthernet.editConf.vlan.bandwidth.correction.predefined.encapsulation.ppp"
   ::= {er1646v2VEthVlanEntry 136595456}

er1646v2VEthVlanBandwidthCorrPredefEncapsAtmHl OBJECT-TYPE
   SYNTAX      INTEGER
               {
               rfc2684 (0),
               ppp (1),
               pppOverEthernet (2)
               }
   MAX-ACCESS  read-write
   STATUS      current
   DESCRIPTION
      "Path: virtualEthernet.editConf.vlan.bandwidth.correction.predefined.encapsulation.atm.higherLayer

       Possibilities:
               rfc2684   (0)
               ppp   (1)
               pppOverEthernet   (2)"
   ::= {er1646v2VEthVlanEntry 136596608}

er1646v2VEthVlanBandwidthCorrPredefEncapsAtmMp OBJECT-TYPE
   SYNTAX      INTEGER
               {
               llcEncapsulation (0),
               vcMultiplexing (1)
               }
   MAX-ACCESS  read-write
   STATUS      current
   DESCRIPTION
      "Path: virtualEthernet.editConf.vlan.bandwidth.correction.predefined.encapsulation.atm.multiProtocol

       Possibilities:
               llcEncapsulation   (0)
               vcMultiplexing   (1)"
   ::= {er1646v2VEthVlanEntry 136596736}

er1646v2VEthVlanBandwidthCorrPredefEncapsHdlc OBJECT-TYPE
   SYNTAX      DisplayString
   MAX-ACCESS  read-write
   STATUS      current
   DESCRIPTION
      "Path: virtualEthernet.editConf.vlan.bandwidth.correction.predefined.encapsulation.hdlc"
   ::= {er1646v2VEthVlanEntry 136597504}

er1646v2VEthVlanBandwidthCorrPredefEncapsEfmFs OBJECT-TYPE
   SYNTAX      Integer32
   MAX-ACCESS  read-write
   STATUS      current
   DESCRIPTION
      "Path: virtualEthernet.editConf.vlan.bandwidth.correction.predefined.encapsulation.efm.fragmentSize"
   ::= {er1646v2VEthVlanEntry 136598656}

er1646v2VEthVlanBandwidthCorrPredefEncapsEfmIb OBJECT-TYPE
   SYNTAX      Integer32
   MAX-ACCESS  read-write
   STATUS      current
   DESCRIPTION
      "Path: virtualEthernet.editConf.vlan.bandwidth.correction.predefined.encapsulation.efm.idleBytes"
   ::= {er1646v2VEthVlanEntry 136598784}

er1646v2VEthVlanBandwidthCorrPredefMode OBJECT-TYPE
   SYNTAX      INTEGER
               {
               routing (0),
               bridging (1)
               }
   MAX-ACCESS  read-write
   STATUS      current
   DESCRIPTION
      "Path: virtualEthernet.editConf.vlan.bandwidth.correction.predefined.mode

       Possibilities:
               routing   (0)
               bridging   (1)"
   ::= {er1646v2VEthVlanEntry 136609792}

er1646v2VEthVlanBandwidthCorrManualOverhead OBJECT-TYPE
   SYNTAX      Integer32
   MAX-ACCESS  read-write
   STATUS      current
   DESCRIPTION
      "Path: virtualEthernet.editConf.vlan.bandwidth.correction.manual.overhead"
   ::= {er1646v2VEthVlanEntry 136708608}

er1646v2VEthVlanBandwidthCorrManualFrameData OBJECT-TYPE
   SYNTAX      Counter32
   MAX-ACCESS  read-write
   STATUS      current
   DESCRIPTION
      "Path: virtualEthernet.editConf.vlan.bandwidth.correction.manual.frameData

       32 bit unsigned wrappable counter."
   ::= {er1646v2VEthVlanEntry 136709120}

er1646v2VEthVlanBandwidthCorrManualFrameHeader OBJECT-TYPE
   SYNTAX      Counter32
   MAX-ACCESS  read-write
   STATUS      current
   DESCRIPTION
      "Path: virtualEthernet.editConf.vlan.bandwidth.correction.manual.frameHeader

       32 bit unsigned wrappable counter."
   ::= {er1646v2VEthVlanEntry 136709632}

er1646v2VEthVlanBandwidthMaxFifoQLen OBJECT-TYPE
   SYNTAX      Integer32
   MAX-ACCESS  read-write
   STATUS      current
   DESCRIPTION
      "Path: virtualEthernet.editConf.vlan.bandwidth.maxFifoQLen"
   ::= {er1646v2VEthVlanEntry 137363456}

er1646v2VEthVlanBandwidthDeFlagCir OBJECT-TYPE
   SYNTAX      INTEGER
               {
               allowed (1),
               notAllowed (2)
               }
   MAX-ACCESS  read-write
   STATUS      current
   DESCRIPTION
      "Path: virtualEthernet.editConf.vlan.bandwidth.deFlag.cir

       Possibilities:
               allowed   (1)
               notAllowed   (2)"
   ::= {er1646v2VEthVlanEntry 147853312}

er1646v2VEthVlanBandwidthDeFlagEir OBJECT-TYPE
   SYNTAX      INTEGER
               {
               allowed (1),
               notAllowed (2)
               }
   MAX-ACCESS  read-write
   STATUS      current
   DESCRIPTION
      "Path: virtualEthernet.editConf.vlan.bandwidth.deFlag.eir

       Possibilities:
               allowed   (1)
               notAllowed   (2)"
   ::= {er1646v2VEthVlanEntry 147857408}

er1646v2VEthVlanBandwidthDeFlagViolate OBJECT-TYPE
   SYNTAX      INTEGER
               {
               allowed (1),
               notAllowed (2)
               }
   MAX-ACCESS  read-write
   STATUS      current
   DESCRIPTION
      "Path: virtualEthernet.editConf.vlan.bandwidth.deFlag.violate

       Possibilities:
               allowed   (1)
               notAllowed   (2)"
   ::= {er1646v2VEthVlanEntry 147861504}

er1646v2VEthVlanBandwidthActCirActNone OBJECT-TYPE
   SYNTAX      OCTET STRING
   MAX-ACCESS  read-write
   STATUS      current
   DESCRIPTION
      "Path: virtualEthernet.editConf.vlan.bandwidth.action.cirAction.none"
   ::= {er1646v2VEthVlanEntry 150085632}

er1646v2VEthVlanBandwidthActCirActEthCos1 OBJECT-TYPE
   SYNTAX      INTEGER
               {
               unchanged (256)
               }
   MAX-ACCESS  read-write
   STATUS      current
   DESCRIPTION
      "Path: virtualEthernet.editConf.vlan.bandwidth.action.cirAction.ethernet.cosDepth1

       Possibilities:
               unchanged   (256)"
   ::= {er1646v2VEthVlanEntry 150094080}

er1646v2VEthVlanBandwidthActCirActEthDei1 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth1

       Possibilities:
               unchanged   (255)
               clear   (0)
               set   (1)"
   ::= {er1646v2VEthVlanEntry 150099200}

er1646v2VEthVlanBandwidthActCirActEthCos2 OBJECT-TYPE
   SYNTAX      INTEGER
               {
               unchanged (256)
               }
   MAX-ACCESS  read-write
   STATUS      current
   DESCRIPTION
      "Path: virtualEthernet.editConf.vlan.bandwidth.action.cirAction.ethernet.cosDepth2

       Possibilities:
               unchanged   (256)"
   ::= {er1646v2VEthVlanEntry 150094336}

er1646v2VEthVlanBandwidthActCirActEthDei2 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth2

       Possibilities:
               unchanged   (255)
               clear   (0)
               set   (1)"
   ::= {er1646v2VEthVlanEntry 150099456}

er1646v2VEthVlanBandwidthActCirActEthCos3 OBJECT-TYPE
   SYNTAX      INTEGER
               {
               unchanged (256)
               }
   MAX-ACCESS  read-write
   STATUS      current
   DESCRIPTION
      "Path: virtualEthernet.editConf.vlan.bandwidth.action.cirAction.ethernet.cosDepth3

       Possibilities:
               unchanged   (256)"
   ::= {er1646v2VEthVlanEntry 150094592}

er1646v2VEthVlanBandwidthActCirActEthDei3 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth3

       Possibilities:
               unchanged   (255)
               clear   (0)
               set   (1)"
   ::= {er1646v2VEthVlanEntry 150099712}

er1646v2VEthVlanBandwidthActCirActEthCos4 OBJECT-TYPE
   SYNTAX      INTEGER
               {
               unchanged (256)
               }
   MAX-ACCESS  read-write
   STATUS      current
   DESCRIPTION
      "Path: virtualEthernet.editConf.vlan.bandwidth.action.cirAction.ethernet.cosDepth4

       Possibilities:
               unchanged   (256)"
   ::= {er1646v2VEthVlanEntry 150094848}

er1646v2VEthVlanBandwidthActCirActEthDei4 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth4

       Possibilities:
               unchanged   (255)
               clear   (0)
               set   (1)"
   ::= {er1646v2VEthVlanEntry 150099968}

er1646v2VEthVlanBandwidthActCirActEthCos5 OBJECT-TYPE
   SYNTAX      INTEGER
               {
               unchanged (256)
               }
   MAX-ACCESS  read-write
   STATUS      current
   DESCRIPTION
      "Path: virtualEthernet.editConf.vlan.bandwidth.action.cirAction.ethernet.cosDepth5

       Possibilities:
               unchanged   (256)"
   ::= {er1646v2VEthVlanEntry 150095104}

er1646v2VEthVlanBandwidthActCirActEthDei5 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth5

       Possibilities:
               unchanged   (255)
               clear   (0)
               set   (1)"
   ::= {er1646v2VEthVlanEntry 150100224}

er1646v2VEthVlanBandwidthActCirActEthCos6 OBJECT-TYPE
   SYNTAX      INTEGER
               {
               unchanged (256)
               }
   MAX-ACCESS  read-write
   STATUS      current
   DESCRIPTION
      "Path: virtualEthernet.editConf.vlan.bandwidth.action.cirAction.ethernet.cosDepth6

       Possibilities:
               unchanged   (256)"
   ::= {er1646v2VEthVlanEntry 150095360}

er1646v2VEthVlanBandwidthActCirActEthDei6 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth6

       Possibilities:
               unchanged   (255)
               clear   (0)
               set   (1)"
   ::= {er1646v2VEthVlanEntry 150100480}

er1646v2VEthVlanBandwidthActCirActEthCos7 OBJECT-TYPE
   SYNTAX      INTEGER
               {
               unchanged (256)
               }
   MAX-ACCESS  read-write
   STATUS      current
   DESCRIPTION
      "Path: virtualEthernet.editConf.vlan.bandwidth.action.cirAction.ethernet.cosDepth7

       Possibilities:
               unchanged   (256)"
   ::= {er1646v2VEthVlanEntry 150095616}

er1646v2VEthVlanBandwidthActCirActEthDei7 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth7

       Possibilities:
               unchanged   (255)
               clear   (0)
               set   (1)"
   ::= {er1646v2VEthVlanEntry 150100736}

er1646v2VEthVlanBandwidthActCirActEthCos8 OBJECT-TYPE
   SYNTAX      INTEGER
               {
               unchanged (256)
               }
   MAX-ACCESS  read-write
   STATUS      current
   DESCRIPTION
      "Path: virtualEthernet.editConf.vlan.bandwidth.action.cirAction.ethernet.cosDepth8

       Possibilities:
               unchanged   (256)"
   ::= {er1646v2VEthVlanEntry 150095872}

er1646v2VEthVlanBandwidthActCirActEthDei8 OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deiDepth8

       Possibilities:
               unchanged   (255)
               clear   (0)
               set   (1)"
   ::= {er1646v2VEthVlanEntry 150100992}

er1646v2VEthVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 150096128}

er1646v2VEthVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 150096384}

er1646v2VEthVlanBandwidthActCirActEthDrpLev OBJECT-TYPE
   SYNTAX      INTEGER
               {
               unchanged (0)
               }
   MAX-ACCESS  read-write
   STATUS      current
   DESCRIPTION
      "Path: virtualEthernet.editConf.vlan.bandwidth.action.cirAction.ethernet.dropLevel

       Possibilities:
               unchanged   (0)"
   ::= {er1646v2VEthVlanEntry 150096640}

er1646v2VEthVlanBandwidthActCirActEthDeFlag OBJECT-TYPE
   SYNTAX      INTEGER
               {
               unchanged (255),
               clear (0),
               set (1)
               }
   MAX-ACCESS  read-write
   STATUS      current
   DESCRIPTION
      "Path: virtualEthernet.editConf.vlan.bandwidth.action.cirAction.ethernet.deFlag

       Possibilities:
               unchanged   (255)
               clear   (0)
               set   (1)"
   ::= {er1646v2VEthVlanEntry 150097408}

er1646v2VEthVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 150120704}

er1646v2VEthVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 150120960}

er1646v2VEthVlanBandwidthActCirActIpDrpLev OBJECT-TYPE
   SYNTAX      INTEGER
               {
               unchanged (0)
               }
   MAX-ACCESS  read-write
   STATUS      current
   DESCRIPTION
      "Path: virtualEthernet.editConf.vlan.bandwidth.action.cirAction.ip.dropLevel

       Possibilities:
               unchanged   (0)"
   ::= {er1646v2VEthVlanEntry 150121216}

er1646v2VEthVlanBandwidthActCirActIpDeFlag OBJECT-TYPE
   SYNTAX      INTEGER
               {
               unchanged (255),
               clear (0),
               set (1)
               }
   MAX-ACCESS  read-write
   STATUS      current
   DESCRIPTION
      "Path: virtualEthernet.editConf.vlan.bandwidth.action.cirAction.ip.deFlag

       Possibilities:
               unchanged   (255)
               clear   (0)
               set   (1)"
   ::= {er1646v2VEthVlanEntry 150121984}

er1646v2VEthVlanBandwidthActEirActNone OBJECT-TYPE
   SYNTAX      OCTET STRING
   MAX-ACCESS  read-write
   STATUS      current
   DESCRIPTION
      "Path: virtualEthernet.editConf.vlan.bandwidth.action.eirAction.none"
   ::= {er1646v2VEthVlanEntry 150216704}

er1646v2VEthVlanBandwidthActEirActEthCos1 OBJECT-TYPE
   SYNTAX      INTEGER
               {
               unchanged (256)
               }
   MAX-ACCESS  read-write
   STATUS      current
   DESCRIPTION
      "Path: virtualEthernet.editConf.vlan.bandwidth.action.eirAction.ethernet.cosDepth1

       Possibilities:
               unchanged   (256)"
   ::= {er1646v2VEthVlanEntry 150225152}

er1646v2VEthVlanBandwidthActEirActEthDei1 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth1

       Possibilities:
               unchanged   (255)
               clear   (0)
               set   (1)"
   ::= {er1646v2VEthVlanEntry 150230272}

er1646v2VEthVlanBandwidthActEirActEthCos2 OBJECT-TYPE
   SYNTAX      INTEGER
               {
               unchanged (256)
               }
   MAX-ACCESS  read-write
   STATUS      current
   DESCRIPTION
      "Path: virtualEthernet.editConf.vlan.bandwidth.action.eirAction.ethernet.cosDepth2

       Possibilities:
               unchanged   (256)"
   ::= {er1646v2VEthVlanEntry 150225408}

er1646v2VEthVlanBandwidthActEirActEthDei2 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth2

       Possibilities:
               unchanged   (255)
               clear   (0)
               set   (1)"
   ::= {er1646v2VEthVlanEntry 150230528}

er1646v2VEthVlanBandwidthActEirActEthCos3 OBJECT-TYPE
   SYNTAX      INTEGER
               {
               unchanged (256)
               }
   MAX-ACCESS  read-write
   STATUS      current
   DESCRIPTION
      "Path: virtualEthernet.editConf.vlan.bandwidth.action.eirAction.ethernet.cosDepth3

       Possibilities:
               unchanged   (256)"
   ::= {er1646v2VEthVlanEntry 150225664}

er1646v2VEthVlanBandwidthActEirActEthDei3 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth3

       Possibilities:
               unchanged   (255)
               clear   (0)
               set   (1)"
   ::= {er1646v2VEthVlanEntry 150230784}

er1646v2VEthVlanBandwidthActEirActEthCos4 OBJECT-TYPE
   SYNTAX      INTEGER
               {
               unchanged (256)
               }
   MAX-ACCESS  read-write
   STATUS      current
   DESCRIPTION
      "Path: virtualEthernet.editConf.vlan.bandwidth.action.eirAction.ethernet.cosDepth4

       Possibilities:
               unchanged   (256)"
   ::= {er1646v2VEthVlanEntry 150225920}

er1646v2VEthVlanBandwidthActEirActEthDei4 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth4

       Possibilities:
               unchanged   (255)
               clear   (0)
               set   (1)"
   ::= {er1646v2VEthVlanEntry 150231040}

er1646v2VEthVlanBandwidthActEirActEthCos5 OBJECT-TYPE
   SYNTAX      INTEGER
               {
               unchanged (256)
               }
   MAX-ACCESS  read-write
   STATUS      current
   DESCRIPTION
      "Path: virtualEthernet.editConf.vlan.bandwidth.action.eirAction.ethernet.cosDepth5

       Possibilities:
               unchanged   (256)"
   ::= {er1646v2VEthVlanEntry 150226176}

er1646v2VEthVlanBandwidthActEirActEthDei5 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth5

       Possibilities:
               unchanged   (255)
               clear   (0)
               set   (1)"
   ::= {er1646v2VEthVlanEntry 150231296}

er1646v2VEthVlanBandwidthActEirActEthCos6 OBJECT-TYPE
   SYNTAX      INTEGER
               {
               unchanged (256)
               }
   MAX-ACCESS  read-write
   STATUS      current
   DESCRIPTION
      "Path: virtualEthernet.editConf.vlan.bandwidth.action.eirAction.ethernet.cosDepth6

       Possibilities:
               unchanged   (256)"
   ::= {er1646v2VEthVlanEntry 150226432}

er1646v2VEthVlanBandwidthActEirActEthDei6 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth6

       Possibilities:
               unchanged   (255)
               clear   (0)
               set   (1)"
   ::= {er1646v2VEthVlanEntry 150231552}

er1646v2VEthVlanBandwidthActEirActEthCos7 OBJECT-TYPE
   SYNTAX      INTEGER
               {
               unchanged (256)
               }
   MAX-ACCESS  read-write
   STATUS      current
   DESCRIPTION
      "Path: virtualEthernet.editConf.vlan.bandwidth.action.eirAction.ethernet.cosDepth7

       Possibilities:
               unchanged   (256)"
   ::= {er1646v2VEthVlanEntry 150226688}

er1646v2VEthVlanBandwidthActEirActEthDei7 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth7

       Possibilities:
               unchanged   (255)
               clear   (0)
               set   (1)"
   ::= {er1646v2VEthVlanEntry 150231808}

er1646v2VEthVlanBandwidthActEirActEthCos8 OBJECT-TYPE
   SYNTAX      INTEGER
               {
               unchanged (256)
               }
   MAX-ACCESS  read-write
   STATUS      current
   DESCRIPTION
      "Path: virtualEthernet.editConf.vlan.bandwidth.action.eirAction.ethernet.cosDepth8

       Possibilities:
               unchanged   (256)"
   ::= {er1646v2VEthVlanEntry 150226944}

er1646v2VEthVlanBandwidthActEirActEthDei8 OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deiDepth8

       Possibilities:
               unchanged   (255)
               clear   (0)
               set   (1)"
   ::= {er1646v2VEthVlanEntry 150232064}

er1646v2VEthVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 150227200}

er1646v2VEthVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 150227456}

er1646v2VEthVlanBandwidthActEirActEthDrpLev OBJECT-TYPE
   SYNTAX      INTEGER
               {
               unchanged (0)
               }
   MAX-ACCESS  read-write
   STATUS      current
   DESCRIPTION
      "Path: virtualEthernet.editConf.vlan.bandwidth.action.eirAction.ethernet.dropLevel

       Possibilities:
               unchanged   (0)"
   ::= {er1646v2VEthVlanEntry 150227712}

er1646v2VEthVlanBandwidthActEirActEthDeFlag OBJECT-TYPE
   SYNTAX      INTEGER
               {
               unchanged (255),
               clear (0),
               set (1)
               }
   MAX-ACCESS  read-write
   STATUS      current
   DESCRIPTION
      "Path: virtualEthernet.editConf.vlan.bandwidth.action.eirAction.ethernet.deFlag

       Possibilities:
               unchanged   (255)
               clear   (0)
               set   (1)"
   ::= {er1646v2VEthVlanEntry 150228480}

er1646v2VEthVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 150251776}

er1646v2VEthVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 150252032}

er1646v2VEthVlanBandwidthActEirActIpDrpLev OBJECT-TYPE
   SYNTAX      INTEGER
               {
               unchanged (0)
               }
   MAX-ACCESS  read-write
   STATUS      current
   DESCRIPTION
      "Path: virtualEthernet.editConf.vlan.bandwidth.action.eirAction.ip.dropLevel

       Possibilities:
               unchanged   (0)"
   ::= {er1646v2VEthVlanEntry 150252288}

er1646v2VEthVlanBandwidthActEirActIpDeFlag OBJECT-TYPE
   SYNTAX      INTEGER
               {
               unchanged (255),
               clear (0),
               set (1)
               }
   MAX-ACCESS  read-write
   STATUS      current
   DESCRIPTION
      "Path: virtualEthernet.editConf.vlan.bandwidth.action.eirAction.ip.deFlag

       Possibilities:
               unchanged   (255)
               clear   (0)
               set   (1)"
   ::= {er1646v2VEthVlanEntry 150253056}

er1646v2VEthVlanBandwidthActViolActNone OBJECT-TYPE
   SYNTAX      OCTET STRING
   MAX-ACCESS  read-write
   STATUS      current
   DESCRIPTION
      "Path: virtualEthernet.editConf.vlan.bandwidth.action.violateAction.none"
   ::= {er1646v2VEthVlanEntry 150347776}

er1646v2VEthVlanBandwidthActViolActDrop OBJECT-TYPE
   SYNTAX      OCTET STRING
   MAX-ACCESS  read-write
   STATUS      current
   DESCRIPTION
      "Path: virtualEthernet.editConf.vlan.bandwidth.action.violateAction.drop"
   ::= {er1646v2VEthVlanEntry 150364160}

er1646v2VEthVlanBandwidthActViolActEthCos1 OBJECT-TYPE
   SYNTAX      INTEGER
               {
               unchanged (256)
               }
   MAX-ACCESS  read-write
   STATUS      current
   DESCRIPTION
      "Path: virtualEthernet.editConf.vlan.bandwidth.action.violateAction.ethernet.cosDepth1

       Possibilities:
               unchanged   (256)"
   ::= {er1646v2VEthVlanEntry 150356224}

er1646v2VEthVlanBandwidthActViolActEthDei1 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth1

       Possibilities:
               unchanged   (255)
               clear   (0)
               set   (1)"
   ::= {er1646v2VEthVlanEntry 150361344}

er1646v2VEthVlanBandwidthActViolActEthCos2 OBJECT-TYPE
   SYNTAX      INTEGER
               {
               unchanged (256)
               }
   MAX-ACCESS  read-write
   STATUS      current
   DESCRIPTION
      "Path: virtualEthernet.editConf.vlan.bandwidth.action.violateAction.ethernet.cosDepth2

       Possibilities:
               unchanged   (256)"
   ::= {er1646v2VEthVlanEntry 150356480}

er1646v2VEthVlanBandwidthActViolActEthDei2 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth2

       Possibilities:
               unchanged   (255)
               clear   (0)
               set   (1)"
   ::= {er1646v2VEthVlanEntry 150361600}

er1646v2VEthVlanBandwidthActViolActEthCos3 OBJECT-TYPE
   SYNTAX      INTEGER
               {
               unchanged (256)
               }
   MAX-ACCESS  read-write
   STATUS      current
   DESCRIPTION
      "Path: virtualEthernet.editConf.vlan.bandwidth.action.violateAction.ethernet.cosDepth3

       Possibilities:
               unchanged   (256)"
   ::= {er1646v2VEthVlanEntry 150356736}

er1646v2VEthVlanBandwidthActViolActEthDei3 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth3

       Possibilities:
               unchanged   (255)
               clear   (0)
               set   (1)"
   ::= {er1646v2VEthVlanEntry 150361856}

er1646v2VEthVlanBandwidthActViolActEthCos4 OBJECT-TYPE
   SYNTAX      INTEGER
               {
               unchanged (256)
               }
   MAX-ACCESS  read-write
   STATUS      current
   DESCRIPTION
      "Path: virtualEthernet.editConf.vlan.bandwidth.action.violateAction.ethernet.cosDepth4

       Possibilities:
               unchanged   (256)"
   ::= {er1646v2VEthVlanEntry 150356992}

er1646v2VEthVlanBandwidthActViolActEthDei4 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth4

       Possibilities:
               unchanged   (255)
               clear   (0)
               set   (1)"
   ::= {er1646v2VEthVlanEntry 150362112}

er1646v2VEthVlanBandwidthActViolActEthCos5 OBJECT-TYPE
   SYNTAX      INTEGER
               {
               unchanged (256)
               }
   MAX-ACCESS  read-write
   STATUS      current
   DESCRIPTION
      "Path: virtualEthernet.editConf.vlan.bandwidth.action.violateAction.ethernet.cosDepth5

       Possibilities:
               unchanged   (256)"
   ::= {er1646v2VEthVlanEntry 150357248}

er1646v2VEthVlanBandwidthActViolActEthDei5 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth5

       Possibilities:
               unchanged   (255)
               clear   (0)
               set   (1)"
   ::= {er1646v2VEthVlanEntry 150362368}

er1646v2VEthVlanBandwidthActViolActEthCos6 OBJECT-TYPE
   SYNTAX      INTEGER
               {
               unchanged (256)
               }
   MAX-ACCESS  read-write
   STATUS      current
   DESCRIPTION
      "Path: virtualEthernet.editConf.vlan.bandwidth.action.violateAction.ethernet.cosDepth6

       Possibilities:
               unchanged   (256)"
   ::= {er1646v2VEthVlanEntry 150357504}

er1646v2VEthVlanBandwidthActViolActEthDei6 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth6

       Possibilities:
               unchanged   (255)
               clear   (0)
               set   (1)"
   ::= {er1646v2VEthVlanEntry 150362624}

er1646v2VEthVlanBandwidthActViolActEthCos7 OBJECT-TYPE
   SYNTAX      INTEGER
               {
               unchanged (256)
               }
   MAX-ACCESS  read-write
   STATUS      current
   DESCRIPTION
      "Path: virtualEthernet.editConf.vlan.bandwidth.action.violateAction.ethernet.cosDepth7

       Possibilities:
               unchanged   (256)"
   ::= {er1646v2VEthVlanEntry 150357760}

er1646v2VEthVlanBandwidthActViolActEthDei7 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth7

       Possibilities:
               unchanged   (255)
               clear   (0)
               set   (1)"
   ::= {er1646v2VEthVlanEntry 150362880}

er1646v2VEthVlanBandwidthActViolActEthCos8 OBJECT-TYPE
   SYNTAX      INTEGER
               {
               unchanged (256)
               }
   MAX-ACCESS  read-write
   STATUS      current
   DESCRIPTION
      "Path: virtualEthernet.editConf.vlan.bandwidth.action.violateAction.ethernet.cosDepth8

       Possibilities:
               unchanged   (256)"
   ::= {er1646v2VEthVlanEntry 150358016}

er1646v2VEthVlanBandwidthActViolActEthDei8 OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deiDepth8

       Possibilities:
               unchanged   (255)
               clear   (0)
               set   (1)"
   ::= {er1646v2VEthVlanEntry 150363136}

er1646v2VEthVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 150358272}

er1646v2VEthVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 150358528}

er1646v2VEthVlanBandwidthActViolActEthDrpLev OBJECT-TYPE
   SYNTAX      INTEGER
               {
               unchanged (0)
               }
   MAX-ACCESS  read-write
   STATUS      current
   DESCRIPTION
      "Path: virtualEthernet.editConf.vlan.bandwidth.action.violateAction.ethernet.dropLevel

       Possibilities:
               unchanged   (0)"
   ::= {er1646v2VEthVlanEntry 150358784}

er1646v2VEthVlanBandwidthActViolActEthDeFlag OBJECT-TYPE
   SYNTAX      INTEGER
               {
               unchanged (255),
               clear (0),
               set (1)
               }
   MAX-ACCESS  read-write
   STATUS      current
   DESCRIPTION
      "Path: virtualEthernet.editConf.vlan.bandwidth.action.violateAction.ethernet.deFlag

       Possibilities:
               unchanged   (255)
               clear   (0)
               set   (1)"
   ::= {er1646v2VEthVlanEntry 150359552}

er1646v2VEthVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 150382848}

er1646v2VEthVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 150383104}

er1646v2VEthVlanBandwidthActViolActIpDrpLev OBJECT-TYPE
   SYNTAX      INTEGER
               {
               unchanged (0)
               }
   MAX-ACCESS  read-write
   STATUS      current
   DESCRIPTION
      "Path: virtualEthernet.editConf.vlan.bandwidth.action.violateAction.ip.dropLevel

       Possibilities:
               unchanged   (0)"
   ::= {er1646v2VEthVlanEntry 150383360}

er1646v2VEthVlanBandwidthActViolActIpDeFlag OBJECT-TYPE
   SYNTAX      INTEGER
               {
               unchanged (255),
               clear (0),
               set (1)
               }
   MAX-ACCESS  read-write
   STATUS      current
   DESCRIPTION
      "Path: virtualEthernet.editConf.vlan.bandwidth.action.violateAction.ip.deFlag

       Possibilities:
               unchanged   (255)
               clear   (0)
               set   (1)"
   ::= {er1646v2VEthVlanEntry 150384128}

er1646v2VEthVlanInbBwMode OBJECT-TYPE
   SYNTAX      INTEGER
               {
               reshaping (1),
               policing (2)
               }
   MAX-ACCESS  read-write
   STATUS      current
   DESCRIPTION
      "Path: virtualEthernet.editConf.vlan.inboundBandwidth.mode

       Possibilities:
               reshaping   (1)
               policing   (2)"
   ::= {er1646v2VEthVlanEntry 132120576}

er1646v2VEthVlanInbBwCir OBJECT-TYPE
   SYNTAX      Integer32
   MAX-ACCESS  read-write
   STATUS      current
   DESCRIPTION
      "Path: virtualEthernet.editConf.vlan.inboundBandwidth.cir"
   ::= {er1646v2VEthVlanEntry 118489088}

er1646v2VEthVlanInbBwEir OBJECT-TYPE
   SYNTAX      Integer32
   MAX-ACCESS  read-write
   STATUS      current
   DESCRIPTION
      "Path: virtualEthernet.editConf.vlan.inboundBandwidth.eir"
   ::= {er1646v2VEthVlanEntry 124780544}

er1646v2VEthVlanInbBwUnit OBJECT-TYPE
   SYNTAX      INTEGER
               {
               bitssec (1),
               percent (2)
               }
   MAX-ACCESS  read-write
   STATUS      current
   DESCRIPTION
      "Path: virtualEthernet.editConf.vlan.inboundBandwidth.unit

       Possibilities:
               bits/sec   (1)
               percent   (2)"
   ::= {er1646v2VEthVlanEntry 122683392}

er1646v2VEthVlanInbBwTc OBJECT-TYPE
   SYNTAX      INTEGER
               {
               auto (0)
               }
   MAX-ACCESS  read-write
   STATUS      current
   DESCRIPTION
      "Path: virtualEthernet.editConf.vlan.inboundBandwidth.tc

       Possibilities:
               auto   (0)"
   ::= {er1646v2VEthVlanEntry 123731968}

er1646v2VEthVlanInbBwTcFactor OBJECT-TYPE
   SYNTAX      INTEGER
               {
               ms (10),
               s100us (1)
               }
   MAX-ACCESS  read-write
   STATUS      current
   DESCRIPTION
      "Path: virtualEthernet.editConf.vlan.inboundBandwidth.tcFactor

       Possibilities:
               ms   (10)
               *100us   (1)"
   ::= {er1646v2VEthVlanEntry 125829120}

er1646v2VEthVlanInbBwCorrType OBJECT-TYPE
   SYNTAX      INTEGER
               {
               noCorrection (0),
               predefined (1),
               manual (2)
               }
   MAX-ACCESS  read-write
   STATUS      current
   DESCRIPTION
      "Path: virtualEthernet.editConf.vlan.inboundBandwidth.correction.type

       Possibilities:
               noCorrection   (0)
               predefined   (1)
               manual   (2)"
   ::= {er1646v2VEthVlanEntry 119668736}

er1646v2VEthVlanInbBwCorrPredefEncapsFrameRelay OBJECT-TYPE
   SYNTAX      DisplayString
   MAX-ACCESS  read-write
   STATUS      current
   DESCRIPTION
      "Path: virtualEthernet.editConf.vlan.inboundBandwidth.correction.predefined.encapsulation.frameRelay"
   ::= {er1646v2VEthVlanEntry 119817216}

er1646v2VEthVlanInbBwCorrPredefEncapsPpp OBJECT-TYPE
   SYNTAX      DisplayString
   MAX-ACCESS  read-write
   STATUS      current
   DESCRIPTION
      "Path: virtualEthernet.editConf.vlan.inboundBandwidth.correction.predefined.encapsulation.ppp"
   ::= {er1646v2VEthVlanEntry 119818240}

er1646v2VEthVlanInbBwCorrPredefEncapsAtmHl OBJECT-TYPE
   SYNTAX      INTEGER
               {
               rfc2684 (0),
               ppp (1),
               pppOverEthernet (2)
               }
   MAX-ACCESS  read-write
   STATUS      current
   DESCRIPTION
      "Path: virtualEthernet.editConf.vlan.inboundBandwidth.correction.predefined.encapsulation.atm.higherLayer

       Possibilities:
               rfc2684   (0)
               ppp   (1)
               pppOverEthernet   (2)"
   ::= {er1646v2VEthVlanEntry 119819392}

er1646v2VEthVlanInbBwCorrPredefEncapsAtmMp OBJECT-TYPE
   SYNTAX      INTEGER
               {
               llcEncapsulation (0),
               vcMultiplexing (1)
               }
   MAX-ACCESS  read-write
   STATUS      current
   DESCRIPTION
      "Path: virtualEthernet.editConf.vlan.inboundBandwidth.correction.predefined.encapsulation.atm.multiProtocol

       Possibilities:
               llcEncapsulation   (0)
               vcMultiplexing   (1)"
   ::= {er1646v2VEthVlanEntry 119819520}

er1646v2VEthVlanInbBwCorrPredefEncapsHdlc OBJECT-TYPE
   SYNTAX      DisplayString
   MAX-ACCESS  read-write
   STATUS      current
   DESCRIPTION
      "Path: virtualEthernet.editConf.vlan.inboundBandwidth.correction.predefined.encapsulation.hdlc"
   ::= {er1646v2VEthVlanEntry 119820288}

er1646v2VEthVlanInbBwCorrPredefEncapsEfmFs OBJECT-TYPE
   SYNTAX      Integer32
   MAX-ACCESS  read-write
   STATUS      current
   DESCRIPTION
      "Path: virtualEthernet.editConf.vlan.inboundBandwidth.correction.predefined.encapsulation.efm.fragmentSize"
   ::= {er1646v2VEthVlanEntry 119821440}

er1646v2VEthVlanInbBwCorrPredefEncapsEfmIb OBJECT-TYPE
   SYNTAX      Integer32
   MAX-ACCESS  read-write
   STATUS      current
   DESCRIPTION
      "Path: virtualEthernet.editConf.vlan.inboundBandwidth.correction.predefined.encapsulation.efm.idleBytes"
   ::= {er1646v2VEthVlanEntry 119821568}

er1646v2VEthVlanInbBwCorrPredefMode OBJECT-TYPE
   SYNTAX      INTEGER
               {
               routing (0),
               bridging (1)
               }
   MAX-ACCESS  read-write
   STATUS      current
   DESCRIPTION
      "Path: virtualEthernet.editConf.vlan.inboundBandwidth.correction.predefined.mode

       Possibilities:
               routing   (0)
               bridging   (1)"
   ::= {er1646v2VEthVlanEntry 119832576}

er1646v2VEthVlanInbBwCorrManualOverhead OBJECT-TYPE
   SYNTAX      Integer32
   MAX-ACCESS  read-write
   STATUS      current
   DESCRIPTION
      "Path: virtualEthernet.editConf.vlan.inboundBandwidth.correction.manual.overhead"
   ::= {er1646v2VEthVlanEntry 119931392}

er1646v2VEthVlanInbBwCorrManualFrameData OBJECT-TYPE
   SYNTAX      Counter32
   MAX-ACCESS  read-write
   STATUS      current
   DESCRIPTION
      "Path: virtualEthernet.editConf.vlan.inboundBandwidth.correction.manual.frameData

       32 bit unsigned wrappable counter."
   ::= {er1646v2VEthVlanEntry 119931904}

er1646v2VEthVlanInbBwCorrManualFrameHeader OBJECT-TYPE
   SYNTAX      Counter32
   MAX-ACCESS  read-write
   STATUS      current
   DESCRIPTION
      "Path: virtualEthernet.editConf.vlan.inboundBandwidth.correction.manual.frameHeader

       32 bit unsigned wrappable counter."
   ::= {er1646v2VEthVlanEntry 119932416}

er1646v2VEthVlanInbBwMaxFifoQLen OBJECT-TYPE
   SYNTAX      Integer32
   MAX-ACCESS  read-write
   STATUS      current
   DESCRIPTION
      "Path: virtualEthernet.editConf.vlan.inboundBandwidth.maxFifoQLen"
   ::= {er1646v2VEthVlanEntry 120586240}

er1646v2VEthVlanInbBwPriorityPolicy OBJECT-TYPE
   SYNTAX      DisplayString
   MAX-ACCESS  read-write
   STATUS      current
   DESCRIPTION
      "Path: virtualEthernet.editConf.vlan.inboundBandwidth.priorityPolicy"
   ::= {er1646v2VEthVlanEntry 121634816}

er1646v2VEthVlanInbBwDeFlagCir OBJECT-TYPE
   SYNTAX      INTEGER
               {
               allowed (1),
               notAllowed (2)
               }
   MAX-ACCESS  read-write
   STATUS      current
   DESCRIPTION
      "Path: virtualEthernet.editConf.vlan.inboundBandwidth.deFlag.cir

       Possibilities:
               allowed   (1)
               notAllowed   (2)"
   ::= {er1646v2VEthVlanEntry 131076096}

er1646v2VEthVlanInbBwDeFlagEir OBJECT-TYPE
   SYNTAX      INTEGER
               {
               allowed (1),
               notAllowed (2)
               }
   MAX-ACCESS  read-write
   STATUS      current
   DESCRIPTION
      "Path: virtualEthernet.editConf.vlan.inboundBandwidth.deFlag.eir

       Possibilities:
               allowed   (1)
               notAllowed   (2)"
   ::= {er1646v2VEthVlanEntry 131080192}

er1646v2VEthVlanInbBwDeFlagViolate OBJECT-TYPE
   SYNTAX      INTEGER
               {
               allowed (1),
               notAllowed (2)
               }
   MAX-ACCESS  read-write
   STATUS      current
   DESCRIPTION
      "Path: virtualEthernet.editConf.vlan.inboundBandwidth.deFlag.violate

       Possibilities:
               allowed   (1)
               notAllowed   (2)"
   ::= {er1646v2VEthVlanEntry 131084288}

er1646v2VEthVlanInbBwActCirActNone OBJECT-TYPE
   SYNTAX      OCTET STRING
   MAX-ACCESS  read-write
   STATUS      current
   DESCRIPTION
      "Path: virtualEthernet.editConf.vlan.inboundBandwidth.action.cirAction.none"
   ::= {er1646v2VEthVlanEntry 133308416}

er1646v2VEthVlanInbBwActCirActEthCos1 OBJECT-TYPE
   SYNTAX      INTEGER
               {
               unchanged (256)
               }
   MAX-ACCESS  read-write
   STATUS      current
   DESCRIPTION
      "Path: virtualEthernet.editConf.vlan.inboundBandwidth.action.cirAction.ethernet.cosDepth1

       Possibilities:
               unchanged   (256)"
   ::= {er1646v2VEthVlanEntry 133316864}

er1646v2VEthVlanInbBwActCirActEthDei1 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth1

       Possibilities:
               unchanged   (255)
               clear   (0)
               set   (1)"
   ::= {er1646v2VEthVlanEntry 133321984}

er1646v2VEthVlanInbBwActCirActEthCos2 OBJECT-TYPE
   SYNTAX      INTEGER
               {
               unchanged (256)
               }
   MAX-ACCESS  read-write
   STATUS      current
   DESCRIPTION
      "Path: virtualEthernet.editConf.vlan.inboundBandwidth.action.cirAction.ethernet.cosDepth2

       Possibilities:
               unchanged   (256)"
   ::= {er1646v2VEthVlanEntry 133317120}

er1646v2VEthVlanInbBwActCirActEthDei2 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth2

       Possibilities:
               unchanged   (255)
               clear   (0)
               set   (1)"
   ::= {er1646v2VEthVlanEntry 133322240}

er1646v2VEthVlanInbBwActCirActEthCos3 OBJECT-TYPE
   SYNTAX      INTEGER
               {
               unchanged (256)
               }
   MAX-ACCESS  read-write
   STATUS      current
   DESCRIPTION
      "Path: virtualEthernet.editConf.vlan.inboundBandwidth.action.cirAction.ethernet.cosDepth3

       Possibilities:
               unchanged   (256)"
   ::= {er1646v2VEthVlanEntry 133317376}

er1646v2VEthVlanInbBwActCirActEthDei3 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth3

       Possibilities:
               unchanged   (255)
               clear   (0)
               set   (1)"
   ::= {er1646v2VEthVlanEntry 133322496}

er1646v2VEthVlanInbBwActCirActEthCos4 OBJECT-TYPE
   SYNTAX      INTEGER
               {
               unchanged (256)
               }
   MAX-ACCESS  read-write
   STATUS      current
   DESCRIPTION
      "Path: virtualEthernet.editConf.vlan.inboundBandwidth.action.cirAction.ethernet.cosDepth4

       Possibilities:
               unchanged   (256)"
   ::= {er1646v2VEthVlanEntry 133317632}

er1646v2VEthVlanInbBwActCirActEthDei4 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth4

       Possibilities:
               unchanged   (255)
               clear   (0)
               set   (1)"
   ::= {er1646v2VEthVlanEntry 133322752}

er1646v2VEthVlanInbBwActCirActEthCos5 OBJECT-TYPE
   SYNTAX      INTEGER
               {
               unchanged (256)
               }
   MAX-ACCESS  read-write
   STATUS      current
   DESCRIPTION
      "Path: virtualEthernet.editConf.vlan.inboundBandwidth.action.cirAction.ethernet.cosDepth5

       Possibilities:
               unchanged   (256)"
   ::= {er1646v2VEthVlanEntry 133317888}

er1646v2VEthVlanInbBwActCirActEthDei5 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth5

       Possibilities:
               unchanged   (255)
               clear   (0)
               set   (1)"
   ::= {er1646v2VEthVlanEntry 133323008}

er1646v2VEthVlanInbBwActCirActEthCos6 OBJECT-TYPE
   SYNTAX      INTEGER
               {
               unchanged (256)
               }
   MAX-ACCESS  read-write
   STATUS      current
   DESCRIPTION
      "Path: virtualEthernet.editConf.vlan.inboundBandwidth.action.cirAction.ethernet.cosDepth6

       Possibilities:
               unchanged   (256)"
   ::= {er1646v2VEthVlanEntry 133318144}

er1646v2VEthVlanInbBwActCirActEthDei6 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth6

       Possibilities:
               unchanged   (255)
               clear   (0)
               set   (1)"
   ::= {er1646v2VEthVlanEntry 133323264}

er1646v2VEthVlanInbBwActCirActEthCos7 OBJECT-TYPE
   SYNTAX      INTEGER
               {
               unchanged (256)
               }
   MAX-ACCESS  read-write
   STATUS      current
   DESCRIPTION
      "Path: virtualEthernet.editConf.vlan.inboundBandwidth.action.cirAction.ethernet.cosDepth7

       Possibilities:
               unchanged   (256)"
   ::= {er1646v2VEthVlanEntry 133318400}

er1646v2VEthVlanInbBwActCirActEthDei7 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth7

       Possibilities:
               unchanged   (255)
               clear   (0)
               set   (1)"
   ::= {er1646v2VEthVlanEntry 133323520}

er1646v2VEthVlanInbBwActCirActEthCos8 OBJECT-TYPE
   SYNTAX      INTEGER
               {
               unchanged (256)
               }
   MAX-ACCESS  read-write
   STATUS      current
   DESCRIPTION
      "Path: virtualEthernet.editConf.vlan.inboundBandwidth.action.cirAction.ethernet.cosDepth8

       Possibilities:
               unchanged   (256)"
   ::= {er1646v2VEthVlanEntry 133318656}

er1646v2VEthVlanInbBwActCirActEthDei8 OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deiDepth8

       Possibilities:
               unchanged   (255)
               clear   (0)
               set   (1)"
   ::= {er1646v2VEthVlanEntry 133323776}

er1646v2VEthVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 133318912}

er1646v2VEthVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 133319168}

er1646v2VEthVlanInbBwActCirActEthDrpLev OBJECT-TYPE
   SYNTAX      INTEGER
               {
               unchanged (0)
               }
   MAX-ACCESS  read-write
   STATUS      current
   DESCRIPTION
      "Path: virtualEthernet.editConf.vlan.inboundBandwidth.action.cirAction.ethernet.dropLevel

       Possibilities:
               unchanged   (0)"
   ::= {er1646v2VEthVlanEntry 133319424}

er1646v2VEthVlanInbBwActCirActEthDeFlag OBJECT-TYPE
   SYNTAX      INTEGER
               {
               unchanged (255),
               clear (0),
               set (1)
               }
   MAX-ACCESS  read-write
   STATUS      current
   DESCRIPTION
      "Path: virtualEthernet.editConf.vlan.inboundBandwidth.action.cirAction.ethernet.deFlag

       Possibilities:
               unchanged   (255)
               clear   (0)
               set   (1)"
   ::= {er1646v2VEthVlanEntry 133320192}

er1646v2VEthVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 133343488}

er1646v2VEthVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 133343744}

er1646v2VEthVlanInbBwActCirActIpDrpLev OBJECT-TYPE
   SYNTAX      INTEGER
               {
               unchanged (0)
               }
   MAX-ACCESS  read-write
   STATUS      current
   DESCRIPTION
      "Path: virtualEthernet.editConf.vlan.inboundBandwidth.action.cirAction.ip.dropLevel

       Possibilities:
               unchanged   (0)"
   ::= {er1646v2VEthVlanEntry 133344000}

er1646v2VEthVlanInbBwActCirActIpDeFlag OBJECT-TYPE
   SYNTAX      INTEGER
               {
               unchanged (255),
               clear (0),
               set (1)
               }
   MAX-ACCESS  read-write
   STATUS      current
   DESCRIPTION
      "Path: virtualEthernet.editConf.vlan.inboundBandwidth.action.cirAction.ip.deFlag

       Possibilities:
               unchanged   (255)
               clear   (0)
               set   (1)"
   ::= {er1646v2VEthVlanEntry 133344768}

er1646v2VEthVlanInbBwActEirActNone OBJECT-TYPE
   SYNTAX      OCTET STRING
   MAX-ACCESS  read-write
   STATUS      current
   DESCRIPTION
      "Path: virtualEthernet.editConf.vlan.inboundBandwidth.action.eirAction.none"
   ::= {er1646v2VEthVlanEntry 133439488}

er1646v2VEthVlanInbBwActEirActEthCos1 OBJECT-TYPE
   SYNTAX      INTEGER
               {
               unchanged (256)
               }
   MAX-ACCESS  read-write
   STATUS      current
   DESCRIPTION
      "Path: virtualEthernet.editConf.vlan.inboundBandwidth.action.eirAction.ethernet.cosDepth1

       Possibilities:
               unchanged   (256)"
   ::= {er1646v2VEthVlanEntry 133447936}

er1646v2VEthVlanInbBwActEirActEthDei1 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth1

       Possibilities:
               unchanged   (255)
               clear   (0)
               set   (1)"
   ::= {er1646v2VEthVlanEntry 133453056}

er1646v2VEthVlanInbBwActEirActEthCos2 OBJECT-TYPE
   SYNTAX      INTEGER
               {
               unchanged (256)
               }
   MAX-ACCESS  read-write
   STATUS      current
   DESCRIPTION
      "Path: virtualEthernet.editConf.vlan.inboundBandwidth.action.eirAction.ethernet.cosDepth2

       Possibilities:
               unchanged   (256)"
   ::= {er1646v2VEthVlanEntry 133448192}

er1646v2VEthVlanInbBwActEirActEthDei2 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth2

       Possibilities:
               unchanged   (255)
               clear   (0)
               set   (1)"
   ::= {er1646v2VEthVlanEntry 133453312}

er1646v2VEthVlanInbBwActEirActEthCos3 OBJECT-TYPE
   SYNTAX      INTEGER
               {
               unchanged (256)
               }
   MAX-ACCESS  read-write
   STATUS      current
   DESCRIPTION
      "Path: virtualEthernet.editConf.vlan.inboundBandwidth.action.eirAction.ethernet.cosDepth3

       Possibilities:
               unchanged   (256)"
   ::= {er1646v2VEthVlanEntry 133448448}

er1646v2VEthVlanInbBwActEirActEthDei3 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth3

       Possibilities:
               unchanged   (255)
               clear   (0)
               set   (1)"
   ::= {er1646v2VEthVlanEntry 133453568}

er1646v2VEthVlanInbBwActEirActEthCos4 OBJECT-TYPE
   SYNTAX      INTEGER
               {
               unchanged (256)
               }
   MAX-ACCESS  read-write
   STATUS      current
   DESCRIPTION
      "Path: virtualEthernet.editConf.vlan.inboundBandwidth.action.eirAction.ethernet.cosDepth4

       Possibilities:
               unchanged   (256)"
   ::= {er1646v2VEthVlanEntry 133448704}

er1646v2VEthVlanInbBwActEirActEthDei4 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth4

       Possibilities:
               unchanged   (255)
               clear   (0)
               set   (1)"
   ::= {er1646v2VEthVlanEntry 133453824}

er1646v2VEthVlanInbBwActEirActEthCos5 OBJECT-TYPE
   SYNTAX      INTEGER
               {
               unchanged (256)
               }
   MAX-ACCESS  read-write
   STATUS      current
   DESCRIPTION
      "Path: virtualEthernet.editConf.vlan.inboundBandwidth.action.eirAction.ethernet.cosDepth5

       Possibilities:
               unchanged   (256)"
   ::= {er1646v2VEthVlanEntry 133448960}

er1646v2VEthVlanInbBwActEirActEthDei5 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth5

       Possibilities:
               unchanged   (255)
               clear   (0)
               set   (1)"
   ::= {er1646v2VEthVlanEntry 133454080}

er1646v2VEthVlanInbBwActEirActEthCos6 OBJECT-TYPE
   SYNTAX      INTEGER
               {
               unchanged (256)
               }
   MAX-ACCESS  read-write
   STATUS      current
   DESCRIPTION
      "Path: virtualEthernet.editConf.vlan.inboundBandwidth.action.eirAction.ethernet.cosDepth6

       Possibilities:
               unchanged   (256)"
   ::= {er1646v2VEthVlanEntry 133449216}

er1646v2VEthVlanInbBwActEirActEthDei6 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth6

       Possibilities:
               unchanged   (255)
               clear   (0)
               set   (1)"
   ::= {er1646v2VEthVlanEntry 133454336}

er1646v2VEthVlanInbBwActEirActEthCos7 OBJECT-TYPE
   SYNTAX      INTEGER
               {
               unchanged (256)
               }
   MAX-ACCESS  read-write
   STATUS      current
   DESCRIPTION
      "Path: virtualEthernet.editConf.vlan.inboundBandwidth.action.eirAction.ethernet.cosDepth7

       Possibilities:
               unchanged   (256)"
   ::= {er1646v2VEthVlanEntry 133449472}

er1646v2VEthVlanInbBwActEirActEthDei7 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth7

       Possibilities:
               unchanged   (255)
               clear   (0)
               set   (1)"
   ::= {er1646v2VEthVlanEntry 133454592}

er1646v2VEthVlanInbBwActEirActEthCos8 OBJECT-TYPE
   SYNTAX      INTEGER
               {
               unchanged (256)
               }
   MAX-ACCESS  read-write
   STATUS      current
   DESCRIPTION
      "Path: virtualEthernet.editConf.vlan.inboundBandwidth.action.eirAction.ethernet.cosDepth8

       Possibilities:
               unchanged   (256)"
   ::= {er1646v2VEthVlanEntry 133449728}

er1646v2VEthVlanInbBwActEirActEthDei8 OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deiDepth8

       Possibilities:
               unchanged   (255)
               clear   (0)
               set   (1)"
   ::= {er1646v2VEthVlanEntry 133454848}

er1646v2VEthVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 133449984}

er1646v2VEthVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 133450240}

er1646v2VEthVlanInbBwActEirActEthDrpLev OBJECT-TYPE
   SYNTAX      INTEGER
               {
               unchanged (0)
               }
   MAX-ACCESS  read-write
   STATUS      current
   DESCRIPTION
      "Path: virtualEthernet.editConf.vlan.inboundBandwidth.action.eirAction.ethernet.dropLevel

       Possibilities:
               unchanged   (0)"
   ::= {er1646v2VEthVlanEntry 133450496}

er1646v2VEthVlanInbBwActEirActEthDeFlag OBJECT-TYPE
   SYNTAX      INTEGER
               {
               unchanged (255),
               clear (0),
               set (1)
               }
   MAX-ACCESS  read-write
   STATUS      current
   DESCRIPTION
      "Path: virtualEthernet.editConf.vlan.inboundBandwidth.action.eirAction.ethernet.deFlag

       Possibilities:
               unchanged   (255)
               clear   (0)
               set   (1)"
   ::= {er1646v2VEthVlanEntry 133451264}

er1646v2VEthVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 133474560}

er1646v2VEthVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 133474816}

er1646v2VEthVlanInbBwActEirActIpDrpLev OBJECT-TYPE
   SYNTAX      INTEGER
               {
               unchanged (0)
               }
   MAX-ACCESS  read-write
   STATUS      current
   DESCRIPTION
      "Path: virtualEthernet.editConf.vlan.inboundBandwidth.action.eirAction.ip.dropLevel

       Possibilities:
               unchanged   (0)"
   ::= {er1646v2VEthVlanEntry 133475072}

er1646v2VEthVlanInbBwActEirActIpDeFlag OBJECT-TYPE
   SYNTAX      INTEGER
               {
               unchanged (255),
               clear (0),
               set (1)
               }
   MAX-ACCESS  read-write
   STATUS      current
   DESCRIPTION
      "Path: virtualEthernet.editConf.vlan.inboundBandwidth.action.eirAction.ip.deFlag

       Possibilities:
               unchanged   (255)
               clear   (0)
               set   (1)"
   ::= {er1646v2VEthVlanEntry 133475840}

er1646v2VEthVlanInbBwActViolActNone OBJECT-TYPE
   SYNTAX      OCTET STRING
   MAX-ACCESS  read-write
   STATUS      current
   DESCRIPTION
      "Path: virtualEthernet.editConf.vlan.inboundBandwidth.action.violateAction.none"
   ::= {er1646v2VEthVlanEntry 133570560}

er1646v2VEthVlanInbBwActViolActDrop OBJECT-TYPE
   SYNTAX      OCTET STRING
   MAX-ACCESS  read-write
   STATUS      current
   DESCRIPTION
      "Path: virtualEthernet.editConf.vlan.inboundBandwidth.action.violateAction.drop"
   ::= {er1646v2VEthVlanEntry 133586944}

er1646v2VEthVlanInbBwActViolActEthCos1 OBJECT-TYPE
   SYNTAX      INTEGER
               {
               unchanged (256)
               }
   MAX-ACCESS  read-write
   STATUS      current
   DESCRIPTION
      "Path: virtualEthernet.editConf.vlan.inboundBandwidth.action.violateAction.ethernet.cosDepth1

       Possibilities:
               unchanged   (256)"
   ::= {er1646v2VEthVlanEntry 133579008}

er1646v2VEthVlanInbBwActViolActEthDei1 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth1

       Possibilities:
               unchanged   (255)
               clear   (0)
               set   (1)"
   ::= {er1646v2VEthVlanEntry 133584128}

er1646v2VEthVlanInbBwActViolActEthCos2 OBJECT-TYPE
   SYNTAX      INTEGER
               {
               unchanged (256)
               }
   MAX-ACCESS  read-write
   STATUS      current
   DESCRIPTION
      "Path: virtualEthernet.editConf.vlan.inboundBandwidth.action.violateAction.ethernet.cosDepth2

       Possibilities:
               unchanged   (256)"
   ::= {er1646v2VEthVlanEntry 133579264}

er1646v2VEthVlanInbBwActViolActEthDei2 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth2

       Possibilities:
               unchanged   (255)
               clear   (0)
               set   (1)"
   ::= {er1646v2VEthVlanEntry 133584384}

er1646v2VEthVlanInbBwActViolActEthCos3 OBJECT-TYPE
   SYNTAX      INTEGER
               {
               unchanged (256)
               }
   MAX-ACCESS  read-write
   STATUS      current
   DESCRIPTION
      "Path: virtualEthernet.editConf.vlan.inboundBandwidth.action.violateAction.ethernet.cosDepth3

       Possibilities:
               unchanged   (256)"
   ::= {er1646v2VEthVlanEntry 133579520}

er1646v2VEthVlanInbBwActViolActEthDei3 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth3

       Possibilities:
               unchanged   (255)
               clear   (0)
               set   (1)"
   ::= {er1646v2VEthVlanEntry 133584640}

er1646v2VEthVlanInbBwActViolActEthCos4 OBJECT-TYPE
   SYNTAX      INTEGER
               {
               unchanged (256)
               }
   MAX-ACCESS  read-write
   STATUS      current
   DESCRIPTION
      "Path: virtualEthernet.editConf.vlan.inboundBandwidth.action.violateAction.ethernet.cosDepth4

       Possibilities:
               unchanged   (256)"
   ::= {er1646v2VEthVlanEntry 133579776}

er1646v2VEthVlanInbBwActViolActEthDei4 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth4

       Possibilities:
               unchanged   (255)
               clear   (0)
               set   (1)"
   ::= {er1646v2VEthVlanEntry 133584896}

er1646v2VEthVlanInbBwActViolActEthCos5 OBJECT-TYPE
   SYNTAX      INTEGER
               {
               unchanged (256)
               }
   MAX-ACCESS  read-write
   STATUS      current
   DESCRIPTION
      "Path: virtualEthernet.editConf.vlan.inboundBandwidth.action.violateAction.ethernet.cosDepth5

       Possibilities:
               unchanged   (256)"
   ::= {er1646v2VEthVlanEntry 133580032}

er1646v2VEthVlanInbBwActViolActEthDei5 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth5

       Possibilities:
               unchanged   (255)
               clear   (0)
               set   (1)"
   ::= {er1646v2VEthVlanEntry 133585152}

er1646v2VEthVlanInbBwActViolActEthCos6 OBJECT-TYPE
   SYNTAX      INTEGER
               {
               unchanged (256)
               }
   MAX-ACCESS  read-write
   STATUS      current
   DESCRIPTION
      "Path: virtualEthernet.editConf.vlan.inboundBandwidth.action.violateAction.ethernet.cosDepth6

       Possibilities:
               unchanged   (256)"
   ::= {er1646v2VEthVlanEntry 133580288}

er1646v2VEthVlanInbBwActViolActEthDei6 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth6

       Possibilities:
               unchanged   (255)
               clear   (0)
               set   (1)"
   ::= {er1646v2VEthVlanEntry 133585408}

er1646v2VEthVlanInbBwActViolActEthCos7 OBJECT-TYPE
   SYNTAX      INTEGER
               {
               unchanged (256)
               }
   MAX-ACCESS  read-write
   STATUS      current
   DESCRIPTION
      "Path: virtualEthernet.editConf.vlan.inboundBandwidth.action.violateAction.ethernet.cosDepth7

       Possibilities:
               unchanged   (256)"
   ::= {er1646v2VEthVlanEntry 133580544}

er1646v2VEthVlanInbBwActViolActEthDei7 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth7

       Possibilities:
               unchanged   (255)
               clear   (0)
               set   (1)"
   ::= {er1646v2VEthVlanEntry 133585664}

er1646v2VEthVlanInbBwActViolActEthCos8 OBJECT-TYPE
   SYNTAX      INTEGER
               {
               unchanged (256)
               }
   MAX-ACCESS  read-write
   STATUS      current
   DESCRIPTION
      "Path: virtualEthernet.editConf.vlan.inboundBandwidth.action.violateAction.ethernet.cosDepth8

       Possibilities:
               unchanged   (256)"
   ::= {er1646v2VEthVlanEntry 133580800}

er1646v2VEthVlanInbBwActViolActEthDei8 OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deiDepth8

       Possibilities:
               unchanged   (255)
               clear   (0)
               set   (1)"
   ::= {er1646v2VEthVlanEntry 133585920}

er1646v2VEthVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 133581056}

er1646v2VEthVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 133581312}

er1646v2VEthVlanInbBwActViolActEthDrpLev OBJECT-TYPE
   SYNTAX      INTEGER
               {
               unchanged (0)
               }
   MAX-ACCESS  read-write
   STATUS      current
   DESCRIPTION
      "Path: virtualEthernet.editConf.vlan.inboundBandwidth.action.violateAction.ethernet.dropLevel

       Possibilities:
               unchanged   (0)"
   ::= {er1646v2VEthVlanEntry 133581568}

er1646v2VEthVlanInbBwActViolActEthDeFlag OBJECT-TYPE
   SYNTAX      INTEGER
               {
               unchanged (255),
               clear (0),
               set (1)
               }
   MAX-ACCESS  read-write
   STATUS      current
   DESCRIPTION
      "Path: virtualEthernet.editConf.vlan.inboundBandwidth.action.violateAction.ethernet.deFlag

       Possibilities:
               unchanged   (255)
               clear   (0)
               set   (1)"
   ::= {er1646v2VEthVlanEntry 133582336}

er1646v2VEthVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanEntry 133605632}

er1646v2VEthVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanEntry 133605888}

er1646v2VEthVlanInbBwActViolActIpDrpLev OBJECT-TYPE
   SYNTAX      INTEGER
               {
               unchanged (0)
               }
   MAX-ACCESS  read-write
   STATUS      current
   DESCRIPTION
      "Path: virtualEthernet.editConf.vlan.inboundBandwidth.action.violateAction.ip.dropLevel

       Possibilities:
               unchanged   (0)"
   ::= {er1646v2VEthVlanEntry 133606144}

er1646v2VEthVlanInbBwActViolActIpDeFlag OBJECT-TYPE
   SYNTAX      INTEGER
               {
               unchanged (255),
               clear (0),
               set (1)
               }
   MAX-ACCESS  read-write
   STATUS      current
   DESCRIPTION
      "Path: virtualEthernet.editConf.vlan.inboundBandwidth.action.violateAction.ip.deFlag

       Possibilities:
               unchanged   (255)
               clear   (0)
               set   (1)"
   ::= {er1646v2VEthVlanEntry 133606912}

er1646v2VEthVlanPppoE OBJECT-TYPE
   SYNTAX      INTEGER
               {
               disabled (0),
               enabled (1)
               }
   MAX-ACCESS  read-write
   STATUS      current
   DESCRIPTION
      "Path: virtualEthernet.editConf.vlan.pppoE

       Possibilities:
               disabled   (0)
               enabled   (1)"
   ::= {er1646v2VEthVlanEntry 838860800}

er1646v2VEthVlanPppLnkMOperation OBJECT-TYPE
   SYNTAX      INTEGER
               {
               disabled (0),
               enabled (1)
               }
   MAX-ACCESS  read-write
   STATUS      current
   DESCRIPTION
      "Path: virtualEthernet.editConf.vlan.ppp.linkMonitoring.operation

       Possibilities:
               disabled   (0)
               enabled   (1)"
   ::= {er1646v2VEthVlanEntry 251724032}

er1646v2VEthVlanPppLnkMInterval OBJECT-TYPE
   SYNTAX      TimeTicks
   MAX-ACCESS  read-write
   STATUS      current
   DESCRIPTION
      "Path: virtualEthernet.editConf.vlan.ppp.linkMonitoring.interval

       Time in centi-second."
   ::= {er1646v2VEthVlanEntry 251724288}

er1646v2VEthVlanPppLnkMRepTimeOut OBJECT-TYPE
   SYNTAX      TimeTicks
   MAX-ACCESS  read-write
   STATUS      current
   DESCRIPTION
      "Path: virtualEthernet.editConf.vlan.ppp.linkMonitoring.replyTimeOut

       Time in centi-second."
   ::= {er1646v2VEthVlanEntry 251724544}

er1646v2VEthVlanPppLnkMFailsPrmt OBJECT-TYPE
   SYNTAX      Integer32
   MAX-ACCESS  read-write
   STATUS      current
   DESCRIPTION
      "Path: virtualEthernet.editConf.vlan.ppp.linkMonitoring.failsPermitted"
   ::= {er1646v2VEthVlanEntry 251724800}

er1646v2VEthVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: virtualEthernet.editConf.vlan.ppp.authentication

       Possibilities:
               disabled   (0)
               chap   (1)
               pap   (2)
               chapOrPap   (3)
               msChap   (4)
               msChapV2   (5)"
   ::= {er1646v2VEthVlanEntry 251789312}

er1646v2VEthVlanPppAuthenPeriod OBJECT-TYPE
   SYNTAX      TimeTicks
   MAX-ACCESS  read-write
   STATUS      current
   DESCRIPTION
      "Path: virtualEthernet.editConf.vlan.ppp.authenPeriod

       Time in centi-second."
   ::= {er1646v2VEthVlanEntry 251854848}

er1646v2VEthVlanPppSessionName OBJECT-TYPE
   SYNTAX      DisplayString
   MAX-ACCESS  read-write
   STATUS      current
   DESCRIPTION
      "Path: virtualEthernet.editConf.vlan.ppp.sessionName"
   ::= {er1646v2VEthVlanEntry 251985920}

er1646v2VEthVlanPppSessionSecret OBJECT-TYPE
   SYNTAX      DisplayString
   MAX-ACCESS  read-write
   STATUS      current
   DESCRIPTION
      "Path: virtualEthernet.editConf.vlan.ppp.sessionSecret"
   ::= {er1646v2VEthVlanEntry 252051456}

er1646v2VEthVlanPppEncModeSessionSecret OBJECT-TYPE
   SYNTAX      INTEGER
               {
               none (1),
               encrypt (2),
               encType1 (3),
               invalid (128)
               }
   MAX-ACCESS  read-write
   STATUS      current
   DESCRIPTION
      "Path: virtualEthernet.editConf.vlan.ppp.encModeSessionSecret

       Possibilities:
               none   (1)
               encrypt   (2)
               encType1   (3)
               invalid   (128)"
   ::= {er1646v2VEthVlanEntry 252182528}

er1646v2VEthVlanPppEncSessionSecret OBJECT-TYPE
   SYNTAX      DisplayString
   MAX-ACCESS  read-write
   STATUS      current
   DESCRIPTION
      "Path: virtualEthernet.editConf.vlan.ppp.encSessionSecret"
   ::= {er1646v2VEthVlanEntry 252248064}

er1646v2VEthVlanPppServiceName OBJECT-TYPE
   SYNTAX      DisplayString
   MAX-ACCESS  read-write
   STATUS      current
   DESCRIPTION
      "Path: virtualEthernet.editConf.vlan.ppp.serviceName"
   ::= {er1646v2VEthVlanEntry 252116992}

er1646v2VEthVlanPbbMode OBJECT-TYPE
   SYNTAX      INTEGER
               {
               disabled (0),
               static (1),
               dynamicPtp (2),
               dynamicPtmp (3)
               }
   MAX-ACCESS  read-write
   STATUS      current
   DESCRIPTION
      "Path: virtualEthernet.editConf.vlan.pbb.mode

       Possibilities:
               disabled   (0)
               static   (1)
               dynamicPtp   (2)
               dynamicPtmp   (3)"
   ::= {er1646v2VEthVlanEntry 1174667264}

er1646v2VEthVlanPbbTxCos OBJECT-TYPE
   SYNTAX      Integer32
   MAX-ACCESS  read-write
   STATUS      current
   DESCRIPTION
      "Path: virtualEthernet.editConf.vlan.pbb.txCos"
   ::= {er1646v2VEthVlanEntry 1175191552}

er1646v2VEthVlanPbbIsid OBJECT-TYPE
   SYNTAX      Integer32
   MAX-ACCESS  read-write
   STATUS      current
   DESCRIPTION
      "Path: virtualEthernet.editConf.vlan.pbb.isid"
   ::= {er1646v2VEthVlanEntry 1175453696}

er1646v2VEthVlanPbbDestMac OBJECT-TYPE
   SYNTAX      OCTET STRING
   MAX-ACCESS  read-write
   STATUS      current
   DESCRIPTION
      "Path: virtualEthernet.editConf.vlan.pbb.destMac

       MAC address."
   ::= {er1646v2VEthVlanEntry 1175715840}

er1646v2VEthVlanPbbCustomGroupMac OBJECT-TYPE
   SYNTAX      OCTET STRING
   MAX-ACCESS  read-write
   STATUS      current
   DESCRIPTION
      "Path: virtualEthernet.editConf.vlan.pbb.customGroupMac

       MAC address."
   ::= {er1646v2VEthVlanEntry 1175977984}

er1646v2VEthVlanIpSaddr OBJECT-TYPE
   SYNTAX      SEQUENCE OF Er1646v2VEthVlanIpSaddrEntry
   MAX-ACCESS  not-accessible
   STATUS      current
   DESCRIPTION
      ""
   ::= {er1646v2VEthVlan 51838976}

er1646v2VEthVlanIpSaddrEntry OBJECT-TYPE
   SYNTAX      Er1646v2VEthVlanIpSaddrEntry
   MAX-ACCESS  not-accessible
   STATUS      current
   DESCRIPTION
      ""
   INDEX      { er1646v2VEthVlanIpSaddrGlobalIx,
                er1646v2VEthVlanTableIx,
                er1646v2VEthVlanIpSaddrTableIx }
   ::= {er1646v2VEthVlanIpSaddr 1}

Er1646v2VEthVlanIpSaddrEntry ::=
   SEQUENCE
      {
      er1646v2VEthVlanIpSaddrActions
         VariableLengthTableActions,
      er1646v2VEthVlanIpSaddrGlobalIx
         GlobalIndex,
      er1646v2VEthVlanIpSaddrTableIx
         TableIndex,
      er1646v2VEthVlanIpSaddrAddress
         IpAddress,
      er1646v2VEthVlanIpSaddrNetMask
         IpAddress
      }

er1646v2VEthVlanIpSaddrActions OBJECT-TYPE
   SYNTAX      VariableLengthTableActions
   MAX-ACCESS  read-write
   STATUS      current
   DESCRIPTION
      "By way of this field, some manipulations
       on this table may be performed."
   ::= {er1646v2VEthVlanIpSaddrEntry 2}

er1646v2VEthVlanIpSaddrGlobalIx OBJECT-TYPE
   SYNTAX      GlobalIndex
   MAX-ACCESS  not-accessible
   STATUS      current
   DESCRIPTION
      "The value of the tlsCntTreeGlobalIndex of the MANAGED OBJECT."
   ::= {er1646v2VEthVlanIpSaddrEntry 10}

er1646v2VEthVlanIpSaddrTableIx OBJECT-TYPE
   SYNTAX      TableIndex
   MAX-ACCESS  not-accessible
   STATUS      current
   DESCRIPTION
      ""
   ::= {er1646v2VEthVlanIpSaddrEntry 11}

er1646v2VEthVlanIpSaddrAddress OBJECT-TYPE
   SYNTAX      IpAddress
   MAX-ACCESS  read-write
   STATUS      current
   DESCRIPTION
      "Path: virtualEthernet.editConf.vlan.ip.secondaryIp.address"
   ::= {er1646v2VEthVlanIpSaddrEntry 2030043136}

er1646v2VEthVlanIpSaddrNetMask OBJECT-TYPE
   SYNTAX      IpAddress
   MAX-ACCESS  read-write
   STATUS      current
   DESCRIPTION
      "Path: virtualEthernet.editConf.vlan.ip.secondaryIp.netMask"
   ::= {er1646v2VEthVlanIpSaddrEntry 2063597568}

er1646v2VEthVlanIpH OBJECT-TYPE
   SYNTAX      SEQUENCE OF Er1646v2VEthVlanIpHEntry
   MAX-ACCESS  not-accessible
   STATUS      current
   DESCRIPTION
      ""
   ::= {er1646v2VEthVlan 51314688}

er1646v2VEthVlanIpHEntry OBJECT-TYPE
   SYNTAX      Er1646v2VEthVlanIpHEntry
   MAX-ACCESS  not-accessible
   STATUS      current
   DESCRIPTION
      ""
   INDEX      { er1646v2VEthVlanIpHGlobalIx,
                er1646v2VEthVlanTableIx,
                er1646v2VEthVlanIpHTableIx }
   ::= {er1646v2VEthVlanIpH 1}

Er1646v2VEthVlanIpHEntry ::=
   SEQUENCE
      {
      er1646v2VEthVlanIpHActions
         VariableLengthTableActions,
      er1646v2VEthVlanIpHGlobalIx
         GlobalIndex,
      er1646v2VEthVlanIpHTableIx
         TableIndex,
      er1646v2VEthVlanIpHAddress
         IpAddress,
      er1646v2VEthVlanIpHDhcpRelayOptionSubscriberId
         DisplayString
      }

er1646v2VEthVlanIpHActions OBJECT-TYPE
   SYNTAX      VariableLengthTableActions
   MAX-ACCESS  read-write
   STATUS      current
   DESCRIPTION
      "By way of this field, some manipulations
       on this table may be performed."
   ::= {er1646v2VEthVlanIpHEntry 2}

er1646v2VEthVlanIpHGlobalIx OBJECT-TYPE
   SYNTAX      GlobalIndex
   MAX-ACCESS  not-accessible
   STATUS      current
   DESCRIPTION
      "The value of the tlsCntTreeGlobalIndex of the MANAGED OBJECT."
   ::= {er1646v2VEthVlanIpHEntry 10}

er1646v2VEthVlanIpHTableIx OBJECT-TYPE
   SYNTAX      TableIndex
   MAX-ACCESS  not-accessible
   STATUS      current
   DESCRIPTION
      ""
   ::= {er1646v2VEthVlanIpHEntry 11}

er1646v2VEthVlanIpHAddress OBJECT-TYPE
   SYNTAX      IpAddress
   MAX-ACCESS  read-write
   STATUS      current
   DESCRIPTION
      "Path: virtualEthernet.editConf.vlan.ip.helpers.address"
   ::= {er1646v2VEthVlanIpHEntry 16777216}

er1646v2VEthVlanIpHDhcpRelayOptionSubscriberId OBJECT-TYPE
   SYNTAX      DisplayString
   MAX-ACCESS  read-write
   STATUS      current
   DESCRIPTION
      "Path: virtualEthernet.editConf.vlan.ip.helpers.dhcpRelayOption.subscriberId"
   ::= {er1646v2VEthVlanIpHEntry 33947648}

er1646v2VEthVlanIpV6Addresses OBJECT-TYPE
   SYNTAX      SEQUENCE OF Er1646v2VEthVlanIpV6AddressesEntry
   MAX-ACCESS  not-accessible
   STATUS      current
   DESCRIPTION
      ""
   ::= {er1646v2VEthVlan 704839680}

er1646v2VEthVlanIpV6AddressesEntry OBJECT-TYPE
   SYNTAX      Er1646v2VEthVlanIpV6AddressesEntry
   MAX-ACCESS  not-accessible
   STATUS      current
   DESCRIPTION
      ""
   INDEX      { er1646v2VEthVlanIpV6AddressesGlobalIx,
                er1646v2VEthVlanTableIx,
                er1646v2VEthVlanIpV6AddressesTableIx }
   ::= {er1646v2VEthVlanIpV6Addresses 1}

Er1646v2VEthVlanIpV6AddressesEntry ::=
   SEQUENCE
      {
      er1646v2VEthVlanIpV6AddressesActions
         VariableLengthTableActions,
      er1646v2VEthVlanIpV6AddressesGlobalIx
         GlobalIndex,
      er1646v2VEthVlanIpV6AddressesTableIx
         TableIndex,
      er1646v2VEthVlanIpV6AddressesType
         INTEGER,
      er1646v2VEthVlanIpV6AddressesAddress
         Ipv6Address,
      er1646v2VEthVlanIpV6AddressesPrefixLength
         Integer32,
      er1646v2VEthVlanIpV6AddressesGeneralPrefix
         DisplayString,
      er1646v2VEthVlanIpV6AddressesRaSend
         INTEGER,
      er1646v2VEthVlanIpV6AddressesRaOnLinkFlag
         INTEGER,
      er1646v2VEthVlanIpV6AddressesRaAutoFlag
         INTEGER,
      er1646v2VEthVlanIpV6AddressesRaValidLifeTime
         TimeTicks,
      er1646v2VEthVlanIpV6AddressesRaValidLTMode
         INTEGER,
      er1646v2VEthVlanIpV6AddressesRaPrefLifeTime
         TimeTicks,
      er1646v2VEthVlanIpV6AddressesRaPrefLTMode
         INTEGER
      }

er1646v2VEthVlanIpV6AddressesActions OBJECT-TYPE
   SYNTAX      VariableLengthTableActions
   MAX-ACCESS  read-write
   STATUS      current
   DESCRIPTION
      "By way of this field, some manipulations
       on this table may be performed."
   ::= {er1646v2VEthVlanIpV6AddressesEntry 2}

er1646v2VEthVlanIpV6AddressesGlobalIx OBJECT-TYPE
   SYNTAX      GlobalIndex
   MAX-ACCESS  not-accessible
   STATUS      current
   DESCRIPTION
      "The value of the tlsCntTreeGlobalIndex of the MANAGED OBJECT."
   ::= {er1646v2VEthVlanIpV6AddressesEntry 10}

er1646v2VEthVlanIpV6AddressesTableIx OBJECT-TYPE
   SYNTAX      TableIndex
   MAX-ACCESS  not-accessible
   STATUS      current
   DESCRIPTION
      ""
   ::= {er1646v2VEthVlanIpV6AddressesEntry 11}

er1646v2VEthVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: virtualEthernet.editConf.vlan.ipV6.addresses.type

       Possibilities:
               unicast   (0)
               eui64   (1)
               anycast   (2)
               linkLocal   (3)
               generalPrefix   (4)"
   ::= {er1646v2VEthVlanIpV6AddressesEntry 50331648}

er1646v2VEthVlanIpV6AddressesAddress OBJECT-TYPE
   SYNTAX      Ipv6Address
   MAX-ACCESS  read-write
   STATUS      current
   DESCRIPTION
      "Path: virtualEthernet.editConf.vlan.ipV6.addresses.address

       ipv6 address"
   ::= {er1646v2VEthVlanIpV6AddressesEntry 16777216}

er1646v2VEthVlanIpV6AddressesPrefixLength OBJECT-TYPE
   SYNTAX      Integer32
   MAX-ACCESS  read-write
   STATUS      current
   DESCRIPTION
      "Path: virtualEthernet.editConf.vlan.ipV6.addresses.prefixLength"
   ::= {er1646v2VEthVlanIpV6AddressesEntry 33554432}

er1646v2VEthVlanIpV6AddressesGeneralPrefix OBJECT-TYPE
   SYNTAX      DisplayString
   MAX-ACCESS  read-write
   STATUS      current
   DESCRIPTION
      "Path: virtualEthernet.editConf.vlan.ipV6.addresses.generalPrefix"
   ::= {er1646v2VEthVlanIpV6AddressesEntry 83886080}

er1646v2VEthVlanIpV6AddressesRaSend OBJECT-TYPE
   SYNTAX      INTEGER
               {
               disabled (0),
               enabled (1)
               }
   MAX-ACCESS  read-write
   STATUS      current
   DESCRIPTION
      "Path: virtualEthernet.editConf.vlan.ipV6.addresses.ra.send

       Possibilities:
               disabled   (0)
               enabled   (1)"
   ::= {er1646v2VEthVlanIpV6AddressesEntry 67174400}

er1646v2VEthVlanIpV6AddressesRaOnLinkFlag OBJECT-TYPE
   SYNTAX      INTEGER
               {
               disabled (0),
               enabled (1)
               }
   MAX-ACCESS  read-write
   STATUS      current
   DESCRIPTION
      "Path: virtualEthernet.editConf.vlan.ipV6.addresses.ra.onLinkFlag

       Possibilities:
               disabled   (0)
               enabled   (1)"
   ::= {er1646v2VEthVlanIpV6AddressesEntry 67371008}

er1646v2VEthVlanIpV6AddressesRaAutoFlag OBJECT-TYPE
   SYNTAX      INTEGER
               {
               disabled (0),
               enabled (1)
               }
   MAX-ACCESS  read-write
   STATUS      current
   DESCRIPTION
      "Path: virtualEthernet.editConf.vlan.ipV6.addresses.ra.autonomousFlag

       Possibilities:
               disabled   (0)
               enabled   (1)"
   ::= {er1646v2VEthVlanIpV6AddressesEntry 67567616}

er1646v2VEthVlanIpV6AddressesRaValidLifeTime OBJECT-TYPE
   SYNTAX      TimeTicks
   MAX-ACCESS  read-write
   STATUS      current
   DESCRIPTION
      "Path: virtualEthernet.editConf.vlan.ipV6.addresses.ra.validLifeTime

       Time in centi-second."
   ::= {er1646v2VEthVlanIpV6AddressesEntry 67239936}

er1646v2VEthVlanIpV6AddressesRaValidLTMode OBJECT-TYPE
   SYNTAX      INTEGER
               {
               fixed (0),
               infinite (2)
               }
   MAX-ACCESS  read-write
   STATUS      current
   DESCRIPTION
      "Path: virtualEthernet.editConf.vlan.ipV6.addresses.ra.validLifeTimeMode

       Possibilities:
               fixed   (0)
               infinite   (2)"
   ::= {er1646v2VEthVlanIpV6AddressesEntry 67305472}

er1646v2VEthVlanIpV6AddressesRaPrefLifeTime OBJECT-TYPE
   SYNTAX      TimeTicks
   MAX-ACCESS  read-write
   STATUS      current
   DESCRIPTION
      "Path: virtualEthernet.editConf.vlan.ipV6.addresses.ra.prefLifeTime

       Time in centi-second."
   ::= {er1646v2VEthVlanIpV6AddressesEntry 67436544}

er1646v2VEthVlanIpV6AddressesRaPrefLTMode OBJECT-TYPE
   SYNTAX      INTEGER
               {
               fixed (0),
               infinite (2)
               }
   MAX-ACCESS  read-write
   STATUS      current
   DESCRIPTION
      "Path: virtualEthernet.editConf.vlan.ipV6.addresses.ra.prefLifeTimeMode

       Possibilities:
               fixed   (0)
               infinite   (2)"
   ::= {er1646v2VEthVlanIpV6AddressesEntry 67502080}

er1646v2VEthVlanIpV6RaDnsOptionsRdnssServers OBJECT-TYPE
   SYNTAX      SEQUENCE OF Er1646v2VEthVlanIpV6RaDnsOptionsRdnssServersEntry
   MAX-ACCESS  not-accessible
   STATUS      current
   DESCRIPTION
      ""
   ::= {er1646v2VEthVlan 705039144}

er1646v2VEthVlanIpV6RaDnsOptionsRdnssServersEntry OBJECT-TYPE
   SYNTAX      Er1646v2VEthVlanIpV6RaDnsOptionsRdnssServersEntry
   MAX-ACCESS  not-accessible
   STATUS      current
   DESCRIPTION
      ""
   INDEX      { er1646v2VEthVlanIpV6RaDnsOptionsRdnssServersGlobalIx,
                er1646v2VEthVlanTableIx,
                er1646v2VEthVlanIpV6RaDnsOptionsRdnssServersTableIx }
   ::= {er1646v2VEthVlanIpV6RaDnsOptionsRdnssServers 1}

Er1646v2VEthVlanIpV6RaDnsOptionsRdnssServersEntry ::=
   SEQUENCE
      {
      er1646v2VEthVlanIpV6RaDnsOptionsRdnssServersActions
         VariableLengthTableActions,
      er1646v2VEthVlanIpV6RaDnsOptionsRdnssServersGlobalIx
         GlobalIndex,
      er1646v2VEthVlanIpV6RaDnsOptionsRdnssServersTableIx
         TableIndex,
      er1646v2VEthVlanIpV6RaDnsOptionsRdnssServersAddress
         Ipv6Address
      }

er1646v2VEthVlanIpV6RaDnsOptionsRdnssServersActions OBJECT-TYPE
   SYNTAX      VariableLengthTableActions
   MAX-ACCESS  read-write
   STATUS      current
   DESCRIPTION
      "By way of this field, some manipulations
       on this table may be performed."
   ::= {er1646v2VEthVlanIpV6RaDnsOptionsRdnssServersEntry 2}

er1646v2VEthVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2VEthVlanIpV6RaDnsOptionsRdnssServersEntry 10}

er1646v2VEthVlanIpV6RaDnsOptionsRdnssServersTableIx OBJECT-TYPE
   SYNTAX      TableIndex
   MAX-ACCESS  not-accessible
   STATUS      current
   DESCRIPTION
      ""
   ::= {er1646v2VEthVlanIpV6RaDnsOptionsRdnssServersEntry 11}

er1646v2VEthVlanIpV6RaDnsOptionsRdnssServersAddress OBJECT-TYPE
   SYNTAX      Ipv6Address
   MAX-ACCESS  read-write
   STATUS      current
   DESCRIPTION
      "Path: virtualEthernet.editConf.vlan.ipV6.ra.dnsOptions.rdnss.servers.address

       ipv6 address"
   ::= {er1646v2VEthVlanIpV6RaDnsOptionsRdnssServersEntry 16777216}

er1646v2VEthVlanIpV6RaDnsOptionsDnsslDomains OBJECT-TYPE
   SYNTAX      SEQUENCE OF Er1646v2VEthVlanIpV6RaDnsOptionsDnsslDomainsEntry
   MAX-ACCESS  not-accessible
   STATUS      current
   DESCRIPTION
      ""
   ::= {er1646v2VEthVlan 705039176}

er1646v2VEthVlanIpV6RaDnsOptionsDnsslDomainsEntry OBJECT-TYPE
   SYNTAX      Er1646v2VEthVlanIpV6RaDnsOptionsDnsslDomainsEntry
   MAX-ACCESS  not-accessible
   STATUS      current
   DESCRIPTION
      ""
   INDEX      { er1646v2VEthVlanIpV6RaDnsOptionsDnsslDomainsGlobalIx,
                er1646v2VEthVlanTableIx,
                er1646v2VEthVlanIpV6RaDnsOptionsDnsslDomainsTableIx }
   ::= {er1646v2VEthVlanIpV6RaDnsOptionsDnsslDomains 1}

Er1646v2VEthVlanIpV6RaDnsOptionsDnsslDomainsEntry ::=
   SEQUENCE
      {
      er1646v2VEthVlanIpV6RaDnsOptionsDnsslDomainsActions
         VariableLengthTableActions,
      er1646v2VEthVlanIpV6RaDnsOptionsDnsslDomainsGlobalIx
         GlobalIndex,
      er1646v2VEthVlanIpV6RaDnsOptionsDnsslDomainsTableIx
         TableIndex,
      er1646v2VEthVlanIpV6RaDnsOptionsDnsslDomainsName
         DisplayString
      }

er1646v2VEthVlanIpV6RaDnsOptionsDnsslDomainsActions OBJECT-TYPE
   SYNTAX      VariableLengthTableActions
   MAX-ACCESS  read-write
   STATUS      current
   DESCRIPTION
      "By way of this field, some manipulations
       on this table may be performed."
   ::= {er1646v2VEthVlanIpV6RaDnsOptionsDnsslDomainsEntry 2}

er1646v2VEthVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2VEthVlanIpV6RaDnsOptionsDnsslDomainsEntry 10}

er1646v2VEthVlanIpV6RaDnsOptionsDnsslDomainsTableIx OBJECT-TYPE
   SYNTAX      TableIndex
   MAX-ACCESS  not-accessible
   STATUS      current
   DESCRIPTION
      ""
   ::= {er1646v2VEthVlanIpV6RaDnsOptionsDnsslDomainsEntry 11}

er1646v2VEthVlanIpV6RaDnsOptionsDnsslDomainsName OBJECT-TYPE
   SYNTAX      DisplayString
   MAX-ACCESS  read-write
   STATUS      current
   DESCRIPTION
      "Path: virtualEthernet.editConf.vlan.ipV6.ra.dnsOptions.dnssl.domains.name"
   ::= {er1646v2VEthVlanIpV6RaDnsOptionsDnsslDomainsEntry 16777216}

er1646v2VEthVlanIpV6DhcpClientUserClassOpt OBJECT-TYPE
   SYNTAX      SEQUENCE OF Er1646v2VEthVlanIpV6DhcpClientUserClassOptEntry
   MAX-ACCESS  not-accessible
   STATUS      current
   DESCRIPTION
      ""
   ::= {er1646v2VEthVlan 705312768}

er1646v2VEthVlanIpV6DhcpClientUserClassOptEntry OBJECT-TYPE
   SYNTAX      Er1646v2VEthVlanIpV6DhcpClientUserClassOptEntry
   MAX-ACCESS  not-accessible
   STATUS      current
   DESCRIPTION
      ""
   INDEX      { er1646v2VEthVlanIpV6DhcpClientUserClassOptGlobalIx,
                er1646v2VEthVlanTableIx,
                er1646v2VEthVlanIpV6DhcpClientUserClassOptTableIx }
   ::= {er1646v2VEthVlanIpV6DhcpClientUserClassOpt 1}

Er1646v2VEthVlanIpV6DhcpClientUserClassOptEntry ::=
   SEQUENCE
      {
      er1646v2VEthVlanIpV6DhcpClientUserClassOptActions
         VariableLengthTableActions,
      er1646v2VEthVlanIpV6DhcpClientUserClassOptGlobalIx
         GlobalIndex,
      er1646v2VEthVlanIpV6DhcpClientUserClassOptTableIx
         TableIndex,
      er1646v2VEthVlanIpV6DhcpClientUserClassOptValueAscii
         DisplayString,
      er1646v2VEthVlanIpV6DhcpClientUserClassOptValueDecimal
         Integer32,
      er1646v2VEthVlanIpV6DhcpClientUserClassOptValueHexData
         OCTET STRING
      }

er1646v2VEthVlanIpV6DhcpClientUserClassOptActions OBJECT-TYPE
   SYNTAX      VariableLengthTableActions
   MAX-ACCESS  read-write
   STATUS      current
   DESCRIPTION
      "By way of this field, some manipulations
       on this table may be performed."
   ::= {er1646v2VEthVlanIpV6DhcpClientUserClassOptEntry 2}

er1646v2VEthVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2VEthVlanIpV6DhcpClientUserClassOptEntry 10}

er1646v2VEthVlanIpV6DhcpClientUserClassOptTableIx OBJECT-TYPE
   SYNTAX      TableIndex
   MAX-ACCESS  not-accessible
   STATUS      current
   DESCRIPTION
      ""
   ::= {er1646v2VEthVlanIpV6DhcpClientUserClassOptEntry 11}

er1646v2VEthVlanIpV6DhcpClientUserClassOptValueAscii OBJECT-TYPE
   SYNTAX      DisplayString
   MAX-ACCESS  read-write
   STATUS      current
   DESCRIPTION
      "Path: virtualEthernet.editConf.vlan.ipV6.dhcp.client.userClassOpt.value.ascii"
   ::= {er1646v2VEthVlanIpV6DhcpClientUserClassOptEntry 16842752}

er1646v2VEthVlanIpV6DhcpClientUserClassOptValueDecimal OBJECT-TYPE
   SYNTAX      Integer32
   MAX-ACCESS  read-write
   STATUS      current
   DESCRIPTION
      "Path: virtualEthernet.editConf.vlan.ipV6.dhcp.client.userClassOpt.value.decimal"
   ::= {er1646v2VEthVlanIpV6DhcpClientUserClassOptEntry 16908288}

er1646v2VEthVlanIpV6DhcpClientUserClassOptValueHexData OBJECT-TYPE
   SYNTAX      OCTET STRING
   MAX-ACCESS  read-write
   STATUS      current
   DESCRIPTION
      "Path: virtualEthernet.editConf.vlan.ipV6.dhcp.client.userClassOpt.value.hexData"
   ::= {er1646v2VEthVlanIpV6DhcpClientUserClassOptEntry 16973824}

er1646v2VEthVlanIpV6DhcpClientVendorCl OBJECT-TYPE
   SYNTAX      SEQUENCE OF Er1646v2VEthVlanIpV6DhcpClientVendorClEntry
   MAX-ACCESS  not-accessible
   STATUS      current
   DESCRIPTION
      ""
   ::= {er1646v2VEthVlan 705313792}

er1646v2VEthVlanIpV6DhcpClientVendorClEntry OBJECT-TYPE
   SYNTAX      Er1646v2VEthVlanIpV6DhcpClientVendorClEntry
   MAX-ACCESS  not-accessible
   STATUS      current
   DESCRIPTION
      ""
   INDEX      { er1646v2VEthVlanIpV6DhcpClientVendorClGlobalIx,
                er1646v2VEthVlanTableIx,
                er1646v2VEthVlanIpV6DhcpClientVendorClTableIx }
   ::= {er1646v2VEthVlanIpV6DhcpClientVendorCl 1}

Er1646v2VEthVlanIpV6DhcpClientVendorClEntry ::=
   SEQUENCE
      {
      er1646v2VEthVlanIpV6DhcpClientVendorClActions
         VariableLengthTableActions,
      er1646v2VEthVlanIpV6DhcpClientVendorClGlobalIx
         GlobalIndex,
      er1646v2VEthVlanIpV6DhcpClientVendorClTableIx
         TableIndex,
      er1646v2VEthVlanIpV6DhcpClientVendorClValueAscii
         DisplayString,
      er1646v2VEthVlanIpV6DhcpClientVendorClValueDecimal
         Integer32,
      er1646v2VEthVlanIpV6DhcpClientVendorClValueHexData
         OCTET STRING
      }

er1646v2VEthVlanIpV6DhcpClientVendorClActions OBJECT-TYPE
   SYNTAX      VariableLengthTableActions
   MAX-ACCESS  read-write
   STATUS      current
   DESCRIPTION
      "By way of this field, some manipulations
       on this table may be performed."
   ::= {er1646v2VEthVlanIpV6DhcpClientVendorClEntry 2}

er1646v2VEthVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2VEthVlanIpV6DhcpClientVendorClEntry 10}

er1646v2VEthVlanIpV6DhcpClientVendorClTableIx OBJECT-TYPE
   SYNTAX      TableIndex
   MAX-ACCESS  not-accessible
   STATUS      current
   DESCRIPTION
      ""
   ::= {er1646v2VEthVlanIpV6DhcpClientVendorClEntry 11}

er1646v2VEthVlanIpV6DhcpClientVendorClValueAscii OBJECT-TYPE
   SYNTAX      DisplayString
   MAX-ACCESS  read-write
   STATUS      current
   DESCRIPTION
      "Path: virtualEthernet.editConf.vlan.ipV6.dhcp.client.vendorClassOpt.value.ascii"
   ::= {er1646v2VEthVlanIpV6DhcpClientVendorClEntry 16842752}

er1646v2VEthVlanIpV6DhcpClientVendorClValueDecimal OBJECT-TYPE
   SYNTAX      Integer32
   MAX-ACCESS  read-write
   STATUS      current
   DESCRIPTION
      "Path: virtualEthernet.editConf.vlan.ipV6.dhcp.client.vendorClassOpt.value.decimal"
   ::= {er1646v2VEthVlanIpV6DhcpClientVendorClEntry 16908288}

er1646v2VEthVlanIpV6DhcpClientVendorClValueHexData OBJECT-TYPE
   SYNTAX      OCTET STRING
   MAX-ACCESS  read-write
   STATUS      current
   DESCRIPTION
      "Path: virtualEthernet.editConf.vlan.ipV6.dhcp.client.vendorClassOpt.value.hexData"
   ::= {er1646v2VEthVlanIpV6DhcpClientVendorClEntry 16973824}

er1646v2VEthVlanIpV6DhcpRelayDestinations OBJECT-TYPE
   SYNTAX      SEQUENCE OF Er1646v2VEthVlanIpV6DhcpRelayDestinationsEntry
   MAX-ACCESS  not-accessible
   STATUS      current
   DESCRIPTION
      ""
   ::= {er1646v2VEthVlan 705323072}

er1646v2VEthVlanIpV6DhcpRelayDestinationsEntry OBJECT-TYPE
   SYNTAX      Er1646v2VEthVlanIpV6DhcpRelayDestinationsEntry
   MAX-ACCESS  not-accessible
   STATUS      current
   DESCRIPTION
      ""
   INDEX      { er1646v2VEthVlanIpV6DhcpRelayDestinationsGlobalIx,
                er1646v2VEthVlanTableIx,
                er1646v2VEthVlanIpV6DhcpRelayDestinationsTableIx }
   ::= {er1646v2VEthVlanIpV6DhcpRelayDestinations 1}

Er1646v2VEthVlanIpV6DhcpRelayDestinationsEntry ::=
   SEQUENCE
      {
      er1646v2VEthVlanIpV6DhcpRelayDestinationsActions
         VariableLengthTableActions,
      er1646v2VEthVlanIpV6DhcpRelayDestinationsGlobalIx
         GlobalIndex,
      er1646v2VEthVlanIpV6DhcpRelayDestinationsTableIx
         TableIndex,
      er1646v2VEthVlanIpV6DhcpRelayDestinationsAddress
         Ipv6Address,
      er1646v2VEthVlanIpV6DhcpRelayDestinationsInterface
         DisplayString
      }

er1646v2VEthVlanIpV6DhcpRelayDestinationsActions OBJECT-TYPE
   SYNTAX      VariableLengthTableActions
   MAX-ACCESS  read-write
   STATUS      current
   DESCRIPTION
      "By way of this field, some manipulations
       on this table may be performed."
   ::= {er1646v2VEthVlanIpV6DhcpRelayDestinationsEntry 2}

er1646v2VEthVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2VEthVlanIpV6DhcpRelayDestinationsEntry 10}

er1646v2VEthVlanIpV6DhcpRelayDestinationsTableIx OBJECT-TYPE
   SYNTAX      TableIndex
   MAX-ACCESS  not-accessible
   STATUS      current
   DESCRIPTION
      ""
   ::= {er1646v2VEthVlanIpV6DhcpRelayDestinationsEntry 11}

er1646v2VEthVlanIpV6DhcpRelayDestinationsAddress OBJECT-TYPE
   SYNTAX      Ipv6Address
   MAX-ACCESS  read-write
   STATUS      current
   DESCRIPTION
      "Path: virtualEthernet.editConf.vlan.ipV6.dhcp.relay.destinations.address

       ipv6 address"
   ::= {er1646v2VEthVlanIpV6DhcpRelayDestinationsEntry 16777216}

er1646v2VEthVlanIpV6DhcpRelayDestinationsInterface OBJECT-TYPE
   SYNTAX      DisplayString
   MAX-ACCESS  read-write
   STATUS      current
   DESCRIPTION
      "Path: virtualEthernet.editConf.vlan.ipV6.dhcp.relay.destinations.interface"
   ::= {er1646v2VEthVlanIpV6DhcpRelayDestinationsEntry 33554432}

er1646v2VEthVlanBridgingVlTVlans OBJECT-TYPE
   SYNTAX      SEQUENCE OF Er1646v2VEthVlanBridgingVlTVlansEntry
   MAX-ACCESS  not-accessible
   STATUS      current
   DESCRIPTION
      ""
   ::= {er1646v2VEthVlan 459079680}

er1646v2VEthVlanBridgingVlTVlansEntry OBJECT-TYPE
   SYNTAX      Er1646v2VEthVlanBridgingVlTVlansEntry
   MAX-ACCESS  not-accessible
   STATUS      current
   DESCRIPTION
      ""
   INDEX      { er1646v2VEthVlanBridgingVlTVlansGlobalIx,
                er1646v2VEthVlanTableIx,
                er1646v2VEthVlanBridgingVlTVlansTableIx }
   ::= {er1646v2VEthVlanBridgingVlTVlans 1}

Er1646v2VEthVlanBridgingVlTVlansEntry ::=
   SEQUENCE
      {
      er1646v2VEthVlanBridgingVlTVlansActions
         VariableLengthTableActions,
      er1646v2VEthVlanBridgingVlTVlansGlobalIx
         GlobalIndex,
      er1646v2VEthVlanBridgingVlTVlansTableIx
         TableIndex,
      er1646v2VEthVlanBridgingVlTVlansVid
         Integer32,
      er1646v2VEthVlanBridgingVlTVlansEndVid
         Integer32,
      er1646v2VEthVlanBridgingVlTVlansAction
         INTEGER,
      er1646v2VEthVlanBridgingVlTVlansTagInfoTpid
         INTEGER,
      er1646v2VEthVlanBridgingVlTVlansTagInfoVid
         Integer32
      }

er1646v2VEthVlanBridgingVlTVlansActions OBJECT-TYPE
   SYNTAX      VariableLengthTableActions
   MAX-ACCESS  read-write
   STATUS      current
   DESCRIPTION
      "By way of this field, some manipulations
       on this table may be performed."
   ::= {er1646v2VEthVlanBridgingVlTVlansEntry 2}

er1646v2VEthVlanBridgingVlTVlansGlobalIx OBJECT-TYPE
   SYNTAX      GlobalIndex
   MAX-ACCESS  not-accessible
   STATUS      current
   DESCRIPTION
      "The value of the tlsCntTreeGlobalIndex of the MANAGED OBJECT."
   ::= {er1646v2VEthVlanBridgingVlTVlansEntry 10}

er1646v2VEthVlanBridgingVlTVlansTableIx OBJECT-TYPE
   SYNTAX      TableIndex
   MAX-ACCESS  not-accessible
   STATUS      current
   DESCRIPTION
      ""
   ::= {er1646v2VEthVlanBridgingVlTVlansEntry 11}

er1646v2VEthVlanBridgingVlTVlansVid OBJECT-TYPE
   SYNTAX      Integer32
   MAX-ACCESS  read-write
   STATUS      current
   DESCRIPTION
      "Path: virtualEthernet.editConf.vlan.bridging.vlanTagging.vlans.vid"
   ::= {er1646v2VEthVlanBridgingVlTVlansEntry 536870912}

er1646v2VEthVlanBridgingVlTVlansEndVid OBJECT-TYPE
   SYNTAX      Integer32
   MAX-ACCESS  read-write
   STATUS      current
   DESCRIPTION
      "Path: virtualEthernet.editConf.vlan.bridging.vlanTagging.vlans.endVid"
   ::= {er1646v2VEthVlanBridgingVlTVlansEntry 2147483648}

er1646v2VEthVlanBridgingVlTVlansAction OBJECT-TYPE
   SYNTAX      INTEGER
               {
               discard (0),
               accept (1),
               tag (2)
               }
   MAX-ACCESS  read-write
   STATUS      current
   DESCRIPTION
      "Path: virtualEthernet.editConf.vlan.bridging.vlanTagging.vlans.action

       Possibilities:
               discard   (0)
               accept   (1)
               tag   (2)"
   ::= {er1646v2VEthVlanBridgingVlTVlansEntry 1073741824}

er1646v2VEthVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.bridging.vlanTagging.vlans.tagInfo.tpid

       Possibilities:
               dot1Q   (33024)
               dot1ad   (34984)
               0x9100   (37120)
               0x9200   (37376)
               0x9300   (37632)"
   ::= {er1646v2VEthVlanBridgingVlTVlansEntry 1677721600}

er1646v2VEthVlanBridgingVlTVlansTagInfoVid OBJECT-TYPE
   SYNTAX      Integer32
   MAX-ACCESS  read-write
   STATUS      current
   DESCRIPTION
      "Path: virtualEthernet.editConf.vlan.bridging.vlanTagging.vlans.tagInfo.vid"
   ::= {er1646v2VEthVlanBridgingVlTVlansEntry 1744830464}

er1646v2VEthVlanVlanVidExtensionTable OBJECT-TYPE
   SYNTAX      SEQUENCE OF Er1646v2VEthVlanVlanVidExtensionTableEntry
   MAX-ACCESS  not-accessible
   STATUS      current
   DESCRIPTION
      ""
   ::= {er1646v2VEthVlan 235340544}

er1646v2VEthVlanVlanVidExtensionTableEntry OBJECT-TYPE
   SYNTAX      Er1646v2VEthVlanVlanVidExtensionTableEntry
   MAX-ACCESS  not-accessible
   STATUS      current
   DESCRIPTION
      ""
   INDEX      { er1646v2VEthVlanVlanVidExtensionTableGlobalIx,
                er1646v2VEthVlanTableIx,
                er1646v2VEthVlanVlanVidExtensionTableTableIx }
   ::= {er1646v2VEthVlanVlanVidExtensionTable 1}

Er1646v2VEthVlanVlanVidExtensionTableEntry ::=
   SEQUENCE
      {
      er1646v2VEthVlanVlanVidExtensionTableActions
         VariableLengthTableActions,
      er1646v2VEthVlanVlanVidExtensionTableGlobalIx
         GlobalIndex,
      er1646v2VEthVlanVlanVidExtensionTableTableIx
         TableIndex,
      er1646v2VEthVlanVlanVidExtensionTableTpid
         INTEGER,
      er1646v2VEthVlanVlanVidExtensionTableVid
         Integer32,
      er1646v2VEthVlanVlanVidExtensionTableEndVid
         Integer32
      }

er1646v2VEthVlanVlanVidExtensionTableActions OBJECT-TYPE
   SYNTAX      VariableLengthTableActions
   MAX-ACCESS  read-write
   STATUS      current
   DESCRIPTION
      "By way of this field, some manipulations
       on this table may be performed."
   ::= {er1646v2VEthVlanVlanVidExtensionTableEntry 2}

er1646v2VEthVlanVlanVidExtensionTableGlobalIx OBJECT-TYPE
   SYNTAX      GlobalIndex
   MAX-ACCESS  not-accessible
   STATUS      current
   DESCRIPTION
      "The value of the tlsCntTreeGlobalIndex of the MANAGED OBJECT."
   ::= {er1646v2VEthVlanVlanVidExtensionTableEntry 10}

er1646v2VEthVlanVlanVidExtensionTableTableIx OBJECT-TYPE
   SYNTAX      TableIndex
   MAX-ACCESS  not-accessible
   STATUS      current
   DESCRIPTION
      ""
   ::= {er1646v2VEthVlanVlanVidExtensionTableEntry 11}

er1646v2VEthVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: virtualEthernet.editConf.vlan.vlan.vidExtension.table.tpid

       Possibilities:
               dot1Q   (33024)
               dot1ad   (34984)
               0x9100   (37120)
               0x9200   (37376)
               0x9300   (37632)"
   ::= {er1646v2VEthVlanVlanVidExtensionTableEntry 16777216}

er1646v2VEthVlanVlanVidExtensionTableVid OBJECT-TYPE
   SYNTAX      Integer32
   MAX-ACCESS  read-write
   STATUS      current
   DESCRIPTION
      "Path: virtualEthernet.editConf.vlan.vlan.vidExtension.table.vid"
   ::= {er1646v2VEthVlanVlanVidExtensionTableEntry 33554432}

er1646v2VEthVlanVlanVidExtensionTableEndVid OBJECT-TYPE
   SYNTAX      Integer32
   MAX-ACCESS  read-write
   STATUS      current
   DESCRIPTION
      "Path: virtualEthernet.editConf.vlan.vlan.vidExtension.table.endVid"
   ::= {er1646v2VEthVlanVlanVidExtensionTableEntry 50331648}

er1646v2VEthVlanVlanCSMap OBJECT-TYPE
   SYNTAX      SEQUENCE OF Er1646v2VEthVlanVlanCSMapEntry
   MAX-ACCESS  not-accessible
   STATUS      current
   DESCRIPTION
      ""
   ::= {er1646v2VEthVlan 235405312}

er1646v2VEthVlanVlanCSMapEntry OBJECT-TYPE
   SYNTAX      Er1646v2VEthVlanVlanCSMapEntry
   MAX-ACCESS  not-accessible
   STATUS      current
   DESCRIPTION
      ""
   INDEX      { er1646v2VEthVlanVlanCSMapGlobalIx,
                er1646v2VEthVlanTableIx,
                er1646v2VEthVlanVlanCSMapTableIx }
   ::= {er1646v2VEthVlanVlanCSMap 1}

Er1646v2VEthVlanVlanCSMapEntry ::=
   SEQUENCE
      {
      er1646v2VEthVlanVlanCSMapActions
         VariableLengthTableActions,
      er1646v2VEthVlanVlanCSMapGlobalIx
         GlobalIndex,
      er1646v2VEthVlanVlanCSMapTableIx
         TableIndex,
      er1646v2VEthVlanVlanCSMapCos
         INTEGER,
      er1646v2VEthVlanVlanCSMapDei
         INTEGER,
      er1646v2VEthVlanVlanCSMapTos
         INTEGER,
      er1646v2VEthVlanVlanCSMapQueue
         INTEGER,
      er1646v2VEthVlanVlanCSMapDropLevel
         INTEGER,
      er1646v2VEthVlanVlanCSMapDeFlag
         INTEGER
      }

er1646v2VEthVlanVlanCSMapActions OBJECT-TYPE
   SYNTAX      VariableLengthTableActions
   MAX-ACCESS  read-write
   STATUS      current
   DESCRIPTION
      "By way of this field, some manipulations
       on this table may be performed."
   ::= {er1646v2VEthVlanVlanCSMapEntry 2}

er1646v2VEthVlanVlanCSMapGlobalIx OBJECT-TYPE
   SYNTAX      GlobalIndex
   MAX-ACCESS  not-accessible
   STATUS      current
   DESCRIPTION
      "The value of the tlsCntTreeGlobalIndex of the MANAGED OBJECT."
   ::= {er1646v2VEthVlanVlanCSMapEntry 10}

er1646v2VEthVlanVlanCSMapTableIx OBJECT-TYPE
   SYNTAX      TableIndex
   MAX-ACCESS  not-accessible
   STATUS      current
   DESCRIPTION
      ""
   ::= {er1646v2VEthVlanVlanCSMapEntry 11}

er1646v2VEthVlanVlanCSMapCos OBJECT-TYPE
   SYNTAX      INTEGER
               {
               any (8)
               }
   MAX-ACCESS  read-write
   STATUS      current
   DESCRIPTION
      "Path: virtualEthernet.editConf.vlan.vlan.cosMap.cos

       Possibilities:
               any   (8)"
   ::= {er1646v2VEthVlanVlanCSMapEntry 16777216}

er1646v2VEthVlanVlanCSMapDei OBJECT-TYPE
   SYNTAX      INTEGER
               {
               clear (0),
               set (1),
               any (2)
               }
   MAX-ACCESS  read-write
   STATUS      current
   DESCRIPTION
      "Path: virtualEthernet.editConf.vlan.vlan.cosMap.dei

       Possibilities:
               clear   (0)
               set   (1)
               any   (2)"
   ::= {er1646v2VEthVlanVlanCSMapEntry 33554432}

er1646v2VEthVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: virtualEthernet.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1646v2VEthVlanVlanCSMapEntry 50331648}

er1646v2VEthVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: virtualEthernet.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1646v2VEthVlanVlanCSMapEntry 67108864}

er1646v2VEthVlanVlanCSMapDropLevel OBJECT-TYPE
   SYNTAX      INTEGER
               {
               unchanged (-1),
               dropOnQueue (0)
               }
   MAX-ACCESS  read-write
   STATUS      current
   DESCRIPTION
      "Path: virtualEthernet.editConf.vlan.vlan.cosMap.dropLevel

       Possibilities:
               unchanged   (-1)
               dropOnQueue   (0)"
   ::= {er1646v2VEthVlanVlanCSMapEntry 83886080}

er1646v2VEthVlanVlanCSMapDeFlag OBJECT-TYPE
   SYNTAX      INTEGER
               {
               unchanged (255),
               clear (0),
               set (1)
               }
   MAX-ACCESS  read-write
   STATUS      current
   DESCRIPTION
      "Path: virtualEthernet.editConf.vlan.vlan.cosMap.deFlag

       Possibilities:
               unchanged   (255)
               clear   (0)
               set   (1)"
   ::= {er1646v2VEthVlanVlanCSMapEntry 117440512}

er1646v2VEthVlanVlanTCMap OBJECT-TYPE
   SYNTAX      SEQUENCE OF Er1646v2VEthVlanVlanTCMapEntry
   MAX-ACCESS  not-accessible
   STATUS      current
   DESCRIPTION
      ""
   ::= {er1646v2VEthVlan 241369088}

er1646v2VEthVlanVlanTCMapEntry OBJECT-TYPE
   SYNTAX      Er1646v2VEthVlanVlanTCMapEntry
   MAX-ACCESS  not-accessible
   STATUS      current
   DESCRIPTION
      ""
   INDEX      { er1646v2VEthVlanVlanTCMapGlobalIx,
                er1646v2VEthVlanTableIx,
                er1646v2VEthVlanVlanTCMapTableIx }
   ::= {er1646v2VEthVlanVlanTCMap 1}

Er1646v2VEthVlanVlanTCMapEntry ::=
   SEQUENCE
      {
      er1646v2VEthVlanVlanTCMapActions
         VariableLengthTableActions,
      er1646v2VEthVlanVlanTCMapGlobalIx
         GlobalIndex,
      er1646v2VEthVlanVlanTCMapTableIx
         TableIndex,
      er1646v2VEthVlanVlanTCMapStartTos
         INTEGER,
      er1646v2VEthVlanVlanTCMapEndTos
         INTEGER,
      er1646v2VEthVlanVlanTCMapCos
         INTEGER
      }

er1646v2VEthVlanVlanTCMapActions OBJECT-TYPE
   SYNTAX      VariableLengthTableActions
   MAX-ACCESS  read-write
   STATUS      current
   DESCRIPTION
      "By way of this field, some manipulations
       on this table may be performed."
   ::= {er1646v2VEthVlanVlanTCMapEntry 2}

er1646v2VEthVlanVlanTCMapGlobalIx OBJECT-TYPE
   SYNTAX      GlobalIndex
   MAX-ACCESS  not-accessible
   STATUS      current
   DESCRIPTION
      "The value of the tlsCntTreeGlobalIndex of the MANAGED OBJECT."
   ::= {er1646v2VEthVlanVlanTCMapEntry 10}

er1646v2VEthVlanVlanTCMapTableIx OBJECT-TYPE
   SYNTAX      TableIndex
   MAX-ACCESS  not-accessible
   STATUS      current
   DESCRIPTION
      ""
   ::= {er1646v2VEthVlanVlanTCMapEntry 11}

er1646v2VEthVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: virtualEthernet.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2VEthVlanVlanTCMapEntry 16777216}

er1646v2VEthVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: virtualEthernet.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1646v2VEthVlanVlanTCMapEntry 33554432}

er1646v2VEthVlanVlanTCMapCos OBJECT-TYPE
   SYNTAX      INTEGER
               {
               queueCosMap (8)
               }
   MAX-ACCESS  read-write
   STATUS      current
   DESCRIPTION
      "Path: virtualEthernet.editConf.vlan.vlan.tosCosMap.cos

       Possibilities:
               queueCosMap   (8)"
   ::= {er1646v2VEthVlanVlanTCMapEntry 50331648}

er1646v2VEthVlanVlanArpStaticArp OBJECT-TYPE
   SYNTAX      SEQUENCE OF Er1646v2VEthVlanVlanArpStaticArpEntry
   MAX-ACCESS  not-accessible
   STATUS      current
   DESCRIPTION
      ""
   ::= {er1646v2VEthVlan 235275008}

er1646v2VEthVlanVlanArpStaticArpEntry OBJECT-TYPE
   SYNTAX      Er1646v2VEthVlanVlanArpStaticArpEntry
   MAX-ACCESS  not-accessible
   STATUS      current
   DESCRIPTION
      ""
   INDEX      { er1646v2VEthVlanVlanArpStaticArpGlobalIx,
                er1646v2VEthVlanTableIx,
                er1646v2VEthVlanVlanArpStaticArpTableIx }
   ::= {er1646v2VEthVlanVlanArpStaticArp 1}

Er1646v2VEthVlanVlanArpStaticArpEntry ::=
   SEQUENCE
      {
      er1646v2VEthVlanVlanArpStaticArpActions
         VariableLengthTableActions,
      er1646v2VEthVlanVlanArpStaticArpGlobalIx
         GlobalIndex,
      er1646v2VEthVlanVlanArpStaticArpTableIx
         TableIndex,
      er1646v2VEthVlanVlanArpStaticArpMacAddress
         OCTET STRING,
      er1646v2VEthVlanVlanArpStaticArpIpAddress
         IpAddress
      }

er1646v2VEthVlanVlanArpStaticArpActions OBJECT-TYPE
   SYNTAX      VariableLengthTableActions
   MAX-ACCESS  read-write
   STATUS      current
   DESCRIPTION
      "By way of this field, some manipulations
       on this table may be performed."
   ::= {er1646v2VEthVlanVlanArpStaticArpEntry 2}

er1646v2VEthVlanVlanArpStaticArpGlobalIx OBJECT-TYPE
   SYNTAX      GlobalIndex
   MAX-ACCESS  not-accessible
   STATUS      current
   DESCRIPTION
      "The value of the tlsCntTreeGlobalIndex of the MANAGED OBJECT."
   ::= {er1646v2VEthVlanVlanArpStaticArpEntry 10}

er1646v2VEthVlanVlanArpStaticArpTableIx OBJECT-TYPE
   SYNTAX      TableIndex
   MAX-ACCESS  not-accessible
   STATUS      current
   DESCRIPTION
      ""
   ::= {er1646v2VEthVlanVlanArpStaticArpEntry 11}

er1646v2VEthVlanVlanArpStaticArpMacAddress OBJECT-TYPE
   SYNTAX      OCTET STRING
   MAX-ACCESS  read-write
   STATUS      current
   DESCRIPTION
      "Path: virtualEthernet.editConf.vlan.vlan.arp.staticArp.macAddress

       MAC address."
   ::= {er1646v2VEthVlanVlanArpStaticArpEntry 16777216}

er1646v2VEthVlanVlanArpStaticArpIpAddress OBJECT-TYPE
   SYNTAX      IpAddress
   MAX-ACCESS  read-write
   STATUS      current
   DESCRIPTION
      "Path: virtualEthernet.editConf.vlan.vlan.arp.staticArp.ipAddress"
   ::= {er1646v2VEthVlanVlanArpStaticArpEntry 33554432}


er1646v2VEthPppOE OBJECT IDENTIFIER ::= {er1646v2VEth 35}

er1646v2VEthPppOESSCTable OBJECT-TYPE
   SYNTAX      SEQUENCE OF Er1646v2VEthPppOEEntry
   MAX-ACCESS  not-accessible
   STATUS      current
   DESCRIPTION
      ""
   ::= {er1646v2VEthPppOE 1}

er1646v2VEthPppOEEntry OBJECT-TYPE
   SYNTAX      Er1646v2VEthPppOEEntry
   MAX-ACCESS  not-accessible
   STATUS      current
   DESCRIPTION
      ""
   INDEX      { er1646v2VEthPppOEGlobalIx,
                er1646v2VEthPppOETableIx }
   ::= {er1646v2VEthPppOESSCTable 1}

Er1646v2VEthPppOEEntry ::=
   SEQUENCE
      {
      er1646v2VEthPppOEActions
         VariableLengthTableActions,
      er1646v2VEthPppOEGlobalIx
         GlobalIndex,
      er1646v2VEthPppOETableIx
         TableIndex,
      er1646v2VEthPppOEName
         DisplayString,
      er1646v2VEthPppOERemark
         DisplayString,
      er1646v2VEthPppOEAdminStatus
         INTEGER,
      er1646v2VEthPppOEMode
         INTEGER,
      er1646v2VEthPppOEIpVrfRouter
         DisplayString,
      er1646v2VEthPppOEIpAdr
         IpAddress,
      er1646v2VEthPppOEIpNetm
         IpAddress,
      er1646v2VEthPppOEIpSNetName
         INTEGER,
      er1646v2VEthPppOEIpSNetCust
         DisplayString,
      er1646v2VEthPppOEIpRem
         IpAddress,
      er1646v2VEthPppOEIpUnnumbered
         DisplayString,
      er1646v2VEthPppOEIpGwPref
         Integer32,
      er1646v2VEthPppOEIpRsn
         INTEGER,
      er1646v2VEthPppOEIpMtu
         Integer32,
      er1646v2VEthPppOEIpMssAdjust
         INTEGER,
      er1646v2VEthPppOEIpRipMetric
         Integer32,
      er1646v2VEthPppOEIpRipMetricOut
         Integer32,
      er1646v2VEthPppOEIpRipMode
         INTEGER,
      er1646v2VEthPppOEIpRipTxVer
         INTEGER,
      er1646v2VEthPppOEIpRipRxVer
         INTEGER,
      er1646v2VEthPppOEIpRipSplitH
         INTEGER,
      er1646v2VEthPppOEIpRipAuth
         INTEGER,
      er1646v2VEthPppOEIpRipFilter
         DisplayString,
      er1646v2VEthPppOEIpRipFilterIn
         DisplayString,
      er1646v2VEthPppOEIpRipClearNextHop
         INTEGER,
      er1646v2VEthPppOEIpAccPol
         DisplayString,
      er1646v2VEthPppOEIpAB
         DisplayString,
      er1646v2VEthPppOEIpMA
         INTEGER,
      er1646v2VEthPppOEIpMF
         Integer32,
      er1646v2VEthPppOEIpDB
         INTEGER,
      er1646v2VEthPppOEIpIR
         INTEGER,
      er1646v2VEthPppOEIpIgmp
         INTEGER,
      er1646v2VEthPppOEIpNN
         DisplayString,
      er1646v2VEthPppOEIpPimMode
         INTEGER,
      er1646v2VEthPppOEIpPimDrPriority
         Counter32,
      er1646v2VEthPppOEIpPimHelloTime
         TimeTicks,
      er1646v2VEthPppOEIpPimPropagationDelay
         TimeTicks,
      er1646v2VEthPppOEIpPimOverrideInterval
         TimeTicks,
      er1646v2VEthPppOEIpPimBsrBorder
         INTEGER,
      er1646v2VEthPppOEIpPimTtlThreshold
         Integer32,
      er1646v2VEthPppOEIpIMNetworkUnreachable
         INTEGER,
      er1646v2VEthPppOEIpIMHostUnreachable
         INTEGER,
      er1646v2VEthPppOEIpIMProtocolUnreachable
         INTEGER,
      er1646v2VEthPppOEIpIMPortUnreachable
         INTEGER,
      er1646v2VEthPppOEIpIMMtuExceeded
         INTEGER,
      er1646v2VEthPppOEIpIMAdminProhibited
         INTEGER,
      er1646v2VEthPppOEIpIMTtlExceeded
         INTEGER,
      er1646v2VEthPppOEIpIMRedirect
         INTEGER,
      er1646v2VEthPppOEIpV6VrfRouter
         DisplayString,
      er1646v2VEthPppOEIpV6AddrAutoConfigNrDupAddrDetects
         Integer32,
      er1646v2VEthPppOEIpV6AddrAutoConfigAcceptRa
         INTEGER,
      er1646v2VEthPppOEIpV6AddrAutoConfigAcceptRaRdnss
         INTEGER,
      er1646v2VEthPppOEIpV6AddrAutoConfigAcceptRaDnssl
         INTEGER,
      er1646v2VEthPppOEIpV6DefaultRoute
         INTEGER,
      er1646v2VEthPppOEIpV6RaSend
         INTEGER,
      er1646v2VEthPppOEIpV6RaMinInterval
         TimeTicks,
      er1646v2VEthPppOEIpV6RaMaxInterval
         TimeTicks,
      er1646v2VEthPppOEIpV6RaManagedFlag
         INTEGER,
      er1646v2VEthPppOEIpV6RaOtherConfFlag
         INTEGER,
      er1646v2VEthPppOEIpV6RaLinkMtu
         Integer32,
      er1646v2VEthPppOEIpV6RaReachableTime
         TimeTicks,
      er1646v2VEthPppOEIpV6RaRetransmitTime
         TimeTicks,
      er1646v2VEthPppOEIpV6RaHopLimit
         Integer32,
      er1646v2VEthPppOEIpV6RaDefaultLifeTime
         TimeTicks,
      er1646v2VEthPppOEIpV6RaDnsOptionsRdnssLifeTime
         TimeTicks,
      er1646v2VEthPppOEIpV6RaDnsOptionsRdnssImportServers
         INTEGER,
      er1646v2VEthPppOEIpV6RaDnsOptionsDnsslLifeTime
         TimeTicks,
      er1646v2VEthPppOEIpV6RaDnsOptionsDnsslImportDomains
         INTEGER,
      er1646v2VEthPppOEIpV6RsSend
         INTEGER,
      er1646v2VEthPppOEIpV6RsMaxRandomDelay
         TimeTicks,
      er1646v2VEthPppOEIpV6RsInterval
         TimeTicks,
      er1646v2VEthPppOEIpV6RsMaxSolicitations
         Integer32,
      er1646v2VEthPppOEIpV6TrafficPolicyInbound
         DisplayString,
      er1646v2VEthPppOEIpV6TrafficPolicyOutbound
         DisplayString,
      er1646v2VEthPppOEIpV6FirewallZone
         DisplayString,
      er1646v2VEthPppOEIpV6DhcpClientAddrAC
         INTEGER,
      er1646v2VEthPppOEIpV6DhcpClientPrDelMode
         INTEGER,
      er1646v2VEthPppOEIpV6DhcpClientPrDelPool
         DisplayString,
      er1646v2VEthPppOEIpV6DhcpClientPrDelPdExclOpt
         INTEGER,
      er1646v2VEthPppOEIpV6DhcpClientDnsServerPref
         Integer32,
      er1646v2VEthPppOEIpV6DhcpClientRapidCommit
         INTEGER,
      er1646v2VEthPppOEIpV6DhcpClientTimersSolTimeOut
         TimeTicks,
      er1646v2VEthPppOEIpV6DhcpClientTimersSolMaxRt
         TimeTicks,
      er1646v2VEthPppOEIpV6DhcpClientTimersInfoRefresh
         TimeTicks,
      er1646v2VEthPppOEIpV6DhcpServerMode
         INTEGER,
      er1646v2VEthPppOEIpV6DhcpServerPreference
         Integer32,
      er1646v2VEthPppOEIpV6DhcpServerPool
         DisplayString,
      er1646v2VEthPppOEIpV6DhcpServerRapidCommit
         INTEGER,
      er1646v2VEthPppOEIpV6DhcpServerTimersInfoRefresh
         TimeTicks,
      er1646v2VEthPppOEIpV6DhcpRelayMode
         INTEGER,
      er1646v2VEthPppOEIpV6SendRedirect
         INTEGER,
      er1646v2VEthPppOEIpV6LinkMtu
         Integer32,
      er1646v2VEthPppOEIpV6InterfaceId
         OCTET STRING,
      er1646v2VEthPppOEIpV6MF
         Integer32,
      er1646v2VEthPppOEIpV6IcmpMessagesNoRoute
         INTEGER,
      er1646v2VEthPppOEIpV6IcmpMessagesBeyondScope
         INTEGER,
      er1646v2VEthPppOEIpV6IcmpMessagesAddressUnreachable
         INTEGER,
      er1646v2VEthPppOEIpV6IcmpMessagesPortUnreachable
         INTEGER,
      er1646v2VEthPppOEIpV6IcmpMessagesPacketTooBig
         INTEGER,
      er1646v2VEthPppOEIpV6IcmpMessagesHopLimitExceeded
         INTEGER,
      er1646v2VEthPppOEIpV6IcmpMessagesFragTimeExceeded
         INTEGER,
      er1646v2VEthPppOEIpV6IcmpMessagesHeaderFieldErr
         INTEGER,
      er1646v2VEthPppOEIpV6IcmpMessagesOptionUnrecognized
         INTEGER,
      er1646v2VEthPppOEIpV6IcmpMessagesRedirect
         INTEGER,
      er1646v2VEthPppOEPppLnkMOperation
         INTEGER,
      er1646v2VEthPppOEPppLnkMInterval
         TimeTicks,
      er1646v2VEthPppOEPppLnkMRepTimeOut
         TimeTicks,
      er1646v2VEthPppOEPppLnkMFailsPrmt
         Integer32,
      er1646v2VEthPppOEPppAuthentication
         INTEGER,
      er1646v2VEthPppOEPppAuthenPeriod
         TimeTicks,
      er1646v2VEthPppOEPppSessionName
         DisplayString,
      er1646v2VEthPppOEPppSessionSecret
         DisplayString,
      er1646v2VEthPppOEPppEncModeSessionSecret
         INTEGER,
      er1646v2VEthPppOEPppEncSessionSecret
         DisplayString,
      er1646v2VEthPppOEPppServiceName
         DisplayString
      }

er1646v2VEthPppOEActions OBJECT-TYPE
   SYNTAX      VariableLengthTableActions
   MAX-ACCESS  read-write
   STATUS      current
   DESCRIPTION
      "By way of this field, some manipulations
       on this table may be performed."
   ::= {er1646v2VEthPppOEEntry 2}

er1646v2VEthPppOEGlobalIx OBJECT-TYPE
   SYNTAX      GlobalIndex
   MAX-ACCESS  not-accessible
   STATUS      current
   DESCRIPTION
      "The value of the tlsCntTreeGlobalIndex of the MANAGED OBJECT."
   ::= {er1646v2VEthPppOEEntry 10}

er1646v2VEthPppOETableIx OBJECT-TYPE
   SYNTAX      TableIndex
   MAX-ACCESS  not-accessible
   STATUS      current
   DESCRIPTION
      ""
   ::= {er1646v2VEthPppOEEntry 11}

er1646v2VEthPppOEName OBJECT-TYPE
   SYNTAX      DisplayString
   MAX-ACCESS  read-write
   STATUS      current
   DESCRIPTION
      "Path: virtualEthernet.editConf.pppoEClient.name"
   ::= {er1646v2VEthPppOEEntry 16777216}

er1646v2VEthPppOERemark OBJECT-TYPE
   SYNTAX      DisplayString
   MAX-ACCESS  read-write
   STATUS      current
   DESCRIPTION
      "Path: virtualEthernet.editConf.pppoEClient.remark"
   ::= {er1646v2VEthPppOEEntry 1157627904}

er1646v2VEthPppOEAdminStatus OBJECT-TYPE
   SYNTAX      INTEGER
               {
               up (1),
               down (2)
               }
   MAX-ACCESS  read-write
   STATUS      current
   DESCRIPTION
      "Path: virtualEthernet.editConf.pppoEClient.adminStatus

       Possibilities:
               up   (1)
               down   (2)"
   ::= {er1646v2VEthPppOEEntry 33554432}

er1646v2VEthPppOEMode OBJECT-TYPE
   SYNTAX      INTEGER
               {
               routing (1),
               multilink (8),
               ipV6 (16),
               ipV6ipV4 (17)
               }
   MAX-ACCESS  read-write
   STATUS      current
   DESCRIPTION
      "Path: virtualEthernet.editConf.pppoEClient.mode

       Possibilities:
               routing   (1)
               multilink   (8)
               ipV6   (16)
               ipV6/ipV4   (17)"
   ::= {er1646v2VEthPppOEEntry 67108864}

er1646v2VEthPppOEIpVrfRouter OBJECT-TYPE
   SYNTAX      DisplayString
   MAX-ACCESS  read-write
   STATUS      current
   DESCRIPTION
      "Path: virtualEthernet.editConf.pppoEClient.ip.vrfRouter"
   ::= {er1646v2VEthPppOEEntry 53215232}

er1646v2VEthPppOEIpAdr OBJECT-TYPE
   SYNTAX      IpAddress
   MAX-ACCESS  read-write
   STATUS      current
   DESCRIPTION
      "Path: virtualEthernet.editConf.pppoEClient.ip.address"
   ::= {er1646v2VEthPppOEEntry 58261504}

er1646v2VEthPppOEIpNetm OBJECT-TYPE
   SYNTAX      IpAddress
   MAX-ACCESS  read-write
   STATUS      current
   DESCRIPTION
      "Path: virtualEthernet.editConf.pppoEClient.ip.netMask"
   ::= {er1646v2VEthPppOEEntry 58392576}

er1646v2VEthPppOEIpSNetName OBJECT-TYPE
   SYNTAX      INTEGER
               {
               slOPTg (0),
               corp (2),
               dmz (3),
               internet (1)
               }
   MAX-ACCESS  read-write
   STATUS      current
   DESCRIPTION
      "Path: virtualEthernet.editConf.pppoEClient.ip.sNet.name

       Possibilities:
               <OPT>   (0)
               corp   (2)
               dmz   (3)
               internet   (1)"
   ::= {er1646v2VEthPppOEEntry 53674240}

er1646v2VEthPppOEIpSNetCust OBJECT-TYPE
   SYNTAX      DisplayString
   MAX-ACCESS  read-write
   STATUS      current
   DESCRIPTION
      "Path: virtualEthernet.editConf.pppoEClient.ip.sNet.custom"
   ::= {er1646v2VEthPppOEEntry 53674496}

er1646v2VEthPppOEIpRem OBJECT-TYPE
   SYNTAX      IpAddress
   MAX-ACCESS  read-write
   STATUS      current
   DESCRIPTION
      "Path: virtualEthernet.editConf.pppoEClient.ip.remote"
   ::= {er1646v2VEthPppOEEntry 58458112}

er1646v2VEthPppOEIpUnnumbered OBJECT-TYPE
   SYNTAX      DisplayString
   MAX-ACCESS  read-write
   STATUS      current
   DESCRIPTION
      "Path: virtualEthernet.editConf.pppoEClient.ip.unnumbered"
   ::= {er1646v2VEthPppOEEntry 52625408}

er1646v2VEthPppOEIpGwPref OBJECT-TYPE
   SYNTAX      Integer32
   MAX-ACCESS  read-write
   STATUS      current
   DESCRIPTION
      "Path: virtualEthernet.editConf.pppoEClient.ip.gatewayPreference"
   ::= {er1646v2VEthPppOEEntry 52690944}

er1646v2VEthPppOEIpRsn OBJECT-TYPE
   SYNTAX      INTEGER
               {
               disabled (0),
               enabled (1)
               }
   MAX-ACCESS  read-write
   STATUS      current
   DESCRIPTION
      "Path: virtualEthernet.editConf.pppoEClient.ip.requestSubnet

       Possibilities:
               disabled   (0)
               enabled   (1)"
   ::= {er1646v2VEthPppOEEntry 56688640}

er1646v2VEthPppOEIpMtu OBJECT-TYPE
   SYNTAX      Integer32
   MAX-ACCESS  read-write
   STATUS      current
   DESCRIPTION
      "Path: virtualEthernet.editConf.pppoEClient.ip.mtu"
   ::= {er1646v2VEthPppOEEntry 52953088}

er1646v2VEthPppOEIpMssAdjust OBJECT-TYPE
   SYNTAX      INTEGER
               {
               disabled (0),
               auto (65536)
               }
   MAX-ACCESS  read-write
   STATUS      current
   DESCRIPTION
      "Path: virtualEthernet.editConf.pppoEClient.ip.mssAdjust

       Possibilities:
               disabled   (0)
               auto   (65536)"
   ::= {er1646v2VEthPppOEEntry 53280768}

er1646v2VEthPppOEIpRipMetric OBJECT-TYPE
   SYNTAX      Integer32
   MAX-ACCESS  read-write
   STATUS      current
   DESCRIPTION
      "Path: virtualEthernet.editConf.pppoEClient.ip.rip.metric"
   ::= {er1646v2VEthPppOEEntry 51712768}

er1646v2VEthPppOEIpRipMetricOut OBJECT-TYPE
   SYNTAX      Integer32
   MAX-ACCESS  read-write
   STATUS      current
   DESCRIPTION
      "Path: virtualEthernet.editConf.pppoEClient.ip.rip.metricOut"
   ::= {er1646v2VEthPppOEEntry 51713024}

er1646v2VEthPppOEIpRipMode OBJECT-TYPE
   SYNTAX      INTEGER
               {
               disabled (0),
               passive (1),
               active (2)
               }
   MAX-ACCESS  read-write
   STATUS      current
   DESCRIPTION
      "Path: virtualEthernet.editConf.pppoEClient.ip.rip.mode

       Possibilities:
               disabled   (0)
               passive   (1)
               active   (2)"
   ::= {er1646v2VEthPppOEEntry 51713280}

er1646v2VEthPppOEIpRipTxVer OBJECT-TYPE
   SYNTAX      INTEGER
               {
               rip1 (0),
               rip2 (1),
               rip1mcompatible (2)
               }
   MAX-ACCESS  read-write
   STATUS      current
   DESCRIPTION
      "Path: virtualEthernet.editConf.pppoEClient.ip.rip.txVersion

       Possibilities:
               rip1   (0)
               rip2   (1)
               rip1-compatible   (2)"
   ::= {er1646v2VEthPppOEEntry 51716864}

er1646v2VEthPppOEIpRipRxVer OBJECT-TYPE
   SYNTAX      INTEGER
               {
               rip1only (0),
               rip2only (1),
               rip12 (2)
               }
   MAX-ACCESS  read-write
   STATUS      current
   DESCRIPTION
      "Path: virtualEthernet.editConf.pppoEClient.ip.rip.rxVersion

       Possibilities:
               rip1only   (0)
               rip2only   (1)
               rip1&2   (2)"
   ::= {er1646v2VEthPppOEEntry 51717120}

er1646v2VEthPppOEIpRipSplitH OBJECT-TYPE
   SYNTAX      INTEGER
               {
               disabled (0),
               enabled (1),
               poisonedReverse (2)
               }
   MAX-ACCESS  read-write
   STATUS      current
   DESCRIPTION
      "Path: virtualEthernet.editConf.pppoEClient.ip.rip.splitHorizon

       Possibilities:
               disabled   (0)
               enabled   (1)
               poisonedReverse   (2)"
   ::= {er1646v2VEthPppOEEntry 51713792}

er1646v2VEthPppOEIpRipAuth OBJECT-TYPE
   SYNTAX      INTEGER
               {
               disabled (0),
               texts (1),
               md5 (2)
               }
   MAX-ACCESS  read-write
   STATUS      current
   DESCRIPTION
      "Path: virtualEthernet.editConf.pppoEClient.ip.rip.authentication

       Possibilities:
               disabled   (0)
               text    (1)
               md5   (2)"
   ::= {er1646v2VEthPppOEEntry 51712512}

er1646v2VEthPppOEIpRipFilter OBJECT-TYPE
   SYNTAX      DisplayString
   MAX-ACCESS  read-write
   STATUS      current
   DESCRIPTION
      "Path: virtualEthernet.editConf.pppoEClient.ip.rip.filter"
   ::= {er1646v2VEthPppOEEntry 51716096}

er1646v2VEthPppOEIpRipFilterIn OBJECT-TYPE
   SYNTAX      DisplayString
   MAX-ACCESS  read-write
   STATUS      current
   DESCRIPTION
      "Path: virtualEthernet.editConf.pppoEClient.ip.rip.filterIn"
   ::= {er1646v2VEthPppOEEntry 51716352}

er1646v2VEthPppOEIpRipClearNextHop OBJECT-TYPE
   SYNTAX      INTEGER
               {
               disabled (0),
               enabled (1)
               }
   MAX-ACCESS  read-write
   STATUS      current
   DESCRIPTION
      "Path: virtualEthernet.editConf.pppoEClient.ip.rip.clearNextHop

       Possibilities:
               disabled   (0)
               enabled   (1)"
   ::= {er1646v2VEthPppOEEntry 51708416}

er1646v2VEthPppOEIpAccPol OBJECT-TYPE
   SYNTAX      DisplayString
   MAX-ACCESS  read-write
   STATUS      current
   DESCRIPTION
      "Path: virtualEthernet.editConf.pppoEClient.ip.accessPolicy"
   ::= {er1646v2VEthPppOEEntry 53084160}

er1646v2VEthPppOEIpAB OBJECT-TYPE
   SYNTAX      DisplayString
   MAX-ACCESS  read-write
   STATUS      current
   DESCRIPTION
      "Path: virtualEthernet.editConf.pppoEClient.ip.trafficPolicy"
   ::= {er1646v2VEthPppOEEntry 51249152}

er1646v2VEthPppOEIpMA OBJECT-TYPE
   SYNTAX      INTEGER
               {
               disabled (0),
               enabled (1)
               }
   MAX-ACCESS  read-write
   STATUS      current
   DESCRIPTION
      "Path: virtualEthernet.editConf.pppoEClient.ip.mgmtAccess

       Possibilities:
               disabled   (0)
               enabled   (1)"
   ::= {er1646v2VEthPppOEEntry 51380224}

er1646v2VEthPppOEIpMF OBJECT-TYPE
   SYNTAX      Integer32
   MAX-ACCESS  read-write
   STATUS      current
   DESCRIPTION
      "Path: virtualEthernet.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1646v2VEthPppOEEntry 51445760}

er1646v2VEthPppOEIpDB OBJECT-TYPE
   SYNTAX      INTEGER
               {
               disabled (0),
               enabled (1)
               }
   MAX-ACCESS  read-write
   STATUS      current
   DESCRIPTION
      "Path: virtualEthernet.editConf.pppoEClient.ip.directedBroadcasts

       Possibilities:
               disabled   (0)
               enabled   (1)"
   ::= {er1646v2VEthPppOEEntry 51773440}

er1646v2VEthPppOEIpIR OBJECT-TYPE
   SYNTAX      INTEGER
               {
               disabled (0),
               enabled (1)
               }
   MAX-ACCESS  read-write
   STATUS      current
   DESCRIPTION
      "Path: virtualEthernet.editConf.pppoEClient.ip.icmpRedirects

       Possibilities:
               disabled   (0)
               enabled   (1)"
   ::= {er1646v2VEthPppOEEntry 52035584}

er1646v2VEthPppOEIpIgmp OBJECT-TYPE
   SYNTAX      INTEGER
               {
               disabled (0),
               proxy (1),
               router (2),
               v3Router (5)
               }
   MAX-ACCESS  read-write
   STATUS      current
   DESCRIPTION
      "Path: virtualEthernet.editConf.pppoEClient.ip.igmp

       Possibilities:
               disabled   (0)
               proxy   (1)
               router   (2)
               v3Router   (5)"
   ::= {er1646v2VEthPppOEEntry 52428800}

er1646v2VEthPppOEIpNN OBJECT-TYPE
   SYNTAX      DisplayString
   MAX-ACCESS  read-write
   STATUS      current
   DESCRIPTION
      "Path: virtualEthernet.editConf.pppoEClient.ip.nat"
   ::= {er1646v2VEthPppOEEntry 52101120}

er1646v2VEthPppOEIpPimMode OBJECT-TYPE
   SYNTAX      INTEGER
               {
               disabled (0),
               sparse (1),
               passive (2)
               }
   MAX-ACCESS  read-write
   STATUS      current
   DESCRIPTION
      "Path: virtualEthernet.editConf.pppoEClient.ip.pim.mode

       Possibilities:
               disabled   (0)
               sparse   (1)
               passive   (2)"
   ::= {er1646v2VEthPppOEEntry 53346560}

er1646v2VEthPppOEIpPimDrPriority OBJECT-TYPE
   SYNTAX      Counter32
   MAX-ACCESS  read-write
   STATUS      current
   DESCRIPTION
      "Path: virtualEthernet.editConf.pppoEClient.ip.pim.drPriority

       32 bit unsigned wrappable counter."
   ::= {er1646v2VEthPppOEEntry 53346816}

er1646v2VEthPppOEIpPimHelloTime OBJECT-TYPE
   SYNTAX      TimeTicks
   MAX-ACCESS  read-write
   STATUS      current
   DESCRIPTION
      "Path: virtualEthernet.editConf.pppoEClient.ip.pim.helloTime

       Time in centi-second."
   ::= {er1646v2VEthPppOEEntry 53347072}

er1646v2VEthPppOEIpPimPropagationDelay OBJECT-TYPE
   SYNTAX      TimeTicks
   MAX-ACCESS  read-write
   STATUS      current
   DESCRIPTION
      "Path: virtualEthernet.editConf.pppoEClient.ip.pim.propagationDelay

       Time in centi-second."
   ::= {er1646v2VEthPppOEEntry 53347328}

er1646v2VEthPppOEIpPimOverrideInterval OBJECT-TYPE
   SYNTAX      TimeTicks
   MAX-ACCESS  read-write
   STATUS      current
   DESCRIPTION
      "Path: virtualEthernet.editConf.pppoEClient.ip.pim.overrideInterval

       Time in centi-second."
   ::= {er1646v2VEthPppOEEntry 53347584}

er1646v2VEthPppOEIpPimBsrBorder OBJECT-TYPE
   SYNTAX      INTEGER
               {
               disabled (0),
               enabled (1)
               }
   MAX-ACCESS  read-write
   STATUS      current
   DESCRIPTION
      "Path: virtualEthernet.editConf.pppoEClient.ip.pim.bsrBorder

       Possibilities:
               disabled   (0)
               enabled   (1)"
   ::= {er1646v2VEthPppOEEntry 53347840}

er1646v2VEthPppOEIpPimTtlThreshold OBJECT-TYPE
   SYNTAX      Integer32
   MAX-ACCESS  read-write
   STATUS      current
   DESCRIPTION
      "Path: virtualEthernet.editConf.pppoEClient.ip.pim.ttlThreshold"
   ::= {er1646v2VEthPppOEEntry 53348096}

er1646v2VEthPppOEIpIMNetworkUnreachable OBJECT-TYPE
   SYNTAX      INTEGER
               {
               disabled (0),
               enabled (1)
               }
   MAX-ACCESS  read-write
   STATUS      current
   DESCRIPTION
      "Path: virtualEthernet.editConf.pppoEClient.ip.icmpMessages.networkUnreachable

       Possibilities:
               disabled   (0)
               enabled   (1)"
   ::= {er1646v2VEthPppOEEntry 53412096}

er1646v2VEthPppOEIpIMHostUnreachable OBJECT-TYPE
   SYNTAX      INTEGER
               {
               disabled (0),
               enabled (1)
               }
   MAX-ACCESS  read-write
   STATUS      current
   DESCRIPTION
      "Path: virtualEthernet.editConf.pppoEClient.ip.icmpMessages.hostUnreachable

       Possibilities:
               disabled   (0)
               enabled   (1)"
   ::= {er1646v2VEthPppOEEntry 53412352}

er1646v2VEthPppOEIpIMProtocolUnreachable OBJECT-TYPE
   SYNTAX      INTEGER
               {
               disabled (0),
               enabled (1)
               }
   MAX-ACCESS  read-write
   STATUS      current
   DESCRIPTION
      "Path: virtualEthernet.editConf.pppoEClient.ip.icmpMessages.protocolUnreachable

       Possibilities:
               disabled   (0)
               enabled   (1)"
   ::= {er1646v2VEthPppOEEntry 53412608}

er1646v2VEthPppOEIpIMPortUnreachable OBJECT-TYPE
   SYNTAX      INTEGER
               {
               disabled (0),
               enabled (1)
               }
   MAX-ACCESS  read-write
   STATUS      current
   DESCRIPTION
      "Path: virtualEthernet.editConf.pppoEClient.ip.icmpMessages.portUnreachable

       Possibilities:
               disabled   (0)
               enabled   (1)"
   ::= {er1646v2VEthPppOEEntry 53412864}

er1646v2VEthPppOEIpIMMtuExceeded OBJECT-TYPE
   SYNTAX      INTEGER
               {
               disabled (0),
               enabled (1)
               }
   MAX-ACCESS  read-write
   STATUS      current
   DESCRIPTION
      "Path: virtualEthernet.editConf.pppoEClient.ip.icmpMessages.mtuExceeded

       Possibilities:
               disabled   (0)
               enabled   (1)"
   ::= {er1646v2VEthPppOEEntry 53413120}

er1646v2VEthPppOEIpIMAdminProhibited OBJECT-TYPE
   SYNTAX      INTEGER
               {
               disabled (0),
               enabled (1)
               }
   MAX-ACCESS  read-write
   STATUS      current
   DESCRIPTION
      "Path: virtualEthernet.editConf.pppoEClient.ip.icmpMessages.adminProhibited

       Possibilities:
               disabled   (0)
               enabled   (1)"
   ::= {er1646v2VEthPppOEEntry 53413376}

er1646v2VEthPppOEIpIMTtlExceeded OBJECT-TYPE
   SYNTAX      INTEGER
               {
               disabled (0),
               enabled (1)
               }
   MAX-ACCESS  read-write
   STATUS      current
   DESCRIPTION
      "Path: virtualEthernet.editConf.pppoEClient.ip.icmpMessages.ttlExceeded

       Possibilities:
               disabled   (0)
               enabled   (1)"
   ::= {er1646v2VEthPppOEEntry 53413632}

er1646v2VEthPppOEIpIMRedirect OBJECT-TYPE
   SYNTAX      INTEGER
               {
               disabled (0),
               enabled (1)
               }
   MAX-ACCESS  read-write
   STATUS      current
   DESCRIPTION
      "Path: virtualEthernet.editConf.pppoEClient.ip.icmpMessages.redirect

       Possibilities:
               disabled   (0)
               enabled   (1)"
   ::= {er1646v2VEthPppOEEntry 53413888}

er1646v2VEthPppOEIpV6VrfRouter OBJECT-TYPE
   SYNTAX      DisplayString
   MAX-ACCESS  read-write
   STATUS      current
   DESCRIPTION
      "Path: virtualEthernet.editConf.pppoEClient.ipV6.vrfRouter"
   ::= {er1646v2VEthPppOEEntry 704708608}

er1646v2VEthPppOEIpV6AddrAutoConfigNrDupAddrDetects OBJECT-TYPE
   SYNTAX      Integer32
   MAX-ACCESS  read-write
   STATUS      current
   DESCRIPTION
      "Path: virtualEthernet.editConf.pppoEClient.ipV6.addrAutoConfig.nrDupAddrDetects"
   ::= {er1646v2VEthPppOEEntry 704905472}

er1646v2VEthPppOEIpV6AddrAutoConfigAcceptRa OBJECT-TYPE
   SYNTAX      INTEGER
               {
               disabled (0),
               enabled (1)
               }
   MAX-ACCESS  read-write
   STATUS      current
   DESCRIPTION
      "Path: virtualEthernet.editConf.pppoEClient.ipV6.addrAutoConfig.acceptRa

       Possibilities:
               disabled   (0)
               enabled   (1)"
   ::= {er1646v2VEthPppOEEntry 704905728}

er1646v2VEthPppOEIpV6AddrAutoConfigAcceptRaRdnss OBJECT-TYPE
   SYNTAX      INTEGER
               {
               disabled (0),
               enabled (1)
               }
   MAX-ACCESS  read-write
   STATUS      current
   DESCRIPTION
      "Path: virtualEthernet.editConf.pppoEClient.ipV6.addrAutoConfig.acceptRaRdnss

       Possibilities:
               disabled   (0)
               enabled   (1)"
   ::= {er1646v2VEthPppOEEntry 704905984}

er1646v2VEthPppOEIpV6AddrAutoConfigAcceptRaDnssl OBJECT-TYPE
   SYNTAX      INTEGER
               {
               disabled (0),
               enabled (1)
               }
   MAX-ACCESS  read-write
   STATUS      current
   DESCRIPTION
      "Path: virtualEthernet.editConf.pppoEClient.ipV6.addrAutoConfig.acceptRaDnssl

       Possibilities:
               disabled   (0)
               enabled   (1)"
   ::= {er1646v2VEthPppOEEntry 704906240}

er1646v2VEthPppOEIpV6DefaultRoute OBJECT-TYPE
   SYNTAX      INTEGER
               {
               disabled (0),
               enabled (1)
               }
   MAX-ACCESS  read-write
   STATUS      current
   DESCRIPTION
      "Path: virtualEthernet.editConf.pppoEClient.ipV6.defaultRoute

       Possibilities:
               disabled   (0)
               enabled   (1)"
   ::= {er1646v2VEthPppOEEntry 704970752}

er1646v2VEthPppOEIpV6RaSend OBJECT-TYPE
   SYNTAX      INTEGER
               {
               disabled (0),
               enabled (1)
               }
   MAX-ACCESS  read-write
   STATUS      current
   DESCRIPTION
      "Path: virtualEthernet.editConf.pppoEClient.ipV6.ra.send

       Possibilities:
               disabled   (0)
               enabled   (1)"
   ::= {er1646v2VEthPppOEEntry 705036544}

er1646v2VEthPppOEIpV6RaMinInterval OBJECT-TYPE
   SYNTAX      TimeTicks
   MAX-ACCESS  read-write
   STATUS      current
   DESCRIPTION
      "Path: virtualEthernet.editConf.pppoEClient.ipV6.ra.minInterval

       Time in centi-second."
   ::= {er1646v2VEthPppOEEntry 705036800}

er1646v2VEthPppOEIpV6RaMaxInterval OBJECT-TYPE
   SYNTAX      TimeTicks
   MAX-ACCESS  read-write
   STATUS      current
   DESCRIPTION
      "Path: virtualEthernet.editConf.pppoEClient.ipV6.ra.maxInterval

       Time in centi-second."
   ::= {er1646v2VEthPppOEEntry 705037056}

er1646v2VEthPppOEIpV6RaManagedFlag OBJECT-TYPE
   SYNTAX      INTEGER
               {
               disabled (0),
               enabled (1)
               }
   MAX-ACCESS  read-write
   STATUS      current
   DESCRIPTION
      "Path: virtualEthernet.editConf.pppoEClient.ipV6.ra.managedFlag

       Possibilities:
               disabled   (0)
               enabled   (1)"
   ::= {er1646v2VEthPppOEEntry 705037312}

er1646v2VEthPppOEIpV6RaOtherConfFlag OBJECT-TYPE
   SYNTAX      INTEGER
               {
               disabled (0),
               enabled (1)
               }
   MAX-ACCESS  read-write
   STATUS      current
   DESCRIPTION
      "Path: virtualEthernet.editConf.pppoEClient.ipV6.ra.otherConfFlag

       Possibilities:
               disabled   (0)
               enabled   (1)"
   ::= {er1646v2VEthPppOEEntry 705037568}

er1646v2VEthPppOEIpV6RaLinkMtu OBJECT-TYPE
   SYNTAX      Integer32
   MAX-ACCESS  read-write
   STATUS      current
   DESCRIPTION
      "Path: virtualEthernet.editConf.pppoEClient.ipV6.ra.linkMtu"
   ::= {er1646v2VEthPppOEEntry 705037824}

er1646v2VEthPppOEIpV6RaReachableTime OBJECT-TYPE
   SYNTAX      TimeTicks
   MAX-ACCESS  read-write
   STATUS      current
   DESCRIPTION
      "Path: virtualEthernet.editConf.pppoEClient.ipV6.ra.reachableTime

       Time in centi-second."
   ::= {er1646v2VEthPppOEEntry 705038080}

er1646v2VEthPppOEIpV6RaRetransmitTime OBJECT-TYPE
   SYNTAX      TimeTicks
   MAX-ACCESS  read-write
   STATUS      current
   DESCRIPTION
      "Path: virtualEthernet.editConf.pppoEClient.ipV6.ra.retransmitTime

       Time in centi-second."
   ::= {er1646v2VEthPppOEEntry 705038336}

er1646v2VEthPppOEIpV6RaHopLimit OBJECT-TYPE
   SYNTAX      Integer32
   MAX-ACCESS  read-write
   STATUS      current
   DESCRIPTION
      "Path: virtualEthernet.editConf.pppoEClient.ipV6.ra.hopLimit"
   ::= {er1646v2VEthPppOEEntry 705038592}

er1646v2VEthPppOEIpV6RaDefaultLifeTime OBJECT-TYPE
   SYNTAX      TimeTicks
   MAX-ACCESS  read-write
   STATUS      current
   DESCRIPTION
      "Path: virtualEthernet.editConf.pppoEClient.ipV6.ra.defaultLifeTime

       Time in centi-second."
   ::= {er1646v2VEthPppOEEntry 705038848}

er1646v2VEthPppOEIpV6RaDnsOptionsRdnssLifeTime OBJECT-TYPE
   SYNTAX      TimeTicks
   MAX-ACCESS  read-write
   STATUS      current
   DESCRIPTION
      "Path: virtualEthernet.editConf.pppoEClient.ipV6.ra.dnsOptions.rdnss.lifeTime

       Time in centi-second."
   ::= {er1646v2VEthPppOEEntry 705039140}

er1646v2VEthPppOEIpV6RaDnsOptionsRdnssImportServers OBJECT-TYPE
   SYNTAX      INTEGER
               {
               disabled (0),
               enabled (1)
               }
   MAX-ACCESS  read-write
   STATUS      current
   DESCRIPTION
      "Path: virtualEthernet.editConf.pppoEClient.ipV6.ra.dnsOptions.rdnss.importServers

       Possibilities:
               disabled   (0)
               enabled   (1)"
   ::= {er1646v2VEthPppOEEntry 705039148}

er1646v2VEthPppOEIpV6RaDnsOptionsDnsslLifeTime OBJECT-TYPE
   SYNTAX      TimeTicks
   MAX-ACCESS  read-write
   STATUS      current
   DESCRIPTION
      "Path: virtualEthernet.editConf.pppoEClient.ipV6.ra.dnsOptions.dnssl.lifeTime

       Time in centi-second."
   ::= {er1646v2VEthPppOEEntry 705039172}

er1646v2VEthPppOEIpV6RaDnsOptionsDnsslImportDomains OBJECT-TYPE
   SYNTAX      INTEGER
               {
               disabled (0),
               enabled (1)
               }
   MAX-ACCESS  read-write
   STATUS      current
   DESCRIPTION
      "Path: virtualEthernet.editConf.pppoEClient.ipV6.ra.dnsOptions.dnssl.importDomains

       Possibilities:
               disabled   (0)
               enabled   (1)"
   ::= {er1646v2VEthPppOEEntry 705039180}

er1646v2VEthPppOEIpV6RsSend OBJECT-TYPE
   SYNTAX      INTEGER
               {
               disabled (0),
               enabled (1)
               }
   MAX-ACCESS  read-write
   STATUS      current
   DESCRIPTION
      "Path: virtualEthernet.editConf.pppoEClient.ipV6.rs.send

       Possibilities:
               disabled   (0)
               enabled   (1)"
   ::= {er1646v2VEthPppOEEntry 705954048}

er1646v2VEthPppOEIpV6RsMaxRandomDelay OBJECT-TYPE
   SYNTAX      TimeTicks
   MAX-ACCESS  read-write
   STATUS      current
   DESCRIPTION
      "Path: virtualEthernet.editConf.pppoEClient.ipV6.rs.maxRandomDelay

       Time in centi-second."
   ::= {er1646v2VEthPppOEEntry 705954304}

er1646v2VEthPppOEIpV6RsInterval OBJECT-TYPE
   SYNTAX      TimeTicks
   MAX-ACCESS  read-write
   STATUS      current
   DESCRIPTION
      "Path: virtualEthernet.editConf.pppoEClient.ipV6.rs.interval

       Time in centi-second."
   ::= {er1646v2VEthPppOEEntry 705954560}

er1646v2VEthPppOEIpV6RsMaxSolicitations OBJECT-TYPE
   SYNTAX      Integer32
   MAX-ACCESS  read-write
   STATUS      current
   DESCRIPTION
      "Path: virtualEthernet.editConf.pppoEClient.ipV6.rs.maxSolicitations"
   ::= {er1646v2VEthPppOEEntry 705954816}

er1646v2VEthPppOEIpV6TrafficPolicyInbound OBJECT-TYPE
   SYNTAX      DisplayString
   MAX-ACCESS  read-write
   STATUS      current
   DESCRIPTION
      "Path: virtualEthernet.editConf.pppoEClient.ipV6.trafficPolicy.inbound"
   ::= {er1646v2VEthPppOEEntry 705364224}

er1646v2VEthPppOEIpV6TrafficPolicyOutbound OBJECT-TYPE
   SYNTAX      DisplayString
   MAX-ACCESS  read-write
   STATUS      current
   DESCRIPTION
      "Path: virtualEthernet.editConf.pppoEClient.ipV6.trafficPolicy.outbound"
   ::= {er1646v2VEthPppOEEntry 705364480}

er1646v2VEthPppOEIpV6FirewallZone OBJECT-TYPE
   SYNTAX      DisplayString
   MAX-ACCESS  read-write
   STATUS      current
   DESCRIPTION
      "Path: virtualEthernet.editConf.pppoEClient.ipV6.firewall.zone"
   ::= {er1646v2VEthPppOEEntry 705429760}

er1646v2VEthPppOEIpV6DhcpClientAddrAC OBJECT-TYPE
   SYNTAX      INTEGER
               {
               disabled (0),
               enabled (1)
               }
   MAX-ACCESS  read-write
   STATUS      current
   DESCRIPTION
      "Path: virtualEthernet.editConf.pppoEClient.ipV6.dhcp.client.addrAutoConfig

       Possibilities:
               disabled   (0)
               enabled   (1)"
   ::= {er1646v2VEthPppOEEntry 705307648}

er1646v2VEthPppOEIpV6DhcpClientPrDelMode OBJECT-TYPE
   SYNTAX      INTEGER
               {
               disabled (0),
               enabled (1)
               }
   MAX-ACCESS  read-write
   STATUS      current
   DESCRIPTION
      "Path: virtualEthernet.editConf.pppoEClient.ipV6.dhcp.client.pd.mode

       Possibilities:
               disabled   (0)
               enabled   (1)"
   ::= {er1646v2VEthPppOEEntry 705308676}

er1646v2VEthPppOEIpV6DhcpClientPrDelPool OBJECT-TYPE
   SYNTAX      DisplayString
   MAX-ACCESS  read-write
   STATUS      current
   DESCRIPTION
      "Path: virtualEthernet.editConf.pppoEClient.ipV6.dhcp.client.pd.pool"
   ::= {er1646v2VEthPppOEEntry 705308680}

er1646v2VEthPppOEIpV6DhcpClientPrDelPdExclOpt OBJECT-TYPE
   SYNTAX      INTEGER
               {
               disabled (0),
               enabled (1)
               }
   MAX-ACCESS  read-write
   STATUS      current
   DESCRIPTION
      "Path: virtualEthernet.editConf.pppoEClient.ipV6.dhcp.client.pd.pdExclOpt

       Possibilities:
               disabled   (0)
               enabled   (1)"
   ::= {er1646v2VEthPppOEEntry 705308684}

er1646v2VEthPppOEIpV6DhcpClientDnsServerPref OBJECT-TYPE
   SYNTAX      Integer32
   MAX-ACCESS  read-write
   STATUS      current
   DESCRIPTION
      "Path: virtualEthernet.editConf.pppoEClient.ipV6.dhcp.client.dns.serverPref"
   ::= {er1646v2VEthPppOEEntry 705310724}

er1646v2VEthPppOEIpV6DhcpClientRapidCommit OBJECT-TYPE
   SYNTAX      INTEGER
               {
               disabled (0),
               enabled (1)
               }
   MAX-ACCESS  read-write
   STATUS      current
   DESCRIPTION
      "Path: virtualEthernet.editConf.pppoEClient.ipV6.dhcp.client.rapidCommit

       Possibilities:
               disabled   (0)
               enabled   (1)"
   ::= {er1646v2VEthPppOEEntry 705309696}

er1646v2VEthPppOEIpV6DhcpClientTimersSolTimeOut OBJECT-TYPE
   SYNTAX      TimeTicks
   MAX-ACCESS  read-write
   STATUS      current
   DESCRIPTION
      "Path: virtualEthernet.editConf.pppoEClient.ipV6.dhcp.client.timers.solTimeOut

       Time in centi-second."
   ::= {er1646v2VEthPppOEEntry 705311748}

er1646v2VEthPppOEIpV6DhcpClientTimersSolMaxRt OBJECT-TYPE
   SYNTAX      TimeTicks
   MAX-ACCESS  read-write
   STATUS      current
   DESCRIPTION
      "Path: virtualEthernet.editConf.pppoEClient.ipV6.dhcp.client.timers.solMaxRt

       Time in centi-second."
   ::= {er1646v2VEthPppOEEntry 705311752}

er1646v2VEthPppOEIpV6DhcpClientTimersInfoRefresh OBJECT-TYPE
   SYNTAX      TimeTicks
   MAX-ACCESS  read-write
   STATUS      current
   DESCRIPTION
      "Path: virtualEthernet.editConf.pppoEClient.ipV6.dhcp.client.timers.infoRefresh

       Time in centi-second."
   ::= {er1646v2VEthPppOEEntry 705311756}

er1646v2VEthPppOEIpV6DhcpServerMode OBJECT-TYPE
   SYNTAX      INTEGER
               {
               disabled (0),
               enabled (1)
               }
   MAX-ACCESS  read-write
   STATUS      current
   DESCRIPTION
      "Path: virtualEthernet.editConf.pppoEClient.ipV6.dhcp.server.mode

       Possibilities:
               disabled   (0)
               enabled   (1)"
   ::= {er1646v2VEthPppOEEntry 705315840}

er1646v2VEthPppOEIpV6DhcpServerPreference OBJECT-TYPE
   SYNTAX      Integer32
   MAX-ACCESS  read-write
   STATUS      current
   DESCRIPTION
      "Path: virtualEthernet.editConf.pppoEClient.ipV6.dhcp.server.preference"
   ::= {er1646v2VEthPppOEEntry 705316864}

er1646v2VEthPppOEIpV6DhcpServerPool OBJECT-TYPE
   SYNTAX      DisplayString
   MAX-ACCESS  read-write
   STATUS      current
   DESCRIPTION
      "Path: virtualEthernet.editConf.pppoEClient.ipV6.dhcp.server.pool"
   ::= {er1646v2VEthPppOEEntry 705317888}

er1646v2VEthPppOEIpV6DhcpServerRapidCommit OBJECT-TYPE
   SYNTAX      INTEGER
               {
               disabled (0),
               enabled (1)
               }
   MAX-ACCESS  read-write
   STATUS      current
   DESCRIPTION
      "Path: virtualEthernet.editConf.pppoEClient.ipV6.dhcp.server.rapidCommit

       Possibilities:
               disabled   (0)
               enabled   (1)"
   ::= {er1646v2VEthPppOEEntry 705318912}

er1646v2VEthPppOEIpV6DhcpServerTimersInfoRefresh OBJECT-TYPE
   SYNTAX      TimeTicks
   MAX-ACCESS  read-write
   STATUS      current
   DESCRIPTION
      "Path: virtualEthernet.editConf.pppoEClient.ipV6.dhcp.server.timers.infoRefresh

       Time in centi-second."
   ::= {er1646v2VEthPppOEEntry 705319940}

er1646v2VEthPppOEIpV6DhcpRelayMode OBJECT-TYPE
   SYNTAX      INTEGER
               {
               disabled (0),
               enabled (1)
               }
   MAX-ACCESS  read-write
   STATUS      current
   DESCRIPTION
      "Path: virtualEthernet.editConf.pppoEClient.ipV6.dhcp.relay.mode

       Possibilities:
               disabled   (0)
               enabled   (1)"
   ::= {er1646v2VEthPppOEEntry 705323040}

er1646v2VEthPppOEIpV6SendRedirect OBJECT-TYPE
   SYNTAX      INTEGER
               {
               disabled (0),
               enabled (1)
               }
   MAX-ACCESS  read-write
   STATUS      current
   DESCRIPTION
      "Path: virtualEthernet.editConf.pppoEClient.ipV6.sendRedirect

       Possibilities:
               disabled   (0)
               enabled   (1)"
   ::= {er1646v2VEthPppOEEntry 705101824}

er1646v2VEthPppOEIpV6LinkMtu OBJECT-TYPE
   SYNTAX      Integer32
   MAX-ACCESS  read-write
   STATUS      current
   DESCRIPTION
      "Path: virtualEthernet.editConf.pppoEClient.ipV6.linkMtu"
   ::= {er1646v2VEthPppOEEntry 705167360}

er1646v2VEthPppOEIpV6InterfaceId OBJECT-TYPE
   SYNTAX      OCTET STRING
   MAX-ACCESS  read-write
   STATUS      current
   DESCRIPTION
      "Path: virtualEthernet.editConf.pppoEClient.ipV6.interfaceId"
   ::= {er1646v2VEthPppOEEntry 705232896}

er1646v2VEthPppOEIpV6MF OBJECT-TYPE
   SYNTAX      Integer32
   MAX-ACCESS  read-write
   STATUS      current
   DESCRIPTION
      "Path: virtualEthernet.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2VEthPppOEEntry 705757184}

er1646v2VEthPppOEIpV6IcmpMessagesNoRoute OBJECT-TYPE
   SYNTAX      INTEGER
               {
               disabled (0),
               enabled (1)
               }
   MAX-ACCESS  read-write
   STATUS      current
   DESCRIPTION
      "Path: virtualEthernet.editConf.pppoEClient.ipV6.icmpMessages.noRoute

       Possibilities:
               disabled   (0)
               enabled   (1)"
   ::= {er1646v2VEthPppOEEntry 705822976}

er1646v2VEthPppOEIpV6IcmpMessagesBeyondScope OBJECT-TYPE
   SYNTAX      INTEGER
               {
               disabled (0),
               enabled (1)
               }
   MAX-ACCESS  read-write
   STATUS      current
   DESCRIPTION
      "Path: virtualEthernet.editConf.pppoEClient.ipV6.icmpMessages.beyondScope

       Possibilities:
               disabled   (0)
               enabled   (1)"
   ::= {er1646v2VEthPppOEEntry 705823488}

er1646v2VEthPppOEIpV6IcmpMessagesAddressUnreachable OBJECT-TYPE
   SYNTAX      INTEGER
               {
               disabled (0),
               enabled (1)
               }
   MAX-ACCESS  read-write
   STATUS      current
   DESCRIPTION
      "Path: virtualEthernet.editConf.pppoEClient.ipV6.icmpMessages.addressUnreachable

       Possibilities:
               disabled   (0)
               enabled   (1)"
   ::= {er1646v2VEthPppOEEntry 705823744}

er1646v2VEthPppOEIpV6IcmpMessagesPortUnreachable OBJECT-TYPE
   SYNTAX      INTEGER
               {
               disabled (0),
               enabled (1)
               }
   MAX-ACCESS  read-write
   STATUS      current
   DESCRIPTION
      "Path: virtualEthernet.editConf.pppoEClient.ipV6.icmpMessages.portUnreachable

       Possibilities:
               disabled   (0)
               enabled   (1)"
   ::= {er1646v2VEthPppOEEntry 705824000}

er1646v2VEthPppOEIpV6IcmpMessagesPacketTooBig OBJECT-TYPE
   SYNTAX      INTEGER
               {
               disabled (0),
               enabled (1)
               }
   MAX-ACCESS  read-write
   STATUS      current
   DESCRIPTION
      "Path: virtualEthernet.editConf.pppoEClient.ipV6.icmpMessages.packetTooBig

       Possibilities:
               disabled   (0)
               enabled   (1)"
   ::= {er1646v2VEthPppOEEntry 705825280}

er1646v2VEthPppOEIpV6IcmpMessagesHopLimitExceeded OBJECT-TYPE
   SYNTAX      INTEGER
               {
               disabled (0),
               enabled (1)
               }
   MAX-ACCESS  read-write
   STATUS      current
   DESCRIPTION
      "Path: virtualEthernet.editConf.pppoEClient.ipV6.icmpMessages.hopLimitExceeded

       Possibilities:
               disabled   (0)
               enabled   (1)"
   ::= {er1646v2VEthPppOEEntry 705827840}

er1646v2VEthPppOEIpV6IcmpMessagesFragTimeExceeded OBJECT-TYPE
   SYNTAX      INTEGER
               {
               disabled (0),
               enabled (1)
               }
   MAX-ACCESS  read-write
   STATUS      current
   DESCRIPTION
      "Path: virtualEthernet.editConf.pppoEClient.ipV6.icmpMessages.fragTimeExceeded

       Possibilities:
               disabled   (0)
               enabled   (1)"
   ::= {er1646v2VEthPppOEEntry 705828096}

er1646v2VEthPppOEIpV6IcmpMessagesHeaderFieldErr OBJECT-TYPE
   SYNTAX      INTEGER
               {
               disabled (0),
               enabled (1)
               }
   MAX-ACCESS  read-write
   STATUS      current
   DESCRIPTION
      "Path: virtualEthernet.editConf.pppoEClient.ipV6.icmpMessages.headerFieldErr

       Possibilities:
               disabled   (0)
               enabled   (1)"
   ::= {er1646v2VEthPppOEEntry 705830400}

er1646v2VEthPppOEIpV6IcmpMessagesOptionUnrecognized OBJECT-TYPE
   SYNTAX      INTEGER
               {
               disabled (0),
               enabled (1)
               }
   MAX-ACCESS  read-write
   STATUS      current
   DESCRIPTION
      "Path: virtualEthernet.editConf.pppoEClient.ipV6.icmpMessages.optionUnrecognized

       Possibilities:
               disabled   (0)
               enabled   (1)"
   ::= {er1646v2VEthPppOEEntry 705830912}

er1646v2VEthPppOEIpV6IcmpMessagesRedirect OBJECT-TYPE
   SYNTAX      INTEGER
               {
               disabled (0),
               enabled (1)
               }
   MAX-ACCESS  read-write
   STATUS      current
   DESCRIPTION
      "Path: virtualEthernet.editConf.pppoEClient.ipV6.icmpMessages.redirect

       Possibilities:
               disabled   (0)
               enabled   (1)"
   ::= {er1646v2VEthPppOEEntry 705832960}

er1646v2VEthPppOEPppLnkMOperation OBJECT-TYPE
   SYNTAX      INTEGER
               {
               disabled (0),
               enabled (1)
               }
   MAX-ACCESS  read-write
   STATUS      current
   DESCRIPTION
      "Path: virtualEthernet.editConf.pppoEClient.ppp.linkMonitoring.operation

       Possibilities:
               disabled   (0)
               enabled   (1)"
   ::= {er1646v2VEthPppOEEntry 251724032}

er1646v2VEthPppOEPppLnkMInterval OBJECT-TYPE
   SYNTAX      TimeTicks
   MAX-ACCESS  read-write
   STATUS      current
   DESCRIPTION
      "Path: virtualEthernet.editConf.pppoEClient.ppp.linkMonitoring.interval

       Time in centi-second."
   ::= {er1646v2VEthPppOEEntry 251724288}

er1646v2VEthPppOEPppLnkMRepTimeOut OBJECT-TYPE
   SYNTAX      TimeTicks
   MAX-ACCESS  read-write
   STATUS      current
   DESCRIPTION
      "Path: virtualEthernet.editConf.pppoEClient.ppp.linkMonitoring.replyTimeOut

       Time in centi-second."
   ::= {er1646v2VEthPppOEEntry 251724544}

er1646v2VEthPppOEPppLnkMFailsPrmt OBJECT-TYPE
   SYNTAX      Integer32
   MAX-ACCESS  read-write
   STATUS      current
   DESCRIPTION
      "Path: virtualEthernet.editConf.pppoEClient.ppp.linkMonitoring.failsPermitted"
   ::= {er1646v2VEthPppOEEntry 251724800}

er1646v2VEthPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: virtualEthernet.editConf.pppoEClient.ppp.authentication

       Possibilities:
               disabled   (0)
               chap   (1)
               pap   (2)
               chapOrPap   (3)
               msChap   (4)
               msChapV2   (5)"
   ::= {er1646v2VEthPppOEEntry 251789312}

er1646v2VEthPppOEPppAuthenPeriod OBJECT-TYPE
   SYNTAX      TimeTicks
   MAX-ACCESS  read-write
   STATUS      current
   DESCRIPTION
      "Path: virtualEthernet.editConf.pppoEClient.ppp.authenPeriod

       Time in centi-second."
   ::= {er1646v2VEthPppOEEntry 251854848}

er1646v2VEthPppOEPppSessionName OBJECT-TYPE
   SYNTAX      DisplayString
   MAX-ACCESS  read-write
   STATUS      current
   DESCRIPTION
      "Path: virtualEthernet.editConf.pppoEClient.ppp.sessionName"
   ::= {er1646v2VEthPppOEEntry 251985920}

er1646v2VEthPppOEPppSessionSecret OBJECT-TYPE
   SYNTAX      DisplayString
   MAX-ACCESS  read-write
   STATUS      current
   DESCRIPTION
      "Path: virtualEthernet.editConf.pppoEClient.ppp.sessionSecret"
   ::= {er1646v2VEthPppOEEntry 252051456}

er1646v2VEthPppOEPppEncModeSessionSecret OBJECT-TYPE
   SYNTAX      INTEGER
               {
               none (1),
               encrypt (2),
               encType1 (3),
               invalid (128)
               }
   MAX-ACCESS  read-write
   STATUS      current
   DESCRIPTION
      "Path: virtualEthernet.editConf.pppoEClient.ppp.encModeSessionSecret

       Possibilities:
               none   (1)
               encrypt   (2)
               encType1   (3)
               invalid   (128)"
   ::= {er1646v2VEthPppOEEntry 252182528}

er1646v2VEthPppOEPppEncSessionSecret OBJECT-TYPE
   SYNTAX      DisplayString
   MAX-ACCESS  read-write
   STATUS      current
   DESCRIPTION
      "Path: virtualEthernet.editConf.pppoEClient.ppp.encSessionSecret"
   ::= {er1646v2VEthPppOEEntry 252248064}

er1646v2VEthPppOEPppServiceName OBJECT-TYPE
   SYNTAX      DisplayString
   MAX-ACCESS  read-write
   STATUS      current
   DESCRIPTION
      "Path: virtualEthernet.editConf.pppoEClient.ppp.serviceName"
   ::= {er1646v2VEthPppOEEntry 252116992}

er1646v2VEthPppOEIpH OBJECT-TYPE
   SYNTAX      SEQUENCE OF Er1646v2VEthPppOEIpHEntry
   MAX-ACCESS  not-accessible
   STATUS      current
   DESCRIPTION
      ""
   ::= {er1646v2VEthPppOE 51314688}

er1646v2VEthPppOEIpHEntry OBJECT-TYPE
   SYNTAX      Er1646v2VEthPppOEIpHEntry
   MAX-ACCESS  not-accessible
   STATUS      current
   DESCRIPTION
      ""
   INDEX      { er1646v2VEthPppOEIpHGlobalIx,
                er1646v2VEthPppOETableIx,
                er1646v2VEthPppOEIpHTableIx }
   ::= {er1646v2VEthPppOEIpH 1}

Er1646v2VEthPppOEIpHEntry ::=
   SEQUENCE
      {
      er1646v2VEthPppOEIpHActions
         VariableLengthTableActions,
      er1646v2VEthPppOEIpHGlobalIx
         GlobalIndex,
      er1646v2VEthPppOEIpHTableIx
         TableIndex,
      er1646v2VEthPppOEIpHAddress
         IpAddress,
      er1646v2VEthPppOEIpHDhcpRelayOptionSubscriberId
         DisplayString
      }

er1646v2VEthPppOEIpHActions OBJECT-TYPE
   SYNTAX      VariableLengthTableActions
   MAX-ACCESS  read-write
   STATUS      current
   DESCRIPTION
      "By way of this field, some manipulations
       on this table may be performed."
   ::= {er1646v2VEthPppOEIpHEntry 2}

er1646v2VEthPppOEIpHGlobalIx OBJECT-TYPE
   SYNTAX      GlobalIndex
   MAX-ACCESS  not-accessible
   STATUS      current
   DESCRIPTION
      "The value of the tlsCntTreeGlobalIndex of the MANAGED OBJECT."
   ::= {er1646v2VEthPppOEIpHEntry 10}

er1646v2VEthPppOEIpHTableIx OBJECT-TYPE
   SYNTAX      TableIndex
   MAX-ACCESS  not-accessible
   STATUS      current
   DESCRIPTION
      ""
   ::= {er1646v2VEthPppOEIpHEntry 11}

er1646v2VEthPppOEIpHAddress OBJECT-TYPE
   SYNTAX      IpAddress
   MAX-ACCESS  read-write
   STATUS      current
   DESCRIPTION
      "Path: virtualEthernet.editConf.pppoEClient.ip.helpers.address"
   ::= {er1646v2VEthPppOEIpHEntry 16777216}

er1646v2VEthPppOEIpHDhcpRelayOptionSubscriberId OBJECT-TYPE
   SYNTAX      DisplayString
   MAX-ACCESS  read-write
   STATUS      current
   DESCRIPTION
      "Path: virtualEthernet.editConf.pppoEClient.ip.helpers.dhcpRelayOption.subscriberId"
   ::= {er1646v2VEthPppOEIpHEntry 33947648}

er1646v2VEthPppOEIpV6Addresses OBJECT-TYPE
   SYNTAX      SEQUENCE OF Er1646v2VEthPppOEIpV6AddressesEntry
   MAX-ACCESS  not-accessible
   STATUS      current
   DESCRIPTION
      ""
   ::= {er1646v2VEthPppOE 704839680}

er1646v2VEthPppOEIpV6AddressesEntry OBJECT-TYPE
   SYNTAX      Er1646v2VEthPppOEIpV6AddressesEntry
   MAX-ACCESS  not-accessible
   STATUS      current
   DESCRIPTION
      ""
   INDEX      { er1646v2VEthPppOEIpV6AddressesGlobalIx,
                er1646v2VEthPppOETableIx,
                er1646v2VEthPppOEIpV6AddressesTableIx }
   ::= {er1646v2VEthPppOEIpV6Addresses 1}

Er1646v2VEthPppOEIpV6AddressesEntry ::=
   SEQUENCE
      {
      er1646v2VEthPppOEIpV6AddressesActions
         VariableLengthTableActions,
      er1646v2VEthPppOEIpV6AddressesGlobalIx
         GlobalIndex,
      er1646v2VEthPppOEIpV6AddressesTableIx
         TableIndex,
      er1646v2VEthPppOEIpV6AddressesType
         INTEGER,
      er1646v2VEthPppOEIpV6AddressesAddress
         Ipv6Address,
      er1646v2VEthPppOEIpV6AddressesPrefixLength
         Integer32,
      er1646v2VEthPppOEIpV6AddressesGeneralPrefix
         DisplayString,
      er1646v2VEthPppOEIpV6AddressesRaSend
         INTEGER,
      er1646v2VEthPppOEIpV6AddressesRaOnLinkFlag
         INTEGER,
      er1646v2VEthPppOEIpV6AddressesRaAutoFlag
         INTEGER,
      er1646v2VEthPppOEIpV6AddressesRaValidLifeTime
         TimeTicks,
      er1646v2VEthPppOEIpV6AddressesRaValidLTMode
         INTEGER,
      er1646v2VEthPppOEIpV6AddressesRaPrefLifeTime
         TimeTicks,
      er1646v2VEthPppOEIpV6AddressesRaPrefLTMode
         INTEGER
      }

er1646v2VEthPppOEIpV6AddressesActions OBJECT-TYPE
   SYNTAX      VariableLengthTableActions
   MAX-ACCESS  read-write
   STATUS      current
   DESCRIPTION
      "By way of this field, some manipulations
       on this table may be performed."
   ::= {er1646v2VEthPppOEIpV6AddressesEntry 2}

er1646v2VEthPppOEIpV6AddressesGlobalIx OBJECT-TYPE
   SYNTAX      GlobalIndex
   MAX-ACCESS  not-accessible
   STATUS      current
   DESCRIPTION
      "The value of the tlsCntTreeGlobalIndex of the MANAGED OBJECT."
   ::= {er1646v2VEthPppOEIpV6AddressesEntry 10}

er1646v2VEthPppOEIpV6AddressesTableIx OBJECT-TYPE
   SYNTAX      TableIndex
   MAX-ACCESS  not-accessible
   STATUS      current
   DESCRIPTION
      ""
   ::= {er1646v2VEthPppOEIpV6AddressesEntry 11}

er1646v2VEthPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: virtualEthernet.editConf.pppoEClient.ipV6.addresses.type

       Possibilities:
               unicast   (0)
               eui64   (1)
               anycast   (2)
               linkLocal   (3)
               generalPrefix   (4)"
   ::= {er1646v2VEthPppOEIpV6AddressesEntry 50331648}

er1646v2VEthPppOEIpV6AddressesAddress OBJECT-TYPE
   SYNTAX      Ipv6Address
   MAX-ACCESS  read-write
   STATUS      current
   DESCRIPTION
      "Path: virtualEthernet.editConf.pppoEClient.ipV6.addresses.address

       ipv6 address"
   ::= {er1646v2VEthPppOEIpV6AddressesEntry 16777216}

er1646v2VEthPppOEIpV6AddressesPrefixLength OBJECT-TYPE
   SYNTAX      Integer32
   MAX-ACCESS  read-write
   STATUS      current
   DESCRIPTION
      "Path: virtualEthernet.editConf.pppoEClient.ipV6.addresses.prefixLength"
   ::= {er1646v2VEthPppOEIpV6AddressesEntry 33554432}

er1646v2VEthPppOEIpV6AddressesGeneralPrefix OBJECT-TYPE
   SYNTAX      DisplayString
   MAX-ACCESS  read-write
   STATUS      current
   DESCRIPTION
      "Path: virtualEthernet.editConf.pppoEClient.ipV6.addresses.generalPrefix"
   ::= {er1646v2VEthPppOEIpV6AddressesEntry 83886080}

er1646v2VEthPppOEIpV6AddressesRaSend OBJECT-TYPE
   SYNTAX      INTEGER
               {
               disabled (0),
               enabled (1)
               }
   MAX-ACCESS  read-write
   STATUS      current
   DESCRIPTION
      "Path: virtualEthernet.editConf.pppoEClient.ipV6.addresses.ra.send

       Possibilities:
               disabled   (0)
               enabled   (1)"
   ::= {er1646v2VEthPppOEIpV6AddressesEntry 67174400}

er1646v2VEthPppOEIpV6AddressesRaOnLinkFlag OBJECT-TYPE
   SYNTAX      INTEGER
               {
               disabled (0),
               enabled (1)
               }
   MAX-ACCESS  read-write
   STATUS      current
   DESCRIPTION
      "Path: virtualEthernet.editConf.pppoEClient.ipV6.addresses.ra.onLinkFlag

       Possibilities:
               disabled   (0)
               enabled   (1)"
   ::= {er1646v2VEthPppOEIpV6AddressesEntry 67371008}

er1646v2VEthPppOEIpV6AddressesRaAutoFlag OBJECT-TYPE
   SYNTAX      INTEGER
               {
               disabled (0),
               enabled (1)
               }
   MAX-ACCESS  read-write
   STATUS      current
   DESCRIPTION
      "Path: virtualEthernet.editConf.pppoEClient.ipV6.addresses.ra.autonomousFlag

       Possibilities:
               disabled   (0)
               enabled   (1)"
   ::= {er1646v2VEthPppOEIpV6AddressesEntry 67567616}

er1646v2VEthPppOEIpV6AddressesRaValidLifeTime OBJECT-TYPE
   SYNTAX      TimeTicks
   MAX-ACCESS  read-write
   STATUS      current
   DESCRIPTION
      "Path: virtualEthernet.editConf.pppoEClient.ipV6.addresses.ra.validLifeTime

       Time in centi-second."
   ::= {er1646v2VEthPppOEIpV6AddressesEntry 67239936}

er1646v2VEthPppOEIpV6AddressesRaValidLTMode OBJECT-TYPE
   SYNTAX      INTEGER
               {
               fixed (0),
               infinite (2)
               }
   MAX-ACCESS  read-write
   STATUS      current
   DESCRIPTION
      "Path: virtualEthernet.editConf.pppoEClient.ipV6.addresses.ra.validLifeTimeMode

       Possibilities:
               fixed   (0)
               infinite   (2)"
   ::= {er1646v2VEthPppOEIpV6AddressesEntry 67305472}

er1646v2VEthPppOEIpV6AddressesRaPrefLifeTime OBJECT-TYPE
   SYNTAX      TimeTicks
   MAX-ACCESS  read-write
   STATUS      current
   DESCRIPTION
      "Path: virtualEthernet.editConf.pppoEClient.ipV6.addresses.ra.prefLifeTime

       Time in centi-second."
   ::= {er1646v2VEthPppOEIpV6AddressesEntry 67436544}

er1646v2VEthPppOEIpV6AddressesRaPrefLTMode OBJECT-TYPE
   SYNTAX      INTEGER
               {
               fixed (0),
               infinite (2)
               }
   MAX-ACCESS  read-write
   STATUS      current
   DESCRIPTION
      "Path: virtualEthernet.editConf.pppoEClient.ipV6.addresses.ra.prefLifeTimeMode

       Possibilities:
               fixed   (0)
               infinite   (2)"
   ::= {er1646v2VEthPppOEIpV6AddressesEntry 67502080}

er1646v2VEthPppOEIpV6RaDnsOptionsRdnssServers OBJECT-TYPE
   SYNTAX      SEQUENCE OF Er1646v2VEthPppOEIpV6RaDnsOptionsRdnssServersEntry
   MAX-ACCESS  not-accessible
   STATUS      current
   DESCRIPTION
      ""
   ::= {er1646v2VEthPppOE 705039144}

er1646v2VEthPppOEIpV6RaDnsOptionsRdnssServersEntry OBJECT-TYPE
   SYNTAX      Er1646v2VEthPppOEIpV6RaDnsOptionsRdnssServersEntry
   MAX-ACCESS  not-accessible
   STATUS      current
   DESCRIPTION
      ""
   INDEX      { er1646v2VEthPppOEIpV6RaDnsOptionsRdnssServersGlobalIx,
                er1646v2VEthPppOETableIx,
                er1646v2VEthPppOEIpV6RaDnsOptionsRdnssServersTableIx }
   ::= {er1646v2VEthPppOEIpV6RaDnsOptionsRdnssServers 1}

Er1646v2VEthPppOEIpV6RaDnsOptionsRdnssServersEntry ::=
   SEQUENCE
      {
      er1646v2VEthPppOEIpV6RaDnsOptionsRdnssServersActions
         VariableLengthTableActions,
      er1646v2VEthPppOEIpV6RaDnsOptionsRdnssServersGlobalIx
         GlobalIndex,
      er1646v2VEthPppOEIpV6RaDnsOptionsRdnssServersTableIx
         TableIndex,
      er1646v2VEthPppOEIpV6RaDnsOptionsRdnssServersAddress
         Ipv6Address
      }

er1646v2VEthPppOEIpV6RaDnsOptionsRdnssServersActions OBJECT-TYPE
   SYNTAX      VariableLengthTableActions
   MAX-ACCESS  read-write
   STATUS      current
   DESCRIPTION
      "By way of this field, some manipulations
       on this table may be performed."
   ::= {er1646v2VEthPppOEIpV6RaDnsOptionsRdnssServersEntry 2}

er1646v2VEthPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2VEthPppOEIpV6RaDnsOptionsRdnssServersEntry 10}

er1646v2VEthPppOEIpV6RaDnsOptionsRdnssServersTableIx OBJECT-TYPE
   SYNTAX      TableIndex
   MAX-ACCESS  not-accessible
   STATUS      current
   DESCRIPTION
      ""
   ::= {er1646v2VEthPppOEIpV6RaDnsOptionsRdnssServersEntry 11}

er1646v2VEthPppOEIpV6RaDnsOptionsRdnssServersAddress OBJECT-TYPE
   SYNTAX      Ipv6Address
   MAX-ACCESS  read-write
   STATUS      current
   DESCRIPTION
      "Path: virtualEthernet.editConf.pppoEClient.ipV6.ra.dnsOptions.rdnss.servers.address

       ipv6 address"
   ::= {er1646v2VEthPppOEIpV6RaDnsOptionsRdnssServersEntry 16777216}

er1646v2VEthPppOEIpV6RaDnsOptionsDnsslDomains OBJECT-TYPE
   SYNTAX      SEQUENCE OF Er1646v2VEthPppOEIpV6RaDnsOptionsDnsslDomainsEntry
   MAX-ACCESS  not-accessible
   STATUS      current
   DESCRIPTION
      ""
   ::= {er1646v2VEthPppOE 705039176}

er1646v2VEthPppOEIpV6RaDnsOptionsDnsslDomainsEntry OBJECT-TYPE
   SYNTAX      Er1646v2VEthPppOEIpV6RaDnsOptionsDnsslDomainsEntry
   MAX-ACCESS  not-accessible
   STATUS      current
   DESCRIPTION
      ""
   INDEX      { er1646v2VEthPppOEIpV6RaDnsOptionsDnsslDomainsGlobalIx,
                er1646v2VEthPppOETableIx,
                er1646v2VEthPppOEIpV6RaDnsOptionsDnsslDomainsTableIx }
   ::= {er1646v2VEthPppOEIpV6RaDnsOptionsDnsslDomains 1}

Er1646v2VEthPppOEIpV6RaDnsOptionsDnsslDomainsEntry ::=
   SEQUENCE
      {
      er1646v2VEthPppOEIpV6RaDnsOptionsDnsslDomainsActions
         VariableLengthTableActions,
      er1646v2VEthPppOEIpV6RaDnsOptionsDnsslDomainsGlobalIx
         GlobalIndex,
      er1646v2VEthPppOEIpV6RaDnsOptionsDnsslDomainsTableIx
         TableIndex,
      er1646v2VEthPppOEIpV6RaDnsOptionsDnsslDomainsName
         DisplayString
      }

er1646v2VEthPppOEIpV6RaDnsOptionsDnsslDomainsActions OBJECT-TYPE
   SYNTAX      VariableLengthTableActions
   MAX-ACCESS  read-write
   STATUS      current
   DESCRIPTION
      "By way of this field, some manipulations
       on this table may be performed."
   ::= {er1646v2VEthPppOEIpV6RaDnsOptionsDnsslDomainsEntry 2}

er1646v2VEthPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2VEthPppOEIpV6RaDnsOptionsDnsslDomainsEntry 10}

er1646v2VEthPppOEIpV6RaDnsOptionsDnsslDomainsTableIx OBJECT-TYPE
   SYNTAX      TableIndex
   MAX-ACCESS  not-accessible
   STATUS      current
   DESCRIPTION
      ""
   ::= {er1646v2VEthPppOEIpV6RaDnsOptionsDnsslDomainsEntry 11}

er1646v2VEthPppOEIpV6RaDnsOptionsDnsslDomainsName OBJECT-TYPE
   SYNTAX      DisplayString
   MAX-ACCESS  read-write
   STATUS      current
   DESCRIPTION
      "Path: virtualEthernet.editConf.pppoEClient.ipV6.ra.dnsOptions.dnssl.domains.name"
   ::= {er1646v2VEthPppOEIpV6RaDnsOptionsDnsslDomainsEntry 16777216}

er1646v2VEthPppOEIpV6DhcpClientUserClassOpt OBJECT-TYPE
   SYNTAX      SEQUENCE OF Er1646v2VEthPppOEIpV6DhcpClientUserClassOptEntry
   MAX-ACCESS  not-accessible
   STATUS      current
   DESCRIPTION
      ""
   ::= {er1646v2VEthPppOE 705312768}

er1646v2VEthPppOEIpV6DhcpClientUserClassOptEntry OBJECT-TYPE
   SYNTAX      Er1646v2VEthPppOEIpV6DhcpClientUserClassOptEntry
   MAX-ACCESS  not-accessible
   STATUS      current
   DESCRIPTION
      ""
   INDEX      { er1646v2VEthPppOEIpV6DhcpClientUserClassOptGlobalIx,
                er1646v2VEthPppOETableIx,
                er1646v2VEthPppOEIpV6DhcpClientUserClassOptTableIx }
   ::= {er1646v2VEthPppOEIpV6DhcpClientUserClassOpt 1}

Er1646v2VEthPppOEIpV6DhcpClientUserClassOptEntry ::=
   SEQUENCE
      {
      er1646v2VEthPppOEIpV6DhcpClientUserClassOptActions
         VariableLengthTableActions,
      er1646v2VEthPppOEIpV6DhcpClientUserClassOptGlobalIx
         GlobalIndex,
      er1646v2VEthPppOEIpV6DhcpClientUserClassOptTableIx
         TableIndex,
      er1646v2VEthPppOEIpV6DhcpClientUserClassOptValueAscii
         DisplayString,
      er1646v2VEthPppOEIpV6DhcpClientUserClassOptValueDecimal
         Integer32,
      er1646v2VEthPppOEIpV6DhcpClientUserClassOptValueHexData
         OCTET STRING
      }

er1646v2VEthPppOEIpV6DhcpClientUserClassOptActions OBJECT-TYPE
   SYNTAX      VariableLengthTableActions
   MAX-ACCESS  read-write
   STATUS      current
   DESCRIPTION
      "By way of this field, some manipulations
       on this table may be performed."
   ::= {er1646v2VEthPppOEIpV6DhcpClientUserClassOptEntry 2}

er1646v2VEthPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2VEthPppOEIpV6DhcpClientUserClassOptEntry 10}

er1646v2VEthPppOEIpV6DhcpClientUserClassOptTableIx OBJECT-TYPE
   SYNTAX      TableIndex
   MAX-ACCESS  not-accessible
   STATUS      current
   DESCRIPTION
      ""
   ::= {er1646v2VEthPppOEIpV6DhcpClientUserClassOptEntry 11}

er1646v2VEthPppOEIpV6DhcpClientUserClassOptValueAscii OBJECT-TYPE
   SYNTAX      DisplayString
   MAX-ACCESS  read-write
   STATUS      current
   DESCRIPTION
      "Path: virtualEthernet.editConf.pppoEClient.ipV6.dhcp.client.userClassOpt.value.ascii"
   ::= {er1646v2VEthPppOEIpV6DhcpClientUserClassOptEntry 16842752}

er1646v2VEthPppOEIpV6DhcpClientUserClassOptValueDecimal OBJECT-TYPE
   SYNTAX      Integer32
   MAX-ACCESS  read-write
   STATUS      current
   DESCRIPTION
      "Path: virtualEthernet.editConf.pppoEClient.ipV6.dhcp.client.userClassOpt.value.decimal"
   ::= {er1646v2VEthPppOEIpV6DhcpClientUserClassOptEntry 16908288}

er1646v2VEthPppOEIpV6DhcpClientUserClassOptValueHexData OBJECT-TYPE
   SYNTAX      OCTET STRING
   MAX-ACCESS  read-write
   STATUS      current
   DESCRIPTION
      "Path: virtualEthernet.editConf.pppoEClient.ipV6.dhcp.client.userClassOpt.value.hexData"
   ::= {er1646v2VEthPppOEIpV6DhcpClientUserClassOptEntry 16973824}

er1646v2VEthPppOEIpV6DhcpClientVendorCl OBJECT-TYPE
   SYNTAX      SEQUENCE OF Er1646v2VEthPppOEIpV6DhcpClientVendorClEntry
   MAX-ACCESS  not-accessible
   STATUS      current
   DESCRIPTION
      ""
   ::= {er1646v2VEthPppOE 705313792}

er1646v2VEthPppOEIpV6DhcpClientVendorClEntry OBJECT-TYPE
   SYNTAX      Er1646v2VEthPppOEIpV6DhcpClientVendorClEntry
   MAX-ACCESS  not-accessible
   STATUS      current
   DESCRIPTION
      ""
   INDEX      { er1646v2VEthPppOEIpV6DhcpClientVendorClGlobalIx,
                er1646v2VEthPppOETableIx,
                er1646v2VEthPppOEIpV6DhcpClientVendorClTableIx }
   ::= {er1646v2VEthPppOEIpV6DhcpClientVendorCl 1}

Er1646v2VEthPppOEIpV6DhcpClientVendorClEntry ::=
   SEQUENCE
      {
      er1646v2VEthPppOEIpV6DhcpClientVendorClActions
         VariableLengthTableActions,
      er1646v2VEthPppOEIpV6DhcpClientVendorClGlobalIx
         GlobalIndex,
      er1646v2VEthPppOEIpV6DhcpClientVendorClTableIx
         TableIndex,
      er1646v2VEthPppOEIpV6DhcpClientVendorClValueAscii
         DisplayString,
      er1646v2VEthPppOEIpV6DhcpClientVendorClValueDecimal
         Integer32,
      er1646v2VEthPppOEIpV6DhcpClientVendorClValueHexData
         OCTET STRING
      }

er1646v2VEthPppOEIpV6DhcpClientVendorClActions OBJECT-TYPE
   SYNTAX      VariableLengthTableActions
   MAX-ACCESS  read-write
   STATUS      current
   DESCRIPTION
      "By way of this field, some manipulations
       on this table may be performed."
   ::= {er1646v2VEthPppOEIpV6DhcpClientVendorClEntry 2}

er1646v2VEthPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2VEthPppOEIpV6DhcpClientVendorClEntry 10}

er1646v2VEthPppOEIpV6DhcpClientVendorClTableIx OBJECT-TYPE
   SYNTAX      TableIndex
   MAX-ACCESS  not-accessible
   STATUS      current
   DESCRIPTION
      ""
   ::= {er1646v2VEthPppOEIpV6DhcpClientVendorClEntry 11}

er1646v2VEthPppOEIpV6DhcpClientVendorClValueAscii OBJECT-TYPE
   SYNTAX      DisplayString
   MAX-ACCESS  read-write
   STATUS      current
   DESCRIPTION
      "Path: virtualEthernet.editConf.pppoEClient.ipV6.dhcp.client.vendorClassOpt.value.ascii"
   ::= {er1646v2VEthPppOEIpV6DhcpClientVendorClEntry 16842752}

er1646v2VEthPppOEIpV6DhcpClientVendorClValueDecimal OBJECT-TYPE
   SYNTAX      Integer32
   MAX-ACCESS  read-write
   STATUS      current
   DESCRIPTION
      "Path: virtualEthernet.editConf.pppoEClient.ipV6.dhcp.client.vendorClassOpt.value.decimal"
   ::= {er1646v2VEthPppOEIpV6DhcpClientVendorClEntry 16908288}

er1646v2VEthPppOEIpV6DhcpClientVendorClValueHexData OBJECT-TYPE
   SYNTAX      OCTET STRING
   MAX-ACCESS  read-write
   STATUS      current
   DESCRIPTION
      "Path: virtualEthernet.editConf.pppoEClient.ipV6.dhcp.client.vendorClassOpt.value.hexData"
   ::= {er1646v2VEthPppOEIpV6DhcpClientVendorClEntry 16973824}

er1646v2VEthPppOEIpV6DhcpRelayDestinations OBJECT-TYPE
   SYNTAX      SEQUENCE OF Er1646v2VEthPppOEIpV6DhcpRelayDestinationsEntry
   MAX-ACCESS  not-accessible
   STATUS      current
   DESCRIPTION
      ""
   ::= {er1646v2VEthPppOE 705323072}

er1646v2VEthPppOEIpV6DhcpRelayDestinationsEntry OBJECT-TYPE
   SYNTAX      Er1646v2VEthPppOEIpV6DhcpRelayDestinationsEntry
   MAX-ACCESS  not-accessible
   STATUS      current
   DESCRIPTION
      ""
   INDEX      { er1646v2VEthPppOEIpV6DhcpRelayDestinationsGlobalIx,
                er1646v2VEthPppOETableIx,
                er1646v2VEthPppOEIpV6DhcpRelayDestinationsTableIx }
   ::= {er1646v2VEthPppOEIpV6DhcpRelayDestinations 1}

Er1646v2VEthPppOEIpV6DhcpRelayDestinationsEntry ::=
   SEQUENCE
      {
      er1646v2VEthPppOEIpV6DhcpRelayDestinationsActions
         VariableLengthTableActions,
      er1646v2VEthPppOEIpV6DhcpRelayDestinationsGlobalIx
         GlobalIndex,
      er1646v2VEthPppOEIpV6DhcpRelayDestinationsTableIx
         TableIndex,
      er1646v2VEthPppOEIpV6DhcpRelayDestinationsAddress
         Ipv6Address,
      er1646v2VEthPppOEIpV6DhcpRelayDestinationsInterface
         DisplayString
      }

er1646v2VEthPppOEIpV6DhcpRelayDestinationsActions OBJECT-TYPE
   SYNTAX      VariableLengthTableActions
   MAX-ACCESS  read-write
   STATUS      current
   DESCRIPTION
      "By way of this field, some manipulations
       on this table may be performed."
   ::= {er1646v2VEthPppOEIpV6DhcpRelayDestinationsEntry 2}

er1646v2VEthPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2VEthPppOEIpV6DhcpRelayDestinationsEntry 10}

er1646v2VEthPppOEIpV6DhcpRelayDestinationsTableIx OBJECT-TYPE
   SYNTAX      TableIndex
   MAX-ACCESS  not-accessible
   STATUS      current
   DESCRIPTION
      ""
   ::= {er1646v2VEthPppOEIpV6DhcpRelayDestinationsEntry 11}

er1646v2VEthPppOEIpV6DhcpRelayDestinationsAddress OBJECT-TYPE
   SYNTAX      Ipv6Address
   MAX-ACCESS  read-write
   STATUS      current
   DESCRIPTION
      "Path: virtualEthernet.editConf.pppoEClient.ipV6.dhcp.relay.destinations.address

       ipv6 address"
   ::= {er1646v2VEthPppOEIpV6DhcpRelayDestinationsEntry 16777216}

er1646v2VEthPppOEIpV6DhcpRelayDestinationsInterface OBJECT-TYPE
   SYNTAX      DisplayString
   MAX-ACCESS  read-write
   STATUS      current
   DESCRIPTION
      "Path: virtualEthernet.editConf.pppoEClient.ipV6.dhcp.relay.destinations.interface"
   ::= {er1646v2VEthPppOEIpV6DhcpRelayDestinationsEntry 33554432}


er1646v2VEthDot1x OBJECT IDENTIFIER ::= {er1646v2VEth 191}

er1646v2VEthDot1xSSCTable OBJECT-TYPE
   SYNTAX      SEQUENCE OF Er1646v2VEthDot1xEntry
   MAX-ACCESS  not-accessible
   STATUS      current
   DESCRIPTION
      "ppp server name on interface"
   ::= {er1646v2VEthDot1x 1}

er1646v2VEthDot1xEntry OBJECT-TYPE
   SYNTAX      Er1646v2VEthDot1xEntry
   MAX-ACCESS  not-accessible
   STATUS      current
   DESCRIPTION
      ""
   INDEX      { er1646v2VEthDot1xGlobalIx }
   ::= {er1646v2VEthDot1xSSCTable 1}

Er1646v2VEthDot1xEntry ::=
   SEQUENCE
      {
      er1646v2VEthDot1xGlobalIx
         GlobalIndex,
      er1646v2VEthDot1xMode
         INTEGER,
      er1646v2VEthDot1xMaxHosts
         Integer32,
      er1646v2VEthDot1xReAuthentication
         INTEGER,
      er1646v2VEthDot1xReAuthPeriod
         TimeTicks,
      er1646v2VEthDot1xQuietPeriod
         TimeTicks,
      er1646v2VEthDot1xSupplTimeout
         TimeTicks,
      er1646v2VEthDot1xServerTimeout
         TimeTicks,
      er1646v2VEthDot1xMaxReqCount
         Integer32
      }

er1646v2VEthDot1xGlobalIx OBJECT-TYPE
   SYNTAX      GlobalIndex
   MAX-ACCESS  not-accessible
   STATUS      current
   DESCRIPTION
      "The value of the tlsCntTreeGlobalIndex of the MANAGED OBJECT."
   ::= {er1646v2VEthDot1xEntry 10}

er1646v2VEthDot1xMode OBJECT-TYPE
   SYNTAX      INTEGER
               {
               inactive (0),
               auto (1)
               }
   MAX-ACCESS  read-write
   STATUS      current
   DESCRIPTION
      "Path: virtualEthernet.editConf.dot1x.mode

       Possibilities:
               inactive   (0)
               auto   (1)"
   ::= {er1646v2VEthDot1xEntry 16777216}

er1646v2VEthDot1xMaxHosts OBJECT-TYPE
   SYNTAX      Integer32
   MAX-ACCESS  read-write
   STATUS      current
   DESCRIPTION
      "Path: virtualEthernet.editConf.dot1x.maxHosts"
   ::= {er1646v2VEthDot1xEntry 33554432}

er1646v2VEthDot1xReAuthentication OBJECT-TYPE
   SYNTAX      INTEGER
               {
               disabled (0),
               enabled (1)
               }
   MAX-ACCESS  read-write
   STATUS      current
   DESCRIPTION
      "Path: virtualEthernet.editConf.dot1x.reAuthentication

       Possibilities:
               disabled   (0)
               enabled   (1)"
   ::= {er1646v2VEthDot1xEntry 50331648}

er1646v2VEthDot1xReAuthPeriod OBJECT-TYPE
   SYNTAX      TimeTicks
   MAX-ACCESS  read-write
   STATUS      current
   DESCRIPTION
      "Path: virtualEthernet.editConf.dot1x.reAuthPeriod

       Time in centi-second."
   ::= {er1646v2VEthDot1xEntry 67108864}

er1646v2VEthDot1xQuietPeriod OBJECT-TYPE
   SYNTAX      TimeTicks
   MAX-ACCESS  read-write
   STATUS      current
   DESCRIPTION
      "Path: virtualEthernet.editConf.dot1x.quietPeriod

       Time in centi-second."
   ::= {er1646v2VEthDot1xEntry 83886080}

er1646v2VEthDot1xSupplTimeout OBJECT-TYPE
   SYNTAX      TimeTicks
   MAX-ACCESS  read-write
   STATUS      current
   DESCRIPTION
      "Path: virtualEthernet.editConf.dot1x.supplTimeout

       Time in centi-second."
   ::= {er1646v2VEthDot1xEntry 100663296}

er1646v2VEthDot1xServerTimeout OBJECT-TYPE
   SYNTAX      TimeTicks
   MAX-ACCESS  read-write
   STATUS      current
   DESCRIPTION
      "Path: virtualEthernet.editConf.dot1x.serverTimeout

       Time in centi-second."
   ::= {er1646v2VEthDot1xEntry 117440512}

er1646v2VEthDot1xMaxReqCount OBJECT-TYPE
   SYNTAX      Integer32
   MAX-ACCESS  read-write
   STATUS      current
   DESCRIPTION
      "Path: virtualEthernet.editConf.dot1x.maxReqCount"
   ::= {er1646v2VEthDot1xEntry 134217728}


er1646v2VEthMode OBJECT IDENTIFIER ::= {er1646v2VEth 29}

er1646v2VEthModeTable OBJECT-TYPE
   SYNTAX      SEQUENCE OF Er1646v2VEthModeEntry
   MAX-ACCESS  not-accessible
   STATUS      current
   DESCRIPTION
      "routing and/or bridging or ipV6 selection"
   ::= {er1646v2VEthMode 1}

er1646v2VEthModeEntry OBJECT-TYPE
   SYNTAX      Er1646v2VEthModeEntry
   MAX-ACCESS  not-accessible
   STATUS      current
   DESCRIPTION
      ""
   INDEX      { er1646v2VEthModeGlobalIx }
   ::= {er1646v2VEthModeTable 1}

Er1646v2VEthModeEntry ::=
   SEQUENCE
      {
      er1646v2VEthModeGlobalIx
         GlobalIndex,
      er1646v2VEthModeValue
         INTEGER
      }

er1646v2VEthModeGlobalIx OBJECT-TYPE
   SYNTAX      GlobalIndex
   MAX-ACCESS  not-accessible
   STATUS      current
   DESCRIPTION
      "The value of the tlsCntTreeGlobalIndex of the MANAGED OBJECT."
   ::= {er1646v2VEthModeEntry 10}

er1646v2VEthModeValue OBJECT-TYPE
   SYNTAX      INTEGER
               {
               bridging (0),
               routing (1),
               routingAndBridging (2),
               ipV6 (3),
               ipV6ipV4 (4)
               }
   MAX-ACCESS  read-write
   STATUS      current
   DESCRIPTION
      "Path: virtualEthernet.editConf.mode

       Possibilities:
               bridging   (0)
               routing   (1)
               routingAndBridging   (2)
               ipV6   (3)
               ipV6/ipV4   (4)"
   ::= {er1646v2VEthModeEntry 2147483648}


er1646v2VEthIpV6 OBJECT IDENTIFIER ::= {er1646v2VEth 15}

er1646v2VEthIpV6SSCTable OBJECT-TYPE
   SYNTAX      SEQUENCE OF Er1646v2VEthIpV6Entry
   MAX-ACCESS  not-accessible
   STATUS      current
   DESCRIPTION
      "IPv6 interface config parameters"
   ::= {er1646v2VEthIpV6 1}

er1646v2VEthIpV6Entry OBJECT-TYPE
   SYNTAX      Er1646v2VEthIpV6Entry
   MAX-ACCESS  not-accessible
   STATUS      current
   DESCRIPTION
      ""
   INDEX      { er1646v2VEthIpV6GlobalIx }
   ::= {er1646v2VEthIpV6SSCTable 1}

Er1646v2VEthIpV6Entry ::=
   SEQUENCE
      {
      er1646v2VEthIpV6GlobalIx
         GlobalIndex,
      er1646v2VEthIpV6VrfRouter
         DisplayString,
      er1646v2VEthIpV6AddrAutoConfigNrDupAddrDetects
         Integer32,
      er1646v2VEthIpV6AddrAutoConfigAcceptRa
         INTEGER,
      er1646v2VEthIpV6AddrAutoConfigAcceptRaRdnss
         INTEGER,
      er1646v2VEthIpV6AddrAutoConfigAcceptRaDnssl
         INTEGER,
      er1646v2VEthIpV6DefaultRoute
         INTEGER,
      er1646v2VEthIpV6RaSend
         INTEGER,
      er1646v2VEthIpV6RaMinInterval
         TimeTicks,
      er1646v2VEthIpV6RaMaxInterval
         TimeTicks,
      er1646v2VEthIpV6RaManagedFlag
         INTEGER,
      er1646v2VEthIpV6RaOtherConfFlag
         INTEGER,
      er1646v2VEthIpV6RaLinkMtu
         Integer32,
      er1646v2VEthIpV6RaReachableTime
         TimeTicks,
      er1646v2VEthIpV6RaRetransmitTime
         TimeTicks,
      er1646v2VEthIpV6RaHopLimit
         Integer32,
      er1646v2VEthIpV6RaDefaultLifeTime
         TimeTicks,
      er1646v2VEthIpV6RaDnsOptionsRdnssLifeTime
         TimeTicks,
      er1646v2VEthIpV6RaDnsOptionsRdnssImportServers
         INTEGER,
      er1646v2VEthIpV6RaDnsOptionsDnsslLifeTime
         TimeTicks,
      er1646v2VEthIpV6RaDnsOptionsDnsslImportDomains
         INTEGER,
      er1646v2VEthIpV6RsSend
         INTEGER,
      er1646v2VEthIpV6RsMaxRandomDelay
         TimeTicks,
      er1646v2VEthIpV6RsInterval
         TimeTicks,
      er1646v2VEthIpV6RsMaxSolicitations
         Integer32,
      er1646v2VEthIpV6TrafficPolicyInbound
         DisplayString,
      er1646v2VEthIpV6TrafficPolicyOutbound
         DisplayString,
      er1646v2VEthIpV6FirewallZone
         DisplayString,
      er1646v2VEthIpV6DhcpClientAddrAC
         INTEGER,
      er1646v2VEthIpV6DhcpClientPrDelMode
         INTEGER,
      er1646v2VEthIpV6DhcpClientPrDelPool
         DisplayString,
      er1646v2VEthIpV6DhcpClientPrDelPdExclOpt
         INTEGER,
      er1646v2VEthIpV6DhcpClientDnsServerPref
         Integer32,
      er1646v2VEthIpV6DhcpClientRapidCommit
         INTEGER,
      er1646v2VEthIpV6DhcpClientTimersSolTimeOut
         TimeTicks,
      er1646v2VEthIpV6DhcpClientTimersSolMaxRt
         TimeTicks,
      er1646v2VEthIpV6DhcpClientTimersInfoRefresh
         TimeTicks,
      er1646v2VEthIpV6DhcpServerMode
         INTEGER,
      er1646v2VEthIpV6DhcpServerPreference
         Integer32,
      er1646v2VEthIpV6DhcpServerPool
         DisplayString,
      er1646v2VEthIpV6DhcpServerRapidCommit
         INTEGER,
      er1646v2VEthIpV6DhcpServerTimersInfoRefresh
         TimeTicks,
      er1646v2VEthIpV6DhcpRelayMode
         INTEGER,
      er1646v2VEthIpV6SendRedirect
         INTEGER,
      er1646v2VEthIpV6LinkMtu
         Integer32,
      er1646v2VEthIpV6InterfaceId
         OCTET STRING,
      er1646v2VEthIpV6MF
         Integer32,
      er1646v2VEthIpV6IcmpMessagesNoRoute
         INTEGER,
      er1646v2VEthIpV6IcmpMessagesBeyondScope
         INTEGER,
      er1646v2VEthIpV6IcmpMessagesAddressUnreachable
         INTEGER,
      er1646v2VEthIpV6IcmpMessagesPortUnreachable
         INTEGER,
      er1646v2VEthIpV6IcmpMessagesPacketTooBig
         INTEGER,
      er1646v2VEthIpV6IcmpMessagesHopLimitExceeded
         INTEGER,
      er1646v2VEthIpV6IcmpMessagesFragTimeExceeded
         INTEGER,
      er1646v2VEthIpV6IcmpMessagesHeaderFieldErr
         INTEGER,
      er1646v2VEthIpV6IcmpMessagesOptionUnrecognized
         INTEGER,
      er1646v2VEthIpV6IcmpMessagesRedirect
         INTEGER
      }

er1646v2VEthIpV6GlobalIx OBJECT-TYPE
   SYNTAX      GlobalIndex
   MAX-ACCESS  not-accessible
   STATUS      current
   DESCRIPTION
      "The value of the tlsCntTreeGlobalIndex of the MANAGED OBJECT."
   ::= {er1646v2VEthIpV6Entry 10}

er1646v2VEthIpV6VrfRouter OBJECT-TYPE
   SYNTAX      DisplayString
   MAX-ACCESS  read-write
   STATUS      current
   DESCRIPTION
      "Path: virtualEthernet.editConf.ipV6.vrfRouter"
   ::= {er1646v2VEthIpV6Entry 16777216}

er1646v2VEthIpV6AddrAutoConfigNrDupAddrDetects OBJECT-TYPE
   SYNTAX      Integer32
   MAX-ACCESS  read-write
   STATUS      current
   DESCRIPTION
      "Path: virtualEthernet.editConf.ipV6.addrAutoConfig.nrDupAddrDetects"
   ::= {er1646v2VEthIpV6Entry 67174400}

er1646v2VEthIpV6AddrAutoConfigAcceptRa OBJECT-TYPE
   SYNTAX      INTEGER
               {
               disabled (0),
               enabled (1)
               }
   MAX-ACCESS  read-write
   STATUS      current
   DESCRIPTION
      "Path: virtualEthernet.editConf.ipV6.addrAutoConfig.acceptRa

       Possibilities:
               disabled   (0)
               enabled   (1)"
   ::= {er1646v2VEthIpV6Entry 67239936}

er1646v2VEthIpV6AddrAutoConfigAcceptRaRdnss OBJECT-TYPE
   SYNTAX      INTEGER
               {
               disabled (0),
               enabled (1)
               }
   MAX-ACCESS  read-write
   STATUS      current
   DESCRIPTION
      "Path: virtualEthernet.editConf.ipV6.addrAutoConfig.acceptRaRdnss

       Possibilities:
               disabled   (0)
               enabled   (1)"
   ::= {er1646v2VEthIpV6Entry 67305472}

er1646v2VEthIpV6AddrAutoConfigAcceptRaDnssl OBJECT-TYPE
   SYNTAX      INTEGER
               {
               disabled (0),
               enabled (1)
               }
   MAX-ACCESS  read-write
   STATUS      current
   DESCRIPTION
      "Path: virtualEthernet.editConf.ipV6.addrAutoConfig.acceptRaDnssl

       Possibilities:
               disabled   (0)
               enabled   (1)"
   ::= {er1646v2VEthIpV6Entry 67371008}

er1646v2VEthIpV6DefaultRoute OBJECT-TYPE
   SYNTAX      INTEGER
               {
               disabled (0),
               enabled (1)
               }
   MAX-ACCESS  read-write
   STATUS      current
   DESCRIPTION
      "Path: virtualEthernet.editConf.ipV6.defaultRoute

       Possibilities:
               disabled   (0)
               enabled   (1)"
   ::= {er1646v2VEthIpV6Entry 83886080}

er1646v2VEthIpV6RaSend OBJECT-TYPE
   SYNTAX      INTEGER
               {
               disabled (0),
               enabled (1)
               }
   MAX-ACCESS  read-write
   STATUS      current
   DESCRIPTION
      "Path: virtualEthernet.editConf.ipV6.ra.send

       Possibilities:
               disabled   (0)
               enabled   (1)"
   ::= {er1646v2VEthIpV6Entry 100728832}

er1646v2VEthIpV6RaMinInterval OBJECT-TYPE
   SYNTAX      TimeTicks
   MAX-ACCESS  read-write
   STATUS      current
   DESCRIPTION
      "Path: virtualEthernet.editConf.ipV6.ra.minInterval

       Time in centi-second."
   ::= {er1646v2VEthIpV6Entry 100794368}

er1646v2VEthIpV6RaMaxInterval OBJECT-TYPE
   SYNTAX      TimeTicks
   MAX-ACCESS  read-write
   STATUS      current
   DESCRIPTION
      "Path: virtualEthernet.editConf.ipV6.ra.maxInterval

       Time in centi-second."
   ::= {er1646v2VEthIpV6Entry 100859904}

er1646v2VEthIpV6RaManagedFlag OBJECT-TYPE
   SYNTAX      INTEGER
               {
               disabled (0),
               enabled (1)
               }
   MAX-ACCESS  read-write
   STATUS      current
   DESCRIPTION
      "Path: virtualEthernet.editConf.ipV6.ra.managedFlag

       Possibilities:
               disabled   (0)
               enabled   (1)"
   ::= {er1646v2VEthIpV6Entry 100925440}

er1646v2VEthIpV6RaOtherConfFlag OBJECT-TYPE
   SYNTAX      INTEGER
               {
               disabled (0),
               enabled (1)
               }
   MAX-ACCESS  read-write
   STATUS      current
   DESCRIPTION
      "Path: virtualEthernet.editConf.ipV6.ra.otherConfFlag

       Possibilities:
               disabled   (0)
               enabled   (1)"
   ::= {er1646v2VEthIpV6Entry 100990976}

er1646v2VEthIpV6RaLinkMtu OBJECT-TYPE
   SYNTAX      Integer32
   MAX-ACCESS  read-write
   STATUS      current
   DESCRIPTION
      "Path: virtualEthernet.editConf.ipV6.ra.linkMtu"
   ::= {er1646v2VEthIpV6Entry 101056512}

er1646v2VEthIpV6RaReachableTime OBJECT-TYPE
   SYNTAX      TimeTicks
   MAX-ACCESS  read-write
   STATUS      current
   DESCRIPTION
      "Path: virtualEthernet.editConf.ipV6.ra.reachableTime

       Time in centi-second."
   ::= {er1646v2VEthIpV6Entry 101122048}

er1646v2VEthIpV6RaRetransmitTime OBJECT-TYPE
   SYNTAX      TimeTicks
   MAX-ACCESS  read-write
   STATUS      current
   DESCRIPTION
      "Path: virtualEthernet.editConf.ipV6.ra.retransmitTime

       Time in centi-second."
   ::= {er1646v2VEthIpV6Entry 101187584}

er1646v2VEthIpV6RaHopLimit OBJECT-TYPE
   SYNTAX      Integer32
   MAX-ACCESS  read-write
   STATUS      current
   DESCRIPTION
      "Path: virtualEthernet.editConf.ipV6.ra.hopLimit"
   ::= {er1646v2VEthIpV6Entry 101253120}

er1646v2VEthIpV6RaDefaultLifeTime OBJECT-TYPE
   SYNTAX      TimeTicks
   MAX-ACCESS  read-write
   STATUS      current
   DESCRIPTION
      "Path: virtualEthernet.editConf.ipV6.ra.defaultLifeTime

       Time in centi-second."
   ::= {er1646v2VEthIpV6Entry 101318656}

er1646v2VEthIpV6RaDnsOptionsRdnssLifeTime OBJECT-TYPE
   SYNTAX      TimeTicks
   MAX-ACCESS  read-write
   STATUS      current
   DESCRIPTION
      "Path: virtualEthernet.editConf.ipV6.ra.dnsOptions.rdnss.lifeTime

       Time in centi-second."
   ::= {er1646v2VEthIpV6Entry 101393408}

er1646v2VEthIpV6RaDnsOptionsRdnssImportServers OBJECT-TYPE
   SYNTAX      INTEGER
               {
               disabled (0),
               enabled (1)
               }
   MAX-ACCESS  read-write
   STATUS      current
   DESCRIPTION
      "Path: virtualEthernet.editConf.ipV6.ra.dnsOptions.rdnss.importServers

       Possibilities:
               disabled   (0)
               enabled   (1)"
   ::= {er1646v2VEthIpV6Entry 101395456}

er1646v2VEthIpV6RaDnsOptionsDnsslLifeTime OBJECT-TYPE
   SYNTAX      TimeTicks
   MAX-ACCESS  read-write
   STATUS      current
   DESCRIPTION
      "Path: virtualEthernet.editConf.ipV6.ra.dnsOptions.dnssl.lifeTime

       Time in centi-second."
   ::= {er1646v2VEthIpV6Entry 101401600}

er1646v2VEthIpV6RaDnsOptionsDnsslImportDomains OBJECT-TYPE
   SYNTAX      INTEGER
               {
               disabled (0),
               enabled (1)
               }
   MAX-ACCESS  read-write
   STATUS      current
   DESCRIPTION
      "Path: virtualEthernet.editConf.ipV6.ra.dnsOptions.dnssl.importDomains

       Possibilities:
               disabled   (0)
               enabled   (1)"
   ::= {er1646v2VEthIpV6Entry 101403648}

er1646v2VEthIpV6RsSend OBJECT-TYPE
   SYNTAX      INTEGER
               {
               disabled (0),
               enabled (1)
               }
   MAX-ACCESS  read-write
   STATUS      current
   DESCRIPTION
      "Path: virtualEthernet.editConf.ipV6.rs.send

       Possibilities:
               disabled   (0)
               enabled   (1)"
   ::= {er1646v2VEthIpV6Entry 335609856}

er1646v2VEthIpV6RsMaxRandomDelay OBJECT-TYPE
   SYNTAX      TimeTicks
   MAX-ACCESS  read-write
   STATUS      current
   DESCRIPTION
      "Path: virtualEthernet.editConf.ipV6.rs.maxRandomDelay

       Time in centi-second."
   ::= {er1646v2VEthIpV6Entry 335675392}

er1646v2VEthIpV6RsInterval OBJECT-TYPE
   SYNTAX      TimeTicks
   MAX-ACCESS  read-write
   STATUS      current
   DESCRIPTION
      "Path: virtualEthernet.editConf.ipV6.rs.interval

       Time in centi-second."
   ::= {er1646v2VEthIpV6Entry 335740928}

er1646v2VEthIpV6RsMaxSolicitations OBJECT-TYPE
   SYNTAX      Integer32
   MAX-ACCESS  read-write
   STATUS      current
   DESCRIPTION
      "Path: virtualEthernet.editConf.ipV6.rs.maxSolicitations"
   ::= {er1646v2VEthIpV6Entry 335806464}

er1646v2VEthIpV6TrafficPolicyInbound OBJECT-TYPE
   SYNTAX      DisplayString
   MAX-ACCESS  read-write
   STATUS      current
   DESCRIPTION
      "Path: virtualEthernet.editConf.ipV6.trafficPolicy.inbound"
   ::= {er1646v2VEthIpV6Entry 184614912}

er1646v2VEthIpV6TrafficPolicyOutbound OBJECT-TYPE
   SYNTAX      DisplayString
   MAX-ACCESS  read-write
   STATUS      current
   DESCRIPTION
      "Path: virtualEthernet.editConf.ipV6.trafficPolicy.outbound"
   ::= {er1646v2VEthIpV6Entry 184680448}

er1646v2VEthIpV6FirewallZone OBJECT-TYPE
   SYNTAX      DisplayString
   MAX-ACCESS  read-write
   STATUS      current
   DESCRIPTION
      "Path: virtualEthernet.editConf.ipV6.firewall.zone"
   ::= {er1646v2VEthIpV6Entry 201392128}

er1646v2VEthIpV6DhcpClientAddrAC OBJECT-TYPE
   SYNTAX      INTEGER
               {
               disabled (0),
               enabled (1)
               }
   MAX-ACCESS  read-write
   STATUS      current
   DESCRIPTION
      "Path: virtualEthernet.editConf.ipV6.dhcp.client.addrAutoConfig

       Possibilities:
               disabled   (0)
               enabled   (1)"
   ::= {er1646v2VEthIpV6Entry 170131456}

er1646v2VEthIpV6DhcpClientPrDelMode OBJECT-TYPE
   SYNTAX      INTEGER
               {
               disabled (0),
               enabled (1)
               }
   MAX-ACCESS  read-write
   STATUS      current
   DESCRIPTION
      "Path: virtualEthernet.editConf.ipV6.dhcp.client.pd.mode

       Possibilities:
               disabled   (0)
               enabled   (1)"
   ::= {er1646v2VEthIpV6Entry 170394624}

er1646v2VEthIpV6DhcpClientPrDelPool OBJECT-TYPE
   SYNTAX      DisplayString
   MAX-ACCESS  read-write
   STATUS      current
   DESCRIPTION
      "Path: virtualEthernet.editConf.ipV6.dhcp.client.pd.pool"
   ::= {er1646v2VEthIpV6Entry 170395648}

er1646v2VEthIpV6DhcpClientPrDelPdExclOpt OBJECT-TYPE
   SYNTAX      INTEGER
               {
               disabled (0),
               enabled (1)
               }
   MAX-ACCESS  read-write
   STATUS      current
   DESCRIPTION
      "Path: virtualEthernet.editConf.ipV6.dhcp.client.pd.pdExclOpt

       Possibilities:
               disabled   (0)
               enabled   (1)"
   ::= {er1646v2VEthIpV6Entry 170396672}

er1646v2VEthIpV6DhcpClientDnsServerPref OBJECT-TYPE
   SYNTAX      Integer32
   MAX-ACCESS  read-write
   STATUS      current
   DESCRIPTION
      "Path: virtualEthernet.editConf.ipV6.dhcp.client.dns.serverPref"
   ::= {er1646v2VEthIpV6Entry 170918912}

er1646v2VEthIpV6DhcpClientRapidCommit OBJECT-TYPE
   SYNTAX      INTEGER
               {
               disabled (0),
               enabled (1)
               }
   MAX-ACCESS  read-write
   STATUS      current
   DESCRIPTION
      "Path: virtualEthernet.editConf.ipV6.dhcp.client.rapidCommit

       Possibilities:
               disabled   (0)
               enabled   (1)"
   ::= {er1646v2VEthIpV6Entry 170655744}

er1646v2VEthIpV6DhcpClientTimersSolTimeOut OBJECT-TYPE
   SYNTAX      TimeTicks
   MAX-ACCESS  read-write
   STATUS      current
   DESCRIPTION
      "Path: virtualEthernet.editConf.ipV6.dhcp.client.timers.solTimeOut

       Time in centi-second."
   ::= {er1646v2VEthIpV6Entry 171181056}

er1646v2VEthIpV6DhcpClientTimersSolMaxRt OBJECT-TYPE
   SYNTAX      TimeTicks
   MAX-ACCESS  read-write
   STATUS      current
   DESCRIPTION
      "Path: virtualEthernet.editConf.ipV6.dhcp.client.timers.solMaxRt

       Time in centi-second."
   ::= {er1646v2VEthIpV6Entry 171182080}

er1646v2VEthIpV6DhcpClientTimersInfoRefresh OBJECT-TYPE
   SYNTAX      TimeTicks
   MAX-ACCESS  read-write
   STATUS      current
   DESCRIPTION
      "Path: virtualEthernet.editConf.ipV6.dhcp.client.timers.infoRefresh

       Time in centi-second."
   ::= {er1646v2VEthIpV6Entry 171183104}

er1646v2VEthIpV6DhcpServerMode OBJECT-TYPE
   SYNTAX      INTEGER
               {
               disabled (0),
               enabled (1)
               }
   MAX-ACCESS  read-write
   STATUS      current
   DESCRIPTION
      "Path: virtualEthernet.editConf.ipV6.dhcp.server.mode

       Possibilities:
               disabled   (0)
               enabled   (1)"
   ::= {er1646v2VEthIpV6Entry 172228608}

er1646v2VEthIpV6DhcpServerPreference OBJECT-TYPE
   SYNTAX      Integer32
   MAX-ACCESS  read-write
   STATUS      current
   DESCRIPTION
      "Path: virtualEthernet.editConf.ipV6.dhcp.server.preference"
   ::= {er1646v2VEthIpV6Entry 172490752}

er1646v2VEthIpV6DhcpServerPool OBJECT-TYPE
   SYNTAX      DisplayString
   MAX-ACCESS  read-write
   STATUS      current
   DESCRIPTION
      "Path: virtualEthernet.editConf.ipV6.dhcp.server.pool"
   ::= {er1646v2VEthIpV6Entry 172752896}

er1646v2VEthIpV6DhcpServerRapidCommit OBJECT-TYPE
   SYNTAX      INTEGER
               {
               disabled (0),
               enabled (1)
               }
   MAX-ACCESS  read-write
   STATUS      current
   DESCRIPTION
      "Path: virtualEthernet.editConf.ipV6.dhcp.server.rapidCommit

       Possibilities:
               disabled   (0)
               enabled   (1)"
   ::= {er1646v2VEthIpV6Entry 173015040}

er1646v2VEthIpV6DhcpServerTimersInfoRefresh OBJECT-TYPE
   SYNTAX      TimeTicks
   MAX-ACCESS  read-write
   STATUS      current
   DESCRIPTION
      "Path: virtualEthernet.editConf.ipV6.dhcp.server.timers.infoRefresh

       Time in centi-second."
   ::= {er1646v2VEthIpV6Entry 173278208}

er1646v2VEthIpV6DhcpRelayMode OBJECT-TYPE
   SYNTAX      INTEGER
               {
               disabled (0),
               enabled (1)
               }
   MAX-ACCESS  read-write
   STATUS      current
   DESCRIPTION
      "Path: virtualEthernet.editConf.ipV6.dhcp.relay.mode

       Possibilities:
               disabled   (0)
               enabled   (1)"
   ::= {er1646v2VEthIpV6Entry 174071808}

er1646v2VEthIpV6SendRedirect OBJECT-TYPE
   SYNTAX      INTEGER
               {
               disabled (0),
               enabled (1)
               }
   MAX-ACCESS  read-write
   STATUS      current
   DESCRIPTION
      "Path: virtualEthernet.editConf.ipV6.sendRedirect

       Possibilities:
               disabled   (0)
               enabled   (1)"
   ::= {er1646v2VEthIpV6Entry 117440512}

er1646v2VEthIpV6LinkMtu OBJECT-TYPE
   SYNTAX      Integer32
   MAX-ACCESS  read-write
   STATUS      current
   DESCRIPTION
      "Path: virtualEthernet.editConf.ipV6.linkMtu"
   ::= {er1646v2VEthIpV6Entry 134217728}

er1646v2VEthIpV6InterfaceId OBJECT-TYPE
   SYNTAX      OCTET STRING
   MAX-ACCESS  read-write
   STATUS      current
   DESCRIPTION
      "Path: virtualEthernet.editConf.ipV6.interfaceId"
   ::= {er1646v2VEthIpV6Entry 150994944}

er1646v2VEthIpV6MF OBJECT-TYPE
   SYNTAX      Integer32
   MAX-ACCESS  read-write
   STATUS      current
   DESCRIPTION
      "Path: virtualEthernet.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1646v2VEthIpV6Entry 285212672}

er1646v2VEthIpV6IcmpMessagesNoRoute OBJECT-TYPE
   SYNTAX      INTEGER
               {
               disabled (0),
               enabled (1)
               }
   MAX-ACCESS  read-write
   STATUS      current
   DESCRIPTION
      "Path: virtualEthernet.editConf.ipV6.icmpMessages.noRoute

       Possibilities:
               disabled   (0)
               enabled   (1)"
   ::= {er1646v2VEthIpV6Entry 302055424}

er1646v2VEthIpV6IcmpMessagesBeyondScope OBJECT-TYPE
   SYNTAX      INTEGER
               {
               disabled (0),
               enabled (1)
               }
   MAX-ACCESS  read-write
   STATUS      current
   DESCRIPTION
      "Path: virtualEthernet.editConf.ipV6.icmpMessages.beyondScope

       Possibilities:
               disabled   (0)
               enabled   (1)"
   ::= {er1646v2VEthIpV6Entry 302186496}

er1646v2VEthIpV6IcmpMessagesAddressUnreachable OBJECT-TYPE
   SYNTAX      INTEGER
               {
               disabled (0),
               enabled (1)
               }
   MAX-ACCESS  read-write
   STATUS      current
   DESCRIPTION
      "Path: virtualEthernet.editConf.ipV6.icmpMessages.addressUnreachable

       Possibilities:
               disabled   (0)
               enabled   (1)"
   ::= {er1646v2VEthIpV6Entry 302252032}

er1646v2VEthIpV6IcmpMessagesPortUnreachable OBJECT-TYPE
   SYNTAX      INTEGER
               {
               disabled (0),
               enabled (1)
               }
   MAX-ACCESS  read-write
   STATUS      current
   DESCRIPTION
      "Path: virtualEthernet.editConf.ipV6.icmpMessages.portUnreachable

       Possibilities:
               disabled   (0)
               enabled   (1)"
   ::= {er1646v2VEthIpV6Entry 302317568}

er1646v2VEthIpV6IcmpMessagesPacketTooBig OBJECT-TYPE
   SYNTAX      INTEGER
               {
               disabled (0),
               enabled (1)
               }
   MAX-ACCESS  read-write
   STATUS      current
   DESCRIPTION
      "Path: virtualEthernet.editConf.ipV6.icmpMessages.packetTooBig

       Possibilities:
               disabled   (0)
               enabled   (1)"
   ::= {er1646v2VEthIpV6Entry 302645248}

er1646v2VEthIpV6IcmpMessagesHopLimitExceeded OBJECT-TYPE
   SYNTAX      INTEGER
               {
               disabled (0),
               enabled (1)
               }
   MAX-ACCESS  read-write
   STATUS      current
   DESCRIPTION
      "Path: virtualEthernet.editConf.ipV6.icmpMessages.hopLimitExceeded

       Possibilities:
               disabled   (0)
               enabled   (1)"
   ::= {er1646v2VEthIpV6Entry 303300608}

er1646v2VEthIpV6IcmpMessagesFragTimeExceeded OBJECT-TYPE
   SYNTAX      INTEGER
               {
               disabled (0),
               enabled (1)
               }
   MAX-ACCESS  read-write
   STATUS      current
   DESCRIPTION
      "Path: virtualEthernet.editConf.ipV6.icmpMessages.fragTimeExceeded

       Possibilities:
               disabled   (0)
               enabled   (1)"
   ::= {er1646v2VEthIpV6Entry 303366144}

er1646v2VEthIpV6IcmpMessagesHeaderFieldErr OBJECT-TYPE
   SYNTAX      INTEGER
               {
               disabled (0),
               enabled (1)
               }
   MAX-ACCESS  read-write
   STATUS      current
   DESCRIPTION
      "Path: virtualEthernet.editConf.ipV6.icmpMessages.headerFieldErr

       Possibilities:
               disabled   (0)
               enabled   (1)"
   ::= {er1646v2VEthIpV6Entry 303955968}

er1646v2VEthIpV6IcmpMessagesOptionUnrecognized OBJECT-TYPE
   SYNTAX      INTEGER
               {
               disabled (0),
               enabled (1)
               }
   MAX-ACCESS  read-write
   STATUS      current
   DESCRIPTION
      "Path: virtualEthernet.editConf.ipV6.icmpMessages.optionUnrecognized

       Possibilities:
               disabled   (0)
               enabled   (1)"
   ::= {er1646v2VEthIpV6Entry 304087040}

er1646v2VEthIpV6IcmpMessagesRedirect OBJECT-TYPE
   SYNTAX      INTEGER
               {
               disabled (0),
               enabled (1)
               }
   MAX-ACCESS  read-write
   STATUS      current
   DESCRIPTION
      "Path: virtualEthernet.editConf.ipV6.icmpMessages.redirect

       Possibilities:
               disabled   (0)
               enabled   (1)"
   ::= {er1646v2VEthIpV6Entry 304611328}

er1646v2VEthIpV6Addresses OBJECT-TYPE
   SYNTAX      SEQUENCE OF Er1646v2VEthIpV6AddressesEntry
   MAX-ACCESS  not-accessible
   STATUS      current
   DESCRIPTION
      ""
   ::= {er1646v2VEthIpV6 50331648}

er1646v2VEthIpV6AddressesEntry OBJECT-TYPE
   SYNTAX      Er1646v2VEthIpV6AddressesEntry
   MAX-ACCESS  not-accessible
   STATUS      current
   DESCRIPTION
      ""
   INDEX      { er1646v2VEthIpV6AddressesGlobalIx,
                er1646v2VEthIpV6AddressesTableIx }
   ::= {er1646v2VEthIpV6Addresses 1}

Er1646v2VEthIpV6AddressesEntry ::=
   SEQUENCE
      {
      er1646v2VEthIpV6AddressesActions
         VariableLengthTableActions,
      er1646v2VEthIpV6AddressesGlobalIx
         GlobalIndex,
      er1646v2VEthIpV6AddressesTableIx
         TableIndex,
      er1646v2VEthIpV6AddressesType
         INTEGER,
      er1646v2VEthIpV6AddressesAddress
         Ipv6Address,
      er1646v2VEthIpV6AddressesPrefixLength
         Integer32,
      er1646v2VEthIpV6AddressesGeneralPrefix
         DisplayString,
      er1646v2VEthIpV6AddressesRaSend
         INTEGER,
      er1646v2VEthIpV6AddressesRaOnLinkFlag
         INTEGER,
      er1646v2VEthIpV6AddressesRaAutoFlag
         INTEGER,
      er1646v2VEthIpV6AddressesRaValidLifeTime
         TimeTicks,
      er1646v2VEthIpV6AddressesRaValidLTMode
         INTEGER,
      er1646v2VEthIpV6AddressesRaPrefLifeTime
         TimeTicks,
      er1646v2VEthIpV6AddressesRaPrefLTMode
         INTEGER
      }

er1646v2VEthIpV6AddressesActions OBJECT-TYPE
   SYNTAX      VariableLengthTableActions
   MAX-ACCESS  read-write
   STATUS      current
   DESCRIPTION
      "By way of this field, some manipulations
       on this table may be performed."
   ::= {er1646v2VEthIpV6AddressesEntry 2}

er1646v2VEthIpV6AddressesGlobalIx OBJECT-TYPE
   SYNTAX      GlobalIndex
   MAX-ACCESS  not-accessible
   STATUS      current
   DESCRIPTION
      "The value of the tlsCntTreeGlobalIndex of the MANAGED OBJECT."
   ::= {er1646v2VEthIpV6AddressesEntry 10}

er1646v2VEthIpV6AddressesTableIx OBJECT-TYPE
   SYNTAX      TableIndex
   MAX-ACCESS  not-accessible
   STATUS      current
   DESCRIPTION
      ""
   ::= {er1646v2VEthIpV6AddressesEntry 11}

er1646v2VEthIpV6AddressesType OBJECT-TYPE
   SYNTAX      INTEGER
               {
               unicast (0),
               eui64 (1),
               anycast (2),
               linkLocal (3),
               generalPrefix (4)
               }
   MAX-ACCESS  read-write
   STATUS      current
   DESCRIPTION
      "Path: virtualEthernet.editConf.ipV6.addresses.type

       Possibilities:
               unicast   (0)
               eui64   (1)
               anycast   (2)
               linkLocal   (3)
               generalPrefix   (4)"
   ::= {er1646v2VEthIpV6AddressesEntry 50331648}

er1646v2VEthIpV6AddressesAddress OBJECT-TYPE
   SYNTAX      Ipv6Address
   MAX-ACCESS  read-write
   STATUS      current
   DESCRIPTION
      "Path: virtualEthernet.editConf.ipV6.addresses.address

       ipv6 address"
   ::= {er1646v2VEthIpV6AddressesEntry 16777216}

er1646v2VEthIpV6AddressesPrefixLength OBJECT-TYPE
   SYNTAX      Integer32
   MAX-ACCESS  read-write
   STATUS      current
   DESCRIPTION
      "Path: virtualEthernet.editConf.ipV6.addresses.prefixLength"
   ::= {er1646v2VEthIpV6AddressesEntry 33554432}

er1646v2VEthIpV6AddressesGeneralPrefix OBJECT-TYPE
   SYNTAX      DisplayString
   MAX-ACCESS  read-write
   STATUS      current
   DESCRIPTION
      "Path: virtualEthernet.editConf.ipV6.addresses.generalPrefix"
   ::= {er1646v2VEthIpV6AddressesEntry 83886080}

er1646v2VEthIpV6AddressesRaSend OBJECT-TYPE
   SYNTAX      INTEGER
               {
               disabled (0),
               enabled (1)
               }
   MAX-ACCESS  read-write
   STATUS      current
   DESCRIPTION
      "Path: virtualEthernet.editConf.ipV6.addresses.ra.send

       Possibilities:
               disabled   (0)
               enabled   (1)"
   ::= {er1646v2VEthIpV6AddressesEntry 67174400}

er1646v2VEthIpV6AddressesRaOnLinkFlag OBJECT-TYPE
   SYNTAX      INTEGER
               {
               disabled (0),
               enabled (1)
               }
   MAX-ACCESS  read-write
   STATUS      current
   DESCRIPTION
      "Path: virtualEthernet.editConf.ipV6.addresses.ra.onLinkFlag

       Possibilities:
               disabled   (0)
               enabled   (1)"
   ::= {er1646v2VEthIpV6AddressesEntry 67371008}

er1646v2VEthIpV6AddressesRaAutoFlag OBJECT-TYPE
   SYNTAX      INTEGER
               {
               disabled (0),
               enabled (1)
               }
   MAX-ACCESS  read-write
   STATUS      current
   DESCRIPTION
      "Path: virtualEthernet.editConf.ipV6.addresses.ra.autonomousFlag

       Possibilities:
               disabled   (0)
               enabled   (1)"
   ::= {er1646v2VEthIpV6AddressesEntry 67567616}

er1646v2VEthIpV6AddressesRaValidLifeTime OBJECT-TYPE
   SYNTAX      TimeTicks
   MAX-ACCESS  read-write
   STATUS      current
   DESCRIPTION
      "Path: virtualEthernet.editConf.ipV6.addresses.ra.validLifeTime

       Time in centi-second."
   ::= {er1646v2VEthIpV6AddressesEntry 67239936}

er1646v2VEthIpV6AddressesRaValidLTMode OBJECT-TYPE
   SYNTAX      INTEGER
               {
               fixed (0),
               infinite (2)
               }
   MAX-ACCESS  read-write
   STATUS      current
   DESCRIPTION
      "Path: virtualEthernet.editConf.ipV6.addresses.ra.validLifeTimeMode

       Possibilities:
               fixed   (0)
               infinite   (2)"
   ::= {er1646v2VEthIpV6AddressesEntry 67305472}

er1646v2VEthIpV6AddressesRaPrefLifeTime OBJECT-TYPE
   SYNTAX      TimeTicks
   MAX-ACCESS  read-write
   STATUS      current
   DESCRIPTION
      "Path: virtualEthernet.editConf.ipV6.addresses.ra.prefLifeTime

       Time in centi-second."
   ::= {er1646v2VEthIpV6AddressesEntry 67436544}

er1646v2VEthIpV6AddressesRaPrefLTMode OBJECT-TYPE
   SYNTAX      INTEGER
               {
               fixed (0),
               infinite (2)
               }
   MAX-ACCESS  read-write
   STATUS      current
   DESCRIPTION
      "Path: virtualEthernet.editConf.ipV6.addresses.ra.prefLifeTimeMode

       Possibilities:
               fixed   (0)
               infinite   (2)"
   ::= {er1646v2VEthIpV6AddressesEntry 67502080}

er1646v2VEthIpV6RaDnsOptionsRdnssServers OBJECT-TYPE
   SYNTAX      SEQUENCE OF Er1646v2VEthIpV6RaDnsOptionsRdnssServersEntry
   MAX-ACCESS  not-accessible
   STATUS      current
   DESCRIPTION
      ""
   ::= {er1646v2VEthIpV6 101394432}

er1646v2VEthIpV6RaDnsOptionsRdnssServersEntry OBJECT-TYPE
   SYNTAX      Er1646v2VEthIpV6RaDnsOptionsRdnssServersEntry
   MAX-ACCESS  not-accessible
   STATUS      current
   DESCRIPTION
      ""
   INDEX      { er1646v2VEthIpV6RaDnsOptionsRdnssServersGlobalIx,
                er1646v2VEthIpV6RaDnsOptionsRdnssServersTableIx }
   ::= {er1646v2VEthIpV6RaDnsOptionsRdnssServers 1}

Er1646v2VEthIpV6RaDnsOptionsRdnssServersEntry ::=
   SEQUENCE
      {
      er1646v2VEthIpV6RaDnsOptionsRdnssServersActions
         VariableLengthTableActions,
      er1646v2VEthIpV6RaDnsOptionsRdnssServersGlobalIx
         GlobalIndex,
      er1646v2VEthIpV6RaDnsOptionsRdnssServersTableIx
         TableIndex,
      er1646v2VEthIpV6RaDnsOptionsRdnssServersAddress
         Ipv6Address
      }

er1646v2VEthIpV6RaDnsOptionsRdnssServersActions OBJECT-TYPE
   SYNTAX      VariableLengthTableActions
   MAX-ACCESS  read-write
   STATUS      current
   DESCRIPTION
      "By way of this field, some manipulations
       on this table may be performed."
   ::= {er1646v2VEthIpV6RaDnsOptionsRdnssServersEntry 2}

er1646v2VEthIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1646v2VEthIpV6RaDnsOptionsRdnssServersEntry 10}

er1646v2VEthIpV6RaDnsOptionsRdnssServersTableIx OBJECT-TYPE
   SYNTAX      TableIndex
   MAX-ACCESS  not-accessible
   STATUS      current
   DESCRIPTION
      ""
   ::= {er1646v2VEthIpV6RaDnsOptionsRdnssServersEntry 11}

er1646v2VEthIpV6RaDnsOptionsRdnssServersAddress OBJECT-TYPE
   SYNTAX      Ipv6Address
   MAX-ACCESS  read-write
   STATUS      current
   DESCRIPTION
      "Path: virtualEthernet.editConf.ipV6.ra.dnsOptions.rdnss.servers.address

       ipv6 address"
   ::= {er1646v2VEthIpV6RaDnsOptionsRdnssServersEntry 16777216}

er1646v2VEthIpV6RaDnsOptionsDnsslDomains OBJECT-TYPE
   SYNTAX      SEQUENCE OF Er1646v2VEthIpV6RaDnsOptionsDnsslDomainsEntry
   MAX-ACCESS  not-accessible
   STATUS      current
   DESCRIPTION
      ""
   ::= {er1646v2VEthIpV6 101402624}

er1646v2VEthIpV6RaDnsOptionsDnsslDomainsEntry OBJECT-TYPE
   SYNTAX      Er1646v2VEthIpV6RaDnsOptionsDnsslDomainsEntry
   MAX-ACCESS  not-accessible
   STATUS      current
   DESCRIPTION
      ""
   INDEX      { er1646v2VEthIpV6RaDnsOptionsDnsslDomainsGlobalIx,
                er1646v2VEthIpV6RaDnsOptionsDnsslDomainsTableIx }
   ::= {er1646v2VEthIpV6RaDnsOptionsDnsslDomains 1}

Er1646v2VEthIpV6RaDnsOptionsDnsslDomainsEntry ::=
   SEQUENCE
      {
      er1646v2VEthIpV6RaDnsOptionsDnsslDomainsActions
         VariableLengthTableActions,
      er1646v2VEthIpV6RaDnsOptionsDnsslDomainsGlobalIx
         GlobalIndex,
      er1646v2VEthIpV6RaDnsOptionsDnsslDomainsTableIx
         TableIndex,
      er1646v2VEthIpV6RaDnsOptionsDnsslDomainsName
         DisplayString
      }

er1646v2VEthIpV6RaDnsOptionsDnsslDomainsActions OBJECT-TYPE
   SYNTAX      VariableLengthTableActions
   MAX-ACCESS  read-write
   STATUS      current
   DESCRIPTION
      "By way of this field, some manipulations
       on this table may be performed."
   ::= {er1646v2VEthIpV6RaDnsOptionsDnsslDomainsEntry 2}

er1646v2VEthIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1646v2VEthIpV6RaDnsOptionsDnsslDomainsEntry 10}

er1646v2VEthIpV6RaDnsOptionsDnsslDomainsTableIx OBJECT-TYPE
   SYNTAX      TableIndex
   MAX-ACCESS  not-accessible
   STATUS      current
   DESCRIPTION
      ""
   ::= {er1646v2VEthIpV6RaDnsOptionsDnsslDomainsEntry 11}

er1646v2VEthIpV6RaDnsOptionsDnsslDomainsName OBJECT-TYPE
   SYNTAX      DisplayString
   MAX-ACCESS  read-write
   STATUS      current
   DESCRIPTION
      "Path: virtualEthernet.editConf.ipV6.ra.dnsOptions.dnssl.domains.name"
   ::= {er1646v2VEthIpV6RaDnsOptionsDnsslDomainsEntry 16777216}

er1646v2VEthIpV6DhcpClientUserClassOpt OBJECT-TYPE
   SYNTAX      SEQUENCE OF Er1646v2VEthIpV6DhcpClientUserClassOptEntry
   MAX-ACCESS  not-accessible
   STATUS      current
   DESCRIPTION
      ""
   ::= {er1646v2VEthIpV6 171442176}

er1646v2VEthIpV6DhcpClientUserClassOptEntry OBJECT-TYPE
   SYNTAX      Er1646v2VEthIpV6DhcpClientUserClassOptEntry
   MAX-ACCESS  not-accessible
   STATUS      current
   DESCRIPTION
      ""
   INDEX      { er1646v2VEthIpV6DhcpClientUserClassOptGlobalIx,
                er1646v2VEthIpV6DhcpClientUserClassOptTableIx }
   ::= {er1646v2VEthIpV6DhcpClientUserClassOpt 1}

Er1646v2VEthIpV6DhcpClientUserClassOptEntry ::=
   SEQUENCE
      {
      er1646v2VEthIpV6DhcpClientUserClassOptActions
         VariableLengthTableActions,
      er1646v2VEthIpV6DhcpClientUserClassOptGlobalIx
         GlobalIndex,
      er1646v2VEthIpV6DhcpClientUserClassOptTableIx
         TableIndex,
      er1646v2VEthIpV6DhcpClientUserClassOptValueAscii
         DisplayString,
      er1646v2VEthIpV6DhcpClientUserClassOptValueDecimal
         Integer32,
      er1646v2VEthIpV6DhcpClientUserClassOptValueHexData
         OCTET STRING
      }

er1646v2VEthIpV6DhcpClientUserClassOptActions OBJECT-TYPE
   SYNTAX      VariableLengthTableActions
   MAX-ACCESS  read-write
   STATUS      current
   DESCRIPTION
      "By way of this field, some manipulations
       on this table may be performed."
   ::= {er1646v2VEthIpV6DhcpClientUserClassOptEntry 2}

er1646v2VEthIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1646v2VEthIpV6DhcpClientUserClassOptEntry 10}

er1646v2VEthIpV6DhcpClientUserClassOptTableIx OBJECT-TYPE
   SYNTAX      TableIndex
   MAX-ACCESS  not-accessible
   STATUS      current
   DESCRIPTION
      ""
   ::= {er1646v2VEthIpV6DhcpClientUserClassOptEntry 11}

er1646v2VEthIpV6DhcpClientUserClassOptValueAscii OBJECT-TYPE
   SYNTAX      DisplayString
   MAX-ACCESS  read-write
   STATUS      current
   DESCRIPTION
      "Path: virtualEthernet.editConf.ipV6.dhcp.client.userClassOpt.value.ascii"
   ::= {er1646v2VEthIpV6DhcpClientUserClassOptEntry 16842752}

er1646v2VEthIpV6DhcpClientUserClassOptValueDecimal OBJECT-TYPE
   SYNTAX      Integer32
   MAX-ACCESS  read-write
   STATUS      current
   DESCRIPTION
      "Path: virtualEthernet.editConf.ipV6.dhcp.client.userClassOpt.value.decimal"
   ::= {er1646v2VEthIpV6DhcpClientUserClassOptEntry 16908288}

er1646v2VEthIpV6DhcpClientUserClassOptValueHexData OBJECT-TYPE
   SYNTAX      OCTET STRING
   MAX-ACCESS  read-write
   STATUS      current
   DESCRIPTION
      "Path: virtualEthernet.editConf.ipV6.dhcp.client.userClassOpt.value.hexData"
   ::= {er1646v2VEthIpV6DhcpClientUserClassOptEntry 16973824}

er1646v2VEthIpV6DhcpClientVendorCl OBJECT-TYPE
   SYNTAX      SEQUENCE OF Er1646v2VEthIpV6DhcpClientVendorClEntry
   MAX-ACCESS  not-accessible
   STATUS      current
   DESCRIPTION
      ""
   ::= {er1646v2VEthIpV6 171704320}

er1646v2VEthIpV6DhcpClientVendorClEntry OBJECT-TYPE
   SYNTAX      Er1646v2VEthIpV6DhcpClientVendorClEntry
   MAX-ACCESS  not-accessible
   STATUS      current
   DESCRIPTION
      ""
   INDEX      { er1646v2VEthIpV6DhcpClientVendorClGlobalIx,
                er1646v2VEthIpV6DhcpClientVendorClTableIx }
   ::= {er1646v2VEthIpV6DhcpClientVendorCl 1}

Er1646v2VEthIpV6DhcpClientVendorClEntry ::=
   SEQUENCE
      {
      er1646v2VEthIpV6DhcpClientVendorClActions
         VariableLengthTableActions,
      er1646v2VEthIpV6DhcpClientVendorClGlobalIx
         GlobalIndex,
      er1646v2VEthIpV6DhcpClientVendorClTableIx
         TableIndex,
      er1646v2VEthIpV6DhcpClientVendorClValueAscii
         DisplayString,
      er1646v2VEthIpV6DhcpClientVendorClValueDecimal
         Integer32,
      er1646v2VEthIpV6DhcpClientVendorClValueHexData
         OCTET STRING
      }

er1646v2VEthIpV6DhcpClientVendorClActions OBJECT-TYPE
   SYNTAX      VariableLengthTableActions
   MAX-ACCESS  read-write
   STATUS      current
   DESCRIPTION
      "By way of this field, some manipulations
       on this table may be performed."
   ::= {er1646v2VEthIpV6DhcpClientVendorClEntry 2}

er1646v2VEthIpV6DhcpClientVendorClGlobalIx OBJECT-TYPE
   SYNTAX      GlobalIndex
   MAX-ACCESS  not-accessible
   STATUS      current
   DESCRIPTION
      "The value of the tlsCntTreeGlobalIndex of the MANAGED OBJECT."
   ::= {er1646v2VEthIpV6DhcpClientVendorClEntry 10}

er1646v2VEthIpV6DhcpClientVendorClTableIx OBJECT-TYPE
   SYNTAX      TableIndex
   MAX-ACCESS  not-accessible
   STATUS      current
   DESCRIPTION
      ""
   ::= {er1646v2VEthIpV6DhcpClientVendorClEntry 11}

er1646v2VEthIpV6DhcpClientVendorClValueAscii OBJECT-TYPE
   SYNTAX      DisplayString
   MAX-ACCESS  read-write
   STATUS      current
   DESCRIPTION
      "Path: virtualEthernet.editConf.ipV6.dhcp.client.vendorClassOpt.value.ascii"
   ::= {er1646v2VEthIpV6DhcpClientVendorClEntry 16842752}

er1646v2VEthIpV6DhcpClientVendorClValueDecimal OBJECT-TYPE
   SYNTAX      Integer32
   MAX-ACCESS  read-write
   STATUS      current
   DESCRIPTION
      "Path: virtualEthernet.editConf.ipV6.dhcp.client.vendorClassOpt.value.decimal"
   ::= {er1646v2VEthIpV6DhcpClientVendorClEntry 16908288}

er1646v2VEthIpV6DhcpClientVendorClValueHexData OBJECT-TYPE
   SYNTAX      OCTET STRING
   MAX-ACCESS  read-write
   STATUS      current
   DESCRIPTION
      "Path: virtualEthernet.editConf.ipV6.dhcp.client.vendorClassOpt.value.hexData"
   ::= {er1646v2VEthIpV6DhcpClientVendorClEntry 16973824}

er1646v2VEthIpV6DhcpRelayDestinations OBJECT-TYPE
   SYNTAX      SEQUENCE OF Er1646v2VEthIpV6DhcpRelayDestinationsEntry
   MAX-ACCESS  not-accessible
   STATUS      current
   DESCRIPTION
      ""
   ::= {er1646v2VEthIpV6 174080000}

er1646v2VEthIpV6DhcpRelayDestinationsEntry OBJECT-TYPE
   SYNTAX      Er1646v2VEthIpV6DhcpRelayDestinationsEntry
   MAX-ACCESS  not-accessible
   STATUS      current
   DESCRIPTION
      ""
   INDEX      { er1646v2VEthIpV6DhcpRelayDestinationsGlobalIx,
                er1646v2VEthIpV6DhcpRelayDestinationsTableIx }
   ::= {er1646v2VEthIpV6DhcpRelayDestinations 1}

Er1646v2VEthIpV6DhcpRelayDestinationsEntry ::=
   SEQUENCE
      {
      er1646v2VEthIpV6DhcpRelayDestinationsActions
         VariableLengthTableActions,
      er1646v2VEthIpV6DhcpRelayDestinationsGlobalIx
         GlobalIndex,
      er1646v2VEthIpV6DhcpRelayDestinationsTableIx
         TableIndex,
      er1646v2VEthIpV6DhcpRelayDestinationsAddress
         Ipv6Address,
      er1646v2VEthIpV6DhcpRelayDestinationsInterface
         DisplayString
      }

er1646v2VEthIpV6DhcpRelayDestinationsActions OBJECT-TYPE
   SYNTAX      VariableLengthTableActions
   MAX-ACCESS  read-write
   STATUS      current
   DESCRIPTION
      "By way of this field, some manipulations
       on this table may be performed."
   ::= {er1646v2VEthIpV6DhcpRelayDestinationsEntry 2}

er1646v2VEthIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1646v2VEthIpV6DhcpRelayDestinationsEntry 10}

er1646v2VEthIpV6DhcpRelayDestinationsTableIx OBJECT-TYPE
   SYNTAX      TableIndex
   MAX-ACCESS  not-accessible
   STATUS      current
   DESCRIPTION
      ""
   ::= {er1646v2VEthIpV6DhcpRelayDestinationsEntry 11}

er1646v2VEthIpV6DhcpRelayDestinationsAddress OBJECT-TYPE
   SYNTAX      Ipv6Address
   MAX-ACCESS  read-write
   STATUS      current
   DESCRIPTION
      "Path: virtualEthernet.editConf.ipV6.dhcp.relay.destinations.address

       ipv6 address"
   ::= {er1646v2VEthIpV6DhcpRelayDestinationsEntry 16777216}

er1646v2VEthIpV6DhcpRelayDestinationsInterface OBJECT-TYPE
   SYNTAX      DisplayString
   MAX-ACCESS  read-write
   STATUS      current
   DESCRIPTION
      "Path: virtualEthernet.editConf.ipV6.dhcp.relay.destinations.interface"
   ::= {er1646v2VEthIpV6DhcpRelayDestinationsEntry 33554432}


er1646v2VEthMacAddress OBJECT IDENTIFIER ::= {er1646v2VEth 201}

er1646v2VEthMacAddressSSCTable OBJECT-TYPE
   SYNTAX      SEQUENCE OF Er1646v2VEthMacAddressEntry
   MAX-ACCESS  not-accessible
   STATUS      current
   DESCRIPTION
      "Configurable MAC address of a Virtual Ethernet"
   ::= {er1646v2VEthMacAddress 1}

er1646v2VEthMacAddressEntry OBJECT-TYPE
   SYNTAX      Er1646v2VEthMacAddressEntry
   MAX-ACCESS  not-accessible
   STATUS      current
   DESCRIPTION
      ""
   INDEX      { er1646v2VEthMacAddressGlobalIx }
   ::= {er1646v2VEthMacAddressSSCTable 1}

Er1646v2VEthMacAddressEntry ::=
   SEQUENCE
      {
      er1646v2VEthMacAddressGlobalIx
         GlobalIndex,
      er1646v2VEthMacAddressUserMac
         OCTET STRING,
      er1646v2VEthMacAddressRandomMac
         Integer32
      }

er1646v2VEthMacAddressGlobalIx OBJECT-TYPE
   SYNTAX      GlobalIndex
   MAX-ACCESS  not-accessible
   STATUS      current
   DESCRIPTION
      "The value of the tlsCntTreeGlobalIndex of the MANAGED OBJECT."
   ::= {er1646v2VEthMacAddressEntry 10}

er1646v2VEthMacAddressUserMac OBJECT-TYPE
   SYNTAX      OCTET STRING
   MAX-ACCESS  read-write
   STATUS      current
   DESCRIPTION
      "Path: virtualEthernet.editConf.macAddress.userMac

       MAC address."
   ::= {er1646v2VEthMacAddressEntry 33554432}

er1646v2VEthMacAddressRandomMac OBJECT-TYPE
   SYNTAX      Integer32
   MAX-ACCESS  read-write
   STATUS      current
   DESCRIPTION
      "Path: virtualEthernet.editConf.macAddress.randomMac"
   ::= {er1646v2VEthMacAddressEntry 67108864}


er1646v2VEthSnmpIndexOffset OBJECT IDENTIFIER ::= {er1646v2VEth 268}

er1646v2VEthSnmpIndexOffsetTable OBJECT-TYPE
   SYNTAX      SEQUENCE OF Er1646v2VEthSnmpIndexOffsetEntry
   MAX-ACCESS  not-accessible
   STATUS      current
   DESCRIPTION
      "Preferred offset in the range of SNMP indices for this SWinst, 0 means automatic"
   ::= {er1646v2VEthSnmpIndexOffset 1}

er1646v2VEthSnmpIndexOffsetEntry OBJECT-TYPE
   SYNTAX      Er1646v2VEthSnmpIndexOffsetEntry
   MAX-ACCESS  not-accessible
   STATUS      current
   DESCRIPTION
      ""
   INDEX      { er1646v2VEthSnmpIndexOffsetGlobalIx }
   ::= {er1646v2VEthSnmpIndexOffsetTable 1}

Er1646v2VEthSnmpIndexOffsetEntry ::=
   SEQUENCE
      {
      er1646v2VEthSnmpIndexOffsetGlobalIx
         GlobalIndex,
      er1646v2VEthSnmpIndexOffsetValue
         Integer32
      }

er1646v2VEthSnmpIndexOffsetGlobalIx OBJECT-TYPE
   SYNTAX      GlobalIndex
   MAX-ACCESS  not-accessible
   STATUS      current
   DESCRIPTION
      "The value of the tlsCntTreeGlobalIndex of the MANAGED OBJECT."
   ::= {er1646v2VEthSnmpIndexOffsetEntry 10}

er1646v2VEthSnmpIndexOffsetValue OBJECT-TYPE
   SYNTAX      Integer32
   MAX-ACCESS  read-write
   STATUS      current
   DESCRIPTION
      "Path: virtualEthernet.editConf.snmpIndexOffset"
   ::= {er1646v2VEthSnmpIndexOffsetEntry 2147483648}


er1646v2VEthAlarmMask OBJECT IDENTIFIER ::= {er1646v2VEth 135}

er1646v2VEthAlarmMaskTable OBJECT-TYPE
   SYNTAX      SEQUENCE OF Er1646v2VEthAlarmMaskEntry
   MAX-ACCESS  not-accessible
   STATUS      current
   DESCRIPTION
      "ifAlarmMask"
   ::= {er1646v2VEthAlarmMask 1}

er1646v2VEthAlarmMaskEntry OBJECT-TYPE
   SYNTAX      Er1646v2VEthAlarmMaskEntry
   MAX-ACCESS  not-accessible
   STATUS      current
   DESCRIPTION
      ""
   INDEX      { er1646v2VEthAlarmMaskGlobalIx }
   ::= {er1646v2VEthAlarmMaskTable 1}

Er1646v2VEthAlarmMaskEntry ::=
   SEQUENCE
      {
      er1646v2VEthAlarmMaskGlobalIx
         GlobalIndex,
      er1646v2VEthAlarmMaskValue
         Integer32
      }

er1646v2VEthAlarmMaskGlobalIx OBJECT-TYPE
   SYNTAX      GlobalIndex
   MAX-ACCESS  not-accessible
   STATUS      current
   DESCRIPTION
      "The value of the tlsCntTreeGlobalIndex of the MANAGED OBJECT."
   ::= {er1646v2VEthAlarmMaskEntry 10}

er1646v2VEthAlarmMaskValue OBJECT-TYPE
   SYNTAX      Integer32
   MAX-ACCESS  read-write
   STATUS      current
   DESCRIPTION
      "Path: virtualEthernet.editConf.alarmMask

       Bit meanings:
               bit 0 = linkDown,
               bit 9 = pppoEDown"
   ::= {er1646v2VEthAlarmMaskEntry 2147483648}


er1646v2VEthAlarmLev OBJECT IDENTIFIER ::= {er1646v2VEth 170}

er1646v2VEthAlarmLevSSCTable OBJECT-TYPE
   SYNTAX      SEQUENCE OF Er1646v2VEthAlarmLevEntry
   MAX-ACCESS  not-accessible
   STATUS      current
   DESCRIPTION
      "IfAlarmLevels"
   ::= {er1646v2VEthAlarmLev 1}

er1646v2VEthAlarmLevEntry OBJECT-TYPE
   SYNTAX      Er1646v2VEthAlarmLevEntry
   MAX-ACCESS  not-accessible
   STATUS      current
   DESCRIPTION
      ""
   INDEX      { er1646v2VEthAlarmLevGlobalIx }
   ::= {er1646v2VEthAlarmLevSSCTable 1}

Er1646v2VEthAlarmLevEntry ::=
   SEQUENCE
      {
      er1646v2VEthAlarmLevGlobalIx
         GlobalIndex,
      er1646v2VEthAlarmLevLinkDown
         Integer32,
      er1646v2VEthAlarmLevPppoEDown
         Integer32
      }

er1646v2VEthAlarmLevGlobalIx OBJECT-TYPE
   SYNTAX      GlobalIndex
   MAX-ACCESS  not-accessible
   STATUS      current
   DESCRIPTION
      "The value of the tlsCntTreeGlobalIndex of the MANAGED OBJECT."
   ::= {er1646v2VEthAlarmLevEntry 10}

er1646v2VEthAlarmLevLinkDown OBJECT-TYPE
   SYNTAX      Integer32
   MAX-ACCESS  read-write
   STATUS      current
   DESCRIPTION
      "Path: virtualEthernet.editConf.alarmLevel.linkDown"
   ::= {er1646v2VEthAlarmLevEntry 16777216}

er1646v2VEthAlarmLevPppoEDown OBJECT-TYPE
   SYNTAX      Integer32
   MAX-ACCESS  read-write
   STATUS      current
   DESCRIPTION
      "Path: virtualEthernet.editConf.alarmLevel.pppoEDown"
   ::= {er1646v2VEthAlarmLevEntry 167772160}



sr1646v2VEth OBJECT IDENTIFIER ::= {r1646v2VEth 14}


sr1646v2VEthDescr OBJECT IDENTIFIER ::= {sr1646v2VEth 101}

sr1646v2VEthDescrTable OBJECT-TYPE
   SYNTAX      SEQUENCE OF Sr1646v2VEthDescrEntry
   MAX-ACCESS  not-accessible
   STATUS      current
   DESCRIPTION
      "ifDescr"
   ::= {sr1646v2VEthDescr 1}

sr1646v2VEthDescrEntry OBJECT-TYPE
   SYNTAX      Sr1646v2VEthDescrEntry
   MAX-ACCESS  not-accessible
   STATUS      current
   DESCRIPTION
      ""
   INDEX      { sr1646v2VEthDescrGlobalIx }
   ::= {sr1646v2VEthDescrTable 1}

Sr1646v2VEthDescrEntry ::=
   SEQUENCE
      {
      sr1646v2VEthDescrGlobalIx
         GlobalIndex,
      sr1646v2VEthDescrValue
         DisplayString
      }

sr1646v2VEthDescrGlobalIx OBJECT-TYPE
   SYNTAX      GlobalIndex
   MAX-ACCESS  not-accessible
   STATUS      current
   DESCRIPTION
      "The value of the tlsCntTreeGlobalIndex of the MANAGED OBJECT."
   ::= {sr1646v2VEthDescrEntry 10}

sr1646v2VEthDescrValue OBJECT-TYPE
   SYNTAX      DisplayString
   MAX-ACCESS  read-only
   STATUS      current
   DESCRIPTION
      "Path: virtualEthernet.status.ifDescr"
   ::= {sr1646v2VEthDescrEntry 2147483648}


sr1646v2VEthType OBJECT IDENTIFIER ::= {sr1646v2VEth 102}

sr1646v2VEthTypeTable OBJECT-TYPE
   SYNTAX      SEQUENCE OF Sr1646v2VEthTypeEntry
   MAX-ACCESS  not-accessible
   STATUS      current
   DESCRIPTION
      "ifType"
   ::= {sr1646v2VEthType 1}

sr1646v2VEthTypeEntry OBJECT-TYPE
   SYNTAX      Sr1646v2VEthTypeEntry
   MAX-ACCESS  not-accessible
   STATUS      current
   DESCRIPTION
      ""
   INDEX      { sr1646v2VEthTypeGlobalIx }
   ::= {sr1646v2VEthTypeTable 1}

Sr1646v2VEthTypeEntry ::=
   SEQUENCE
      {
      sr1646v2VEthTypeGlobalIx
         GlobalIndex,
      sr1646v2VEthTypeValue
         INTEGER
      }

sr1646v2VEthTypeGlobalIx OBJECT-TYPE
   SYNTAX      GlobalIndex
   MAX-ACCESS  not-accessible
   STATUS      current
   DESCRIPTION
      "The value of the tlsCntTreeGlobalIndex of the MANAGED OBJECT."
   ::= {sr1646v2VEthTypeEntry 10}

sr1646v2VEthTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: virtualEthernet.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1646v2VEthTypeEntry 2147483648}


sr1646v2VEthMtu OBJECT IDENTIFIER ::= {sr1646v2VEth 103}

sr1646v2VEthMtuTable OBJECT-TYPE
   SYNTAX      SEQUENCE OF Sr1646v2VEthMtuEntry
   MAX-ACCESS  not-accessible
   STATUS      current
   DESCRIPTION
      "ifMtu"
   ::= {sr1646v2VEthMtu 1}

sr1646v2VEthMtuEntry OBJECT-TYPE
   SYNTAX      Sr1646v2VEthMtuEntry
   MAX-ACCESS  not-accessible
   STATUS      current
   DESCRIPTION
      ""
   INDEX      { sr1646v2VEthMtuGlobalIx }
   ::= {sr1646v2VEthMtuTable 1}

Sr1646v2VEthMtuEntry ::=
   SEQUENCE
      {
      sr1646v2VEthMtuGlobalIx
         GlobalIndex,
      sr1646v2VEthMtuValue
         Integer32
      }

sr1646v2VEthMtuGlobalIx OBJECT-TYPE
   SYNTAX      GlobalIndex
   MAX-ACCESS  not-accessible
   STATUS      current
   DESCRIPTION
      "The value of the tlsCntTreeGlobalIndex of the MANAGED OBJECT."
   ::= {sr1646v2VEthMtuEntry 10}

sr1646v2VEthMtuValue OBJECT-TYPE
   SYNTAX      Integer32
   MAX-ACCESS  read-only
   STATUS      current
   DESCRIPTION
      "Path: virtualEthernet.status.ifMtu"
   ::= {sr1646v2VEthMtuEntry 2147483648}


sr1646v2VEthOperStatus OBJECT IDENTIFIER ::= {sr1646v2VEth 107}

sr1646v2VEthOperStatusTable OBJECT-TYPE
   SYNTAX      SEQUENCE OF Sr1646v2VEthOperStatusEntry
   MAX-ACCESS  not-accessible
   STATUS      current
   DESCRIPTION
      "ifOperStatus"
   ::= {sr1646v2VEthOperStatus 1}

sr1646v2VEthOperStatusEntry OBJECT-TYPE
   SYNTAX      Sr1646v2VEthOperStatusEntry
   MAX-ACCESS  not-accessible
   STATUS      current
   DESCRIPTION
      ""
   INDEX      { sr1646v2VEthOperStatusGlobalIx }
   ::= {sr1646v2VEthOperStatusTable 1}

Sr1646v2VEthOperStatusEntry ::=
   SEQUENCE
      {
      sr1646v2VEthOperStatusGlobalIx
         GlobalIndex,
      sr1646v2VEthOperStatusValue
         INTEGER
      }

sr1646v2VEthOperStatusGlobalIx OBJECT-TYPE
   SYNTAX      GlobalIndex
   MAX-ACCESS  not-accessible
   STATUS      current
   DESCRIPTION
      "The value of the tlsCntTreeGlobalIndex of the MANAGED OBJECT."
   ::= {sr1646v2VEthOperStatusEntry 10}

sr1646v2VEthOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.ifOperStatus

       Possibilities:
               up   (1)
               down   (2)
               testing   (3)
               unknown   (4)
               dormant   (5)
               notPresent   (6)
               lowerLayerDown   (7)"
   ::= {sr1646v2VEthOperStatusEntry 2147483648}


sr1646v2VEthLastChange OBJECT IDENTIFIER ::= {sr1646v2VEth 108}

sr1646v2VEthLastChangeTable OBJECT-TYPE
   SYNTAX      SEQUENCE OF Sr1646v2VEthLastChangeEntry
   MAX-ACCESS  not-accessible
   STATUS      current
   DESCRIPTION
      "ifLastChange"
   ::= {sr1646v2VEthLastChange 1}

sr1646v2VEthLastChangeEntry OBJECT-TYPE
   SYNTAX      Sr1646v2VEthLastChangeEntry
   MAX-ACCESS  not-accessible
   STATUS      current
   DESCRIPTION
      ""
   INDEX      { sr1646v2VEthLastChangeGlobalIx }
   ::= {sr1646v2VEthLastChangeTable 1}

Sr1646v2VEthLastChangeEntry ::=
   SEQUENCE
      {
      sr1646v2VEthLastChangeGlobalIx
         GlobalIndex,
      sr1646v2VEthLastChangeValue
         TimeTicks
      }

sr1646v2VEthLastChangeGlobalIx OBJECT-TYPE
   SYNTAX      GlobalIndex
   MAX-ACCESS  not-accessible
   STATUS      current
   DESCRIPTION
      "The value of the tlsCntTreeGlobalIndex of the MANAGED OBJECT."
   ::= {sr1646v2VEthLastChangeEntry 10}

sr1646v2VEthLastChangeValue OBJECT-TYPE
   SYNTAX      TimeTicks
   MAX-ACCESS  read-only
   STATUS      current
   DESCRIPTION
      "Path: virtualEthernet.status.ifLastChange

       Time in centi-second."
   ::= {sr1646v2VEthLastChangeEntry 2147483648}


sr1646v2VEthLastChangeD OBJECT IDENTIFIER ::= {sr1646v2VEth 183}

sr1646v2VEthLastChangeDTable OBJECT-TYPE
   SYNTAX      SEQUENCE OF Sr1646v2VEthLastChangeDEntry
   MAX-ACCESS  not-accessible
   STATUS      current
   DESCRIPTION
      "ifLastChangeDate"
   ::= {sr1646v2VEthLastChangeD 1}

sr1646v2VEthLastChangeDEntry OBJECT-TYPE
   SYNTAX      Sr1646v2VEthLastChangeDEntry
   MAX-ACCESS  not-accessible
   STATUS      current
   DESCRIPTION
      ""
   INDEX      { sr1646v2VEthLastChangeDGlobalIx }
   ::= {sr1646v2VEthLastChangeDTable 1}

Sr1646v2VEthLastChangeDEntry ::=
   SEQUENCE
      {
      sr1646v2VEthLastChangeDGlobalIx
         GlobalIndex,
      sr1646v2VEthLastChangeDValue
         DisplayString
      }

sr1646v2VEthLastChangeDGlobalIx OBJECT-TYPE
   SYNTAX      GlobalIndex
   MAX-ACCESS  not-accessible
   STATUS      current
   DESCRIPTION
      "The value of the tlsCntTreeGlobalIndex of the MANAGED OBJECT."
   ::= {sr1646v2VEthLastChangeDEntry 10}

sr1646v2VEthLastChangeDValue OBJECT-TYPE
   SYNTAX      DisplayString
   MAX-ACCESS  read-only
   STATUS      current
   DESCRIPTION
      "Path: virtualEthernet.status.ifLastChangeDate"
   ::= {sr1646v2VEthLastChangeDEntry 2147483648}


sr1646v2VEthSpeed OBJECT IDENTIFIER ::= {sr1646v2VEth 104}

sr1646v2VEthSpeedTable OBJECT-TYPE
   SYNTAX      SEQUENCE OF Sr1646v2VEthSpeedEntry
   MAX-ACCESS  not-accessible
   STATUS      current
   DESCRIPTION
      "ifSpeed"
   ::= {sr1646v2VEthSpeed 1}

sr1646v2VEthSpeedEntry OBJECT-TYPE
   SYNTAX      Sr1646v2VEthSpeedEntry
   MAX-ACCESS  not-accessible
   STATUS      current
   DESCRIPTION
      ""
   INDEX      { sr1646v2VEthSpeedGlobalIx }
   ::= {sr1646v2VEthSpeedTable 1}

Sr1646v2VEthSpeedEntry ::=
   SEQUENCE
      {
      sr1646v2VEthSpeedGlobalIx
         GlobalIndex,
      sr1646v2VEthSpeedValue
         Gauge32
      }

sr1646v2VEthSpeedGlobalIx OBJECT-TYPE
   SYNTAX      GlobalIndex
   MAX-ACCESS  not-accessible
   STATUS      current
   DESCRIPTION
      "The value of the tlsCntTreeGlobalIndex of the MANAGED OBJECT."
   ::= {sr1646v2VEthSpeedEntry 10}

sr1646v2VEthSpeedValue OBJECT-TYPE
   SYNTAX      Gauge32
   MAX-ACCESS  read-only
   STATUS      current
   DESCRIPTION
      "Path: virtualEthernet.status.ifSpeed

       32 bit unsigned gauge value."
   ::= {sr1646v2VEthSpeedEntry 2147483648}


sr1646v2VEthIp OBJECT IDENTIFIER ::= {sr1646v2VEth 16}

sr1646v2VEthIpSSCTable OBJECT-TYPE
   SYNTAX      SEQUENCE OF Sr1646v2VEthIpEntry
   MAX-ACCESS  not-accessible
   STATUS      current
   DESCRIPTION
      "ip interface status parameters"
   ::= {sr1646v2VEthIp 1}

sr1646v2VEthIpEntry OBJECT-TYPE
   SYNTAX      Sr1646v2VEthIpEntry
   MAX-ACCESS  not-accessible
   STATUS      current
   DESCRIPTION
      ""
   INDEX      { sr1646v2VEthIpGlobalIx }
   ::= {sr1646v2VEthIpSSCTable 1}

Sr1646v2VEthIpEntry ::=
   SEQUENCE
      {
      sr1646v2VEthIpGlobalIx
         GlobalIndex,
      sr1646v2VEthIpStatus
         INTEGER,
      sr1646v2VEthIpAddress
         IpAddress,
      sr1646v2VEthIpNetMask
         IpAddress,
      sr1646v2VEthIpDhcpStatus
         INTEGER,
      sr1646v2VEthIpDhcpLeaseTime
         TimeTicks
      }

sr1646v2VEthIpGlobalIx OBJECT-TYPE
   SYNTAX      GlobalIndex
   MAX-ACCESS  not-accessible
   STATUS      current
   DESCRIPTION
      "The value of the tlsCntTreeGlobalIndex of the MANAGED OBJECT."
   ::= {sr1646v2VEthIpEntry 10}

sr1646v2VEthIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.ip.status

       Possibilities:
               up   (1)
               down   (2)
               testing   (3)
               unknown   (4)
               dormant   (5)
               notPresent   (6)
               lowerLayerDown   (7)"
   ::= {sr1646v2VEthIpEntry 1795162112}

sr1646v2VEthIpAddress OBJECT-TYPE
   SYNTAX      IpAddress
   MAX-ACCESS  read-only
   STATUS      current
   DESCRIPTION
      "Path: virtualEthernet.status.ip.address"
   ::= {sr1646v2VEthIpEntry 2030043136}

sr1646v2VEthIpNetMask OBJECT-TYPE
   SYNTAX      IpAddress
   MAX-ACCESS  read-only
   STATUS      current
   DESCRIPTION
      "Path: virtualEthernet.status.ip.netMask"
   ::= {sr1646v2VEthIpEntry 2063597568}

sr1646v2VEthIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: virtualEthernet.status.ip.dhcp.status

       Possibilities:
               none   (0)
               selecting   (1)
               requesting   (2)
               rebinding   (3)
               bound   (4)
               renewing   (5)
               rebooting   (6)
               initreboot   (7)"
   ::= {sr1646v2VEthIpEntry 402718720}

sr1646v2VEthIpDhcpLeaseTime OBJECT-TYPE
   SYNTAX      TimeTicks
   MAX-ACCESS  read-only
   STATUS      current
   DESCRIPTION
      "Path: virtualEthernet.status.ip.dhcp.leaseTime

       Time in centi-second."
   ::= {sr1646v2VEthIpEntry 402784256}

sr1646v2VEthIpSecondaryIp OBJECT-TYPE
   SYNTAX      SEQUENCE OF Sr1646v2VEthIpSecondaryIpEntry
   MAX-ACCESS  not-accessible
   STATUS      current
   DESCRIPTION
      ""
   ::= {sr1646v2VEthIp 385875968}

sr1646v2VEthIpSecondaryIpEntry OBJECT-TYPE
   SYNTAX      Sr1646v2VEthIpSecondaryIpEntry
   MAX-ACCESS  not-accessible
   STATUS      current
   DESCRIPTION
      ""
   INDEX      { sr1646v2VEthIpSecondaryIpGlobalIx,
                sr1646v2VEthIpSecondaryIpTableIx }
   ::= {sr1646v2VEthIpSecondaryIp 1}

Sr1646v2VEthIpSecondaryIpEntry ::=
   SEQUENCE
      {
      sr1646v2VEthIpSecondaryIpGlobalIx
         GlobalIndex,
      sr1646v2VEthIpSecondaryIpTableIx
         TableIndex,
      sr1646v2VEthIpSecondaryIpAddress
         IpAddress,
      sr1646v2VEthIpSecondaryIpNetMask
         IpAddress
      }

sr1646v2VEthIpSecondaryIpGlobalIx OBJECT-TYPE
   SYNTAX      GlobalIndex
   MAX-ACCESS  not-accessible
   STATUS      current
   DESCRIPTION
      "The value of the tlsCntTreeGlobalIndex of the MANAGED OBJECT."
   ::= {sr1646v2VEthIpSecondaryIpEntry 10}

sr1646v2VEthIpSecondaryIpTableIx OBJECT-TYPE
   SYNTAX      TableIndex
   MAX-ACCESS  not-accessible
   STATUS      current
   DESCRIPTION
      ""
   ::= {sr1646v2VEthIpSecondaryIpEntry 11}

sr1646v2VEthIpSecondaryIpAddress OBJECT-TYPE
   SYNTAX      IpAddress
   MAX-ACCESS  read-only
   STATUS      current
   DESCRIPTION
      "Path: virtualEthernet.status.ip.secondaryIp.address"
   ::= {sr1646v2VEthIpSecondaryIpEntry 2030043136}

sr1646v2VEthIpSecondaryIpNetMask OBJECT-TYPE
   SYNTAX      IpAddress
   MAX-ACCESS  read-only
   STATUS      current
   DESCRIPTION
      "Path: virtualEthernet.status.ip.secondaryIp.netMask"
   ::= {sr1646v2VEthIpSecondaryIpEntry 2063597568}


sr1646v2VEthArpCache OBJECT IDENTIFIER ::= {sr1646v2VEth 11}

sr1646v2VEthArpCacheSSCTable OBJECT-TYPE
   SYNTAX      SEQUENCE OF Sr1646v2VEthArpCacheEntry
   MAX-ACCESS  not-accessible
   STATUS      current
   DESCRIPTION
      "arp cache of ethernet interface"
   ::= {sr1646v2VEthArpCache 1}

sr1646v2VEthArpCacheEntry OBJECT-TYPE
   SYNTAX      Sr1646v2VEthArpCacheEntry
   MAX-ACCESS  not-accessible
   STATUS      current
   DESCRIPTION
      ""
   INDEX      { sr1646v2VEthArpCacheGlobalIx,
                sr1646v2VEthArpCacheTableIx }
   ::= {sr1646v2VEthArpCacheSSCTable 1}

Sr1646v2VEthArpCacheEntry ::=
   SEQUENCE
      {
      sr1646v2VEthArpCacheGlobalIx
         GlobalIndex,
      sr1646v2VEthArpCacheTableIx
         TableIndex,
      sr1646v2VEthArpCacheMacAddress
         OCTET STRING,
      sr1646v2VEthArpCacheIpAddress
         IpAddress,
      sr1646v2VEthArpCacheType
         INTEGER,
      sr1646v2VEthArpCacheTimeOut
         TimeTicks
      }

sr1646v2VEthArpCacheGlobalIx OBJECT-TYPE
   SYNTAX      GlobalIndex
   MAX-ACCESS  not-accessible
   STATUS      current
   DESCRIPTION
      "The value of the tlsCntTreeGlobalIndex of the MANAGED OBJECT."
   ::= {sr1646v2VEthArpCacheEntry 10}

sr1646v2VEthArpCacheTableIx OBJECT-TYPE
   SYNTAX      TableIndex
   MAX-ACCESS  not-accessible
   STATUS      current
   DESCRIPTION
      ""
   ::= {sr1646v2VEthArpCacheEntry 11}

sr1646v2VEthArpCacheMacAddress OBJECT-TYPE
   SYNTAX      OCTET STRING
   MAX-ACCESS  read-only
   STATUS      current
   DESCRIPTION
      "Path: virtualEthernet.status.arpCache.macAddress

       MAC address."
   ::= {sr1646v2VEthArpCacheEntry 16777216}

sr1646v2VEthArpCacheIpAddress OBJECT-TYPE
   SYNTAX      IpAddress
   MAX-ACCESS  read-only
   STATUS      current
   DESCRIPTION
      "Path: virtualEthernet.status.arpCache.ipAddress"
   ::= {sr1646v2VEthArpCacheEntry 33554432}

sr1646v2VEthArpCacheType OBJECT-TYPE
   SYNTAX      INTEGER
               {
               static (0),
               dynamic (1)
               }
   MAX-ACCESS  read-only
   STATUS      current
   DESCRIPTION
      "Path: virtualEthernet.status.arpCache.type

       Possibilities:
               static   (0)
               dynamic   (1)"
   ::= {sr1646v2VEthArpCacheEntry 50331648}

sr1646v2VEthArpCacheTimeOut OBJECT-TYPE
   SYNTAX      TimeTicks
   MAX-ACCESS  read-only
   STATUS      current
   DESCRIPTION
      "Path: virtualEthernet.status.arpCache.timeOut

       Time in centi-second."
   ::= {sr1646v2VEthArpCacheEntry 67108864}


sr1646v2VEthBrS OBJECT IDENTIFIER ::= {sr1646v2VEth 28}

sr1646v2VEthBrSSSCTable OBJECT-TYPE
   SYNTAX      SEQUENCE OF Sr1646v2VEthBrSEntry
   MAX-ACCESS  not-accessible
   STATUS      current
   DESCRIPTION
      "spanning tree status ethernet interface"
   ::= {sr1646v2VEthBrS 1}

sr1646v2VEthBrSEntry OBJECT-TYPE
   SYNTAX      Sr1646v2VEthBrSEntry
   MAX-ACCESS  not-accessible
   STATUS      current
   DESCRIPTION
      ""
   INDEX      { sr1646v2VEthBrSGlobalIx }
   ::= {sr1646v2VEthBrSSSCTable 1}

Sr1646v2VEthBrSEntry ::=
   SEQUENCE
      {
      sr1646v2VEthBrSGlobalIx
         GlobalIndex,
      sr1646v2VEthBrSStatus
         INTEGER,
      sr1646v2VEthBrSStPortRole
         INTEGER,
      sr1646v2VEthBrSStPortId
         Integer32,
      sr1646v2VEthBrSStPpCostExtPathCost
         Integer32,
      sr1646v2VEthBrSStPpCostIntPathCost
         Integer32,
      sr1646v2VEthBrSStExtRpCost
         Integer32,
      sr1646v2VEthBrSStIntRpCost
         Integer32,
      sr1646v2VEthBrSStDesBrIdPriority
         Integer32,
      sr1646v2VEthBrSStDesBrIdMacAddress
         OCTET STRING,
      sr1646v2VEthBrSStDesPrtId
         Integer32,
      sr1646v2VEthBrSStDesInt
         INTEGER,
      sr1646v2VEthBrSStEdgeDetection
         INTEGER
      }

sr1646v2VEthBrSGlobalIx OBJECT-TYPE
   SYNTAX      GlobalIndex
   MAX-ACCESS  not-accessible
   STATUS      current
   DESCRIPTION
      "The value of the tlsCntTreeGlobalIndex of the MANAGED OBJECT."
   ::= {sr1646v2VEthBrSEntry 10}

sr1646v2VEthBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: virtualEthernet.status.bridging.status

       Possibilities:
               disabled   (0)
               discarding   (1)
               learning   (2)
               forwarding   (3)
               backupBlockedIntfDown   (256)
               backupBlockedIntfUp   (259)
               shutdown   (255)"
   ::= {sr1646v2VEthBrSEntry 16777216}

sr1646v2VEthBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: virtualEthernet.status.bridging.spanningTree.portRole

       Possibilities:
               none   (0)
               root   (1)
               designated   (2)
               alternate   (3)
               backup   (4)
               disabled   (5)
               master   (6)"
   ::= {sr1646v2VEthBrSEntry 33619968}

sr1646v2VEthBrSStPortId OBJECT-TYPE
   SYNTAX      Integer32
   MAX-ACCESS  read-only
   STATUS      current
   DESCRIPTION
      "Path: virtualEthernet.status.bridging.spanningTree.portId"
   ::= {sr1646v2VEthBrSEntry 33685504}

sr1646v2VEthBrSStPpCostExtPathCost OBJECT-TYPE
   SYNTAX      Integer32
   MAX-ACCESS  read-only
   STATUS      current
   DESCRIPTION
      "Path: virtualEthernet.status.bridging.spanningTree.portPathCosts.extPathCost"
   ::= {sr1646v2VEthBrSEntry 33751296}

sr1646v2VEthBrSStPpCostIntPathCost OBJECT-TYPE
   SYNTAX      Integer32
   MAX-ACCESS  read-only
   STATUS      current
   DESCRIPTION
      "Path: virtualEthernet.status.bridging.spanningTree.portPathCosts.intPathCost"
   ::= {sr1646v2VEthBrSEntry 33751552}

sr1646v2VEthBrSStExtRpCost OBJECT-TYPE
   SYNTAX      Integer32
   MAX-ACCESS  read-only
   STATUS      current
   DESCRIPTION
      "Path: virtualEthernet.status.bridging.spanningTree.extRootPathCost"
   ::= {sr1646v2VEthBrSEntry 33816576}

sr1646v2VEthBrSStIntRpCost OBJECT-TYPE
   SYNTAX      Integer32
   MAX-ACCESS  read-only
   STATUS      current
   DESCRIPTION
      "Path: virtualEthernet.status.bridging.spanningTree.intRootPathCost"
   ::= {sr1646v2VEthBrSEntry 33882112}

sr1646v2VEthBrSStDesBrIdPriority OBJECT-TYPE
   SYNTAX      Integer32
   MAX-ACCESS  read-only
   STATUS      current
   DESCRIPTION
      "Path: virtualEthernet.status.bridging.spanningTree.designatedBridgeId.priority"
   ::= {sr1646v2VEthBrSEntry 33947904}

sr1646v2VEthBrSStDesBrIdMacAddress OBJECT-TYPE
   SYNTAX      OCTET STRING
   MAX-ACCESS  read-only
   STATUS      current
   DESCRIPTION
      "Path: virtualEthernet.status.bridging.spanningTree.designatedBridgeId.macAddress

       MAC address."
   ::= {sr1646v2VEthBrSEntry 33948160}

sr1646v2VEthBrSStDesPrtId OBJECT-TYPE
   SYNTAX      Integer32
   MAX-ACCESS  read-only
   STATUS      current
   DESCRIPTION
      "Path: virtualEthernet.status.bridging.spanningTree.designatedPortId"
   ::= {sr1646v2VEthBrSEntry 34013184}

sr1646v2VEthBrSStDesInt OBJECT-TYPE
   SYNTAX      INTEGER
               {
               no (0),
               yes (1)
               }
   MAX-ACCESS  read-only
   STATUS      current
   DESCRIPTION
      "Path: virtualEthernet.status.bridging.spanningTree.designatedOrInternal

       Possibilities:
               no   (0)
               yes   (1)"
   ::= {sr1646v2VEthBrSEntry 34078720}

sr1646v2VEthBrSStEdgeDetection OBJECT-TYPE
   SYNTAX      INTEGER
               {
               none (0),
               edge (1),
               notEdge (2)
               }
   MAX-ACCESS  read-only
   STATUS      current
   DESCRIPTION
      "Path: virtualEthernet.status.bridging.spanningTree.edgeDetection

       Possibilities:
               none   (0)
               edge   (1)
               notEdge   (2)"
   ::= {sr1646v2VEthBrSEntry 34144256}


sr1646v2VEthMacAddress OBJECT IDENTIFIER ::= {sr1646v2VEth 105}

sr1646v2VEthMacAddressTable OBJECT-TYPE
   SYNTAX      SEQUENCE OF Sr1646v2VEthMacAddressEntry
   MAX-ACCESS  not-accessible
   STATUS      current
   DESCRIPTION
      "ifPhysAddress"
   ::= {sr1646v2VEthMacAddress 1}

sr1646v2VEthMacAddressEntry OBJECT-TYPE
   SYNTAX      Sr1646v2VEthMacAddressEntry
   MAX-ACCESS  not-accessible
   STATUS      current
   DESCRIPTION
      ""
   INDEX      { sr1646v2VEthMacAddressGlobalIx }
   ::= {sr1646v2VEthMacAddressTable 1}

Sr1646v2VEthMacAddressEntry ::=
   SEQUENCE
      {
      sr1646v2VEthMacAddressGlobalIx
         GlobalIndex,
      sr1646v2VEthMacAddressValue
         OCTET STRING
      }

sr1646v2VEthMacAddressGlobalIx OBJECT-TYPE
   SYNTAX      GlobalIndex
   MAX-ACCESS  not-accessible
   STATUS      current
   DESCRIPTION
      "The value of the tlsCntTreeGlobalIndex of the MANAGED OBJECT."
   ::= {sr1646v2VEthMacAddressEntry 10}

sr1646v2VEthMacAddressValue OBJECT-TYPE
   SYNTAX      OCTET STRING
   MAX-ACCESS  read-only
   STATUS      current
   DESCRIPTION
      "Path: virtualEthernet.status.macAddress

       MAC address."
   ::= {sr1646v2VEthMacAddressEntry 2147483648}


sr1646v2VEthIpAdEntBcastAddr OBJECT IDENTIFIER ::= {sr1646v2VEth 124}

sr1646v2VEthIpAdEntBcastAddrTable OBJECT-TYPE
   SYNTAX      SEQUENCE OF Sr1646v2VEthIpAdEntBcastAddrEntry
   MAX-ACCESS  not-accessible
   STATUS      current
   DESCRIPTION
      "ipAdEntBcastAddr"
   ::= {sr1646v2VEthIpAdEntBcastAddr 1}

sr1646v2VEthIpAdEntBcastAddrEntry OBJECT-TYPE
   SYNTAX      Sr1646v2VEthIpAdEntBcastAddrEntry
   MAX-ACCESS  not-accessible
   STATUS      current
   DESCRIPTION
      ""
   INDEX      { sr1646v2VEthIpAdEntBcastAddrGlobalIx }
   ::= {sr1646v2VEthIpAdEntBcastAddrTable 1}

Sr1646v2VEthIpAdEntBcastAddrEntry ::=
   SEQUENCE
      {
      sr1646v2VEthIpAdEntBcastAddrGlobalIx
         GlobalIndex,
      sr1646v2VEthIpAdEntBcastAddrValue
         Integer32
      }

sr1646v2VEthIpAdEntBcastAddrGlobalIx OBJECT-TYPE
   SYNTAX      GlobalIndex
   MAX-ACCESS  not-accessible
   STATUS      current
   DESCRIPTION
      "The value of the tlsCntTreeGlobalIndex of the MANAGED OBJECT."
   ::= {sr1646v2VEthIpAdEntBcastAddrEntry 10}

sr1646v2VEthIpAdEntBcastAddrValue OBJECT-TYPE
   SYNTAX      Integer32
   MAX-ACCESS  read-only
   STATUS      current
   DESCRIPTION
      "Path: virtualEthernet.status.ipAdEntBcastAddr"
   ::= {sr1646v2VEthIpAdEntBcastAddrEntry 2147483648}


sr1646v2VEthIpAdEntReasmMaxSize OBJECT IDENTIFIER ::= {sr1646v2VEth 125}

sr1646v2VEthIpAdEntReasmMaxSizeTable OBJECT-TYPE
   SYNTAX      SEQUENCE OF Sr1646v2VEthIpAdEntReasmMaxSizeEntry
   MAX-ACCESS  not-accessible
   STATUS      current
   DESCRIPTION
      "ipAdEntReasmMaxSize"
   ::= {sr1646v2VEthIpAdEntReasmMaxSize 1}

sr1646v2VEthIpAdEntReasmMaxSizeEntry OBJECT-TYPE
   SYNTAX      Sr1646v2VEthIpAdEntReasmMaxSizeEntry
   MAX-ACCESS  not-accessible
   STATUS      current
   DESCRIPTION
      ""
   INDEX      { sr1646v2VEthIpAdEntReasmMaxSizeGlobalIx }
   ::= {sr1646v2VEthIpAdEntReasmMaxSizeTable 1}

Sr1646v2VEthIpAdEntReasmMaxSizeEntry ::=
   SEQUENCE
      {
      sr1646v2VEthIpAdEntReasmMaxSizeGlobalIx
         GlobalIndex,
      sr1646v2VEthIpAdEntReasmMaxSizeValue
         Integer32
      }

sr1646v2VEthIpAdEntReasmMaxSizeGlobalIx OBJECT-TYPE
   SYNTAX      GlobalIndex
   MAX-ACCESS  not-accessible
   STATUS      current
   DESCRIPTION
      "The value of the tlsCntTreeGlobalIndex of the MANAGED OBJECT."
   ::= {sr1646v2VEthIpAdEntReasmMaxSizeEntry 10}

sr1646v2VEthIpAdEntReasmMaxSizeValue OBJECT-TYPE
   SYNTAX      Integer32
   MAX-ACCESS  read-only
   STATUS      current
   DESCRIPTION
      "Path: virtualEthernet.status.ipAdEntReasmMaxSize"
   ::= {sr1646v2VEthIpAdEntReasmMaxSizeEntry 2147483648}


sr1646v2VEthOam OBJECT IDENTIFIER ::= {sr1646v2VEth 901}

sr1646v2VEthOamSSCTable OBJECT-TYPE
   SYNTAX      SEQUENCE OF Sr1646v2VEthOamEntry
   MAX-ACCESS  not-accessible
   STATUS      current
   DESCRIPTION
      "OAM discovery state"
   ::= {sr1646v2VEthOam 1}

sr1646v2VEthOamEntry OBJECT-TYPE
   SYNTAX      Sr1646v2VEthOamEntry
   MAX-ACCESS  not-accessible
   STATUS      current
   DESCRIPTION
      ""
   INDEX      { sr1646v2VEthOamGlobalIx }
   ::= {sr1646v2VEthOamSSCTable 1}

Sr1646v2VEthOamEntry ::=
   SEQUENCE
      {
      sr1646v2VEthOamGlobalIx
         GlobalIndex,
      sr1646v2VEthOamDiscovery
         INTEGER,
      sr1646v2VEthOamLoopback
         INTEGER,
      sr1646v2VEthOamLocalInfoVersion
         Integer32,
      sr1646v2VEthOamLocalInfoRevision
         Integer32,
      sr1646v2VEthOamLocalInfoStateMuxAction
         INTEGER,
      sr1646v2VEthOamLocalInfoStateParserAction
         INTEGER,
      sr1646v2VEthOamLocalInfoOui
         OCTET STRING,
      sr1646v2VEthOamLocalInfoVendorInfo
         OCTET STRING,
      sr1646v2VEthOamLocalInfoVarRetrieval
         INTEGER,
      sr1646v2VEthOamLocalInfoLinkEvents
         INTEGER,
      sr1646v2VEthOamLocalInfoLoopback
         INTEGER,
      sr1646v2VEthOamLocalInfoUnidirectional
         INTEGER,
      sr1646v2VEthOamLocalInfoMode
         INTEGER,
      sr1646v2VEthOamLocalInfoMaxPduSize
         Integer32,
      sr1646v2VEthOamRemoteInfoVersion
         Integer32,
      sr1646v2VEthOamRemoteInfoRevision
         Integer32,
      sr1646v2VEthOamRemoteInfoStateMuxAction
         INTEGER,
      sr1646v2VEthOamRemoteInfoStateParserAction
         INTEGER,
      sr1646v2VEthOamRemoteInfoOui
         OCTET STRING,
      sr1646v2VEthOamRemoteInfoVendorInfo
         OCTET STRING,
      sr1646v2VEthOamRemoteInfoVarRetrieval
         INTEGER,
      sr1646v2VEthOamRemoteInfoLinkEvents
         INTEGER,
      sr1646v2VEthOamRemoteInfoLoopback
         INTEGER,
      sr1646v2VEthOamRemoteInfoUnidirectional
         INTEGER,
      sr1646v2VEthOamRemoteInfoMode
         INTEGER,
      sr1646v2VEthOamRemoteInfoMaxPduSize
         Integer32,
      sr1646v2VEthOamEventsErroredSymbolWindow
         Integer32,
      sr1646v2VEthOamEventsErroredSymbolThreshold
         OCTET STRING,
      sr1646v2VEthOamEventsErroredFramePeriodWindow
         INTEGER,
      sr1646v2VEthOamEventsErroredFramePeriodThreshold
         Integer32,
      sr1646v2VEthOamEventsErroredFrameWindow
         Integer32,
      sr1646v2VEthOamEventsErroredFrameThreshold
         Integer32,
      sr1646v2VEthOamEventsErroredFrameSecondsWindow
         Integer32,
      sr1646v2VEthOamEventsErroredFrameSecondsThreshold
         Integer32
      }

sr1646v2VEthOamGlobalIx OBJECT-TYPE
   SYNTAX      GlobalIndex
   MAX-ACCESS  not-accessible
   STATUS      current
   DESCRIPTION
      "The value of the tlsCntTreeGlobalIndex of the MANAGED OBJECT."
   ::= {sr1646v2VEthOamEntry 10}

sr1646v2VEthOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: virtualEthernet.status.oam.discovery

       Possibilities:
               fault   (0)
               sendLocal   (1)
               passiveWait   (2)
               sendLocalRemote   (3)
               sendLocalRemoteOk   (4)
               sendAny   (5)"
   ::= {sr1646v2VEthOamEntry 16777216}

sr1646v2VEthOamLoopback OBJECT-TYPE
   SYNTAX      INTEGER
               {
               idle (0),
               waiting (1),
               localRunning (2),
               remoteRunning (3)
               }
   MAX-ACCESS  read-only
   STATUS      current
   DESCRIPTION
      "Path: virtualEthernet.status.oam.loopback

       Possibilities:
               idle   (0)
               waiting   (1)
               localRunning   (2)
               remoteRunning   (3)"
   ::= {sr1646v2VEthOamEntry 33554432}

sr1646v2VEthOamLocalInfoVersion OBJECT-TYPE
   SYNTAX      Integer32
   MAX-ACCESS  read-only
   STATUS      current
   DESCRIPTION
      "Path: virtualEthernet.status.oam.localInfo.version"
   ::= {sr1646v2VEthOamEntry 50397184}

sr1646v2VEthOamLocalInfoRevision OBJECT-TYPE
   SYNTAX      Integer32
   MAX-ACCESS  read-only
   STATUS      current
   DESCRIPTION
      "Path: virtualEthernet.status.oam.localInfo.revision"
   ::= {sr1646v2VEthOamEntry 50462720}

sr1646v2VEthOamLocalInfoStateMuxAction OBJECT-TYPE
   SYNTAX      INTEGER
               {
               forwarding (0),
               discarding (1)
               }
   MAX-ACCESS  read-only
   STATUS      current
   DESCRIPTION
      "Path: virtualEthernet.status.oam.localInfo.state.muxAction

       Possibilities:
               forwarding   (0)
               discarding   (1)"
   ::= {sr1646v2VEthOamEntry 50528512}

sr1646v2VEthOamLocalInfoStateParserAction OBJECT-TYPE
   SYNTAX      INTEGER
               {
               forwarding (0),
               loopback (1),
               discarding (2),
               reserved (3)
               }
   MAX-ACCESS  read-only
   STATUS      current
   DESCRIPTION
      "Path: virtualEthernet.status.oam.localInfo.state.parserAction

       Possibilities:
               forwarding   (0)
               loopback   (1)
               discarding   (2)
               reserved   (3)"
   ::= {sr1646v2VEthOamEntry 50528768}

sr1646v2VEthOamLocalInfoOui OBJECT-TYPE
   SYNTAX      OCTET STRING
   MAX-ACCESS  read-only
   STATUS      current
   DESCRIPTION
      "Path: virtualEthernet.status.oam.localInfo.oui"
   ::= {sr1646v2VEthOamEntry 50593792}

sr1646v2VEthOamLocalInfoVendorInfo OBJECT-TYPE
   SYNTAX      OCTET STRING
   MAX-ACCESS  read-only
   STATUS      current
   DESCRIPTION
      "Path: virtualEthernet.status.oam.localInfo.vendorInfo"
   ::= {sr1646v2VEthOamEntry 50659328}

sr1646v2VEthOamLocalInfoVarRetrieval OBJECT-TYPE
   SYNTAX      INTEGER
               {
               notSupported (0),
               supported (1)
               }
   MAX-ACCESS  read-only
   STATUS      current
   DESCRIPTION
      "Path: virtualEthernet.status.oam.localInfo.varRetrieval

       Possibilities:
               notSupported   (0)
               supported   (1)"
   ::= {sr1646v2VEthOamEntry 50724864}

sr1646v2VEthOamLocalInfoLinkEvents OBJECT-TYPE
   SYNTAX      INTEGER
               {
               ignored (0),
               interpreted (1)
               }
   MAX-ACCESS  read-only
   STATUS      current
   DESCRIPTION
      "Path: virtualEthernet.status.oam.localInfo.linkEvents

       Possibilities:
               ignored   (0)
               interpreted   (1)"
   ::= {sr1646v2VEthOamEntry 50790400}

sr1646v2VEthOamLocalInfoLoopback OBJECT-TYPE
   SYNTAX      INTEGER
               {
               notSupported (0),
               supported (1)
               }
   MAX-ACCESS  read-only
   STATUS      current
   DESCRIPTION
      "Path: virtualEthernet.status.oam.localInfo.loopback

       Possibilities:
               notSupported   (0)
               supported   (1)"
   ::= {sr1646v2VEthOamEntry 50855936}

sr1646v2VEthOamLocalInfoUnidirectional OBJECT-TYPE
   SYNTAX      INTEGER
               {
               notSupported (0),
               supported (1)
               }
   MAX-ACCESS  read-only
   STATUS      current
   DESCRIPTION
      "Path: virtualEthernet.status.oam.localInfo.unidirectional

       Possibilities:
               notSupported   (0)
               supported   (1)"
   ::= {sr1646v2VEthOamEntry 50921472}

sr1646v2VEthOamLocalInfoMode OBJECT-TYPE
   SYNTAX      INTEGER
               {
               passive (0),
               active (1)
               }
   MAX-ACCESS  read-only
   STATUS      current
   DESCRIPTION
      "Path: virtualEthernet.status.oam.localInfo.mode

       Possibilities:
               passive   (0)
               active   (1)"
   ::= {sr1646v2VEthOamEntry 50987008}

sr1646v2VEthOamLocalInfoMaxPduSize OBJECT-TYPE
   SYNTAX      Integer32
   MAX-ACCESS  read-only
   STATUS      current
   DESCRIPTION
      "Path: virtualEthernet.status.oam.localInfo.maxPduSize"
   ::= {sr1646v2VEthOamEntry 51052544}

sr1646v2VEthOamRemoteInfoVersion OBJECT-TYPE
   SYNTAX      Integer32
   MAX-ACCESS  read-only
   STATUS      current
   DESCRIPTION
      "Path: virtualEthernet.status.oam.remoteInfo.version"
   ::= {sr1646v2VEthOamEntry 67174400}

sr1646v2VEthOamRemoteInfoRevision OBJECT-TYPE
   SYNTAX      Integer32
   MAX-ACCESS  read-only
   STATUS      current
   DESCRIPTION
      "Path: virtualEthernet.status.oam.remoteInfo.revision"
   ::= {sr1646v2VEthOamEntry 67239936}

sr1646v2VEthOamRemoteInfoStateMuxAction OBJECT-TYPE
   SYNTAX      INTEGER
               {
               forwarding (0),
               discarding (1)
               }
   MAX-ACCESS  read-only
   STATUS      current
   DESCRIPTION
      "Path: virtualEthernet.status.oam.remoteInfo.state.muxAction

       Possibilities:
               forwarding   (0)
               discarding   (1)"
   ::= {sr1646v2VEthOamEntry 67305728}

sr1646v2VEthOamRemoteInfoStateParserAction OBJECT-TYPE
   SYNTAX      INTEGER
               {
               forwarding (0),
               loopback (1),
               discarding (2),
               reserved (3)
               }
   MAX-ACCESS  read-only
   STATUS      current
   DESCRIPTION
      "Path: virtualEthernet.status.oam.remoteInfo.state.parserAction

       Possibilities:
               forwarding   (0)
               loopback   (1)
               discarding   (2)
               reserved   (3)"
   ::= {sr1646v2VEthOamEntry 67305984}

sr1646v2VEthOamRemoteInfoOui OBJECT-TYPE
   SYNTAX      OCTET STRING
   MAX-ACCESS  read-only
   STATUS      current
   DESCRIPTION
      "Path: virtualEthernet.status.oam.remoteInfo.oui"
   ::= {sr1646v2VEthOamEntry 67371008}

sr1646v2VEthOamRemoteInfoVendorInfo OBJECT-TYPE
   SYNTAX      OCTET STRING
   MAX-ACCESS  read-only
   STATUS      current
   DESCRIPTION
      "Path: virtualEthernet.status.oam.remoteInfo.vendorInfo"
   ::= {sr1646v2VEthOamEntry 67436544}

sr1646v2VEthOamRemoteInfoVarRetrieval OBJECT-TYPE
   SYNTAX      INTEGER
               {
               notSupported (0),
               supported (1)
               }
   MAX-ACCESS  read-only
   STATUS      current
   DESCRIPTION
      "Path: virtualEthernet.status.oam.remoteInfo.varRetrieval

       Possibilities:
               notSupported   (0)
               supported   (1)"
   ::= {sr1646v2VEthOamEntry 67502080}

sr1646v2VEthOamRemoteInfoLinkEvents OBJECT-TYPE
   SYNTAX      INTEGER
               {
               ignored (0),
               interpreted (1)
               }
   MAX-ACCESS  read-only
   STATUS      current
   DESCRIPTION
      "Path: virtualEthernet.status.oam.remoteInfo.linkEvents

       Possibilities:
               ignored   (0)
               interpreted   (1)"
   ::= {sr1646v2VEthOamEntry 67567616}

sr1646v2VEthOamRemoteInfoLoopback OBJECT-TYPE
   SYNTAX      INTEGER
               {
               notSupported (0),
               supported (1)
               }
   MAX-ACCESS  read-only
   STATUS      current
   DESCRIPTION
      "Path: virtualEthernet.status.oam.remoteInfo.loopback

       Possibilities:
               notSupported   (0)
               supported   (1)"
   ::= {sr1646v2VEthOamEntry 67633152}

sr1646v2VEthOamRemoteInfoUnidirectional OBJECT-TYPE
   SYNTAX      INTEGER
               {
               notSupported (0),
               supported (1)
               }
   MAX-ACCESS  read-only
   STATUS      current
   DESCRIPTION
      "Path: virtualEthernet.status.oam.remoteInfo.unidirectional

       Possibilities:
               notSupported   (0)
               supported   (1)"
   ::= {sr1646v2VEthOamEntry 67698688}

sr1646v2VEthOamRemoteInfoMode OBJECT-TYPE
   SYNTAX      INTEGER
               {
               passive (0),
               active (1)
               }
   MAX-ACCESS  read-only
   STATUS      current
   DESCRIPTION
      "Path: virtualEthernet.status.oam.remoteInfo.mode

       Possibilities:
               passive   (0)
               active   (1)"
   ::= {sr1646v2VEthOamEntry 67764224}

sr1646v2VEthOamRemoteInfoMaxPduSize OBJECT-TYPE
   SYNTAX      Integer32
   MAX-ACCESS  read-only
   STATUS      current
   DESCRIPTION
      "Path: virtualEthernet.status.oam.remoteInfo.maxPduSize"
   ::= {sr1646v2VEthOamEntry 67829760}

sr1646v2VEthOamEventsErroredSymbolWindow OBJECT-TYPE
   SYNTAX      Integer32
   UNITS       "symbols"
   MAX-ACCESS  read-only
   STATUS      current
   DESCRIPTION
      "Path: virtualEthernet.status.oam.events.erroredSymbol.window

       unit name = symbols"
   ::= {sr1646v2VEthOamEntry 83951872}

sr1646v2VEthOamEventsErroredSymbolThreshold OBJECT-TYPE
   SYNTAX      OCTET STRING
   UNITS       "symbols"
   MAX-ACCESS  read-only
   STATUS      current
   DESCRIPTION
      "Path: virtualEthernet.status.oam.events.erroredSymbol.threshold

       unit name = symbols"
   ::= {sr1646v2VEthOamEntry 83952128}

sr1646v2VEthOamEventsErroredFramePeriodWindow OBJECT-TYPE
   SYNTAX      INTEGER
               {
               default (0)
               }
   UNITS       "frames"
   MAX-ACCESS  read-only
   STATUS      current
   DESCRIPTION
      "Path: virtualEthernet.status.oam.events.erroredFramePeriod.window

       unit name = frames

       Possibilities:
               default   (0)"
   ::= {sr1646v2VEthOamEntry 84017408}

sr1646v2VEthOamEventsErroredFramePeriodThreshold OBJECT-TYPE
   SYNTAX      Integer32
   UNITS       "frames"
   MAX-ACCESS  read-only
   STATUS      current
   DESCRIPTION
      "Path: virtualEthernet.status.oam.events.erroredFramePeriod.threshold

       unit name = frames"
   ::= {sr1646v2VEthOamEntry 84017664}

sr1646v2VEthOamEventsErroredFrameWindow OBJECT-TYPE
   SYNTAX      Integer32
   UNITS       "100msec"
   MAX-ACCESS  read-only
   STATUS      current
   DESCRIPTION
      "Path: virtualEthernet.status.oam.events.erroredFrame.window

       unit name = 100msec"
   ::= {sr1646v2VEthOamEntry 84082944}

sr1646v2VEthOamEventsErroredFrameThreshold OBJECT-TYPE
   SYNTAX      Integer32
   UNITS       "frames"
   MAX-ACCESS  read-only
   STATUS      current
   DESCRIPTION
      "Path: virtualEthernet.status.oam.events.erroredFrame.threshold

       unit name = frames"
   ::= {sr1646v2VEthOamEntry 84083200}

sr1646v2VEthOamEventsErroredFrameSecondsWindow OBJECT-TYPE
   SYNTAX      Integer32
   UNITS       "100msec"
   MAX-ACCESS  read-only
   STATUS      current
   DESCRIPTION
      "Path: virtualEthernet.status.oam.events.erroredFrameSeconds.window

       unit name = 100msec"
   ::= {sr1646v2VEthOamEntry 84148480}

sr1646v2VEthOamEventsErroredFrameSecondsThreshold OBJECT-TYPE
   SYNTAX      Integer32
   UNITS       "frames"
   MAX-ACCESS  read-only
   STATUS      current
   DESCRIPTION
      "Path: virtualEthernet.status.oam.events.erroredFrameSeconds.threshold

       unit name = frames"
   ::= {sr1646v2VEthOamEntry 84148736}


sr1646v2VEthOamEventLog OBJECT IDENTIFIER ::= {sr1646v2VEth 911}

sr1646v2VEthOamEventLogSSCTable OBJECT-TYPE
   SYNTAX      SEQUENCE OF Sr1646v2VEthOamEventLogEntry
   MAX-ACCESS  not-accessible
   STATUS      current
   DESCRIPTION
      "OAM event log"
   ::= {sr1646v2VEthOamEventLog 1}

sr1646v2VEthOamEventLogEntry OBJECT-TYPE
   SYNTAX      Sr1646v2VEthOamEventLogEntry
   MAX-ACCESS  not-accessible
   STATUS      current
   DESCRIPTION
      ""
   INDEX      { sr1646v2VEthOamEventLogGlobalIx,
                sr1646v2VEthOamEventLogTableIx }
   ::= {sr1646v2VEthOamEventLogSSCTable 1}

Sr1646v2VEthOamEventLogEntry ::=
   SEQUENCE
      {
      sr1646v2VEthOamEventLogGlobalIx
         GlobalIndex,
      sr1646v2VEthOamEventLogTableIx
         TableIndex,
      sr1646v2VEthOamEventLogSysUpTime
         TimeTicks,
      sr1646v2VEthOamEventLogLocation
         INTEGER,
      sr1646v2VEthOamEventLogType
         INTEGER,
      sr1646v2VEthOamEventLogOui
         OCTET STRING,
      sr1646v2VEthOamEventLogWindow
         Counter64,
      sr1646v2VEthOamEventLogThreshold
         Counter64,
      sr1646v2VEthOamEventLogTotal
         Counter32,
      sr1646v2VEthOamEventLogValue
         Counter64,
      sr1646v2VEthOamEventLogRunningTotal
         Counter64
      }

sr1646v2VEthOamEventLogGlobalIx OBJECT-TYPE
   SYNTAX      GlobalIndex
   MAX-ACCESS  not-accessible
   STATUS      current
   DESCRIPTION
      "The value of the tlsCntTreeGlobalIndex of the MANAGED OBJECT."
   ::= {sr1646v2VEthOamEventLogEntry 10}

sr1646v2VEthOamEventLogTableIx OBJECT-TYPE
   SYNTAX      TableIndex
   MAX-ACCESS  not-accessible
   STATUS      current
   DESCRIPTION
      ""
   ::= {sr1646v2VEthOamEventLogEntry 11}

sr1646v2VEthOamEventLogSysUpTime OBJECT-TYPE
   SYNTAX      TimeTicks
   MAX-ACCESS  read-only
   STATUS      current
   DESCRIPTION
      "Path: virtualEthernet.status.oamEventLog.sysUpTime

       Time in centi-second."
   ::= {sr1646v2VEthOamEventLogEntry 16777216}

sr1646v2VEthOamEventLogLocation OBJECT-TYPE
   SYNTAX      INTEGER
               {
               local (1),
               remote (2)
               }
   MAX-ACCESS  read-only
   STATUS      current
   DESCRIPTION
      "Path: virtualEthernet.status.oamEventLog.location

       Possibilities:
               local   (1)
               remote   (2)"
   ::= {sr1646v2VEthOamEventLogEntry 33554432}

sr1646v2VEthOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: virtualEthernet.status.oamEventLog.type

       Possibilities:
               erroredSymbols   (1)
               erroredFramePeriod   (2)
               erroredFrame   (3)
               erroredFrameSeconds   (4)
               linkFault   (256)
               dyingGasp   (257)
               criticalLink   (258)"
   ::= {sr1646v2VEthOamEventLogEntry 50331648}

sr1646v2VEthOamEventLogOui OBJECT-TYPE
   SYNTAX      OCTET STRING
   MAX-ACCESS  read-only
   STATUS      current
   DESCRIPTION
      "Path: virtualEthernet.status.oamEventLog.oui"
   ::= {sr1646v2VEthOamEventLogEntry 67108864}

sr1646v2VEthOamEventLogWindow OBJECT-TYPE
   SYNTAX      Counter64
   MAX-ACCESS  read-only
   STATUS      current
   DESCRIPTION
      "Path: virtualEthernet.status.oamEventLog.window

       64 bit unsigned wrappable counter."
   ::= {sr1646v2VEthOamEventLogEntry 83886080}

sr1646v2VEthOamEventLogThreshold OBJECT-TYPE
   SYNTAX      Counter64
   MAX-ACCESS  read-only
   STATUS      current
   DESCRIPTION
      "Path: virtualEthernet.status.oamEventLog.threshold

       64 bit unsigned wrappable counter."
   ::= {sr1646v2VEthOamEventLogEntry 100663296}

sr1646v2VEthOamEventLogTotal OBJECT-TYPE
   SYNTAX      Counter32
   MAX-ACCESS  read-only
   STATUS      current
   DESCRIPTION
      "Path: virtualEthernet.status.oamEventLog.total

       32 bit unsigned wrappable counter."
   ::= {sr1646v2VEthOamEventLogEntry 117440512}

sr1646v2VEthOamEventLogValue OBJECT-TYPE
   SYNTAX      Counter64
   MAX-ACCESS  read-only
   STATUS      current
   DESCRIPTION
      "Path: virtualEthernet.status.oamEventLog.value

       64 bit unsigned wrappable counter."
   ::= {sr1646v2VEthOamEventLogEntry 134217728}

sr1646v2VEthOamEventLogRunningTotal OBJECT-TYPE
   SYNTAX      Counter64
   MAX-ACCESS  read-only
   STATUS      current
   DESCRIPTION
      "Path: virtualEthernet.status.oamEventLog.runningTotal

       64 bit unsigned wrappable counter."
   ::= {sr1646v2VEthOamEventLogEntry 150994944}


sr1646v2VEthVlan OBJECT IDENTIFIER ::= {sr1646v2VEth 34}

sr1646v2VEthVlanSSCTable OBJECT-TYPE
   SYNTAX      SEQUENCE OF Sr1646v2VEthVlanEntry
   MAX-ACCESS  not-accessible
   STATUS      current
   DESCRIPTION
      ""
   ::= {sr1646v2VEthVlan 1}

sr1646v2VEthVlanEntry OBJECT-TYPE
   SYNTAX      Sr1646v2VEthVlanEntry
   MAX-ACCESS  not-accessible
   STATUS      current
   DESCRIPTION
      ""
   INDEX      { sr1646v2VEthVlanGlobalIx,
                sr1646v2VEthVlanTableIx }
   ::= {sr1646v2VEthVlanSSCTable 1}

Sr1646v2VEthVlanEntry ::=
   SEQUENCE
      {
      sr1646v2VEthVlanGlobalIx
         GlobalIndex,
      sr1646v2VEthVlanTableIx
         TableIndex,
      sr1646v2VEthVlanName
         DisplayString,
      sr1646v2VEthVlanMode
         INTEGER,
      sr1646v2VEthVlanIfOperStatus
         INTEGER,
      sr1646v2VEthVlanIfLastChange
         TimeTicks,
      sr1646v2VEthVlanIfLastChangeDate
         DisplayString,
      sr1646v2VEthVlanIpAddress
         IpAddress,
      sr1646v2VEthVlanIpNetMask
         IpAddress,
      sr1646v2VEthVlanIpRemote
         IpAddress,
      sr1646v2VEthVlanIpDhcpStatus
         INTEGER,
      sr1646v2VEthVlanIpDhcpLeaseTime
         TimeTicks,
      sr1646v2VEthVlanIpV6State
         INTEGER,
      sr1646v2VEthVlanIpV6InterfaceId
         OCTET STRING,
      sr1646v2VEthVlanIpV6LinkMtu
         Integer32,
      sr1646v2VEthVlanIpV6HopLimit
         Integer32,
      sr1646v2VEthVlanIpV6DhcpIaid
         Counter32,
      sr1646v2VEthVlanIpV6RaRcvOption
         Integer32,
      sr1646v2VEthVlanBridgingStatus
         INTEGER,
      sr1646v2VEthVlanBridgingSpanningTreePortRole
         INTEGER,
      sr1646v2VEthVlanBridgingSpanningTreePortId
         Integer32,
      sr1646v2VEthVlanBridgingSpanningTreePpCostExtPathCost
         Integer32,
      sr1646v2VEthVlanBridgingSpanningTreePpCostIntPathCost
         Integer32,
      sr1646v2VEthVlanBridgingSpanningTreeExtRpCost
         Integer32,
      sr1646v2VEthVlanBridgingSpanningTreeIntRpCost
         Integer32,
      sr1646v2VEthVlanBridgingSpanningTreeDesBrIdPriority
         Integer32,
      sr1646v2VEthVlanBridgingSpanningTreeDesBrIdMacAddress
         OCTET STRING,
      sr1646v2VEthVlanBridgingSpanningTreeDesPrtId
         Integer32,
      sr1646v2VEthVlanBridgingSpanningTreeDesInt
         INTEGER,
      sr1646v2VEthVlanBridgingSpanningTreeEdgeDetection
         INTEGER,
      sr1646v2VEthVlanVlanVid
         Integer32,
      sr1646v2VEthVlanPppOEthDiscState
         INTEGER,
      sr1646v2VEthVlanPppOEthPeerMac
         OCTET STRING,
      sr1646v2VEthVlanPppOEthServiceName
         DisplayString,
      sr1646v2VEthVlanPppLcpState
         INTEGER,
      sr1646v2VEthVlanPppIpcpState
         INTEGER,
      sr1646v2VEthVlanPppIp6cpState
         INTEGER,
      sr1646v2VEthVlanPppMyAutSt
         INTEGER,
      sr1646v2VEthVlanPppHisAutSt
         INTEGER,
      sr1646v2VEthVlanPppMru
         Integer32
      }

sr1646v2VEthVlanGlobalIx OBJECT-TYPE
   SYNTAX      GlobalIndex
   MAX-ACCESS  not-accessible
   STATUS      current
   DESCRIPTION
      "The value of the tlsCntTreeGlobalIndex of the MANAGED OBJECT."
   ::= {sr1646v2VEthVlanEntry 10}

sr1646v2VEthVlanTableIx OBJECT-TYPE
   SYNTAX      TableIndex
   MAX-ACCESS  not-accessible
   STATUS      current
   DESCRIPTION
      ""
   ::= {sr1646v2VEthVlanEntry 11}

sr1646v2VEthVlanName OBJECT-TYPE
   SYNTAX      DisplayString
   MAX-ACCESS  read-only
   STATUS      current
   DESCRIPTION
      "Path: virtualEthernet.status.vlan.name"
   ::= {sr1646v2VEthVlanEntry 16777216}

sr1646v2VEthVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: virtualEthernet.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2VEthVlanEntry 335544320}

sr1646v2VEthVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.vlan.ifOperStatus

       Possibilities:
               up   (1)
               down   (2)
               testing   (3)
               unknown   (4)
               dormant   (5)
               notPresent   (6)
               lowerLayerDown   (7)"
   ::= {sr1646v2VEthVlanEntry 1795162112}

sr1646v2VEthVlanIfLastChange OBJECT-TYPE
   SYNTAX      TimeTicks
   MAX-ACCESS  read-only
   STATUS      current
   DESCRIPTION
      "Path: virtualEthernet.status.vlan.ifLastChange

       Time in centi-second."
   ::= {sr1646v2VEthVlanEntry 1811939328}

sr1646v2VEthVlanIfLastChangeDate OBJECT-TYPE
   SYNTAX      DisplayString
   MAX-ACCESS  read-only
   STATUS      current
   DESCRIPTION
      "Path: virtualEthernet.status.vlan.ifLastChangeDate"
   ::= {sr1646v2VEthVlanEntry 3070230528}

sr1646v2VEthVlanIpAddress OBJECT-TYPE
   SYNTAX      IpAddress
   MAX-ACCESS  read-only
   STATUS      current
   DESCRIPTION
      "Path: virtualEthernet.status.vlan.ip.address"
   ::= {sr1646v2VEthVlanEntry 51380224}

sr1646v2VEthVlanIpNetMask OBJECT-TYPE
   SYNTAX      IpAddress
   MAX-ACCESS  read-only
   STATUS      current
   DESCRIPTION
      "Path: virtualEthernet.status.vlan.ip.netMask"
   ::= {sr1646v2VEthVlanEntry 51445760}

sr1646v2VEthVlanIpRemote OBJECT-TYPE
   SYNTAX      IpAddress
   MAX-ACCESS  read-only
   STATUS      current
   DESCRIPTION
      "Path: virtualEthernet.status.vlan.ip.remote"
   ::= {sr1646v2VEthVlanEntry 51511296}

sr1646v2VEthVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: virtualEthernet.status.vlan.ip.dhcp.status

       Possibilities:
               none   (0)
               selecting   (1)
               requesting   (2)
               rebinding   (3)
               bound   (4)
               renewing   (5)
               rebooting   (6)
               initreboot   (7)"
   ::= {sr1646v2VEthVlanEntry 51904768}

sr1646v2VEthVlanIpDhcpLeaseTime OBJECT-TYPE
   SYNTAX      TimeTicks
   MAX-ACCESS  read-only
   STATUS      current
   DESCRIPTION
      "Path: virtualEthernet.status.vlan.ip.dhcp.leaseTime

       Time in centi-second."
   ::= {sr1646v2VEthVlanEntry 51905024}

sr1646v2VEthVlanIpV6State OBJECT-TYPE
   SYNTAX      INTEGER
               {
               disabled (0),
               enabled (1)
               }
   MAX-ACCESS  read-only
   STATUS      current
   DESCRIPTION
      "Path: virtualEthernet.status.vlan.ipV6.state

       Possibilities:
               disabled   (0)
               enabled   (1)"
   ::= {sr1646v2VEthVlanEntry 100728832}

sr1646v2VEthVlanIpV6InterfaceId OBJECT-TYPE
   SYNTAX      OCTET STRING
   MAX-ACCESS  read-only
   STATUS      current
   DESCRIPTION
      "Path: virtualEthernet.status.vlan.ipV6.interfaceId"
   ::= {sr1646v2VEthVlanEntry 100794368}

sr1646v2VEthVlanIpV6LinkMtu OBJECT-TYPE
   SYNTAX      Integer32
   MAX-ACCESS  read-only
   STATUS      current
   DESCRIPTION
      "Path: virtualEthernet.status.vlan.ipV6.linkMtu"
   ::= {sr1646v2VEthVlanEntry 100925440}

sr1646v2VEthVlanIpV6HopLimit OBJECT-TYPE
   SYNTAX      Integer32
   MAX-ACCESS  read-only
   STATUS      current
   DESCRIPTION
      "Path: virtualEthernet.status.vlan.ipV6.hopLimit"
   ::= {sr1646v2VEthVlanEntry 100990976}

sr1646v2VEthVlanIpV6DhcpIaid OBJECT-TYPE
   SYNTAX      Counter32
   MAX-ACCESS  read-only
   STATUS      current
   DESCRIPTION
      "Path: virtualEthernet.status.vlan.ipV6.dhcp.iaid

       32 bit unsigned wrappable counter."
   ::= {sr1646v2VEthVlanEntry 101056768}

sr1646v2VEthVlanIpV6RaRcvOption OBJECT-TYPE
   SYNTAX      Integer32
   MAX-ACCESS  read-only
   STATUS      current
   DESCRIPTION
      "Path: virtualEthernet.status.vlan.ipV6.raRcvOption

       Bit meanings:
               bit 0 = linkMtu,
               bit 1 = srcLinkLayer,
               bit 2 = prefixInfo,
               bit 3 = rdnss,
               bit 4 = dnssl"
   ::= {sr1646v2VEthVlanEntry 101122048}

sr1646v2VEthVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: virtualEthernet.status.vlan.bridging.status

       Possibilities:
               disabled   (0)
               discarding   (1)
               learning   (2)
               forwarding   (3)
               backupBlockedIntfDown   (256)
               backupBlockedIntfUp   (259)
               shutdown   (255)"
   ::= {sr1646v2VEthVlanEntry 453050368}

sr1646v2VEthVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: virtualEthernet.status.vlan.bridging.spanningTree.portRole

       Possibilities:
               none   (0)
               root   (1)
               designated   (2)
               alternate   (3)
               backup   (4)
               disabled   (5)
               master   (6)"
   ::= {sr1646v2VEthVlanEntry 453116160}

sr1646v2VEthVlanBridgingSpanningTreePortId OBJECT-TYPE
   SYNTAX      Integer32
   MAX-ACCESS  read-only
   STATUS      current
   DESCRIPTION
      "Path: virtualEthernet.status.vlan.bridging.spanningTree.portId"
   ::= {sr1646v2VEthVlanEntry 453116416}

sr1646v2VEthVlanBridgingSpanningTreePpCostExtPathCost OBJECT-TYPE
   SYNTAX      Integer32
   MAX-ACCESS  read-only
   STATUS      current
   DESCRIPTION
      "Path: virtualEthernet.status.vlan.bridging.spanningTree.portPathCosts.extPathCost"
   ::= {sr1646v2VEthVlanEntry 453116673}

sr1646v2VEthVlanBridgingSpanningTreePpCostIntPathCost OBJECT-TYPE
   SYNTAX      Integer32
   MAX-ACCESS  read-only
   STATUS      current
   DESCRIPTION
      "Path: virtualEthernet.status.vlan.bridging.spanningTree.portPathCosts.intPathCost"
   ::= {sr1646v2VEthVlanEntry 453116674}

sr1646v2VEthVlanBridgingSpanningTreeExtRpCost OBJECT-TYPE
   SYNTAX      Integer32
   MAX-ACCESS  read-only
   STATUS      current
   DESCRIPTION
      "Path: virtualEthernet.status.vlan.bridging.spanningTree.extRootPathCost"
   ::= {sr1646v2VEthVlanEntry 453116928}

sr1646v2VEthVlanBridgingSpanningTreeIntRpCost OBJECT-TYPE
   SYNTAX      Integer32
   MAX-ACCESS  read-only
   STATUS      current
   DESCRIPTION
      "Path: virtualEthernet.status.vlan.bridging.spanningTree.intRootPathCost"
   ::= {sr1646v2VEthVlanEntry 453117184}

sr1646v2VEthVlanBridgingSpanningTreeDesBrIdPriority OBJECT-TYPE
   SYNTAX      Integer32
   MAX-ACCESS  read-only
   STATUS      current
   DESCRIPTION
      "Path: virtualEthernet.status.vlan.bridging.spanningTree.designatedBridgeId.priority"
   ::= {sr1646v2VEthVlanEntry 453117441}

sr1646v2VEthVlanBridgingSpanningTreeDesBrIdMacAddress OBJECT-TYPE
   SYNTAX      OCTET STRING
   MAX-ACCESS  read-only
   STATUS      current
   DESCRIPTION
      "Path: virtualEthernet.status.vlan.bridging.spanningTree.designatedBridgeId.macAddress

       MAC address."
   ::= {sr1646v2VEthVlanEntry 453117442}

sr1646v2VEthVlanBridgingSpanningTreeDesPrtId OBJECT-TYPE
   SYNTAX      Integer32
   MAX-ACCESS  read-only
   STATUS      current
   DESCRIPTION
      "Path: virtualEthernet.status.vlan.bridging.spanningTree.designatedPortId"
   ::= {sr1646v2VEthVlanEntry 453117696}

sr1646v2VEthVlanBridgingSpanningTreeDesInt OBJECT-TYPE
   SYNTAX      INTEGER
               {
               no (0),
               yes (1)
               }
   MAX-ACCESS  read-only
   STATUS      current
   DESCRIPTION
      "Path: virtualEthernet.status.vlan.bridging.spanningTree.designatedOrInternal

       Possibilities:
               no   (0)
               yes   (1)"
   ::= {sr1646v2VEthVlanEntry 453117952}

sr1646v2VEthVlanBridgingSpanningTreeEdgeDetection OBJECT-TYPE
   SYNTAX      INTEGER
               {
               none (0),
               edge (1),
               notEdge (2)
               }
   MAX-ACCESS  read-only
   STATUS      current
   DESCRIPTION
      "Path: virtualEthernet.status.vlan.bridging.spanningTree.edgeDetection

       Possibilities:
               none   (0)
               edge   (1)
               notEdge   (2)"
   ::= {sr1646v2VEthVlanEntry 453118208}

sr1646v2VEthVlanVlanVid OBJECT-TYPE
   SYNTAX      Integer32
   MAX-ACCESS  read-only
   STATUS      current
   DESCRIPTION
      "Path: virtualEthernet.status.vlan.vlan.vid"
   ::= {sr1646v2VEthVlanEntry 234946560}

sr1646v2VEthVlanPppOEthDiscState OBJECT-TYPE
   SYNTAX      INTEGER
               {
               idle (0),
               waitForPADO (1),
               waitForPADS (2),
               established (3)
               }
   MAX-ACCESS  read-only
   STATUS      current
   DESCRIPTION
      "Path: virtualEthernet.status.vlan.pppOverEth.discState

       Possibilities:
               idle   (0)
               waitForPADO   (1)
               waitForPADS   (2)
               established   (3)"
   ::= {sr1646v2VEthVlanEntry 67174400}

sr1646v2VEthVlanPppOEthPeerMac OBJECT-TYPE
   SYNTAX      OCTET STRING
   MAX-ACCESS  read-only
   STATUS      current
   DESCRIPTION
      "Path: virtualEthernet.status.vlan.pppOverEth.remoteMacAddress

       MAC address."
   ::= {sr1646v2VEthVlanEntry 67239936}

sr1646v2VEthVlanPppOEthServiceName OBJECT-TYPE
   SYNTAX      DisplayString
   MAX-ACCESS  read-only
   STATUS      current
   DESCRIPTION
      "Path: virtualEthernet.status.vlan.pppOverEth.serviceName"
   ::= {sr1646v2VEthVlanEntry 67305472}

sr1646v2VEthVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VEthVlanEntry 83951616}

sr1646v2VEthVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VEthVlanEntry 84017152}

sr1646v2VEthVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VEthVlanEntry 84869120}

sr1646v2VEthVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: virtualEthernet.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2VEthVlanEntry 84541440}

sr1646v2VEthVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: virtualEthernet.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2VEthVlanEntry 84606976}

sr1646v2VEthVlanPppMru OBJECT-TYPE
   SYNTAX      Integer32
   MAX-ACCESS  read-only
   STATUS      current
   DESCRIPTION
      "Path: virtualEthernet.status.vlan.ppp.mru"
   ::= {sr1646v2VEthVlanEntry 84934656}

sr1646v2VEthVlanIpSecondaryIp OBJECT-TYPE
   SYNTAX      SEQUENCE OF Sr1646v2VEthVlanIpSecondaryIpEntry
   MAX-ACCESS  not-accessible
   STATUS      current
   DESCRIPTION
      ""
   ::= {sr1646v2VEthVlan 51838976}

sr1646v2VEthVlanIpSecondaryIpEntry OBJECT-TYPE
   SYNTAX      Sr1646v2VEthVlanIpSecondaryIpEntry
   MAX-ACCESS  not-accessible
   STATUS      current
   DESCRIPTION
      ""
   INDEX      { sr1646v2VEthVlanIpSecondaryIpGlobalIx,
                sr1646v2VEthVlanTableIx,
                sr1646v2VEthVlanIpSecondaryIpTableIx }
   ::= {sr1646v2VEthVlanIpSecondaryIp 1}

Sr1646v2VEthVlanIpSecondaryIpEntry ::=
   SEQUENCE
      {
      sr1646v2VEthVlanIpSecondaryIpGlobalIx
         GlobalIndex,
      sr1646v2VEthVlanIpSecondaryIpTableIx
         TableIndex,
      sr1646v2VEthVlanIpSecondaryIpAddress
         IpAddress,
      sr1646v2VEthVlanIpSecondaryIpNetMask
         IpAddress
      }

sr1646v2VEthVlanIpSecondaryIpGlobalIx OBJECT-TYPE
   SYNTAX      GlobalIndex
   MAX-ACCESS  not-accessible
   STATUS      current
   DESCRIPTION
      "The value of the tlsCntTreeGlobalIndex of the MANAGED OBJECT."
   ::= {sr1646v2VEthVlanIpSecondaryIpEntry 10}

sr1646v2VEthVlanIpSecondaryIpTableIx OBJECT-TYPE
   SYNTAX      TableIndex
   MAX-ACCESS  not-accessible
   STATUS      current
   DESCRIPTION
      ""
   ::= {sr1646v2VEthVlanIpSecondaryIpEntry 11}

sr1646v2VEthVlanIpSecondaryIpAddress OBJECT-TYPE
   SYNTAX      IpAddress
   MAX-ACCESS  read-only
   STATUS      current
   DESCRIPTION
      "Path: virtualEthernet.status.vlan.ip.secondaryIp.address"
   ::= {sr1646v2VEthVlanIpSecondaryIpEntry 2030043136}

sr1646v2VEthVlanIpSecondaryIpNetMask OBJECT-TYPE
   SYNTAX      IpAddress
   MAX-ACCESS  read-only
   STATUS      current
   DESCRIPTION
      "Path: virtualEthernet.status.vlan.ip.secondaryIp.netMask"
   ::= {sr1646v2VEthVlanIpSecondaryIpEntry 2063597568}

sr1646v2VEthVlanIpV6Addresses OBJECT-TYPE
   SYNTAX      SEQUENCE OF Sr1646v2VEthVlanIpV6AddressesEntry
   MAX-ACCESS  not-accessible
   STATUS      current
   DESCRIPTION
      ""
   ::= {sr1646v2VEthVlan 100859904}

sr1646v2VEthVlanIpV6AddressesEntry OBJECT-TYPE
   SYNTAX      Sr1646v2VEthVlanIpV6AddressesEntry
   MAX-ACCESS  not-accessible
   STATUS      current
   DESCRIPTION
      ""
   INDEX      { sr1646v2VEthVlanIpV6AddressesGlobalIx,
                sr1646v2VEthVlanTableIx,
                sr1646v2VEthVlanIpV6AddressesTableIx }
   ::= {sr1646v2VEthVlanIpV6Addresses 1}

Sr1646v2VEthVlanIpV6AddressesEntry ::=
   SEQUENCE
      {
      sr1646v2VEthVlanIpV6AddressesGlobalIx
         GlobalIndex,
      sr1646v2VEthVlanIpV6AddressesTableIx
         TableIndex,
      sr1646v2VEthVlanIpV6AddressesAddress
         Ipv6Address,
      sr1646v2VEthVlanIpV6AddressesPrefixLength
         Integer32,
      sr1646v2VEthVlanIpV6AddressesStatus
         INTEGER,
      sr1646v2VEthVlanIpV6AddressesOrigin
         INTEGER,
      sr1646v2VEthVlanIpV6AddressesFlagsInterfaceId
         INTEGER,
      sr1646v2VEthVlanIpV6AddressesFlagsAnycast
         INTEGER,
      sr1646v2VEthVlanIpV6AddressesTimersValidLifeTime
         TimeTicks,
      sr1646v2VEthVlanIpV6AddressesTimersPrefLifeTime
         TimeTicks
      }

sr1646v2VEthVlanIpV6AddressesGlobalIx OBJECT-TYPE
   SYNTAX      GlobalIndex
   MAX-ACCESS  not-accessible
   STATUS      current
   DESCRIPTION
      "The value of the tlsCntTreeGlobalIndex of the MANAGED OBJECT."
   ::= {sr1646v2VEthVlanIpV6AddressesEntry 10}

sr1646v2VEthVlanIpV6AddressesTableIx OBJECT-TYPE
   SYNTAX      TableIndex
   MAX-ACCESS  not-accessible
   STATUS      current
   DESCRIPTION
      ""
   ::= {sr1646v2VEthVlanIpV6AddressesEntry 11}

sr1646v2VEthVlanIpV6AddressesAddress OBJECT-TYPE
   SYNTAX      Ipv6Address
   MAX-ACCESS  read-only
   STATUS      current
   DESCRIPTION
      "Path: virtualEthernet.status.vlan.ipV6.addresses.address

       ipv6 address"
   ::= {sr1646v2VEthVlanIpV6AddressesEntry 16777216}

sr1646v2VEthVlanIpV6AddressesPrefixLength OBJECT-TYPE
   SYNTAX      Integer32
   MAX-ACCESS  read-only
   STATUS      current
   DESCRIPTION
      "Path: virtualEthernet.status.vlan.ipV6.addresses.prefixLength"
   ::= {sr1646v2VEthVlanIpV6AddressesEntry 33554432}

sr1646v2VEthVlanIpV6AddressesStatus OBJECT-TYPE
   SYNTAX      INTEGER
               {
               invalid (0),
               tentative (1),
               deprecated (2),
               preferred (3)
               }
   MAX-ACCESS  read-only
   STATUS      current
   DESCRIPTION
      "Path: virtualEthernet.status.vlan.ipV6.addresses.status

       Possibilities:
               invalid   (0)
               tentative   (1)
               deprecated   (2)
               preferred   (3)"
   ::= {sr1646v2VEthVlanIpV6AddressesEntry 50331648}

sr1646v2VEthVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: virtualEthernet.status.vlan.ipV6.addresses.origin

       Possibilities:
               unknown   (0)
               manual   (1)
               generalPrefix   (2)
               statelessAuto   (3)
               statefullAuto   (4)"
   ::= {sr1646v2VEthVlanIpV6AddressesEntry 67108864}

sr1646v2VEthVlanIpV6AddressesFlagsInterfaceId OBJECT-TYPE
   SYNTAX      INTEGER
               {
               no (0),
               yes (1)
               }
   MAX-ACCESS  read-only
   STATUS      current
   DESCRIPTION
      "Path: virtualEthernet.status.vlan.ipV6.addresses.flags.interfaceId

       Possibilities:
               no   (0)
               yes   (1)"
   ::= {sr1646v2VEthVlanIpV6AddressesEntry 83951616}

sr1646v2VEthVlanIpV6AddressesFlagsAnycast OBJECT-TYPE
   SYNTAX      INTEGER
               {
               no (0),
               yes (1)
               }
   MAX-ACCESS  read-only
   STATUS      current
   DESCRIPTION
      "Path: virtualEthernet.status.vlan.ipV6.addresses.flags.anycast

       Possibilities:
               no   (0)
               yes   (1)"
   ::= {sr1646v2VEthVlanIpV6AddressesEntry 84017152}

sr1646v2VEthVlanIpV6AddressesTimersValidLifeTime OBJECT-TYPE
   SYNTAX      TimeTicks
   MAX-ACCESS  read-only
   STATUS      current
   DESCRIPTION
      "Path: virtualEthernet.status.vlan.ipV6.addresses.timers.validLifeTime

       Time in centi-second."
   ::= {sr1646v2VEthVlanIpV6AddressesEntry 100794368}

sr1646v2VEthVlanIpV6AddressesTimersPrefLifeTime OBJECT-TYPE
   SYNTAX      TimeTicks
   MAX-ACCESS  read-only
   STATUS      current
   DESCRIPTION
      "Path: virtualEthernet.status.vlan.ipV6.addresses.timers.prefLifeTime

       Time in centi-second."
   ::= {sr1646v2VEthVlanIpV6AddressesEntry 100728832}

sr1646v2VEthVlanVlanArpCache OBJECT-TYPE
   SYNTAX      SEQUENCE OF Sr1646v2VEthVlanVlanArpCacheEntry
   MAX-ACCESS  not-accessible
   STATUS      current
   DESCRIPTION
      ""
   ::= {sr1646v2VEthVlan 235601920}

sr1646v2VEthVlanVlanArpCacheEntry OBJECT-TYPE
   SYNTAX      Sr1646v2VEthVlanVlanArpCacheEntry
   MAX-ACCESS  not-accessible
   STATUS      current
   DESCRIPTION
      ""
   INDEX      { sr1646v2VEthVlanVlanArpCacheGlobalIx,
                sr1646v2VEthVlanTableIx,
                sr1646v2VEthVlanVlanArpCacheTableIx }
   ::= {sr1646v2VEthVlanVlanArpCache 1}

Sr1646v2VEthVlanVlanArpCacheEntry ::=
   SEQUENCE
      {
      sr1646v2VEthVlanVlanArpCacheGlobalIx
         GlobalIndex,
      sr1646v2VEthVlanVlanArpCacheTableIx
         TableIndex,
      sr1646v2VEthVlanVlanArpCacheMacAddress
         OCTET STRING,
      sr1646v2VEthVlanVlanArpCacheIpAddress
         IpAddress,
      sr1646v2VEthVlanVlanArpCacheType
         INTEGER,
      sr1646v2VEthVlanVlanArpCacheTimeOut
         TimeTicks
      }

sr1646v2VEthVlanVlanArpCacheGlobalIx OBJECT-TYPE
   SYNTAX      GlobalIndex
   MAX-ACCESS  not-accessible
   STATUS      current
   DESCRIPTION
      "The value of the tlsCntTreeGlobalIndex of the MANAGED OBJECT."
   ::= {sr1646v2VEthVlanVlanArpCacheEntry 10}

sr1646v2VEthVlanVlanArpCacheTableIx OBJECT-TYPE
   SYNTAX      TableIndex
   MAX-ACCESS  not-accessible
   STATUS      current
   DESCRIPTION
      ""
   ::= {sr1646v2VEthVlanVlanArpCacheEntry 11}

sr1646v2VEthVlanVlanArpCacheMacAddress OBJECT-TYPE
   SYNTAX      OCTET STRING
   MAX-ACCESS  read-only
   STATUS      current
   DESCRIPTION
      "Path: virtualEthernet.status.vlan.vlan.arpCache.macAddress

       MAC address."
   ::= {sr1646v2VEthVlanVlanArpCacheEntry 16777216}

sr1646v2VEthVlanVlanArpCacheIpAddress OBJECT-TYPE
   SYNTAX      IpAddress
   MAX-ACCESS  read-only
   STATUS      current
   DESCRIPTION
      "Path: virtualEthernet.status.vlan.vlan.arpCache.ipAddress"
   ::= {sr1646v2VEthVlanVlanArpCacheEntry 33554432}

sr1646v2VEthVlanVlanArpCacheType OBJECT-TYPE
   SYNTAX      INTEGER
               {
               static (0),
               dynamic (1)
               }
   MAX-ACCESS  read-only
   STATUS      current
   DESCRIPTION
      "Path: virtualEthernet.status.vlan.vlan.arpCache.type

       Possibilities:
               static   (0)
               dynamic   (1)"
   ::= {sr1646v2VEthVlanVlanArpCacheEntry 50331648}

sr1646v2VEthVlanVlanArpCacheTimeOut OBJECT-TYPE
   SYNTAX      TimeTicks
   MAX-ACCESS  read-only
   STATUS      current
   DESCRIPTION
      "Path: virtualEthernet.status.vlan.vlan.arpCache.timeOut

       Time in centi-second."
   ::= {sr1646v2VEthVlanVlanArpCacheEntry 67108864}


sr1646v2VEthPppOE OBJECT IDENTIFIER ::= {sr1646v2VEth 36}

sr1646v2VEthPppOESSCTable OBJECT-TYPE
   SYNTAX      SEQUENCE OF Sr1646v2VEthPppOEEntry
   MAX-ACCESS  not-accessible
   STATUS      current
   DESCRIPTION
      ""
   ::= {sr1646v2VEthPppOE 1}

sr1646v2VEthPppOEEntry OBJECT-TYPE
   SYNTAX      Sr1646v2VEthPppOEEntry
   MAX-ACCESS  not-accessible
   STATUS      current
   DESCRIPTION
      ""
   INDEX      { sr1646v2VEthPppOEGlobalIx,
                sr1646v2VEthPppOETableIx }
   ::= {sr1646v2VEthPppOESSCTable 1}

Sr1646v2VEthPppOEEntry ::=
   SEQUENCE
      {
      sr1646v2VEthPppOEGlobalIx
         GlobalIndex,
      sr1646v2VEthPppOETableIx
         TableIndex,
      sr1646v2VEthPppOEName
         DisplayString,
      sr1646v2VEthPppOEMode
         INTEGER,
      sr1646v2VEthPppOEIfOperStatus
         INTEGER,
      sr1646v2VEthPppOEIfLastChange
         TimeTicks,
      sr1646v2VEthPppOEIfLastChangeDate
         DisplayString,
      sr1646v2VEthPppOEIpAddress
         IpAddress,
      sr1646v2VEthPppOEIpNetMask
         IpAddress,
      sr1646v2VEthPppOEIpRemote
         IpAddress,
      sr1646v2VEthPppOEPppOEthDiscState
         INTEGER,
      sr1646v2VEthPppOEPppOEthPeerMac
         OCTET STRING,
      sr1646v2VEthPppOEPppOEthServiceName
         DisplayString,
      sr1646v2VEthPppOEPppLcpState
         INTEGER,
      sr1646v2VEthPppOEPppIpcpState
         INTEGER,
      sr1646v2VEthPppOEPppIp6cpState
         INTEGER,
      sr1646v2VEthPppOEPppMyAutSt
         INTEGER,
      sr1646v2VEthPppOEPppHisAutSt
         INTEGER,
      sr1646v2VEthPppOEPppMru
         Integer32,
      sr1646v2VEthPppOEIpV6State
         INTEGER,
      sr1646v2VEthPppOEIpV6InterfaceId
         OCTET STRING,
      sr1646v2VEthPppOEIpV6LinkMtu
         Integer32,
      sr1646v2VEthPppOEIpV6HopLimit
         Integer32,
      sr1646v2VEthPppOEIpV6DhcpIaid
         Counter32,
      sr1646v2VEthPppOEIpV6RaRcvOption
         Integer32
      }

sr1646v2VEthPppOEGlobalIx OBJECT-TYPE
   SYNTAX      GlobalIndex
   MAX-ACCESS  not-accessible
   STATUS      current
   DESCRIPTION
      "The value of the tlsCntTreeGlobalIndex of the MANAGED OBJECT."
   ::= {sr1646v2VEthPppOEEntry 10}

sr1646v2VEthPppOETableIx OBJECT-TYPE
   SYNTAX      TableIndex
   MAX-ACCESS  not-accessible
   STATUS      current
   DESCRIPTION
      ""
   ::= {sr1646v2VEthPppOEEntry 11}

sr1646v2VEthPppOEName OBJECT-TYPE
   SYNTAX      DisplayString
   MAX-ACCESS  read-only
   STATUS      current
   DESCRIPTION
      "Path: virtualEthernet.status.pppoEClient.name"
   ::= {sr1646v2VEthPppOEEntry 16777216}

sr1646v2VEthPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: virtualEthernet.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1646v2VEthPppOEEntry 335544320}

sr1646v2VEthPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: virtualEthernet.status.pppoEClient.ifOperStatus

       Possibilities:
               up   (1)
               down   (2)
               testing   (3)
               unknown   (4)
               dormant   (5)
               notPresent   (6)
               lowerLayerDown   (7)"
   ::= {sr1646v2VEthPppOEEntry 1795162112}

sr1646v2VEthPppOEIfLastChange OBJECT-TYPE
   SYNTAX      TimeTicks
   MAX-ACCESS  read-only
   STATUS      current
   DESCRIPTION
      "Path: virtualEthernet.status.pppoEClient.ifLastChange

       Time in centi-second."
   ::= {sr1646v2VEthPppOEEntry 1811939328}

sr1646v2VEthPppOEIfLastChangeDate OBJECT-TYPE
   SYNTAX      DisplayString
   MAX-ACCESS  read-only
   STATUS      current
   DESCRIPTION
      "Path: virtualEthernet.status.pppoEClient.ifLastChangeDate"
   ::= {sr1646v2VEthPppOEEntry 3070230528}

sr1646v2VEthPppOEIpAddress OBJECT-TYPE
   SYNTAX      IpAddress
   MAX-ACCESS  read-only
   STATUS      current
   DESCRIPTION
      "Path: virtualEthernet.status.pppoEClient.ip.address"
   ::= {sr1646v2VEthPppOEEntry 51380224}

sr1646v2VEthPppOEIpNetMask OBJECT-TYPE
   SYNTAX      IpAddress
   MAX-ACCESS  read-only
   STATUS      current
   DESCRIPTION
      "Path: virtualEthernet.status.pppoEClient.ip.netMask"
   ::= {sr1646v2VEthPppOEEntry 51445760}

sr1646v2VEthPppOEIpRemote OBJECT-TYPE
   SYNTAX      IpAddress
   MAX-ACCESS  read-only
   STATUS      current
   DESCRIPTION
      "Path: virtualEthernet.status.pppoEClient.ip.remote"
   ::= {sr1646v2VEthPppOEEntry 51511296}

sr1646v2VEthPppOEPppOEthDiscState OBJECT-TYPE
   SYNTAX      INTEGER
               {
               idle (0),
               waitForPADO (1),
               waitForPADS (2),
               established (3)
               }
   MAX-ACCESS  read-only
   STATUS      current
   DESCRIPTION
      "Path: virtualEthernet.status.pppoEClient.pppOverEth.discState

       Possibilities:
               idle   (0)
               waitForPADO   (1)
               waitForPADS   (2)
               established   (3)"
   ::= {sr1646v2VEthPppOEEntry 67174400}

sr1646v2VEthPppOEPppOEthPeerMac OBJECT-TYPE
   SYNTAX      OCTET STRING
   MAX-ACCESS  read-only
   STATUS      current
   DESCRIPTION
      "Path: virtualEthernet.status.pppoEClient.pppOverEth.remoteMacAddress

       MAC address."
   ::= {sr1646v2VEthPppOEEntry 67239936}

sr1646v2VEthPppOEPppOEthServiceName OBJECT-TYPE
   SYNTAX      DisplayString
   MAX-ACCESS  read-only
   STATUS      current
   DESCRIPTION
      "Path: virtualEthernet.status.pppoEClient.pppOverEth.serviceName"
   ::= {sr1646v2VEthPppOEEntry 67305472}

sr1646v2VEthPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VEthPppOEEntry 83951616}

sr1646v2VEthPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VEthPppOEEntry 84017152}

sr1646v2VEthPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: virtualEthernet.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1646v2VEthPppOEEntry 84869120}

sr1646v2VEthPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: virtualEthernet.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1646v2VEthPppOEEntry 84541440}

sr1646v2VEthPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: virtualEthernet.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1646v2VEthPppOEEntry 84606976}

sr1646v2VEthPppOEPppMru OBJECT-TYPE
   SYNTAX      Integer32
   MAX-ACCESS  read-only
   STATUS      current
   DESCRIPTION
      "Path: virtualEthernet.status.pppoEClient.ppp.mru"
   ::= {sr1646v2VEthPppOEEntry 84934656}

sr1646v2VEthPppOEIpV6State OBJECT-TYPE
   SYNTAX      INTEGER
               {
               disabled (0),
               enabled (1)
               }
   MAX-ACCESS  read-only
   STATUS      current
   DESCRIPTION
      "Path: virtualEthernet.status.pppoEClient.ipV6.state

       Possibilities:
               disabled   (0)
               enabled   (1)"
   ::= {sr1646v2VEthPppOEEntry 100728832}

sr1646v2VEthPppOEIpV6InterfaceId OBJECT-TYPE
   SYNTAX      OCTET STRING
   MAX-ACCESS  read-only
   STATUS      current
   DESCRIPTION
      "Path: virtualEthernet.status.pppoEClient.ipV6.interfaceId"
   ::= {sr1646v2VEthPppOEEntry 100794368}

sr1646v2VEthPppOEIpV6LinkMtu OBJECT-TYPE
   SYNTAX      Integer32
   MAX-ACCESS  read-only
   STATUS      current
   DESCRIPTION
      "Path: virtualEthernet.status.pppoEClient.ipV6.linkMtu"
   ::= {sr1646v2VEthPppOEEntry 100925440}

sr1646v2VEthPppOEIpV6HopLimit OBJECT-TYPE
   SYNTAX      Integer32
   MAX-ACCESS  read-only
   STATUS      current
   DESCRIPTION
      "Path: virtualEthernet.status.pppoEClient.ipV6.hopLimit"
   ::= {sr1646v2VEthPppOEEntry 100990976}

sr1646v2VEthPppOEIpV6DhcpIaid OBJECT-TYPE
   SYNTAX      Counter32
   MAX-ACCESS  read-only
   STATUS      current
   DESCRIPTION
      "Path: virtualEthernet.status.pppoEClient.ipV6.dhcp.iaid

       32 bit unsigned wrappable counter."
   ::= {sr1646v2VEthPppOEEntry 101056768}

sr1646v2VEthPppOEIpV6RaRcvOption OBJECT-TYPE
   SYNTAX      Integer32
   MAX-ACCESS  read-only
   STATUS      current
   DESCRIPTION
      "Path: virtualEthernet.status.pppoEClient.ipV6.raRcvOption

       Bit meanings:
               bit 0 = linkMtu,
               bit 1 = srcLinkLayer,
               bit 2 = prefixInfo,
               bit 3 = rdnss,
               bit 4 = dnssl"
   ::= {sr1646v2VEthPppOEEntry 101122048}

sr1646v2VEthPppOEIpV6Addresses OBJECT-TYPE
   SYNTAX      SEQUENCE OF Sr1646v2VEthPppOEIpV6AddressesEntry
   MAX-ACCESS  not-accessible
   STATUS      current
   DESCRIPTION
      ""
   ::= {sr1646v2VEthPppOE 100859904}

sr1646v2VEthPppOEIpV6AddressesEntry OBJECT-TYPE
   SYNTAX      Sr1646v2VEthPppOEIpV6AddressesEntry
   MAX-ACCESS  not-accessible
   STATUS      current
   DESCRIPTION
      ""
   INDEX      { sr1646v2VEthPppOEIpV6AddressesGlobalIx,
                sr1646v2VEthPppOETableIx,
                sr1646v2VEthPppOEIpV6AddressesTableIx }
   ::= {sr1646v2VEthPppOEIpV6Addresses 1}

Sr1646v2VEthPppOEIpV6AddressesEntry ::=
   SEQUENCE
      {
      sr1646v2VEthPppOEIpV6AddressesGlobalIx
         GlobalIndex,
      sr1646v2VEthPppOEIpV6AddressesTableIx
         TableIndex,
      sr1646v2VEthPppOEIpV6AddressesAddress
         Ipv6Address,
      sr1646v2VEthPppOEIpV6AddressesPrefixLength
         Integer32,
      sr1646v2VEthPppOEIpV6AddressesStatus
         INTEGER,
      sr1646v2VEthPppOEIpV6AddressesOrigin
         INTEGER,
      sr1646v2VEthPppOEIpV6AddressesFlagsInterfaceId
         INTEGER,
      sr1646v2VEthPppOEIpV6AddressesFlagsAnycast
         INTEGER,
      sr1646v2VEthPppOEIpV6AddressesTimersValidLifeTime
         TimeTicks,
      sr1646v2VEthPppOEIpV6AddressesTimersPrefLifeTime
         TimeTicks
      }

sr1646v2VEthPppOEIpV6AddressesGlobalIx OBJECT-TYPE
   SYNTAX      GlobalIndex
   MAX-ACCESS  not-accessible
   STATUS      current
   DESCRIPTION
      "The value of the tlsCntTreeGlobalIndex of the MANAGED OBJECT."
   ::= {sr1646v2VEthPppOEIpV6AddressesEntry 10}

sr1646v2VEthPppOEIpV6AddressesTableIx OBJECT-TYPE
   SYNTAX      TableIndex
   MAX-ACCESS  not-accessible
   STATUS      current
   DESCRIPTION
      ""
   ::= {sr1646v2VEthPppOEIpV6AddressesEntry 11}

sr1646v2VEthPppOEIpV6AddressesAddress OBJECT-TYPE
   SYNTAX      Ipv6Address
   MAX-ACCESS  read-only
   STATUS      current
   DESCRIPTION
      "Path: virtualEthernet.status.pppoEClient.ipV6.addresses.address

       ipv6 address"
   ::= {sr1646v2VEthPppOEIpV6AddressesEntry 16777216}

sr1646v2VEthPppOEIpV6AddressesPrefixLength OBJECT-TYPE
   SYNTAX      Integer32
   MAX-ACCESS  read-only
   STATUS      current
   DESCRIPTION
      "Path: virtualEthernet.status.pppoEClient.ipV6.addresses.prefixLength"
   ::= {sr1646v2VEthPppOEIpV6AddressesEntry 33554432}

sr1646v2VEthPppOEIpV6AddressesStatus OBJECT-TYPE
   SYNTAX      INTEGER
               {
               invalid (0),
               tentative (1),
               deprecated (2),
               preferred (3)
               }
   MAX-ACCESS  read-only
   STATUS      current
   DESCRIPTION
      "Path: virtualEthernet.status.pppoEClient.ipV6.addresses.status

       Possibilities:
               invalid   (0)
               tentative   (1)
               deprecated   (2)
               preferred   (3)"
   ::= {sr1646v2VEthPppOEIpV6AddressesEntry 50331648}

sr1646v2VEthPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: virtualEthernet.status.pppoEClient.ipV6.addresses.origin

       Possibilities:
               unknown   (0)
               manual   (1)
               generalPrefix   (2)
               statelessAuto   (3)
               statefullAuto   (4)"
   ::= {sr1646v2VEthPppOEIpV6AddressesEntry 67108864}

sr1646v2VEthPppOEIpV6AddressesFlagsInterfaceId OBJECT-TYPE
   SYNTAX      INTEGER
               {
               no (0),
               yes (1)
               }
   MAX-ACCESS  read-only
   STATUS      current
   DESCRIPTION
      "Path: virtualEthernet.status.pppoEClient.ipV6.addresses.flags.interfaceId

       Possibilities:
               no   (0)
               yes   (1)"
   ::= {sr1646v2VEthPppOEIpV6AddressesEntry 83951616}

sr1646v2VEthPppOEIpV6AddressesFlagsAnycast OBJECT-TYPE
   SYNTAX      INTEGER
               {
               no (0),
               yes (1)
               }
   MAX-ACCESS  read-only
   STATUS      current
   DESCRIPTION
      "Path: virtualEthernet.status.pppoEClient.ipV6.addresses.flags.anycast

       Possibilities:
               no   (0)
               yes   (1)"
   ::= {sr1646v2VEthPppOEIpV6AddressesEntry 84017152}

sr1646v2VEthPppOEIpV6AddressesTimersValidLifeTime OBJECT-TYPE
   SYNTAX      TimeTicks
   MAX-ACCESS  read-only
   STATUS      current
   DESCRIPTION
      "Path: virtualEthernet.status.pppoEClient.ipV6.addresses.timers.validLifeTime

       Time in centi-second."
   ::= {sr1646v2VEthPppOEIpV6AddressesEntry 100794368}

sr1646v2VEthPppOEIpV6AddressesTimersPrefLifeTime OBJECT-TYPE
   SYNTAX      TimeTicks
   MAX-ACCESS  read-only
   STATUS      current
   DESCRIPTION
      "Path: virtualEthernet.status.pppoEClient.ipV6.addresses.timers.prefLifeTime

       Time in centi-second."
   ::= {sr1646v2VEthPppOEIpV6AddressesEntry 100728832}


sr1646v2VEthDot1x OBJECT IDENTIFIER ::= {sr1646v2VEth 190}

sr1646v2VEthDot1xSSCTable OBJECT-TYPE
   SYNTAX      SEQUENCE OF Sr1646v2VEthDot1xEntry
   MAX-ACCESS  not-accessible
   STATUS      current
   DESCRIPTION
      "Ethernet Switch VLAN Table"
   ::= {sr1646v2VEthDot1x 1}

sr1646v2VEthDot1xEntry OBJECT-TYPE
   SYNTAX      Sr1646v2VEthDot1xEntry
   MAX-ACCESS  not-accessible
   STATUS      current
   DESCRIPTION
      ""
   INDEX      { sr1646v2VEthDot1xGlobalIx,
                sr1646v2VEthDot1xTableIx }
   ::= {sr1646v2VEthDot1xSSCTable 1}

Sr1646v2VEthDot1xEntry ::=
   SEQUENCE
      {
      sr1646v2VEthDot1xGlobalIx
         GlobalIndex,
      sr1646v2VEthDot1xTableIx
         TableIndex,
      sr1646v2VEthDot1xRemote
         OCTET STRING,
      sr1646v2VEthDot1xAuthorized
         INTEGER,
      sr1646v2VEthDot1xAuthenticator
         INTEGER,
      sr1646v2VEthDot1xBackEnd
         INTEGER,
      sr1646v2VEthDot1xRetries
         Integer32,
      sr1646v2VEthDot1xReAuthTime
         TimeTicks,
      sr1646v2VEthDot1xHoldTime
         TimeTicks
      }

sr1646v2VEthDot1xGlobalIx OBJECT-TYPE
   SYNTAX      GlobalIndex
   MAX-ACCESS  not-accessible
   STATUS      current
   DESCRIPTION
      "The value of the tlsCntTreeGlobalIndex of the MANAGED OBJECT."
   ::= {sr1646v2VEthDot1xEntry 10}

sr1646v2VEthDot1xTableIx OBJECT-TYPE
   SYNTAX      TableIndex
   MAX-ACCESS  not-accessible
   STATUS      current
   DESCRIPTION
      ""
   ::= {sr1646v2VEthDot1xEntry 11}

sr1646v2VEthDot1xRemote OBJECT-TYPE
   SYNTAX      OCTET STRING
   MAX-ACCESS  read-only
   STATUS      current
   DESCRIPTION
      "Path: virtualEthernet.status.dot1x.remote

       MAC address."
   ::= {sr1646v2VEthDot1xEntry 16777216}

sr1646v2VEthDot1xAuthorized OBJECT-TYPE
   SYNTAX      INTEGER
               {
               no (0),
               yes (1)
               }
   MAX-ACCESS  read-only
   STATUS      current
   DESCRIPTION
      "Path: virtualEthernet.status.dot1x.authorized

       Possibilities:
               no   (0)
               yes   (1)"
   ::= {sr1646v2VEthDot1xEntry 33554432}

sr1646v2VEthDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: virtualEthernet.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1646v2VEthDot1xEntry 50331648}

sr1646v2VEthDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: virtualEthernet.status.dot1x.backEnd

       Possibilities:
               preInit   (0)
               initialize   (1)
               idle   (2)
               request   (3)
               response   (4)
               success   (5)
               failure   (6)
               radiusTimeout   (7)
               timeout   (8)"
   ::= {sr1646v2VEthDot1xEntry 67108864}

sr1646v2VEthDot1xRetries OBJECT-TYPE
   SYNTAX      Integer32
   MAX-ACCESS  read-only
   STATUS      current
   DESCRIPTION
      "Path: virtualEthernet.status.dot1x.retries"
   ::= {sr1646v2VEthDot1xEntry 83886080}

sr1646v2VEthDot1xReAuthTime OBJECT-TYPE
   SYNTAX      TimeTicks
   MAX-ACCESS  read-only
   STATUS      current
   DESCRIPTION
      "Path: virtualEthernet.status.dot1x.reAuthTime

       Time in centi-second."
   ::= {sr1646v2VEthDot1xEntry 100663296}

sr1646v2VEthDot1xHoldTime OBJECT-TYPE
   SYNTAX      TimeTicks
   MAX-ACCESS  read-only
   STATUS      current
   DESCRIPTION
      "Path: virtualEthernet.status.dot1x.holdTime

       Time in centi-second."
   ::= {sr1646v2VEthDot1xEntry 117440512}


sr1646v2VEthIpV6 OBJECT IDENTIFIER ::= {sr1646v2VEth 17}

sr1646v2VEthIpV6SSCTable OBJECT-TYPE
   SYNTAX      SEQUENCE OF Sr1646v2VEthIpV6Entry
   MAX-ACCESS  not-accessible
   STATUS      current
   DESCRIPTION
      "IPv6 interface config parameters"
   ::= {sr1646v2VEthIpV6 1}

sr1646v2VEthIpV6Entry OBJECT-TYPE
   SYNTAX      Sr1646v2VEthIpV6Entry
   MAX-ACCESS  not-accessible
   STATUS      current
   DESCRIPTION
      ""
   INDEX      { sr1646v2VEthIpV6GlobalIx }
   ::= {sr1646v2VEthIpV6SSCTable 1}

Sr1646v2VEthIpV6Entry ::=
   SEQUENCE
      {
      sr1646v2VEthIpV6GlobalIx
         GlobalIndex,
      sr1646v2VEthIpV6State
         INTEGER,
      sr1646v2VEthIpV6InterfaceId
         OCTET STRING,
      sr1646v2VEthIpV6LinkMtu
         Integer32,
      sr1646v2VEthIpV6HopLimit
         Integer32,
      sr1646v2VEthIpV6DhcpIaid
         Counter32,
      sr1646v2VEthIpV6RaRcvOption
         Integer32
      }

sr1646v2VEthIpV6GlobalIx OBJECT-TYPE
   SYNTAX      GlobalIndex
   MAX-ACCESS  not-accessible
   STATUS      current
   DESCRIPTION
      "The value of the tlsCntTreeGlobalIndex of the MANAGED OBJECT."
   ::= {sr1646v2VEthIpV6Entry 10}

sr1646v2VEthIpV6State OBJECT-TYPE
   SYNTAX      INTEGER
               {
               disabled (0),
               enabled (1)
               }
   MAX-ACCESS  read-only
   STATUS      current
   DESCRIPTION
      "Path: virtualEthernet.status.ipV6.state

       Possibilities:
               disabled   (0)
               enabled   (1)"
   ::= {sr1646v2VEthIpV6Entry 16777216}

sr1646v2VEthIpV6InterfaceId OBJECT-TYPE
   SYNTAX      OCTET STRING
   MAX-ACCESS  read-only
   STATUS      current
   DESCRIPTION
      "Path: virtualEthernet.status.ipV6.interfaceId"
   ::= {sr1646v2VEthIpV6Entry 33554432}

sr1646v2VEthIpV6LinkMtu OBJECT-TYPE
   SYNTAX      Integer32
   MAX-ACCESS  read-only
   STATUS      current
   DESCRIPTION
      "Path: virtualEthernet.status.ipV6.linkMtu"
   ::= {sr1646v2VEthIpV6Entry 67108864}

sr1646v2VEthIpV6HopLimit OBJECT-TYPE
   SYNTAX      Integer32
   MAX-ACCESS  read-only
   STATUS      current
   DESCRIPTION
      "Path: virtualEthernet.status.ipV6.hopLimit"
   ::= {sr1646v2VEthIpV6Entry 83886080}

sr1646v2VEthIpV6DhcpIaid OBJECT-TYPE
   SYNTAX      Counter32
   MAX-ACCESS  read-only
   STATUS      current
   DESCRIPTION
      "Path: virtualEthernet.status.ipV6.dhcp.iaid

       32 bit unsigned wrappable counter."
   ::= {sr1646v2VEthIpV6Entry 100728832}

sr1646v2VEthIpV6RaRcvOption OBJECT-TYPE
   SYNTAX      Integer32
   MAX-ACCESS  read-only
   STATUS      current
   DESCRIPTION
      "Path: virtualEthernet.status.ipV6.raRcvOption

       Bit meanings:
               bit 0 = linkMtu,
               bit 1 = srcLinkLayer,
               bit 2 = prefixInfo,
               bit 3 = rdnss,
               bit 4 = dnssl"
   ::= {sr1646v2VEthIpV6Entry 117440512}

sr1646v2VEthIpV6Addresses OBJECT-TYPE
   SYNTAX      SEQUENCE OF Sr1646v2VEthIpV6AddressesEntry
   MAX-ACCESS  not-accessible
   STATUS      current
   DESCRIPTION
      ""
   ::= {sr1646v2VEthIpV6 50331648}

sr1646v2VEthIpV6AddressesEntry OBJECT-TYPE
   SYNTAX      Sr1646v2VEthIpV6AddressesEntry
   MAX-ACCESS  not-accessible
   STATUS      current
   DESCRIPTION
      ""
   INDEX      { sr1646v2VEthIpV6AddressesGlobalIx,
                sr1646v2VEthIpV6AddressesTableIx }
   ::= {sr1646v2VEthIpV6Addresses 1}

Sr1646v2VEthIpV6AddressesEntry ::=
   SEQUENCE
      {
      sr1646v2VEthIpV6AddressesGlobalIx
         GlobalIndex,
      sr1646v2VEthIpV6AddressesTableIx
         TableIndex,
      sr1646v2VEthIpV6AddressesAddress
         Ipv6Address,
      sr1646v2VEthIpV6AddressesPrefixLength
         Integer32,
      sr1646v2VEthIpV6AddressesStatus
         INTEGER,
      sr1646v2VEthIpV6AddressesOrigin
         INTEGER,
      sr1646v2VEthIpV6AddressesFlagsInterfaceId
         INTEGER,
      sr1646v2VEthIpV6AddressesFlagsAnycast
         INTEGER,
      sr1646v2VEthIpV6AddressesTimersValidLifeTime
         TimeTicks,
      sr1646v2VEthIpV6AddressesTimersPrefLifeTime
         TimeTicks
      }

sr1646v2VEthIpV6AddressesGlobalIx OBJECT-TYPE
   SYNTAX      GlobalIndex
   MAX-ACCESS  not-accessible
   STATUS      current
   DESCRIPTION
      "The value of the tlsCntTreeGlobalIndex of the MANAGED OBJECT."
   ::= {sr1646v2VEthIpV6AddressesEntry 10}

sr1646v2VEthIpV6AddressesTableIx OBJECT-TYPE
   SYNTAX      TableIndex
   MAX-ACCESS  not-accessible
   STATUS      current
   DESCRIPTION
      ""
   ::= {sr1646v2VEthIpV6AddressesEntry 11}

sr1646v2VEthIpV6AddressesAddress OBJECT-TYPE
   SYNTAX      Ipv6Address
   MAX-ACCESS  read-only
   STATUS      current
   DESCRIPTION
      "Path: virtualEthernet.status.ipV6.addresses.address

       ipv6 address"
   ::= {sr1646v2VEthIpV6AddressesEntry 16777216}

sr1646v2VEthIpV6AddressesPrefixLength OBJECT-TYPE
   SYNTAX      Integer32
   MAX-ACCESS  read-only
   STATUS      current
   DESCRIPTION
      "Path: virtualEthernet.status.ipV6.addresses.prefixLength"
   ::= {sr1646v2VEthIpV6AddressesEntry 33554432}

sr1646v2VEthIpV6AddressesStatus OBJECT-TYPE
   SYNTAX      INTEGER
               {
               invalid (0),
               tentative (1),
               deprecated (2),
               preferred (3)
               }
   MAX-ACCESS  read-only
   STATUS      current
   DESCRIPTION
      "Path: virtualEthernet.status.ipV6.addresses.status

       Possibilities:
               invalid   (0)
               tentative   (1)
               deprecated   (2)
               preferred   (3)"
   ::= {sr1646v2VEthIpV6AddressesEntry 50331648}

sr1646v2VEthIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: virtualEthernet.status.ipV6.addresses.origin

       Possibilities:
               unknown   (0)
               manual   (1)
               generalPrefix   (2)
               statelessAuto   (3)
               statefullAuto   (4)"
   ::= {sr1646v2VEthIpV6AddressesEntry 67108864}

sr1646v2VEthIpV6AddressesFlagsInterfaceId OBJECT-TYPE
   SYNTAX      INTEGER
               {
               no (0),
               yes (1)
               }
   MAX-ACCESS  read-only
   STATUS      current
   DESCRIPTION
      "Path: virtualEthernet.status.ipV6.addresses.flags.interfaceId

       Possibilities:
               no   (0)
               yes   (1)"
   ::= {sr1646v2VEthIpV6AddressesEntry 83951616}

sr1646v2VEthIpV6AddressesFlagsAnycast OBJECT-TYPE
   SYNTAX      INTEGER
               {
               no (0),
               yes (1)
               }
   MAX-ACCESS  read-only
   STATUS      current
   DESCRIPTION
      "Path: virtualEthernet.status.ipV6.addresses.flags.anycast

       Possibilities:
               no   (0)
               yes   (1)"
   ::= {sr1646v2VEthIpV6AddressesEntry 84017152}

sr1646v2VEthIpV6AddressesTimersValidLifeTime OBJECT-TYPE
   SYNTAX      TimeTicks
   MAX-ACCESS  read-only
   STATUS      current
   DESCRIPTION
      "Path: virtualEthernet.status.ipV6.addresses.timers.validLifeTime

       Time in centi-second."
   ::= {sr1646v2VEthIpV6AddressesEntry 100794368}

sr1646v2VEthIpV6AddressesTimersPrefLifeTime OBJECT-TYPE
   SYNTAX      TimeTicks
   MAX-ACCESS  read-only
   STATUS      current
   DESCRIPTION
      "Path: virtualEthernet.status.ipV6.addresses.timers.prefLifeTime

       Time in centi-second."
   ::= {sr1646v2VEthIpV6AddressesEntry 100728832}


sr1646v2VEthSnmpIndex OBJECT IDENTIFIER ::= {sr1646v2VEth 269}

sr1646v2VEthSnmpIndexTable OBJECT-TYPE
   SYNTAX      SEQUENCE OF Sr1646v2VEthSnmpIndexEntry
   MAX-ACCESS  not-accessible
   STATUS      current
   DESCRIPTION
      "SNMP index assigned to this object"
   ::= {sr1646v2VEthSnmpIndex 1}

sr1646v2VEthSnmpIndexEntry OBJECT-TYPE
   SYNTAX      Sr1646v2VEthSnmpIndexEntry
   MAX-ACCESS  not-accessible
   STATUS      current
   DESCRIPTION
      ""
   INDEX      { sr1646v2VEthSnmpIndexGlobalIx }
   ::= {sr1646v2VEthSnmpIndexTable 1}

Sr1646v2VEthSnmpIndexEntry ::=
   SEQUENCE
      {
      sr1646v2VEthSnmpIndexGlobalIx
         GlobalIndex,
      sr1646v2VEthSnmpIndexValue
         Integer32
      }

sr1646v2VEthSnmpIndexGlobalIx OBJECT-TYPE
   SYNTAX      GlobalIndex
   MAX-ACCESS  not-accessible
   STATUS      current
   DESCRIPTION
      "The value of the tlsCntTreeGlobalIndex of the MANAGED OBJECT."
   ::= {sr1646v2VEthSnmpIndexEntry 10}

sr1646v2VEthSnmpIndexValue OBJECT-TYPE
   SYNTAX      Integer32
   MAX-ACCESS  read-only
   STATUS      current
   DESCRIPTION
      "Path: virtualEthernet.status.snmpIndex"
   ::= {sr1646v2VEthSnmpIndexEntry 2147483648}



pr1646v2VEth OBJECT IDENTIFIER ::= {r1646v2VEth 12}


pr1646v2VEthInOctets OBJECT IDENTIFIER ::= {pr1646v2VEth 109}

pr1646v2VEthInOctetsTable OBJECT-TYPE
   SYNTAX      SEQUENCE OF Pr1646v2VEthInOctetsEntry
   MAX-ACCESS  not-accessible
   STATUS      current
   DESCRIPTION
      "ifInOctets"
   ::= {pr1646v2VEthInOctets 1}

pr1646v2VEthInOctetsEntry OBJECT-TYPE
   SYNTAX      Pr1646v2VEthInOctetsEntry
   MAX-ACCESS  not-accessible
   STATUS      current
   DESCRIPTION
      ""
   INDEX      { pr1646v2VEthInOctetsGlobalIx }
   ::= {pr1646v2VEthInOctetsTable 1}

Pr1646v2VEthInOctetsEntry ::=
   SEQUENCE
      {
      pr1646v2VEthInOctetsGlobalIx
         GlobalIndex,
      pr1646v2VEthInOctetsValue
         Counter64
      }

pr1646v2VEthInOctetsGlobalIx OBJECT-TYPE
   SYNTAX      GlobalIndex
   MAX-ACCESS  not-accessible
   STATUS      current
   DESCRIPTION
      "The value of the tlsCntTreeGlobalIndex of the MANAGED OBJECT."
   ::= {pr1646v2VEthInOctetsEntry 10}

pr1646v2VEthInOctetsValue OBJECT-TYPE
   SYNTAX      Counter64
   MAX-ACCESS  read-only
   STATUS      current
   DESCRIPTION
      "Path: virtualEthernet.performance.ifInOctets

       64 bit unsigned wrappable counter."
   ::= {pr1646v2VEthInOctetsEntry 2147483648}


pr1646v2VEthInUcast OBJECT IDENTIFIER ::= {pr1646v2VEth 110}

pr1646v2VEthInUcastTable OBJECT-TYPE
   SYNTAX      SEQUENCE OF Pr1646v2VEthInUcastEntry
   MAX-ACCESS  not-accessible
   STATUS      current
   DESCRIPTION
      "ifInUcastPkts"
   ::= {pr1646v2VEthInUcast 1}

pr1646v2VEthInUcastEntry OBJECT-TYPE
   SYNTAX      Pr1646v2VEthInUcastEntry
   MAX-ACCESS  not-accessible
   STATUS      current
   DESCRIPTION
      ""
   INDEX      { pr1646v2VEthInUcastGlobalIx }
   ::= {pr1646v2VEthInUcastTable 1}

Pr1646v2VEthInUcastEntry ::=
   SEQUENCE
      {
      pr1646v2VEthInUcastGlobalIx
         GlobalIndex,
      pr1646v2VEthInUcastValue
         Counter64
      }

pr1646v2VEthInUcastGlobalIx OBJECT-TYPE
   SYNTAX      GlobalIndex
   MAX-ACCESS  not-accessible
   STATUS      current
   DESCRIPTION
      "The value of the tlsCntTreeGlobalIndex of the MANAGED OBJECT."
   ::= {pr1646v2VEthInUcastEntry 10}

pr1646v2VEthInUcastValue OBJECT-TYPE
   SYNTAX      Counter64
   MAX-ACCESS  read-only
   STATUS      current
   DESCRIPTION
      "Path: virtualEthernet.performance.ifInUcastPkts

       64 bit unsigned wrappable counter."
   ::= {pr1646v2VEthInUcastEntry 2147483648}


pr1646v2VEthInNUcastPkts OBJECT IDENTIFIER ::= {pr1646v2VEth 111}

pr1646v2VEthInNUcastPktsTable OBJECT-TYPE
   SYNTAX      SEQUENCE OF Pr1646v2VEthInNUcastPktsEntry
   MAX-ACCESS  not-accessible
   STATUS      current
   DESCRIPTION
      "ifInNUcastPkts"
   ::= {pr1646v2VEthInNUcastPkts 1}

pr1646v2VEthInNUcastPktsEntry OBJECT-TYPE
   SYNTAX      Pr1646v2VEthInNUcastPktsEntry
   MAX-ACCESS  not-accessible
   STATUS      current
   DESCRIPTION
      ""
   INDEX      { pr1646v2VEthInNUcastPktsGlobalIx }
   ::= {pr1646v2VEthInNUcastPktsTable 1}

Pr1646v2VEthInNUcastPktsEntry ::=
   SEQUENCE
      {
      pr1646v2VEthInNUcastPktsGlobalIx
         GlobalIndex,
      pr1646v2VEthInNUcastPktsValue
         Counter64
      }

pr1646v2VEthInNUcastPktsGlobalIx OBJECT-TYPE
   SYNTAX      GlobalIndex
   MAX-ACCESS  not-accessible
   STATUS      current
   DESCRIPTION
      "The value of the tlsCntTreeGlobalIndex of the MANAGED OBJECT."
   ::= {pr1646v2VEthInNUcastPktsEntry 10}

pr1646v2VEthInNUcastPktsValue OBJECT-TYPE
   SYNTAX      Counter64
   MAX-ACCESS  read-only
   STATUS      current
   DESCRIPTION
      "Path: virtualEthernet.performance.ifInNUcastPkts

       64 bit unsigned wrappable counter."
   ::= {pr1646v2VEthInNUcastPktsEntry 2147483648}


pr1646v2VEthInBcastPkts OBJECT IDENTIFIER ::= {pr1646v2VEth 211}

pr1646v2VEthInBcastPktsTable OBJECT-TYPE
   SYNTAX      SEQUENCE OF Pr1646v2VEthInBcastPktsEntry
   MAX-ACCESS  not-accessible
   STATUS      current
   DESCRIPTION
      "ifInBcastPkts"
   ::= {pr1646v2VEthInBcastPkts 1}

pr1646v2VEthInBcastPktsEntry OBJECT-TYPE
   SYNTAX      Pr1646v2VEthInBcastPktsEntry
   MAX-ACCESS  not-accessible
   STATUS      current
   DESCRIPTION
      ""
   INDEX      { pr1646v2VEthInBcastPktsGlobalIx }
   ::= {pr1646v2VEthInBcastPktsTable 1}

Pr1646v2VEthInBcastPktsEntry ::=
   SEQUENCE
      {
      pr1646v2VEthInBcastPktsGlobalIx
         GlobalIndex,
      pr1646v2VEthInBcastPktsValue
         Counter64
      }

pr1646v2VEthInBcastPktsGlobalIx OBJECT-TYPE
   SYNTAX      GlobalIndex
   MAX-ACCESS  not-accessible
   STATUS      current
   DESCRIPTION
      "The value of the tlsCntTreeGlobalIndex of the MANAGED OBJECT."
   ::= {pr1646v2VEthInBcastPktsEntry 10}

pr1646v2VEthInBcastPktsValue OBJECT-TYPE
   SYNTAX      Counter64
   MAX-ACCESS  read-only
   STATUS      current
   DESCRIPTION
      "Path: virtualEthernet.performance.ifInBcastPkts

       64 bit unsigned wrappable counter."
   ::= {pr1646v2VEthInBcastPktsEntry 2147483648}


pr1646v2VEthInMcastPkts OBJECT IDENTIFIER ::= {pr1646v2VEth 221}

pr1646v2VEthInMcastPktsTable OBJECT-TYPE
   SYNTAX      SEQUENCE OF Pr1646v2VEthInMcastPktsEntry
   MAX-ACCESS  not-accessible
   STATUS      current
   DESCRIPTION
      "ifInNUcastPkts"
   ::= {pr1646v2VEthInMcastPkts 1}

pr1646v2VEthInMcastPktsEntry OBJECT-TYPE
   SYNTAX      Pr1646v2VEthInMcastPktsEntry
   MAX-ACCESS  not-accessible
   STATUS      current
   DESCRIPTION
      ""
   INDEX      { pr1646v2VEthInMcastPktsGlobalIx }
   ::= {pr1646v2VEthInMcastPktsTable 1}

Pr1646v2VEthInMcastPktsEntry ::=
   SEQUENCE
      {
      pr1646v2VEthInMcastPktsGlobalIx
         GlobalIndex,
      pr1646v2VEthInMcastPktsValue
         Counter64
      }

pr1646v2VEthInMcastPktsGlobalIx OBJECT-TYPE
   SYNTAX      GlobalIndex
   MAX-ACCESS  not-accessible
   STATUS      current
   DESCRIPTION
      "The value of the tlsCntTreeGlobalIndex of the MANAGED OBJECT."
   ::= {pr1646v2VEthInMcastPktsEntry 10}

pr1646v2VEthInMcastPktsValue OBJECT-TYPE
   SYNTAX      Counter64
   MAX-ACCESS  read-only
   STATUS      current
   DESCRIPTION
      "Path: virtualEthernet.performance.ifInMcastPkts

       64 bit unsigned wrappable counter."
   ::= {pr1646v2VEthInMcastPktsEntry 2147483648}


pr1646v2VEthInDiscards OBJECT IDENTIFIER ::= {pr1646v2VEth 112}

pr1646v2VEthInDiscardsTable OBJECT-TYPE
   SYNTAX      SEQUENCE OF Pr1646v2VEthInDiscardsEntry
   MAX-ACCESS  not-accessible
   STATUS      current
   DESCRIPTION
      "ifInDiscards"
   ::= {pr1646v2VEthInDiscards 1}

pr1646v2VEthInDiscardsEntry OBJECT-TYPE
   SYNTAX      Pr1646v2VEthInDiscardsEntry
   MAX-ACCESS  not-accessible
   STATUS      current
   DESCRIPTION
      ""
   INDEX      { pr1646v2VEthInDiscardsGlobalIx }
   ::= {pr1646v2VEthInDiscardsTable 1}

Pr1646v2VEthInDiscardsEntry ::=
   SEQUENCE
      {
      pr1646v2VEthInDiscardsGlobalIx
         GlobalIndex,
      pr1646v2VEthInDiscardsValue
         Counter64
      }

pr1646v2VEthInDiscardsGlobalIx OBJECT-TYPE
   SYNTAX      GlobalIndex
   MAX-ACCESS  not-accessible
   STATUS      current
   DESCRIPTION
      "The value of the tlsCntTreeGlobalIndex of the MANAGED OBJECT."
   ::= {pr1646v2VEthInDiscardsEntry 10}

pr1646v2VEthInDiscardsValue OBJECT-TYPE
   SYNTAX      Counter64
   MAX-ACCESS  read-only
   STATUS      current
   DESCRIPTION
      "Path: virtualEthernet.performance.ifInDiscards

       64 bit unsigned wrappable counter."
   ::= {pr1646v2VEthInDiscardsEntry 2147483648}


pr1646v2VEthInErrors OBJECT IDENTIFIER ::= {pr1646v2VEth 113}

pr1646v2VEthInErrorsTable OBJECT-TYPE
   SYNTAX      SEQUENCE OF Pr1646v2VEthInErrorsEntry
   MAX-ACCESS  not-accessible
   STATUS      current
   DESCRIPTION
      "ifInErrors"
   ::= {pr1646v2VEthInErrors 1}

pr1646v2VEthInErrorsEntry OBJECT-TYPE
   SYNTAX      Pr1646v2VEthInErrorsEntry
   MAX-ACCESS  not-accessible
   STATUS      current
   DESCRIPTION
      ""
   INDEX      { pr1646v2VEthInErrorsGlobalIx }
   ::= {pr1646v2VEthInErrorsTable 1}

Pr1646v2VEthInErrorsEntry ::=
   SEQUENCE
      {
      pr1646v2VEthInErrorsGlobalIx
         GlobalIndex,
      pr1646v2VEthInErrorsValue
         Counter64
      }

pr1646v2VEthInErrorsGlobalIx OBJECT-TYPE
   SYNTAX      GlobalIndex
   MAX-ACCESS  not-accessible
   STATUS      current
   DESCRIPTION
      "The value of the tlsCntTreeGlobalIndex of the MANAGED OBJECT."
   ::= {pr1646v2VEthInErrorsEntry 10}

pr1646v2VEthInErrorsValue OBJECT-TYPE
   SYNTAX      Counter64
   MAX-ACCESS  read-only
   STATUS      current
   DESCRIPTION
      "Path: virtualEthernet.performance.ifInErrors

       64 bit unsigned wrappable counter."
   ::= {pr1646v2VEthInErrorsEntry 2147483648}


pr1646v2VEthInUnknownProtos OBJECT IDENTIFIER ::= {pr1646v2VEth 114}

pr1646v2VEthInUnknownProtosTable OBJECT-TYPE
   SYNTAX      SEQUENCE OF Pr1646v2VEthInUnknownProtosEntry
   MAX-ACCESS  not-accessible
   STATUS      current
   DESCRIPTION
      "ifInUnknownprotos"
   ::= {pr1646v2VEthInUnknownProtos 1}

pr1646v2VEthInUnknownProtosEntry OBJECT-TYPE
   SYNTAX      Pr1646v2VEthInUnknownProtosEntry
   MAX-ACCESS  not-accessible
   STATUS      current
   DESCRIPTION
      ""
   INDEX      { pr1646v2VEthInUnknownProtosGlobalIx }
   ::= {pr1646v2VEthInUnknownProtosTable 1}

Pr1646v2VEthInUnknownProtosEntry ::=
   SEQUENCE
      {
      pr1646v2VEthInUnknownProtosGlobalIx
         GlobalIndex,
      pr1646v2VEthInUnknownProtosValue
         Counter64
      }

pr1646v2VEthInUnknownProtosGlobalIx OBJECT-TYPE
   SYNTAX      GlobalIndex
   MAX-ACCESS  not-accessible
   STATUS      current
   DESCRIPTION
      "The value of the tlsCntTreeGlobalIndex of the MANAGED OBJECT."
   ::= {pr1646v2VEthInUnknownProtosEntry 10}

pr1646v2VEthInUnknownProtosValue OBJECT-TYPE
   SYNTAX      Counter64
   MAX-ACCESS  read-only
   STATUS      current
   DESCRIPTION
      "Path: virtualEthernet.performance.ifInUnknownProtos

       64 bit unsigned wrappable counter."
   ::= {pr1646v2VEthInUnknownProtosEntry 2147483648}


pr1646v2VEthInQLen OBJECT IDENTIFIER ::= {pr1646v2VEth 128}

pr1646v2VEthInQLenTable OBJECT-TYPE
   SYNTAX      SEQUENCE OF Pr1646v2VEthInQLenEntry
   MAX-ACCESS  not-accessible
   STATUS      current
   DESCRIPTION
      "ifInQLen"
   ::= {pr1646v2VEthInQLen 1}

pr1646v2VEthInQLenEntry OBJECT-TYPE
   SYNTAX      Pr1646v2VEthInQLenEntry
   MAX-ACCESS  not-accessible
   STATUS      current
   DESCRIPTION
      ""
   INDEX      { pr1646v2VEthInQLenGlobalIx }
   ::= {pr1646v2VEthInQLenTable 1}

Pr1646v2VEthInQLenEntry ::=
   SEQUENCE
      {
      pr1646v2VEthInQLenGlobalIx
         GlobalIndex,
      pr1646v2VEthInQLenValue
         Gauge32
      }

pr1646v2VEthInQLenGlobalIx OBJECT-TYPE
   SYNTAX      GlobalIndex
   MAX-ACCESS  not-accessible
   STATUS      current
   DESCRIPTION
      "The value of the tlsCntTreeGlobalIndex of the MANAGED OBJECT."
   ::= {pr1646v2VEthInQLenEntry 10}

pr1646v2VEthInQLenValue OBJECT-TYPE
   SYNTAX      Gauge32
   MAX-ACCESS  read-only
   STATUS      current
   DESCRIPTION
      "Path: virtualEthernet.performance.ifInQLen

       32 bit unsigned gauge value."
   ::= {pr1646v2VEthInQLenEntry 2147483648}


pr1646v2VEthInDropEx OBJECT IDENTIFIER ::= {pr1646v2VEth 130}

pr1646v2VEthInDropExTable OBJECT-TYPE
   SYNTAX      SEQUENCE OF Pr1646v2VEthInDropExEntry
   MAX-ACCESS  not-accessible
   STATUS      current
   DESCRIPTION
      "ifInDiscards"
   ::= {pr1646v2VEthInDropEx 1}

pr1646v2VEthInDropExEntry OBJECT-TYPE
   SYNTAX      Pr1646v2VEthInDropExEntry
   MAX-ACCESS  not-accessible
   STATUS      current
   DESCRIPTION
      ""
   INDEX      { pr1646v2VEthInDropExGlobalIx }
   ::= {pr1646v2VEthInDropExTable 1}

Pr1646v2VEthInDropExEntry ::=
   SEQUENCE
      {
      pr1646v2VEthInDropExGlobalIx
         GlobalIndex,
      pr1646v2VEthInDropExValue
         Counter64
      }

pr1646v2VEthInDropExGlobalIx OBJECT-TYPE
   SYNTAX      GlobalIndex
   MAX-ACCESS  not-accessible
   STATUS      current
   DESCRIPTION
      "The value of the tlsCntTreeGlobalIndex of the MANAGED OBJECT."
   ::= {pr1646v2VEthInDropExEntry 10}

pr1646v2VEthInDropExValue OBJECT-TYPE
   SYNTAX      Counter64
   MAX-ACCESS  read-only
   STATUS      current
   DESCRIPTION
      "Path: virtualEthernet.performance.ifInDropLevelExceeded

       64 bit unsigned wrappable counter."
   ::= {pr1646v2VEthInDropExEntry 2147483648}


pr1646v2VEthInDropNoMac OBJECT IDENTIFIER ::= {pr1646v2VEth 133}

pr1646v2VEthInDropNoMacTable OBJECT-TYPE
   SYNTAX      SEQUENCE OF Pr1646v2VEthInDropNoMacEntry
   MAX-ACCESS  not-accessible
   STATUS      current
   DESCRIPTION
      "ifInDiscards"
   ::= {pr1646v2VEthInDropNoMac 1}

pr1646v2VEthInDropNoMacEntry OBJECT-TYPE
   SYNTAX      Pr1646v2VEthInDropNoMacEntry
   MAX-ACCESS  not-accessible
   STATUS      current
   DESCRIPTION
      ""
   INDEX      { pr1646v2VEthInDropNoMacGlobalIx }
   ::= {pr1646v2VEthInDropNoMacTable 1}

Pr1646v2VEthInDropNoMacEntry ::=
   SEQUENCE
      {
      pr1646v2VEthInDropNoMacGlobalIx
         GlobalIndex,
      pr1646v2VEthInDropNoMacValue
         Counter64
      }

pr1646v2VEthInDropNoMacGlobalIx OBJECT-TYPE
   SYNTAX      GlobalIndex
   MAX-ACCESS  not-accessible
   STATUS      current
   DESCRIPTION
      "The value of the tlsCntTreeGlobalIndex of the MANAGED OBJECT."
   ::= {pr1646v2VEthInDropNoMacEntry 10}

pr1646v2VEthInDropNoMacValue OBJECT-TYPE
   SYNTAX      Counter64
   MAX-ACCESS  read-only
   STATUS      current
   DESCRIPTION
      "Path: virtualEthernet.performance.ifInDiscardsNoMacFit

       64 bit unsigned wrappable counter."
   ::= {pr1646v2VEthInDropNoMacEntry 2147483648}


pr1646v2VEthInDropNUCast OBJECT IDENTIFIER ::= {pr1646v2VEth 136}

pr1646v2VEthInDropNUCastTable OBJECT-TYPE
   SYNTAX      SEQUENCE OF Pr1646v2VEthInDropNUCastEntry
   MAX-ACCESS  not-accessible
   STATUS      current
   DESCRIPTION
      "ifInDiscards"
   ::= {pr1646v2VEthInDropNUCast 1}

pr1646v2VEthInDropNUCastEntry OBJECT-TYPE
   SYNTAX      Pr1646v2VEthInDropNUCastEntry
   MAX-ACCESS  not-accessible
   STATUS      current
   DESCRIPTION
      ""
   INDEX      { pr1646v2VEthInDropNUCastGlobalIx }
   ::= {pr1646v2VEthInDropNUCastTable 1}

Pr1646v2VEthInDropNUCastEntry ::=
   SEQUENCE
      {
      pr1646v2VEthInDropNUCastGlobalIx
         GlobalIndex,
      pr1646v2VEthInDropNUCastValue
         Counter64
      }

pr1646v2VEthInDropNUCastGlobalIx OBJECT-TYPE
   SYNTAX      GlobalIndex
   MAX-ACCESS  not-accessible
   STATUS      current
   DESCRIPTION
      "The value of the tlsCntTreeGlobalIndex of the MANAGED OBJECT."
   ::= {pr1646v2VEthInDropNUCastEntry 10}

pr1646v2VEthInDropNUCastValue OBJECT-TYPE
   SYNTAX      Counter64
   MAX-ACCESS  read-only
   STATUS      current
   DESCRIPTION
      "Path: virtualEthernet.performance.ifInDiscardsNUCast

       64 bit unsigned wrappable counter."
   ::= {pr1646v2VEthInDropNUCastEntry 2147483648}


pr1646v2VEthInDropFilter OBJECT IDENTIFIER ::= {pr1646v2VEth 137}

pr1646v2VEthInDropFilterTable OBJECT-TYPE
   SYNTAX      SEQUENCE OF Pr1646v2VEthInDropFilterEntry
   MAX-ACCESS  not-accessible
   STATUS      current
   DESCRIPTION
      "ifInDiscards"
   ::= {pr1646v2VEthInDropFilter 1}

pr1646v2VEthInDropFilterEntry OBJECT-TYPE
   SYNTAX      Pr1646v2VEthInDropFilterEntry
   MAX-ACCESS  not-accessible
   STATUS      current
   DESCRIPTION
      ""
   INDEX      { pr1646v2VEthInDropFilterGlobalIx }
   ::= {pr1646v2VEthInDropFilterTable 1}

Pr1646v2VEthInDropFilterEntry ::=
   SEQUENCE
      {
      pr1646v2VEthInDropFilterGlobalIx
         GlobalIndex,
      pr1646v2VEthInDropFilterValue
         Counter64
      }

pr1646v2VEthInDropFilterGlobalIx OBJECT-TYPE
   SYNTAX      GlobalIndex
   MAX-ACCESS  not-accessible
   STATUS      current
   DESCRIPTION
      "The value of the tlsCntTreeGlobalIndex of the MANAGED OBJECT."
   ::= {pr1646v2VEthInDropFilterEntry 10}

pr1646v2VEthInDropFilterValue OBJECT-TYPE
   SYNTAX      Counter64
   MAX-ACCESS  read-only
   STATUS      current
   DESCRIPTION
      "Path: virtualEthernet.performance.ifInDiscardsFilter

       64 bit unsigned wrappable counter."
   ::= {pr1646v2VEthInDropFilterEntry 2147483648}


pr1646v2VEthInQueues OBJECT IDENTIFIER ::= {pr1646v2VEth 131}

pr1646v2VEthInQueuesSSCTable OBJECT-TYPE
   SYNTAX      SEQUENCE OF Pr1646v2VEthInQueuesEntry
   MAX-ACCESS  not-accessible
   STATUS      current
   DESCRIPTION
      "Queue Lengths"
   ::= {pr1646v2VEthInQueues 1}

pr1646v2VEthInQueuesEntry OBJECT-TYPE
   SYNTAX      Pr1646v2VEthInQueuesEntry
   MAX-ACCESS  not-accessible
   STATUS      current
   DESCRIPTION
      ""
   INDEX      { pr1646v2VEthInQueuesGlobalIx,
                pr1646v2VEthInQueuesTableIx }
   ::= {pr1646v2VEthInQueuesSSCTable 1}

Pr1646v2VEthInQueuesEntry ::=
   SEQUENCE
      {
      pr1646v2VEthInQueuesGlobalIx
         GlobalIndex,
      pr1646v2VEthInQueuesTableIx
         TableIndex,
      pr1646v2VEthInQueuesName
         INTEGER,
      pr1646v2VEthInQueuesLength
         Integer32,
      pr1646v2VEthInQueuesOctetLength
         Integer32,
      pr1646v2VEthInQueuesRedLength
         Integer32,
      pr1646v2VEthInQueuesPacketsTotal
         Counter64,
      pr1646v2VEthInQueuesPacketsDirectTx
         Counter64,
      pr1646v2VEthInQueuesPacketsQueued
         Counter64,
      pr1646v2VEthInQueuesPacketsDropped
         Counter64,
      pr1646v2VEthInQueuesPacketsRedDropped
         Counter64,
      pr1646v2VEthInQueuesPacketsCirTx
         Counter64,
      pr1646v2VEthInQueuesPacketsEirTx
         Counter64,
      pr1646v2VEthInQueuesPacketsViolateTx
         Counter64,
      pr1646v2VEthInQueuesOctetsTotal
         Counter64,
      pr1646v2VEthInQueuesOctetsDirectTx
         Counter64,
      pr1646v2VEthInQueuesOctetsQueued
         Counter64,
      pr1646v2VEthInQueuesOctetsDropped
         Counter64,
      pr1646v2VEthInQueuesOctetsRedDropped
         Counter64,
      pr1646v2VEthInQueuesOctetsCirTx
         Counter64,
      pr1646v2VEthInQueuesOctetsEirTx
         Counter64,
      pr1646v2VEthInQueuesOctetsViolateTx
         Counter64,
      pr1646v2VEthInQueuesOctetsBandwidth15sec
         Integer32,
      pr1646v2VEthInQueuesOctetsBandwidth30sec
         Integer32,
      pr1646v2VEthInQueuesOctetsBandwidth1min
         Integer32,
      pr1646v2VEthInQueuesOctetsBandwidth2min
         Integer32,
      pr1646v2VEthInQueuesOctetsBandwidth5min
         Integer32
      }

pr1646v2VEthInQueuesGlobalIx OBJECT-TYPE
   SYNTAX      GlobalIndex
   MAX-ACCESS  not-accessible
   STATUS      current
   DESCRIPTION
      "The value of the tlsCntTreeGlobalIndex of the MANAGED OBJECT."
   ::= {pr1646v2VEthInQueuesEntry 10}

pr1646v2VEthInQueuesTableIx OBJECT-TYPE
   SYNTAX      TableIndex
   MAX-ACCESS  not-accessible
   STATUS      current
   DESCRIPTION
      ""
   ::= {pr1646v2VEthInQueuesEntry 11}

pr1646v2VEthInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2VEthInQueuesEntry 16777216}

pr1646v2VEthInQueuesLength OBJECT-TYPE
   SYNTAX      Integer32
   MAX-ACCESS  read-only
   STATUS      current
   DESCRIPTION
      "Path: virtualEthernet.performance.ifInPriorityQueues.length"
   ::= {pr1646v2VEthInQueuesEntry 33554432}

pr1646v2VEthInQueuesOctetLength OBJECT-TYPE
   SYNTAX      Integer32
   MAX-ACCESS  read-only
   STATUS      current
   DESCRIPTION
      "Path: virtualEthernet.performance.ifInPriorityQueues.octetLength"
   ::= {pr1646v2VEthInQueuesEntry 150994944}

pr1646v2VEthInQueuesRedLength OBJECT-TYPE
   SYNTAX      Integer32
   MAX-ACCESS  read-only
   STATUS      current
   DESCRIPTION
      "Path: virtualEthernet.performance.ifInPriorityQueues.redLength"
   ::= {pr1646v2VEthInQueuesEntry 134217728}

pr1646v2VEthInQueuesPacketsTotal OBJECT-TYPE
   SYNTAX      Counter64
   MAX-ACCESS  read-only
   STATUS      current
   DESCRIPTION
      "Path: virtualEthernet.performance.ifInPriorityQueues.packets.total

       64 bit unsigned wrappable counter."
   ::= {pr1646v2VEthInQueuesEntry 50790400}

pr1646v2VEthInQueuesPacketsDirectTx OBJECT-TYPE
   SYNTAX      Counter64
   MAX-ACCESS  read-only
   STATUS      current
   DESCRIPTION
      "Path: virtualEthernet.performance.ifInPriorityQueues.packets.directTx

       64 bit unsigned wrappable counter."
   ::= {pr1646v2VEthInQueuesEntry 50397184}

pr1646v2VEthInQueuesPacketsQueued OBJECT-TYPE
   SYNTAX      Counter64
   MAX-ACCESS  read-only
   STATUS      current
   DESCRIPTION
      "Path: virtualEthernet.performance.ifInPriorityQueues.packets.queued

       64 bit unsigned wrappable counter."
   ::= {pr1646v2VEthInQueuesEntry 50462720}

pr1646v2VEthInQueuesPacketsDropped OBJECT-TYPE
   SYNTAX      Counter64
   MAX-ACCESS  read-only
   STATUS      current
   DESCRIPTION
      "Path: virtualEthernet.performance.ifInPriorityQueues.packets.dropped

       64 bit unsigned wrappable counter."
   ::= {pr1646v2VEthInQueuesEntry 50528256}

pr1646v2VEthInQueuesPacketsRedDropped OBJECT-TYPE
   SYNTAX      Counter64
   MAX-ACCESS  read-only
   STATUS      current
   DESCRIPTION
      "Path: virtualEthernet.performance.ifInPriorityQueues.packets.redDropped

       64 bit unsigned wrappable counter."
   ::= {pr1646v2VEthInQueuesEntry 50724864}

pr1646v2VEthInQueuesPacketsCirTx OBJECT-TYPE
   SYNTAX      Counter64
   MAX-ACCESS  read-only
   STATUS      current
   DESCRIPTION
      "Path: virtualEthernet.performance.ifInPriorityQueues.packets.cirTx

       64 bit unsigned wrappable counter."
   ::= {pr1646v2VEthInQueuesEntry 50593792}

pr1646v2VEthInQueuesPacketsEirTx OBJECT-TYPE
   SYNTAX      Counter64
   MAX-ACCESS  read-only
   STATUS      current
   DESCRIPTION
      "Path: virtualEthernet.performance.ifInPriorityQueues.packets.eirTx

       64 bit unsigned wrappable counter."
   ::= {pr1646v2VEthInQueuesEntry 50659328}

pr1646v2VEthInQueuesPacketsViolateTx OBJECT-TYPE
   SYNTAX      Counter64
   MAX-ACCESS  read-only
   STATUS      current
   DESCRIPTION
      "Path: virtualEthernet.performance.ifInPriorityQueues.packets.violateTx

       64 bit unsigned wrappable counter."
   ::= {pr1646v2VEthInQueuesEntry 50855936}

pr1646v2VEthInQueuesOctetsTotal OBJECT-TYPE
   SYNTAX      Counter64
   MAX-ACCESS  read-only
   STATUS      current
   DESCRIPTION
      "Path: virtualEthernet.performance.ifInPriorityQueues.octets.total

       64 bit unsigned wrappable counter."
   ::= {pr1646v2VEthInQueuesEntry 67567616}

pr1646v2VEthInQueuesOctetsDirectTx OBJECT-TYPE
   SYNTAX      Counter64
   MAX-ACCESS  read-only
   STATUS      current
   DESCRIPTION
      "Path: virtualEthernet.performance.ifInPriorityQueues.octets.directTx

       64 bit unsigned wrappable counter."
   ::= {pr1646v2VEthInQueuesEntry 67174400}

pr1646v2VEthInQueuesOctetsQueued OBJECT-TYPE
   SYNTAX      Counter64
   MAX-ACCESS  read-only
   STATUS      current
   DESCRIPTION
      "Path: virtualEthernet.performance.ifInPriorityQueues.octets.queued

       64 bit unsigned wrappable counter."
   ::= {pr1646v2VEthInQueuesEntry 67239936}

pr1646v2VEthInQueuesOctetsDropped OBJECT-TYPE
   SYNTAX      Counter64
   MAX-ACCESS  read-only
   STATUS      current
   DESCRIPTION
      "Path: virtualEthernet.performance.ifInPriorityQueues.octets.dropped

       64 bit unsigned wrappable counter."
   ::= {pr1646v2VEthInQueuesEntry 67305472}

pr1646v2VEthInQueuesOctetsRedDropped OBJECT-TYPE
   SYNTAX      Counter64
   MAX-ACCESS  read-only
   STATUS      current
   DESCRIPTION
      "Path: virtualEthernet.performance.ifInPriorityQueues.octets.redDropped

       64 bit unsigned wrappable counter."
   ::= {pr1646v2VEthInQueuesEntry 67502080}

pr1646v2VEthInQueuesOctetsCirTx OBJECT-TYPE
   SYNTAX      Counter64
   MAX-ACCESS  read-only
   STATUS      current
   DESCRIPTION
      "Path: virtualEthernet.performance.ifInPriorityQueues.octets.cirTx

       64 bit unsigned wrappable counter."
   ::= {pr1646v2VEthInQueuesEntry 67371008}

pr1646v2VEthInQueuesOctetsEirTx OBJECT-TYPE
   SYNTAX      Counter64
   MAX-ACCESS  read-only
   STATUS      current
   DESCRIPTION
      "Path: virtualEthernet.performance.ifInPriorityQueues.octets.eirTx

       64 bit unsigned wrappable counter."
   ::= {pr1646v2VEthInQueuesEntry 67436544}

pr1646v2VEthInQueuesOctetsViolateTx OBJECT-TYPE
   SYNTAX      Counter64
   MAX-ACCESS  read-only
   STATUS      current
   DESCRIPTION
      "Path: virtualEthernet.performance.ifInPriorityQueues.octets.violateTx

       64 bit unsigned wrappable counter."
   ::= {pr1646v2VEthInQueuesEntry 67633152}

pr1646v2VEthInQueuesOctetsBandwidth15sec OBJECT-TYPE
   SYNTAX      Integer32
   MAX-ACCESS  read-only
   STATUS      current
   DESCRIPTION
      "Path: virtualEthernet.performance.ifInPriorityQueues.octets.bandwidth.15sec

       unit name = bps
       formula = 8 * ; 8 /"
   ::= {pr1646v2VEthInQueuesEntry 70386944}

pr1646v2VEthInQueuesOctetsBandwidth30sec OBJECT-TYPE
   SYNTAX      Integer32
   MAX-ACCESS  read-only
   STATUS      current
   DESCRIPTION
      "Path: virtualEthernet.performance.ifInPriorityQueues.octets.bandwidth.30sec

       unit name = bps
       formula = 8 * ; 8 /"
   ::= {pr1646v2VEthInQueuesEntry 70388224}

pr1646v2VEthInQueuesOctetsBandwidth1min OBJECT-TYPE
   SYNTAX      Integer32
   MAX-ACCESS  read-only
   STATUS      current
   DESCRIPTION
      "Path: virtualEthernet.performance.ifInPriorityQueues.octets.bandwidth.1min

       unit name = bps
       formula = 8 * ; 8 /"
   ::= {pr1646v2VEthInQueuesEntry 70390784}

pr1646v2VEthInQueuesOctetsBandwidth2min OBJECT-TYPE
   SYNTAX      Integer32
   MAX-ACCESS  read-only
   STATUS      current
   DESCRIPTION
      "Path: virtualEthernet.performance.ifInPriorityQueues.octets.bandwidth.2min

       unit name = bps
       formula = 8 * ; 8 /"
   ::= {pr1646v2VEthInQueuesEntry 70395904}

pr1646v2VEthInQueuesOctetsBandwidth5min OBJECT-TYPE
   SYNTAX      Integer32
   MAX-ACCESS  read-only
   STATUS      current
   DESCRIPTION
      "Path: virtualEthernet.performance.ifInPriorityQueues.octets.bandwidth.5min

       unit name = bps
       formula = 8 * ; 8 /"
   ::= {pr1646v2VEthInQueuesEntry 70411264}

pr1646v2VEthInQueuesH2Performance OBJECT-TYPE
   SYNTAX      SEQUENCE OF Pr1646v2VEthInQueuesH2PerformanceEntry
   MAX-ACCESS  not-accessible
   STATUS      current
   DESCRIPTION
      ""
   ::= {pr1646v2VEthInQueues 83886080}

pr1646v2VEthInQueuesH2PerformanceEntry OBJECT-TYPE
   SYNTAX      Pr1646v2VEthInQueuesH2PerformanceEntry
   MAX-ACCESS  not-accessible
   STATUS      current
   DESCRIPTION
      ""
   INDEX      { pr1646v2VEthInQueuesH2PerformanceGlobalIx,
                pr1646v2VEthInQueuesTableIx,
                pr1646v2VEthInQueuesH2PerformanceTableIx }
   ::= {pr1646v2VEthInQueuesH2Performance 1}

Pr1646v2VEthInQueuesH2PerformanceEntry ::=
   SEQUENCE
      {
      pr1646v2VEthInQueuesH2PerformanceGlobalIx
         GlobalIndex,
      pr1646v2VEthInQueuesH2PerformanceTableIx
         TableIndex,
      pr1646v2VEthInQueuesH2PerformanceSysUpTime
         TimeTicks,
      pr1646v2VEthInQueuesH2PerformanceTotPkts
         Counter64,
      pr1646v2VEthInQueuesH2PerformanceDirTxPkts
         Counter64,
      pr1646v2VEthInQueuesH2PerformanceQdPkts
         Counter64,
      pr1646v2VEthInQueuesH2PerformanceDropPkts
         Counter64,
      pr1646v2VEthInQueuesH2PerformanceRDropPkts
         Counter64,
      pr1646v2VEthInQueuesH2PerformanceCirTxPkts
         Counter64,
      pr1646v2VEthInQueuesH2PerformanceEirTxPkts
         Counter64,
      pr1646v2VEthInQueuesH2PerformanceViolTxPkts
         Counter64,
      pr1646v2VEthInQueuesH2PerformanceTotOcts
         Counter64,
      pr1646v2VEthInQueuesH2PerformanceDirTxOcts
         Counter64,
      pr1646v2VEthInQueuesH2PerformanceQdOcts
         Counter64,
      pr1646v2VEthInQueuesH2PerformanceDropOcts
         Counter64,
      pr1646v2VEthInQueuesH2PerformanceRDropOcts
         Counter64,
      pr1646v2VEthInQueuesH2PerformanceCirTxOcts
         Counter64,
      pr1646v2VEthInQueuesH2PerformanceEirTxOcts
         Counter64,
      pr1646v2VEthInQueuesH2PerformanceViolTxOcts
         Counter64,
      pr1646v2VEthInQueuesH2PerformanceBandwidth
         Integer32
      }

pr1646v2VEthInQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2VEthInQueuesH2PerformanceEntry 10}

pr1646v2VEthInQueuesH2PerformanceTableIx OBJECT-TYPE
   SYNTAX      TableIndex
   MAX-ACCESS  not-accessible
   STATUS      current
   DESCRIPTION
      ""
   ::= {pr1646v2VEthInQueuesH2PerformanceEntry 11}

pr1646v2VEthInQueuesH2PerformanceSysUpTime OBJECT-TYPE
   SYNTAX      TimeTicks
   MAX-ACCESS  read-only
   STATUS      current
   DESCRIPTION
      "Path: virtualEthernet.performance.ifInPriorityQueues.h2Performance.sysUpTime

       Time in centi-second."
   ::= {pr1646v2VEthInQueuesH2PerformanceEntry 16777216}

pr1646v2VEthInQueuesH2PerformanceTotPkts OBJECT-TYPE
   SYNTAX      Counter64
   MAX-ACCESS  read-only
   STATUS      current
   DESCRIPTION
      "Path: virtualEthernet.performance.ifInPriorityQueues.h2Performance.totalPkts

       64 bit unsigned wrappable counter."
   ::= {pr1646v2VEthInQueuesH2PerformanceEntry 234881024}

pr1646v2VEthInQueuesH2PerformanceDirTxPkts OBJECT-TYPE
   SYNTAX      Counter64
   MAX-ACCESS  read-only
   STATUS      current
   DESCRIPTION
      "Path: virtualEthernet.performance.ifInPriorityQueues.h2Performance.directTxPkts

       64 bit unsigned wrappable counter."
   ::= {pr1646v2VEthInQueuesH2PerformanceEntry 33554432}

pr1646v2VEthInQueuesH2PerformanceQdPkts OBJECT-TYPE
   SYNTAX      Counter64
   MAX-ACCESS  read-only
   STATUS      current
   DESCRIPTION
      "Path: virtualEthernet.performance.ifInPriorityQueues.h2Performance.queuedPkts

       64 bit unsigned wrappable counter."
   ::= {pr1646v2VEthInQueuesH2PerformanceEntry 50331648}

pr1646v2VEthInQueuesH2PerformanceDropPkts OBJECT-TYPE
   SYNTAX      Counter64
   MAX-ACCESS  read-only
   STATUS      current
   DESCRIPTION
      "Path: virtualEthernet.performance.ifInPriorityQueues.h2Performance.droppedPkts

       64 bit unsigned wrappable counter."
   ::= {pr1646v2VEthInQueuesH2PerformanceEntry 67108864}

pr1646v2VEthInQueuesH2PerformanceRDropPkts OBJECT-TYPE
   SYNTAX      Counter64
   MAX-ACCESS  read-only
   STATUS      current
   DESCRIPTION
      "Path: virtualEthernet.performance.ifInPriorityQueues.h2Performance.redDroppedPkts

       64 bit unsigned wrappable counter."
   ::= {pr1646v2VEthInQueuesH2PerformanceEntry 201326592}

pr1646v2VEthInQueuesH2PerformanceCirTxPkts OBJECT-TYPE
   SYNTAX      Counter64
   MAX-ACCESS  read-only
   STATUS      current
   DESCRIPTION
      "Path: virtualEthernet.performance.ifInPriorityQueues.h2Performance.cirTxPkts

       64 bit unsigned wrappable counter."
   ::= {pr1646v2VEthInQueuesH2PerformanceEntry 83886080}

pr1646v2VEthInQueuesH2PerformanceEirTxPkts OBJECT-TYPE
   SYNTAX      Counter64
   MAX-ACCESS  read-only
   STATUS      current
   DESCRIPTION
      "Path: virtualEthernet.performance.ifInPriorityQueues.h2Performance.eirTxPkts

       64 bit unsigned wrappable counter."
   ::= {pr1646v2VEthInQueuesH2PerformanceEntry 100663296}

pr1646v2VEthInQueuesH2PerformanceViolTxPkts OBJECT-TYPE
   SYNTAX      Counter64
   MAX-ACCESS  read-only
   STATUS      current
   DESCRIPTION
      "Path: virtualEthernet.performance.ifInPriorityQueues.h2Performance.violateTxPkts

       64 bit unsigned wrappable counter."
   ::= {pr1646v2VEthInQueuesH2PerformanceEntry 301989888}

pr1646v2VEthInQueuesH2PerformanceTotOcts OBJECT-TYPE
   SYNTAX      Counter64
   MAX-ACCESS  read-only
   STATUS      current
   DESCRIPTION
      "Path: virtualEthernet.performance.ifInPriorityQueues.h2Performance.totalOctets

       64 bit unsigned wrappable counter."
   ::= {pr1646v2VEthInQueuesH2PerformanceEntry 251658240}

pr1646v2VEthInQueuesH2PerformanceDirTxOcts OBJECT-TYPE
   SYNTAX      Counter64
   MAX-ACCESS  read-only
   STATUS      current
   DESCRIPTION
      "Path: virtualEthernet.performance.ifInPriorityQueues.h2Performance.directTxOctets

       64 bit unsigned wrappable counter."
   ::= {pr1646v2VEthInQueuesH2PerformanceEntry 117440512}

pr1646v2VEthInQueuesH2PerformanceQdOcts OBJECT-TYPE
   SYNTAX      Counter64
   MAX-ACCESS  read-only
   STATUS      current
   DESCRIPTION
      "Path: virtualEthernet.performance.ifInPriorityQueues.h2Performance.queuedOctets

       64 bit unsigned wrappable counter."
   ::= {pr1646v2VEthInQueuesH2PerformanceEntry 134217728}

pr1646v2VEthInQueuesH2PerformanceDropOcts OBJECT-TYPE
   SYNTAX      Counter64
   MAX-ACCESS  read-only
   STATUS      current
   DESCRIPTION
      "Path: virtualEthernet.performance.ifInPriorityQueues.h2Performance.droppedOctets

       64 bit unsigned wrappable counter."
   ::= {pr1646v2VEthInQueuesH2PerformanceEntry 150994944}

pr1646v2VEthInQueuesH2PerformanceRDropOcts OBJECT-TYPE
   SYNTAX      Counter64
   MAX-ACCESS  read-only
   STATUS      current
   DESCRIPTION
      "Path: virtualEthernet.performance.ifInPriorityQueues.h2Performance.redDroppedOctets

       64 bit unsigned wrappable counter."
   ::= {pr1646v2VEthInQueuesH2PerformanceEntry 218103808}

pr1646v2VEthInQueuesH2PerformanceCirTxOcts OBJECT-TYPE
   SYNTAX      Counter64
   MAX-ACCESS  read-only
   STATUS      current
   DESCRIPTION
      "Path: virtualEthernet.performance.ifInPriorityQueues.h2Performance.cirTxOctets

       64 bit unsigned wrappable counter."
   ::= {pr1646v2VEthInQueuesH2PerformanceEntry 167772160}

pr1646v2VEthInQueuesH2PerformanceEirTxOcts OBJECT-TYPE
   SYNTAX      Counter64
   MAX-ACCESS  read-only
   STATUS      current
   DESCRIPTION
      "Path: virtualEthernet.performance.ifInPriorityQueues.h2Performance.eirTxOctets

       64 bit unsigned wrappable counter."
   ::= {pr1646v2VEthInQueuesH2PerformanceEntry 184549376}

pr1646v2VEthInQueuesH2PerformanceViolTxOcts OBJECT-TYPE
   SYNTAX      Counter64
   MAX-ACCESS  read-only
   STATUS      current
   DESCRIPTION
      "Path: virtualEthernet.performance.ifInPriorityQueues.h2Performance.violateTxOctets

       64 bit unsigned wrappable counter."
   ::= {pr1646v2VEthInQueuesH2PerformanceEntry 318767104}

pr1646v2VEthInQueuesH2PerformanceBandwidth OBJECT-TYPE
   SYNTAX      Integer32
   MAX-ACCESS  read-only
   STATUS      current
   DESCRIPTION
      "Path: virtualEthernet.performance.ifInPriorityQueues.h2Performance.bandwidth

       unit name = bps
       formula = 8 * ; 8 /"
   ::= {pr1646v2VEthInQueuesH2PerformanceEntry 268435456}

pr1646v2VEthInQueuesH24Performance OBJECT-TYPE
   SYNTAX      SEQUENCE OF Pr1646v2VEthInQueuesH24PerformanceEntry
   MAX-ACCESS  not-accessible
   STATUS      current
   DESCRIPTION
      ""
   ::= {pr1646v2VEthInQueues 100663296}

pr1646v2VEthInQueuesH24PerformanceEntry OBJECT-TYPE
   SYNTAX      Pr1646v2VEthInQueuesH24PerformanceEntry
   MAX-ACCESS  not-accessible
   STATUS      current
   DESCRIPTION
      ""
   INDEX      { pr1646v2VEthInQueuesH24PerformanceGlobalIx,
                pr1646v2VEthInQueuesTableIx,
                pr1646v2VEthInQueuesH24PerformanceTableIx }
   ::= {pr1646v2VEthInQueuesH24Performance 1}

Pr1646v2VEthInQueuesH24PerformanceEntry ::=
   SEQUENCE
      {
      pr1646v2VEthInQueuesH24PerformanceGlobalIx
         GlobalIndex,
      pr1646v2VEthInQueuesH24PerformanceTableIx
         TableIndex,
      pr1646v2VEthInQueuesH24PerformanceSysUpTime
         TimeTicks,
      pr1646v2VEthInQueuesH24PerformanceTotPkts
         Counter64,
      pr1646v2VEthInQueuesH24PerformanceDirTxPkts
         Counter64,
      pr1646v2VEthInQueuesH24PerformanceQdPkts
         Counter64,
      pr1646v2VEthInQueuesH24PerformanceDropPkts
         Counter64,
      pr1646v2VEthInQueuesH24PerformanceRDropPkts
         Counter64,
      pr1646v2VEthInQueuesH24PerformanceCirTxPkts
         Counter64,
      pr1646v2VEthInQueuesH24PerformanceEirTxPkts
         Counter64,
      pr1646v2VEthInQueuesH24PerformanceViolTxPkts
         Counter64,
      pr1646v2VEthInQueuesH24PerformanceTotOcts
         Counter64,
      pr1646v2VEthInQueuesH24PerformanceDirTxOcts
         Counter64,
      pr1646v2VEthInQueuesH24PerformanceQdOcts
         Counter64,
      pr1646v2VEthInQueuesH24PerformanceDropOcts
         Counter64,
      pr1646v2VEthInQueuesH24PerformanceRDropOcts
         Counter64,
      pr1646v2VEthInQueuesH24PerformanceCirTxOcts
         Counter64,
      pr1646v2VEthInQueuesH24PerformanceEirTxOcts
         Counter64,
      pr1646v2VEthInQueuesH24PerformanceViolTxOcts
         Counter64,
      pr1646v2VEthInQueuesH24PerformanceBandwidth
         Integer32
      }

pr1646v2VEthInQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2VEthInQueuesH24PerformanceEntry 10}

pr1646v2VEthInQueuesH24PerformanceTableIx OBJECT-TYPE
   SYNTAX      TableIndex
   MAX-ACCESS  not-accessible
   STATUS      current
   DESCRIPTION
      ""
   ::= {pr1646v2VEthInQueuesH24PerformanceEntry 11}

pr1646v2VEthInQueuesH24PerformanceSysUpTime OBJECT-TYPE
   SYNTAX      TimeTicks
   MAX-ACCESS  read-only
   STATUS      current
   DESCRIPTION
      "Path: virtualEthernet.performance.ifInPriorityQueues.h24Performance.sysUpTime

       Time in centi-second."
   ::= {pr1646v2VEthInQueuesH24PerformanceEntry 16777216}

pr1646v2VEthInQueuesH24PerformanceTotPkts OBJECT-TYPE
   SYNTAX      Counter64
   MAX-ACCESS  read-only
   STATUS      current
   DESCRIPTION
      "Path: virtualEthernet.performance.ifInPriorityQueues.h24Performance.totalPkts

       64 bit unsigned wrappable counter."
   ::= {pr1646v2VEthInQueuesH24PerformanceEntry 234881024}

pr1646v2VEthInQueuesH24PerformanceDirTxPkts OBJECT-TYPE
   SYNTAX      Counter64
   MAX-ACCESS  read-only
   STATUS      current
   DESCRIPTION
      "Path: virtualEthernet.performance.ifInPriorityQueues.h24Performance.directTxPkts

       64 bit unsigned wrappable counter."
   ::= {pr1646v2VEthInQueuesH24PerformanceEntry 33554432}

pr1646v2VEthInQueuesH24PerformanceQdPkts OBJECT-TYPE
   SYNTAX      Counter64
   MAX-ACCESS  read-only
   STATUS      current
   DESCRIPTION
      "Path: virtualEthernet.performance.ifInPriorityQueues.h24Performance.queuedPkts

       64 bit unsigned wrappable counter."
   ::= {pr1646v2VEthInQueuesH24PerformanceEntry 50331648}

pr1646v2VEthInQueuesH24PerformanceDropPkts OBJECT-TYPE
   SYNTAX      Counter64
   MAX-ACCESS  read-only
   STATUS      current
   DESCRIPTION
      "Path: virtualEthernet.performance.ifInPriorityQueues.h24Performance.droppedPkts

       64 bit unsigned wrappable counter."
   ::= {pr1646v2VEthInQueuesH24PerformanceEntry 67108864}

pr1646v2VEthInQueuesH24PerformanceRDropPkts OBJECT-TYPE
   SYNTAX      Counter64
   MAX-ACCESS  read-only
   STATUS      current
   DESCRIPTION
      "Path: virtualEthernet.performance.ifInPriorityQueues.h24Performance.redDroppedPkts

       64 bit unsigned wrappable counter."
   ::= {pr1646v2VEthInQueuesH24PerformanceEntry 201326592}

pr1646v2VEthInQueuesH24PerformanceCirTxPkts OBJECT-TYPE
   SYNTAX      Counter64
   MAX-ACCESS  read-only
   STATUS      current
   DESCRIPTION
      "Path: virtualEthernet.performance.ifInPriorityQueues.h24Performance.cirTxPkts

       64 bit unsigned wrappable counter."
   ::= {pr1646v2VEthInQueuesH24PerformanceEntry 83886080}

pr1646v2VEthInQueuesH24PerformanceEirTxPkts OBJECT-TYPE
   SYNTAX      Counter64
   MAX-ACCESS  read-only
   STATUS      current
   DESCRIPTION
      "Path: virtualEthernet.performance.ifInPriorityQueues.h24Performance.eirTxPkts

       64 bit unsigned wrappable counter."
   ::= {pr1646v2VEthInQueuesH24PerformanceEntry 100663296}

pr1646v2VEthInQueuesH24PerformanceViolTxPkts OBJECT-TYPE
   SYNTAX      Counter64
   MAX-ACCESS  read-only
   STATUS      current
   DESCRIPTION
      "Path: virtualEthernet.performance.ifInPriorityQueues.h24Performance.violateTxPkts

       64 bit unsigned wrappable counter."
   ::= {pr1646v2VEthInQueuesH24PerformanceEntry 301989888}

pr1646v2VEthInQueuesH24PerformanceTotOcts OBJECT-TYPE
   SYNTAX      Counter64
   MAX-ACCESS  read-only
   STATUS      current
   DESCRIPTION
      "Path: virtualEthernet.performance.ifInPriorityQueues.h24Performance.totalOctets

       64 bit unsigned wrappable counter."
   ::= {pr1646v2VEthInQueuesH24PerformanceEntry 251658240}

pr1646v2VEthInQueuesH24PerformanceDirTxOcts OBJECT-TYPE
   SYNTAX      Counter64
   MAX-ACCESS  read-only
   STATUS      current
   DESCRIPTION
      "Path: virtualEthernet.performance.ifInPriorityQueues.h24Performance.directTxOctets

       64 bit unsigned wrappable counter."
   ::= {pr1646v2VEthInQueuesH24PerformanceEntry 117440512}

pr1646v2VEthInQueuesH24PerformanceQdOcts OBJECT-TYPE
   SYNTAX      Counter64
   MAX-ACCESS  read-only
   STATUS      current
   DESCRIPTION
      "Path: virtualEthernet.performance.ifInPriorityQueues.h24Performance.queuedOctets

       64 bit unsigned wrappable counter."
   ::= {pr1646v2VEthInQueuesH24PerformanceEntry 134217728}

pr1646v2VEthInQueuesH24PerformanceDropOcts OBJECT-TYPE
   SYNTAX      Counter64
   MAX-ACCESS  read-only
   STATUS      current
   DESCRIPTION
      "Path: virtualEthernet.performance.ifInPriorityQueues.h24Performance.droppedOctets

       64 bit unsigned wrappable counter."
   ::= {pr1646v2VEthInQueuesH24PerformanceEntry 150994944}

pr1646v2VEthInQueuesH24PerformanceRDropOcts OBJECT-TYPE
   SYNTAX      Counter64
   MAX-ACCESS  read-only
   STATUS      current
   DESCRIPTION
      "Path: virtualEthernet.performance.ifInPriorityQueues.h24Performance.redDroppedOctets

       64 bit unsigned wrappable counter."
   ::= {pr1646v2VEthInQueuesH24PerformanceEntry 218103808}

pr1646v2VEthInQueuesH24PerformanceCirTxOcts OBJECT-TYPE
   SYNTAX      Counter64
   MAX-ACCESS  read-only
   STATUS      current
   DESCRIPTION
      "Path: virtualEthernet.performance.ifInPriorityQueues.h24Performance.cirTxOctets

       64 bit unsigned wrappable counter."
   ::= {pr1646v2VEthInQueuesH24PerformanceEntry 167772160}

pr1646v2VEthInQueuesH24PerformanceEirTxOcts OBJECT-TYPE
   SYNTAX      Counter64
   MAX-ACCESS  read-only
   STATUS      current
   DESCRIPTION
      "Path: virtualEthernet.performance.ifInPriorityQueues.h24Performance.eirTxOctets

       64 bit unsigned wrappable counter."
   ::= {pr1646v2VEthInQueuesH24PerformanceEntry 184549376}

pr1646v2VEthInQueuesH24PerformanceViolTxOcts OBJECT-TYPE
   SYNTAX      Counter64
   MAX-ACCESS  read-only
   STATUS      current
   DESCRIPTION
      "Path: virtualEthernet.performance.ifInPriorityQueues.h24Performance.violateTxOctets

       64 bit unsigned wrappable counter."
   ::= {pr1646v2VEthInQueuesH24PerformanceEntry 318767104}

pr1646v2VEthInQueuesH24PerformanceBandwidth OBJECT-TYPE
   SYNTAX      Integer32
   MAX-ACCESS  read-only
   STATUS      current
   DESCRIPTION
      "Path: virtualEthernet.performance.ifInPriorityQueues.h24Performance.bandwidth

       unit name = bps
       formula = 8 * ; 8 /"
   ::= {pr1646v2VEthInQueuesH24PerformanceEntry 268435456}

pr1646v2VEthInQueuesD7Performance OBJECT-TYPE
   SYNTAX      SEQUENCE OF Pr1646v2VEthInQueuesD7PerformanceEntry
   MAX-ACCESS  not-accessible
   STATUS      current
   DESCRIPTION
      ""
   ::= {pr1646v2VEthInQueues 117440512}

pr1646v2VEthInQueuesD7PerformanceEntry OBJECT-TYPE
   SYNTAX      Pr1646v2VEthInQueuesD7PerformanceEntry
   MAX-ACCESS  not-accessible
   STATUS      current
   DESCRIPTION
      ""
   INDEX      { pr1646v2VEthInQueuesD7PerformanceGlobalIx,
                pr1646v2VEthInQueuesTableIx,
                pr1646v2VEthInQueuesD7PerformanceTableIx }
   ::= {pr1646v2VEthInQueuesD7Performance 1}

Pr1646v2VEthInQueuesD7PerformanceEntry ::=
   SEQUENCE
      {
      pr1646v2VEthInQueuesD7PerformanceGlobalIx
         GlobalIndex,
      pr1646v2VEthInQueuesD7PerformanceTableIx
         TableIndex,
      pr1646v2VEthInQueuesD7PerformanceSysUpTime
         TimeTicks,
      pr1646v2VEthInQueuesD7PerformanceTotPkts
         Counter64,
      pr1646v2VEthInQueuesD7PerformanceDirTxPkts
         Counter64,
      pr1646v2VEthInQueuesD7PerformanceQdPkts
         Counter64,
      pr1646v2VEthInQueuesD7PerformanceDropPkts
         Counter64,
      pr1646v2VEthInQueuesD7PerformanceRDropPkts
         Counter64,
      pr1646v2VEthInQueuesD7PerformanceCirTxPkts
         Counter64,
      pr1646v2VEthInQueuesD7PerformanceEirTxPkts
         Counter64,
      pr1646v2VEthInQueuesD7PerformanceViolTxPkts
         Counter64,
      pr1646v2VEthInQueuesD7PerformanceTotOcts
         Counter64,
      pr1646v2VEthInQueuesD7PerformanceDirTxOcts
         Counter64,
      pr1646v2VEthInQueuesD7PerformanceQdOcts
         Counter64,
      pr1646v2VEthInQueuesD7PerformanceDropOcts
         Counter64,
      pr1646v2VEthInQueuesD7PerformanceRDropOcts
         Counter64,
      pr1646v2VEthInQueuesD7PerformanceCirTxOcts
         Counter64,
      pr1646v2VEthInQueuesD7PerformanceEirTxOcts
         Counter64,
      pr1646v2VEthInQueuesD7PerformanceViolTxOcts
         Counter64,
      pr1646v2VEthInQueuesD7PerformanceBandwidth
         Integer32
      }

pr1646v2VEthInQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2VEthInQueuesD7PerformanceEntry 10}

pr1646v2VEthInQueuesD7PerformanceTableIx OBJECT-TYPE
   SYNTAX      TableIndex
   MAX-ACCESS  not-accessible
   STATUS      current
   DESCRIPTION
      ""
   ::= {pr1646v2VEthInQueuesD7PerformanceEntry 11}

pr1646v2VEthInQueuesD7PerformanceSysUpTime OBJECT-TYPE
   SYNTAX      TimeTicks
   MAX-ACCESS  read-only
   STATUS      current
   DESCRIPTION
      "Path: virtualEthernet.performance.ifInPriorityQueues.d7Performance.sysUpTime

       Time in centi-second."
   ::= {pr1646v2VEthInQueuesD7PerformanceEntry 16777216}

pr1646v2VEthInQueuesD7PerformanceTotPkts OBJECT-TYPE
   SYNTAX      Counter64
   MAX-ACCESS  read-only
   STATUS      current
   DESCRIPTION
      "Path: virtualEthernet.performance.ifInPriorityQueues.d7Performance.totalPkts

       64 bit unsigned wrappable counter."
   ::= {pr1646v2VEthInQueuesD7PerformanceEntry 234881024}

pr1646v2VEthInQueuesD7PerformanceDirTxPkts OBJECT-TYPE
   SYNTAX      Counter64
   MAX-ACCESS  read-only
   STATUS      current
   DESCRIPTION
      "Path: virtualEthernet.performance.ifInPriorityQueues.d7Performance.directTxPkts

       64 bit unsigned wrappable counter."
   ::= {pr1646v2VEthInQueuesD7PerformanceEntry 33554432}

pr1646v2VEthInQueuesD7PerformanceQdPkts OBJECT-TYPE
   SYNTAX      Counter64
   MAX-ACCESS  read-only
   STATUS      current
   DESCRIPTION
      "Path: virtualEthernet.performance.ifInPriorityQueues.d7Performance.queuedPkts

       64 bit unsigned wrappable counter."
   ::= {pr1646v2VEthInQueuesD7PerformanceEntry 50331648}

pr1646v2VEthInQueuesD7PerformanceDropPkts OBJECT-TYPE
   SYNTAX      Counter64
   MAX-ACCESS  read-only
   STATUS      current
   DESCRIPTION
      "Path: virtualEthernet.performance.ifInPriorityQueues.d7Performance.droppedPkts

       64 bit unsigned wrappable counter."
   ::= {pr1646v2VEthInQueuesD7PerformanceEntry 67108864}

pr1646v2VEthInQueuesD7PerformanceRDropPkts OBJECT-TYPE
   SYNTAX      Counter64
   MAX-ACCESS  read-only
   STATUS      current
   DESCRIPTION
      "Path: virtualEthernet.performance.ifInPriorityQueues.d7Performance.redDroppedPkts

       64 bit unsigned wrappable counter."
   ::= {pr1646v2VEthInQueuesD7PerformanceEntry 201326592}

pr1646v2VEthInQueuesD7PerformanceCirTxPkts OBJECT-TYPE
   SYNTAX      Counter64
   MAX-ACCESS  read-only
   STATUS      current
   DESCRIPTION
      "Path: virtualEthernet.performance.ifInPriorityQueues.d7Performance.cirTxPkts

       64 bit unsigned wrappable counter."
   ::= {pr1646v2VEthInQueuesD7PerformanceEntry 83886080}

pr1646v2VEthInQueuesD7PerformanceEirTxPkts OBJECT-TYPE
   SYNTAX      Counter64
   MAX-ACCESS  read-only
   STATUS      current
   DESCRIPTION
      "Path: virtualEthernet.performance.ifInPriorityQueues.d7Performance.eirTxPkts

       64 bit unsigned wrappable counter."
   ::= {pr1646v2VEthInQueuesD7PerformanceEntry 100663296}

pr1646v2VEthInQueuesD7PerformanceViolTxPkts OBJECT-TYPE
   SYNTAX      Counter64
   MAX-ACCESS  read-only
   STATUS      current
   DESCRIPTION
      "Path: virtualEthernet.performance.ifInPriorityQueues.d7Performance.violateTxPkts

       64 bit unsigned wrappable counter."
   ::= {pr1646v2VEthInQueuesD7PerformanceEntry 301989888}

pr1646v2VEthInQueuesD7PerformanceTotOcts OBJECT-TYPE
   SYNTAX      Counter64
   MAX-ACCESS  read-only
   STATUS      current
   DESCRIPTION
      "Path: virtualEthernet.performance.ifInPriorityQueues.d7Performance.totalOctets

       64 bit unsigned wrappable counter."
   ::= {pr1646v2VEthInQueuesD7PerformanceEntry 251658240}

pr1646v2VEthInQueuesD7PerformanceDirTxOcts OBJECT-TYPE
   SYNTAX      Counter64
   MAX-ACCESS  read-only
   STATUS      current
   DESCRIPTION
      "Path: virtualEthernet.performance.ifInPriorityQueues.d7Performance.directTxOctets

       64 bit unsigned wrappable counter."
   ::= {pr1646v2VEthInQueuesD7PerformanceEntry 117440512}

pr1646v2VEthInQueuesD7PerformanceQdOcts OBJECT-TYPE
   SYNTAX      Counter64
   MAX-ACCESS  read-only
   STATUS      current
   DESCRIPTION
      "Path: virtualEthernet.performance.ifInPriorityQueues.d7Performance.queuedOctets

       64 bit unsigned wrappable counter."
   ::= {pr1646v2VEthInQueuesD7PerformanceEntry 134217728}

pr1646v2VEthInQueuesD7PerformanceDropOcts OBJECT-TYPE
   SYNTAX      Counter64
   MAX-ACCESS  read-only
   STATUS      current
   DESCRIPTION
      "Path: virtualEthernet.performance.ifInPriorityQueues.d7Performance.droppedOctets

       64 bit unsigned wrappable counter."
   ::= {pr1646v2VEthInQueuesD7PerformanceEntry 150994944}

pr1646v2VEthInQueuesD7PerformanceRDropOcts OBJECT-TYPE
   SYNTAX      Counter64
   MAX-ACCESS  read-only
   STATUS      current
   DESCRIPTION
      "Path: virtualEthernet.performance.ifInPriorityQueues.d7Performance.redDroppedOctets

       64 bit unsigned wrappable counter."
   ::= {pr1646v2VEthInQueuesD7PerformanceEntry 218103808}

pr1646v2VEthInQueuesD7PerformanceCirTxOcts OBJECT-TYPE
   SYNTAX      Counter64
   MAX-ACCESS  read-only
   STATUS      current
   DESCRIPTION
      "Path: virtualEthernet.performance.ifInPriorityQueues.d7Performance.cirTxOctets

       64 bit unsigned wrappable counter."
   ::= {pr1646v2VEthInQueuesD7PerformanceEntry 167772160}

pr1646v2VEthInQueuesD7PerformanceEirTxOcts OBJECT-TYPE
   SYNTAX      Counter64
   MAX-ACCESS  read-only
   STATUS      current
   DESCRIPTION
      "Path: virtualEthernet.performance.ifInPriorityQueues.d7Performance.eirTxOctets

       64 bit unsigned wrappable counter."
   ::= {pr1646v2VEthInQueuesD7PerformanceEntry 184549376}

pr1646v2VEthInQueuesD7PerformanceViolTxOcts OBJECT-TYPE
   SYNTAX      Counter64
   MAX-ACCESS  read-only
   STATUS      current
   DESCRIPTION
      "Path: virtualEthernet.performance.ifInPriorityQueues.d7Performance.violateTxOctets

       64 bit unsigned wrappable counter."
   ::= {pr1646v2VEthInQueuesD7PerformanceEntry 318767104}

pr1646v2VEthInQueuesD7PerformanceBandwidth OBJECT-TYPE
   SYNTAX      Integer32
   MAX-ACCESS  read-only
   STATUS      current
   DESCRIPTION
      "Path: virtualEthernet.performance.ifInPriorityQueues.d7Performance.bandwidth

       unit name = bps
       formula = 8 * ; 8 /"
   ::= {pr1646v2VEthInQueuesD7PerformanceEntry 268435456}


pr1646v2VEthInBandwidth OBJECT IDENTIFIER ::= {pr1646v2VEth 181}

pr1646v2VEthInBandwidthSSCTable OBJECT-TYPE
   SYNTAX      SEQUENCE OF Pr1646v2VEthInBandwidthEntry
   MAX-ACCESS  not-accessible
   STATUS      current
   DESCRIPTION
      "bandwidth"
   ::= {pr1646v2VEthInBandwidth 1}

pr1646v2VEthInBandwidthEntry OBJECT-TYPE
   SYNTAX      Pr1646v2VEthInBandwidthEntry
   MAX-ACCESS  not-accessible
   STATUS      current
   DESCRIPTION
      ""
   INDEX      { pr1646v2VEthInBandwidthGlobalIx }
   ::= {pr1646v2VEthInBandwidthSSCTable 1}

Pr1646v2VEthInBandwidthEntry ::=
   SEQUENCE
      {
      pr1646v2VEthInBandwidthGlobalIx
         GlobalIndex,
      pr1646v2VEthInBandwidth15sec
         Integer32,
      pr1646v2VEthInBandwidth30sec
         Integer32,
      pr1646v2VEthInBandwidth1min
         Integer32,
      pr1646v2VEthInBandwidth2min
         Integer32,
      pr1646v2VEthInBandwidth5min
         Integer32
      }

pr1646v2VEthInBandwidthGlobalIx OBJECT-TYPE
   SYNTAX      GlobalIndex
   MAX-ACCESS  not-accessible
   STATUS      current
   DESCRIPTION
      "The value of the tlsCntTreeGlobalIndex of the MANAGED OBJECT."
   ::= {pr1646v2VEthInBandwidthEntry 10}

pr1646v2VEthInBandwidth15sec OBJECT-TYPE
   SYNTAX      Integer32
   MAX-ACCESS  read-only
   STATUS      current
   DESCRIPTION
      "Path: virtualEthernet.performance.ifInBandwidth.15sec

       unit name = bps
       formula = 8 * ; 8 /"
   ::= {pr1646v2VEthInBandwidthEntry 83886080}

pr1646v2VEthInBandwidth30sec OBJECT-TYPE
   SYNTAX      Integer32
   MAX-ACCESS  read-only
   STATUS      current
   DESCRIPTION
      "Path: virtualEthernet.performance.ifInBandwidth.30sec

       unit name = bps
       formula = 8 * ; 8 /"
   ::= {pr1646v2VEthInBandwidthEntry 167772160}

pr1646v2VEthInBandwidth1min OBJECT-TYPE
   SYNTAX      Integer32
   MAX-ACCESS  read-only
   STATUS      current
   DESCRIPTION
      "Path: virtualEthernet.performance.ifInBandwidth.1min

       unit name = bps
       formula = 8 * ; 8 /"
   ::= {pr1646v2VEthInBandwidthEntry 335544320}

pr1646v2VEthInBandwidth2min OBJECT-TYPE
   SYNTAX      Integer32
   MAX-ACCESS  read-only
   STATUS      current
   DESCRIPTION
      "Path: virtualEthernet.performance.ifInBandwidth.2min

       unit name = bps
       formula = 8 * ; 8 /"
   ::= {pr1646v2VEthInBandwidthEntry 671088640}

pr1646v2VEthInBandwidth5min OBJECT-TYPE
   SYNTAX      Integer32
   MAX-ACCESS  read-only
   STATUS      current
   DESCRIPTION
      "Path: virtualEthernet.performance.ifInBandwidth.5min

       unit name = bps
       formula = 8 * ; 8 /"
   ::= {pr1646v2VEthInBandwidthEntry 1677721600}


pr1646v2VEthOutOctets OBJECT IDENTIFIER ::= {pr1646v2VEth 115}

pr1646v2VEthOutOctetsTable OBJECT-TYPE
   SYNTAX      SEQUENCE OF Pr1646v2VEthOutOctetsEntry
   MAX-ACCESS  not-accessible
   STATUS      current
   DESCRIPTION
      "ifOutOctets"
   ::= {pr1646v2VEthOutOctets 1}

pr1646v2VEthOutOctetsEntry OBJECT-TYPE
   SYNTAX      Pr1646v2VEthOutOctetsEntry
   MAX-ACCESS  not-accessible
   STATUS      current
   DESCRIPTION
      ""
   INDEX      { pr1646v2VEthOutOctetsGlobalIx }
   ::= {pr1646v2VEthOutOctetsTable 1}

Pr1646v2VEthOutOctetsEntry ::=
   SEQUENCE
      {
      pr1646v2VEthOutOctetsGlobalIx
         GlobalIndex,
      pr1646v2VEthOutOctetsValue
         Counter64
      }

pr1646v2VEthOutOctetsGlobalIx OBJECT-TYPE
   SYNTAX      GlobalIndex
   MAX-ACCESS  not-accessible
   STATUS      current
   DESCRIPTION
      "The value of the tlsCntTreeGlobalIndex of the MANAGED OBJECT."
   ::= {pr1646v2VEthOutOctetsEntry 10}

pr1646v2VEthOutOctetsValue OBJECT-TYPE
   SYNTAX      Counter64
   MAX-ACCESS  read-only
   STATUS      current
   DESCRIPTION
      "Path: virtualEthernet.performance.ifOutOctets

       64 bit unsigned wrappable counter."
   ::= {pr1646v2VEthOutOctetsEntry 2147483648}


pr1646v2VEthOutUcastPkts OBJECT IDENTIFIER ::= {pr1646v2VEth 116}

pr1646v2VEthOutUcastPktsTable OBJECT-TYPE
   SYNTAX      SEQUENCE OF Pr1646v2VEthOutUcastPktsEntry
   MAX-ACCESS  not-accessible
   STATUS      current
   DESCRIPTION
      "ifOutUcastPkts"
   ::= {pr1646v2VEthOutUcastPkts 1}

pr1646v2VEthOutUcastPktsEntry OBJECT-TYPE
   SYNTAX      Pr1646v2VEthOutUcastPktsEntry
   MAX-ACCESS  not-accessible
   STATUS      current
   DESCRIPTION
      ""
   INDEX      { pr1646v2VEthOutUcastPktsGlobalIx }
   ::= {pr1646v2VEthOutUcastPktsTable 1}

Pr1646v2VEthOutUcastPktsEntry ::=
   SEQUENCE
      {
      pr1646v2VEthOutUcastPktsGlobalIx
         GlobalIndex,
      pr1646v2VEthOutUcastPktsValue
         Counter64
      }

pr1646v2VEthOutUcastPktsGlobalIx OBJECT-TYPE
   SYNTAX      GlobalIndex
   MAX-ACCESS  not-accessible
   STATUS      current
   DESCRIPTION
      "The value of the tlsCntTreeGlobalIndex of the MANAGED OBJECT."
   ::= {pr1646v2VEthOutUcastPktsEntry 10}

pr1646v2VEthOutUcastPktsValue OBJECT-TYPE
   SYNTAX      Counter64
   MAX-ACCESS  read-only
   STATUS      current
   DESCRIPTION
      "Path: virtualEthernet.performance.ifOutUcastPkts

       64 bit unsigned wrappable counter."
   ::= {pr1646v2VEthOutUcastPktsEntry 2147483648}


pr1646v2VEthOutNUcastPkts OBJECT IDENTIFIER ::= {pr1646v2VEth 117}

pr1646v2VEthOutNUcastPktsTable OBJECT-TYPE
   SYNTAX      SEQUENCE OF Pr1646v2VEthOutNUcastPktsEntry
   MAX-ACCESS  not-accessible
   STATUS      current
   DESCRIPTION
      "ifOutNUcastPkts"
   ::= {pr1646v2VEthOutNUcastPkts 1}

pr1646v2VEthOutNUcastPktsEntry OBJECT-TYPE
   SYNTAX      Pr1646v2VEthOutNUcastPktsEntry
   MAX-ACCESS  not-accessible
   STATUS      current
   DESCRIPTION
      ""
   INDEX      { pr1646v2VEthOutNUcastPktsGlobalIx }
   ::= {pr1646v2VEthOutNUcastPktsTable 1}

Pr1646v2VEthOutNUcastPktsEntry ::=
   SEQUENCE
      {
      pr1646v2VEthOutNUcastPktsGlobalIx
         GlobalIndex,
      pr1646v2VEthOutNUcastPktsValue
         Counter64
      }

pr1646v2VEthOutNUcastPktsGlobalIx OBJECT-TYPE
   SYNTAX      GlobalIndex
   MAX-ACCESS  not-accessible
   STATUS      current
   DESCRIPTION
      "The value of the tlsCntTreeGlobalIndex of the MANAGED OBJECT."
   ::= {pr1646v2VEthOutNUcastPktsEntry 10}

pr1646v2VEthOutNUcastPktsValue OBJECT-TYPE
   SYNTAX      Counter64
   MAX-ACCESS  read-only
   STATUS      current
   DESCRIPTION
      "Path: virtualEthernet.performance.ifOutNUcastPkts

       64 bit unsigned wrappable counter."
   ::= {pr1646v2VEthOutNUcastPktsEntry 2147483648}


pr1646v2VEthOutBcastPkts OBJECT IDENTIFIER ::= {pr1646v2VEth 217}

pr1646v2VEthOutBcastPktsTable OBJECT-TYPE
   SYNTAX      SEQUENCE OF Pr1646v2VEthOutBcastPktsEntry
   MAX-ACCESS  not-accessible
   STATUS      current
   DESCRIPTION
      "ifOutBcastPkts"
   ::= {pr1646v2VEthOutBcastPkts 1}

pr1646v2VEthOutBcastPktsEntry OBJECT-TYPE
   SYNTAX      Pr1646v2VEthOutBcastPktsEntry
   MAX-ACCESS  not-accessible
   STATUS      current
   DESCRIPTION
      ""
   INDEX      { pr1646v2VEthOutBcastPktsGlobalIx }
   ::= {pr1646v2VEthOutBcastPktsTable 1}

Pr1646v2VEthOutBcastPktsEntry ::=
   SEQUENCE
      {
      pr1646v2VEthOutBcastPktsGlobalIx
         GlobalIndex,
      pr1646v2VEthOutBcastPktsValue
         Counter64
      }

pr1646v2VEthOutBcastPktsGlobalIx OBJECT-TYPE
   SYNTAX      GlobalIndex
   MAX-ACCESS  not-accessible
   STATUS      current
   DESCRIPTION
      "The value of the tlsCntTreeGlobalIndex of the MANAGED OBJECT."
   ::= {pr1646v2VEthOutBcastPktsEntry 10}

pr1646v2VEthOutBcastPktsValue OBJECT-TYPE
   SYNTAX      Counter64
   MAX-ACCESS  read-only
   STATUS      current
   DESCRIPTION
      "Path: virtualEthernet.performance.ifOutBcastPkts

       64 bit unsigned wrappable counter."
   ::= {pr1646v2VEthOutBcastPktsEntry 2147483648}


pr1646v2VEthOutMcastPkts OBJECT IDENTIFIER ::= {pr1646v2VEth 227}

pr1646v2VEthOutMcastPktsTable OBJECT-TYPE
   SYNTAX      SEQUENCE OF Pr1646v2VEthOutMcastPktsEntry
   MAX-ACCESS  not-accessible
   STATUS      current
   DESCRIPTION
      "ifOutMcastPkts"
   ::= {pr1646v2VEthOutMcastPkts 1}

pr1646v2VEthOutMcastPktsEntry OBJECT-TYPE
   SYNTAX      Pr1646v2VEthOutMcastPktsEntry
   MAX-ACCESS  not-accessible
   STATUS      current
   DESCRIPTION
      ""
   INDEX      { pr1646v2VEthOutMcastPktsGlobalIx }
   ::= {pr1646v2VEthOutMcastPktsTable 1}

Pr1646v2VEthOutMcastPktsEntry ::=
   SEQUENCE
      {
      pr1646v2VEthOutMcastPktsGlobalIx
         GlobalIndex,
      pr1646v2VEthOutMcastPktsValue
         Counter64
      }

pr1646v2VEthOutMcastPktsGlobalIx OBJECT-TYPE
   SYNTAX      GlobalIndex
   MAX-ACCESS  not-accessible
   STATUS      current
   DESCRIPTION
      "The value of the tlsCntTreeGlobalIndex of the MANAGED OBJECT."
   ::= {pr1646v2VEthOutMcastPktsEntry 10}

pr1646v2VEthOutMcastPktsValue OBJECT-TYPE
   SYNTAX      Counter64
   MAX-ACCESS  read-only
   STATUS      current
   DESCRIPTION
      "Path: virtualEthernet.performance.ifOutMcastPkts

       64 bit unsigned wrappable counter."
   ::= {pr1646v2VEthOutMcastPktsEntry 2147483648}


pr1646v2VEthOutDiscards OBJECT IDENTIFIER ::= {pr1646v2VEth 118}

pr1646v2VEthOutDiscardsTable OBJECT-TYPE
   SYNTAX      SEQUENCE OF Pr1646v2VEthOutDiscardsEntry
   MAX-ACCESS  not-accessible
   STATUS      current
   DESCRIPTION
      "ifOutDiscards"
   ::= {pr1646v2VEthOutDiscards 1}

pr1646v2VEthOutDiscardsEntry OBJECT-TYPE
   SYNTAX      Pr1646v2VEthOutDiscardsEntry
   MAX-ACCESS  not-accessible
   STATUS      current
   DESCRIPTION
      ""
   INDEX      { pr1646v2VEthOutDiscardsGlobalIx }
   ::= {pr1646v2VEthOutDiscardsTable 1}

Pr1646v2VEthOutDiscardsEntry ::=
   SEQUENCE
      {
      pr1646v2VEthOutDiscardsGlobalIx
         GlobalIndex,
      pr1646v2VEthOutDiscardsValue
         Counter64
      }

pr1646v2VEthOutDiscardsGlobalIx OBJECT-TYPE
   SYNTAX      GlobalIndex
   MAX-ACCESS  not-accessible
   STATUS      current
   DESCRIPTION
      "The value of the tlsCntTreeGlobalIndex of the MANAGED OBJECT."
   ::= {pr1646v2VEthOutDiscardsEntry 10}

pr1646v2VEthOutDiscardsValue OBJECT-TYPE
   SYNTAX      Counter64
   MAX-ACCESS  read-only
   STATUS      current
   DESCRIPTION
      "Path: virtualEthernet.performance.ifOutDiscards

       64 bit unsigned wrappable counter."
   ::= {pr1646v2VEthOutDiscardsEntry 2147483648}


pr1646v2VEthOutErrors OBJECT IDENTIFIER ::= {pr1646v2VEth 119}

pr1646v2VEthOutErrorsTable OBJECT-TYPE
   SYNTAX      SEQUENCE OF Pr1646v2VEthOutErrorsEntry
   MAX-ACCESS  not-accessible
   STATUS      current
   DESCRIPTION
      "ifOutErrors"
   ::= {pr1646v2VEthOutErrors 1}

pr1646v2VEthOutErrorsEntry OBJECT-TYPE
   SYNTAX      Pr1646v2VEthOutErrorsEntry
   MAX-ACCESS  not-accessible
   STATUS      current
   DESCRIPTION
      ""
   INDEX      { pr1646v2VEthOutErrorsGlobalIx }
   ::= {pr1646v2VEthOutErrorsTable 1}

Pr1646v2VEthOutErrorsEntry ::=
   SEQUENCE
      {
      pr1646v2VEthOutErrorsGlobalIx
         GlobalIndex,
      pr1646v2VEthOutErrorsValue
         Counter64
      }

pr1646v2VEthOutErrorsGlobalIx OBJECT-TYPE
   SYNTAX      GlobalIndex
   MAX-ACCESS  not-accessible
   STATUS      current
   DESCRIPTION
      "The value of the tlsCntTreeGlobalIndex of the MANAGED OBJECT."
   ::= {pr1646v2VEthOutErrorsEntry 10}

pr1646v2VEthOutErrorsValue OBJECT-TYPE
   SYNTAX      Counter64
   MAX-ACCESS  read-only
   STATUS      current
   DESCRIPTION
      "Path: virtualEthernet.performance.ifOutErrors

       64 bit unsigned wrappable counter."
   ::= {pr1646v2VEthOutErrorsEntry 2147483648}


pr1646v2VEthOutQLen OBJECT IDENTIFIER ::= {pr1646v2VEth 120}

pr1646v2VEthOutQLenTable OBJECT-TYPE
   SYNTAX      SEQUENCE OF Pr1646v2VEthOutQLenEntry
   MAX-ACCESS  not-accessible
   STATUS      current
   DESCRIPTION
      "ifOutQLen"
   ::= {pr1646v2VEthOutQLen 1}

pr1646v2VEthOutQLenEntry OBJECT-TYPE
   SYNTAX      Pr1646v2VEthOutQLenEntry
   MAX-ACCESS  not-accessible
   STATUS      current
   DESCRIPTION
      ""
   INDEX      { pr1646v2VEthOutQLenGlobalIx }
   ::= {pr1646v2VEthOutQLenTable 1}

Pr1646v2VEthOutQLenEntry ::=
   SEQUENCE
      {
      pr1646v2VEthOutQLenGlobalIx
         GlobalIndex,
      pr1646v2VEthOutQLenValue
         Gauge32
      }

pr1646v2VEthOutQLenGlobalIx OBJECT-TYPE
   SYNTAX      GlobalIndex
   MAX-ACCESS  not-accessible
   STATUS      current
   DESCRIPTION
      "The value of the tlsCntTreeGlobalIndex of the MANAGED OBJECT."
   ::= {pr1646v2VEthOutQLenEntry 10}

pr1646v2VEthOutQLenValue OBJECT-TYPE
   SYNTAX      Gauge32
   MAX-ACCESS  read-only
   STATUS      current
   DESCRIPTION
      "Path: virtualEthernet.performance.ifOutQLen

       32 bit unsigned gauge value."
   ::= {pr1646v2VEthOutQLenEntry 2147483648}


pr1646v2VEthOutDropEx OBJECT IDENTIFIER ::= {pr1646v2VEth 127}

pr1646v2VEthOutDropExTable OBJECT-TYPE
   SYNTAX      SEQUENCE OF Pr1646v2VEthOutDropExEntry
   MAX-ACCESS  not-accessible
   STATUS      current
   DESCRIPTION
      "ifOutDiscards"
   ::= {pr1646v2VEthOutDropEx 1}

pr1646v2VEthOutDropExEntry OBJECT-TYPE
   SYNTAX      Pr1646v2VEthOutDropExEntry
   MAX-ACCESS  not-accessible
   STATUS      current
   DESCRIPTION
      ""
   INDEX      { pr1646v2VEthOutDropExGlobalIx }
   ::= {pr1646v2VEthOutDropExTable 1}

Pr1646v2VEthOutDropExEntry ::=
   SEQUENCE
      {
      pr1646v2VEthOutDropExGlobalIx
         GlobalIndex,
      pr1646v2VEthOutDropExValue
         Counter64
      }

pr1646v2VEthOutDropExGlobalIx OBJECT-TYPE
   SYNTAX      GlobalIndex
   MAX-ACCESS  not-accessible
   STATUS      current
   DESCRIPTION
      "The value of the tlsCntTreeGlobalIndex of the MANAGED OBJECT."
   ::= {pr1646v2VEthOutDropExEntry 10}

pr1646v2VEthOutDropExValue OBJECT-TYPE
   SYNTAX      Counter64
   MAX-ACCESS  read-only
   STATUS      current
   DESCRIPTION
      "Path: virtualEthernet.performance.ifOutDropLevelExceeded

       64 bit unsigned wrappable counter."
   ::= {pr1646v2VEthOutDropExEntry 2147483648}


pr1646v2VEthOutDropNoArp OBJECT IDENTIFIER ::= {pr1646v2VEth 134}

pr1646v2VEthOutDropNoArpTable OBJECT-TYPE
   SYNTAX      SEQUENCE OF Pr1646v2VEthOutDropNoArpEntry
   MAX-ACCESS  not-accessible
   STATUS      current
   DESCRIPTION
      "ifOutDiscards"
   ::= {pr1646v2VEthOutDropNoArp 1}

pr1646v2VEthOutDropNoArpEntry OBJECT-TYPE
   SYNTAX      Pr1646v2VEthOutDropNoArpEntry
   MAX-ACCESS  not-accessible
   STATUS      current
   DESCRIPTION
      ""
   INDEX      { pr1646v2VEthOutDropNoArpGlobalIx }
   ::= {pr1646v2VEthOutDropNoArpTable 1}

Pr1646v2VEthOutDropNoArpEntry ::=
   SEQUENCE
      {
      pr1646v2VEthOutDropNoArpGlobalIx
         GlobalIndex,
      pr1646v2VEthOutDropNoArpValue
         Counter64
      }

pr1646v2VEthOutDropNoArpGlobalIx OBJECT-TYPE
   SYNTAX      GlobalIndex
   MAX-ACCESS  not-accessible
   STATUS      current
   DESCRIPTION
      "The value of the tlsCntTreeGlobalIndex of the MANAGED OBJECT."
   ::= {pr1646v2VEthOutDropNoArpEntry 10}

pr1646v2VEthOutDropNoArpValue OBJECT-TYPE
   SYNTAX      Counter64
   MAX-ACCESS  read-only
   STATUS      current
   DESCRIPTION
      "Path: virtualEthernet.performance.ifOutDiscardsNoArp

       64 bit unsigned wrappable counter."
   ::= {pr1646v2VEthOutDropNoArpEntry 2147483648}


pr1646v2VEthOutDropFilter OBJECT IDENTIFIER ::= {pr1646v2VEth 138}

pr1646v2VEthOutDropFilterTable OBJECT-TYPE
   SYNTAX      SEQUENCE OF Pr1646v2VEthOutDropFilterEntry
   MAX-ACCESS  not-accessible
   STATUS      current
   DESCRIPTION
      "ifOutDiscards"
   ::= {pr1646v2VEthOutDropFilter 1}

pr1646v2VEthOutDropFilterEntry OBJECT-TYPE
   SYNTAX      Pr1646v2VEthOutDropFilterEntry
   MAX-ACCESS  not-accessible
   STATUS      current
   DESCRIPTION
      ""
   INDEX      { pr1646v2VEthOutDropFilterGlobalIx }
   ::= {pr1646v2VEthOutDropFilterTable 1}

Pr1646v2VEthOutDropFilterEntry ::=
   SEQUENCE
      {
      pr1646v2VEthOutDropFilterGlobalIx
         GlobalIndex,
      pr1646v2VEthOutDropFilterValue
         Counter64
      }

pr1646v2VEthOutDropFilterGlobalIx OBJECT-TYPE
   SYNTAX      GlobalIndex
   MAX-ACCESS  not-accessible
   STATUS      current
   DESCRIPTION
      "The value of the tlsCntTreeGlobalIndex of the MANAGED OBJECT."
   ::= {pr1646v2VEthOutDropFilterEntry 10}

pr1646v2VEthOutDropFilterValue OBJECT-TYPE
   SYNTAX      Counter64
   MAX-ACCESS  read-only
   STATUS      current
   DESCRIPTION
      "Path: virtualEthernet.performance.ifOutDiscardsFilter

       64 bit unsigned wrappable counter."
   ::= {pr1646v2VEthOutDropFilterEntry 2147483648}


pr1646v2VEthOutQueues OBJECT IDENTIFIER ::= {pr1646v2VEth 129}

pr1646v2VEthOutQueuesSSCTable OBJECT-TYPE
   SYNTAX      SEQUENCE OF Pr1646v2VEthOutQueuesEntry
   MAX-ACCESS  not-accessible
   STATUS      current
   DESCRIPTION
      "Queue Lengths"
   ::= {pr1646v2VEthOutQueues 1}

pr1646v2VEthOutQueuesEntry OBJECT-TYPE
   SYNTAX      Pr1646v2VEthOutQueuesEntry
   MAX-ACCESS  not-accessible
   STATUS      current
   DESCRIPTION
      ""
   INDEX      { pr1646v2VEthOutQueuesGlobalIx,
                pr1646v2VEthOutQueuesTableIx }
   ::= {pr1646v2VEthOutQueuesSSCTable 1}

Pr1646v2VEthOutQueuesEntry ::=
   SEQUENCE
      {
      pr1646v2VEthOutQueuesGlobalIx
         GlobalIndex,
      pr1646v2VEthOutQueuesTableIx
         TableIndex,
      pr1646v2VEthOutQueuesName
         INTEGER,
      pr1646v2VEthOutQueuesLength
         Integer32,
      pr1646v2VEthOutQueuesOctetLength
         Integer32,
      pr1646v2VEthOutQueuesRedLength
         Integer32,
      pr1646v2VEthOutQueuesPacketsTotal
         Counter64,
      pr1646v2VEthOutQueuesPacketsDirectTx
         Counter64,
      pr1646v2VEthOutQueuesPacketsQueued
         Counter64,
      pr1646v2VEthOutQueuesPacketsDropped
         Counter64,
      pr1646v2VEthOutQueuesPacketsRedDropped
         Counter64,
      pr1646v2VEthOutQueuesPacketsCirTx
         Counter64,
      pr1646v2VEthOutQueuesPacketsEirTx
         Counter64,
      pr1646v2VEthOutQueuesPacketsViolateTx
         Counter64,
      pr1646v2VEthOutQueuesOctetsTotal
         Counter64,
      pr1646v2VEthOutQueuesOctetsDirectTx
         Counter64,
      pr1646v2VEthOutQueuesOctetsQueued
         Counter64,
      pr1646v2VEthOutQueuesOctetsDropped
         Counter64,
      pr1646v2VEthOutQueuesOctetsRedDropped
         Counter64,
      pr1646v2VEthOutQueuesOctetsCirTx
         Counter64,
      pr1646v2VEthOutQueuesOctetsEirTx
         Counter64,
      pr1646v2VEthOutQueuesOctetsViolateTx
         Counter64,
      pr1646v2VEthOutQueuesOctetsBandwidth15sec
         Integer32,
      pr1646v2VEthOutQueuesOctetsBandwidth30sec
         Integer32,
      pr1646v2VEthOutQueuesOctetsBandwidth1min
         Integer32,
      pr1646v2VEthOutQueuesOctetsBandwidth2min
         Integer32,
      pr1646v2VEthOutQueuesOctetsBandwidth5min
         Integer32
      }

pr1646v2VEthOutQueuesGlobalIx OBJECT-TYPE
   SYNTAX      GlobalIndex
   MAX-ACCESS  not-accessible
   STATUS      current
   DESCRIPTION
      "The value of the tlsCntTreeGlobalIndex of the MANAGED OBJECT."
   ::= {pr1646v2VEthOutQueuesEntry 10}

pr1646v2VEthOutQueuesTableIx OBJECT-TYPE
   SYNTAX      TableIndex
   MAX-ACCESS  not-accessible
   STATUS      current
   DESCRIPTION
      ""
   ::= {pr1646v2VEthOutQueuesEntry 11}

pr1646v2VEthOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2VEthOutQueuesEntry 16777216}

pr1646v2VEthOutQueuesLength OBJECT-TYPE
   SYNTAX      Integer32
   MAX-ACCESS  read-only
   STATUS      current
   DESCRIPTION
      "Path: virtualEthernet.performance.ifOutPriorityQueues.length"
   ::= {pr1646v2VEthOutQueuesEntry 33554432}

pr1646v2VEthOutQueuesOctetLength OBJECT-TYPE
   SYNTAX      Integer32
   MAX-ACCESS  read-only
   STATUS      current
   DESCRIPTION
      "Path: virtualEthernet.performance.ifOutPriorityQueues.octetLength"
   ::= {pr1646v2VEthOutQueuesEntry 150994944}

pr1646v2VEthOutQueuesRedLength OBJECT-TYPE
   SYNTAX      Integer32
   MAX-ACCESS  read-only
   STATUS      current
   DESCRIPTION
      "Path: virtualEthernet.performance.ifOutPriorityQueues.redLength"
   ::= {pr1646v2VEthOutQueuesEntry 134217728}

pr1646v2VEthOutQueuesPacketsTotal OBJECT-TYPE
   SYNTAX      Counter64
   MAX-ACCESS  read-only
   STATUS      current
   DESCRIPTION
      "Path: virtualEthernet.performance.ifOutPriorityQueues.packets.total

       64 bit unsigned wrappable counter."
   ::= {pr1646v2VEthOutQueuesEntry 50790400}

pr1646v2VEthOutQueuesPacketsDirectTx OBJECT-TYPE
   SYNTAX      Counter64
   MAX-ACCESS  read-only
   STATUS      current
   DESCRIPTION
      "Path: virtualEthernet.performance.ifOutPriorityQueues.packets.directTx

       64 bit unsigned wrappable counter."
   ::= {pr1646v2VEthOutQueuesEntry 50397184}

pr1646v2VEthOutQueuesPacketsQueued OBJECT-TYPE
   SYNTAX      Counter64
   MAX-ACCESS  read-only
   STATUS      current
   DESCRIPTION
      "Path: virtualEthernet.performance.ifOutPriorityQueues.packets.queued

       64 bit unsigned wrappable counter."
   ::= {pr1646v2VEthOutQueuesEntry 50462720}

pr1646v2VEthOutQueuesPacketsDropped OBJECT-TYPE
   SYNTAX      Counter64
   MAX-ACCESS  read-only
   STATUS      current
   DESCRIPTION
      "Path: virtualEthernet.performance.ifOutPriorityQueues.packets.dropped

       64 bit unsigned wrappable counter."
   ::= {pr1646v2VEthOutQueuesEntry 50528256}

pr1646v2VEthOutQueuesPacketsRedDropped OBJECT-TYPE
   SYNTAX      Counter64
   MAX-ACCESS  read-only
   STATUS      current
   DESCRIPTION
      "Path: virtualEthernet.performance.ifOutPriorityQueues.packets.redDropped

       64 bit unsigned wrappable counter."
   ::= {pr1646v2VEthOutQueuesEntry 50724864}

pr1646v2VEthOutQueuesPacketsCirTx OBJECT-TYPE
   SYNTAX      Counter64
   MAX-ACCESS  read-only
   STATUS      current
   DESCRIPTION
      "Path: virtualEthernet.performance.ifOutPriorityQueues.packets.cirTx

       64 bit unsigned wrappable counter."
   ::= {pr1646v2VEthOutQueuesEntry 50593792}

pr1646v2VEthOutQueuesPacketsEirTx OBJECT-TYPE
   SYNTAX      Counter64
   MAX-ACCESS  read-only
   STATUS      current
   DESCRIPTION
      "Path: virtualEthernet.performance.ifOutPriorityQueues.packets.eirTx

       64 bit unsigned wrappable counter."
   ::= {pr1646v2VEthOutQueuesEntry 50659328}

pr1646v2VEthOutQueuesPacketsViolateTx OBJECT-TYPE
   SYNTAX      Counter64
   MAX-ACCESS  read-only
   STATUS      current
   DESCRIPTION
      "Path: virtualEthernet.performance.ifOutPriorityQueues.packets.violateTx

       64 bit unsigned wrappable counter."
   ::= {pr1646v2VEthOutQueuesEntry 50855936}

pr1646v2VEthOutQueuesOctetsTotal OBJECT-TYPE
   SYNTAX      Counter64
   MAX-ACCESS  read-only
   STATUS      current
   DESCRIPTION
      "Path: virtualEthernet.performance.ifOutPriorityQueues.octets.total

       64 bit unsigned wrappable counter."
   ::= {pr1646v2VEthOutQueuesEntry 67567616}

pr1646v2VEthOutQueuesOctetsDirectTx OBJECT-TYPE
   SYNTAX      Counter64
   MAX-ACCESS  read-only
   STATUS      current
   DESCRIPTION
      "Path: virtualEthernet.performance.ifOutPriorityQueues.octets.directTx

       64 bit unsigned wrappable counter."
   ::= {pr1646v2VEthOutQueuesEntry 67174400}

pr1646v2VEthOutQueuesOctetsQueued OBJECT-TYPE
   SYNTAX      Counter64
   MAX-ACCESS  read-only
   STATUS      current
   DESCRIPTION
      "Path: virtualEthernet.performance.ifOutPriorityQueues.octets.queued

       64 bit unsigned wrappable counter."
   ::= {pr1646v2VEthOutQueuesEntry 67239936}

pr1646v2VEthOutQueuesOctetsDropped OBJECT-TYPE
   SYNTAX      Counter64
   MAX-ACCESS  read-only
   STATUS      current
   DESCRIPTION
      "Path: virtualEthernet.performance.ifOutPriorityQueues.octets.dropped

       64 bit unsigned wrappable counter."
   ::= {pr1646v2VEthOutQueuesEntry 67305472}

pr1646v2VEthOutQueuesOctetsRedDropped OBJECT-TYPE
   SYNTAX      Counter64
   MAX-ACCESS  read-only
   STATUS      current
   DESCRIPTION
      "Path: virtualEthernet.performance.ifOutPriorityQueues.octets.redDropped

       64 bit unsigned wrappable counter."
   ::= {pr1646v2VEthOutQueuesEntry 67502080}

pr1646v2VEthOutQueuesOctetsCirTx OBJECT-TYPE
   SYNTAX      Counter64
   MAX-ACCESS  read-only
   STATUS      current
   DESCRIPTION
      "Path: virtualEthernet.performance.ifOutPriorityQueues.octets.cirTx

       64 bit unsigned wrappable counter."
   ::= {pr1646v2VEthOutQueuesEntry 67371008}

pr1646v2VEthOutQueuesOctetsEirTx OBJECT-TYPE
   SYNTAX      Counter64
   MAX-ACCESS  read-only
   STATUS      current
   DESCRIPTION
      "Path: virtualEthernet.performance.ifOutPriorityQueues.octets.eirTx

       64 bit unsigned wrappable counter."
   ::= {pr1646v2VEthOutQueuesEntry 67436544}

pr1646v2VEthOutQueuesOctetsViolateTx OBJECT-TYPE
   SYNTAX      Counter64
   MAX-ACCESS  read-only
   STATUS      current
   DESCRIPTION
      "Path: virtualEthernet.performance.ifOutPriorityQueues.octets.violateTx

       64 bit unsigned wrappable counter."
   ::= {pr1646v2VEthOutQueuesEntry 67633152}

pr1646v2VEthOutQueuesOctetsBandwidth15sec OBJECT-TYPE
   SYNTAX      Integer32
   MAX-ACCESS  read-only
   STATUS      current
   DESCRIPTION
      "Path: virtualEthernet.performance.ifOutPriorityQueues.octets.bandwidth.15sec

       unit name = bps
       formula = 8 * ; 8 /"
   ::= {pr1646v2VEthOutQueuesEntry 70386944}

pr1646v2VEthOutQueuesOctetsBandwidth30sec OBJECT-TYPE
   SYNTAX      Integer32
   MAX-ACCESS  read-only
   STATUS      current
   DESCRIPTION
      "Path: virtualEthernet.performance.ifOutPriorityQueues.octets.bandwidth.30sec

       unit name = bps
       formula = 8 * ; 8 /"
   ::= {pr1646v2VEthOutQueuesEntry 70388224}

pr1646v2VEthOutQueuesOctetsBandwidth1min OBJECT-TYPE
   SYNTAX      Integer32
   MAX-ACCESS  read-only
   STATUS      current
   DESCRIPTION
      "Path: virtualEthernet.performance.ifOutPriorityQueues.octets.bandwidth.1min

       unit name = bps
       formula = 8 * ; 8 /"
   ::= {pr1646v2VEthOutQueuesEntry 70390784}

pr1646v2VEthOutQueuesOctetsBandwidth2min OBJECT-TYPE
   SYNTAX      Integer32
   MAX-ACCESS  read-only
   STATUS      current
   DESCRIPTION
      "Path: virtualEthernet.performance.ifOutPriorityQueues.octets.bandwidth.2min

       unit name = bps
       formula = 8 * ; 8 /"
   ::= {pr1646v2VEthOutQueuesEntry 70395904}

pr1646v2VEthOutQueuesOctetsBandwidth5min OBJECT-TYPE
   SYNTAX      Integer32
   MAX-ACCESS  read-only
   STATUS      current
   DESCRIPTION
      "Path: virtualEthernet.performance.ifOutPriorityQueues.octets.bandwidth.5min

       unit name = bps
       formula = 8 * ; 8 /"
   ::= {pr1646v2VEthOutQueuesEntry 70411264}

pr1646v2VEthOutQueuesH2Performance OBJECT-TYPE
   SYNTAX      SEQUENCE OF Pr1646v2VEthOutQueuesH2PerformanceEntry
   MAX-ACCESS  not-accessible
   STATUS      current
   DESCRIPTION
      ""
   ::= {pr1646v2VEthOutQueues 83886080}

pr1646v2VEthOutQueuesH2PerformanceEntry OBJECT-TYPE
   SYNTAX      Pr1646v2VEthOutQueuesH2PerformanceEntry
   MAX-ACCESS  not-accessible
   STATUS      current
   DESCRIPTION
      ""
   INDEX      { pr1646v2VEthOutQueuesH2PerformanceGlobalIx,
                pr1646v2VEthOutQueuesTableIx,
                pr1646v2VEthOutQueuesH2PerformanceTableIx }
   ::= {pr1646v2VEthOutQueuesH2Performance 1}

Pr1646v2VEthOutQueuesH2PerformanceEntry ::=
   SEQUENCE
      {
      pr1646v2VEthOutQueuesH2PerformanceGlobalIx
         GlobalIndex,
      pr1646v2VEthOutQueuesH2PerformanceTableIx
         TableIndex,
      pr1646v2VEthOutQueuesH2PerformanceSysUpTime
         TimeTicks,
      pr1646v2VEthOutQueuesH2PerformanceTotPkts
         Counter64,
      pr1646v2VEthOutQueuesH2PerformanceDirTxPkts
         Counter64,
      pr1646v2VEthOutQueuesH2PerformanceQdPkts
         Counter64,
      pr1646v2VEthOutQueuesH2PerformanceDropPkts
         Counter64,
      pr1646v2VEthOutQueuesH2PerformanceRDropPkts
         Counter64,
      pr1646v2VEthOutQueuesH2PerformanceCirTxPkts
         Counter64,
      pr1646v2VEthOutQueuesH2PerformanceEirTxPkts
         Counter64,
      pr1646v2VEthOutQueuesH2PerformanceViolTxPkts
         Counter64,
      pr1646v2VEthOutQueuesH2PerformanceTotOcts
         Counter64,
      pr1646v2VEthOutQueuesH2PerformanceDirTxOcts
         Counter64,
      pr1646v2VEthOutQueuesH2PerformanceQdOcts
         Counter64,
      pr1646v2VEthOutQueuesH2PerformanceDropOcts
         Counter64,
      pr1646v2VEthOutQueuesH2PerformanceRDropOcts
         Counter64,
      pr1646v2VEthOutQueuesH2PerformanceCirTxOcts
         Counter64,
      pr1646v2VEthOutQueuesH2PerformanceEirTxOcts
         Counter64,
      pr1646v2VEthOutQueuesH2PerformanceViolTxOcts
         Counter64,
      pr1646v2VEthOutQueuesH2PerformanceBandwidth
         Integer32
      }

pr1646v2VEthOutQueuesH2PerformanceGlobalIx OBJECT-TYPE
   SYNTAX      GlobalIndex
   MAX-ACCESS  not-accessible
   STATUS      current
   DESCRIPTION
      "The value of the tlsCntTreeGlobalIndex of the MANAGED OBJECT."
   ::= {pr1646v2VEthOutQueuesH2PerformanceEntry 10}

pr1646v2VEthOutQueuesH2PerformanceTableIx OBJECT-TYPE
   SYNTAX      TableIndex
   MAX-ACCESS  not-accessible
   STATUS      current
   DESCRIPTION
      ""
   ::= {pr1646v2VEthOutQueuesH2PerformanceEntry 11}

pr1646v2VEthOutQueuesH2PerformanceSysUpTime OBJECT-TYPE
   SYNTAX      TimeTicks
   MAX-ACCESS  read-only
   STATUS      current
   DESCRIPTION
      "Path: virtualEthernet.performance.ifOutPriorityQueues.h2Performance.sysUpTime

       Time in centi-second."
   ::= {pr1646v2VEthOutQueuesH2PerformanceEntry 16777216}

pr1646v2VEthOutQueuesH2PerformanceTotPkts OBJECT-TYPE
   SYNTAX      Counter64
   MAX-ACCESS  read-only
   STATUS      current
   DESCRIPTION
      "Path: virtualEthernet.performance.ifOutPriorityQueues.h2Performance.totalPkts

       64 bit unsigned wrappable counter."
   ::= {pr1646v2VEthOutQueuesH2PerformanceEntry 234881024}

pr1646v2VEthOutQueuesH2PerformanceDirTxPkts OBJECT-TYPE
   SYNTAX      Counter64
   MAX-ACCESS  read-only
   STATUS      current
   DESCRIPTION
      "Path: virtualEthernet.performance.ifOutPriorityQueues.h2Performance.directTxPkts

       64 bit unsigned wrappable counter."
   ::= {pr1646v2VEthOutQueuesH2PerformanceEntry 33554432}

pr1646v2VEthOutQueuesH2PerformanceQdPkts OBJECT-TYPE
   SYNTAX      Counter64
   MAX-ACCESS  read-only
   STATUS      current
   DESCRIPTION
      "Path: virtualEthernet.performance.ifOutPriorityQueues.h2Performance.queuedPkts

       64 bit unsigned wrappable counter."
   ::= {pr1646v2VEthOutQueuesH2PerformanceEntry 50331648}

pr1646v2VEthOutQueuesH2PerformanceDropPkts OBJECT-TYPE
   SYNTAX      Counter64
   MAX-ACCESS  read-only
   STATUS      current
   DESCRIPTION
      "Path: virtualEthernet.performance.ifOutPriorityQueues.h2Performance.droppedPkts

       64 bit unsigned wrappable counter."
   ::= {pr1646v2VEthOutQueuesH2PerformanceEntry 67108864}

pr1646v2VEthOutQueuesH2PerformanceRDropPkts OBJECT-TYPE
   SYNTAX      Counter64
   MAX-ACCESS  read-only
   STATUS      current
   DESCRIPTION
      "Path: virtualEthernet.performance.ifOutPriorityQueues.h2Performance.redDroppedPkts

       64 bit unsigned wrappable counter."
   ::= {pr1646v2VEthOutQueuesH2PerformanceEntry 201326592}

pr1646v2VEthOutQueuesH2PerformanceCirTxPkts OBJECT-TYPE
   SYNTAX      Counter64
   MAX-ACCESS  read-only
   STATUS      current
   DESCRIPTION
      "Path: virtualEthernet.performance.ifOutPriorityQueues.h2Performance.cirTxPkts

       64 bit unsigned wrappable counter."
   ::= {pr1646v2VEthOutQueuesH2PerformanceEntry 83886080}

pr1646v2VEthOutQueuesH2PerformanceEirTxPkts OBJECT-TYPE
   SYNTAX      Counter64
   MAX-ACCESS  read-only
   STATUS      current
   DESCRIPTION
      "Path: virtualEthernet.performance.ifOutPriorityQueues.h2Performance.eirTxPkts

       64 bit unsigned wrappable counter."
   ::= {pr1646v2VEthOutQueuesH2PerformanceEntry 100663296}

pr1646v2VEthOutQueuesH2PerformanceViolTxPkts OBJECT-TYPE
   SYNTAX      Counter64
   MAX-ACCESS  read-only
   STATUS      current
   DESCRIPTION
      "Path: virtualEthernet.performance.ifOutPriorityQueues.h2Performance.violateTxPkts

       64 bit unsigned wrappable counter."
   ::= {pr1646v2VEthOutQueuesH2PerformanceEntry 301989888}

pr1646v2VEthOutQueuesH2PerformanceTotOcts OBJECT-TYPE
   SYNTAX      Counter64
   MAX-ACCESS  read-only
   STATUS      current
   DESCRIPTION
      "Path: virtualEthernet.performance.ifOutPriorityQueues.h2Performance.totalOctets

       64 bit unsigned wrappable counter."
   ::= {pr1646v2VEthOutQueuesH2PerformanceEntry 251658240}

pr1646v2VEthOutQueuesH2PerformanceDirTxOcts OBJECT-TYPE
   SYNTAX      Counter64
   MAX-ACCESS  read-only
   STATUS      current
   DESCRIPTION
      "Path: virtualEthernet.performance.ifOutPriorityQueues.h2Performance.directTxOctets

       64 bit unsigned wrappable counter."
   ::= {pr1646v2VEthOutQueuesH2PerformanceEntry 117440512}

pr1646v2VEthOutQueuesH2PerformanceQdOcts OBJECT-TYPE
   SYNTAX      Counter64
   MAX-ACCESS  read-only
   STATUS      current
   DESCRIPTION
      "Path: virtualEthernet.performance.ifOutPriorityQueues.h2Performance.queuedOctets

       64 bit unsigned wrappable counter."
   ::= {pr1646v2VEthOutQueuesH2PerformanceEntry 134217728}

pr1646v2VEthOutQueuesH2PerformanceDropOcts OBJECT-TYPE
   SYNTAX      Counter64
   MAX-ACCESS  read-only
   STATUS      current
   DESCRIPTION
      "Path: virtualEthernet.performance.ifOutPriorityQueues.h2Performance.droppedOctets

       64 bit unsigned wrappable counter."
   ::= {pr1646v2VEthOutQueuesH2PerformanceEntry 150994944}

pr1646v2VEthOutQueuesH2PerformanceRDropOcts OBJECT-TYPE
   SYNTAX      Counter64
   MAX-ACCESS  read-only
   STATUS      current
   DESCRIPTION
      "Path: virtualEthernet.performance.ifOutPriorityQueues.h2Performance.redDroppedOctets

       64 bit unsigned wrappable counter."
   ::= {pr1646v2VEthOutQueuesH2PerformanceEntry 218103808}

pr1646v2VEthOutQueuesH2PerformanceCirTxOcts OBJECT-TYPE
   SYNTAX      Counter64
   MAX-ACCESS  read-only
   STATUS      current
   DESCRIPTION
      "Path: virtualEthernet.performance.ifOutPriorityQueues.h2Performance.cirTxOctets

       64 bit unsigned wrappable counter."
   ::= {pr1646v2VEthOutQueuesH2PerformanceEntry 167772160}

pr1646v2VEthOutQueuesH2PerformanceEirTxOcts OBJECT-TYPE
   SYNTAX      Counter64
   MAX-ACCESS  read-only
   STATUS      current
   DESCRIPTION
      "Path: virtualEthernet.performance.ifOutPriorityQueues.h2Performance.eirTxOctets

       64 bit unsigned wrappable counter."
   ::= {pr1646v2VEthOutQueuesH2PerformanceEntry 184549376}

pr1646v2VEthOutQueuesH2PerformanceViolTxOcts OBJECT-TYPE
   SYNTAX      Counter64
   MAX-ACCESS  read-only
   STATUS      current
   DESCRIPTION
      "Path: virtualEthernet.performance.ifOutPriorityQueues.h2Performance.violateTxOctets

       64 bit unsigned wrappable counter."
   ::= {pr1646v2VEthOutQueuesH2PerformanceEntry 318767104}

pr1646v2VEthOutQueuesH2PerformanceBandwidth OBJECT-TYPE
   SYNTAX      Integer32
   MAX-ACCESS  read-only
   STATUS      current
   DESCRIPTION
      "Path: virtualEthernet.performance.ifOutPriorityQueues.h2Performance.bandwidth

       unit name = bps
       formula = 8 * ; 8 /"
   ::= {pr1646v2VEthOutQueuesH2PerformanceEntry 268435456}

pr1646v2VEthOutQueuesH24Performance OBJECT-TYPE
   SYNTAX      SEQUENCE OF Pr1646v2VEthOutQueuesH24PerformanceEntry
   MAX-ACCESS  not-accessible
   STATUS      current
   DESCRIPTION
      ""
   ::= {pr1646v2VEthOutQueues 100663296}

pr1646v2VEthOutQueuesH24PerformanceEntry OBJECT-TYPE
   SYNTAX      Pr1646v2VEthOutQueuesH24PerformanceEntry
   MAX-ACCESS  not-accessible
   STATUS      current
   DESCRIPTION
      ""
   INDEX      { pr1646v2VEthOutQueuesH24PerformanceGlobalIx,
                pr1646v2VEthOutQueuesTableIx,
                pr1646v2VEthOutQueuesH24PerformanceTableIx }
   ::= {pr1646v2VEthOutQueuesH24Performance 1}

Pr1646v2VEthOutQueuesH24PerformanceEntry ::=
   SEQUENCE
      {
      pr1646v2VEthOutQueuesH24PerformanceGlobalIx
         GlobalIndex,
      pr1646v2VEthOutQueuesH24PerformanceTableIx
         TableIndex,
      pr1646v2VEthOutQueuesH24PerformanceSysUpTime
         TimeTicks,
      pr1646v2VEthOutQueuesH24PerformanceTotPkts
         Counter64,
      pr1646v2VEthOutQueuesH24PerformanceDirTxPkts
         Counter64,
      pr1646v2VEthOutQueuesH24PerformanceQdPkts
         Counter64,
      pr1646v2VEthOutQueuesH24PerformanceDropPkts
         Counter64,
      pr1646v2VEthOutQueuesH24PerformanceRDropPkts
         Counter64,
      pr1646v2VEthOutQueuesH24PerformanceCirTxPkts
         Counter64,
      pr1646v2VEthOutQueuesH24PerformanceEirTxPkts
         Counter64,
      pr1646v2VEthOutQueuesH24PerformanceViolTxPkts
         Counter64,
      pr1646v2VEthOutQueuesH24PerformanceTotOcts
         Counter64,
      pr1646v2VEthOutQueuesH24PerformanceDirTxOcts
         Counter64,
      pr1646v2VEthOutQueuesH24PerformanceQdOcts
         Counter64,
      pr1646v2VEthOutQueuesH24PerformanceDropOcts
         Counter64,
      pr1646v2VEthOutQueuesH24PerformanceRDropOcts
         Counter64,
      pr1646v2VEthOutQueuesH24PerformanceCirTxOcts
         Counter64,
      pr1646v2VEthOutQueuesH24PerformanceEirTxOcts
         Counter64,
      pr1646v2VEthOutQueuesH24PerformanceViolTxOcts
         Counter64,
      pr1646v2VEthOutQueuesH24PerformanceBandwidth
         Integer32
      }

pr1646v2VEthOutQueuesH24PerformanceGlobalIx OBJECT-TYPE
   SYNTAX      GlobalIndex
   MAX-ACCESS  not-accessible
   STATUS      current
   DESCRIPTION
      "The value of the tlsCntTreeGlobalIndex of the MANAGED OBJECT."
   ::= {pr1646v2VEthOutQueuesH24PerformanceEntry 10}

pr1646v2VEthOutQueuesH24PerformanceTableIx OBJECT-TYPE
   SYNTAX      TableIndex
   MAX-ACCESS  not-accessible
   STATUS      current
   DESCRIPTION
      ""
   ::= {pr1646v2VEthOutQueuesH24PerformanceEntry 11}

pr1646v2VEthOutQueuesH24PerformanceSysUpTime OBJECT-TYPE
   SYNTAX      TimeTicks
   MAX-ACCESS  read-only
   STATUS      current
   DESCRIPTION
      "Path: virtualEthernet.performance.ifOutPriorityQueues.h24Performance.sysUpTime

       Time in centi-second."
   ::= {pr1646v2VEthOutQueuesH24PerformanceEntry 16777216}

pr1646v2VEthOutQueuesH24PerformanceTotPkts OBJECT-TYPE
   SYNTAX      Counter64
   MAX-ACCESS  read-only
   STATUS      current
   DESCRIPTION
      "Path: virtualEthernet.performance.ifOutPriorityQueues.h24Performance.totalPkts

       64 bit unsigned wrappable counter."
   ::= {pr1646v2VEthOutQueuesH24PerformanceEntry 234881024}

pr1646v2VEthOutQueuesH24PerformanceDirTxPkts OBJECT-TYPE
   SYNTAX      Counter64
   MAX-ACCESS  read-only
   STATUS      current
   DESCRIPTION
      "Path: virtualEthernet.performance.ifOutPriorityQueues.h24Performance.directTxPkts

       64 bit unsigned wrappable counter."
   ::= {pr1646v2VEthOutQueuesH24PerformanceEntry 33554432}

pr1646v2VEthOutQueuesH24PerformanceQdPkts OBJECT-TYPE
   SYNTAX      Counter64
   MAX-ACCESS  read-only
   STATUS      current
   DESCRIPTION
      "Path: virtualEthernet.performance.ifOutPriorityQueues.h24Performance.queuedPkts

       64 bit unsigned wrappable counter."
   ::= {pr1646v2VEthOutQueuesH24PerformanceEntry 50331648}

pr1646v2VEthOutQueuesH24PerformanceDropPkts OBJECT-TYPE
   SYNTAX      Counter64
   MAX-ACCESS  read-only
   STATUS      current
   DESCRIPTION
      "Path: virtualEthernet.performance.ifOutPriorityQueues.h24Performance.droppedPkts

       64 bit unsigned wrappable counter."
   ::= {pr1646v2VEthOutQueuesH24PerformanceEntry 67108864}

pr1646v2VEthOutQueuesH24PerformanceRDropPkts OBJECT-TYPE
   SYNTAX      Counter64
   MAX-ACCESS  read-only
   STATUS      current
   DESCRIPTION
      "Path: virtualEthernet.performance.ifOutPriorityQueues.h24Performance.redDroppedPkts

       64 bit unsigned wrappable counter."
   ::= {pr1646v2VEthOutQueuesH24PerformanceEntry 201326592}

pr1646v2VEthOutQueuesH24PerformanceCirTxPkts OBJECT-TYPE
   SYNTAX      Counter64
   MAX-ACCESS  read-only
   STATUS      current
   DESCRIPTION
      "Path: virtualEthernet.performance.ifOutPriorityQueues.h24Performance.cirTxPkts

       64 bit unsigned wrappable counter."
   ::= {pr1646v2VEthOutQueuesH24PerformanceEntry 83886080}

pr1646v2VEthOutQueuesH24PerformanceEirTxPkts OBJECT-TYPE
   SYNTAX      Counter64
   MAX-ACCESS  read-only
   STATUS      current
   DESCRIPTION
      "Path: virtualEthernet.performance.ifOutPriorityQueues.h24Performance.eirTxPkts

       64 bit unsigned wrappable counter."
   ::= {pr1646v2VEthOutQueuesH24PerformanceEntry 100663296}

pr1646v2VEthOutQueuesH24PerformanceViolTxPkts OBJECT-TYPE
   SYNTAX      Counter64
   MAX-ACCESS  read-only
   STATUS      current
   DESCRIPTION
      "Path: virtualEthernet.performance.ifOutPriorityQueues.h24Performance.violateTxPkts

       64 bit unsigned wrappable counter."
   ::= {pr1646v2VEthOutQueuesH24PerformanceEntry 301989888}

pr1646v2VEthOutQueuesH24PerformanceTotOcts OBJECT-TYPE
   SYNTAX      Counter64
   MAX-ACCESS  read-only
   STATUS      current
   DESCRIPTION
      "Path: virtualEthernet.performance.ifOutPriorityQueues.h24Performance.totalOctets

       64 bit unsigned wrappable counter."
   ::= {pr1646v2VEthOutQueuesH24PerformanceEntry 251658240}

pr1646v2VEthOutQueuesH24PerformanceDirTxOcts OBJECT-TYPE
   SYNTAX      Counter64
   MAX-ACCESS  read-only
   STATUS      current
   DESCRIPTION
      "Path: virtualEthernet.performance.ifOutPriorityQueues.h24Performance.directTxOctets

       64 bit unsigned wrappable counter."
   ::= {pr1646v2VEthOutQueuesH24PerformanceEntry 117440512}

pr1646v2VEthOutQueuesH24PerformanceQdOcts OBJECT-TYPE
   SYNTAX      Counter64
   MAX-ACCESS  read-only
   STATUS      current
   DESCRIPTION
      "Path: virtualEthernet.performance.ifOutPriorityQueues.h24Performance.queuedOctets

       64 bit unsigned wrappable counter."
   ::= {pr1646v2VEthOutQueuesH24PerformanceEntry 134217728}

pr1646v2VEthOutQueuesH24PerformanceDropOcts OBJECT-TYPE
   SYNTAX      Counter64
   MAX-ACCESS  read-only
   STATUS      current
   DESCRIPTION
      "Path: virtualEthernet.performance.ifOutPriorityQueues.h24Performance.droppedOctets

       64 bit unsigned wrappable counter."
   ::= {pr1646v2VEthOutQueuesH24PerformanceEntry 150994944}

pr1646v2VEthOutQueuesH24PerformanceRDropOcts OBJECT-TYPE
   SYNTAX      Counter64
   MAX-ACCESS  read-only
   STATUS      current
   DESCRIPTION
      "Path: virtualEthernet.performance.ifOutPriorityQueues.h24Performance.redDroppedOctets

       64 bit unsigned wrappable counter."
   ::= {pr1646v2VEthOutQueuesH24PerformanceEntry 218103808}

pr1646v2VEthOutQueuesH24PerformanceCirTxOcts OBJECT-TYPE
   SYNTAX      Counter64
   MAX-ACCESS  read-only
   STATUS      current
   DESCRIPTION
      "Path: virtualEthernet.performance.ifOutPriorityQueues.h24Performance.cirTxOctets

       64 bit unsigned wrappable counter."
   ::= {pr1646v2VEthOutQueuesH24PerformanceEntry 167772160}

pr1646v2VEthOutQueuesH24PerformanceEirTxOcts OBJECT-TYPE
   SYNTAX      Counter64
   MAX-ACCESS  read-only
   STATUS      current
   DESCRIPTION
      "Path: virtualEthernet.performance.ifOutPriorityQueues.h24Performance.eirTxOctets

       64 bit unsigned wrappable counter."
   ::= {pr1646v2VEthOutQueuesH24PerformanceEntry 184549376}

pr1646v2VEthOutQueuesH24PerformanceViolTxOcts OBJECT-TYPE
   SYNTAX      Counter64
   MAX-ACCESS  read-only
   STATUS      current
   DESCRIPTION
      "Path: virtualEthernet.performance.ifOutPriorityQueues.h24Performance.violateTxOctets

       64 bit unsigned wrappable counter."
   ::= {pr1646v2VEthOutQueuesH24PerformanceEntry 318767104}

pr1646v2VEthOutQueuesH24PerformanceBandwidth OBJECT-TYPE
   SYNTAX      Integer32
   MAX-ACCESS  read-only
   STATUS      current
   DESCRIPTION
      "Path: virtualEthernet.performance.ifOutPriorityQueues.h24Performance.bandwidth

       unit name = bps
       formula = 8 * ; 8 /"
   ::= {pr1646v2VEthOutQueuesH24PerformanceEntry 268435456}

pr1646v2VEthOutQueuesD7Performance OBJECT-TYPE
   SYNTAX      SEQUENCE OF Pr1646v2VEthOutQueuesD7PerformanceEntry
   MAX-ACCESS  not-accessible
   STATUS      current
   DESCRIPTION
      ""
   ::= {pr1646v2VEthOutQueues 117440512}

pr1646v2VEthOutQueuesD7PerformanceEntry OBJECT-TYPE
   SYNTAX      Pr1646v2VEthOutQueuesD7PerformanceEntry
   MAX-ACCESS  not-accessible
   STATUS      current
   DESCRIPTION
      ""
   INDEX      { pr1646v2VEthOutQueuesD7PerformanceGlobalIx,
                pr1646v2VEthOutQueuesTableIx,
                pr1646v2VEthOutQueuesD7PerformanceTableIx }
   ::= {pr1646v2VEthOutQueuesD7Performance 1}

Pr1646v2VEthOutQueuesD7PerformanceEntry ::=
   SEQUENCE
      {
      pr1646v2VEthOutQueuesD7PerformanceGlobalIx
         GlobalIndex,
      pr1646v2VEthOutQueuesD7PerformanceTableIx
         TableIndex,
      pr1646v2VEthOutQueuesD7PerformanceSysUpTime
         TimeTicks,
      pr1646v2VEthOutQueuesD7PerformanceTotPkts
         Counter64,
      pr1646v2VEthOutQueuesD7PerformanceDirTxPkts
         Counter64,
      pr1646v2VEthOutQueuesD7PerformanceQdPkts
         Counter64,
      pr1646v2VEthOutQueuesD7PerformanceDropPkts
         Counter64,
      pr1646v2VEthOutQueuesD7PerformanceRDropPkts
         Counter64,
      pr1646v2VEthOutQueuesD7PerformanceCirTxPkts
         Counter64,
      pr1646v2VEthOutQueuesD7PerformanceEirTxPkts
         Counter64,
      pr1646v2VEthOutQueuesD7PerformanceViolTxPkts
         Counter64,
      pr1646v2VEthOutQueuesD7PerformanceTotOcts
         Counter64,
      pr1646v2VEthOutQueuesD7PerformanceDirTxOcts
         Counter64,
      pr1646v2VEthOutQueuesD7PerformanceQdOcts
         Counter64,
      pr1646v2VEthOutQueuesD7PerformanceDropOcts
         Counter64,
      pr1646v2VEthOutQueuesD7PerformanceRDropOcts
         Counter64,
      pr1646v2VEthOutQueuesD7PerformanceCirTxOcts
         Counter64,
      pr1646v2VEthOutQueuesD7PerformanceEirTxOcts
         Counter64,
      pr1646v2VEthOutQueuesD7PerformanceViolTxOcts
         Counter64,
      pr1646v2VEthOutQueuesD7PerformanceBandwidth
         Integer32
      }

pr1646v2VEthOutQueuesD7PerformanceGlobalIx OBJECT-TYPE
   SYNTAX      GlobalIndex
   MAX-ACCESS  not-accessible
   STATUS      current
   DESCRIPTION
      "The value of the tlsCntTreeGlobalIndex of the MANAGED OBJECT."
   ::= {pr1646v2VEthOutQueuesD7PerformanceEntry 10}

pr1646v2VEthOutQueuesD7PerformanceTableIx OBJECT-TYPE
   SYNTAX      TableIndex
   MAX-ACCESS  not-accessible
   STATUS      current
   DESCRIPTION
      ""
   ::= {pr1646v2VEthOutQueuesD7PerformanceEntry 11}

pr1646v2VEthOutQueuesD7PerformanceSysUpTime OBJECT-TYPE
   SYNTAX      TimeTicks
   MAX-ACCESS  read-only
   STATUS      current
   DESCRIPTION
      "Path: virtualEthernet.performance.ifOutPriorityQueues.d7Performance.sysUpTime

       Time in centi-second."
   ::= {pr1646v2VEthOutQueuesD7PerformanceEntry 16777216}

pr1646v2VEthOutQueuesD7PerformanceTotPkts OBJECT-TYPE
   SYNTAX      Counter64
   MAX-ACCESS  read-only
   STATUS      current
   DESCRIPTION
      "Path: virtualEthernet.performance.ifOutPriorityQueues.d7Performance.totalPkts

       64 bit unsigned wrappable counter."
   ::= {pr1646v2VEthOutQueuesD7PerformanceEntry 234881024}

pr1646v2VEthOutQueuesD7PerformanceDirTxPkts OBJECT-TYPE
   SYNTAX      Counter64
   MAX-ACCESS  read-only
   STATUS      current
   DESCRIPTION
      "Path: virtualEthernet.performance.ifOutPriorityQueues.d7Performance.directTxPkts

       64 bit unsigned wrappable counter."
   ::= {pr1646v2VEthOutQueuesD7PerformanceEntry 33554432}

pr1646v2VEthOutQueuesD7PerformanceQdPkts OBJECT-TYPE
   SYNTAX      Counter64
   MAX-ACCESS  read-only
   STATUS      current
   DESCRIPTION
      "Path: virtualEthernet.performance.ifOutPriorityQueues.d7Performance.queuedPkts

       64 bit unsigned wrappable counter."
   ::= {pr1646v2VEthOutQueuesD7PerformanceEntry 50331648}

pr1646v2VEthOutQueuesD7PerformanceDropPkts OBJECT-TYPE
   SYNTAX      Counter64
   MAX-ACCESS  read-only
   STATUS      current
   DESCRIPTION
      "Path: virtualEthernet.performance.ifOutPriorityQueues.d7Performance.droppedPkts

       64 bit unsigned wrappable counter."
   ::= {pr1646v2VEthOutQueuesD7PerformanceEntry 67108864}

pr1646v2VEthOutQueuesD7PerformanceRDropPkts OBJECT-TYPE
   SYNTAX      Counter64
   MAX-ACCESS  read-only
   STATUS      current
   DESCRIPTION
      "Path: virtualEthernet.performance.ifOutPriorityQueues.d7Performance.redDroppedPkts

       64 bit unsigned wrappable counter."
   ::= {pr1646v2VEthOutQueuesD7PerformanceEntry 201326592}

pr1646v2VEthOutQueuesD7PerformanceCirTxPkts OBJECT-TYPE
   SYNTAX      Counter64
   MAX-ACCESS  read-only
   STATUS      current
   DESCRIPTION
      "Path: virtualEthernet.performance.ifOutPriorityQueues.d7Performance.cirTxPkts

       64 bit unsigned wrappable counter."
   ::= {pr1646v2VEthOutQueuesD7PerformanceEntry 83886080}

pr1646v2VEthOutQueuesD7PerformanceEirTxPkts OBJECT-TYPE
   SYNTAX      Counter64
   MAX-ACCESS  read-only
   STATUS      current
   DESCRIPTION
      "Path: virtualEthernet.performance.ifOutPriorityQueues.d7Performance.eirTxPkts

       64 bit unsigned wrappable counter."
   ::= {pr1646v2VEthOutQueuesD7PerformanceEntry 100663296}

pr1646v2VEthOutQueuesD7PerformanceViolTxPkts OBJECT-TYPE
   SYNTAX      Counter64
   MAX-ACCESS  read-only
   STATUS      current
   DESCRIPTION
      "Path: virtualEthernet.performance.ifOutPriorityQueues.d7Performance.violateTxPkts

       64 bit unsigned wrappable counter."
   ::= {pr1646v2VEthOutQueuesD7PerformanceEntry 301989888}

pr1646v2VEthOutQueuesD7PerformanceTotOcts OBJECT-TYPE
   SYNTAX      Counter64
   MAX-ACCESS  read-only
   STATUS      current
   DESCRIPTION
      "Path: virtualEthernet.performance.ifOutPriorityQueues.d7Performance.totalOctets

       64 bit unsigned wrappable counter."
   ::= {pr1646v2VEthOutQueuesD7PerformanceEntry 251658240}

pr1646v2VEthOutQueuesD7PerformanceDirTxOcts OBJECT-TYPE
   SYNTAX      Counter64
   MAX-ACCESS  read-only
   STATUS      current
   DESCRIPTION
      "Path: virtualEthernet.performance.ifOutPriorityQueues.d7Performance.directTxOctets

       64 bit unsigned wrappable counter."
   ::= {pr1646v2VEthOutQueuesD7PerformanceEntry 117440512}

pr1646v2VEthOutQueuesD7PerformanceQdOcts OBJECT-TYPE
   SYNTAX      Counter64
   MAX-ACCESS  read-only
   STATUS      current
   DESCRIPTION
      "Path: virtualEthernet.performance.ifOutPriorityQueues.d7Performance.queuedOctets

       64 bit unsigned wrappable counter."
   ::= {pr1646v2VEthOutQueuesD7PerformanceEntry 134217728}

pr1646v2VEthOutQueuesD7PerformanceDropOcts OBJECT-TYPE
   SYNTAX      Counter64
   MAX-ACCESS  read-only
   STATUS      current
   DESCRIPTION
      "Path: virtualEthernet.performance.ifOutPriorityQueues.d7Performance.droppedOctets

       64 bit unsigned wrappable counter."
   ::= {pr1646v2VEthOutQueuesD7PerformanceEntry 150994944}

pr1646v2VEthOutQueuesD7PerformanceRDropOcts OBJECT-TYPE
   SYNTAX      Counter64
   MAX-ACCESS  read-only
   STATUS      current
   DESCRIPTION
      "Path: virtualEthernet.performance.ifOutPriorityQueues.d7Performance.redDroppedOctets

       64 bit unsigned wrappable counter."
   ::= {pr1646v2VEthOutQueuesD7PerformanceEntry 218103808}

pr1646v2VEthOutQueuesD7PerformanceCirTxOcts OBJECT-TYPE
   SYNTAX      Counter64
   MAX-ACCESS  read-only
   STATUS      current
   DESCRIPTION
      "Path: virtualEthernet.performance.ifOutPriorityQueues.d7Performance.cirTxOctets

       64 bit unsigned wrappable counter."
   ::= {pr1646v2VEthOutQueuesD7PerformanceEntry 167772160}

pr1646v2VEthOutQueuesD7PerformanceEirTxOcts OBJECT-TYPE
   SYNTAX      Counter64
   MAX-ACCESS  read-only
   STATUS      current
   DESCRIPTION
      "Path: virtualEthernet.performance.ifOutPriorityQueues.d7Performance.eirTxOctets

       64 bit unsigned wrappable counter."
   ::= {pr1646v2VEthOutQueuesD7PerformanceEntry 184549376}

pr1646v2VEthOutQueuesD7PerformanceViolTxOcts OBJECT-TYPE
   SYNTAX      Counter64
   MAX-ACCESS  read-only
   STATUS      current
   DESCRIPTION
      "Path: virtualEthernet.performance.ifOutPriorityQueues.d7Performance.violateTxOctets

       64 bit unsigned wrappable counter."
   ::= {pr1646v2VEthOutQueuesD7PerformanceEntry 318767104}

pr1646v2VEthOutQueuesD7PerformanceBandwidth OBJECT-TYPE
   SYNTAX      Integer32
   MAX-ACCESS  read-only
   STATUS      current
   DESCRIPTION
      "Path: virtualEthernet.performance.ifOutPriorityQueues.d7Performance.bandwidth

       unit name = bps
       formula = 8 * ; 8 /"
   ::= {pr1646v2VEthOutQueuesD7PerformanceEntry 268435456}


pr1646v2VEthOutBandwidth OBJECT IDENTIFIER ::= {pr1646v2VEth 182}

pr1646v2VEthOutBandwidthSSCTable OBJECT-TYPE
   SYNTAX      SEQUENCE OF Pr1646v2VEthOutBandwidthEntry
   MAX-ACCESS  not-accessible
   STATUS      current
   DESCRIPTION
      "bandwidth"
   ::= {pr1646v2VEthOutBandwidth 1}

pr1646v2VEthOutBandwidthEntry OBJECT-TYPE
   SYNTAX      Pr1646v2VEthOutBandwidthEntry
   MAX-ACCESS  not-accessible
   STATUS      current
   DESCRIPTION
      ""
   INDEX      { pr1646v2VEthOutBandwidthGlobalIx }
   ::= {pr1646v2VEthOutBandwidthSSCTable 1}

Pr1646v2VEthOutBandwidthEntry ::=
   SEQUENCE
      {
      pr1646v2VEthOutBandwidthGlobalIx
         GlobalIndex,
      pr1646v2VEthOutBandwidth15sec
         Integer32,
      pr1646v2VEthOutBandwidth30sec
         Integer32,
      pr1646v2VEthOutBandwidth1min
         Integer32,
      pr1646v2VEthOutBandwidth2min
         Integer32,
      pr1646v2VEthOutBandwidth5min
         Integer32
      }

pr1646v2VEthOutBandwidthGlobalIx OBJECT-TYPE
   SYNTAX      GlobalIndex
   MAX-ACCESS  not-accessible
   STATUS      current
   DESCRIPTION
      "The value of the tlsCntTreeGlobalIndex of the MANAGED OBJECT."
   ::= {pr1646v2VEthOutBandwidthEntry 10}

pr1646v2VEthOutBandwidth15sec OBJECT-TYPE
   SYNTAX      Integer32
   MAX-ACCESS  read-only
   STATUS      current
   DESCRIPTION
      "Path: virtualEthernet.performance.ifOutBandwidth.15sec

       unit name = bps
       formula = 8 * ; 8 /"
   ::= {pr1646v2VEthOutBandwidthEntry 83886080}

pr1646v2VEthOutBandwidth30sec OBJECT-TYPE
   SYNTAX      Integer32
   MAX-ACCESS  read-only
   STATUS      current
   DESCRIPTION
      "Path: virtualEthernet.performance.ifOutBandwidth.30sec

       unit name = bps
       formula = 8 * ; 8 /"
   ::= {pr1646v2VEthOutBandwidthEntry 167772160}

pr1646v2VEthOutBandwidth1min OBJECT-TYPE
   SYNTAX      Integer32
   MAX-ACCESS  read-only
   STATUS      current
   DESCRIPTION
      "Path: virtualEthernet.performance.ifOutBandwidth.1min

       unit name = bps
       formula = 8 * ; 8 /"
   ::= {pr1646v2VEthOutBandwidthEntry 335544320}

pr1646v2VEthOutBandwidth2min OBJECT-TYPE
   SYNTAX      Integer32
   MAX-ACCESS  read-only
   STATUS      current
   DESCRIPTION
      "Path: virtualEthernet.performance.ifOutBandwidth.2min

       unit name = bps
       formula = 8 * ; 8 /"
   ::= {pr1646v2VEthOutBandwidthEntry 671088640}

pr1646v2VEthOutBandwidth5min OBJECT-TYPE
   SYNTAX      Integer32
   MAX-ACCESS  read-only
   STATUS      current
   DESCRIPTION
      "Path: virtualEthernet.performance.ifOutBandwidth.5min

       unit name = bps
       formula = 8 * ; 8 /"
   ::= {pr1646v2VEthOutBandwidthEntry 1677721600}


pr1646v2VEthInP OBJECT IDENTIFIER ::= {pr1646v2VEth 307}

pr1646v2VEthInPSSCTable OBJECT-TYPE
   SYNTAX      SEQUENCE OF Pr1646v2VEthInPEntry
   MAX-ACCESS  not-accessible
   STATUS      current
   DESCRIPTION
      "h2IfInPerformance"
   ::= {pr1646v2VEthInP 1}

pr1646v2VEthInPEntry OBJECT-TYPE
   SYNTAX      Pr1646v2VEthInPEntry
   MAX-ACCESS  not-accessible
   STATUS      current
   DESCRIPTION
      ""
   INDEX      { pr1646v2VEthInPGlobalIx,
                pr1646v2VEthInPTableIx }
   ::= {pr1646v2VEthInPSSCTable 1}

Pr1646v2VEthInPEntry ::=
   SEQUENCE
      {
      pr1646v2VEthInPGlobalIx
         GlobalIndex,
      pr1646v2VEthInPTableIx
         TableIndex,
      pr1646v2VEthInPSysUpTime
         TimeTicks,
      pr1646v2VEthInPIfUpTime
         TimeTicks,
      pr1646v2VEthInPIfStatChanges
         Counter32,
      pr1646v2VEthInPIfInOctets
         Counter64,
      pr1646v2VEthInPIfInUCPkts
         Counter64,
      pr1646v2VEthInPIfInNUCPkts
         Counter64,
      pr1646v2VEthInPIfInBCPkts
         Counter64,
      pr1646v2VEthInPIfInMCPkts
         Counter64,
      pr1646v2VEthInPIfInDiscards
         Counter64,
      pr1646v2VEthInPIfInErrors
         Counter64,
      pr1646v2VEthInPIfInUnkwn
         Counter64,
      pr1646v2VEthInPInDropEx
         Counter64,
      pr1646v2VEthInPInDropNoMac
         Counter64,
      pr1646v2VEthInPInDropNUCast
         Counter64,
      pr1646v2VEthInPInDropFilter
         Counter64,
      pr1646v2VEthInPIfInBandwidth
         Integer32,
      pr1646v2VEthInPIfOutOctets
         Counter64,
      pr1646v2VEthInPIfOutUCPkts
         Counter64,
      pr1646v2VEthInPIfOutNUCPkts
         Counter64,
      pr1646v2VEthInPIfOutBCPkts
         Counter64,
      pr1646v2VEthInPIfOutMCPkts
         Counter64,
      pr1646v2VEthInPIfOutDiscards
         Counter64,
      pr1646v2VEthInPIfOutErrors
         Counter64,
      pr1646v2VEthInPOutDropEx
         Counter64,
      pr1646v2VEthInPOutDropNoArp
         Counter64,
      pr1646v2VEthInPOutDropFilter
         Counter64,
      pr1646v2VEthInPIfOutBandwidth
         Integer32,
      pr1646v2VEthInPIfErrSec
         Counter32
      }

pr1646v2VEthInPGlobalIx OBJECT-TYPE
   SYNTAX      GlobalIndex
   MAX-ACCESS  not-accessible
   STATUS      current
   DESCRIPTION
      "The value of the tlsCntTreeGlobalIndex of the MANAGED OBJECT."
   ::= {pr1646v2VEthInPEntry 10}

pr1646v2VEthInPTableIx OBJECT-TYPE
   SYNTAX      TableIndex
   MAX-ACCESS  not-accessible
   STATUS      current
   DESCRIPTION
      ""
   ::= {pr1646v2VEthInPEntry 11}

pr1646v2VEthInPSysUpTime OBJECT-TYPE
   SYNTAX      TimeTicks
   MAX-ACCESS  read-only
   STATUS      current
   DESCRIPTION
      "Path: virtualEthernet.performance.h2Performance.sysUpTime

       Time in centi-second."
   ::= {pr1646v2VEthInPEntry 16777216}

pr1646v2VEthInPIfUpTime OBJECT-TYPE
   SYNTAX      TimeTicks
   MAX-ACCESS  read-only
   STATUS      current
   DESCRIPTION
      "Path: virtualEthernet.performance.h2Performance.ifUpTime

       Time in centi-second."
   ::= {pr1646v2VEthInPEntry 33554432}

pr1646v2VEthInPIfStatChanges OBJECT-TYPE
   SYNTAX      Counter32
   MAX-ACCESS  read-only
   STATUS      current
   DESCRIPTION
      "Path: virtualEthernet.performance.h2Performance.ifStatusChanges

       32 bit unsigned wrappable counter."
   ::= {pr1646v2VEthInPEntry 50331648}

pr1646v2VEthInPIfInOctets OBJECT-TYPE
   SYNTAX      Counter64
   MAX-ACCESS  read-only
   STATUS      current
   DESCRIPTION
      "Path: virtualEthernet.performance.h2Performance.ifInOctets

       64 bit unsigned wrappable counter."
   ::= {pr1646v2VEthInPEntry 67108864}

pr1646v2VEthInPIfInUCPkts OBJECT-TYPE
   SYNTAX      Counter64
   MAX-ACCESS  read-only
   STATUS      current
   DESCRIPTION
      "Path: virtualEthernet.performance.h2Performance.ifInUcastPkts

       64 bit unsigned wrappable counter."
   ::= {pr1646v2VEthInPEntry 83886080}

pr1646v2VEthInPIfInNUCPkts OBJECT-TYPE
   SYNTAX      Counter64
   MAX-ACCESS  read-only
   STATUS      current
   DESCRIPTION
      "Path: virtualEthernet.performance.h2Performance.ifInNUcastPkts

       64 bit unsigned wrappable counter."
   ::= {pr1646v2VEthInPEntry 100663296}

pr1646v2VEthInPIfInBCPkts OBJECT-TYPE
   SYNTAX      Counter64
   MAX-ACCESS  read-only
   STATUS      current
   DESCRIPTION
      "Path: virtualEthernet.performance.h2Performance.ifInBcastPkts

       64 bit unsigned wrappable counter."
   ::= {pr1646v2VEthInPEntry 419430400}

pr1646v2VEthInPIfInMCPkts OBJECT-TYPE
   SYNTAX      Counter64
   MAX-ACCESS  read-only
   STATUS      current
   DESCRIPTION
      "Path: virtualEthernet.performance.h2Performance.ifInMcastPkts

       64 bit unsigned wrappable counter."
   ::= {pr1646v2VEthInPEntry 436207616}

pr1646v2VEthInPIfInDiscards OBJECT-TYPE
   SYNTAX      Counter64
   MAX-ACCESS  read-only
   STATUS      current
   DESCRIPTION
      "Path: virtualEthernet.performance.h2Performance.ifInDiscards

       64 bit unsigned wrappable counter."
   ::= {pr1646v2VEthInPEntry 117440512}

pr1646v2VEthInPIfInErrors OBJECT-TYPE
   SYNTAX      Counter64
   MAX-ACCESS  read-only
   STATUS      current
   DESCRIPTION
      "Path: virtualEthernet.performance.h2Performance.ifInErrors

       64 bit unsigned wrappable counter."
   ::= {pr1646v2VEthInPEntry 134217728}

pr1646v2VEthInPIfInUnkwn OBJECT-TYPE
   SYNTAX      Counter64
   MAX-ACCESS  read-only
   STATUS      current
   DESCRIPTION
      "Path: virtualEthernet.performance.h2Performance.ifInUnknownProtos

       64 bit unsigned wrappable counter."
   ::= {pr1646v2VEthInPEntry 150994944}

pr1646v2VEthInPInDropEx OBJECT-TYPE
   SYNTAX      Counter64
   MAX-ACCESS  read-only
   STATUS      current
   DESCRIPTION
      "Path: virtualEthernet.performance.h2Performance.ifInDropLevelExceeded

       64 bit unsigned wrappable counter."
   ::= {pr1646v2VEthInPEntry 335544320}

pr1646v2VEthInPInDropNoMac OBJECT-TYPE
   SYNTAX      Counter64
   MAX-ACCESS  read-only
   STATUS      current
   DESCRIPTION
      "Path: virtualEthernet.performance.h2Performance.fInDiscardsNoMacFit

       64 bit unsigned wrappable counter."
   ::= {pr1646v2VEthInPEntry 301989888}

pr1646v2VEthInPInDropNUCast OBJECT-TYPE
   SYNTAX      Counter64
   MAX-ACCESS  read-only
   STATUS      current
   DESCRIPTION
      "Path: virtualEthernet.performance.h2Performance.fInDiscardsNUCast

       64 bit unsigned wrappable counter."
   ::= {pr1646v2VEthInPEntry 318767104}

pr1646v2VEthInPInDropFilter OBJECT-TYPE
   SYNTAX      Counter64
   MAX-ACCESS  read-only
   STATUS      current
   DESCRIPTION
      "Path: virtualEthernet.performance.h2Performance.fInDiscardsFilter

       64 bit unsigned wrappable counter."
   ::= {pr1646v2VEthInPEntry 385875968}

pr1646v2VEthInPIfInBandwidth OBJECT-TYPE
   SYNTAX      Integer32
   MAX-ACCESS  read-only
   STATUS      current
   DESCRIPTION
      "Path: virtualEthernet.performance.h2Performance.ifInBandwidth

       unit name = bps
       formula = 8 * ; 8 /"
   ::= {pr1646v2VEthInPEntry 268435456}

pr1646v2VEthInPIfOutOctets OBJECT-TYPE
   SYNTAX      Counter64
   MAX-ACCESS  read-only
   STATUS      current
   DESCRIPTION
      "Path: virtualEthernet.performance.h2Performance.ifOutOctets

       64 bit unsigned wrappable counter."
   ::= {pr1646v2VEthInPEntry 167772160}

pr1646v2VEthInPIfOutUCPkts OBJECT-TYPE
   SYNTAX      Counter64
   MAX-ACCESS  read-only
   STATUS      current
   DESCRIPTION
      "Path: virtualEthernet.performance.h2Performance.ifOutUcastPkts

       64 bit unsigned wrappable counter."
   ::= {pr1646v2VEthInPEntry 184549376}

pr1646v2VEthInPIfOutNUCPkts OBJECT-TYPE
   SYNTAX      Counter64
   MAX-ACCESS  read-only
   STATUS      current
   DESCRIPTION
      "Path: virtualEthernet.performance.h2Performance.ifOutNUcastPkts

       64 bit unsigned wrappable counter."
   ::= {pr1646v2VEthInPEntry 201326592}

pr1646v2VEthInPIfOutBCPkts OBJECT-TYPE
   SYNTAX      Counter64
   MAX-ACCESS  read-only
   STATUS      current
   DESCRIPTION
      "Path: virtualEthernet.performance.h2Performance.ifOutBcastPkts

       64 bit unsigned wrappable counter."
   ::= {pr1646v2VEthInPEntry 452984832}

pr1646v2VEthInPIfOutMCPkts OBJECT-TYPE
   SYNTAX      Counter64
   MAX-ACCESS  read-only
   STATUS      current
   DESCRIPTION
      "Path: virtualEthernet.performance.h2Performance.ifOutMcastPkts

       64 bit unsigned wrappable counter."
   ::= {pr1646v2VEthInPEntry 469762048}

pr1646v2VEthInPIfOutDiscards OBJECT-TYPE
   SYNTAX      Counter64
   MAX-ACCESS  read-only
   STATUS      current
   DESCRIPTION
      "Path: virtualEthernet.performance.h2Performance.ifOutDiscards

       64 bit unsigned wrappable counter."
   ::= {pr1646v2VEthInPEntry 218103808}

pr1646v2VEthInPIfOutErrors OBJECT-TYPE
   SYNTAX      Counter64
   MAX-ACCESS  read-only
   STATUS      current
   DESCRIPTION
      "Path: virtualEthernet.performance.h2Performance.ifOutErrors

       64 bit unsigned wrappable counter."
   ::= {pr1646v2VEthInPEntry 234881024}

pr1646v2VEthInPOutDropEx OBJECT-TYPE
   SYNTAX      Counter64
   MAX-ACCESS  read-only
   STATUS      current
   DESCRIPTION
      "Path: virtualEthernet.performance.h2Performance.ifOutDropLevelExceeded

       64 bit unsigned wrappable counter."
   ::= {pr1646v2VEthInPEntry 352321536}

pr1646v2VEthInPOutDropNoArp OBJECT-TYPE
   SYNTAX      Counter64
   MAX-ACCESS  read-only
   STATUS      current
   DESCRIPTION
      "Path: virtualEthernet.performance.h2Performance.ifOutDiscardsNoArp

       64 bit unsigned wrappable counter."
   ::= {pr1646v2VEthInPEntry 369098752}

pr1646v2VEthInPOutDropFilter OBJECT-TYPE
   SYNTAX      Counter64
   MAX-ACCESS  read-only
   STATUS      current
   DESCRIPTION
      "Path: virtualEthernet.performance.h2Performance.ifOutDiscardsFilter

       64 bit unsigned wrappable counter."
   ::= {pr1646v2VEthInPEntry 402653184}

pr1646v2VEthInPIfOutBandwidth OBJECT-TYPE
   SYNTAX      Integer32
   MAX-ACCESS  read-only
   STATUS      current
   DESCRIPTION
      "Path: virtualEthernet.performance.h2Performance.ifOutBandwidth

       unit name = bps
       formula = 8 * ; 8 /"
   ::= {pr1646v2VEthInPEntry 285212672}

pr1646v2VEthInPIfErrSec OBJECT-TYPE
   SYNTAX      Counter32
   MAX-ACCESS  read-only
   STATUS      current
   DESCRIPTION
      "Path: virtualEthernet.performance.h2Performance.ifErrSec

       32 bit unsigned wrappable counter."
   ::= {pr1646v2VEthInPEntry 251658240}


pr1646v2VEthH24InP OBJECT IDENTIFIER ::= {pr1646v2VEth 308}

pr1646v2VEthH24InPSSCTable OBJECT-TYPE
   SYNTAX      SEQUENCE OF Pr1646v2VEthH24InPEntry
   MAX-ACCESS  not-accessible
   STATUS      current
   DESCRIPTION
      "h24IfInPerformance"
   ::= {pr1646v2VEthH24InP 1}

pr1646v2VEthH24InPEntry OBJECT-TYPE
   SYNTAX      Pr1646v2VEthH24InPEntry
   MAX-ACCESS  not-accessible
   STATUS      current
   DESCRIPTION
      ""
   INDEX      { pr1646v2VEthH24InPGlobalIx,
                pr1646v2VEthH24InPTableIx }
   ::= {pr1646v2VEthH24InPSSCTable 1}

Pr1646v2VEthH24InPEntry ::=
   SEQUENCE
      {
      pr1646v2VEthH24InPGlobalIx
         GlobalIndex,
      pr1646v2VEthH24InPTableIx
         TableIndex,
      pr1646v2VEthH24InPSysUpTime
         TimeTicks,
      pr1646v2VEthH24InPIfUpTime
         TimeTicks,
      pr1646v2VEthH24InPIfStatChanges
         Counter32,
      pr1646v2VEthH24InPIfInOctets
         Counter64,
      pr1646v2VEthH24InPIfInUCPkts
         Counter64,
      pr1646v2VEthH24InPIfInNUCPkts
         Counter64,
      pr1646v2VEthH24InPIfInBCPkts
         Counter64,
      pr1646v2VEthH24InPIfInMCPkts
         Counter64,
      pr1646v2VEthH24InPIfInDiscards
         Counter64,
      pr1646v2VEthH24InPIfInErrors
         Counter64,
      pr1646v2VEthH24InPIfInUnkwn
         Counter64,
      pr1646v2VEthH24InPInDropEx
         Counter64,
      pr1646v2VEthH24InPInDropNoMac
         Counter64,
      pr1646v2VEthH24InPInDropNUCast
         Counter64,
      pr1646v2VEthH24InPInDropFilter
         Counter64,
      pr1646v2VEthH24InPIfInBandwidth
         Integer32,
      pr1646v2VEthH24InPIfOutOctets
         Counter64,
      pr1646v2VEthH24InPIfOutUCPkts
         Counter64,
      pr1646v2VEthH24InPIfOutNUCPkts
         Counter64,
      pr1646v2VEthH24InPIfOutBCPkts
         Counter64,
      pr1646v2VEthH24InPIfOutMCPkts
         Counter64,
      pr1646v2VEthH24InPIfOutDiscards
         Counter64,
      pr1646v2VEthH24InPIfOutErrors
         Counter64,
      pr1646v2VEthH24InPOutDropEx
         Counter64,
      pr1646v2VEthH24InPOutDropNoArp
         Counter64,
      pr1646v2VEthH24InPOutDropFilter
         Counter64,
      pr1646v2VEthH24InPIfOutBandwidth
         Integer32,
      pr1646v2VEthH24InPIfErrSec
         Counter32
      }

pr1646v2VEthH24InPGlobalIx OBJECT-TYPE
   SYNTAX      GlobalIndex
   MAX-ACCESS  not-accessible
   STATUS      current
   DESCRIPTION
      "The value of the tlsCntTreeGlobalIndex of the MANAGED OBJECT."
   ::= {pr1646v2VEthH24InPEntry 10}

pr1646v2VEthH24InPTableIx OBJECT-TYPE
   SYNTAX      TableIndex
   MAX-ACCESS  not-accessible
   STATUS      current
   DESCRIPTION
      ""
   ::= {pr1646v2VEthH24InPEntry 11}

pr1646v2VEthH24InPSysUpTime OBJECT-TYPE
   SYNTAX      TimeTicks
   MAX-ACCESS  read-only
   STATUS      current
   DESCRIPTION
      "Path: virtualEthernet.performance.h24Performance.sysUpTime

       Time in centi-second."
   ::= {pr1646v2VEthH24InPEntry 16777216}

pr1646v2VEthH24InPIfUpTime OBJECT-TYPE
   SYNTAX      TimeTicks
   MAX-ACCESS  read-only
   STATUS      current
   DESCRIPTION
      "Path: virtualEthernet.performance.h24Performance.ifUpTime

       Time in centi-second."
   ::= {pr1646v2VEthH24InPEntry 33554432}

pr1646v2VEthH24InPIfStatChanges OBJECT-TYPE
   SYNTAX      Counter32
   MAX-ACCESS  read-only
   STATUS      current
   DESCRIPTION
      "Path: virtualEthernet.performance.h24Performance.ifStatusChanges

       32 bit unsigned wrappable counter."
   ::= {pr1646v2VEthH24InPEntry 50331648}

pr1646v2VEthH24InPIfInOctets OBJECT-TYPE
   SYNTAX      Counter64
   MAX-ACCESS  read-only
   STATUS      current
   DESCRIPTION
      "Path: virtualEthernet.performance.h24Performance.ifInOctets

       64 bit unsigned wrappable counter."
   ::= {pr1646v2VEthH24InPEntry 67108864}

pr1646v2VEthH24InPIfInUCPkts OBJECT-TYPE
   SYNTAX      Counter64
   MAX-ACCESS  read-only
   STATUS      current
   DESCRIPTION
      "Path: virtualEthernet.performance.h24Performance.ifInUcastPkts

       64 bit unsigned wrappable counter."
   ::= {pr1646v2VEthH24InPEntry 83886080}

pr1646v2VEthH24InPIfInNUCPkts OBJECT-TYPE
   SYNTAX      Counter64
   MAX-ACCESS  read-only
   STATUS      current
   DESCRIPTION
      "Path: virtualEthernet.performance.h24Performance.ifInNUcastPkts

       64 bit unsigned wrappable counter."
   ::= {pr1646v2VEthH24InPEntry 100663296}

pr1646v2VEthH24InPIfInBCPkts OBJECT-TYPE
   SYNTAX      Counter64
   MAX-ACCESS  read-only
   STATUS      current
   DESCRIPTION
      "Path: virtualEthernet.performance.h24Performance.ifInBcastPkts

       64 bit unsigned wrappable counter."
   ::= {pr1646v2VEthH24InPEntry 419430400}

pr1646v2VEthH24InPIfInMCPkts OBJECT-TYPE
   SYNTAX      Counter64
   MAX-ACCESS  read-only
   STATUS      current
   DESCRIPTION
      "Path: virtualEthernet.performance.h24Performance.ifInMcastPkts

       64 bit unsigned wrappable counter."
   ::= {pr1646v2VEthH24InPEntry 436207616}

pr1646v2VEthH24InPIfInDiscards OBJECT-TYPE
   SYNTAX      Counter64
   MAX-ACCESS  read-only
   STATUS      current
   DESCRIPTION
      "Path: virtualEthernet.performance.h24Performance.ifInDiscards

       64 bit unsigned wrappable counter."
   ::= {pr1646v2VEthH24InPEntry 117440512}

pr1646v2VEthH24InPIfInErrors OBJECT-TYPE
   SYNTAX      Counter64
   MAX-ACCESS  read-only
   STATUS      current
   DESCRIPTION
      "Path: virtualEthernet.performance.h24Performance.ifInErrors

       64 bit unsigned wrappable counter."
   ::= {pr1646v2VEthH24InPEntry 134217728}

pr1646v2VEthH24InPIfInUnkwn OBJECT-TYPE
   SYNTAX      Counter64
   MAX-ACCESS  read-only
   STATUS      current
   DESCRIPTION
      "Path: virtualEthernet.performance.h24Performance.ifInUnknownProtos

       64 bit unsigned wrappable counter."
   ::= {pr1646v2VEthH24InPEntry 150994944}

pr1646v2VEthH24InPInDropEx OBJECT-TYPE
   SYNTAX      Counter64
   MAX-ACCESS  read-only
   STATUS      current
   DESCRIPTION
      "Path: virtualEthernet.performance.h24Performance.ifInDropLevelExceeded

       64 bit unsigned wrappable counter."
   ::= {pr1646v2VEthH24InPEntry 335544320}

pr1646v2VEthH24InPInDropNoMac OBJECT-TYPE
   SYNTAX      Counter64
   MAX-ACCESS  read-only
   STATUS      current
   DESCRIPTION
      "Path: virtualEthernet.performance.h24Performance.fInDiscardsNoMacFit

       64 bit unsigned wrappable counter."
   ::= {pr1646v2VEthH24InPEntry 301989888}

pr1646v2VEthH24InPInDropNUCast OBJECT-TYPE
   SYNTAX      Counter64
   MAX-ACCESS  read-only
   STATUS      current
   DESCRIPTION
      "Path: virtualEthernet.performance.h24Performance.fInDiscardsNUCast

       64 bit unsigned wrappable counter."
   ::= {pr1646v2VEthH24InPEntry 318767104}

pr1646v2VEthH24InPInDropFilter OBJECT-TYPE
   SYNTAX      Counter64
   MAX-ACCESS  read-only
   STATUS      current
   DESCRIPTION
      "Path: virtualEthernet.performance.h24Performance.fInDiscardsFilter

       64 bit unsigned wrappable counter."
   ::= {pr1646v2VEthH24InPEntry 385875968}

pr1646v2VEthH24InPIfInBandwidth OBJECT-TYPE
   SYNTAX      Integer32
   MAX-ACCESS  read-only
   STATUS      current
   DESCRIPTION
      "Path: virtualEthernet.performance.h24Performance.ifInBandwidth

       unit name = bps
       formula = 8 * ; 8 /"
   ::= {pr1646v2VEthH24InPEntry 268435456}

pr1646v2VEthH24InPIfOutOctets OBJECT-TYPE
   SYNTAX      Counter64
   MAX-ACCESS  read-only
   STATUS      current
   DESCRIPTION
      "Path: virtualEthernet.performance.h24Performance.ifOutOctets

       64 bit unsigned wrappable counter."
   ::= {pr1646v2VEthH24InPEntry 167772160}

pr1646v2VEthH24InPIfOutUCPkts OBJECT-TYPE
   SYNTAX      Counter64
   MAX-ACCESS  read-only
   STATUS      current
   DESCRIPTION
      "Path: virtualEthernet.performance.h24Performance.ifOutUcastPkts

       64 bit unsigned wrappable counter."
   ::= {pr1646v2VEthH24InPEntry 184549376}

pr1646v2VEthH24InPIfOutNUCPkts OBJECT-TYPE
   SYNTAX      Counter64
   MAX-ACCESS  read-only
   STATUS      current
   DESCRIPTION
      "Path: virtualEthernet.performance.h24Performance.ifOutNUcastPkts

       64 bit unsigned wrappable counter."
   ::= {pr1646v2VEthH24InPEntry 201326592}

pr1646v2VEthH24InPIfOutBCPkts OBJECT-TYPE
   SYNTAX      Counter64
   MAX-ACCESS  read-only
   STATUS      current
   DESCRIPTION
      "Path: virtualEthernet.performance.h24Performance.ifOutBcastPkts

       64 bit unsigned wrappable counter."
   ::= {pr1646v2VEthH24InPEntry 452984832}

pr1646v2VEthH24InPIfOutMCPkts OBJECT-TYPE
   SYNTAX      Counter64
   MAX-ACCESS  read-only
   STATUS      current
   DESCRIPTION
      "Path: virtualEthernet.performance.h24Performance.ifOutMcastPkts

       64 bit unsigned wrappable counter."
   ::= {pr1646v2VEthH24InPEntry 469762048}

pr1646v2VEthH24InPIfOutDiscards OBJECT-TYPE
   SYNTAX      Counter64
   MAX-ACCESS  read-only
   STATUS      current
   DESCRIPTION
      "Path: virtualEthernet.performance.h24Performance.ifOutDiscards

       64 bit unsigned wrappable counter."
   ::= {pr1646v2VEthH24InPEntry 218103808}

pr1646v2VEthH24InPIfOutErrors OBJECT-TYPE
   SYNTAX      Counter64
   MAX-ACCESS  read-only
   STATUS      current
   DESCRIPTION
      "Path: virtualEthernet.performance.h24Performance.ifOutErrors

       64 bit unsigned wrappable counter."
   ::= {pr1646v2VEthH24InPEntry 234881024}

pr1646v2VEthH24InPOutDropEx OBJECT-TYPE
   SYNTAX      Counter64
   MAX-ACCESS  read-only
   STATUS      current
   DESCRIPTION
      "Path: virtualEthernet.performance.h24Performance.ifOutDropLevelExceeded

       64 bit unsigned wrappable counter."
   ::= {pr1646v2VEthH24InPEntry 352321536}

pr1646v2VEthH24InPOutDropNoArp OBJECT-TYPE
   SYNTAX      Counter64
   MAX-ACCESS  read-only
   STATUS      current
   DESCRIPTION
      "Path: virtualEthernet.performance.h24Performance.ifOutDiscardsNoArp

       64 bit unsigned wrappable counter."
   ::= {pr1646v2VEthH24InPEntry 369098752}

pr1646v2VEthH24InPOutDropFilter OBJECT-TYPE
   SYNTAX      Counter64
   MAX-ACCESS  read-only
   STATUS      current
   DESCRIPTION
      "Path: virtualEthernet.performance.h24Performance.ifOutDiscardsFilter

       64 bit unsigned wrappable counter."
   ::= {pr1646v2VEthH24InPEntry 402653184}

pr1646v2VEthH24InPIfOutBandwidth OBJECT-TYPE
   SYNTAX      Integer32
   MAX-ACCESS  read-only
   STATUS      current
   DESCRIPTION
      "Path: virtualEthernet.performance.h24Performance.ifOutBandwidth

       unit name = bps
       formula = 8 * ; 8 /"
   ::= {pr1646v2VEthH24InPEntry 285212672}

pr1646v2VEthH24InPIfErrSec OBJECT-TYPE
   SYNTAX      Counter32
   MAX-ACCESS  read-only
   STATUS      current
   DESCRIPTION
      "Path: virtualEthernet.performance.h24Performance.ifErrSec

       32 bit unsigned wrappable counter."
   ::= {pr1646v2VEthH24InPEntry 251658240}


pr1646v2VEthD7InP OBJECT IDENTIFIER ::= {pr1646v2VEth 309}

pr1646v2VEthD7InPSSCTable OBJECT-TYPE
   SYNTAX      SEQUENCE OF Pr1646v2VEthD7InPEntry
   MAX-ACCESS  not-accessible
   STATUS      current
   DESCRIPTION
      "d7IfInPerformance"
   ::= {pr1646v2VEthD7InP 1}

pr1646v2VEthD7InPEntry OBJECT-TYPE
   SYNTAX      Pr1646v2VEthD7InPEntry
   MAX-ACCESS  not-accessible
   STATUS      current
   DESCRIPTION
      ""
   INDEX      { pr1646v2VEthD7InPGlobalIx,
                pr1646v2VEthD7InPTableIx }
   ::= {pr1646v2VEthD7InPSSCTable 1}

Pr1646v2VEthD7InPEntry ::=
   SEQUENCE
      {
      pr1646v2VEthD7InPGlobalIx
         GlobalIndex,
      pr1646v2VEthD7InPTableIx
         TableIndex,
      pr1646v2VEthD7InPSysUpTime
         TimeTicks,
      pr1646v2VEthD7InPIfUpTime
         TimeTicks,
      pr1646v2VEthD7InPIfStatChanges
         Counter32,
      pr1646v2VEthD7InPIfInOctets
         Counter64,
      pr1646v2VEthD7InPIfInUCPkts
         Counter64,
      pr1646v2VEthD7InPIfInNUCPkts
         Counter64,
      pr1646v2VEthD7InPIfInBCPkts
         Counter64,
      pr1646v2VEthD7InPIfInMCPkts
         Counter64,
      pr1646v2VEthD7InPIfInDiscards
         Counter64,
      pr1646v2VEthD7InPIfInErrors
         Counter64,
      pr1646v2VEthD7InPIfInUnkwn
         Counter64,
      pr1646v2VEthD7InPInDropEx
         Counter64,
      pr1646v2VEthD7InPInDropNoMac
         Counter64,
      pr1646v2VEthD7InPInDropNUCast
         Counter64,
      pr1646v2VEthD7InPInDropFilter
         Counter64,
      pr1646v2VEthD7InPIfInBandwidth
         Integer32,
      pr1646v2VEthD7InPIfOutOctets
         Counter64,
      pr1646v2VEthD7InPIfOutUCPkts
         Counter64,
      pr1646v2VEthD7InPIfOutNUCPkts
         Counter64,
      pr1646v2VEthD7InPIfOutBCPkts
         Counter64,
      pr1646v2VEthD7InPIfOutMCPkts
         Counter64,
      pr1646v2VEthD7InPIfOutDiscards
         Counter64,
      pr1646v2VEthD7InPIfOutErrors
         Counter64,
      pr1646v2VEthD7InPOutDropEx
         Counter64,
      pr1646v2VEthD7InPOutDropNoArp
         Counter64,
      pr1646v2VEthD7InPOutDropFilter
         Counter64,
      pr1646v2VEthD7InPIfOutBandwidth
         Integer32,
      pr1646v2VEthD7InPIfErrSec
         Counter32
      }

pr1646v2VEthD7InPGlobalIx OBJECT-TYPE
   SYNTAX      GlobalIndex
   MAX-ACCESS  not-accessible
   STATUS      current
   DESCRIPTION
      "The value of the tlsCntTreeGlobalIndex of the MANAGED OBJECT."
   ::= {pr1646v2VEthD7InPEntry 10}

pr1646v2VEthD7InPTableIx OBJECT-TYPE
   SYNTAX      TableIndex
   MAX-ACCESS  not-accessible
   STATUS      current
   DESCRIPTION
      ""
   ::= {pr1646v2VEthD7InPEntry 11}

pr1646v2VEthD7InPSysUpTime OBJECT-TYPE
   SYNTAX      TimeTicks
   MAX-ACCESS  read-only
   STATUS      current
   DESCRIPTION
      "Path: virtualEthernet.performance.d7Performance.sysUpTime

       Time in centi-second."
   ::= {pr1646v2VEthD7InPEntry 16777216}

pr1646v2VEthD7InPIfUpTime OBJECT-TYPE
   SYNTAX      TimeTicks
   MAX-ACCESS  read-only
   STATUS      current
   DESCRIPTION
      "Path: virtualEthernet.performance.d7Performance.ifUpTime

       Time in centi-second."
   ::= {pr1646v2VEthD7InPEntry 33554432}

pr1646v2VEthD7InPIfStatChanges OBJECT-TYPE
   SYNTAX      Counter32
   MAX-ACCESS  read-only
   STATUS      current
   DESCRIPTION
      "Path: virtualEthernet.performance.d7Performance.ifStatusChanges

       32 bit unsigned wrappable counter."
   ::= {pr1646v2VEthD7InPEntry 50331648}

pr1646v2VEthD7InPIfInOctets OBJECT-TYPE
   SYNTAX      Counter64
   MAX-ACCESS  read-only
   STATUS      current
   DESCRIPTION
      "Path: virtualEthernet.performance.d7Performance.ifInOctets

       64 bit unsigned wrappable counter."
   ::= {pr1646v2VEthD7InPEntry 67108864}

pr1646v2VEthD7InPIfInUCPkts OBJECT-TYPE
   SYNTAX      Counter64
   MAX-ACCESS  read-only
   STATUS      current
   DESCRIPTION
      "Path: virtualEthernet.performance.d7Performance.ifInUcastPkts

       64 bit unsigned wrappable counter."
   ::= {pr1646v2VEthD7InPEntry 83886080}

pr1646v2VEthD7InPIfInNUCPkts OBJECT-TYPE
   SYNTAX      Counter64
   MAX-ACCESS  read-only
   STATUS      current
   DESCRIPTION
      "Path: virtualEthernet.performance.d7Performance.ifInNUcastPkts

       64 bit unsigned wrappable counter."
   ::= {pr1646v2VEthD7InPEntry 100663296}

pr1646v2VEthD7InPIfInBCPkts OBJECT-TYPE
   SYNTAX      Counter64
   MAX-ACCESS  read-only
   STATUS      current
   DESCRIPTION
      "Path: virtualEthernet.performance.d7Performance.ifInBcastPkts

       64 bit unsigned wrappable counter."
   ::= {pr1646v2VEthD7InPEntry 419430400}

pr1646v2VEthD7InPIfInMCPkts OBJECT-TYPE
   SYNTAX      Counter64
   MAX-ACCESS  read-only
   STATUS      current
   DESCRIPTION
      "Path: virtualEthernet.performance.d7Performance.ifInMcastPkts

       64 bit unsigned wrappable counter."
   ::= {pr1646v2VEthD7InPEntry 436207616}

pr1646v2VEthD7InPIfInDiscards OBJECT-TYPE
   SYNTAX      Counter64
   MAX-ACCESS  read-only
   STATUS      current
   DESCRIPTION
      "Path: virtualEthernet.performance.d7Performance.ifInDiscards

       64 bit unsigned wrappable counter."
   ::= {pr1646v2VEthD7InPEntry 117440512}

pr1646v2VEthD7InPIfInErrors OBJECT-TYPE
   SYNTAX      Counter64
   MAX-ACCESS  read-only
   STATUS      current
   DESCRIPTION
      "Path: virtualEthernet.performance.d7Performance.ifInErrors

       64 bit unsigned wrappable counter."
   ::= {pr1646v2VEthD7InPEntry 134217728}

pr1646v2VEthD7InPIfInUnkwn OBJECT-TYPE
   SYNTAX      Counter64
   MAX-ACCESS  read-only
   STATUS      current
   DESCRIPTION
      "Path: virtualEthernet.performance.d7Performance.ifInUnknownProtos

       64 bit unsigned wrappable counter."
   ::= {pr1646v2VEthD7InPEntry 150994944}

pr1646v2VEthD7InPInDropEx OBJECT-TYPE
   SYNTAX      Counter64
   MAX-ACCESS  read-only
   STATUS      current
   DESCRIPTION
      "Path: virtualEthernet.performance.d7Performance.ifInDropLevelExceeded

       64 bit unsigned wrappable counter."
   ::= {pr1646v2VEthD7InPEntry 335544320}

pr1646v2VEthD7InPInDropNoMac OBJECT-TYPE
   SYNTAX      Counter64
   MAX-ACCESS  read-only
   STATUS      current
   DESCRIPTION
      "Path: virtualEthernet.performance.d7Performance.fInDiscardsNoMacFit

       64 bit unsigned wrappable counter."
   ::= {pr1646v2VEthD7InPEntry 301989888}

pr1646v2VEthD7InPInDropNUCast OBJECT-TYPE
   SYNTAX      Counter64
   MAX-ACCESS  read-only
   STATUS      current
   DESCRIPTION
      "Path: virtualEthernet.performance.d7Performance.fInDiscardsNUCast

       64 bit unsigned wrappable counter."
   ::= {pr1646v2VEthD7InPEntry 318767104}

pr1646v2VEthD7InPInDropFilter OBJECT-TYPE
   SYNTAX      Counter64
   MAX-ACCESS  read-only
   STATUS      current
   DESCRIPTION
      "Path: virtualEthernet.performance.d7Performance.fInDiscardsFilter

       64 bit unsigned wrappable counter."
   ::= {pr1646v2VEthD7InPEntry 385875968}

pr1646v2VEthD7InPIfInBandwidth OBJECT-TYPE
   SYNTAX      Integer32
   MAX-ACCESS  read-only
   STATUS      current
   DESCRIPTION
      "Path: virtualEthernet.performance.d7Performance.ifInBandwidth

       unit name = bps
       formula = 8 * ; 8 /"
   ::= {pr1646v2VEthD7InPEntry 268435456}

pr1646v2VEthD7InPIfOutOctets OBJECT-TYPE
   SYNTAX      Counter64
   MAX-ACCESS  read-only
   STATUS      current
   DESCRIPTION
      "Path: virtualEthernet.performance.d7Performance.ifOutOctets

       64 bit unsigned wrappable counter."
   ::= {pr1646v2VEthD7InPEntry 167772160}

pr1646v2VEthD7InPIfOutUCPkts OBJECT-TYPE
   SYNTAX      Counter64
   MAX-ACCESS  read-only
   STATUS      current
   DESCRIPTION
      "Path: virtualEthernet.performance.d7Performance.ifOutUcastPkts

       64 bit unsigned wrappable counter."
   ::= {pr1646v2VEthD7InPEntry 184549376}

pr1646v2VEthD7InPIfOutNUCPkts OBJECT-TYPE
   SYNTAX      Counter64
   MAX-ACCESS  read-only
   STATUS      current
   DESCRIPTION
      "Path: virtualEthernet.performance.d7Performance.ifOutNUcastPkts

       64 bit unsigned wrappable counter."
   ::= {pr1646v2VEthD7InPEntry 201326592}

pr1646v2VEthD7InPIfOutBCPkts OBJECT-TYPE
   SYNTAX      Counter64
   MAX-ACCESS  read-only
   STATUS      current
   DESCRIPTION
      "Path: virtualEthernet.performance.d7Performance.ifOutBcastPkts

       64 bit unsigned wrappable counter."
   ::= {pr1646v2VEthD7InPEntry 452984832}

pr1646v2VEthD7InPIfOutMCPkts OBJECT-TYPE
   SYNTAX      Counter64
   MAX-ACCESS  read-only
   STATUS      current
   DESCRIPTION
      "Path: virtualEthernet.performance.d7Performance.ifOutMcastPkts

       64 bit unsigned wrappable counter."
   ::= {pr1646v2VEthD7InPEntry 469762048}

pr1646v2VEthD7InPIfOutDiscards OBJECT-TYPE
   SYNTAX      Counter64
   MAX-ACCESS  read-only
   STATUS      current
   DESCRIPTION
      "Path: virtualEthernet.performance.d7Performance.ifOutDiscards

       64 bit unsigned wrappable counter."
   ::= {pr1646v2VEthD7InPEntry 218103808}

pr1646v2VEthD7InPIfOutErrors OBJECT-TYPE
   SYNTAX      Counter64
   MAX-ACCESS  read-only
   STATUS      current
   DESCRIPTION
      "Path: virtualEthernet.performance.d7Performance.ifOutErrors

       64 bit unsigned wrappable counter."
   ::= {pr1646v2VEthD7InPEntry 234881024}

pr1646v2VEthD7InPOutDropEx OBJECT-TYPE
   SYNTAX      Counter64
   MAX-ACCESS  read-only
   STATUS      current
   DESCRIPTION
      "Path: virtualEthernet.performance.d7Performance.ifOutDropLevelExceeded

       64 bit unsigned wrappable counter."
   ::= {pr1646v2VEthD7InPEntry 352321536}

pr1646v2VEthD7InPOutDropNoArp OBJECT-TYPE
   SYNTAX      Counter64
   MAX-ACCESS  read-only
   STATUS      current
   DESCRIPTION
      "Path: virtualEthernet.performance.d7Performance.ifOutDiscardsNoArp

       64 bit unsigned wrappable counter."
   ::= {pr1646v2VEthD7InPEntry 369098752}

pr1646v2VEthD7InPOutDropFilter OBJECT-TYPE
   SYNTAX      Counter64
   MAX-ACCESS  read-only
   STATUS      current
   DESCRIPTION
      "Path: virtualEthernet.performance.d7Performance.ifOutDiscardsFilter

       64 bit unsigned wrappable counter."
   ::= {pr1646v2VEthD7InPEntry 402653184}

pr1646v2VEthD7InPIfOutBandwidth OBJECT-TYPE
   SYNTAX      Integer32
   MAX-ACCESS  read-only
   STATUS      current
   DESCRIPTION
      "Path: virtualEthernet.performance.d7Performance.ifOutBandwidth

       unit name = bps
       formula = 8 * ; 8 /"
   ::= {pr1646v2VEthD7InPEntry 285212672}

pr1646v2VEthD7InPIfErrSec OBJECT-TYPE
   SYNTAX      Counter32
   MAX-ACCESS  read-only
   STATUS      current
   DESCRIPTION
      "Path: virtualEthernet.performance.d7Performance.ifErrSec

       32 bit unsigned wrappable counter."
   ::= {pr1646v2VEthD7InPEntry 251658240}


pr1646v2VEthOam OBJECT IDENTIFIER ::= {pr1646v2VEth 910}

pr1646v2VEthOamSSCTable OBJECT-TYPE
   SYNTAX      SEQUENCE OF Pr1646v2VEthOamEntry
   MAX-ACCESS  not-accessible
   STATUS      current
   DESCRIPTION
      "OAM statistics"
   ::= {pr1646v2VEthOam 1}

pr1646v2VEthOamEntry OBJECT-TYPE
   SYNTAX      Pr1646v2VEthOamEntry
   MAX-ACCESS  not-accessible
   STATUS      current
   DESCRIPTION
      ""
   INDEX      { pr1646v2VEthOamGlobalIx }
   ::= {pr1646v2VEthOamSSCTable 1}

Pr1646v2VEthOamEntry ::=
   SEQUENCE
      {
      pr1646v2VEthOamGlobalIx
         GlobalIndex,
      pr1646v2VEthOamInformationTx
         Counter32,
      pr1646v2VEthOamInformationRx
         Counter32,
      pr1646v2VEthOamUniqueEventNotifTx
         Counter32,
      pr1646v2VEthOamUniqueEventNotifRx
         Counter32,
      pr1646v2VEthOamLoopbackCtrlTx
         Counter32,
      pr1646v2VEthOamLoopbackCtrlRx
         Counter32,
      pr1646v2VEthOamVarReqTx
         Counter32,
      pr1646v2VEthOamVarReqRx
         Counter32,
      pr1646v2VEthOamVarRespTx
         Counter32,
      pr1646v2VEthOamVarRespRx
         Counter32,
      pr1646v2VEthOamOrgSpecificTx
         Counter32,
      pr1646v2VEthOamOrgSpecificRx
         Counter32,
      pr1646v2VEthOamUnsupportedCodesTx
         Counter32,
      pr1646v2VEthOamUnsupportedCodesRx
         Counter32,
      pr1646v2VEthOamPduDiscardRx
         Counter32,
      pr1646v2VEthOamDataDiscardTx
         Counter32,
      pr1646v2VEthOamDataDiscardRx
         Counter32
      }

pr1646v2VEthOamGlobalIx OBJECT-TYPE
   SYNTAX      GlobalIndex
   MAX-ACCESS  not-accessible
   STATUS      current
   DESCRIPTION
      "The value of the tlsCntTreeGlobalIndex of the MANAGED OBJECT."
   ::= {pr1646v2VEthOamEntry 10}

pr1646v2VEthOamInformationTx OBJECT-TYPE
   SYNTAX      Counter32
   MAX-ACCESS  read-only
   STATUS      current
   DESCRIPTION
      "Path: virtualEthernet.performance.oam.informationTx

       32 bit unsigned wrappable counter."
   ::= {pr1646v2VEthOamEntry 16777216}

pr1646v2VEthOamInformationRx OBJECT-TYPE
   SYNTAX      Counter32
   MAX-ACCESS  read-only
   STATUS      current
   DESCRIPTION
      "Path: virtualEthernet.performance.oam.informationRx

       32 bit unsigned wrappable counter."
   ::= {pr1646v2VEthOamEntry 33554432}

pr1646v2VEthOamUniqueEventNotifTx OBJECT-TYPE
   SYNTAX      Counter32
   MAX-ACCESS  read-only
   STATUS      current
   DESCRIPTION
      "Path: virtualEthernet.performance.oam.uniqueEventNotifTx

       32 bit unsigned wrappable counter."
   ::= {pr1646v2VEthOamEntry 50331648}

pr1646v2VEthOamUniqueEventNotifRx OBJECT-TYPE
   SYNTAX      Counter32
   MAX-ACCESS  read-only
   STATUS      current
   DESCRIPTION
      "Path: virtualEthernet.performance.oam.uniqueEventNotifRx

       32 bit unsigned wrappable counter."
   ::= {pr1646v2VEthOamEntry 67108864}

pr1646v2VEthOamLoopbackCtrlTx OBJECT-TYPE
   SYNTAX      Counter32
   MAX-ACCESS  read-only
   STATUS      current
   DESCRIPTION
      "Path: virtualEthernet.performance.oam.loopbackCtrlTx

       32 bit unsigned wrappable counter."
   ::= {pr1646v2VEthOamEntry 117440512}

pr1646v2VEthOamLoopbackCtrlRx OBJECT-TYPE
   SYNTAX      Counter32
   MAX-ACCESS  read-only
   STATUS      current
   DESCRIPTION
      "Path: virtualEthernet.performance.oam.loopbackCtrlRx

       32 bit unsigned wrappable counter."
   ::= {pr1646v2VEthOamEntry 134217728}

pr1646v2VEthOamVarReqTx OBJECT-TYPE
   SYNTAX      Counter32
   MAX-ACCESS  read-only
   STATUS      current
   DESCRIPTION
      "Path: virtualEthernet.performance.oam.varReqTx

       32 bit unsigned wrappable counter."
   ::= {pr1646v2VEthOamEntry 150994944}

pr1646v2VEthOamVarReqRx OBJECT-TYPE
   SYNTAX      Counter32
   MAX-ACCESS  read-only
   STATUS      current
   DESCRIPTION
      "Path: virtualEthernet.performance.oam.varReqRx

       32 bit unsigned wrappable counter."
   ::= {pr1646v2VEthOamEntry 167772160}

pr1646v2VEthOamVarRespTx OBJECT-TYPE
   SYNTAX      Counter32
   MAX-ACCESS  read-only
   STATUS      current
   DESCRIPTION
      "Path: virtualEthernet.performance.oam.varRespTx

       32 bit unsigned wrappable counter."
   ::= {pr1646v2VEthOamEntry 184549376}

pr1646v2VEthOamVarRespRx OBJECT-TYPE
   SYNTAX      Counter32
   MAX-ACCESS  read-only
   STATUS      current
   DESCRIPTION
      "Path: virtualEthernet.performance.oam.varRespRx

       32 bit unsigned wrappable counter."
   ::= {pr1646v2VEthOamEntry 201326592}

pr1646v2VEthOamOrgSpecificTx OBJECT-TYPE
   SYNTAX      Counter32
   MAX-ACCESS  read-only
   STATUS      current
   DESCRIPTION
      "Path: virtualEthernet.performance.oam.orgSpecificTx

       32 bit unsigned wrappable counter."
   ::= {pr1646v2VEthOamEntry 218103808}

pr1646v2VEthOamOrgSpecificRx OBJECT-TYPE
   SYNTAX      Counter32
   MAX-ACCESS  read-only
   STATUS      current
   DESCRIPTION
      "Path: virtualEthernet.performance.oam.orgSpecificRx

       32 bit unsigned wrappable counter."
   ::= {pr1646v2VEthOamEntry 234881024}

pr1646v2VEthOamUnsupportedCodesTx OBJECT-TYPE
   SYNTAX      Counter32
   MAX-ACCESS  read-only
   STATUS      current
   DESCRIPTION
      "Path: virtualEthernet.performance.oam.unsupportedCodesTx

       32 bit unsigned wrappable counter."
   ::= {pr1646v2VEthOamEntry 251658240}

pr1646v2VEthOamUnsupportedCodesRx OBJECT-TYPE
   SYNTAX      Counter32
   MAX-ACCESS  read-only
   STATUS      current
   DESCRIPTION
      "Path: virtualEthernet.performance.oam.unsupportedCodesRx

       32 bit unsigned wrappable counter."
   ::= {pr1646v2VEthOamEntry 268435456}

pr1646v2VEthOamPduDiscardRx OBJECT-TYPE
   SYNTAX      Counter32
   MAX-ACCESS  read-only
   STATUS      current
   DESCRIPTION
      "Path: virtualEthernet.performance.oam.pduDiscardRx

       32 bit unsigned wrappable counter."
   ::= {pr1646v2VEthOamEntry 1694498816}

pr1646v2VEthOamDataDiscardTx OBJECT-TYPE
   SYNTAX      Counter32
   MAX-ACCESS  read-only
   STATUS      current
   DESCRIPTION
      "Path: virtualEthernet.performance.oam.dataDiscardTx

       32 bit unsigned wrappable counter."
   ::= {pr1646v2VEthOamEntry 1711276032}

pr1646v2VEthOamDataDiscardRx OBJECT-TYPE
   SYNTAX      Counter32
   MAX-ACCESS  read-only
   STATUS      current
   DESCRIPTION
      "Path: virtualEthernet.performance.oam.dataDiscardRx

       32 bit unsigned wrappable counter."
   ::= {pr1646v2VEthOamEntry 1728053248}


pr1646v2VEthVlan OBJECT IDENTIFIER ::= {pr1646v2VEth 310}

pr1646v2VEthVlanSSCTable OBJECT-TYPE
   SYNTAX      SEQUENCE OF Pr1646v2VEthVlanEntry
   MAX-ACCESS  not-accessible
   STATUS      current
   DESCRIPTION
      ""
   ::= {pr1646v2VEthVlan 1}

pr1646v2VEthVlanEntry OBJECT-TYPE
   SYNTAX      Pr1646v2VEthVlanEntry
   MAX-ACCESS  not-accessible
   STATUS      current
   DESCRIPTION
      ""
   INDEX      { pr1646v2VEthVlanGlobalIx,
                pr1646v2VEthVlanTableIx }
   ::= {pr1646v2VEthVlanSSCTable 1}

Pr1646v2VEthVlanEntry ::=
   SEQUENCE
      {
      pr1646v2VEthVlanGlobalIx
         GlobalIndex,
      pr1646v2VEthVlanTableIx
         TableIndex,
      pr1646v2VEthVlanName
         DisplayString,
      pr1646v2VEthVlanMCInOctets
         Counter64,
      pr1646v2VEthVlanMCInUcast
         Counter64,
      pr1646v2VEthVlanMCInNUcastPkts
         Counter64,
      pr1646v2VEthVlanMCInBcastPkts
         Counter64,
      pr1646v2VEthVlanMCInMcastPkts
         Counter64,
      pr1646v2VEthVlanMCInDiscards
         Counter64,
      pr1646v2VEthVlanMCInErrors
         Counter64,
      pr1646v2VEthVlanMCInUnknownProtos
         Counter64,
      pr1646v2VEthVlanMCInDropEx
         Counter64,
      pr1646v2VEthVlanMCInDropNoMac
         Counter64,
      pr1646v2VEthVlanMCInDropNUCast
         Counter64,
      pr1646v2VEthVlanMCInDropFilter
         Counter64,
      pr1646v2VEthVlanMCInBandwidth15sec
         Integer32,
      pr1646v2VEthVlanMCInBandwidth30sec
         Integer32,
      pr1646v2VEthVlanMCInBandwidth1min
         Integer32,
      pr1646v2VEthVlanMCInBandwidth2min
         Integer32,
      pr1646v2VEthVlanMCInBandwidth5min
         Integer32,
      pr1646v2VEthVlanMCOutOctets
         Counter64,
      pr1646v2VEthVlanMCOutUcastPkts
         Counter64,
      pr1646v2VEthVlanMCOutNUcastPkts
         Counter64,
      pr1646v2VEthVlanMCOutBcastPkts
         Counter64,
      pr1646v2VEthVlanMCOutMcastPkts
         Counter64,
      pr1646v2VEthVlanMCOutDiscards
         Counter64,
      pr1646v2VEthVlanMCOutErrors
         Counter64,
      pr1646v2VEthVlanMCOutQLen
         Counter32,
      pr1646v2VEthVlanMCOutDropEx
         Counter64,
      pr1646v2VEthVlanMCOutDropNoArp
         Counter64,
      pr1646v2VEthVlanMCOutDropFilter
         Counter64,
      pr1646v2VEthVlanMCOutBandwidth15sec
         Integer32,
      pr1646v2VEthVlanMCOutBandwidth30sec
         Integer32,
      pr1646v2VEthVlanMCOutBandwidth1min
         Integer32,
      pr1646v2VEthVlanMCOutBandwidth2min
         Integer32,
      pr1646v2VEthVlanMCOutBandwidth5min
         Integer32,
      pr1646v2VEthVlanVlanVid
         Integer32,
      pr1646v2VEthVlanPppLinkMonitoringRequestsSent
         Gauge32,
      pr1646v2VEthVlanPppLinkMonitoringRepliesRcvd
         Gauge32,
      pr1646v2VEthVlanPppLinkMonitoringRequestsRcvd
         Gauge32,
      pr1646v2VEthVlanPppLinkMonitoringRepliesSent
         Gauge32
      }

pr1646v2VEthVlanGlobalIx OBJECT-TYPE
   SYNTAX      GlobalIndex
   MAX-ACCESS  not-accessible
   STATUS      current
   DESCRIPTION
      "The value of the tlsCntTreeGlobalIndex of the MANAGED OBJECT."
   ::= {pr1646v2VEthVlanEntry 10}

pr1646v2VEthVlanTableIx OBJECT-TYPE
   SYNTAX      TableIndex
   MAX-ACCESS  not-accessible
   STATUS      current
   DESCRIPTION
      ""
   ::= {pr1646v2VEthVlanEntry 11}

pr1646v2VEthVlanName OBJECT-TYPE
   SYNTAX      DisplayString
   MAX-ACCESS  read-only
   STATUS      current
   DESCRIPTION
      "Path: virtualEthernet.performance.vlan.name"
   ::= {pr1646v2VEthVlanEntry 16777216}

pr1646v2VEthVlanMCInOctets OBJECT-TYPE
   SYNTAX      Counter64
   MAX-ACCESS  read-only
   STATUS      current
   DESCRIPTION
      "Path: virtualEthernet.performance.vlan.mibCounters.ifInOctets

       64 bit unsigned wrappable counter."
   ::= {pr1646v2VEthVlanEntry 40697856}

pr1646v2VEthVlanMCInUcast OBJECT-TYPE
   SYNTAX      Counter64
   MAX-ACCESS  read-only
   STATUS      current
   DESCRIPTION
      "Path: virtualEthernet.performance.vlan.mibCounters.ifInUcastPkts

       64 bit unsigned wrappable counter."
   ::= {pr1646v2VEthVlanEntry 40763392}

pr1646v2VEthVlanMCInNUcastPkts OBJECT-TYPE
   SYNTAX      Counter64
   MAX-ACCESS  read-only
   STATUS      current
   DESCRIPTION
      "Path: virtualEthernet.performance.vlan.mibCounters.ifInNUcastPkts

       64 bit unsigned wrappable counter."
   ::= {pr1646v2VEthVlanEntry 40828928}

pr1646v2VEthVlanMCInBcastPkts OBJECT-TYPE
   SYNTAX      Counter64
   MAX-ACCESS  read-only
   STATUS      current
   DESCRIPTION
      "Path: virtualEthernet.performance.vlan.mibCounters.ifInBcastPkts

       64 bit unsigned wrappable counter."
   ::= {pr1646v2VEthVlanEntry 47382528}

pr1646v2VEthVlanMCInMcastPkts OBJECT-TYPE
   SYNTAX      Counter64
   MAX-ACCESS  read-only
   STATUS      current
   DESCRIPTION
      "Path: virtualEthernet.performance.vlan.mibCounters.ifInMcastPkts

       64 bit unsigned wrappable counter."
   ::= {pr1646v2VEthVlanEntry 48037888}

pr1646v2VEthVlanMCInDiscards OBJECT-TYPE
   SYNTAX      Counter64
   MAX-ACCESS  read-only
   STATUS      current
   DESCRIPTION
      "Path: virtualEthernet.performance.vlan.mibCounters.ifInDiscards

       64 bit unsigned wrappable counter."
   ::= {pr1646v2VEthVlanEntry 40894464}

pr1646v2VEthVlanMCInErrors OBJECT-TYPE
   SYNTAX      Counter64
   MAX-ACCESS  read-only
   STATUS      current
   DESCRIPTION
      "Path: virtualEthernet.performance.vlan.mibCounters.ifInErrors

       64 bit unsigned wrappable counter."
   ::= {pr1646v2VEthVlanEntry 40960000}

pr1646v2VEthVlanMCInUnknownProtos OBJECT-TYPE
   SYNTAX      Counter64
   MAX-ACCESS  read-only
   STATUS      current
   DESCRIPTION
      "Path: virtualEthernet.performance.vlan.mibCounters.ifInUnknownProtos

       64 bit unsigned wrappable counter."
   ::= {pr1646v2VEthVlanEntry 41025536}

pr1646v2VEthVlanMCInDropEx OBJECT-TYPE
   SYNTAX      Counter64
   MAX-ACCESS  read-only
   STATUS      current
   DESCRIPTION
      "Path: virtualEthernet.performance.vlan.mibCounters.ifInDropLevelExceeded

       64 bit unsigned wrappable counter."
   ::= {pr1646v2VEthVlanEntry 42074112}

pr1646v2VEthVlanMCInDropNoMac OBJECT-TYPE
   SYNTAX      Counter64
   MAX-ACCESS  read-only
   STATUS      current
   DESCRIPTION
      "Path: virtualEthernet.performance.vlan.mibCounters.ifInDiscardsNoMacFit

       64 bit unsigned wrappable counter."
   ::= {pr1646v2VEthVlanEntry 42270720}

pr1646v2VEthVlanMCInDropNUCast OBJECT-TYPE
   SYNTAX      Counter64
   MAX-ACCESS  read-only
   STATUS      current
   DESCRIPTION
      "Path: virtualEthernet.performance.vlan.mibCounters.ifInDiscardsNUCast

       64 bit unsigned wrappable counter."
   ::= {pr1646v2VEthVlanEntry 42467328}

pr1646v2VEthVlanMCInDropFilter OBJECT-TYPE
   SYNTAX      Counter64
   MAX-ACCESS  read-only
   STATUS      current
   DESCRIPTION
      "Path: virtualEthernet.performance.vlan.mibCounters.ifInDiscardsFilter

       64 bit unsigned wrappable counter."
   ::= {pr1646v2VEthVlanEntry 42532864}

pr1646v2VEthVlanMCInBandwidth15sec OBJECT-TYPE
   SYNTAX      Integer32
   MAX-ACCESS  read-only
   STATUS      current
   DESCRIPTION
      "Path: virtualEthernet.performance.vlan.mibCounters.ifInBandwidth.15sec

       unit name = bps
       formula = 8 * ; 8 /"
   ::= {pr1646v2VEthVlanEntry 45417728}

pr1646v2VEthVlanMCInBandwidth30sec OBJECT-TYPE
   SYNTAX      Integer32
   MAX-ACCESS  read-only
   STATUS      current
   DESCRIPTION
      "Path: virtualEthernet.performance.vlan.mibCounters.ifInBandwidth.30sec

       unit name = bps
       formula = 8 * ; 8 /"
   ::= {pr1646v2VEthVlanEntry 45419008}

pr1646v2VEthVlanMCInBandwidth1min OBJECT-TYPE
   SYNTAX      Integer32
   MAX-ACCESS  read-only
   STATUS      current
   DESCRIPTION
      "Path: virtualEthernet.performance.vlan.mibCounters.ifInBandwidth.1min

       unit name = bps
       formula = 8 * ; 8 /"
   ::= {pr1646v2VEthVlanEntry 45421568}

pr1646v2VEthVlanMCInBandwidth2min OBJECT-TYPE
   SYNTAX      Integer32
   MAX-ACCESS  read-only
   STATUS      current
   DESCRIPTION
      "Path: virtualEthernet.performance.vlan.mibCounters.ifInBandwidth.2min

       unit name = bps
       formula = 8 * ; 8 /"
   ::= {pr1646v2VEthVlanEntry 45426688}

pr1646v2VEthVlanMCInBandwidth5min OBJECT-TYPE
   SYNTAX      Integer32
   MAX-ACCESS  read-only
   STATUS      current
   DESCRIPTION
      "Path: virtualEthernet.performance.vlan.mibCounters.ifInBandwidth.5min

       unit name = bps
       formula = 8 * ; 8 /"
   ::= {pr1646v2VEthVlanEntry 45442048}

pr1646v2VEthVlanMCOutOctets OBJECT-TYPE
   SYNTAX      Counter64
   MAX-ACCESS  read-only
   STATUS      current
   DESCRIPTION
      "Path: virtualEthernet.performance.vlan.mibCounters.ifOutOctets

       64 bit unsigned wrappable counter."
   ::= {pr1646v2VEthVlanEntry 41091072}

pr1646v2VEthVlanMCOutUcastPkts OBJECT-TYPE
   SYNTAX      Counter64
   MAX-ACCESS  read-only
   STATUS      current
   DESCRIPTION
      "Path: virtualEthernet.performance.vlan.mibCounters.ifOutUcastPkts

       64 bit unsigned wrappable counter."
   ::= {pr1646v2VEthVlanEntry 41156608}

pr1646v2VEthVlanMCOutNUcastPkts OBJECT-TYPE
   SYNTAX      Counter64
   MAX-ACCESS  read-only
   STATUS      current
   DESCRIPTION
      "Path: virtualEthernet.performance.vlan.mibCounters.ifOutNUcastPkts

       64 bit unsigned wrappable counter."
   ::= {pr1646v2VEthVlanEntry 41222144}

pr1646v2VEthVlanMCOutBcastPkts OBJECT-TYPE
   SYNTAX      Counter64
   MAX-ACCESS  read-only
   STATUS      current
   DESCRIPTION
      "Path: virtualEthernet.performance.vlan.mibCounters.ifOutBcastPkts

       64 bit unsigned wrappable counter."
   ::= {pr1646v2VEthVlanEntry 47775744}

pr1646v2VEthVlanMCOutMcastPkts OBJECT-TYPE
   SYNTAX      Counter64
   MAX-ACCESS  read-only
   STATUS      current
   DESCRIPTION
      "Path: virtualEthernet.performance.vlan.mibCounters.ifOutMcastPkts

       64 bit unsigned wrappable counter."
   ::= {pr1646v2VEthVlanEntry 48431104}

pr1646v2VEthVlanMCOutDiscards OBJECT-TYPE
   SYNTAX      Counter64
   MAX-ACCESS  read-only
   STATUS      current
   DESCRIPTION
      "Path: virtualEthernet.performance.vlan.mibCounters.ifOutDiscards

       64 bit unsigned wrappable counter."
   ::= {pr1646v2VEthVlanEntry 41287680}

pr1646v2VEthVlanMCOutErrors OBJECT-TYPE
   SYNTAX      Counter64
   MAX-ACCESS  read-only
   STATUS      current
   DESCRIPTION
      "Path: virtualEthernet.performance.vlan.mibCounters.ifOutErrors

       64 bit unsigned wrappable counter."
   ::= {pr1646v2VEthVlanEntry 41353216}

pr1646v2VEthVlanMCOutQLen OBJECT-TYPE
   SYNTAX      Counter32
   MAX-ACCESS  read-only
   STATUS      current
   DESCRIPTION
      "Path: virtualEthernet.performance.vlan.mibCounters.ifOutQLen

       32 bit unsigned wrappable counter."
   ::= {pr1646v2VEthVlanEntry 41418752}

pr1646v2VEthVlanMCOutDropEx OBJECT-TYPE
   SYNTAX      Counter64
   MAX-ACCESS  read-only
   STATUS      current
   DESCRIPTION
      "Path: virtualEthernet.performance.vlan.mibCounters.ifOutDropLevelExceeded

       64 bit unsigned wrappable counter."
   ::= {pr1646v2VEthVlanEntry 41484288}

pr1646v2VEthVlanMCOutDropNoArp OBJECT-TYPE
   SYNTAX      Counter64
   MAX-ACCESS  read-only
   STATUS      current
   DESCRIPTION
      "Path: virtualEthernet.performance.vlan.mibCounters.ifOutDiscardsNoArp

       64 bit unsigned wrappable counter."
   ::= {pr1646v2VEthVlanEntry 42336256}

pr1646v2VEthVlanMCOutDropFilter OBJECT-TYPE
   SYNTAX      Counter64
   MAX-ACCESS  read-only
   STATUS      current
   DESCRIPTION
      "Path: virtualEthernet.performance.vlan.mibCounters.ifOutDiscardsFilter

       64 bit unsigned wrappable counter."
   ::= {pr1646v2VEthVlanEntry 42598400}

pr1646v2VEthVlanMCOutBandwidth15sec OBJECT-TYPE
   SYNTAX      Integer32
   MAX-ACCESS  read-only
   STATUS      current
   DESCRIPTION
      "Path: virtualEthernet.performance.vlan.mibCounters.ifOutBandwidth.15sec

       unit name = bps
       formula = 8 * ; 8 /"
   ::= {pr1646v2VEthVlanEntry 45483264}

pr1646v2VEthVlanMCOutBandwidth30sec OBJECT-TYPE
   SYNTAX      Integer32
   MAX-ACCESS  read-only
   STATUS      current
   DESCRIPTION
      "Path: virtualEthernet.performance.vlan.mibCounters.ifOutBandwidth.30sec

       unit name = bps
       formula = 8 * ; 8 /"
   ::= {pr1646v2VEthVlanEntry 45484544}

pr1646v2VEthVlanMCOutBandwidth1min OBJECT-TYPE
   SYNTAX      Integer32
   MAX-ACCESS  read-only
   STATUS      current
   DESCRIPTION
      "Path: virtualEthernet.performance.vlan.mibCounters.ifOutBandwidth.1min

       unit name = bps
       formula = 8 * ; 8 /"
   ::= {pr1646v2VEthVlanEntry 45487104}

pr1646v2VEthVlanMCOutBandwidth2min OBJECT-TYPE
   SYNTAX      Integer32
   MAX-ACCESS  read-only
   STATUS      current
   DESCRIPTION
      "Path: virtualEthernet.performance.vlan.mibCounters.ifOutBandwidth.2min

       unit name = bps
       formula = 8 * ; 8 /"
   ::= {pr1646v2VEthVlanEntry 45492224}

pr1646v2VEthVlanMCOutBandwidth5min OBJECT-TYPE
   SYNTAX      Integer32
   MAX-ACCESS  read-only
   STATUS      current
   DESCRIPTION
      "Path: virtualEthernet.performance.vlan.mibCounters.ifOutBandwidth.5min

       unit name = bps
       formula = 8 * ; 8 /"
   ::= {pr1646v2VEthVlanEntry 45507584}

pr1646v2VEthVlanVlanVid OBJECT-TYPE
   SYNTAX      Integer32
   MAX-ACCESS  read-only
   STATUS      current
   DESCRIPTION
      "Path: virtualEthernet.performance.vlan.vlan.vid"
   ::= {pr1646v2VEthVlanEntry 234946560}

pr1646v2VEthVlanPppLinkMonitoringRequestsSent OBJECT-TYPE
   SYNTAX      Gauge32
   MAX-ACCESS  read-only
   STATUS      current
   DESCRIPTION
      "Path: virtualEthernet.performance.vlan.ppp.linkMonitoring.requestsSent

       32 bit unsigned gauge value."
   ::= {pr1646v2VEthVlanEntry 50397440}

pr1646v2VEthVlanPppLinkMonitoringRepliesRcvd OBJECT-TYPE
   SYNTAX      Gauge32
   MAX-ACCESS  read-only
   STATUS      current
   DESCRIPTION
      "Path: virtualEthernet.performance.vlan.ppp.linkMonitoring.repliesRcvd

       32 bit unsigned gauge value."
   ::= {pr1646v2VEthVlanEntry 50397696}

pr1646v2VEthVlanPppLinkMonitoringRequestsRcvd OBJECT-TYPE
   SYNTAX      Gauge32
   MAX-ACCESS  read-only
   STATUS      current
   DESCRIPTION
      "Path: virtualEthernet.performance.vlan.ppp.linkMonitoring.requestsRcvd

       32 bit unsigned gauge value."
   ::= {pr1646v2VEthVlanEntry 50397952}

pr1646v2VEthVlanPppLinkMonitoringRepliesSent OBJECT-TYPE
   SYNTAX      Gauge32
   MAX-ACCESS  read-only
   STATUS      current
   DESCRIPTION
      "Path: virtualEthernet.performance.vlan.ppp.linkMonitoring.repliesSent

       32 bit unsigned gauge value."
   ::= {pr1646v2VEthVlanEntry 50398208}

pr1646v2VEthVlanMCH2P OBJECT-TYPE
   SYNTAX      SEQUENCE OF Pr1646v2VEthVlanMCH2PEntry
   MAX-ACCESS  not-accessible
   STATUS      current
   DESCRIPTION
      ""
   ::= {pr1646v2VEthVlan 41549824}

pr1646v2VEthVlanMCH2PEntry OBJECT-TYPE
   SYNTAX      Pr1646v2VEthVlanMCH2PEntry
   MAX-ACCESS  not-accessible
   STATUS      current
   DESCRIPTION
      ""
   INDEX      { pr1646v2VEthVlanMCH2PGlobalIx,
                pr1646v2VEthVlanTableIx,
                pr1646v2VEthVlanMCH2PTableIx }
   ::= {pr1646v2VEthVlanMCH2P 1}

Pr1646v2VEthVlanMCH2PEntry ::=
   SEQUENCE
      {
      pr1646v2VEthVlanMCH2PGlobalIx
         GlobalIndex,
      pr1646v2VEthVlanMCH2PTableIx
         TableIndex,
      pr1646v2VEthVlanMCH2PSysUpTime
         TimeTicks,
      pr1646v2VEthVlanMCH2PIfUpTime
         TimeTicks,
      pr1646v2VEthVlanMCH2PIfStatChanges
         Counter32,
      pr1646v2VEthVlanMCH2PIfInOctets
         Counter64,
      pr1646v2VEthVlanMCH2PIfInUCPkts
         Counter64,
      pr1646v2VEthVlanMCH2PIfInNUCPkts
         Counter64,
      pr1646v2VEthVlanMCH2PIfInBCPkts
         Counter64,
      pr1646v2VEthVlanMCH2PIfInMCPkts
         Counter64,
      pr1646v2VEthVlanMCH2PIfInDiscards
         Counter64,
      pr1646v2VEthVlanMCH2PIfInErrors
         Counter64,
      pr1646v2VEthVlanMCH2PIfInUnkwn
         Counter64,
      pr1646v2VEthVlanMCH2PInDropEx
         Counter64,
      pr1646v2VEthVlanMCH2PInDropNoMac
         Counter64,
      pr1646v2VEthVlanMCH2PInDropNUCast
         Counter64,
      pr1646v2VEthVlanMCH2PInDropFilter
         Counter64,
      pr1646v2VEthVlanMCH2PIfInBandwidth
         Integer32,
      pr1646v2VEthVlanMCH2PIfOutOctets
         Counter64,
      pr1646v2VEthVlanMCH2PIfOutUCPkts
         Counter64,
      pr1646v2VEthVlanMCH2PIfOutNUCPkts
         Counter64,
      pr1646v2VEthVlanMCH2PIfOutBCPkts
         Counter64,
      pr1646v2VEthVlanMCH2PIfOutMCPkts
         Counter64,
      pr1646v2VEthVlanMCH2PIfOutDiscards
         Counter64,
      pr1646v2VEthVlanMCH2PIfOutErrors
         Counter64,
      pr1646v2VEthVlanMCH2POutDropEx
         Counter64,
      pr1646v2VEthVlanMCH2POutDropNoArp
         Counter64,
      pr1646v2VEthVlanMCH2POutDropFilter
         Counter64,
      pr1646v2VEthVlanMCH2PIfOutBandwidth
         Integer32,
      pr1646v2VEthVlanMCH2PIfErrSec
         Counter32
      }

pr1646v2VEthVlanMCH2PGlobalIx OBJECT-TYPE
   SYNTAX      GlobalIndex
   MAX-ACCESS  not-accessible
   STATUS      current
   DESCRIPTION
      "The value of the tlsCntTreeGlobalIndex of the MANAGED OBJECT."
   ::= {pr1646v2VEthVlanMCH2PEntry 10}

pr1646v2VEthVlanMCH2PTableIx OBJECT-TYPE
   SYNTAX      TableIndex
   MAX-ACCESS  not-accessible
   STATUS      current
   DESCRIPTION
      ""
   ::= {pr1646v2VEthVlanMCH2PEntry 11}

pr1646v2VEthVlanMCH2PSysUpTime OBJECT-TYPE
   SYNTAX      TimeTicks
   MAX-ACCESS  read-only
   STATUS      current
   DESCRIPTION
      "Path: virtualEthernet.performance.vlan.mibCounters.h2Performance.sysUpTime

       Time in centi-second."
   ::= {pr1646v2VEthVlanMCH2PEntry 16777216}

pr1646v2VEthVlanMCH2PIfUpTime OBJECT-TYPE
   SYNTAX      TimeTicks
   MAX-ACCESS  read-only
   STATUS      current
   DESCRIPTION
      "Path: virtualEthernet.performance.vlan.mibCounters.h2Performance.ifUpTime

       Time in centi-second."
   ::= {pr1646v2VEthVlanMCH2PEntry 33554432}

pr1646v2VEthVlanMCH2PIfStatChanges OBJECT-TYPE
   SYNTAX      Counter32
   MAX-ACCESS  read-only
   STATUS      current
   DESCRIPTION
      "Path: virtualEthernet.performance.vlan.mibCounters.h2Performance.ifStatusChanges

       32 bit unsigned wrappable counter."
   ::= {pr1646v2VEthVlanMCH2PEntry 50331648}

pr1646v2VEthVlanMCH2PIfInOctets OBJECT-TYPE
   SYNTAX      Counter64
   MAX-ACCESS  read-only
   STATUS      current
   DESCRIPTION
      "Path: virtualEthernet.performance.vlan.mibCounters.h2Performance.ifInOctets

       64 bit unsigned wrappable counter."
   ::= {pr1646v2VEthVlanMCH2PEntry 67108864}

pr1646v2VEthVlanMCH2PIfInUCPkts OBJECT-TYPE
   SYNTAX      Counter64
   MAX-ACCESS  read-only
   STATUS      current
   DESCRIPTION
      "Path: virtualEthernet.performance.vlan.mibCounters.h2Performance.ifInUcastPkts

       64 bit unsigned wrappable counter."
   ::= {pr1646v2VEthVlanMCH2PEntry 83886080}

pr1646v2VEthVlanMCH2PIfInNUCPkts OBJECT-TYPE
   SYNTAX      Counter64
   MAX-ACCESS  read-only
   STATUS      current
   DESCRIPTION
      "Path: virtualEthernet.performance.vlan.mibCounters.h2Performance.ifInNUcastPkts

       64 bit unsigned wrappable counter."
   ::= {pr1646v2VEthVlanMCH2PEntry 100663296}

pr1646v2VEthVlanMCH2PIfInBCPkts OBJECT-TYPE
   SYNTAX      Counter64
   MAX-ACCESS  read-only
   STATUS      current
   DESCRIPTION
      "Path: virtualEthernet.performance.vlan.mibCounters.h2Performance.ifInBcastPkts

       64 bit unsigned wrappable counter."
   ::= {pr1646v2VEthVlanMCH2PEntry 419430400}

pr1646v2VEthVlanMCH2PIfInMCPkts OBJECT-TYPE
   SYNTAX      Counter64
   MAX-ACCESS  read-only
   STATUS      current
   DESCRIPTION
      "Path: virtualEthernet.performance.vlan.mibCounters.h2Performance.ifInMcastPkts

       64 bit unsigned wrappable counter."
   ::= {pr1646v2VEthVlanMCH2PEntry 436207616}

pr1646v2VEthVlanMCH2PIfInDiscards OBJECT-TYPE
   SYNTAX      Counter64
   MAX-ACCESS  read-only
   STATUS      current
   DESCRIPTION
      "Path: virtualEthernet.performance.vlan.mibCounters.h2Performance.ifInDiscards

       64 bit unsigned wrappable counter."
   ::= {pr1646v2VEthVlanMCH2PEntry 117440512}

pr1646v2VEthVlanMCH2PIfInErrors OBJECT-TYPE
   SYNTAX      Counter64
   MAX-ACCESS  read-only
   STATUS      current
   DESCRIPTION
      "Path: virtualEthernet.performance.vlan.mibCounters.h2Performance.ifInErrors

       64 bit unsigned wrappable counter."
   ::= {pr1646v2VEthVlanMCH2PEntry 134217728}

pr1646v2VEthVlanMCH2PIfInUnkwn OBJECT-TYPE
   SYNTAX      Counter64
   MAX-ACCESS  read-only
   STATUS      current
   DESCRIPTION
      "Path: virtualEthernet.performance.vlan.mibCounters.h2Performance.ifInUnknownProtos

       64 bit unsigned wrappable counter."
   ::= {pr1646v2VEthVlanMCH2PEntry 150994944}

pr1646v2VEthVlanMCH2PInDropEx OBJECT-TYPE
   SYNTAX      Counter64
   MAX-ACCESS  read-only
   STATUS      current
   DESCRIPTION
      "Path: virtualEthernet.performance.vlan.mibCounters.h2Performance.ifInDropLevelExceeded

       64 bit unsigned wrappable counter."
   ::= {pr1646v2VEthVlanMCH2PEntry 335544320}

pr1646v2VEthVlanMCH2PInDropNoMac OBJECT-TYPE
   SYNTAX      Counter64
   MAX-ACCESS  read-only
   STATUS      current
   DESCRIPTION
      "Path: virtualEthernet.performance.vlan.mibCounters.h2Performance.fInDiscardsNoMacFit

       64 bit unsigned wrappable counter."
   ::= {pr1646v2VEthVlanMCH2PEntry 301989888}

pr1646v2VEthVlanMCH2PInDropNUCast OBJECT-TYPE
   SYNTAX      Counter64
   MAX-ACCESS  read-only
   STATUS      current
   DESCRIPTION
      "Path: virtualEthernet.performance.vlan.mibCounters.h2Performance.fInDiscardsNUCast

       64 bit unsigned wrappable counter."
   ::= {pr1646v2VEthVlanMCH2PEntry 318767104}

pr1646v2VEthVlanMCH2PInDropFilter OBJECT-TYPE
   SYNTAX      Counter64
   MAX-ACCESS  read-only
   STATUS      current
   DESCRIPTION
      "Path: virtualEthernet.performance.vlan.mibCounters.h2Performance.fInDiscardsFilter

       64 bit unsigned wrappable counter."
   ::= {pr1646v2VEthVlanMCH2PEntry 385875968}

pr1646v2VEthVlanMCH2PIfInBandwidth OBJECT-TYPE
   SYNTAX      Integer32
   MAX-ACCESS  read-only
   STATUS      current
   DESCRIPTION
      "Path: virtualEthernet.performance.vlan.mibCounters.h2Performance.ifInBandwidth

       unit name = bps
       formula = 8 * ; 8 /"
   ::= {pr1646v2VEthVlanMCH2PEntry 268435456}

pr1646v2VEthVlanMCH2PIfOutOctets OBJECT-TYPE
   SYNTAX      Counter64
   MAX-ACCESS  read-only
   STATUS      current
   DESCRIPTION
      "Path: virtualEthernet.performance.vlan.mibCounters.h2Performance.ifOutOctets

       64 bit unsigned wrappable counter."
   ::= {pr1646v2VEthVlanMCH2PEntry 167772160}

pr1646v2VEthVlanMCH2PIfOutUCPkts OBJECT-TYPE
   SYNTAX      Counter64
   MAX-ACCESS  read-only
   STATUS      current
   DESCRIPTION
      "Path: virtualEthernet.performance.vlan.mibCounters.h2Performance.ifOutUcastPkts

       64 bit unsigned wrappable counter."
   ::= {pr1646v2VEthVlanMCH2PEntry 184549376}

pr1646v2VEthVlanMCH2PIfOutNUCPkts OBJECT-TYPE
   SYNTAX      Counter64
   MAX-ACCESS  read-only
   STATUS      current
   DESCRIPTION
      "Path: virtualEthernet.performance.vlan.mibCounters.h2Performance.ifOutNUcastPkts

       64 bit unsigned wrappable counter."
   ::= {pr1646v2VEthVlanMCH2PEntry 201326592}

pr1646v2VEthVlanMCH2PIfOutBCPkts OBJECT-TYPE
   SYNTAX      Counter64
   MAX-ACCESS  read-only
   STATUS      current
   DESCRIPTION
      "Path: virtualEthernet.performance.vlan.mibCounters.h2Performance.ifOutBcastPkts

       64 bit unsigned wrappable counter."
   ::= {pr1646v2VEthVlanMCH2PEntry 452984832}

pr1646v2VEthVlanMCH2PIfOutMCPkts OBJECT-TYPE
   SYNTAX      Counter64
   MAX-ACCESS  read-only
   STATUS      current
   DESCRIPTION
      "Path: virtualEthernet.performance.vlan.mibCounters.h2Performance.ifOutMcastPkts

       64 bit unsigned wrappable counter."
   ::= {pr1646v2VEthVlanMCH2PEntry 469762048}

pr1646v2VEthVlanMCH2PIfOutDiscards OBJECT-TYPE
   SYNTAX      Counter64
   MAX-ACCESS  read-only
   STATUS      current
   DESCRIPTION
      "Path: virtualEthernet.performance.vlan.mibCounters.h2Performance.ifOutDiscards

       64 bit unsigned wrappable counter."
   ::= {pr1646v2VEthVlanMCH2PEntry 218103808}

pr1646v2VEthVlanMCH2PIfOutErrors OBJECT-TYPE
   SYNTAX      Counter64
   MAX-ACCESS  read-only
   STATUS      current
   DESCRIPTION
      "Path: virtualEthernet.performance.vlan.mibCounters.h2Performance.ifOutErrors

       64 bit unsigned wrappable counter."
   ::= {pr1646v2VEthVlanMCH2PEntry 234881024}

pr1646v2VEthVlanMCH2POutDropEx OBJECT-TYPE
   SYNTAX      Counter64
   MAX-ACCESS  read-only
   STATUS      current
   DESCRIPTION
      "Path: virtualEthernet.performance.vlan.mibCounters.h2Performance.ifOutDropLevelExceeded

       64 bit unsigned wrappable counter."
   ::= {pr1646v2VEthVlanMCH2PEntry 352321536}

pr1646v2VEthVlanMCH2POutDropNoArp OBJECT-TYPE
   SYNTAX      Counter64
   MAX-ACCESS  read-only
   STATUS      current
   DESCRIPTION
      "Path: virtualEthernet.performance.vlan.mibCounters.h2Performance.ifOutDiscardsNoArp

       64 bit unsigned wrappable counter."
   ::= {pr1646v2VEthVlanMCH2PEntry 369098752}

pr1646v2VEthVlanMCH2POutDropFilter OBJECT-TYPE
   SYNTAX      Counter64
   MAX-ACCESS  read-only
   STATUS      current
   DESCRIPTION
      "Path: virtualEthernet.performance.vlan.mibCounters.h2Performance.ifOutDiscardsFilter

       64 bit unsigned wrappable counter."
   ::= {pr1646v2VEthVlanMCH2PEntry 402653184}

pr1646v2VEthVlanMCH2PIfOutBandwidth OBJECT-TYPE
   SYNTAX      Integer32
   MAX-ACCESS  read-only
   STATUS      current
   DESCRIPTION
      "Path: virtualEthernet.performance.vlan.mibCounters.h2Performance.ifOutBandwidth

       unit name = bps
       formula = 8 * ; 8 /"
   ::= {pr1646v2VEthVlanMCH2PEntry 285212672}

pr1646v2VEthVlanMCH2PIfErrSec OBJECT-TYPE
   SYNTAX      Counter32
   MAX-ACCESS  read-only
   STATUS      current
   DESCRIPTION
      "Path: virtualEthernet.performance.vlan.mibCounters.h2Performance.ifErrSec

       32 bit unsigned wrappable counter."
   ::= {pr1646v2VEthVlanMCH2PEntry 251658240}

pr1646v2VEthVlanMCH24P OBJECT-TYPE
   SYNTAX      SEQUENCE OF Pr1646v2VEthVlanMCH24PEntry
   MAX-ACCESS  not-accessible
   STATUS      current
   DESCRIPTION
      ""
   ::= {pr1646v2VEthVlan 41615360}

pr1646v2VEthVlanMCH24PEntry OBJECT-TYPE
   SYNTAX      Pr1646v2VEthVlanMCH24PEntry
   MAX-ACCESS  not-accessible
   STATUS      current
   DESCRIPTION
      ""
   INDEX      { pr1646v2VEthVlanMCH24PGlobalIx,
                pr1646v2VEthVlanTableIx,
                pr1646v2VEthVlanMCH24PTableIx }
   ::= {pr1646v2VEthVlanMCH24P 1}

Pr1646v2VEthVlanMCH24PEntry ::=
   SEQUENCE
      {
      pr1646v2VEthVlanMCH24PGlobalIx
         GlobalIndex,
      pr1646v2VEthVlanMCH24PTableIx
         TableIndex,
      pr1646v2VEthVlanMCH24PSysUpTime
         TimeTicks,
      pr1646v2VEthVlanMCH24PIfUpTime
         TimeTicks,
      pr1646v2VEthVlanMCH24PIfStatChanges
         Counter32,
      pr1646v2VEthVlanMCH24PIfInOctets
         Counter64,
      pr1646v2VEthVlanMCH24PIfInUCPkts
         Counter64,
      pr1646v2VEthVlanMCH24PIfInNUCPkts
         Counter64,
      pr1646v2VEthVlanMCH24PIfInBCPkts
         Counter64,
      pr1646v2VEthVlanMCH24PIfInMCPkts
         Counter64,
      pr1646v2VEthVlanMCH24PIfInDiscards
         Counter64,
      pr1646v2VEthVlanMCH24PIfInErrors
         Counter64,
      pr1646v2VEthVlanMCH24PIfInUnkwn
         Counter64,
      pr1646v2VEthVlanMCH24PInDropEx
         Counter64,
      pr1646v2VEthVlanMCH24PInDropNoMac
         Counter64,
      pr1646v2VEthVlanMCH24PInDropNUCast
         Counter64,
      pr1646v2VEthVlanMCH24PInDropFilter
         Counter64,
      pr1646v2VEthVlanMCH24PIfInBandwidth
         Integer32,
      pr1646v2VEthVlanMCH24PIfOutOctets
         Counter64,
      pr1646v2VEthVlanMCH24PIfOutUCPkts
         Counter64,
      pr1646v2VEthVlanMCH24PIfOutNUCPkts
         Counter64,
      pr1646v2VEthVlanMCH24PIfOutBCPkts
         Counter64,
      pr1646v2VEthVlanMCH24PIfOutMCPkts
         Counter64,
      pr1646v2VEthVlanMCH24PIfOutDiscards
         Counter64,
      pr1646v2VEthVlanMCH24PIfOutErrors
         Counter64,
      pr1646v2VEthVlanMCH24POutDropEx
         Counter64,
      pr1646v2VEthVlanMCH24POutDropNoArp
         Counter64,
      pr1646v2VEthVlanMCH24POutDropFilter
         Counter64,
      pr1646v2VEthVlanMCH24PIfOutBandwidth
         Integer32,
      pr1646v2VEthVlanMCH24PIfErrSec
         Counter32
      }

pr1646v2VEthVlanMCH24PGlobalIx OBJECT-TYPE
   SYNTAX      GlobalIndex
   MAX-ACCESS  not-accessible
   STATUS      current
   DESCRIPTION
      "The value of the tlsCntTreeGlobalIndex of the MANAGED OBJECT."
   ::= {pr1646v2VEthVlanMCH24PEntry 10}

pr1646v2VEthVlanMCH24PTableIx OBJECT-TYPE
   SYNTAX      TableIndex
   MAX-ACCESS  not-accessible
   STATUS      current
   DESCRIPTION
      ""
   ::= {pr1646v2VEthVlanMCH24PEntry 11}

pr1646v2VEthVlanMCH24PSysUpTime OBJECT-TYPE
   SYNTAX      TimeTicks
   MAX-ACCESS  read-only
   STATUS      current
   DESCRIPTION
      "Path: virtualEthernet.performance.vlan.mibCounters.h24Performance.sysUpTime

       Time in centi-second."
   ::= {pr1646v2VEthVlanMCH24PEntry 16777216}

pr1646v2VEthVlanMCH24PIfUpTime OBJECT-TYPE
   SYNTAX      TimeTicks
   MAX-ACCESS  read-only
   STATUS      current
   DESCRIPTION
      "Path: virtualEthernet.performance.vlan.mibCounters.h24Performance.ifUpTime

       Time in centi-second."
   ::= {pr1646v2VEthVlanMCH24PEntry 33554432}

pr1646v2VEthVlanMCH24PIfStatChanges OBJECT-TYPE
   SYNTAX      Counter32
   MAX-ACCESS  read-only
   STATUS      current
   DESCRIPTION
      "Path: virtualEthernet.performance.vlan.mibCounters.h24Performance.ifStatusChanges

       32 bit unsigned wrappable counter."
   ::= {pr1646v2VEthVlanMCH24PEntry 50331648}

pr1646v2VEthVlanMCH24PIfInOctets OBJECT-TYPE
   SYNTAX      Counter64
   MAX-ACCESS  read-only
   STATUS      current
   DESCRIPTION
      "Path: virtualEthernet.performance.vlan.mibCounters.h24Performance.ifInOctets

       64 bit unsigned wrappable counter."
   ::= {pr1646v2VEthVlanMCH24PEntry 67108864}

pr1646v2VEthVlanMCH24PIfInUCPkts OBJECT-TYPE
   SYNTAX      Counter64
   MAX-ACCESS  read-only
   STATUS      current
   DESCRIPTION
      "Path: virtualEthernet.performance.vlan.mibCounters.h24Performance.ifInUcastPkts

       64 bit unsigned wrappable counter."
   ::= {pr1646v2VEthVlanMCH24PEntry 83886080}

pr1646v2VEthVlanMCH24PIfInNUCPkts OBJECT-TYPE
   SYNTAX      Counter64
   MAX-ACCESS  read-only
   STATUS      current
   DESCRIPTION
      "Path: virtualEthernet.performance.vlan.mibCounters.h24Performance.ifInNUcastPkts

       64 bit unsigned wrappable counter."
   ::= {pr1646v2VEthVlanMCH24PEntry 100663296}

pr1646v2VEthVlanMCH24PIfInBCPkts OBJECT-TYPE
   SYNTAX      Counter64
   MAX-ACCESS  read-only
   STATUS      current
   DESCRIPTION
      "Path: virtualEthernet.performance.vlan.mibCounters.h24Performance.ifInBcastPkts

       64 bit unsigned wrappable counter."
   ::= {pr1646v2VEthVlanMCH24PEntry 419430400}

pr1646v2VEthVlanMCH24PIfInMCPkts OBJECT-TYPE
   SYNTAX      Counter64
   MAX-ACCESS  read-only
   STATUS      current
   DESCRIPTION
      "Path: virtualEthernet.performance.vlan.mibCounters.h24Performance.ifInMcastPkts

       64 bit unsigned wrappable counter."
   ::= {pr1646v2VEthVlanMCH24PEntry 436207616}

pr1646v2VEthVlanMCH24PIfInDiscards OBJECT-TYPE
   SYNTAX      Counter64
   MAX-ACCESS  read-only
   STATUS      current
   DESCRIPTION
      "Path: virtualEthernet.performance.vlan.mibCounters.h24Performance.ifInDiscards

       64 bit unsigned wrappable counter."
   ::= {pr1646v2VEthVlanMCH24PEntry 117440512}

pr1646v2VEthVlanMCH24PIfInErrors OBJECT-TYPE
   SYNTAX      Counter64
   MAX-ACCESS  read-only
   STATUS      current
   DESCRIPTION
      "Path: virtualEthernet.performance.vlan.mibCounters.h24Performance.ifInErrors

       64 bit unsigned wrappable counter."
   ::= {pr1646v2VEthVlanMCH24PEntry 134217728}

pr1646v2VEthVlanMCH24PIfInUnkwn OBJECT-TYPE
   SYNTAX      Counter64
   MAX-ACCESS  read-only
   STATUS      current
   DESCRIPTION
      "Path: virtualEthernet.performance.vlan.mibCounters.h24Performance.ifInUnknownProtos

       64 bit unsigned wrappable counter."
   ::= {pr1646v2VEthVlanMCH24PEntry 150994944}

pr1646v2VEthVlanMCH24PInDropEx OBJECT-TYPE
   SYNTAX      Counter64
   MAX-ACCESS  read-only
   STATUS      current
   DESCRIPTION
      "Path: virtualEthernet.performance.vlan.mibCounters.h24Performance.ifInDropLevelExceeded

       64 bit unsigned wrappable counter."
   ::= {pr1646v2VEthVlanMCH24PEntry 335544320}

pr1646v2VEthVlanMCH24PInDropNoMac OBJECT-TYPE
   SYNTAX      Counter64
   MAX-ACCESS  read-only
   STATUS      current
   DESCRIPTION
      "Path: virtualEthernet.performance.vlan.mibCounters.h24Performance.fInDiscardsNoMacFit

       64 bit unsigned wrappable counter."
   ::= {pr1646v2VEthVlanMCH24PEntry 301989888}

pr1646v2VEthVlanMCH24PInDropNUCast OBJECT-TYPE
   SYNTAX      Counter64
   MAX-ACCESS  read-only
   STATUS      current
   DESCRIPTION
      "Path: virtualEthernet.performance.vlan.mibCounters.h24Performance.fInDiscardsNUCast

       64 bit unsigned wrappable counter."
   ::= {pr1646v2VEthVlanMCH24PEntry 318767104}

pr1646v2VEthVlanMCH24PInDropFilter OBJECT-TYPE
   SYNTAX      Counter64
   MAX-ACCESS  read-only
   STATUS      current
   DESCRIPTION
      "Path: virtualEthernet.performance.vlan.mibCounters.h24Performance.fInDiscardsFilter

       64 bit unsigned wrappable counter."
   ::= {pr1646v2VEthVlanMCH24PEntry 385875968}

pr1646v2VEthVlanMCH24PIfInBandwidth OBJECT-TYPE
   SYNTAX      Integer32
   MAX-ACCESS  read-only
   STATUS      current
   DESCRIPTION
      "Path: virtualEthernet.performance.vlan.mibCounters.h24Performance.ifInBandwidth

       unit name = bps
       formula = 8 * ; 8 /"
   ::= {pr1646v2VEthVlanMCH24PEntry 268435456}

pr1646v2VEthVlanMCH24PIfOutOctets OBJECT-TYPE
   SYNTAX      Counter64
   MAX-ACCESS  read-only
   STATUS      current
   DESCRIPTION
      "Path: virtualEthernet.performance.vlan.mibCounters.h24Performance.ifOutOctets

       64 bit unsigned wrappable counter."
   ::= {pr1646v2VEthVlanMCH24PEntry 167772160}

pr1646v2VEthVlanMCH24PIfOutUCPkts OBJECT-TYPE
   SYNTAX      Counter64
   MAX-ACCESS  read-only
   STATUS      current
   DESCRIPTION
      "Path: virtualEthernet.performance.vlan.mibCounters.h24Performance.ifOutUcastPkts

       64 bit unsigned wrappable counter."
   ::= {pr1646v2VEthVlanMCH24PEntry 184549376}

pr1646v2VEthVlanMCH24PIfOutNUCPkts OBJECT-TYPE
   SYNTAX      Counter64
   MAX-ACCESS  read-only
   STATUS      current
   DESCRIPTION
      "Path: virtualEthernet.performance.vlan.mibCounters.h24Performance.ifOutNUcastPkts

       64 bit unsigned wrappable counter."
   ::= {pr1646v2VEthVlanMCH24PEntry 201326592}

pr1646v2VEthVlanMCH24PIfOutBCPkts OBJECT-TYPE
   SYNTAX      Counter64
   MAX-ACCESS  read-only
   STATUS      current
   DESCRIPTION
      "Path: virtualEthernet.performance.vlan.mibCounters.h24Performance.ifOutBcastPkts

       64 bit unsigned wrappable counter."
   ::= {pr1646v2VEthVlanMCH24PEntry 452984832}

pr1646v2VEthVlanMCH24PIfOutMCPkts OBJECT-TYPE
   SYNTAX      Counter64
   MAX-ACCESS  read-only
   STATUS      current
   DESCRIPTION
      "Path: virtualEthernet.performance.vlan.mibCounters.h24Performance.ifOutMcastPkts

       64 bit unsigned wrappable counter."
   ::= {pr1646v2VEthVlanMCH24PEntry 469762048}

pr1646v2VEthVlanMCH24PIfOutDiscards OBJECT-TYPE
   SYNTAX      Counter64
   MAX-ACCESS  read-only
   STATUS      current
   DESCRIPTION
      "Path: virtualEthernet.performance.vlan.mibCounters.h24Performance.ifOutDiscards

       64 bit unsigned wrappable counter."
   ::= {pr1646v2VEthVlanMCH24PEntry 218103808}

pr1646v2VEthVlanMCH24PIfOutErrors OBJECT-TYPE
   SYNTAX      Counter64
   MAX-ACCESS  read-only
   STATUS      current
   DESCRIPTION
      "Path: virtualEthernet.performance.vlan.mibCounters.h24Performance.ifOutErrors

       64 bit unsigned wrappable counter."
   ::= {pr1646v2VEthVlanMCH24PEntry 234881024}

pr1646v2VEthVlanMCH24POutDropEx OBJECT-TYPE
   SYNTAX      Counter64
   MAX-ACCESS  read-only
   STATUS      current
   DESCRIPTION
      "Path: virtualEthernet.performance.vlan.mibCounters.h24Performance.ifOutDropLevelExceeded

       64 bit unsigned wrappable counter."
   ::= {pr1646v2VEthVlanMCH24PEntry 352321536}

pr1646v2VEthVlanMCH24POutDropNoArp OBJECT-TYPE
   SYNTAX      Counter64
   MAX-ACCESS  read-only
   STATUS      current
   DESCRIPTION
      "Path: virtualEthernet.performance.vlan.mibCounters.h24Performance.ifOutDiscardsNoArp

       64 bit unsigned wrappable counter."
   ::= {pr1646v2VEthVlanMCH24PEntry 369098752}

pr1646v2VEthVlanMCH24POutDropFilter OBJECT-TYPE
   SYNTAX      Counter64
   MAX-ACCESS  read-only
   STATUS      current
   DESCRIPTION
      "Path: virtualEthernet.performance.vlan.mibCounters.h24Performance.ifOutDiscardsFilter

       64 bit unsigned wrappable counter."
   ::= {pr1646v2VEthVlanMCH24PEntry 402653184}

pr1646v2VEthVlanMCH24PIfOutBandwidth OBJECT-TYPE
   SYNTAX      Integer32
   MAX-ACCESS  read-only
   STATUS      current
   DESCRIPTION
      "Path: virtualEthernet.performance.vlan.mibCounters.h24Performance.ifOutBandwidth

       unit name = bps
       formula = 8 * ; 8 /"
   ::= {pr1646v2VEthVlanMCH24PEntry 285212672}

pr1646v2VEthVlanMCH24PIfErrSec OBJECT-TYPE
   SYNTAX      Counter32
   MAX-ACCESS  read-only
   STATUS      current
   DESCRIPTION
      "Path: virtualEthernet.performance.vlan.mibCounters.h24Performance.ifErrSec

       32 bit unsigned wrappable counter."
   ::= {pr1646v2VEthVlanMCH24PEntry 251658240}

pr1646v2VEthVlanMCD7P OBJECT-TYPE
   SYNTAX      SEQUENCE OF Pr1646v2VEthVlanMCD7PEntry
   MAX-ACCESS  not-accessible
   STATUS      current
   DESCRIPTION
      ""
   ::= {pr1646v2VEthVlan 41680896}

pr1646v2VEthVlanMCD7PEntry OBJECT-TYPE
   SYNTAX      Pr1646v2VEthVlanMCD7PEntry
   MAX-ACCESS  not-accessible
   STATUS      current
   DESCRIPTION
      ""
   INDEX      { pr1646v2VEthVlanMCD7PGlobalIx,
                pr1646v2VEthVlanTableIx,
                pr1646v2VEthVlanMCD7PTableIx }
   ::= {pr1646v2VEthVlanMCD7P 1}

Pr1646v2VEthVlanMCD7PEntry ::=
   SEQUENCE
      {
      pr1646v2VEthVlanMCD7PGlobalIx
         GlobalIndex,
      pr1646v2VEthVlanMCD7PTableIx
         TableIndex,
      pr1646v2VEthVlanMCD7PSysUpTime
         TimeTicks,
      pr1646v2VEthVlanMCD7PIfUpTime
         TimeTicks,
      pr1646v2VEthVlanMCD7PIfStatChanges
         Counter32,
      pr1646v2VEthVlanMCD7PIfInOctets
         Counter64,
      pr1646v2VEthVlanMCD7PIfInUCPkts
         Counter64,
      pr1646v2VEthVlanMCD7PIfInNUCPkts
         Counter64,
      pr1646v2VEthVlanMCD7PIfInBCPkts
         Counter64,
      pr1646v2VEthVlanMCD7PIfInMCPkts
         Counter64,
      pr1646v2VEthVlanMCD7PIfInDiscards
         Counter64,
      pr1646v2VEthVlanMCD7PIfInErrors
         Counter64,
      pr1646v2VEthVlanMCD7PIfInUnkwn
         Counter64,
      pr1646v2VEthVlanMCD7PInDropEx
         Counter64,
      pr1646v2VEthVlanMCD7PInDropNoMac
         Counter64,
      pr1646v2VEthVlanMCD7PInDropNUCast
         Counter64,
      pr1646v2VEthVlanMCD7PInDropFilter
         Counter64,
      pr1646v2VEthVlanMCD7PIfInBandwidth
         Integer32,
      pr1646v2VEthVlanMCD7PIfOutOctets
         Counter64,
      pr1646v2VEthVlanMCD7PIfOutUCPkts
         Counter64,
      pr1646v2VEthVlanMCD7PIfOutNUCPkts
         Counter64,
      pr1646v2VEthVlanMCD7PIfOutBCPkts
         Counter64,
      pr1646v2VEthVlanMCD7PIfOutMCPkts
         Counter64,
      pr1646v2VEthVlanMCD7PIfOutDiscards
         Counter64,
      pr1646v2VEthVlanMCD7PIfOutErrors
         Counter64,
      pr1646v2VEthVlanMCD7POutDropEx
         Counter64,
      pr1646v2VEthVlanMCD7POutDropNoArp
         Counter64,
      pr1646v2VEthVlanMCD7POutDropFilter
         Counter64,
      pr1646v2VEthVlanMCD7PIfOutBandwidth
         Integer32,
      pr1646v2VEthVlanMCD7PIfErrSec
         Counter32
      }

pr1646v2VEthVlanMCD7PGlobalIx OBJECT-TYPE
   SYNTAX      GlobalIndex
   MAX-ACCESS  not-accessible
   STATUS      current
   DESCRIPTION
      "The value of the tlsCntTreeGlobalIndex of the MANAGED OBJECT."
   ::= {pr1646v2VEthVlanMCD7PEntry 10}

pr1646v2VEthVlanMCD7PTableIx OBJECT-TYPE
   SYNTAX      TableIndex
   MAX-ACCESS  not-accessible
   STATUS      current
   DESCRIPTION
      ""
   ::= {pr1646v2VEthVlanMCD7PEntry 11}

pr1646v2VEthVlanMCD7PSysUpTime OBJECT-TYPE
   SYNTAX      TimeTicks
   MAX-ACCESS  read-only
   STATUS      current
   DESCRIPTION
      "Path: virtualEthernet.performance.vlan.mibCounters.d7Performance.sysUpTime

       Time in centi-second."
   ::= {pr1646v2VEthVlanMCD7PEntry 16777216}

pr1646v2VEthVlanMCD7PIfUpTime OBJECT-TYPE
   SYNTAX      TimeTicks
   MAX-ACCESS  read-only
   STATUS      current
   DESCRIPTION
      "Path: virtualEthernet.performance.vlan.mibCounters.d7Performance.ifUpTime

       Time in centi-second."
   ::= {pr1646v2VEthVlanMCD7PEntry 33554432}

pr1646v2VEthVlanMCD7PIfStatChanges OBJECT-TYPE
   SYNTAX      Counter32
   MAX-ACCESS  read-only
   STATUS      current
   DESCRIPTION
      "Path: virtualEthernet.performance.vlan.mibCounters.d7Performance.ifStatusChanges

       32 bit unsigned wrappable counter."
   ::= {pr1646v2VEthVlanMCD7PEntry 50331648}

pr1646v2VEthVlanMCD7PIfInOctets OBJECT-TYPE
   SYNTAX      Counter64
   MAX-ACCESS  read-only
   STATUS      current
   DESCRIPTION
      "Path: virtualEthernet.performance.vlan.mibCounters.d7Performance.ifInOctets

       64 bit unsigned wrappable counter."
   ::= {pr1646v2VEthVlanMCD7PEntry 67108864}

pr1646v2VEthVlanMCD7PIfInUCPkts OBJECT-TYPE
   SYNTAX      Counter64
   MAX-ACCESS  read-only
   STATUS      current
   DESCRIPTION
      "Path: virtualEthernet.performance.vlan.mibCounters.d7Performance.ifInUcastPkts

       64 bit unsigned wrappable counter."
   ::= {pr1646v2VEthVlanMCD7PEntry 83886080}

pr1646v2VEthVlanMCD7PIfInNUCPkts OBJECT-TYPE
   SYNTAX      Counter64
   MAX-ACCESS  read-only
   STATUS      current
   DESCRIPTION
      "Path: virtualEthernet.performance.vlan.mibCounters.d7Performance.ifInNUcastPkts

       64 bit unsigned wrappable counter."
   ::= {pr1646v2VEthVlanMCD7PEntry 100663296}

pr1646v2VEthVlanMCD7PIfInBCPkts OBJECT-TYPE
   SYNTAX      Counter64
   MAX-ACCESS  read-only
   STATUS      current
   DESCRIPTION
      "Path: virtualEthernet.performance.vlan.mibCounters.d7Performance.ifInBcastPkts

       64 bit unsigned wrappable counter."
   ::= {pr1646v2VEthVlanMCD7PEntry 419430400}

pr1646v2VEthVlanMCD7PIfInMCPkts OBJECT-TYPE
   SYNTAX      Counter64
   MAX-ACCESS  read-only
   STATUS      current
   DESCRIPTION
      "Path: virtualEthernet.performance.vlan.mibCounters.d7Performance.ifInMcastPkts

       64 bit unsigned wrappable counter."
   ::= {pr1646v2VEthVlanMCD7PEntry 436207616}

pr1646v2VEthVlanMCD7PIfInDiscards OBJECT-TYPE
   SYNTAX      Counter64
   MAX-ACCESS  read-only
   STATUS      current
   DESCRIPTION
      "Path: virtualEthernet.performance.vlan.mibCounters.d7Performance.ifInDiscards

       64 bit unsigned wrappable counter."
   ::= {pr1646v2VEthVlanMCD7PEntry 117440512}

pr1646v2VEthVlanMCD7PIfInErrors OBJECT-TYPE
   SYNTAX      Counter64
   MAX-ACCESS  read-only
   STATUS      current
   DESCRIPTION
      "Path: virtualEthernet.performance.vlan.mibCounters.d7Performance.ifInErrors

       64 bit unsigned wrappable counter."
   ::= {pr1646v2VEthVlanMCD7PEntry 134217728}

pr1646v2VEthVlanMCD7PIfInUnkwn OBJECT-TYPE
   SYNTAX      Counter64
   MAX-ACCESS  read-only
   STATUS      current
   DESCRIPTION
      "Path: virtualEthernet.performance.vlan.mibCounters.d7Performance.ifInUnknownProtos

       64 bit unsigned wrappable counter."
   ::= {pr1646v2VEthVlanMCD7PEntry 150994944}

pr1646v2VEthVlanMCD7PInDropEx OBJECT-TYPE
   SYNTAX      Counter64
   MAX-ACCESS  read-only
   STATUS      current
   DESCRIPTION
      "Path: virtualEthernet.performance.vlan.mibCounters.d7Performance.ifInDropLevelExceeded

       64 bit unsigned wrappable counter."
   ::= {pr1646v2VEthVlanMCD7PEntry 335544320}

pr1646v2VEthVlanMCD7PInDropNoMac OBJECT-TYPE
   SYNTAX      Counter64
   MAX-ACCESS  read-only
   STATUS      current
   DESCRIPTION
      "Path: virtualEthernet.performance.vlan.mibCounters.d7Performance.fInDiscardsNoMacFit

       64 bit unsigned wrappable counter."
   ::= {pr1646v2VEthVlanMCD7PEntry 301989888}

pr1646v2VEthVlanMCD7PInDropNUCast OBJECT-TYPE
   SYNTAX      Counter64
   MAX-ACCESS  read-only
   STATUS      current
   DESCRIPTION
      "Path: virtualEthernet.performance.vlan.mibCounters.d7Performance.fInDiscardsNUCast

       64 bit unsigned wrappable counter."
   ::= {pr1646v2VEthVlanMCD7PEntry 318767104}

pr1646v2VEthVlanMCD7PInDropFilter OBJECT-TYPE
   SYNTAX      Counter64
   MAX-ACCESS  read-only
   STATUS      current
   DESCRIPTION
      "Path: virtualEthernet.performance.vlan.mibCounters.d7Performance.fInDiscardsFilter

       64 bit unsigned wrappable counter."
   ::= {pr1646v2VEthVlanMCD7PEntry 385875968}

pr1646v2VEthVlanMCD7PIfInBandwidth OBJECT-TYPE
   SYNTAX      Integer32
   MAX-ACCESS  read-only
   STATUS      current
   DESCRIPTION
      "Path: virtualEthernet.performance.vlan.mibCounters.d7Performance.ifInBandwidth

       unit name = bps
       formula = 8 * ; 8 /"
   ::= {pr1646v2VEthVlanMCD7PEntry 268435456}

pr1646v2VEthVlanMCD7PIfOutOctets OBJECT-TYPE
   SYNTAX      Counter64
   MAX-ACCESS  read-only
   STATUS      current
   DESCRIPTION
      "Path: virtualEthernet.performance.vlan.mibCounters.d7Performance.ifOutOctets

       64 bit unsigned wrappable counter."
   ::= {pr1646v2VEthVlanMCD7PEntry 167772160}

pr1646v2VEthVlanMCD7PIfOutUCPkts OBJECT-TYPE
   SYNTAX      Counter64
   MAX-ACCESS  read-only
   STATUS      current
   DESCRIPTION
      "Path: virtualEthernet.performance.vlan.mibCounters.d7Performance.ifOutUcastPkts

       64 bit unsigned wrappable counter."
   ::= {pr1646v2VEthVlanMCD7PEntry 184549376}

pr1646v2VEthVlanMCD7PIfOutNUCPkts OBJECT-TYPE
   SYNTAX      Counter64
   MAX-ACCESS  read-only
   STATUS      current
   DESCRIPTION
      "Path: virtualEthernet.performance.vlan.mibCounters.d7Performance.ifOutNUcastPkts

       64 bit unsigned wrappable counter."
   ::= {pr1646v2VEthVlanMCD7PEntry 201326592}

pr1646v2VEthVlanMCD7PIfOutBCPkts OBJECT-TYPE
   SYNTAX      Counter64
   MAX-ACCESS  read-only
   STATUS      current
   DESCRIPTION
      "Path: virtualEthernet.performance.vlan.mibCounters.d7Performance.ifOutBcastPkts

       64 bit unsigned wrappable counter."
   ::= {pr1646v2VEthVlanMCD7PEntry 452984832}

pr1646v2VEthVlanMCD7PIfOutMCPkts OBJECT-TYPE
   SYNTAX      Counter64
   MAX-ACCESS  read-only
   STATUS      current
   DESCRIPTION
      "Path: virtualEthernet.performance.vlan.mibCounters.d7Performance.ifOutMcastPkts

       64 bit unsigned wrappable counter."
   ::= {pr1646v2VEthVlanMCD7PEntry 469762048}

pr1646v2VEthVlanMCD7PIfOutDiscards OBJECT-TYPE
   SYNTAX      Counter64
   MAX-ACCESS  read-only
   STATUS      current
   DESCRIPTION
      "Path: virtualEthernet.performance.vlan.mibCounters.d7Performance.ifOutDiscards

       64 bit unsigned wrappable counter."
   ::= {pr1646v2VEthVlanMCD7PEntry 218103808}

pr1646v2VEthVlanMCD7PIfOutErrors OBJECT-TYPE
   SYNTAX      Counter64
   MAX-ACCESS  read-only
   STATUS      current
   DESCRIPTION
      "Path: virtualEthernet.performance.vlan.mibCounters.d7Performance.ifOutErrors

       64 bit unsigned wrappable counter."
   ::= {pr1646v2VEthVlanMCD7PEntry 234881024}

pr1646v2VEthVlanMCD7POutDropEx OBJECT-TYPE
   SYNTAX      Counter64
   MAX-ACCESS  read-only
   STATUS      current
   DESCRIPTION
      "Path: virtualEthernet.performance.vlan.mibCounters.d7Performance.ifOutDropLevelExceeded

       64 bit unsigned wrappable counter."
   ::= {pr1646v2VEthVlanMCD7PEntry 352321536}

pr1646v2VEthVlanMCD7POutDropNoArp OBJECT-TYPE
   SYNTAX      Counter64
   MAX-ACCESS  read-only
   STATUS      current
   DESCRIPTION
      "Path: virtualEthernet.performance.vlan.mibCounters.d7Performance.ifOutDiscardsNoArp

       64 bit unsigned wrappable counter."
   ::= {pr1646v2VEthVlanMCD7PEntry 369098752}

pr1646v2VEthVlanMCD7POutDropFilter OBJECT-TYPE
   SYNTAX      Counter64
   MAX-ACCESS  read-only
   STATUS      current
   DESCRIPTION
      "Path: virtualEthernet.performance.vlan.mibCounters.d7Performance.ifOutDiscardsFilter

       64 bit unsigned wrappable counter."
   ::= {pr1646v2VEthVlanMCD7PEntry 402653184}

pr1646v2VEthVlanMCD7PIfOutBandwidth OBJECT-TYPE
   SYNTAX      Integer32
   MAX-ACCESS  read-only
   STATUS      current
   DESCRIPTION
      "Path: virtualEthernet.performance.vlan.mibCounters.d7Performance.ifOutBandwidth

       unit name = bps
       formula = 8 * ; 8 /"
   ::= {pr1646v2VEthVlanMCD7PEntry 285212672}

pr1646v2VEthVlanMCD7PIfErrSec OBJECT-TYPE
   SYNTAX      Counter32
   MAX-ACCESS  read-only
   STATUS      current
   DESCRIPTION
      "Path: virtualEthernet.performance.vlan.mibCounters.d7Performance.ifErrSec

       32 bit unsigned wrappable counter."
   ::= {pr1646v2VEthVlanMCD7PEntry 251658240}

pr1646v2VEthVlanInPQs OBJECT-TYPE
   SYNTAX      SEQUENCE OF Pr1646v2VEthVlanInPQsEntry
   MAX-ACCESS  not-accessible
   STATUS      current
   DESCRIPTION
      ""
   ::= {pr1646v2VEthVlan 100663296}

pr1646v2VEthVlanInPQsEntry OBJECT-TYPE
   SYNTAX      Pr1646v2VEthVlanInPQsEntry
   MAX-ACCESS  not-accessible
   STATUS      current
   DESCRIPTION
      ""
   INDEX      { pr1646v2VEthVlanInPQsGlobalIx,
                pr1646v2VEthVlanTableIx,
                pr1646v2VEthVlanInPQsTableIx }
   ::= {pr1646v2VEthVlanInPQs 1}

Pr1646v2VEthVlanInPQsEntry ::=
   SEQUENCE
      {
      pr1646v2VEthVlanInPQsGlobalIx
         GlobalIndex,
      pr1646v2VEthVlanInPQsTableIx
         TableIndex,
      pr1646v2VEthVlanInPQsName
         INTEGER,
      pr1646v2VEthVlanInPQsLength
         Integer32,
      pr1646v2VEthVlanInPQsOctetLength
         Integer32,
      pr1646v2VEthVlanInPQsRedLength
         Integer32,
      pr1646v2VEthVlanInPQsPacketsTotal
         Counter64,
      pr1646v2VEthVlanInPQsPacketsDirectTx
         Counter64,
      pr1646v2VEthVlanInPQsPacketsQueued
         Counter64,
      pr1646v2VEthVlanInPQsPacketsDropped
         Counter64,
      pr1646v2VEthVlanInPQsPacketsRedDropped
         Counter64,
      pr1646v2VEthVlanInPQsPacketsCirTx
         Counter64,
      pr1646v2VEthVlanInPQsPacketsEirTx
         Counter64,
      pr1646v2VEthVlanInPQsPacketsViolateTx
         Counter64,
      pr1646v2VEthVlanInPQsOctetsTotal
         Counter64,
      pr1646v2VEthVlanInPQsOctetsDirectTx
         Counter64,
      pr1646v2VEthVlanInPQsOctetsQueued
         Counter64,
      pr1646v2VEthVlanInPQsOctetsDropped
         Counter64,
      pr1646v2VEthVlanInPQsOctetsRedDropped
         Counter64,
      pr1646v2VEthVlanInPQsOctetsCirTx
         Counter64,
      pr1646v2VEthVlanInPQsOctetsEirTx
         Counter64,
      pr1646v2VEthVlanInPQsOctetsViolateTx
         Counter64,
      pr1646v2VEthVlanInPQsOctetsBandwidth15sec
         Integer32,
      pr1646v2VEthVlanInPQsOctetsBandwidth30sec
         Integer32,
      pr1646v2VEthVlanInPQsOctetsBandwidth1min
         Integer32,
      pr1646v2VEthVlanInPQsOctetsBandwidth2min
         Integer32,
      pr1646v2VEthVlanInPQsOctetsBandwidth5min
         Integer32
      }

pr1646v2VEthVlanInPQsGlobalIx OBJECT-TYPE
   SYNTAX      GlobalIndex
   MAX-ACCESS  not-accessible
   STATUS      current
   DESCRIPTION
      "The value of the tlsCntTreeGlobalIndex of the MANAGED OBJECT."
   ::= {pr1646v2VEthVlanInPQsEntry 10}

pr1646v2VEthVlanInPQsTableIx OBJECT-TYPE
   SYNTAX      TableIndex
   MAX-ACCESS  not-accessible
   STATUS      current
   DESCRIPTION
      ""
   ::= {pr1646v2VEthVlanInPQsEntry 11}

pr1646v2VEthVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2VEthVlanInPQsEntry 16777216}

pr1646v2VEthVlanInPQsLength OBJECT-TYPE
   SYNTAX      Integer32
   MAX-ACCESS  read-only
   STATUS      current
   DESCRIPTION
      "Path: virtualEthernet.performance.vlan.inPriorityQueues.length"
   ::= {pr1646v2VEthVlanInPQsEntry 33554432}

pr1646v2VEthVlanInPQsOctetLength OBJECT-TYPE
   SYNTAX      Integer32
   MAX-ACCESS  read-only
   STATUS      current
   DESCRIPTION
      "Path: virtualEthernet.performance.vlan.inPriorityQueues.octetLength"
   ::= {pr1646v2VEthVlanInPQsEntry 150994944}

pr1646v2VEthVlanInPQsRedLength OBJECT-TYPE
   SYNTAX      Integer32
   MAX-ACCESS  read-only
   STATUS      current
   DESCRIPTION
      "Path: virtualEthernet.performance.vlan.inPriorityQueues.redLength"
   ::= {pr1646v2VEthVlanInPQsEntry 134217728}

pr1646v2VEthVlanInPQsPacketsTotal OBJECT-TYPE
   SYNTAX      Counter64
   MAX-ACCESS  read-only
   STATUS      current
   DESCRIPTION
      "Path: virtualEthernet.performance.vlan.inPriorityQueues.packets.total

       64 bit unsigned wrappable counter."
   ::= {pr1646v2VEthVlanInPQsEntry 50790400}

pr1646v2VEthVlanInPQsPacketsDirectTx OBJECT-TYPE
   SYNTAX      Counter64
   MAX-ACCESS  read-only
   STATUS      current
   DESCRIPTION
      "Path: virtualEthernet.performance.vlan.inPriorityQueues.packets.directTx

       64 bit unsigned wrappable counter."
   ::= {pr1646v2VEthVlanInPQsEntry 50397184}

pr1646v2VEthVlanInPQsPacketsQueued OBJECT-TYPE
   SYNTAX      Counter64
   MAX-ACCESS  read-only
   STATUS      current
   DESCRIPTION
      "Path: virtualEthernet.performance.vlan.inPriorityQueues.packets.queued

       64 bit unsigned wrappable counter."
   ::= {pr1646v2VEthVlanInPQsEntry 50462720}

pr1646v2VEthVlanInPQsPacketsDropped OBJECT-TYPE
   SYNTAX      Counter64
   MAX-ACCESS  read-only
   STATUS      current
   DESCRIPTION
      "Path: virtualEthernet.performance.vlan.inPriorityQueues.packets.dropped

       64 bit unsigned wrappable counter."
   ::= {pr1646v2VEthVlanInPQsEntry 50528256}

pr1646v2VEthVlanInPQsPacketsRedDropped OBJECT-TYPE
   SYNTAX      Counter64
   MAX-ACCESS  read-only
   STATUS      current
   DESCRIPTION
      "Path: virtualEthernet.performance.vlan.inPriorityQueues.packets.redDropped

       64 bit unsigned wrappable counter."
   ::= {pr1646v2VEthVlanInPQsEntry 50724864}

pr1646v2VEthVlanInPQsPacketsCirTx OBJECT-TYPE
   SYNTAX      Counter64
   MAX-ACCESS  read-only
   STATUS      current
   DESCRIPTION
      "Path: virtualEthernet.performance.vlan.inPriorityQueues.packets.cirTx

       64 bit unsigned wrappable counter."
   ::= {pr1646v2VEthVlanInPQsEntry 50593792}

pr1646v2VEthVlanInPQsPacketsEirTx OBJECT-TYPE
   SYNTAX      Counter64
   MAX-ACCESS  read-only
   STATUS      current
   DESCRIPTION
      "Path: virtualEthernet.performance.vlan.inPriorityQueues.packets.eirTx

       64 bit unsigned wrappable counter."
   ::= {pr1646v2VEthVlanInPQsEntry 50659328}

pr1646v2VEthVlanInPQsPacketsViolateTx OBJECT-TYPE
   SYNTAX      Counter64
   MAX-ACCESS  read-only
   STATUS      current
   DESCRIPTION
      "Path: virtualEthernet.performance.vlan.inPriorityQueues.packets.violateTx

       64 bit unsigned wrappable counter."
   ::= {pr1646v2VEthVlanInPQsEntry 50855936}

pr1646v2VEthVlanInPQsOctetsTotal OBJECT-TYPE
   SYNTAX      Counter64
   MAX-ACCESS  read-only
   STATUS      current
   DESCRIPTION
      "Path: virtualEthernet.performance.vlan.inPriorityQueues.octets.total

       64 bit unsigned wrappable counter."
   ::= {pr1646v2VEthVlanInPQsEntry 67567616}

pr1646v2VEthVlanInPQsOctetsDirectTx OBJECT-TYPE
   SYNTAX      Counter64
   MAX-ACCESS  read-only
   STATUS      current
   DESCRIPTION
      "Path: virtualEthernet.performance.vlan.inPriorityQueues.octets.directTx

       64 bit unsigned wrappable counter."
   ::= {pr1646v2VEthVlanInPQsEntry 67174400}

pr1646v2VEthVlanInPQsOctetsQueued OBJECT-TYPE
   SYNTAX      Counter64
   MAX-ACCESS  read-only
   STATUS      current
   DESCRIPTION
      "Path: virtualEthernet.performance.vlan.inPriorityQueues.octets.queued

       64 bit unsigned wrappable counter."
   ::= {pr1646v2VEthVlanInPQsEntry 67239936}

pr1646v2VEthVlanInPQsOctetsDropped OBJECT-TYPE
   SYNTAX      Counter64
   MAX-ACCESS  read-only
   STATUS      current
   DESCRIPTION
      "Path: virtualEthernet.performance.vlan.inPriorityQueues.octets.dropped

       64 bit unsigned wrappable counter."
   ::= {pr1646v2VEthVlanInPQsEntry 67305472}

pr1646v2VEthVlanInPQsOctetsRedDropped OBJECT-TYPE
   SYNTAX      Counter64
   MAX-ACCESS  read-only
   STATUS      current
   DESCRIPTION
      "Path: virtualEthernet.performance.vlan.inPriorityQueues.octets.redDropped

       64 bit unsigned wrappable counter."
   ::= {pr1646v2VEthVlanInPQsEntry 67502080}

pr1646v2VEthVlanInPQsOctetsCirTx OBJECT-TYPE
   SYNTAX      Counter64
   MAX-ACCESS  read-only
   STATUS      current
   DESCRIPTION
      "Path: virtualEthernet.performance.vlan.inPriorityQueues.octets.cirTx

       64 bit unsigned wrappable counter."
   ::= {pr1646v2VEthVlanInPQsEntry 67371008}

pr1646v2VEthVlanInPQsOctetsEirTx OBJECT-TYPE
   SYNTAX      Counter64
   MAX-ACCESS  read-only
   STATUS      current
   DESCRIPTION
      "Path: virtualEthernet.performance.vlan.inPriorityQueues.octets.eirTx

       64 bit unsigned wrappable counter."
   ::= {pr1646v2VEthVlanInPQsEntry 67436544}

pr1646v2VEthVlanInPQsOctetsViolateTx OBJECT-TYPE
   SYNTAX      Counter64
   MAX-ACCESS  read-only
   STATUS      current
   DESCRIPTION
      "Path: virtualEthernet.performance.vlan.inPriorityQueues.octets.violateTx

       64 bit unsigned wrappable counter."
   ::= {pr1646v2VEthVlanInPQsEntry 67633152}

pr1646v2VEthVlanInPQsOctetsBandwidth15sec OBJECT-TYPE
   SYNTAX      Integer32
   MAX-ACCESS  read-only
   STATUS      current
   DESCRIPTION
      "Path: virtualEthernet.performance.vlan.inPriorityQueues.octets.bandwidth.15sec

       unit name = bps
       formula = 8 * ; 8 /"
   ::= {pr1646v2VEthVlanInPQsEntry 70386944}

pr1646v2VEthVlanInPQsOctetsBandwidth30sec OBJECT-TYPE
   SYNTAX      Integer32
   MAX-ACCESS  read-only
   STATUS      current
   DESCRIPTION
      "Path: virtualEthernet.performance.vlan.inPriorityQueues.octets.bandwidth.30sec

       unit name = bps
       formula = 8 * ; 8 /"
   ::= {pr1646v2VEthVlanInPQsEntry 70388224}

pr1646v2VEthVlanInPQsOctetsBandwidth1min OBJECT-TYPE
   SYNTAX      Integer32
   MAX-ACCESS  read-only
   STATUS      current
   DESCRIPTION
      "Path: virtualEthernet.performance.vlan.inPriorityQueues.octets.bandwidth.1min

       unit name = bps
       formula = 8 * ; 8 /"
   ::= {pr1646v2VEthVlanInPQsEntry 70390784}

pr1646v2VEthVlanInPQsOctetsBandwidth2min OBJECT-TYPE
   SYNTAX      Integer32
   MAX-ACCESS  read-only
   STATUS      current
   DESCRIPTION
      "Path: virtualEthernet.performance.vlan.inPriorityQueues.octets.bandwidth.2min

       unit name = bps
       formula = 8 * ; 8 /"
   ::= {pr1646v2VEthVlanInPQsEntry 70395904}

pr1646v2VEthVlanInPQsOctetsBandwidth5min OBJECT-TYPE
   SYNTAX      Integer32
   MAX-ACCESS  read-only
   STATUS      current
   DESCRIPTION
      "Path: virtualEthernet.performance.vlan.inPriorityQueues.octets.bandwidth.5min

       unit name = bps
       formula = 8 * ; 8 /"
   ::= {pr1646v2VEthVlanInPQsEntry 70411264}

pr1646v2VEthVlanInPQsH2Performance OBJECT-TYPE
   SYNTAX      SEQUENCE OF Pr1646v2VEthVlanInPQsH2PerformanceEntry
   MAX-ACCESS  not-accessible
   STATUS      current
   DESCRIPTION
      ""
   ::= {pr1646v2VEthVlan 100990976}

pr1646v2VEthVlanInPQsH2PerformanceEntry OBJECT-TYPE
   SYNTAX      Pr1646v2VEthVlanInPQsH2PerformanceEntry
   MAX-ACCESS  not-accessible
   STATUS      current
   DESCRIPTION
      ""
   INDEX      { pr1646v2VEthVlanInPQsH2PerformanceGlobalIx,
                pr1646v2VEthVlanTableIx,
                pr1646v2VEthVlanInPQsTableIx,
                pr1646v2VEthVlanInPQsH2PerformanceTableIx }
   ::= {pr1646v2VEthVlanInPQsH2Performance 1}

Pr1646v2VEthVlanInPQsH2PerformanceEntry ::=
   SEQUENCE
      {
      pr1646v2VEthVlanInPQsH2PerformanceGlobalIx
         GlobalIndex,
      pr1646v2VEthVlanInPQsH2PerformanceTableIx
         TableIndex,
      pr1646v2VEthVlanInPQsH2PerformanceSysUpTime
         TimeTicks,
      pr1646v2VEthVlanInPQsH2PerformanceTotPkts
         Counter64,
      pr1646v2VEthVlanInPQsH2PerformanceDirTxPkts
         Counter64,
      pr1646v2VEthVlanInPQsH2PerformanceQdPkts
         Counter64,
      pr1646v2VEthVlanInPQsH2PerformanceDropPkts
         Counter64,
      pr1646v2VEthVlanInPQsH2PerformanceRDropPkts
         Counter64,
      pr1646v2VEthVlanInPQsH2PerformanceCirTxPkts
         Counter64,
      pr1646v2VEthVlanInPQsH2PerformanceEirTxPkts
         Counter64,
      pr1646v2VEthVlanInPQsH2PerformanceViolTxPkts
         Counter64,
      pr1646v2VEthVlanInPQsH2PerformanceTotOcts
         Counter64,
      pr1646v2VEthVlanInPQsH2PerformanceDirTxOcts
         Counter64,
      pr1646v2VEthVlanInPQsH2PerformanceQdOcts
         Counter64,
      pr1646v2VEthVlanInPQsH2PerformanceDropOcts
         Counter64,
      pr1646v2VEthVlanInPQsH2PerformanceRDropOcts
         Counter64,
      pr1646v2VEthVlanInPQsH2PerformanceCirTxOcts
         Counter64,
      pr1646v2VEthVlanInPQsH2PerformanceEirTxOcts
         Counter64,
      pr1646v2VEthVlanInPQsH2PerformanceViolTxOcts
         Counter64,
      pr1646v2VEthVlanInPQsH2PerformanceBandwidth
         Integer32
      }

pr1646v2VEthVlanInPQsH2PerformanceGlobalIx OBJECT-TYPE
   SYNTAX      GlobalIndex
   MAX-ACCESS  not-accessible
   STATUS      current
   DESCRIPTION
      "The value of the tlsCntTreeGlobalIndex of the MANAGED OBJECT."
   ::= {pr1646v2VEthVlanInPQsH2PerformanceEntry 10}

pr1646v2VEthVlanInPQsH2PerformanceTableIx OBJECT-TYPE
   SYNTAX      TableIndex
   MAX-ACCESS  not-accessible
   STATUS      current
   DESCRIPTION
      ""
   ::= {pr1646v2VEthVlanInPQsH2PerformanceEntry 11}

pr1646v2VEthVlanInPQsH2PerformanceSysUpTime OBJECT-TYPE
   SYNTAX      TimeTicks
   MAX-ACCESS  read-only
   STATUS      current
   DESCRIPTION
      "Path: virtualEthernet.performance.vlan.inPriorityQueues.h2Performance.sysUpTime

       Time in centi-second."
   ::= {pr1646v2VEthVlanInPQsH2PerformanceEntry 16777216}

pr1646v2VEthVlanInPQsH2PerformanceTotPkts OBJECT-TYPE
   SYNTAX      Counter64
   MAX-ACCESS  read-only
   STATUS      current
   DESCRIPTION
      "Path: virtualEthernet.performance.vlan.inPriorityQueues.h2Performance.totalPkts

       64 bit unsigned wrappable counter."
   ::= {pr1646v2VEthVlanInPQsH2PerformanceEntry 234881024}

pr1646v2VEthVlanInPQsH2PerformanceDirTxPkts OBJECT-TYPE
   SYNTAX      Counter64
   MAX-ACCESS  read-only
   STATUS      current
   DESCRIPTION
      "Path: virtualEthernet.performance.vlan.inPriorityQueues.h2Performance.directTxPkts

       64 bit unsigned wrappable counter."
   ::= {pr1646v2VEthVlanInPQsH2PerformanceEntry 33554432}

pr1646v2VEthVlanInPQsH2PerformanceQdPkts OBJECT-TYPE
   SYNTAX      Counter64
   MAX-ACCESS  read-only
   STATUS      current
   DESCRIPTION
      "Path: virtualEthernet.performance.vlan.inPriorityQueues.h2Performance.queuedPkts

       64 bit unsigned wrappable counter."
   ::= {pr1646v2VEthVlanInPQsH2PerformanceEntry 50331648}

pr1646v2VEthVlanInPQsH2PerformanceDropPkts OBJECT-TYPE
   SYNTAX      Counter64
   MAX-ACCESS  read-only
   STATUS      current
   DESCRIPTION
      "Path: virtualEthernet.performance.vlan.inPriorityQueues.h2Performance.droppedPkts

       64 bit unsigned wrappable counter."
   ::= {pr1646v2VEthVlanInPQsH2PerformanceEntry 67108864}

pr1646v2VEthVlanInPQsH2PerformanceRDropPkts OBJECT-TYPE
   SYNTAX      Counter64
   MAX-ACCESS  read-only
   STATUS      current
   DESCRIPTION
      "Path: virtualEthernet.performance.vlan.inPriorityQueues.h2Performance.redDroppedPkts

       64 bit unsigned wrappable counter."
   ::= {pr1646v2VEthVlanInPQsH2PerformanceEntry 201326592}

pr1646v2VEthVlanInPQsH2PerformanceCirTxPkts OBJECT-TYPE
   SYNTAX      Counter64
   MAX-ACCESS  read-only
   STATUS      current
   DESCRIPTION
      "Path: virtualEthernet.performance.vlan.inPriorityQueues.h2Performance.cirTxPkts

       64 bit unsigned wrappable counter."
   ::= {pr1646v2VEthVlanInPQsH2PerformanceEntry 83886080}

pr1646v2VEthVlanInPQsH2PerformanceEirTxPkts OBJECT-TYPE
   SYNTAX      Counter64
   MAX-ACCESS  read-only
   STATUS      current
   DESCRIPTION
      "Path: virtualEthernet.performance.vlan.inPriorityQueues.h2Performance.eirTxPkts

       64 bit unsigned wrappable counter."
   ::= {pr1646v2VEthVlanInPQsH2PerformanceEntry 100663296}

pr1646v2VEthVlanInPQsH2PerformanceViolTxPkts OBJECT-TYPE
   SYNTAX      Counter64
   MAX-ACCESS  read-only
   STATUS      current
   DESCRIPTION
      "Path: virtualEthernet.performance.vlan.inPriorityQueues.h2Performance.violateTxPkts

       64 bit unsigned wrappable counter."
   ::= {pr1646v2VEthVlanInPQsH2PerformanceEntry 301989888}

pr1646v2VEthVlanInPQsH2PerformanceTotOcts OBJECT-TYPE
   SYNTAX      Counter64
   MAX-ACCESS  read-only
   STATUS      current
   DESCRIPTION
      "Path: virtualEthernet.performance.vlan.inPriorityQueues.h2Performance.totalOctets

       64 bit unsigned wrappable counter."
   ::= {pr1646v2VEthVlanInPQsH2PerformanceEntry 251658240}

pr1646v2VEthVlanInPQsH2PerformanceDirTxOcts OBJECT-TYPE
   SYNTAX      Counter64
   MAX-ACCESS  read-only
   STATUS      current
   DESCRIPTION
      "Path: virtualEthernet.performance.vlan.inPriorityQueues.h2Performance.directTxOctets

       64 bit unsigned wrappable counter."
   ::= {pr1646v2VEthVlanInPQsH2PerformanceEntry 117440512}

pr1646v2VEthVlanInPQsH2PerformanceQdOcts OBJECT-TYPE
   SYNTAX      Counter64
   MAX-ACCESS  read-only
   STATUS      current
   DESCRIPTION
      "Path: virtualEthernet.performance.vlan.inPriorityQueues.h2Performance.queuedOctets

       64 bit unsigned wrappable counter."
   ::= {pr1646v2VEthVlanInPQsH2PerformanceEntry 134217728}

pr1646v2VEthVlanInPQsH2PerformanceDropOcts OBJECT-TYPE
   SYNTAX      Counter64
   MAX-ACCESS  read-only
   STATUS      current
   DESCRIPTION
      "Path: virtualEthernet.performance.vlan.inPriorityQueues.h2Performance.droppedOctets

       64 bit unsigned wrappable counter."
   ::= {pr1646v2VEthVlanInPQsH2PerformanceEntry 150994944}

pr1646v2VEthVlanInPQsH2PerformanceRDropOcts OBJECT-TYPE
   SYNTAX      Counter64
   MAX-ACCESS  read-only
   STATUS      current
   DESCRIPTION
      "Path: virtualEthernet.performance.vlan.inPriorityQueues.h2Performance.redDroppedOctets

       64 bit unsigned wrappable counter."
   ::= {pr1646v2VEthVlanInPQsH2PerformanceEntry 218103808}

pr1646v2VEthVlanInPQsH2PerformanceCirTxOcts OBJECT-TYPE
   SYNTAX      Counter64
   MAX-ACCESS  read-only
   STATUS      current
   DESCRIPTION
      "Path: virtualEthernet.performance.vlan.inPriorityQueues.h2Performance.cirTxOctets

       64 bit unsigned wrappable counter."
   ::= {pr1646v2VEthVlanInPQsH2PerformanceEntry 167772160}

pr1646v2VEthVlanInPQsH2PerformanceEirTxOcts OBJECT-TYPE
   SYNTAX      Counter64
   MAX-ACCESS  read-only
   STATUS      current
   DESCRIPTION
      "Path: virtualEthernet.performance.vlan.inPriorityQueues.h2Performance.eirTxOctets

       64 bit unsigned wrappable counter."
   ::= {pr1646v2VEthVlanInPQsH2PerformanceEntry 184549376}

pr1646v2VEthVlanInPQsH2PerformanceViolTxOcts OBJECT-TYPE
   SYNTAX      Counter64
   MAX-ACCESS  read-only
   STATUS      current
   DESCRIPTION
      "Path: virtualEthernet.performance.vlan.inPriorityQueues.h2Performance.violateTxOctets

       64 bit unsigned wrappable counter."
   ::= {pr1646v2VEthVlanInPQsH2PerformanceEntry 318767104}

pr1646v2VEthVlanInPQsH2PerformanceBandwidth OBJECT-TYPE
   SYNTAX      Integer32
   MAX-ACCESS  read-only
   STATUS      current
   DESCRIPTION
      "Path: virtualEthernet.performance.vlan.inPriorityQueues.h2Performance.bandwidth

       unit name = bps
       formula = 8 * ; 8 /"
   ::= {pr1646v2VEthVlanInPQsH2PerformanceEntry 268435456}

pr1646v2VEthVlanInPQsH24Performance OBJECT-TYPE
   SYNTAX      SEQUENCE OF Pr1646v2VEthVlanInPQsH24PerformanceEntry
   MAX-ACCESS  not-accessible
   STATUS      current
   DESCRIPTION
      ""
   ::= {pr1646v2VEthVlan 101056512}

pr1646v2VEthVlanInPQsH24PerformanceEntry OBJECT-TYPE
   SYNTAX      Pr1646v2VEthVlanInPQsH24PerformanceEntry
   MAX-ACCESS  not-accessible
   STATUS      current
   DESCRIPTION
      ""
   INDEX      { pr1646v2VEthVlanInPQsH24PerformanceGlobalIx,
                pr1646v2VEthVlanTableIx,
                pr1646v2VEthVlanInPQsTableIx,
                pr1646v2VEthVlanInPQsH24PerformanceTableIx }
   ::= {pr1646v2VEthVlanInPQsH24Performance 1}

Pr1646v2VEthVlanInPQsH24PerformanceEntry ::=
   SEQUENCE
      {
      pr1646v2VEthVlanInPQsH24PerformanceGlobalIx
         GlobalIndex,
      pr1646v2VEthVlanInPQsH24PerformanceTableIx
         TableIndex,
      pr1646v2VEthVlanInPQsH24PerformanceSysUpTime
         TimeTicks,
      pr1646v2VEthVlanInPQsH24PerformanceTotPkts
         Counter64,
      pr1646v2VEthVlanInPQsH24PerformanceDirTxPkts
         Counter64,
      pr1646v2VEthVlanInPQsH24PerformanceQdPkts
         Counter64,
      pr1646v2VEthVlanInPQsH24PerformanceDropPkts
         Counter64,
      pr1646v2VEthVlanInPQsH24PerformanceRDropPkts
         Counter64,
      pr1646v2VEthVlanInPQsH24PerformanceCirTxPkts
         Counter64,
      pr1646v2VEthVlanInPQsH24PerformanceEirTxPkts
         Counter64,
      pr1646v2VEthVlanInPQsH24PerformanceViolTxPkts
         Counter64,
      pr1646v2VEthVlanInPQsH24PerformanceTotOcts
         Counter64,
      pr1646v2VEthVlanInPQsH24PerformanceDirTxOcts
         Counter64,
      pr1646v2VEthVlanInPQsH24PerformanceQdOcts
         Counter64,
      pr1646v2VEthVlanInPQsH24PerformanceDropOcts
         Counter64,
      pr1646v2VEthVlanInPQsH24PerformanceRDropOcts
         Counter64,
      pr1646v2VEthVlanInPQsH24PerformanceCirTxOcts
         Counter64,
      pr1646v2VEthVlanInPQsH24PerformanceEirTxOcts
         Counter64,
      pr1646v2VEthVlanInPQsH24PerformanceViolTxOcts
         Counter64,
      pr1646v2VEthVlanInPQsH24PerformanceBandwidth
         Integer32
      }

pr1646v2VEthVlanInPQsH24PerformanceGlobalIx OBJECT-TYPE
   SYNTAX      GlobalIndex
   MAX-ACCESS  not-accessible
   STATUS      current
   DESCRIPTION
      "The value of the tlsCntTreeGlobalIndex of the MANAGED OBJECT."
   ::= {pr1646v2VEthVlanInPQsH24PerformanceEntry 10}

pr1646v2VEthVlanInPQsH24PerformanceTableIx OBJECT-TYPE
   SYNTAX      TableIndex
   MAX-ACCESS  not-accessible
   STATUS      current
   DESCRIPTION
      ""
   ::= {pr1646v2VEthVlanInPQsH24PerformanceEntry 11}

pr1646v2VEthVlanInPQsH24PerformanceSysUpTime OBJECT-TYPE
   SYNTAX      TimeTicks
   MAX-ACCESS  read-only
   STATUS      current
   DESCRIPTION
      "Path: virtualEthernet.performance.vlan.inPriorityQueues.h24Performance.sysUpTime

       Time in centi-second."
   ::= {pr1646v2VEthVlanInPQsH24PerformanceEntry 16777216}

pr1646v2VEthVlanInPQsH24PerformanceTotPkts OBJECT-TYPE
   SYNTAX      Counter64
   MAX-ACCESS  read-only
   STATUS      current
   DESCRIPTION
      "Path: virtualEthernet.performance.vlan.inPriorityQueues.h24Performance.totalPkts

       64 bit unsigned wrappable counter."
   ::= {pr1646v2VEthVlanInPQsH24PerformanceEntry 234881024}

pr1646v2VEthVlanInPQsH24PerformanceDirTxPkts OBJECT-TYPE
   SYNTAX      Counter64
   MAX-ACCESS  read-only
   STATUS      current
   DESCRIPTION
      "Path: virtualEthernet.performance.vlan.inPriorityQueues.h24Performance.directTxPkts

       64 bit unsigned wrappable counter."
   ::= {pr1646v2VEthVlanInPQsH24PerformanceEntry 33554432}

pr1646v2VEthVlanInPQsH24PerformanceQdPkts OBJECT-TYPE
   SYNTAX      Counter64
   MAX-ACCESS  read-only
   STATUS      current
   DESCRIPTION
      "Path: virtualEthernet.performance.vlan.inPriorityQueues.h24Performance.queuedPkts

       64 bit unsigned wrappable counter."
   ::= {pr1646v2VEthVlanInPQsH24PerformanceEntry 50331648}

pr1646v2VEthVlanInPQsH24PerformanceDropPkts OBJECT-TYPE
   SYNTAX      Counter64
   MAX-ACCESS  read-only
   STATUS      current
   DESCRIPTION
      "Path: virtualEthernet.performance.vlan.inPriorityQueues.h24Performance.droppedPkts

       64 bit unsigned wrappable counter."
   ::= {pr1646v2VEthVlanInPQsH24PerformanceEntry 67108864}

pr1646v2VEthVlanInPQsH24PerformanceRDropPkts OBJECT-TYPE
   SYNTAX      Counter64
   MAX-ACCESS  read-only
   STATUS      current
   DESCRIPTION
      "Path: virtualEthernet.performance.vlan.inPriorityQueues.h24Performance.redDroppedPkts

       64 bit unsigned wrappable counter."
   ::= {pr1646v2VEthVlanInPQsH24PerformanceEntry 201326592}

pr1646v2VEthVlanInPQsH24PerformanceCirTxPkts OBJECT-TYPE
   SYNTAX      Counter64
   MAX-ACCESS  read-only
   STATUS      current
   DESCRIPTION
      "Path: virtualEthernet.performance.vlan.inPriorityQueues.h24Performance.cirTxPkts

       64 bit unsigned wrappable counter."
   ::= {pr1646v2VEthVlanInPQsH24PerformanceEntry 83886080}

pr1646v2VEthVlanInPQsH24PerformanceEirTxPkts OBJECT-TYPE
   SYNTAX      Counter64
   MAX-ACCESS  read-only
   STATUS      current
   DESCRIPTION
      "Path: virtualEthernet.performance.vlan.inPriorityQueues.h24Performance.eirTxPkts

       64 bit unsigned wrappable counter."
   ::= {pr1646v2VEthVlanInPQsH24PerformanceEntry 100663296}

pr1646v2VEthVlanInPQsH24PerformanceViolTxPkts OBJECT-TYPE
   SYNTAX      Counter64
   MAX-ACCESS  read-only
   STATUS      current
   DESCRIPTION
      "Path: virtualEthernet.performance.vlan.inPriorityQueues.h24Performance.violateTxPkts

       64 bit unsigned wrappable counter."
   ::= {pr1646v2VEthVlanInPQsH24PerformanceEntry 301989888}

pr1646v2VEthVlanInPQsH24PerformanceTotOcts OBJECT-TYPE
   SYNTAX      Counter64
   MAX-ACCESS  read-only
   STATUS      current
   DESCRIPTION
      "Path: virtualEthernet.performance.vlan.inPriorityQueues.h24Performance.totalOctets

       64 bit unsigned wrappable counter."
   ::= {pr1646v2VEthVlanInPQsH24PerformanceEntry 251658240}

pr1646v2VEthVlanInPQsH24PerformanceDirTxOcts OBJECT-TYPE
   SYNTAX      Counter64
   MAX-ACCESS  read-only
   STATUS      current
   DESCRIPTION
      "Path: virtualEthernet.performance.vlan.inPriorityQueues.h24Performance.directTxOctets

       64 bit unsigned wrappable counter."
   ::= {pr1646v2VEthVlanInPQsH24PerformanceEntry 117440512}

pr1646v2VEthVlanInPQsH24PerformanceQdOcts OBJECT-TYPE
   SYNTAX      Counter64
   MAX-ACCESS  read-only
   STATUS      current
   DESCRIPTION
      "Path: virtualEthernet.performance.vlan.inPriorityQueues.h24Performance.queuedOctets

       64 bit unsigned wrappable counter."
   ::= {pr1646v2VEthVlanInPQsH24PerformanceEntry 134217728}

pr1646v2VEthVlanInPQsH24PerformanceDropOcts OBJECT-TYPE
   SYNTAX      Counter64
   MAX-ACCESS  read-only
   STATUS      current
   DESCRIPTION
      "Path: virtualEthernet.performance.vlan.inPriorityQueues.h24Performance.droppedOctets

       64 bit unsigned wrappable counter."
   ::= {pr1646v2VEthVlanInPQsH24PerformanceEntry 150994944}

pr1646v2VEthVlanInPQsH24PerformanceRDropOcts OBJECT-TYPE
   SYNTAX      Counter64
   MAX-ACCESS  read-only
   STATUS      current
   DESCRIPTION
      "Path: virtualEthernet.performance.vlan.inPriorityQueues.h24Performance.redDroppedOctets

       64 bit unsigned wrappable counter."
   ::= {pr1646v2VEthVlanInPQsH24PerformanceEntry 218103808}

pr1646v2VEthVlanInPQsH24PerformanceCirTxOcts OBJECT-TYPE
   SYNTAX      Counter64
   MAX-ACCESS  read-only
   STATUS      current
   DESCRIPTION
      "Path: virtualEthernet.performance.vlan.inPriorityQueues.h24Performance.cirTxOctets

       64 bit unsigned wrappable counter."
   ::= {pr1646v2VEthVlanInPQsH24PerformanceEntry 167772160}

pr1646v2VEthVlanInPQsH24PerformanceEirTxOcts OBJECT-TYPE
   SYNTAX      Counter64
   MAX-ACCESS  read-only
   STATUS      current
   DESCRIPTION
      "Path: virtualEthernet.performance.vlan.inPriorityQueues.h24Performance.eirTxOctets

       64 bit unsigned wrappable counter."
   ::= {pr1646v2VEthVlanInPQsH24PerformanceEntry 184549376}

pr1646v2VEthVlanInPQsH24PerformanceViolTxOcts OBJECT-TYPE
   SYNTAX      Counter64
   MAX-ACCESS  read-only
   STATUS      current
   DESCRIPTION
      "Path: virtualEthernet.performance.vlan.inPriorityQueues.h24Performance.violateTxOctets

       64 bit unsigned wrappable counter."
   ::= {pr1646v2VEthVlanInPQsH24PerformanceEntry 318767104}

pr1646v2VEthVlanInPQsH24PerformanceBandwidth OBJECT-TYPE
   SYNTAX      Integer32
   MAX-ACCESS  read-only
   STATUS      current
   DESCRIPTION
      "Path: virtualEthernet.performance.vlan.inPriorityQueues.h24Performance.bandwidth

       unit name = bps
       formula = 8 * ; 8 /"
   ::= {pr1646v2VEthVlanInPQsH24PerformanceEntry 268435456}

pr1646v2VEthVlanInPQsD7Performance OBJECT-TYPE
   SYNTAX      SEQUENCE OF Pr1646v2VEthVlanInPQsD7PerformanceEntry
   MAX-ACCESS  not-accessible
   STATUS      current
   DESCRIPTION
      ""
   ::= {pr1646v2VEthVlan 101122048}

pr1646v2VEthVlanInPQsD7PerformanceEntry OBJECT-TYPE
   SYNTAX      Pr1646v2VEthVlanInPQsD7PerformanceEntry
   MAX-ACCESS  not-accessible
   STATUS      current
   DESCRIPTION
      ""
   INDEX      { pr1646v2VEthVlanInPQsD7PerformanceGlobalIx,
                pr1646v2VEthVlanTableIx,
                pr1646v2VEthVlanInPQsTableIx,
                pr1646v2VEthVlanInPQsD7PerformanceTableIx }
   ::= {pr1646v2VEthVlanInPQsD7Performance 1}

Pr1646v2VEthVlanInPQsD7PerformanceEntry ::=
   SEQUENCE
      {
      pr1646v2VEthVlanInPQsD7PerformanceGlobalIx
         GlobalIndex,
      pr1646v2VEthVlanInPQsD7PerformanceTableIx
         TableIndex,
      pr1646v2VEthVlanInPQsD7PerformanceSysUpTime
         TimeTicks,
      pr1646v2VEthVlanInPQsD7PerformanceTotPkts
         Counter64,
      pr1646v2VEthVlanInPQsD7PerformanceDirTxPkts
         Counter64,
      pr1646v2VEthVlanInPQsD7PerformanceQdPkts
         Counter64,
      pr1646v2VEthVlanInPQsD7PerformanceDropPkts
         Counter64,
      pr1646v2VEthVlanInPQsD7PerformanceRDropPkts
         Counter64,
      pr1646v2VEthVlanInPQsD7PerformanceCirTxPkts
         Counter64,
      pr1646v2VEthVlanInPQsD7PerformanceEirTxPkts
         Counter64,
      pr1646v2VEthVlanInPQsD7PerformanceViolTxPkts
         Counter64,
      pr1646v2VEthVlanInPQsD7PerformanceTotOcts
         Counter64,
      pr1646v2VEthVlanInPQsD7PerformanceDirTxOcts
         Counter64,
      pr1646v2VEthVlanInPQsD7PerformanceQdOcts
         Counter64,
      pr1646v2VEthVlanInPQsD7PerformanceDropOcts
         Counter64,
      pr1646v2VEthVlanInPQsD7PerformanceRDropOcts
         Counter64,
      pr1646v2VEthVlanInPQsD7PerformanceCirTxOcts
         Counter64,
      pr1646v2VEthVlanInPQsD7PerformanceEirTxOcts
         Counter64,
      pr1646v2VEthVlanInPQsD7PerformanceViolTxOcts
         Counter64,
      pr1646v2VEthVlanInPQsD7PerformanceBandwidth
         Integer32
      }

pr1646v2VEthVlanInPQsD7PerformanceGlobalIx OBJECT-TYPE
   SYNTAX      GlobalIndex
   MAX-ACCESS  not-accessible
   STATUS      current
   DESCRIPTION
      "The value of the tlsCntTreeGlobalIndex of the MANAGED OBJECT."
   ::= {pr1646v2VEthVlanInPQsD7PerformanceEntry 10}

pr1646v2VEthVlanInPQsD7PerformanceTableIx OBJECT-TYPE
   SYNTAX      TableIndex
   MAX-ACCESS  not-accessible
   STATUS      current
   DESCRIPTION
      ""
   ::= {pr1646v2VEthVlanInPQsD7PerformanceEntry 11}

pr1646v2VEthVlanInPQsD7PerformanceSysUpTime OBJECT-TYPE
   SYNTAX      TimeTicks
   MAX-ACCESS  read-only
   STATUS      current
   DESCRIPTION
      "Path: virtualEthernet.performance.vlan.inPriorityQueues.d7Performance.sysUpTime

       Time in centi-second."
   ::= {pr1646v2VEthVlanInPQsD7PerformanceEntry 16777216}

pr1646v2VEthVlanInPQsD7PerformanceTotPkts OBJECT-TYPE
   SYNTAX      Counter64
   MAX-ACCESS  read-only
   STATUS      current
   DESCRIPTION
      "Path: virtualEthernet.performance.vlan.inPriorityQueues.d7Performance.totalPkts

       64 bit unsigned wrappable counter."
   ::= {pr1646v2VEthVlanInPQsD7PerformanceEntry 234881024}

pr1646v2VEthVlanInPQsD7PerformanceDirTxPkts OBJECT-TYPE
   SYNTAX      Counter64
   MAX-ACCESS  read-only
   STATUS      current
   DESCRIPTION
      "Path: virtualEthernet.performance.vlan.inPriorityQueues.d7Performance.directTxPkts

       64 bit unsigned wrappable counter."
   ::= {pr1646v2VEthVlanInPQsD7PerformanceEntry 33554432}

pr1646v2VEthVlanInPQsD7PerformanceQdPkts OBJECT-TYPE
   SYNTAX      Counter64
   MAX-ACCESS  read-only
   STATUS      current
   DESCRIPTION
      "Path: virtualEthernet.performance.vlan.inPriorityQueues.d7Performance.queuedPkts

       64 bit unsigned wrappable counter."
   ::= {pr1646v2VEthVlanInPQsD7PerformanceEntry 50331648}

pr1646v2VEthVlanInPQsD7PerformanceDropPkts OBJECT-TYPE
   SYNTAX      Counter64
   MAX-ACCESS  read-only
   STATUS      current
   DESCRIPTION
      "Path: virtualEthernet.performance.vlan.inPriorityQueues.d7Performance.droppedPkts

       64 bit unsigned wrappable counter."
   ::= {pr1646v2VEthVlanInPQsD7PerformanceEntry 67108864}

pr1646v2VEthVlanInPQsD7PerformanceRDropPkts OBJECT-TYPE
   SYNTAX      Counter64
   MAX-ACCESS  read-only
   STATUS      current
   DESCRIPTION
      "Path: virtualEthernet.performance.vlan.inPriorityQueues.d7Performance.redDroppedPkts

       64 bit unsigned wrappable counter."
   ::= {pr1646v2VEthVlanInPQsD7PerformanceEntry 201326592}

pr1646v2VEthVlanInPQsD7PerformanceCirTxPkts OBJECT-TYPE
   SYNTAX      Counter64
   MAX-ACCESS  read-only
   STATUS      current
   DESCRIPTION
      "Path: virtualEthernet.performance.vlan.inPriorityQueues.d7Performance.cirTxPkts

       64 bit unsigned wrappable counter."
   ::= {pr1646v2VEthVlanInPQsD7PerformanceEntry 83886080}

pr1646v2VEthVlanInPQsD7PerformanceEirTxPkts OBJECT-TYPE
   SYNTAX      Counter64
   MAX-ACCESS  read-only
   STATUS      current
   DESCRIPTION
      "Path: virtualEthernet.performance.vlan.inPriorityQueues.d7Performance.eirTxPkts

       64 bit unsigned wrappable counter."
   ::= {pr1646v2VEthVlanInPQsD7PerformanceEntry 100663296}

pr1646v2VEthVlanInPQsD7PerformanceViolTxPkts OBJECT-TYPE
   SYNTAX      Counter64
   MAX-ACCESS  read-only
   STATUS      current
   DESCRIPTION
      "Path: virtualEthernet.performance.vlan.inPriorityQueues.d7Performance.violateTxPkts

       64 bit unsigned wrappable counter."
   ::= {pr1646v2VEthVlanInPQsD7PerformanceEntry 301989888}

pr1646v2VEthVlanInPQsD7PerformanceTotOcts OBJECT-TYPE
   SYNTAX      Counter64
   MAX-ACCESS  read-only
   STATUS      current
   DESCRIPTION
      "Path: virtualEthernet.performance.vlan.inPriorityQueues.d7Performance.totalOctets

       64 bit unsigned wrappable counter."
   ::= {pr1646v2VEthVlanInPQsD7PerformanceEntry 251658240}

pr1646v2VEthVlanInPQsD7PerformanceDirTxOcts OBJECT-TYPE
   SYNTAX      Counter64
   MAX-ACCESS  read-only
   STATUS      current
   DESCRIPTION
      "Path: virtualEthernet.performance.vlan.inPriorityQueues.d7Performance.directTxOctets

       64 bit unsigned wrappable counter."
   ::= {pr1646v2VEthVlanInPQsD7PerformanceEntry 117440512}

pr1646v2VEthVlanInPQsD7PerformanceQdOcts OBJECT-TYPE
   SYNTAX      Counter64
   MAX-ACCESS  read-only
   STATUS      current
   DESCRIPTION
      "Path: virtualEthernet.performance.vlan.inPriorityQueues.d7Performance.queuedOctets

       64 bit unsigned wrappable counter."
   ::= {pr1646v2VEthVlanInPQsD7PerformanceEntry 134217728}

pr1646v2VEthVlanInPQsD7PerformanceDropOcts OBJECT-TYPE
   SYNTAX      Counter64
   MAX-ACCESS  read-only
   STATUS      current
   DESCRIPTION
      "Path: virtualEthernet.performance.vlan.inPriorityQueues.d7Performance.droppedOctets

       64 bit unsigned wrappable counter."
   ::= {pr1646v2VEthVlanInPQsD7PerformanceEntry 150994944}

pr1646v2VEthVlanInPQsD7PerformanceRDropOcts OBJECT-TYPE
   SYNTAX      Counter64
   MAX-ACCESS  read-only
   STATUS      current
   DESCRIPTION
      "Path: virtualEthernet.performance.vlan.inPriorityQueues.d7Performance.redDroppedOctets

       64 bit unsigned wrappable counter."
   ::= {pr1646v2VEthVlanInPQsD7PerformanceEntry 218103808}

pr1646v2VEthVlanInPQsD7PerformanceCirTxOcts OBJECT-TYPE
   SYNTAX      Counter64
   MAX-ACCESS  read-only
   STATUS      current
   DESCRIPTION
      "Path: virtualEthernet.performance.vlan.inPriorityQueues.d7Performance.cirTxOctets

       64 bit unsigned wrappable counter."
   ::= {pr1646v2VEthVlanInPQsD7PerformanceEntry 167772160}

pr1646v2VEthVlanInPQsD7PerformanceEirTxOcts OBJECT-TYPE
   SYNTAX      Counter64
   MAX-ACCESS  read-only
   STATUS      current
   DESCRIPTION
      "Path: virtualEthernet.performance.vlan.inPriorityQueues.d7Performance.eirTxOctets

       64 bit unsigned wrappable counter."
   ::= {pr1646v2VEthVlanInPQsD7PerformanceEntry 184549376}

pr1646v2VEthVlanInPQsD7PerformanceViolTxOcts OBJECT-TYPE
   SYNTAX      Counter64
   MAX-ACCESS  read-only
   STATUS      current
   DESCRIPTION
      "Path: virtualEthernet.performance.vlan.inPriorityQueues.d7Performance.violateTxOctets

       64 bit unsigned wrappable counter."
   ::= {pr1646v2VEthVlanInPQsD7PerformanceEntry 318767104}

pr1646v2VEthVlanInPQsD7PerformanceBandwidth OBJECT-TYPE
   SYNTAX      Integer32
   MAX-ACCESS  read-only
   STATUS      current
   DESCRIPTION
      "Path: virtualEthernet.performance.vlan.inPriorityQueues.d7Performance.bandwidth

       unit name = bps
       formula = 8 * ; 8 /"
   ::= {pr1646v2VEthVlanInPQsD7PerformanceEntry 268435456}

pr1646v2VEthVlanOutPQs OBJECT-TYPE
   SYNTAX      SEQUENCE OF Pr1646v2VEthVlanOutPQsEntry
   MAX-ACCESS  not-accessible
   STATUS      current
   DESCRIPTION
      ""
   ::= {pr1646v2VEthVlan 83886080}

pr1646v2VEthVlanOutPQsEntry OBJECT-TYPE
   SYNTAX      Pr1646v2VEthVlanOutPQsEntry
   MAX-ACCESS  not-accessible
   STATUS      current
   DESCRIPTION
      ""
   INDEX      { pr1646v2VEthVlanOutPQsGlobalIx,
                pr1646v2VEthVlanTableIx,
                pr1646v2VEthVlanOutPQsTableIx }
   ::= {pr1646v2VEthVlanOutPQs 1}

Pr1646v2VEthVlanOutPQsEntry ::=
   SEQUENCE
      {
      pr1646v2VEthVlanOutPQsGlobalIx
         GlobalIndex,
      pr1646v2VEthVlanOutPQsTableIx
         TableIndex,
      pr1646v2VEthVlanOutPQsName
         INTEGER,
      pr1646v2VEthVlanOutPQsLength
         Integer32,
      pr1646v2VEthVlanOutPQsOctetLength
         Integer32,
      pr1646v2VEthVlanOutPQsRedLength
         Integer32,
      pr1646v2VEthVlanOutPQsPacketsTotal
         Counter64,
      pr1646v2VEthVlanOutPQsPacketsDirectTx
         Counter64,
      pr1646v2VEthVlanOutPQsPacketsQueued
         Counter64,
      pr1646v2VEthVlanOutPQsPacketsDropped
         Counter64,
      pr1646v2VEthVlanOutPQsPacketsRedDropped
         Counter64,
      pr1646v2VEthVlanOutPQsPacketsCirTx
         Counter64,
      pr1646v2VEthVlanOutPQsPacketsEirTx
         Counter64,
      pr1646v2VEthVlanOutPQsPacketsViolateTx
         Counter64,
      pr1646v2VEthVlanOutPQsOctetsTotal
         Counter64,
      pr1646v2VEthVlanOutPQsOctetsDirectTx
         Counter64,
      pr1646v2VEthVlanOutPQsOctetsQueued
         Counter64,
      pr1646v2VEthVlanOutPQsOctetsDropped
         Counter64,
      pr1646v2VEthVlanOutPQsOctetsRedDropped
         Counter64,
      pr1646v2VEthVlanOutPQsOctetsCirTx
         Counter64,
      pr1646v2VEthVlanOutPQsOctetsEirTx
         Counter64,
      pr1646v2VEthVlanOutPQsOctetsViolateTx
         Counter64,
      pr1646v2VEthVlanOutPQsOctetsBandwidth15sec
         Integer32,
      pr1646v2VEthVlanOutPQsOctetsBandwidth30sec
         Integer32,
      pr1646v2VEthVlanOutPQsOctetsBandwidth1min
         Integer32,
      pr1646v2VEthVlanOutPQsOctetsBandwidth2min
         Integer32,
      pr1646v2VEthVlanOutPQsOctetsBandwidth5min
         Integer32
      }

pr1646v2VEthVlanOutPQsGlobalIx OBJECT-TYPE
   SYNTAX      GlobalIndex
   MAX-ACCESS  not-accessible
   STATUS      current
   DESCRIPTION
      "The value of the tlsCntTreeGlobalIndex of the MANAGED OBJECT."
   ::= {pr1646v2VEthVlanOutPQsEntry 10}

pr1646v2VEthVlanOutPQsTableIx OBJECT-TYPE
   SYNTAX      TableIndex
   MAX-ACCESS  not-accessible
   STATUS      current
   DESCRIPTION
      ""
   ::= {pr1646v2VEthVlanOutPQsEntry 11}

pr1646v2VEthVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: virtualEthernet.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1646v2VEthVlanOutPQsEntry 16777216}

pr1646v2VEthVlanOutPQsLength OBJECT-TYPE
   SYNTAX      Integer32
   MAX-ACCESS  read-only
   STATUS      current
   DESCRIPTION
      "Path: virtualEthernet.performance.vlan.outPriorityQueues.length"
   ::= {pr1646v2VEthVlanOutPQsEntry 33554432}

pr1646v2VEthVlanOutPQsOctetLength OBJECT-TYPE
   SYNTAX      Integer32
   MAX-ACCESS  read-only
   STATUS      current
   DESCRIPTION
      "Path: virtualEthernet.performance.vlan.outPriorityQueues.octetLength"
   ::= {pr1646v2VEthVlanOutPQsEntry 150994944}

pr1646v2VEthVlanOutPQsRedLength OBJECT-TYPE
   SYNTAX      Integer32
   MAX-ACCESS  read-only
   STATUS      current
   DESCRIPTION
      "Path: virtualEthernet.performance.vlan.outPriorityQueues.redLength"
   ::= {pr1646v2VEthVlanOutPQsEntry 134217728}

pr1646v2VEthVlanOutPQsPacketsTotal OBJECT-TYPE
   SYNTAX      Counter64
   MAX-ACCESS  read-only
   STATUS      current
   DESCRIPTION
      "Path: virtualEthernet.performance.vlan.outPriorityQueues.packets.total

       64 bit unsigned wrappable counter."
   ::= {pr1646v2VEthVlanOutPQsEntry 50790400}

pr1646v2VEthVlanOutPQsPacketsDirectTx OBJECT-TYPE
   SYNTAX      Counter64
   MAX-ACCESS  read-only
   STATUS      current
   DESCRIPTION
      "Path: virtualEthernet.performance.vlan.outPriorityQueues.packets.directTx

       64 bit unsigned wrappable counter."
   ::= {pr1646v2VEthVlanOutPQsEntry 50397184}

pr1646v2VEthVlanOutPQsPacketsQueued OBJECT-TYPE
   SYNTAX      Counter64
   MAX-ACCESS  read-only
   STATUS      current
   DESCRIPTION
      "Path: virtualEthernet.performance.vlan.outPriorityQueues.packets.queued

       64 bit unsigned wrappable counter."
   ::= {pr1646v2VEthVlanOutPQsEntry 50462720}

pr1646v2VEthVlanOutPQsPacketsDropped OBJECT-TYPE
   SYNTAX      Counter64
   MAX-ACCESS  read-only
   STATUS      current
   DESCRIPTION
      "Path: virtualEthernet.performance.vlan.outPriorityQueues.packets.dropped

       64 bit unsigned wrappable counter."
   ::= {pr1646v2VEthVlanOutPQsEntry 50528256}

pr1646v2VEthVlanOutPQsPacketsRedDropped OBJECT-TYPE
   SYNTAX      Counter64
   MAX-ACCESS  read-only
   STATUS      current
   DESCRIPTION
      "Path: virtualEthernet.performance.vlan.outPriorityQueues.packets.redDropped

       64 bit unsigned wrappable counter."
   ::= {pr1646v2VEthVlanOutPQsEntry 50724864}

pr1646v2VEthVlanOutPQsPacketsCirTx OBJECT-TYPE
   SYNTAX      Counter64
   MAX-ACCESS  read-only
   STATUS      current
   DESCRIPTION
      "Path: virtualEthernet.performance.vlan.outPriorityQueues.packets.cirTx

       64 bit unsigned wrappable counter."
   ::= {pr1646v2VEthVlanOutPQsEntry 50593792}

pr1646v2VEthVlanOutPQsPacketsEirTx OBJECT-TYPE
   SYNTAX      Counter64
   MAX-ACCESS  read-only
   STATUS      current
   DESCRIPTION
      "Path: virtualEthernet.performance.vlan.outPriorityQueues.packets.eirTx

       64 bit unsigned wrappable counter."
   ::= {pr1646v2VEthVlanOutPQsEntry 50659328}

pr1646v2VEthVlanOutPQsPacketsViolateTx OBJECT-TYPE
   SYNTAX      Counter64
   MAX-ACCESS  read-only
   STATUS      current
   DESCRIPTION
      "Path: virtualEthernet.performance.vlan.outPriorityQueues.packets.violateTx

       64 bit unsigned wrappable counter."
   ::= {pr1646v2VEthVlanOutPQsEntry 50855936}

pr1646v2VEthVlanOutPQsOctetsTotal OBJECT-TYPE
   SYNTAX      Counter64
   MAX-ACCESS  read-only
   STATUS      current
   DESCRIPTION
      "Path: virtualEthernet.performance.vlan.outPriorityQueues.octets.total

       64 bit unsigned wrappable counter."
   ::= {pr1646v2VEthVlanOutPQsEntry 67567616}

pr1646v2VEthVlanOutPQsOctetsDirectTx OBJECT-TYPE
   SYNTAX      Counter64
   MAX-ACCESS  read-only
   STATUS      current
   DESCRIPTION
      "Path: virtualEthernet.performance.vlan.outPriorityQueues.octets.directTx

       64 bit unsigned wrappable counter."
   ::= {pr1646v2VEthVlanOutPQsEntry 67174400}

pr1646v2VEthVlanOutPQsOctetsQueued OBJECT-TYPE
   SYNTAX      Counter64
   MAX-ACCESS  read-only
   STATUS      current
   DESCRIPTION
      "Path: virtualEthernet.performance.vlan.outPriorityQueues.octets.queued

       64 bit unsigned wrappable counter."
   ::= {pr1646v2VEthVlanOutPQsEntry 67239936}

pr1646v2VEthVlanOutPQsOctetsDropped OBJECT-TYPE
   SYNTAX      Counter64
   MAX-ACCESS  read-only
   STATUS      current
   DESCRIPTION
      "Path: virtualEthernet.performance.vlan.outPriorityQueues.octets.dropped

       64 bit unsigned wrappable counter."
   ::= {pr1646v2VEthVlanOutPQsEntry 67305472}

pr1646v2VEthVlanOutPQsOctetsRedDropped OBJECT-TYPE
   SYNTAX      Counter64
   MAX-ACCESS  read-only
   STATUS      current
   DESCRIPTION
      "Path: virtualEthernet.performance.vlan.outPriorityQueues.octets.redDropped

       64 bit unsigned wrappable counter."
   ::= {pr1646v2VEthVlanOutPQsEntry 67502080}

pr1646v2VEthVlanOutPQsOctetsCirTx OBJECT-TYPE
   SYNTAX      Counter64
   MAX-ACCESS  read-only
   STATUS      current
   DESCRIPTION
      "Path: virtualEthernet.performance.vlan.outPriorityQueues.octets.cirTx

       64 bit unsigned wrappable counter."
   ::= {pr1646v2VEthVlanOutPQsEntry 67371008}

pr1646v2VEthVlanOutPQsOctetsEirTx OBJECT-TYPE
   SYNTAX      Counter64
   MAX-ACCESS  read-only
   STATUS      current
   DESCRIPTION
      "Path: virtualEthernet.performance.vlan.outPriorityQueues.octets.eirTx

       64 bit unsigned wrappable counter."
   ::= {pr1646v2VEthVlanOutPQsEntry 67436544}

pr1646v2VEthVlanOutPQsOctetsViolateTx OBJECT-TYPE
   SYNTAX      Counter64
   MAX-ACCESS  read-only
   STATUS      current
   DESCRIPTION
      "Path: virtualEthernet.performance.vlan.outPriorityQueues.octets.violateTx

       64 bit unsigned wrappable counter."
   ::= {pr1646v2VEthVlanOutPQsEntry 67633152}

pr1646v2VEthVlanOutPQsOctetsBandwidth15sec OBJECT-TYPE
   SYNTAX      Integer32
   MAX-ACCESS  read-only
   STATUS      current
   DESCRIPTION
      "Path: virtualEthernet.performance.vlan.outPriorityQueues.octets.bandwidth.15sec

       unit name = bps
       formula = 8 * ; 8 /"
   ::= {pr1646v2VEthVlanOutPQsEntry 70386944}

pr1646v2VEthVlanOutPQsOctetsBandwidth30sec OBJECT-TYPE
   SYNTAX      Integer32
   MAX-ACCESS  read-only
   STATUS      current
   DESCRIPTION
      "Path: virtualEthernet.performance.vlan.outPriorityQueues.octets.bandwidth.30sec

       unit name = bps
       formula = 8 * ; 8 /"
   ::= {pr1646v2VEthVlanOutPQsEntry 70388224}

pr1646v2VEthVlanOutPQsOctetsBandwidth1min OBJECT-TYPE
   SYNTAX      Integer32
   MAX-ACCESS  read-only
   STATUS      current
   DESCRIPTION
      "Path: virtualEthernet.performance.vlan.outPriorityQueues.octets.bandwidth.1min

       unit name = bps
       formula = 8 * ; 8 /"
   ::= {pr1646v2VEthVlanOutPQsEntry 70390784}

pr1646v2VEthVlanOutPQsOctetsBandwidth2min OBJECT-TYPE
   SYNTAX      Integer32
   MAX-ACCESS  read-only
   STATUS      current
   DESCRIPTION
      "Path: virtualEthernet.performance.vlan.outPriorityQueues.octets.bandwidth.2min

       unit name = bps
       formula = 8 * ; 8 /"
   ::= {pr1646v2VEthVlanOutPQsEntry 70395904}

pr1646v2VEthVlanOutPQsOctetsBandwidth5min OBJECT-TYPE
   SYNTAX      Integer32
   MAX-ACCESS  read-only
   STATUS      current
   DESCRIPTION
      "Path: virtualEthernet.performance.vlan.outPriorityQueues.octets.bandwidth.5min

       unit name = bps
       formula = 8 * ; 8 /"
   ::= {pr1646v2VEthVlanOutPQsEntry 70411264}

pr1646v2VEthVlanOutPQsH2Performance OBJECT-TYPE
   SYNTAX      SEQUENCE OF Pr1646v2VEthVlanOutPQsH2PerformanceEntry
   MAX-ACCESS  not-accessible
   STATUS      current
   DESCRIPTION
      ""
   ::= {pr1646v2VEthVlan 84213760}

pr1646v2VEthVlanOutPQsH2PerformanceEntry OBJECT-TYPE
   SYNTAX      Pr1646v2VEthVlanOutPQsH2PerformanceEntry
   MAX-ACCESS  not-accessible
   STATUS      current
   DESCRIPTION
      ""
   INDEX      { pr1646v2VEthVlanOutPQsH2PerformanceGlobalIx,
                pr1646v2VEthVlanTableIx,
                pr1646v2VEthVlanOutPQsTableIx,
                pr1646v2VEthVlanOutPQsH2PerformanceTableIx }
   ::= {pr1646v2VEthVlanOutPQsH2Performance 1}

Pr1646v2VEthVlanOutPQsH2PerformanceEntry ::=
   SEQUENCE
      {
      pr1646v2VEthVlanOutPQsH2PerformanceGlobalIx
         GlobalIndex,
      pr1646v2VEthVlanOutPQsH2PerformanceTableIx
         TableIndex,
      pr1646v2VEthVlanOutPQsH2PerformanceSysUpTime
         TimeTicks,
      pr1646v2VEthVlanOutPQsH2PerformanceTotPkts
         Counter64,
      pr1646v2VEthVlanOutPQsH2PerformanceDirTxPkts
         Counter64,
      pr1646v2VEthVlanOutPQsH2PerformanceQdPkts
         Counter64,
      pr1646v2VEthVlanOutPQsH2PerformanceDropPkts
         Counter64,
      pr1646v2VEthVlanOutPQsH2PerformanceRDropPkts
         Counter64,
      pr1646v2VEthVlanOutPQsH2PerformanceCirTxPkts
         Counter64,
      pr1646v2VEthVlanOutPQsH2PerformanceEirTxPkts
         Counter64,
      pr1646v2VEthVlanOutPQsH2PerformanceViolTxPkts
         Counter64,
      pr1646v2VEthVlanOutPQsH2PerformanceTotOcts
         Counter64,
      pr1646v2VEthVlanOutPQsH2PerformanceDirTxOcts
         Counter64,
      pr1646v2VEthVlanOutPQsH2PerformanceQdOcts
         Counter64,
      pr1646v2VEthVlanOutPQsH2PerformanceDropOcts
         Counter64,
      pr1646v2VEthVlanOutPQsH2PerformanceRDropOcts
         Counter64,
      pr1646v2VEthVlanOutPQsH2PerformanceCirTxOcts
         Counter64,
      pr1646v2VEthVlanOutPQsH2PerformanceEirTxOcts
         Counter64,
      pr1646v2VEthVlanOutPQsH2PerformanceViolTxOcts
         Counter64,
      pr1646v2VEthVlanOutPQsH2PerformanceBandwidth
         Integer32
      }

pr1646v2VEthVlanOutPQsH2PerformanceGlobalIx OBJECT-TYPE
   SYNTAX      GlobalIndex
   MAX-ACCESS  not-accessible
   STATUS      current
   DESCRIPTION
      "The value of the tlsCntTreeGlobalIndex of the MANAGED OBJECT."
   ::= {pr1646v2VEthVlanOutPQsH2PerformanceEntry 10}

pr1646v2VEthVlanOutPQsH2PerformanceTableIx OBJECT-TYPE
   SYNTAX      TableIndex
   MAX-ACCESS  not-accessible
   STATUS      current
   DESCRIPTION
      ""
   ::= {pr1646v2VEthVlanOutPQsH2PerformanceEntry 11}

pr1646v2VEthVlanOutPQsH2PerformanceSysUpTime OBJECT-TYPE
   SYNTAX      TimeTicks
   MAX-ACCESS  read-only
   STATUS      current
   DESCRIPTION
      "Path: virtualEthernet.performance.vlan.outPriorityQueues.h2Performance.sysUpTime

       Time in centi-second."
   ::= {pr1646v2VEthVlanOutPQsH2PerformanceEntry 16777216}

pr1646v2VEthVlanOutPQsH2PerformanceTotPkts OBJECT-TYPE
   SYNTAX      Counter64
   MAX-ACCESS  read-only
   STATUS      current
   DESCRIPTION
      "Path: virtualEthernet.performance.vlan.outPriorityQueues.h2Performance.totalPkts

       64 bit unsigned wrappable counter."
   ::= {pr1646v2VEthVlanOutPQsH2PerformanceEntry 234881024}

pr1646v2VEthVlanOutPQsH2PerformanceDirTxPkts OBJECT-TYPE
   SYNTAX      Counter64
   MAX-ACCESS  read-only
   STATUS      current
   DESCRIPTION
      "Path: virtualEthernet.performance.vlan.outPriorityQueues.h2Performance.directTxPkts

       64 bit unsigned wrappable counter."
   ::= {pr1646v2VEthVlanOutPQsH2PerformanceEntry 33554432}

pr1646v2VEthVlanOutPQsH2PerformanceQdPkts OBJECT-TYPE
   SYNTAX      Counter64
   MAX-ACCESS  read-only
   STATUS      current
   DESCRIPTION
      "Path: virtualEthernet.performance.vlan.outPriorityQueues.h2Performance.queuedPkts

       64 bit unsigned wrappable counter."
   ::= {pr1646v2VEthVlanOutPQsH2PerformanceEntry 50331648}

pr1646v2VEthVlanOutPQsH2PerformanceDropPkts OBJECT-TYPE
   SYNTAX      Counter64
   MAX-ACCESS  read-only
   STATUS      current
   DESCRIPTION
      "Path: virtualEthernet.performance.vlan.outPriorityQueues.h2Performance.droppedPkts

       64 bit unsigned wrappable counter."
   ::= {pr1646v2VEthVlanOutPQsH2PerformanceEntry 67108864}

pr1646v2VEthVlanOutPQsH2PerformanceRDropPkts OBJECT-TYPE
   SYNTAX      Counter64
   MAX-ACCESS  read-only
   STATUS      current
   DESCRIPTION
      "Path: virtualEthernet.performance.vlan.outPriorityQueues.h2Performance.redDroppedPkts

       64 bit unsigned wrappable counter."
   ::= {pr1646v2VEthVlanOutPQsH2PerformanceEntry 201326592}

pr1646v2VEthVlanOutPQsH2PerformanceCirTxPkts OBJECT-TYPE
   SYNTAX      Counter64
   MAX-ACCESS  read-only
   STATUS      current
   DESCRIPTION
      "Path: virtualEthernet.performance.vlan.outPriorityQueues.h2Performance.cirTxPkts

       64 bit unsigned wrappable counter."
   ::= {pr1646v2VEthVlanOutPQsH2PerformanceEntry 83886080}

pr1646v2VEthVlanOutPQsH2PerformanceEirTxPkts OBJECT-TYPE
   SYNTAX      Counter64
   MAX-ACCESS  read-only
   STATUS      current
   DESCRIPTION
      "Path: virtualEthernet.performance.vlan.outPriorityQueues.h2Performance.eirTxPkts

       64 bit unsigned wrappable counter."
   ::= {pr1646v2VEthVlanOutPQsH2PerformanceEntry 100663296}

pr1646v2VEthVlanOutPQsH2PerformanceViolTxPkts OBJECT-TYPE
   SYNTAX      Counter64
   MAX-ACCESS  read-only
   STATUS      current
   DESCRIPTION
      "Path: virtualEthernet.performance.vlan.outPriorityQueues.h2Performance.violateTxPkts

       64 bit unsigned wrappable counter."
   ::= {pr1646v2VEthVlanOutPQsH2PerformanceEntry 301989888}

pr1646v2VEthVlanOutPQsH2PerformanceTotOcts OBJECT-TYPE
   SYNTAX      Counter64
   MAX-ACCESS  read-only
   STATUS      current
   DESCRIPTION
      "Path: virtualEthernet.performance.vlan.outPriorityQueues.h2Performance.totalOctets

       64 bit unsigned wrappable counter."
   ::= {pr1646v2VEthVlanOutPQsH2PerformanceEntry 251658240}

pr1646v2VEthVlanOutPQsH2PerformanceDirTxOcts OBJECT-TYPE
   SYNTAX      Counter64
   MAX-ACCESS  read-only
   STATUS      current
   DESCRIPTION
      "Path: virtualEthernet.performance.vlan.outPriorityQueues.h2Performance.directTxOctets

       64 bit unsigned wrappable counter."
   ::= {pr1646v2VEthVlanOutPQsH2PerformanceEntry 117440512}

pr1646v2VEthVlanOutPQsH2PerformanceQdOcts OBJECT-TYPE
   SYNTAX      Counter64
   MAX-ACCESS  read-only
   STATUS      current
   DESCRIPTION
      "Path: virtualEthernet.performance.vlan.outPriorityQueues.h2Performance.queuedOctets

       64 bit unsigned wrappable counter."
   ::= {pr1646v2VEthVlanOutPQsH2PerformanceEntry 134217728}

pr1646v2VEthVlanOutPQsH2PerformanceDropOcts OBJECT-TYPE
   SYNTAX      Counter64
   MAX-ACCESS  read-only
   STATUS      current
   DESCRIPTION
      "Path: virtualEthernet.performance.vlan.outPriorityQueues.h2Performance.droppedOctets

       64 bit unsigned wrappable counter."
   ::= {pr1646v2VEthVlanOutPQsH2PerformanceEntry 150994944}

pr1646v2VEthVlanOutPQsH2PerformanceRDropOcts OBJECT-TYPE
   SYNTAX      Counter64
   MAX-ACCESS  read-only
   STATUS      current
   DESCRIPTION
      "Path: virtualEthernet.performance.vlan.outPriorityQueues.h2Performance.redDroppedOctets

       64 bit unsigned wrappable counter."
   ::= {pr1646v2VEthVlanOutPQsH2PerformanceEntry 218103808}

pr1646v2VEthVlanOutPQsH2PerformanceCirTxOcts OBJECT-TYPE
   SYNTAX      Counter64
   MAX-ACCESS  read-only
   STATUS      current
   DESCRIPTION
      "Path: virtualEthernet.performance.vlan.outPriorityQueues.h2Performance.cirTxOctets

       64 bit unsigned wrappable counter."
   ::= {pr1646v2VEthVlanOutPQsH2PerformanceEntry 167772160}

pr1646v2VEthVlanOutPQsH2PerformanceEirTxOcts OBJECT-TYPE
   SYNTAX      Counter64
   MAX-ACCESS  read-only
   STATUS      current
   DESCRIPTION
      "Path: virtualEthernet.performance.vlan.outPriorityQueues.h2Performance.eirTxOctets

       64 bit unsigned wrappable counter."
   ::= {pr1646v2VEthVlanOutPQsH2PerformanceEntry 184549376}

pr1646v2VEthVlanOutPQsH2PerformanceViolTxOcts OBJECT-TYPE
   SYNTAX      Counter64
   MAX-ACCESS  read-only
   STATUS      current
   DESCRIPTION
      "Path: virtualEthernet.performance.vlan.outPriorityQueues.h2Performance.violateTxOctets

       64 bit unsigned wrappable counter."
   ::= {pr1646v2VEthVlanOutPQsH2PerformanceEntry 318767104}

pr1646v2VEthVlanOutPQsH2PerformanceBandwidth OBJECT-TYPE
   SYNTAX      Integer32
   MAX-ACCESS  read-only
   STATUS      current
   DESCRIPTION
      "Path: virtualEthernet.performance.vlan.outPriorityQueues.h2Performance.bandwidth

       unit name = bps
       formula = 8 * ; 8 /"
   ::= {pr1646v2VEthVlanOutPQsH2PerformanceEntry 268435456}

pr1646v2VEthVlanOutPQsH24Performance OBJECT-TYPE
   SYNTAX      SEQUENCE OF Pr1646v2VEthVlanOutPQsH24PerformanceEntry
   MAX-ACCESS  not-accessible
   STATUS      current
   DESCRIPTION
      ""
   ::= {pr1646v2VEthVlan 84279296}

pr1646v2VEthVlanOutPQsH24PerformanceEntry OBJECT-TYPE
   SYNTAX      Pr1646v2VEthVlanOutPQsH24PerformanceEntry
   MAX-ACCESS  not-accessible
   STATUS      current
   DESCRIPTION
      ""
   INDEX      { pr1646v2VEthVlanOutPQsH24PerformanceGlobalIx,
                pr1646v2VEthVlanTableIx,
                pr1646v2VEthVlanOutPQsTableIx,
                pr1646v2VEthVlanOutPQsH24PerformanceTableIx }
   ::= {pr1646v2VEthVlanOutPQsH24Performance 1}

Pr1646v2VEthVlanOutPQsH24PerformanceEntry ::=
   SEQUENCE
      {
      pr1646v2VEthVlanOutPQsH24PerformanceGlobalIx
         GlobalIndex,
      pr1646v2VEthVlanOutPQsH24PerformanceTableIx
         TableIndex,
      pr1646v2VEthVlanOutPQsH24PerformanceSysUpTime
         TimeTicks,
      pr1646v2VEthVlanOutPQsH24PerformanceTotPkts
         Counter64,
      pr1646v2VEthVlanOutPQsH24PerformanceDirTxPkts
         Counter64,
      pr1646v2VEthVlanOutPQsH24PerformanceQdPkts
         Counter64,
      pr1646v2VEthVlanOutPQsH24PerformanceDropPkts
         Counter64,
      pr1646v2VEthVlanOutPQsH24PerformanceRDropPkts
         Counter64,
      pr1646v2VEthVlanOutPQsH24PerformanceCirTxPkts
         Counter64,
      pr1646v2VEthVlanOutPQsH24PerformanceEirTxPkts
         Counter64,
      pr1646v2VEthVlanOutPQsH24PerformanceViolTxPkts
         Counter64,
      pr1646v2VEthVlanOutPQsH24PerformanceTotOcts
         Counter64,
      pr1646v2VEthVlanOutPQsH24PerformanceDirTxOcts
         Counter64,
      pr1646v2VEthVlanOutPQsH24PerformanceQdOcts
         Counter64,
      pr1646v2VEthVlanOutPQsH24PerformanceDropOcts
         Counter64,
      pr1646v2VEthVlanOutPQsH24PerformanceRDropOcts
         Counter64,
      pr1646v2VEthVlanOutPQsH24PerformanceCirTxOcts
         Counter64,
      pr1646v2VEthVlanOutPQsH24PerformanceEirTxOcts
         Counter64,
      pr1646v2VEthVlanOutPQsH24PerformanceViolTxOcts
         Counter64,
      pr1646v2VEthVlanOutPQsH24PerformanceBandwidth
         Integer32
      }

pr1646v2VEthVlanOutPQsH24PerformanceGlobalIx OBJECT-TYPE
   SYNTAX      GlobalIndex
   MAX-ACCESS  not-accessible
   STATUS      current
   DESCRIPTION
      "The value of the tlsCntTreeGlobalIndex of the MANAGED OBJECT."
   ::= {pr1646v2VEthVlanOutPQsH24PerformanceEntry 10}

pr1646v2VEthVlanOutPQsH24PerformanceTableIx OBJECT-TYPE
   SYNTAX      TableIndex
   MAX-ACCESS  not-accessible
   STATUS      current
   DESCRIPTION
      ""
   ::= {pr1646v2VEthVlanOutPQsH24PerformanceEntry 11}

pr1646v2VEthVlanOutPQsH24PerformanceSysUpTime OBJECT-TYPE
   SYNTAX      TimeTicks
   MAX-ACCESS  read-only
   STATUS      current
   DESCRIPTION
      "Path: virtualEthernet.performance.vlan.outPriorityQueues.h24Performance.sysUpTime

       Time in centi-second."
   ::= {pr1646v2VEthVlanOutPQsH24PerformanceEntry 16777216}

pr1646v2VEthVlanOutPQsH24PerformanceTotPkts OBJECT-TYPE
   SYNTAX      Counter64
   MAX-ACCESS  read-only
   STATUS      current
   DESCRIPTION
      "Path: virtualEthernet.performance.vlan.outPriorityQueues.h24Performance.totalPkts

       64 bit unsigned wrappable counter."
   ::= {pr1646v2VEthVlanOutPQsH24PerformanceEntry 234881024}

pr1646v2VEthVlanOutPQsH24PerformanceDirTxPkts OBJECT-TYPE
   SYNTAX      Counter64
   MAX-ACCESS  read-only
   STATUS      current
   DESCRIPTION
      "Path: virtualEthernet.performance.vlan.outPriorityQueues.h24Performance.directTxPkts

       64 bit unsigned wrappable counter."
   ::= {pr1646v2VEthVlanOutPQsH24PerformanceEntry 33554432}

pr1646v2VEthVlanOutPQsH24PerformanceQdPkts OBJECT-TYPE
   SYNTAX      Counter64
   MAX-ACCESS  read-only
   STATUS      current
   DESCRIPTION
      "Path: virtualEthernet.performance.vlan.outPriorityQueues.h24Performance.queuedPkts

       64 bit unsigned wrappable counter."
   ::= {pr1646v2VEthVlanOutPQsH24PerformanceEntry 50331648}

pr1646v2VEthVlanOutPQsH24PerformanceDropPkts OBJECT-TYPE
   SYNTAX      Counter64
   MAX-ACCESS  read-only
   STATUS      current
   DESCRIPTION
      "Path: virtualEthernet.performance.vlan.outPriorityQueues.h24Performance.droppedPkts

       64 bit unsigned wrappable counter."
   ::= {pr1646v2VEthVlanOutPQsH24PerformanceEntry 67108864}

pr1646v2VEthVlanOutPQsH24PerformanceRDropPkts OBJECT-TYPE
   SYNTAX      Counter64
   MAX-ACCESS  read-only
   STATUS      current
   DESCRIPTION
      "Path: virtualEthernet.performance.vlan.outPriorityQueues.h24Performance.redDroppedPkts

       64 bit unsigned wrappable counter."
   ::= {pr1646v2VEthVlanOutPQsH24PerformanceEntry 201326592}

pr1646v2VEthVlanOutPQsH24PerformanceCirTxPkts OBJECT-TYPE
   SYNTAX      Counter64
   MAX-ACCESS  read-only
   STATUS      current
   DESCRIPTION
      "Path: virtualEthernet.performance.vlan.outPriorityQueues.h24Performance.cirTxPkts

       64 bit unsigned wrappable counter."
   ::= {pr1646v2VEthVlanOutPQsH24PerformanceEntry 83886080}

pr1646v2VEthVlanOutPQsH24PerformanceEirTxPkts OBJECT-TYPE
   SYNTAX      Counter64
   MAX-ACCESS  read-only
   STATUS      current
   DESCRIPTION
      "Path: virtualEthernet.performance.vlan.outPriorityQueues.h24Performance.eirTxPkts

       64 bit unsigned wrappable counter."
   ::= {pr1646v2VEthVlanOutPQsH24PerformanceEntry 100663296}

pr1646v2VEthVlanOutPQsH24PerformanceViolTxPkts OBJECT-TYPE
   SYNTAX      Counter64
   MAX-ACCESS  read-only
   STATUS      current
   DESCRIPTION
      "Path: virtualEthernet.performance.vlan.outPriorityQueues.h24Performance.violateTxPkts

       64 bit unsigned wrappable counter."
   ::= {pr1646v2VEthVlanOutPQsH24PerformanceEntry 301989888}

pr1646v2VEthVlanOutPQsH24PerformanceTotOcts OBJECT-TYPE
   SYNTAX      Counter64
   MAX-ACCESS  read-only
   STATUS      current
   DESCRIPTION
      "Path: virtualEthernet.performance.vlan.outPriorityQueues.h24Performance.totalOctets

       64 bit unsigned wrappable counter."
   ::= {pr1646v2VEthVlanOutPQsH24PerformanceEntry 251658240}

pr1646v2VEthVlanOutPQsH24PerformanceDirTxOcts OBJECT-TYPE
   SYNTAX      Counter64
   MAX-ACCESS  read-only
   STATUS      current
   DESCRIPTION
      "Path: virtualEthernet.performance.vlan.outPriorityQueues.h24Performance.directTxOctets

       64 bit unsigned wrappable counter."
   ::= {pr1646v2VEthVlanOutPQsH24PerformanceEntry 117440512}

pr1646v2VEthVlanOutPQsH24PerformanceQdOcts OBJECT-TYPE
   SYNTAX      Counter64
   MAX-ACCESS  read-only
   STATUS      current
   DESCRIPTION
      "Path: virtualEthernet.performance.vlan.outPriorityQueues.h24Performance.queuedOctets

       64 bit unsigned wrappable counter."
   ::= {pr1646v2VEthVlanOutPQsH24PerformanceEntry 134217728}

pr1646v2VEthVlanOutPQsH24PerformanceDropOcts OBJECT-TYPE
   SYNTAX      Counter64
   MAX-ACCESS  read-only
   STATUS      current
   DESCRIPTION
      "Path: virtualEthernet.performance.vlan.outPriorityQueues.h24Performance.droppedOctets

       64 bit unsigned wrappable counter."
   ::= {pr1646v2VEthVlanOutPQsH24PerformanceEntry 150994944}

pr1646v2VEthVlanOutPQsH24PerformanceRDropOcts OBJECT-TYPE
   SYNTAX      Counter64
   MAX-ACCESS  read-only
   STATUS      current
   DESCRIPTION
      "Path: virtualEthernet.performance.vlan.outPriorityQueues.h24Performance.redDroppedOctets

       64 bit unsigned wrappable counter."
   ::= {pr1646v2VEthVlanOutPQsH24PerformanceEntry 218103808}

pr1646v2VEthVlanOutPQsH24PerformanceCirTxOcts OBJECT-TYPE
   SYNTAX      Counter64
   MAX-ACCESS  read-only
   STATUS      current
   DESCRIPTION
      "Path: virtualEthernet.performance.vlan.outPriorityQueues.h24Performance.cirTxOctets

       64 bit unsigned wrappable counter."
   ::= {pr1646v2VEthVlanOutPQsH24PerformanceEntry 167772160}

pr1646v2VEthVlanOutPQsH24PerformanceEirTxOcts OBJECT-TYPE
   SYNTAX      Counter64
   MAX-ACCESS  read-only
   STATUS      current
   DESCRIPTION
      "Path: virtualEthernet.performance.vlan.outPriorityQueues.h24Performance.eirTxOctets

       64 bit unsigned wrappable counter."
   ::= {pr1646v2VEthVlanOutPQsH24PerformanceEntry 184549376}

pr1646v2VEthVlanOutPQsH24PerformanceViolTxOcts OBJECT-TYPE
   SYNTAX      Counter64
   MAX-ACCESS  read-only
   STATUS      current
   DESCRIPTION
      "Path: virtualEthernet.performance.vlan.outPriorityQueues.h24Performance.violateTxOctets

       64 bit unsigned wrappable counter."
   ::= {pr1646v2VEthVlanOutPQsH24PerformanceEntry 318767104}

pr1646v2VEthVlanOutPQsH24PerformanceBandwidth OBJECT-TYPE
   SYNTAX      Integer32
   MAX-ACCESS  read-only
   STATUS      current
   DESCRIPTION
      "Path: virtualEthernet.performance.vlan.outPriorityQueues.h24Performance.bandwidth

       unit name = bps
       formula = 8 * ; 8 /"
   ::= {pr1646v2VEthVlanOutPQsH24PerformanceEntry 268435456}

pr1646v2VEthVlanOutPQsD7Performance OBJECT-TYPE
   SYNTAX      SEQUENCE OF Pr1646v2VEthVlanOutPQsD7PerformanceEntry
   MAX-ACCESS  not-accessible
   STATUS      current
   DESCRIPTION
      ""
   ::= {pr1646v2VEthVlan 84344832}

pr1646v2VEthVlanOutPQsD7PerformanceEntry OBJECT-TYPE
   SYNTAX      Pr1646v2VEthVlanOutPQsD7PerformanceEntry
   MAX-ACCESS  not-accessible
   STATUS      current
   DESCRIPTION
      ""
   INDEX      { pr1646v2VEthVlanOutPQsD7PerformanceGlobalIx,
                pr1646v2VEthVlanTableIx,
                pr1646v2VEthVlanOutPQsTableIx,
                pr1646v2VEthVlanOutPQsD7PerformanceTableIx }
   ::= {pr1646v2VEthVlanOutPQsD7Performance 1}

Pr1646v2VEthVlanOutPQsD7PerformanceEntry ::=
   SEQUENCE
      {
      pr1646v2VEthVlanOutPQsD7PerformanceGlobalIx
         GlobalIndex,
      pr1646v2VEthVlanOutPQsD7PerformanceTableIx
         TableIndex,
      pr1646v2VEthVlanOutPQsD7PerformanceSysUpTime
         TimeTicks,
      pr1646v2VEthVlanOutPQsD7PerformanceTotPkts
         Counter64,
      pr1646v2VEthVlanOutPQsD7PerformanceDirTxPkts
         Counter64,
      pr1646v2VEthVlanOutPQsD7PerformanceQdPkts
         Counter64,
      pr1646v2VEthVlanOutPQsD7PerformanceDropPkts
         Counter64,
      pr1646v2VEthVlanOutPQsD7PerformanceRDropPkts
         Counter64,
      pr1646v2VEthVlanOutPQsD7PerformanceCirTxPkts
         Counter64,
      pr1646v2VEthVlanOutPQsD7PerformanceEirTxPkts
         Counter64,
      pr1646v2VEthVlanOutPQsD7PerformanceViolTxPkts
         Counter64,
      pr1646v2VEthVlanOutPQsD7PerformanceTotOcts
         Counter64,
      pr1646v2VEthVlanOutPQsD7PerformanceDirTxOcts
         Counter64,
      pr1646v2VEthVlanOutPQsD7PerformanceQdOcts
         Counter64,
      pr1646v2VEthVlanOutPQsD7PerformanceDropOcts
         Counter64,
      pr1646v2VEthVlanOutPQsD7PerformanceRDropOcts
         Counter64,
      pr1646v2VEthVlanOutPQsD7PerformanceCirTxOcts
         Counter64,
      pr1646v2VEthVlanOutPQsD7PerformanceEirTxOcts
         Counter64,
      pr1646v2VEthVlanOutPQsD7PerformanceViolTxOcts
         Counter64,
      pr1646v2VEthVlanOutPQsD7PerformanceBandwidth
         Integer32
      }

pr1646v2VEthVlanOutPQsD7PerformanceGlobalIx OBJECT-TYPE
   SYNTAX      GlobalIndex
   MAX-ACCESS  not-accessible
   STATUS      current
   DESCRIPTION
      "The value of the tlsCntTreeGlobalIndex of the MANAGED OBJECT."
   ::= {pr1646v2VEthVlanOutPQsD7PerformanceEntry 10}

pr1646v2VEthVlanOutPQsD7PerformanceTableIx OBJECT-TYPE
   SYNTAX      TableIndex
   MAX-ACCESS  not-accessible
   STATUS      current
   DESCRIPTION
      ""
   ::= {pr1646v2VEthVlanOutPQsD7PerformanceEntry 11}

pr1646v2VEthVlanOutPQsD7PerformanceSysUpTime OBJECT-TYPE
   SYNTAX      TimeTicks
   MAX-ACCESS  read-only
   STATUS      current
   DESCRIPTION
      "Path: virtualEthernet.performance.vlan.outPriorityQueues.d7Performance.sysUpTime

       Time in centi-second."
   ::= {pr1646v2VEthVlanOutPQsD7PerformanceEntry 16777216}

pr1646v2VEthVlanOutPQsD7PerformanceTotPkts OBJECT-TYPE
   SYNTAX      Counter64
   MAX-ACCESS  read-only
   STATUS      current
   DESCRIPTION
      "Path: virtualEthernet.performance.vlan.outPriorityQueues.d7Performance.totalPkts

       64 bit unsigned wrappable counter."
   ::= {pr1646v2VEthVlanOutPQsD7PerformanceEntry 234881024}

pr1646v2VEthVlanOutPQsD7PerformanceDirTxPkts OBJECT-TYPE
   SYNTAX      Counter64
   MAX-ACCESS  read-only
   STATUS      current
   DESCRIPTION
      "Path: virtualEthernet.performance.vlan.outPriorityQueues.d7Performance.directTxPkts

       64 bit unsigned wrappable counter."
   ::= {pr1646v2VEthVlanOutPQsD7PerformanceEntry 33554432}

pr1646v2VEthVlanOutPQsD7PerformanceQdPkts OBJECT-TYPE
   SYNTAX      Counter64
   MAX-ACCESS  read-only
   STATUS      current
   DESCRIPTION
      "Path: virtualEthernet.performance.vlan.outPriorityQueues.d7Performance.queuedPkts

       64 bit unsigned wrappable counter."
   ::= {pr1646v2VEthVlanOutPQsD7PerformanceEntry 50331648}

pr1646v2VEthVlanOutPQsD7PerformanceDropPkts OBJECT-TYPE
   SYNTAX      Counter64
   MAX-ACCESS  read-only
   STATUS      current
   DESCRIPTION
      "Path: virtualEthernet.performance.vlan.outPriorityQueues.d7Performance.droppedPkts

       64 bit unsigned wrappable counter."
   ::= {pr1646v2VEthVlanOutPQsD7PerformanceEntry 67108864}

pr1646v2VEthVlanOutPQsD7PerformanceRDropPkts OBJECT-TYPE
   SYNTAX      Counter64
   MAX-ACCESS  read-only
   STATUS      current
   DESCRIPTION
      "Path: virtualEthernet.performance.vlan.outPriorityQueues.d7Performance.redDroppedPkts

       64 bit unsigned wrappable counter."
   ::= {pr1646v2VEthVlanOutPQsD7PerformanceEntry 201326592}

pr1646v2VEthVlanOutPQsD7PerformanceCirTxPkts OBJECT-TYPE
   SYNTAX      Counter64
   MAX-ACCESS  read-only
   STATUS      current
   DESCRIPTION
      "Path: virtualEthernet.performance.vlan.outPriorityQueues.d7Performance.cirTxPkts

       64 bit unsigned wrappable counter."
   ::= {pr1646v2VEthVlanOutPQsD7PerformanceEntry 83886080}

pr1646v2VEthVlanOutPQsD7PerformanceEirTxPkts OBJECT-TYPE
   SYNTAX      Counter64
   MAX-ACCESS  read-only
   STATUS      current
   DESCRIPTION
      "Path: virtualEthernet.performance.vlan.outPriorityQueues.d7Performance.eirTxPkts

       64 bit unsigned wrappable counter."
   ::= {pr1646v2VEthVlanOutPQsD7PerformanceEntry 100663296}

pr1646v2VEthVlanOutPQsD7PerformanceViolTxPkts OBJECT-TYPE
   SYNTAX      Counter64
   MAX-ACCESS  read-only
   STATUS      current
   DESCRIPTION
      "Path: virtualEthernet.performance.vlan.outPriorityQueues.d7Performance.violateTxPkts

       64 bit unsigned wrappable counter."
   ::= {pr1646v2VEthVlanOutPQsD7PerformanceEntry 301989888}

pr1646v2VEthVlanOutPQsD7PerformanceTotOcts OBJECT-TYPE
   SYNTAX      Counter64
   MAX-ACCESS  read-only
   STATUS      current
   DESCRIPTION
      "Path: virtualEthernet.performance.vlan.outPriorityQueues.d7Performance.totalOctets

       64 bit unsigned wrappable counter."
   ::= {pr1646v2VEthVlanOutPQsD7PerformanceEntry 251658240}

pr1646v2VEthVlanOutPQsD7PerformanceDirTxOcts OBJECT-TYPE
   SYNTAX      Counter64
   MAX-ACCESS  read-only
   STATUS      current
   DESCRIPTION
      "Path: virtualEthernet.performance.vlan.outPriorityQueues.d7Performance.directTxOctets

       64 bit unsigned wrappable counter."
   ::= {pr1646v2VEthVlanOutPQsD7PerformanceEntry 117440512}

pr1646v2VEthVlanOutPQsD7PerformanceQdOcts OBJECT-TYPE
   SYNTAX      Counter64
   MAX-ACCESS  read-only
   STATUS      current
   DESCRIPTION
      "Path: virtualEthernet.performance.vlan.outPriorityQueues.d7Performance.queuedOctets

       64 bit unsigned wrappable counter."
   ::= {pr1646v2VEthVlanOutPQsD7PerformanceEntry 134217728}

pr1646v2VEthVlanOutPQsD7PerformanceDropOcts OBJECT-TYPE
   SYNTAX      Counter64
   MAX-ACCESS  read-only
   STATUS      current
   DESCRIPTION
      "Path: virtualEthernet.performance.vlan.outPriorityQueues.d7Performance.droppedOctets

       64 bit unsigned wrappable counter."
   ::= {pr1646v2VEthVlanOutPQsD7PerformanceEntry 150994944}

pr1646v2VEthVlanOutPQsD7PerformanceRDropOcts OBJECT-TYPE
   SYNTAX      Counter64
   MAX-ACCESS  read-only
   STATUS      current
   DESCRIPTION
      "Path: virtualEthernet.performance.vlan.outPriorityQueues.d7Performance.redDroppedOctets

       64 bit unsigned wrappable counter."
   ::= {pr1646v2VEthVlanOutPQsD7PerformanceEntry 218103808}

pr1646v2VEthVlanOutPQsD7PerformanceCirTxOcts OBJECT-TYPE
   SYNTAX      Counter64
   MAX-ACCESS  read-only
   STATUS      current
   DESCRIPTION
      "Path: virtualEthernet.performance.vlan.outPriorityQueues.d7Performance.cirTxOctets

       64 bit unsigned wrappable counter."
   ::= {pr1646v2VEthVlanOutPQsD7PerformanceEntry 167772160}

pr1646v2VEthVlanOutPQsD7PerformanceEirTxOcts OBJECT-TYPE
   SYNTAX      Counter64
   MAX-ACCESS  read-only
   STATUS      current
   DESCRIPTION
      "Path: virtualEthernet.performance.vlan.outPriorityQueues.d7Performance.eirTxOctets

       64 bit unsigned wrappable counter."
   ::= {pr1646v2VEthVlanOutPQsD7PerformanceEntry 184549376}

pr1646v2VEthVlanOutPQsD7PerformanceViolTxOcts OBJECT-TYPE
   SYNTAX      Counter64
   MAX-ACCESS  read-only
   STATUS      current
   DESCRIPTION
      "Path: virtualEthernet.performance.vlan.outPriorityQueues.d7Performance.violateTxOctets

       64 bit unsigned wrappable counter."
   ::= {pr1646v2VEthVlanOutPQsD7PerformanceEntry 318767104}

pr1646v2VEthVlanOutPQsD7PerformanceBandwidth OBJECT-TYPE
   SYNTAX      Integer32
   MAX-ACCESS  read-only
   STATUS      current
   DESCRIPTION
      "Path: virtualEthernet.performance.vlan.outPriorityQueues.d7Performance.bandwidth

       unit name = bps
       formula = 8 * ; 8 /"
   ::= {pr1646v2VEthVlanOutPQsD7PerformanceEntry 268435456}


pr1646v2VEthPPPoE OBJECT IDENTIFIER ::= {pr1646v2VEth 53}

pr1646v2VEthPPPoESSCTable OBJECT-TYPE
   SYNTAX      SEQUENCE OF Pr1646v2VEthPPPoEEntry
   MAX-ACCESS  not-accessible
   STATUS      current
   DESCRIPTION
      ""
   ::= {pr1646v2VEthPPPoE 1}

pr1646v2VEthPPPoEEntry OBJECT-TYPE
   SYNTAX      Pr1646v2VEthPPPoEEntry
   MAX-ACCESS  not-accessible
   STATUS      current
   DESCRIPTION
      ""
   INDEX      { pr1646v2VEthPPPoEGlobalIx,
                pr1646v2VEthPPPoETableIx }
   ::= {pr1646v2VEthPPPoESSCTable 1}

Pr1646v2VEthPPPoEEntry ::=
   SEQUENCE
      {
      pr1646v2VEthPPPoEGlobalIx
         GlobalIndex,
      pr1646v2VEthPPPoETableIx
         TableIndex,
      pr1646v2VEthPPPoEName
         DisplayString,
      pr1646v2VEthPPPoEMCInOctets
         Counter64,
      pr1646v2VEthPPPoEMCInUcast
         Counter64,
      pr1646v2VEthPPPoEMCInNUcastPkts
         Counter64,
      pr1646v2VEthPPPoEMCInBcastPkts
         Counter64,
      pr1646v2VEthPPPoEMCInMcastPkts
         Counter64,
      pr1646v2VEthPPPoEMCInDiscards
         Counter64,
      pr1646v2VEthPPPoEMCInErrors
         Counter64,
      pr1646v2VEthPPPoEMCInUnknownProtos
         Counter64,
      pr1646v2VEthPPPoEMCInDropEx
         Counter64,
      pr1646v2VEthPPPoEMCInDropNoMac
         Counter64,
      pr1646v2VEthPPPoEMCInDropNUCast
         Counter64,
      pr1646v2VEthPPPoEMCInDropFilter
         Counter64,
      pr1646v2VEthPPPoEMCInBandwidth15sec
         Integer32,
      pr1646v2VEthPPPoEMCInBandwidth30sec
         Integer32,
      pr1646v2VEthPPPoEMCInBandwidth1min
         Integer32,
      pr1646v2VEthPPPoEMCInBandwidth2min
         Integer32,
      pr1646v2VEthPPPoEMCInBandwidth5min
         Integer32,
      pr1646v2VEthPPPoEMCOutOctets
         Counter64,
      pr1646v2VEthPPPoEMCOutUcastPkts
         Counter64,
      pr1646v2VEthPPPoEMCOutNUcastPkts
         Counter64,
      pr1646v2VEthPPPoEMCOutBcastPkts
         Counter64,
      pr1646v2VEthPPPoEMCOutMcastPkts
         Counter64,
      pr1646v2VEthPPPoEMCOutDiscards
         Counter64,
      pr1646v2VEthPPPoEMCOutErrors
         Counter64,
      pr1646v2VEthPPPoEMCOutQLen
         Counter32,
      pr1646v2VEthPPPoEMCOutDropEx
         Counter64,
      pr1646v2VEthPPPoEMCOutDropNoArp
         Counter64,
      pr1646v2VEthPPPoEMCOutDropFilter
         Counter64,
      pr1646v2VEthPPPoEMCOutBandwidth15sec
         Integer32,
      pr1646v2VEthPPPoEMCOutBandwidth30sec
         Integer32,
      pr1646v2VEthPPPoEMCOutBandwidth1min
         Integer32,
      pr1646v2VEthPPPoEMCOutBandwidth2min
         Integer32,
      pr1646v2VEthPPPoEMCOutBandwidth5min
         Integer32,
      pr1646v2VEthPPPoEPppLinkMonitoringRequestsSent
         Gauge32,
      pr1646v2VEthPPPoEPppLinkMonitoringRepliesRcvd
         Gauge32,
      pr1646v2VEthPPPoEPppLinkMonitoringRequestsRcvd
         Gauge32,
      pr1646v2VEthPPPoEPppLinkMonitoringRepliesSent
         Gauge32
      }

pr1646v2VEthPPPoEGlobalIx OBJECT-TYPE
   SYNTAX      GlobalIndex
   MAX-ACCESS  not-accessible
   STATUS      current
   DESCRIPTION
      "The value of the tlsCntTreeGlobalIndex of the MANAGED OBJECT."
   ::= {pr1646v2VEthPPPoEEntry 10}

pr1646v2VEthPPPoETableIx OBJECT-TYPE
   SYNTAX      TableIndex
   MAX-ACCESS  not-accessible
   STATUS      current
   DESCRIPTION
      ""
   ::= {pr1646v2VEthPPPoEEntry 11}

pr1646v2VEthPPPoEName OBJECT-TYPE
   SYNTAX      DisplayString
   MAX-ACCESS  read-only
   STATUS      current
   DESCRIPTION
      "Path: virtualEthernet.performance.pppoEClient.name"
   ::= {pr1646v2VEthPPPoEEntry 16777216}

pr1646v2VEthPPPoEMCInOctets OBJECT-TYPE
   SYNTAX      Counter64
   MAX-ACCESS  read-only
   STATUS      current
   DESCRIPTION
      "Path: virtualEthernet.performance.pppoEClient.mibCounters.ifInOctets

       64 bit unsigned wrappable counter."
   ::= {pr1646v2VEthPPPoEEntry 40697856}

pr1646v2VEthPPPoEMCInUcast OBJECT-TYPE
   SYNTAX      Counter64
   MAX-ACCESS  read-only
   STATUS      current
   DESCRIPTION
      "Path: virtualEthernet.performance.pppoEClient.mibCounters.ifInUcastPkts

       64 bit unsigned wrappable counter."
   ::= {pr1646v2VEthPPPoEEntry 40763392}

pr1646v2VEthPPPoEMCInNUcastPkts OBJECT-TYPE
   SYNTAX      Counter64
   MAX-ACCESS  read-only
   STATUS      current
   DESCRIPTION
      "Path: virtualEthernet.performance.pppoEClient.mibCounters.ifInNUcastPkts

       64 bit unsigned wrappable counter."
   ::= {pr1646v2VEthPPPoEEntry 40828928}

pr1646v2VEthPPPoEMCInBcastPkts OBJECT-TYPE
   SYNTAX      Counter64
   MAX-ACCESS  read-only
   STATUS      current
   DESCRIPTION
      "Path: virtualEthernet.performance.pppoEClient.mibCounters.ifInBcastPkts

       64 bit unsigned wrappable counter."
   ::= {pr1646v2VEthPPPoEEntry 47382528}

pr1646v2VEthPPPoEMCInMcastPkts OBJECT-TYPE
   SYNTAX      Counter64
   MAX-ACCESS  read-only
   STATUS      current
   DESCRIPTION
      "Path: virtualEthernet.performance.pppoEClient.mibCounters.ifInMcastPkts

       64 bit unsigned wrappable counter."
   ::= {pr1646v2VEthPPPoEEntry 48037888}

pr1646v2VEthPPPoEMCInDiscards OBJECT-TYPE
   SYNTAX      Counter64
   MAX-ACCESS  read-only
   STATUS      current
   DESCRIPTION
      "Path: virtualEthernet.performance.pppoEClient.mibCounters.ifInDiscards

       64 bit unsigned wrappable counter."
   ::= {pr1646v2VEthPPPoEEntry 40894464}

pr1646v2VEthPPPoEMCInErrors OBJECT-TYPE
   SYNTAX      Counter64
   MAX-ACCESS  read-only
   STATUS      current
   DESCRIPTION
      "Path: virtualEthernet.performance.pppoEClient.mibCounters.ifInErrors

       64 bit unsigned wrappable counter."
   ::= {pr1646v2VEthPPPoEEntry 40960000}

pr1646v2VEthPPPoEMCInUnknownProtos OBJECT-TYPE
   SYNTAX      Counter64
   MAX-ACCESS  read-only
   STATUS      current
   DESCRIPTION
      "Path: virtualEthernet.performance.pppoEClient.mibCounters.ifInUnknownProtos

       64 bit unsigned wrappable counter."
   ::= {pr1646v2VEthPPPoEEntry 41025536}

pr1646v2VEthPPPoEMCInDropEx OBJECT-TYPE
   SYNTAX      Counter64
   MAX-ACCESS  read-only
   STATUS      current
   DESCRIPTION
      "Path: virtualEthernet.performance.pppoEClient.mibCounters.ifInDropLevelExceeded

       64 bit unsigned wrappable counter."
   ::= {pr1646v2VEthPPPoEEntry 42074112}

pr1646v2VEthPPPoEMCInDropNoMac OBJECT-TYPE
   SYNTAX      Counter64
   MAX-ACCESS  read-only
   STATUS      current
   DESCRIPTION
      "Path: virtualEthernet.performance.pppoEClient.mibCounters.ifInDiscardsNoMacFit

       64 bit unsigned wrappable counter."
   ::= {pr1646v2VEthPPPoEEntry 42270720}

pr1646v2VEthPPPoEMCInDropNUCast OBJECT-TYPE
   SYNTAX      Counter64
   MAX-ACCESS  read-only
   STATUS      current
   DESCRIPTION
      "Path: virtualEthernet.performance.pppoEClient.mibCounters.ifInDiscardsNUCast

       64 bit unsigned wrappable counter."
   ::= {pr1646v2VEthPPPoEEntry 42467328}

pr1646v2VEthPPPoEMCInDropFilter OBJECT-TYPE
   SYNTAX      Counter64
   MAX-ACCESS  read-only
   STATUS      current
   DESCRIPTION
      "Path: virtualEthernet.performance.pppoEClient.mibCounters.ifInDiscardsFilter

       64 bit unsigned wrappable counter."
   ::= {pr1646v2VEthPPPoEEntry 42532864}

pr1646v2VEthPPPoEMCInBandwidth15sec OBJECT-TYPE
   SYNTAX      Integer32
   MAX-ACCESS  read-only
   STATUS      current
   DESCRIPTION
      "Path: virtualEthernet.performance.pppoEClient.mibCounters.ifInBandwidth.15sec

       unit name = bps
       formula = 8 * ; 8 /"
   ::= {pr1646v2VEthPPPoEEntry 45417728}

pr1646v2VEthPPPoEMCInBandwidth30sec OBJECT-TYPE
   SYNTAX      Integer32
   MAX-ACCESS  read-only
   STATUS      current
   DESCRIPTION
      "Path: virtualEthernet.performance.pppoEClient.mibCounters.ifInBandwidth.30sec

       unit name = bps
       formula = 8 * ; 8 /"
   ::= {pr1646v2VEthPPPoEEntry 45419008}

pr1646v2VEthPPPoEMCInBandwidth1min OBJECT-TYPE
   SYNTAX      Integer32
   MAX-ACCESS  read-only
   STATUS      current
   DESCRIPTION
      "Path: virtualEthernet.performance.pppoEClient.mibCounters.ifInBandwidth.1min

       unit name = bps
       formula = 8 * ; 8 /"
   ::= {pr1646v2VEthPPPoEEntry 45421568}

pr1646v2VEthPPPoEMCInBandwidth2min OBJECT-TYPE
   SYNTAX      Integer32
   MAX-ACCESS  read-only
   STATUS      current
   DESCRIPTION
      "Path: virtualEthernet.performance.pppoEClient.mibCounters.ifInBandwidth.2min

       unit name = bps
       formula = 8 * ; 8 /"
   ::= {pr1646v2VEthPPPoEEntry 45426688}

pr1646v2VEthPPPoEMCInBandwidth5min OBJECT-TYPE
   SYNTAX      Integer32
   MAX-ACCESS  read-only
   STATUS      current
   DESCRIPTION
      "Path: virtualEthernet.performance.pppoEClient.mibCounters.ifInBandwidth.5min

       unit name = bps
       formula = 8 * ; 8 /"
   ::= {pr1646v2VEthPPPoEEntry 45442048}

pr1646v2VEthPPPoEMCOutOctets OBJECT-TYPE
   SYNTAX      Counter64
   MAX-ACCESS  read-only
   STATUS      current
   DESCRIPTION
      "Path: virtualEthernet.performance.pppoEClient.mibCounters.ifOutOctets

       64 bit unsigned wrappable counter."
   ::= {pr1646v2VEthPPPoEEntry 41091072}

pr1646v2VEthPPPoEMCOutUcastPkts OBJECT-TYPE
   SYNTAX      Counter64
   MAX-ACCESS  read-only
   STATUS      current
   DESCRIPTION
      "Path: virtualEthernet.performance.pppoEClient.mibCounters.ifOutUcastPkts

       64 bit unsigned wrappable counter."
   ::= {pr1646v2VEthPPPoEEntry 41156608}

pr1646v2VEthPPPoEMCOutNUcastPkts OBJECT-TYPE
   SYNTAX      Counter64
   MAX-ACCESS  read-only
   STATUS      current
   DESCRIPTION
      "Path: virtualEthernet.performance.pppoEClient.mibCounters.ifOutNUcastPkts

       64 bit unsigned wrappable counter."
   ::= {pr1646v2VEthPPPoEEntry 41222144}

pr1646v2VEthPPPoEMCOutBcastPkts OBJECT-TYPE
   SYNTAX      Counter64
   MAX-ACCESS  read-only
   STATUS      current
   DESCRIPTION
      "Path: virtualEthernet.performance.pppoEClient.mibCounters.ifOutBcastPkts

       64 bit unsigned wrappable counter."
   ::= {pr1646v2VEthPPPoEEntry 47775744}

pr1646v2VEthPPPoEMCOutMcastPkts OBJECT-TYPE
   SYNTAX      Counter64
   MAX-ACCESS  read-only
   STATUS      current
   DESCRIPTION
      "Path: virtualEthernet.performance.pppoEClient.mibCounters.ifOutMcastPkts

       64 bit unsigned wrappable counter."
   ::= {pr1646v2VEthPPPoEEntry 48431104}

pr1646v2VEthPPPoEMCOutDiscards OBJECT-TYPE
   SYNTAX      Counter64
   MAX-ACCESS  read-only
   STATUS      current
   DESCRIPTION
      "Path: virtualEthernet.performance.pppoEClient.mibCounters.ifOutDiscards

       64 bit unsigned wrappable counter."
   ::= {pr1646v2VEthPPPoEEntry 41287680}

pr1646v2VEthPPPoEMCOutErrors OBJECT-TYPE
   SYNTAX      Counter64
   MAX-ACCESS  read-only
   STATUS      current
   DESCRIPTION
      "Path: virtualEthernet.performance.pppoEClient.mibCounters.ifOutErrors

       64 bit unsigned wrappable counter."
   ::= {pr1646v2VEthPPPoEEntry 41353216}

pr1646v2VEthPPPoEMCOutQLen OBJECT-TYPE
   SYNTAX      Counter32
   MAX-ACCESS  read-only
   STATUS      current
   DESCRIPTION
      "Path: virtualEthernet.performance.pppoEClient.mibCounters.ifOutQLen

       32 bit unsigned wrappable counter."
   ::= {pr1646v2VEthPPPoEEntry 41418752}

pr1646v2VEthPPPoEMCOutDropEx OBJECT-TYPE
   SYNTAX      Counter64
   MAX-ACCESS  read-only
   STATUS      current
   DESCRIPTION
      "Path: virtualEthernet.performance.pppoEClient.mibCounters.ifOutDropLevelExceeded

       64 bit unsigned wrappable counter."
   ::= {pr1646v2VEthPPPoEEntry 41484288}

pr1646v2VEthPPPoEMCOutDropNoArp OBJECT-TYPE
   SYNTAX      Counter64
   MAX-ACCESS  read-only
   STATUS      current
   DESCRIPTION
      "Path: virtualEthernet.performance.pppoEClient.mibCounters.ifOutDiscardsNoArp

       64 bit unsigned wrappable counter."
   ::= {pr1646v2VEthPPPoEEntry 42336256}

pr1646v2VEthPPPoEMCOutDropFilter OBJECT-TYPE
   SYNTAX      Counter64
   MAX-ACCESS  read-only
   STATUS      current
   DESCRIPTION
      "Path: virtualEthernet.performance.pppoEClient.mibCounters.ifOutDiscardsFilter

       64 bit unsigned wrappable counter."
   ::= {pr1646v2VEthPPPoEEntry 42598400}

pr1646v2VEthPPPoEMCOutBandwidth15sec OBJECT-TYPE
   SYNTAX      Integer32
   MAX-ACCESS  read-only
   STATUS      current
   DESCRIPTION
      "Path: virtualEthernet.performance.pppoEClient.mibCounters.ifOutBandwidth.15sec

       unit name = bps
       formula = 8 * ; 8 /"
   ::= {pr1646v2VEthPPPoEEntry 45483264}

pr1646v2VEthPPPoEMCOutBandwidth30sec OBJECT-TYPE
   SYNTAX      Integer32
   MAX-ACCESS  read-only
   STATUS      current
   DESCRIPTION
      "Path: virtualEthernet.performance.pppoEClient.mibCounters.ifOutBandwidth.30sec

       unit name = bps
       formula = 8 * ; 8 /"
   ::= {pr1646v2VEthPPPoEEntry 45484544}

pr1646v2VEthPPPoEMCOutBandwidth1min OBJECT-TYPE
   SYNTAX      Integer32
   MAX-ACCESS  read-only
   STATUS      current
   DESCRIPTION
      "Path: virtualEthernet.performance.pppoEClient.mibCounters.ifOutBandwidth.1min

       unit name = bps
       formula = 8 * ; 8 /"
   ::= {pr1646v2VEthPPPoEEntry 45487104}

pr1646v2VEthPPPoEMCOutBandwidth2min OBJECT-TYPE
   SYNTAX      Integer32
   MAX-ACCESS  read-only
   STATUS      current
   DESCRIPTION
      "Path: virtualEthernet.performance.pppoEClient.mibCounters.ifOutBandwidth.2min

       unit name = bps
       formula = 8 * ; 8 /"
   ::= {pr1646v2VEthPPPoEEntry 45492224}

pr1646v2VEthPPPoEMCOutBandwidth5min OBJECT-TYPE
   SYNTAX      Integer32
   MAX-ACCESS  read-only
   STATUS      current
   DESCRIPTION
      "Path: virtualEthernet.performance.pppoEClient.mibCounters.ifOutBandwidth.5min

       unit name = bps
       formula = 8 * ; 8 /"
   ::= {pr1646v2VEthPPPoEEntry 45507584}

pr1646v2VEthPPPoEPppLinkMonitoringRequestsSent OBJECT-TYPE
   SYNTAX      Gauge32
   MAX-ACCESS  read-only
   STATUS      current
   DESCRIPTION
      "Path: virtualEthernet.performance.pppoEClient.ppp.linkMonitoring.requestsSent

       32 bit unsigned gauge value."
   ::= {pr1646v2VEthPPPoEEntry 50397440}

pr1646v2VEthPPPoEPppLinkMonitoringRepliesRcvd OBJECT-TYPE
   SYNTAX      Gauge32
   MAX-ACCESS  read-only
   STATUS      current
   DESCRIPTION
      "Path: virtualEthernet.performance.pppoEClient.ppp.linkMonitoring.repliesRcvd

       32 bit unsigned gauge value."
   ::= {pr1646v2VEthPPPoEEntry 50397696}

pr1646v2VEthPPPoEPppLinkMonitoringRequestsRcvd OBJECT-TYPE
   SYNTAX      Gauge32
   MAX-ACCESS  read-only
   STATUS      current
   DESCRIPTION
      "Path: virtualEthernet.performance.pppoEClient.ppp.linkMonitoring.requestsRcvd

       32 bit unsigned gauge value."
   ::= {pr1646v2VEthPPPoEEntry 50397952}

pr1646v2VEthPPPoEPppLinkMonitoringRepliesSent OBJECT-TYPE
   SYNTAX      Gauge32
   MAX-ACCESS  read-only
   STATUS      current
   DESCRIPTION
      "Path: virtualEthernet.performance.pppoEClient.ppp.linkMonitoring.repliesSent

       32 bit unsigned gauge value."
   ::= {pr1646v2VEthPPPoEEntry 50398208}

pr1646v2VEthPPPoEMCH2P OBJECT-TYPE
   SYNTAX      SEQUENCE OF Pr1646v2VEthPPPoEMCH2PEntry
   MAX-ACCESS  not-accessible
   STATUS      current
   DESCRIPTION
      ""
   ::= {pr1646v2VEthPPPoE 41549824}

pr1646v2VEthPPPoEMCH2PEntry OBJECT-TYPE
   SYNTAX      Pr1646v2VEthPPPoEMCH2PEntry
   MAX-ACCESS  not-accessible
   STATUS      current
   DESCRIPTION
      ""
   INDEX      { pr1646v2VEthPPPoEMCH2PGlobalIx,
                pr1646v2VEthPPPoETableIx,
                pr1646v2VEthPPPoEMCH2PTableIx }
   ::= {pr1646v2VEthPPPoEMCH2P 1}

Pr1646v2VEthPPPoEMCH2PEntry ::=
   SEQUENCE
      {
      pr1646v2VEthPPPoEMCH2PGlobalIx
         GlobalIndex,
      pr1646v2VEthPPPoEMCH2PTableIx
         TableIndex,
      pr1646v2VEthPPPoEMCH2PSysUpTime
         TimeTicks,
      pr1646v2VEthPPPoEMCH2PIfUpTime
         TimeTicks,
      pr1646v2VEthPPPoEMCH2PIfStatChanges
         Counter32,
      pr1646v2VEthPPPoEMCH2PIfInOctets
         Counter64,
      pr1646v2VEthPPPoEMCH2PIfInUCPkts
         Counter64,
      pr1646v2VEthPPPoEMCH2PIfInNUCPkts
         Counter64,
      pr1646v2VEthPPPoEMCH2PIfInBCPkts
         Counter64,
      pr1646v2VEthPPPoEMCH2PIfInMCPkts
         Counter64,
      pr1646v2VEthPPPoEMCH2PIfInDiscards
         Counter64,
      pr1646v2VEthPPPoEMCH2PIfInErrors
         Counter64,
      pr1646v2VEthPPPoEMCH2PIfInUnkwn
         Counter64,
      pr1646v2VEthPPPoEMCH2PInDropEx
         Counter64,
      pr1646v2VEthPPPoEMCH2PInDropNoMac
         Counter64,
      pr1646v2VEthPPPoEMCH2PInDropNUCast
         Counter64,
      pr1646v2VEthPPPoEMCH2PInDropFilter
         Counter64,
      pr1646v2VEthPPPoEMCH2PIfInBandwidth
         Integer32,
      pr1646v2VEthPPPoEMCH2PIfOutOctets
         Counter64,
      pr1646v2VEthPPPoEMCH2PIfOutUCPkts
         Counter64,
      pr1646v2VEthPPPoEMCH2PIfOutNUCPkts
         Counter64,
      pr1646v2VEthPPPoEMCH2PIfOutBCPkts
         Counter64,
      pr1646v2VEthPPPoEMCH2PIfOutMCPkts
         Counter64,
      pr1646v2VEthPPPoEMCH2PIfOutDiscards
         Counter64,
      pr1646v2VEthPPPoEMCH2PIfOutErrors
         Counter64,
      pr1646v2VEthPPPoEMCH2POutDropEx
         Counter64,
      pr1646v2VEthPPPoEMCH2POutDropNoArp
         Counter64,
      pr1646v2VEthPPPoEMCH2POutDropFilter
         Counter64,
      pr1646v2VEthPPPoEMCH2PIfOutBandwidth
         Integer32,
      pr1646v2VEthPPPoEMCH2PIfErrSec
         Counter32
      }

pr1646v2VEthPPPoEMCH2PGlobalIx OBJECT-TYPE
   SYNTAX      GlobalIndex
   MAX-ACCESS  not-accessible
   STATUS      current
   DESCRIPTION
      "The value of the tlsCntTreeGlobalIndex of the MANAGED OBJECT."
   ::= {pr1646v2VEthPPPoEMCH2PEntry 10}

pr1646v2VEthPPPoEMCH2PTableIx OBJECT-TYPE
   SYNTAX      TableIndex
   MAX-ACCESS  not-accessible
   STATUS      current
   DESCRIPTION
      ""
   ::= {pr1646v2VEthPPPoEMCH2PEntry 11}

pr1646v2VEthPPPoEMCH2PSysUpTime OBJECT-TYPE
   SYNTAX      TimeTicks
   MAX-ACCESS  read-only
   STATUS      current
   DESCRIPTION
      "Path: virtualEthernet.performance.pppoEClient.mibCounters.h2Performance.sysUpTime

       Time in centi-second."
   ::= {pr1646v2VEthPPPoEMCH2PEntry 16777216}

pr1646v2VEthPPPoEMCH2PIfUpTime OBJECT-TYPE
   SYNTAX      TimeTicks
   MAX-ACCESS  read-only
   STATUS      current
   DESCRIPTION
      "Path: virtualEthernet.performance.pppoEClient.mibCounters.h2Performance.ifUpTime

       Time in centi-second."
   ::= {pr1646v2VEthPPPoEMCH2PEntry 33554432}

pr1646v2VEthPPPoEMCH2PIfStatChanges OBJECT-TYPE
   SYNTAX      Counter32
   MAX-ACCESS  read-only
   STATUS      current
   DESCRIPTION
      "Path: virtualEthernet.performance.pppoEClient.mibCounters.h2Performance.ifStatusChanges

       32 bit unsigned wrappable counter."
   ::= {pr1646v2VEthPPPoEMCH2PEntry 50331648}

pr1646v2VEthPPPoEMCH2PIfInOctets OBJECT-TYPE
   SYNTAX      Counter64
   MAX-ACCESS  read-only
   STATUS      current
   DESCRIPTION
      "Path: virtualEthernet.performance.pppoEClient.mibCounters.h2Performance.ifInOctets

       64 bit unsigned wrappable counter."
   ::= {pr1646v2VEthPPPoEMCH2PEntry 67108864}

pr1646v2VEthPPPoEMCH2PIfInUCPkts OBJECT-TYPE
   SYNTAX      Counter64
   MAX-ACCESS  read-only
   STATUS      current
   DESCRIPTION
      "Path: virtualEthernet.performance.pppoEClient.mibCounters.h2Performance.ifInUcastPkts

       64 bit unsigned wrappable counter."
   ::= {pr1646v2VEthPPPoEMCH2PEntry 83886080}

pr1646v2VEthPPPoEMCH2PIfInNUCPkts OBJECT-TYPE
   SYNTAX      Counter64
   MAX-ACCESS  read-only
   STATUS      current
   DESCRIPTION
      "Path: virtualEthernet.performance.pppoEClient.mibCounters.h2Performance.ifInNUcastPkts

       64 bit unsigned wrappable counter."
   ::= {pr1646v2VEthPPPoEMCH2PEntry 100663296}

pr1646v2VEthPPPoEMCH2PIfInBCPkts OBJECT-TYPE
   SYNTAX      Counter64
   MAX-ACCESS  read-only
   STATUS      current
   DESCRIPTION
      "Path: virtualEthernet.performance.pppoEClient.mibCounters.h2Performance.ifInBcastPkts

       64 bit unsigned wrappable counter."
   ::= {pr1646v2VEthPPPoEMCH2PEntry 419430400}

pr1646v2VEthPPPoEMCH2PIfInMCPkts OBJECT-TYPE
   SYNTAX      Counter64
   MAX-ACCESS  read-only
   STATUS      current
   DESCRIPTION
      "Path: virtualEthernet.performance.pppoEClient.mibCounters.h2Performance.ifInMcastPkts

       64 bit unsigned wrappable counter."
   ::= {pr1646v2VEthPPPoEMCH2PEntry 436207616}

pr1646v2VEthPPPoEMCH2PIfInDiscards OBJECT-TYPE
   SYNTAX      Counter64
   MAX-ACCESS  read-only
   STATUS      current
   DESCRIPTION
      "Path: virtualEthernet.performance.pppoEClient.mibCounters.h2Performance.ifInDiscards

       64 bit unsigned wrappable counter."
   ::= {pr1646v2VEthPPPoEMCH2PEntry 117440512}

pr1646v2VEthPPPoEMCH2PIfInErrors OBJECT-TYPE
   SYNTAX      Counter64
   MAX-ACCESS  read-only
   STATUS      current
   DESCRIPTION
      "Path: virtualEthernet.performance.pppoEClient.mibCounters.h2Performance.ifInErrors

       64 bit unsigned wrappable counter."
   ::= {pr1646v2VEthPPPoEMCH2PEntry 134217728}

pr1646v2VEthPPPoEMCH2PIfInUnkwn OBJECT-TYPE
   SYNTAX      Counter64
   MAX-ACCESS  read-only
   STATUS      current
   DESCRIPTION
      "Path: virtualEthernet.performance.pppoEClient.mibCounters.h2Performance.ifInUnknownProtos

       64 bit unsigned wrappable counter."
   ::= {pr1646v2VEthPPPoEMCH2PEntry 150994944}

pr1646v2VEthPPPoEMCH2PInDropEx OBJECT-TYPE
   SYNTAX      Counter64
   MAX-ACCESS  read-only
   STATUS      current
   DESCRIPTION
      "Path: virtualEthernet.performance.pppoEClient.mibCounters.h2Performance.ifInDropLevelExceeded

       64 bit unsigned wrappable counter."
   ::= {pr1646v2VEthPPPoEMCH2PEntry 335544320}

pr1646v2VEthPPPoEMCH2PInDropNoMac OBJECT-TYPE
   SYNTAX      Counter64
   MAX-ACCESS  read-only
   STATUS      current
   DESCRIPTION
      "Path: virtualEthernet.performance.pppoEClient.mibCounters.h2Performance.fInDiscardsNoMacFit

       64 bit unsigned wrappable counter."
   ::= {pr1646v2VEthPPPoEMCH2PEntry 301989888}

pr1646v2VEthPPPoEMCH2PInDropNUCast OBJECT-TYPE
   SYNTAX      Counter64
   MAX-ACCESS  read-only
   STATUS      current
   DESCRIPTION
      "Path: virtualEthernet.performance.pppoEClient.mibCounters.h2Performance.fInDiscardsNUCast

       64 bit unsigned wrappable counter."
   ::= {pr1646v2VEthPPPoEMCH2PEntry 318767104}

pr1646v2VEthPPPoEMCH2PInDropFilter OBJECT-TYPE
   SYNTAX      Counter64
   MAX-ACCESS  read-only
   STATUS      current
   DESCRIPTION
      "Path: virtualEthernet.performance.pppoEClient.mibCounters.h2Performance.fInDiscardsFilter

       64 bit unsigned wrappable counter."
   ::= {pr1646v2VEthPPPoEMCH2PEntry 385875968}

pr1646v2VEthPPPoEMCH2PIfInBandwidth OBJECT-TYPE
   SYNTAX      Integer32
   MAX-ACCESS  read-only
   STATUS      current
   DESCRIPTION
      "Path: virtualEthernet.performance.pppoEClient.mibCounters.h2Performance.ifInBandwidth

       unit name = bps
       formula = 8 * ; 8 /"
   ::= {pr1646v2VEthPPPoEMCH2PEntry 268435456}

pr1646v2VEthPPPoEMCH2PIfOutOctets OBJECT-TYPE
   SYNTAX      Counter64
   MAX-ACCESS  read-only
   STATUS      current
   DESCRIPTION
      "Path: virtualEthernet.performance.pppoEClient.mibCounters.h2Performance.ifOutOctets

       64 bit unsigned wrappable counter."
   ::= {pr1646v2VEthPPPoEMCH2PEntry 167772160}

pr1646v2VEthPPPoEMCH2PIfOutUCPkts OBJECT-TYPE
   SYNTAX      Counter64
   MAX-ACCESS  read-only
   STATUS      current
   DESCRIPTION
      "Path: virtualEthernet.performance.pppoEClient.mibCounters.h2Performance.ifOutUcastPkts

       64 bit unsigned wrappable counter."
   ::= {pr1646v2VEthPPPoEMCH2PEntry 184549376}

pr1646v2VEthPPPoEMCH2PIfOutNUCPkts OBJECT-TYPE
   SYNTAX      Counter64
   MAX-ACCESS  read-only
   STATUS      current
   DESCRIPTION
      "Path: virtualEthernet.performance.pppoEClient.mibCounters.h2Performance.ifOutNUcastPkts

       64 bit unsigned wrappable counter."
   ::= {pr1646v2VEthPPPoEMCH2PEntry 201326592}

pr1646v2VEthPPPoEMCH2PIfOutBCPkts OBJECT-TYPE
   SYNTAX      Counter64
   MAX-ACCESS  read-only
   STATUS      current
   DESCRIPTION
      "Path: virtualEthernet.performance.pppoEClient.mibCounters.h2Performance.ifOutBcastPkts

       64 bit unsigned wrappable counter."
   ::= {pr1646v2VEthPPPoEMCH2PEntry 452984832}

pr1646v2VEthPPPoEMCH2PIfOutMCPkts OBJECT-TYPE
   SYNTAX      Counter64
   MAX-ACCESS  read-only
   STATUS      current
   DESCRIPTION
      "Path: virtualEthernet.performance.pppoEClient.mibCounters.h2Performance.ifOutMcastPkts

       64 bit unsigned wrappable counter."
   ::= {pr1646v2VEthPPPoEMCH2PEntry 469762048}

pr1646v2VEthPPPoEMCH2PIfOutDiscards OBJECT-TYPE
   SYNTAX      Counter64
   MAX-ACCESS  read-only
   STATUS      current
   DESCRIPTION
      "Path: virtualEthernet.performance.pppoEClient.mibCounters.h2Performance.ifOutDiscards

       64 bit unsigned wrappable counter."
   ::= {pr1646v2VEthPPPoEMCH2PEntry 218103808}

pr1646v2VEthPPPoEMCH2PIfOutErrors OBJECT-TYPE
   SYNTAX      Counter64
   MAX-ACCESS  read-only
   STATUS      current
   DESCRIPTION
      "Path: virtualEthernet.performance.pppoEClient.mibCounters.h2Performance.ifOutErrors

       64 bit unsigned wrappable counter."
   ::= {pr1646v2VEthPPPoEMCH2PEntry 234881024}

pr1646v2VEthPPPoEMCH2POutDropEx OBJECT-TYPE
   SYNTAX      Counter64
   MAX-ACCESS  read-only
   STATUS      current
   DESCRIPTION
      "Path: virtualEthernet.performance.pppoEClient.mibCounters.h2Performance.ifOutDropLevelExceeded

       64 bit unsigned wrappable counter."
   ::= {pr1646v2VEthPPPoEMCH2PEntry 352321536}

pr1646v2VEthPPPoEMCH2POutDropNoArp OBJECT-TYPE
   SYNTAX      Counter64
   MAX-ACCESS  read-only
   STATUS      current
   DESCRIPTION
      "Path: virtualEthernet.performance.pppoEClient.mibCounters.h2Performance.ifOutDiscardsNoArp

       64 bit unsigned wrappable counter."
   ::= {pr1646v2VEthPPPoEMCH2PEntry 369098752}

pr1646v2VEthPPPoEMCH2POutDropFilter OBJECT-TYPE
   SYNTAX      Counter64
   MAX-ACCESS  read-only
   STATUS      current
   DESCRIPTION
      "Path: virtualEthernet.performance.pppoEClient.mibCounters.h2Performance.ifOutDiscardsFilter

       64 bit unsigned wrappable counter."
   ::= {pr1646v2VEthPPPoEMCH2PEntry 402653184}

pr1646v2VEthPPPoEMCH2PIfOutBandwidth OBJECT-TYPE
   SYNTAX      Integer32
   MAX-ACCESS  read-only
   STATUS      current
   DESCRIPTION
      "Path: virtualEthernet.performance.pppoEClient.mibCounters.h2Performance.ifOutBandwidth

       unit name = bps
       formula = 8 * ; 8 /"
   ::= {pr1646v2VEthPPPoEMCH2PEntry 285212672}

pr1646v2VEthPPPoEMCH2PIfErrSec OBJECT-TYPE
   SYNTAX      Counter32
   MAX-ACCESS  read-only
   STATUS      current
   DESCRIPTION
      "Path: virtualEthernet.performance.pppoEClient.mibCounters.h2Performance.ifErrSec

       32 bit unsigned wrappable counter."
   ::= {pr1646v2VEthPPPoEMCH2PEntry 251658240}

pr1646v2VEthPPPoEMCH24P OBJECT-TYPE
   SYNTAX      SEQUENCE OF Pr1646v2VEthPPPoEMCH24PEntry
   MAX-ACCESS  not-accessible
   STATUS      current
   DESCRIPTION
      ""
   ::= {pr1646v2VEthPPPoE 41615360}

pr1646v2VEthPPPoEMCH24PEntry OBJECT-TYPE
   SYNTAX      Pr1646v2VEthPPPoEMCH24PEntry
   MAX-ACCESS  not-accessible
   STATUS      current
   DESCRIPTION
      ""
   INDEX      { pr1646v2VEthPPPoEMCH24PGlobalIx,
                pr1646v2VEthPPPoETableIx,
                pr1646v2VEthPPPoEMCH24PTableIx }
   ::= {pr1646v2VEthPPPoEMCH24P 1}

Pr1646v2VEthPPPoEMCH24PEntry ::=
   SEQUENCE
      {
      pr1646v2VEthPPPoEMCH24PGlobalIx
         GlobalIndex,
      pr1646v2VEthPPPoEMCH24PTableIx
         TableIndex,
      pr1646v2VEthPPPoEMCH24PSysUpTime
         TimeTicks,
      pr1646v2VEthPPPoEMCH24PIfUpTime
         TimeTicks,
      pr1646v2VEthPPPoEMCH24PIfStatChanges
         Counter32,
      pr1646v2VEthPPPoEMCH24PIfInOctets
         Counter64,
      pr1646v2VEthPPPoEMCH24PIfInUCPkts
         Counter64,
      pr1646v2VEthPPPoEMCH24PIfInNUCPkts
         Counter64,
      pr1646v2VEthPPPoEMCH24PIfInBCPkts
         Counter64,
      pr1646v2VEthPPPoEMCH24PIfInMCPkts
         Counter64,
      pr1646v2VEthPPPoEMCH24PIfInDiscards
         Counter64,
      pr1646v2VEthPPPoEMCH24PIfInErrors
         Counter64,
      pr1646v2VEthPPPoEMCH24PIfInUnkwn
         Counter64,
      pr1646v2VEthPPPoEMCH24PInDropEx
         Counter64,
      pr1646v2VEthPPPoEMCH24PInDropNoMac
         Counter64,
      pr1646v2VEthPPPoEMCH24PInDropNUCast
         Counter64,
      pr1646v2VEthPPPoEMCH24PInDropFilter
         Counter64,
      pr1646v2VEthPPPoEMCH24PIfInBandwidth
         Integer32,
      pr1646v2VEthPPPoEMCH24PIfOutOctets
         Counter64,
      pr1646v2VEthPPPoEMCH24PIfOutUCPkts
         Counter64,
      pr1646v2VEthPPPoEMCH24PIfOutNUCPkts
         Counter64,
      pr1646v2VEthPPPoEMCH24PIfOutBCPkts
         Counter64,
      pr1646v2VEthPPPoEMCH24PIfOutMCPkts
         Counter64,
      pr1646v2VEthPPPoEMCH24PIfOutDiscards
         Counter64,
      pr1646v2VEthPPPoEMCH24PIfOutErrors
         Counter64,
      pr1646v2VEthPPPoEMCH24POutDropEx
         Counter64,
      pr1646v2VEthPPPoEMCH24POutDropNoArp
         Counter64,
      pr1646v2VEthPPPoEMCH24POutDropFilter
         Counter64,
      pr1646v2VEthPPPoEMCH24PIfOutBandwidth
         Integer32,
      pr1646v2VEthPPPoEMCH24PIfErrSec
         Counter32
      }

pr1646v2VEthPPPoEMCH24PGlobalIx OBJECT-TYPE
   SYNTAX      GlobalIndex
   MAX-ACCESS  not-accessible
   STATUS      current
   DESCRIPTION
      "The value of the tlsCntTreeGlobalIndex of the MANAGED OBJECT."
   ::= {pr1646v2VEthPPPoEMCH24PEntry 10}

pr1646v2VEthPPPoEMCH24PTableIx OBJECT-TYPE
   SYNTAX      TableIndex
   MAX-ACCESS  not-accessible
   STATUS      current
   DESCRIPTION
      ""
   ::= {pr1646v2VEthPPPoEMCH24PEntry 11}

pr1646v2VEthPPPoEMCH24PSysUpTime OBJECT-TYPE
   SYNTAX      TimeTicks
   MAX-ACCESS  read-only
   STATUS      current
   DESCRIPTION
      "Path: virtualEthernet.performance.pppoEClient.mibCounters.h24Performance.sysUpTime

       Time in centi-second."
   ::= {pr1646v2VEthPPPoEMCH24PEntry 16777216}

pr1646v2VEthPPPoEMCH24PIfUpTime OBJECT-TYPE
   SYNTAX      TimeTicks
   MAX-ACCESS  read-only
   STATUS      current
   DESCRIPTION
      "Path: virtualEthernet.performance.pppoEClient.mibCounters.h24Performance.ifUpTime

       Time in centi-second."
   ::= {pr1646v2VEthPPPoEMCH24PEntry 33554432}

pr1646v2VEthPPPoEMCH24PIfStatChanges OBJECT-TYPE
   SYNTAX      Counter32
   MAX-ACCESS  read-only
   STATUS      current
   DESCRIPTION
      "Path: virtualEthernet.performance.pppoEClient.mibCounters.h24Performance.ifStatusChanges

       32 bit unsigned wrappable counter."
   ::= {pr1646v2VEthPPPoEMCH24PEntry 50331648}

pr1646v2VEthPPPoEMCH24PIfInOctets OBJECT-TYPE
   SYNTAX      Counter64
   MAX-ACCESS  read-only
   STATUS      current
   DESCRIPTION
      "Path: virtualEthernet.performance.pppoEClient.mibCounters.h24Performance.ifInOctets

       64 bit unsigned wrappable counter."
   ::= {pr1646v2VEthPPPoEMCH24PEntry 67108864}

pr1646v2VEthPPPoEMCH24PIfInUCPkts OBJECT-TYPE
   SYNTAX      Counter64
   MAX-ACCESS  read-only
   STATUS      current
   DESCRIPTION
      "Path: virtualEthernet.performance.pppoEClient.mibCounters.h24Performance.ifInUcastPkts

       64 bit unsigned wrappable counter."
   ::= {pr1646v2VEthPPPoEMCH24PEntry 83886080}

pr1646v2VEthPPPoEMCH24PIfInNUCPkts OBJECT-TYPE
   SYNTAX      Counter64
   MAX-ACCESS  read-only
   STATUS      current
   DESCRIPTION
      "Path: virtualEthernet.performance.pppoEClient.mibCounters.h24Performance.ifInNUcastPkts

       64 bit unsigned wrappable counter."
   ::= {pr1646v2VEthPPPoEMCH24PEntry 100663296}

pr1646v2VEthPPPoEMCH24PIfInBCPkts OBJECT-TYPE
   SYNTAX      Counter64
   MAX-ACCESS  read-only
   STATUS      current
   DESCRIPTION
      "Path: virtualEthernet.performance.pppoEClient.mibCounters.h24Performance.ifInBcastPkts

       64 bit unsigned wrappable counter."
   ::= {pr1646v2VEthPPPoEMCH24PEntry 419430400}

pr1646v2VEthPPPoEMCH24PIfInMCPkts OBJECT-TYPE
   SYNTAX      Counter64
   MAX-ACCESS  read-only
   STATUS      current
   DESCRIPTION
      "Path: virtualEthernet.performance.pppoEClient.mibCounters.h24Performance.ifInMcastPkts

       64 bit unsigned wrappable counter."
   ::= {pr1646v2VEthPPPoEMCH24PEntry 436207616}

pr1646v2VEthPPPoEMCH24PIfInDiscards OBJECT-TYPE
   SYNTAX      Counter64
   MAX-ACCESS  read-only
   STATUS      current
   DESCRIPTION
      "Path: virtualEthernet.performance.pppoEClient.mibCounters.h24Performance.ifInDiscards

       64 bit unsigned wrappable counter."
   ::= {pr1646v2VEthPPPoEMCH24PEntry 117440512}

pr1646v2VEthPPPoEMCH24PIfInErrors OBJECT-TYPE
   SYNTAX      Counter64
   MAX-ACCESS  read-only
   STATUS      current
   DESCRIPTION
      "Path: virtualEthernet.performance.pppoEClient.mibCounters.h24Performance.ifInErrors

       64 bit unsigned wrappable counter."
   ::= {pr1646v2VEthPPPoEMCH24PEntry 134217728}

pr1646v2VEthPPPoEMCH24PIfInUnkwn OBJECT-TYPE
   SYNTAX      Counter64
   MAX-ACCESS  read-only
   STATUS      current
   DESCRIPTION
      "Path: virtualEthernet.performance.pppoEClient.mibCounters.h24Performance.ifInUnknownProtos

       64 bit unsigned wrappable counter."
   ::= {pr1646v2VEthPPPoEMCH24PEntry 150994944}

pr1646v2VEthPPPoEMCH24PInDropEx OBJECT-TYPE
   SYNTAX      Counter64
   MAX-ACCESS  read-only
   STATUS      current
   DESCRIPTION
      "Path: virtualEthernet.performance.pppoEClient.mibCounters.h24Performance.ifInDropLevelExceeded

       64 bit unsigned wrappable counter."
   ::= {pr1646v2VEthPPPoEMCH24PEntry 335544320}

pr1646v2VEthPPPoEMCH24PInDropNoMac OBJECT-TYPE
   SYNTAX      Counter64
   MAX-ACCESS  read-only
   STATUS      current
   DESCRIPTION
      "Path: virtualEthernet.performance.pppoEClient.mibCounters.h24Performance.fInDiscardsNoMacFit

       64 bit unsigned wrappable counter."
   ::= {pr1646v2VEthPPPoEMCH24PEntry 301989888}

pr1646v2VEthPPPoEMCH24PInDropNUCast OBJECT-TYPE
   SYNTAX      Counter64
   MAX-ACCESS  read-only
   STATUS      current
   DESCRIPTION
      "Path: virtualEthernet.performance.pppoEClient.mibCounters.h24Performance.fInDiscardsNUCast

       64 bit unsigned wrappable counter."
   ::= {pr1646v2VEthPPPoEMCH24PEntry 318767104}

pr1646v2VEthPPPoEMCH24PInDropFilter OBJECT-TYPE
   SYNTAX      Counter64
   MAX-ACCESS  read-only
   STATUS      current
   DESCRIPTION
      "Path: virtualEthernet.performance.pppoEClient.mibCounters.h24Performance.fInDiscardsFilter

       64 bit unsigned wrappable counter."
   ::= {pr1646v2VEthPPPoEMCH24PEntry 385875968}

pr1646v2VEthPPPoEMCH24PIfInBandwidth OBJECT-TYPE
   SYNTAX      Integer32
   MAX-ACCESS  read-only
   STATUS      current
   DESCRIPTION
      "Path: virtualEthernet.performance.pppoEClient.mibCounters.h24Performance.ifInBandwidth

       unit name = bps
       formula = 8 * ; 8 /"
   ::= {pr1646v2VEthPPPoEMCH24PEntry 268435456}

pr1646v2VEthPPPoEMCH24PIfOutOctets OBJECT-TYPE
   SYNTAX      Counter64
   MAX-ACCESS  read-only
   STATUS      current
   DESCRIPTION
      "Path: virtualEthernet.performance.pppoEClient.mibCounters.h24Performance.ifOutOctets

       64 bit unsigned wrappable counter."
   ::= {pr1646v2VEthPPPoEMCH24PEntry 167772160}

pr1646v2VEthPPPoEMCH24PIfOutUCPkts OBJECT-TYPE
   SYNTAX      Counter64
   MAX-ACCESS  read-only
   STATUS      current
   DESCRIPTION
      "Path: virtualEthernet.performance.pppoEClient.mibCounters.h24Performance.ifOutUcastPkts

       64 bit unsigned wrappable counter."
   ::= {pr1646v2VEthPPPoEMCH24PEntry 184549376}

pr1646v2VEthPPPoEMCH24PIfOutNUCPkts OBJECT-TYPE
   SYNTAX      Counter64
   MAX-ACCESS  read-only
   STATUS      current
   DESCRIPTION
      "Path: virtualEthernet.performance.pppoEClient.mibCounters.h24Performance.ifOutNUcastPkts

       64 bit unsigned wrappable counter."
   ::= {pr1646v2VEthPPPoEMCH24PEntry 201326592}

pr1646v2VEthPPPoEMCH24PIfOutBCPkts OBJECT-TYPE
   SYNTAX      Counter64
   MAX-ACCESS  read-only
   STATUS      current
   DESCRIPTION
      "Path: virtualEthernet.performance.pppoEClient.mibCounters.h24Performance.ifOutBcastPkts

       64 bit unsigned wrappable counter."
   ::= {pr1646v2VEthPPPoEMCH24PEntry 452984832}

pr1646v2VEthPPPoEMCH24PIfOutMCPkts OBJECT-TYPE
   SYNTAX      Counter64
   MAX-ACCESS  read-only
   STATUS      current
   DESCRIPTION
      "Path: virtualEthernet.performance.pppoEClient.mibCounters.h24Performance.ifOutMcastPkts

       64 bit unsigned wrappable counter."
   ::= {pr1646v2VEthPPPoEMCH24PEntry 469762048}

pr1646v2VEthPPPoEMCH24PIfOutDiscards OBJECT-TYPE
   SYNTAX      Counter64
   MAX-ACCESS  read-only
   STATUS      current
   DESCRIPTION
      "Path: virtualEthernet.performance.pppoEClient.mibCounters.h24Performance.ifOutDiscards

       64 bit unsigned wrappable counter."
   ::= {pr1646v2VEthPPPoEMCH24PEntry 218103808}

pr1646v2VEthPPPoEMCH24PIfOutErrors OBJECT-TYPE
   SYNTAX      Counter64
   MAX-ACCESS  read-only
   STATUS      current
   DESCRIPTION
      "Path: virtualEthernet.performance.pppoEClient.mibCounters.h24Performance.ifOutErrors

       64 bit unsigned wrappable counter."
   ::= {pr1646v2VEthPPPoEMCH24PEntry 234881024}

pr1646v2VEthPPPoEMCH24POutDropEx OBJECT-TYPE
   SYNTAX      Counter64
   MAX-ACCESS  read-only
   STATUS      current
   DESCRIPTION
      "Path: virtualEthernet.performance.pppoEClient.mibCounters.h24Performance.ifOutDropLevelExceeded

       64 bit unsigned wrappable counter."
   ::= {pr1646v2VEthPPPoEMCH24PEntry 352321536}

pr1646v2VEthPPPoEMCH24POutDropNoArp OBJECT-TYPE
   SYNTAX      Counter64
   MAX-ACCESS  read-only
   STATUS      current
   DESCRIPTION
      "Path: virtualEthernet.performance.pppoEClient.mibCounters.h24Performance.ifOutDiscardsNoArp

       64 bit unsigned wrappable counter."
   ::= {pr1646v2VEthPPPoEMCH24PEntry 369098752}

pr1646v2VEthPPPoEMCH24POutDropFilter OBJECT-TYPE
   SYNTAX      Counter64
   MAX-ACCESS  read-only
   STATUS      current
   DESCRIPTION
      "Path: virtualEthernet.performance.pppoEClient.mibCounters.h24Performance.ifOutDiscardsFilter

       64 bit unsigned wrappable counter."
   ::= {pr1646v2VEthPPPoEMCH24PEntry 402653184}

pr1646v2VEthPPPoEMCH24PIfOutBandwidth OBJECT-TYPE
   SYNTAX      Integer32
   MAX-ACCESS  read-only
   STATUS      current
   DESCRIPTION
      "Path: virtualEthernet.performance.pppoEClient.mibCounters.h24Performance.ifOutBandwidth

       unit name = bps
       formula = 8 * ; 8 /"
   ::= {pr1646v2VEthPPPoEMCH24PEntry 285212672}

pr1646v2VEthPPPoEMCH24PIfErrSec OBJECT-TYPE
   SYNTAX      Counter32
   MAX-ACCESS  read-only
   STATUS      current
   DESCRIPTION
      "Path: virtualEthernet.performance.pppoEClient.mibCounters.h24Performance.ifErrSec

       32 bit unsigned wrappable counter."
   ::= {pr1646v2VEthPPPoEMCH24PEntry 251658240}

pr1646v2VEthPPPoEMCD7P OBJECT-TYPE
   SYNTAX      SEQUENCE OF Pr1646v2VEthPPPoEMCD7PEntry
   MAX-ACCESS  not-accessible
   STATUS      current
   DESCRIPTION
      ""
   ::= {pr1646v2VEthPPPoE 41680896}

pr1646v2VEthPPPoEMCD7PEntry OBJECT-TYPE
   SYNTAX      Pr1646v2VEthPPPoEMCD7PEntry
   MAX-ACCESS  not-accessible
   STATUS      current
   DESCRIPTION
      ""
   INDEX      { pr1646v2VEthPPPoEMCD7PGlobalIx,
                pr1646v2VEthPPPoETableIx,
                pr1646v2VEthPPPoEMCD7PTableIx }
   ::= {pr1646v2VEthPPPoEMCD7P 1}

Pr1646v2VEthPPPoEMCD7PEntry ::=
   SEQUENCE
      {
      pr1646v2VEthPPPoEMCD7PGlobalIx
         GlobalIndex,
      pr1646v2VEthPPPoEMCD7PTableIx
         TableIndex,
      pr1646v2VEthPPPoEMCD7PSysUpTime
         TimeTicks,
      pr1646v2VEthPPPoEMCD7PIfUpTime
         TimeTicks,
      pr1646v2VEthPPPoEMCD7PIfStatChanges
         Counter32,
      pr1646v2VEthPPPoEMCD7PIfInOctets
         Counter64,
      pr1646v2VEthPPPoEMCD7PIfInUCPkts
         Counter64,
      pr1646v2VEthPPPoEMCD7PIfInNUCPkts
         Counter64,
      pr1646v2VEthPPPoEMCD7PIfInBCPkts
         Counter64,
      pr1646v2VEthPPPoEMCD7PIfInMCPkts
         Counter64,
      pr1646v2VEthPPPoEMCD7PIfInDiscards
         Counter64,
      pr1646v2VEthPPPoEMCD7PIfInErrors
         Counter64,
      pr1646v2VEthPPPoEMCD7PIfInUnkwn
         Counter64,
      pr1646v2VEthPPPoEMCD7PInDropEx
         Counter64,
      pr1646v2VEthPPPoEMCD7PInDropNoMac
         Counter64,
      pr1646v2VEthPPPoEMCD7PInDropNUCast
         Counter64,
      pr1646v2VEthPPPoEMCD7PInDropFilter
         Counter64,
      pr1646v2VEthPPPoEMCD7PIfInBandwidth
         Integer32,
      pr1646v2VEthPPPoEMCD7PIfOutOctets
         Counter64,
      pr1646v2VEthPPPoEMCD7PIfOutUCPkts
         Counter64,
      pr1646v2VEthPPPoEMCD7PIfOutNUCPkts
         Counter64,
      pr1646v2VEthPPPoEMCD7PIfOutBCPkts
         Counter64,
      pr1646v2VEthPPPoEMCD7PIfOutMCPkts
         Counter64,
      pr1646v2VEthPPPoEMCD7PIfOutDiscards
         Counter64,
      pr1646v2VEthPPPoEMCD7PIfOutErrors
         Counter64,
      pr1646v2VEthPPPoEMCD7POutDropEx
         Counter64,
      pr1646v2VEthPPPoEMCD7POutDropNoArp
         Counter64,
      pr1646v2VEthPPPoEMCD7POutDropFilter
         Counter64,
      pr1646v2VEthPPPoEMCD7PIfOutBandwidth
         Integer32,
      pr1646v2VEthPPPoEMCD7PIfErrSec
         Counter32
      }

pr1646v2VEthPPPoEMCD7PGlobalIx OBJECT-TYPE
   SYNTAX      GlobalIndex
   MAX-ACCESS  not-accessible
   STATUS      current
   DESCRIPTION
      "The value of the tlsCntTreeGlobalIndex of the MANAGED OBJECT."
   ::= {pr1646v2VEthPPPoEMCD7PEntry 10}

pr1646v2VEthPPPoEMCD7PTableIx OBJECT-TYPE
   SYNTAX      TableIndex
   MAX-ACCESS  not-accessible
   STATUS      current
   DESCRIPTION
      ""
   ::= {pr1646v2VEthPPPoEMCD7PEntry 11}

pr1646v2VEthPPPoEMCD7PSysUpTime OBJECT-TYPE
   SYNTAX      TimeTicks
   MAX-ACCESS  read-only
   STATUS      current
   DESCRIPTION
      "Path: virtualEthernet.performance.pppoEClient.mibCounters.d7Performance.sysUpTime

       Time in centi-second."
   ::= {pr1646v2VEthPPPoEMCD7PEntry 16777216}

pr1646v2VEthPPPoEMCD7PIfUpTime OBJECT-TYPE
   SYNTAX      TimeTicks
   MAX-ACCESS  read-only
   STATUS      current
   DESCRIPTION
      "Path: virtualEthernet.performance.pppoEClient.mibCounters.d7Performance.ifUpTime

       Time in centi-second."
   ::= {pr1646v2VEthPPPoEMCD7PEntry 33554432}

pr1646v2VEthPPPoEMCD7PIfStatChanges OBJECT-TYPE
   SYNTAX      Counter32
   MAX-ACCESS  read-only
   STATUS      current
   DESCRIPTION
      "Path: virtualEthernet.performance.pppoEClient.mibCounters.d7Performance.ifStatusChanges

       32 bit unsigned wrappable counter."
   ::= {pr1646v2VEthPPPoEMCD7PEntry 50331648}

pr1646v2VEthPPPoEMCD7PIfInOctets OBJECT-TYPE
   SYNTAX      Counter64
   MAX-ACCESS  read-only
   STATUS      current
   DESCRIPTION
      "Path: virtualEthernet.performance.pppoEClient.mibCounters.d7Performance.ifInOctets

       64 bit unsigned wrappable counter."
   ::= {pr1646v2VEthPPPoEMCD7PEntry 67108864}

pr1646v2VEthPPPoEMCD7PIfInUCPkts OBJECT-TYPE
   SYNTAX      Counter64
   MAX-ACCESS  read-only
   STATUS      current
   DESCRIPTION
      "Path: virtualEthernet.performance.pppoEClient.mibCounters.d7Performance.ifInUcastPkts

       64 bit unsigned wrappable counter."
   ::= {pr1646v2VEthPPPoEMCD7PEntry 83886080}

pr1646v2VEthPPPoEMCD7PIfInNUCPkts OBJECT-TYPE
   SYNTAX      Counter64
   MAX-ACCESS  read-only
   STATUS      current
   DESCRIPTION
      "Path: virtualEthernet.performance.pppoEClient.mibCounters.d7Performance.ifInNUcastPkts

       64 bit unsigned wrappable counter."
   ::= {pr1646v2VEthPPPoEMCD7PEntry 100663296}

pr1646v2VEthPPPoEMCD7PIfInBCPkts OBJECT-TYPE
   SYNTAX      Counter64
   MAX-ACCESS  read-only
   STATUS      current
   DESCRIPTION
      "Path: virtualEthernet.performance.pppoEClient.mibCounters.d7Performance.ifInBcastPkts

       64 bit unsigned wrappable counter."
   ::= {pr1646v2VEthPPPoEMCD7PEntry 419430400}

pr1646v2VEthPPPoEMCD7PIfInMCPkts OBJECT-TYPE
   SYNTAX      Counter64
   MAX-ACCESS  read-only
   STATUS      current
   DESCRIPTION
      "Path: virtualEthernet.performance.pppoEClient.mibCounters.d7Performance.ifInMcastPkts

       64 bit unsigned wrappable counter."
   ::= {pr1646v2VEthPPPoEMCD7PEntry 436207616}

pr1646v2VEthPPPoEMCD7PIfInDiscards OBJECT-TYPE
   SYNTAX      Counter64
   MAX-ACCESS  read-only
   STATUS      current
   DESCRIPTION
      "Path: virtualEthernet.performance.pppoEClient.mibCounters.d7Performance.ifInDiscards

       64 bit unsigned wrappable counter."
   ::= {pr1646v2VEthPPPoEMCD7PEntry 117440512}

pr1646v2VEthPPPoEMCD7PIfInErrors OBJECT-TYPE
   SYNTAX      Counter64
   MAX-ACCESS  read-only
   STATUS      current
   DESCRIPTION
      "Path: virtualEthernet.performance.pppoEClient.mibCounters.d7Performance.ifInErrors

       64 bit unsigned wrappable counter."
   ::= {pr1646v2VEthPPPoEMCD7PEntry 134217728}

pr1646v2VEthPPPoEMCD7PIfInUnkwn OBJECT-TYPE
   SYNTAX      Counter64
   MAX-ACCESS  read-only
   STATUS      current
   DESCRIPTION
      "Path: virtualEthernet.performance.pppoEClient.mibCounters.d7Performance.ifInUnknownProtos

       64 bit unsigned wrappable counter."
   ::= {pr1646v2VEthPPPoEMCD7PEntry 150994944}

pr1646v2VEthPPPoEMCD7PInDropEx OBJECT-TYPE
   SYNTAX      Counter64
   MAX-ACCESS  read-only
   STATUS      current
   DESCRIPTION
      "Path: virtualEthernet.performance.pppoEClient.mibCounters.d7Performance.ifInDropLevelExceeded

       64 bit unsigned wrappable counter."
   ::= {pr1646v2VEthPPPoEMCD7PEntry 335544320}

pr1646v2VEthPPPoEMCD7PInDropNoMac OBJECT-TYPE
   SYNTAX      Counter64
   MAX-ACCESS  read-only
   STATUS      current
   DESCRIPTION
      "Path: virtualEthernet.performance.pppoEClient.mibCounters.d7Performance.fInDiscardsNoMacFit

       64 bit unsigned wrappable counter."
   ::= {pr1646v2VEthPPPoEMCD7PEntry 301989888}

pr1646v2VEthPPPoEMCD7PInDropNUCast OBJECT-TYPE
   SYNTAX      Counter64
   MAX-ACCESS  read-only
   STATUS      current
   DESCRIPTION
      "Path: virtualEthernet.performance.pppoEClient.mibCounters.d7Performance.fInDiscardsNUCast

       64 bit unsigned wrappable counter."
   ::= {pr1646v2VEthPPPoEMCD7PEntry 318767104}

pr1646v2VEthPPPoEMCD7PInDropFilter OBJECT-TYPE
   SYNTAX      Counter64
   MAX-ACCESS  read-only
   STATUS      current
   DESCRIPTION
      "Path: virtualEthernet.performance.pppoEClient.mibCounters.d7Performance.fInDiscardsFilter

       64 bit unsigned wrappable counter."
   ::= {pr1646v2VEthPPPoEMCD7PEntry 385875968}

pr1646v2VEthPPPoEMCD7PIfInBandwidth OBJECT-TYPE
   SYNTAX      Integer32
   MAX-ACCESS  read-only
   STATUS      current
   DESCRIPTION
      "Path: virtualEthernet.performance.pppoEClient.mibCounters.d7Performance.ifInBandwidth

       unit name = bps
       formula = 8 * ; 8 /"
   ::= {pr1646v2VEthPPPoEMCD7PEntry 268435456}

pr1646v2VEthPPPoEMCD7PIfOutOctets OBJECT-TYPE
   SYNTAX      Counter64
   MAX-ACCESS  read-only
   STATUS      current
   DESCRIPTION
      "Path: virtualEthernet.performance.pppoEClient.mibCounters.d7Performance.ifOutOctets

       64 bit unsigned wrappable counter."
   ::= {pr1646v2VEthPPPoEMCD7PEntry 167772160}

pr1646v2VEthPPPoEMCD7PIfOutUCPkts OBJECT-TYPE
   SYNTAX      Counter64
   MAX-ACCESS  read-only
   STATUS      current
   DESCRIPTION
      "Path: virtualEthernet.performance.pppoEClient.mibCounters.d7Performance.ifOutUcastPkts

       64 bit unsigned wrappable counter."
   ::= {pr1646v2VEthPPPoEMCD7PEntry 184549376}

pr1646v2VEthPPPoEMCD7PIfOutNUCPkts OBJECT-TYPE
   SYNTAX      Counter64
   MAX-ACCESS  read-only
   STATUS      current
   DESCRIPTION
      "Path: virtualEthernet.performance.pppoEClient.mibCounters.d7Performance.ifOutNUcastPkts

       64 bit unsigned wrappable counter."
   ::= {pr1646v2VEthPPPoEMCD7PEntry 201326592}

pr1646v2VEthPPPoEMCD7PIfOutBCPkts OBJECT-TYPE
   SYNTAX      Counter64
   MAX-ACCESS  read-only
   STATUS      current
   DESCRIPTION
      "Path: virtualEthernet.performance.pppoEClient.mibCounters.d7Performance.ifOutBcastPkts

       64 bit unsigned wrappable counter."
   ::= {pr1646v2VEthPPPoEMCD7PEntry 452984832}

pr1646v2VEthPPPoEMCD7PIfOutMCPkts OBJECT-TYPE
   SYNTAX      Counter64
   MAX-ACCESS  read-only
   STATUS      current
   DESCRIPTION
      "Path: virtualEthernet.performance.pppoEClient.mibCounters.d7Performance.ifOutMcastPkts

       64 bit unsigned wrappable counter."
   ::= {pr1646v2VEthPPPoEMCD7PEntry 469762048}

pr1646v2VEthPPPoEMCD7PIfOutDiscards OBJECT-TYPE
   SYNTAX      Counter64
   MAX-ACCESS  read-only
   STATUS      current
   DESCRIPTION
      "Path: virtualEthernet.performance.pppoEClient.mibCounters.d7Performance.ifOutDiscards

       64 bit unsigned wrappable counter."
   ::= {pr1646v2VEthPPPoEMCD7PEntry 218103808}

pr1646v2VEthPPPoEMCD7PIfOutErrors OBJECT-TYPE
   SYNTAX      Counter64
   MAX-ACCESS  read-only
   STATUS      current
   DESCRIPTION
      "Path: virtualEthernet.performance.pppoEClient.mibCounters.d7Performance.ifOutErrors

       64 bit unsigned wrappable counter."
   ::= {pr1646v2VEthPPPoEMCD7PEntry 234881024}

pr1646v2VEthPPPoEMCD7POutDropEx OBJECT-TYPE
   SYNTAX      Counter64
   MAX-ACCESS  read-only
   STATUS      current
   DESCRIPTION
      "Path: virtualEthernet.performance.pppoEClient.mibCounters.d7Performance.ifOutDropLevelExceeded

       64 bit unsigned wrappable counter."
   ::= {pr1646v2VEthPPPoEMCD7PEntry 352321536}

pr1646v2VEthPPPoEMCD7POutDropNoArp OBJECT-TYPE
   SYNTAX      Counter64
   MAX-ACCESS  read-only
   STATUS      current
   DESCRIPTION
      "Path: virtualEthernet.performance.pppoEClient.mibCounters.d7Performance.ifOutDiscardsNoArp

       64 bit unsigned wrappable counter."
   ::= {pr1646v2VEthPPPoEMCD7PEntry 369098752}

pr1646v2VEthPPPoEMCD7POutDropFilter OBJECT-TYPE
   SYNTAX      Counter64
   MAX-ACCESS  read-only
   STATUS      current
   DESCRIPTION
      "Path: virtualEthernet.performance.pppoEClient.mibCounters.d7Performance.ifOutDiscardsFilter

       64 bit unsigned wrappable counter."
   ::= {pr1646v2VEthPPPoEMCD7PEntry 402653184}

pr1646v2VEthPPPoEMCD7PIfOutBandwidth OBJECT-TYPE
   SYNTAX      Integer32
   MAX-ACCESS  read-only
   STATUS      current
   DESCRIPTION
      "Path: virtualEthernet.performance.pppoEClient.mibCounters.d7Performance.ifOutBandwidth

       unit name = bps
       formula = 8 * ; 8 /"
   ::= {pr1646v2VEthPPPoEMCD7PEntry 285212672}

pr1646v2VEthPPPoEMCD7PIfErrSec OBJECT-TYPE
   SYNTAX      Counter32
   MAX-ACCESS  read-only
   STATUS      current
   DESCRIPTION
      "Path: virtualEthernet.performance.pppoEClient.mibCounters.d7Performance.ifErrSec

       32 bit unsigned wrappable counter."
   ::= {pr1646v2VEthPPPoEMCD7PEntry 251658240}



ar1646v2VEth OBJECT IDENTIFIER ::= {r1646v2VEth 16}


ar1646v2VEthClearCounters OBJECT IDENTIFIER ::= {ar1646v2VEth 263}

ar1646v2VEthClearCountersTable OBJECT-TYPE
   SYNTAX      SEQUENCE OF Ar1646v2VEthClearCountersEntry
   MAX-ACCESS  not-accessible
   STATUS      current
   DESCRIPTION
      "reset counters"
   ::= {ar1646v2VEthClearCounters 1}

ar1646v2VEthClearCountersEntry OBJECT-TYPE
   SYNTAX      Ar1646v2VEthClearCountersEntry
   MAX-ACCESS  not-accessible
   STATUS      current
   DESCRIPTION
      ""
   INDEX      { ar1646v2VEthClearCountersGlobalIx }
   ::= {ar1646v2VEthClearCountersTable 1}

Ar1646v2VEthClearCountersEntry ::=
   SEQUENCE
      {
      ar1646v2VEthClearCountersGlobalIx
         GlobalIndex,
      ar1646v2VEthClearCountersValue
         Integer32
      }

ar1646v2VEthClearCountersGlobalIx OBJECT-TYPE
   SYNTAX      GlobalIndex
   MAX-ACCESS  not-accessible
   STATUS      current
   DESCRIPTION
      "The value of the tlsCntTreeGlobalIndex of the MANAGED OBJECT."
   ::= {ar1646v2VEthClearCountersEntry 10}

ar1646v2VEthClearCountersValue OBJECT-TYPE
   SYNTAX      Integer32
   MAX-ACCESS  read-write
   STATUS      current
   DESCRIPTION
      "Path: virtualEthernet.actions.clearCounters"
   ::= {ar1646v2VEthClearCountersEntry 2147483648}


ar1646v2VEthRestartIntf OBJECT IDENTIFIER ::= {ar1646v2VEth 67}

ar1646v2VEthRestartIntfTable OBJECT-TYPE
   SYNTAX      SEQUENCE OF Ar1646v2VEthRestartIntfEntry
   MAX-ACCESS  not-accessible
   STATUS      current
   DESCRIPTION
      "action in the debug group"
   ::= {ar1646v2VEthRestartIntf 1}

ar1646v2VEthRestartIntfEntry OBJECT-TYPE
   SYNTAX      Ar1646v2VEthRestartIntfEntry
   MAX-ACCESS  not-accessible
   STATUS      current
   DESCRIPTION
      ""
   INDEX      { ar1646v2VEthRestartIntfGlobalIx }
   ::= {ar1646v2VEthRestartIntfTable 1}

Ar1646v2VEthRestartIntfEntry ::=
   SEQUENCE
      {
      ar1646v2VEthRestartIntfGlobalIx
         GlobalIndex,
      ar1646v2VEthRestartIntfValue
         Integer32
      }

ar1646v2VEthRestartIntfGlobalIx OBJECT-TYPE
   SYNTAX      GlobalIndex
   MAX-ACCESS  not-accessible
   STATUS      current
   DESCRIPTION
      "The value of the tlsCntTreeGlobalIndex of the MANAGED OBJECT."
   ::= {ar1646v2VEthRestartIntfEntry 10}

ar1646v2VEthRestartIntfValue OBJECT-TYPE
   SYNTAX      Integer32
   MAX-ACCESS  read-write
   STATUS      current
   DESCRIPTION
      "Path: virtualEthernet.actions.restartIntf"
   ::= {ar1646v2VEthRestartIntfEntry 2147483648}


ar1646v2VEthClearOamEventLog OBJECT IDENTIFIER ::= {ar1646v2VEth 916}

ar1646v2VEthClearOamEventLogTable OBJECT-TYPE
   SYNTAX      SEQUENCE OF Ar1646v2VEthClearOamEventLogEntry
   MAX-ACCESS  not-accessible
   STATUS      current
   DESCRIPTION
      "clear the OAM event log"
   ::= {ar1646v2VEthClearOamEventLog 1}

ar1646v2VEthClearOamEventLogEntry OBJECT-TYPE
   SYNTAX      Ar1646v2VEthClearOamEventLogEntry
   MAX-ACCESS  not-accessible
   STATUS      current
   DESCRIPTION
      ""
   INDEX      { ar1646v2VEthClearOamEventLogGlobalIx }
   ::= {ar1646v2VEthClearOamEventLogTable 1}

Ar1646v2VEthClearOamEventLogEntry ::=
   SEQUENCE
      {
      ar1646v2VEthClearOamEventLogGlobalIx
         GlobalIndex,
      ar1646v2VEthClearOamEventLogValue
         Integer32
      }

ar1646v2VEthClearOamEventLogGlobalIx OBJECT-TYPE
   SYNTAX      GlobalIndex
   MAX-ACCESS  not-accessible
   STATUS      current
   DESCRIPTION
      "The value of the tlsCntTreeGlobalIndex of the MANAGED OBJECT."
   ::= {ar1646v2VEthClearOamEventLogEntry 10}

ar1646v2VEthClearOamEventLogValue OBJECT-TYPE
   SYNTAX      Integer32
   MAX-ACCESS  read-write
   STATUS      current
   DESCRIPTION
      "Path: virtualEthernet.actions.clearOamEventLog"
   ::= {ar1646v2VEthClearOamEventLogEntry 2147483648}


ar1646v2VEthLoopback OBJECT IDENTIFIER ::= {ar1646v2VEth 914}

ar1646v2VEthLoopbackTable OBJECT-TYPE
   SYNTAX      SEQUENCE OF Ar1646v2VEthLoopbackEntry
   MAX-ACCESS  not-accessible
   STATUS      current
   DESCRIPTION
      "ethernet loopback"
   ::= {ar1646v2VEthLoopback 1}

ar1646v2VEthLoopbackEntry OBJECT-TYPE
   SYNTAX      Ar1646v2VEthLoopbackEntry
   MAX-ACCESS  not-accessible
   STATUS      current
   DESCRIPTION
      ""
   INDEX      { ar1646v2VEthLoopbackGlobalIx }
   ::= {ar1646v2VEthLoopbackTable 1}

Ar1646v2VEthLoopbackEntry ::=
   SEQUENCE
      {
      ar1646v2VEthLoopbackGlobalIx
         GlobalIndex,
      ar1646v2VEthLoopbackValue
         Integer32
      }

ar1646v2VEthLoopbackGlobalIx OBJECT-TYPE
   SYNTAX      GlobalIndex
   MAX-ACCESS  not-accessible
   STATUS      current
   DESCRIPTION
      "The value of the tlsCntTreeGlobalIndex of the MANAGED OBJECT."
   ::= {ar1646v2VEthLoopbackEntry 10}

ar1646v2VEthLoopbackValue OBJECT-TYPE
   SYNTAX      Integer32
   MAX-ACCESS  read-write
   STATUS      current
   DESCRIPTION
      "Path: virtualEthernet.actions.loopback"
   ::= {ar1646v2VEthLoopbackEntry 2147483648}


ar1646v2VEthLoop OBJECT IDENTIFIER ::= {ar1646v2VEth 915}

ar1646v2VEthLoopSSCTable OBJECT-TYPE
   SYNTAX      SEQUENCE OF Ar1646v2VEthLoopEntry
   MAX-ACCESS  not-accessible
   STATUS      current
   DESCRIPTION
      "ethernet loopback type"
   ::= {ar1646v2VEthLoop 1}

ar1646v2VEthLoopEntry OBJECT-TYPE
   SYNTAX      Ar1646v2VEthLoopEntry
   MAX-ACCESS  not-accessible
   STATUS      current
   DESCRIPTION
      ""
   INDEX      { ar1646v2VEthLoopGlobalIx }
   ::= {ar1646v2VEthLoopSSCTable 1}

Ar1646v2VEthLoopEntry ::=
   SEQUENCE
      {
      ar1646v2VEthLoopGlobalIx
         GlobalIndex,
      ar1646v2VEthLoopAction
         INTEGER,
      ar1646v2VEthLoopTime
         TimeTicks,
      ar1646v2VEthLoopIntfName
         DisplayString
      }

ar1646v2VEthLoopGlobalIx OBJECT-TYPE
   SYNTAX      GlobalIndex
   MAX-ACCESS  not-accessible
   STATUS      current
   DESCRIPTION
      "The value of the tlsCntTreeGlobalIndex of the MANAGED OBJECT."
   ::= {ar1646v2VEthLoopEntry 10}

ar1646v2VEthLoopAction OBJECT-TYPE
   SYNTAX      INTEGER
               {
               start (1),
               stop (2)
               }
   MAX-ACCESS  read-write
   STATUS      current
   DESCRIPTION
      "Path: virtualEthernet.actions.loop.action

       Possibilities:
               start   (1)
               stop   (2)"
   ::= {ar1646v2VEthLoopEntry 16777216}

ar1646v2VEthLoopTime OBJECT-TYPE
   SYNTAX      TimeTicks
   MAX-ACCESS  read-write
   STATUS      current
   DESCRIPTION
      "Path: virtualEthernet.actions.loop.time

       Time in centi-second."
   ::= {ar1646v2VEthLoopEntry 50331648}

ar1646v2VEthLoopIntfName OBJECT-TYPE
   SYNTAX      DisplayString
   MAX-ACCESS  read-write
   STATUS      current
   DESCRIPTION
      "Path: virtualEthernet.actions.loop.intfName"
   ::= {ar1646v2VEthLoopEntry 67108864}


ar1646v2VEthOamRemLoopback OBJECT IDENTIFIER ::= {ar1646v2VEth 912}

ar1646v2VEthOamRemLoopbackTable OBJECT-TYPE
   SYNTAX      SEQUENCE OF Ar1646v2VEthOamRemLoopbackEntry
   MAX-ACCESS  not-accessible
   STATUS      current
   DESCRIPTION
      "OAM Remote Loopback"
   ::= {ar1646v2VEthOamRemLoopback 1}

ar1646v2VEthOamRemLoopbackEntry OBJECT-TYPE
   SYNTAX      Ar1646v2VEthOamRemLoopbackEntry
   MAX-ACCESS  not-accessible
   STATUS      current
   DESCRIPTION
      ""
   INDEX      { ar1646v2VEthOamRemLoopbackGlobalIx }
   ::= {ar1646v2VEthOamRemLoopbackTable 1}

Ar1646v2VEthOamRemLoopbackEntry ::=
   SEQUENCE
      {
      ar1646v2VEthOamRemLoopbackGlobalIx
         GlobalIndex,
      ar1646v2VEthOamRemLoopbackValue
         Integer32
      }

ar1646v2VEthOamRemLoopbackGlobalIx OBJECT-TYPE
   SYNTAX      GlobalIndex
   MAX-ACCESS  not-accessible
   STATUS      current
   DESCRIPTION
      "The value of the tlsCntTreeGlobalIndex of the MANAGED OBJECT."
   ::= {ar1646v2VEthOamRemLoopbackEntry 10}

ar1646v2VEthOamRemLoopbackValue OBJECT-TYPE
   SYNTAX      Integer32
   MAX-ACCESS  read-write
   STATUS      current
   DESCRIPTION
      "Path: virtualEthernet.actions.oamRemLoopback"
   ::= {ar1646v2VEthOamRemLoopbackEntry 2147483648}


ar1646v2VEthType OBJECT IDENTIFIER ::= {ar1646v2VEth 913}

ar1646v2VEthTypeTable OBJECT-TYPE
   SYNTAX      SEQUENCE OF Ar1646v2VEthTypeEntry
   MAX-ACCESS  not-accessible
   STATUS      current
   DESCRIPTION
      "OAM Remote Loopback type"
   ::= {ar1646v2VEthType 1}

ar1646v2VEthTypeEntry OBJECT-TYPE
   SYNTAX      Ar1646v2VEthTypeEntry
   MAX-ACCESS  not-accessible
   STATUS      current
   DESCRIPTION
      ""
   INDEX      { ar1646v2VEthTypeGlobalIx }
   ::= {ar1646v2VEthTypeTable 1}

Ar1646v2VEthTypeEntry ::=
   SEQUENCE
      {
      ar1646v2VEthTypeGlobalIx
         GlobalIndex,
      ar1646v2VEthTypeValue
         INTEGER
      }

ar1646v2VEthTypeGlobalIx OBJECT-TYPE
   SYNTAX      GlobalIndex
   MAX-ACCESS  not-accessible
   STATUS      current
   DESCRIPTION
      "The value of the tlsCntTreeGlobalIndex of the MANAGED OBJECT."
   ::= {ar1646v2VEthTypeEntry 10}

ar1646v2VEthTypeValue OBJECT-TYPE
   SYNTAX      INTEGER
               {
               start (0),
               stop (1)
               }
   MAX-ACCESS  read-write
   STATUS      current
   DESCRIPTION
      "Path: virtualEthernet.actions.type

       Possibilities:
               start   (0)
               stop   (1)"
   ::= {ar1646v2VEthTypeEntry 2147483648}


ar1646v2VEthSendWOL OBJECT IDENTIFIER ::= {ar1646v2VEth 333}

ar1646v2VEthSendWOLTable OBJECT-TYPE
   SYNTAX      SEQUENCE OF Ar1646v2VEthSendWOLEntry
   MAX-ACCESS  not-accessible
   STATUS      current
   DESCRIPTION
      "send a WakeOnLan message on this interface"
   ::= {ar1646v2VEthSendWOL 1}

ar1646v2VEthSendWOLEntry OBJECT-TYPE
   SYNTAX      Ar1646v2VEthSendWOLEntry
   MAX-ACCESS  not-accessible
   STATUS      current
   DESCRIPTION
      ""
   INDEX      { ar1646v2VEthSendWOLGlobalIx }
   ::= {ar1646v2VEthSendWOLTable 1}

Ar1646v2VEthSendWOLEntry ::=
   SEQUENCE
      {
      ar1646v2VEthSendWOLGlobalIx
         GlobalIndex,
      ar1646v2VEthSendWOLValue
         Integer32
      }

ar1646v2VEthSendWOLGlobalIx OBJECT-TYPE
   SYNTAX      GlobalIndex
   MAX-ACCESS  not-accessible
   STATUS      current
   DESCRIPTION
      "The value of the tlsCntTreeGlobalIndex of the MANAGED OBJECT."
   ::= {ar1646v2VEthSendWOLEntry 10}

ar1646v2VEthSendWOLValue OBJECT-TYPE
   SYNTAX      Integer32
   MAX-ACCESS  read-write
   STATUS      current
   DESCRIPTION
      "Path: virtualEthernet.actions.sendWOL"
   ::= {ar1646v2VEthSendWOLEntry 2147483648}


ar1646v2VEthWolInfo OBJECT IDENTIFIER ::= {ar1646v2VEth 332}

ar1646v2VEthWolInfoSSCTable OBJECT-TYPE
   SYNTAX      SEQUENCE OF Ar1646v2VEthWolInfoEntry
   MAX-ACCESS  not-accessible
   STATUS      current
   DESCRIPTION
      "content of a WakeOnLan message"
   ::= {ar1646v2VEthWolInfo 1}

ar1646v2VEthWolInfoEntry OBJECT-TYPE
   SYNTAX      Ar1646v2VEthWolInfoEntry
   MAX-ACCESS  not-accessible
   STATUS      current
   DESCRIPTION
      ""
   INDEX      { ar1646v2VEthWolInfoGlobalIx }
   ::= {ar1646v2VEthWolInfoSSCTable 1}

Ar1646v2VEthWolInfoEntry ::=
   SEQUENCE
      {
      ar1646v2VEthWolInfoGlobalIx
         GlobalIndex,
      ar1646v2VEthWolInfoTargetMAC
         OCTET STRING,
      ar1646v2VEthWolInfoPassword
         OCTET STRING
      }

ar1646v2VEthWolInfoGlobalIx OBJECT-TYPE
   SYNTAX      GlobalIndex
   MAX-ACCESS  not-accessible
   STATUS      current
   DESCRIPTION
      "The value of the tlsCntTreeGlobalIndex of the MANAGED OBJECT."
   ::= {ar1646v2VEthWolInfoEntry 10}

ar1646v2VEthWolInfoTargetMAC OBJECT-TYPE
   SYNTAX      OCTET STRING
   MAX-ACCESS  read-write
   STATUS      current
   DESCRIPTION
      "Path: virtualEthernet.actions.wolInfo.targetMAC

       MAC address."
   ::= {ar1646v2VEthWolInfoEntry 16777216}

ar1646v2VEthWolInfoPassword OBJECT-TYPE
   SYNTAX      OCTET STRING
   MAX-ACCESS  read-write
   STATUS      current
   DESCRIPTION
      "Path: virtualEthernet.actions.wolInfo.password"
   ::= {ar1646v2VEthWolInfoEntry 33554432}


ar1646v2VEthClearArpCache OBJECT IDENTIFIER ::= {ar1646v2VEth 25}

ar1646v2VEthClearArpCacheTable OBJECT-TYPE
   SYNTAX      SEQUENCE OF Ar1646v2VEthClearArpCacheEntry
   MAX-ACCESS  not-accessible
   STATUS      current
   DESCRIPTION
      "clear all dynamic enties in ARP cache table"
   ::= {ar1646v2VEthClearArpCache 1}

ar1646v2VEthClearArpCacheEntry OBJECT-TYPE
   SYNTAX      Ar1646v2VEthClearArpCacheEntry
   MAX-ACCESS  not-accessible
   STATUS      current
   DESCRIPTION
      ""
   INDEX      { ar1646v2VEthClearArpCacheGlobalIx }
   ::= {ar1646v2VEthClearArpCacheTable 1}

Ar1646v2VEthClearArpCacheEntry ::=
   SEQUENCE
      {
      ar1646v2VEthClearArpCacheGlobalIx
         GlobalIndex,
      ar1646v2VEthClearArpCacheValue
         Integer32
      }

ar1646v2VEthClearArpCacheGlobalIx OBJECT-TYPE
   SYNTAX      GlobalIndex
   MAX-ACCESS  not-accessible
   STATUS      current
   DESCRIPTION
      "The value of the tlsCntTreeGlobalIndex of the MANAGED OBJECT."
   ::= {ar1646v2VEthClearArpCacheEntry 10}

ar1646v2VEthClearArpCacheValue OBJECT-TYPE
   SYNTAX      Integer32
   MAX-ACCESS  read-write
   STATUS      current
   DESCRIPTION
      "Path: virtualEthernet.actions.clearArpCache"
   ::= {ar1646v2VEthClearArpCacheEntry 2147483648}



fr1646v2VEth OBJECT IDENTIFIER ::= {r1646v2VEth 13}


fr1646v2VEthAlarm OBJECT IDENTIFIER ::= {fr1646v2VEth 207}

fr1646v2VEthAlarmSSCTable OBJECT-TYPE
   SYNTAX      SEQUENCE OF Fr1646v2VEthAlarmEntry
   MAX-ACCESS  not-accessible
   STATUS      current
   DESCRIPTION
      "IfAlarmInfo"
   ::= {fr1646v2VEthAlarm 1}

fr1646v2VEthAlarmEntry OBJECT-TYPE
   SYNTAX      Fr1646v2VEthAlarmEntry
   MAX-ACCESS  not-accessible
   STATUS      current
   DESCRIPTION
      ""
   INDEX      { fr1646v2VEthAlarmGlobalIx }
   ::= {fr1646v2VEthAlarmSSCTable 1}

Fr1646v2VEthAlarmEntry ::=
   SEQUENCE
      {
      fr1646v2VEthAlarmGlobalIx
         GlobalIndex,
      fr1646v2VEthAlarmDiscriminator
         Integer32,
      fr1646v2VEthAlarmCurrent
         Integer32,
      fr1646v2VEthAlarmPrevious
         Integer32,
      fr1646v2VEthAlarmMask
         Integer32,
      fr1646v2VEthAlarmLevLinkDown
         Integer32,
      fr1646v2VEthAlarmLevPppoEDown
         Integer32
      }

fr1646v2VEthAlarmGlobalIx OBJECT-TYPE
   SYNTAX      GlobalIndex
   MAX-ACCESS  not-accessible
   STATUS      current
   DESCRIPTION
      "The value of the tlsCntTreeGlobalIndex of the MANAGED OBJECT."
   ::= {fr1646v2VEthAlarmEntry 10}

fr1646v2VEthAlarmDiscriminator OBJECT-TYPE
   SYNTAX      Integer32
   MAX-ACCESS  read-only
   STATUS      current
   DESCRIPTION
      "Path: virtualEthernet.alarms.alarmInfo.discriminator"
   ::= {fr1646v2VEthAlarmEntry 16777216}

fr1646v2VEthAlarmCurrent OBJECT-TYPE
   SYNTAX      Integer32
   MAX-ACCESS  read-only
   STATUS      current
   DESCRIPTION
      "Path: virtualEthernet.alarms.alarmInfo.currentAlarms

       Bit meanings:
               bit 0 = linkDown,
               bit 9 = pppoEDown"
   ::= {fr1646v2VEthAlarmEntry 33554432}

fr1646v2VEthAlarmPrevious OBJECT-TYPE
   SYNTAX      Integer32
   MAX-ACCESS  read-only
   STATUS      current
   DESCRIPTION
      "Path: virtualEthernet.alarms.alarmInfo.previousAlarms

       Bit meanings:
               bit 0 = linkDown,
               bit 9 = pppoEDown"
   ::= {fr1646v2VEthAlarmEntry 50331648}

fr1646v2VEthAlarmMask OBJECT-TYPE
   SYNTAX      Integer32
   MAX-ACCESS  read-only
   STATUS      current
   DESCRIPTION
      "Path: virtualEthernet.alarms.alarmInfo.alarmMask

       Bit meanings:
               bit 0 = linkDown,
               bit 9 = pppoEDown"
   ::= {fr1646v2VEthAlarmEntry 67108864}

fr1646v2VEthAlarmLevLinkDown OBJECT-TYPE
   SYNTAX      Integer32
   MAX-ACCESS  read-only
   STATUS      current
   DESCRIPTION
      "Path: virtualEthernet.alarms.alarmInfo.alarmLevel.linkDown"
   ::= {fr1646v2VEthAlarmEntry 83951616}

fr1646v2VEthAlarmLevPppoEDown OBJECT-TYPE
   SYNTAX      Integer32
   MAX-ACCESS  read-only
   STATUS      current
   DESCRIPTION
      "Path: virtualEthernet.alarms.alarmInfo.alarmLevel.pppoEDown"
   ::= {fr1646v2VEthAlarmEntry 84541440}


fr1646v2VEthAlarmE2 OBJECT IDENTIFIER ::= {fr1646v2VEthAlarm 2}

fr1646v2VEthAlarmE2Entry OBJECT IDENTIFIER ::= {fr1646v2VEthAlarmE2 1}

fr1646v2VEthAlarmE2LinkDown OBJECT IDENTIFIER ::= {fr1646v2VEthAlarmE2Entry 10}

fr1646v2VEthAlarmE2LinkDownPfx OBJECT IDENTIFIER ::= {fr1646v2VEthAlarmE2LinkDown 0}

fr1646v2VEthAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'virtualEthernet'
                (root='router1646') has changed from the ON to the OFF state."
   ::= {fr1646v2VEthAlarmE2LinkDownPfx 1}

fr1646v2VEthAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'virtualEthernet'
                (root='router1646') has changed from the OFF to the ON state."
   ::= {fr1646v2VEthAlarmE2LinkDownPfx 2}

fr1646v2VEthAlarmE2PppoEDown OBJECT IDENTIFIER ::= {fr1646v2VEthAlarmE2Entry 19}

fr1646v2VEthAlarmE2PppoEDownPfx OBJECT IDENTIFIER ::= {fr1646v2VEthAlarmE2PppoEDown 0}

fr1646v2VEthAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'virtualEthernet'
                (root='router1646') has changed from the ON to the OFF state."
   ::= {fr1646v2VEthAlarmE2PppoEDownPfx 1}

fr1646v2VEthAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'virtualEthernet'
                (root='router1646') has changed from the OFF to the ON state."
   ::= {fr1646v2VEthAlarmE2PppoEDownPfx 2}



END
