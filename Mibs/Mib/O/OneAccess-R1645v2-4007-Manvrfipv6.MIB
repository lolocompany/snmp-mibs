OneAccess-R1645v2-4007-Manvrfipv6 DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Manvrfipv6 OBJECT IDENTIFIER ::= {r1645Rootv2 4007}

r1645v2Manvrfipv6MOProp OBJECT-TYPE
   SYNTAX      SEQUENCE OF R1645v2Manvrfipv6MOPropEntry
   MAX-ACCESS  not-accessible
   STATUS      current
   DESCRIPTION
      ""
   ::= {r1645v2Manvrfipv6 1}

r1645v2Manvrfipv6MOPropEntry OBJECT-TYPE
   SYNTAX      R1645v2Manvrfipv6MOPropEntry
   MAX-ACCESS  not-accessible
   STATUS      current
   DESCRIPTION
      ""
   INDEX      { r1645v2Manvrfipv6MOPropGlobalIx }
   ::= {r1645v2Manvrfipv6MOProp 1}

R1645v2Manvrfipv6MOPropEntry ::=
   SEQUENCE
      {
      r1645v2Manvrfipv6MOPropPath
         ContainmentPath,
      r1645v2Manvrfipv6MOPropRev
         ObjectRevision,
      r1645v2Manvrfipv6MOPropGlobalIx
         GlobalIndex
      }

r1645v2Manvrfipv6MOPropPath OBJECT-TYPE
   SYNTAX      ContainmentPath
   MAX-ACCESS  read-only
   STATUS      current
   DESCRIPTION
      "Textual description of the containment tree from the instance of
       the root object down to the instance of the current object."
   ::= {r1645v2Manvrfipv6MOPropEntry 3}

r1645v2Manvrfipv6MOPropRev OBJECT-TYPE
   SYNTAX      ObjectRevision
   MAX-ACCESS  read-only
   STATUS      current
   DESCRIPTION
      "This value corresponds with the revision of the MANAGED OBJECT."
   ::= {r1645v2Manvrfipv6MOPropEntry 4}

r1645v2Manvrfipv6MOPropGlobalIx OBJECT-TYPE
   SYNTAX      GlobalIndex
   MAX-ACCESS  read-only
   STATUS      current
   DESCRIPTION
      "The value of the tlsCntTreeGlobalIndex of the MANAGED OBJECT."
   ::= {r1645v2Manvrfipv6MOPropEntry 10}



er1645v2Manvrfipv6 OBJECT IDENTIFIER ::= {r1645v2Manvrfipv6 11}


er1645v2Manvrfipv6Tma OBJECT IDENTIFIER ::= {er1645v2Manvrfipv6 36}

er1645v2Manvrfipv6TmaTable OBJECT-TYPE
   SYNTAX      SEQUENCE OF Er1645v2Manvrfipv6TmaEntry
   MAX-ACCESS  not-accessible
   STATUS      current
   DESCRIPTION
      "Attribute that controls the orchid how to treat the UDP packets for the TMA port
                         enabled:    act on UDP packets destined for the TMA port
                         disabled:   discard UDP packets destined for the TMA port"
   ::= {er1645v2Manvrfipv6Tma 1}

er1645v2Manvrfipv6TmaEntry OBJECT-TYPE
   SYNTAX      Er1645v2Manvrfipv6TmaEntry
   MAX-ACCESS  not-accessible
   STATUS      current
   DESCRIPTION
      ""
   INDEX      { er1645v2Manvrfipv6TmaGlobalIx }
   ::= {er1645v2Manvrfipv6TmaTable 1}

Er1645v2Manvrfipv6TmaEntry ::=
   SEQUENCE
      {
      er1645v2Manvrfipv6TmaGlobalIx
         GlobalIndex,
      er1645v2Manvrfipv6TmaValue
         INTEGER
      }

er1645v2Manvrfipv6TmaGlobalIx OBJECT-TYPE
   SYNTAX      GlobalIndex
   MAX-ACCESS  not-accessible
   STATUS      current
   DESCRIPTION
      "The value of the tlsCntTreeGlobalIndex of the MANAGED OBJECT."
   ::= {er1645v2Manvrfipv6TmaEntry 10}

er1645v2Manvrfipv6TmaValue OBJECT-TYPE
   SYNTAX      INTEGER
               {
               disabled (0),
               enabled (1)
               }
   MAX-ACCESS  read-write
   STATUS      current
   DESCRIPTION
      "Path: management.editConf.tma

       Possibilities:
               disabled   (0)
               enabled   (1)"
   ::= {er1645v2Manvrfipv6TmaEntry 2147483648}


er1645v2Manvrfipv6Snmp OBJECT IDENTIFIER ::= {er1645v2Manvrfipv6 18}

er1645v2Manvrfipv6SnmpTable OBJECT-TYPE
   SYNTAX      SEQUENCE OF Er1645v2Manvrfipv6SnmpEntry
   MAX-ACCESS  not-accessible
   STATUS      current
   DESCRIPTION
      "Attribute that controls the orchid how to treat the UDP packets for the SNMP port (161)
                         enabled:    act on UDP packets destined for the SNMP port
                         disabled:   discard UDP packets destined for the SNMP port"
   ::= {er1645v2Manvrfipv6Snmp 1}

er1645v2Manvrfipv6SnmpEntry OBJECT-TYPE
   SYNTAX      Er1645v2Manvrfipv6SnmpEntry
   MAX-ACCESS  not-accessible
   STATUS      current
   DESCRIPTION
      ""
   INDEX      { er1645v2Manvrfipv6SnmpGlobalIx }
   ::= {er1645v2Manvrfipv6SnmpTable 1}

Er1645v2Manvrfipv6SnmpEntry ::=
   SEQUENCE
      {
      er1645v2Manvrfipv6SnmpGlobalIx
         GlobalIndex,
      er1645v2Manvrfipv6SnmpValue
         INTEGER
      }

er1645v2Manvrfipv6SnmpGlobalIx OBJECT-TYPE
   SYNTAX      GlobalIndex
   MAX-ACCESS  not-accessible
   STATUS      current
   DESCRIPTION
      "The value of the tlsCntTreeGlobalIndex of the MANAGED OBJECT."
   ::= {er1645v2Manvrfipv6SnmpEntry 10}

er1645v2Manvrfipv6SnmpValue OBJECT-TYPE
   SYNTAX      INTEGER
               {
               disabled (0),
               enabled (1)
               }
   MAX-ACCESS  read-write
   STATUS      current
   DESCRIPTION
      "Path: management.editConf.snmp

       Possibilities:
               disabled   (0)
               enabled   (1)"
   ::= {er1645v2Manvrfipv6SnmpEntry 2147483648}


er1645v2Manvrfipv6Telnet OBJECT IDENTIFIER ::= {er1645v2Manvrfipv6 19}

er1645v2Manvrfipv6TelnetTable OBJECT-TYPE
   SYNTAX      SEQUENCE OF Er1645v2Manvrfipv6TelnetEntry
   MAX-ACCESS  not-accessible
   STATUS      current
   DESCRIPTION
      "Attribute that controls the orchid how to treat the TCP packets for the TELNET port
                         enabled:    act on TCP packets destined for the TELNET port
                         disabled:   discard TCP packets destined for the TELNET port"
   ::= {er1645v2Manvrfipv6Telnet 1}

er1645v2Manvrfipv6TelnetEntry OBJECT-TYPE
   SYNTAX      Er1645v2Manvrfipv6TelnetEntry
   MAX-ACCESS  not-accessible
   STATUS      current
   DESCRIPTION
      ""
   INDEX      { er1645v2Manvrfipv6TelnetGlobalIx }
   ::= {er1645v2Manvrfipv6TelnetTable 1}

Er1645v2Manvrfipv6TelnetEntry ::=
   SEQUENCE
      {
      er1645v2Manvrfipv6TelnetGlobalIx
         GlobalIndex,
      er1645v2Manvrfipv6TelnetValue
         INTEGER
      }

er1645v2Manvrfipv6TelnetGlobalIx OBJECT-TYPE
   SYNTAX      GlobalIndex
   MAX-ACCESS  not-accessible
   STATUS      current
   DESCRIPTION
      "The value of the tlsCntTreeGlobalIndex of the MANAGED OBJECT."
   ::= {er1645v2Manvrfipv6TelnetEntry 10}

er1645v2Manvrfipv6TelnetValue OBJECT-TYPE
   SYNTAX      INTEGER
               {
               disabled (0),
               enabled (1)
               }
   MAX-ACCESS  read-write
   STATUS      current
   DESCRIPTION
      "Path: management.editConf.telnet

       Possibilities:
               disabled   (0)
               enabled   (1)"
   ::= {er1645v2Manvrfipv6TelnetEntry 2147483648}


er1645v2Manvrfipv6Tcp OBJECT IDENTIFIER ::= {er1645v2Manvrfipv6 34}

er1645v2Manvrfipv6TcpSSCTable OBJECT-TYPE
   SYNTAX      SEQUENCE OF Er1645v2Manvrfipv6TcpEntry
   MAX-ACCESS  not-accessible
   STATUS      current
   DESCRIPTION
      "tcp configuration parameters"
   ::= {er1645v2Manvrfipv6Tcp 1}

er1645v2Manvrfipv6TcpEntry OBJECT-TYPE
   SYNTAX      Er1645v2Manvrfipv6TcpEntry
   MAX-ACCESS  not-accessible
   STATUS      current
   DESCRIPTION
      ""
   INDEX      { er1645v2Manvrfipv6TcpGlobalIx }
   ::= {er1645v2Manvrfipv6TcpSSCTable 1}

Er1645v2Manvrfipv6TcpEntry ::=
   SEQUENCE
      {
      er1645v2Manvrfipv6TcpGlobalIx
         GlobalIndex,
      er1645v2Manvrfipv6TcpMaxReceiveWindow
         Integer32,
      er1645v2Manvrfipv6TcpMaxSegmentSize
         Integer32
      }

er1645v2Manvrfipv6TcpGlobalIx OBJECT-TYPE
   SYNTAX      GlobalIndex
   MAX-ACCESS  not-accessible
   STATUS      current
   DESCRIPTION
      "The value of the tlsCntTreeGlobalIndex of the MANAGED OBJECT."
   ::= {er1645v2Manvrfipv6TcpEntry 10}

er1645v2Manvrfipv6TcpMaxReceiveWindow OBJECT-TYPE
   SYNTAX      Integer32
   MAX-ACCESS  read-write
   STATUS      current
   DESCRIPTION
      "Path: management.editConf.tcp.maxReceiveWindow"
   ::= {er1645v2Manvrfipv6TcpEntry 16777216}

er1645v2Manvrfipv6TcpMaxSegmentSize OBJECT-TYPE
   SYNTAX      Integer32
   MAX-ACCESS  read-write
   STATUS      current
   DESCRIPTION
      "Path: management.editConf.tcp.maxSegmentSize"
   ::= {er1645v2Manvrfipv6TcpEntry 33554432}


er1645v2Manvrfipv6MaxPingReplies OBJECT IDENTIFIER ::= {er1645v2Manvrfipv6 26}

er1645v2Manvrfipv6MaxPingRepliesTable OBJECT-TYPE
   SYNTAX      SEQUENCE OF Er1645v2Manvrfipv6MaxPingRepliesEntry
   MAX-ACCESS  not-accessible
   STATUS      current
   DESCRIPTION
      "max nr of ping replies per second"
   ::= {er1645v2Manvrfipv6MaxPingReplies 1}

er1645v2Manvrfipv6MaxPingRepliesEntry OBJECT-TYPE
   SYNTAX      Er1645v2Manvrfipv6MaxPingRepliesEntry
   MAX-ACCESS  not-accessible
   STATUS      current
   DESCRIPTION
      ""
   INDEX      { er1645v2Manvrfipv6MaxPingRepliesGlobalIx }
   ::= {er1645v2Manvrfipv6MaxPingRepliesTable 1}

Er1645v2Manvrfipv6MaxPingRepliesEntry ::=
   SEQUENCE
      {
      er1645v2Manvrfipv6MaxPingRepliesGlobalIx
         GlobalIndex,
      er1645v2Manvrfipv6MaxPingRepliesValue
         INTEGER
      }

er1645v2Manvrfipv6MaxPingRepliesGlobalIx OBJECT-TYPE
   SYNTAX      GlobalIndex
   MAX-ACCESS  not-accessible
   STATUS      current
   DESCRIPTION
      "The value of the tlsCntTreeGlobalIndex of the MANAGED OBJECT."
   ::= {er1645v2Manvrfipv6MaxPingRepliesEntry 10}

er1645v2Manvrfipv6MaxPingRepliesValue OBJECT-TYPE
   SYNTAX      INTEGER
               {
               disabled (0)
               }
   MAX-ACCESS  read-write
   STATUS      current
   DESCRIPTION
      "Path: management.editConf.maxPingReplies

       Possibilities:
               disabled   (0)"
   ::= {er1645v2Manvrfipv6MaxPingRepliesEntry 2147483648}


er1645v2Manvrfipv6Http OBJECT IDENTIFIER ::= {er1645v2Manvrfipv6 77}

er1645v2Manvrfipv6HttpTable OBJECT-TYPE
   SYNTAX      SEQUENCE OF Er1645v2Manvrfipv6HttpEntry
   MAX-ACCESS  not-accessible
   STATUS      current
   DESCRIPTION
      "Attribute that controls the orchid how to treat the TCP packets for the TELNET port
                         enabled:    act on TCP packets destined for the TELNET port
                         disabled:   discard TCP packets destined for the TELNET port"
   ::= {er1645v2Manvrfipv6Http 1}

er1645v2Manvrfipv6HttpEntry OBJECT-TYPE
   SYNTAX      Er1645v2Manvrfipv6HttpEntry
   MAX-ACCESS  not-accessible
   STATUS      current
   DESCRIPTION
      ""
   INDEX      { er1645v2Manvrfipv6HttpGlobalIx }
   ::= {er1645v2Manvrfipv6HttpTable 1}

Er1645v2Manvrfipv6HttpEntry ::=
   SEQUENCE
      {
      er1645v2Manvrfipv6HttpGlobalIx
         GlobalIndex,
      er1645v2Manvrfipv6HttpValue
         INTEGER
      }

er1645v2Manvrfipv6HttpGlobalIx OBJECT-TYPE
   SYNTAX      GlobalIndex
   MAX-ACCESS  not-accessible
   STATUS      current
   DESCRIPTION
      "The value of the tlsCntTreeGlobalIndex of the MANAGED OBJECT."
   ::= {er1645v2Manvrfipv6HttpEntry 10}

er1645v2Manvrfipv6HttpValue OBJECT-TYPE
   SYNTAX      INTEGER
               {
               disabled (0),
               enabled (1)
               }
   MAX-ACCESS  read-write
   STATUS      current
   DESCRIPTION
      "Path: management.editConf.http

       Possibilities:
               disabled   (0)
               enabled   (1)"
   ::= {er1645v2Manvrfipv6HttpEntry 2147483648}


er1645v2Manvrfipv6Https OBJECT IDENTIFIER ::= {er1645v2Manvrfipv6 27}

er1645v2Manvrfipv6HttpsTable OBJECT-TYPE
   SYNTAX      SEQUENCE OF Er1645v2Manvrfipv6HttpsEntry
   MAX-ACCESS  not-accessible
   STATUS      current
   DESCRIPTION
      "Attribute that controls the orchid how to treat the TCP packets for the TELNET port
                         enabled:    act on TCP packets destined for the TELNET port
                         disabled:   discard TCP packets destined for the TELNET port"
   ::= {er1645v2Manvrfipv6Https 1}

er1645v2Manvrfipv6HttpsEntry OBJECT-TYPE
   SYNTAX      Er1645v2Manvrfipv6HttpsEntry
   MAX-ACCESS  not-accessible
   STATUS      current
   DESCRIPTION
      ""
   INDEX      { er1645v2Manvrfipv6HttpsGlobalIx }
   ::= {er1645v2Manvrfipv6HttpsTable 1}

Er1645v2Manvrfipv6HttpsEntry ::=
   SEQUENCE
      {
      er1645v2Manvrfipv6HttpsGlobalIx
         GlobalIndex,
      er1645v2Manvrfipv6HttpsValue
         INTEGER
      }

er1645v2Manvrfipv6HttpsGlobalIx OBJECT-TYPE
   SYNTAX      GlobalIndex
   MAX-ACCESS  not-accessible
   STATUS      current
   DESCRIPTION
      "The value of the tlsCntTreeGlobalIndex of the MANAGED OBJECT."
   ::= {er1645v2Manvrfipv6HttpsEntry 10}

er1645v2Manvrfipv6HttpsValue OBJECT-TYPE
   SYNTAX      INTEGER
               {
               disabled (0),
               enabled (1)
               }
   MAX-ACCESS  read-write
   STATUS      current
   DESCRIPTION
      "Path: management.editConf.https

       Possibilities:
               disabled   (0)
               enabled   (1)"
   ::= {er1645v2Manvrfipv6HttpsEntry 2147483648}


er1645v2Manvrfipv6Ssh OBJECT IDENTIFIER ::= {er1645v2Manvrfipv6 30}

er1645v2Manvrfipv6SshTable OBJECT-TYPE
   SYNTAX      SEQUENCE OF Er1645v2Manvrfipv6SshEntry
   MAX-ACCESS  not-accessible
   STATUS      current
   DESCRIPTION
      "Attribute that controls the orchid how to treat the TCP packets for the TELNET port
                         enabled:    act on TCP packets destined for the TELNET port
                         disabled:   discard TCP packets destined for the TELNET port"
   ::= {er1645v2Manvrfipv6Ssh 1}

er1645v2Manvrfipv6SshEntry OBJECT-TYPE
   SYNTAX      Er1645v2Manvrfipv6SshEntry
   MAX-ACCESS  not-accessible
   STATUS      current
   DESCRIPTION
      ""
   INDEX      { er1645v2Manvrfipv6SshGlobalIx }
   ::= {er1645v2Manvrfipv6SshTable 1}

Er1645v2Manvrfipv6SshEntry ::=
   SEQUENCE
      {
      er1645v2Manvrfipv6SshGlobalIx
         GlobalIndex,
      er1645v2Manvrfipv6SshValue
         INTEGER
      }

er1645v2Manvrfipv6SshGlobalIx OBJECT-TYPE
   SYNTAX      GlobalIndex
   MAX-ACCESS  not-accessible
   STATUS      current
   DESCRIPTION
      "The value of the tlsCntTreeGlobalIndex of the MANAGED OBJECT."
   ::= {er1645v2Manvrfipv6SshEntry 10}

er1645v2Manvrfipv6SshValue OBJECT-TYPE
   SYNTAX      INTEGER
               {
               disabled (0),
               enabled (1)
               }
   MAX-ACCESS  read-write
   STATUS      current
   DESCRIPTION
      "Path: management.editConf.ssh

       Possibilities:
               disabled   (0)
               enabled   (1)"
   ::= {er1645v2Manvrfipv6SshEntry 2147483648}


er1645v2Manvrfipv6Echo OBJECT IDENTIFIER ::= {er1645v2Manvrfipv6 7}

er1645v2Manvrfipv6EchoTable OBJECT-TYPE
   SYNTAX      SEQUENCE OF Er1645v2Manvrfipv6EchoEntry
   MAX-ACCESS  not-accessible
   STATUS      current
   DESCRIPTION
      "Attribute that controls the orchid how to treat the TCP packets for the TELNET port
                         enabled:    act on TCP packets destined for the TELNET port
                         disabled:   discard TCP packets destined for the TELNET port"
   ::= {er1645v2Manvrfipv6Echo 1}

er1645v2Manvrfipv6EchoEntry OBJECT-TYPE
   SYNTAX      Er1645v2Manvrfipv6EchoEntry
   MAX-ACCESS  not-accessible
   STATUS      current
   DESCRIPTION
      ""
   INDEX      { er1645v2Manvrfipv6EchoGlobalIx }
   ::= {er1645v2Manvrfipv6EchoTable 1}

Er1645v2Manvrfipv6EchoEntry ::=
   SEQUENCE
      {
      er1645v2Manvrfipv6EchoGlobalIx
         GlobalIndex,
      er1645v2Manvrfipv6EchoValue
         INTEGER
      }

er1645v2Manvrfipv6EchoGlobalIx OBJECT-TYPE
   SYNTAX      GlobalIndex
   MAX-ACCESS  not-accessible
   STATUS      current
   DESCRIPTION
      "The value of the tlsCntTreeGlobalIndex of the MANAGED OBJECT."
   ::= {er1645v2Manvrfipv6EchoEntry 10}

er1645v2Manvrfipv6EchoValue OBJECT-TYPE
   SYNTAX      INTEGER
               {
               disabled (0),
               enabled (1)
               }
   MAX-ACCESS  read-write
   STATUS      current
   DESCRIPTION
      "Path: management.editConf.echo

       Possibilities:
               disabled   (0)
               enabled   (1)"
   ::= {er1645v2Manvrfipv6EchoEntry 2147483648}


er1645v2Manvrfipv6Discard OBJECT IDENTIFIER ::= {er1645v2Manvrfipv6 9}

er1645v2Manvrfipv6DiscardTable OBJECT-TYPE
   SYNTAX      SEQUENCE OF Er1645v2Manvrfipv6DiscardEntry
   MAX-ACCESS  not-accessible
   STATUS      current
   DESCRIPTION
      "Attribute that controls the orchid how to treat the TCP packets for the TELNET port
                         enabled:    act on TCP packets destined for the TELNET port
                         disabled:   discard TCP packets destined for the TELNET port"
   ::= {er1645v2Manvrfipv6Discard 1}

er1645v2Manvrfipv6DiscardEntry OBJECT-TYPE
   SYNTAX      Er1645v2Manvrfipv6DiscardEntry
   MAX-ACCESS  not-accessible
   STATUS      current
   DESCRIPTION
      ""
   INDEX      { er1645v2Manvrfipv6DiscardGlobalIx }
   ::= {er1645v2Manvrfipv6DiscardTable 1}

Er1645v2Manvrfipv6DiscardEntry ::=
   SEQUENCE
      {
      er1645v2Manvrfipv6DiscardGlobalIx
         GlobalIndex,
      er1645v2Manvrfipv6DiscardValue
         INTEGER
      }

er1645v2Manvrfipv6DiscardGlobalIx OBJECT-TYPE
   SYNTAX      GlobalIndex
   MAX-ACCESS  not-accessible
   STATUS      current
   DESCRIPTION
      "The value of the tlsCntTreeGlobalIndex of the MANAGED OBJECT."
   ::= {er1645v2Manvrfipv6DiscardEntry 10}

er1645v2Manvrfipv6DiscardValue OBJECT-TYPE
   SYNTAX      INTEGER
               {
               disabled (0),
               enabled (1)
               }
   MAX-ACCESS  read-write
   STATUS      current
   DESCRIPTION
      "Path: management.editConf.discard

       Possibilities:
               disabled   (0)
               enabled   (1)"
   ::= {er1645v2Manvrfipv6DiscardEntry 2147483648}


er1645v2Manvrfipv6AutoConfigure OBJECT IDENTIFIER ::= {er1645v2Manvrfipv6 35}

er1645v2Manvrfipv6AutoConfigureTable OBJECT-TYPE
   SYNTAX      SEQUENCE OF Er1645v2Manvrfipv6AutoConfigureEntry
   MAX-ACCESS  not-accessible
   STATUS      current
   DESCRIPTION
      "set restrictions to auto configuration using TFTP"
   ::= {er1645v2Manvrfipv6AutoConfigure 1}

er1645v2Manvrfipv6AutoConfigureEntry OBJECT-TYPE
   SYNTAX      Er1645v2Manvrfipv6AutoConfigureEntry
   MAX-ACCESS  not-accessible
   STATUS      current
   DESCRIPTION
      ""
   INDEX      { er1645v2Manvrfipv6AutoConfigureGlobalIx }
   ::= {er1645v2Manvrfipv6AutoConfigureTable 1}

Er1645v2Manvrfipv6AutoConfigureEntry ::=
   SEQUENCE
      {
      er1645v2Manvrfipv6AutoConfigureGlobalIx
         GlobalIndex,
      er1645v2Manvrfipv6AutoConfigureValue
         INTEGER
      }

er1645v2Manvrfipv6AutoConfigureGlobalIx OBJECT-TYPE
   SYNTAX      GlobalIndex
   MAX-ACCESS  not-accessible
   STATUS      current
   DESCRIPTION
      "The value of the tlsCntTreeGlobalIndex of the MANAGED OBJECT."
   ::= {er1645v2Manvrfipv6AutoConfigureEntry 10}

er1645v2Manvrfipv6AutoConfigureValue OBJECT-TYPE
   SYNTAX      INTEGER
               {
               enabled (0),
               onTftpServer (1),
               onBootFile (2),
               onTftpServerAndBootFile (3),
               disabled (4)
               }
   MAX-ACCESS  read-write
   STATUS      current
   DESCRIPTION
      "Path: management.editConf.autoConfigure

       Possibilities:
               enabled   (0)
               onTftpServer   (1)
               onBootFile   (2)
               onTftpServerAndBootFile   (3)
               disabled   (4)"
   ::= {er1645v2Manvrfipv6AutoConfigureEntry 2147483648}


er1645v2Manvrfipv6TrafficPolicy OBJECT IDENTIFIER ::= {er1645v2Manvrfipv6 73}

er1645v2Manvrfipv6TrafficPolicySSCTable OBJECT-TYPE
   SYNTAX      SEQUENCE OF Er1645v2Manvrfipv6TrafficPolicyEntry
   MAX-ACCESS  not-accessible
   STATUS      current
   DESCRIPTION
      "access traffic policy name"
   ::= {er1645v2Manvrfipv6TrafficPolicy 1}

er1645v2Manvrfipv6TrafficPolicyEntry OBJECT-TYPE
   SYNTAX      Er1645v2Manvrfipv6TrafficPolicyEntry
   MAX-ACCESS  not-accessible
   STATUS      current
   DESCRIPTION
      ""
   INDEX      { er1645v2Manvrfipv6TrafficPolicyGlobalIx }
   ::= {er1645v2Manvrfipv6TrafficPolicySSCTable 1}

Er1645v2Manvrfipv6TrafficPolicyEntry ::=
   SEQUENCE
      {
      er1645v2Manvrfipv6TrafficPolicyGlobalIx
         GlobalIndex,
      er1645v2Manvrfipv6TrafficPolicyInbound
         DisplayString,
      er1645v2Manvrfipv6TrafficPolicyOutbound
         DisplayString
      }

er1645v2Manvrfipv6TrafficPolicyGlobalIx OBJECT-TYPE
   SYNTAX      GlobalIndex
   MAX-ACCESS  not-accessible
   STATUS      current
   DESCRIPTION
      "The value of the tlsCntTreeGlobalIndex of the MANAGED OBJECT."
   ::= {er1645v2Manvrfipv6TrafficPolicyEntry 10}

er1645v2Manvrfipv6TrafficPolicyInbound OBJECT-TYPE
   SYNTAX      DisplayString
   MAX-ACCESS  read-write
   STATUS      current
   DESCRIPTION
      "Path: management.editConf.trafficPolicy.inbound"
   ::= {er1645v2Manvrfipv6TrafficPolicyEntry 16777216}

er1645v2Manvrfipv6TrafficPolicyOutbound OBJECT-TYPE
   SYNTAX      DisplayString
   MAX-ACCESS  read-write
   STATUS      current
   DESCRIPTION
      "Path: management.editConf.trafficPolicy.outbound"
   ::= {er1645v2Manvrfipv6TrafficPolicyEntry 33554432}



sr1645v2Manvrfipv6 OBJECT IDENTIFIER ::= {r1645v2Manvrfipv6 14}


sr1645v2Manvrfipv6SnmpIndex OBJECT IDENTIFIER ::= {sr1645v2Manvrfipv6 269}

sr1645v2Manvrfipv6SnmpIndexTable OBJECT-TYPE
   SYNTAX      SEQUENCE OF Sr1645v2Manvrfipv6SnmpIndexEntry
   MAX-ACCESS  not-accessible
   STATUS      current
   DESCRIPTION
      "SNMP index assigned to this object"
   ::= {sr1645v2Manvrfipv6SnmpIndex 1}

sr1645v2Manvrfipv6SnmpIndexEntry OBJECT-TYPE
   SYNTAX      Sr1645v2Manvrfipv6SnmpIndexEntry
   MAX-ACCESS  not-accessible
   STATUS      current
   DESCRIPTION
      ""
   INDEX      { sr1645v2Manvrfipv6SnmpIndexGlobalIx }
   ::= {sr1645v2Manvrfipv6SnmpIndexTable 1}

Sr1645v2Manvrfipv6SnmpIndexEntry ::=
   SEQUENCE
      {
      sr1645v2Manvrfipv6SnmpIndexGlobalIx
         GlobalIndex,
      sr1645v2Manvrfipv6SnmpIndexValue
         Integer32
      }

sr1645v2Manvrfipv6SnmpIndexGlobalIx OBJECT-TYPE
   SYNTAX      GlobalIndex
   MAX-ACCESS  not-accessible
   STATUS      current
   DESCRIPTION
      "The value of the tlsCntTreeGlobalIndex of the MANAGED OBJECT."
   ::= {sr1645v2Manvrfipv6SnmpIndexEntry 10}

sr1645v2Manvrfipv6SnmpIndexValue OBJECT-TYPE
   SYNTAX      Integer32
   MAX-ACCESS  read-only
   STATUS      current
   DESCRIPTION
      "Path: management.status.snmpIndex"
   ::= {sr1645v2Manvrfipv6SnmpIndexEntry 2147483648}


sr1645v2Manvrfipv6TcpSession OBJECT IDENTIFIER ::= {sr1645v2Manvrfipv6 45}

sr1645v2Manvrfipv6TcpSessionSSCTable OBJECT-TYPE
   SYNTAX      SEQUENCE OF Sr1645v2Manvrfipv6TcpSessionEntry
   MAX-ACCESS  not-accessible
   STATUS      current
   DESCRIPTION
      "TCP session overview"
   ::= {sr1645v2Manvrfipv6TcpSession 1}

sr1645v2Manvrfipv6TcpSessionEntry OBJECT-TYPE
   SYNTAX      Sr1645v2Manvrfipv6TcpSessionEntry
   MAX-ACCESS  not-accessible
   STATUS      current
   DESCRIPTION
      ""
   INDEX      { sr1645v2Manvrfipv6TcpSessionGlobalIx,
                sr1645v2Manvrfipv6TcpSessionTableIx }
   ::= {sr1645v2Manvrfipv6TcpSessionSSCTable 1}

Sr1645v2Manvrfipv6TcpSessionEntry ::=
   SEQUENCE
      {
      sr1645v2Manvrfipv6TcpSessionGlobalIx
         GlobalIndex,
      sr1645v2Manvrfipv6TcpSessionTableIx
         TableIndex,
      sr1645v2Manvrfipv6TcpSessionLocalIp
         Ipv6Address,
      sr1645v2Manvrfipv6TcpSessionLocalPort
         INTEGER,
      sr1645v2Manvrfipv6TcpSessionRemoteIp
         Ipv6Address,
      sr1645v2Manvrfipv6TcpSessionRemotePort
         INTEGER,
      sr1645v2Manvrfipv6TcpSessionState
         INTEGER,
      sr1645v2Manvrfipv6TcpSessionType
         INTEGER,
      sr1645v2Manvrfipv6TcpSessionInOctets
         Counter32,
      sr1645v2Manvrfipv6TcpSessionOutOctets
         Counter32,
      sr1645v2Manvrfipv6TcpSessionOutQLen
         Counter32,
      sr1645v2Manvrfipv6TcpSessionOutQOctets
         Counter32,
      sr1645v2Manvrfipv6TcpSessionOutOfOrder
         Counter32
      }

sr1645v2Manvrfipv6TcpSessionGlobalIx OBJECT-TYPE
   SYNTAX      GlobalIndex
   MAX-ACCESS  not-accessible
   STATUS      current
   DESCRIPTION
      "The value of the tlsCntTreeGlobalIndex of the MANAGED OBJECT."
   ::= {sr1645v2Manvrfipv6TcpSessionEntry 10}

sr1645v2Manvrfipv6TcpSessionTableIx OBJECT-TYPE
   SYNTAX      TableIndex
   MAX-ACCESS  not-accessible
   STATUS      current
   DESCRIPTION
      ""
   ::= {sr1645v2Manvrfipv6TcpSessionEntry 11}

sr1645v2Manvrfipv6TcpSessionLocalIp OBJECT-TYPE
   SYNTAX      Ipv6Address
   MAX-ACCESS  read-only
   STATUS      current
   DESCRIPTION
      "Path: management.status.tcpSession.localIp

       ipv6 address"
   ::= {sr1645v2Manvrfipv6TcpSessionEntry 16777216}

sr1645v2Manvrfipv6TcpSessionLocalPort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: management.status.tcpSession.localPort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1645v2Manvrfipv6TcpSessionEntry 33554432}

sr1645v2Manvrfipv6TcpSessionRemoteIp OBJECT-TYPE
   SYNTAX      Ipv6Address
   MAX-ACCESS  read-only
   STATUS      current
   DESCRIPTION
      "Path: management.status.tcpSession.remoteIp

       ipv6 address"
   ::= {sr1645v2Manvrfipv6TcpSessionEntry 50331648}

sr1645v2Manvrfipv6TcpSessionRemotePort OBJECT-TYPE
   SYNTAX      INTEGER
               {
               discard (9),
               bgp (179),
               bootpmdhcpmc (68),
               bootpmdhcpms (67),
               cpudpencap (2746),
               domain (53),
               echo (7),
               emailmsub (587),
               empty (0),
               ftp (21),
               ftpmdata (20),
               ftps (990),
               ftpsmdata (989),
               httpmalt (8080),
               https (443),
               h225ras (1719),
               h323 (1720),
               imap (143),
               imap3 (220),
               imaps (993),
               ipsecmnatmt (4500),
               isakmp (500),
               l2tp (1701),
               ldap (389),
               microsoftmds (445),
               msmstreaming (1755),
               msmwbtmserver (3389),
               msnp (1863),
               nameserver (42),
               netbiosmdgm (138),
               netbiosmns (137),
               netbiosmssn (139),
               nntp (119),
               ntp (123),
               pop3 (110),
               pop3s (995),
               pptp (1723),
               radius (1812),
               router (520),
               rsync (873),
               rtsp (554),
               sip (5060),
               smtp (25),
               smtps (465),
               snmp (161),
               snmptrap (162),
               socks (1080),
               ssdpmuPnP (1900),
               ssh (22),
               syslog (514),
               tacacs (49),
               tma (1728),
               telnet (23),
               telnets (992),
               tftp (69),
               whip (8700),
               wwwmhttp (80),
               z39d50 (210)
               }
   MAX-ACCESS  read-only
   STATUS      current
   DESCRIPTION
      "Path: management.status.tcpSession.remotePort

       Possibilities:
               discard   (9)
               bgp   (179)
               bootp-dhcp-c   (68)
               bootp-dhcp-s   (67)
               cpudpencap   (2746)
               domain   (53)
               echo   (7)
               email-sub   (587)
               empty   (0)
               ftp   (21)
               ftp-data   (20)
               ftps   (990)
               ftps-data   (989)
               http-alt   (8080)
               https   (443)
               h225ras   (1719)
               h323   (1720)
               imap   (143)
               imap3   (220)
               imaps   (993)
               ipsec-nat-t   (4500)
               isakmp   (500)
               l2tp   (1701)
               ldap   (389)
               microsoft-ds   (445)
               ms-streaming   (1755)
               ms-wbt-server   (3389)
               msnp   (1863)
               nameserver   (42)
               netbios-dgm   (138)
               netbios-ns   (137)
               netbios-ssn   (139)
               nntp   (119)
               ntp   (123)
               pop3   (110)
               pop3s   (995)
               pptp   (1723)
               radius   (1812)
               router   (520)
               rsync   (873)
               rtsp   (554)
               sip   (5060)
               smtp   (25)
               smtps   (465)
               snmp   (161)
               snmptrap   (162)
               socks   (1080)
               ssdp-uPnP   (1900)
               ssh   (22)
               syslog   (514)
               tacacs   (49)
               tma   (1728)
               telnet   (23)
               telnets   (992)
               tftp   (69)
               whip   (8700)
               www-http   (80)
               z39.50   (210)"
   ::= {sr1645v2Manvrfipv6TcpSessionEntry 67108864}

sr1645v2Manvrfipv6TcpSessionState OBJECT-TYPE
   SYNTAX      INTEGER
               {
               closed (0),
               listen (1),
               synSent (2),
               synReceived (3),
               established (4),
               finWait1 (5),
               finWait2 (6),
               closing (7),
               timeWait (8),
               closeWait (9),
               lastAck (10),
               notFound (11),
               dnsReqSent (12)
               }
   MAX-ACCESS  read-only
   STATUS      current
   DESCRIPTION
      "Path: management.status.tcpSession.state

       Possibilities:
               closed   (0)
               listen   (1)
               synSent   (2)
               synReceived   (3)
               established   (4)
               finWait1   (5)
               finWait2   (6)
               closing   (7)
               timeWait   (8)
               closeWait   (9)
               lastAck   (10)
               notFound   (11)
               dnsReqSent   (12)"
   ::= {sr1645v2Manvrfipv6TcpSessionEntry 83886080}

sr1645v2Manvrfipv6TcpSessionType OBJECT-TYPE
   SYNTAX      INTEGER
               {
               passivesstatic (1),
               active (2),
               passivesdynamic (3)
               }
   MAX-ACCESS  read-only
   STATUS      current
   DESCRIPTION
      "Path: management.status.tcpSession.type

       Possibilities:
               passive static   (1)
               active   (2)
               passive dynamic   (3)"
   ::= {sr1645v2Manvrfipv6TcpSessionEntry 117440512}

sr1645v2Manvrfipv6TcpSessionInOctets OBJECT-TYPE
   SYNTAX      Counter32
   MAX-ACCESS  read-only
   STATUS      current
   DESCRIPTION
      "Path: management.status.tcpSession.inOctets

       32 bit unsigned wrappable counter."
   ::= {sr1645v2Manvrfipv6TcpSessionEntry 134217728}

sr1645v2Manvrfipv6TcpSessionOutOctets OBJECT-TYPE
   SYNTAX      Counter32
   MAX-ACCESS  read-only
   STATUS      current
   DESCRIPTION
      "Path: management.status.tcpSession.outOctets

       32 bit unsigned wrappable counter."
   ::= {sr1645v2Manvrfipv6TcpSessionEntry 150994944}

sr1645v2Manvrfipv6TcpSessionOutQLen OBJECT-TYPE
   SYNTAX      Counter32
   MAX-ACCESS  read-only
   STATUS      current
   DESCRIPTION
      "Path: management.status.tcpSession.outQLen

       32 bit unsigned wrappable counter."
   ::= {sr1645v2Manvrfipv6TcpSessionEntry 167772160}

sr1645v2Manvrfipv6TcpSessionOutQOctets OBJECT-TYPE
   SYNTAX      Counter32
   MAX-ACCESS  read-only
   STATUS      current
   DESCRIPTION
      "Path: management.status.tcpSession.outQOctets

       32 bit unsigned wrappable counter."
   ::= {sr1645v2Manvrfipv6TcpSessionEntry 184549376}

sr1645v2Manvrfipv6TcpSessionOutOfOrder OBJECT-TYPE
   SYNTAX      Counter32
   MAX-ACCESS  read-only
   STATUS      current
   DESCRIPTION
      "Path: management.status.tcpSession.outOfOrder

       32 bit unsigned wrappable counter."
   ::= {sr1645v2Manvrfipv6TcpSessionEntry 201326592}



pr1645v2Manvrfipv6 OBJECT IDENTIFIER ::= {r1645v2Manvrfipv6 12}


pr1645v2Manvrfipv6TcpSessionCount OBJECT IDENTIFIER ::= {pr1645v2Manvrfipv6 43}

pr1645v2Manvrfipv6TcpSessionCountTable OBJECT-TYPE
   SYNTAX      SEQUENCE OF Pr1645v2Manvrfipv6TcpSessionCountEntry
   MAX-ACCESS  not-accessible
   STATUS      current
   DESCRIPTION
      "Number of sessions currently in use."
   ::= {pr1645v2Manvrfipv6TcpSessionCount 1}

pr1645v2Manvrfipv6TcpSessionCountEntry OBJECT-TYPE
   SYNTAX      Pr1645v2Manvrfipv6TcpSessionCountEntry
   MAX-ACCESS  not-accessible
   STATUS      current
   DESCRIPTION
      ""
   INDEX      { pr1645v2Manvrfipv6TcpSessionCountGlobalIx }
   ::= {pr1645v2Manvrfipv6TcpSessionCountTable 1}

Pr1645v2Manvrfipv6TcpSessionCountEntry ::=
   SEQUENCE
      {
      pr1645v2Manvrfipv6TcpSessionCountGlobalIx
         GlobalIndex,
      pr1645v2Manvrfipv6TcpSessionCountValue
         Gauge32
      }

pr1645v2Manvrfipv6TcpSessionCountGlobalIx OBJECT-TYPE
   SYNTAX      GlobalIndex
   MAX-ACCESS  not-accessible
   STATUS      current
   DESCRIPTION
      "The value of the tlsCntTreeGlobalIndex of the MANAGED OBJECT."
   ::= {pr1645v2Manvrfipv6TcpSessionCountEntry 10}

pr1645v2Manvrfipv6TcpSessionCountValue OBJECT-TYPE
   SYNTAX      Gauge32
   MAX-ACCESS  read-only
   STATUS      current
   DESCRIPTION
      "Path: management.performance.tcpSessionCount

       32 bit unsigned gauge value."
   ::= {pr1645v2Manvrfipv6TcpSessionCountEntry 2147483648}


pr1645v2Manvrfipv6TcpSession OBJECT IDENTIFIER ::= {pr1645v2Manvrfipv6 47}

pr1645v2Manvrfipv6TcpSessionSSCTable OBJECT-TYPE
   SYNTAX      SEQUENCE OF Pr1645v2Manvrfipv6TcpSessionEntry
   MAX-ACCESS  not-accessible
   STATUS      current
   DESCRIPTION
      "Total sessions used"
   ::= {pr1645v2Manvrfipv6TcpSession 1}

pr1645v2Manvrfipv6TcpSessionEntry OBJECT-TYPE
   SYNTAX      Pr1645v2Manvrfipv6TcpSessionEntry
   MAX-ACCESS  not-accessible
   STATUS      current
   DESCRIPTION
      ""
   INDEX      { pr1645v2Manvrfipv6TcpSessionGlobalIx }
   ::= {pr1645v2Manvrfipv6TcpSessionSSCTable 1}

Pr1645v2Manvrfipv6TcpSessionEntry ::=
   SEQUENCE
      {
      pr1645v2Manvrfipv6TcpSessionGlobalIx
         GlobalIndex,
      pr1645v2Manvrfipv6TcpSessionIncomingHttp
         Counter32,
      pr1645v2Manvrfipv6TcpSessionIncomingHttps
         Counter32,
      pr1645v2Manvrfipv6TcpSessionIncomingTelnet
         Counter32,
      pr1645v2Manvrfipv6TcpSessionIncomingSsh
         Counter32,
      pr1645v2Manvrfipv6TcpSessionIncomingFtpCtrl
         Counter32,
      pr1645v2Manvrfipv6TcpSessionIncomingFtpData
         Counter32
      }

pr1645v2Manvrfipv6TcpSessionGlobalIx OBJECT-TYPE
   SYNTAX      GlobalIndex
   MAX-ACCESS  not-accessible
   STATUS      current
   DESCRIPTION
      "The value of the tlsCntTreeGlobalIndex of the MANAGED OBJECT."
   ::= {pr1645v2Manvrfipv6TcpSessionEntry 10}

pr1645v2Manvrfipv6TcpSessionIncomingHttp OBJECT-TYPE
   SYNTAX      Counter32
   MAX-ACCESS  read-only
   STATUS      current
   DESCRIPTION
      "Path: management.performance.tcpSession.incoming.http

       32 bit unsigned wrappable counter."
   ::= {pr1645v2Manvrfipv6TcpSessionEntry 16842752}

pr1645v2Manvrfipv6TcpSessionIncomingHttps OBJECT-TYPE
   SYNTAX      Counter32
   MAX-ACCESS  read-only
   STATUS      current
   DESCRIPTION
      "Path: management.performance.tcpSession.incoming.https

       32 bit unsigned wrappable counter."
   ::= {pr1645v2Manvrfipv6TcpSessionEntry 17170432}

pr1645v2Manvrfipv6TcpSessionIncomingTelnet OBJECT-TYPE
   SYNTAX      Counter32
   MAX-ACCESS  read-only
   STATUS      current
   DESCRIPTION
      "Path: management.performance.tcpSession.incoming.telnet

       32 bit unsigned wrappable counter."
   ::= {pr1645v2Manvrfipv6TcpSessionEntry 16908288}

pr1645v2Manvrfipv6TcpSessionIncomingSsh OBJECT-TYPE
   SYNTAX      Counter32
   MAX-ACCESS  read-only
   STATUS      current
   DESCRIPTION
      "Path: management.performance.tcpSession.incoming.ssh

       32 bit unsigned wrappable counter."
   ::= {pr1645v2Manvrfipv6TcpSessionEntry 16973824}

pr1645v2Manvrfipv6TcpSessionIncomingFtpCtrl OBJECT-TYPE
   SYNTAX      Counter32
   MAX-ACCESS  read-only
   STATUS      current
   DESCRIPTION
      "Path: management.performance.tcpSession.incoming.ftpCtrl

       32 bit unsigned wrappable counter."
   ::= {pr1645v2Manvrfipv6TcpSessionEntry 17039360}

pr1645v2Manvrfipv6TcpSessionIncomingFtpData OBJECT-TYPE
   SYNTAX      Counter32
   MAX-ACCESS  read-only
   STATUS      current
   DESCRIPTION
      "Path: management.performance.tcpSession.incoming.ftpData

       32 bit unsigned wrappable counter."
   ::= {pr1645v2Manvrfipv6TcpSessionEntry 17104896}


pr1645v2Manvrfipv6TcpSyn OBJECT IDENTIFIER ::= {pr1645v2Manvrfipv6 76}

pr1645v2Manvrfipv6TcpSynSSCTable OBJECT-TYPE
   SYNTAX      SEQUENCE OF Pr1645v2Manvrfipv6TcpSynEntry
   MAX-ACCESS  not-accessible
   STATUS      current
   DESCRIPTION
      "statistics for TCP SYN packets to device"
   ::= {pr1645v2Manvrfipv6TcpSyn 1}

pr1645v2Manvrfipv6TcpSynEntry OBJECT-TYPE
   SYNTAX      Pr1645v2Manvrfipv6TcpSynEntry
   MAX-ACCESS  not-accessible
   STATUS      current
   DESCRIPTION
      ""
   INDEX      { pr1645v2Manvrfipv6TcpSynGlobalIx }
   ::= {pr1645v2Manvrfipv6TcpSynSSCTable 1}

Pr1645v2Manvrfipv6TcpSynEntry ::=
   SEQUENCE
      {
      pr1645v2Manvrfipv6TcpSynGlobalIx
         GlobalIndex,
      pr1645v2Manvrfipv6TcpSynTotalRxSyn
         Counter32,
      pr1645v2Manvrfipv6TcpSynTotalMaxSynRate
         Gauge32,
      pr1645v2Manvrfipv6TcpSynTotalDropped
         Counter32,
      pr1645v2Manvrfipv6TcpSynKnownPortsRxSyn
         Counter32,
      pr1645v2Manvrfipv6TcpSynKnownPortsMaxSynRate
         Gauge32,
      pr1645v2Manvrfipv6TcpSynKnownPortsDropped
         Counter32
      }

pr1645v2Manvrfipv6TcpSynGlobalIx OBJECT-TYPE
   SYNTAX      GlobalIndex
   MAX-ACCESS  not-accessible
   STATUS      current
   DESCRIPTION
      "The value of the tlsCntTreeGlobalIndex of the MANAGED OBJECT."
   ::= {pr1645v2Manvrfipv6TcpSynEntry 10}

pr1645v2Manvrfipv6TcpSynTotalRxSyn OBJECT-TYPE
   SYNTAX      Counter32
   MAX-ACCESS  read-only
   STATUS      current
   DESCRIPTION
      "Path: management.performance.tcpSyn.total.rxSyn

       32 bit unsigned wrappable counter."
   ::= {pr1645v2Manvrfipv6TcpSynEntry 16842752}

pr1645v2Manvrfipv6TcpSynTotalMaxSynRate OBJECT-TYPE
   SYNTAX      Gauge32
   MAX-ACCESS  read-only
   STATUS      current
   DESCRIPTION
      "Path: management.performance.tcpSyn.total.maxSynRate

       32 bit unsigned gauge value."
   ::= {pr1645v2Manvrfipv6TcpSynEntry 16908288}

pr1645v2Manvrfipv6TcpSynTotalDropped OBJECT-TYPE
   SYNTAX      Counter32
   MAX-ACCESS  read-only
   STATUS      current
   DESCRIPTION
      "Path: management.performance.tcpSyn.total.dropped

       32 bit unsigned wrappable counter."
   ::= {pr1645v2Manvrfipv6TcpSynEntry 16973824}

pr1645v2Manvrfipv6TcpSynKnownPortsRxSyn OBJECT-TYPE
   SYNTAX      Counter32
   MAX-ACCESS  read-only
   STATUS      current
   DESCRIPTION
      "Path: management.performance.tcpSyn.knownPorts.rxSyn

       32 bit unsigned wrappable counter."
   ::= {pr1645v2Manvrfipv6TcpSynEntry 33619968}

pr1645v2Manvrfipv6TcpSynKnownPortsMaxSynRate OBJECT-TYPE
   SYNTAX      Gauge32
   MAX-ACCESS  read-only
   STATUS      current
   DESCRIPTION
      "Path: management.performance.tcpSyn.knownPorts.maxSynRate

       32 bit unsigned gauge value."
   ::= {pr1645v2Manvrfipv6TcpSynEntry 33685504}

pr1645v2Manvrfipv6TcpSynKnownPortsDropped OBJECT-TYPE
   SYNTAX      Counter32
   MAX-ACCESS  read-only
   STATUS      current
   DESCRIPTION
      "Path: management.performance.tcpSyn.knownPorts.dropped

       32 bit unsigned wrappable counter."
   ::= {pr1645v2Manvrfipv6TcpSynEntry 33751040}



ar1645v2Manvrfipv6 OBJECT IDENTIFIER ::= {r1645v2Manvrfipv6 16}


ar1645v2Manvrfipv6ClearCounters OBJECT IDENTIFIER ::= {ar1645v2Manvrfipv6 263}

ar1645v2Manvrfipv6ClearCountersTable OBJECT-TYPE
   SYNTAX      SEQUENCE OF Ar1645v2Manvrfipv6ClearCountersEntry
   MAX-ACCESS  not-accessible
   STATUS      current
   DESCRIPTION
      "reset counters"
   ::= {ar1645v2Manvrfipv6ClearCounters 1}

ar1645v2Manvrfipv6ClearCountersEntry OBJECT-TYPE
   SYNTAX      Ar1645v2Manvrfipv6ClearCountersEntry
   MAX-ACCESS  not-accessible
   STATUS      current
   DESCRIPTION
      ""
   INDEX      { ar1645v2Manvrfipv6ClearCountersGlobalIx }
   ::= {ar1645v2Manvrfipv6ClearCountersTable 1}

Ar1645v2Manvrfipv6ClearCountersEntry ::=
   SEQUENCE
      {
      ar1645v2Manvrfipv6ClearCountersGlobalIx
         GlobalIndex,
      ar1645v2Manvrfipv6ClearCountersValue
         Integer32
      }

ar1645v2Manvrfipv6ClearCountersGlobalIx OBJECT-TYPE
   SYNTAX      GlobalIndex
   MAX-ACCESS  not-accessible
   STATUS      current
   DESCRIPTION
      "The value of the tlsCntTreeGlobalIndex of the MANAGED OBJECT."
   ::= {ar1645v2Manvrfipv6ClearCountersEntry 10}

ar1645v2Manvrfipv6ClearCountersValue OBJECT-TYPE
   SYNTAX      Integer32
   MAX-ACCESS  read-write
   STATUS      current
   DESCRIPTION
      "Path: management.actions.clearCounters"
   ::= {ar1645v2Manvrfipv6ClearCountersEntry 2147483648}



END
