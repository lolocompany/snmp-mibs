OneAccess-R1645v2-4823-Lan2MC DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2Lan2MC OBJECT IDENTIFIER ::= {r1645Rootv2 4823}

r1645v2Lan2MCMOProp OBJECT IDENTIFIER ::= {r1645v2Lan2MC 1}

r1645v2Lan2MCMOPropEntry OBJECT IDENTIFIER ::= {r1645v2Lan2MCMOProp 1}

r1645v2Lan2MCMOPropPath OBJECT-TYPE
   SYNTAX      ContainmentPath
   MAX-ACCESS  read-only
   STATUS      current
   DESCRIPTION
      "Textual description of the containment tree from the instance of
       the root object down to the instance of the current object."
   ::= {r1645v2Lan2MCMOPropEntry 3}

r1645v2Lan2MCMOPropRev OBJECT-TYPE
   SYNTAX      ObjectRevision
   MAX-ACCESS  read-only
   STATUS      current
   DESCRIPTION
      "This value corresponds with the revision of the MANAGED OBJECT."
   ::= {r1645v2Lan2MCMOPropEntry 4}



er1645v2Lan2MC OBJECT IDENTIFIER ::= {r1645v2Lan2MC 11}


er1645v2Lan2MCRemark OBJECT-TYPE
   SYNTAX      DisplayString
   MAX-ACCESS  read-write
   STATUS      current
   DESCRIPTION
      "Path: ethernet2.editConf.remark
       Info: intfRemark"
   ::= {er1645v2Lan2MC 321}


er1645v2Lan2MCAdminStatus OBJECT-TYPE
   SYNTAX      INTEGER
               {
               up (1),
               down (2)
               }
   MAX-ACCESS  read-write
   STATUS      current
   DESCRIPTION
      "Path: ethernet2.editConf.adminStatus
       Info: ifAdminStatus

       Possibilities:
               up   (1)
               down   (2)"
   ::= {er1645v2Lan2MC 106}


er1645v2Lan2MCBw OBJECT IDENTIFIER ::= {er1645v2Lan2MC 5}

er1645v2Lan2MCBwSSC OBJECT IDENTIFIER ::= {er1645v2Lan2MCBw 1}

er1645v2Lan2MCBwEntry OBJECT IDENTIFIER ::= {er1645v2Lan2MCBwSSC 1}

er1645v2Lan2MCBwMode OBJECT-TYPE
   SYNTAX      INTEGER
               {
               reshaping (1),
               policing (2),
               policingReshape (3)
               }
   MAX-ACCESS  read-write
   STATUS      current
   DESCRIPTION
      "Path: ethernet2.editConf.bandwidth.mode

       Possibilities:
               reshaping   (1)
               policing   (2)
               policingReshape   (3)"
   ::= {er1645v2Lan2MCBwEntry 3758096384}

er1645v2Lan2MCBwCir OBJECT-TYPE
   SYNTAX      Integer32
   MAX-ACCESS  read-write
   STATUS      current
   DESCRIPTION
      "Path: ethernet2.editConf.bandwidth.cir"
   ::= {er1645v2Lan2MCBwEntry 268435456}

er1645v2Lan2MCBwEir OBJECT-TYPE
   SYNTAX      Integer32
   MAX-ACCESS  read-write
   STATUS      current
   DESCRIPTION
      "Path: ethernet2.editConf.bandwidth.eir"
   ::= {er1645v2Lan2MCBwEntry 1879048192}

er1645v2Lan2MCBwUnit OBJECT-TYPE
   SYNTAX      INTEGER
               {
               bitssec (1),
               percent (2)
               }
   MAX-ACCESS  read-write
   STATUS      current
   DESCRIPTION
      "Path: ethernet2.editConf.bandwidth.unit

       Possibilities:
               bits/sec   (1)
               percent   (2)"
   ::= {er1645v2Lan2MCBwEntry 1342177280}

er1645v2Lan2MCBwTc OBJECT-TYPE
   SYNTAX      INTEGER
               {
               auto (0)
               }
   MAX-ACCESS  read-write
   STATUS      current
   DESCRIPTION
      "Path: ethernet2.editConf.bandwidth.tc

       Possibilities:
               auto   (0)"
   ::= {er1645v2Lan2MCBwEntry 1610612736}

er1645v2Lan2MCBwTcFactor OBJECT-TYPE
   SYNTAX      INTEGER
               {
               ms (10),
               s100us (1)
               }
   MAX-ACCESS  read-write
   STATUS      current
   DESCRIPTION
      "Path: ethernet2.editConf.bandwidth.tcFactor

       Possibilities:
               ms   (10)
               *100us   (1)"
   ::= {er1645v2Lan2MCBwEntry 2147483648}

er1645v2Lan2MCBwCorrType OBJECT-TYPE
   SYNTAX      INTEGER
               {
               noCorrection (0),
               predefined (1),
               manual (2)
               }
   MAX-ACCESS  read-write
   STATUS      current
   DESCRIPTION
      "Path: ethernet2.editConf.bandwidth.correction.type

       Possibilities:
               noCorrection   (0)
               predefined   (1)
               manual   (2)"
   ::= {er1645v2Lan2MCBwEntry 570425344}

er1645v2Lan2MCBwCorrPredefEncapsFrameRelay OBJECT-TYPE
   SYNTAX      DisplayString
   MAX-ACCESS  read-write
   STATUS      current
   DESCRIPTION
      "Path: ethernet2.editConf.bandwidth.correction.predefined.encapsulation.frameRelay"
   ::= {er1645v2Lan2MCBwEntry 608436224}

er1645v2Lan2MCBwCorrPredefEncapsPpp OBJECT-TYPE
   SYNTAX      DisplayString
   MAX-ACCESS  read-write
   STATUS      current
   DESCRIPTION
      "Path: ethernet2.editConf.bandwidth.correction.predefined.encapsulation.ppp"
   ::= {er1645v2Lan2MCBwEntry 608698368}

er1645v2Lan2MCBwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.bandwidth.correction.predefined.encapsulation.atm.higherLayer

       Possibilities:
               rfc2684   (0)
               ppp   (1)
               pppOverEthernet   (2)"
   ::= {er1645v2Lan2MCBwEntry 608993280}

er1645v2Lan2MCBwCorrPredefEncapsAtmMp OBJECT-TYPE
   SYNTAX      INTEGER
               {
               llcEncapsulation (0),
               vcMultiplexing (1)
               }
   MAX-ACCESS  read-write
   STATUS      current
   DESCRIPTION
      "Path: ethernet2.editConf.bandwidth.correction.predefined.encapsulation.atm.multiProtocol

       Possibilities:
               llcEncapsulation   (0)
               vcMultiplexing   (1)"
   ::= {er1645v2Lan2MCBwEntry 609026048}

er1645v2Lan2MCBwCorrPredefEncapsHdlc OBJECT-TYPE
   SYNTAX      DisplayString
   MAX-ACCESS  read-write
   STATUS      current
   DESCRIPTION
      "Path: ethernet2.editConf.bandwidth.correction.predefined.encapsulation.hdlc"
   ::= {er1645v2Lan2MCBwEntry 609222656}

er1645v2Lan2MCBwCorrPredefEncapsEfmFs OBJECT-TYPE
   SYNTAX      Integer32
   MAX-ACCESS  read-write
   STATUS      current
   DESCRIPTION
      "Path: ethernet2.editConf.bandwidth.correction.predefined.encapsulation.efm.fragmentSize"
   ::= {er1645v2Lan2MCBwEntry 609517568}

er1645v2Lan2MCBwCorrPredefEncapsEfmIb OBJECT-TYPE
   SYNTAX      Integer32
   MAX-ACCESS  read-write
   STATUS      current
   DESCRIPTION
      "Path: ethernet2.editConf.bandwidth.correction.predefined.encapsulation.efm.idleBytes"
   ::= {er1645v2Lan2MCBwEntry 609550336}

er1645v2Lan2MCBwCorrPredefMode OBJECT-TYPE
   SYNTAX      INTEGER
               {
               routing (0),
               bridging (1)
               }
   MAX-ACCESS  read-write
   STATUS      current
   DESCRIPTION
      "Path: ethernet2.editConf.bandwidth.correction.predefined.mode

       Possibilities:
               routing   (0)
               bridging   (1)"
   ::= {er1645v2Lan2MCBwEntry 612368384}

er1645v2Lan2MCBwCorrManualOverhead OBJECT-TYPE
   SYNTAX      Integer32
   MAX-ACCESS  read-write
   STATUS      current
   DESCRIPTION
      "Path: ethernet2.editConf.bandwidth.correction.manual.overhead"
   ::= {er1645v2Lan2MCBwEntry 637665280}

er1645v2Lan2MCBwCorrManualFrameData OBJECT-TYPE
   SYNTAX      Counter32
   MAX-ACCESS  read-write
   STATUS      current
   DESCRIPTION
      "Path: ethernet2.editConf.bandwidth.correction.manual.frameData

       32 bit unsigned wrappable counter."
   ::= {er1645v2Lan2MCBwEntry 637796352}

er1645v2Lan2MCBwCorrManualFrameHeader OBJECT-TYPE
   SYNTAX      Counter32
   MAX-ACCESS  read-write
   STATUS      current
   DESCRIPTION
      "Path: ethernet2.editConf.bandwidth.correction.manual.frameHeader

       32 bit unsigned wrappable counter."
   ::= {er1645v2Lan2MCBwEntry 637927424}

er1645v2Lan2MCBwMaxFifoQLen OBJECT-TYPE
   SYNTAX      Integer32
   MAX-ACCESS  read-write
   STATUS      current
   DESCRIPTION
      "Path: ethernet2.editConf.bandwidth.maxFifoQLen"
   ::= {er1645v2Lan2MCBwEntry 805306368}

er1645v2Lan2MCBwDeFlagCir OBJECT-TYPE
   SYNTAX      INTEGER
               {
               allowed (1),
               notAllowed (2)
               }
   MAX-ACCESS  read-write
   STATUS      current
   DESCRIPTION
      "Path: ethernet2.editConf.bandwidth.deFlag.cir

       Possibilities:
               allowed   (1)
               notAllowed   (2)"
   ::= {er1645v2Lan2MCBwEntry 3490709504}

er1645v2Lan2MCBwDeFlagEir OBJECT-TYPE
   SYNTAX      INTEGER
               {
               allowed (1),
               notAllowed (2)
               }
   MAX-ACCESS  read-write
   STATUS      current
   DESCRIPTION
      "Path: ethernet2.editConf.bandwidth.deFlag.eir

       Possibilities:
               allowed   (1)
               notAllowed   (2)"
   ::= {er1645v2Lan2MCBwEntry 3491758080}

er1645v2Lan2MCBwDeFlagViolate OBJECT-TYPE
   SYNTAX      INTEGER
               {
               allowed (1),
               notAllowed (2)
               }
   MAX-ACCESS  read-write
   STATUS      current
   DESCRIPTION
      "Path: ethernet2.editConf.bandwidth.deFlag.violate

       Possibilities:
               allowed   (1)
               notAllowed   (2)"
   ::= {er1645v2Lan2MCBwEntry 3492806656}

er1645v2Lan2MCBwActCirActNone OBJECT-TYPE
   SYNTAX      OCTET STRING
   MAX-ACCESS  read-write
   STATUS      current
   DESCRIPTION
      "Path: ethernet2.editConf.bandwidth.action.cirAction.none"
   ::= {er1645v2Lan2MCBwEntry 4062183424}

er1645v2Lan2MCBwActCirActEthCos1 OBJECT-TYPE
   SYNTAX      INTEGER
               {
               unchanged (256)
               }
   MAX-ACCESS  read-write
   STATUS      current
   DESCRIPTION
      "Path: ethernet2.editConf.bandwidth.action.cirAction.ethernet.cosDepth1

       Possibilities:
               unchanged   (256)"
   ::= {er1645v2Lan2MCBwEntry 4064346112}

er1645v2Lan2MCBwActCirActEthDei1 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth1

       Possibilities:
               unchanged   (255)
               clear   (0)
               set   (1)"
   ::= {er1645v2Lan2MCBwEntry 4065656832}

er1645v2Lan2MCBwActCirActEthCos2 OBJECT-TYPE
   SYNTAX      INTEGER
               {
               unchanged (256)
               }
   MAX-ACCESS  read-write
   STATUS      current
   DESCRIPTION
      "Path: ethernet2.editConf.bandwidth.action.cirAction.ethernet.cosDepth2

       Possibilities:
               unchanged   (256)"
   ::= {er1645v2Lan2MCBwEntry 4064411648}

er1645v2Lan2MCBwActCirActEthDei2 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth2

       Possibilities:
               unchanged   (255)
               clear   (0)
               set   (1)"
   ::= {er1645v2Lan2MCBwEntry 4065722368}

er1645v2Lan2MCBwActCirActEthCos3 OBJECT-TYPE
   SYNTAX      INTEGER
               {
               unchanged (256)
               }
   MAX-ACCESS  read-write
   STATUS      current
   DESCRIPTION
      "Path: ethernet2.editConf.bandwidth.action.cirAction.ethernet.cosDepth3

       Possibilities:
               unchanged   (256)"
   ::= {er1645v2Lan2MCBwEntry 4064477184}

er1645v2Lan2MCBwActCirActEthDei3 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth3

       Possibilities:
               unchanged   (255)
               clear   (0)
               set   (1)"
   ::= {er1645v2Lan2MCBwEntry 4065787904}

er1645v2Lan2MCBwActCirActEthCos4 OBJECT-TYPE
   SYNTAX      INTEGER
               {
               unchanged (256)
               }
   MAX-ACCESS  read-write
   STATUS      current
   DESCRIPTION
      "Path: ethernet2.editConf.bandwidth.action.cirAction.ethernet.cosDepth4

       Possibilities:
               unchanged   (256)"
   ::= {er1645v2Lan2MCBwEntry 4064542720}

er1645v2Lan2MCBwActCirActEthDei4 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth4

       Possibilities:
               unchanged   (255)
               clear   (0)
               set   (1)"
   ::= {er1645v2Lan2MCBwEntry 4065853440}

er1645v2Lan2MCBwActCirActEthCos5 OBJECT-TYPE
   SYNTAX      INTEGER
               {
               unchanged (256)
               }
   MAX-ACCESS  read-write
   STATUS      current
   DESCRIPTION
      "Path: ethernet2.editConf.bandwidth.action.cirAction.ethernet.cosDepth5

       Possibilities:
               unchanged   (256)"
   ::= {er1645v2Lan2MCBwEntry 4064608256}

er1645v2Lan2MCBwActCirActEthDei5 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth5

       Possibilities:
               unchanged   (255)
               clear   (0)
               set   (1)"
   ::= {er1645v2Lan2MCBwEntry 4065918976}

er1645v2Lan2MCBwActCirActEthCos6 OBJECT-TYPE
   SYNTAX      INTEGER
               {
               unchanged (256)
               }
   MAX-ACCESS  read-write
   STATUS      current
   DESCRIPTION
      "Path: ethernet2.editConf.bandwidth.action.cirAction.ethernet.cosDepth6

       Possibilities:
               unchanged   (256)"
   ::= {er1645v2Lan2MCBwEntry 4064673792}

er1645v2Lan2MCBwActCirActEthDei6 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth6

       Possibilities:
               unchanged   (255)
               clear   (0)
               set   (1)"
   ::= {er1645v2Lan2MCBwEntry 4065984512}

er1645v2Lan2MCBwActCirActEthCos7 OBJECT-TYPE
   SYNTAX      INTEGER
               {
               unchanged (256)
               }
   MAX-ACCESS  read-write
   STATUS      current
   DESCRIPTION
      "Path: ethernet2.editConf.bandwidth.action.cirAction.ethernet.cosDepth7

       Possibilities:
               unchanged   (256)"
   ::= {er1645v2Lan2MCBwEntry 4064739328}

er1645v2Lan2MCBwActCirActEthDei7 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth7

       Possibilities:
               unchanged   (255)
               clear   (0)
               set   (1)"
   ::= {er1645v2Lan2MCBwEntry 4066050048}

er1645v2Lan2MCBwActCirActEthCos8 OBJECT-TYPE
   SYNTAX      INTEGER
               {
               unchanged (256)
               }
   MAX-ACCESS  read-write
   STATUS      current
   DESCRIPTION
      "Path: ethernet2.editConf.bandwidth.action.cirAction.ethernet.cosDepth8

       Possibilities:
               unchanged   (256)"
   ::= {er1645v2Lan2MCBwEntry 4064804864}

er1645v2Lan2MCBwActCirActEthDei8 OBJECT-TYPE
   SYNTAX      INTEGER
               {
               unchanged (255),
               clear (0),
               set (1)
               }
   MAX-ACCESS  read-write
   STATUS      current
   DESCRIPTION
      "Path: ethernet2.editConf.bandwidth.action.cirAction.ethernet.deiDepth8

       Possibilities:
               unchanged   (255)
               clear   (0)
               set   (1)"
   ::= {er1645v2Lan2MCBwEntry 4066115584}

er1645v2Lan2MCBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCBwEntry 4064870400}

er1645v2Lan2MCBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCBwEntry 4064935936}

er1645v2Lan2MCBwActCirActEthDrpLev OBJECT-TYPE
   SYNTAX      INTEGER
               {
               unchanged (0)
               }
   MAX-ACCESS  read-write
   STATUS      current
   DESCRIPTION
      "Path: ethernet2.editConf.bandwidth.action.cirAction.ethernet.dropLevel

       Possibilities:
               unchanged   (0)"
   ::= {er1645v2Lan2MCBwEntry 4065001472}

er1645v2Lan2MCBwActCirActEthDeFlag OBJECT-TYPE
   SYNTAX      INTEGER
               {
               unchanged (255),
               clear (0),
               set (1)
               }
   MAX-ACCESS  read-write
   STATUS      current
   DESCRIPTION
      "Path: ethernet2.editConf.bandwidth.action.cirAction.ethernet.deFlag

       Possibilities:
               unchanged   (255)
               clear   (0)
               set   (1)"
   ::= {er1645v2Lan2MCBwEntry 4065198080}

er1645v2Lan2MCBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCBwEntry 4071161856}

er1645v2Lan2MCBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCBwEntry 4071227392}

er1645v2Lan2MCBwActCirActIpDrpLev OBJECT-TYPE
   SYNTAX      INTEGER
               {
               unchanged (0)
               }
   MAX-ACCESS  read-write
   STATUS      current
   DESCRIPTION
      "Path: ethernet2.editConf.bandwidth.action.cirAction.ip.dropLevel

       Possibilities:
               unchanged   (0)"
   ::= {er1645v2Lan2MCBwEntry 4071292928}

er1645v2Lan2MCBwActCirActIpDeFlag OBJECT-TYPE
   SYNTAX      INTEGER
               {
               unchanged (255),
               clear (0),
               set (1)
               }
   MAX-ACCESS  read-write
   STATUS      current
   DESCRIPTION
      "Path: ethernet2.editConf.bandwidth.action.cirAction.ip.deFlag

       Possibilities:
               unchanged   (255)
               clear   (0)
               set   (1)"
   ::= {er1645v2Lan2MCBwEntry 4071489536}

er1645v2Lan2MCBwActEirActNone OBJECT-TYPE
   SYNTAX      OCTET STRING
   MAX-ACCESS  read-write
   STATUS      current
   DESCRIPTION
      "Path: ethernet2.editConf.bandwidth.action.eirAction.none"
   ::= {er1645v2Lan2MCBwEntry 4095737856}

er1645v2Lan2MCBwActEirActEthCos1 OBJECT-TYPE
   SYNTAX      INTEGER
               {
               unchanged (256)
               }
   MAX-ACCESS  read-write
   STATUS      current
   DESCRIPTION
      "Path: ethernet2.editConf.bandwidth.action.eirAction.ethernet.cosDepth1

       Possibilities:
               unchanged   (256)"
   ::= {er1645v2Lan2MCBwEntry 4097900544}

er1645v2Lan2MCBwActEirActEthDei1 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth1

       Possibilities:
               unchanged   (255)
               clear   (0)
               set   (1)"
   ::= {er1645v2Lan2MCBwEntry 4099211264}

er1645v2Lan2MCBwActEirActEthCos2 OBJECT-TYPE
   SYNTAX      INTEGER
               {
               unchanged (256)
               }
   MAX-ACCESS  read-write
   STATUS      current
   DESCRIPTION
      "Path: ethernet2.editConf.bandwidth.action.eirAction.ethernet.cosDepth2

       Possibilities:
               unchanged   (256)"
   ::= {er1645v2Lan2MCBwEntry 4097966080}

er1645v2Lan2MCBwActEirActEthDei2 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth2

       Possibilities:
               unchanged   (255)
               clear   (0)
               set   (1)"
   ::= {er1645v2Lan2MCBwEntry 4099276800}

er1645v2Lan2MCBwActEirActEthCos3 OBJECT-TYPE
   SYNTAX      INTEGER
               {
               unchanged (256)
               }
   MAX-ACCESS  read-write
   STATUS      current
   DESCRIPTION
      "Path: ethernet2.editConf.bandwidth.action.eirAction.ethernet.cosDepth3

       Possibilities:
               unchanged   (256)"
   ::= {er1645v2Lan2MCBwEntry 4098031616}

er1645v2Lan2MCBwActEirActEthDei3 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth3

       Possibilities:
               unchanged   (255)
               clear   (0)
               set   (1)"
   ::= {er1645v2Lan2MCBwEntry 4099342336}

er1645v2Lan2MCBwActEirActEthCos4 OBJECT-TYPE
   SYNTAX      INTEGER
               {
               unchanged (256)
               }
   MAX-ACCESS  read-write
   STATUS      current
   DESCRIPTION
      "Path: ethernet2.editConf.bandwidth.action.eirAction.ethernet.cosDepth4

       Possibilities:
               unchanged   (256)"
   ::= {er1645v2Lan2MCBwEntry 4098097152}

er1645v2Lan2MCBwActEirActEthDei4 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth4

       Possibilities:
               unchanged   (255)
               clear   (0)
               set   (1)"
   ::= {er1645v2Lan2MCBwEntry 4099407872}

er1645v2Lan2MCBwActEirActEthCos5 OBJECT-TYPE
   SYNTAX      INTEGER
               {
               unchanged (256)
               }
   MAX-ACCESS  read-write
   STATUS      current
   DESCRIPTION
      "Path: ethernet2.editConf.bandwidth.action.eirAction.ethernet.cosDepth5

       Possibilities:
               unchanged   (256)"
   ::= {er1645v2Lan2MCBwEntry 4098162688}

er1645v2Lan2MCBwActEirActEthDei5 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth5

       Possibilities:
               unchanged   (255)
               clear   (0)
               set   (1)"
   ::= {er1645v2Lan2MCBwEntry 4099473408}

er1645v2Lan2MCBwActEirActEthCos6 OBJECT-TYPE
   SYNTAX      INTEGER
               {
               unchanged (256)
               }
   MAX-ACCESS  read-write
   STATUS      current
   DESCRIPTION
      "Path: ethernet2.editConf.bandwidth.action.eirAction.ethernet.cosDepth6

       Possibilities:
               unchanged   (256)"
   ::= {er1645v2Lan2MCBwEntry 4098228224}

er1645v2Lan2MCBwActEirActEthDei6 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth6

       Possibilities:
               unchanged   (255)
               clear   (0)
               set   (1)"
   ::= {er1645v2Lan2MCBwEntry 4099538944}

er1645v2Lan2MCBwActEirActEthCos7 OBJECT-TYPE
   SYNTAX      INTEGER
               {
               unchanged (256)
               }
   MAX-ACCESS  read-write
   STATUS      current
   DESCRIPTION
      "Path: ethernet2.editConf.bandwidth.action.eirAction.ethernet.cosDepth7

       Possibilities:
               unchanged   (256)"
   ::= {er1645v2Lan2MCBwEntry 4098293760}

er1645v2Lan2MCBwActEirActEthDei7 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth7

       Possibilities:
               unchanged   (255)
               clear   (0)
               set   (1)"
   ::= {er1645v2Lan2MCBwEntry 4099604480}

er1645v2Lan2MCBwActEirActEthCos8 OBJECT-TYPE
   SYNTAX      INTEGER
               {
               unchanged (256)
               }
   MAX-ACCESS  read-write
   STATUS      current
   DESCRIPTION
      "Path: ethernet2.editConf.bandwidth.action.eirAction.ethernet.cosDepth8

       Possibilities:
               unchanged   (256)"
   ::= {er1645v2Lan2MCBwEntry 4098359296}

er1645v2Lan2MCBwActEirActEthDei8 OBJECT-TYPE
   SYNTAX      INTEGER
               {
               unchanged (255),
               clear (0),
               set (1)
               }
   MAX-ACCESS  read-write
   STATUS      current
   DESCRIPTION
      "Path: ethernet2.editConf.bandwidth.action.eirAction.ethernet.deiDepth8

       Possibilities:
               unchanged   (255)
               clear   (0)
               set   (1)"
   ::= {er1645v2Lan2MCBwEntry 4099670016}

er1645v2Lan2MCBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCBwEntry 4098424832}

er1645v2Lan2MCBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCBwEntry 4098490368}

er1645v2Lan2MCBwActEirActEthDrpLev OBJECT-TYPE
   SYNTAX      INTEGER
               {
               unchanged (0)
               }
   MAX-ACCESS  read-write
   STATUS      current
   DESCRIPTION
      "Path: ethernet2.editConf.bandwidth.action.eirAction.ethernet.dropLevel

       Possibilities:
               unchanged   (0)"
   ::= {er1645v2Lan2MCBwEntry 4098555904}

er1645v2Lan2MCBwActEirActEthDeFlag OBJECT-TYPE
   SYNTAX      INTEGER
               {
               unchanged (255),
               clear (0),
               set (1)
               }
   MAX-ACCESS  read-write
   STATUS      current
   DESCRIPTION
      "Path: ethernet2.editConf.bandwidth.action.eirAction.ethernet.deFlag

       Possibilities:
               unchanged   (255)
               clear   (0)
               set   (1)"
   ::= {er1645v2Lan2MCBwEntry 4098752512}

er1645v2Lan2MCBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCBwEntry 4104716288}

er1645v2Lan2MCBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCBwEntry 4104781824}

er1645v2Lan2MCBwActEirActIpDrpLev OBJECT-TYPE
   SYNTAX      INTEGER
               {
               unchanged (0)
               }
   MAX-ACCESS  read-write
   STATUS      current
   DESCRIPTION
      "Path: ethernet2.editConf.bandwidth.action.eirAction.ip.dropLevel

       Possibilities:
               unchanged   (0)"
   ::= {er1645v2Lan2MCBwEntry 4104847360}

er1645v2Lan2MCBwActEirActIpDeFlag OBJECT-TYPE
   SYNTAX      INTEGER
               {
               unchanged (255),
               clear (0),
               set (1)
               }
   MAX-ACCESS  read-write
   STATUS      current
   DESCRIPTION
      "Path: ethernet2.editConf.bandwidth.action.eirAction.ip.deFlag

       Possibilities:
               unchanged   (255)
               clear   (0)
               set   (1)"
   ::= {er1645v2Lan2MCBwEntry 4105043968}

er1645v2Lan2MCBwActViolActNone OBJECT-TYPE
   SYNTAX      OCTET STRING
   MAX-ACCESS  read-write
   STATUS      current
   DESCRIPTION
      "Path: ethernet2.editConf.bandwidth.action.violateAction.none"
   ::= {er1645v2Lan2MCBwEntry 4129292288}

er1645v2Lan2MCBwActViolActDrop OBJECT-TYPE
   SYNTAX      OCTET STRING
   MAX-ACCESS  read-write
   STATUS      current
   DESCRIPTION
      "Path: ethernet2.editConf.bandwidth.action.violateAction.drop"
   ::= {er1645v2Lan2MCBwEntry 4133486592}

er1645v2Lan2MCBwActViolActEthCos1 OBJECT-TYPE
   SYNTAX      INTEGER
               {
               unchanged (256)
               }
   MAX-ACCESS  read-write
   STATUS      current
   DESCRIPTION
      "Path: ethernet2.editConf.bandwidth.action.violateAction.ethernet.cosDepth1

       Possibilities:
               unchanged   (256)"
   ::= {er1645v2Lan2MCBwEntry 4131454976}

er1645v2Lan2MCBwActViolActEthDei1 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth1

       Possibilities:
               unchanged   (255)
               clear   (0)
               set   (1)"
   ::= {er1645v2Lan2MCBwEntry 4132765696}

er1645v2Lan2MCBwActViolActEthCos2 OBJECT-TYPE
   SYNTAX      INTEGER
               {
               unchanged (256)
               }
   MAX-ACCESS  read-write
   STATUS      current
   DESCRIPTION
      "Path: ethernet2.editConf.bandwidth.action.violateAction.ethernet.cosDepth2

       Possibilities:
               unchanged   (256)"
   ::= {er1645v2Lan2MCBwEntry 4131520512}

er1645v2Lan2MCBwActViolActEthDei2 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth2

       Possibilities:
               unchanged   (255)
               clear   (0)
               set   (1)"
   ::= {er1645v2Lan2MCBwEntry 4132831232}

er1645v2Lan2MCBwActViolActEthCos3 OBJECT-TYPE
   SYNTAX      INTEGER
               {
               unchanged (256)
               }
   MAX-ACCESS  read-write
   STATUS      current
   DESCRIPTION
      "Path: ethernet2.editConf.bandwidth.action.violateAction.ethernet.cosDepth3

       Possibilities:
               unchanged   (256)"
   ::= {er1645v2Lan2MCBwEntry 4131586048}

er1645v2Lan2MCBwActViolActEthDei3 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth3

       Possibilities:
               unchanged   (255)
               clear   (0)
               set   (1)"
   ::= {er1645v2Lan2MCBwEntry 4132896768}

er1645v2Lan2MCBwActViolActEthCos4 OBJECT-TYPE
   SYNTAX      INTEGER
               {
               unchanged (256)
               }
   MAX-ACCESS  read-write
   STATUS      current
   DESCRIPTION
      "Path: ethernet2.editConf.bandwidth.action.violateAction.ethernet.cosDepth4

       Possibilities:
               unchanged   (256)"
   ::= {er1645v2Lan2MCBwEntry 4131651584}

er1645v2Lan2MCBwActViolActEthDei4 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth4

       Possibilities:
               unchanged   (255)
               clear   (0)
               set   (1)"
   ::= {er1645v2Lan2MCBwEntry 4132962304}

er1645v2Lan2MCBwActViolActEthCos5 OBJECT-TYPE
   SYNTAX      INTEGER
               {
               unchanged (256)
               }
   MAX-ACCESS  read-write
   STATUS      current
   DESCRIPTION
      "Path: ethernet2.editConf.bandwidth.action.violateAction.ethernet.cosDepth5

       Possibilities:
               unchanged   (256)"
   ::= {er1645v2Lan2MCBwEntry 4131717120}

er1645v2Lan2MCBwActViolActEthDei5 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth5

       Possibilities:
               unchanged   (255)
               clear   (0)
               set   (1)"
   ::= {er1645v2Lan2MCBwEntry 4133027840}

er1645v2Lan2MCBwActViolActEthCos6 OBJECT-TYPE
   SYNTAX      INTEGER
               {
               unchanged (256)
               }
   MAX-ACCESS  read-write
   STATUS      current
   DESCRIPTION
      "Path: ethernet2.editConf.bandwidth.action.violateAction.ethernet.cosDepth6

       Possibilities:
               unchanged   (256)"
   ::= {er1645v2Lan2MCBwEntry 4131782656}

er1645v2Lan2MCBwActViolActEthDei6 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth6

       Possibilities:
               unchanged   (255)
               clear   (0)
               set   (1)"
   ::= {er1645v2Lan2MCBwEntry 4133093376}

er1645v2Lan2MCBwActViolActEthCos7 OBJECT-TYPE
   SYNTAX      INTEGER
               {
               unchanged (256)
               }
   MAX-ACCESS  read-write
   STATUS      current
   DESCRIPTION
      "Path: ethernet2.editConf.bandwidth.action.violateAction.ethernet.cosDepth7

       Possibilities:
               unchanged   (256)"
   ::= {er1645v2Lan2MCBwEntry 4131848192}

er1645v2Lan2MCBwActViolActEthDei7 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth7

       Possibilities:
               unchanged   (255)
               clear   (0)
               set   (1)"
   ::= {er1645v2Lan2MCBwEntry 4133158912}

er1645v2Lan2MCBwActViolActEthCos8 OBJECT-TYPE
   SYNTAX      INTEGER
               {
               unchanged (256)
               }
   MAX-ACCESS  read-write
   STATUS      current
   DESCRIPTION
      "Path: ethernet2.editConf.bandwidth.action.violateAction.ethernet.cosDepth8

       Possibilities:
               unchanged   (256)"
   ::= {er1645v2Lan2MCBwEntry 4131913728}

er1645v2Lan2MCBwActViolActEthDei8 OBJECT-TYPE
   SYNTAX      INTEGER
               {
               unchanged (255),
               clear (0),
               set (1)
               }
   MAX-ACCESS  read-write
   STATUS      current
   DESCRIPTION
      "Path: ethernet2.editConf.bandwidth.action.violateAction.ethernet.deiDepth8

       Possibilities:
               unchanged   (255)
               clear   (0)
               set   (1)"
   ::= {er1645v2Lan2MCBwEntry 4133224448}

er1645v2Lan2MCBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCBwEntry 4131979264}

er1645v2Lan2MCBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCBwEntry 4132044800}

er1645v2Lan2MCBwActViolActEthDrpLev OBJECT-TYPE
   SYNTAX      INTEGER
               {
               unchanged (0)
               }
   MAX-ACCESS  read-write
   STATUS      current
   DESCRIPTION
      "Path: ethernet2.editConf.bandwidth.action.violateAction.ethernet.dropLevel

       Possibilities:
               unchanged   (0)"
   ::= {er1645v2Lan2MCBwEntry 4132110336}

er1645v2Lan2MCBwActViolActEthDeFlag OBJECT-TYPE
   SYNTAX      INTEGER
               {
               unchanged (255),
               clear (0),
               set (1)
               }
   MAX-ACCESS  read-write
   STATUS      current
   DESCRIPTION
      "Path: ethernet2.editConf.bandwidth.action.violateAction.ethernet.deFlag

       Possibilities:
               unchanged   (255)
               clear   (0)
               set   (1)"
   ::= {er1645v2Lan2MCBwEntry 4132306944}

er1645v2Lan2MCBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCBwEntry 4138270720}

er1645v2Lan2MCBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCBwEntry 4138336256}

er1645v2Lan2MCBwActViolActIpDrpLev OBJECT-TYPE
   SYNTAX      INTEGER
               {
               unchanged (0)
               }
   MAX-ACCESS  read-write
   STATUS      current
   DESCRIPTION
      "Path: ethernet2.editConf.bandwidth.action.violateAction.ip.dropLevel

       Possibilities:
               unchanged   (0)"
   ::= {er1645v2Lan2MCBwEntry 4138401792}

er1645v2Lan2MCBwActViolActIpDeFlag OBJECT-TYPE
   SYNTAX      INTEGER
               {
               unchanged (255),
               clear (0),
               set (1)
               }
   MAX-ACCESS  read-write
   STATUS      current
   DESCRIPTION
      "Path: ethernet2.editConf.bandwidth.action.violateAction.ip.deFlag

       Possibilities:
               unchanged   (255)
               clear   (0)
               set   (1)"
   ::= {er1645v2Lan2MCBwEntry 4138598400}


er1645v2Lan2MCIbw OBJECT IDENTIFIER ::= {er1645v2Lan2MC 13}

er1645v2Lan2MCIbwSSC OBJECT IDENTIFIER ::= {er1645v2Lan2MCIbw 1}

er1645v2Lan2MCIbwEntry OBJECT IDENTIFIER ::= {er1645v2Lan2MCIbwSSC 1}

er1645v2Lan2MCIbwMode OBJECT-TYPE
   SYNTAX      INTEGER
               {
               reshaping (1),
               policing (2)
               }
   MAX-ACCESS  read-write
   STATUS      current
   DESCRIPTION
      "Path: ethernet2.editConf.inboundBandwidth.mode

       Possibilities:
               reshaping   (1)
               policing   (2)"
   ::= {er1645v2Lan2MCIbwEntry 3758096384}

er1645v2Lan2MCIbwCir OBJECT-TYPE
   SYNTAX      Integer32
   MAX-ACCESS  read-write
   STATUS      current
   DESCRIPTION
      "Path: ethernet2.editConf.inboundBandwidth.cir"
   ::= {er1645v2Lan2MCIbwEntry 268435456}

er1645v2Lan2MCIbwEir OBJECT-TYPE
   SYNTAX      Integer32
   MAX-ACCESS  read-write
   STATUS      current
   DESCRIPTION
      "Path: ethernet2.editConf.inboundBandwidth.eir"
   ::= {er1645v2Lan2MCIbwEntry 1879048192}

er1645v2Lan2MCIbwUnit OBJECT-TYPE
   SYNTAX      INTEGER
               {
               bitssec (1),
               percent (2)
               }
   MAX-ACCESS  read-write
   STATUS      current
   DESCRIPTION
      "Path: ethernet2.editConf.inboundBandwidth.unit

       Possibilities:
               bits/sec   (1)
               percent   (2)"
   ::= {er1645v2Lan2MCIbwEntry 1342177280}

er1645v2Lan2MCIbwTc OBJECT-TYPE
   SYNTAX      INTEGER
               {
               auto (0)
               }
   MAX-ACCESS  read-write
   STATUS      current
   DESCRIPTION
      "Path: ethernet2.editConf.inboundBandwidth.tc

       Possibilities:
               auto   (0)"
   ::= {er1645v2Lan2MCIbwEntry 1610612736}

er1645v2Lan2MCIbwTcFactor OBJECT-TYPE
   SYNTAX      INTEGER
               {
               ms (10),
               s100us (1)
               }
   MAX-ACCESS  read-write
   STATUS      current
   DESCRIPTION
      "Path: ethernet2.editConf.inboundBandwidth.tcFactor

       Possibilities:
               ms   (10)
               *100us   (1)"
   ::= {er1645v2Lan2MCIbwEntry 2147483648}

er1645v2Lan2MCIbwCorrType OBJECT-TYPE
   SYNTAX      INTEGER
               {
               noCorrection (0),
               predefined (1),
               manual (2)
               }
   MAX-ACCESS  read-write
   STATUS      current
   DESCRIPTION
      "Path: ethernet2.editConf.inboundBandwidth.correction.type

       Possibilities:
               noCorrection   (0)
               predefined   (1)
               manual   (2)"
   ::= {er1645v2Lan2MCIbwEntry 570425344}

er1645v2Lan2MCIbwCorrPredefEncapsFrameRelay OBJECT-TYPE
   SYNTAX      DisplayString
   MAX-ACCESS  read-write
   STATUS      current
   DESCRIPTION
      "Path: ethernet2.editConf.inboundBandwidth.correction.predefined.encapsulation.frameRelay"
   ::= {er1645v2Lan2MCIbwEntry 608436224}

er1645v2Lan2MCIbwCorrPredefEncapsPpp OBJECT-TYPE
   SYNTAX      DisplayString
   MAX-ACCESS  read-write
   STATUS      current
   DESCRIPTION
      "Path: ethernet2.editConf.inboundBandwidth.correction.predefined.encapsulation.ppp"
   ::= {er1645v2Lan2MCIbwEntry 608698368}

er1645v2Lan2MCIbwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.inboundBandwidth.correction.predefined.encapsulation.atm.higherLayer

       Possibilities:
               rfc2684   (0)
               ppp   (1)
               pppOverEthernet   (2)"
   ::= {er1645v2Lan2MCIbwEntry 608993280}

er1645v2Lan2MCIbwCorrPredefEncapsAtmMp OBJECT-TYPE
   SYNTAX      INTEGER
               {
               llcEncapsulation (0),
               vcMultiplexing (1)
               }
   MAX-ACCESS  read-write
   STATUS      current
   DESCRIPTION
      "Path: ethernet2.editConf.inboundBandwidth.correction.predefined.encapsulation.atm.multiProtocol

       Possibilities:
               llcEncapsulation   (0)
               vcMultiplexing   (1)"
   ::= {er1645v2Lan2MCIbwEntry 609026048}

er1645v2Lan2MCIbwCorrPredefEncapsHdlc OBJECT-TYPE
   SYNTAX      DisplayString
   MAX-ACCESS  read-write
   STATUS      current
   DESCRIPTION
      "Path: ethernet2.editConf.inboundBandwidth.correction.predefined.encapsulation.hdlc"
   ::= {er1645v2Lan2MCIbwEntry 609222656}

er1645v2Lan2MCIbwCorrPredefEncapsEfmFs OBJECT-TYPE
   SYNTAX      Integer32
   MAX-ACCESS  read-write
   STATUS      current
   DESCRIPTION
      "Path: ethernet2.editConf.inboundBandwidth.correction.predefined.encapsulation.efm.fragmentSize"
   ::= {er1645v2Lan2MCIbwEntry 609517568}

er1645v2Lan2MCIbwCorrPredefEncapsEfmIb OBJECT-TYPE
   SYNTAX      Integer32
   MAX-ACCESS  read-write
   STATUS      current
   DESCRIPTION
      "Path: ethernet2.editConf.inboundBandwidth.correction.predefined.encapsulation.efm.idleBytes"
   ::= {er1645v2Lan2MCIbwEntry 609550336}

er1645v2Lan2MCIbwCorrPredefMode OBJECT-TYPE
   SYNTAX      INTEGER
               {
               routing (0),
               bridging (1)
               }
   MAX-ACCESS  read-write
   STATUS      current
   DESCRIPTION
      "Path: ethernet2.editConf.inboundBandwidth.correction.predefined.mode

       Possibilities:
               routing   (0)
               bridging   (1)"
   ::= {er1645v2Lan2MCIbwEntry 612368384}

er1645v2Lan2MCIbwCorrManualOverhead OBJECT-TYPE
   SYNTAX      Integer32
   MAX-ACCESS  read-write
   STATUS      current
   DESCRIPTION
      "Path: ethernet2.editConf.inboundBandwidth.correction.manual.overhead"
   ::= {er1645v2Lan2MCIbwEntry 637665280}

er1645v2Lan2MCIbwCorrManualFrameData OBJECT-TYPE
   SYNTAX      Counter32
   MAX-ACCESS  read-write
   STATUS      current
   DESCRIPTION
      "Path: ethernet2.editConf.inboundBandwidth.correction.manual.frameData

       32 bit unsigned wrappable counter."
   ::= {er1645v2Lan2MCIbwEntry 637796352}

er1645v2Lan2MCIbwCorrManualFrameHeader OBJECT-TYPE
   SYNTAX      Counter32
   MAX-ACCESS  read-write
   STATUS      current
   DESCRIPTION
      "Path: ethernet2.editConf.inboundBandwidth.correction.manual.frameHeader

       32 bit unsigned wrappable counter."
   ::= {er1645v2Lan2MCIbwEntry 637927424}

er1645v2Lan2MCIbwMaxFifoQLen OBJECT-TYPE
   SYNTAX      Integer32
   MAX-ACCESS  read-write
   STATUS      current
   DESCRIPTION
      "Path: ethernet2.editConf.inboundBandwidth.maxFifoQLen"
   ::= {er1645v2Lan2MCIbwEntry 805306368}

er1645v2Lan2MCIbwPriorityPolicy OBJECT-TYPE
   SYNTAX      DisplayString
   MAX-ACCESS  read-write
   STATUS      current
   DESCRIPTION
      "Path: ethernet2.editConf.inboundBandwidth.priorityPolicy"
   ::= {er1645v2Lan2MCIbwEntry 1073741824}

er1645v2Lan2MCIbwDeFlagCir OBJECT-TYPE
   SYNTAX      INTEGER
               {
               allowed (1),
               notAllowed (2)
               }
   MAX-ACCESS  read-write
   STATUS      current
   DESCRIPTION
      "Path: ethernet2.editConf.inboundBandwidth.deFlag.cir

       Possibilities:
               allowed   (1)
               notAllowed   (2)"
   ::= {er1645v2Lan2MCIbwEntry 3490709504}

er1645v2Lan2MCIbwDeFlagEir OBJECT-TYPE
   SYNTAX      INTEGER
               {
               allowed (1),
               notAllowed (2)
               }
   MAX-ACCESS  read-write
   STATUS      current
   DESCRIPTION
      "Path: ethernet2.editConf.inboundBandwidth.deFlag.eir

       Possibilities:
               allowed   (1)
               notAllowed   (2)"
   ::= {er1645v2Lan2MCIbwEntry 3491758080}

er1645v2Lan2MCIbwDeFlagViolate OBJECT-TYPE
   SYNTAX      INTEGER
               {
               allowed (1),
               notAllowed (2)
               }
   MAX-ACCESS  read-write
   STATUS      current
   DESCRIPTION
      "Path: ethernet2.editConf.inboundBandwidth.deFlag.violate

       Possibilities:
               allowed   (1)
               notAllowed   (2)"
   ::= {er1645v2Lan2MCIbwEntry 3492806656}

er1645v2Lan2MCIbwActCirActNone OBJECT-TYPE
   SYNTAX      OCTET STRING
   MAX-ACCESS  read-write
   STATUS      current
   DESCRIPTION
      "Path: ethernet2.editConf.inboundBandwidth.action.cirAction.none"
   ::= {er1645v2Lan2MCIbwEntry 4062183424}

er1645v2Lan2MCIbwActCirActEthCos1 OBJECT-TYPE
   SYNTAX      INTEGER
               {
               unchanged (256)
               }
   MAX-ACCESS  read-write
   STATUS      current
   DESCRIPTION
      "Path: ethernet2.editConf.inboundBandwidth.action.cirAction.ethernet.cosDepth1

       Possibilities:
               unchanged   (256)"
   ::= {er1645v2Lan2MCIbwEntry 4064346112}

er1645v2Lan2MCIbwActCirActEthDei1 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth1

       Possibilities:
               unchanged   (255)
               clear   (0)
               set   (1)"
   ::= {er1645v2Lan2MCIbwEntry 4065656832}

er1645v2Lan2MCIbwActCirActEthCos2 OBJECT-TYPE
   SYNTAX      INTEGER
               {
               unchanged (256)
               }
   MAX-ACCESS  read-write
   STATUS      current
   DESCRIPTION
      "Path: ethernet2.editConf.inboundBandwidth.action.cirAction.ethernet.cosDepth2

       Possibilities:
               unchanged   (256)"
   ::= {er1645v2Lan2MCIbwEntry 4064411648}

er1645v2Lan2MCIbwActCirActEthDei2 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth2

       Possibilities:
               unchanged   (255)
               clear   (0)
               set   (1)"
   ::= {er1645v2Lan2MCIbwEntry 4065722368}

er1645v2Lan2MCIbwActCirActEthCos3 OBJECT-TYPE
   SYNTAX      INTEGER
               {
               unchanged (256)
               }
   MAX-ACCESS  read-write
   STATUS      current
   DESCRIPTION
      "Path: ethernet2.editConf.inboundBandwidth.action.cirAction.ethernet.cosDepth3

       Possibilities:
               unchanged   (256)"
   ::= {er1645v2Lan2MCIbwEntry 4064477184}

er1645v2Lan2MCIbwActCirActEthDei3 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth3

       Possibilities:
               unchanged   (255)
               clear   (0)
               set   (1)"
   ::= {er1645v2Lan2MCIbwEntry 4065787904}

er1645v2Lan2MCIbwActCirActEthCos4 OBJECT-TYPE
   SYNTAX      INTEGER
               {
               unchanged (256)
               }
   MAX-ACCESS  read-write
   STATUS      current
   DESCRIPTION
      "Path: ethernet2.editConf.inboundBandwidth.action.cirAction.ethernet.cosDepth4

       Possibilities:
               unchanged   (256)"
   ::= {er1645v2Lan2MCIbwEntry 4064542720}

er1645v2Lan2MCIbwActCirActEthDei4 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth4

       Possibilities:
               unchanged   (255)
               clear   (0)
               set   (1)"
   ::= {er1645v2Lan2MCIbwEntry 4065853440}

er1645v2Lan2MCIbwActCirActEthCos5 OBJECT-TYPE
   SYNTAX      INTEGER
               {
               unchanged (256)
               }
   MAX-ACCESS  read-write
   STATUS      current
   DESCRIPTION
      "Path: ethernet2.editConf.inboundBandwidth.action.cirAction.ethernet.cosDepth5

       Possibilities:
               unchanged   (256)"
   ::= {er1645v2Lan2MCIbwEntry 4064608256}

er1645v2Lan2MCIbwActCirActEthDei5 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth5

       Possibilities:
               unchanged   (255)
               clear   (0)
               set   (1)"
   ::= {er1645v2Lan2MCIbwEntry 4065918976}

er1645v2Lan2MCIbwActCirActEthCos6 OBJECT-TYPE
   SYNTAX      INTEGER
               {
               unchanged (256)
               }
   MAX-ACCESS  read-write
   STATUS      current
   DESCRIPTION
      "Path: ethernet2.editConf.inboundBandwidth.action.cirAction.ethernet.cosDepth6

       Possibilities:
               unchanged   (256)"
   ::= {er1645v2Lan2MCIbwEntry 4064673792}

er1645v2Lan2MCIbwActCirActEthDei6 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth6

       Possibilities:
               unchanged   (255)
               clear   (0)
               set   (1)"
   ::= {er1645v2Lan2MCIbwEntry 4065984512}

er1645v2Lan2MCIbwActCirActEthCos7 OBJECT-TYPE
   SYNTAX      INTEGER
               {
               unchanged (256)
               }
   MAX-ACCESS  read-write
   STATUS      current
   DESCRIPTION
      "Path: ethernet2.editConf.inboundBandwidth.action.cirAction.ethernet.cosDepth7

       Possibilities:
               unchanged   (256)"
   ::= {er1645v2Lan2MCIbwEntry 4064739328}

er1645v2Lan2MCIbwActCirActEthDei7 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth7

       Possibilities:
               unchanged   (255)
               clear   (0)
               set   (1)"
   ::= {er1645v2Lan2MCIbwEntry 4066050048}

er1645v2Lan2MCIbwActCirActEthCos8 OBJECT-TYPE
   SYNTAX      INTEGER
               {
               unchanged (256)
               }
   MAX-ACCESS  read-write
   STATUS      current
   DESCRIPTION
      "Path: ethernet2.editConf.inboundBandwidth.action.cirAction.ethernet.cosDepth8

       Possibilities:
               unchanged   (256)"
   ::= {er1645v2Lan2MCIbwEntry 4064804864}

er1645v2Lan2MCIbwActCirActEthDei8 OBJECT-TYPE
   SYNTAX      INTEGER
               {
               unchanged (255),
               clear (0),
               set (1)
               }
   MAX-ACCESS  read-write
   STATUS      current
   DESCRIPTION
      "Path: ethernet2.editConf.inboundBandwidth.action.cirAction.ethernet.deiDepth8

       Possibilities:
               unchanged   (255)
               clear   (0)
               set   (1)"
   ::= {er1645v2Lan2MCIbwEntry 4066115584}

er1645v2Lan2MCIbwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCIbwEntry 4064870400}

er1645v2Lan2MCIbwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCIbwEntry 4064935936}

er1645v2Lan2MCIbwActCirActEthDrpLev OBJECT-TYPE
   SYNTAX      INTEGER
               {
               unchanged (0)
               }
   MAX-ACCESS  read-write
   STATUS      current
   DESCRIPTION
      "Path: ethernet2.editConf.inboundBandwidth.action.cirAction.ethernet.dropLevel

       Possibilities:
               unchanged   (0)"
   ::= {er1645v2Lan2MCIbwEntry 4065001472}

er1645v2Lan2MCIbwActCirActEthDeFlag OBJECT-TYPE
   SYNTAX      INTEGER
               {
               unchanged (255),
               clear (0),
               set (1)
               }
   MAX-ACCESS  read-write
   STATUS      current
   DESCRIPTION
      "Path: ethernet2.editConf.inboundBandwidth.action.cirAction.ethernet.deFlag

       Possibilities:
               unchanged   (255)
               clear   (0)
               set   (1)"
   ::= {er1645v2Lan2MCIbwEntry 4065198080}

er1645v2Lan2MCIbwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCIbwEntry 4071161856}

er1645v2Lan2MCIbwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCIbwEntry 4071227392}

er1645v2Lan2MCIbwActCirActIpDrpLev OBJECT-TYPE
   SYNTAX      INTEGER
               {
               unchanged (0)
               }
   MAX-ACCESS  read-write
   STATUS      current
   DESCRIPTION
      "Path: ethernet2.editConf.inboundBandwidth.action.cirAction.ip.dropLevel

       Possibilities:
               unchanged   (0)"
   ::= {er1645v2Lan2MCIbwEntry 4071292928}

er1645v2Lan2MCIbwActCirActIpDeFlag OBJECT-TYPE
   SYNTAX      INTEGER
               {
               unchanged (255),
               clear (0),
               set (1)
               }
   MAX-ACCESS  read-write
   STATUS      current
   DESCRIPTION
      "Path: ethernet2.editConf.inboundBandwidth.action.cirAction.ip.deFlag

       Possibilities:
               unchanged   (255)
               clear   (0)
               set   (1)"
   ::= {er1645v2Lan2MCIbwEntry 4071489536}

er1645v2Lan2MCIbwActEirActNone OBJECT-TYPE
   SYNTAX      OCTET STRING
   MAX-ACCESS  read-write
   STATUS      current
   DESCRIPTION
      "Path: ethernet2.editConf.inboundBandwidth.action.eirAction.none"
   ::= {er1645v2Lan2MCIbwEntry 4095737856}

er1645v2Lan2MCIbwActEirActEthCos1 OBJECT-TYPE
   SYNTAX      INTEGER
               {
               unchanged (256)
               }
   MAX-ACCESS  read-write
   STATUS      current
   DESCRIPTION
      "Path: ethernet2.editConf.inboundBandwidth.action.eirAction.ethernet.cosDepth1

       Possibilities:
               unchanged   (256)"
   ::= {er1645v2Lan2MCIbwEntry 4097900544}

er1645v2Lan2MCIbwActEirActEthDei1 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth1

       Possibilities:
               unchanged   (255)
               clear   (0)
               set   (1)"
   ::= {er1645v2Lan2MCIbwEntry 4099211264}

er1645v2Lan2MCIbwActEirActEthCos2 OBJECT-TYPE
   SYNTAX      INTEGER
               {
               unchanged (256)
               }
   MAX-ACCESS  read-write
   STATUS      current
   DESCRIPTION
      "Path: ethernet2.editConf.inboundBandwidth.action.eirAction.ethernet.cosDepth2

       Possibilities:
               unchanged   (256)"
   ::= {er1645v2Lan2MCIbwEntry 4097966080}

er1645v2Lan2MCIbwActEirActEthDei2 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth2

       Possibilities:
               unchanged   (255)
               clear   (0)
               set   (1)"
   ::= {er1645v2Lan2MCIbwEntry 4099276800}

er1645v2Lan2MCIbwActEirActEthCos3 OBJECT-TYPE
   SYNTAX      INTEGER
               {
               unchanged (256)
               }
   MAX-ACCESS  read-write
   STATUS      current
   DESCRIPTION
      "Path: ethernet2.editConf.inboundBandwidth.action.eirAction.ethernet.cosDepth3

       Possibilities:
               unchanged   (256)"
   ::= {er1645v2Lan2MCIbwEntry 4098031616}

er1645v2Lan2MCIbwActEirActEthDei3 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth3

       Possibilities:
               unchanged   (255)
               clear   (0)
               set   (1)"
   ::= {er1645v2Lan2MCIbwEntry 4099342336}

er1645v2Lan2MCIbwActEirActEthCos4 OBJECT-TYPE
   SYNTAX      INTEGER
               {
               unchanged (256)
               }
   MAX-ACCESS  read-write
   STATUS      current
   DESCRIPTION
      "Path: ethernet2.editConf.inboundBandwidth.action.eirAction.ethernet.cosDepth4

       Possibilities:
               unchanged   (256)"
   ::= {er1645v2Lan2MCIbwEntry 4098097152}

er1645v2Lan2MCIbwActEirActEthDei4 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth4

       Possibilities:
               unchanged   (255)
               clear   (0)
               set   (1)"
   ::= {er1645v2Lan2MCIbwEntry 4099407872}

er1645v2Lan2MCIbwActEirActEthCos5 OBJECT-TYPE
   SYNTAX      INTEGER
               {
               unchanged (256)
               }
   MAX-ACCESS  read-write
   STATUS      current
   DESCRIPTION
      "Path: ethernet2.editConf.inboundBandwidth.action.eirAction.ethernet.cosDepth5

       Possibilities:
               unchanged   (256)"
   ::= {er1645v2Lan2MCIbwEntry 4098162688}

er1645v2Lan2MCIbwActEirActEthDei5 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth5

       Possibilities:
               unchanged   (255)
               clear   (0)
               set   (1)"
   ::= {er1645v2Lan2MCIbwEntry 4099473408}

er1645v2Lan2MCIbwActEirActEthCos6 OBJECT-TYPE
   SYNTAX      INTEGER
               {
               unchanged (256)
               }
   MAX-ACCESS  read-write
   STATUS      current
   DESCRIPTION
      "Path: ethernet2.editConf.inboundBandwidth.action.eirAction.ethernet.cosDepth6

       Possibilities:
               unchanged   (256)"
   ::= {er1645v2Lan2MCIbwEntry 4098228224}

er1645v2Lan2MCIbwActEirActEthDei6 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth6

       Possibilities:
               unchanged   (255)
               clear   (0)
               set   (1)"
   ::= {er1645v2Lan2MCIbwEntry 4099538944}

er1645v2Lan2MCIbwActEirActEthCos7 OBJECT-TYPE
   SYNTAX      INTEGER
               {
               unchanged (256)
               }
   MAX-ACCESS  read-write
   STATUS      current
   DESCRIPTION
      "Path: ethernet2.editConf.inboundBandwidth.action.eirAction.ethernet.cosDepth7

       Possibilities:
               unchanged   (256)"
   ::= {er1645v2Lan2MCIbwEntry 4098293760}

er1645v2Lan2MCIbwActEirActEthDei7 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth7

       Possibilities:
               unchanged   (255)
               clear   (0)
               set   (1)"
   ::= {er1645v2Lan2MCIbwEntry 4099604480}

er1645v2Lan2MCIbwActEirActEthCos8 OBJECT-TYPE
   SYNTAX      INTEGER
               {
               unchanged (256)
               }
   MAX-ACCESS  read-write
   STATUS      current
   DESCRIPTION
      "Path: ethernet2.editConf.inboundBandwidth.action.eirAction.ethernet.cosDepth8

       Possibilities:
               unchanged   (256)"
   ::= {er1645v2Lan2MCIbwEntry 4098359296}

er1645v2Lan2MCIbwActEirActEthDei8 OBJECT-TYPE
   SYNTAX      INTEGER
               {
               unchanged (255),
               clear (0),
               set (1)
               }
   MAX-ACCESS  read-write
   STATUS      current
   DESCRIPTION
      "Path: ethernet2.editConf.inboundBandwidth.action.eirAction.ethernet.deiDepth8

       Possibilities:
               unchanged   (255)
               clear   (0)
               set   (1)"
   ::= {er1645v2Lan2MCIbwEntry 4099670016}

er1645v2Lan2MCIbwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCIbwEntry 4098424832}

er1645v2Lan2MCIbwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCIbwEntry 4098490368}

er1645v2Lan2MCIbwActEirActEthDrpLev OBJECT-TYPE
   SYNTAX      INTEGER
               {
               unchanged (0)
               }
   MAX-ACCESS  read-write
   STATUS      current
   DESCRIPTION
      "Path: ethernet2.editConf.inboundBandwidth.action.eirAction.ethernet.dropLevel

       Possibilities:
               unchanged   (0)"
   ::= {er1645v2Lan2MCIbwEntry 4098555904}

er1645v2Lan2MCIbwActEirActEthDeFlag OBJECT-TYPE
   SYNTAX      INTEGER
               {
               unchanged (255),
               clear (0),
               set (1)
               }
   MAX-ACCESS  read-write
   STATUS      current
   DESCRIPTION
      "Path: ethernet2.editConf.inboundBandwidth.action.eirAction.ethernet.deFlag

       Possibilities:
               unchanged   (255)
               clear   (0)
               set   (1)"
   ::= {er1645v2Lan2MCIbwEntry 4098752512}

er1645v2Lan2MCIbwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCIbwEntry 4104716288}

er1645v2Lan2MCIbwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCIbwEntry 4104781824}

er1645v2Lan2MCIbwActEirActIpDrpLev OBJECT-TYPE
   SYNTAX      INTEGER
               {
               unchanged (0)
               }
   MAX-ACCESS  read-write
   STATUS      current
   DESCRIPTION
      "Path: ethernet2.editConf.inboundBandwidth.action.eirAction.ip.dropLevel

       Possibilities:
               unchanged   (0)"
   ::= {er1645v2Lan2MCIbwEntry 4104847360}

er1645v2Lan2MCIbwActEirActIpDeFlag OBJECT-TYPE
   SYNTAX      INTEGER
               {
               unchanged (255),
               clear (0),
               set (1)
               }
   MAX-ACCESS  read-write
   STATUS      current
   DESCRIPTION
      "Path: ethernet2.editConf.inboundBandwidth.action.eirAction.ip.deFlag

       Possibilities:
               unchanged   (255)
               clear   (0)
               set   (1)"
   ::= {er1645v2Lan2MCIbwEntry 4105043968}

er1645v2Lan2MCIbwActViolActNone OBJECT-TYPE
   SYNTAX      OCTET STRING
   MAX-ACCESS  read-write
   STATUS      current
   DESCRIPTION
      "Path: ethernet2.editConf.inboundBandwidth.action.violateAction.none"
   ::= {er1645v2Lan2MCIbwEntry 4129292288}

er1645v2Lan2MCIbwActViolActDrop OBJECT-TYPE
   SYNTAX      OCTET STRING
   MAX-ACCESS  read-write
   STATUS      current
   DESCRIPTION
      "Path: ethernet2.editConf.inboundBandwidth.action.violateAction.drop"
   ::= {er1645v2Lan2MCIbwEntry 4133486592}

er1645v2Lan2MCIbwActViolActEthCos1 OBJECT-TYPE
   SYNTAX      INTEGER
               {
               unchanged (256)
               }
   MAX-ACCESS  read-write
   STATUS      current
   DESCRIPTION
      "Path: ethernet2.editConf.inboundBandwidth.action.violateAction.ethernet.cosDepth1

       Possibilities:
               unchanged   (256)"
   ::= {er1645v2Lan2MCIbwEntry 4131454976}

er1645v2Lan2MCIbwActViolActEthDei1 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth1

       Possibilities:
               unchanged   (255)
               clear   (0)
               set   (1)"
   ::= {er1645v2Lan2MCIbwEntry 4132765696}

er1645v2Lan2MCIbwActViolActEthCos2 OBJECT-TYPE
   SYNTAX      INTEGER
               {
               unchanged (256)
               }
   MAX-ACCESS  read-write
   STATUS      current
   DESCRIPTION
      "Path: ethernet2.editConf.inboundBandwidth.action.violateAction.ethernet.cosDepth2

       Possibilities:
               unchanged   (256)"
   ::= {er1645v2Lan2MCIbwEntry 4131520512}

er1645v2Lan2MCIbwActViolActEthDei2 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth2

       Possibilities:
               unchanged   (255)
               clear   (0)
               set   (1)"
   ::= {er1645v2Lan2MCIbwEntry 4132831232}

er1645v2Lan2MCIbwActViolActEthCos3 OBJECT-TYPE
   SYNTAX      INTEGER
               {
               unchanged (256)
               }
   MAX-ACCESS  read-write
   STATUS      current
   DESCRIPTION
      "Path: ethernet2.editConf.inboundBandwidth.action.violateAction.ethernet.cosDepth3

       Possibilities:
               unchanged   (256)"
   ::= {er1645v2Lan2MCIbwEntry 4131586048}

er1645v2Lan2MCIbwActViolActEthDei3 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth3

       Possibilities:
               unchanged   (255)
               clear   (0)
               set   (1)"
   ::= {er1645v2Lan2MCIbwEntry 4132896768}

er1645v2Lan2MCIbwActViolActEthCos4 OBJECT-TYPE
   SYNTAX      INTEGER
               {
               unchanged (256)
               }
   MAX-ACCESS  read-write
   STATUS      current
   DESCRIPTION
      "Path: ethernet2.editConf.inboundBandwidth.action.violateAction.ethernet.cosDepth4

       Possibilities:
               unchanged   (256)"
   ::= {er1645v2Lan2MCIbwEntry 4131651584}

er1645v2Lan2MCIbwActViolActEthDei4 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth4

       Possibilities:
               unchanged   (255)
               clear   (0)
               set   (1)"
   ::= {er1645v2Lan2MCIbwEntry 4132962304}

er1645v2Lan2MCIbwActViolActEthCos5 OBJECT-TYPE
   SYNTAX      INTEGER
               {
               unchanged (256)
               }
   MAX-ACCESS  read-write
   STATUS      current
   DESCRIPTION
      "Path: ethernet2.editConf.inboundBandwidth.action.violateAction.ethernet.cosDepth5

       Possibilities:
               unchanged   (256)"
   ::= {er1645v2Lan2MCIbwEntry 4131717120}

er1645v2Lan2MCIbwActViolActEthDei5 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth5

       Possibilities:
               unchanged   (255)
               clear   (0)
               set   (1)"
   ::= {er1645v2Lan2MCIbwEntry 4133027840}

er1645v2Lan2MCIbwActViolActEthCos6 OBJECT-TYPE
   SYNTAX      INTEGER
               {
               unchanged (256)
               }
   MAX-ACCESS  read-write
   STATUS      current
   DESCRIPTION
      "Path: ethernet2.editConf.inboundBandwidth.action.violateAction.ethernet.cosDepth6

       Possibilities:
               unchanged   (256)"
   ::= {er1645v2Lan2MCIbwEntry 4131782656}

er1645v2Lan2MCIbwActViolActEthDei6 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth6

       Possibilities:
               unchanged   (255)
               clear   (0)
               set   (1)"
   ::= {er1645v2Lan2MCIbwEntry 4133093376}

er1645v2Lan2MCIbwActViolActEthCos7 OBJECT-TYPE
   SYNTAX      INTEGER
               {
               unchanged (256)
               }
   MAX-ACCESS  read-write
   STATUS      current
   DESCRIPTION
      "Path: ethernet2.editConf.inboundBandwidth.action.violateAction.ethernet.cosDepth7

       Possibilities:
               unchanged   (256)"
   ::= {er1645v2Lan2MCIbwEntry 4131848192}

er1645v2Lan2MCIbwActViolActEthDei7 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth7

       Possibilities:
               unchanged   (255)
               clear   (0)
               set   (1)"
   ::= {er1645v2Lan2MCIbwEntry 4133158912}

er1645v2Lan2MCIbwActViolActEthCos8 OBJECT-TYPE
   SYNTAX      INTEGER
               {
               unchanged (256)
               }
   MAX-ACCESS  read-write
   STATUS      current
   DESCRIPTION
      "Path: ethernet2.editConf.inboundBandwidth.action.violateAction.ethernet.cosDepth8

       Possibilities:
               unchanged   (256)"
   ::= {er1645v2Lan2MCIbwEntry 4131913728}

er1645v2Lan2MCIbwActViolActEthDei8 OBJECT-TYPE
   SYNTAX      INTEGER
               {
               unchanged (255),
               clear (0),
               set (1)
               }
   MAX-ACCESS  read-write
   STATUS      current
   DESCRIPTION
      "Path: ethernet2.editConf.inboundBandwidth.action.violateAction.ethernet.deiDepth8

       Possibilities:
               unchanged   (255)
               clear   (0)
               set   (1)"
   ::= {er1645v2Lan2MCIbwEntry 4133224448}

er1645v2Lan2MCIbwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCIbwEntry 4131979264}

er1645v2Lan2MCIbwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCIbwEntry 4132044800}

er1645v2Lan2MCIbwActViolActEthDrpLev OBJECT-TYPE
   SYNTAX      INTEGER
               {
               unchanged (0)
               }
   MAX-ACCESS  read-write
   STATUS      current
   DESCRIPTION
      "Path: ethernet2.editConf.inboundBandwidth.action.violateAction.ethernet.dropLevel

       Possibilities:
               unchanged   (0)"
   ::= {er1645v2Lan2MCIbwEntry 4132110336}

er1645v2Lan2MCIbwActViolActEthDeFlag OBJECT-TYPE
   SYNTAX      INTEGER
               {
               unchanged (255),
               clear (0),
               set (1)
               }
   MAX-ACCESS  read-write
   STATUS      current
   DESCRIPTION
      "Path: ethernet2.editConf.inboundBandwidth.action.violateAction.ethernet.deFlag

       Possibilities:
               unchanged   (255)
               clear   (0)
               set   (1)"
   ::= {er1645v2Lan2MCIbwEntry 4132306944}

er1645v2Lan2MCIbwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCIbwEntry 4138270720}

er1645v2Lan2MCIbwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCIbwEntry 4138336256}

er1645v2Lan2MCIbwActViolActIpDrpLev OBJECT-TYPE
   SYNTAX      INTEGER
               {
               unchanged (0)
               }
   MAX-ACCESS  read-write
   STATUS      current
   DESCRIPTION
      "Path: ethernet2.editConf.inboundBandwidth.action.violateAction.ip.dropLevel

       Possibilities:
               unchanged   (0)"
   ::= {er1645v2Lan2MCIbwEntry 4138401792}

er1645v2Lan2MCIbwActViolActIpDeFlag OBJECT-TYPE
   SYNTAX      INTEGER
               {
               unchanged (255),
               clear (0),
               set (1)
               }
   MAX-ACCESS  read-write
   STATUS      current
   DESCRIPTION
      "Path: ethernet2.editConf.inboundBandwidth.action.violateAction.ip.deFlag

       Possibilities:
               unchanged   (255)
               clear   (0)
               set   (1)"
   ::= {er1645v2Lan2MCIbwEntry 4138598400}

er1645v2Lan2MCIbwSubInterfacesExcluded OBJECT-TYPE
   SYNTAX      INTEGER
               {
               s (1)
               }
   MAX-ACCESS  read-write
   STATUS      current
   DESCRIPTION
      "Path: ethernet2.editConf.inboundBandwidth.subInterfaces.excluded

       Possibilities:
                  (1)"
   ::= {er1645v2Lan2MCIbwEntry 2416967680}

er1645v2Lan2MCIbwSubInterfacesIncludedInAccessList OBJECT-TYPE
   SYNTAX      DisplayString
   MAX-ACCESS  read-write
   STATUS      current
   DESCRIPTION
      "Path: ethernet2.editConf.inboundBandwidth.subInterfaces.included.inAccessList"
   ::= {er1645v2Lan2MCIbwEntry 2418020352}


er1645v2Lan2MCPriorityPolicy OBJECT-TYPE
   SYNTAX      DisplayString
   MAX-ACCESS  read-write
   STATUS      current
   DESCRIPTION
      "Path: ethernet2.editConf.priorityPolicy
       Info: Preferred Policy"
   ::= {er1645v2Lan2MC 39}


er1645v2Lan2MCMru OBJECT-TYPE
   SYNTAX      Integer32
   MAX-ACCESS  read-write
   STATUS      current
   DESCRIPTION
      "Path: ethernet2.editConf.mru"
   ::= {er1645v2Lan2MC 43}


er1645v2Lan2MCDelayOptimisation OBJECT-TYPE
   SYNTAX      INTEGER
               {
               disabled (0),
               enabled (1)
               }
   MAX-ACCESS  read-write
   STATUS      current
   DESCRIPTION
      "Path: ethernet2.editConf.delayOptimisation
       Info: optimise delay

       Possibilities:
               disabled   (0)
               enabled   (1)"
   ::= {er1645v2Lan2MC 80}


er1645v2Lan2MCAlarmMask OBJECT-TYPE
   SYNTAX      Integer32
   MAX-ACCESS  read-write
   STATUS      current
   DESCRIPTION
      "Path: ethernet2.editConf.alarmMask
       Info: ifAlarmMask

       Bit meanings:
               bit 0 = linkDown,
               bit 9 = pppoEDown"
   ::= {er1645v2Lan2MC 135}


er1645v2Lan2MCAlarmLev OBJECT IDENTIFIER ::= {er1645v2Lan2MC 170}

er1645v2Lan2MCAlarmLevSSC OBJECT IDENTIFIER ::= {er1645v2Lan2MCAlarmLev 1}

er1645v2Lan2MCAlarmLevEntry OBJECT IDENTIFIER ::= {er1645v2Lan2MCAlarmLevSSC 1}

er1645v2Lan2MCAlarmLevLinkDown OBJECT-TYPE
   SYNTAX      Integer32
   MAX-ACCESS  read-write
   STATUS      current
   DESCRIPTION
      "Path: ethernet2.editConf.alarmLevel.linkDown"
   ::= {er1645v2Lan2MCAlarmLevEntry 16777216}

er1645v2Lan2MCAlarmLevPppoEDown OBJECT-TYPE
   SYNTAX      Integer32
   MAX-ACCESS  read-write
   STATUS      current
   DESCRIPTION
      "Path: ethernet2.editConf.alarmLevel.pppoEDown"
   ::= {er1645v2Lan2MCAlarmLevEntry 167772160}


er1645v2Lan2MCArp OBJECT IDENTIFIER ::= {er1645v2Lan2MC 19}

er1645v2Lan2MCArpSSC OBJECT IDENTIFIER ::= {er1645v2Lan2MCArp 1}

er1645v2Lan2MCArpEntry OBJECT IDENTIFIER ::= {er1645v2Lan2MCArpSSC 1}

er1645v2Lan2MCArpTimeOut OBJECT-TYPE
   SYNTAX      TimeTicks
   MAX-ACCESS  read-write
   STATUS      current
   DESCRIPTION
      "Path: ethernet2.editConf.arp.timeOut

       Time in centi-second."
   ::= {er1645v2Lan2MCArpEntry 201326592}

er1645v2Lan2MCArpProxyArp OBJECT-TYPE
   SYNTAX      INTEGER
               {
               disabled (0),
               enabled (1)
               }
   MAX-ACCESS  read-write
   STATUS      current
   DESCRIPTION
      "Path: ethernet2.editConf.arp.proxyArp

       Possibilities:
               disabled   (0)
               enabled   (1)"
   ::= {er1645v2Lan2MCArpEntry 838860800}

er1645v2Lan2MCArpStaticArp OBJECT-TYPE
   SYNTAX      SEQUENCE OF Er1645v2Lan2MCArpStaticArpEntry
   MAX-ACCESS  not-accessible
   STATUS      current
   DESCRIPTION
      ""
   ::= {er1645v2Lan2MCArp 50331648}

er1645v2Lan2MCArpStaticArpEntry OBJECT-TYPE
   SYNTAX      Er1645v2Lan2MCArpStaticArpEntry
   MAX-ACCESS  not-accessible
   STATUS      current
   DESCRIPTION
      ""
   INDEX      { er1645v2Lan2MCArpStaticArpTableIx }
   ::= {er1645v2Lan2MCArpStaticArp 1}

Er1645v2Lan2MCArpStaticArpEntry ::=
   SEQUENCE
      {
      er1645v2Lan2MCArpStaticArpActions
         VariableLengthTableActions,
      er1645v2Lan2MCArpStaticArpTableIx
         TableIndex,
      er1645v2Lan2MCArpStaticArpMacAddress
         OCTET STRING,
      er1645v2Lan2MCArpStaticArpIpAddress
         IpAddress
      }

er1645v2Lan2MCArpStaticArpActions OBJECT-TYPE
   SYNTAX      VariableLengthTableActions
   MAX-ACCESS  read-write
   STATUS      current
   DESCRIPTION
      "By way of this field, some manipulations
       on this table may be performed."
   ::= {er1645v2Lan2MCArpStaticArpEntry 2}

er1645v2Lan2MCArpStaticArpTableIx OBJECT-TYPE
   SYNTAX      TableIndex
   MAX-ACCESS  not-accessible
   STATUS      current
   DESCRIPTION
      ""
   ::= {er1645v2Lan2MCArpStaticArpEntry 11}

er1645v2Lan2MCArpStaticArpMacAddress OBJECT-TYPE
   SYNTAX      OCTET STRING
   MAX-ACCESS  read-write
   STATUS      current
   DESCRIPTION
      "Path: ethernet2.editConf.arp.staticArp.macAddress

       MAC address."
   ::= {er1645v2Lan2MCArpStaticArpEntry 16777216}

er1645v2Lan2MCArpStaticArpIpAddress OBJECT-TYPE
   SYNTAX      IpAddress
   MAX-ACCESS  read-write
   STATUS      current
   DESCRIPTION
      "Path: ethernet2.editConf.arp.staticArp.ipAddress"
   ::= {er1645v2Lan2MCArpStaticArpEntry 33554432}


er1645v2Lan2MCBrC OBJECT IDENTIFIER ::= {er1645v2Lan2MC 27}

er1645v2Lan2MCBrCSSC OBJECT IDENTIFIER ::= {er1645v2Lan2MCBrC 1}

er1645v2Lan2MCBrCEntry OBJECT IDENTIFIER ::= {er1645v2Lan2MCBrCSSC 1}

er1645v2Lan2MCBrCAccessList OBJECT-TYPE
   SYNTAX      DisplayString
   MAX-ACCESS  read-write
   STATUS      current
   DESCRIPTION
      "Path: ethernet2.editConf.bridging.accessList"
   ::= {er1645v2Lan2MCBrCEntry 83886080}

er1645v2Lan2MCBrCInAccessList OBJECT-TYPE
   SYNTAX      DisplayString
   MAX-ACCESS  read-write
   STATUS      current
   DESCRIPTION
      "Path: ethernet2.editConf.bridging.inAccessList"
   ::= {er1645v2Lan2MCBrCEntry 251658240}

er1645v2Lan2MCBrCTp OBJECT-TYPE
   SYNTAX      DisplayString
   MAX-ACCESS  read-write
   STATUS      current
   DESCRIPTION
      "Path: ethernet2.editConf.bridging.trafficPolicy"
   ::= {er1645v2Lan2MCBrCEntry 100663296}

er1645v2Lan2MCBrCBridgeGroup OBJECT-TYPE
   SYNTAX      DisplayString
   MAX-ACCESS  read-write
   STATUS      current
   DESCRIPTION
      "Path: ethernet2.editConf.bridging.bridgeGroup"
   ::= {er1645v2Lan2MCBrCEntry 117440512}

er1645v2Lan2MCBrCLimBC OBJECT-TYPE
   SYNTAX      INTEGER
               {
               disabled (0),
               enabled (1)
               }
   MAX-ACCESS  read-write
   STATUS      current
   DESCRIPTION
      "Path: ethernet2.editConf.bridging.limitBroadcasts

       Possibilities:
               disabled   (0)
               enabled   (1)"
   ::= {er1645v2Lan2MCBrCEntry 134217728}

er1645v2Lan2MCBrCPrivateMode OBJECT-TYPE
   SYNTAX      INTEGER
               {
               disabled (0),
               enabled (1)
               }
   MAX-ACCESS  read-write
   STATUS      current
   DESCRIPTION
      "Path: ethernet2.editConf.bridging.privateMode

       Possibilities:
               disabled   (0)
               enabled   (1)"
   ::= {er1645v2Lan2MCBrCEntry 419430400}

er1645v2Lan2MCBrCLearning OBJECT-TYPE
   SYNTAX      INTEGER
               {
               disabled (0),
               enabled (1)
               }
   MAX-ACCESS  read-write
   STATUS      current
   DESCRIPTION
      "Path: ethernet2.editConf.bridging.learning

       Possibilities:
               disabled   (0)
               enabled   (1)"
   ::= {er1645v2Lan2MCBrCEntry 201326592}

er1645v2Lan2MCBrCMaxCacheSize OBJECT-TYPE
   SYNTAX      INTEGER
               {
               unlimited (0)
               }
   MAX-ACCESS  read-write
   STATUS      current
   DESCRIPTION
      "Path: ethernet2.editConf.bridging.maxCacheSize

       Possibilities:
               unlimited   (0)"
   ::= {er1645v2Lan2MCBrCEntry 218103808}

er1645v2Lan2MCBrCRelearnDropOnRelearn OBJECT-TYPE
   SYNTAX      INTEGER
               {
               disabled (0),
               enabled (1)
               }
   MAX-ACCESS  read-write
   STATUS      current
   DESCRIPTION
      "Path: ethernet2.editConf.bridging.relearn.dropOnRelearn

       Possibilities:
               disabled   (0)
               enabled   (1)"
   ::= {er1645v2Lan2MCBrCEntry 234946560}

er1645v2Lan2MCBrCRelearnShutdownThreshold OBJECT-TYPE
   SYNTAX      Integer32
   MAX-ACCESS  read-write
   STATUS      current
   DESCRIPTION
      "Path: ethernet2.editConf.bridging.relearn.shutdownThreshold"
   ::= {er1645v2Lan2MCBrCEntry 235012096}

er1645v2Lan2MCBrCRelearnShutdownTime OBJECT-TYPE
   SYNTAX      TimeTicks
   MAX-ACCESS  read-write
   STATUS      current
   DESCRIPTION
      "Path: ethernet2.editConf.bridging.relearn.shutdownTime

       Time in centi-second."
   ::= {er1645v2Lan2MCBrCEntry 235077632}

er1645v2Lan2MCBrCRelearnLoopDetection OBJECT-TYPE
   SYNTAX      INTEGER
               {
               disabled (0),
               passive (1),
               active (2)
               }
   MAX-ACCESS  read-write
   STATUS      current
   DESCRIPTION
      "Path: ethernet2.editConf.bridging.relearn.loopDetection

       Possibilities:
               disabled   (0)
               passive   (1)
               active   (2)"
   ::= {er1645v2Lan2MCBrCEntry 235143168}

er1645v2Lan2MCBrCRelearnLoopDetectionInterval OBJECT-TYPE
   SYNTAX      TimeTicks
   MAX-ACCESS  read-write
   STATUS      current
   DESCRIPTION
      "Path: ethernet2.editConf.bridging.relearn.loopDetectionInterval

       Time in centi-second."
   ::= {er1645v2Lan2MCBrCEntry 235208704}

er1645v2Lan2MCBrCVlanMemberShip OBJECT-TYPE
   SYNTAX      INTEGER
               {
               all (0),
               none (1),
               grouped (2)
               }
   MAX-ACCESS  read-write
   STATUS      current
   DESCRIPTION
      "Path: ethernet2.editConf.bridging.vlanMemberShip

       Possibilities:
               all   (0)
               none   (1)
               grouped   (2)"
   ::= {er1645v2Lan2MCBrCEntry 318767104}

er1645v2Lan2MCBrCDot1adType OBJECT-TYPE
   SYNTAX      INTEGER
               {
               slOPTg (0),
               cPort (4),
               sPort (1),
               nni (2)
               }
   MAX-ACCESS  read-write
   STATUS      current
   DESCRIPTION
      "Path: ethernet2.editConf.bridging.dot1ad.type

       Possibilities:
               <OPT>   (0)
               cPort   (4)
               sPort   (1)
               nni   (2)"
   ::= {er1645v2Lan2MCBrCEntry 503382016}

er1645v2Lan2MCBrCPriority OBJECT-TYPE
   SYNTAX      Integer32
   MAX-ACCESS  read-write
   STATUS      current
   DESCRIPTION
      "Path: ethernet2.editConf.bridging.priority"
   ::= {er1645v2Lan2MCBrCEntry 33554432}

er1645v2Lan2MCBrCPathCost OBJECT-TYPE
   SYNTAX      Integer32
   MAX-ACCESS  read-write
   STATUS      current
   DESCRIPTION
      "Path: ethernet2.editConf.bridging.pathCost"
   ::= {er1645v2Lan2MCBrCEntry 50331648}

er1645v2Lan2MCBrCInternalPathCost OBJECT-TYPE
   SYNTAX      Integer32
   MAX-ACCESS  read-write
   STATUS      current
   DESCRIPTION
      "Path: ethernet2.editConf.bridging.internalPathCost"
   ::= {er1645v2Lan2MCBrCEntry 301989888}

er1645v2Lan2MCBrCTCD OBJECT-TYPE
   SYNTAX      INTEGER
               {
               disabled (0),
               enabled (1)
               }
   MAX-ACCESS  read-write
   STATUS      current
   DESCRIPTION
      "Path: ethernet2.editConf.bridging.topologyChangeDetection

       Possibilities:
               disabled   (0)
               enabled   (1)"
   ::= {er1645v2Lan2MCBrCEntry 67108864}

er1645v2Lan2MCBrCRestrictedRole OBJECT-TYPE
   SYNTAX      INTEGER
               {
               disabled (0),
               enabled (1)
               }
   MAX-ACCESS  read-write
   STATUS      current
   DESCRIPTION
      "Path: ethernet2.editConf.bridging.restrictedRole

       Possibilities:
               disabled   (0)
               enabled   (1)"
   ::= {er1645v2Lan2MCBrCEntry 335544320}

er1645v2Lan2MCBrCAdminEdge OBJECT-TYPE
   SYNTAX      INTEGER
               {
               disabled (0),
               enabled (1)
               }
   MAX-ACCESS  read-write
   STATUS      current
   DESCRIPTION
      "Path: ethernet2.editConf.bridging.adminEdge

       Possibilities:
               disabled   (0)
               enabled   (1)"
   ::= {er1645v2Lan2MCBrCEntry 268435456}

er1645v2Lan2MCBrCMgmtInline OBJECT-TYPE
   SYNTAX      INTEGER
               {
               disabled (0),
               enabled (1)
               }
   MAX-ACCESS  read-write
   STATUS      current
   DESCRIPTION
      "Path: ethernet2.editConf.bridging.mgmtInline

       Possibilities:
               disabled   (0)
               enabled   (1)"
   ::= {er1645v2Lan2MCBrCEntry 369098752}

er1645v2Lan2MCBrCL2ptMode OBJECT-TYPE
   SYNTAX      INTEGER
               {
               disabled (0),
               enabled (1)
               }
   MAX-ACCESS  read-write
   STATUS      current
   DESCRIPTION
      "Path: ethernet2.editConf.bridging.l2ProtTunnel.mode

       Possibilities:
               disabled   (0)
               enabled   (1)"
   ::= {er1645v2Lan2MCBrCEntry 403701760}

er1645v2Lan2MCBrCL2ptProtocols OBJECT-TYPE
   SYNTAX      Integer32
   MAX-ACCESS  read-write
   STATUS      current
   DESCRIPTION
      "Path: ethernet2.editConf.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan2MCBrCEntry 404750336}

er1645v2Lan2MCBrCL2ptDestMac OBJECT-TYPE
   SYNTAX      OCTET STRING
   MAX-ACCESS  read-write
   STATUS      current
   DESCRIPTION
      "Path: ethernet2.editConf.bridging.l2ProtTunnel.destinationMac

       MAC address."
   ::= {er1645v2Lan2MCBrCEntry 405798912}

er1645v2Lan2MCBrCL2ptCos OBJECT-TYPE
   SYNTAX      INTEGER
               {
               unchanged (255)
               }
   MAX-ACCESS  read-write
   STATUS      current
   DESCRIPTION
      "Path: ethernet2.editConf.bridging.l2ProtTunnel.cos

       Possibilities:
               unchanged   (255)"
   ::= {er1645v2Lan2MCBrCEntry 406847488}

er1645v2Lan2MCBrCL2ptDropThrStp OBJECT-TYPE
   SYNTAX      INTEGER
               {
               unlimited (0)
               }
   UNITS       "packets/sec"
   MAX-ACCESS  read-write
   STATUS      current
   DESCRIPTION
      "Path: ethernet2.editConf.bridging.l2ProtTunnel.dropThresholds.stp

       unit name = packets/sec

       Possibilities:
               unlimited   (0)"
   ::= {er1645v2Lan2MCBrCEntry 407900160}

er1645v2Lan2MCBrCL2ptDropThrLldp OBJECT-TYPE
   SYNTAX      INTEGER
               {
               unlimited (0)
               }
   UNITS       "packets/sec"
   MAX-ACCESS  read-write
   STATUS      current
   DESCRIPTION
      "Path: ethernet2.editConf.bridging.l2ProtTunnel.dropThresholds.lldp

       unit name = packets/sec

       Possibilities:
               unlimited   (0)"
   ::= {er1645v2Lan2MCBrCEntry 407904256}

er1645v2Lan2MCBrCL2ptDropThrOam OBJECT-TYPE
   SYNTAX      INTEGER
               {
               unlimited (0)
               }
   UNITS       "packets/sec"
   MAX-ACCESS  read-write
   STATUS      current
   DESCRIPTION
      "Path: ethernet2.editConf.bridging.l2ProtTunnel.dropThresholds.oam

       unit name = packets/sec

       Possibilities:
               unlimited   (0)"
   ::= {er1645v2Lan2MCBrCEntry 407908352}

er1645v2Lan2MCBrCL2ptDropThrCdp OBJECT-TYPE
   SYNTAX      INTEGER
               {
               unlimited (0)
               }
   UNITS       "packets/sec"
   MAX-ACCESS  read-write
   STATUS      current
   DESCRIPTION
      "Path: ethernet2.editConf.bridging.l2ProtTunnel.dropThresholds.cdp

       unit name = packets/sec

       Possibilities:
               unlimited   (0)"
   ::= {er1645v2Lan2MCBrCEntry 407912448}

er1645v2Lan2MCBrCL2ptDropThrVtp OBJECT-TYPE
   SYNTAX      INTEGER
               {
               unlimited (0)
               }
   UNITS       "packets/sec"
   MAX-ACCESS  read-write
   STATUS      current
   DESCRIPTION
      "Path: ethernet2.editConf.bridging.l2ProtTunnel.dropThresholds.vtp

       unit name = packets/sec

       Possibilities:
               unlimited   (0)"
   ::= {er1645v2Lan2MCBrCEntry 407916544}

er1645v2Lan2MCBrCL2ptDropThrLacp OBJECT-TYPE
   SYNTAX      INTEGER
               {
               unlimited (0)
               }
   UNITS       "packets/sec"
   MAX-ACCESS  read-write
   STATUS      current
   DESCRIPTION
      "Path: ethernet2.editConf.bridging.l2ProtTunnel.dropThresholds.lacp

       unit name = packets/sec

       Possibilities:
               unlimited   (0)"
   ::= {er1645v2Lan2MCBrCEntry 407920640}

er1645v2Lan2MCBrCL2ptDropThrEfmOam OBJECT-TYPE
   SYNTAX      INTEGER
               {
               unlimited (0)
               }
   UNITS       "packets/sec"
   MAX-ACCESS  read-write
   STATUS      current
   DESCRIPTION
      "Path: ethernet2.editConf.bridging.l2ProtTunnel.dropThresholds.efmOam

       unit name = packets/sec

       Possibilities:
               unlimited   (0)"
   ::= {er1645v2Lan2MCBrCEntry 407924736}

er1645v2Lan2MCBrCL2ptDropThrPvst OBJECT-TYPE
   SYNTAX      INTEGER
               {
               unlimited (0)
               }
   UNITS       "packets/sec"
   MAX-ACCESS  read-write
   STATUS      current
   DESCRIPTION
      "Path: ethernet2.editConf.bridging.l2ProtTunnel.dropThresholds.pvst

       unit name = packets/sec

       Possibilities:
               unlimited   (0)"
   ::= {er1645v2Lan2MCBrCEntry 407928832}

er1645v2Lan2MCBrCL2ptDropThrMmrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.mmrp

       unit name = packets/sec

       Possibilities:
               unlimited   (0)"
   ::= {er1645v2Lan2MCBrCEntry 407932928}

er1645v2Lan2MCBrCL2ptDropThrMvrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.mvrp

       unit name = packets/sec

       Possibilities:
               unlimited   (0)"
   ::= {er1645v2Lan2MCBrCEntry 407937024}

er1645v2Lan2MCBrCL2ptDropThrGvrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.gvrp

       unit name = packets/sec

       Possibilities:
               unlimited   (0)"
   ::= {er1645v2Lan2MCBrCEntry 407941120}

er1645v2Lan2MCBrCL2ptDropThrGmrp OBJECT-TYPE
   SYNTAX      INTEGER
               {
               unlimited (0)
               }
   UNITS       "packets/sec"
   MAX-ACCESS  read-write
   STATUS      current
   DESCRIPTION
      "Path: ethernet2.editConf.bridging.l2ProtTunnel.dropThresholds.gmrp

       unit name = packets/sec

       Possibilities:
               unlimited   (0)"
   ::= {er1645v2Lan2MCBrCEntry 407945216}

er1645v2Lan2MCBrCL2ptDropThrDtp OBJECT-TYPE
   SYNTAX      INTEGER
               {
               unlimited (0)
               }
   UNITS       "packets/sec"
   MAX-ACCESS  read-write
   STATUS      current
   DESCRIPTION
      "Path: ethernet2.editConf.bridging.l2ProtTunnel.dropThresholds.dtp

       unit name = packets/sec

       Possibilities:
               unlimited   (0)"
   ::= {er1645v2Lan2MCBrCEntry 407949312}

er1645v2Lan2MCBrCL2ptDropThrPagp OBJECT-TYPE
   SYNTAX      INTEGER
               {
               unlimited (0)
               }
   UNITS       "packets/sec"
   MAX-ACCESS  read-write
   STATUS      current
   DESCRIPTION
      "Path: ethernet2.editConf.bridging.l2ProtTunnel.dropThresholds.pagp

       unit name = packets/sec

       Possibilities:
               unlimited   (0)"
   ::= {er1645v2Lan2MCBrCEntry 407953408}

er1645v2Lan2MCBrCL2ptDropThrUdld OBJECT-TYPE
   SYNTAX      INTEGER
               {
               unlimited (0)
               }
   UNITS       "packets/sec"
   MAX-ACCESS  read-write
   STATUS      current
   DESCRIPTION
      "Path: ethernet2.editConf.bridging.l2ProtTunnel.dropThresholds.udld

       unit name = packets/sec

       Possibilities:
               unlimited   (0)"
   ::= {er1645v2Lan2MCBrCEntry 407957504}


er1645v2Lan2MCVlanTagging OBJECT IDENTIFIER ::= {er1645v2Lan2MC 14}

er1645v2Lan2MCVlanTaggingSSC OBJECT IDENTIFIER ::= {er1645v2Lan2MCVlanTagging 1}

er1645v2Lan2MCVlanTaggingEntry OBJECT IDENTIFIER ::= {er1645v2Lan2MCVlanTaggingSSC 1}

er1645v2Lan2MCVlanTaggingUntaggedAction OBJECT-TYPE
   SYNTAX      INTEGER
               {
               discard (0),
               accept (1),
               tag (2)
               }
   MAX-ACCESS  read-write
   STATUS      current
   DESCRIPTION
      "Path: ethernet2.editConf.vlanTagging.untagged.action

       Possibilities:
               discard   (0)
               accept   (1)
               tag   (2)"
   ::= {er1645v2Lan2MCVlanTaggingEntry 671088640}

er1645v2Lan2MCVlanTaggingUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.untagged.tagInfo.tpid

       Possibilities:
               dot1Q   (33024)
               dot1ad   (34984)
               0x9100   (37120)
               0x9200   (37376)
               0x9300   (37632)"
   ::= {er1645v2Lan2MCVlanTaggingEntry 746586112}

er1645v2Lan2MCVlanTaggingUntaggedTagInfoVid OBJECT-TYPE
   SYNTAX      Integer32
   MAX-ACCESS  read-write
   STATUS      current
   DESCRIPTION
      "Path: ethernet2.editConf.vlanTagging.untagged.tagInfo.vid"
   ::= {er1645v2Lan2MCVlanTaggingEntry 754974720}

er1645v2Lan2MCVlanTaggingUnknownVlansAction OBJECT-TYPE
   SYNTAX      INTEGER
               {
               discard (0),
               accept (1),
               tag (2)
               }
   MAX-ACCESS  read-write
   STATUS      current
   DESCRIPTION
      "Path: ethernet2.editConf.vlanTagging.unknownVlans.action

       Possibilities:
               discard   (0)
               accept   (1)
               tag   (2)"
   ::= {er1645v2Lan2MCVlanTaggingEntry 1744830464}

er1645v2Lan2MCVlanTaggingUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.unknownVlans.tagInfo.tpid

       Possibilities:
               dot1Q   (33024)
               dot1ad   (34984)
               0x9100   (37120)
               0x9200   (37376)
               0x9300   (37632)"
   ::= {er1645v2Lan2MCVlanTaggingEntry 1820327936}

er1645v2Lan2MCVlanTaggingUnknownVlansTagInfoVid OBJECT-TYPE
   SYNTAX      Integer32
   MAX-ACCESS  read-write
   STATUS      current
   DESCRIPTION
      "Path: ethernet2.editConf.vlanTagging.unknownVlans.tagInfo.vid"
   ::= {er1645v2Lan2MCVlanTaggingEntry 1828716544}

er1645v2Lan2MCVlanTaggingVlans OBJECT-TYPE
   SYNTAX      SEQUENCE OF Er1645v2Lan2MCVlanTaggingVlansEntry
   MAX-ACCESS  not-accessible
   STATUS      current
   DESCRIPTION
      ""
   ::= {er1645v2Lan2MCVlanTagging 1073741824}

er1645v2Lan2MCVlanTaggingVlansEntry OBJECT-TYPE
   SYNTAX      Er1645v2Lan2MCVlanTaggingVlansEntry
   MAX-ACCESS  not-accessible
   STATUS      current
   DESCRIPTION
      ""
   INDEX      { er1645v2Lan2MCVlanTaggingVlansTableIx }
   ::= {er1645v2Lan2MCVlanTaggingVlans 1}

Er1645v2Lan2MCVlanTaggingVlansEntry ::=
   SEQUENCE
      {
      er1645v2Lan2MCVlanTaggingVlansActions
         VariableLengthTableActions,
      er1645v2Lan2MCVlanTaggingVlansTableIx
         TableIndex,
      er1645v2Lan2MCVlanTaggingVlansVid
         Integer32,
      er1645v2Lan2MCVlanTaggingVlansEndVid
         Integer32,
      er1645v2Lan2MCVlanTaggingVlansAction
         INTEGER,
      er1645v2Lan2MCVlanTaggingVlansTagInfoTpid
         INTEGER,
      er1645v2Lan2MCVlanTaggingVlansTagInfoVid
         Integer32
      }

er1645v2Lan2MCVlanTaggingVlansActions OBJECT-TYPE
   SYNTAX      VariableLengthTableActions
   MAX-ACCESS  read-write
   STATUS      current
   DESCRIPTION
      "By way of this field, some manipulations
       on this table may be performed."
   ::= {er1645v2Lan2MCVlanTaggingVlansEntry 2}

er1645v2Lan2MCVlanTaggingVlansTableIx OBJECT-TYPE
   SYNTAX      TableIndex
   MAX-ACCESS  not-accessible
   STATUS      current
   DESCRIPTION
      ""
   ::= {er1645v2Lan2MCVlanTaggingVlansEntry 11}

er1645v2Lan2MCVlanTaggingVlansVid OBJECT-TYPE
   SYNTAX      Integer32
   MAX-ACCESS  read-write
   STATUS      current
   DESCRIPTION
      "Path: ethernet2.editConf.vlanTagging.vlans.vid"
   ::= {er1645v2Lan2MCVlanTaggingVlansEntry 536870912}

er1645v2Lan2MCVlanTaggingVlansEndVid OBJECT-TYPE
   SYNTAX      Integer32
   MAX-ACCESS  read-write
   STATUS      current
   DESCRIPTION
      "Path: ethernet2.editConf.vlanTagging.vlans.endVid"
   ::= {er1645v2Lan2MCVlanTaggingVlansEntry 2147483648}

er1645v2Lan2MCVlanTaggingVlansAction OBJECT-TYPE
   SYNTAX      INTEGER
               {
               discard (0),
               accept (1),
               tag (2)
               }
   MAX-ACCESS  read-write
   STATUS      current
   DESCRIPTION
      "Path: ethernet2.editConf.vlanTagging.vlans.action

       Possibilities:
               discard   (0)
               accept   (1)
               tag   (2)"
   ::= {er1645v2Lan2MCVlanTaggingVlansEntry 1073741824}

er1645v2Lan2MCVlanTaggingVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlanTagging.vlans.tagInfo.tpid

       Possibilities:
               dot1Q   (33024)
               dot1ad   (34984)
               0x9100   (37120)
               0x9200   (37376)
               0x9300   (37632)"
   ::= {er1645v2Lan2MCVlanTaggingVlansEntry 1677721600}

er1645v2Lan2MCVlanTaggingVlansTagInfoVid OBJECT-TYPE
   SYNTAX      Integer32
   MAX-ACCESS  read-write
   STATUS      current
   DESCRIPTION
      "Path: ethernet2.editConf.vlanTagging.vlans.tagInfo.vid"
   ::= {er1645v2Lan2MCVlanTaggingVlansEntry 1744830464}


er1645v2Lan2MCOam OBJECT IDENTIFIER ::= {er1645v2Lan2MC 900}

er1645v2Lan2MCOamSSC OBJECT IDENTIFIER ::= {er1645v2Lan2MCOam 1}

er1645v2Lan2MCOamEntry OBJECT IDENTIFIER ::= {er1645v2Lan2MCOamSSC 1}

er1645v2Lan2MCOamMode OBJECT-TYPE
   SYNTAX      INTEGER
               {
               disabled (0),
               passive (3),
               active (2)
               }
   MAX-ACCESS  read-write
   STATUS      current
   DESCRIPTION
      "Path: ethernet2.editConf.oam.mode

       Possibilities:
               disabled   (0)
               passive   (3)
               active   (2)"
   ::= {er1645v2Lan2MCOamEntry 16777216}

er1645v2Lan2MCOamLpbkLocalParAction OBJECT-TYPE
   SYNTAX      INTEGER
               {
               discard (0),
               forward (1)
               }
   MAX-ACCESS  read-write
   STATUS      current
   DESCRIPTION
      "Path: ethernet2.editConf.oam.loopbackLocalParserAction

       Possibilities:
               discard   (0)
               forward   (1)"
   ::= {er1645v2Lan2MCOamEntry 33554432}

er1645v2Lan2MCOamLpbkSwapMacAddr OBJECT-TYPE
   SYNTAX      INTEGER
               {
               disabled (0),
               enabled (1)
               }
   MAX-ACCESS  read-write
   STATUS      current
   DESCRIPTION
      "Path: ethernet2.editConf.oam.loopbackSwapMacAddresses

       Possibilities:
               disabled   (0)
               enabled   (1)"
   ::= {er1645v2Lan2MCOamEntry 50331648}

er1645v2Lan2MCOamLoopbackIgnoreRx OBJECT-TYPE
   SYNTAX      INTEGER
               {
               no (0),
               yes (1)
               }
   MAX-ACCESS  read-write
   STATUS      current
   DESCRIPTION
      "Path: ethernet2.editConf.oam.loopbackIgnoreRx

       Possibilities:
               no   (0)
               yes   (1)"
   ::= {er1645v2Lan2MCOamEntry 67108864}

er1645v2Lan2MCOamEventsErroredSymbolEnabled OBJECT-TYPE
   SYNTAX      INTEGER
               {
               no (0),
               yes (1)
               }
   MAX-ACCESS  read-write
   STATUS      current
   DESCRIPTION
      "Path: ethernet2.editConf.oam.events.erroredSymbol.enabled

       Possibilities:
               no   (0)
               yes   (1)"
   ::= {er1645v2Lan2MCOamEntry 83951872}

er1645v2Lan2MCOamEventsErroredSymbolWindowHi OBJECT-TYPE
   SYNTAX      INTEGER
               {
               default (0)
               }
   UNITS       "symbols"
   MAX-ACCESS  read-write
   STATUS      current
   DESCRIPTION
      "Path: ethernet2.editConf.oam.events.erroredSymbol.windowHi

       unit name = symbols

       Possibilities:
               default   (0)"
   ::= {er1645v2Lan2MCOamEntry 83952128}

er1645v2Lan2MCOamEventsErroredSymbolWindowLo OBJECT-TYPE
   SYNTAX      INTEGER
               {
               default (0)
               }
   UNITS       "symbols"
   MAX-ACCESS  read-write
   STATUS      current
   DESCRIPTION
      "Path: ethernet2.editConf.oam.events.erroredSymbol.windowLo

       unit name = symbols

       Possibilities:
               default   (0)"
   ::= {er1645v2Lan2MCOamEntry 83952384}

er1645v2Lan2MCOamEventsErroredSymbolThresholdHi OBJECT-TYPE
   SYNTAX      Integer32
   UNITS       "symbols"
   MAX-ACCESS  read-write
   STATUS      current
   DESCRIPTION
      "Path: ethernet2.editConf.oam.events.erroredSymbol.thresholdHi

       unit name = symbols"
   ::= {er1645v2Lan2MCOamEntry 83952640}

er1645v2Lan2MCOamEventsErroredSymbolThresholdLo OBJECT-TYPE
   SYNTAX      Integer32
   UNITS       "symbols"
   MAX-ACCESS  read-write
   STATUS      current
   DESCRIPTION
      "Path: ethernet2.editConf.oam.events.erroredSymbol.thresholdLo

       unit name = symbols"
   ::= {er1645v2Lan2MCOamEntry 83952896}

er1645v2Lan2MCOamEventsErroredFramePeriodEnabled OBJECT-TYPE
   SYNTAX      INTEGER
               {
               no (0),
               yes (1)
               }
   MAX-ACCESS  read-write
   STATUS      current
   DESCRIPTION
      "Path: ethernet2.editConf.oam.events.erroredFramePeriod.enabled

       Possibilities:
               no   (0)
               yes   (1)"
   ::= {er1645v2Lan2MCOamEntry 84017408}

er1645v2Lan2MCOamEventsErroredFramePeriodWindow OBJECT-TYPE
   SYNTAX      INTEGER
               {
               default (0)
               }
   UNITS       "frames"
   MAX-ACCESS  read-write
   STATUS      current
   DESCRIPTION
      "Path: ethernet2.editConf.oam.events.erroredFramePeriod.window

       unit name = frames

       Possibilities:
               default   (0)"
   ::= {er1645v2Lan2MCOamEntry 84017664}

er1645v2Lan2MCOamEventsErroredFramePeriodThreshold OBJECT-TYPE
   SYNTAX      Integer32
   UNITS       "frames"
   MAX-ACCESS  read-write
   STATUS      current
   DESCRIPTION
      "Path: ethernet2.editConf.oam.events.erroredFramePeriod.threshold

       unit name = frames"
   ::= {er1645v2Lan2MCOamEntry 84017920}

er1645v2Lan2MCOamEventsErroredFrameEnabled OBJECT-TYPE
   SYNTAX      INTEGER
               {
               no (0),
               yes (1)
               }
   MAX-ACCESS  read-write
   STATUS      current
   DESCRIPTION
      "Path: ethernet2.editConf.oam.events.erroredFrame.enabled

       Possibilities:
               no   (0)
               yes   (1)"
   ::= {er1645v2Lan2MCOamEntry 84082944}

er1645v2Lan2MCOamEventsErroredFrameWindow OBJECT-TYPE
   SYNTAX      Integer32
   UNITS       "100msec"
   MAX-ACCESS  read-write
   STATUS      current
   DESCRIPTION
      "Path: ethernet2.editConf.oam.events.erroredFrame.window

       unit name = 100msec"
   ::= {er1645v2Lan2MCOamEntry 84083200}

er1645v2Lan2MCOamEventsErroredFrameThreshold OBJECT-TYPE
   SYNTAX      Integer32
   UNITS       "frames"
   MAX-ACCESS  read-write
   STATUS      current
   DESCRIPTION
      "Path: ethernet2.editConf.oam.events.erroredFrame.threshold

       unit name = frames"
   ::= {er1645v2Lan2MCOamEntry 84083456}

er1645v2Lan2MCOamEventsErroredFrameSecondsEnabled OBJECT-TYPE
   SYNTAX      INTEGER
               {
               no (0),
               yes (1)
               }
   MAX-ACCESS  read-write
   STATUS      current
   DESCRIPTION
      "Path: ethernet2.editConf.oam.events.erroredFrameSeconds.enabled

       Possibilities:
               no   (0)
               yes   (1)"
   ::= {er1645v2Lan2MCOamEntry 84148480}

er1645v2Lan2MCOamEventsErroredFrameSecondsWindow OBJECT-TYPE
   SYNTAX      Integer32
   UNITS       "100msec"
   MAX-ACCESS  read-write
   STATUS      current
   DESCRIPTION
      "Path: ethernet2.editConf.oam.events.erroredFrameSeconds.window

       unit name = 100msec"
   ::= {er1645v2Lan2MCOamEntry 84148736}

er1645v2Lan2MCOamEventsErroredFrameSecondsThreshold OBJECT-TYPE
   SYNTAX      Integer32
   UNITS       "frames"
   MAX-ACCESS  read-write
   STATUS      current
   DESCRIPTION
      "Path: ethernet2.editConf.oam.events.erroredFrameSeconds.threshold

       unit name = frames"
   ::= {er1645v2Lan2MCOamEntry 84148992}

er1645v2Lan2MCOamEventsDyingGasp OBJECT-TYPE
   SYNTAX      INTEGER
               {
               disabled (0),
               enabled (1)
               }
   MAX-ACCESS  read-write
   STATUS      current
   DESCRIPTION
      "Path: ethernet2.editConf.oam.events.dyingGasp

       Possibilities:
               disabled   (0)
               enabled   (1)"
   ::= {er1645v2Lan2MCOamEntry 84213760}

er1645v2Lan2MCOamEventsCriticalEvent OBJECT-TYPE
   SYNTAX      INTEGER
               {
               disabled (0),
               enabled (1)
               }
   MAX-ACCESS  read-write
   STATUS      current
   DESCRIPTION
      "Path: ethernet2.editConf.oam.events.criticalEvent

       Possibilities:
               disabled   (0)
               enabled   (1)"
   ::= {er1645v2Lan2MCOamEntry 84279296}


er1645v2Lan2MCLst OBJECT IDENTIFIER ::= {er1645v2Lan2MC 12}

er1645v2Lan2MCLstSSC OBJECT IDENTIFIER ::= {er1645v2Lan2MCLst 1}

er1645v2Lan2MCLstEntry OBJECT IDENTIFIER ::= {er1645v2Lan2MCLstSSC 1}

er1645v2Lan2MCLstTrackedInterface OBJECT-TYPE
   SYNTAX      DisplayString
   MAX-ACCESS  read-write
   STATUS      current
   DESCRIPTION
      "Path: ethernet2.editConf.linkStateTracking.trackedInterface"
   ::= {er1645v2Lan2MCLstEntry 16777216}


er1645v2Lan2MCDot1x OBJECT IDENTIFIER ::= {er1645v2Lan2MC 191}

er1645v2Lan2MCDot1xSSC OBJECT IDENTIFIER ::= {er1645v2Lan2MCDot1x 1}

er1645v2Lan2MCDot1xEntry OBJECT IDENTIFIER ::= {er1645v2Lan2MCDot1xSSC 1}

er1645v2Lan2MCDot1xMode OBJECT-TYPE
   SYNTAX      INTEGER
               {
               inactive (0),
               auto (1)
               }
   MAX-ACCESS  read-write
   STATUS      current
   DESCRIPTION
      "Path: ethernet2.editConf.dot1x.mode

       Possibilities:
               inactive   (0)
               auto   (1)"
   ::= {er1645v2Lan2MCDot1xEntry 16777216}

er1645v2Lan2MCDot1xMaxHosts OBJECT-TYPE
   SYNTAX      Integer32
   MAX-ACCESS  read-write
   STATUS      current
   DESCRIPTION
      "Path: ethernet2.editConf.dot1x.maxHosts"
   ::= {er1645v2Lan2MCDot1xEntry 33554432}

er1645v2Lan2MCDot1xReAuthentication OBJECT-TYPE
   SYNTAX      INTEGER
               {
               disabled (0),
               enabled (1)
               }
   MAX-ACCESS  read-write
   STATUS      current
   DESCRIPTION
      "Path: ethernet2.editConf.dot1x.reAuthentication

       Possibilities:
               disabled   (0)
               enabled   (1)"
   ::= {er1645v2Lan2MCDot1xEntry 50331648}

er1645v2Lan2MCDot1xReAuthPeriod OBJECT-TYPE
   SYNTAX      TimeTicks
   MAX-ACCESS  read-write
   STATUS      current
   DESCRIPTION
      "Path: ethernet2.editConf.dot1x.reAuthPeriod

       Time in centi-second."
   ::= {er1645v2Lan2MCDot1xEntry 67108864}

er1645v2Lan2MCDot1xQuietPeriod OBJECT-TYPE
   SYNTAX      TimeTicks
   MAX-ACCESS  read-write
   STATUS      current
   DESCRIPTION
      "Path: ethernet2.editConf.dot1x.quietPeriod

       Time in centi-second."
   ::= {er1645v2Lan2MCDot1xEntry 83886080}

er1645v2Lan2MCDot1xSupplTimeout OBJECT-TYPE
   SYNTAX      TimeTicks
   MAX-ACCESS  read-write
   STATUS      current
   DESCRIPTION
      "Path: ethernet2.editConf.dot1x.supplTimeout

       Time in centi-second."
   ::= {er1645v2Lan2MCDot1xEntry 100663296}

er1645v2Lan2MCDot1xServerTimeout OBJECT-TYPE
   SYNTAX      TimeTicks
   MAX-ACCESS  read-write
   STATUS      current
   DESCRIPTION
      "Path: ethernet2.editConf.dot1x.serverTimeout

       Time in centi-second."
   ::= {er1645v2Lan2MCDot1xEntry 117440512}

er1645v2Lan2MCDot1xMaxReqCount OBJECT-TYPE
   SYNTAX      Integer32
   MAX-ACCESS  read-write
   STATUS      current
   DESCRIPTION
      "Path: ethernet2.editConf.dot1x.maxReqCount"
   ::= {er1645v2Lan2MCDot1xEntry 134217728}


er1645v2Lan2MCMode OBJECT-TYPE
   SYNTAX      INTEGER
               {
               bridging (0),
               routing (1),
               routingAndBridging (2),
               ipV6 (3),
               ipV6ipV4 (4),
               multilink (5)
               }
   MAX-ACCESS  read-write
   STATUS      current
   DESCRIPTION
      "Path: ethernet2.editConf.mode
       Info: routing and/or bridging or ipV6 or multilink selection

       Possibilities:
               bridging   (0)
               routing   (1)
               routingAndBridging   (2)
               ipV6   (3)
               ipV6/ipV4   (4)
               multilink   (5)"
   ::= {er1645v2Lan2MC 29}


er1645v2Lan2MCIpV6 OBJECT IDENTIFIER ::= {er1645v2Lan2MC 15}

er1645v2Lan2MCIpV6SSC OBJECT IDENTIFIER ::= {er1645v2Lan2MCIpV6 1}

er1645v2Lan2MCIpV6Entry OBJECT IDENTIFIER ::= {er1645v2Lan2MCIpV6SSC 1}

er1645v2Lan2MCIpV6VrfRouter OBJECT-TYPE
   SYNTAX      DisplayString
   MAX-ACCESS  read-write
   STATUS      current
   DESCRIPTION
      "Path: ethernet2.editConf.ipV6.vrfRouter"
   ::= {er1645v2Lan2MCIpV6Entry 16777216}

er1645v2Lan2MCIpV6AddrAutoConfigNrDupAddrDetects OBJECT-TYPE
   SYNTAX      Integer32
   MAX-ACCESS  read-write
   STATUS      current
   DESCRIPTION
      "Path: ethernet2.editConf.ipV6.addrAutoConfig.nrDupAddrDetects"
   ::= {er1645v2Lan2MCIpV6Entry 67174400}

er1645v2Lan2MCIpV6AddrAutoConfigAcceptRa OBJECT-TYPE
   SYNTAX      INTEGER
               {
               disabled (0),
               enabled (1)
               }
   MAX-ACCESS  read-write
   STATUS      current
   DESCRIPTION
      "Path: ethernet2.editConf.ipV6.addrAutoConfig.acceptRa

       Possibilities:
               disabled   (0)
               enabled   (1)"
   ::= {er1645v2Lan2MCIpV6Entry 67239936}

er1645v2Lan2MCIpV6AddrAutoConfigAcceptRaRdnss OBJECT-TYPE
   SYNTAX      INTEGER
               {
               disabled (0),
               enabled (1)
               }
   MAX-ACCESS  read-write
   STATUS      current
   DESCRIPTION
      "Path: ethernet2.editConf.ipV6.addrAutoConfig.acceptRaRdnss

       Possibilities:
               disabled   (0)
               enabled   (1)"
   ::= {er1645v2Lan2MCIpV6Entry 67305472}

er1645v2Lan2MCIpV6AddrAutoConfigAcceptRaDnssl OBJECT-TYPE
   SYNTAX      INTEGER
               {
               disabled (0),
               enabled (1)
               }
   MAX-ACCESS  read-write
   STATUS      current
   DESCRIPTION
      "Path: ethernet2.editConf.ipV6.addrAutoConfig.acceptRaDnssl

       Possibilities:
               disabled   (0)
               enabled   (1)"
   ::= {er1645v2Lan2MCIpV6Entry 67371008}

er1645v2Lan2MCIpV6DefaultRoute OBJECT-TYPE
   SYNTAX      INTEGER
               {
               disabled (0),
               enabled (1)
               }
   MAX-ACCESS  read-write
   STATUS      current
   DESCRIPTION
      "Path: ethernet2.editConf.ipV6.defaultRoute

       Possibilities:
               disabled   (0)
               enabled   (1)"
   ::= {er1645v2Lan2MCIpV6Entry 83886080}

er1645v2Lan2MCIpV6RaSend OBJECT-TYPE
   SYNTAX      INTEGER
               {
               disabled (0),
               enabled (1)
               }
   MAX-ACCESS  read-write
   STATUS      current
   DESCRIPTION
      "Path: ethernet2.editConf.ipV6.ra.send

       Possibilities:
               disabled   (0)
               enabled   (1)"
   ::= {er1645v2Lan2MCIpV6Entry 100728832}

er1645v2Lan2MCIpV6RaMinInterval OBJECT-TYPE
   SYNTAX      TimeTicks
   MAX-ACCESS  read-write
   STATUS      current
   DESCRIPTION
      "Path: ethernet2.editConf.ipV6.ra.minInterval

       Time in centi-second."
   ::= {er1645v2Lan2MCIpV6Entry 100794368}

er1645v2Lan2MCIpV6RaMaxInterval OBJECT-TYPE
   SYNTAX      TimeTicks
   MAX-ACCESS  read-write
   STATUS      current
   DESCRIPTION
      "Path: ethernet2.editConf.ipV6.ra.maxInterval

       Time in centi-second."
   ::= {er1645v2Lan2MCIpV6Entry 100859904}

er1645v2Lan2MCIpV6RaManagedFlag OBJECT-TYPE
   SYNTAX      INTEGER
               {
               disabled (0),
               enabled (1)
               }
   MAX-ACCESS  read-write
   STATUS      current
   DESCRIPTION
      "Path: ethernet2.editConf.ipV6.ra.managedFlag

       Possibilities:
               disabled   (0)
               enabled   (1)"
   ::= {er1645v2Lan2MCIpV6Entry 100925440}

er1645v2Lan2MCIpV6RaOtherConfFlag OBJECT-TYPE
   SYNTAX      INTEGER
               {
               disabled (0),
               enabled (1)
               }
   MAX-ACCESS  read-write
   STATUS      current
   DESCRIPTION
      "Path: ethernet2.editConf.ipV6.ra.otherConfFlag

       Possibilities:
               disabled   (0)
               enabled   (1)"
   ::= {er1645v2Lan2MCIpV6Entry 100990976}

er1645v2Lan2MCIpV6RaLinkMtu OBJECT-TYPE
   SYNTAX      Integer32
   MAX-ACCESS  read-write
   STATUS      current
   DESCRIPTION
      "Path: ethernet2.editConf.ipV6.ra.linkMtu"
   ::= {er1645v2Lan2MCIpV6Entry 101056512}

er1645v2Lan2MCIpV6RaReachableTime OBJECT-TYPE
   SYNTAX      TimeTicks
   MAX-ACCESS  read-write
   STATUS      current
   DESCRIPTION
      "Path: ethernet2.editConf.ipV6.ra.reachableTime

       Time in centi-second."
   ::= {er1645v2Lan2MCIpV6Entry 101122048}

er1645v2Lan2MCIpV6RaRetransmitTime OBJECT-TYPE
   SYNTAX      TimeTicks
   MAX-ACCESS  read-write
   STATUS      current
   DESCRIPTION
      "Path: ethernet2.editConf.ipV6.ra.retransmitTime

       Time in centi-second."
   ::= {er1645v2Lan2MCIpV6Entry 101187584}

er1645v2Lan2MCIpV6RaHopLimit OBJECT-TYPE
   SYNTAX      Integer32
   MAX-ACCESS  read-write
   STATUS      current
   DESCRIPTION
      "Path: ethernet2.editConf.ipV6.ra.hopLimit"
   ::= {er1645v2Lan2MCIpV6Entry 101253120}

er1645v2Lan2MCIpV6RaDefaultLifeTime OBJECT-TYPE
   SYNTAX      TimeTicks
   MAX-ACCESS  read-write
   STATUS      current
   DESCRIPTION
      "Path: ethernet2.editConf.ipV6.ra.defaultLifeTime

       Time in centi-second."
   ::= {er1645v2Lan2MCIpV6Entry 101318656}

er1645v2Lan2MCIpV6RaDnsOptionsRdnssLifeTime OBJECT-TYPE
   SYNTAX      TimeTicks
   MAX-ACCESS  read-write
   STATUS      current
   DESCRIPTION
      "Path: ethernet2.editConf.ipV6.ra.dnsOptions.rdnss.lifeTime

       Time in centi-second."
   ::= {er1645v2Lan2MCIpV6Entry 101393408}

er1645v2Lan2MCIpV6RaDnsOptionsRdnssImportServers OBJECT-TYPE
   SYNTAX      INTEGER
               {
               disabled (0),
               enabled (1)
               }
   MAX-ACCESS  read-write
   STATUS      current
   DESCRIPTION
      "Path: ethernet2.editConf.ipV6.ra.dnsOptions.rdnss.importServers

       Possibilities:
               disabled   (0)
               enabled   (1)"
   ::= {er1645v2Lan2MCIpV6Entry 101395456}

er1645v2Lan2MCIpV6RaDnsOptionsDnsslLifeTime OBJECT-TYPE
   SYNTAX      TimeTicks
   MAX-ACCESS  read-write
   STATUS      current
   DESCRIPTION
      "Path: ethernet2.editConf.ipV6.ra.dnsOptions.dnssl.lifeTime

       Time in centi-second."
   ::= {er1645v2Lan2MCIpV6Entry 101401600}

er1645v2Lan2MCIpV6RaDnsOptionsDnsslImportDomains OBJECT-TYPE
   SYNTAX      INTEGER
               {
               disabled (0),
               enabled (1)
               }
   MAX-ACCESS  read-write
   STATUS      current
   DESCRIPTION
      "Path: ethernet2.editConf.ipV6.ra.dnsOptions.dnssl.importDomains

       Possibilities:
               disabled   (0)
               enabled   (1)"
   ::= {er1645v2Lan2MCIpV6Entry 101403648}

er1645v2Lan2MCIpV6RsSend OBJECT-TYPE
   SYNTAX      INTEGER
               {
               disabled (0),
               enabled (1)
               }
   MAX-ACCESS  read-write
   STATUS      current
   DESCRIPTION
      "Path: ethernet2.editConf.ipV6.rs.send

       Possibilities:
               disabled   (0)
               enabled   (1)"
   ::= {er1645v2Lan2MCIpV6Entry 335609856}

er1645v2Lan2MCIpV6RsMaxRandomDelay OBJECT-TYPE
   SYNTAX      TimeTicks
   MAX-ACCESS  read-write
   STATUS      current
   DESCRIPTION
      "Path: ethernet2.editConf.ipV6.rs.maxRandomDelay

       Time in centi-second."
   ::= {er1645v2Lan2MCIpV6Entry 335675392}

er1645v2Lan2MCIpV6RsInterval OBJECT-TYPE
   SYNTAX      TimeTicks
   MAX-ACCESS  read-write
   STATUS      current
   DESCRIPTION
      "Path: ethernet2.editConf.ipV6.rs.interval

       Time in centi-second."
   ::= {er1645v2Lan2MCIpV6Entry 335740928}

er1645v2Lan2MCIpV6RsMaxSolicitations OBJECT-TYPE
   SYNTAX      Integer32
   MAX-ACCESS  read-write
   STATUS      current
   DESCRIPTION
      "Path: ethernet2.editConf.ipV6.rs.maxSolicitations"
   ::= {er1645v2Lan2MCIpV6Entry 335806464}

er1645v2Lan2MCIpV6TrafficPolicyInbound OBJECT-TYPE
   SYNTAX      DisplayString
   MAX-ACCESS  read-write
   STATUS      current
   DESCRIPTION
      "Path: ethernet2.editConf.ipV6.trafficPolicy.inbound"
   ::= {er1645v2Lan2MCIpV6Entry 184614912}

er1645v2Lan2MCIpV6TrafficPolicyOutbound OBJECT-TYPE
   SYNTAX      DisplayString
   MAX-ACCESS  read-write
   STATUS      current
   DESCRIPTION
      "Path: ethernet2.editConf.ipV6.trafficPolicy.outbound"
   ::= {er1645v2Lan2MCIpV6Entry 184680448}

er1645v2Lan2MCIpV6FirewallZone OBJECT-TYPE
   SYNTAX      DisplayString
   MAX-ACCESS  read-write
   STATUS      current
   DESCRIPTION
      "Path: ethernet2.editConf.ipV6.firewall.zone"
   ::= {er1645v2Lan2MCIpV6Entry 201392128}

er1645v2Lan2MCIpV6DhcpClientAddrAC OBJECT-TYPE
   SYNTAX      INTEGER
               {
               disabled (0),
               enabled (1)
               }
   MAX-ACCESS  read-write
   STATUS      current
   DESCRIPTION
      "Path: ethernet2.editConf.ipV6.dhcp.client.addrAutoConfig

       Possibilities:
               disabled   (0)
               enabled   (1)"
   ::= {er1645v2Lan2MCIpV6Entry 170131456}

er1645v2Lan2MCIpV6DhcpClientPrDelMode OBJECT-TYPE
   SYNTAX      INTEGER
               {
               disabled (0),
               enabled (1)
               }
   MAX-ACCESS  read-write
   STATUS      current
   DESCRIPTION
      "Path: ethernet2.editConf.ipV6.dhcp.client.pd.mode

       Possibilities:
               disabled   (0)
               enabled   (1)"
   ::= {er1645v2Lan2MCIpV6Entry 170394624}

er1645v2Lan2MCIpV6DhcpClientPrDelPool OBJECT-TYPE
   SYNTAX      DisplayString
   MAX-ACCESS  read-write
   STATUS      current
   DESCRIPTION
      "Path: ethernet2.editConf.ipV6.dhcp.client.pd.pool"
   ::= {er1645v2Lan2MCIpV6Entry 170395648}

er1645v2Lan2MCIpV6DhcpClientPrDelPdExclOpt OBJECT-TYPE
   SYNTAX      INTEGER
               {
               disabled (0),
               enabled (1)
               }
   MAX-ACCESS  read-write
   STATUS      current
   DESCRIPTION
      "Path: ethernet2.editConf.ipV6.dhcp.client.pd.pdExclOpt

       Possibilities:
               disabled   (0)
               enabled   (1)"
   ::= {er1645v2Lan2MCIpV6Entry 170396672}

er1645v2Lan2MCIpV6DhcpClientDnsServerPref OBJECT-TYPE
   SYNTAX      Integer32
   MAX-ACCESS  read-write
   STATUS      current
   DESCRIPTION
      "Path: ethernet2.editConf.ipV6.dhcp.client.dns.serverPref"
   ::= {er1645v2Lan2MCIpV6Entry 170918912}

er1645v2Lan2MCIpV6DhcpClientRapidCommit OBJECT-TYPE
   SYNTAX      INTEGER
               {
               disabled (0),
               enabled (1)
               }
   MAX-ACCESS  read-write
   STATUS      current
   DESCRIPTION
      "Path: ethernet2.editConf.ipV6.dhcp.client.rapidCommit

       Possibilities:
               disabled   (0)
               enabled   (1)"
   ::= {er1645v2Lan2MCIpV6Entry 170655744}

er1645v2Lan2MCIpV6DhcpClientTimersSolTimeOut OBJECT-TYPE
   SYNTAX      TimeTicks
   MAX-ACCESS  read-write
   STATUS      current
   DESCRIPTION
      "Path: ethernet2.editConf.ipV6.dhcp.client.timers.solTimeOut

       Time in centi-second."
   ::= {er1645v2Lan2MCIpV6Entry 171181056}

er1645v2Lan2MCIpV6DhcpClientTimersSolMaxRt OBJECT-TYPE
   SYNTAX      TimeTicks
   MAX-ACCESS  read-write
   STATUS      current
   DESCRIPTION
      "Path: ethernet2.editConf.ipV6.dhcp.client.timers.solMaxRt

       Time in centi-second."
   ::= {er1645v2Lan2MCIpV6Entry 171182080}

er1645v2Lan2MCIpV6DhcpClientTimersInfoRefresh OBJECT-TYPE
   SYNTAX      TimeTicks
   MAX-ACCESS  read-write
   STATUS      current
   DESCRIPTION
      "Path: ethernet2.editConf.ipV6.dhcp.client.timers.infoRefresh

       Time in centi-second."
   ::= {er1645v2Lan2MCIpV6Entry 171183104}

er1645v2Lan2MCIpV6DhcpServerMode OBJECT-TYPE
   SYNTAX      INTEGER
               {
               disabled (0),
               enabled (1)
               }
   MAX-ACCESS  read-write
   STATUS      current
   DESCRIPTION
      "Path: ethernet2.editConf.ipV6.dhcp.server.mode

       Possibilities:
               disabled   (0)
               enabled   (1)"
   ::= {er1645v2Lan2MCIpV6Entry 172228608}

er1645v2Lan2MCIpV6DhcpServerPreference OBJECT-TYPE
   SYNTAX      Integer32
   MAX-ACCESS  read-write
   STATUS      current
   DESCRIPTION
      "Path: ethernet2.editConf.ipV6.dhcp.server.preference"
   ::= {er1645v2Lan2MCIpV6Entry 172490752}

er1645v2Lan2MCIpV6DhcpServerPool OBJECT-TYPE
   SYNTAX      DisplayString
   MAX-ACCESS  read-write
   STATUS      current
   DESCRIPTION
      "Path: ethernet2.editConf.ipV6.dhcp.server.pool"
   ::= {er1645v2Lan2MCIpV6Entry 172752896}

er1645v2Lan2MCIpV6DhcpServerRapidCommit OBJECT-TYPE
   SYNTAX      INTEGER
               {
               disabled (0),
               enabled (1)
               }
   MAX-ACCESS  read-write
   STATUS      current
   DESCRIPTION
      "Path: ethernet2.editConf.ipV6.dhcp.server.rapidCommit

       Possibilities:
               disabled   (0)
               enabled   (1)"
   ::= {er1645v2Lan2MCIpV6Entry 173015040}

er1645v2Lan2MCIpV6DhcpServerTimersInfoRefresh OBJECT-TYPE
   SYNTAX      TimeTicks
   MAX-ACCESS  read-write
   STATUS      current
   DESCRIPTION
      "Path: ethernet2.editConf.ipV6.dhcp.server.timers.infoRefresh

       Time in centi-second."
   ::= {er1645v2Lan2MCIpV6Entry 173278208}

er1645v2Lan2MCIpV6DhcpRelayMode OBJECT-TYPE
   SYNTAX      INTEGER
               {
               disabled (0),
               enabled (1)
               }
   MAX-ACCESS  read-write
   STATUS      current
   DESCRIPTION
      "Path: ethernet2.editConf.ipV6.dhcp.relay.mode

       Possibilities:
               disabled   (0)
               enabled   (1)"
   ::= {er1645v2Lan2MCIpV6Entry 174071808}

er1645v2Lan2MCIpV6SendRedirect OBJECT-TYPE
   SYNTAX      INTEGER
               {
               disabled (0),
               enabled (1)
               }
   MAX-ACCESS  read-write
   STATUS      current
   DESCRIPTION
      "Path: ethernet2.editConf.ipV6.sendRedirect

       Possibilities:
               disabled   (0)
               enabled   (1)"
   ::= {er1645v2Lan2MCIpV6Entry 117440512}

er1645v2Lan2MCIpV6LinkMtu OBJECT-TYPE
   SYNTAX      Integer32
   MAX-ACCESS  read-write
   STATUS      current
   DESCRIPTION
      "Path: ethernet2.editConf.ipV6.linkMtu"
   ::= {er1645v2Lan2MCIpV6Entry 134217728}

er1645v2Lan2MCIpV6InterfaceId OBJECT-TYPE
   SYNTAX      OCTET STRING
   MAX-ACCESS  read-write
   STATUS      current
   DESCRIPTION
      "Path: ethernet2.editConf.ipV6.interfaceId"
   ::= {er1645v2Lan2MCIpV6Entry 150994944}

er1645v2Lan2MCIpV6MF OBJECT-TYPE
   SYNTAX      Integer32
   MAX-ACCESS  read-write
   STATUS      current
   DESCRIPTION
      "Path: ethernet2.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2MCIpV6Entry 285212672}

er1645v2Lan2MCIpV6IcmpMessagesNoRoute OBJECT-TYPE
   SYNTAX      INTEGER
               {
               disabled (0),
               enabled (1)
               }
   MAX-ACCESS  read-write
   STATUS      current
   DESCRIPTION
      "Path: ethernet2.editConf.ipV6.icmpMessages.noRoute

       Possibilities:
               disabled   (0)
               enabled   (1)"
   ::= {er1645v2Lan2MCIpV6Entry 302055424}

er1645v2Lan2MCIpV6IcmpMessagesBeyondScope OBJECT-TYPE
   SYNTAX      INTEGER
               {
               disabled (0),
               enabled (1)
               }
   MAX-ACCESS  read-write
   STATUS      current
   DESCRIPTION
      "Path: ethernet2.editConf.ipV6.icmpMessages.beyondScope

       Possibilities:
               disabled   (0)
               enabled   (1)"
   ::= {er1645v2Lan2MCIpV6Entry 302186496}

er1645v2Lan2MCIpV6IcmpMessagesAddressUnreachable OBJECT-TYPE
   SYNTAX      INTEGER
               {
               disabled (0),
               enabled (1)
               }
   MAX-ACCESS  read-write
   STATUS      current
   DESCRIPTION
      "Path: ethernet2.editConf.ipV6.icmpMessages.addressUnreachable

       Possibilities:
               disabled   (0)
               enabled   (1)"
   ::= {er1645v2Lan2MCIpV6Entry 302252032}

er1645v2Lan2MCIpV6IcmpMessagesPortUnreachable OBJECT-TYPE
   SYNTAX      INTEGER
               {
               disabled (0),
               enabled (1)
               }
   MAX-ACCESS  read-write
   STATUS      current
   DESCRIPTION
      "Path: ethernet2.editConf.ipV6.icmpMessages.portUnreachable

       Possibilities:
               disabled   (0)
               enabled   (1)"
   ::= {er1645v2Lan2MCIpV6Entry 302317568}

er1645v2Lan2MCIpV6IcmpMessagesPacketTooBig OBJECT-TYPE
   SYNTAX      INTEGER
               {
               disabled (0),
               enabled (1)
               }
   MAX-ACCESS  read-write
   STATUS      current
   DESCRIPTION
      "Path: ethernet2.editConf.ipV6.icmpMessages.packetTooBig

       Possibilities:
               disabled   (0)
               enabled   (1)"
   ::= {er1645v2Lan2MCIpV6Entry 302645248}

er1645v2Lan2MCIpV6IcmpMessagesHopLimitExceeded OBJECT-TYPE
   SYNTAX      INTEGER
               {
               disabled (0),
               enabled (1)
               }
   MAX-ACCESS  read-write
   STATUS      current
   DESCRIPTION
      "Path: ethernet2.editConf.ipV6.icmpMessages.hopLimitExceeded

       Possibilities:
               disabled   (0)
               enabled   (1)"
   ::= {er1645v2Lan2MCIpV6Entry 303300608}

er1645v2Lan2MCIpV6IcmpMessagesFragTimeExceeded OBJECT-TYPE
   SYNTAX      INTEGER
               {
               disabled (0),
               enabled (1)
               }
   MAX-ACCESS  read-write
   STATUS      current
   DESCRIPTION
      "Path: ethernet2.editConf.ipV6.icmpMessages.fragTimeExceeded

       Possibilities:
               disabled   (0)
               enabled   (1)"
   ::= {er1645v2Lan2MCIpV6Entry 303366144}

er1645v2Lan2MCIpV6IcmpMessagesHeaderFieldErr OBJECT-TYPE
   SYNTAX      INTEGER
               {
               disabled (0),
               enabled (1)
               }
   MAX-ACCESS  read-write
   STATUS      current
   DESCRIPTION
      "Path: ethernet2.editConf.ipV6.icmpMessages.headerFieldErr

       Possibilities:
               disabled   (0)
               enabled   (1)"
   ::= {er1645v2Lan2MCIpV6Entry 303955968}

er1645v2Lan2MCIpV6IcmpMessagesOptionUnrecognized OBJECT-TYPE
   SYNTAX      INTEGER
               {
               disabled (0),
               enabled (1)
               }
   MAX-ACCESS  read-write
   STATUS      current
   DESCRIPTION
      "Path: ethernet2.editConf.ipV6.icmpMessages.optionUnrecognized

       Possibilities:
               disabled   (0)
               enabled   (1)"
   ::= {er1645v2Lan2MCIpV6Entry 304087040}

er1645v2Lan2MCIpV6IcmpMessagesRedirect OBJECT-TYPE
   SYNTAX      INTEGER
               {
               disabled (0),
               enabled (1)
               }
   MAX-ACCESS  read-write
   STATUS      current
   DESCRIPTION
      "Path: ethernet2.editConf.ipV6.icmpMessages.redirect

       Possibilities:
               disabled   (0)
               enabled   (1)"
   ::= {er1645v2Lan2MCIpV6Entry 304611328}

er1645v2Lan2MCIpV6Addresses OBJECT-TYPE
   SYNTAX      SEQUENCE OF Er1645v2Lan2MCIpV6AddressesEntry
   MAX-ACCESS  not-accessible
   STATUS      current
   DESCRIPTION
      ""
   ::= {er1645v2Lan2MCIpV6 50331648}

er1645v2Lan2MCIpV6AddressesEntry OBJECT-TYPE
   SYNTAX      Er1645v2Lan2MCIpV6AddressesEntry
   MAX-ACCESS  not-accessible
   STATUS      current
   DESCRIPTION
      ""
   INDEX      { er1645v2Lan2MCIpV6AddressesTableIx }
   ::= {er1645v2Lan2MCIpV6Addresses 1}

Er1645v2Lan2MCIpV6AddressesEntry ::=
   SEQUENCE
      {
      er1645v2Lan2MCIpV6AddressesActions
         VariableLengthTableActions,
      er1645v2Lan2MCIpV6AddressesTableIx
         TableIndex,
      er1645v2Lan2MCIpV6AddressesType
         INTEGER,
      er1645v2Lan2MCIpV6AddressesAddress
         Ipv6Address,
      er1645v2Lan2MCIpV6AddressesPrefixLength
         Integer32,
      er1645v2Lan2MCIpV6AddressesGeneralPrefix
         DisplayString,
      er1645v2Lan2MCIpV6AddressesRaSend
         INTEGER,
      er1645v2Lan2MCIpV6AddressesRaOnLinkFlag
         INTEGER,
      er1645v2Lan2MCIpV6AddressesRaAutoFlag
         INTEGER,
      er1645v2Lan2MCIpV6AddressesRaValidLifeTime
         TimeTicks,
      er1645v2Lan2MCIpV6AddressesRaValidLTMode
         INTEGER,
      er1645v2Lan2MCIpV6AddressesRaPrefLifeTime
         TimeTicks,
      er1645v2Lan2MCIpV6AddressesRaPrefLTMode
         INTEGER
      }

er1645v2Lan2MCIpV6AddressesActions OBJECT-TYPE
   SYNTAX      VariableLengthTableActions
   MAX-ACCESS  read-write
   STATUS      current
   DESCRIPTION
      "By way of this field, some manipulations
       on this table may be performed."
   ::= {er1645v2Lan2MCIpV6AddressesEntry 2}

er1645v2Lan2MCIpV6AddressesTableIx OBJECT-TYPE
   SYNTAX      TableIndex
   MAX-ACCESS  not-accessible
   STATUS      current
   DESCRIPTION
      ""
   ::= {er1645v2Lan2MCIpV6AddressesEntry 11}

er1645v2Lan2MCIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.ipV6.addresses.type

       Possibilities:
               unicast   (0)
               eui64   (1)
               anycast   (2)
               linkLocal   (3)
               generalPrefix   (4)"
   ::= {er1645v2Lan2MCIpV6AddressesEntry 50331648}

er1645v2Lan2MCIpV6AddressesAddress OBJECT-TYPE
   SYNTAX      Ipv6Address
   MAX-ACCESS  read-write
   STATUS      current
   DESCRIPTION
      "Path: ethernet2.editConf.ipV6.addresses.address

       ipv6 address"
   ::= {er1645v2Lan2MCIpV6AddressesEntry 16777216}

er1645v2Lan2MCIpV6AddressesPrefixLength OBJECT-TYPE
   SYNTAX      Integer32
   MAX-ACCESS  read-write
   STATUS      current
   DESCRIPTION
      "Path: ethernet2.editConf.ipV6.addresses.prefixLength"
   ::= {er1645v2Lan2MCIpV6AddressesEntry 33554432}

er1645v2Lan2MCIpV6AddressesGeneralPrefix OBJECT-TYPE
   SYNTAX      DisplayString
   MAX-ACCESS  read-write
   STATUS      current
   DESCRIPTION
      "Path: ethernet2.editConf.ipV6.addresses.generalPrefix"
   ::= {er1645v2Lan2MCIpV6AddressesEntry 83886080}

er1645v2Lan2MCIpV6AddressesRaSend OBJECT-TYPE
   SYNTAX      INTEGER
               {
               disabled (0),
               enabled (1)
               }
   MAX-ACCESS  read-write
   STATUS      current
   DESCRIPTION
      "Path: ethernet2.editConf.ipV6.addresses.ra.send

       Possibilities:
               disabled   (0)
               enabled   (1)"
   ::= {er1645v2Lan2MCIpV6AddressesEntry 67174400}

er1645v2Lan2MCIpV6AddressesRaOnLinkFlag OBJECT-TYPE
   SYNTAX      INTEGER
               {
               disabled (0),
               enabled (1)
               }
   MAX-ACCESS  read-write
   STATUS      current
   DESCRIPTION
      "Path: ethernet2.editConf.ipV6.addresses.ra.onLinkFlag

       Possibilities:
               disabled   (0)
               enabled   (1)"
   ::= {er1645v2Lan2MCIpV6AddressesEntry 67371008}

er1645v2Lan2MCIpV6AddressesRaAutoFlag OBJECT-TYPE
   SYNTAX      INTEGER
               {
               disabled (0),
               enabled (1)
               }
   MAX-ACCESS  read-write
   STATUS      current
   DESCRIPTION
      "Path: ethernet2.editConf.ipV6.addresses.ra.autonomousFlag

       Possibilities:
               disabled   (0)
               enabled   (1)"
   ::= {er1645v2Lan2MCIpV6AddressesEntry 67567616}

er1645v2Lan2MCIpV6AddressesRaValidLifeTime OBJECT-TYPE
   SYNTAX      TimeTicks
   MAX-ACCESS  read-write
   STATUS      current
   DESCRIPTION
      "Path: ethernet2.editConf.ipV6.addresses.ra.validLifeTime

       Time in centi-second."
   ::= {er1645v2Lan2MCIpV6AddressesEntry 67239936}

er1645v2Lan2MCIpV6AddressesRaValidLTMode OBJECT-TYPE
   SYNTAX      INTEGER
               {
               fixed (0),
               infinite (2)
               }
   MAX-ACCESS  read-write
   STATUS      current
   DESCRIPTION
      "Path: ethernet2.editConf.ipV6.addresses.ra.validLifeTimeMode

       Possibilities:
               fixed   (0)
               infinite   (2)"
   ::= {er1645v2Lan2MCIpV6AddressesEntry 67305472}

er1645v2Lan2MCIpV6AddressesRaPrefLifeTime OBJECT-TYPE
   SYNTAX      TimeTicks
   MAX-ACCESS  read-write
   STATUS      current
   DESCRIPTION
      "Path: ethernet2.editConf.ipV6.addresses.ra.prefLifeTime

       Time in centi-second."
   ::= {er1645v2Lan2MCIpV6AddressesEntry 67436544}

er1645v2Lan2MCIpV6AddressesRaPrefLTMode OBJECT-TYPE
   SYNTAX      INTEGER
               {
               fixed (0),
               infinite (2)
               }
   MAX-ACCESS  read-write
   STATUS      current
   DESCRIPTION
      "Path: ethernet2.editConf.ipV6.addresses.ra.prefLifeTimeMode

       Possibilities:
               fixed   (0)
               infinite   (2)"
   ::= {er1645v2Lan2MCIpV6AddressesEntry 67502080}

er1645v2Lan2MCIpV6RaDnsOptionsRdnssServers OBJECT-TYPE
   SYNTAX      SEQUENCE OF Er1645v2Lan2MCIpV6RaDnsOptionsRdnssServersEntry
   MAX-ACCESS  not-accessible
   STATUS      current
   DESCRIPTION
      ""
   ::= {er1645v2Lan2MCIpV6 101394432}

er1645v2Lan2MCIpV6RaDnsOptionsRdnssServersEntry OBJECT-TYPE
   SYNTAX      Er1645v2Lan2MCIpV6RaDnsOptionsRdnssServersEntry
   MAX-ACCESS  not-accessible
   STATUS      current
   DESCRIPTION
      ""
   INDEX      { er1645v2Lan2MCIpV6RaDnsOptionsRdnssServersTableIx }
   ::= {er1645v2Lan2MCIpV6RaDnsOptionsRdnssServers 1}

Er1645v2Lan2MCIpV6RaDnsOptionsRdnssServersEntry ::=
   SEQUENCE
      {
      er1645v2Lan2MCIpV6RaDnsOptionsRdnssServersActions
         VariableLengthTableActions,
      er1645v2Lan2MCIpV6RaDnsOptionsRdnssServersTableIx
         TableIndex,
      er1645v2Lan2MCIpV6RaDnsOptionsRdnssServersAddress
         Ipv6Address
      }

er1645v2Lan2MCIpV6RaDnsOptionsRdnssServersActions OBJECT-TYPE
   SYNTAX      VariableLengthTableActions
   MAX-ACCESS  read-write
   STATUS      current
   DESCRIPTION
      "By way of this field, some manipulations
       on this table may be performed."
   ::= {er1645v2Lan2MCIpV6RaDnsOptionsRdnssServersEntry 2}

er1645v2Lan2MCIpV6RaDnsOptionsRdnssServersTableIx OBJECT-TYPE
   SYNTAX      TableIndex
   MAX-ACCESS  not-accessible
   STATUS      current
   DESCRIPTION
      ""
   ::= {er1645v2Lan2MCIpV6RaDnsOptionsRdnssServersEntry 11}

er1645v2Lan2MCIpV6RaDnsOptionsRdnssServersAddress OBJECT-TYPE
   SYNTAX      Ipv6Address
   MAX-ACCESS  read-write
   STATUS      current
   DESCRIPTION
      "Path: ethernet2.editConf.ipV6.ra.dnsOptions.rdnss.servers.address

       ipv6 address"
   ::= {er1645v2Lan2MCIpV6RaDnsOptionsRdnssServersEntry 16777216}

er1645v2Lan2MCIpV6RaDnsOptionsDnsslDomains OBJECT-TYPE
   SYNTAX      SEQUENCE OF Er1645v2Lan2MCIpV6RaDnsOptionsDnsslDomainsEntry
   MAX-ACCESS  not-accessible
   STATUS      current
   DESCRIPTION
      ""
   ::= {er1645v2Lan2MCIpV6 101402624}

er1645v2Lan2MCIpV6RaDnsOptionsDnsslDomainsEntry OBJECT-TYPE
   SYNTAX      Er1645v2Lan2MCIpV6RaDnsOptionsDnsslDomainsEntry
   MAX-ACCESS  not-accessible
   STATUS      current
   DESCRIPTION
      ""
   INDEX      { er1645v2Lan2MCIpV6RaDnsOptionsDnsslDomainsTableIx }
   ::= {er1645v2Lan2MCIpV6RaDnsOptionsDnsslDomains 1}

Er1645v2Lan2MCIpV6RaDnsOptionsDnsslDomainsEntry ::=
   SEQUENCE
      {
      er1645v2Lan2MCIpV6RaDnsOptionsDnsslDomainsActions
         VariableLengthTableActions,
      er1645v2Lan2MCIpV6RaDnsOptionsDnsslDomainsTableIx
         TableIndex,
      er1645v2Lan2MCIpV6RaDnsOptionsDnsslDomainsName
         DisplayString
      }

er1645v2Lan2MCIpV6RaDnsOptionsDnsslDomainsActions OBJECT-TYPE
   SYNTAX      VariableLengthTableActions
   MAX-ACCESS  read-write
   STATUS      current
   DESCRIPTION
      "By way of this field, some manipulations
       on this table may be performed."
   ::= {er1645v2Lan2MCIpV6RaDnsOptionsDnsslDomainsEntry 2}

er1645v2Lan2MCIpV6RaDnsOptionsDnsslDomainsTableIx OBJECT-TYPE
   SYNTAX      TableIndex
   MAX-ACCESS  not-accessible
   STATUS      current
   DESCRIPTION
      ""
   ::= {er1645v2Lan2MCIpV6RaDnsOptionsDnsslDomainsEntry 11}

er1645v2Lan2MCIpV6RaDnsOptionsDnsslDomainsName OBJECT-TYPE
   SYNTAX      DisplayString
   MAX-ACCESS  read-write
   STATUS      current
   DESCRIPTION
      "Path: ethernet2.editConf.ipV6.ra.dnsOptions.dnssl.domains.name"
   ::= {er1645v2Lan2MCIpV6RaDnsOptionsDnsslDomainsEntry 16777216}

er1645v2Lan2MCIpV6DhcpClientUserClassOpt OBJECT-TYPE
   SYNTAX      SEQUENCE OF Er1645v2Lan2MCIpV6DhcpClientUserClassOptEntry
   MAX-ACCESS  not-accessible
   STATUS      current
   DESCRIPTION
      ""
   ::= {er1645v2Lan2MCIpV6 171442176}

er1645v2Lan2MCIpV6DhcpClientUserClassOptEntry OBJECT-TYPE
   SYNTAX      Er1645v2Lan2MCIpV6DhcpClientUserClassOptEntry
   MAX-ACCESS  not-accessible
   STATUS      current
   DESCRIPTION
      ""
   INDEX      { er1645v2Lan2MCIpV6DhcpClientUserClassOptTableIx }
   ::= {er1645v2Lan2MCIpV6DhcpClientUserClassOpt 1}

Er1645v2Lan2MCIpV6DhcpClientUserClassOptEntry ::=
   SEQUENCE
      {
      er1645v2Lan2MCIpV6DhcpClientUserClassOptActions
         VariableLengthTableActions,
      er1645v2Lan2MCIpV6DhcpClientUserClassOptTableIx
         TableIndex,
      er1645v2Lan2MCIpV6DhcpClientUserClassOptValueAscii
         DisplayString,
      er1645v2Lan2MCIpV6DhcpClientUserClassOptValueDecimal
         Integer32,
      er1645v2Lan2MCIpV6DhcpClientUserClassOptValueHexData
         OCTET STRING
      }

er1645v2Lan2MCIpV6DhcpClientUserClassOptActions OBJECT-TYPE
   SYNTAX      VariableLengthTableActions
   MAX-ACCESS  read-write
   STATUS      current
   DESCRIPTION
      "By way of this field, some manipulations
       on this table may be performed."
   ::= {er1645v2Lan2MCIpV6DhcpClientUserClassOptEntry 2}

er1645v2Lan2MCIpV6DhcpClientUserClassOptTableIx OBJECT-TYPE
   SYNTAX      TableIndex
   MAX-ACCESS  not-accessible
   STATUS      current
   DESCRIPTION
      ""
   ::= {er1645v2Lan2MCIpV6DhcpClientUserClassOptEntry 11}

er1645v2Lan2MCIpV6DhcpClientUserClassOptValueAscii OBJECT-TYPE
   SYNTAX      DisplayString
   MAX-ACCESS  read-write
   STATUS      current
   DESCRIPTION
      "Path: ethernet2.editConf.ipV6.dhcp.client.userClassOpt.value.ascii"
   ::= {er1645v2Lan2MCIpV6DhcpClientUserClassOptEntry 16842752}

er1645v2Lan2MCIpV6DhcpClientUserClassOptValueDecimal OBJECT-TYPE
   SYNTAX      Integer32
   MAX-ACCESS  read-write
   STATUS      current
   DESCRIPTION
      "Path: ethernet2.editConf.ipV6.dhcp.client.userClassOpt.value.decimal"
   ::= {er1645v2Lan2MCIpV6DhcpClientUserClassOptEntry 16908288}

er1645v2Lan2MCIpV6DhcpClientUserClassOptValueHexData OBJECT-TYPE
   SYNTAX      OCTET STRING
   MAX-ACCESS  read-write
   STATUS      current
   DESCRIPTION
      "Path: ethernet2.editConf.ipV6.dhcp.client.userClassOpt.value.hexData"
   ::= {er1645v2Lan2MCIpV6DhcpClientUserClassOptEntry 16973824}

er1645v2Lan2MCIpV6DhcpClientVendorCl OBJECT-TYPE
   SYNTAX      SEQUENCE OF Er1645v2Lan2MCIpV6DhcpClientVendorClEntry
   MAX-ACCESS  not-accessible
   STATUS      current
   DESCRIPTION
      ""
   ::= {er1645v2Lan2MCIpV6 171704320}

er1645v2Lan2MCIpV6DhcpClientVendorClEntry OBJECT-TYPE
   SYNTAX      Er1645v2Lan2MCIpV6DhcpClientVendorClEntry
   MAX-ACCESS  not-accessible
   STATUS      current
   DESCRIPTION
      ""
   INDEX      { er1645v2Lan2MCIpV6DhcpClientVendorClTableIx }
   ::= {er1645v2Lan2MCIpV6DhcpClientVendorCl 1}

Er1645v2Lan2MCIpV6DhcpClientVendorClEntry ::=
   SEQUENCE
      {
      er1645v2Lan2MCIpV6DhcpClientVendorClActions
         VariableLengthTableActions,
      er1645v2Lan2MCIpV6DhcpClientVendorClTableIx
         TableIndex,
      er1645v2Lan2MCIpV6DhcpClientVendorClValueAscii
         DisplayString,
      er1645v2Lan2MCIpV6DhcpClientVendorClValueDecimal
         Integer32,
      er1645v2Lan2MCIpV6DhcpClientVendorClValueHexData
         OCTET STRING
      }

er1645v2Lan2MCIpV6DhcpClientVendorClActions OBJECT-TYPE
   SYNTAX      VariableLengthTableActions
   MAX-ACCESS  read-write
   STATUS      current
   DESCRIPTION
      "By way of this field, some manipulations
       on this table may be performed."
   ::= {er1645v2Lan2MCIpV6DhcpClientVendorClEntry 2}

er1645v2Lan2MCIpV6DhcpClientVendorClTableIx OBJECT-TYPE
   SYNTAX      TableIndex
   MAX-ACCESS  not-accessible
   STATUS      current
   DESCRIPTION
      ""
   ::= {er1645v2Lan2MCIpV6DhcpClientVendorClEntry 11}

er1645v2Lan2MCIpV6DhcpClientVendorClValueAscii OBJECT-TYPE
   SYNTAX      DisplayString
   MAX-ACCESS  read-write
   STATUS      current
   DESCRIPTION
      "Path: ethernet2.editConf.ipV6.dhcp.client.vendorClassOpt.value.ascii"
   ::= {er1645v2Lan2MCIpV6DhcpClientVendorClEntry 16842752}

er1645v2Lan2MCIpV6DhcpClientVendorClValueDecimal OBJECT-TYPE
   SYNTAX      Integer32
   MAX-ACCESS  read-write
   STATUS      current
   DESCRIPTION
      "Path: ethernet2.editConf.ipV6.dhcp.client.vendorClassOpt.value.decimal"
   ::= {er1645v2Lan2MCIpV6DhcpClientVendorClEntry 16908288}

er1645v2Lan2MCIpV6DhcpClientVendorClValueHexData OBJECT-TYPE
   SYNTAX      OCTET STRING
   MAX-ACCESS  read-write
   STATUS      current
   DESCRIPTION
      "Path: ethernet2.editConf.ipV6.dhcp.client.vendorClassOpt.value.hexData"
   ::= {er1645v2Lan2MCIpV6DhcpClientVendorClEntry 16973824}

er1645v2Lan2MCIpV6DhcpRelayDestinations OBJECT-TYPE
   SYNTAX      SEQUENCE OF Er1645v2Lan2MCIpV6DhcpRelayDestinationsEntry
   MAX-ACCESS  not-accessible
   STATUS      current
   DESCRIPTION
      ""
   ::= {er1645v2Lan2MCIpV6 174080000}

er1645v2Lan2MCIpV6DhcpRelayDestinationsEntry OBJECT-TYPE
   SYNTAX      Er1645v2Lan2MCIpV6DhcpRelayDestinationsEntry
   MAX-ACCESS  not-accessible
   STATUS      current
   DESCRIPTION
      ""
   INDEX      { er1645v2Lan2MCIpV6DhcpRelayDestinationsTableIx }
   ::= {er1645v2Lan2MCIpV6DhcpRelayDestinations 1}

Er1645v2Lan2MCIpV6DhcpRelayDestinationsEntry ::=
   SEQUENCE
      {
      er1645v2Lan2MCIpV6DhcpRelayDestinationsActions
         VariableLengthTableActions,
      er1645v2Lan2MCIpV6DhcpRelayDestinationsTableIx
         TableIndex,
      er1645v2Lan2MCIpV6DhcpRelayDestinationsAddress
         Ipv6Address,
      er1645v2Lan2MCIpV6DhcpRelayDestinationsInterface
         DisplayString
      }

er1645v2Lan2MCIpV6DhcpRelayDestinationsActions OBJECT-TYPE
   SYNTAX      VariableLengthTableActions
   MAX-ACCESS  read-write
   STATUS      current
   DESCRIPTION
      "By way of this field, some manipulations
       on this table may be performed."
   ::= {er1645v2Lan2MCIpV6DhcpRelayDestinationsEntry 2}

er1645v2Lan2MCIpV6DhcpRelayDestinationsTableIx OBJECT-TYPE
   SYNTAX      TableIndex
   MAX-ACCESS  not-accessible
   STATUS      current
   DESCRIPTION
      ""
   ::= {er1645v2Lan2MCIpV6DhcpRelayDestinationsEntry 11}

er1645v2Lan2MCIpV6DhcpRelayDestinationsAddress OBJECT-TYPE
   SYNTAX      Ipv6Address
   MAX-ACCESS  read-write
   STATUS      current
   DESCRIPTION
      "Path: ethernet2.editConf.ipV6.dhcp.relay.destinations.address

       ipv6 address"
   ::= {er1645v2Lan2MCIpV6DhcpRelayDestinationsEntry 16777216}

er1645v2Lan2MCIpV6DhcpRelayDestinationsInterface OBJECT-TYPE
   SYNTAX      DisplayString
   MAX-ACCESS  read-write
   STATUS      current
   DESCRIPTION
      "Path: ethernet2.editConf.ipV6.dhcp.relay.destinations.interface"
   ::= {er1645v2Lan2MCIpV6DhcpRelayDestinationsEntry 33554432}


er1645v2Lan2MCFlowControl OBJECT-TYPE
   SYNTAX      INTEGER
               {
               disabled (1),
               rx (2),
               tx (3),
               rxAndTx (4)
               }
   MAX-ACCESS  read-write
   STATUS      current
   DESCRIPTION
      "Path: ethernet2.editConf.flowControl
       Info: LAN flow control

       Possibilities:
               disabled   (1)
               rx   (2)
               tx   (3)
               rxAndTx   (4)"
   ::= {er1645v2Lan2MC 7}


er1645v2Lan2MCInboundNUcastPriority OBJECT IDENTIFIER ::= {er1645v2Lan2MC 230}

er1645v2Lan2MCInboundNUcastPrioritySSC OBJECT IDENTIFIER ::= {er1645v2Lan2MCInboundNUcastPriority 1}

er1645v2Lan2MCInboundNUcastPriorityEntry OBJECT IDENTIFIER ::= {er1645v2Lan2MCInboundNUcastPrioritySSC 1}

er1645v2Lan2MCInboundNUcastPriorityBroadcast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundNUcastPriority.broadcast

       Possibilities:
               queue1   (0)
               queue2   (1)
               queue3   (2)
               queue4   (3)
               queue5   (4)
               lowDelayQueue   (5)
               lowDelay2Queue   (6)
               systemQueue   (7)"
   ::= {er1645v2Lan2MCInboundNUcastPriorityEntry 16777216}

er1645v2Lan2MCInboundNUcastPriorityMulticast OBJECT-TYPE
   SYNTAX      INTEGER
               {
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.inboundNUcastPriority.multicast

       Possibilities:
               queue1   (0)
               queue2   (1)
               queue3   (2)
               queue4   (3)
               queue5   (4)
               lowDelayQueue   (5)
               lowDelay2Queue   (6)
               systemQueue   (7)"
   ::= {er1645v2Lan2MCInboundNUcastPriorityEntry 33554432}


er1645v2Lan2MCIp OBJECT IDENTIFIER ::= {er1645v2Lan2MC 1}

er1645v2Lan2MCIpSSC OBJECT IDENTIFIER ::= {er1645v2Lan2MCIp 1}

er1645v2Lan2MCIpEntry OBJECT IDENTIFIER ::= {er1645v2Lan2MCIpSSC 1}

er1645v2Lan2MCIpVrfRouter OBJECT-TYPE
   SYNTAX      DisplayString
   MAX-ACCESS  read-write
   STATUS      current
   DESCRIPTION
      "Path: ethernet2.editConf.ip.vrfRouter"
   ::= {er1645v2Lan2MCIpEntry 738197504}

er1645v2Lan2MCIpAdr OBJECT-TYPE
   SYNTAX      IpAddress
   MAX-ACCESS  read-write
   STATUS      current
   DESCRIPTION
      "Path: ethernet2.editConf.ip.address"
   ::= {er1645v2Lan2MCIpEntry 2030043136}

er1645v2Lan2MCIpNetm OBJECT-TYPE
   SYNTAX      IpAddress
   MAX-ACCESS  read-write
   STATUS      current
   DESCRIPTION
      "Path: ethernet2.editConf.ip.netMask"
   ::= {er1645v2Lan2MCIpEntry 2063597568}

er1645v2Lan2MCIpSNetName OBJECT-TYPE
   SYNTAX      INTEGER
               {
               slOPTg (0),
               corp (2),
               dmz (3),
               internet (1)
               }
   MAX-ACCESS  read-write
   STATUS      current
   DESCRIPTION
      "Path: ethernet2.editConf.ip.sNet.name

       Possibilities:
               <OPT>   (0)
               corp   (2)
               dmz   (3)
               internet   (1)"
   ::= {er1645v2Lan2MCIpEntry 855703552}

er1645v2Lan2MCIpSNetCust OBJECT-TYPE
   SYNTAX      DisplayString
   MAX-ACCESS  read-write
   STATUS      current
   DESCRIPTION
      "Path: ethernet2.editConf.ip.sNet.custom"
   ::= {er1645v2Lan2MCIpEntry 855769088}

er1645v2Lan2MCIpDhcpC OBJECT-TYPE
   SYNTAX      INTEGER
               {
               disabled (0),
               enabled (1)
               }
   MAX-ACCESS  read-write
   STATUS      current
   DESCRIPTION
      "Path: ethernet2.editConf.ip.dhcpClient

       Possibilities:
               disabled   (0)
               enabled   (1)"
   ::= {er1645v2Lan2MCIpEntry 838860800}

er1645v2Lan2MCIpDhcpGatewayPreference OBJECT-TYPE
   SYNTAX      Integer32
   MAX-ACCESS  read-write
   STATUS      current
   DESCRIPTION
      "Path: ethernet2.editConf.ip.dhcp.gatewayPreference"
   ::= {er1645v2Lan2MCIpEntry 872480768}

er1645v2Lan2MCIpDhcpRoutePreference OBJECT-TYPE
   SYNTAX      Integer32
   MAX-ACCESS  read-write
   STATUS      current
   DESCRIPTION
      "Path: ethernet2.editConf.ip.dhcp.routePreference"
   ::= {er1645v2Lan2MCIpEntry 872546304}

er1645v2Lan2MCIpDhcpDnsPreference OBJECT-TYPE
   SYNTAX      Integer32
   MAX-ACCESS  read-write
   STATUS      current
   DESCRIPTION
      "Path: ethernet2.editConf.ip.dhcp.dnsPreference"
   ::= {er1645v2Lan2MCIpEntry 872611840}

er1645v2Lan2MCIpMtu OBJECT-TYPE
   SYNTAX      Integer32
   MAX-ACCESS  read-write
   STATUS      current
   DESCRIPTION
      "Path: ethernet2.editConf.ip.mtu"
   ::= {er1645v2Lan2MCIpEntry 671088640}

er1645v2Lan2MCIpMssAdjust OBJECT-TYPE
   SYNTAX      INTEGER
               {
               disabled (0),
               auto (65536)
               }
   MAX-ACCESS  read-write
   STATUS      current
   DESCRIPTION
      "Path: ethernet2.editConf.ip.mssAdjust

       Possibilities:
               disabled   (0)
               auto   (65536)"
   ::= {er1645v2Lan2MCIpEntry 754974720}

er1645v2Lan2MCIpRipMetric OBJECT-TYPE
   SYNTAX      Integer32
   MAX-ACCESS  read-write
   STATUS      current
   DESCRIPTION
      "Path: ethernet2.editConf.ip.rip.metric"
   ::= {er1645v2Lan2MCIpEntry 353566720}

er1645v2Lan2MCIpRipMetricOut OBJECT-TYPE
   SYNTAX      Integer32
   MAX-ACCESS  read-write
   STATUS      current
   DESCRIPTION
      "Path: ethernet2.editConf.ip.rip.metricOut"
   ::= {er1645v2Lan2MCIpEntry 353632256}

er1645v2Lan2MCIpRipMode OBJECT-TYPE
   SYNTAX      INTEGER
               {
               disabled (0),
               passive (1),
               active (2)
               }
   MAX-ACCESS  read-write
   STATUS      current
   DESCRIPTION
      "Path: ethernet2.editConf.ip.rip.mode

       Possibilities:
               disabled   (0)
               passive   (1)
               active   (2)"
   ::= {er1645v2Lan2MCIpEntry 353697792}

er1645v2Lan2MCIpRipTxVer OBJECT-TYPE
   SYNTAX      INTEGER
               {
               rip1 (0),
               rip2 (1),
               rip1mcompatible (2)
               }
   MAX-ACCESS  read-write
   STATUS      current
   DESCRIPTION
      "Path: ethernet2.editConf.ip.rip.txVersion

       Possibilities:
               rip1   (0)
               rip2   (1)
               rip1-compatible   (2)"
   ::= {er1645v2Lan2MCIpEntry 354615296}

er1645v2Lan2MCIpRipRxVer OBJECT-TYPE
   SYNTAX      INTEGER
               {
               rip1only (0),
               rip2only (1),
               rip12 (2)
               }
   MAX-ACCESS  read-write
   STATUS      current
   DESCRIPTION
      "Path: ethernet2.editConf.ip.rip.rxVersion

       Possibilities:
               rip1only   (0)
               rip2only   (1)
               rip1&2   (2)"
   ::= {er1645v2Lan2MCIpEntry 354680832}

er1645v2Lan2MCIpRipSplitH OBJECT-TYPE
   SYNTAX      INTEGER
               {
               disabled (0),
               enabled (1),
               poisonedReverse (2)
               }
   MAX-ACCESS  read-write
   STATUS      current
   DESCRIPTION
      "Path: ethernet2.editConf.ip.rip.splitHorizon

       Possibilities:
               disabled   (0)
               enabled   (1)
               poisonedReverse   (2)"
   ::= {er1645v2Lan2MCIpEntry 353828864}

er1645v2Lan2MCIpRipAuth OBJECT-TYPE
   SYNTAX      INTEGER
               {
               disabled (0),
               texts (1),
               md5 (2)
               }
   MAX-ACCESS  read-write
   STATUS      current
   DESCRIPTION
      "Path: ethernet2.editConf.ip.rip.authentication

       Possibilities:
               disabled   (0)
               text    (1)
               md5   (2)"
   ::= {er1645v2Lan2MCIpEntry 353501184}

er1645v2Lan2MCIpRipFilter OBJECT-TYPE
   SYNTAX      DisplayString
   MAX-ACCESS  read-write
   STATUS      current
   DESCRIPTION
      "Path: ethernet2.editConf.ip.rip.filter"
   ::= {er1645v2Lan2MCIpEntry 354418688}

er1645v2Lan2MCIpRipFilterIn OBJECT-TYPE
   SYNTAX      DisplayString
   MAX-ACCESS  read-write
   STATUS      current
   DESCRIPTION
      "Path: ethernet2.editConf.ip.rip.filterIn"
   ::= {er1645v2Lan2MCIpEntry 354484224}

er1645v2Lan2MCIpRipClearNextHop OBJECT-TYPE
   SYNTAX      INTEGER
               {
               disabled (0),
               enabled (1)
               }
   MAX-ACCESS  read-write
   STATUS      current
   DESCRIPTION
      "Path: ethernet2.editConf.ip.rip.clearNextHop

       Possibilities:
               disabled   (0)
               enabled   (1)"
   ::= {er1645v2Lan2MCIpEntry 352452608}

er1645v2Lan2MCIpAccPol OBJECT-TYPE
   SYNTAX      DisplayString
   MAX-ACCESS  read-write
   STATUS      current
   DESCRIPTION
      "Path: ethernet2.editConf.ip.accessPolicy"
   ::= {er1645v2Lan2MCIpEntry 704643072}

er1645v2Lan2MCIpAB OBJECT-TYPE
   SYNTAX      DisplayString
   MAX-ACCESS  read-write
   STATUS      current
   DESCRIPTION
      "Path: ethernet2.editConf.ip.trafficPolicy"
   ::= {er1645v2Lan2MCIpEntry 234881024}

er1645v2Lan2MCIpMA OBJECT-TYPE
   SYNTAX      INTEGER
               {
               disabled (0),
               enabled (1)
               }
   MAX-ACCESS  read-write
   STATUS      current
   DESCRIPTION
      "Path: ethernet2.editConf.ip.mgmtAccess

       Possibilities:
               disabled   (0)
               enabled   (1)"
   ::= {er1645v2Lan2MCIpEntry 268435456}

er1645v2Lan2MCIpMF OBJECT-TYPE
   SYNTAX      Integer32
   MAX-ACCESS  read-write
   STATUS      current
   DESCRIPTION
      "Path: ethernet2.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2MCIpEntry 285212672}

er1645v2Lan2MCIpDB OBJECT-TYPE
   SYNTAX      INTEGER
               {
               disabled (0),
               enabled (1)
               }
   MAX-ACCESS  read-write
   STATUS      current
   DESCRIPTION
      "Path: ethernet2.editConf.ip.directedBroadcasts

       Possibilities:
               disabled   (0)
               enabled   (1)"
   ::= {er1645v2Lan2MCIpEntry 369098752}

er1645v2Lan2MCIpIR OBJECT-TYPE
   SYNTAX      INTEGER
               {
               disabled (0),
               enabled (1)
               }
   MAX-ACCESS  read-write
   STATUS      current
   DESCRIPTION
      "Path: ethernet2.editConf.ip.icmpRedirects

       Possibilities:
               disabled   (0)
               enabled   (1)"
   ::= {er1645v2Lan2MCIpEntry 436207616}

er1645v2Lan2MCIpIgmp OBJECT-TYPE
   SYNTAX      INTEGER
               {
               disabled (0),
               proxy (1),
               router (2),
               v3Router (5)
               }
   MAX-ACCESS  read-write
   STATUS      current
   DESCRIPTION
      "Path: ethernet2.editConf.ip.igmp

       Possibilities:
               disabled   (0)
               proxy   (1)
               router   (2)
               v3Router   (5)"
   ::= {er1645v2Lan2MCIpEntry 536870912}

er1645v2Lan2MCIpNN OBJECT-TYPE
   SYNTAX      DisplayString
   MAX-ACCESS  read-write
   STATUS      current
   DESCRIPTION
      "Path: ethernet2.editConf.ip.nat"
   ::= {er1645v2Lan2MCIpEntry 452984832}

er1645v2Lan2MCIpVrrp OBJECT-TYPE
   SYNTAX      INTEGER
               {
               disabled (0),
               enabled (1)
               }
   MAX-ACCESS  read-write
   STATUS      current
   DESCRIPTION
      "Path: ethernet2.editConf.ip.vrrp

       Possibilities:
               disabled   (0)
               enabled   (1)"
   ::= {er1645v2Lan2MCIpEntry 721420288}

er1645v2Lan2MCIpPimMode OBJECT-TYPE
   SYNTAX      INTEGER
               {
               disabled (0),
               sparse (1),
               passive (2)
               }
   MAX-ACCESS  read-write
   STATUS      current
   DESCRIPTION
      "Path: ethernet2.editConf.ip.pim.mode

       Possibilities:
               disabled   (0)
               sparse   (1)
               passive   (2)"
   ::= {er1645v2Lan2MCIpEntry 771817472}

er1645v2Lan2MCIpPimDrPriority OBJECT-TYPE
   SYNTAX      Counter32
   MAX-ACCESS  read-write
   STATUS      current
   DESCRIPTION
      "Path: ethernet2.editConf.ip.pim.drPriority

       32 bit unsigned wrappable counter."
   ::= {er1645v2Lan2MCIpEntry 771883008}

er1645v2Lan2MCIpPimHelloTime OBJECT-TYPE
   SYNTAX      TimeTicks
   MAX-ACCESS  read-write
   STATUS      current
   DESCRIPTION
      "Path: ethernet2.editConf.ip.pim.helloTime

       Time in centi-second."
   ::= {er1645v2Lan2MCIpEntry 771948544}

er1645v2Lan2MCIpPimPropagationDelay OBJECT-TYPE
   SYNTAX      TimeTicks
   MAX-ACCESS  read-write
   STATUS      current
   DESCRIPTION
      "Path: ethernet2.editConf.ip.pim.propagationDelay

       Time in centi-second."
   ::= {er1645v2Lan2MCIpEntry 772014080}

er1645v2Lan2MCIpPimOverrideInterval OBJECT-TYPE
   SYNTAX      TimeTicks
   MAX-ACCESS  read-write
   STATUS      current
   DESCRIPTION
      "Path: ethernet2.editConf.ip.pim.overrideInterval

       Time in centi-second."
   ::= {er1645v2Lan2MCIpEntry 772079616}

er1645v2Lan2MCIpPimBsrBorder OBJECT-TYPE
   SYNTAX      INTEGER
               {
               disabled (0),
               enabled (1)
               }
   MAX-ACCESS  read-write
   STATUS      current
   DESCRIPTION
      "Path: ethernet2.editConf.ip.pim.bsrBorder

       Possibilities:
               disabled   (0)
               enabled   (1)"
   ::= {er1645v2Lan2MCIpEntry 772145152}

er1645v2Lan2MCIpPimTtlThreshold OBJECT-TYPE
   SYNTAX      Integer32
   MAX-ACCESS  read-write
   STATUS      current
   DESCRIPTION
      "Path: ethernet2.editConf.ip.pim.ttlThreshold"
   ::= {er1645v2Lan2MCIpEntry 772210688}

er1645v2Lan2MCIpIMNetworkUnreachable OBJECT-TYPE
   SYNTAX      INTEGER
               {
               disabled (0),
               enabled (1)
               }
   MAX-ACCESS  read-write
   STATUS      current
   DESCRIPTION
      "Path: ethernet2.editConf.ip.icmpMessages.networkUnreachable

       Possibilities:
               disabled   (0)
               enabled   (1)"
   ::= {er1645v2Lan2MCIpEntry 788594688}

er1645v2Lan2MCIpIMHostUnreachable OBJECT-TYPE
   SYNTAX      INTEGER
               {
               disabled (0),
               enabled (1)
               }
   MAX-ACCESS  read-write
   STATUS      current
   DESCRIPTION
      "Path: ethernet2.editConf.ip.icmpMessages.hostUnreachable

       Possibilities:
               disabled   (0)
               enabled   (1)"
   ::= {er1645v2Lan2MCIpEntry 788660224}

er1645v2Lan2MCIpIMProtocolUnreachable OBJECT-TYPE
   SYNTAX      INTEGER
               {
               disabled (0),
               enabled (1)
               }
   MAX-ACCESS  read-write
   STATUS      current
   DESCRIPTION
      "Path: ethernet2.editConf.ip.icmpMessages.protocolUnreachable

       Possibilities:
               disabled   (0)
               enabled   (1)"
   ::= {er1645v2Lan2MCIpEntry 788725760}

er1645v2Lan2MCIpIMPortUnreachable OBJECT-TYPE
   SYNTAX      INTEGER
               {
               disabled (0),
               enabled (1)
               }
   MAX-ACCESS  read-write
   STATUS      current
   DESCRIPTION
      "Path: ethernet2.editConf.ip.icmpMessages.portUnreachable

       Possibilities:
               disabled   (0)
               enabled   (1)"
   ::= {er1645v2Lan2MCIpEntry 788791296}

er1645v2Lan2MCIpIMMtuExceeded OBJECT-TYPE
   SYNTAX      INTEGER
               {
               disabled (0),
               enabled (1)
               }
   MAX-ACCESS  read-write
   STATUS      current
   DESCRIPTION
      "Path: ethernet2.editConf.ip.icmpMessages.mtuExceeded

       Possibilities:
               disabled   (0)
               enabled   (1)"
   ::= {er1645v2Lan2MCIpEntry 788856832}

er1645v2Lan2MCIpIMAdminProhibited OBJECT-TYPE
   SYNTAX      INTEGER
               {
               disabled (0),
               enabled (1)
               }
   MAX-ACCESS  read-write
   STATUS      current
   DESCRIPTION
      "Path: ethernet2.editConf.ip.icmpMessages.adminProhibited

       Possibilities:
               disabled   (0)
               enabled   (1)"
   ::= {er1645v2Lan2MCIpEntry 788922368}

er1645v2Lan2MCIpIMTtlExceeded OBJECT-TYPE
   SYNTAX      INTEGER
               {
               disabled (0),
               enabled (1)
               }
   MAX-ACCESS  read-write
   STATUS      current
   DESCRIPTION
      "Path: ethernet2.editConf.ip.icmpMessages.ttlExceeded

       Possibilities:
               disabled   (0)
               enabled   (1)"
   ::= {er1645v2Lan2MCIpEntry 788987904}

er1645v2Lan2MCIpIMRedirect OBJECT-TYPE
   SYNTAX      INTEGER
               {
               disabled (0),
               enabled (1)
               }
   MAX-ACCESS  read-write
   STATUS      current
   DESCRIPTION
      "Path: ethernet2.editConf.ip.icmpMessages.redirect

       Possibilities:
               disabled   (0)
               enabled   (1)"
   ::= {er1645v2Lan2MCIpEntry 789053440}

er1645v2Lan2MCIpSaddr OBJECT-TYPE
   SYNTAX      SEQUENCE OF Er1645v2Lan2MCIpSaddrEntry
   MAX-ACCESS  not-accessible
   STATUS      current
   DESCRIPTION
      ""
   ::= {er1645v2Lan2MCIp 385875968}

er1645v2Lan2MCIpSaddrEntry OBJECT-TYPE
   SYNTAX      Er1645v2Lan2MCIpSaddrEntry
   MAX-ACCESS  not-accessible
   STATUS      current
   DESCRIPTION
      ""
   INDEX      { er1645v2Lan2MCIpSaddrTableIx }
   ::= {er1645v2Lan2MCIpSaddr 1}

Er1645v2Lan2MCIpSaddrEntry ::=
   SEQUENCE
      {
      er1645v2Lan2MCIpSaddrActions
         VariableLengthTableActions,
      er1645v2Lan2MCIpSaddrTableIx
         TableIndex,
      er1645v2Lan2MCIpSaddrAddress
         IpAddress,
      er1645v2Lan2MCIpSaddrNetMask
         IpAddress
      }

er1645v2Lan2MCIpSaddrActions OBJECT-TYPE
   SYNTAX      VariableLengthTableActions
   MAX-ACCESS  read-write
   STATUS      current
   DESCRIPTION
      "By way of this field, some manipulations
       on this table may be performed."
   ::= {er1645v2Lan2MCIpSaddrEntry 2}

er1645v2Lan2MCIpSaddrTableIx OBJECT-TYPE
   SYNTAX      TableIndex
   MAX-ACCESS  not-accessible
   STATUS      current
   DESCRIPTION
      ""
   ::= {er1645v2Lan2MCIpSaddrEntry 11}

er1645v2Lan2MCIpSaddrAddress OBJECT-TYPE
   SYNTAX      IpAddress
   MAX-ACCESS  read-write
   STATUS      current
   DESCRIPTION
      "Path: ethernet2.editConf.ip.secondaryIp.address"
   ::= {er1645v2Lan2MCIpSaddrEntry 2030043136}

er1645v2Lan2MCIpSaddrNetMask OBJECT-TYPE
   SYNTAX      IpAddress
   MAX-ACCESS  read-write
   STATUS      current
   DESCRIPTION
      "Path: ethernet2.editConf.ip.secondaryIp.netMask"
   ::= {er1645v2Lan2MCIpSaddrEntry 2063597568}

er1645v2Lan2MCIpH OBJECT-TYPE
   SYNTAX      SEQUENCE OF Er1645v2Lan2MCIpHEntry
   MAX-ACCESS  not-accessible
   STATUS      current
   DESCRIPTION
      ""
   ::= {er1645v2Lan2MCIp 251658240}

er1645v2Lan2MCIpHEntry OBJECT-TYPE
   SYNTAX      Er1645v2Lan2MCIpHEntry
   MAX-ACCESS  not-accessible
   STATUS      current
   DESCRIPTION
      ""
   INDEX      { er1645v2Lan2MCIpHTableIx }
   ::= {er1645v2Lan2MCIpH 1}

Er1645v2Lan2MCIpHEntry ::=
   SEQUENCE
      {
      er1645v2Lan2MCIpHActions
         VariableLengthTableActions,
      er1645v2Lan2MCIpHTableIx
         TableIndex,
      er1645v2Lan2MCIpHAddress
         IpAddress,
      er1645v2Lan2MCIpHDhcpRelayOptionSubscriberId
         DisplayString
      }

er1645v2Lan2MCIpHActions OBJECT-TYPE
   SYNTAX      VariableLengthTableActions
   MAX-ACCESS  read-write
   STATUS      current
   DESCRIPTION
      "By way of this field, some manipulations
       on this table may be performed."
   ::= {er1645v2Lan2MCIpHEntry 2}

er1645v2Lan2MCIpHTableIx OBJECT-TYPE
   SYNTAX      TableIndex
   MAX-ACCESS  not-accessible
   STATUS      current
   DESCRIPTION
      ""
   ::= {er1645v2Lan2MCIpHEntry 11}

er1645v2Lan2MCIpHAddress OBJECT-TYPE
   SYNTAX      IpAddress
   MAX-ACCESS  read-write
   STATUS      current
   DESCRIPTION
      "Path: ethernet2.editConf.ip.helpers.address"
   ::= {er1645v2Lan2MCIpHEntry 16777216}

er1645v2Lan2MCIpHDhcpRelayOptionSubscriberId OBJECT-TYPE
   SYNTAX      DisplayString
   MAX-ACCESS  read-write
   STATUS      current
   DESCRIPTION
      "Path: ethernet2.editConf.ip.helpers.dhcpRelayOption.subscriberId"
   ::= {er1645v2Lan2MCIpHEntry 33947648}


er1645v2Lan2MCAdapter OBJECT-TYPE
   SYNTAX      INTEGER
               {
               autoDetect (0),
               s10MbhalfDuplex (1),
               s10MbfullDuplex (2),
               s100MbhalfDuplex (3),
               s100MbfullDuplex (4),
               s1000MbfullDuplex (6)
               }
   MAX-ACCESS  read-write
   STATUS      current
   DESCRIPTION
      "Path: ethernet2.editConf.adapter

       Possibilities:
               autoDetect   (0)
               10Mb/halfDuplex   (1)
               10Mb/fullDuplex   (2)
               100Mb/halfDuplex   (3)
               100Mb/fullDuplex   (4)
               1000Mb/fullDuplex   (6)"
   ::= {er1645v2Lan2MC 32}


er1645v2Lan2MCVlan OBJECT IDENTIFIER ::= {er1645v2Lan2MC 33}

er1645v2Lan2MCVlanSSCTable OBJECT-TYPE
   SYNTAX      SEQUENCE OF Er1645v2Lan2MCVlanEntry
   MAX-ACCESS  not-accessible
   STATUS      current
   DESCRIPTION
      ""
   ::= {er1645v2Lan2MCVlan 1}

er1645v2Lan2MCVlanEntry OBJECT-TYPE
   SYNTAX      Er1645v2Lan2MCVlanEntry
   MAX-ACCESS  not-accessible
   STATUS      current
   DESCRIPTION
      ""
   INDEX      { er1645v2Lan2MCVlanTableIx }
   ::= {er1645v2Lan2MCVlanSSCTable 1}

Er1645v2Lan2MCVlanEntry ::=
   SEQUENCE
      {
      er1645v2Lan2MCVlanActions
         VariableLengthTableActions,
      er1645v2Lan2MCVlanTableIx
         TableIndex,
      er1645v2Lan2MCVlanName
         DisplayString,
      er1645v2Lan2MCVlanRemark
         DisplayString,
      er1645v2Lan2MCVlanAdminStatus
         INTEGER,
      er1645v2Lan2MCVlanMode
         INTEGER,
      er1645v2Lan2MCVlanPriorityPolicy
         DisplayString,
      er1645v2Lan2MCVlanIpVrfRouter
         DisplayString,
      er1645v2Lan2MCVlanIpAdr
         IpAddress,
      er1645v2Lan2MCVlanIpNetm
         IpAddress,
      er1645v2Lan2MCVlanIpSNetName
         INTEGER,
      er1645v2Lan2MCVlanIpSNetCust
         DisplayString,
      er1645v2Lan2MCVlanIpDhcpC
         INTEGER,
      er1645v2Lan2MCVlanIpDhcpGatewayPreference
         Integer32,
      er1645v2Lan2MCVlanIpDhcpRoutePreference
         Integer32,
      er1645v2Lan2MCVlanIpDhcpDnsPreference
         Integer32,
      er1645v2Lan2MCVlanIpMtu
         Integer32,
      er1645v2Lan2MCVlanIpMssAdjust
         INTEGER,
      er1645v2Lan2MCVlanIpRipMetric
         Integer32,
      er1645v2Lan2MCVlanIpRipMetricOut
         Integer32,
      er1645v2Lan2MCVlanIpRipMode
         INTEGER,
      er1645v2Lan2MCVlanIpRipTxVer
         INTEGER,
      er1645v2Lan2MCVlanIpRipRxVer
         INTEGER,
      er1645v2Lan2MCVlanIpRipSplitH
         INTEGER,
      er1645v2Lan2MCVlanIpRipAuth
         INTEGER,
      er1645v2Lan2MCVlanIpRipFilter
         DisplayString,
      er1645v2Lan2MCVlanIpRipFilterIn
         DisplayString,
      er1645v2Lan2MCVlanIpRipClearNextHop
         INTEGER,
      er1645v2Lan2MCVlanIpAccPol
         DisplayString,
      er1645v2Lan2MCVlanIpAB
         DisplayString,
      er1645v2Lan2MCVlanIpMA
         INTEGER,
      er1645v2Lan2MCVlanIpMF
         Integer32,
      er1645v2Lan2MCVlanIpDB
         INTEGER,
      er1645v2Lan2MCVlanIpIR
         INTEGER,
      er1645v2Lan2MCVlanIpIgmp
         INTEGER,
      er1645v2Lan2MCVlanIpNN
         DisplayString,
      er1645v2Lan2MCVlanIpVrrp
         INTEGER,
      er1645v2Lan2MCVlanIpPimMode
         INTEGER,
      er1645v2Lan2MCVlanIpPimDrPriority
         Counter32,
      er1645v2Lan2MCVlanIpPimHelloTime
         TimeTicks,
      er1645v2Lan2MCVlanIpPimPropagationDelay
         TimeTicks,
      er1645v2Lan2MCVlanIpPimOverrideInterval
         TimeTicks,
      er1645v2Lan2MCVlanIpPimBsrBorder
         INTEGER,
      er1645v2Lan2MCVlanIpPimTtlThreshold
         Integer32,
      er1645v2Lan2MCVlanIpIMNetworkUnreachable
         INTEGER,
      er1645v2Lan2MCVlanIpIMHostUnreachable
         INTEGER,
      er1645v2Lan2MCVlanIpIMProtocolUnreachable
         INTEGER,
      er1645v2Lan2MCVlanIpIMPortUnreachable
         INTEGER,
      er1645v2Lan2MCVlanIpIMMtuExceeded
         INTEGER,
      er1645v2Lan2MCVlanIpIMAdminProhibited
         INTEGER,
      er1645v2Lan2MCVlanIpIMTtlExceeded
         INTEGER,
      er1645v2Lan2MCVlanIpIMRedirect
         INTEGER,
      er1645v2Lan2MCVlanIpV6VrfRouter
         DisplayString,
      er1645v2Lan2MCVlanIpV6AddrAutoConfigNrDupAddrDetects
         Integer32,
      er1645v2Lan2MCVlanIpV6AddrAutoConfigAcceptRa
         INTEGER,
      er1645v2Lan2MCVlanIpV6AddrAutoConfigAcceptRaRdnss
         INTEGER,
      er1645v2Lan2MCVlanIpV6AddrAutoConfigAcceptRaDnssl
         INTEGER,
      er1645v2Lan2MCVlanIpV6DefaultRoute
         INTEGER,
      er1645v2Lan2MCVlanIpV6RaSend
         INTEGER,
      er1645v2Lan2MCVlanIpV6RaMinInterval
         TimeTicks,
      er1645v2Lan2MCVlanIpV6RaMaxInterval
         TimeTicks,
      er1645v2Lan2MCVlanIpV6RaManagedFlag
         INTEGER,
      er1645v2Lan2MCVlanIpV6RaOtherConfFlag
         INTEGER,
      er1645v2Lan2MCVlanIpV6RaLinkMtu
         Integer32,
      er1645v2Lan2MCVlanIpV6RaReachableTime
         TimeTicks,
      er1645v2Lan2MCVlanIpV6RaRetransmitTime
         TimeTicks,
      er1645v2Lan2MCVlanIpV6RaHopLimit
         Integer32,
      er1645v2Lan2MCVlanIpV6RaDefaultLifeTime
         TimeTicks,
      er1645v2Lan2MCVlanIpV6RaDnsOptionsRdnssLifeTime
         TimeTicks,
      er1645v2Lan2MCVlanIpV6RaDnsOptionsRdnssImportServers
         INTEGER,
      er1645v2Lan2MCVlanIpV6RaDnsOptionsDnsslLifeTime
         TimeTicks,
      er1645v2Lan2MCVlanIpV6RaDnsOptionsDnsslImportDomains
         INTEGER,
      er1645v2Lan2MCVlanIpV6RsSend
         INTEGER,
      er1645v2Lan2MCVlanIpV6RsMaxRandomDelay
         TimeTicks,
      er1645v2Lan2MCVlanIpV6RsInterval
         TimeTicks,
      er1645v2Lan2MCVlanIpV6RsMaxSolicitations
         Integer32,
      er1645v2Lan2MCVlanIpV6TrafficPolicyInbound
         DisplayString,
      er1645v2Lan2MCVlanIpV6TrafficPolicyOutbound
         DisplayString,
      er1645v2Lan2MCVlanIpV6FirewallZone
         DisplayString,
      er1645v2Lan2MCVlanIpV6DhcpClientAddrAC
         INTEGER,
      er1645v2Lan2MCVlanIpV6DhcpClientPrDelMode
         INTEGER,
      er1645v2Lan2MCVlanIpV6DhcpClientPrDelPool
         DisplayString,
      er1645v2Lan2MCVlanIpV6DhcpClientPrDelPdExclOpt
         INTEGER,
      er1645v2Lan2MCVlanIpV6DhcpClientDnsServerPref
         Integer32,
      er1645v2Lan2MCVlanIpV6DhcpClientRapidCommit
         INTEGER,
      er1645v2Lan2MCVlanIpV6DhcpClientTimersSolTimeOut
         TimeTicks,
      er1645v2Lan2MCVlanIpV6DhcpClientTimersSolMaxRt
         TimeTicks,
      er1645v2Lan2MCVlanIpV6DhcpClientTimersInfoRefresh
         TimeTicks,
      er1645v2Lan2MCVlanIpV6DhcpServerMode
         INTEGER,
      er1645v2Lan2MCVlanIpV6DhcpServerPreference
         Integer32,
      er1645v2Lan2MCVlanIpV6DhcpServerPool
         DisplayString,
      er1645v2Lan2MCVlanIpV6DhcpServerRapidCommit
         INTEGER,
      er1645v2Lan2MCVlanIpV6DhcpServerTimersInfoRefresh
         TimeTicks,
      er1645v2Lan2MCVlanIpV6DhcpRelayMode
         INTEGER,
      er1645v2Lan2MCVlanIpV6SendRedirect
         INTEGER,
      er1645v2Lan2MCVlanIpV6LinkMtu
         Integer32,
      er1645v2Lan2MCVlanIpV6InterfaceId
         OCTET STRING,
      er1645v2Lan2MCVlanIpV6MF
         Integer32,
      er1645v2Lan2MCVlanIpV6IcmpMessagesNoRoute
         INTEGER,
      er1645v2Lan2MCVlanIpV6IcmpMessagesBeyondScope
         INTEGER,
      er1645v2Lan2MCVlanIpV6IcmpMessagesAddressUnreachable
         INTEGER,
      er1645v2Lan2MCVlanIpV6IcmpMessagesPortUnreachable
         INTEGER,
      er1645v2Lan2MCVlanIpV6IcmpMessagesPacketTooBig
         INTEGER,
      er1645v2Lan2MCVlanIpV6IcmpMessagesHopLimitExceeded
         INTEGER,
      er1645v2Lan2MCVlanIpV6IcmpMessagesFragTimeExceeded
         INTEGER,
      er1645v2Lan2MCVlanIpV6IcmpMessagesHeaderFieldErr
         INTEGER,
      er1645v2Lan2MCVlanIpV6IcmpMessagesOptionUnrecognized
         INTEGER,
      er1645v2Lan2MCVlanIpV6IcmpMessagesRedirect
         INTEGER,
      er1645v2Lan2MCVlanBridgingAccList
         DisplayString,
      er1645v2Lan2MCVlanBridgingInACL
         DisplayString,
      er1645v2Lan2MCVlanBridgingTp
         DisplayString,
      er1645v2Lan2MCVlanBridgingBrGrp
         DisplayString,
      er1645v2Lan2MCVlanBridgingLimBC
         INTEGER,
      er1645v2Lan2MCVlanBridgingPrivateMode
         INTEGER,
      er1645v2Lan2MCVlanBridgingLearning
         INTEGER,
      er1645v2Lan2MCVlanBridgingMaxCacheSize
         INTEGER,
      er1645v2Lan2MCVlanBridgingRelearnDropOnRelearn
         INTEGER,
      er1645v2Lan2MCVlanBridgingRelearnShutdownThreshold
         Integer32,
      er1645v2Lan2MCVlanBridgingRelearnShutdownTime
         TimeTicks,
      er1645v2Lan2MCVlanBridgingRelearnLoopDetection
         INTEGER,
      er1645v2Lan2MCVlanBridgingRelearnLoopDetectionInterval
         TimeTicks,
      er1645v2Lan2MCVlanBridgingVlanMemberShip
         INTEGER,
      er1645v2Lan2MCVlanBridgingVlTUntaggedAction
         INTEGER,
      er1645v2Lan2MCVlanBridgingVlTUntaggedTagInfoTpid
         INTEGER,
      er1645v2Lan2MCVlanBridgingVlTUntaggedTagInfoVid
         Integer32,
      er1645v2Lan2MCVlanBridgingVlTUnknownVlansAction
         INTEGER,
      er1645v2Lan2MCVlanBridgingVlTUnknownVlansTagInfoTpid
         INTEGER,
      er1645v2Lan2MCVlanBridgingVlTUnknownVlansTagInfoVid
         Integer32,
      er1645v2Lan2MCVlanBridgingDot1adType
         INTEGER,
      er1645v2Lan2MCVlanBridgingPriority
         Integer32,
      er1645v2Lan2MCVlanBridgingPathCost
         Integer32,
      er1645v2Lan2MCVlanBridgingInternalPathCost
         Integer32,
      er1645v2Lan2MCVlanBridgingTCD
         INTEGER,
      er1645v2Lan2MCVlanBridgingRestrictedRole
         INTEGER,
      er1645v2Lan2MCVlanBridgingAdminEdge
         INTEGER,
      er1645v2Lan2MCVlanBridgingOamMacDeviceMac
         DisplayString,
      er1645v2Lan2MCVlanBridgingOamMacUserMac
         OCTET STRING,
      er1645v2Lan2MCVlanBridgingOamMacBridgeMac
         DisplayString,
      er1645v2Lan2MCVlanBridgingMgmtInline
         INTEGER,
      er1645v2Lan2MCVlanBridgingL2ptMode
         INTEGER,
      er1645v2Lan2MCVlanBridgingL2ptProtocols
         Integer32,
      er1645v2Lan2MCVlanBridgingL2ptDestMac
         OCTET STRING,
      er1645v2Lan2MCVlanBridgingL2ptCos
         INTEGER,
      er1645v2Lan2MCVlanBridgingL2ptDropThrStp
         INTEGER,
      er1645v2Lan2MCVlanBridgingL2ptDropThrLldp
         INTEGER,
      er1645v2Lan2MCVlanBridgingL2ptDropThrOam
         INTEGER,
      er1645v2Lan2MCVlanBridgingL2ptDropThrCdp
         INTEGER,
      er1645v2Lan2MCVlanBridgingL2ptDropThrVtp
         INTEGER,
      er1645v2Lan2MCVlanBridgingL2ptDropThrLacp
         INTEGER,
      er1645v2Lan2MCVlanBridgingL2ptDropThrEfmOam
         INTEGER,
      er1645v2Lan2MCVlanBridgingL2ptDropThrPvst
         INTEGER,
      er1645v2Lan2MCVlanBridgingL2ptDropThrMmrp
         INTEGER,
      er1645v2Lan2MCVlanBridgingL2ptDropThrMvrp
         INTEGER,
      er1645v2Lan2MCVlanBridgingL2ptDropThrGvrp
         INTEGER,
      er1645v2Lan2MCVlanBridgingL2ptDropThrGmrp
         INTEGER,
      er1645v2Lan2MCVlanBridgingL2ptDropThrDtp
         INTEGER,
      er1645v2Lan2MCVlanBridgingL2ptDropThrPagp
         INTEGER,
      er1645v2Lan2MCVlanBridgingL2ptDropThrUdld
         INTEGER,
      er1645v2Lan2MCVlanVlanVid
         INTEGER,
      er1645v2Lan2MCVlanVlanVidExtensionSingle
         OCTET STRING,
      er1645v2Lan2MCVlanVlanVidExtensionEndVid
         Integer32,
      er1645v2Lan2MCVlanVlanTpid
         INTEGER,
      er1645v2Lan2MCVlanVlanTagSign
         INTEGER,
      er1645v2Lan2MCVlanVlanChTos
         INTEGER,
      er1645v2Lan2MCVlanVlanCTMapP0
         INTEGER,
      er1645v2Lan2MCVlanVlanCTMapP1
         INTEGER,
      er1645v2Lan2MCVlanVlanCTMapP2
         INTEGER,
      er1645v2Lan2MCVlanVlanCTMapP3
         INTEGER,
      er1645v2Lan2MCVlanVlanCTMapP4
         INTEGER,
      er1645v2Lan2MCVlanVlanCTMapP5
         INTEGER,
      er1645v2Lan2MCVlanVlanCTMapP6
         INTEGER,
      er1645v2Lan2MCVlanVlanCTMapP7
         INTEGER,
      er1645v2Lan2MCVlanVlanTxCos
         INTEGER,
      er1645v2Lan2MCVlanVlanCCMapP0
         Integer32,
      er1645v2Lan2MCVlanVlanCCMapP1
         Integer32,
      er1645v2Lan2MCVlanVlanCCMapP2
         Integer32,
      er1645v2Lan2MCVlanVlanCCMapP3
         Integer32,
      er1645v2Lan2MCVlanVlanCCMapP4
         Integer32,
      er1645v2Lan2MCVlanVlanCCMapP5
         Integer32,
      er1645v2Lan2MCVlanVlanCCMapP6
         Integer32,
      er1645v2Lan2MCVlanVlanCCMapP7
         Integer32,
      er1645v2Lan2MCVlanVlanQCMapQueue1
         Integer32,
      er1645v2Lan2MCVlanVlanQCMapQueue2
         Integer32,
      er1645v2Lan2MCVlanVlanQCMapQueue3
         Integer32,
      er1645v2Lan2MCVlanVlanQCMapQueue4
         Integer32,
      er1645v2Lan2MCVlanVlanQCMapQueue5
         Integer32,
      er1645v2Lan2MCVlanVlanQCMapLowDelayQueue
         Integer32,
      er1645v2Lan2MCVlanVlanQCMapLowDelay2Queue
         Integer32,
      er1645v2Lan2MCVlanVlanQCMapSystemQueue
         Integer32,
      er1645v2Lan2MCVlanVlanQinQSVid
         Integer32,
      er1645v2Lan2MCVlanVlanQinQSTpid
         INTEGER,
      er1645v2Lan2MCVlanVlanArpTimeOut
         TimeTicks,
      er1645v2Lan2MCVlanVlanArpProxyArp
         INTEGER,
      er1645v2Lan2MCVlanBandwidthMode
         INTEGER,
      er1645v2Lan2MCVlanBandwidthCir
         Integer32,
      er1645v2Lan2MCVlanBandwidthEir
         Integer32,
      er1645v2Lan2MCVlanBandwidthUnit
         INTEGER,
      er1645v2Lan2MCVlanBandwidthTc
         INTEGER,
      er1645v2Lan2MCVlanBandwidthTcFactor
         INTEGER,
      er1645v2Lan2MCVlanBandwidthCorrType
         INTEGER,
      er1645v2Lan2MCVlanBandwidthCorrPredefEncapsFrameRelay
         DisplayString,
      er1645v2Lan2MCVlanBandwidthCorrPredefEncapsPpp
         DisplayString,
      er1645v2Lan2MCVlanBandwidthCorrPredefEncapsAtmHl
         INTEGER,
      er1645v2Lan2MCVlanBandwidthCorrPredefEncapsAtmMp
         INTEGER,
      er1645v2Lan2MCVlanBandwidthCorrPredefEncapsHdlc
         DisplayString,
      er1645v2Lan2MCVlanBandwidthCorrPredefEncapsEfmFs
         Integer32,
      er1645v2Lan2MCVlanBandwidthCorrPredefEncapsEfmIb
         Integer32,
      er1645v2Lan2MCVlanBandwidthCorrPredefMode
         INTEGER,
      er1645v2Lan2MCVlanBandwidthCorrManualOverhead
         Integer32,
      er1645v2Lan2MCVlanBandwidthCorrManualFrameData
         Counter32,
      er1645v2Lan2MCVlanBandwidthCorrManualFrameHeader
         Counter32,
      er1645v2Lan2MCVlanBandwidthMaxFifoQLen
         Integer32,
      er1645v2Lan2MCVlanBandwidthDeFlagCir
         INTEGER,
      er1645v2Lan2MCVlanBandwidthDeFlagEir
         INTEGER,
      er1645v2Lan2MCVlanBandwidthDeFlagViolate
         INTEGER,
      er1645v2Lan2MCVlanBandwidthActCirActNone
         OCTET STRING,
      er1645v2Lan2MCVlanBandwidthActCirActEthCos1
         INTEGER,
      er1645v2Lan2MCVlanBandwidthActCirActEthDei1
         INTEGER,
      er1645v2Lan2MCVlanBandwidthActCirActEthCos2
         INTEGER,
      er1645v2Lan2MCVlanBandwidthActCirActEthDei2
         INTEGER,
      er1645v2Lan2MCVlanBandwidthActCirActEthCos3
         INTEGER,
      er1645v2Lan2MCVlanBandwidthActCirActEthDei3
         INTEGER,
      er1645v2Lan2MCVlanBandwidthActCirActEthCos4
         INTEGER,
      er1645v2Lan2MCVlanBandwidthActCirActEthDei4
         INTEGER,
      er1645v2Lan2MCVlanBandwidthActCirActEthCos5
         INTEGER,
      er1645v2Lan2MCVlanBandwidthActCirActEthDei5
         INTEGER,
      er1645v2Lan2MCVlanBandwidthActCirActEthCos6
         INTEGER,
      er1645v2Lan2MCVlanBandwidthActCirActEthDei6
         INTEGER,
      er1645v2Lan2MCVlanBandwidthActCirActEthCos7
         INTEGER,
      er1645v2Lan2MCVlanBandwidthActCirActEthDei7
         INTEGER,
      er1645v2Lan2MCVlanBandwidthActCirActEthCos8
         INTEGER,
      er1645v2Lan2MCVlanBandwidthActCirActEthDei8
         INTEGER,
      er1645v2Lan2MCVlanBandwidthActCirActEthTos
         INTEGER,
      er1645v2Lan2MCVlanBandwidthActCirActEthQueue
         INTEGER,
      er1645v2Lan2MCVlanBandwidthActCirActEthDrpLev
         INTEGER,
      er1645v2Lan2MCVlanBandwidthActCirActEthDeFlag
         INTEGER,
      er1645v2Lan2MCVlanBandwidthActCirActIpTos
         INTEGER,
      er1645v2Lan2MCVlanBandwidthActCirActIpQueue
         INTEGER,
      er1645v2Lan2MCVlanBandwidthActCirActIpDrpLev
         INTEGER,
      er1645v2Lan2MCVlanBandwidthActCirActIpDeFlag
         INTEGER,
      er1645v2Lan2MCVlanBandwidthActEirActNone
         OCTET STRING,
      er1645v2Lan2MCVlanBandwidthActEirActEthCos1
         INTEGER,
      er1645v2Lan2MCVlanBandwidthActEirActEthDei1
         INTEGER,
      er1645v2Lan2MCVlanBandwidthActEirActEthCos2
         INTEGER,
      er1645v2Lan2MCVlanBandwidthActEirActEthDei2
         INTEGER,
      er1645v2Lan2MCVlanBandwidthActEirActEthCos3
         INTEGER,
      er1645v2Lan2MCVlanBandwidthActEirActEthDei3
         INTEGER,
      er1645v2Lan2MCVlanBandwidthActEirActEthCos4
         INTEGER,
      er1645v2Lan2MCVlanBandwidthActEirActEthDei4
         INTEGER,
      er1645v2Lan2MCVlanBandwidthActEirActEthCos5
         INTEGER,
      er1645v2Lan2MCVlanBandwidthActEirActEthDei5
         INTEGER,
      er1645v2Lan2MCVlanBandwidthActEirActEthCos6
         INTEGER,
      er1645v2Lan2MCVlanBandwidthActEirActEthDei6
         INTEGER,
      er1645v2Lan2MCVlanBandwidthActEirActEthCos7
         INTEGER,
      er1645v2Lan2MCVlanBandwidthActEirActEthDei7
         INTEGER,
      er1645v2Lan2MCVlanBandwidthActEirActEthCos8
         INTEGER,
      er1645v2Lan2MCVlanBandwidthActEirActEthDei8
         INTEGER,
      er1645v2Lan2MCVlanBandwidthActEirActEthTos
         INTEGER,
      er1645v2Lan2MCVlanBandwidthActEirActEthQueue
         INTEGER,
      er1645v2Lan2MCVlanBandwidthActEirActEthDrpLev
         INTEGER,
      er1645v2Lan2MCVlanBandwidthActEirActEthDeFlag
         INTEGER,
      er1645v2Lan2MCVlanBandwidthActEirActIpTos
         INTEGER,
      er1645v2Lan2MCVlanBandwidthActEirActIpQueue
         INTEGER,
      er1645v2Lan2MCVlanBandwidthActEirActIpDrpLev
         INTEGER,
      er1645v2Lan2MCVlanBandwidthActEirActIpDeFlag
         INTEGER,
      er1645v2Lan2MCVlanBandwidthActViolActNone
         OCTET STRING,
      er1645v2Lan2MCVlanBandwidthActViolActDrop
         OCTET STRING,
      er1645v2Lan2MCVlanBandwidthActViolActEthCos1
         INTEGER,
      er1645v2Lan2MCVlanBandwidthActViolActEthDei1
         INTEGER,
      er1645v2Lan2MCVlanBandwidthActViolActEthCos2
         INTEGER,
      er1645v2Lan2MCVlanBandwidthActViolActEthDei2
         INTEGER,
      er1645v2Lan2MCVlanBandwidthActViolActEthCos3
         INTEGER,
      er1645v2Lan2MCVlanBandwidthActViolActEthDei3
         INTEGER,
      er1645v2Lan2MCVlanBandwidthActViolActEthCos4
         INTEGER,
      er1645v2Lan2MCVlanBandwidthActViolActEthDei4
         INTEGER,
      er1645v2Lan2MCVlanBandwidthActViolActEthCos5
         INTEGER,
      er1645v2Lan2MCVlanBandwidthActViolActEthDei5
         INTEGER,
      er1645v2Lan2MCVlanBandwidthActViolActEthCos6
         INTEGER,
      er1645v2Lan2MCVlanBandwidthActViolActEthDei6
         INTEGER,
      er1645v2Lan2MCVlanBandwidthActViolActEthCos7
         INTEGER,
      er1645v2Lan2MCVlanBandwidthActViolActEthDei7
         INTEGER,
      er1645v2Lan2MCVlanBandwidthActViolActEthCos8
         INTEGER,
      er1645v2Lan2MCVlanBandwidthActViolActEthDei8
         INTEGER,
      er1645v2Lan2MCVlanBandwidthActViolActEthTos
         INTEGER,
      er1645v2Lan2MCVlanBandwidthActViolActEthQueue
         INTEGER,
      er1645v2Lan2MCVlanBandwidthActViolActEthDrpLev
         INTEGER,
      er1645v2Lan2MCVlanBandwidthActViolActEthDeFlag
         INTEGER,
      er1645v2Lan2MCVlanBandwidthActViolActIpTos
         INTEGER,
      er1645v2Lan2MCVlanBandwidthActViolActIpQueue
         INTEGER,
      er1645v2Lan2MCVlanBandwidthActViolActIpDrpLev
         INTEGER,
      er1645v2Lan2MCVlanBandwidthActViolActIpDeFlag
         INTEGER,
      er1645v2Lan2MCVlanInbBwMode
         INTEGER,
      er1645v2Lan2MCVlanInbBwCir
         Integer32,
      er1645v2Lan2MCVlanInbBwEir
         Integer32,
      er1645v2Lan2MCVlanInbBwUnit
         INTEGER,
      er1645v2Lan2MCVlanInbBwTc
         INTEGER,
      er1645v2Lan2MCVlanInbBwTcFactor
         INTEGER,
      er1645v2Lan2MCVlanInbBwCorrType
         INTEGER,
      er1645v2Lan2MCVlanInbBwCorrPredefEncapsFrameRelay
         DisplayString,
      er1645v2Lan2MCVlanInbBwCorrPredefEncapsPpp
         DisplayString,
      er1645v2Lan2MCVlanInbBwCorrPredefEncapsAtmHl
         INTEGER,
      er1645v2Lan2MCVlanInbBwCorrPredefEncapsAtmMp
         INTEGER,
      er1645v2Lan2MCVlanInbBwCorrPredefEncapsHdlc
         DisplayString,
      er1645v2Lan2MCVlanInbBwCorrPredefEncapsEfmFs
         Integer32,
      er1645v2Lan2MCVlanInbBwCorrPredefEncapsEfmIb
         Integer32,
      er1645v2Lan2MCVlanInbBwCorrPredefMode
         INTEGER,
      er1645v2Lan2MCVlanInbBwCorrManualOverhead
         Integer32,
      er1645v2Lan2MCVlanInbBwCorrManualFrameData
         Counter32,
      er1645v2Lan2MCVlanInbBwCorrManualFrameHeader
         Counter32,
      er1645v2Lan2MCVlanInbBwMaxFifoQLen
         Integer32,
      er1645v2Lan2MCVlanInbBwPriorityPolicy
         DisplayString,
      er1645v2Lan2MCVlanInbBwDeFlagCir
         INTEGER,
      er1645v2Lan2MCVlanInbBwDeFlagEir
         INTEGER,
      er1645v2Lan2MCVlanInbBwDeFlagViolate
         INTEGER,
      er1645v2Lan2MCVlanInbBwActCirActNone
         OCTET STRING,
      er1645v2Lan2MCVlanInbBwActCirActEthCos1
         INTEGER,
      er1645v2Lan2MCVlanInbBwActCirActEthDei1
         INTEGER,
      er1645v2Lan2MCVlanInbBwActCirActEthCos2
         INTEGER,
      er1645v2Lan2MCVlanInbBwActCirActEthDei2
         INTEGER,
      er1645v2Lan2MCVlanInbBwActCirActEthCos3
         INTEGER,
      er1645v2Lan2MCVlanInbBwActCirActEthDei3
         INTEGER,
      er1645v2Lan2MCVlanInbBwActCirActEthCos4
         INTEGER,
      er1645v2Lan2MCVlanInbBwActCirActEthDei4
         INTEGER,
      er1645v2Lan2MCVlanInbBwActCirActEthCos5
         INTEGER,
      er1645v2Lan2MCVlanInbBwActCirActEthDei5
         INTEGER,
      er1645v2Lan2MCVlanInbBwActCirActEthCos6
         INTEGER,
      er1645v2Lan2MCVlanInbBwActCirActEthDei6
         INTEGER,
      er1645v2Lan2MCVlanInbBwActCirActEthCos7
         INTEGER,
      er1645v2Lan2MCVlanInbBwActCirActEthDei7
         INTEGER,
      er1645v2Lan2MCVlanInbBwActCirActEthCos8
         INTEGER,
      er1645v2Lan2MCVlanInbBwActCirActEthDei8
         INTEGER,
      er1645v2Lan2MCVlanInbBwActCirActEthTos
         INTEGER,
      er1645v2Lan2MCVlanInbBwActCirActEthQueue
         INTEGER,
      er1645v2Lan2MCVlanInbBwActCirActEthDrpLev
         INTEGER,
      er1645v2Lan2MCVlanInbBwActCirActEthDeFlag
         INTEGER,
      er1645v2Lan2MCVlanInbBwActCirActIpTos
         INTEGER,
      er1645v2Lan2MCVlanInbBwActCirActIpQueue
         INTEGER,
      er1645v2Lan2MCVlanInbBwActCirActIpDrpLev
         INTEGER,
      er1645v2Lan2MCVlanInbBwActCirActIpDeFlag
         INTEGER,
      er1645v2Lan2MCVlanInbBwActEirActNone
         OCTET STRING,
      er1645v2Lan2MCVlanInbBwActEirActEthCos1
         INTEGER,
      er1645v2Lan2MCVlanInbBwActEirActEthDei1
         INTEGER,
      er1645v2Lan2MCVlanInbBwActEirActEthCos2
         INTEGER,
      er1645v2Lan2MCVlanInbBwActEirActEthDei2
         INTEGER,
      er1645v2Lan2MCVlanInbBwActEirActEthCos3
         INTEGER,
      er1645v2Lan2MCVlanInbBwActEirActEthDei3
         INTEGER,
      er1645v2Lan2MCVlanInbBwActEirActEthCos4
         INTEGER,
      er1645v2Lan2MCVlanInbBwActEirActEthDei4
         INTEGER,
      er1645v2Lan2MCVlanInbBwActEirActEthCos5
         INTEGER,
      er1645v2Lan2MCVlanInbBwActEirActEthDei5
         INTEGER,
      er1645v2Lan2MCVlanInbBwActEirActEthCos6
         INTEGER,
      er1645v2Lan2MCVlanInbBwActEirActEthDei6
         INTEGER,
      er1645v2Lan2MCVlanInbBwActEirActEthCos7
         INTEGER,
      er1645v2Lan2MCVlanInbBwActEirActEthDei7
         INTEGER,
      er1645v2Lan2MCVlanInbBwActEirActEthCos8
         INTEGER,
      er1645v2Lan2MCVlanInbBwActEirActEthDei8
         INTEGER,
      er1645v2Lan2MCVlanInbBwActEirActEthTos
         INTEGER,
      er1645v2Lan2MCVlanInbBwActEirActEthQueue
         INTEGER,
      er1645v2Lan2MCVlanInbBwActEirActEthDrpLev
         INTEGER,
      er1645v2Lan2MCVlanInbBwActEirActEthDeFlag
         INTEGER,
      er1645v2Lan2MCVlanInbBwActEirActIpTos
         INTEGER,
      er1645v2Lan2MCVlanInbBwActEirActIpQueue
         INTEGER,
      er1645v2Lan2MCVlanInbBwActEirActIpDrpLev
         INTEGER,
      er1645v2Lan2MCVlanInbBwActEirActIpDeFlag
         INTEGER,
      er1645v2Lan2MCVlanInbBwActViolActNone
         OCTET STRING,
      er1645v2Lan2MCVlanInbBwActViolActDrop
         OCTET STRING,
      er1645v2Lan2MCVlanInbBwActViolActEthCos1
         INTEGER,
      er1645v2Lan2MCVlanInbBwActViolActEthDei1
         INTEGER,
      er1645v2Lan2MCVlanInbBwActViolActEthCos2
         INTEGER,
      er1645v2Lan2MCVlanInbBwActViolActEthDei2
         INTEGER,
      er1645v2Lan2MCVlanInbBwActViolActEthCos3
         INTEGER,
      er1645v2Lan2MCVlanInbBwActViolActEthDei3
         INTEGER,
      er1645v2Lan2MCVlanInbBwActViolActEthCos4
         INTEGER,
      er1645v2Lan2MCVlanInbBwActViolActEthDei4
         INTEGER,
      er1645v2Lan2MCVlanInbBwActViolActEthCos5
         INTEGER,
      er1645v2Lan2MCVlanInbBwActViolActEthDei5
         INTEGER,
      er1645v2Lan2MCVlanInbBwActViolActEthCos6
         INTEGER,
      er1645v2Lan2MCVlanInbBwActViolActEthDei6
         INTEGER,
      er1645v2Lan2MCVlanInbBwActViolActEthCos7
         INTEGER,
      er1645v2Lan2MCVlanInbBwActViolActEthDei7
         INTEGER,
      er1645v2Lan2MCVlanInbBwActViolActEthCos8
         INTEGER,
      er1645v2Lan2MCVlanInbBwActViolActEthDei8
         INTEGER,
      er1645v2Lan2MCVlanInbBwActViolActEthTos
         INTEGER,
      er1645v2Lan2MCVlanInbBwActViolActEthQueue
         INTEGER,
      er1645v2Lan2MCVlanInbBwActViolActEthDrpLev
         INTEGER,
      er1645v2Lan2MCVlanInbBwActViolActEthDeFlag
         INTEGER,
      er1645v2Lan2MCVlanInbBwActViolActIpTos
         INTEGER,
      er1645v2Lan2MCVlanInbBwActViolActIpQueue
         INTEGER,
      er1645v2Lan2MCVlanInbBwActViolActIpDrpLev
         INTEGER,
      er1645v2Lan2MCVlanInbBwActViolActIpDeFlag
         INTEGER,
      er1645v2Lan2MCVlanPppoE
         INTEGER,
      er1645v2Lan2MCVlanPppLnkMOperation
         INTEGER,
      er1645v2Lan2MCVlanPppLnkMInterval
         TimeTicks,
      er1645v2Lan2MCVlanPppLnkMRepTimeOut
         TimeTicks,
      er1645v2Lan2MCVlanPppLnkMFailsPrmt
         Integer32,
      er1645v2Lan2MCVlanPppAuthentication
         INTEGER,
      er1645v2Lan2MCVlanPppAuthenPeriod
         TimeTicks,
      er1645v2Lan2MCVlanPppSessionName
         DisplayString,
      er1645v2Lan2MCVlanPppSessionSecret
         DisplayString,
      er1645v2Lan2MCVlanPppEncModeSessionSecret
         INTEGER,
      er1645v2Lan2MCVlanPppEncSessionSecret
         DisplayString,
      er1645v2Lan2MCVlanPppServiceName
         DisplayString,
      er1645v2Lan2MCVlanPbbMode
         INTEGER,
      er1645v2Lan2MCVlanPbbTxCos
         Integer32,
      er1645v2Lan2MCVlanPbbIsid
         Integer32,
      er1645v2Lan2MCVlanPbbDestMac
         OCTET STRING,
      er1645v2Lan2MCVlanPbbCustomGroupMac
         OCTET STRING
      }

er1645v2Lan2MCVlanActions OBJECT-TYPE
   SYNTAX      VariableLengthTableActions
   MAX-ACCESS  read-write
   STATUS      current
   DESCRIPTION
      "By way of this field, some manipulations
       on this table may be performed."
   ::= {er1645v2Lan2MCVlanEntry 2}

er1645v2Lan2MCVlanTableIx OBJECT-TYPE
   SYNTAX      TableIndex
   MAX-ACCESS  not-accessible
   STATUS      current
   DESCRIPTION
      ""
   ::= {er1645v2Lan2MCVlanEntry 11}

er1645v2Lan2MCVlanName OBJECT-TYPE
   SYNTAX      DisplayString
   MAX-ACCESS  read-write
   STATUS      current
   DESCRIPTION
      "Path: ethernet2.editConf.vlan.name"
   ::= {er1645v2Lan2MCVlanEntry 16777216}

er1645v2Lan2MCVlanRemark OBJECT-TYPE
   SYNTAX      DisplayString
   MAX-ACCESS  read-write
   STATUS      current
   DESCRIPTION
      "Path: ethernet2.editConf.vlan.remark"
   ::= {er1645v2Lan2MCVlanEntry 1157627904}

er1645v2Lan2MCVlanAdminStatus OBJECT-TYPE
   SYNTAX      INTEGER
               {
               up (1),
               down (2)
               }
   MAX-ACCESS  read-write
   STATUS      current
   DESCRIPTION
      "Path: ethernet2.editConf.vlan.adminStatus

       Possibilities:
               up   (1)
               down   (2)"
   ::= {er1645v2Lan2MCVlanEntry 33554432}

er1645v2Lan2MCVlanMode OBJECT-TYPE
   SYNTAX      INTEGER
               {
               routing (1),
               bridging (2),
               ipV6 (16),
               ipV6ipV4 (17),
               multilink (8)
               }
   MAX-ACCESS  read-write
   STATUS      current
   DESCRIPTION
      "Path: ethernet2.editConf.vlan.mode

       Possibilities:
               routing   (1)
               bridging   (2)
               ipV6   (16)
               ipV6/ipV4   (17)
               multilink   (8)"
   ::= {er1645v2Lan2MCVlanEntry 67108864}

er1645v2Lan2MCVlanPriorityPolicy OBJECT-TYPE
   SYNTAX      DisplayString
   MAX-ACCESS  read-write
   STATUS      current
   DESCRIPTION
      "Path: ethernet2.editConf.vlan.priorityPolicy"
   ::= {er1645v2Lan2MCVlanEntry 83886080}

er1645v2Lan2MCVlanIpVrfRouter OBJECT-TYPE
   SYNTAX      DisplayString
   MAX-ACCESS  read-write
   STATUS      current
   DESCRIPTION
      "Path: ethernet2.editConf.vlan.ip.vrfRouter"
   ::= {er1645v2Lan2MCVlanEntry 53215232}

er1645v2Lan2MCVlanIpAdr OBJECT-TYPE
   SYNTAX      IpAddress
   MAX-ACCESS  read-write
   STATUS      current
   DESCRIPTION
      "Path: ethernet2.editConf.vlan.ip.address"
   ::= {er1645v2Lan2MCVlanEntry 58261504}

er1645v2Lan2MCVlanIpNetm OBJECT-TYPE
   SYNTAX      IpAddress
   MAX-ACCESS  read-write
   STATUS      current
   DESCRIPTION
      "Path: ethernet2.editConf.vlan.ip.netMask"
   ::= {er1645v2Lan2MCVlanEntry 58392576}

er1645v2Lan2MCVlanIpSNetName OBJECT-TYPE
   SYNTAX      INTEGER
               {
               slOPTg (0),
               corp (2),
               dmz (3),
               internet (1)
               }
   MAX-ACCESS  read-write
   STATUS      current
   DESCRIPTION
      "Path: ethernet2.editConf.vlan.ip.sNet.name

       Possibilities:
               <OPT>   (0)
               corp   (2)
               dmz   (3)
               internet   (1)"
   ::= {er1645v2Lan2MCVlanEntry 53674240}

er1645v2Lan2MCVlanIpSNetCust OBJECT-TYPE
   SYNTAX      DisplayString
   MAX-ACCESS  read-write
   STATUS      current
   DESCRIPTION
      "Path: ethernet2.editConf.vlan.ip.sNet.custom"
   ::= {er1645v2Lan2MCVlanEntry 53674496}

er1645v2Lan2MCVlanIpDhcpC OBJECT-TYPE
   SYNTAX      INTEGER
               {
               disabled (0),
               enabled (1)
               }
   MAX-ACCESS  read-write
   STATUS      current
   DESCRIPTION
      "Path: ethernet2.editConf.vlan.ip.dhcpClient

       Possibilities:
               disabled   (0)
               enabled   (1)"
   ::= {er1645v2Lan2MCVlanEntry 53608448}

er1645v2Lan2MCVlanIpDhcpGatewayPreference OBJECT-TYPE
   SYNTAX      Integer32
   MAX-ACCESS  read-write
   STATUS      current
   DESCRIPTION
      "Path: ethernet2.editConf.vlan.ip.dhcp.gatewayPreference"
   ::= {er1645v2Lan2MCVlanEntry 53739776}

er1645v2Lan2MCVlanIpDhcpRoutePreference OBJECT-TYPE
   SYNTAX      Integer32
   MAX-ACCESS  read-write
   STATUS      current
   DESCRIPTION
      "Path: ethernet2.editConf.vlan.ip.dhcp.routePreference"
   ::= {er1645v2Lan2MCVlanEntry 53740032}

er1645v2Lan2MCVlanIpDhcpDnsPreference OBJECT-TYPE
   SYNTAX      Integer32
   MAX-ACCESS  read-write
   STATUS      current
   DESCRIPTION
      "Path: ethernet2.editConf.vlan.ip.dhcp.dnsPreference"
   ::= {er1645v2Lan2MCVlanEntry 53740288}

er1645v2Lan2MCVlanIpMtu OBJECT-TYPE
   SYNTAX      Integer32
   MAX-ACCESS  read-write
   STATUS      current
   DESCRIPTION
      "Path: ethernet2.editConf.vlan.ip.mtu"
   ::= {er1645v2Lan2MCVlanEntry 52953088}

er1645v2Lan2MCVlanIpMssAdjust OBJECT-TYPE
   SYNTAX      INTEGER
               {
               disabled (0),
               auto (65536)
               }
   MAX-ACCESS  read-write
   STATUS      current
   DESCRIPTION
      "Path: ethernet2.editConf.vlan.ip.mssAdjust

       Possibilities:
               disabled   (0)
               auto   (65536)"
   ::= {er1645v2Lan2MCVlanEntry 53280768}

er1645v2Lan2MCVlanIpRipMetric OBJECT-TYPE
   SYNTAX      Integer32
   MAX-ACCESS  read-write
   STATUS      current
   DESCRIPTION
      "Path: ethernet2.editConf.vlan.ip.rip.metric"
   ::= {er1645v2Lan2MCVlanEntry 51712768}

er1645v2Lan2MCVlanIpRipMetricOut OBJECT-TYPE
   SYNTAX      Integer32
   MAX-ACCESS  read-write
   STATUS      current
   DESCRIPTION
      "Path: ethernet2.editConf.vlan.ip.rip.metricOut"
   ::= {er1645v2Lan2MCVlanEntry 51713024}

er1645v2Lan2MCVlanIpRipMode OBJECT-TYPE
   SYNTAX      INTEGER
               {
               disabled (0),
               passive (1),
               active (2)
               }
   MAX-ACCESS  read-write
   STATUS      current
   DESCRIPTION
      "Path: ethernet2.editConf.vlan.ip.rip.mode

       Possibilities:
               disabled   (0)
               passive   (1)
               active   (2)"
   ::= {er1645v2Lan2MCVlanEntry 51713280}

er1645v2Lan2MCVlanIpRipTxVer OBJECT-TYPE
   SYNTAX      INTEGER
               {
               rip1 (0),
               rip2 (1),
               rip1mcompatible (2)
               }
   MAX-ACCESS  read-write
   STATUS      current
   DESCRIPTION
      "Path: ethernet2.editConf.vlan.ip.rip.txVersion

       Possibilities:
               rip1   (0)
               rip2   (1)
               rip1-compatible   (2)"
   ::= {er1645v2Lan2MCVlanEntry 51716864}

er1645v2Lan2MCVlanIpRipRxVer OBJECT-TYPE
   SYNTAX      INTEGER
               {
               rip1only (0),
               rip2only (1),
               rip12 (2)
               }
   MAX-ACCESS  read-write
   STATUS      current
   DESCRIPTION
      "Path: ethernet2.editConf.vlan.ip.rip.rxVersion

       Possibilities:
               rip1only   (0)
               rip2only   (1)
               rip1&2   (2)"
   ::= {er1645v2Lan2MCVlanEntry 51717120}

er1645v2Lan2MCVlanIpRipSplitH OBJECT-TYPE
   SYNTAX      INTEGER
               {
               disabled (0),
               enabled (1),
               poisonedReverse (2)
               }
   MAX-ACCESS  read-write
   STATUS      current
   DESCRIPTION
      "Path: ethernet2.editConf.vlan.ip.rip.splitHorizon

       Possibilities:
               disabled   (0)
               enabled   (1)
               poisonedReverse   (2)"
   ::= {er1645v2Lan2MCVlanEntry 51713792}

er1645v2Lan2MCVlanIpRipAuth OBJECT-TYPE
   SYNTAX      INTEGER
               {
               disabled (0),
               texts (1),
               md5 (2)
               }
   MAX-ACCESS  read-write
   STATUS      current
   DESCRIPTION
      "Path: ethernet2.editConf.vlan.ip.rip.authentication

       Possibilities:
               disabled   (0)
               text    (1)
               md5   (2)"
   ::= {er1645v2Lan2MCVlanEntry 51712512}

er1645v2Lan2MCVlanIpRipFilter OBJECT-TYPE
   SYNTAX      DisplayString
   MAX-ACCESS  read-write
   STATUS      current
   DESCRIPTION
      "Path: ethernet2.editConf.vlan.ip.rip.filter"
   ::= {er1645v2Lan2MCVlanEntry 51716096}

er1645v2Lan2MCVlanIpRipFilterIn OBJECT-TYPE
   SYNTAX      DisplayString
   MAX-ACCESS  read-write
   STATUS      current
   DESCRIPTION
      "Path: ethernet2.editConf.vlan.ip.rip.filterIn"
   ::= {er1645v2Lan2MCVlanEntry 51716352}

er1645v2Lan2MCVlanIpRipClearNextHop OBJECT-TYPE
   SYNTAX      INTEGER
               {
               disabled (0),
               enabled (1)
               }
   MAX-ACCESS  read-write
   STATUS      current
   DESCRIPTION
      "Path: ethernet2.editConf.vlan.ip.rip.clearNextHop

       Possibilities:
               disabled   (0)
               enabled   (1)"
   ::= {er1645v2Lan2MCVlanEntry 51708416}

er1645v2Lan2MCVlanIpAccPol OBJECT-TYPE
   SYNTAX      DisplayString
   MAX-ACCESS  read-write
   STATUS      current
   DESCRIPTION
      "Path: ethernet2.editConf.vlan.ip.accessPolicy"
   ::= {er1645v2Lan2MCVlanEntry 53084160}

er1645v2Lan2MCVlanIpAB OBJECT-TYPE
   SYNTAX      DisplayString
   MAX-ACCESS  read-write
   STATUS      current
   DESCRIPTION
      "Path: ethernet2.editConf.vlan.ip.trafficPolicy"
   ::= {er1645v2Lan2MCVlanEntry 51249152}

er1645v2Lan2MCVlanIpMA OBJECT-TYPE
   SYNTAX      INTEGER
               {
               disabled (0),
               enabled (1)
               }
   MAX-ACCESS  read-write
   STATUS      current
   DESCRIPTION
      "Path: ethernet2.editConf.vlan.ip.mgmtAccess

       Possibilities:
               disabled   (0)
               enabled   (1)"
   ::= {er1645v2Lan2MCVlanEntry 51380224}

er1645v2Lan2MCVlanIpMF OBJECT-TYPE
   SYNTAX      Integer32
   MAX-ACCESS  read-write
   STATUS      current
   DESCRIPTION
      "Path: ethernet2.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2MCVlanEntry 51445760}

er1645v2Lan2MCVlanIpDB OBJECT-TYPE
   SYNTAX      INTEGER
               {
               disabled (0),
               enabled (1)
               }
   MAX-ACCESS  read-write
   STATUS      current
   DESCRIPTION
      "Path: ethernet2.editConf.vlan.ip.directedBroadcasts

       Possibilities:
               disabled   (0)
               enabled   (1)"
   ::= {er1645v2Lan2MCVlanEntry 51773440}

er1645v2Lan2MCVlanIpIR OBJECT-TYPE
   SYNTAX      INTEGER
               {
               disabled (0),
               enabled (1)
               }
   MAX-ACCESS  read-write
   STATUS      current
   DESCRIPTION
      "Path: ethernet2.editConf.vlan.ip.icmpRedirects

       Possibilities:
               disabled   (0)
               enabled   (1)"
   ::= {er1645v2Lan2MCVlanEntry 52035584}

er1645v2Lan2MCVlanIpIgmp OBJECT-TYPE
   SYNTAX      INTEGER
               {
               disabled (0),
               proxy (1),
               router (2),
               v3Router (5)
               }
   MAX-ACCESS  read-write
   STATUS      current
   DESCRIPTION
      "Path: ethernet2.editConf.vlan.ip.igmp

       Possibilities:
               disabled   (0)
               proxy   (1)
               router   (2)
               v3Router   (5)"
   ::= {er1645v2Lan2MCVlanEntry 52428800}

er1645v2Lan2MCVlanIpNN OBJECT-TYPE
   SYNTAX      DisplayString
   MAX-ACCESS  read-write
   STATUS      current
   DESCRIPTION
      "Path: ethernet2.editConf.vlan.ip.nat"
   ::= {er1645v2Lan2MCVlanEntry 52101120}

er1645v2Lan2MCVlanIpVrrp OBJECT-TYPE
   SYNTAX      INTEGER
               {
               disabled (0),
               enabled (1)
               }
   MAX-ACCESS  read-write
   STATUS      current
   DESCRIPTION
      "Path: ethernet2.editConf.vlan.ip.vrrp

       Possibilities:
               disabled   (0)
               enabled   (1)"
   ::= {er1645v2Lan2MCVlanEntry 53149696}

er1645v2Lan2MCVlanIpPimMode OBJECT-TYPE
   SYNTAX      INTEGER
               {
               disabled (0),
               sparse (1),
               passive (2)
               }
   MAX-ACCESS  read-write
   STATUS      current
   DESCRIPTION
      "Path: ethernet2.editConf.vlan.ip.pim.mode

       Possibilities:
               disabled   (0)
               sparse   (1)
               passive   (2)"
   ::= {er1645v2Lan2MCVlanEntry 53346560}

er1645v2Lan2MCVlanIpPimDrPriority OBJECT-TYPE
   SYNTAX      Counter32
   MAX-ACCESS  read-write
   STATUS      current
   DESCRIPTION
      "Path: ethernet2.editConf.vlan.ip.pim.drPriority

       32 bit unsigned wrappable counter."
   ::= {er1645v2Lan2MCVlanEntry 53346816}

er1645v2Lan2MCVlanIpPimHelloTime OBJECT-TYPE
   SYNTAX      TimeTicks
   MAX-ACCESS  read-write
   STATUS      current
   DESCRIPTION
      "Path: ethernet2.editConf.vlan.ip.pim.helloTime

       Time in centi-second."
   ::= {er1645v2Lan2MCVlanEntry 53347072}

er1645v2Lan2MCVlanIpPimPropagationDelay OBJECT-TYPE
   SYNTAX      TimeTicks
   MAX-ACCESS  read-write
   STATUS      current
   DESCRIPTION
      "Path: ethernet2.editConf.vlan.ip.pim.propagationDelay

       Time in centi-second."
   ::= {er1645v2Lan2MCVlanEntry 53347328}

er1645v2Lan2MCVlanIpPimOverrideInterval OBJECT-TYPE
   SYNTAX      TimeTicks
   MAX-ACCESS  read-write
   STATUS      current
   DESCRIPTION
      "Path: ethernet2.editConf.vlan.ip.pim.overrideInterval

       Time in centi-second."
   ::= {er1645v2Lan2MCVlanEntry 53347584}

er1645v2Lan2MCVlanIpPimBsrBorder OBJECT-TYPE
   SYNTAX      INTEGER
               {
               disabled (0),
               enabled (1)
               }
   MAX-ACCESS  read-write
   STATUS      current
   DESCRIPTION
      "Path: ethernet2.editConf.vlan.ip.pim.bsrBorder

       Possibilities:
               disabled   (0)
               enabled   (1)"
   ::= {er1645v2Lan2MCVlanEntry 53347840}

er1645v2Lan2MCVlanIpPimTtlThreshold OBJECT-TYPE
   SYNTAX      Integer32
   MAX-ACCESS  read-write
   STATUS      current
   DESCRIPTION
      "Path: ethernet2.editConf.vlan.ip.pim.ttlThreshold"
   ::= {er1645v2Lan2MCVlanEntry 53348096}

er1645v2Lan2MCVlanIpIMNetworkUnreachable OBJECT-TYPE
   SYNTAX      INTEGER
               {
               disabled (0),
               enabled (1)
               }
   MAX-ACCESS  read-write
   STATUS      current
   DESCRIPTION
      "Path: ethernet2.editConf.vlan.ip.icmpMessages.networkUnreachable

       Possibilities:
               disabled   (0)
               enabled   (1)"
   ::= {er1645v2Lan2MCVlanEntry 53412096}

er1645v2Lan2MCVlanIpIMHostUnreachable OBJECT-TYPE
   SYNTAX      INTEGER
               {
               disabled (0),
               enabled (1)
               }
   MAX-ACCESS  read-write
   STATUS      current
   DESCRIPTION
      "Path: ethernet2.editConf.vlan.ip.icmpMessages.hostUnreachable

       Possibilities:
               disabled   (0)
               enabled   (1)"
   ::= {er1645v2Lan2MCVlanEntry 53412352}

er1645v2Lan2MCVlanIpIMProtocolUnreachable OBJECT-TYPE
   SYNTAX      INTEGER
               {
               disabled (0),
               enabled (1)
               }
   MAX-ACCESS  read-write
   STATUS      current
   DESCRIPTION
      "Path: ethernet2.editConf.vlan.ip.icmpMessages.protocolUnreachable

       Possibilities:
               disabled   (0)
               enabled   (1)"
   ::= {er1645v2Lan2MCVlanEntry 53412608}

er1645v2Lan2MCVlanIpIMPortUnreachable OBJECT-TYPE
   SYNTAX      INTEGER
               {
               disabled (0),
               enabled (1)
               }
   MAX-ACCESS  read-write
   STATUS      current
   DESCRIPTION
      "Path: ethernet2.editConf.vlan.ip.icmpMessages.portUnreachable

       Possibilities:
               disabled   (0)
               enabled   (1)"
   ::= {er1645v2Lan2MCVlanEntry 53412864}

er1645v2Lan2MCVlanIpIMMtuExceeded OBJECT-TYPE
   SYNTAX      INTEGER
               {
               disabled (0),
               enabled (1)
               }
   MAX-ACCESS  read-write
   STATUS      current
   DESCRIPTION
      "Path: ethernet2.editConf.vlan.ip.icmpMessages.mtuExceeded

       Possibilities:
               disabled   (0)
               enabled   (1)"
   ::= {er1645v2Lan2MCVlanEntry 53413120}

er1645v2Lan2MCVlanIpIMAdminProhibited OBJECT-TYPE
   SYNTAX      INTEGER
               {
               disabled (0),
               enabled (1)
               }
   MAX-ACCESS  read-write
   STATUS      current
   DESCRIPTION
      "Path: ethernet2.editConf.vlan.ip.icmpMessages.adminProhibited

       Possibilities:
               disabled   (0)
               enabled   (1)"
   ::= {er1645v2Lan2MCVlanEntry 53413376}

er1645v2Lan2MCVlanIpIMTtlExceeded OBJECT-TYPE
   SYNTAX      INTEGER
               {
               disabled (0),
               enabled (1)
               }
   MAX-ACCESS  read-write
   STATUS      current
   DESCRIPTION
      "Path: ethernet2.editConf.vlan.ip.icmpMessages.ttlExceeded

       Possibilities:
               disabled   (0)
               enabled   (1)"
   ::= {er1645v2Lan2MCVlanEntry 53413632}

er1645v2Lan2MCVlanIpIMRedirect OBJECT-TYPE
   SYNTAX      INTEGER
               {
               disabled (0),
               enabled (1)
               }
   MAX-ACCESS  read-write
   STATUS      current
   DESCRIPTION
      "Path: ethernet2.editConf.vlan.ip.icmpMessages.redirect

       Possibilities:
               disabled   (0)
               enabled   (1)"
   ::= {er1645v2Lan2MCVlanEntry 53413888}

er1645v2Lan2MCVlanIpV6VrfRouter OBJECT-TYPE
   SYNTAX      DisplayString
   MAX-ACCESS  read-write
   STATUS      current
   DESCRIPTION
      "Path: ethernet2.editConf.vlan.ipV6.vrfRouter"
   ::= {er1645v2Lan2MCVlanEntry 704708608}

er1645v2Lan2MCVlanIpV6AddrAutoConfigNrDupAddrDetects OBJECT-TYPE
   SYNTAX      Integer32
   MAX-ACCESS  read-write
   STATUS      current
   DESCRIPTION
      "Path: ethernet2.editConf.vlan.ipV6.addrAutoConfig.nrDupAddrDetects"
   ::= {er1645v2Lan2MCVlanEntry 704905472}

er1645v2Lan2MCVlanIpV6AddrAutoConfigAcceptRa OBJECT-TYPE
   SYNTAX      INTEGER
               {
               disabled (0),
               enabled (1)
               }
   MAX-ACCESS  read-write
   STATUS      current
   DESCRIPTION
      "Path: ethernet2.editConf.vlan.ipV6.addrAutoConfig.acceptRa

       Possibilities:
               disabled   (0)
               enabled   (1)"
   ::= {er1645v2Lan2MCVlanEntry 704905728}

er1645v2Lan2MCVlanIpV6AddrAutoConfigAcceptRaRdnss OBJECT-TYPE
   SYNTAX      INTEGER
               {
               disabled (0),
               enabled (1)
               }
   MAX-ACCESS  read-write
   STATUS      current
   DESCRIPTION
      "Path: ethernet2.editConf.vlan.ipV6.addrAutoConfig.acceptRaRdnss

       Possibilities:
               disabled   (0)
               enabled   (1)"
   ::= {er1645v2Lan2MCVlanEntry 704905984}

er1645v2Lan2MCVlanIpV6AddrAutoConfigAcceptRaDnssl OBJECT-TYPE
   SYNTAX      INTEGER
               {
               disabled (0),
               enabled (1)
               }
   MAX-ACCESS  read-write
   STATUS      current
   DESCRIPTION
      "Path: ethernet2.editConf.vlan.ipV6.addrAutoConfig.acceptRaDnssl

       Possibilities:
               disabled   (0)
               enabled   (1)"
   ::= {er1645v2Lan2MCVlanEntry 704906240}

er1645v2Lan2MCVlanIpV6DefaultRoute OBJECT-TYPE
   SYNTAX      INTEGER
               {
               disabled (0),
               enabled (1)
               }
   MAX-ACCESS  read-write
   STATUS      current
   DESCRIPTION
      "Path: ethernet2.editConf.vlan.ipV6.defaultRoute

       Possibilities:
               disabled   (0)
               enabled   (1)"
   ::= {er1645v2Lan2MCVlanEntry 704970752}

er1645v2Lan2MCVlanIpV6RaSend OBJECT-TYPE
   SYNTAX      INTEGER
               {
               disabled (0),
               enabled (1)
               }
   MAX-ACCESS  read-write
   STATUS      current
   DESCRIPTION
      "Path: ethernet2.editConf.vlan.ipV6.ra.send

       Possibilities:
               disabled   (0)
               enabled   (1)"
   ::= {er1645v2Lan2MCVlanEntry 705036544}

er1645v2Lan2MCVlanIpV6RaMinInterval OBJECT-TYPE
   SYNTAX      TimeTicks
   MAX-ACCESS  read-write
   STATUS      current
   DESCRIPTION
      "Path: ethernet2.editConf.vlan.ipV6.ra.minInterval

       Time in centi-second."
   ::= {er1645v2Lan2MCVlanEntry 705036800}

er1645v2Lan2MCVlanIpV6RaMaxInterval OBJECT-TYPE
   SYNTAX      TimeTicks
   MAX-ACCESS  read-write
   STATUS      current
   DESCRIPTION
      "Path: ethernet2.editConf.vlan.ipV6.ra.maxInterval

       Time in centi-second."
   ::= {er1645v2Lan2MCVlanEntry 705037056}

er1645v2Lan2MCVlanIpV6RaManagedFlag OBJECT-TYPE
   SYNTAX      INTEGER
               {
               disabled (0),
               enabled (1)
               }
   MAX-ACCESS  read-write
   STATUS      current
   DESCRIPTION
      "Path: ethernet2.editConf.vlan.ipV6.ra.managedFlag

       Possibilities:
               disabled   (0)
               enabled   (1)"
   ::= {er1645v2Lan2MCVlanEntry 705037312}

er1645v2Lan2MCVlanIpV6RaOtherConfFlag OBJECT-TYPE
   SYNTAX      INTEGER
               {
               disabled (0),
               enabled (1)
               }
   MAX-ACCESS  read-write
   STATUS      current
   DESCRIPTION
      "Path: ethernet2.editConf.vlan.ipV6.ra.otherConfFlag

       Possibilities:
               disabled   (0)
               enabled   (1)"
   ::= {er1645v2Lan2MCVlanEntry 705037568}

er1645v2Lan2MCVlanIpV6RaLinkMtu OBJECT-TYPE
   SYNTAX      Integer32
   MAX-ACCESS  read-write
   STATUS      current
   DESCRIPTION
      "Path: ethernet2.editConf.vlan.ipV6.ra.linkMtu"
   ::= {er1645v2Lan2MCVlanEntry 705037824}

er1645v2Lan2MCVlanIpV6RaReachableTime OBJECT-TYPE
   SYNTAX      TimeTicks
   MAX-ACCESS  read-write
   STATUS      current
   DESCRIPTION
      "Path: ethernet2.editConf.vlan.ipV6.ra.reachableTime

       Time in centi-second."
   ::= {er1645v2Lan2MCVlanEntry 705038080}

er1645v2Lan2MCVlanIpV6RaRetransmitTime OBJECT-TYPE
   SYNTAX      TimeTicks
   MAX-ACCESS  read-write
   STATUS      current
   DESCRIPTION
      "Path: ethernet2.editConf.vlan.ipV6.ra.retransmitTime

       Time in centi-second."
   ::= {er1645v2Lan2MCVlanEntry 705038336}

er1645v2Lan2MCVlanIpV6RaHopLimit OBJECT-TYPE
   SYNTAX      Integer32
   MAX-ACCESS  read-write
   STATUS      current
   DESCRIPTION
      "Path: ethernet2.editConf.vlan.ipV6.ra.hopLimit"
   ::= {er1645v2Lan2MCVlanEntry 705038592}

er1645v2Lan2MCVlanIpV6RaDefaultLifeTime OBJECT-TYPE
   SYNTAX      TimeTicks
   MAX-ACCESS  read-write
   STATUS      current
   DESCRIPTION
      "Path: ethernet2.editConf.vlan.ipV6.ra.defaultLifeTime

       Time in centi-second."
   ::= {er1645v2Lan2MCVlanEntry 705038848}

er1645v2Lan2MCVlanIpV6RaDnsOptionsRdnssLifeTime OBJECT-TYPE
   SYNTAX      TimeTicks
   MAX-ACCESS  read-write
   STATUS      current
   DESCRIPTION
      "Path: ethernet2.editConf.vlan.ipV6.ra.dnsOptions.rdnss.lifeTime

       Time in centi-second."
   ::= {er1645v2Lan2MCVlanEntry 705039140}

er1645v2Lan2MCVlanIpV6RaDnsOptionsRdnssImportServers OBJECT-TYPE
   SYNTAX      INTEGER
               {
               disabled (0),
               enabled (1)
               }
   MAX-ACCESS  read-write
   STATUS      current
   DESCRIPTION
      "Path: ethernet2.editConf.vlan.ipV6.ra.dnsOptions.rdnss.importServers

       Possibilities:
               disabled   (0)
               enabled   (1)"
   ::= {er1645v2Lan2MCVlanEntry 705039148}

er1645v2Lan2MCVlanIpV6RaDnsOptionsDnsslLifeTime OBJECT-TYPE
   SYNTAX      TimeTicks
   MAX-ACCESS  read-write
   STATUS      current
   DESCRIPTION
      "Path: ethernet2.editConf.vlan.ipV6.ra.dnsOptions.dnssl.lifeTime

       Time in centi-second."
   ::= {er1645v2Lan2MCVlanEntry 705039172}

er1645v2Lan2MCVlanIpV6RaDnsOptionsDnsslImportDomains OBJECT-TYPE
   SYNTAX      INTEGER
               {
               disabled (0),
               enabled (1)
               }
   MAX-ACCESS  read-write
   STATUS      current
   DESCRIPTION
      "Path: ethernet2.editConf.vlan.ipV6.ra.dnsOptions.dnssl.importDomains

       Possibilities:
               disabled   (0)
               enabled   (1)"
   ::= {er1645v2Lan2MCVlanEntry 705039180}

er1645v2Lan2MCVlanIpV6RsSend OBJECT-TYPE
   SYNTAX      INTEGER
               {
               disabled (0),
               enabled (1)
               }
   MAX-ACCESS  read-write
   STATUS      current
   DESCRIPTION
      "Path: ethernet2.editConf.vlan.ipV6.rs.send

       Possibilities:
               disabled   (0)
               enabled   (1)"
   ::= {er1645v2Lan2MCVlanEntry 705954048}

er1645v2Lan2MCVlanIpV6RsMaxRandomDelay OBJECT-TYPE
   SYNTAX      TimeTicks
   MAX-ACCESS  read-write
   STATUS      current
   DESCRIPTION
      "Path: ethernet2.editConf.vlan.ipV6.rs.maxRandomDelay

       Time in centi-second."
   ::= {er1645v2Lan2MCVlanEntry 705954304}

er1645v2Lan2MCVlanIpV6RsInterval OBJECT-TYPE
   SYNTAX      TimeTicks
   MAX-ACCESS  read-write
   STATUS      current
   DESCRIPTION
      "Path: ethernet2.editConf.vlan.ipV6.rs.interval

       Time in centi-second."
   ::= {er1645v2Lan2MCVlanEntry 705954560}

er1645v2Lan2MCVlanIpV6RsMaxSolicitations OBJECT-TYPE
   SYNTAX      Integer32
   MAX-ACCESS  read-write
   STATUS      current
   DESCRIPTION
      "Path: ethernet2.editConf.vlan.ipV6.rs.maxSolicitations"
   ::= {er1645v2Lan2MCVlanEntry 705954816}

er1645v2Lan2MCVlanIpV6TrafficPolicyInbound OBJECT-TYPE
   SYNTAX      DisplayString
   MAX-ACCESS  read-write
   STATUS      current
   DESCRIPTION
      "Path: ethernet2.editConf.vlan.ipV6.trafficPolicy.inbound"
   ::= {er1645v2Lan2MCVlanEntry 705364224}

er1645v2Lan2MCVlanIpV6TrafficPolicyOutbound OBJECT-TYPE
   SYNTAX      DisplayString
   MAX-ACCESS  read-write
   STATUS      current
   DESCRIPTION
      "Path: ethernet2.editConf.vlan.ipV6.trafficPolicy.outbound"
   ::= {er1645v2Lan2MCVlanEntry 705364480}

er1645v2Lan2MCVlanIpV6FirewallZone OBJECT-TYPE
   SYNTAX      DisplayString
   MAX-ACCESS  read-write
   STATUS      current
   DESCRIPTION
      "Path: ethernet2.editConf.vlan.ipV6.firewall.zone"
   ::= {er1645v2Lan2MCVlanEntry 705429760}

er1645v2Lan2MCVlanIpV6DhcpClientAddrAC OBJECT-TYPE
   SYNTAX      INTEGER
               {
               disabled (0),
               enabled (1)
               }
   MAX-ACCESS  read-write
   STATUS      current
   DESCRIPTION
      "Path: ethernet2.editConf.vlan.ipV6.dhcp.client.addrAutoConfig

       Possibilities:
               disabled   (0)
               enabled   (1)"
   ::= {er1645v2Lan2MCVlanEntry 705307648}

er1645v2Lan2MCVlanIpV6DhcpClientPrDelMode OBJECT-TYPE
   SYNTAX      INTEGER
               {
               disabled (0),
               enabled (1)
               }
   MAX-ACCESS  read-write
   STATUS      current
   DESCRIPTION
      "Path: ethernet2.editConf.vlan.ipV6.dhcp.client.pd.mode

       Possibilities:
               disabled   (0)
               enabled   (1)"
   ::= {er1645v2Lan2MCVlanEntry 705308676}

er1645v2Lan2MCVlanIpV6DhcpClientPrDelPool OBJECT-TYPE
   SYNTAX      DisplayString
   MAX-ACCESS  read-write
   STATUS      current
   DESCRIPTION
      "Path: ethernet2.editConf.vlan.ipV6.dhcp.client.pd.pool"
   ::= {er1645v2Lan2MCVlanEntry 705308680}

er1645v2Lan2MCVlanIpV6DhcpClientPrDelPdExclOpt OBJECT-TYPE
   SYNTAX      INTEGER
               {
               disabled (0),
               enabled (1)
               }
   MAX-ACCESS  read-write
   STATUS      current
   DESCRIPTION
      "Path: ethernet2.editConf.vlan.ipV6.dhcp.client.pd.pdExclOpt

       Possibilities:
               disabled   (0)
               enabled   (1)"
   ::= {er1645v2Lan2MCVlanEntry 705308684}

er1645v2Lan2MCVlanIpV6DhcpClientDnsServerPref OBJECT-TYPE
   SYNTAX      Integer32
   MAX-ACCESS  read-write
   STATUS      current
   DESCRIPTION
      "Path: ethernet2.editConf.vlan.ipV6.dhcp.client.dns.serverPref"
   ::= {er1645v2Lan2MCVlanEntry 705310724}

er1645v2Lan2MCVlanIpV6DhcpClientRapidCommit OBJECT-TYPE
   SYNTAX      INTEGER
               {
               disabled (0),
               enabled (1)
               }
   MAX-ACCESS  read-write
   STATUS      current
   DESCRIPTION
      "Path: ethernet2.editConf.vlan.ipV6.dhcp.client.rapidCommit

       Possibilities:
               disabled   (0)
               enabled   (1)"
   ::= {er1645v2Lan2MCVlanEntry 705309696}

er1645v2Lan2MCVlanIpV6DhcpClientTimersSolTimeOut OBJECT-TYPE
   SYNTAX      TimeTicks
   MAX-ACCESS  read-write
   STATUS      current
   DESCRIPTION
      "Path: ethernet2.editConf.vlan.ipV6.dhcp.client.timers.solTimeOut

       Time in centi-second."
   ::= {er1645v2Lan2MCVlanEntry 705311748}

er1645v2Lan2MCVlanIpV6DhcpClientTimersSolMaxRt OBJECT-TYPE
   SYNTAX      TimeTicks
   MAX-ACCESS  read-write
   STATUS      current
   DESCRIPTION
      "Path: ethernet2.editConf.vlan.ipV6.dhcp.client.timers.solMaxRt

       Time in centi-second."
   ::= {er1645v2Lan2MCVlanEntry 705311752}

er1645v2Lan2MCVlanIpV6DhcpClientTimersInfoRefresh OBJECT-TYPE
   SYNTAX      TimeTicks
   MAX-ACCESS  read-write
   STATUS      current
   DESCRIPTION
      "Path: ethernet2.editConf.vlan.ipV6.dhcp.client.timers.infoRefresh

       Time in centi-second."
   ::= {er1645v2Lan2MCVlanEntry 705311756}

er1645v2Lan2MCVlanIpV6DhcpServerMode OBJECT-TYPE
   SYNTAX      INTEGER
               {
               disabled (0),
               enabled (1)
               }
   MAX-ACCESS  read-write
   STATUS      current
   DESCRIPTION
      "Path: ethernet2.editConf.vlan.ipV6.dhcp.server.mode

       Possibilities:
               disabled   (0)
               enabled   (1)"
   ::= {er1645v2Lan2MCVlanEntry 705315840}

er1645v2Lan2MCVlanIpV6DhcpServerPreference OBJECT-TYPE
   SYNTAX      Integer32
   MAX-ACCESS  read-write
   STATUS      current
   DESCRIPTION
      "Path: ethernet2.editConf.vlan.ipV6.dhcp.server.preference"
   ::= {er1645v2Lan2MCVlanEntry 705316864}

er1645v2Lan2MCVlanIpV6DhcpServerPool OBJECT-TYPE
   SYNTAX      DisplayString
   MAX-ACCESS  read-write
   STATUS      current
   DESCRIPTION
      "Path: ethernet2.editConf.vlan.ipV6.dhcp.server.pool"
   ::= {er1645v2Lan2MCVlanEntry 705317888}

er1645v2Lan2MCVlanIpV6DhcpServerRapidCommit OBJECT-TYPE
   SYNTAX      INTEGER
               {
               disabled (0),
               enabled (1)
               }
   MAX-ACCESS  read-write
   STATUS      current
   DESCRIPTION
      "Path: ethernet2.editConf.vlan.ipV6.dhcp.server.rapidCommit

       Possibilities:
               disabled   (0)
               enabled   (1)"
   ::= {er1645v2Lan2MCVlanEntry 705318912}

er1645v2Lan2MCVlanIpV6DhcpServerTimersInfoRefresh OBJECT-TYPE
   SYNTAX      TimeTicks
   MAX-ACCESS  read-write
   STATUS      current
   DESCRIPTION
      "Path: ethernet2.editConf.vlan.ipV6.dhcp.server.timers.infoRefresh

       Time in centi-second."
   ::= {er1645v2Lan2MCVlanEntry 705319940}

er1645v2Lan2MCVlanIpV6DhcpRelayMode OBJECT-TYPE
   SYNTAX      INTEGER
               {
               disabled (0),
               enabled (1)
               }
   MAX-ACCESS  read-write
   STATUS      current
   DESCRIPTION
      "Path: ethernet2.editConf.vlan.ipV6.dhcp.relay.mode

       Possibilities:
               disabled   (0)
               enabled   (1)"
   ::= {er1645v2Lan2MCVlanEntry 705323040}

er1645v2Lan2MCVlanIpV6SendRedirect OBJECT-TYPE
   SYNTAX      INTEGER
               {
               disabled (0),
               enabled (1)
               }
   MAX-ACCESS  read-write
   STATUS      current
   DESCRIPTION
      "Path: ethernet2.editConf.vlan.ipV6.sendRedirect

       Possibilities:
               disabled   (0)
               enabled   (1)"
   ::= {er1645v2Lan2MCVlanEntry 705101824}

er1645v2Lan2MCVlanIpV6LinkMtu OBJECT-TYPE
   SYNTAX      Integer32
   MAX-ACCESS  read-write
   STATUS      current
   DESCRIPTION
      "Path: ethernet2.editConf.vlan.ipV6.linkMtu"
   ::= {er1645v2Lan2MCVlanEntry 705167360}

er1645v2Lan2MCVlanIpV6InterfaceId OBJECT-TYPE
   SYNTAX      OCTET STRING
   MAX-ACCESS  read-write
   STATUS      current
   DESCRIPTION
      "Path: ethernet2.editConf.vlan.ipV6.interfaceId"
   ::= {er1645v2Lan2MCVlanEntry 705232896}

er1645v2Lan2MCVlanIpV6MF OBJECT-TYPE
   SYNTAX      Integer32
   MAX-ACCESS  read-write
   STATUS      current
   DESCRIPTION
      "Path: ethernet2.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2MCVlanEntry 705757184}

er1645v2Lan2MCVlanIpV6IcmpMessagesNoRoute OBJECT-TYPE
   SYNTAX      INTEGER
               {
               disabled (0),
               enabled (1)
               }
   MAX-ACCESS  read-write
   STATUS      current
   DESCRIPTION
      "Path: ethernet2.editConf.vlan.ipV6.icmpMessages.noRoute

       Possibilities:
               disabled   (0)
               enabled   (1)"
   ::= {er1645v2Lan2MCVlanEntry 705822976}

er1645v2Lan2MCVlanIpV6IcmpMessagesBeyondScope OBJECT-TYPE
   SYNTAX      INTEGER
               {
               disabled (0),
               enabled (1)
               }
   MAX-ACCESS  read-write
   STATUS      current
   DESCRIPTION
      "Path: ethernet2.editConf.vlan.ipV6.icmpMessages.beyondScope

       Possibilities:
               disabled   (0)
               enabled   (1)"
   ::= {er1645v2Lan2MCVlanEntry 705823488}

er1645v2Lan2MCVlanIpV6IcmpMessagesAddressUnreachable OBJECT-TYPE
   SYNTAX      INTEGER
               {
               disabled (0),
               enabled (1)
               }
   MAX-ACCESS  read-write
   STATUS      current
   DESCRIPTION
      "Path: ethernet2.editConf.vlan.ipV6.icmpMessages.addressUnreachable

       Possibilities:
               disabled   (0)
               enabled   (1)"
   ::= {er1645v2Lan2MCVlanEntry 705823744}

er1645v2Lan2MCVlanIpV6IcmpMessagesPortUnreachable OBJECT-TYPE
   SYNTAX      INTEGER
               {
               disabled (0),
               enabled (1)
               }
   MAX-ACCESS  read-write
   STATUS      current
   DESCRIPTION
      "Path: ethernet2.editConf.vlan.ipV6.icmpMessages.portUnreachable

       Possibilities:
               disabled   (0)
               enabled   (1)"
   ::= {er1645v2Lan2MCVlanEntry 705824000}

er1645v2Lan2MCVlanIpV6IcmpMessagesPacketTooBig OBJECT-TYPE
   SYNTAX      INTEGER
               {
               disabled (0),
               enabled (1)
               }
   MAX-ACCESS  read-write
   STATUS      current
   DESCRIPTION
      "Path: ethernet2.editConf.vlan.ipV6.icmpMessages.packetTooBig

       Possibilities:
               disabled   (0)
               enabled   (1)"
   ::= {er1645v2Lan2MCVlanEntry 705825280}

er1645v2Lan2MCVlanIpV6IcmpMessagesHopLimitExceeded OBJECT-TYPE
   SYNTAX      INTEGER
               {
               disabled (0),
               enabled (1)
               }
   MAX-ACCESS  read-write
   STATUS      current
   DESCRIPTION
      "Path: ethernet2.editConf.vlan.ipV6.icmpMessages.hopLimitExceeded

       Possibilities:
               disabled   (0)
               enabled   (1)"
   ::= {er1645v2Lan2MCVlanEntry 705827840}

er1645v2Lan2MCVlanIpV6IcmpMessagesFragTimeExceeded OBJECT-TYPE
   SYNTAX      INTEGER
               {
               disabled (0),
               enabled (1)
               }
   MAX-ACCESS  read-write
   STATUS      current
   DESCRIPTION
      "Path: ethernet2.editConf.vlan.ipV6.icmpMessages.fragTimeExceeded

       Possibilities:
               disabled   (0)
               enabled   (1)"
   ::= {er1645v2Lan2MCVlanEntry 705828096}

er1645v2Lan2MCVlanIpV6IcmpMessagesHeaderFieldErr OBJECT-TYPE
   SYNTAX      INTEGER
               {
               disabled (0),
               enabled (1)
               }
   MAX-ACCESS  read-write
   STATUS      current
   DESCRIPTION
      "Path: ethernet2.editConf.vlan.ipV6.icmpMessages.headerFieldErr

       Possibilities:
               disabled   (0)
               enabled   (1)"
   ::= {er1645v2Lan2MCVlanEntry 705830400}

er1645v2Lan2MCVlanIpV6IcmpMessagesOptionUnrecognized OBJECT-TYPE
   SYNTAX      INTEGER
               {
               disabled (0),
               enabled (1)
               }
   MAX-ACCESS  read-write
   STATUS      current
   DESCRIPTION
      "Path: ethernet2.editConf.vlan.ipV6.icmpMessages.optionUnrecognized

       Possibilities:
               disabled   (0)
               enabled   (1)"
   ::= {er1645v2Lan2MCVlanEntry 705830912}

er1645v2Lan2MCVlanIpV6IcmpMessagesRedirect OBJECT-TYPE
   SYNTAX      INTEGER
               {
               disabled (0),
               enabled (1)
               }
   MAX-ACCESS  read-write
   STATUS      current
   DESCRIPTION
      "Path: ethernet2.editConf.vlan.ipV6.icmpMessages.redirect

       Possibilities:
               disabled   (0)
               enabled   (1)"
   ::= {er1645v2Lan2MCVlanEntry 705832960}

er1645v2Lan2MCVlanBridgingAccList OBJECT-TYPE
   SYNTAX      DisplayString
   MAX-ACCESS  read-write
   STATUS      current
   DESCRIPTION
      "Path: ethernet2.editConf.vlan.bridging.accessList"
   ::= {er1645v2Lan2MCVlanEntry 453246976}

er1645v2Lan2MCVlanBridgingInACL OBJECT-TYPE
   SYNTAX      DisplayString
   MAX-ACCESS  read-write
   STATUS      current
   DESCRIPTION
      "Path: ethernet2.editConf.vlan.bridging.inAccessList"
   ::= {er1645v2Lan2MCVlanEntry 456916992}

er1645v2Lan2MCVlanBridgingTp OBJECT-TYPE
   SYNTAX      DisplayString
   MAX-ACCESS  read-write
   STATUS      current
   DESCRIPTION
      "Path: ethernet2.editConf.vlan.bridging.trafficPolicy"
   ::= {er1645v2Lan2MCVlanEntry 454295552}

er1645v2Lan2MCVlanBridgingBrGrp OBJECT-TYPE
   SYNTAX      DisplayString
   MAX-ACCESS  read-write
   STATUS      current
   DESCRIPTION
      "Path: ethernet2.editConf.vlan.bridging.bridgeGroup"
   ::= {er1645v2Lan2MCVlanEntry 454819840}

er1645v2Lan2MCVlanBridgingLimBC OBJECT-TYPE
   SYNTAX      INTEGER
               {
               disabled (0),
               enabled (1)
               }
   MAX-ACCESS  read-write
   STATUS      current
   DESCRIPTION
      "Path: ethernet2.editConf.vlan.bridging.limitBroadcasts

       Possibilities:
               disabled   (0)
               enabled   (1)"
   ::= {er1645v2Lan2MCVlanEntry 455081984}

er1645v2Lan2MCVlanBridgingPrivateMode OBJECT-TYPE
   SYNTAX      INTEGER
               {
               disabled (0),
               enabled (1)
               }
   MAX-ACCESS  read-write
   STATUS      current
   DESCRIPTION
      "Path: ethernet2.editConf.vlan.bridging.privateMode

       Possibilities:
               disabled   (0)
               enabled   (1)"
   ::= {er1645v2Lan2MCVlanEntry 459538432}

er1645v2Lan2MCVlanBridgingLearning OBJECT-TYPE
   SYNTAX      INTEGER
               {
               disabled (0),
               enabled (1)
               }
   MAX-ACCESS  read-write
   STATUS      current
   DESCRIPTION
      "Path: ethernet2.editConf.vlan.bridging.learning

       Possibilities:
               disabled   (0)
               enabled   (1)"
   ::= {er1645v2Lan2MCVlanEntry 456130560}

er1645v2Lan2MCVlanBridgingMaxCacheSize OBJECT-TYPE
   SYNTAX      INTEGER
               {
               unlimited (0)
               }
   MAX-ACCESS  read-write
   STATUS      current
   DESCRIPTION
      "Path: ethernet2.editConf.vlan.bridging.maxCacheSize

       Possibilities:
               unlimited   (0)"
   ::= {er1645v2Lan2MCVlanEntry 456392704}

er1645v2Lan2MCVlanBridgingRelearnDropOnRelearn OBJECT-TYPE
   SYNTAX      INTEGER
               {
               disabled (0),
               enabled (1)
               }
   MAX-ACCESS  read-write
   STATUS      current
   DESCRIPTION
      "Path: ethernet2.editConf.vlan.bridging.relearn.dropOnRelearn

       Possibilities:
               disabled   (0)
               enabled   (1)"
   ::= {er1645v2Lan2MCVlanEntry 456655872}

er1645v2Lan2MCVlanBridgingRelearnShutdownThreshold OBJECT-TYPE
   SYNTAX      Integer32
   MAX-ACCESS  read-write
   STATUS      current
   DESCRIPTION
      "Path: ethernet2.editConf.vlan.bridging.relearn.shutdownThreshold"
   ::= {er1645v2Lan2MCVlanEntry 456656896}

er1645v2Lan2MCVlanBridgingRelearnShutdownTime OBJECT-TYPE
   SYNTAX      TimeTicks
   MAX-ACCESS  read-write
   STATUS      current
   DESCRIPTION
      "Path: ethernet2.editConf.vlan.bridging.relearn.shutdownTime

       Time in centi-second."
   ::= {er1645v2Lan2MCVlanEntry 456657920}

er1645v2Lan2MCVlanBridgingRelearnLoopDetection OBJECT-TYPE
   SYNTAX      INTEGER
               {
               disabled (0),
               passive (1),
               active (2)
               }
   MAX-ACCESS  read-write
   STATUS      current
   DESCRIPTION
      "Path: ethernet2.editConf.vlan.bridging.relearn.loopDetection

       Possibilities:
               disabled   (0)
               passive   (1)
               active   (2)"
   ::= {er1645v2Lan2MCVlanEntry 456658944}

er1645v2Lan2MCVlanBridgingRelearnLoopDetectionInterval OBJECT-TYPE
   SYNTAX      TimeTicks
   MAX-ACCESS  read-write
   STATUS      current
   DESCRIPTION
      "Path: ethernet2.editConf.vlan.bridging.relearn.loopDetectionInterval

       Time in centi-second."
   ::= {er1645v2Lan2MCVlanEntry 456659968}

er1645v2Lan2MCVlanBridgingVlanMemberShip OBJECT-TYPE
   SYNTAX      INTEGER
               {
               all (0),
               none (1),
               grouped (2)
               }
   MAX-ACCESS  read-write
   STATUS      current
   DESCRIPTION
      "Path: ethernet2.editConf.vlan.bridging.vlanMemberShip

       Possibilities:
               all   (0)
               none   (1)
               grouped   (2)"
   ::= {er1645v2Lan2MCVlanEntry 457965568}

er1645v2Lan2MCVlanBridgingVlTUntaggedAction OBJECT-TYPE
   SYNTAX      INTEGER
               {
               discard (0),
               accept (1),
               tag (2)
               }
   MAX-ACCESS  read-write
   STATUS      current
   DESCRIPTION
      "Path: ethernet2.editConf.vlan.bridging.vlanTagging.untagged.action

       Possibilities:
               discard   (0)
               accept   (1)
               tag   (2)"
   ::= {er1645v2Lan2MCVlanEntry 459055104}

er1645v2Lan2MCVlanBridgingVlTUntaggedTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.untagged.tagInfo.tpid

       Possibilities:
               dot1Q   (33024)
               dot1ad   (34984)
               0x9100   (37120)
               0x9200   (37376)
               0x9300   (37632)"
   ::= {er1645v2Lan2MCVlanEntry 459059712}

er1645v2Lan2MCVlanBridgingVlTUntaggedTagInfoVid OBJECT-TYPE
   SYNTAX      Integer32
   MAX-ACCESS  read-write
   STATUS      current
   DESCRIPTION
      "Path: ethernet2.editConf.vlan.bridging.vlanTagging.untagged.tagInfo.vid"
   ::= {er1645v2Lan2MCVlanEntry 459060224}

er1645v2Lan2MCVlanBridgingVlTUnknownVlansAction OBJECT-TYPE
   SYNTAX      INTEGER
               {
               discard (0),
               accept (1),
               tag (2)
               }
   MAX-ACCESS  read-write
   STATUS      current
   DESCRIPTION
      "Path: ethernet2.editConf.vlan.bridging.vlanTagging.unknownVlans.action

       Possibilities:
               discard   (0)
               accept   (1)
               tag   (2)"
   ::= {er1645v2Lan2MCVlanEntry 459120640}

er1645v2Lan2MCVlanBridgingVlTUnknownVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.unknownVlans.tagInfo.tpid

       Possibilities:
               dot1Q   (33024)
               dot1ad   (34984)
               0x9100   (37120)
               0x9200   (37376)
               0x9300   (37632)"
   ::= {er1645v2Lan2MCVlanEntry 459125248}

er1645v2Lan2MCVlanBridgingVlTUnknownVlansTagInfoVid OBJECT-TYPE
   SYNTAX      Integer32
   MAX-ACCESS  read-write
   STATUS      current
   DESCRIPTION
      "Path: ethernet2.editConf.vlan.bridging.vlanTagging.unknownVlans.tagInfo.vid"
   ::= {er1645v2Lan2MCVlanEntry 459125760}

er1645v2Lan2MCVlanBridgingDot1adType OBJECT-TYPE
   SYNTAX      INTEGER
               {
               slOPTg (0),
               cPort (4),
               sPort (1),
               nni (2)
               }
   MAX-ACCESS  read-write
   STATUS      current
   DESCRIPTION
      "Path: ethernet2.editConf.vlan.bridging.dot1ad.type

       Possibilities:
               <OPT>   (0)
               cPort   (4)
               sPort   (1)
               nni   (2)"
   ::= {er1645v2Lan2MCVlanEntry 460850176}

er1645v2Lan2MCVlanBridgingPriority OBJECT-TYPE
   SYNTAX      Integer32
   MAX-ACCESS  read-write
   STATUS      current
   DESCRIPTION
      "Path: ethernet2.editConf.vlan.bridging.priority"
   ::= {er1645v2Lan2MCVlanEntry 453509120}

er1645v2Lan2MCVlanBridgingPathCost OBJECT-TYPE
   SYNTAX      Integer32
   MAX-ACCESS  read-write
   STATUS      current
   DESCRIPTION
      "Path: ethernet2.editConf.vlan.bridging.pathCost"
   ::= {er1645v2Lan2MCVlanEntry 453771264}

er1645v2Lan2MCVlanBridgingInternalPathCost OBJECT-TYPE
   SYNTAX      Integer32
   MAX-ACCESS  read-write
   STATUS      current
   DESCRIPTION
      "Path: ethernet2.editConf.vlan.bridging.internalPathCost"
   ::= {er1645v2Lan2MCVlanEntry 457703424}

er1645v2Lan2MCVlanBridgingTCD OBJECT-TYPE
   SYNTAX      INTEGER
               {
               disabled (0),
               enabled (1)
               }
   MAX-ACCESS  read-write
   STATUS      current
   DESCRIPTION
      "Path: ethernet2.editConf.vlan.bridging.topologyChangeDetection

       Possibilities:
               disabled   (0)
               enabled   (1)"
   ::= {er1645v2Lan2MCVlanEntry 454033408}

er1645v2Lan2MCVlanBridgingRestrictedRole OBJECT-TYPE
   SYNTAX      INTEGER
               {
               disabled (0),
               enabled (1)
               }
   MAX-ACCESS  read-write
   STATUS      current
   DESCRIPTION
      "Path: ethernet2.editConf.vlan.bridging.restrictedRole

       Possibilities:
               disabled   (0)
               enabled   (1)"
   ::= {er1645v2Lan2MCVlanEntry 458227712}

er1645v2Lan2MCVlanBridgingAdminEdge OBJECT-TYPE
   SYNTAX      INTEGER
               {
               disabled (0),
               enabled (1)
               }
   MAX-ACCESS  read-write
   STATUS      current
   DESCRIPTION
      "Path: ethernet2.editConf.vlan.bridging.adminEdge

       Possibilities:
               disabled   (0)
               enabled   (1)"
   ::= {er1645v2Lan2MCVlanEntry 457179136}

er1645v2Lan2MCVlanBridgingOamMacDeviceMac OBJECT-TYPE
   SYNTAX      DisplayString
   MAX-ACCESS  read-write
   STATUS      current
   DESCRIPTION
      "Path: ethernet2.editConf.vlan.bridging.ethOam.macAddress.deviceMac"
   ::= {er1645v2Lan2MCVlanEntry 458506496}

er1645v2Lan2MCVlanBridgingOamMacUserMac OBJECT-TYPE
   SYNTAX      OCTET STRING
   MAX-ACCESS  read-write
   STATUS      current
   DESCRIPTION
      "Path: ethernet2.editConf.vlan.bridging.ethOam.macAddress.userMac

       MAC address."
   ::= {er1645v2Lan2MCVlanEntry 458506368}

er1645v2Lan2MCVlanBridgingOamMacBridgeMac OBJECT-TYPE
   SYNTAX      DisplayString
   MAX-ACCESS  read-write
   STATUS      current
   DESCRIPTION
      "Path: ethernet2.editConf.vlan.bridging.ethOam.macAddress.bridgeMac"
   ::= {er1645v2Lan2MCVlanEntry 458506432}

er1645v2Lan2MCVlanBridgingMgmtInline OBJECT-TYPE
   SYNTAX      INTEGER
               {
               disabled (0),
               enabled (1)
               }
   MAX-ACCESS  read-write
   STATUS      current
   DESCRIPTION
      "Path: ethernet2.editConf.vlan.bridging.mgmtInline

       Possibilities:
               disabled   (0)
               enabled   (1)"
   ::= {er1645v2Lan2MCVlanEntry 458752000}

er1645v2Lan2MCVlanBridgingL2ptMode OBJECT-TYPE
   SYNTAX      INTEGER
               {
               disabled (0),
               enabled (1)
               }
   MAX-ACCESS  read-write
   STATUS      current
   DESCRIPTION
      "Path: ethernet2.editConf.vlan.bridging.l2ProtTunnel.mode

       Possibilities:
               disabled   (0)
               enabled   (1)"
   ::= {er1645v2Lan2MCVlanEntry 459292672}

er1645v2Lan2MCVlanBridgingL2ptProtocols OBJECT-TYPE
   SYNTAX      Integer32
   MAX-ACCESS  read-write
   STATUS      current
   DESCRIPTION
      "Path: ethernet2.editConf.vlan.bridging.l2ProtTunnel.protocols

       Bit meanings:
               bit 0 = stp,
               bit 1 = lldp,
               bit 2 = oam,
               bit 3 = cdp,
               bit 4 = vtp,
               bit 5 = lacp,
               bit 6 = efmOam,
               bit 7 = pvst,
               bit 8 = mmrp,
               bit 9 = mvrp,
               bit 10 = gvrp,
               bit 11 = gmrp,
               bit 12 = dtp,
               bit 13 = pagp,
               bit 14 = udld"
   ::= {er1645v2Lan2MCVlanEntry 459309056}

er1645v2Lan2MCVlanBridgingL2ptDestMac OBJECT-TYPE
   SYNTAX      OCTET STRING
   MAX-ACCESS  read-write
   STATUS      current
   DESCRIPTION
      "Path: ethernet2.editConf.vlan.bridging.l2ProtTunnel.destinationMac

       MAC address."
   ::= {er1645v2Lan2MCVlanEntry 459325440}

er1645v2Lan2MCVlanBridgingL2ptCos OBJECT-TYPE
   SYNTAX      INTEGER
               {
               unchanged (255)
               }
   MAX-ACCESS  read-write
   STATUS      current
   DESCRIPTION
      "Path: ethernet2.editConf.vlan.bridging.l2ProtTunnel.cos

       Possibilities:
               unchanged   (255)"
   ::= {er1645v2Lan2MCVlanEntry 459341824}

er1645v2Lan2MCVlanBridgingL2ptDropThrStp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.stp

       unit name = packets/sec

       Possibilities:
               unlimited   (0)"
   ::= {er1645v2Lan2MCVlanEntry 459358272}

er1645v2Lan2MCVlanBridgingL2ptDropThrLldp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.lldp

       unit name = packets/sec

       Possibilities:
               unlimited   (0)"
   ::= {er1645v2Lan2MCVlanEntry 459358336}

er1645v2Lan2MCVlanBridgingL2ptDropThrOam OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.oam

       unit name = packets/sec

       Possibilities:
               unlimited   (0)"
   ::= {er1645v2Lan2MCVlanEntry 459358400}

er1645v2Lan2MCVlanBridgingL2ptDropThrCdp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.cdp

       unit name = packets/sec

       Possibilities:
               unlimited   (0)"
   ::= {er1645v2Lan2MCVlanEntry 459358464}

er1645v2Lan2MCVlanBridgingL2ptDropThrVtp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.vtp

       unit name = packets/sec

       Possibilities:
               unlimited   (0)"
   ::= {er1645v2Lan2MCVlanEntry 459358528}

er1645v2Lan2MCVlanBridgingL2ptDropThrLacp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.lacp

       unit name = packets/sec

       Possibilities:
               unlimited   (0)"
   ::= {er1645v2Lan2MCVlanEntry 459358592}

er1645v2Lan2MCVlanBridgingL2ptDropThrEfmOam OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.efmOam

       unit name = packets/sec

       Possibilities:
               unlimited   (0)"
   ::= {er1645v2Lan2MCVlanEntry 459358656}

er1645v2Lan2MCVlanBridgingL2ptDropThrPvst OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.pvst

       unit name = packets/sec

       Possibilities:
               unlimited   (0)"
   ::= {er1645v2Lan2MCVlanEntry 459358720}

er1645v2Lan2MCVlanBridgingL2ptDropThrMmrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.mmrp

       unit name = packets/sec

       Possibilities:
               unlimited   (0)"
   ::= {er1645v2Lan2MCVlanEntry 459358784}

er1645v2Lan2MCVlanBridgingL2ptDropThrMvrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.mvrp

       unit name = packets/sec

       Possibilities:
               unlimited   (0)"
   ::= {er1645v2Lan2MCVlanEntry 459358848}

er1645v2Lan2MCVlanBridgingL2ptDropThrGvrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.gvrp

       unit name = packets/sec

       Possibilities:
               unlimited   (0)"
   ::= {er1645v2Lan2MCVlanEntry 459358912}

er1645v2Lan2MCVlanBridgingL2ptDropThrGmrp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.gmrp

       unit name = packets/sec

       Possibilities:
               unlimited   (0)"
   ::= {er1645v2Lan2MCVlanEntry 459358976}

er1645v2Lan2MCVlanBridgingL2ptDropThrDtp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.dtp

       unit name = packets/sec

       Possibilities:
               unlimited   (0)"
   ::= {er1645v2Lan2MCVlanEntry 459359040}

er1645v2Lan2MCVlanBridgingL2ptDropThrPagp OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.pagp

       unit name = packets/sec

       Possibilities:
               unlimited   (0)"
   ::= {er1645v2Lan2MCVlanEntry 459359104}

er1645v2Lan2MCVlanBridgingL2ptDropThrUdld OBJECT-TYPE
   SYNTAX      INTEGER
               {
               unlimited (0)
               }
   UNITS       "packets/sec"
   MAX-ACCESS  read-write
   STATUS      current
   DESCRIPTION
      "Path: ethernet2.editConf.vlan.bridging.l2ProtTunnel.dropThresholds.udld

       unit name = packets/sec

       Possibilities:
               unlimited   (0)"
   ::= {er1645v2Lan2MCVlanEntry 459359168}

er1645v2Lan2MCVlanVlanVid OBJECT-TYPE
   SYNTAX      INTEGER
               {
               untagged (0),
               prioTagged (4096),
               notUsed (4097)
               }
   MAX-ACCESS  read-write
   STATUS      current
   DESCRIPTION
      "Path: ethernet2.editConf.vlan.vlan.vid

       Possibilities:
               untagged   (0)
               prioTagged   (4096)
               notUsed   (4097)"
   ::= {er1645v2Lan2MCVlanEntry 234946560}

er1645v2Lan2MCVlanVlanVidExtensionSingle OBJECT-TYPE
   SYNTAX      OCTET STRING
   MAX-ACCESS  read-write
   STATUS      current
   DESCRIPTION
      "Path: ethernet2.editConf.vlan.vlan.vidExtension.single"
   ::= {er1645v2Lan2MCVlanEntry 235340032}

er1645v2Lan2MCVlanVlanVidExtensionEndVid OBJECT-TYPE
   SYNTAX      Integer32
   MAX-ACCESS  read-write
   STATUS      current
   DESCRIPTION
      "Path: ethernet2.editConf.vlan.vlan.vidExtension.endVid"
   ::= {er1645v2Lan2MCVlanEntry 235340288}

er1645v2Lan2MCVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.tpid

       Possibilities:
               dot1Q   (33024)
               dot1ad   (34984)
               0x9100   (37120)
               0x9200   (37376)
               0x9300   (37632)"
   ::= {er1645v2Lan2MCVlanEntry 241238016}

er1645v2Lan2MCVlanVlanTagSign OBJECT-TYPE
   SYNTAX      INTEGER
               {
               global (0),
               local (1),
               sVlan (2),
               sVlanGlobal (6),
               cVlan (3),
               scVlan (5),
               cVlanLocal (4)
               }
   MAX-ACCESS  read-write
   STATUS      current
   DESCRIPTION
      "Path: ethernet2.editConf.vlan.vlan.tagSignificance

       Possibilities:
               global   (0)
               local   (1)
               sVlan   (2)
               sVlanGlobal   (6)
               cVlan   (3)
               scVlan   (5)
               cVlanLocal   (4)"
   ::= {er1645v2Lan2MCVlanEntry 235012096}

er1645v2Lan2MCVlanVlanChTos OBJECT-TYPE
   SYNTAX      INTEGER
               {
               disabled (0),
               enabled (1)
               }
   MAX-ACCESS  read-write
   STATUS      current
   DESCRIPTION
      "Path: ethernet2.editConf.vlan.vlan.changeTos

       Possibilities:
               disabled   (0)
               enabled   (1)"
   ::= {er1645v2Lan2MCVlanEntry 235208704}

er1645v2Lan2MCVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235143424}

er1645v2Lan2MCVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235143680}

er1645v2Lan2MCVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235143936}

er1645v2Lan2MCVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235144192}

er1645v2Lan2MCVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235144448}

er1645v2Lan2MCVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235144704}

er1645v2Lan2MCVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235144960}

er1645v2Lan2MCVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: ethernet2.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2Lan2MCVlanEntry 235145216}

er1645v2Lan2MCVlanVlanTxCos OBJECT-TYPE
   SYNTAX      INTEGER
               {
               tosCosMap (8),
               queueCosMap (16)
               }
   MAX-ACCESS  read-write
   STATUS      current
   DESCRIPTION
      "Path: ethernet2.editConf.vlan.vlan.txCos

       Possibilities:
               tosCosMap   (8)
               queueCosMap   (16)"
   ::= {er1645v2Lan2MCVlanEntry 235077632}

er1645v2Lan2MCVlanVlanCCMapP0 OBJECT-TYPE
   SYNTAX      Integer32
   MAX-ACCESS  read-write
   STATUS      current
   DESCRIPTION
      "Path: ethernet2.editConf.vlan.vlan.cosCosMap.p0"
   ::= {er1645v2Lan2MCVlanEntry 241303808}

er1645v2Lan2MCVlanVlanCCMapP1 OBJECT-TYPE
   SYNTAX      Integer32
   MAX-ACCESS  read-write
   STATUS      current
   DESCRIPTION
      "Path: ethernet2.editConf.vlan.vlan.cosCosMap.p1"
   ::= {er1645v2Lan2MCVlanEntry 241304064}

er1645v2Lan2MCVlanVlanCCMapP2 OBJECT-TYPE
   SYNTAX      Integer32
   MAX-ACCESS  read-write
   STATUS      current
   DESCRIPTION
      "Path: ethernet2.editConf.vlan.vlan.cosCosMap.p2"
   ::= {er1645v2Lan2MCVlanEntry 241304320}

er1645v2Lan2MCVlanVlanCCMapP3 OBJECT-TYPE
   SYNTAX      Integer32
   MAX-ACCESS  read-write
   STATUS      current
   DESCRIPTION
      "Path: ethernet2.editConf.vlan.vlan.cosCosMap.p3"
   ::= {er1645v2Lan2MCVlanEntry 241304576}

er1645v2Lan2MCVlanVlanCCMapP4 OBJECT-TYPE
   SYNTAX      Integer32
   MAX-ACCESS  read-write
   STATUS      current
   DESCRIPTION
      "Path: ethernet2.editConf.vlan.vlan.cosCosMap.p4"
   ::= {er1645v2Lan2MCVlanEntry 241304832}

er1645v2Lan2MCVlanVlanCCMapP5 OBJECT-TYPE
   SYNTAX      Integer32
   MAX-ACCESS  read-write
   STATUS      current
   DESCRIPTION
      "Path: ethernet2.editConf.vlan.vlan.cosCosMap.p5"
   ::= {er1645v2Lan2MCVlanEntry 241305088}

er1645v2Lan2MCVlanVlanCCMapP6 OBJECT-TYPE
   SYNTAX      Integer32
   MAX-ACCESS  read-write
   STATUS      current
   DESCRIPTION
      "Path: ethernet2.editConf.vlan.vlan.cosCosMap.p6"
   ::= {er1645v2Lan2MCVlanEntry 241305344}

er1645v2Lan2MCVlanVlanCCMapP7 OBJECT-TYPE
   SYNTAX      Integer32
   MAX-ACCESS  read-write
   STATUS      current
   DESCRIPTION
      "Path: ethernet2.editConf.vlan.vlan.cosCosMap.p7"
   ::= {er1645v2Lan2MCVlanEntry 241305600}

er1645v2Lan2MCVlanVlanQCMapQueue1 OBJECT-TYPE
   SYNTAX      Integer32
   MAX-ACCESS  read-write
   STATUS      current
   DESCRIPTION
      "Path: ethernet2.editConf.vlan.vlan.queueCosMap.queue1"
   ::= {er1645v2Lan2MCVlanEntry 241434880}

er1645v2Lan2MCVlanVlanQCMapQueue2 OBJECT-TYPE
   SYNTAX      Integer32
   MAX-ACCESS  read-write
   STATUS      current
   DESCRIPTION
      "Path: ethernet2.editConf.vlan.vlan.queueCosMap.queue2"
   ::= {er1645v2Lan2MCVlanEntry 241435136}

er1645v2Lan2MCVlanVlanQCMapQueue3 OBJECT-TYPE
   SYNTAX      Integer32
   MAX-ACCESS  read-write
   STATUS      current
   DESCRIPTION
      "Path: ethernet2.editConf.vlan.vlan.queueCosMap.queue3"
   ::= {er1645v2Lan2MCVlanEntry 241435392}

er1645v2Lan2MCVlanVlanQCMapQueue4 OBJECT-TYPE
   SYNTAX      Integer32
   MAX-ACCESS  read-write
   STATUS      current
   DESCRIPTION
      "Path: ethernet2.editConf.vlan.vlan.queueCosMap.queue4"
   ::= {er1645v2Lan2MCVlanEntry 241435648}

er1645v2Lan2MCVlanVlanQCMapQueue5 OBJECT-TYPE
   SYNTAX      Integer32
   MAX-ACCESS  read-write
   STATUS      current
   DESCRIPTION
      "Path: ethernet2.editConf.vlan.vlan.queueCosMap.queue5"
   ::= {er1645v2Lan2MCVlanEntry 241435904}

er1645v2Lan2MCVlanVlanQCMapLowDelayQueue OBJECT-TYPE
   SYNTAX      Integer32
   MAX-ACCESS  read-write
   STATUS      current
   DESCRIPTION
      "Path: ethernet2.editConf.vlan.vlan.queueCosMap.lowDelayQueue"
   ::= {er1645v2Lan2MCVlanEntry 241436160}

er1645v2Lan2MCVlanVlanQCMapLowDelay2Queue OBJECT-TYPE
   SYNTAX      Integer32
   MAX-ACCESS  read-write
   STATUS      current
   DESCRIPTION
      "Path: ethernet2.editConf.vlan.vlan.queueCosMap.lowDelay2Queue"
   ::= {er1645v2Lan2MCVlanEntry 241436416}

er1645v2Lan2MCVlanVlanQCMapSystemQueue OBJECT-TYPE
   SYNTAX      Integer32
   MAX-ACCESS  read-write
   STATUS      current
   DESCRIPTION
      "Path: ethernet2.editConf.vlan.vlan.queueCosMap.systemQueue"
   ::= {er1645v2Lan2MCVlanEntry 241436672}

er1645v2Lan2MCVlanVlanQinQSVid OBJECT-TYPE
   SYNTAX      Integer32
   MAX-ACCESS  read-write
   STATUS      current
   DESCRIPTION
      "Path: ethernet2.editConf.vlan.vlan.tunnel.sVid"
   ::= {er1645v2Lan2MCVlanEntry 241172736}

er1645v2Lan2MCVlanVlanQinQSTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.tunnel.sTpid

       Possibilities:
               dot1Q   (33024)
               dot1ad   (34984)
               0x9100   (37120)
               0x9200   (37376)
               0x9300   (37632)"
   ::= {er1645v2Lan2MCVlanEntry 241172992}

er1645v2Lan2MCVlanVlanArpTimeOut OBJECT-TYPE
   SYNTAX      TimeTicks
   MAX-ACCESS  read-write
   STATUS      current
   DESCRIPTION
      "Path: ethernet2.editConf.vlan.vlan.arp.timeOut

       Time in centi-second."
   ::= {er1645v2Lan2MCVlanEntry 235277312}

er1645v2Lan2MCVlanVlanArpProxyArp OBJECT-TYPE
   SYNTAX      INTEGER
               {
               disabled (0),
               enabled (1)
               }
   MAX-ACCESS  read-write
   STATUS      current
   DESCRIPTION
      "Path: ethernet2.editConf.vlan.vlan.arp.proxyArp

       Possibilities:
               disabled   (0)
               enabled   (1)"
   ::= {er1645v2Lan2MCVlanEntry 235287040}

er1645v2Lan2MCVlanBandwidthMode OBJECT-TYPE
   SYNTAX      INTEGER
               {
               reshaping (1),
               policing (2),
               policingReshape (3)
               }
   MAX-ACCESS  read-write
   STATUS      current
   DESCRIPTION
      "Path: ethernet2.editConf.vlan.bandwidth.mode

       Possibilities:
               reshaping   (1)
               policing   (2)
               policingReshape   (3)"
   ::= {er1645v2Lan2MCVlanEntry 148897792}

er1645v2Lan2MCVlanBandwidthCir OBJECT-TYPE
   SYNTAX      Integer32
   MAX-ACCESS  read-write
   STATUS      current
   DESCRIPTION
      "Path: ethernet2.editConf.vlan.bandwidth.cir"
   ::= {er1645v2Lan2MCVlanEntry 135266304}

er1645v2Lan2MCVlanBandwidthEir OBJECT-TYPE
   SYNTAX      Integer32
   MAX-ACCESS  read-write
   STATUS      current
   DESCRIPTION
      "Path: ethernet2.editConf.vlan.bandwidth.eir"
   ::= {er1645v2Lan2MCVlanEntry 141557760}

er1645v2Lan2MCVlanBandwidthUnit OBJECT-TYPE
   SYNTAX      INTEGER
               {
               bitssec (1),
               percent (2)
               }
   MAX-ACCESS  read-write
   STATUS      current
   DESCRIPTION
      "Path: ethernet2.editConf.vlan.bandwidth.unit

       Possibilities:
               bits/sec   (1)
               percent   (2)"
   ::= {er1645v2Lan2MCVlanEntry 139460608}

er1645v2Lan2MCVlanBandwidthTc OBJECT-TYPE
   SYNTAX      INTEGER
               {
               auto (0)
               }
   MAX-ACCESS  read-write
   STATUS      current
   DESCRIPTION
      "Path: ethernet2.editConf.vlan.bandwidth.tc

       Possibilities:
               auto   (0)"
   ::= {er1645v2Lan2MCVlanEntry 140509184}

er1645v2Lan2MCVlanBandwidthTcFactor OBJECT-TYPE
   SYNTAX      INTEGER
               {
               ms (10),
               s100us (1)
               }
   MAX-ACCESS  read-write
   STATUS      current
   DESCRIPTION
      "Path: ethernet2.editConf.vlan.bandwidth.tcFactor

       Possibilities:
               ms   (10)
               *100us   (1)"
   ::= {er1645v2Lan2MCVlanEntry 142606336}

er1645v2Lan2MCVlanBandwidthCorrType OBJECT-TYPE
   SYNTAX      INTEGER
               {
               noCorrection (0),
               predefined (1),
               manual (2)
               }
   MAX-ACCESS  read-write
   STATUS      current
   DESCRIPTION
      "Path: ethernet2.editConf.vlan.bandwidth.correction.type

       Possibilities:
               noCorrection   (0)
               predefined   (1)
               manual   (2)"
   ::= {er1645v2Lan2MCVlanEntry 136445952}

er1645v2Lan2MCVlanBandwidthCorrPredefEncapsFrameRelay OBJECT-TYPE
   SYNTAX      DisplayString
   MAX-ACCESS  read-write
   STATUS      current
   DESCRIPTION
      "Path: ethernet2.editConf.vlan.bandwidth.correction.predefined.encapsulation.frameRelay"
   ::= {er1645v2Lan2MCVlanEntry 136594432}

er1645v2Lan2MCVlanBandwidthCorrPredefEncapsPpp OBJECT-TYPE
   SYNTAX      DisplayString
   MAX-ACCESS  read-write
   STATUS      current
   DESCRIPTION
      "Path: ethernet2.editConf.vlan.bandwidth.correction.predefined.encapsulation.ppp"
   ::= {er1645v2Lan2MCVlanEntry 136595456}

er1645v2Lan2MCVlanBandwidthCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.vlan.bandwidth.correction.predefined.encapsulation.atm.higherLayer

       Possibilities:
               rfc2684   (0)
               ppp   (1)
               pppOverEthernet   (2)"
   ::= {er1645v2Lan2MCVlanEntry 136596608}

er1645v2Lan2MCVlanBandwidthCorrPredefEncapsAtmMp OBJECT-TYPE
   SYNTAX      INTEGER
               {
               llcEncapsulation (0),
               vcMultiplexing (1)
               }
   MAX-ACCESS  read-write
   STATUS      current
   DESCRIPTION
      "Path: ethernet2.editConf.vlan.bandwidth.correction.predefined.encapsulation.atm.multiProtocol

       Possibilities:
               llcEncapsulation   (0)
               vcMultiplexing   (1)"
   ::= {er1645v2Lan2MCVlanEntry 136596736}

er1645v2Lan2MCVlanBandwidthCorrPredefEncapsHdlc OBJECT-TYPE
   SYNTAX      DisplayString
   MAX-ACCESS  read-write
   STATUS      current
   DESCRIPTION
      "Path: ethernet2.editConf.vlan.bandwidth.correction.predefined.encapsulation.hdlc"
   ::= {er1645v2Lan2MCVlanEntry 136597504}

er1645v2Lan2MCVlanBandwidthCorrPredefEncapsEfmFs OBJECT-TYPE
   SYNTAX      Integer32
   MAX-ACCESS  read-write
   STATUS      current
   DESCRIPTION
      "Path: ethernet2.editConf.vlan.bandwidth.correction.predefined.encapsulation.efm.fragmentSize"
   ::= {er1645v2Lan2MCVlanEntry 136598656}

er1645v2Lan2MCVlanBandwidthCorrPredefEncapsEfmIb OBJECT-TYPE
   SYNTAX      Integer32
   MAX-ACCESS  read-write
   STATUS      current
   DESCRIPTION
      "Path: ethernet2.editConf.vlan.bandwidth.correction.predefined.encapsulation.efm.idleBytes"
   ::= {er1645v2Lan2MCVlanEntry 136598784}

er1645v2Lan2MCVlanBandwidthCorrPredefMode OBJECT-TYPE
   SYNTAX      INTEGER
               {
               routing (0),
               bridging (1)
               }
   MAX-ACCESS  read-write
   STATUS      current
   DESCRIPTION
      "Path: ethernet2.editConf.vlan.bandwidth.correction.predefined.mode

       Possibilities:
               routing   (0)
               bridging   (1)"
   ::= {er1645v2Lan2MCVlanEntry 136609792}

er1645v2Lan2MCVlanBandwidthCorrManualOverhead OBJECT-TYPE
   SYNTAX      Integer32
   MAX-ACCESS  read-write
   STATUS      current
   DESCRIPTION
      "Path: ethernet2.editConf.vlan.bandwidth.correction.manual.overhead"
   ::= {er1645v2Lan2MCVlanEntry 136708608}

er1645v2Lan2MCVlanBandwidthCorrManualFrameData OBJECT-TYPE
   SYNTAX      Counter32
   MAX-ACCESS  read-write
   STATUS      current
   DESCRIPTION
      "Path: ethernet2.editConf.vlan.bandwidth.correction.manual.frameData

       32 bit unsigned wrappable counter."
   ::= {er1645v2Lan2MCVlanEntry 136709120}

er1645v2Lan2MCVlanBandwidthCorrManualFrameHeader OBJECT-TYPE
   SYNTAX      Counter32
   MAX-ACCESS  read-write
   STATUS      current
   DESCRIPTION
      "Path: ethernet2.editConf.vlan.bandwidth.correction.manual.frameHeader

       32 bit unsigned wrappable counter."
   ::= {er1645v2Lan2MCVlanEntry 136709632}

er1645v2Lan2MCVlanBandwidthMaxFifoQLen OBJECT-TYPE
   SYNTAX      Integer32
   MAX-ACCESS  read-write
   STATUS      current
   DESCRIPTION
      "Path: ethernet2.editConf.vlan.bandwidth.maxFifoQLen"
   ::= {er1645v2Lan2MCVlanEntry 137363456}

er1645v2Lan2MCVlanBandwidthDeFlagCir OBJECT-TYPE
   SYNTAX      INTEGER
               {
               allowed (1),
               notAllowed (2)
               }
   MAX-ACCESS  read-write
   STATUS      current
   DESCRIPTION
      "Path: ethernet2.editConf.vlan.bandwidth.deFlag.cir

       Possibilities:
               allowed   (1)
               notAllowed   (2)"
   ::= {er1645v2Lan2MCVlanEntry 147853312}

er1645v2Lan2MCVlanBandwidthDeFlagEir OBJECT-TYPE
   SYNTAX      INTEGER
               {
               allowed (1),
               notAllowed (2)
               }
   MAX-ACCESS  read-write
   STATUS      current
   DESCRIPTION
      "Path: ethernet2.editConf.vlan.bandwidth.deFlag.eir

       Possibilities:
               allowed   (1)
               notAllowed   (2)"
   ::= {er1645v2Lan2MCVlanEntry 147857408}

er1645v2Lan2MCVlanBandwidthDeFlagViolate OBJECT-TYPE
   SYNTAX      INTEGER
               {
               allowed (1),
               notAllowed (2)
               }
   MAX-ACCESS  read-write
   STATUS      current
   DESCRIPTION
      "Path: ethernet2.editConf.vlan.bandwidth.deFlag.violate

       Possibilities:
               allowed   (1)
               notAllowed   (2)"
   ::= {er1645v2Lan2MCVlanEntry 147861504}

er1645v2Lan2MCVlanBandwidthActCirActNone OBJECT-TYPE
   SYNTAX      OCTET STRING
   MAX-ACCESS  read-write
   STATUS      current
   DESCRIPTION
      "Path: ethernet2.editConf.vlan.bandwidth.action.cirAction.none"
   ::= {er1645v2Lan2MCVlanEntry 150085632}

er1645v2Lan2MCVlanBandwidthActCirActEthCos1 OBJECT-TYPE
   SYNTAX      INTEGER
               {
               unchanged (256)
               }
   MAX-ACCESS  read-write
   STATUS      current
   DESCRIPTION
      "Path: ethernet2.editConf.vlan.bandwidth.action.cirAction.ethernet.cosDepth1

       Possibilities:
               unchanged   (256)"
   ::= {er1645v2Lan2MCVlanEntry 150094080}

er1645v2Lan2MCVlanBandwidthActCirActEthDei1 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth1

       Possibilities:
               unchanged   (255)
               clear   (0)
               set   (1)"
   ::= {er1645v2Lan2MCVlanEntry 150099200}

er1645v2Lan2MCVlanBandwidthActCirActEthCos2 OBJECT-TYPE
   SYNTAX      INTEGER
               {
               unchanged (256)
               }
   MAX-ACCESS  read-write
   STATUS      current
   DESCRIPTION
      "Path: ethernet2.editConf.vlan.bandwidth.action.cirAction.ethernet.cosDepth2

       Possibilities:
               unchanged   (256)"
   ::= {er1645v2Lan2MCVlanEntry 150094336}

er1645v2Lan2MCVlanBandwidthActCirActEthDei2 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth2

       Possibilities:
               unchanged   (255)
               clear   (0)
               set   (1)"
   ::= {er1645v2Lan2MCVlanEntry 150099456}

er1645v2Lan2MCVlanBandwidthActCirActEthCos3 OBJECT-TYPE
   SYNTAX      INTEGER
               {
               unchanged (256)
               }
   MAX-ACCESS  read-write
   STATUS      current
   DESCRIPTION
      "Path: ethernet2.editConf.vlan.bandwidth.action.cirAction.ethernet.cosDepth3

       Possibilities:
               unchanged   (256)"
   ::= {er1645v2Lan2MCVlanEntry 150094592}

er1645v2Lan2MCVlanBandwidthActCirActEthDei3 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth3

       Possibilities:
               unchanged   (255)
               clear   (0)
               set   (1)"
   ::= {er1645v2Lan2MCVlanEntry 150099712}

er1645v2Lan2MCVlanBandwidthActCirActEthCos4 OBJECT-TYPE
   SYNTAX      INTEGER
               {
               unchanged (256)
               }
   MAX-ACCESS  read-write
   STATUS      current
   DESCRIPTION
      "Path: ethernet2.editConf.vlan.bandwidth.action.cirAction.ethernet.cosDepth4

       Possibilities:
               unchanged   (256)"
   ::= {er1645v2Lan2MCVlanEntry 150094848}

er1645v2Lan2MCVlanBandwidthActCirActEthDei4 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth4

       Possibilities:
               unchanged   (255)
               clear   (0)
               set   (1)"
   ::= {er1645v2Lan2MCVlanEntry 150099968}

er1645v2Lan2MCVlanBandwidthActCirActEthCos5 OBJECT-TYPE
   SYNTAX      INTEGER
               {
               unchanged (256)
               }
   MAX-ACCESS  read-write
   STATUS      current
   DESCRIPTION
      "Path: ethernet2.editConf.vlan.bandwidth.action.cirAction.ethernet.cosDepth5

       Possibilities:
               unchanged   (256)"
   ::= {er1645v2Lan2MCVlanEntry 150095104}

er1645v2Lan2MCVlanBandwidthActCirActEthDei5 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth5

       Possibilities:
               unchanged   (255)
               clear   (0)
               set   (1)"
   ::= {er1645v2Lan2MCVlanEntry 150100224}

er1645v2Lan2MCVlanBandwidthActCirActEthCos6 OBJECT-TYPE
   SYNTAX      INTEGER
               {
               unchanged (256)
               }
   MAX-ACCESS  read-write
   STATUS      current
   DESCRIPTION
      "Path: ethernet2.editConf.vlan.bandwidth.action.cirAction.ethernet.cosDepth6

       Possibilities:
               unchanged   (256)"
   ::= {er1645v2Lan2MCVlanEntry 150095360}

er1645v2Lan2MCVlanBandwidthActCirActEthDei6 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth6

       Possibilities:
               unchanged   (255)
               clear   (0)
               set   (1)"
   ::= {er1645v2Lan2MCVlanEntry 150100480}

er1645v2Lan2MCVlanBandwidthActCirActEthCos7 OBJECT-TYPE
   SYNTAX      INTEGER
               {
               unchanged (256)
               }
   MAX-ACCESS  read-write
   STATUS      current
   DESCRIPTION
      "Path: ethernet2.editConf.vlan.bandwidth.action.cirAction.ethernet.cosDepth7

       Possibilities:
               unchanged   (256)"
   ::= {er1645v2Lan2MCVlanEntry 150095616}

er1645v2Lan2MCVlanBandwidthActCirActEthDei7 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth7

       Possibilities:
               unchanged   (255)
               clear   (0)
               set   (1)"
   ::= {er1645v2Lan2MCVlanEntry 150100736}

er1645v2Lan2MCVlanBandwidthActCirActEthCos8 OBJECT-TYPE
   SYNTAX      INTEGER
               {
               unchanged (256)
               }
   MAX-ACCESS  read-write
   STATUS      current
   DESCRIPTION
      "Path: ethernet2.editConf.vlan.bandwidth.action.cirAction.ethernet.cosDepth8

       Possibilities:
               unchanged   (256)"
   ::= {er1645v2Lan2MCVlanEntry 150095872}

er1645v2Lan2MCVlanBandwidthActCirActEthDei8 OBJECT-TYPE
   SYNTAX      INTEGER
               {
               unchanged (255),
               clear (0),
               set (1)
               }
   MAX-ACCESS  read-write
   STATUS      current
   DESCRIPTION
      "Path: ethernet2.editConf.vlan.bandwidth.action.cirAction.ethernet.deiDepth8

       Possibilities:
               unchanged   (255)
               clear   (0)
               set   (1)"
   ::= {er1645v2Lan2MCVlanEntry 150100992}

er1645v2Lan2MCVlanBandwidthActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 150096128}

er1645v2Lan2MCVlanBandwidthActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 150096384}

er1645v2Lan2MCVlanBandwidthActCirActEthDrpLev OBJECT-TYPE
   SYNTAX      INTEGER
               {
               unchanged (0)
               }
   MAX-ACCESS  read-write
   STATUS      current
   DESCRIPTION
      "Path: ethernet2.editConf.vlan.bandwidth.action.cirAction.ethernet.dropLevel

       Possibilities:
               unchanged   (0)"
   ::= {er1645v2Lan2MCVlanEntry 150096640}

er1645v2Lan2MCVlanBandwidthActCirActEthDeFlag OBJECT-TYPE
   SYNTAX      INTEGER
               {
               unchanged (255),
               clear (0),
               set (1)
               }
   MAX-ACCESS  read-write
   STATUS      current
   DESCRIPTION
      "Path: ethernet2.editConf.vlan.bandwidth.action.cirAction.ethernet.deFlag

       Possibilities:
               unchanged   (255)
               clear   (0)
               set   (1)"
   ::= {er1645v2Lan2MCVlanEntry 150097408}

er1645v2Lan2MCVlanBandwidthActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 150120704}

er1645v2Lan2MCVlanBandwidthActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 150120960}

er1645v2Lan2MCVlanBandwidthActCirActIpDrpLev OBJECT-TYPE
   SYNTAX      INTEGER
               {
               unchanged (0)
               }
   MAX-ACCESS  read-write
   STATUS      current
   DESCRIPTION
      "Path: ethernet2.editConf.vlan.bandwidth.action.cirAction.ip.dropLevel

       Possibilities:
               unchanged   (0)"
   ::= {er1645v2Lan2MCVlanEntry 150121216}

er1645v2Lan2MCVlanBandwidthActCirActIpDeFlag OBJECT-TYPE
   SYNTAX      INTEGER
               {
               unchanged (255),
               clear (0),
               set (1)
               }
   MAX-ACCESS  read-write
   STATUS      current
   DESCRIPTION
      "Path: ethernet2.editConf.vlan.bandwidth.action.cirAction.ip.deFlag

       Possibilities:
               unchanged   (255)
               clear   (0)
               set   (1)"
   ::= {er1645v2Lan2MCVlanEntry 150121984}

er1645v2Lan2MCVlanBandwidthActEirActNone OBJECT-TYPE
   SYNTAX      OCTET STRING
   MAX-ACCESS  read-write
   STATUS      current
   DESCRIPTION
      "Path: ethernet2.editConf.vlan.bandwidth.action.eirAction.none"
   ::= {er1645v2Lan2MCVlanEntry 150216704}

er1645v2Lan2MCVlanBandwidthActEirActEthCos1 OBJECT-TYPE
   SYNTAX      INTEGER
               {
               unchanged (256)
               }
   MAX-ACCESS  read-write
   STATUS      current
   DESCRIPTION
      "Path: ethernet2.editConf.vlan.bandwidth.action.eirAction.ethernet.cosDepth1

       Possibilities:
               unchanged   (256)"
   ::= {er1645v2Lan2MCVlanEntry 150225152}

er1645v2Lan2MCVlanBandwidthActEirActEthDei1 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth1

       Possibilities:
               unchanged   (255)
               clear   (0)
               set   (1)"
   ::= {er1645v2Lan2MCVlanEntry 150230272}

er1645v2Lan2MCVlanBandwidthActEirActEthCos2 OBJECT-TYPE
   SYNTAX      INTEGER
               {
               unchanged (256)
               }
   MAX-ACCESS  read-write
   STATUS      current
   DESCRIPTION
      "Path: ethernet2.editConf.vlan.bandwidth.action.eirAction.ethernet.cosDepth2

       Possibilities:
               unchanged   (256)"
   ::= {er1645v2Lan2MCVlanEntry 150225408}

er1645v2Lan2MCVlanBandwidthActEirActEthDei2 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth2

       Possibilities:
               unchanged   (255)
               clear   (0)
               set   (1)"
   ::= {er1645v2Lan2MCVlanEntry 150230528}

er1645v2Lan2MCVlanBandwidthActEirActEthCos3 OBJECT-TYPE
   SYNTAX      INTEGER
               {
               unchanged (256)
               }
   MAX-ACCESS  read-write
   STATUS      current
   DESCRIPTION
      "Path: ethernet2.editConf.vlan.bandwidth.action.eirAction.ethernet.cosDepth3

       Possibilities:
               unchanged   (256)"
   ::= {er1645v2Lan2MCVlanEntry 150225664}

er1645v2Lan2MCVlanBandwidthActEirActEthDei3 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth3

       Possibilities:
               unchanged   (255)
               clear   (0)
               set   (1)"
   ::= {er1645v2Lan2MCVlanEntry 150230784}

er1645v2Lan2MCVlanBandwidthActEirActEthCos4 OBJECT-TYPE
   SYNTAX      INTEGER
               {
               unchanged (256)
               }
   MAX-ACCESS  read-write
   STATUS      current
   DESCRIPTION
      "Path: ethernet2.editConf.vlan.bandwidth.action.eirAction.ethernet.cosDepth4

       Possibilities:
               unchanged   (256)"
   ::= {er1645v2Lan2MCVlanEntry 150225920}

er1645v2Lan2MCVlanBandwidthActEirActEthDei4 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth4

       Possibilities:
               unchanged   (255)
               clear   (0)
               set   (1)"
   ::= {er1645v2Lan2MCVlanEntry 150231040}

er1645v2Lan2MCVlanBandwidthActEirActEthCos5 OBJECT-TYPE
   SYNTAX      INTEGER
               {
               unchanged (256)
               }
   MAX-ACCESS  read-write
   STATUS      current
   DESCRIPTION
      "Path: ethernet2.editConf.vlan.bandwidth.action.eirAction.ethernet.cosDepth5

       Possibilities:
               unchanged   (256)"
   ::= {er1645v2Lan2MCVlanEntry 150226176}

er1645v2Lan2MCVlanBandwidthActEirActEthDei5 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth5

       Possibilities:
               unchanged   (255)
               clear   (0)
               set   (1)"
   ::= {er1645v2Lan2MCVlanEntry 150231296}

er1645v2Lan2MCVlanBandwidthActEirActEthCos6 OBJECT-TYPE
   SYNTAX      INTEGER
               {
               unchanged (256)
               }
   MAX-ACCESS  read-write
   STATUS      current
   DESCRIPTION
      "Path: ethernet2.editConf.vlan.bandwidth.action.eirAction.ethernet.cosDepth6

       Possibilities:
               unchanged   (256)"
   ::= {er1645v2Lan2MCVlanEntry 150226432}

er1645v2Lan2MCVlanBandwidthActEirActEthDei6 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth6

       Possibilities:
               unchanged   (255)
               clear   (0)
               set   (1)"
   ::= {er1645v2Lan2MCVlanEntry 150231552}

er1645v2Lan2MCVlanBandwidthActEirActEthCos7 OBJECT-TYPE
   SYNTAX      INTEGER
               {
               unchanged (256)
               }
   MAX-ACCESS  read-write
   STATUS      current
   DESCRIPTION
      "Path: ethernet2.editConf.vlan.bandwidth.action.eirAction.ethernet.cosDepth7

       Possibilities:
               unchanged   (256)"
   ::= {er1645v2Lan2MCVlanEntry 150226688}

er1645v2Lan2MCVlanBandwidthActEirActEthDei7 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth7

       Possibilities:
               unchanged   (255)
               clear   (0)
               set   (1)"
   ::= {er1645v2Lan2MCVlanEntry 150231808}

er1645v2Lan2MCVlanBandwidthActEirActEthCos8 OBJECT-TYPE
   SYNTAX      INTEGER
               {
               unchanged (256)
               }
   MAX-ACCESS  read-write
   STATUS      current
   DESCRIPTION
      "Path: ethernet2.editConf.vlan.bandwidth.action.eirAction.ethernet.cosDepth8

       Possibilities:
               unchanged   (256)"
   ::= {er1645v2Lan2MCVlanEntry 150226944}

er1645v2Lan2MCVlanBandwidthActEirActEthDei8 OBJECT-TYPE
   SYNTAX      INTEGER
               {
               unchanged (255),
               clear (0),
               set (1)
               }
   MAX-ACCESS  read-write
   STATUS      current
   DESCRIPTION
      "Path: ethernet2.editConf.vlan.bandwidth.action.eirAction.ethernet.deiDepth8

       Possibilities:
               unchanged   (255)
               clear   (0)
               set   (1)"
   ::= {er1645v2Lan2MCVlanEntry 150232064}

er1645v2Lan2MCVlanBandwidthActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 150227200}

er1645v2Lan2MCVlanBandwidthActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 150227456}

er1645v2Lan2MCVlanBandwidthActEirActEthDrpLev OBJECT-TYPE
   SYNTAX      INTEGER
               {
               unchanged (0)
               }
   MAX-ACCESS  read-write
   STATUS      current
   DESCRIPTION
      "Path: ethernet2.editConf.vlan.bandwidth.action.eirAction.ethernet.dropLevel

       Possibilities:
               unchanged   (0)"
   ::= {er1645v2Lan2MCVlanEntry 150227712}

er1645v2Lan2MCVlanBandwidthActEirActEthDeFlag OBJECT-TYPE
   SYNTAX      INTEGER
               {
               unchanged (255),
               clear (0),
               set (1)
               }
   MAX-ACCESS  read-write
   STATUS      current
   DESCRIPTION
      "Path: ethernet2.editConf.vlan.bandwidth.action.eirAction.ethernet.deFlag

       Possibilities:
               unchanged   (255)
               clear   (0)
               set   (1)"
   ::= {er1645v2Lan2MCVlanEntry 150228480}

er1645v2Lan2MCVlanBandwidthActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 150251776}

er1645v2Lan2MCVlanBandwidthActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 150252032}

er1645v2Lan2MCVlanBandwidthActEirActIpDrpLev OBJECT-TYPE
   SYNTAX      INTEGER
               {
               unchanged (0)
               }
   MAX-ACCESS  read-write
   STATUS      current
   DESCRIPTION
      "Path: ethernet2.editConf.vlan.bandwidth.action.eirAction.ip.dropLevel

       Possibilities:
               unchanged   (0)"
   ::= {er1645v2Lan2MCVlanEntry 150252288}

er1645v2Lan2MCVlanBandwidthActEirActIpDeFlag OBJECT-TYPE
   SYNTAX      INTEGER
               {
               unchanged (255),
               clear (0),
               set (1)
               }
   MAX-ACCESS  read-write
   STATUS      current
   DESCRIPTION
      "Path: ethernet2.editConf.vlan.bandwidth.action.eirAction.ip.deFlag

       Possibilities:
               unchanged   (255)
               clear   (0)
               set   (1)"
   ::= {er1645v2Lan2MCVlanEntry 150253056}

er1645v2Lan2MCVlanBandwidthActViolActNone OBJECT-TYPE
   SYNTAX      OCTET STRING
   MAX-ACCESS  read-write
   STATUS      current
   DESCRIPTION
      "Path: ethernet2.editConf.vlan.bandwidth.action.violateAction.none"
   ::= {er1645v2Lan2MCVlanEntry 150347776}

er1645v2Lan2MCVlanBandwidthActViolActDrop OBJECT-TYPE
   SYNTAX      OCTET STRING
   MAX-ACCESS  read-write
   STATUS      current
   DESCRIPTION
      "Path: ethernet2.editConf.vlan.bandwidth.action.violateAction.drop"
   ::= {er1645v2Lan2MCVlanEntry 150364160}

er1645v2Lan2MCVlanBandwidthActViolActEthCos1 OBJECT-TYPE
   SYNTAX      INTEGER
               {
               unchanged (256)
               }
   MAX-ACCESS  read-write
   STATUS      current
   DESCRIPTION
      "Path: ethernet2.editConf.vlan.bandwidth.action.violateAction.ethernet.cosDepth1

       Possibilities:
               unchanged   (256)"
   ::= {er1645v2Lan2MCVlanEntry 150356224}

er1645v2Lan2MCVlanBandwidthActViolActEthDei1 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth1

       Possibilities:
               unchanged   (255)
               clear   (0)
               set   (1)"
   ::= {er1645v2Lan2MCVlanEntry 150361344}

er1645v2Lan2MCVlanBandwidthActViolActEthCos2 OBJECT-TYPE
   SYNTAX      INTEGER
               {
               unchanged (256)
               }
   MAX-ACCESS  read-write
   STATUS      current
   DESCRIPTION
      "Path: ethernet2.editConf.vlan.bandwidth.action.violateAction.ethernet.cosDepth2

       Possibilities:
               unchanged   (256)"
   ::= {er1645v2Lan2MCVlanEntry 150356480}

er1645v2Lan2MCVlanBandwidthActViolActEthDei2 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth2

       Possibilities:
               unchanged   (255)
               clear   (0)
               set   (1)"
   ::= {er1645v2Lan2MCVlanEntry 150361600}

er1645v2Lan2MCVlanBandwidthActViolActEthCos3 OBJECT-TYPE
   SYNTAX      INTEGER
               {
               unchanged (256)
               }
   MAX-ACCESS  read-write
   STATUS      current
   DESCRIPTION
      "Path: ethernet2.editConf.vlan.bandwidth.action.violateAction.ethernet.cosDepth3

       Possibilities:
               unchanged   (256)"
   ::= {er1645v2Lan2MCVlanEntry 150356736}

er1645v2Lan2MCVlanBandwidthActViolActEthDei3 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth3

       Possibilities:
               unchanged   (255)
               clear   (0)
               set   (1)"
   ::= {er1645v2Lan2MCVlanEntry 150361856}

er1645v2Lan2MCVlanBandwidthActViolActEthCos4 OBJECT-TYPE
   SYNTAX      INTEGER
               {
               unchanged (256)
               }
   MAX-ACCESS  read-write
   STATUS      current
   DESCRIPTION
      "Path: ethernet2.editConf.vlan.bandwidth.action.violateAction.ethernet.cosDepth4

       Possibilities:
               unchanged   (256)"
   ::= {er1645v2Lan2MCVlanEntry 150356992}

er1645v2Lan2MCVlanBandwidthActViolActEthDei4 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth4

       Possibilities:
               unchanged   (255)
               clear   (0)
               set   (1)"
   ::= {er1645v2Lan2MCVlanEntry 150362112}

er1645v2Lan2MCVlanBandwidthActViolActEthCos5 OBJECT-TYPE
   SYNTAX      INTEGER
               {
               unchanged (256)
               }
   MAX-ACCESS  read-write
   STATUS      current
   DESCRIPTION
      "Path: ethernet2.editConf.vlan.bandwidth.action.violateAction.ethernet.cosDepth5

       Possibilities:
               unchanged   (256)"
   ::= {er1645v2Lan2MCVlanEntry 150357248}

er1645v2Lan2MCVlanBandwidthActViolActEthDei5 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth5

       Possibilities:
               unchanged   (255)
               clear   (0)
               set   (1)"
   ::= {er1645v2Lan2MCVlanEntry 150362368}

er1645v2Lan2MCVlanBandwidthActViolActEthCos6 OBJECT-TYPE
   SYNTAX      INTEGER
               {
               unchanged (256)
               }
   MAX-ACCESS  read-write
   STATUS      current
   DESCRIPTION
      "Path: ethernet2.editConf.vlan.bandwidth.action.violateAction.ethernet.cosDepth6

       Possibilities:
               unchanged   (256)"
   ::= {er1645v2Lan2MCVlanEntry 150357504}

er1645v2Lan2MCVlanBandwidthActViolActEthDei6 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth6

       Possibilities:
               unchanged   (255)
               clear   (0)
               set   (1)"
   ::= {er1645v2Lan2MCVlanEntry 150362624}

er1645v2Lan2MCVlanBandwidthActViolActEthCos7 OBJECT-TYPE
   SYNTAX      INTEGER
               {
               unchanged (256)
               }
   MAX-ACCESS  read-write
   STATUS      current
   DESCRIPTION
      "Path: ethernet2.editConf.vlan.bandwidth.action.violateAction.ethernet.cosDepth7

       Possibilities:
               unchanged   (256)"
   ::= {er1645v2Lan2MCVlanEntry 150357760}

er1645v2Lan2MCVlanBandwidthActViolActEthDei7 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth7

       Possibilities:
               unchanged   (255)
               clear   (0)
               set   (1)"
   ::= {er1645v2Lan2MCVlanEntry 150362880}

er1645v2Lan2MCVlanBandwidthActViolActEthCos8 OBJECT-TYPE
   SYNTAX      INTEGER
               {
               unchanged (256)
               }
   MAX-ACCESS  read-write
   STATUS      current
   DESCRIPTION
      "Path: ethernet2.editConf.vlan.bandwidth.action.violateAction.ethernet.cosDepth8

       Possibilities:
               unchanged   (256)"
   ::= {er1645v2Lan2MCVlanEntry 150358016}

er1645v2Lan2MCVlanBandwidthActViolActEthDei8 OBJECT-TYPE
   SYNTAX      INTEGER
               {
               unchanged (255),
               clear (0),
               set (1)
               }
   MAX-ACCESS  read-write
   STATUS      current
   DESCRIPTION
      "Path: ethernet2.editConf.vlan.bandwidth.action.violateAction.ethernet.deiDepth8

       Possibilities:
               unchanged   (255)
               clear   (0)
               set   (1)"
   ::= {er1645v2Lan2MCVlanEntry 150363136}

er1645v2Lan2MCVlanBandwidthActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 150358272}

er1645v2Lan2MCVlanBandwidthActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 150358528}

er1645v2Lan2MCVlanBandwidthActViolActEthDrpLev OBJECT-TYPE
   SYNTAX      INTEGER
               {
               unchanged (0)
               }
   MAX-ACCESS  read-write
   STATUS      current
   DESCRIPTION
      "Path: ethernet2.editConf.vlan.bandwidth.action.violateAction.ethernet.dropLevel

       Possibilities:
               unchanged   (0)"
   ::= {er1645v2Lan2MCVlanEntry 150358784}

er1645v2Lan2MCVlanBandwidthActViolActEthDeFlag OBJECT-TYPE
   SYNTAX      INTEGER
               {
               unchanged (255),
               clear (0),
               set (1)
               }
   MAX-ACCESS  read-write
   STATUS      current
   DESCRIPTION
      "Path: ethernet2.editConf.vlan.bandwidth.action.violateAction.ethernet.deFlag

       Possibilities:
               unchanged   (255)
               clear   (0)
               set   (1)"
   ::= {er1645v2Lan2MCVlanEntry 150359552}

er1645v2Lan2MCVlanBandwidthActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.bandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 150382848}

er1645v2Lan2MCVlanBandwidthActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.bandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 150383104}

er1645v2Lan2MCVlanBandwidthActViolActIpDrpLev OBJECT-TYPE
   SYNTAX      INTEGER
               {
               unchanged (0)
               }
   MAX-ACCESS  read-write
   STATUS      current
   DESCRIPTION
      "Path: ethernet2.editConf.vlan.bandwidth.action.violateAction.ip.dropLevel

       Possibilities:
               unchanged   (0)"
   ::= {er1645v2Lan2MCVlanEntry 150383360}

er1645v2Lan2MCVlanBandwidthActViolActIpDeFlag OBJECT-TYPE
   SYNTAX      INTEGER
               {
               unchanged (255),
               clear (0),
               set (1)
               }
   MAX-ACCESS  read-write
   STATUS      current
   DESCRIPTION
      "Path: ethernet2.editConf.vlan.bandwidth.action.violateAction.ip.deFlag

       Possibilities:
               unchanged   (255)
               clear   (0)
               set   (1)"
   ::= {er1645v2Lan2MCVlanEntry 150384128}

er1645v2Lan2MCVlanInbBwMode OBJECT-TYPE
   SYNTAX      INTEGER
               {
               reshaping (1),
               policing (2)
               }
   MAX-ACCESS  read-write
   STATUS      current
   DESCRIPTION
      "Path: ethernet2.editConf.vlan.inboundBandwidth.mode

       Possibilities:
               reshaping   (1)
               policing   (2)"
   ::= {er1645v2Lan2MCVlanEntry 132120576}

er1645v2Lan2MCVlanInbBwCir OBJECT-TYPE
   SYNTAX      Integer32
   MAX-ACCESS  read-write
   STATUS      current
   DESCRIPTION
      "Path: ethernet2.editConf.vlan.inboundBandwidth.cir"
   ::= {er1645v2Lan2MCVlanEntry 118489088}

er1645v2Lan2MCVlanInbBwEir OBJECT-TYPE
   SYNTAX      Integer32
   MAX-ACCESS  read-write
   STATUS      current
   DESCRIPTION
      "Path: ethernet2.editConf.vlan.inboundBandwidth.eir"
   ::= {er1645v2Lan2MCVlanEntry 124780544}

er1645v2Lan2MCVlanInbBwUnit OBJECT-TYPE
   SYNTAX      INTEGER
               {
               bitssec (1),
               percent (2)
               }
   MAX-ACCESS  read-write
   STATUS      current
   DESCRIPTION
      "Path: ethernet2.editConf.vlan.inboundBandwidth.unit

       Possibilities:
               bits/sec   (1)
               percent   (2)"
   ::= {er1645v2Lan2MCVlanEntry 122683392}

er1645v2Lan2MCVlanInbBwTc OBJECT-TYPE
   SYNTAX      INTEGER
               {
               auto (0)
               }
   MAX-ACCESS  read-write
   STATUS      current
   DESCRIPTION
      "Path: ethernet2.editConf.vlan.inboundBandwidth.tc

       Possibilities:
               auto   (0)"
   ::= {er1645v2Lan2MCVlanEntry 123731968}

er1645v2Lan2MCVlanInbBwTcFactor OBJECT-TYPE
   SYNTAX      INTEGER
               {
               ms (10),
               s100us (1)
               }
   MAX-ACCESS  read-write
   STATUS      current
   DESCRIPTION
      "Path: ethernet2.editConf.vlan.inboundBandwidth.tcFactor

       Possibilities:
               ms   (10)
               *100us   (1)"
   ::= {er1645v2Lan2MCVlanEntry 125829120}

er1645v2Lan2MCVlanInbBwCorrType OBJECT-TYPE
   SYNTAX      INTEGER
               {
               noCorrection (0),
               predefined (1),
               manual (2)
               }
   MAX-ACCESS  read-write
   STATUS      current
   DESCRIPTION
      "Path: ethernet2.editConf.vlan.inboundBandwidth.correction.type

       Possibilities:
               noCorrection   (0)
               predefined   (1)
               manual   (2)"
   ::= {er1645v2Lan2MCVlanEntry 119668736}

er1645v2Lan2MCVlanInbBwCorrPredefEncapsFrameRelay OBJECT-TYPE
   SYNTAX      DisplayString
   MAX-ACCESS  read-write
   STATUS      current
   DESCRIPTION
      "Path: ethernet2.editConf.vlan.inboundBandwidth.correction.predefined.encapsulation.frameRelay"
   ::= {er1645v2Lan2MCVlanEntry 119817216}

er1645v2Lan2MCVlanInbBwCorrPredefEncapsPpp OBJECT-TYPE
   SYNTAX      DisplayString
   MAX-ACCESS  read-write
   STATUS      current
   DESCRIPTION
      "Path: ethernet2.editConf.vlan.inboundBandwidth.correction.predefined.encapsulation.ppp"
   ::= {er1645v2Lan2MCVlanEntry 119818240}

er1645v2Lan2MCVlanInbBwCorrPredefEncapsAtmHl OBJECT-TYPE
   SYNTAX      INTEGER
               {
               rfc2684 (0),
               ppp (1),
               pppOverEthernet (2)
               }
   MAX-ACCESS  read-write
   STATUS      current
   DESCRIPTION
      "Path: ethernet2.editConf.vlan.inboundBandwidth.correction.predefined.encapsulation.atm.higherLayer

       Possibilities:
               rfc2684   (0)
               ppp   (1)
               pppOverEthernet   (2)"
   ::= {er1645v2Lan2MCVlanEntry 119819392}

er1645v2Lan2MCVlanInbBwCorrPredefEncapsAtmMp OBJECT-TYPE
   SYNTAX      INTEGER
               {
               llcEncapsulation (0),
               vcMultiplexing (1)
               }
   MAX-ACCESS  read-write
   STATUS      current
   DESCRIPTION
      "Path: ethernet2.editConf.vlan.inboundBandwidth.correction.predefined.encapsulation.atm.multiProtocol

       Possibilities:
               llcEncapsulation   (0)
               vcMultiplexing   (1)"
   ::= {er1645v2Lan2MCVlanEntry 119819520}

er1645v2Lan2MCVlanInbBwCorrPredefEncapsHdlc OBJECT-TYPE
   SYNTAX      DisplayString
   MAX-ACCESS  read-write
   STATUS      current
   DESCRIPTION
      "Path: ethernet2.editConf.vlan.inboundBandwidth.correction.predefined.encapsulation.hdlc"
   ::= {er1645v2Lan2MCVlanEntry 119820288}

er1645v2Lan2MCVlanInbBwCorrPredefEncapsEfmFs OBJECT-TYPE
   SYNTAX      Integer32
   MAX-ACCESS  read-write
   STATUS      current
   DESCRIPTION
      "Path: ethernet2.editConf.vlan.inboundBandwidth.correction.predefined.encapsulation.efm.fragmentSize"
   ::= {er1645v2Lan2MCVlanEntry 119821440}

er1645v2Lan2MCVlanInbBwCorrPredefEncapsEfmIb OBJECT-TYPE
   SYNTAX      Integer32
   MAX-ACCESS  read-write
   STATUS      current
   DESCRIPTION
      "Path: ethernet2.editConf.vlan.inboundBandwidth.correction.predefined.encapsulation.efm.idleBytes"
   ::= {er1645v2Lan2MCVlanEntry 119821568}

er1645v2Lan2MCVlanInbBwCorrPredefMode OBJECT-TYPE
   SYNTAX      INTEGER
               {
               routing (0),
               bridging (1)
               }
   MAX-ACCESS  read-write
   STATUS      current
   DESCRIPTION
      "Path: ethernet2.editConf.vlan.inboundBandwidth.correction.predefined.mode

       Possibilities:
               routing   (0)
               bridging   (1)"
   ::= {er1645v2Lan2MCVlanEntry 119832576}

er1645v2Lan2MCVlanInbBwCorrManualOverhead OBJECT-TYPE
   SYNTAX      Integer32
   MAX-ACCESS  read-write
   STATUS      current
   DESCRIPTION
      "Path: ethernet2.editConf.vlan.inboundBandwidth.correction.manual.overhead"
   ::= {er1645v2Lan2MCVlanEntry 119931392}

er1645v2Lan2MCVlanInbBwCorrManualFrameData OBJECT-TYPE
   SYNTAX      Counter32
   MAX-ACCESS  read-write
   STATUS      current
   DESCRIPTION
      "Path: ethernet2.editConf.vlan.inboundBandwidth.correction.manual.frameData

       32 bit unsigned wrappable counter."
   ::= {er1645v2Lan2MCVlanEntry 119931904}

er1645v2Lan2MCVlanInbBwCorrManualFrameHeader OBJECT-TYPE
   SYNTAX      Counter32
   MAX-ACCESS  read-write
   STATUS      current
   DESCRIPTION
      "Path: ethernet2.editConf.vlan.inboundBandwidth.correction.manual.frameHeader

       32 bit unsigned wrappable counter."
   ::= {er1645v2Lan2MCVlanEntry 119932416}

er1645v2Lan2MCVlanInbBwMaxFifoQLen OBJECT-TYPE
   SYNTAX      Integer32
   MAX-ACCESS  read-write
   STATUS      current
   DESCRIPTION
      "Path: ethernet2.editConf.vlan.inboundBandwidth.maxFifoQLen"
   ::= {er1645v2Lan2MCVlanEntry 120586240}

er1645v2Lan2MCVlanInbBwPriorityPolicy OBJECT-TYPE
   SYNTAX      DisplayString
   MAX-ACCESS  read-write
   STATUS      current
   DESCRIPTION
      "Path: ethernet2.editConf.vlan.inboundBandwidth.priorityPolicy"
   ::= {er1645v2Lan2MCVlanEntry 121634816}

er1645v2Lan2MCVlanInbBwDeFlagCir OBJECT-TYPE
   SYNTAX      INTEGER
               {
               allowed (1),
               notAllowed (2)
               }
   MAX-ACCESS  read-write
   STATUS      current
   DESCRIPTION
      "Path: ethernet2.editConf.vlan.inboundBandwidth.deFlag.cir

       Possibilities:
               allowed   (1)
               notAllowed   (2)"
   ::= {er1645v2Lan2MCVlanEntry 131076096}

er1645v2Lan2MCVlanInbBwDeFlagEir OBJECT-TYPE
   SYNTAX      INTEGER
               {
               allowed (1),
               notAllowed (2)
               }
   MAX-ACCESS  read-write
   STATUS      current
   DESCRIPTION
      "Path: ethernet2.editConf.vlan.inboundBandwidth.deFlag.eir

       Possibilities:
               allowed   (1)
               notAllowed   (2)"
   ::= {er1645v2Lan2MCVlanEntry 131080192}

er1645v2Lan2MCVlanInbBwDeFlagViolate OBJECT-TYPE
   SYNTAX      INTEGER
               {
               allowed (1),
               notAllowed (2)
               }
   MAX-ACCESS  read-write
   STATUS      current
   DESCRIPTION
      "Path: ethernet2.editConf.vlan.inboundBandwidth.deFlag.violate

       Possibilities:
               allowed   (1)
               notAllowed   (2)"
   ::= {er1645v2Lan2MCVlanEntry 131084288}

er1645v2Lan2MCVlanInbBwActCirActNone OBJECT-TYPE
   SYNTAX      OCTET STRING
   MAX-ACCESS  read-write
   STATUS      current
   DESCRIPTION
      "Path: ethernet2.editConf.vlan.inboundBandwidth.action.cirAction.none"
   ::= {er1645v2Lan2MCVlanEntry 133308416}

er1645v2Lan2MCVlanInbBwActCirActEthCos1 OBJECT-TYPE
   SYNTAX      INTEGER
               {
               unchanged (256)
               }
   MAX-ACCESS  read-write
   STATUS      current
   DESCRIPTION
      "Path: ethernet2.editConf.vlan.inboundBandwidth.action.cirAction.ethernet.cosDepth1

       Possibilities:
               unchanged   (256)"
   ::= {er1645v2Lan2MCVlanEntry 133316864}

er1645v2Lan2MCVlanInbBwActCirActEthDei1 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth1

       Possibilities:
               unchanged   (255)
               clear   (0)
               set   (1)"
   ::= {er1645v2Lan2MCVlanEntry 133321984}

er1645v2Lan2MCVlanInbBwActCirActEthCos2 OBJECT-TYPE
   SYNTAX      INTEGER
               {
               unchanged (256)
               }
   MAX-ACCESS  read-write
   STATUS      current
   DESCRIPTION
      "Path: ethernet2.editConf.vlan.inboundBandwidth.action.cirAction.ethernet.cosDepth2

       Possibilities:
               unchanged   (256)"
   ::= {er1645v2Lan2MCVlanEntry 133317120}

er1645v2Lan2MCVlanInbBwActCirActEthDei2 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth2

       Possibilities:
               unchanged   (255)
               clear   (0)
               set   (1)"
   ::= {er1645v2Lan2MCVlanEntry 133322240}

er1645v2Lan2MCVlanInbBwActCirActEthCos3 OBJECT-TYPE
   SYNTAX      INTEGER
               {
               unchanged (256)
               }
   MAX-ACCESS  read-write
   STATUS      current
   DESCRIPTION
      "Path: ethernet2.editConf.vlan.inboundBandwidth.action.cirAction.ethernet.cosDepth3

       Possibilities:
               unchanged   (256)"
   ::= {er1645v2Lan2MCVlanEntry 133317376}

er1645v2Lan2MCVlanInbBwActCirActEthDei3 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth3

       Possibilities:
               unchanged   (255)
               clear   (0)
               set   (1)"
   ::= {er1645v2Lan2MCVlanEntry 133322496}

er1645v2Lan2MCVlanInbBwActCirActEthCos4 OBJECT-TYPE
   SYNTAX      INTEGER
               {
               unchanged (256)
               }
   MAX-ACCESS  read-write
   STATUS      current
   DESCRIPTION
      "Path: ethernet2.editConf.vlan.inboundBandwidth.action.cirAction.ethernet.cosDepth4

       Possibilities:
               unchanged   (256)"
   ::= {er1645v2Lan2MCVlanEntry 133317632}

er1645v2Lan2MCVlanInbBwActCirActEthDei4 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth4

       Possibilities:
               unchanged   (255)
               clear   (0)
               set   (1)"
   ::= {er1645v2Lan2MCVlanEntry 133322752}

er1645v2Lan2MCVlanInbBwActCirActEthCos5 OBJECT-TYPE
   SYNTAX      INTEGER
               {
               unchanged (256)
               }
   MAX-ACCESS  read-write
   STATUS      current
   DESCRIPTION
      "Path: ethernet2.editConf.vlan.inboundBandwidth.action.cirAction.ethernet.cosDepth5

       Possibilities:
               unchanged   (256)"
   ::= {er1645v2Lan2MCVlanEntry 133317888}

er1645v2Lan2MCVlanInbBwActCirActEthDei5 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth5

       Possibilities:
               unchanged   (255)
               clear   (0)
               set   (1)"
   ::= {er1645v2Lan2MCVlanEntry 133323008}

er1645v2Lan2MCVlanInbBwActCirActEthCos6 OBJECT-TYPE
   SYNTAX      INTEGER
               {
               unchanged (256)
               }
   MAX-ACCESS  read-write
   STATUS      current
   DESCRIPTION
      "Path: ethernet2.editConf.vlan.inboundBandwidth.action.cirAction.ethernet.cosDepth6

       Possibilities:
               unchanged   (256)"
   ::= {er1645v2Lan2MCVlanEntry 133318144}

er1645v2Lan2MCVlanInbBwActCirActEthDei6 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth6

       Possibilities:
               unchanged   (255)
               clear   (0)
               set   (1)"
   ::= {er1645v2Lan2MCVlanEntry 133323264}

er1645v2Lan2MCVlanInbBwActCirActEthCos7 OBJECT-TYPE
   SYNTAX      INTEGER
               {
               unchanged (256)
               }
   MAX-ACCESS  read-write
   STATUS      current
   DESCRIPTION
      "Path: ethernet2.editConf.vlan.inboundBandwidth.action.cirAction.ethernet.cosDepth7

       Possibilities:
               unchanged   (256)"
   ::= {er1645v2Lan2MCVlanEntry 133318400}

er1645v2Lan2MCVlanInbBwActCirActEthDei7 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth7

       Possibilities:
               unchanged   (255)
               clear   (0)
               set   (1)"
   ::= {er1645v2Lan2MCVlanEntry 133323520}

er1645v2Lan2MCVlanInbBwActCirActEthCos8 OBJECT-TYPE
   SYNTAX      INTEGER
               {
               unchanged (256)
               }
   MAX-ACCESS  read-write
   STATUS      current
   DESCRIPTION
      "Path: ethernet2.editConf.vlan.inboundBandwidth.action.cirAction.ethernet.cosDepth8

       Possibilities:
               unchanged   (256)"
   ::= {er1645v2Lan2MCVlanEntry 133318656}

er1645v2Lan2MCVlanInbBwActCirActEthDei8 OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deiDepth8

       Possibilities:
               unchanged   (255)
               clear   (0)
               set   (1)"
   ::= {er1645v2Lan2MCVlanEntry 133323776}

er1645v2Lan2MCVlanInbBwActCirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.cirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 133318912}

er1645v2Lan2MCVlanInbBwActCirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.cirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 133319168}

er1645v2Lan2MCVlanInbBwActCirActEthDrpLev OBJECT-TYPE
   SYNTAX      INTEGER
               {
               unchanged (0)
               }
   MAX-ACCESS  read-write
   STATUS      current
   DESCRIPTION
      "Path: ethernet2.editConf.vlan.inboundBandwidth.action.cirAction.ethernet.dropLevel

       Possibilities:
               unchanged   (0)"
   ::= {er1645v2Lan2MCVlanEntry 133319424}

er1645v2Lan2MCVlanInbBwActCirActEthDeFlag OBJECT-TYPE
   SYNTAX      INTEGER
               {
               unchanged (255),
               clear (0),
               set (1)
               }
   MAX-ACCESS  read-write
   STATUS      current
   DESCRIPTION
      "Path: ethernet2.editConf.vlan.inboundBandwidth.action.cirAction.ethernet.deFlag

       Possibilities:
               unchanged   (255)
               clear   (0)
               set   (1)"
   ::= {er1645v2Lan2MCVlanEntry 133320192}

er1645v2Lan2MCVlanInbBwActCirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.cirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 133343488}

er1645v2Lan2MCVlanInbBwActCirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.cirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 133343744}

er1645v2Lan2MCVlanInbBwActCirActIpDrpLev OBJECT-TYPE
   SYNTAX      INTEGER
               {
               unchanged (0)
               }
   MAX-ACCESS  read-write
   STATUS      current
   DESCRIPTION
      "Path: ethernet2.editConf.vlan.inboundBandwidth.action.cirAction.ip.dropLevel

       Possibilities:
               unchanged   (0)"
   ::= {er1645v2Lan2MCVlanEntry 133344000}

er1645v2Lan2MCVlanInbBwActCirActIpDeFlag OBJECT-TYPE
   SYNTAX      INTEGER
               {
               unchanged (255),
               clear (0),
               set (1)
               }
   MAX-ACCESS  read-write
   STATUS      current
   DESCRIPTION
      "Path: ethernet2.editConf.vlan.inboundBandwidth.action.cirAction.ip.deFlag

       Possibilities:
               unchanged   (255)
               clear   (0)
               set   (1)"
   ::= {er1645v2Lan2MCVlanEntry 133344768}

er1645v2Lan2MCVlanInbBwActEirActNone OBJECT-TYPE
   SYNTAX      OCTET STRING
   MAX-ACCESS  read-write
   STATUS      current
   DESCRIPTION
      "Path: ethernet2.editConf.vlan.inboundBandwidth.action.eirAction.none"
   ::= {er1645v2Lan2MCVlanEntry 133439488}

er1645v2Lan2MCVlanInbBwActEirActEthCos1 OBJECT-TYPE
   SYNTAX      INTEGER
               {
               unchanged (256)
               }
   MAX-ACCESS  read-write
   STATUS      current
   DESCRIPTION
      "Path: ethernet2.editConf.vlan.inboundBandwidth.action.eirAction.ethernet.cosDepth1

       Possibilities:
               unchanged   (256)"
   ::= {er1645v2Lan2MCVlanEntry 133447936}

er1645v2Lan2MCVlanInbBwActEirActEthDei1 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth1

       Possibilities:
               unchanged   (255)
               clear   (0)
               set   (1)"
   ::= {er1645v2Lan2MCVlanEntry 133453056}

er1645v2Lan2MCVlanInbBwActEirActEthCos2 OBJECT-TYPE
   SYNTAX      INTEGER
               {
               unchanged (256)
               }
   MAX-ACCESS  read-write
   STATUS      current
   DESCRIPTION
      "Path: ethernet2.editConf.vlan.inboundBandwidth.action.eirAction.ethernet.cosDepth2

       Possibilities:
               unchanged   (256)"
   ::= {er1645v2Lan2MCVlanEntry 133448192}

er1645v2Lan2MCVlanInbBwActEirActEthDei2 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth2

       Possibilities:
               unchanged   (255)
               clear   (0)
               set   (1)"
   ::= {er1645v2Lan2MCVlanEntry 133453312}

er1645v2Lan2MCVlanInbBwActEirActEthCos3 OBJECT-TYPE
   SYNTAX      INTEGER
               {
               unchanged (256)
               }
   MAX-ACCESS  read-write
   STATUS      current
   DESCRIPTION
      "Path: ethernet2.editConf.vlan.inboundBandwidth.action.eirAction.ethernet.cosDepth3

       Possibilities:
               unchanged   (256)"
   ::= {er1645v2Lan2MCVlanEntry 133448448}

er1645v2Lan2MCVlanInbBwActEirActEthDei3 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth3

       Possibilities:
               unchanged   (255)
               clear   (0)
               set   (1)"
   ::= {er1645v2Lan2MCVlanEntry 133453568}

er1645v2Lan2MCVlanInbBwActEirActEthCos4 OBJECT-TYPE
   SYNTAX      INTEGER
               {
               unchanged (256)
               }
   MAX-ACCESS  read-write
   STATUS      current
   DESCRIPTION
      "Path: ethernet2.editConf.vlan.inboundBandwidth.action.eirAction.ethernet.cosDepth4

       Possibilities:
               unchanged   (256)"
   ::= {er1645v2Lan2MCVlanEntry 133448704}

er1645v2Lan2MCVlanInbBwActEirActEthDei4 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth4

       Possibilities:
               unchanged   (255)
               clear   (0)
               set   (1)"
   ::= {er1645v2Lan2MCVlanEntry 133453824}

er1645v2Lan2MCVlanInbBwActEirActEthCos5 OBJECT-TYPE
   SYNTAX      INTEGER
               {
               unchanged (256)
               }
   MAX-ACCESS  read-write
   STATUS      current
   DESCRIPTION
      "Path: ethernet2.editConf.vlan.inboundBandwidth.action.eirAction.ethernet.cosDepth5

       Possibilities:
               unchanged   (256)"
   ::= {er1645v2Lan2MCVlanEntry 133448960}

er1645v2Lan2MCVlanInbBwActEirActEthDei5 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth5

       Possibilities:
               unchanged   (255)
               clear   (0)
               set   (1)"
   ::= {er1645v2Lan2MCVlanEntry 133454080}

er1645v2Lan2MCVlanInbBwActEirActEthCos6 OBJECT-TYPE
   SYNTAX      INTEGER
               {
               unchanged (256)
               }
   MAX-ACCESS  read-write
   STATUS      current
   DESCRIPTION
      "Path: ethernet2.editConf.vlan.inboundBandwidth.action.eirAction.ethernet.cosDepth6

       Possibilities:
               unchanged   (256)"
   ::= {er1645v2Lan2MCVlanEntry 133449216}

er1645v2Lan2MCVlanInbBwActEirActEthDei6 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth6

       Possibilities:
               unchanged   (255)
               clear   (0)
               set   (1)"
   ::= {er1645v2Lan2MCVlanEntry 133454336}

er1645v2Lan2MCVlanInbBwActEirActEthCos7 OBJECT-TYPE
   SYNTAX      INTEGER
               {
               unchanged (256)
               }
   MAX-ACCESS  read-write
   STATUS      current
   DESCRIPTION
      "Path: ethernet2.editConf.vlan.inboundBandwidth.action.eirAction.ethernet.cosDepth7

       Possibilities:
               unchanged   (256)"
   ::= {er1645v2Lan2MCVlanEntry 133449472}

er1645v2Lan2MCVlanInbBwActEirActEthDei7 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth7

       Possibilities:
               unchanged   (255)
               clear   (0)
               set   (1)"
   ::= {er1645v2Lan2MCVlanEntry 133454592}

er1645v2Lan2MCVlanInbBwActEirActEthCos8 OBJECT-TYPE
   SYNTAX      INTEGER
               {
               unchanged (256)
               }
   MAX-ACCESS  read-write
   STATUS      current
   DESCRIPTION
      "Path: ethernet2.editConf.vlan.inboundBandwidth.action.eirAction.ethernet.cosDepth8

       Possibilities:
               unchanged   (256)"
   ::= {er1645v2Lan2MCVlanEntry 133449728}

er1645v2Lan2MCVlanInbBwActEirActEthDei8 OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deiDepth8

       Possibilities:
               unchanged   (255)
               clear   (0)
               set   (1)"
   ::= {er1645v2Lan2MCVlanEntry 133454848}

er1645v2Lan2MCVlanInbBwActEirActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.eirAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 133449984}

er1645v2Lan2MCVlanInbBwActEirActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.eirAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 133450240}

er1645v2Lan2MCVlanInbBwActEirActEthDrpLev OBJECT-TYPE
   SYNTAX      INTEGER
               {
               unchanged (0)
               }
   MAX-ACCESS  read-write
   STATUS      current
   DESCRIPTION
      "Path: ethernet2.editConf.vlan.inboundBandwidth.action.eirAction.ethernet.dropLevel

       Possibilities:
               unchanged   (0)"
   ::= {er1645v2Lan2MCVlanEntry 133450496}

er1645v2Lan2MCVlanInbBwActEirActEthDeFlag OBJECT-TYPE
   SYNTAX      INTEGER
               {
               unchanged (255),
               clear (0),
               set (1)
               }
   MAX-ACCESS  read-write
   STATUS      current
   DESCRIPTION
      "Path: ethernet2.editConf.vlan.inboundBandwidth.action.eirAction.ethernet.deFlag

       Possibilities:
               unchanged   (255)
               clear   (0)
               set   (1)"
   ::= {er1645v2Lan2MCVlanEntry 133451264}

er1645v2Lan2MCVlanInbBwActEirActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.eirAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 133474560}

er1645v2Lan2MCVlanInbBwActEirActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.eirAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 133474816}

er1645v2Lan2MCVlanInbBwActEirActIpDrpLev OBJECT-TYPE
   SYNTAX      INTEGER
               {
               unchanged (0)
               }
   MAX-ACCESS  read-write
   STATUS      current
   DESCRIPTION
      "Path: ethernet2.editConf.vlan.inboundBandwidth.action.eirAction.ip.dropLevel

       Possibilities:
               unchanged   (0)"
   ::= {er1645v2Lan2MCVlanEntry 133475072}

er1645v2Lan2MCVlanInbBwActEirActIpDeFlag OBJECT-TYPE
   SYNTAX      INTEGER
               {
               unchanged (255),
               clear (0),
               set (1)
               }
   MAX-ACCESS  read-write
   STATUS      current
   DESCRIPTION
      "Path: ethernet2.editConf.vlan.inboundBandwidth.action.eirAction.ip.deFlag

       Possibilities:
               unchanged   (255)
               clear   (0)
               set   (1)"
   ::= {er1645v2Lan2MCVlanEntry 133475840}

er1645v2Lan2MCVlanInbBwActViolActNone OBJECT-TYPE
   SYNTAX      OCTET STRING
   MAX-ACCESS  read-write
   STATUS      current
   DESCRIPTION
      "Path: ethernet2.editConf.vlan.inboundBandwidth.action.violateAction.none"
   ::= {er1645v2Lan2MCVlanEntry 133570560}

er1645v2Lan2MCVlanInbBwActViolActDrop OBJECT-TYPE
   SYNTAX      OCTET STRING
   MAX-ACCESS  read-write
   STATUS      current
   DESCRIPTION
      "Path: ethernet2.editConf.vlan.inboundBandwidth.action.violateAction.drop"
   ::= {er1645v2Lan2MCVlanEntry 133586944}

er1645v2Lan2MCVlanInbBwActViolActEthCos1 OBJECT-TYPE
   SYNTAX      INTEGER
               {
               unchanged (256)
               }
   MAX-ACCESS  read-write
   STATUS      current
   DESCRIPTION
      "Path: ethernet2.editConf.vlan.inboundBandwidth.action.violateAction.ethernet.cosDepth1

       Possibilities:
               unchanged   (256)"
   ::= {er1645v2Lan2MCVlanEntry 133579008}

er1645v2Lan2MCVlanInbBwActViolActEthDei1 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth1

       Possibilities:
               unchanged   (255)
               clear   (0)
               set   (1)"
   ::= {er1645v2Lan2MCVlanEntry 133584128}

er1645v2Lan2MCVlanInbBwActViolActEthCos2 OBJECT-TYPE
   SYNTAX      INTEGER
               {
               unchanged (256)
               }
   MAX-ACCESS  read-write
   STATUS      current
   DESCRIPTION
      "Path: ethernet2.editConf.vlan.inboundBandwidth.action.violateAction.ethernet.cosDepth2

       Possibilities:
               unchanged   (256)"
   ::= {er1645v2Lan2MCVlanEntry 133579264}

er1645v2Lan2MCVlanInbBwActViolActEthDei2 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth2

       Possibilities:
               unchanged   (255)
               clear   (0)
               set   (1)"
   ::= {er1645v2Lan2MCVlanEntry 133584384}

er1645v2Lan2MCVlanInbBwActViolActEthCos3 OBJECT-TYPE
   SYNTAX      INTEGER
               {
               unchanged (256)
               }
   MAX-ACCESS  read-write
   STATUS      current
   DESCRIPTION
      "Path: ethernet2.editConf.vlan.inboundBandwidth.action.violateAction.ethernet.cosDepth3

       Possibilities:
               unchanged   (256)"
   ::= {er1645v2Lan2MCVlanEntry 133579520}

er1645v2Lan2MCVlanInbBwActViolActEthDei3 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth3

       Possibilities:
               unchanged   (255)
               clear   (0)
               set   (1)"
   ::= {er1645v2Lan2MCVlanEntry 133584640}

er1645v2Lan2MCVlanInbBwActViolActEthCos4 OBJECT-TYPE
   SYNTAX      INTEGER
               {
               unchanged (256)
               }
   MAX-ACCESS  read-write
   STATUS      current
   DESCRIPTION
      "Path: ethernet2.editConf.vlan.inboundBandwidth.action.violateAction.ethernet.cosDepth4

       Possibilities:
               unchanged   (256)"
   ::= {er1645v2Lan2MCVlanEntry 133579776}

er1645v2Lan2MCVlanInbBwActViolActEthDei4 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth4

       Possibilities:
               unchanged   (255)
               clear   (0)
               set   (1)"
   ::= {er1645v2Lan2MCVlanEntry 133584896}

er1645v2Lan2MCVlanInbBwActViolActEthCos5 OBJECT-TYPE
   SYNTAX      INTEGER
               {
               unchanged (256)
               }
   MAX-ACCESS  read-write
   STATUS      current
   DESCRIPTION
      "Path: ethernet2.editConf.vlan.inboundBandwidth.action.violateAction.ethernet.cosDepth5

       Possibilities:
               unchanged   (256)"
   ::= {er1645v2Lan2MCVlanEntry 133580032}

er1645v2Lan2MCVlanInbBwActViolActEthDei5 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth5

       Possibilities:
               unchanged   (255)
               clear   (0)
               set   (1)"
   ::= {er1645v2Lan2MCVlanEntry 133585152}

er1645v2Lan2MCVlanInbBwActViolActEthCos6 OBJECT-TYPE
   SYNTAX      INTEGER
               {
               unchanged (256)
               }
   MAX-ACCESS  read-write
   STATUS      current
   DESCRIPTION
      "Path: ethernet2.editConf.vlan.inboundBandwidth.action.violateAction.ethernet.cosDepth6

       Possibilities:
               unchanged   (256)"
   ::= {er1645v2Lan2MCVlanEntry 133580288}

er1645v2Lan2MCVlanInbBwActViolActEthDei6 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth6

       Possibilities:
               unchanged   (255)
               clear   (0)
               set   (1)"
   ::= {er1645v2Lan2MCVlanEntry 133585408}

er1645v2Lan2MCVlanInbBwActViolActEthCos7 OBJECT-TYPE
   SYNTAX      INTEGER
               {
               unchanged (256)
               }
   MAX-ACCESS  read-write
   STATUS      current
   DESCRIPTION
      "Path: ethernet2.editConf.vlan.inboundBandwidth.action.violateAction.ethernet.cosDepth7

       Possibilities:
               unchanged   (256)"
   ::= {er1645v2Lan2MCVlanEntry 133580544}

er1645v2Lan2MCVlanInbBwActViolActEthDei7 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth7

       Possibilities:
               unchanged   (255)
               clear   (0)
               set   (1)"
   ::= {er1645v2Lan2MCVlanEntry 133585664}

er1645v2Lan2MCVlanInbBwActViolActEthCos8 OBJECT-TYPE
   SYNTAX      INTEGER
               {
               unchanged (256)
               }
   MAX-ACCESS  read-write
   STATUS      current
   DESCRIPTION
      "Path: ethernet2.editConf.vlan.inboundBandwidth.action.violateAction.ethernet.cosDepth8

       Possibilities:
               unchanged   (256)"
   ::= {er1645v2Lan2MCVlanEntry 133580800}

er1645v2Lan2MCVlanInbBwActViolActEthDei8 OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deiDepth8

       Possibilities:
               unchanged   (255)
               clear   (0)
               set   (1)"
   ::= {er1645v2Lan2MCVlanEntry 133585920}

er1645v2Lan2MCVlanInbBwActViolActEthTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.violateAction.ethernet.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 133581056}

er1645v2Lan2MCVlanInbBwActViolActEthQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.violateAction.ethernet.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 133581312}

er1645v2Lan2MCVlanInbBwActViolActEthDrpLev OBJECT-TYPE
   SYNTAX      INTEGER
               {
               unchanged (0)
               }
   MAX-ACCESS  read-write
   STATUS      current
   DESCRIPTION
      "Path: ethernet2.editConf.vlan.inboundBandwidth.action.violateAction.ethernet.dropLevel

       Possibilities:
               unchanged   (0)"
   ::= {er1645v2Lan2MCVlanEntry 133581568}

er1645v2Lan2MCVlanInbBwActViolActEthDeFlag OBJECT-TYPE
   SYNTAX      INTEGER
               {
               unchanged (255),
               clear (0),
               set (1)
               }
   MAX-ACCESS  read-write
   STATUS      current
   DESCRIPTION
      "Path: ethernet2.editConf.vlan.inboundBandwidth.action.violateAction.ethernet.deFlag

       Possibilities:
               unchanged   (255)
               clear   (0)
               set   (1)"
   ::= {er1645v2Lan2MCVlanEntry 133582336}

er1645v2Lan2MCVlanInbBwActViolActIpTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.inboundBandwidth.action.violateAction.ip.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanEntry 133605632}

er1645v2Lan2MCVlanInbBwActViolActIpQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.inboundBandwidth.action.violateAction.ip.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanEntry 133605888}

er1645v2Lan2MCVlanInbBwActViolActIpDrpLev OBJECT-TYPE
   SYNTAX      INTEGER
               {
               unchanged (0)
               }
   MAX-ACCESS  read-write
   STATUS      current
   DESCRIPTION
      "Path: ethernet2.editConf.vlan.inboundBandwidth.action.violateAction.ip.dropLevel

       Possibilities:
               unchanged   (0)"
   ::= {er1645v2Lan2MCVlanEntry 133606144}

er1645v2Lan2MCVlanInbBwActViolActIpDeFlag OBJECT-TYPE
   SYNTAX      INTEGER
               {
               unchanged (255),
               clear (0),
               set (1)
               }
   MAX-ACCESS  read-write
   STATUS      current
   DESCRIPTION
      "Path: ethernet2.editConf.vlan.inboundBandwidth.action.violateAction.ip.deFlag

       Possibilities:
               unchanged   (255)
               clear   (0)
               set   (1)"
   ::= {er1645v2Lan2MCVlanEntry 133606912}

er1645v2Lan2MCVlanPppoE OBJECT-TYPE
   SYNTAX      INTEGER
               {
               disabled (0),
               enabled (1)
               }
   MAX-ACCESS  read-write
   STATUS      current
   DESCRIPTION
      "Path: ethernet2.editConf.vlan.pppoE

       Possibilities:
               disabled   (0)
               enabled   (1)"
   ::= {er1645v2Lan2MCVlanEntry 838860800}

er1645v2Lan2MCVlanPppLnkMOperation OBJECT-TYPE
   SYNTAX      INTEGER
               {
               disabled (0),
               enabled (1)
               }
   MAX-ACCESS  read-write
   STATUS      current
   DESCRIPTION
      "Path: ethernet2.editConf.vlan.ppp.linkMonitoring.operation

       Possibilities:
               disabled   (0)
               enabled   (1)"
   ::= {er1645v2Lan2MCVlanEntry 251724032}

er1645v2Lan2MCVlanPppLnkMInterval OBJECT-TYPE
   SYNTAX      TimeTicks
   MAX-ACCESS  read-write
   STATUS      current
   DESCRIPTION
      "Path: ethernet2.editConf.vlan.ppp.linkMonitoring.interval

       Time in centi-second."
   ::= {er1645v2Lan2MCVlanEntry 251724288}

er1645v2Lan2MCVlanPppLnkMRepTimeOut OBJECT-TYPE
   SYNTAX      TimeTicks
   MAX-ACCESS  read-write
   STATUS      current
   DESCRIPTION
      "Path: ethernet2.editConf.vlan.ppp.linkMonitoring.replyTimeOut

       Time in centi-second."
   ::= {er1645v2Lan2MCVlanEntry 251724544}

er1645v2Lan2MCVlanPppLnkMFailsPrmt OBJECT-TYPE
   SYNTAX      Integer32
   MAX-ACCESS  read-write
   STATUS      current
   DESCRIPTION
      "Path: ethernet2.editConf.vlan.ppp.linkMonitoring.failsPermitted"
   ::= {er1645v2Lan2MCVlanEntry 251724800}

er1645v2Lan2MCVlanPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet2.editConf.vlan.ppp.authentication

       Possibilities:
               disabled   (0)
               chap   (1)
               pap   (2)
               chapOrPap   (3)
               msChap   (4)
               msChapV2   (5)"
   ::= {er1645v2Lan2MCVlanEntry 251789312}

er1645v2Lan2MCVlanPppAuthenPeriod OBJECT-TYPE
   SYNTAX      TimeTicks
   MAX-ACCESS  read-write
   STATUS      current
   DESCRIPTION
      "Path: ethernet2.editConf.vlan.ppp.authenPeriod

       Time in centi-second."
   ::= {er1645v2Lan2MCVlanEntry 251854848}

er1645v2Lan2MCVlanPppSessionName OBJECT-TYPE
   SYNTAX      DisplayString
   MAX-ACCESS  read-write
   STATUS      current
   DESCRIPTION
      "Path: ethernet2.editConf.vlan.ppp.sessionName"
   ::= {er1645v2Lan2MCVlanEntry 251985920}

er1645v2Lan2MCVlanPppSessionSecret OBJECT-TYPE
   SYNTAX      DisplayString
   MAX-ACCESS  read-write
   STATUS      current
   DESCRIPTION
      "Path: ethernet2.editConf.vlan.ppp.sessionSecret"
   ::= {er1645v2Lan2MCVlanEntry 252051456}

er1645v2Lan2MCVlanPppEncModeSessionSecret OBJECT-TYPE
   SYNTAX      INTEGER
               {
               none (1),
               encrypt (2),
               encType1 (3),
               invalid (128)
               }
   MAX-ACCESS  read-write
   STATUS      current
   DESCRIPTION
      "Path: ethernet2.editConf.vlan.ppp.encModeSessionSecret

       Possibilities:
               none   (1)
               encrypt   (2)
               encType1   (3)
               invalid   (128)"
   ::= {er1645v2Lan2MCVlanEntry 252182528}

er1645v2Lan2MCVlanPppEncSessionSecret OBJECT-TYPE
   SYNTAX      DisplayString
   MAX-ACCESS  read-write
   STATUS      current
   DESCRIPTION
      "Path: ethernet2.editConf.vlan.ppp.encSessionSecret"
   ::= {er1645v2Lan2MCVlanEntry 252248064}

er1645v2Lan2MCVlanPppServiceName OBJECT-TYPE
   SYNTAX      DisplayString
   MAX-ACCESS  read-write
   STATUS      current
   DESCRIPTION
      "Path: ethernet2.editConf.vlan.ppp.serviceName"
   ::= {er1645v2Lan2MCVlanEntry 252116992}

er1645v2Lan2MCVlanPbbMode OBJECT-TYPE
   SYNTAX      INTEGER
               {
               disabled (0),
               static (1),
               dynamicPtp (2),
               dynamicPtmp (3)
               }
   MAX-ACCESS  read-write
   STATUS      current
   DESCRIPTION
      "Path: ethernet2.editConf.vlan.pbb.mode

       Possibilities:
               disabled   (0)
               static   (1)
               dynamicPtp   (2)
               dynamicPtmp   (3)"
   ::= {er1645v2Lan2MCVlanEntry 1174667264}

er1645v2Lan2MCVlanPbbTxCos OBJECT-TYPE
   SYNTAX      Integer32
   MAX-ACCESS  read-write
   STATUS      current
   DESCRIPTION
      "Path: ethernet2.editConf.vlan.pbb.txCos"
   ::= {er1645v2Lan2MCVlanEntry 1175191552}

er1645v2Lan2MCVlanPbbIsid OBJECT-TYPE
   SYNTAX      Integer32
   MAX-ACCESS  read-write
   STATUS      current
   DESCRIPTION
      "Path: ethernet2.editConf.vlan.pbb.isid"
   ::= {er1645v2Lan2MCVlanEntry 1175453696}

er1645v2Lan2MCVlanPbbDestMac OBJECT-TYPE
   SYNTAX      OCTET STRING
   MAX-ACCESS  read-write
   STATUS      current
   DESCRIPTION
      "Path: ethernet2.editConf.vlan.pbb.destMac

       MAC address."
   ::= {er1645v2Lan2MCVlanEntry 1175715840}

er1645v2Lan2MCVlanPbbCustomGroupMac OBJECT-TYPE
   SYNTAX      OCTET STRING
   MAX-ACCESS  read-write
   STATUS      current
   DESCRIPTION
      "Path: ethernet2.editConf.vlan.pbb.customGroupMac

       MAC address."
   ::= {er1645v2Lan2MCVlanEntry 1175977984}

er1645v2Lan2MCVlanIpSaddr OBJECT-TYPE
   SYNTAX      SEQUENCE OF Er1645v2Lan2MCVlanIpSaddrEntry
   MAX-ACCESS  not-accessible
   STATUS      current
   DESCRIPTION
      ""
   ::= {er1645v2Lan2MCVlan 51838976}

er1645v2Lan2MCVlanIpSaddrEntry OBJECT-TYPE
   SYNTAX      Er1645v2Lan2MCVlanIpSaddrEntry
   MAX-ACCESS  not-accessible
   STATUS      current
   DESCRIPTION
      ""
   INDEX      { er1645v2Lan2MCVlanTableIx,
                er1645v2Lan2MCVlanIpSaddrTableIx }
   ::= {er1645v2Lan2MCVlanIpSaddr 1}

Er1645v2Lan2MCVlanIpSaddrEntry ::=
   SEQUENCE
      {
      er1645v2Lan2MCVlanIpSaddrActions
         VariableLengthTableActions,
      er1645v2Lan2MCVlanIpSaddrTableIx
         TableIndex,
      er1645v2Lan2MCVlanIpSaddrAddress
         IpAddress,
      er1645v2Lan2MCVlanIpSaddrNetMask
         IpAddress
      }

er1645v2Lan2MCVlanIpSaddrActions OBJECT-TYPE
   SYNTAX      VariableLengthTableActions
   MAX-ACCESS  read-write
   STATUS      current
   DESCRIPTION
      "By way of this field, some manipulations
       on this table may be performed."
   ::= {er1645v2Lan2MCVlanIpSaddrEntry 2}

er1645v2Lan2MCVlanIpSaddrTableIx OBJECT-TYPE
   SYNTAX      TableIndex
   MAX-ACCESS  not-accessible
   STATUS      current
   DESCRIPTION
      ""
   ::= {er1645v2Lan2MCVlanIpSaddrEntry 11}

er1645v2Lan2MCVlanIpSaddrAddress OBJECT-TYPE
   SYNTAX      IpAddress
   MAX-ACCESS  read-write
   STATUS      current
   DESCRIPTION
      "Path: ethernet2.editConf.vlan.ip.secondaryIp.address"
   ::= {er1645v2Lan2MCVlanIpSaddrEntry 2030043136}

er1645v2Lan2MCVlanIpSaddrNetMask OBJECT-TYPE
   SYNTAX      IpAddress
   MAX-ACCESS  read-write
   STATUS      current
   DESCRIPTION
      "Path: ethernet2.editConf.vlan.ip.secondaryIp.netMask"
   ::= {er1645v2Lan2MCVlanIpSaddrEntry 2063597568}

er1645v2Lan2MCVlanIpH OBJECT-TYPE
   SYNTAX      SEQUENCE OF Er1645v2Lan2MCVlanIpHEntry
   MAX-ACCESS  not-accessible
   STATUS      current
   DESCRIPTION
      ""
   ::= {er1645v2Lan2MCVlan 51314688}

er1645v2Lan2MCVlanIpHEntry OBJECT-TYPE
   SYNTAX      Er1645v2Lan2MCVlanIpHEntry
   MAX-ACCESS  not-accessible
   STATUS      current
   DESCRIPTION
      ""
   INDEX      { er1645v2Lan2MCVlanTableIx,
                er1645v2Lan2MCVlanIpHTableIx }
   ::= {er1645v2Lan2MCVlanIpH 1}

Er1645v2Lan2MCVlanIpHEntry ::=
   SEQUENCE
      {
      er1645v2Lan2MCVlanIpHActions
         VariableLengthTableActions,
      er1645v2Lan2MCVlanIpHTableIx
         TableIndex,
      er1645v2Lan2MCVlanIpHAddress
         IpAddress,
      er1645v2Lan2MCVlanIpHDhcpRelayOptionSubscriberId
         DisplayString
      }

er1645v2Lan2MCVlanIpHActions OBJECT-TYPE
   SYNTAX      VariableLengthTableActions
   MAX-ACCESS  read-write
   STATUS      current
   DESCRIPTION
      "By way of this field, some manipulations
       on this table may be performed."
   ::= {er1645v2Lan2MCVlanIpHEntry 2}

er1645v2Lan2MCVlanIpHTableIx OBJECT-TYPE
   SYNTAX      TableIndex
   MAX-ACCESS  not-accessible
   STATUS      current
   DESCRIPTION
      ""
   ::= {er1645v2Lan2MCVlanIpHEntry 11}

er1645v2Lan2MCVlanIpHAddress OBJECT-TYPE
   SYNTAX      IpAddress
   MAX-ACCESS  read-write
   STATUS      current
   DESCRIPTION
      "Path: ethernet2.editConf.vlan.ip.helpers.address"
   ::= {er1645v2Lan2MCVlanIpHEntry 16777216}

er1645v2Lan2MCVlanIpHDhcpRelayOptionSubscriberId OBJECT-TYPE
   SYNTAX      DisplayString
   MAX-ACCESS  read-write
   STATUS      current
   DESCRIPTION
      "Path: ethernet2.editConf.vlan.ip.helpers.dhcpRelayOption.subscriberId"
   ::= {er1645v2Lan2MCVlanIpHEntry 33947648}

er1645v2Lan2MCVlanIpV6Addresses OBJECT-TYPE
   SYNTAX      SEQUENCE OF Er1645v2Lan2MCVlanIpV6AddressesEntry
   MAX-ACCESS  not-accessible
   STATUS      current
   DESCRIPTION
      ""
   ::= {er1645v2Lan2MCVlan 704839680}

er1645v2Lan2MCVlanIpV6AddressesEntry OBJECT-TYPE
   SYNTAX      Er1645v2Lan2MCVlanIpV6AddressesEntry
   MAX-ACCESS  not-accessible
   STATUS      current
   DESCRIPTION
      ""
   INDEX      { er1645v2Lan2MCVlanTableIx,
                er1645v2Lan2MCVlanIpV6AddressesTableIx }
   ::= {er1645v2Lan2MCVlanIpV6Addresses 1}

Er1645v2Lan2MCVlanIpV6AddressesEntry ::=
   SEQUENCE
      {
      er1645v2Lan2MCVlanIpV6AddressesActions
         VariableLengthTableActions,
      er1645v2Lan2MCVlanIpV6AddressesTableIx
         TableIndex,
      er1645v2Lan2MCVlanIpV6AddressesType
         INTEGER,
      er1645v2Lan2MCVlanIpV6AddressesAddress
         Ipv6Address,
      er1645v2Lan2MCVlanIpV6AddressesPrefixLength
         Integer32,
      er1645v2Lan2MCVlanIpV6AddressesGeneralPrefix
         DisplayString,
      er1645v2Lan2MCVlanIpV6AddressesRaSend
         INTEGER,
      er1645v2Lan2MCVlanIpV6AddressesRaOnLinkFlag
         INTEGER,
      er1645v2Lan2MCVlanIpV6AddressesRaAutoFlag
         INTEGER,
      er1645v2Lan2MCVlanIpV6AddressesRaValidLifeTime
         TimeTicks,
      er1645v2Lan2MCVlanIpV6AddressesRaValidLTMode
         INTEGER,
      er1645v2Lan2MCVlanIpV6AddressesRaPrefLifeTime
         TimeTicks,
      er1645v2Lan2MCVlanIpV6AddressesRaPrefLTMode
         INTEGER
      }

er1645v2Lan2MCVlanIpV6AddressesActions OBJECT-TYPE
   SYNTAX      VariableLengthTableActions
   MAX-ACCESS  read-write
   STATUS      current
   DESCRIPTION
      "By way of this field, some manipulations
       on this table may be performed."
   ::= {er1645v2Lan2MCVlanIpV6AddressesEntry 2}

er1645v2Lan2MCVlanIpV6AddressesTableIx OBJECT-TYPE
   SYNTAX      TableIndex
   MAX-ACCESS  not-accessible
   STATUS      current
   DESCRIPTION
      ""
   ::= {er1645v2Lan2MCVlanIpV6AddressesEntry 11}

er1645v2Lan2MCVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.vlan.ipV6.addresses.type

       Possibilities:
               unicast   (0)
               eui64   (1)
               anycast   (2)
               linkLocal   (3)
               generalPrefix   (4)"
   ::= {er1645v2Lan2MCVlanIpV6AddressesEntry 50331648}

er1645v2Lan2MCVlanIpV6AddressesAddress OBJECT-TYPE
   SYNTAX      Ipv6Address
   MAX-ACCESS  read-write
   STATUS      current
   DESCRIPTION
      "Path: ethernet2.editConf.vlan.ipV6.addresses.address

       ipv6 address"
   ::= {er1645v2Lan2MCVlanIpV6AddressesEntry 16777216}

er1645v2Lan2MCVlanIpV6AddressesPrefixLength OBJECT-TYPE
   SYNTAX      Integer32
   MAX-ACCESS  read-write
   STATUS      current
   DESCRIPTION
      "Path: ethernet2.editConf.vlan.ipV6.addresses.prefixLength"
   ::= {er1645v2Lan2MCVlanIpV6AddressesEntry 33554432}

er1645v2Lan2MCVlanIpV6AddressesGeneralPrefix OBJECT-TYPE
   SYNTAX      DisplayString
   MAX-ACCESS  read-write
   STATUS      current
   DESCRIPTION
      "Path: ethernet2.editConf.vlan.ipV6.addresses.generalPrefix"
   ::= {er1645v2Lan2MCVlanIpV6AddressesEntry 83886080}

er1645v2Lan2MCVlanIpV6AddressesRaSend OBJECT-TYPE
   SYNTAX      INTEGER
               {
               disabled (0),
               enabled (1)
               }
   MAX-ACCESS  read-write
   STATUS      current
   DESCRIPTION
      "Path: ethernet2.editConf.vlan.ipV6.addresses.ra.send

       Possibilities:
               disabled   (0)
               enabled   (1)"
   ::= {er1645v2Lan2MCVlanIpV6AddressesEntry 67174400}

er1645v2Lan2MCVlanIpV6AddressesRaOnLinkFlag OBJECT-TYPE
   SYNTAX      INTEGER
               {
               disabled (0),
               enabled (1)
               }
   MAX-ACCESS  read-write
   STATUS      current
   DESCRIPTION
      "Path: ethernet2.editConf.vlan.ipV6.addresses.ra.onLinkFlag

       Possibilities:
               disabled   (0)
               enabled   (1)"
   ::= {er1645v2Lan2MCVlanIpV6AddressesEntry 67371008}

er1645v2Lan2MCVlanIpV6AddressesRaAutoFlag OBJECT-TYPE
   SYNTAX      INTEGER
               {
               disabled (0),
               enabled (1)
               }
   MAX-ACCESS  read-write
   STATUS      current
   DESCRIPTION
      "Path: ethernet2.editConf.vlan.ipV6.addresses.ra.autonomousFlag

       Possibilities:
               disabled   (0)
               enabled   (1)"
   ::= {er1645v2Lan2MCVlanIpV6AddressesEntry 67567616}

er1645v2Lan2MCVlanIpV6AddressesRaValidLifeTime OBJECT-TYPE
   SYNTAX      TimeTicks
   MAX-ACCESS  read-write
   STATUS      current
   DESCRIPTION
      "Path: ethernet2.editConf.vlan.ipV6.addresses.ra.validLifeTime

       Time in centi-second."
   ::= {er1645v2Lan2MCVlanIpV6AddressesEntry 67239936}

er1645v2Lan2MCVlanIpV6AddressesRaValidLTMode OBJECT-TYPE
   SYNTAX      INTEGER
               {
               fixed (0),
               infinite (2)
               }
   MAX-ACCESS  read-write
   STATUS      current
   DESCRIPTION
      "Path: ethernet2.editConf.vlan.ipV6.addresses.ra.validLifeTimeMode

       Possibilities:
               fixed   (0)
               infinite   (2)"
   ::= {er1645v2Lan2MCVlanIpV6AddressesEntry 67305472}

er1645v2Lan2MCVlanIpV6AddressesRaPrefLifeTime OBJECT-TYPE
   SYNTAX      TimeTicks
   MAX-ACCESS  read-write
   STATUS      current
   DESCRIPTION
      "Path: ethernet2.editConf.vlan.ipV6.addresses.ra.prefLifeTime

       Time in centi-second."
   ::= {er1645v2Lan2MCVlanIpV6AddressesEntry 67436544}

er1645v2Lan2MCVlanIpV6AddressesRaPrefLTMode OBJECT-TYPE
   SYNTAX      INTEGER
               {
               fixed (0),
               infinite (2)
               }
   MAX-ACCESS  read-write
   STATUS      current
   DESCRIPTION
      "Path: ethernet2.editConf.vlan.ipV6.addresses.ra.prefLifeTimeMode

       Possibilities:
               fixed   (0)
               infinite   (2)"
   ::= {er1645v2Lan2MCVlanIpV6AddressesEntry 67502080}

er1645v2Lan2MCVlanIpV6RaDnsOptionsRdnssServers OBJECT-TYPE
   SYNTAX      SEQUENCE OF Er1645v2Lan2MCVlanIpV6RaDnsOptionsRdnssServersEntry
   MAX-ACCESS  not-accessible
   STATUS      current
   DESCRIPTION
      ""
   ::= {er1645v2Lan2MCVlan 705039144}

er1645v2Lan2MCVlanIpV6RaDnsOptionsRdnssServersEntry OBJECT-TYPE
   SYNTAX      Er1645v2Lan2MCVlanIpV6RaDnsOptionsRdnssServersEntry
   MAX-ACCESS  not-accessible
   STATUS      current
   DESCRIPTION
      ""
   INDEX      { er1645v2Lan2MCVlanTableIx,
                er1645v2Lan2MCVlanIpV6RaDnsOptionsRdnssServersTableIx }
   ::= {er1645v2Lan2MCVlanIpV6RaDnsOptionsRdnssServers 1}

Er1645v2Lan2MCVlanIpV6RaDnsOptionsRdnssServersEntry ::=
   SEQUENCE
      {
      er1645v2Lan2MCVlanIpV6RaDnsOptionsRdnssServersActions
         VariableLengthTableActions,
      er1645v2Lan2MCVlanIpV6RaDnsOptionsRdnssServersTableIx
         TableIndex,
      er1645v2Lan2MCVlanIpV6RaDnsOptionsRdnssServersAddress
         Ipv6Address
      }

er1645v2Lan2MCVlanIpV6RaDnsOptionsRdnssServersActions OBJECT-TYPE
   SYNTAX      VariableLengthTableActions
   MAX-ACCESS  read-write
   STATUS      current
   DESCRIPTION
      "By way of this field, some manipulations
       on this table may be performed."
   ::= {er1645v2Lan2MCVlanIpV6RaDnsOptionsRdnssServersEntry 2}

er1645v2Lan2MCVlanIpV6RaDnsOptionsRdnssServersTableIx OBJECT-TYPE
   SYNTAX      TableIndex
   MAX-ACCESS  not-accessible
   STATUS      current
   DESCRIPTION
      ""
   ::= {er1645v2Lan2MCVlanIpV6RaDnsOptionsRdnssServersEntry 11}

er1645v2Lan2MCVlanIpV6RaDnsOptionsRdnssServersAddress OBJECT-TYPE
   SYNTAX      Ipv6Address
   MAX-ACCESS  read-write
   STATUS      current
   DESCRIPTION
      "Path: ethernet2.editConf.vlan.ipV6.ra.dnsOptions.rdnss.servers.address

       ipv6 address"
   ::= {er1645v2Lan2MCVlanIpV6RaDnsOptionsRdnssServersEntry 16777216}

er1645v2Lan2MCVlanIpV6RaDnsOptionsDnsslDomains OBJECT-TYPE
   SYNTAX      SEQUENCE OF Er1645v2Lan2MCVlanIpV6RaDnsOptionsDnsslDomainsEntry
   MAX-ACCESS  not-accessible
   STATUS      current
   DESCRIPTION
      ""
   ::= {er1645v2Lan2MCVlan 705039176}

er1645v2Lan2MCVlanIpV6RaDnsOptionsDnsslDomainsEntry OBJECT-TYPE
   SYNTAX      Er1645v2Lan2MCVlanIpV6RaDnsOptionsDnsslDomainsEntry
   MAX-ACCESS  not-accessible
   STATUS      current
   DESCRIPTION
      ""
   INDEX      { er1645v2Lan2MCVlanTableIx,
                er1645v2Lan2MCVlanIpV6RaDnsOptionsDnsslDomainsTableIx }
   ::= {er1645v2Lan2MCVlanIpV6RaDnsOptionsDnsslDomains 1}

Er1645v2Lan2MCVlanIpV6RaDnsOptionsDnsslDomainsEntry ::=
   SEQUENCE
      {
      er1645v2Lan2MCVlanIpV6RaDnsOptionsDnsslDomainsActions
         VariableLengthTableActions,
      er1645v2Lan2MCVlanIpV6RaDnsOptionsDnsslDomainsTableIx
         TableIndex,
      er1645v2Lan2MCVlanIpV6RaDnsOptionsDnsslDomainsName
         DisplayString
      }

er1645v2Lan2MCVlanIpV6RaDnsOptionsDnsslDomainsActions OBJECT-TYPE
   SYNTAX      VariableLengthTableActions
   MAX-ACCESS  read-write
   STATUS      current
   DESCRIPTION
      "By way of this field, some manipulations
       on this table may be performed."
   ::= {er1645v2Lan2MCVlanIpV6RaDnsOptionsDnsslDomainsEntry 2}

er1645v2Lan2MCVlanIpV6RaDnsOptionsDnsslDomainsTableIx OBJECT-TYPE
   SYNTAX      TableIndex
   MAX-ACCESS  not-accessible
   STATUS      current
   DESCRIPTION
      ""
   ::= {er1645v2Lan2MCVlanIpV6RaDnsOptionsDnsslDomainsEntry 11}

er1645v2Lan2MCVlanIpV6RaDnsOptionsDnsslDomainsName OBJECT-TYPE
   SYNTAX      DisplayString
   MAX-ACCESS  read-write
   STATUS      current
   DESCRIPTION
      "Path: ethernet2.editConf.vlan.ipV6.ra.dnsOptions.dnssl.domains.name"
   ::= {er1645v2Lan2MCVlanIpV6RaDnsOptionsDnsslDomainsEntry 16777216}

er1645v2Lan2MCVlanIpV6DhcpClientUserClassOpt OBJECT-TYPE
   SYNTAX      SEQUENCE OF Er1645v2Lan2MCVlanIpV6DhcpClientUserClassOptEntry
   MAX-ACCESS  not-accessible
   STATUS      current
   DESCRIPTION
      ""
   ::= {er1645v2Lan2MCVlan 705312768}

er1645v2Lan2MCVlanIpV6DhcpClientUserClassOptEntry OBJECT-TYPE
   SYNTAX      Er1645v2Lan2MCVlanIpV6DhcpClientUserClassOptEntry
   MAX-ACCESS  not-accessible
   STATUS      current
   DESCRIPTION
      ""
   INDEX      { er1645v2Lan2MCVlanTableIx,
                er1645v2Lan2MCVlanIpV6DhcpClientUserClassOptTableIx }
   ::= {er1645v2Lan2MCVlanIpV6DhcpClientUserClassOpt 1}

Er1645v2Lan2MCVlanIpV6DhcpClientUserClassOptEntry ::=
   SEQUENCE
      {
      er1645v2Lan2MCVlanIpV6DhcpClientUserClassOptActions
         VariableLengthTableActions,
      er1645v2Lan2MCVlanIpV6DhcpClientUserClassOptTableIx
         TableIndex,
      er1645v2Lan2MCVlanIpV6DhcpClientUserClassOptValueAscii
         DisplayString,
      er1645v2Lan2MCVlanIpV6DhcpClientUserClassOptValueDecimal
         Integer32,
      er1645v2Lan2MCVlanIpV6DhcpClientUserClassOptValueHexData
         OCTET STRING
      }

er1645v2Lan2MCVlanIpV6DhcpClientUserClassOptActions OBJECT-TYPE
   SYNTAX      VariableLengthTableActions
   MAX-ACCESS  read-write
   STATUS      current
   DESCRIPTION
      "By way of this field, some manipulations
       on this table may be performed."
   ::= {er1645v2Lan2MCVlanIpV6DhcpClientUserClassOptEntry 2}

er1645v2Lan2MCVlanIpV6DhcpClientUserClassOptTableIx OBJECT-TYPE
   SYNTAX      TableIndex
   MAX-ACCESS  not-accessible
   STATUS      current
   DESCRIPTION
      ""
   ::= {er1645v2Lan2MCVlanIpV6DhcpClientUserClassOptEntry 11}

er1645v2Lan2MCVlanIpV6DhcpClientUserClassOptValueAscii OBJECT-TYPE
   SYNTAX      DisplayString
   MAX-ACCESS  read-write
   STATUS      current
   DESCRIPTION
      "Path: ethernet2.editConf.vlan.ipV6.dhcp.client.userClassOpt.value.ascii"
   ::= {er1645v2Lan2MCVlanIpV6DhcpClientUserClassOptEntry 16842752}

er1645v2Lan2MCVlanIpV6DhcpClientUserClassOptValueDecimal OBJECT-TYPE
   SYNTAX      Integer32
   MAX-ACCESS  read-write
   STATUS      current
   DESCRIPTION
      "Path: ethernet2.editConf.vlan.ipV6.dhcp.client.userClassOpt.value.decimal"
   ::= {er1645v2Lan2MCVlanIpV6DhcpClientUserClassOptEntry 16908288}

er1645v2Lan2MCVlanIpV6DhcpClientUserClassOptValueHexData OBJECT-TYPE
   SYNTAX      OCTET STRING
   MAX-ACCESS  read-write
   STATUS      current
   DESCRIPTION
      "Path: ethernet2.editConf.vlan.ipV6.dhcp.client.userClassOpt.value.hexData"
   ::= {er1645v2Lan2MCVlanIpV6DhcpClientUserClassOptEntry 16973824}

er1645v2Lan2MCVlanIpV6DhcpClientVendorCl OBJECT-TYPE
   SYNTAX      SEQUENCE OF Er1645v2Lan2MCVlanIpV6DhcpClientVendorClEntry
   MAX-ACCESS  not-accessible
   STATUS      current
   DESCRIPTION
      ""
   ::= {er1645v2Lan2MCVlan 705313792}

er1645v2Lan2MCVlanIpV6DhcpClientVendorClEntry OBJECT-TYPE
   SYNTAX      Er1645v2Lan2MCVlanIpV6DhcpClientVendorClEntry
   MAX-ACCESS  not-accessible
   STATUS      current
   DESCRIPTION
      ""
   INDEX      { er1645v2Lan2MCVlanTableIx,
                er1645v2Lan2MCVlanIpV6DhcpClientVendorClTableIx }
   ::= {er1645v2Lan2MCVlanIpV6DhcpClientVendorCl 1}

Er1645v2Lan2MCVlanIpV6DhcpClientVendorClEntry ::=
   SEQUENCE
      {
      er1645v2Lan2MCVlanIpV6DhcpClientVendorClActions
         VariableLengthTableActions,
      er1645v2Lan2MCVlanIpV6DhcpClientVendorClTableIx
         TableIndex,
      er1645v2Lan2MCVlanIpV6DhcpClientVendorClValueAscii
         DisplayString,
      er1645v2Lan2MCVlanIpV6DhcpClientVendorClValueDecimal
         Integer32,
      er1645v2Lan2MCVlanIpV6DhcpClientVendorClValueHexData
         OCTET STRING
      }

er1645v2Lan2MCVlanIpV6DhcpClientVendorClActions OBJECT-TYPE
   SYNTAX      VariableLengthTableActions
   MAX-ACCESS  read-write
   STATUS      current
   DESCRIPTION
      "By way of this field, some manipulations
       on this table may be performed."
   ::= {er1645v2Lan2MCVlanIpV6DhcpClientVendorClEntry 2}

er1645v2Lan2MCVlanIpV6DhcpClientVendorClTableIx OBJECT-TYPE
   SYNTAX      TableIndex
   MAX-ACCESS  not-accessible
   STATUS      current
   DESCRIPTION
      ""
   ::= {er1645v2Lan2MCVlanIpV6DhcpClientVendorClEntry 11}

er1645v2Lan2MCVlanIpV6DhcpClientVendorClValueAscii OBJECT-TYPE
   SYNTAX      DisplayString
   MAX-ACCESS  read-write
   STATUS      current
   DESCRIPTION
      "Path: ethernet2.editConf.vlan.ipV6.dhcp.client.vendorClassOpt.value.ascii"
   ::= {er1645v2Lan2MCVlanIpV6DhcpClientVendorClEntry 16842752}

er1645v2Lan2MCVlanIpV6DhcpClientVendorClValueDecimal OBJECT-TYPE
   SYNTAX      Integer32
   MAX-ACCESS  read-write
   STATUS      current
   DESCRIPTION
      "Path: ethernet2.editConf.vlan.ipV6.dhcp.client.vendorClassOpt.value.decimal"
   ::= {er1645v2Lan2MCVlanIpV6DhcpClientVendorClEntry 16908288}

er1645v2Lan2MCVlanIpV6DhcpClientVendorClValueHexData OBJECT-TYPE
   SYNTAX      OCTET STRING
   MAX-ACCESS  read-write
   STATUS      current
   DESCRIPTION
      "Path: ethernet2.editConf.vlan.ipV6.dhcp.client.vendorClassOpt.value.hexData"
   ::= {er1645v2Lan2MCVlanIpV6DhcpClientVendorClEntry 16973824}

er1645v2Lan2MCVlanIpV6DhcpRelayDestinations OBJECT-TYPE
   SYNTAX      SEQUENCE OF Er1645v2Lan2MCVlanIpV6DhcpRelayDestinationsEntry
   MAX-ACCESS  not-accessible
   STATUS      current
   DESCRIPTION
      ""
   ::= {er1645v2Lan2MCVlan 705323072}

er1645v2Lan2MCVlanIpV6DhcpRelayDestinationsEntry OBJECT-TYPE
   SYNTAX      Er1645v2Lan2MCVlanIpV6DhcpRelayDestinationsEntry
   MAX-ACCESS  not-accessible
   STATUS      current
   DESCRIPTION
      ""
   INDEX      { er1645v2Lan2MCVlanTableIx,
                er1645v2Lan2MCVlanIpV6DhcpRelayDestinationsTableIx }
   ::= {er1645v2Lan2MCVlanIpV6DhcpRelayDestinations 1}

Er1645v2Lan2MCVlanIpV6DhcpRelayDestinationsEntry ::=
   SEQUENCE
      {
      er1645v2Lan2MCVlanIpV6DhcpRelayDestinationsActions
         VariableLengthTableActions,
      er1645v2Lan2MCVlanIpV6DhcpRelayDestinationsTableIx
         TableIndex,
      er1645v2Lan2MCVlanIpV6DhcpRelayDestinationsAddress
         Ipv6Address,
      er1645v2Lan2MCVlanIpV6DhcpRelayDestinationsInterface
         DisplayString
      }

er1645v2Lan2MCVlanIpV6DhcpRelayDestinationsActions OBJECT-TYPE
   SYNTAX      VariableLengthTableActions
   MAX-ACCESS  read-write
   STATUS      current
   DESCRIPTION
      "By way of this field, some manipulations
       on this table may be performed."
   ::= {er1645v2Lan2MCVlanIpV6DhcpRelayDestinationsEntry 2}

er1645v2Lan2MCVlanIpV6DhcpRelayDestinationsTableIx OBJECT-TYPE
   SYNTAX      TableIndex
   MAX-ACCESS  not-accessible
   STATUS      current
   DESCRIPTION
      ""
   ::= {er1645v2Lan2MCVlanIpV6DhcpRelayDestinationsEntry 11}

er1645v2Lan2MCVlanIpV6DhcpRelayDestinationsAddress OBJECT-TYPE
   SYNTAX      Ipv6Address
   MAX-ACCESS  read-write
   STATUS      current
   DESCRIPTION
      "Path: ethernet2.editConf.vlan.ipV6.dhcp.relay.destinations.address

       ipv6 address"
   ::= {er1645v2Lan2MCVlanIpV6DhcpRelayDestinationsEntry 16777216}

er1645v2Lan2MCVlanIpV6DhcpRelayDestinationsInterface OBJECT-TYPE
   SYNTAX      DisplayString
   MAX-ACCESS  read-write
   STATUS      current
   DESCRIPTION
      "Path: ethernet2.editConf.vlan.ipV6.dhcp.relay.destinations.interface"
   ::= {er1645v2Lan2MCVlanIpV6DhcpRelayDestinationsEntry 33554432}

er1645v2Lan2MCVlanBridgingVlTVlans OBJECT-TYPE
   SYNTAX      SEQUENCE OF Er1645v2Lan2MCVlanBridgingVlTVlansEntry
   MAX-ACCESS  not-accessible
   STATUS      current
   DESCRIPTION
      ""
   ::= {er1645v2Lan2MCVlan 459079680}

er1645v2Lan2MCVlanBridgingVlTVlansEntry OBJECT-TYPE
   SYNTAX      Er1645v2Lan2MCVlanBridgingVlTVlansEntry
   MAX-ACCESS  not-accessible
   STATUS      current
   DESCRIPTION
      ""
   INDEX      { er1645v2Lan2MCVlanTableIx,
                er1645v2Lan2MCVlanBridgingVlTVlansTableIx }
   ::= {er1645v2Lan2MCVlanBridgingVlTVlans 1}

Er1645v2Lan2MCVlanBridgingVlTVlansEntry ::=
   SEQUENCE
      {
      er1645v2Lan2MCVlanBridgingVlTVlansActions
         VariableLengthTableActions,
      er1645v2Lan2MCVlanBridgingVlTVlansTableIx
         TableIndex,
      er1645v2Lan2MCVlanBridgingVlTVlansVid
         Integer32,
      er1645v2Lan2MCVlanBridgingVlTVlansEndVid
         Integer32,
      er1645v2Lan2MCVlanBridgingVlTVlansAction
         INTEGER,
      er1645v2Lan2MCVlanBridgingVlTVlansTagInfoTpid
         INTEGER,
      er1645v2Lan2MCVlanBridgingVlTVlansTagInfoVid
         Integer32
      }

er1645v2Lan2MCVlanBridgingVlTVlansActions OBJECT-TYPE
   SYNTAX      VariableLengthTableActions
   MAX-ACCESS  read-write
   STATUS      current
   DESCRIPTION
      "By way of this field, some manipulations
       on this table may be performed."
   ::= {er1645v2Lan2MCVlanBridgingVlTVlansEntry 2}

er1645v2Lan2MCVlanBridgingVlTVlansTableIx OBJECT-TYPE
   SYNTAX      TableIndex
   MAX-ACCESS  not-accessible
   STATUS      current
   DESCRIPTION
      ""
   ::= {er1645v2Lan2MCVlanBridgingVlTVlansEntry 11}

er1645v2Lan2MCVlanBridgingVlTVlansVid OBJECT-TYPE
   SYNTAX      Integer32
   MAX-ACCESS  read-write
   STATUS      current
   DESCRIPTION
      "Path: ethernet2.editConf.vlan.bridging.vlanTagging.vlans.vid"
   ::= {er1645v2Lan2MCVlanBridgingVlTVlansEntry 536870912}

er1645v2Lan2MCVlanBridgingVlTVlansEndVid OBJECT-TYPE
   SYNTAX      Integer32
   MAX-ACCESS  read-write
   STATUS      current
   DESCRIPTION
      "Path: ethernet2.editConf.vlan.bridging.vlanTagging.vlans.endVid"
   ::= {er1645v2Lan2MCVlanBridgingVlTVlansEntry 2147483648}

er1645v2Lan2MCVlanBridgingVlTVlansAction OBJECT-TYPE
   SYNTAX      INTEGER
               {
               discard (0),
               accept (1),
               tag (2)
               }
   MAX-ACCESS  read-write
   STATUS      current
   DESCRIPTION
      "Path: ethernet2.editConf.vlan.bridging.vlanTagging.vlans.action

       Possibilities:
               discard   (0)
               accept   (1)
               tag   (2)"
   ::= {er1645v2Lan2MCVlanBridgingVlTVlansEntry 1073741824}

er1645v2Lan2MCVlanBridgingVlTVlansTagInfoTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.bridging.vlanTagging.vlans.tagInfo.tpid

       Possibilities:
               dot1Q   (33024)
               dot1ad   (34984)
               0x9100   (37120)
               0x9200   (37376)
               0x9300   (37632)"
   ::= {er1645v2Lan2MCVlanBridgingVlTVlansEntry 1677721600}

er1645v2Lan2MCVlanBridgingVlTVlansTagInfoVid OBJECT-TYPE
   SYNTAX      Integer32
   MAX-ACCESS  read-write
   STATUS      current
   DESCRIPTION
      "Path: ethernet2.editConf.vlan.bridging.vlanTagging.vlans.tagInfo.vid"
   ::= {er1645v2Lan2MCVlanBridgingVlTVlansEntry 1744830464}

er1645v2Lan2MCVlanVlanVidExtensionTable OBJECT-TYPE
   SYNTAX      SEQUENCE OF Er1645v2Lan2MCVlanVlanVidExtensionTableEntry
   MAX-ACCESS  not-accessible
   STATUS      current
   DESCRIPTION
      ""
   ::= {er1645v2Lan2MCVlan 235340544}

er1645v2Lan2MCVlanVlanVidExtensionTableEntry OBJECT-TYPE
   SYNTAX      Er1645v2Lan2MCVlanVlanVidExtensionTableEntry
   MAX-ACCESS  not-accessible
   STATUS      current
   DESCRIPTION
      ""
   INDEX      { er1645v2Lan2MCVlanTableIx,
                er1645v2Lan2MCVlanVlanVidExtensionTableTableIx }
   ::= {er1645v2Lan2MCVlanVlanVidExtensionTable 1}

Er1645v2Lan2MCVlanVlanVidExtensionTableEntry ::=
   SEQUENCE
      {
      er1645v2Lan2MCVlanVlanVidExtensionTableActions
         VariableLengthTableActions,
      er1645v2Lan2MCVlanVlanVidExtensionTableTableIx
         TableIndex,
      er1645v2Lan2MCVlanVlanVidExtensionTableTpid
         INTEGER,
      er1645v2Lan2MCVlanVlanVidExtensionTableVid
         Integer32,
      er1645v2Lan2MCVlanVlanVidExtensionTableEndVid
         Integer32
      }

er1645v2Lan2MCVlanVlanVidExtensionTableActions OBJECT-TYPE
   SYNTAX      VariableLengthTableActions
   MAX-ACCESS  read-write
   STATUS      current
   DESCRIPTION
      "By way of this field, some manipulations
       on this table may be performed."
   ::= {er1645v2Lan2MCVlanVlanVidExtensionTableEntry 2}

er1645v2Lan2MCVlanVlanVidExtensionTableTableIx OBJECT-TYPE
   SYNTAX      TableIndex
   MAX-ACCESS  not-accessible
   STATUS      current
   DESCRIPTION
      ""
   ::= {er1645v2Lan2MCVlanVlanVidExtensionTableEntry 11}

er1645v2Lan2MCVlanVlanVidExtensionTableTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: ethernet2.editConf.vlan.vlan.vidExtension.table.tpid

       Possibilities:
               dot1Q   (33024)
               dot1ad   (34984)
               0x9100   (37120)
               0x9200   (37376)
               0x9300   (37632)"
   ::= {er1645v2Lan2MCVlanVlanVidExtensionTableEntry 16777216}

er1645v2Lan2MCVlanVlanVidExtensionTableVid OBJECT-TYPE
   SYNTAX      Integer32
   MAX-ACCESS  read-write
   STATUS      current
   DESCRIPTION
      "Path: ethernet2.editConf.vlan.vlan.vidExtension.table.vid"
   ::= {er1645v2Lan2MCVlanVlanVidExtensionTableEntry 33554432}

er1645v2Lan2MCVlanVlanVidExtensionTableEndVid OBJECT-TYPE
   SYNTAX      Integer32
   MAX-ACCESS  read-write
   STATUS      current
   DESCRIPTION
      "Path: ethernet2.editConf.vlan.vlan.vidExtension.table.endVid"
   ::= {er1645v2Lan2MCVlanVlanVidExtensionTableEntry 50331648}

er1645v2Lan2MCVlanVlanCSMap OBJECT-TYPE
   SYNTAX      SEQUENCE OF Er1645v2Lan2MCVlanVlanCSMapEntry
   MAX-ACCESS  not-accessible
   STATUS      current
   DESCRIPTION
      ""
   ::= {er1645v2Lan2MCVlan 235405312}

er1645v2Lan2MCVlanVlanCSMapEntry OBJECT-TYPE
   SYNTAX      Er1645v2Lan2MCVlanVlanCSMapEntry
   MAX-ACCESS  not-accessible
   STATUS      current
   DESCRIPTION
      ""
   INDEX      { er1645v2Lan2MCVlanTableIx,
                er1645v2Lan2MCVlanVlanCSMapTableIx }
   ::= {er1645v2Lan2MCVlanVlanCSMap 1}

Er1645v2Lan2MCVlanVlanCSMapEntry ::=
   SEQUENCE
      {
      er1645v2Lan2MCVlanVlanCSMapActions
         VariableLengthTableActions,
      er1645v2Lan2MCVlanVlanCSMapTableIx
         TableIndex,
      er1645v2Lan2MCVlanVlanCSMapCos
         INTEGER,
      er1645v2Lan2MCVlanVlanCSMapDei
         INTEGER,
      er1645v2Lan2MCVlanVlanCSMapTos
         INTEGER,
      er1645v2Lan2MCVlanVlanCSMapQueue
         INTEGER,
      er1645v2Lan2MCVlanVlanCSMapDropLevel
         INTEGER,
      er1645v2Lan2MCVlanVlanCSMapDeFlag
         INTEGER
      }

er1645v2Lan2MCVlanVlanCSMapActions OBJECT-TYPE
   SYNTAX      VariableLengthTableActions
   MAX-ACCESS  read-write
   STATUS      current
   DESCRIPTION
      "By way of this field, some manipulations
       on this table may be performed."
   ::= {er1645v2Lan2MCVlanVlanCSMapEntry 2}

er1645v2Lan2MCVlanVlanCSMapTableIx OBJECT-TYPE
   SYNTAX      TableIndex
   MAX-ACCESS  not-accessible
   STATUS      current
   DESCRIPTION
      ""
   ::= {er1645v2Lan2MCVlanVlanCSMapEntry 11}

er1645v2Lan2MCVlanVlanCSMapCos OBJECT-TYPE
   SYNTAX      INTEGER
               {
               any (8)
               }
   MAX-ACCESS  read-write
   STATUS      current
   DESCRIPTION
      "Path: ethernet2.editConf.vlan.vlan.cosMap.cos

       Possibilities:
               any   (8)"
   ::= {er1645v2Lan2MCVlanVlanCSMapEntry 16777216}

er1645v2Lan2MCVlanVlanCSMapDei OBJECT-TYPE
   SYNTAX      INTEGER
               {
               clear (0),
               set (1),
               any (2)
               }
   MAX-ACCESS  read-write
   STATUS      current
   DESCRIPTION
      "Path: ethernet2.editConf.vlan.vlan.cosMap.dei

       Possibilities:
               clear   (0)
               set   (1)
               any   (2)"
   ::= {er1645v2Lan2MCVlanVlanCSMapEntry 33554432}

er1645v2Lan2MCVlanVlanCSMapTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               unchanged (256)
               }
   MAX-ACCESS  read-write
   STATUS      current
   DESCRIPTION
      "Path: ethernet2.editConf.vlan.vlan.cosMap.tos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               unchanged   (256)"
   ::= {er1645v2Lan2MCVlanVlanCSMapEntry 50331648}

er1645v2Lan2MCVlanVlanCSMapQueue OBJECT-TYPE
   SYNTAX      INTEGER
               {
               unchanged (-1),
               queue1 (0),
               queue2 (1),
               queue3 (2),
               queue4 (3),
               queue5 (4),
               lowDelayQueue (5),
               lowDelay2Queue (6),
               systemQueue (7)
               }
   MAX-ACCESS  read-write
   STATUS      current
   DESCRIPTION
      "Path: ethernet2.editConf.vlan.vlan.cosMap.queue

       Possibilities:
               unchanged   (-1)
               queue1   (0)
               queue2   (1)
               queue3   (2)
               queue4   (3)
               queue5   (4)
               lowDelayQueue   (5)
               lowDelay2Queue   (6)
               systemQueue   (7)"
   ::= {er1645v2Lan2MCVlanVlanCSMapEntry 67108864}

er1645v2Lan2MCVlanVlanCSMapDropLevel OBJECT-TYPE
   SYNTAX      INTEGER
               {
               unchanged (-1),
               dropOnQueue (0)
               }
   MAX-ACCESS  read-write
   STATUS      current
   DESCRIPTION
      "Path: ethernet2.editConf.vlan.vlan.cosMap.dropLevel

       Possibilities:
               unchanged   (-1)
               dropOnQueue   (0)"
   ::= {er1645v2Lan2MCVlanVlanCSMapEntry 83886080}

er1645v2Lan2MCVlanVlanCSMapDeFlag OBJECT-TYPE
   SYNTAX      INTEGER
               {
               unchanged (255),
               clear (0),
               set (1)
               }
   MAX-ACCESS  read-write
   STATUS      current
   DESCRIPTION
      "Path: ethernet2.editConf.vlan.vlan.cosMap.deFlag

       Possibilities:
               unchanged   (255)
               clear   (0)
               set   (1)"
   ::= {er1645v2Lan2MCVlanVlanCSMapEntry 117440512}

er1645v2Lan2MCVlanVlanTCMap OBJECT-TYPE
   SYNTAX      SEQUENCE OF Er1645v2Lan2MCVlanVlanTCMapEntry
   MAX-ACCESS  not-accessible
   STATUS      current
   DESCRIPTION
      ""
   ::= {er1645v2Lan2MCVlan 241369088}

er1645v2Lan2MCVlanVlanTCMapEntry OBJECT-TYPE
   SYNTAX      Er1645v2Lan2MCVlanVlanTCMapEntry
   MAX-ACCESS  not-accessible
   STATUS      current
   DESCRIPTION
      ""
   INDEX      { er1645v2Lan2MCVlanTableIx,
                er1645v2Lan2MCVlanVlanTCMapTableIx }
   ::= {er1645v2Lan2MCVlanVlanTCMap 1}

Er1645v2Lan2MCVlanVlanTCMapEntry ::=
   SEQUENCE
      {
      er1645v2Lan2MCVlanVlanTCMapActions
         VariableLengthTableActions,
      er1645v2Lan2MCVlanVlanTCMapTableIx
         TableIndex,
      er1645v2Lan2MCVlanVlanTCMapStartTos
         INTEGER,
      er1645v2Lan2MCVlanVlanTCMapEndTos
         INTEGER,
      er1645v2Lan2MCVlanVlanTCMapCos
         INTEGER
      }

er1645v2Lan2MCVlanVlanTCMapActions OBJECT-TYPE
   SYNTAX      VariableLengthTableActions
   MAX-ACCESS  read-write
   STATUS      current
   DESCRIPTION
      "By way of this field, some manipulations
       on this table may be performed."
   ::= {er1645v2Lan2MCVlanVlanTCMapEntry 2}

er1645v2Lan2MCVlanVlanTCMapTableIx OBJECT-TYPE
   SYNTAX      TableIndex
   MAX-ACCESS  not-accessible
   STATUS      current
   DESCRIPTION
      ""
   ::= {er1645v2Lan2MCVlanVlanTCMapEntry 11}

er1645v2Lan2MCVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet2.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan2MCVlanVlanTCMapEntry 16777216}

er1645v2Lan2MCVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: ethernet2.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2Lan2MCVlanVlanTCMapEntry 33554432}

er1645v2Lan2MCVlanVlanTCMapCos OBJECT-TYPE
   SYNTAX      INTEGER
               {
               queueCosMap (8)
               }
   MAX-ACCESS  read-write
   STATUS      current
   DESCRIPTION
      "Path: ethernet2.editConf.vlan.vlan.tosCosMap.cos

       Possibilities:
               queueCosMap   (8)"
   ::= {er1645v2Lan2MCVlanVlanTCMapEntry 50331648}

er1645v2Lan2MCVlanVlanArpStaticArp OBJECT-TYPE
   SYNTAX      SEQUENCE OF Er1645v2Lan2MCVlanVlanArpStaticArpEntry
   MAX-ACCESS  not-accessible
   STATUS      current
   DESCRIPTION
      ""
   ::= {er1645v2Lan2MCVlan 235275008}

er1645v2Lan2MCVlanVlanArpStaticArpEntry OBJECT-TYPE
   SYNTAX      Er1645v2Lan2MCVlanVlanArpStaticArpEntry
   MAX-ACCESS  not-accessible
   STATUS      current
   DESCRIPTION
      ""
   INDEX      { er1645v2Lan2MCVlanTableIx,
                er1645v2Lan2MCVlanVlanArpStaticArpTableIx }
   ::= {er1645v2Lan2MCVlanVlanArpStaticArp 1}

Er1645v2Lan2MCVlanVlanArpStaticArpEntry ::=
   SEQUENCE
      {
      er1645v2Lan2MCVlanVlanArpStaticArpActions
         VariableLengthTableActions,
      er1645v2Lan2MCVlanVlanArpStaticArpTableIx
         TableIndex,
      er1645v2Lan2MCVlanVlanArpStaticArpMacAddress
         OCTET STRING,
      er1645v2Lan2MCVlanVlanArpStaticArpIpAddress
         IpAddress
      }

er1645v2Lan2MCVlanVlanArpStaticArpActions OBJECT-TYPE
   SYNTAX      VariableLengthTableActions
   MAX-ACCESS  read-write
   STATUS      current
   DESCRIPTION
      "By way of this field, some manipulations
       on this table may be performed."
   ::= {er1645v2Lan2MCVlanVlanArpStaticArpEntry 2}

er1645v2Lan2MCVlanVlanArpStaticArpTableIx OBJECT-TYPE
   SYNTAX      TableIndex
   MAX-ACCESS  not-accessible
   STATUS      current
   DESCRIPTION
      ""
   ::= {er1645v2Lan2MCVlanVlanArpStaticArpEntry 11}

er1645v2Lan2MCVlanVlanArpStaticArpMacAddress OBJECT-TYPE
   SYNTAX      OCTET STRING
   MAX-ACCESS  read-write
   STATUS      current
   DESCRIPTION
      "Path: ethernet2.editConf.vlan.vlan.arp.staticArp.macAddress

       MAC address."
   ::= {er1645v2Lan2MCVlanVlanArpStaticArpEntry 16777216}

er1645v2Lan2MCVlanVlanArpStaticArpIpAddress OBJECT-TYPE
   SYNTAX      IpAddress
   MAX-ACCESS  read-write
   STATUS      current
   DESCRIPTION
      "Path: ethernet2.editConf.vlan.vlan.arp.staticArp.ipAddress"
   ::= {er1645v2Lan2MCVlanVlanArpStaticArpEntry 33554432}


er1645v2Lan2MCPppOE OBJECT IDENTIFIER ::= {er1645v2Lan2MC 35}

er1645v2Lan2MCPppOESSCTable OBJECT-TYPE
   SYNTAX      SEQUENCE OF Er1645v2Lan2MCPppOEEntry
   MAX-ACCESS  not-accessible
   STATUS      current
   DESCRIPTION
      ""
   ::= {er1645v2Lan2MCPppOE 1}

er1645v2Lan2MCPppOEEntry OBJECT-TYPE
   SYNTAX      Er1645v2Lan2MCPppOEEntry
   MAX-ACCESS  not-accessible
   STATUS      current
   DESCRIPTION
      ""
   INDEX      { er1645v2Lan2MCPppOETableIx }
   ::= {er1645v2Lan2MCPppOESSCTable 1}

Er1645v2Lan2MCPppOEEntry ::=
   SEQUENCE
      {
      er1645v2Lan2MCPppOEActions
         VariableLengthTableActions,
      er1645v2Lan2MCPppOETableIx
         TableIndex,
      er1645v2Lan2MCPppOEName
         DisplayString,
      er1645v2Lan2MCPppOERemark
         DisplayString,
      er1645v2Lan2MCPppOEAdminStatus
         INTEGER,
      er1645v2Lan2MCPppOEMode
         INTEGER,
      er1645v2Lan2MCPppOEIpVrfRouter
         DisplayString,
      er1645v2Lan2MCPppOEIpAdr
         IpAddress,
      er1645v2Lan2MCPppOEIpNetm
         IpAddress,
      er1645v2Lan2MCPppOEIpSNetName
         INTEGER,
      er1645v2Lan2MCPppOEIpSNetCust
         DisplayString,
      er1645v2Lan2MCPppOEIpRem
         IpAddress,
      er1645v2Lan2MCPppOEIpUnnumbered
         DisplayString,
      er1645v2Lan2MCPppOEIpGwPref
         Integer32,
      er1645v2Lan2MCPppOEIpRsn
         INTEGER,
      er1645v2Lan2MCPppOEIpMtu
         Integer32,
      er1645v2Lan2MCPppOEIpMssAdjust
         INTEGER,
      er1645v2Lan2MCPppOEIpRipMetric
         Integer32,
      er1645v2Lan2MCPppOEIpRipMetricOut
         Integer32,
      er1645v2Lan2MCPppOEIpRipMode
         INTEGER,
      er1645v2Lan2MCPppOEIpRipTxVer
         INTEGER,
      er1645v2Lan2MCPppOEIpRipRxVer
         INTEGER,
      er1645v2Lan2MCPppOEIpRipSplitH
         INTEGER,
      er1645v2Lan2MCPppOEIpRipAuth
         INTEGER,
      er1645v2Lan2MCPppOEIpRipFilter
         DisplayString,
      er1645v2Lan2MCPppOEIpRipFilterIn
         DisplayString,
      er1645v2Lan2MCPppOEIpRipClearNextHop
         INTEGER,
      er1645v2Lan2MCPppOEIpAccPol
         DisplayString,
      er1645v2Lan2MCPppOEIpAB
         DisplayString,
      er1645v2Lan2MCPppOEIpMA
         INTEGER,
      er1645v2Lan2MCPppOEIpMF
         Integer32,
      er1645v2Lan2MCPppOEIpDB
         INTEGER,
      er1645v2Lan2MCPppOEIpIR
         INTEGER,
      er1645v2Lan2MCPppOEIpIgmp
         INTEGER,
      er1645v2Lan2MCPppOEIpNN
         DisplayString,
      er1645v2Lan2MCPppOEIpPimMode
         INTEGER,
      er1645v2Lan2MCPppOEIpPimDrPriority
         Counter32,
      er1645v2Lan2MCPppOEIpPimHelloTime
         TimeTicks,
      er1645v2Lan2MCPppOEIpPimPropagationDelay
         TimeTicks,
      er1645v2Lan2MCPppOEIpPimOverrideInterval
         TimeTicks,
      er1645v2Lan2MCPppOEIpPimBsrBorder
         INTEGER,
      er1645v2Lan2MCPppOEIpPimTtlThreshold
         Integer32,
      er1645v2Lan2MCPppOEIpIMNetworkUnreachable
         INTEGER,
      er1645v2Lan2MCPppOEIpIMHostUnreachable
         INTEGER,
      er1645v2Lan2MCPppOEIpIMProtocolUnreachable
         INTEGER,
      er1645v2Lan2MCPppOEIpIMPortUnreachable
         INTEGER,
      er1645v2Lan2MCPppOEIpIMMtuExceeded
         INTEGER,
      er1645v2Lan2MCPppOEIpIMAdminProhibited
         INTEGER,
      er1645v2Lan2MCPppOEIpIMTtlExceeded
         INTEGER,
      er1645v2Lan2MCPppOEIpIMRedirect
         INTEGER,
      er1645v2Lan2MCPppOEIpV6VrfRouter
         DisplayString,
      er1645v2Lan2MCPppOEIpV6AddrAutoConfigNrDupAddrDetects
         Integer32,
      er1645v2Lan2MCPppOEIpV6AddrAutoConfigAcceptRa
         INTEGER,
      er1645v2Lan2MCPppOEIpV6AddrAutoConfigAcceptRaRdnss
         INTEGER,
      er1645v2Lan2MCPppOEIpV6AddrAutoConfigAcceptRaDnssl
         INTEGER,
      er1645v2Lan2MCPppOEIpV6DefaultRoute
         INTEGER,
      er1645v2Lan2MCPppOEIpV6RaSend
         INTEGER,
      er1645v2Lan2MCPppOEIpV6RaMinInterval
         TimeTicks,
      er1645v2Lan2MCPppOEIpV6RaMaxInterval
         TimeTicks,
      er1645v2Lan2MCPppOEIpV6RaManagedFlag
         INTEGER,
      er1645v2Lan2MCPppOEIpV6RaOtherConfFlag
         INTEGER,
      er1645v2Lan2MCPppOEIpV6RaLinkMtu
         Integer32,
      er1645v2Lan2MCPppOEIpV6RaReachableTime
         TimeTicks,
      er1645v2Lan2MCPppOEIpV6RaRetransmitTime
         TimeTicks,
      er1645v2Lan2MCPppOEIpV6RaHopLimit
         Integer32,
      er1645v2Lan2MCPppOEIpV6RaDefaultLifeTime
         TimeTicks,
      er1645v2Lan2MCPppOEIpV6RaDnsOptionsRdnssLifeTime
         TimeTicks,
      er1645v2Lan2MCPppOEIpV6RaDnsOptionsRdnssImportServers
         INTEGER,
      er1645v2Lan2MCPppOEIpV6RaDnsOptionsDnsslLifeTime
         TimeTicks,
      er1645v2Lan2MCPppOEIpV6RaDnsOptionsDnsslImportDomains
         INTEGER,
      er1645v2Lan2MCPppOEIpV6RsSend
         INTEGER,
      er1645v2Lan2MCPppOEIpV6RsMaxRandomDelay
         TimeTicks,
      er1645v2Lan2MCPppOEIpV6RsInterval
         TimeTicks,
      er1645v2Lan2MCPppOEIpV6RsMaxSolicitations
         Integer32,
      er1645v2Lan2MCPppOEIpV6TrafficPolicyInbound
         DisplayString,
      er1645v2Lan2MCPppOEIpV6TrafficPolicyOutbound
         DisplayString,
      er1645v2Lan2MCPppOEIpV6FirewallZone
         DisplayString,
      er1645v2Lan2MCPppOEIpV6DhcpClientAddrAC
         INTEGER,
      er1645v2Lan2MCPppOEIpV6DhcpClientPrDelMode
         INTEGER,
      er1645v2Lan2MCPppOEIpV6DhcpClientPrDelPool
         DisplayString,
      er1645v2Lan2MCPppOEIpV6DhcpClientPrDelPdExclOpt
         INTEGER,
      er1645v2Lan2MCPppOEIpV6DhcpClientDnsServerPref
         Integer32,
      er1645v2Lan2MCPppOEIpV6DhcpClientRapidCommit
         INTEGER,
      er1645v2Lan2MCPppOEIpV6DhcpClientTimersSolTimeOut
         TimeTicks,
      er1645v2Lan2MCPppOEIpV6DhcpClientTimersSolMaxRt
         TimeTicks,
      er1645v2Lan2MCPppOEIpV6DhcpClientTimersInfoRefresh
         TimeTicks,
      er1645v2Lan2MCPppOEIpV6DhcpServerMode
         INTEGER,
      er1645v2Lan2MCPppOEIpV6DhcpServerPreference
         Integer32,
      er1645v2Lan2MCPppOEIpV6DhcpServerPool
         DisplayString,
      er1645v2Lan2MCPppOEIpV6DhcpServerRapidCommit
         INTEGER,
      er1645v2Lan2MCPppOEIpV6DhcpServerTimersInfoRefresh
         TimeTicks,
      er1645v2Lan2MCPppOEIpV6DhcpRelayMode
         INTEGER,
      er1645v2Lan2MCPppOEIpV6SendRedirect
         INTEGER,
      er1645v2Lan2MCPppOEIpV6LinkMtu
         Integer32,
      er1645v2Lan2MCPppOEIpV6InterfaceId
         OCTET STRING,
      er1645v2Lan2MCPppOEIpV6MF
         Integer32,
      er1645v2Lan2MCPppOEIpV6IcmpMessagesNoRoute
         INTEGER,
      er1645v2Lan2MCPppOEIpV6IcmpMessagesBeyondScope
         INTEGER,
      er1645v2Lan2MCPppOEIpV6IcmpMessagesAddressUnreachable
         INTEGER,
      er1645v2Lan2MCPppOEIpV6IcmpMessagesPortUnreachable
         INTEGER,
      er1645v2Lan2MCPppOEIpV6IcmpMessagesPacketTooBig
         INTEGER,
      er1645v2Lan2MCPppOEIpV6IcmpMessagesHopLimitExceeded
         INTEGER,
      er1645v2Lan2MCPppOEIpV6IcmpMessagesFragTimeExceeded
         INTEGER,
      er1645v2Lan2MCPppOEIpV6IcmpMessagesHeaderFieldErr
         INTEGER,
      er1645v2Lan2MCPppOEIpV6IcmpMessagesOptionUnrecognized
         INTEGER,
      er1645v2Lan2MCPppOEIpV6IcmpMessagesRedirect
         INTEGER,
      er1645v2Lan2MCPppOEPppLnkMOperation
         INTEGER,
      er1645v2Lan2MCPppOEPppLnkMInterval
         TimeTicks,
      er1645v2Lan2MCPppOEPppLnkMRepTimeOut
         TimeTicks,
      er1645v2Lan2MCPppOEPppLnkMFailsPrmt
         Integer32,
      er1645v2Lan2MCPppOEPppAuthentication
         INTEGER,
      er1645v2Lan2MCPppOEPppAuthenPeriod
         TimeTicks,
      er1645v2Lan2MCPppOEPppSessionName
         DisplayString,
      er1645v2Lan2MCPppOEPppSessionSecret
         DisplayString,
      er1645v2Lan2MCPppOEPppEncModeSessionSecret
         INTEGER,
      er1645v2Lan2MCPppOEPppEncSessionSecret
         DisplayString,
      er1645v2Lan2MCPppOEPppServiceName
         DisplayString
      }

er1645v2Lan2MCPppOEActions OBJECT-TYPE
   SYNTAX      VariableLengthTableActions
   MAX-ACCESS  read-write
   STATUS      current
   DESCRIPTION
      "By way of this field, some manipulations
       on this table may be performed."
   ::= {er1645v2Lan2MCPppOEEntry 2}

er1645v2Lan2MCPppOETableIx OBJECT-TYPE
   SYNTAX      TableIndex
   MAX-ACCESS  not-accessible
   STATUS      current
   DESCRIPTION
      ""
   ::= {er1645v2Lan2MCPppOEEntry 11}

er1645v2Lan2MCPppOEName OBJECT-TYPE
   SYNTAX      DisplayString
   MAX-ACCESS  read-write
   STATUS      current
   DESCRIPTION
      "Path: ethernet2.editConf.pppoEClient.name"
   ::= {er1645v2Lan2MCPppOEEntry 16777216}

er1645v2Lan2MCPppOERemark OBJECT-TYPE
   SYNTAX      DisplayString
   MAX-ACCESS  read-write
   STATUS      current
   DESCRIPTION
      "Path: ethernet2.editConf.pppoEClient.remark"
   ::= {er1645v2Lan2MCPppOEEntry 1157627904}

er1645v2Lan2MCPppOEAdminStatus OBJECT-TYPE
   SYNTAX      INTEGER
               {
               up (1),
               down (2)
               }
   MAX-ACCESS  read-write
   STATUS      current
   DESCRIPTION
      "Path: ethernet2.editConf.pppoEClient.adminStatus

       Possibilities:
               up   (1)
               down   (2)"
   ::= {er1645v2Lan2MCPppOEEntry 33554432}

er1645v2Lan2MCPppOEMode OBJECT-TYPE
   SYNTAX      INTEGER
               {
               routing (1),
               multilink (8),
               ipV6 (16),
               ipV6ipV4 (17)
               }
   MAX-ACCESS  read-write
   STATUS      current
   DESCRIPTION
      "Path: ethernet2.editConf.pppoEClient.mode

       Possibilities:
               routing   (1)
               multilink   (8)
               ipV6   (16)
               ipV6/ipV4   (17)"
   ::= {er1645v2Lan2MCPppOEEntry 67108864}

er1645v2Lan2MCPppOEIpVrfRouter OBJECT-TYPE
   SYNTAX      DisplayString
   MAX-ACCESS  read-write
   STATUS      current
   DESCRIPTION
      "Path: ethernet2.editConf.pppoEClient.ip.vrfRouter"
   ::= {er1645v2Lan2MCPppOEEntry 53215232}

er1645v2Lan2MCPppOEIpAdr OBJECT-TYPE
   SYNTAX      IpAddress
   MAX-ACCESS  read-write
   STATUS      current
   DESCRIPTION
      "Path: ethernet2.editConf.pppoEClient.ip.address"
   ::= {er1645v2Lan2MCPppOEEntry 58261504}

er1645v2Lan2MCPppOEIpNetm OBJECT-TYPE
   SYNTAX      IpAddress
   MAX-ACCESS  read-write
   STATUS      current
   DESCRIPTION
      "Path: ethernet2.editConf.pppoEClient.ip.netMask"
   ::= {er1645v2Lan2MCPppOEEntry 58392576}

er1645v2Lan2MCPppOEIpSNetName OBJECT-TYPE
   SYNTAX      INTEGER
               {
               slOPTg (0),
               corp (2),
               dmz (3),
               internet (1)
               }
   MAX-ACCESS  read-write
   STATUS      current
   DESCRIPTION
      "Path: ethernet2.editConf.pppoEClient.ip.sNet.name

       Possibilities:
               <OPT>   (0)
               corp   (2)
               dmz   (3)
               internet   (1)"
   ::= {er1645v2Lan2MCPppOEEntry 53674240}

er1645v2Lan2MCPppOEIpSNetCust OBJECT-TYPE
   SYNTAX      DisplayString
   MAX-ACCESS  read-write
   STATUS      current
   DESCRIPTION
      "Path: ethernet2.editConf.pppoEClient.ip.sNet.custom"
   ::= {er1645v2Lan2MCPppOEEntry 53674496}

er1645v2Lan2MCPppOEIpRem OBJECT-TYPE
   SYNTAX      IpAddress
   MAX-ACCESS  read-write
   STATUS      current
   DESCRIPTION
      "Path: ethernet2.editConf.pppoEClient.ip.remote"
   ::= {er1645v2Lan2MCPppOEEntry 58458112}

er1645v2Lan2MCPppOEIpUnnumbered OBJECT-TYPE
   SYNTAX      DisplayString
   MAX-ACCESS  read-write
   STATUS      current
   DESCRIPTION
      "Path: ethernet2.editConf.pppoEClient.ip.unnumbered"
   ::= {er1645v2Lan2MCPppOEEntry 52625408}

er1645v2Lan2MCPppOEIpGwPref OBJECT-TYPE
   SYNTAX      Integer32
   MAX-ACCESS  read-write
   STATUS      current
   DESCRIPTION
      "Path: ethernet2.editConf.pppoEClient.ip.gatewayPreference"
   ::= {er1645v2Lan2MCPppOEEntry 52690944}

er1645v2Lan2MCPppOEIpRsn OBJECT-TYPE
   SYNTAX      INTEGER
               {
               disabled (0),
               enabled (1)
               }
   MAX-ACCESS  read-write
   STATUS      current
   DESCRIPTION
      "Path: ethernet2.editConf.pppoEClient.ip.requestSubnet

       Possibilities:
               disabled   (0)
               enabled   (1)"
   ::= {er1645v2Lan2MCPppOEEntry 56688640}

er1645v2Lan2MCPppOEIpMtu OBJECT-TYPE
   SYNTAX      Integer32
   MAX-ACCESS  read-write
   STATUS      current
   DESCRIPTION
      "Path: ethernet2.editConf.pppoEClient.ip.mtu"
   ::= {er1645v2Lan2MCPppOEEntry 52953088}

er1645v2Lan2MCPppOEIpMssAdjust OBJECT-TYPE
   SYNTAX      INTEGER
               {
               disabled (0),
               auto (65536)
               }
   MAX-ACCESS  read-write
   STATUS      current
   DESCRIPTION
      "Path: ethernet2.editConf.pppoEClient.ip.mssAdjust

       Possibilities:
               disabled   (0)
               auto   (65536)"
   ::= {er1645v2Lan2MCPppOEEntry 53280768}

er1645v2Lan2MCPppOEIpRipMetric OBJECT-TYPE
   SYNTAX      Integer32
   MAX-ACCESS  read-write
   STATUS      current
   DESCRIPTION
      "Path: ethernet2.editConf.pppoEClient.ip.rip.metric"
   ::= {er1645v2Lan2MCPppOEEntry 51712768}

er1645v2Lan2MCPppOEIpRipMetricOut OBJECT-TYPE
   SYNTAX      Integer32
   MAX-ACCESS  read-write
   STATUS      current
   DESCRIPTION
      "Path: ethernet2.editConf.pppoEClient.ip.rip.metricOut"
   ::= {er1645v2Lan2MCPppOEEntry 51713024}

er1645v2Lan2MCPppOEIpRipMode OBJECT-TYPE
   SYNTAX      INTEGER
               {
               disabled (0),
               passive (1),
               active (2)
               }
   MAX-ACCESS  read-write
   STATUS      current
   DESCRIPTION
      "Path: ethernet2.editConf.pppoEClient.ip.rip.mode

       Possibilities:
               disabled   (0)
               passive   (1)
               active   (2)"
   ::= {er1645v2Lan2MCPppOEEntry 51713280}

er1645v2Lan2MCPppOEIpRipTxVer OBJECT-TYPE
   SYNTAX      INTEGER
               {
               rip1 (0),
               rip2 (1),
               rip1mcompatible (2)
               }
   MAX-ACCESS  read-write
   STATUS      current
   DESCRIPTION
      "Path: ethernet2.editConf.pppoEClient.ip.rip.txVersion

       Possibilities:
               rip1   (0)
               rip2   (1)
               rip1-compatible   (2)"
   ::= {er1645v2Lan2MCPppOEEntry 51716864}

er1645v2Lan2MCPppOEIpRipRxVer OBJECT-TYPE
   SYNTAX      INTEGER
               {
               rip1only (0),
               rip2only (1),
               rip12 (2)
               }
   MAX-ACCESS  read-write
   STATUS      current
   DESCRIPTION
      "Path: ethernet2.editConf.pppoEClient.ip.rip.rxVersion

       Possibilities:
               rip1only   (0)
               rip2only   (1)
               rip1&2   (2)"
   ::= {er1645v2Lan2MCPppOEEntry 51717120}

er1645v2Lan2MCPppOEIpRipSplitH OBJECT-TYPE
   SYNTAX      INTEGER
               {
               disabled (0),
               enabled (1),
               poisonedReverse (2)
               }
   MAX-ACCESS  read-write
   STATUS      current
   DESCRIPTION
      "Path: ethernet2.editConf.pppoEClient.ip.rip.splitHorizon

       Possibilities:
               disabled   (0)
               enabled   (1)
               poisonedReverse   (2)"
   ::= {er1645v2Lan2MCPppOEEntry 51713792}

er1645v2Lan2MCPppOEIpRipAuth OBJECT-TYPE
   SYNTAX      INTEGER
               {
               disabled (0),
               texts (1),
               md5 (2)
               }
   MAX-ACCESS  read-write
   STATUS      current
   DESCRIPTION
      "Path: ethernet2.editConf.pppoEClient.ip.rip.authentication

       Possibilities:
               disabled   (0)
               text    (1)
               md5   (2)"
   ::= {er1645v2Lan2MCPppOEEntry 51712512}

er1645v2Lan2MCPppOEIpRipFilter OBJECT-TYPE
   SYNTAX      DisplayString
   MAX-ACCESS  read-write
   STATUS      current
   DESCRIPTION
      "Path: ethernet2.editConf.pppoEClient.ip.rip.filter"
   ::= {er1645v2Lan2MCPppOEEntry 51716096}

er1645v2Lan2MCPppOEIpRipFilterIn OBJECT-TYPE
   SYNTAX      DisplayString
   MAX-ACCESS  read-write
   STATUS      current
   DESCRIPTION
      "Path: ethernet2.editConf.pppoEClient.ip.rip.filterIn"
   ::= {er1645v2Lan2MCPppOEEntry 51716352}

er1645v2Lan2MCPppOEIpRipClearNextHop OBJECT-TYPE
   SYNTAX      INTEGER
               {
               disabled (0),
               enabled (1)
               }
   MAX-ACCESS  read-write
   STATUS      current
   DESCRIPTION
      "Path: ethernet2.editConf.pppoEClient.ip.rip.clearNextHop

       Possibilities:
               disabled   (0)
               enabled   (1)"
   ::= {er1645v2Lan2MCPppOEEntry 51708416}

er1645v2Lan2MCPppOEIpAccPol OBJECT-TYPE
   SYNTAX      DisplayString
   MAX-ACCESS  read-write
   STATUS      current
   DESCRIPTION
      "Path: ethernet2.editConf.pppoEClient.ip.accessPolicy"
   ::= {er1645v2Lan2MCPppOEEntry 53084160}

er1645v2Lan2MCPppOEIpAB OBJECT-TYPE
   SYNTAX      DisplayString
   MAX-ACCESS  read-write
   STATUS      current
   DESCRIPTION
      "Path: ethernet2.editConf.pppoEClient.ip.trafficPolicy"
   ::= {er1645v2Lan2MCPppOEEntry 51249152}

er1645v2Lan2MCPppOEIpMA OBJECT-TYPE
   SYNTAX      INTEGER
               {
               disabled (0),
               enabled (1)
               }
   MAX-ACCESS  read-write
   STATUS      current
   DESCRIPTION
      "Path: ethernet2.editConf.pppoEClient.ip.mgmtAccess

       Possibilities:
               disabled   (0)
               enabled   (1)"
   ::= {er1645v2Lan2MCPppOEEntry 51380224}

er1645v2Lan2MCPppOEIpMF OBJECT-TYPE
   SYNTAX      Integer32
   MAX-ACCESS  read-write
   STATUS      current
   DESCRIPTION
      "Path: ethernet2.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2Lan2MCPppOEEntry 51445760}

er1645v2Lan2MCPppOEIpDB OBJECT-TYPE
   SYNTAX      INTEGER
               {
               disabled (0),
               enabled (1)
               }
   MAX-ACCESS  read-write
   STATUS      current
   DESCRIPTION
      "Path: ethernet2.editConf.pppoEClient.ip.directedBroadcasts

       Possibilities:
               disabled   (0)
               enabled   (1)"
   ::= {er1645v2Lan2MCPppOEEntry 51773440}

er1645v2Lan2MCPppOEIpIR OBJECT-TYPE
   SYNTAX      INTEGER
               {
               disabled (0),
               enabled (1)
               }
   MAX-ACCESS  read-write
   STATUS      current
   DESCRIPTION
      "Path: ethernet2.editConf.pppoEClient.ip.icmpRedirects

       Possibilities:
               disabled   (0)
               enabled   (1)"
   ::= {er1645v2Lan2MCPppOEEntry 52035584}

er1645v2Lan2MCPppOEIpIgmp OBJECT-TYPE
   SYNTAX      INTEGER
               {
               disabled (0),
               proxy (1),
               router (2),
               v3Router (5)
               }
   MAX-ACCESS  read-write
   STATUS      current
   DESCRIPTION
      "Path: ethernet2.editConf.pppoEClient.ip.igmp

       Possibilities:
               disabled   (0)
               proxy   (1)
               router   (2)
               v3Router   (5)"
   ::= {er1645v2Lan2MCPppOEEntry 52428800}

er1645v2Lan2MCPppOEIpNN OBJECT-TYPE
   SYNTAX      DisplayString
   MAX-ACCESS  read-write
   STATUS      current
   DESCRIPTION
      "Path: ethernet2.editConf.pppoEClient.ip.nat"
   ::= {er1645v2Lan2MCPppOEEntry 52101120}

er1645v2Lan2MCPppOEIpPimMode OBJECT-TYPE
   SYNTAX      INTEGER
               {
               disabled (0),
               sparse (1),
               passive (2)
               }
   MAX-ACCESS  read-write
   STATUS      current
   DESCRIPTION
      "Path: ethernet2.editConf.pppoEClient.ip.pim.mode

       Possibilities:
               disabled   (0)
               sparse   (1)
               passive   (2)"
   ::= {er1645v2Lan2MCPppOEEntry 53346560}

er1645v2Lan2MCPppOEIpPimDrPriority OBJECT-TYPE
   SYNTAX      Counter32
   MAX-ACCESS  read-write
   STATUS      current
   DESCRIPTION
      "Path: ethernet2.editConf.pppoEClient.ip.pim.drPriority

       32 bit unsigned wrappable counter."
   ::= {er1645v2Lan2MCPppOEEntry 53346816}

er1645v2Lan2MCPppOEIpPimHelloTime OBJECT-TYPE
   SYNTAX      TimeTicks
   MAX-ACCESS  read-write
   STATUS      current
   DESCRIPTION
      "Path: ethernet2.editConf.pppoEClient.ip.pim.helloTime

       Time in centi-second."
   ::= {er1645v2Lan2MCPppOEEntry 53347072}

er1645v2Lan2MCPppOEIpPimPropagationDelay OBJECT-TYPE
   SYNTAX      TimeTicks
   MAX-ACCESS  read-write
   STATUS      current
   DESCRIPTION
      "Path: ethernet2.editConf.pppoEClient.ip.pim.propagationDelay

       Time in centi-second."
   ::= {er1645v2Lan2MCPppOEEntry 53347328}

er1645v2Lan2MCPppOEIpPimOverrideInterval OBJECT-TYPE
   SYNTAX      TimeTicks
   MAX-ACCESS  read-write
   STATUS      current
   DESCRIPTION
      "Path: ethernet2.editConf.pppoEClient.ip.pim.overrideInterval

       Time in centi-second."
   ::= {er1645v2Lan2MCPppOEEntry 53347584}

er1645v2Lan2MCPppOEIpPimBsrBorder OBJECT-TYPE
   SYNTAX      INTEGER
               {
               disabled (0),
               enabled (1)
               }
   MAX-ACCESS  read-write
   STATUS      current
   DESCRIPTION
      "Path: ethernet2.editConf.pppoEClient.ip.pim.bsrBorder

       Possibilities:
               disabled   (0)
               enabled   (1)"
   ::= {er1645v2Lan2MCPppOEEntry 53347840}

er1645v2Lan2MCPppOEIpPimTtlThreshold OBJECT-TYPE
   SYNTAX      Integer32
   MAX-ACCESS  read-write
   STATUS      current
   DESCRIPTION
      "Path: ethernet2.editConf.pppoEClient.ip.pim.ttlThreshold"
   ::= {er1645v2Lan2MCPppOEEntry 53348096}

er1645v2Lan2MCPppOEIpIMNetworkUnreachable OBJECT-TYPE
   SYNTAX      INTEGER
               {
               disabled (0),
               enabled (1)
               }
   MAX-ACCESS  read-write
   STATUS      current
   DESCRIPTION
      "Path: ethernet2.editConf.pppoEClient.ip.icmpMessages.networkUnreachable

       Possibilities:
               disabled   (0)
               enabled   (1)"
   ::= {er1645v2Lan2MCPppOEEntry 53412096}

er1645v2Lan2MCPppOEIpIMHostUnreachable OBJECT-TYPE
   SYNTAX      INTEGER
               {
               disabled (0),
               enabled (1)
               }
   MAX-ACCESS  read-write
   STATUS      current
   DESCRIPTION
      "Path: ethernet2.editConf.pppoEClient.ip.icmpMessages.hostUnreachable

       Possibilities:
               disabled   (0)
               enabled   (1)"
   ::= {er1645v2Lan2MCPppOEEntry 53412352}

er1645v2Lan2MCPppOEIpIMProtocolUnreachable OBJECT-TYPE
   SYNTAX      INTEGER
               {
               disabled (0),
               enabled (1)
               }
   MAX-ACCESS  read-write
   STATUS      current
   DESCRIPTION
      "Path: ethernet2.editConf.pppoEClient.ip.icmpMessages.protocolUnreachable

       Possibilities:
               disabled   (0)
               enabled   (1)"
   ::= {er1645v2Lan2MCPppOEEntry 53412608}

er1645v2Lan2MCPppOEIpIMPortUnreachable OBJECT-TYPE
   SYNTAX      INTEGER
               {
               disabled (0),
               enabled (1)
               }
   MAX-ACCESS  read-write
   STATUS      current
   DESCRIPTION
      "Path: ethernet2.editConf.pppoEClient.ip.icmpMessages.portUnreachable

       Possibilities:
               disabled   (0)
               enabled   (1)"
   ::= {er1645v2Lan2MCPppOEEntry 53412864}

er1645v2Lan2MCPppOEIpIMMtuExceeded OBJECT-TYPE
   SYNTAX      INTEGER
               {
               disabled (0),
               enabled (1)
               }
   MAX-ACCESS  read-write
   STATUS      current
   DESCRIPTION
      "Path: ethernet2.editConf.pppoEClient.ip.icmpMessages.mtuExceeded

       Possibilities:
               disabled   (0)
               enabled   (1)"
   ::= {er1645v2Lan2MCPppOEEntry 53413120}

er1645v2Lan2MCPppOEIpIMAdminProhibited OBJECT-TYPE
   SYNTAX      INTEGER
               {
               disabled (0),
               enabled (1)
               }
   MAX-ACCESS  read-write
   STATUS      current
   DESCRIPTION
      "Path: ethernet2.editConf.pppoEClient.ip.icmpMessages.adminProhibited

       Possibilities:
               disabled   (0)
               enabled   (1)"
   ::= {er1645v2Lan2MCPppOEEntry 53413376}

er1645v2Lan2MCPppOEIpIMTtlExceeded OBJECT-TYPE
   SYNTAX      INTEGER
               {
               disabled (0),
               enabled (1)
               }
   MAX-ACCESS  read-write
   STATUS      current
   DESCRIPTION
      "Path: ethernet2.editConf.pppoEClient.ip.icmpMessages.ttlExceeded

       Possibilities:
               disabled   (0)
               enabled   (1)"
   ::= {er1645v2Lan2MCPppOEEntry 53413632}

er1645v2Lan2MCPppOEIpIMRedirect OBJECT-TYPE
   SYNTAX      INTEGER
               {
               disabled (0),
               enabled (1)
               }
   MAX-ACCESS  read-write
   STATUS      current
   DESCRIPTION
      "Path: ethernet2.editConf.pppoEClient.ip.icmpMessages.redirect

       Possibilities:
               disabled   (0)
               enabled   (1)"
   ::= {er1645v2Lan2MCPppOEEntry 53413888}

er1645v2Lan2MCPppOEIpV6VrfRouter OBJECT-TYPE
   SYNTAX      DisplayString
   MAX-ACCESS  read-write
   STATUS      current
   DESCRIPTION
      "Path: ethernet2.editConf.pppoEClient.ipV6.vrfRouter"
   ::= {er1645v2Lan2MCPppOEEntry 704708608}

er1645v2Lan2MCPppOEIpV6AddrAutoConfigNrDupAddrDetects OBJECT-TYPE
   SYNTAX      Integer32
   MAX-ACCESS  read-write
   STATUS      current
   DESCRIPTION
      "Path: ethernet2.editConf.pppoEClient.ipV6.addrAutoConfig.nrDupAddrDetects"
   ::= {er1645v2Lan2MCPppOEEntry 704905472}

er1645v2Lan2MCPppOEIpV6AddrAutoConfigAcceptRa OBJECT-TYPE
   SYNTAX      INTEGER
               {
               disabled (0),
               enabled (1)
               }
   MAX-ACCESS  read-write
   STATUS      current
   DESCRIPTION
      "Path: ethernet2.editConf.pppoEClient.ipV6.addrAutoConfig.acceptRa

       Possibilities:
               disabled   (0)
               enabled   (1)"
   ::= {er1645v2Lan2MCPppOEEntry 704905728}

er1645v2Lan2MCPppOEIpV6AddrAutoConfigAcceptRaRdnss OBJECT-TYPE
   SYNTAX      INTEGER
               {
               disabled (0),
               enabled (1)
               }
   MAX-ACCESS  read-write
   STATUS      current
   DESCRIPTION
      "Path: ethernet2.editConf.pppoEClient.ipV6.addrAutoConfig.acceptRaRdnss

       Possibilities:
               disabled   (0)
               enabled   (1)"
   ::= {er1645v2Lan2MCPppOEEntry 704905984}

er1645v2Lan2MCPppOEIpV6AddrAutoConfigAcceptRaDnssl OBJECT-TYPE
   SYNTAX      INTEGER
               {
               disabled (0),
               enabled (1)
               }
   MAX-ACCESS  read-write
   STATUS      current
   DESCRIPTION
      "Path: ethernet2.editConf.pppoEClient.ipV6.addrAutoConfig.acceptRaDnssl

       Possibilities:
               disabled   (0)
               enabled   (1)"
   ::= {er1645v2Lan2MCPppOEEntry 704906240}

er1645v2Lan2MCPppOEIpV6DefaultRoute OBJECT-TYPE
   SYNTAX      INTEGER
               {
               disabled (0),
               enabled (1)
               }
   MAX-ACCESS  read-write
   STATUS      current
   DESCRIPTION
      "Path: ethernet2.editConf.pppoEClient.ipV6.defaultRoute

       Possibilities:
               disabled   (0)
               enabled   (1)"
   ::= {er1645v2Lan2MCPppOEEntry 704970752}

er1645v2Lan2MCPppOEIpV6RaSend OBJECT-TYPE
   SYNTAX      INTEGER
               {
               disabled (0),
               enabled (1)
               }
   MAX-ACCESS  read-write
   STATUS      current
   DESCRIPTION
      "Path: ethernet2.editConf.pppoEClient.ipV6.ra.send

       Possibilities:
               disabled   (0)
               enabled   (1)"
   ::= {er1645v2Lan2MCPppOEEntry 705036544}

er1645v2Lan2MCPppOEIpV6RaMinInterval OBJECT-TYPE
   SYNTAX      TimeTicks
   MAX-ACCESS  read-write
   STATUS      current
   DESCRIPTION
      "Path: ethernet2.editConf.pppoEClient.ipV6.ra.minInterval

       Time in centi-second."
   ::= {er1645v2Lan2MCPppOEEntry 705036800}

er1645v2Lan2MCPppOEIpV6RaMaxInterval OBJECT-TYPE
   SYNTAX      TimeTicks
   MAX-ACCESS  read-write
   STATUS      current
   DESCRIPTION
      "Path: ethernet2.editConf.pppoEClient.ipV6.ra.maxInterval

       Time in centi-second."
   ::= {er1645v2Lan2MCPppOEEntry 705037056}

er1645v2Lan2MCPppOEIpV6RaManagedFlag OBJECT-TYPE
   SYNTAX      INTEGER
               {
               disabled (0),
               enabled (1)
               }
   MAX-ACCESS  read-write
   STATUS      current
   DESCRIPTION
      "Path: ethernet2.editConf.pppoEClient.ipV6.ra.managedFlag

       Possibilities:
               disabled   (0)
               enabled   (1)"
   ::= {er1645v2Lan2MCPppOEEntry 705037312}

er1645v2Lan2MCPppOEIpV6RaOtherConfFlag OBJECT-TYPE
   SYNTAX      INTEGER
               {
               disabled (0),
               enabled (1)
               }
   MAX-ACCESS  read-write
   STATUS      current
   DESCRIPTION
      "Path: ethernet2.editConf.pppoEClient.ipV6.ra.otherConfFlag

       Possibilities:
               disabled   (0)
               enabled   (1)"
   ::= {er1645v2Lan2MCPppOEEntry 705037568}

er1645v2Lan2MCPppOEIpV6RaLinkMtu OBJECT-TYPE
   SYNTAX      Integer32
   MAX-ACCESS  read-write
   STATUS      current
   DESCRIPTION
      "Path: ethernet2.editConf.pppoEClient.ipV6.ra.linkMtu"
   ::= {er1645v2Lan2MCPppOEEntry 705037824}

er1645v2Lan2MCPppOEIpV6RaReachableTime OBJECT-TYPE
   SYNTAX      TimeTicks
   MAX-ACCESS  read-write
   STATUS      current
   DESCRIPTION
      "Path: ethernet2.editConf.pppoEClient.ipV6.ra.reachableTime

       Time in centi-second."
   ::= {er1645v2Lan2MCPppOEEntry 705038080}

er1645v2Lan2MCPppOEIpV6RaRetransmitTime OBJECT-TYPE
   SYNTAX      TimeTicks
   MAX-ACCESS  read-write
   STATUS      current
   DESCRIPTION
      "Path: ethernet2.editConf.pppoEClient.ipV6.ra.retransmitTime

       Time in centi-second."
   ::= {er1645v2Lan2MCPppOEEntry 705038336}

er1645v2Lan2MCPppOEIpV6RaHopLimit OBJECT-TYPE
   SYNTAX      Integer32
   MAX-ACCESS  read-write
   STATUS      current
   DESCRIPTION
      "Path: ethernet2.editConf.pppoEClient.ipV6.ra.hopLimit"
   ::= {er1645v2Lan2MCPppOEEntry 705038592}

er1645v2Lan2MCPppOEIpV6RaDefaultLifeTime OBJECT-TYPE
   SYNTAX      TimeTicks
   MAX-ACCESS  read-write
   STATUS      current
   DESCRIPTION
      "Path: ethernet2.editConf.pppoEClient.ipV6.ra.defaultLifeTime

       Time in centi-second."
   ::= {er1645v2Lan2MCPppOEEntry 705038848}

er1645v2Lan2MCPppOEIpV6RaDnsOptionsRdnssLifeTime OBJECT-TYPE
   SYNTAX      TimeTicks
   MAX-ACCESS  read-write
   STATUS      current
   DESCRIPTION
      "Path: ethernet2.editConf.pppoEClient.ipV6.ra.dnsOptions.rdnss.lifeTime

       Time in centi-second."
   ::= {er1645v2Lan2MCPppOEEntry 705039140}

er1645v2Lan2MCPppOEIpV6RaDnsOptionsRdnssImportServers OBJECT-TYPE
   SYNTAX      INTEGER
               {
               disabled (0),
               enabled (1)
               }
   MAX-ACCESS  read-write
   STATUS      current
   DESCRIPTION
      "Path: ethernet2.editConf.pppoEClient.ipV6.ra.dnsOptions.rdnss.importServers

       Possibilities:
               disabled   (0)
               enabled   (1)"
   ::= {er1645v2Lan2MCPppOEEntry 705039148}

er1645v2Lan2MCPppOEIpV6RaDnsOptionsDnsslLifeTime OBJECT-TYPE
   SYNTAX      TimeTicks
   MAX-ACCESS  read-write
   STATUS      current
   DESCRIPTION
      "Path: ethernet2.editConf.pppoEClient.ipV6.ra.dnsOptions.dnssl.lifeTime

       Time in centi-second."
   ::= {er1645v2Lan2MCPppOEEntry 705039172}

er1645v2Lan2MCPppOEIpV6RaDnsOptionsDnsslImportDomains OBJECT-TYPE
   SYNTAX      INTEGER
               {
               disabled (0),
               enabled (1)
               }
   MAX-ACCESS  read-write
   STATUS      current
   DESCRIPTION
      "Path: ethernet2.editConf.pppoEClient.ipV6.ra.dnsOptions.dnssl.importDomains

       Possibilities:
               disabled   (0)
               enabled   (1)"
   ::= {er1645v2Lan2MCPppOEEntry 705039180}

er1645v2Lan2MCPppOEIpV6RsSend OBJECT-TYPE
   SYNTAX      INTEGER
               {
               disabled (0),
               enabled (1)
               }
   MAX-ACCESS  read-write
   STATUS      current
   DESCRIPTION
      "Path: ethernet2.editConf.pppoEClient.ipV6.rs.send

       Possibilities:
               disabled   (0)
               enabled   (1)"
   ::= {er1645v2Lan2MCPppOEEntry 705954048}

er1645v2Lan2MCPppOEIpV6RsMaxRandomDelay OBJECT-TYPE
   SYNTAX      TimeTicks
   MAX-ACCESS  read-write
   STATUS      current
   DESCRIPTION
      "Path: ethernet2.editConf.pppoEClient.ipV6.rs.maxRandomDelay

       Time in centi-second."
   ::= {er1645v2Lan2MCPppOEEntry 705954304}

er1645v2Lan2MCPppOEIpV6RsInterval OBJECT-TYPE
   SYNTAX      TimeTicks
   MAX-ACCESS  read-write
   STATUS      current
   DESCRIPTION
      "Path: ethernet2.editConf.pppoEClient.ipV6.rs.interval

       Time in centi-second."
   ::= {er1645v2Lan2MCPppOEEntry 705954560}

er1645v2Lan2MCPppOEIpV6RsMaxSolicitations OBJECT-TYPE
   SYNTAX      Integer32
   MAX-ACCESS  read-write
   STATUS      current
   DESCRIPTION
      "Path: ethernet2.editConf.pppoEClient.ipV6.rs.maxSolicitations"
   ::= {er1645v2Lan2MCPppOEEntry 705954816}

er1645v2Lan2MCPppOEIpV6TrafficPolicyInbound OBJECT-TYPE
   SYNTAX      DisplayString
   MAX-ACCESS  read-write
   STATUS      current
   DESCRIPTION
      "Path: ethernet2.editConf.pppoEClient.ipV6.trafficPolicy.inbound"
   ::= {er1645v2Lan2MCPppOEEntry 705364224}

er1645v2Lan2MCPppOEIpV6TrafficPolicyOutbound OBJECT-TYPE
   SYNTAX      DisplayString
   MAX-ACCESS  read-write
   STATUS      current
   DESCRIPTION
      "Path: ethernet2.editConf.pppoEClient.ipV6.trafficPolicy.outbound"
   ::= {er1645v2Lan2MCPppOEEntry 705364480}

er1645v2Lan2MCPppOEIpV6FirewallZone OBJECT-TYPE
   SYNTAX      DisplayString
   MAX-ACCESS  read-write
   STATUS      current
   DESCRIPTION
      "Path: ethernet2.editConf.pppoEClient.ipV6.firewall.zone"
   ::= {er1645v2Lan2MCPppOEEntry 705429760}

er1645v2Lan2MCPppOEIpV6DhcpClientAddrAC OBJECT-TYPE
   SYNTAX      INTEGER
               {
               disabled (0),
               enabled (1)
               }
   MAX-ACCESS  read-write
   STATUS      current
   DESCRIPTION
      "Path: ethernet2.editConf.pppoEClient.ipV6.dhcp.client.addrAutoConfig

       Possibilities:
               disabled   (0)
               enabled   (1)"
   ::= {er1645v2Lan2MCPppOEEntry 705307648}

er1645v2Lan2MCPppOEIpV6DhcpClientPrDelMode OBJECT-TYPE
   SYNTAX      INTEGER
               {
               disabled (0),
               enabled (1)
               }
   MAX-ACCESS  read-write
   STATUS      current
   DESCRIPTION
      "Path: ethernet2.editConf.pppoEClient.ipV6.dhcp.client.pd.mode

       Possibilities:
               disabled   (0)
               enabled   (1)"
   ::= {er1645v2Lan2MCPppOEEntry 705308676}

er1645v2Lan2MCPppOEIpV6DhcpClientPrDelPool OBJECT-TYPE
   SYNTAX      DisplayString
   MAX-ACCESS  read-write
   STATUS      current
   DESCRIPTION
      "Path: ethernet2.editConf.pppoEClient.ipV6.dhcp.client.pd.pool"
   ::= {er1645v2Lan2MCPppOEEntry 705308680}

er1645v2Lan2MCPppOEIpV6DhcpClientPrDelPdExclOpt OBJECT-TYPE
   SYNTAX      INTEGER
               {
               disabled (0),
               enabled (1)
               }
   MAX-ACCESS  read-write
   STATUS      current
   DESCRIPTION
      "Path: ethernet2.editConf.pppoEClient.ipV6.dhcp.client.pd.pdExclOpt

       Possibilities:
               disabled   (0)
               enabled   (1)"
   ::= {er1645v2Lan2MCPppOEEntry 705308684}

er1645v2Lan2MCPppOEIpV6DhcpClientDnsServerPref OBJECT-TYPE
   SYNTAX      Integer32
   MAX-ACCESS  read-write
   STATUS      current
   DESCRIPTION
      "Path: ethernet2.editConf.pppoEClient.ipV6.dhcp.client.dns.serverPref"
   ::= {er1645v2Lan2MCPppOEEntry 705310724}

er1645v2Lan2MCPppOEIpV6DhcpClientRapidCommit OBJECT-TYPE
   SYNTAX      INTEGER
               {
               disabled (0),
               enabled (1)
               }
   MAX-ACCESS  read-write
   STATUS      current
   DESCRIPTION
      "Path: ethernet2.editConf.pppoEClient.ipV6.dhcp.client.rapidCommit

       Possibilities:
               disabled   (0)
               enabled   (1)"
   ::= {er1645v2Lan2MCPppOEEntry 705309696}

er1645v2Lan2MCPppOEIpV6DhcpClientTimersSolTimeOut OBJECT-TYPE
   SYNTAX      TimeTicks
   MAX-ACCESS  read-write
   STATUS      current
   DESCRIPTION
      "Path: ethernet2.editConf.pppoEClient.ipV6.dhcp.client.timers.solTimeOut

       Time in centi-second."
   ::= {er1645v2Lan2MCPppOEEntry 705311748}

er1645v2Lan2MCPppOEIpV6DhcpClientTimersSolMaxRt OBJECT-TYPE
   SYNTAX      TimeTicks
   MAX-ACCESS  read-write
   STATUS      current
   DESCRIPTION
      "Path: ethernet2.editConf.pppoEClient.ipV6.dhcp.client.timers.solMaxRt

       Time in centi-second."
   ::= {er1645v2Lan2MCPppOEEntry 705311752}

er1645v2Lan2MCPppOEIpV6DhcpClientTimersInfoRefresh OBJECT-TYPE
   SYNTAX      TimeTicks
   MAX-ACCESS  read-write
   STATUS      current
   DESCRIPTION
      "Path: ethernet2.editConf.pppoEClient.ipV6.dhcp.client.timers.infoRefresh

       Time in centi-second."
   ::= {er1645v2Lan2MCPppOEEntry 705311756}

er1645v2Lan2MCPppOEIpV6DhcpServerMode OBJECT-TYPE
   SYNTAX      INTEGER
               {
               disabled (0),
               enabled (1)
               }
   MAX-ACCESS  read-write
   STATUS      current
   DESCRIPTION
      "Path: ethernet2.editConf.pppoEClient.ipV6.dhcp.server.mode

       Possibilities:
               disabled   (0)
               enabled   (1)"
   ::= {er1645v2Lan2MCPppOEEntry 705315840}

er1645v2Lan2MCPppOEIpV6DhcpServerPreference OBJECT-TYPE
   SYNTAX      Integer32
   MAX-ACCESS  read-write
   STATUS      current
   DESCRIPTION
      "Path: ethernet2.editConf.pppoEClient.ipV6.dhcp.server.preference"
   ::= {er1645v2Lan2MCPppOEEntry 705316864}

er1645v2Lan2MCPppOEIpV6DhcpServerPool OBJECT-TYPE
   SYNTAX      DisplayString
   MAX-ACCESS  read-write
   STATUS      current
   DESCRIPTION
      "Path: ethernet2.editConf.pppoEClient.ipV6.dhcp.server.pool"
   ::= {er1645v2Lan2MCPppOEEntry 705317888}

er1645v2Lan2MCPppOEIpV6DhcpServerRapidCommit OBJECT-TYPE
   SYNTAX      INTEGER
               {
               disabled (0),
               enabled (1)
               }
   MAX-ACCESS  read-write
   STATUS      current
   DESCRIPTION
      "Path: ethernet2.editConf.pppoEClient.ipV6.dhcp.server.rapidCommit

       Possibilities:
               disabled   (0)
               enabled   (1)"
   ::= {er1645v2Lan2MCPppOEEntry 705318912}

er1645v2Lan2MCPppOEIpV6DhcpServerTimersInfoRefresh OBJECT-TYPE
   SYNTAX      TimeTicks
   MAX-ACCESS  read-write
   STATUS      current
   DESCRIPTION
      "Path: ethernet2.editConf.pppoEClient.ipV6.dhcp.server.timers.infoRefresh

       Time in centi-second."
   ::= {er1645v2Lan2MCPppOEEntry 705319940}

er1645v2Lan2MCPppOEIpV6DhcpRelayMode OBJECT-TYPE
   SYNTAX      INTEGER
               {
               disabled (0),
               enabled (1)
               }
   MAX-ACCESS  read-write
   STATUS      current
   DESCRIPTION
      "Path: ethernet2.editConf.pppoEClient.ipV6.dhcp.relay.mode

       Possibilities:
               disabled   (0)
               enabled   (1)"
   ::= {er1645v2Lan2MCPppOEEntry 705323040}

er1645v2Lan2MCPppOEIpV6SendRedirect OBJECT-TYPE
   SYNTAX      INTEGER
               {
               disabled (0),
               enabled (1)
               }
   MAX-ACCESS  read-write
   STATUS      current
   DESCRIPTION
      "Path: ethernet2.editConf.pppoEClient.ipV6.sendRedirect

       Possibilities:
               disabled   (0)
               enabled   (1)"
   ::= {er1645v2Lan2MCPppOEEntry 705101824}

er1645v2Lan2MCPppOEIpV6LinkMtu OBJECT-TYPE
   SYNTAX      Integer32
   MAX-ACCESS  read-write
   STATUS      current
   DESCRIPTION
      "Path: ethernet2.editConf.pppoEClient.ipV6.linkMtu"
   ::= {er1645v2Lan2MCPppOEEntry 705167360}

er1645v2Lan2MCPppOEIpV6InterfaceId OBJECT-TYPE
   SYNTAX      OCTET STRING
   MAX-ACCESS  read-write
   STATUS      current
   DESCRIPTION
      "Path: ethernet2.editConf.pppoEClient.ipV6.interfaceId"
   ::= {er1645v2Lan2MCPppOEEntry 705232896}

er1645v2Lan2MCPppOEIpV6MF OBJECT-TYPE
   SYNTAX      Integer32
   MAX-ACCESS  read-write
   STATUS      current
   DESCRIPTION
      "Path: ethernet2.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2Lan2MCPppOEEntry 705757184}

er1645v2Lan2MCPppOEIpV6IcmpMessagesNoRoute OBJECT-TYPE
   SYNTAX      INTEGER
               {
               disabled (0),
               enabled (1)
               }
   MAX-ACCESS  read-write
   STATUS      current
   DESCRIPTION
      "Path: ethernet2.editConf.pppoEClient.ipV6.icmpMessages.noRoute

       Possibilities:
               disabled   (0)
               enabled   (1)"
   ::= {er1645v2Lan2MCPppOEEntry 705822976}

er1645v2Lan2MCPppOEIpV6IcmpMessagesBeyondScope OBJECT-TYPE
   SYNTAX      INTEGER
               {
               disabled (0),
               enabled (1)
               }
   MAX-ACCESS  read-write
   STATUS      current
   DESCRIPTION
      "Path: ethernet2.editConf.pppoEClient.ipV6.icmpMessages.beyondScope

       Possibilities:
               disabled   (0)
               enabled   (1)"
   ::= {er1645v2Lan2MCPppOEEntry 705823488}

er1645v2Lan2MCPppOEIpV6IcmpMessagesAddressUnreachable OBJECT-TYPE
   SYNTAX      INTEGER
               {
               disabled (0),
               enabled (1)
               }
   MAX-ACCESS  read-write
   STATUS      current
   DESCRIPTION
      "Path: ethernet2.editConf.pppoEClient.ipV6.icmpMessages.addressUnreachable

       Possibilities:
               disabled   (0)
               enabled   (1)"
   ::= {er1645v2Lan2MCPppOEEntry 705823744}

er1645v2Lan2MCPppOEIpV6IcmpMessagesPortUnreachable OBJECT-TYPE
   SYNTAX      INTEGER
               {
               disabled (0),
               enabled (1)
               }
   MAX-ACCESS  read-write
   STATUS      current
   DESCRIPTION
      "Path: ethernet2.editConf.pppoEClient.ipV6.icmpMessages.portUnreachable

       Possibilities:
               disabled   (0)
               enabled   (1)"
   ::= {er1645v2Lan2MCPppOEEntry 705824000}

er1645v2Lan2MCPppOEIpV6IcmpMessagesPacketTooBig OBJECT-TYPE
   SYNTAX      INTEGER
               {
               disabled (0),
               enabled (1)
               }
   MAX-ACCESS  read-write
   STATUS      current
   DESCRIPTION
      "Path: ethernet2.editConf.pppoEClient.ipV6.icmpMessages.packetTooBig

       Possibilities:
               disabled   (0)
               enabled   (1)"
   ::= {er1645v2Lan2MCPppOEEntry 705825280}

er1645v2Lan2MCPppOEIpV6IcmpMessagesHopLimitExceeded OBJECT-TYPE
   SYNTAX      INTEGER
               {
               disabled (0),
               enabled (1)
               }
   MAX-ACCESS  read-write
   STATUS      current
   DESCRIPTION
      "Path: ethernet2.editConf.pppoEClient.ipV6.icmpMessages.hopLimitExceeded

       Possibilities:
               disabled   (0)
               enabled   (1)"
   ::= {er1645v2Lan2MCPppOEEntry 705827840}

er1645v2Lan2MCPppOEIpV6IcmpMessagesFragTimeExceeded OBJECT-TYPE
   SYNTAX      INTEGER
               {
               disabled (0),
               enabled (1)
               }
   MAX-ACCESS  read-write
   STATUS      current
   DESCRIPTION
      "Path: ethernet2.editConf.pppoEClient.ipV6.icmpMessages.fragTimeExceeded

       Possibilities:
               disabled   (0)
               enabled   (1)"
   ::= {er1645v2Lan2MCPppOEEntry 705828096}

er1645v2Lan2MCPppOEIpV6IcmpMessagesHeaderFieldErr OBJECT-TYPE
   SYNTAX      INTEGER
               {
               disabled (0),
               enabled (1)
               }
   MAX-ACCESS  read-write
   STATUS      current
   DESCRIPTION
      "Path: ethernet2.editConf.pppoEClient.ipV6.icmpMessages.headerFieldErr

       Possibilities:
               disabled   (0)
               enabled   (1)"
   ::= {er1645v2Lan2MCPppOEEntry 705830400}

er1645v2Lan2MCPppOEIpV6IcmpMessagesOptionUnrecognized OBJECT-TYPE
   SYNTAX      INTEGER
               {
               disabled (0),
               enabled (1)
               }
   MAX-ACCESS  read-write
   STATUS      current
   DESCRIPTION
      "Path: ethernet2.editConf.pppoEClient.ipV6.icmpMessages.optionUnrecognized

       Possibilities:
               disabled   (0)
               enabled   (1)"
   ::= {er1645v2Lan2MCPppOEEntry 705830912}

er1645v2Lan2MCPppOEIpV6IcmpMessagesRedirect OBJECT-TYPE
   SYNTAX      INTEGER
               {
               disabled (0),
               enabled (1)
               }
   MAX-ACCESS  read-write
   STATUS      current
   DESCRIPTION
      "Path: ethernet2.editConf.pppoEClient.ipV6.icmpMessages.redirect

       Possibilities:
               disabled   (0)
               enabled   (1)"
   ::= {er1645v2Lan2MCPppOEEntry 705832960}

er1645v2Lan2MCPppOEPppLnkMOperation OBJECT-TYPE
   SYNTAX      INTEGER
               {
               disabled (0),
               enabled (1)
               }
   MAX-ACCESS  read-write
   STATUS      current
   DESCRIPTION
      "Path: ethernet2.editConf.pppoEClient.ppp.linkMonitoring.operation

       Possibilities:
               disabled   (0)
               enabled   (1)"
   ::= {er1645v2Lan2MCPppOEEntry 251724032}

er1645v2Lan2MCPppOEPppLnkMInterval OBJECT-TYPE
   SYNTAX      TimeTicks
   MAX-ACCESS  read-write
   STATUS      current
   DESCRIPTION
      "Path: ethernet2.editConf.pppoEClient.ppp.linkMonitoring.interval

       Time in centi-second."
   ::= {er1645v2Lan2MCPppOEEntry 251724288}

er1645v2Lan2MCPppOEPppLnkMRepTimeOut OBJECT-TYPE
   SYNTAX      TimeTicks
   MAX-ACCESS  read-write
   STATUS      current
   DESCRIPTION
      "Path: ethernet2.editConf.pppoEClient.ppp.linkMonitoring.replyTimeOut

       Time in centi-second."
   ::= {er1645v2Lan2MCPppOEEntry 251724544}

er1645v2Lan2MCPppOEPppLnkMFailsPrmt OBJECT-TYPE
   SYNTAX      Integer32
   MAX-ACCESS  read-write
   STATUS      current
   DESCRIPTION
      "Path: ethernet2.editConf.pppoEClient.ppp.linkMonitoring.failsPermitted"
   ::= {er1645v2Lan2MCPppOEEntry 251724800}

er1645v2Lan2MCPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: ethernet2.editConf.pppoEClient.ppp.authentication

       Possibilities:
               disabled   (0)
               chap   (1)
               pap   (2)
               chapOrPap   (3)
               msChap   (4)
               msChapV2   (5)"
   ::= {er1645v2Lan2MCPppOEEntry 251789312}

er1645v2Lan2MCPppOEPppAuthenPeriod OBJECT-TYPE
   SYNTAX      TimeTicks
   MAX-ACCESS  read-write
   STATUS      current
   DESCRIPTION
      "Path: ethernet2.editConf.pppoEClient.ppp.authenPeriod

       Time in centi-second."
   ::= {er1645v2Lan2MCPppOEEntry 251854848}

er1645v2Lan2MCPppOEPppSessionName OBJECT-TYPE
   SYNTAX      DisplayString
   MAX-ACCESS  read-write
   STATUS      current
   DESCRIPTION
      "Path: ethernet2.editConf.pppoEClient.ppp.sessionName"
   ::= {er1645v2Lan2MCPppOEEntry 251985920}

er1645v2Lan2MCPppOEPppSessionSecret OBJECT-TYPE
   SYNTAX      DisplayString
   MAX-ACCESS  read-write
   STATUS      current
   DESCRIPTION
      "Path: ethernet2.editConf.pppoEClient.ppp.sessionSecret"
   ::= {er1645v2Lan2MCPppOEEntry 252051456}

er1645v2Lan2MCPppOEPppEncModeSessionSecret OBJECT-TYPE
   SYNTAX      INTEGER
               {
               none (1),
               encrypt (2),
               encType1 (3),
               invalid (128)
               }
   MAX-ACCESS  read-write
   STATUS      current
   DESCRIPTION
      "Path: ethernet2.editConf.pppoEClient.ppp.encModeSessionSecret

       Possibilities:
               none   (1)
               encrypt   (2)
               encType1   (3)
               invalid   (128)"
   ::= {er1645v2Lan2MCPppOEEntry 252182528}

er1645v2Lan2MCPppOEPppEncSessionSecret OBJECT-TYPE
   SYNTAX      DisplayString
   MAX-ACCESS  read-write
   STATUS      current
   DESCRIPTION
      "Path: ethernet2.editConf.pppoEClient.ppp.encSessionSecret"
   ::= {er1645v2Lan2MCPppOEEntry 252248064}

er1645v2Lan2MCPppOEPppServiceName OBJECT-TYPE
   SYNTAX      DisplayString
   MAX-ACCESS  read-write
   STATUS      current
   DESCRIPTION
      "Path: ethernet2.editConf.pppoEClient.ppp.serviceName"
   ::= {er1645v2Lan2MCPppOEEntry 252116992}

er1645v2Lan2MCPppOEIpH OBJECT-TYPE
   SYNTAX      SEQUENCE OF Er1645v2Lan2MCPppOEIpHEntry
   MAX-ACCESS  not-accessible
   STATUS      current
   DESCRIPTION
      ""
   ::= {er1645v2Lan2MCPppOE 51314688}

er1645v2Lan2MCPppOEIpHEntry OBJECT-TYPE
   SYNTAX      Er1645v2Lan2MCPppOEIpHEntry
   MAX-ACCESS  not-accessible
   STATUS      current
   DESCRIPTION
      ""
   INDEX      { er1645v2Lan2MCPppOETableIx,
                er1645v2Lan2MCPppOEIpHTableIx }
   ::= {er1645v2Lan2MCPppOEIpH 1}

Er1645v2Lan2MCPppOEIpHEntry ::=
   SEQUENCE
      {
      er1645v2Lan2MCPppOEIpHActions
         VariableLengthTableActions,
      er1645v2Lan2MCPppOEIpHTableIx
         TableIndex,
      er1645v2Lan2MCPppOEIpHAddress
         IpAddress,
      er1645v2Lan2MCPppOEIpHDhcpRelayOptionSubscriberId
         DisplayString
      }

er1645v2Lan2MCPppOEIpHActions OBJECT-TYPE
   SYNTAX      VariableLengthTableActions
   MAX-ACCESS  read-write
   STATUS      current
   DESCRIPTION
      "By way of this field, some manipulations
       on this table may be performed."
   ::= {er1645v2Lan2MCPppOEIpHEntry 2}

er1645v2Lan2MCPppOEIpHTableIx OBJECT-TYPE
   SYNTAX      TableIndex
   MAX-ACCESS  not-accessible
   STATUS      current
   DESCRIPTION
      ""
   ::= {er1645v2Lan2MCPppOEIpHEntry 11}

er1645v2Lan2MCPppOEIpHAddress OBJECT-TYPE
   SYNTAX      IpAddress
   MAX-ACCESS  read-write
   STATUS      current
   DESCRIPTION
      "Path: ethernet2.editConf.pppoEClient.ip.helpers.address"
   ::= {er1645v2Lan2MCPppOEIpHEntry 16777216}

er1645v2Lan2MCPppOEIpHDhcpRelayOptionSubscriberId OBJECT-TYPE
   SYNTAX      DisplayString
   MAX-ACCESS  read-write
   STATUS      current
   DESCRIPTION
      "Path: ethernet2.editConf.pppoEClient.ip.helpers.dhcpRelayOption.subscriberId"
   ::= {er1645v2Lan2MCPppOEIpHEntry 33947648}

er1645v2Lan2MCPppOEIpV6Addresses OBJECT-TYPE
   SYNTAX      SEQUENCE OF Er1645v2Lan2MCPppOEIpV6AddressesEntry
   MAX-ACCESS  not-accessible
   STATUS      current
   DESCRIPTION
      ""
   ::= {er1645v2Lan2MCPppOE 704839680}

er1645v2Lan2MCPppOEIpV6AddressesEntry OBJECT-TYPE
   SYNTAX      Er1645v2Lan2MCPppOEIpV6AddressesEntry
   MAX-ACCESS  not-accessible
   STATUS      current
   DESCRIPTION
      ""
   INDEX      { er1645v2Lan2MCPppOETableIx,
                er1645v2Lan2MCPppOEIpV6AddressesTableIx }
   ::= {er1645v2Lan2MCPppOEIpV6Addresses 1}

Er1645v2Lan2MCPppOEIpV6AddressesEntry ::=
   SEQUENCE
      {
      er1645v2Lan2MCPppOEIpV6AddressesActions
         VariableLengthTableActions,
      er1645v2Lan2MCPppOEIpV6AddressesTableIx
         TableIndex,
      er1645v2Lan2MCPppOEIpV6AddressesType
         INTEGER,
      er1645v2Lan2MCPppOEIpV6AddressesAddress
         Ipv6Address,
      er1645v2Lan2MCPppOEIpV6AddressesPrefixLength
         Integer32,
      er1645v2Lan2MCPppOEIpV6AddressesGeneralPrefix
         DisplayString,
      er1645v2Lan2MCPppOEIpV6AddressesRaSend
         INTEGER,
      er1645v2Lan2MCPppOEIpV6AddressesRaOnLinkFlag
         INTEGER,
      er1645v2Lan2MCPppOEIpV6AddressesRaAutoFlag
         INTEGER,
      er1645v2Lan2MCPppOEIpV6AddressesRaValidLifeTime
         TimeTicks,
      er1645v2Lan2MCPppOEIpV6AddressesRaValidLTMode
         INTEGER,
      er1645v2Lan2MCPppOEIpV6AddressesRaPrefLifeTime
         TimeTicks,
      er1645v2Lan2MCPppOEIpV6AddressesRaPrefLTMode
         INTEGER
      }

er1645v2Lan2MCPppOEIpV6AddressesActions OBJECT-TYPE
   SYNTAX      VariableLengthTableActions
   MAX-ACCESS  read-write
   STATUS      current
   DESCRIPTION
      "By way of this field, some manipulations
       on this table may be performed."
   ::= {er1645v2Lan2MCPppOEIpV6AddressesEntry 2}

er1645v2Lan2MCPppOEIpV6AddressesTableIx OBJECT-TYPE
   SYNTAX      TableIndex
   MAX-ACCESS  not-accessible
   STATUS      current
   DESCRIPTION
      ""
   ::= {er1645v2Lan2MCPppOEIpV6AddressesEntry 11}

er1645v2Lan2MCPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: ethernet2.editConf.pppoEClient.ipV6.addresses.type

       Possibilities:
               unicast   (0)
               eui64   (1)
               anycast   (2)
               linkLocal   (3)
               generalPrefix   (4)"
   ::= {er1645v2Lan2MCPppOEIpV6AddressesEntry 50331648}

er1645v2Lan2MCPppOEIpV6AddressesAddress OBJECT-TYPE
   SYNTAX      Ipv6Address
   MAX-ACCESS  read-write
   STATUS      current
   DESCRIPTION
      "Path: ethernet2.editConf.pppoEClient.ipV6.addresses.address

       ipv6 address"
   ::= {er1645v2Lan2MCPppOEIpV6AddressesEntry 16777216}

er1645v2Lan2MCPppOEIpV6AddressesPrefixLength OBJECT-TYPE
   SYNTAX      Integer32
   MAX-ACCESS  read-write
   STATUS      current
   DESCRIPTION
      "Path: ethernet2.editConf.pppoEClient.ipV6.addresses.prefixLength"
   ::= {er1645v2Lan2MCPppOEIpV6AddressesEntry 33554432}

er1645v2Lan2MCPppOEIpV6AddressesGeneralPrefix OBJECT-TYPE
   SYNTAX      DisplayString
   MAX-ACCESS  read-write
   STATUS      current
   DESCRIPTION
      "Path: ethernet2.editConf.pppoEClient.ipV6.addresses.generalPrefix"
   ::= {er1645v2Lan2MCPppOEIpV6AddressesEntry 83886080}

er1645v2Lan2MCPppOEIpV6AddressesRaSend OBJECT-TYPE
   SYNTAX      INTEGER
               {
               disabled (0),
               enabled (1)
               }
   MAX-ACCESS  read-write
   STATUS      current
   DESCRIPTION
      "Path: ethernet2.editConf.pppoEClient.ipV6.addresses.ra.send

       Possibilities:
               disabled   (0)
               enabled   (1)"
   ::= {er1645v2Lan2MCPppOEIpV6AddressesEntry 67174400}

er1645v2Lan2MCPppOEIpV6AddressesRaOnLinkFlag OBJECT-TYPE
   SYNTAX      INTEGER
               {
               disabled (0),
               enabled (1)
               }
   MAX-ACCESS  read-write
   STATUS      current
   DESCRIPTION
      "Path: ethernet2.editConf.pppoEClient.ipV6.addresses.ra.onLinkFlag

       Possibilities:
               disabled   (0)
               enabled   (1)"
   ::= {er1645v2Lan2MCPppOEIpV6AddressesEntry 67371008}

er1645v2Lan2MCPppOEIpV6AddressesRaAutoFlag OBJECT-TYPE
   SYNTAX      INTEGER
               {
               disabled (0),
               enabled (1)
               }
   MAX-ACCESS  read-write
   STATUS      current
   DESCRIPTION
      "Path: ethernet2.editConf.pppoEClient.ipV6.addresses.ra.autonomousFlag

       Possibilities:
               disabled   (0)
               enabled   (1)"
   ::= {er1645v2Lan2MCPppOEIpV6AddressesEntry 67567616}

er1645v2Lan2MCPppOEIpV6AddressesRaValidLifeTime OBJECT-TYPE
   SYNTAX      TimeTicks
   MAX-ACCESS  read-write
   STATUS      current
   DESCRIPTION
      "Path: ethernet2.editConf.pppoEClient.ipV6.addresses.ra.validLifeTime

       Time in centi-second."
   ::= {er1645v2Lan2MCPppOEIpV6AddressesEntry 67239936}

er1645v2Lan2MCPppOEIpV6AddressesRaValidLTMode OBJECT-TYPE
   SYNTAX      INTEGER
               {
               fixed (0),
               infinite (2)
               }
   MAX-ACCESS  read-write
   STATUS      current
   DESCRIPTION
      "Path: ethernet2.editConf.pppoEClient.ipV6.addresses.ra.validLifeTimeMode

       Possibilities:
               fixed   (0)
               infinite   (2)"
   ::= {er1645v2Lan2MCPppOEIpV6AddressesEntry 67305472}

er1645v2Lan2MCPppOEIpV6AddressesRaPrefLifeTime OBJECT-TYPE
   SYNTAX      TimeTicks
   MAX-ACCESS  read-write
   STATUS      current
   DESCRIPTION
      "Path: ethernet2.editConf.pppoEClient.ipV6.addresses.ra.prefLifeTime

       Time in centi-second."
   ::= {er1645v2Lan2MCPppOEIpV6AddressesEntry 67436544}

er1645v2Lan2MCPppOEIpV6AddressesRaPrefLTMode OBJECT-TYPE
   SYNTAX      INTEGER
               {
               fixed (0),
               infinite (2)
               }
   MAX-ACCESS  read-write
   STATUS      current
   DESCRIPTION
      "Path: ethernet2.editConf.pppoEClient.ipV6.addresses.ra.prefLifeTimeMode

       Possibilities:
               fixed   (0)
               infinite   (2)"
   ::= {er1645v2Lan2MCPppOEIpV6AddressesEntry 67502080}

er1645v2Lan2MCPppOEIpV6RaDnsOptionsRdnssServers OBJECT-TYPE
   SYNTAX      SEQUENCE OF Er1645v2Lan2MCPppOEIpV6RaDnsOptionsRdnssServersEntry
   MAX-ACCESS  not-accessible
   STATUS      current
   DESCRIPTION
      ""
   ::= {er1645v2Lan2MCPppOE 705039144}

er1645v2Lan2MCPppOEIpV6RaDnsOptionsRdnssServersEntry OBJECT-TYPE
   SYNTAX      Er1645v2Lan2MCPppOEIpV6RaDnsOptionsRdnssServersEntry
   MAX-ACCESS  not-accessible
   STATUS      current
   DESCRIPTION
      ""
   INDEX      { er1645v2Lan2MCPppOETableIx,
                er1645v2Lan2MCPppOEIpV6RaDnsOptionsRdnssServersTableIx }
   ::= {er1645v2Lan2MCPppOEIpV6RaDnsOptionsRdnssServers 1}

Er1645v2Lan2MCPppOEIpV6RaDnsOptionsRdnssServersEntry ::=
   SEQUENCE
      {
      er1645v2Lan2MCPppOEIpV6RaDnsOptionsRdnssServersActions
         VariableLengthTableActions,
      er1645v2Lan2MCPppOEIpV6RaDnsOptionsRdnssServersTableIx
         TableIndex,
      er1645v2Lan2MCPppOEIpV6RaDnsOptionsRdnssServersAddress
         Ipv6Address
      }

er1645v2Lan2MCPppOEIpV6RaDnsOptionsRdnssServersActions OBJECT-TYPE
   SYNTAX      VariableLengthTableActions
   MAX-ACCESS  read-write
   STATUS      current
   DESCRIPTION
      "By way of this field, some manipulations
       on this table may be performed."
   ::= {er1645v2Lan2MCPppOEIpV6RaDnsOptionsRdnssServersEntry 2}

er1645v2Lan2MCPppOEIpV6RaDnsOptionsRdnssServersTableIx OBJECT-TYPE
   SYNTAX      TableIndex
   MAX-ACCESS  not-accessible
   STATUS      current
   DESCRIPTION
      ""
   ::= {er1645v2Lan2MCPppOEIpV6RaDnsOptionsRdnssServersEntry 11}

er1645v2Lan2MCPppOEIpV6RaDnsOptionsRdnssServersAddress OBJECT-TYPE
   SYNTAX      Ipv6Address
   MAX-ACCESS  read-write
   STATUS      current
   DESCRIPTION
      "Path: ethernet2.editConf.pppoEClient.ipV6.ra.dnsOptions.rdnss.servers.address

       ipv6 address"
   ::= {er1645v2Lan2MCPppOEIpV6RaDnsOptionsRdnssServersEntry 16777216}

er1645v2Lan2MCPppOEIpV6RaDnsOptionsDnsslDomains OBJECT-TYPE
   SYNTAX      SEQUENCE OF Er1645v2Lan2MCPppOEIpV6RaDnsOptionsDnsslDomainsEntry
   MAX-ACCESS  not-accessible
   STATUS      current
   DESCRIPTION
      ""
   ::= {er1645v2Lan2MCPppOE 705039176}

er1645v2Lan2MCPppOEIpV6RaDnsOptionsDnsslDomainsEntry OBJECT-TYPE
   SYNTAX      Er1645v2Lan2MCPppOEIpV6RaDnsOptionsDnsslDomainsEntry
   MAX-ACCESS  not-accessible
   STATUS      current
   DESCRIPTION
      ""
   INDEX      { er1645v2Lan2MCPppOETableIx,
                er1645v2Lan2MCPppOEIpV6RaDnsOptionsDnsslDomainsTableIx }
   ::= {er1645v2Lan2MCPppOEIpV6RaDnsOptionsDnsslDomains 1}

Er1645v2Lan2MCPppOEIpV6RaDnsOptionsDnsslDomainsEntry ::=
   SEQUENCE
      {
      er1645v2Lan2MCPppOEIpV6RaDnsOptionsDnsslDomainsActions
         VariableLengthTableActions,
      er1645v2Lan2MCPppOEIpV6RaDnsOptionsDnsslDomainsTableIx
         TableIndex,
      er1645v2Lan2MCPppOEIpV6RaDnsOptionsDnsslDomainsName
         DisplayString
      }

er1645v2Lan2MCPppOEIpV6RaDnsOptionsDnsslDomainsActions OBJECT-TYPE
   SYNTAX      VariableLengthTableActions
   MAX-ACCESS  read-write
   STATUS      current
   DESCRIPTION
      "By way of this field, some manipulations
       on this table may be performed."
   ::= {er1645v2Lan2MCPppOEIpV6RaDnsOptionsDnsslDomainsEntry 2}

er1645v2Lan2MCPppOEIpV6RaDnsOptionsDnsslDomainsTableIx OBJECT-TYPE
   SYNTAX      TableIndex
   MAX-ACCESS  not-accessible
   STATUS      current
   DESCRIPTION
      ""
   ::= {er1645v2Lan2MCPppOEIpV6RaDnsOptionsDnsslDomainsEntry 11}

er1645v2Lan2MCPppOEIpV6RaDnsOptionsDnsslDomainsName OBJECT-TYPE
   SYNTAX      DisplayString
   MAX-ACCESS  read-write
   STATUS      current
   DESCRIPTION
      "Path: ethernet2.editConf.pppoEClient.ipV6.ra.dnsOptions.dnssl.domains.name"
   ::= {er1645v2Lan2MCPppOEIpV6RaDnsOptionsDnsslDomainsEntry 16777216}

er1645v2Lan2MCPppOEIpV6DhcpClientUserClassOpt OBJECT-TYPE
   SYNTAX      SEQUENCE OF Er1645v2Lan2MCPppOEIpV6DhcpClientUserClassOptEntry
   MAX-ACCESS  not-accessible
   STATUS      current
   DESCRIPTION
      ""
   ::= {er1645v2Lan2MCPppOE 705312768}

er1645v2Lan2MCPppOEIpV6DhcpClientUserClassOptEntry OBJECT-TYPE
   SYNTAX      Er1645v2Lan2MCPppOEIpV6DhcpClientUserClassOptEntry
   MAX-ACCESS  not-accessible
   STATUS      current
   DESCRIPTION
      ""
   INDEX      { er1645v2Lan2MCPppOETableIx,
                er1645v2Lan2MCPppOEIpV6DhcpClientUserClassOptTableIx }
   ::= {er1645v2Lan2MCPppOEIpV6DhcpClientUserClassOpt 1}

Er1645v2Lan2MCPppOEIpV6DhcpClientUserClassOptEntry ::=
   SEQUENCE
      {
      er1645v2Lan2MCPppOEIpV6DhcpClientUserClassOptActions
         VariableLengthTableActions,
      er1645v2Lan2MCPppOEIpV6DhcpClientUserClassOptTableIx
         TableIndex,
      er1645v2Lan2MCPppOEIpV6DhcpClientUserClassOptValueAscii
         DisplayString,
      er1645v2Lan2MCPppOEIpV6DhcpClientUserClassOptValueDecimal
         Integer32,
      er1645v2Lan2MCPppOEIpV6DhcpClientUserClassOptValueHexData
         OCTET STRING
      }

er1645v2Lan2MCPppOEIpV6DhcpClientUserClassOptActions OBJECT-TYPE
   SYNTAX      VariableLengthTableActions
   MAX-ACCESS  read-write
   STATUS      current
   DESCRIPTION
      "By way of this field, some manipulations
       on this table may be performed."
   ::= {er1645v2Lan2MCPppOEIpV6DhcpClientUserClassOptEntry 2}

er1645v2Lan2MCPppOEIpV6DhcpClientUserClassOptTableIx OBJECT-TYPE
   SYNTAX      TableIndex
   MAX-ACCESS  not-accessible
   STATUS      current
   DESCRIPTION
      ""
   ::= {er1645v2Lan2MCPppOEIpV6DhcpClientUserClassOptEntry 11}

er1645v2Lan2MCPppOEIpV6DhcpClientUserClassOptValueAscii OBJECT-TYPE
   SYNTAX      DisplayString
   MAX-ACCESS  read-write
   STATUS      current
   DESCRIPTION
      "Path: ethernet2.editConf.pppoEClient.ipV6.dhcp.client.userClassOpt.value.ascii"
   ::= {er1645v2Lan2MCPppOEIpV6DhcpClientUserClassOptEntry 16842752}

er1645v2Lan2MCPppOEIpV6DhcpClientUserClassOptValueDecimal OBJECT-TYPE
   SYNTAX      Integer32
   MAX-ACCESS  read-write
   STATUS      current
   DESCRIPTION
      "Path: ethernet2.editConf.pppoEClient.ipV6.dhcp.client.userClassOpt.value.decimal"
   ::= {er1645v2Lan2MCPppOEIpV6DhcpClientUserClassOptEntry 16908288}

er1645v2Lan2MCPppOEIpV6DhcpClientUserClassOptValueHexData OBJECT-TYPE
   SYNTAX      OCTET STRING
   MAX-ACCESS  read-write
   STATUS      current
   DESCRIPTION
      "Path: ethernet2.editConf.pppoEClient.ipV6.dhcp.client.userClassOpt.value.hexData"
   ::= {er1645v2Lan2MCPppOEIpV6DhcpClientUserClassOptEntry 16973824}

er1645v2Lan2MCPppOEIpV6DhcpClientVendorCl OBJECT-TYPE
   SYNTAX      SEQUENCE OF Er1645v2Lan2MCPppOEIpV6DhcpClientVendorClEntry
   MAX-ACCESS  not-accessible
   STATUS      current
   DESCRIPTION
      ""
   ::= {er1645v2Lan2MCPppOE 705313792}

er1645v2Lan2MCPppOEIpV6DhcpClientVendorClEntry OBJECT-TYPE
   SYNTAX      Er1645v2Lan2MCPppOEIpV6DhcpClientVendorClEntry
   MAX-ACCESS  not-accessible
   STATUS      current
   DESCRIPTION
      ""
   INDEX      { er1645v2Lan2MCPppOETableIx,
                er1645v2Lan2MCPppOEIpV6DhcpClientVendorClTableIx }
   ::= {er1645v2Lan2MCPppOEIpV6DhcpClientVendorCl 1}

Er1645v2Lan2MCPppOEIpV6DhcpClientVendorClEntry ::=
   SEQUENCE
      {
      er1645v2Lan2MCPppOEIpV6DhcpClientVendorClActions
         VariableLengthTableActions,
      er1645v2Lan2MCPppOEIpV6DhcpClientVendorClTableIx
         TableIndex,
      er1645v2Lan2MCPppOEIpV6DhcpClientVendorClValueAscii
         DisplayString,
      er1645v2Lan2MCPppOEIpV6DhcpClientVendorClValueDecimal
         Integer32,
      er1645v2Lan2MCPppOEIpV6DhcpClientVendorClValueHexData
         OCTET STRING
      }

er1645v2Lan2MCPppOEIpV6DhcpClientVendorClActions OBJECT-TYPE
   SYNTAX      VariableLengthTableActions
   MAX-ACCESS  read-write
   STATUS      current
   DESCRIPTION
      "By way of this field, some manipulations
       on this table may be performed."
   ::= {er1645v2Lan2MCPppOEIpV6DhcpClientVendorClEntry 2}

er1645v2Lan2MCPppOEIpV6DhcpClientVendorClTableIx OBJECT-TYPE
   SYNTAX      TableIndex
   MAX-ACCESS  not-accessible
   STATUS      current
   DESCRIPTION
      ""
   ::= {er1645v2Lan2MCPppOEIpV6DhcpClientVendorClEntry 11}

er1645v2Lan2MCPppOEIpV6DhcpClientVendorClValueAscii OBJECT-TYPE
   SYNTAX      DisplayString
   MAX-ACCESS  read-write
   STATUS      current
   DESCRIPTION
      "Path: ethernet2.editConf.pppoEClient.ipV6.dhcp.client.vendorClassOpt.value.ascii"
   ::= {er1645v2Lan2MCPppOEIpV6DhcpClientVendorClEntry 16842752}

er1645v2Lan2MCPppOEIpV6DhcpClientVendorClValueDecimal OBJECT-TYPE
   SYNTAX      Integer32
   MAX-ACCESS  read-write
   STATUS      current
   DESCRIPTION
      "Path: ethernet2.editConf.pppoEClient.ipV6.dhcp.client.vendorClassOpt.value.decimal"
   ::= {er1645v2Lan2MCPppOEIpV6DhcpClientVendorClEntry 16908288}

er1645v2Lan2MCPppOEIpV6DhcpClientVendorClValueHexData OBJECT-TYPE
   SYNTAX      OCTET STRING
   MAX-ACCESS  read-write
   STATUS      current
   DESCRIPTION
      "Path: ethernet2.editConf.pppoEClient.ipV6.dhcp.client.vendorClassOpt.value.hexData"
   ::= {er1645v2Lan2MCPppOEIpV6DhcpClientVendorClEntry 16973824}

er1645v2Lan2MCPppOEIpV6DhcpRelayDestinations OBJECT-TYPE
   SYNTAX      SEQUENCE OF Er1645v2Lan2MCPppOEIpV6DhcpRelayDestinationsEntry
   MAX-ACCESS  not-accessible
   STATUS      current
   DESCRIPTION
      ""
   ::= {er1645v2Lan2MCPppOE 705323072}

er1645v2Lan2MCPppOEIpV6DhcpRelayDestinationsEntry OBJECT-TYPE
   SYNTAX      Er1645v2Lan2MCPppOEIpV6DhcpRelayDestinationsEntry
   MAX-ACCESS  not-accessible
   STATUS      current
   DESCRIPTION
      ""
   INDEX      { er1645v2Lan2MCPppOETableIx,
                er1645v2Lan2MCPppOEIpV6DhcpRelayDestinationsTableIx }
   ::= {er1645v2Lan2MCPppOEIpV6DhcpRelayDestinations 1}

Er1645v2Lan2MCPppOEIpV6DhcpRelayDestinationsEntry ::=
   SEQUENCE
      {
      er1645v2Lan2MCPppOEIpV6DhcpRelayDestinationsActions
         VariableLengthTableActions,
      er1645v2Lan2MCPppOEIpV6DhcpRelayDestinationsTableIx
         TableIndex,
      er1645v2Lan2MCPppOEIpV6DhcpRelayDestinationsAddress
         Ipv6Address,
      er1645v2Lan2MCPppOEIpV6DhcpRelayDestinationsInterface
         DisplayString
      }

er1645v2Lan2MCPppOEIpV6DhcpRelayDestinationsActions OBJECT-TYPE
   SYNTAX      VariableLengthTableActions
   MAX-ACCESS  read-write
   STATUS      current
   DESCRIPTION
      "By way of this field, some manipulations
       on this table may be performed."
   ::= {er1645v2Lan2MCPppOEIpV6DhcpRelayDestinationsEntry 2}

er1645v2Lan2MCPppOEIpV6DhcpRelayDestinationsTableIx OBJECT-TYPE
   SYNTAX      TableIndex
   MAX-ACCESS  not-accessible
   STATUS      current
   DESCRIPTION
      ""
   ::= {er1645v2Lan2MCPppOEIpV6DhcpRelayDestinationsEntry 11}

er1645v2Lan2MCPppOEIpV6DhcpRelayDestinationsAddress OBJECT-TYPE
   SYNTAX      Ipv6Address
   MAX-ACCESS  read-write
   STATUS      current
   DESCRIPTION
      "Path: ethernet2.editConf.pppoEClient.ipV6.dhcp.relay.destinations.address

       ipv6 address"
   ::= {er1645v2Lan2MCPppOEIpV6DhcpRelayDestinationsEntry 16777216}

er1645v2Lan2MCPppOEIpV6DhcpRelayDestinationsInterface OBJECT-TYPE
   SYNTAX      DisplayString
   MAX-ACCESS  read-write
   STATUS      current
   DESCRIPTION
      "Path: ethernet2.editConf.pppoEClient.ipV6.dhcp.relay.destinations.interface"
   ::= {er1645v2Lan2MCPppOEIpV6DhcpRelayDestinationsEntry 33554432}


er1645v2Lan2MCPppoEServer OBJECT-TYPE
   SYNTAX      DisplayString
   MAX-ACCESS  read-write
   STATUS      current
   DESCRIPTION
      "Path: ethernet2.editConf.pppoEServer
       Info: ppp server name on interface"
   ::= {er1645v2Lan2MC 37}


er1645v2Lan2MCMediaType OBJECT-TYPE
   SYNTAX      INTEGER
               {
               utp (1),
               sfp (2),
               auto (3)
               }
   MAX-ACCESS  read-write
   STATUS      current
   DESCRIPTION
      "Path: ethernet2.editConf.mediaType

       Possibilities:
               utp   (1)
               sfp   (2)
               auto   (3)"
   ::= {er1645v2Lan2MC 38}


er1645v2Lan2MCInboundHwPriority OBJECT IDENTIFIER ::= {er1645v2Lan2MC 231}

er1645v2Lan2MCInboundHwPrioritySSC OBJECT IDENTIFIER ::= {er1645v2Lan2MCInboundHwPriority 1}

er1645v2Lan2MCInboundHwPriorityEntry OBJECT IDENTIFIER ::= {er1645v2Lan2MCInboundHwPrioritySSC 1}

er1645v2Lan2MCInboundHwPriorityNone OBJECT-TYPE
   SYNTAX      OCTET STRING
   MAX-ACCESS  read-write
   STATUS      current
   DESCRIPTION
      "Path: ethernet2.editConf.inboundHwPriority.none"
   ::= {er1645v2Lan2MCInboundHwPriorityEntry 16777216}

er1645v2Lan2MCInboundHwPriorityMapCosToQueueP0 OBJECT-TYPE
   SYNTAX      INTEGER
               {
               queue1 (1),
               queue2 (2)
               }
   MAX-ACCESS  read-write
   STATUS      current
   DESCRIPTION
      "Path: ethernet2.editConf.inboundHwPriority.mapCosToQueue.p0

       Possibilities:
               queue1   (1)
               queue2   (2)"
   ::= {er1645v2Lan2MCInboundHwPriorityEntry 33619968}

er1645v2Lan2MCInboundHwPriorityMapCosToQueueP1 OBJECT-TYPE
   SYNTAX      INTEGER
               {
               queue1 (1),
               queue2 (2)
               }
   MAX-ACCESS  read-write
   STATUS      current
   DESCRIPTION
      "Path: ethernet2.editConf.inboundHwPriority.mapCosToQueue.p1

       Possibilities:
               queue1   (1)
               queue2   (2)"
   ::= {er1645v2Lan2MCInboundHwPriorityEntry 33685504}

er1645v2Lan2MCInboundHwPriorityMapCosToQueueP2 OBJECT-TYPE
   SYNTAX      INTEGER
               {
               queue1 (1),
               queue2 (2)
               }
   MAX-ACCESS  read-write
   STATUS      current
   DESCRIPTION
      "Path: ethernet2.editConf.inboundHwPriority.mapCosToQueue.p2

       Possibilities:
               queue1   (1)
               queue2   (2)"
   ::= {er1645v2Lan2MCInboundHwPriorityEntry 33751040}

er1645v2Lan2MCInboundHwPriorityMapCosToQueueP3 OBJECT-TYPE
   SYNTAX      INTEGER
               {
               queue1 (1),
               queue2 (2)
               }
   MAX-ACCESS  read-write
   STATUS      current
   DESCRIPTION
      "Path: ethernet2.editConf.inboundHwPriority.mapCosToQueue.p3

       Possibilities:
               queue1   (1)
               queue2   (2)"
   ::= {er1645v2Lan2MCInboundHwPriorityEntry 33816576}

er1645v2Lan2MCInboundHwPriorityMapCosToQueueP4 OBJECT-TYPE
   SYNTAX      INTEGER
               {
               queue1 (1),
               queue2 (2)
               }
   MAX-ACCESS  read-write
   STATUS      current
   DESCRIPTION
      "Path: ethernet2.editConf.inboundHwPriority.mapCosToQueue.p4

       Possibilities:
               queue1   (1)
               queue2   (2)"
   ::= {er1645v2Lan2MCInboundHwPriorityEntry 33882112}

er1645v2Lan2MCInboundHwPriorityMapCosToQueueP5 OBJECT-TYPE
   SYNTAX      INTEGER
               {
               queue1 (1),
               queue2 (2)
               }
   MAX-ACCESS  read-write
   STATUS      current
   DESCRIPTION
      "Path: ethernet2.editConf.inboundHwPriority.mapCosToQueue.p5

       Possibilities:
               queue1   (1)
               queue2   (2)"
   ::= {er1645v2Lan2MCInboundHwPriorityEntry 33947648}

er1645v2Lan2MCInboundHwPriorityMapCosToQueueP6 OBJECT-TYPE
   SYNTAX      INTEGER
               {
               queue1 (1),
               queue2 (2)
               }
   MAX-ACCESS  read-write
   STATUS      current
   DESCRIPTION
      "Path: ethernet2.editConf.inboundHwPriority.mapCosToQueue.p6

       Possibilities:
               queue1   (1)
               queue2   (2)"
   ::= {er1645v2Lan2MCInboundHwPriorityEntry 34013184}

er1645v2Lan2MCInboundHwPriorityMapCosToQueueP7 OBJECT-TYPE
   SYNTAX      INTEGER
               {
               queue1 (1),
               queue2 (2)
               }
   MAX-ACCESS  read-write
   STATUS      current
   DESCRIPTION
      "Path: ethernet2.editConf.inboundHwPriority.mapCosToQueue.p7

       Possibilities:
               queue1   (1)
               queue2   (2)"
   ::= {er1645v2Lan2MCInboundHwPriorityEntry 34078720}

er1645v2Lan2MCInboundHwPriorityMapDscpToQueue OBJECT-TYPE
   SYNTAX      SEQUENCE OF Er1645v2Lan2MCInboundHwPriorityMapDscpToQueueEntry
   MAX-ACCESS  not-accessible
   STATUS      current
   DESCRIPTION
      ""
   ::= {er1645v2Lan2MCInboundHwPriority 50331648}

er1645v2Lan2MCInboundHwPriorityMapDscpToQueueEntry OBJECT-TYPE
   SYNTAX      Er1645v2Lan2MCInboundHwPriorityMapDscpToQueueEntry
   MAX-ACCESS  not-accessible
   STATUS      current
   DESCRIPTION
      ""
   INDEX      { er1645v2Lan2MCInboundHwPriorityMapDscpToQueueTableIx }
   ::= {er1645v2Lan2MCInboundHwPriorityMapDscpToQueue 1}

Er1645v2Lan2MCInboundHwPriorityMapDscpToQueueEntry ::=
   SEQUENCE
      {
      er1645v2Lan2MCInboundHwPriorityMapDscpToQueueActions
         VariableLengthTableActions,
      er1645v2Lan2MCInboundHwPriorityMapDscpToQueueTableIx
         TableIndex,
      er1645v2Lan2MCInboundHwPriorityMapDscpToQueueStartDscp
         INTEGER,
      er1645v2Lan2MCInboundHwPriorityMapDscpToQueueEndDscp
         INTEGER,
      er1645v2Lan2MCInboundHwPriorityMapDscpToQueueQueue
         INTEGER
      }

er1645v2Lan2MCInboundHwPriorityMapDscpToQueueActions OBJECT-TYPE
   SYNTAX      VariableLengthTableActions
   MAX-ACCESS  read-write
   STATUS      current
   DESCRIPTION
      "By way of this field, some manipulations
       on this table may be performed."
   ::= {er1645v2Lan2MCInboundHwPriorityMapDscpToQueueEntry 2}

er1645v2Lan2MCInboundHwPriorityMapDscpToQueueTableIx OBJECT-TYPE
   SYNTAX      TableIndex
   MAX-ACCESS  not-accessible
   STATUS      current
   DESCRIPTION
      ""
   ::= {er1645v2Lan2MCInboundHwPriorityMapDscpToQueueEntry 11}

er1645v2Lan2MCInboundHwPriorityMapDscpToQueueStartDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet2.editConf.inboundHwPriority.mapDscpToQueue.startDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan2MCInboundHwPriorityMapDscpToQueueEntry 16777216}

er1645v2Lan2MCInboundHwPriorityMapDscpToQueueEndDscp OBJECT-TYPE
   SYNTAX      INTEGER
               {
               cs1 (8),
               cs2 (16),
               cs3 (24),
               cs4 (32),
               cs5 (40),
               cs6 (48),
               cs7 (56),
               af11 (10),
               af12 (12),
               af13 (14),
               af21 (18),
               af22 (20),
               af23 (22),
               af31 (26),
               af32 (28),
               af33 (30),
               af41 (34),
               af42 (36),
               af43 (38),
               ef (46)
               }
   MAX-ACCESS  read-write
   STATUS      current
   DESCRIPTION
      "Path: ethernet2.editConf.inboundHwPriority.mapDscpToQueue.endDscp

       Possibilities:
               cs1   (8)
               cs2   (16)
               cs3   (24)
               cs4   (32)
               cs5   (40)
               cs6   (48)
               cs7   (56)
               af11   (10)
               af12   (12)
               af13   (14)
               af21   (18)
               af22   (20)
               af23   (22)
               af31   (26)
               af32   (28)
               af33   (30)
               af41   (34)
               af42   (36)
               af43   (38)
               ef   (46)"
   ::= {er1645v2Lan2MCInboundHwPriorityMapDscpToQueueEntry 33554432}

er1645v2Lan2MCInboundHwPriorityMapDscpToQueueQueue OBJECT-TYPE
   SYNTAX      INTEGER
               {
               queue1 (1),
               queue2 (2)
               }
   MAX-ACCESS  read-write
   STATUS      current
   DESCRIPTION
      "Path: ethernet2.editConf.inboundHwPriority.mapDscpToQueue.queue

       Possibilities:
               queue1   (1)
               queue2   (2)"
   ::= {er1645v2Lan2MCInboundHwPriorityMapDscpToQueueEntry 50331648}


er1645v2Lan2MCName OBJECT-TYPE
   SYNTAX      DisplayString
   MAX-ACCESS  read-write
   STATUS      current
   DESCRIPTION
      "Path: ethernet2.editConf.name
       Info: config interface name"
   ::= {er1645v2Lan2MC 2}


er1645v2Lan2MCInterfaceSide OBJECT-TYPE
   SYNTAX      INTEGER
               {
               user (1),
               network (2)
               }
   MAX-ACCESS  read-write
   STATUS      current
   DESCRIPTION
      "Path: ethernet2.editConf.interfaceSide

       Possibilities:
               user   (1)
               network   (2)"
   ::= {er1645v2Lan2MC 232}



sr1645v2Lan2MC OBJECT IDENTIFIER ::= {r1645v2Lan2MC 14}


sr1645v2Lan2MCDescr OBJECT-TYPE
   SYNTAX      DisplayString
   MAX-ACCESS  read-only
   STATUS      current
   DESCRIPTION
      "Path: ethernet2.status.ifDescr
       Info: ifDescr"
   ::= {sr1645v2Lan2MC 101}


sr1645v2Lan2MCType OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: ethernet2.status.ifType
       Info: ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2Lan2MC 102}


sr1645v2Lan2MCMtu OBJECT-TYPE
   SYNTAX      Integer32
   MAX-ACCESS  read-only
   STATUS      current
   DESCRIPTION
      "Path: ethernet2.status.ifMtu
       Info: ifMtu"
   ::= {sr1645v2Lan2MC 103}


sr1645v2Lan2MCOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.ifOperStatus
       Info: ifOperStatus

       Possibilities:
               up   (1)
               down   (2)
               testing   (3)
               unknown   (4)
               dormant   (5)
               notPresent   (6)
               lowerLayerDown   (7)"
   ::= {sr1645v2Lan2MC 107}


sr1645v2Lan2MCLastChange OBJECT-TYPE
   SYNTAX      TimeTicks
   MAX-ACCESS  read-only
   STATUS      current
   DESCRIPTION
      "Path: ethernet2.status.ifLastChange
       Info: ifLastChange

       Time in centi-second."
   ::= {sr1645v2Lan2MC 108}


sr1645v2Lan2MCLastChangeD OBJECT-TYPE
   SYNTAX      DisplayString
   MAX-ACCESS  read-only
   STATUS      current
   DESCRIPTION
      "Path: ethernet2.status.ifLastChangeDate
       Info: ifLastChangeDate"
   ::= {sr1645v2Lan2MC 183}


sr1645v2Lan2MCSpeed OBJECT-TYPE
   SYNTAX      Gauge32
   MAX-ACCESS  read-only
   STATUS      current
   DESCRIPTION
      "Path: ethernet2.status.ifSpeed
       Info: ifSpeed

       32 bit unsigned gauge value."
   ::= {sr1645v2Lan2MC 104}


sr1645v2Lan2MCSnmpIndex OBJECT-TYPE
   SYNTAX      Integer32
   MAX-ACCESS  read-only
   STATUS      current
   DESCRIPTION
      "Path: ethernet2.status.snmpIndex
       Info: SNMP index assigned to this object"
   ::= {sr1645v2Lan2MC 269}


sr1645v2Lan2MCIp OBJECT IDENTIFIER ::= {sr1645v2Lan2MC 16}

sr1645v2Lan2MCIpSSC OBJECT IDENTIFIER ::= {sr1645v2Lan2MCIp 1}

sr1645v2Lan2MCIpEntry OBJECT IDENTIFIER ::= {sr1645v2Lan2MCIpSSC 1}

sr1645v2Lan2MCIpStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.ip.status

       Possibilities:
               up   (1)
               down   (2)
               testing   (3)
               unknown   (4)
               dormant   (5)
               notPresent   (6)
               lowerLayerDown   (7)"
   ::= {sr1645v2Lan2MCIpEntry 1795162112}

sr1645v2Lan2MCIpAddress OBJECT-TYPE
   SYNTAX      IpAddress
   MAX-ACCESS  read-only
   STATUS      current
   DESCRIPTION
      "Path: ethernet2.status.ip.address"
   ::= {sr1645v2Lan2MCIpEntry 2030043136}

sr1645v2Lan2MCIpNetMask OBJECT-TYPE
   SYNTAX      IpAddress
   MAX-ACCESS  read-only
   STATUS      current
   DESCRIPTION
      "Path: ethernet2.status.ip.netMask"
   ::= {sr1645v2Lan2MCIpEntry 2063597568}

sr1645v2Lan2MCIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet2.status.ip.dhcp.status

       Possibilities:
               none   (0)
               selecting   (1)
               requesting   (2)
               rebinding   (3)
               bound   (4)
               renewing   (5)
               rebooting   (6)
               initreboot   (7)"
   ::= {sr1645v2Lan2MCIpEntry 402718720}

sr1645v2Lan2MCIpDhcpLeaseTime OBJECT-TYPE
   SYNTAX      TimeTicks
   MAX-ACCESS  read-only
   STATUS      current
   DESCRIPTION
      "Path: ethernet2.status.ip.dhcp.leaseTime

       Time in centi-second."
   ::= {sr1645v2Lan2MCIpEntry 402784256}

sr1645v2Lan2MCIpSecondaryIp OBJECT-TYPE
   SYNTAX      SEQUENCE OF Sr1645v2Lan2MCIpSecondaryIpEntry
   MAX-ACCESS  not-accessible
   STATUS      current
   DESCRIPTION
      ""
   ::= {sr1645v2Lan2MCIp 385875968}

sr1645v2Lan2MCIpSecondaryIpEntry OBJECT-TYPE
   SYNTAX      Sr1645v2Lan2MCIpSecondaryIpEntry
   MAX-ACCESS  not-accessible
   STATUS      current
   DESCRIPTION
      ""
   INDEX      { sr1645v2Lan2MCIpSecondaryIpTableIx }
   ::= {sr1645v2Lan2MCIpSecondaryIp 1}

Sr1645v2Lan2MCIpSecondaryIpEntry ::=
   SEQUENCE
      {
      sr1645v2Lan2MCIpSecondaryIpTableIx
         TableIndex,
      sr1645v2Lan2MCIpSecondaryIpAddress
         IpAddress,
      sr1645v2Lan2MCIpSecondaryIpNetMask
         IpAddress
      }

sr1645v2Lan2MCIpSecondaryIpTableIx OBJECT-TYPE
   SYNTAX      TableIndex
   MAX-ACCESS  not-accessible
   STATUS      current
   DESCRIPTION
      ""
   ::= {sr1645v2Lan2MCIpSecondaryIpEntry 11}

sr1645v2Lan2MCIpSecondaryIpAddress OBJECT-TYPE
   SYNTAX      IpAddress
   MAX-ACCESS  read-only
   STATUS      current
   DESCRIPTION
      "Path: ethernet2.status.ip.secondaryIp.address"
   ::= {sr1645v2Lan2MCIpSecondaryIpEntry 2030043136}

sr1645v2Lan2MCIpSecondaryIpNetMask OBJECT-TYPE
   SYNTAX      IpAddress
   MAX-ACCESS  read-only
   STATUS      current
   DESCRIPTION
      "Path: ethernet2.status.ip.secondaryIp.netMask"
   ::= {sr1645v2Lan2MCIpSecondaryIpEntry 2063597568}


sr1645v2Lan2MCArpCache OBJECT IDENTIFIER ::= {sr1645v2Lan2MC 11}

sr1645v2Lan2MCArpCacheSSCTable OBJECT-TYPE
   SYNTAX      SEQUENCE OF Sr1645v2Lan2MCArpCacheEntry
   MAX-ACCESS  not-accessible
   STATUS      current
   DESCRIPTION
      "arp cache of ethernet interface"
   ::= {sr1645v2Lan2MCArpCache 1}

sr1645v2Lan2MCArpCacheEntry OBJECT-TYPE
   SYNTAX      Sr1645v2Lan2MCArpCacheEntry
   MAX-ACCESS  not-accessible
   STATUS      current
   DESCRIPTION
      ""
   INDEX      { sr1645v2Lan2MCArpCacheTableIx }
   ::= {sr1645v2Lan2MCArpCacheSSCTable 1}

Sr1645v2Lan2MCArpCacheEntry ::=
   SEQUENCE
      {
      sr1645v2Lan2MCArpCacheTableIx
         TableIndex,
      sr1645v2Lan2MCArpCacheMacAddress
         OCTET STRING,
      sr1645v2Lan2MCArpCacheIpAddress
         IpAddress,
      sr1645v2Lan2MCArpCacheType
         INTEGER,
      sr1645v2Lan2MCArpCacheTimeOut
         TimeTicks
      }

sr1645v2Lan2MCArpCacheTableIx OBJECT-TYPE
   SYNTAX      TableIndex
   MAX-ACCESS  not-accessible
   STATUS      current
   DESCRIPTION
      ""
   ::= {sr1645v2Lan2MCArpCacheEntry 11}

sr1645v2Lan2MCArpCacheMacAddress OBJECT-TYPE
   SYNTAX      OCTET STRING
   MAX-ACCESS  read-only
   STATUS      current
   DESCRIPTION
      "Path: ethernet2.status.arpCache.macAddress

       MAC address."
   ::= {sr1645v2Lan2MCArpCacheEntry 16777216}

sr1645v2Lan2MCArpCacheIpAddress OBJECT-TYPE
   SYNTAX      IpAddress
   MAX-ACCESS  read-only
   STATUS      current
   DESCRIPTION
      "Path: ethernet2.status.arpCache.ipAddress"
   ::= {sr1645v2Lan2MCArpCacheEntry 33554432}

sr1645v2Lan2MCArpCacheType OBJECT-TYPE
   SYNTAX      INTEGER
               {
               static (0),
               dynamic (1)
               }
   MAX-ACCESS  read-only
   STATUS      current
   DESCRIPTION
      "Path: ethernet2.status.arpCache.type

       Possibilities:
               static   (0)
               dynamic   (1)"
   ::= {sr1645v2Lan2MCArpCacheEntry 50331648}

sr1645v2Lan2MCArpCacheTimeOut OBJECT-TYPE
   SYNTAX      TimeTicks
   MAX-ACCESS  read-only
   STATUS      current
   DESCRIPTION
      "Path: ethernet2.status.arpCache.timeOut

       Time in centi-second."
   ::= {sr1645v2Lan2MCArpCacheEntry 67108864}


sr1645v2Lan2MCBrS OBJECT IDENTIFIER ::= {sr1645v2Lan2MC 28}

sr1645v2Lan2MCBrSSSC OBJECT IDENTIFIER ::= {sr1645v2Lan2MCBrS 1}

sr1645v2Lan2MCBrSEntry OBJECT IDENTIFIER ::= {sr1645v2Lan2MCBrSSSC 1}

sr1645v2Lan2MCBrSStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet2.status.bridging.status

       Possibilities:
               disabled   (0)
               discarding   (1)
               learning   (2)
               forwarding   (3)
               backupBlockedIntfDown   (256)
               backupBlockedIntfUp   (259)
               shutdown   (255)"
   ::= {sr1645v2Lan2MCBrSEntry 16777216}

sr1645v2Lan2MCBrSStPortRole OBJECT-TYPE
   SYNTAX      INTEGER
               {
               none (0),
               root (1),
               designated (2),
               alternate (3),
               backup (4),
               disabled (5),
               master (6)
               }
   MAX-ACCESS  read-only
   STATUS      current
   DESCRIPTION
      "Path: ethernet2.status.bridging.spanningTree.portRole

       Possibilities:
               none   (0)
               root   (1)
               designated   (2)
               alternate   (3)
               backup   (4)
               disabled   (5)
               master   (6)"
   ::= {sr1645v2Lan2MCBrSEntry 33619968}

sr1645v2Lan2MCBrSStPortId OBJECT-TYPE
   SYNTAX      Integer32
   MAX-ACCESS  read-only
   STATUS      current
   DESCRIPTION
      "Path: ethernet2.status.bridging.spanningTree.portId"
   ::= {sr1645v2Lan2MCBrSEntry 33685504}

sr1645v2Lan2MCBrSStPpCostExtPathCost OBJECT-TYPE
   SYNTAX      Integer32
   MAX-ACCESS  read-only
   STATUS      current
   DESCRIPTION
      "Path: ethernet2.status.bridging.spanningTree.portPathCosts.extPathCost"
   ::= {sr1645v2Lan2MCBrSEntry 33751296}

sr1645v2Lan2MCBrSStPpCostIntPathCost OBJECT-TYPE
   SYNTAX      Integer32
   MAX-ACCESS  read-only
   STATUS      current
   DESCRIPTION
      "Path: ethernet2.status.bridging.spanningTree.portPathCosts.intPathCost"
   ::= {sr1645v2Lan2MCBrSEntry 33751552}

sr1645v2Lan2MCBrSStExtRpCost OBJECT-TYPE
   SYNTAX      Integer32
   MAX-ACCESS  read-only
   STATUS      current
   DESCRIPTION
      "Path: ethernet2.status.bridging.spanningTree.extRootPathCost"
   ::= {sr1645v2Lan2MCBrSEntry 33816576}

sr1645v2Lan2MCBrSStIntRpCost OBJECT-TYPE
   SYNTAX      Integer32
   MAX-ACCESS  read-only
   STATUS      current
   DESCRIPTION
      "Path: ethernet2.status.bridging.spanningTree.intRootPathCost"
   ::= {sr1645v2Lan2MCBrSEntry 33882112}

sr1645v2Lan2MCBrSStDesBrIdPriority OBJECT-TYPE
   SYNTAX      Integer32
   MAX-ACCESS  read-only
   STATUS      current
   DESCRIPTION
      "Path: ethernet2.status.bridging.spanningTree.designatedBridgeId.priority"
   ::= {sr1645v2Lan2MCBrSEntry 33947904}

sr1645v2Lan2MCBrSStDesBrIdMacAddress OBJECT-TYPE
   SYNTAX      OCTET STRING
   MAX-ACCESS  read-only
   STATUS      current
   DESCRIPTION
      "Path: ethernet2.status.bridging.spanningTree.designatedBridgeId.macAddress

       MAC address."
   ::= {sr1645v2Lan2MCBrSEntry 33948160}

sr1645v2Lan2MCBrSStDesPrtId OBJECT-TYPE
   SYNTAX      Integer32
   MAX-ACCESS  read-only
   STATUS      current
   DESCRIPTION
      "Path: ethernet2.status.bridging.spanningTree.designatedPortId"
   ::= {sr1645v2Lan2MCBrSEntry 34013184}

sr1645v2Lan2MCBrSStDesInt OBJECT-TYPE
   SYNTAX      INTEGER
               {
               no (0),
               yes (1)
               }
   MAX-ACCESS  read-only
   STATUS      current
   DESCRIPTION
      "Path: ethernet2.status.bridging.spanningTree.designatedOrInternal

       Possibilities:
               no   (0)
               yes   (1)"
   ::= {sr1645v2Lan2MCBrSEntry 34078720}

sr1645v2Lan2MCBrSStEdgeDetection OBJECT-TYPE
   SYNTAX      INTEGER
               {
               none (0),
               edge (1),
               notEdge (2)
               }
   MAX-ACCESS  read-only
   STATUS      current
   DESCRIPTION
      "Path: ethernet2.status.bridging.spanningTree.edgeDetection

       Possibilities:
               none   (0)
               edge   (1)
               notEdge   (2)"
   ::= {sr1645v2Lan2MCBrSEntry 34144256}


sr1645v2Lan2MCMacAddress OBJECT-TYPE
   SYNTAX      OCTET STRING
   MAX-ACCESS  read-only
   STATUS      current
   DESCRIPTION
      "Path: ethernet2.status.macAddress
       Info: ifPhysAddress

       MAC address."
   ::= {sr1645v2Lan2MC 105}


sr1645v2Lan2MCIpAdEntBcastAddr OBJECT-TYPE
   SYNTAX      Integer32
   MAX-ACCESS  read-only
   STATUS      current
   DESCRIPTION
      "Path: ethernet2.status.ipAdEntBcastAddr
       Info: ipAdEntBcastAddr"
   ::= {sr1645v2Lan2MC 124}


sr1645v2Lan2MCIpAdEntReasmMaxSize OBJECT-TYPE
   SYNTAX      Integer32
   MAX-ACCESS  read-only
   STATUS      current
   DESCRIPTION
      "Path: ethernet2.status.ipAdEntReasmMaxSize
       Info: ipAdEntReasmMaxSize"
   ::= {sr1645v2Lan2MC 125}


sr1645v2Lan2MCAdapter OBJECT IDENTIFIER ::= {sr1645v2Lan2MC 145}

sr1645v2Lan2MCAdapterSSC OBJECT IDENTIFIER ::= {sr1645v2Lan2MCAdapter 1}

sr1645v2Lan2MCAdapterEntry OBJECT IDENTIFIER ::= {sr1645v2Lan2MCAdapterSSC 1}

sr1645v2Lan2MCAdapterSpeed OBJECT-TYPE
   SYNTAX      INTEGER
               {
               s10 (0),
               s100 (1),
               s1000 (2),
               s200 (3)
               }
   MAX-ACCESS  read-only
   STATUS      current
   DESCRIPTION
      "Path: ethernet2.status.adapter.speed

       Possibilities:
               10   (0)
               100   (1)
               1000   (2)
               200   (3)"
   ::= {sr1645v2Lan2MCAdapterEntry 16777216}

sr1645v2Lan2MCAdapterDuplex OBJECT-TYPE
   SYNTAX      INTEGER
               {
               halfDuplex (0),
               fullDuplex (1)
               }
   MAX-ACCESS  read-only
   STATUS      current
   DESCRIPTION
      "Path: ethernet2.status.adapter.duplex

       Possibilities:
               halfDuplex   (0)
               fullDuplex   (1)"
   ::= {sr1645v2Lan2MCAdapterEntry 33554432}


sr1645v2Lan2MCOam OBJECT IDENTIFIER ::= {sr1645v2Lan2MC 901}

sr1645v2Lan2MCOamSSC OBJECT IDENTIFIER ::= {sr1645v2Lan2MCOam 1}

sr1645v2Lan2MCOamEntry OBJECT IDENTIFIER ::= {sr1645v2Lan2MCOamSSC 1}

sr1645v2Lan2MCOamDiscovery OBJECT-TYPE
   SYNTAX      INTEGER
               {
               fault (0),
               sendLocal (1),
               passiveWait (2),
               sendLocalRemote (3),
               sendLocalRemoteOk (4),
               sendAny (5)
               }
   MAX-ACCESS  read-only
   STATUS      current
   DESCRIPTION
      "Path: ethernet2.status.oam.discovery

       Possibilities:
               fault   (0)
               sendLocal   (1)
               passiveWait   (2)
               sendLocalRemote   (3)
               sendLocalRemoteOk   (4)
               sendAny   (5)"
   ::= {sr1645v2Lan2MCOamEntry 16777216}

sr1645v2Lan2MCOamLoopback OBJECT-TYPE
   SYNTAX      INTEGER
               {
               idle (0),
               waiting (1),
               localRunning (2),
               remoteRunning (3)
               }
   MAX-ACCESS  read-only
   STATUS      current
   DESCRIPTION
      "Path: ethernet2.status.oam.loopback

       Possibilities:
               idle   (0)
               waiting   (1)
               localRunning   (2)
               remoteRunning   (3)"
   ::= {sr1645v2Lan2MCOamEntry 33554432}

sr1645v2Lan2MCOamLocalInfoVersion OBJECT-TYPE
   SYNTAX      Integer32
   MAX-ACCESS  read-only
   STATUS      current
   DESCRIPTION
      "Path: ethernet2.status.oam.localInfo.version"
   ::= {sr1645v2Lan2MCOamEntry 50397184}

sr1645v2Lan2MCOamLocalInfoRevision OBJECT-TYPE
   SYNTAX      Integer32
   MAX-ACCESS  read-only
   STATUS      current
   DESCRIPTION
      "Path: ethernet2.status.oam.localInfo.revision"
   ::= {sr1645v2Lan2MCOamEntry 50462720}

sr1645v2Lan2MCOamLocalInfoStateMuxAction OBJECT-TYPE
   SYNTAX      INTEGER
               {
               forwarding (0),
               discarding (1)
               }
   MAX-ACCESS  read-only
   STATUS      current
   DESCRIPTION
      "Path: ethernet2.status.oam.localInfo.state.muxAction

       Possibilities:
               forwarding   (0)
               discarding   (1)"
   ::= {sr1645v2Lan2MCOamEntry 50528512}

sr1645v2Lan2MCOamLocalInfoStateParserAction OBJECT-TYPE
   SYNTAX      INTEGER
               {
               forwarding (0),
               loopback (1),
               discarding (2),
               reserved (3)
               }
   MAX-ACCESS  read-only
   STATUS      current
   DESCRIPTION
      "Path: ethernet2.status.oam.localInfo.state.parserAction

       Possibilities:
               forwarding   (0)
               loopback   (1)
               discarding   (2)
               reserved   (3)"
   ::= {sr1645v2Lan2MCOamEntry 50528768}

sr1645v2Lan2MCOamLocalInfoOui OBJECT-TYPE
   SYNTAX      OCTET STRING
   MAX-ACCESS  read-only
   STATUS      current
   DESCRIPTION
      "Path: ethernet2.status.oam.localInfo.oui"
   ::= {sr1645v2Lan2MCOamEntry 50593792}

sr1645v2Lan2MCOamLocalInfoVendorInfo OBJECT-TYPE
   SYNTAX      OCTET STRING
   MAX-ACCESS  read-only
   STATUS      current
   DESCRIPTION
      "Path: ethernet2.status.oam.localInfo.vendorInfo"
   ::= {sr1645v2Lan2MCOamEntry 50659328}

sr1645v2Lan2MCOamLocalInfoVarRetrieval OBJECT-TYPE
   SYNTAX      INTEGER
               {
               notSupported (0),
               supported (1)
               }
   MAX-ACCESS  read-only
   STATUS      current
   DESCRIPTION
      "Path: ethernet2.status.oam.localInfo.varRetrieval

       Possibilities:
               notSupported   (0)
               supported   (1)"
   ::= {sr1645v2Lan2MCOamEntry 50724864}

sr1645v2Lan2MCOamLocalInfoLinkEvents OBJECT-TYPE
   SYNTAX      INTEGER
               {
               ignored (0),
               interpreted (1)
               }
   MAX-ACCESS  read-only
   STATUS      current
   DESCRIPTION
      "Path: ethernet2.status.oam.localInfo.linkEvents

       Possibilities:
               ignored   (0)
               interpreted   (1)"
   ::= {sr1645v2Lan2MCOamEntry 50790400}

sr1645v2Lan2MCOamLocalInfoLoopback OBJECT-TYPE
   SYNTAX      INTEGER
               {
               notSupported (0),
               supported (1)
               }
   MAX-ACCESS  read-only
   STATUS      current
   DESCRIPTION
      "Path: ethernet2.status.oam.localInfo.loopback

       Possibilities:
               notSupported   (0)
               supported   (1)"
   ::= {sr1645v2Lan2MCOamEntry 50855936}

sr1645v2Lan2MCOamLocalInfoUnidirectional OBJECT-TYPE
   SYNTAX      INTEGER
               {
               notSupported (0),
               supported (1)
               }
   MAX-ACCESS  read-only
   STATUS      current
   DESCRIPTION
      "Path: ethernet2.status.oam.localInfo.unidirectional

       Possibilities:
               notSupported   (0)
               supported   (1)"
   ::= {sr1645v2Lan2MCOamEntry 50921472}

sr1645v2Lan2MCOamLocalInfoMode OBJECT-TYPE
   SYNTAX      INTEGER
               {
               passive (0),
               active (1)
               }
   MAX-ACCESS  read-only
   STATUS      current
   DESCRIPTION
      "Path: ethernet2.status.oam.localInfo.mode

       Possibilities:
               passive   (0)
               active   (1)"
   ::= {sr1645v2Lan2MCOamEntry 50987008}

sr1645v2Lan2MCOamLocalInfoMaxPduSize OBJECT-TYPE
   SYNTAX      Integer32
   MAX-ACCESS  read-only
   STATUS      current
   DESCRIPTION
      "Path: ethernet2.status.oam.localInfo.maxPduSize"
   ::= {sr1645v2Lan2MCOamEntry 51052544}

sr1645v2Lan2MCOamRemoteInfoVersion OBJECT-TYPE
   SYNTAX      Integer32
   MAX-ACCESS  read-only
   STATUS      current
   DESCRIPTION
      "Path: ethernet2.status.oam.remoteInfo.version"
   ::= {sr1645v2Lan2MCOamEntry 67174400}

sr1645v2Lan2MCOamRemoteInfoRevision OBJECT-TYPE
   SYNTAX      Integer32
   MAX-ACCESS  read-only
   STATUS      current
   DESCRIPTION
      "Path: ethernet2.status.oam.remoteInfo.revision"
   ::= {sr1645v2Lan2MCOamEntry 67239936}

sr1645v2Lan2MCOamRemoteInfoStateMuxAction OBJECT-TYPE
   SYNTAX      INTEGER
               {
               forwarding (0),
               discarding (1)
               }
   MAX-ACCESS  read-only
   STATUS      current
   DESCRIPTION
      "Path: ethernet2.status.oam.remoteInfo.state.muxAction

       Possibilities:
               forwarding   (0)
               discarding   (1)"
   ::= {sr1645v2Lan2MCOamEntry 67305728}

sr1645v2Lan2MCOamRemoteInfoStateParserAction OBJECT-TYPE
   SYNTAX      INTEGER
               {
               forwarding (0),
               loopback (1),
               discarding (2),
               reserved (3)
               }
   MAX-ACCESS  read-only
   STATUS      current
   DESCRIPTION
      "Path: ethernet2.status.oam.remoteInfo.state.parserAction

       Possibilities:
               forwarding   (0)
               loopback   (1)
               discarding   (2)
               reserved   (3)"
   ::= {sr1645v2Lan2MCOamEntry 67305984}

sr1645v2Lan2MCOamRemoteInfoOui OBJECT-TYPE
   SYNTAX      OCTET STRING
   MAX-ACCESS  read-only
   STATUS      current
   DESCRIPTION
      "Path: ethernet2.status.oam.remoteInfo.oui"
   ::= {sr1645v2Lan2MCOamEntry 67371008}

sr1645v2Lan2MCOamRemoteInfoVendorInfo OBJECT-TYPE
   SYNTAX      OCTET STRING
   MAX-ACCESS  read-only
   STATUS      current
   DESCRIPTION
      "Path: ethernet2.status.oam.remoteInfo.vendorInfo"
   ::= {sr1645v2Lan2MCOamEntry 67436544}

sr1645v2Lan2MCOamRemoteInfoVarRetrieval OBJECT-TYPE
   SYNTAX      INTEGER
               {
               notSupported (0),
               supported (1)
               }
   MAX-ACCESS  read-only
   STATUS      current
   DESCRIPTION
      "Path: ethernet2.status.oam.remoteInfo.varRetrieval

       Possibilities:
               notSupported   (0)
               supported   (1)"
   ::= {sr1645v2Lan2MCOamEntry 67502080}

sr1645v2Lan2MCOamRemoteInfoLinkEvents OBJECT-TYPE
   SYNTAX      INTEGER
               {
               ignored (0),
               interpreted (1)
               }
   MAX-ACCESS  read-only
   STATUS      current
   DESCRIPTION
      "Path: ethernet2.status.oam.remoteInfo.linkEvents

       Possibilities:
               ignored   (0)
               interpreted   (1)"
   ::= {sr1645v2Lan2MCOamEntry 67567616}

sr1645v2Lan2MCOamRemoteInfoLoopback OBJECT-TYPE
   SYNTAX      INTEGER
               {
               notSupported (0),
               supported (1)
               }
   MAX-ACCESS  read-only
   STATUS      current
   DESCRIPTION
      "Path: ethernet2.status.oam.remoteInfo.loopback

       Possibilities:
               notSupported   (0)
               supported   (1)"
   ::= {sr1645v2Lan2MCOamEntry 67633152}

sr1645v2Lan2MCOamRemoteInfoUnidirectional OBJECT-TYPE
   SYNTAX      INTEGER
               {
               notSupported (0),
               supported (1)
               }
   MAX-ACCESS  read-only
   STATUS      current
   DESCRIPTION
      "Path: ethernet2.status.oam.remoteInfo.unidirectional

       Possibilities:
               notSupported   (0)
               supported   (1)"
   ::= {sr1645v2Lan2MCOamEntry 67698688}

sr1645v2Lan2MCOamRemoteInfoMode OBJECT-TYPE
   SYNTAX      INTEGER
               {
               passive (0),
               active (1)
               }
   MAX-ACCESS  read-only
   STATUS      current
   DESCRIPTION
      "Path: ethernet2.status.oam.remoteInfo.mode

       Possibilities:
               passive   (0)
               active   (1)"
   ::= {sr1645v2Lan2MCOamEntry 67764224}

sr1645v2Lan2MCOamRemoteInfoMaxPduSize OBJECT-TYPE
   SYNTAX      Integer32
   MAX-ACCESS  read-only
   STATUS      current
   DESCRIPTION
      "Path: ethernet2.status.oam.remoteInfo.maxPduSize"
   ::= {sr1645v2Lan2MCOamEntry 67829760}

sr1645v2Lan2MCOamEventsErroredSymbolWindow OBJECT-TYPE
   SYNTAX      Integer32
   UNITS       "symbols"
   MAX-ACCESS  read-only
   STATUS      current
   DESCRIPTION
      "Path: ethernet2.status.oam.events.erroredSymbol.window

       unit name = symbols"
   ::= {sr1645v2Lan2MCOamEntry 83951872}

sr1645v2Lan2MCOamEventsErroredSymbolThreshold OBJECT-TYPE
   SYNTAX      OCTET STRING
   UNITS       "symbols"
   MAX-ACCESS  read-only
   STATUS      current
   DESCRIPTION
      "Path: ethernet2.status.oam.events.erroredSymbol.threshold

       unit name = symbols"
   ::= {sr1645v2Lan2MCOamEntry 83952128}

sr1645v2Lan2MCOamEventsErroredFramePeriodWindow OBJECT-TYPE
   SYNTAX      INTEGER
               {
               default (0)
               }
   UNITS       "frames"
   MAX-ACCESS  read-only
   STATUS      current
   DESCRIPTION
      "Path: ethernet2.status.oam.events.erroredFramePeriod.window

       unit name = frames

       Possibilities:
               default   (0)"
   ::= {sr1645v2Lan2MCOamEntry 84017408}

sr1645v2Lan2MCOamEventsErroredFramePeriodThreshold OBJECT-TYPE
   SYNTAX      Integer32
   UNITS       "frames"
   MAX-ACCESS  read-only
   STATUS      current
   DESCRIPTION
      "Path: ethernet2.status.oam.events.erroredFramePeriod.threshold

       unit name = frames"
   ::= {sr1645v2Lan2MCOamEntry 84017664}

sr1645v2Lan2MCOamEventsErroredFrameWindow OBJECT-TYPE
   SYNTAX      Integer32
   UNITS       "100msec"
   MAX-ACCESS  read-only
   STATUS      current
   DESCRIPTION
      "Path: ethernet2.status.oam.events.erroredFrame.window

       unit name = 100msec"
   ::= {sr1645v2Lan2MCOamEntry 84082944}

sr1645v2Lan2MCOamEventsErroredFrameThreshold OBJECT-TYPE
   SYNTAX      Integer32
   UNITS       "frames"
   MAX-ACCESS  read-only
   STATUS      current
   DESCRIPTION
      "Path: ethernet2.status.oam.events.erroredFrame.threshold

       unit name = frames"
   ::= {sr1645v2Lan2MCOamEntry 84083200}

sr1645v2Lan2MCOamEventsErroredFrameSecondsWindow OBJECT-TYPE
   SYNTAX      Integer32
   UNITS       "100msec"
   MAX-ACCESS  read-only
   STATUS      current
   DESCRIPTION
      "Path: ethernet2.status.oam.events.erroredFrameSeconds.window

       unit name = 100msec"
   ::= {sr1645v2Lan2MCOamEntry 84148480}

sr1645v2Lan2MCOamEventsErroredFrameSecondsThreshold OBJECT-TYPE
   SYNTAX      Integer32
   UNITS       "frames"
   MAX-ACCESS  read-only
   STATUS      current
   DESCRIPTION
      "Path: ethernet2.status.oam.events.erroredFrameSeconds.threshold

       unit name = frames"
   ::= {sr1645v2Lan2MCOamEntry 84148736}


sr1645v2Lan2MCOamEventLog OBJECT IDENTIFIER ::= {sr1645v2Lan2MC 911}

sr1645v2Lan2MCOamEventLogSSCTable OBJECT-TYPE
   SYNTAX      SEQUENCE OF Sr1645v2Lan2MCOamEventLogEntry
   MAX-ACCESS  not-accessible
   STATUS      current
   DESCRIPTION
      "OAM event log"
   ::= {sr1645v2Lan2MCOamEventLog 1}

sr1645v2Lan2MCOamEventLogEntry OBJECT-TYPE
   SYNTAX      Sr1645v2Lan2MCOamEventLogEntry
   MAX-ACCESS  not-accessible
   STATUS      current
   DESCRIPTION
      ""
   INDEX      { sr1645v2Lan2MCOamEventLogTableIx }
   ::= {sr1645v2Lan2MCOamEventLogSSCTable 1}

Sr1645v2Lan2MCOamEventLogEntry ::=
   SEQUENCE
      {
      sr1645v2Lan2MCOamEventLogTableIx
         TableIndex,
      sr1645v2Lan2MCOamEventLogSysUpTime
         TimeTicks,
      sr1645v2Lan2MCOamEventLogLocation
         INTEGER,
      sr1645v2Lan2MCOamEventLogType
         INTEGER,
      sr1645v2Lan2MCOamEventLogOui
         OCTET STRING,
      sr1645v2Lan2MCOamEventLogWindow
         Counter64,
      sr1645v2Lan2MCOamEventLogThreshold
         Counter64,
      sr1645v2Lan2MCOamEventLogTotal
         Counter32,
      sr1645v2Lan2MCOamEventLogValue
         Counter64,
      sr1645v2Lan2MCOamEventLogRunningTotal
         Counter64
      }

sr1645v2Lan2MCOamEventLogTableIx OBJECT-TYPE
   SYNTAX      TableIndex
   MAX-ACCESS  not-accessible
   STATUS      current
   DESCRIPTION
      ""
   ::= {sr1645v2Lan2MCOamEventLogEntry 11}

sr1645v2Lan2MCOamEventLogSysUpTime OBJECT-TYPE
   SYNTAX      TimeTicks
   MAX-ACCESS  read-only
   STATUS      current
   DESCRIPTION
      "Path: ethernet2.status.oamEventLog.sysUpTime

       Time in centi-second."
   ::= {sr1645v2Lan2MCOamEventLogEntry 16777216}

sr1645v2Lan2MCOamEventLogLocation OBJECT-TYPE
   SYNTAX      INTEGER
               {
               local (1),
               remote (2)
               }
   MAX-ACCESS  read-only
   STATUS      current
   DESCRIPTION
      "Path: ethernet2.status.oamEventLog.location

       Possibilities:
               local   (1)
               remote   (2)"
   ::= {sr1645v2Lan2MCOamEventLogEntry 33554432}

sr1645v2Lan2MCOamEventLogType OBJECT-TYPE
   SYNTAX      INTEGER
               {
               erroredSymbols (1),
               erroredFramePeriod (2),
               erroredFrame (3),
               erroredFrameSeconds (4),
               linkFault (256),
               dyingGasp (257),
               criticalLink (258)
               }
   MAX-ACCESS  read-only
   STATUS      current
   DESCRIPTION
      "Path: ethernet2.status.oamEventLog.type

       Possibilities:
               erroredSymbols   (1)
               erroredFramePeriod   (2)
               erroredFrame   (3)
               erroredFrameSeconds   (4)
               linkFault   (256)
               dyingGasp   (257)
               criticalLink   (258)"
   ::= {sr1645v2Lan2MCOamEventLogEntry 50331648}

sr1645v2Lan2MCOamEventLogOui OBJECT-TYPE
   SYNTAX      OCTET STRING
   MAX-ACCESS  read-only
   STATUS      current
   DESCRIPTION
      "Path: ethernet2.status.oamEventLog.oui"
   ::= {sr1645v2Lan2MCOamEventLogEntry 67108864}

sr1645v2Lan2MCOamEventLogWindow OBJECT-TYPE
   SYNTAX      Counter64
   MAX-ACCESS  read-only
   STATUS      current
   DESCRIPTION
      "Path: ethernet2.status.oamEventLog.window

       64 bit unsigned wrappable counter."
   ::= {sr1645v2Lan2MCOamEventLogEntry 83886080}

sr1645v2Lan2MCOamEventLogThreshold OBJECT-TYPE
   SYNTAX      Counter64
   MAX-ACCESS  read-only
   STATUS      current
   DESCRIPTION
      "Path: ethernet2.status.oamEventLog.threshold

       64 bit unsigned wrappable counter."
   ::= {sr1645v2Lan2MCOamEventLogEntry 100663296}

sr1645v2Lan2MCOamEventLogTotal OBJECT-TYPE
   SYNTAX      Counter32
   MAX-ACCESS  read-only
   STATUS      current
   DESCRIPTION
      "Path: ethernet2.status.oamEventLog.total

       32 bit unsigned wrappable counter."
   ::= {sr1645v2Lan2MCOamEventLogEntry 117440512}

sr1645v2Lan2MCOamEventLogValue OBJECT-TYPE
   SYNTAX      Counter64
   MAX-ACCESS  read-only
   STATUS      current
   DESCRIPTION
      "Path: ethernet2.status.oamEventLog.value

       64 bit unsigned wrappable counter."
   ::= {sr1645v2Lan2MCOamEventLogEntry 134217728}

sr1645v2Lan2MCOamEventLogRunningTotal OBJECT-TYPE
   SYNTAX      Counter64
   MAX-ACCESS  read-only
   STATUS      current
   DESCRIPTION
      "Path: ethernet2.status.oamEventLog.runningTotal

       64 bit unsigned wrappable counter."
   ::= {sr1645v2Lan2MCOamEventLogEntry 150994944}


sr1645v2Lan2MCLst OBJECT IDENTIFIER ::= {sr1645v2Lan2MC 18}

sr1645v2Lan2MCLstSSC OBJECT IDENTIFIER ::= {sr1645v2Lan2MCLst 1}

sr1645v2Lan2MCLstEntry OBJECT IDENTIFIER ::= {sr1645v2Lan2MCLstSSC 1}

sr1645v2Lan2MCLstTrackedInterface OBJECT-TYPE
   SYNTAX      DisplayString
   MAX-ACCESS  read-only
   STATUS      current
   DESCRIPTION
      "Path: ethernet2.status.linkStateTracking.trackedInterface"
   ::= {sr1645v2Lan2MCLstEntry 16777216}

sr1645v2Lan2MCLstIfOperStatus OBJECT-TYPE
   SYNTAX      INTEGER
               {
               up (1),
               down (2),
               testing (3),
               unknown (4),
               dormant (5),
               notPresent (6),
               lowerLayerDown (7),
               s (255)
               }
   MAX-ACCESS  read-only
   STATUS      current
   DESCRIPTION
      "Path: ethernet2.status.linkStateTracking.ifOperStatus

       Possibilities:
               up   (1)
               down   (2)
               testing   (3)
               unknown   (4)
               dormant   (5)
               notPresent   (6)
               lowerLayerDown   (7)
                  (255)"
   ::= {sr1645v2Lan2MCLstEntry 50331648}


sr1645v2Lan2MCVlan OBJECT IDENTIFIER ::= {sr1645v2Lan2MC 34}

sr1645v2Lan2MCVlanSSCTable OBJECT-TYPE
   SYNTAX      SEQUENCE OF Sr1645v2Lan2MCVlanEntry
   MAX-ACCESS  not-accessible
   STATUS      current
   DESCRIPTION
      ""
   ::= {sr1645v2Lan2MCVlan 1}

sr1645v2Lan2MCVlanEntry OBJECT-TYPE
   SYNTAX      Sr1645v2Lan2MCVlanEntry
   MAX-ACCESS  not-accessible
   STATUS      current
   DESCRIPTION
      ""
   INDEX      { sr1645v2Lan2MCVlanTableIx }
   ::= {sr1645v2Lan2MCVlanSSCTable 1}

Sr1645v2Lan2MCVlanEntry ::=
   SEQUENCE
      {
      sr1645v2Lan2MCVlanTableIx
         TableIndex,
      sr1645v2Lan2MCVlanName
         DisplayString,
      sr1645v2Lan2MCVlanMode
         INTEGER,
      sr1645v2Lan2MCVlanIfOperStatus
         INTEGER,
      sr1645v2Lan2MCVlanIfLastChange
         TimeTicks,
      sr1645v2Lan2MCVlanIfLastChangeDate
         DisplayString,
      sr1645v2Lan2MCVlanIpAddress
         IpAddress,
      sr1645v2Lan2MCVlanIpNetMask
         IpAddress,
      sr1645v2Lan2MCVlanIpRemote
         IpAddress,
      sr1645v2Lan2MCVlanIpDhcpStatus
         INTEGER,
      sr1645v2Lan2MCVlanIpDhcpLeaseTime
         TimeTicks,
      sr1645v2Lan2MCVlanIpV6State
         INTEGER,
      sr1645v2Lan2MCVlanIpV6InterfaceId
         OCTET STRING,
      sr1645v2Lan2MCVlanIpV6LinkMtu
         Integer32,
      sr1645v2Lan2MCVlanIpV6HopLimit
         Integer32,
      sr1645v2Lan2MCVlanIpV6DhcpIaid
         Counter32,
      sr1645v2Lan2MCVlanIpV6RaRcvOption
         Integer32,
      sr1645v2Lan2MCVlanBridgingStatus
         INTEGER,
      sr1645v2Lan2MCVlanBridgingSpanningTreePortRole
         INTEGER,
      sr1645v2Lan2MCVlanBridgingSpanningTreePortId
         Integer32,
      sr1645v2Lan2MCVlanBridgingSpanningTreePpCostExtPathCost
         Integer32,
      sr1645v2Lan2MCVlanBridgingSpanningTreePpCostIntPathCost
         Integer32,
      sr1645v2Lan2MCVlanBridgingSpanningTreeExtRpCost
         Integer32,
      sr1645v2Lan2MCVlanBridgingSpanningTreeIntRpCost
         Integer32,
      sr1645v2Lan2MCVlanBridgingSpanningTreeDesBrIdPriority
         Integer32,
      sr1645v2Lan2MCVlanBridgingSpanningTreeDesBrIdMacAddress
         OCTET STRING,
      sr1645v2Lan2MCVlanBridgingSpanningTreeDesPrtId
         Integer32,
      sr1645v2Lan2MCVlanBridgingSpanningTreeDesInt
         INTEGER,
      sr1645v2Lan2MCVlanBridgingSpanningTreeEdgeDetection
         INTEGER,
      sr1645v2Lan2MCVlanVlanVid
         Integer32,
      sr1645v2Lan2MCVlanPppOEthDiscState
         INTEGER,
      sr1645v2Lan2MCVlanPppOEthPeerMac
         OCTET STRING,
      sr1645v2Lan2MCVlanPppOEthServiceName
         DisplayString,
      sr1645v2Lan2MCVlanPppLcpState
         INTEGER,
      sr1645v2Lan2MCVlanPppIpcpState
         INTEGER,
      sr1645v2Lan2MCVlanPppIp6cpState
         INTEGER,
      sr1645v2Lan2MCVlanPppMyAutSt
         INTEGER,
      sr1645v2Lan2MCVlanPppHisAutSt
         INTEGER,
      sr1645v2Lan2MCVlanPppMru
         Integer32
      }

sr1645v2Lan2MCVlanTableIx OBJECT-TYPE
   SYNTAX      TableIndex
   MAX-ACCESS  not-accessible
   STATUS      current
   DESCRIPTION
      ""
   ::= {sr1645v2Lan2MCVlanEntry 11}

sr1645v2Lan2MCVlanName OBJECT-TYPE
   SYNTAX      DisplayString
   MAX-ACCESS  read-only
   STATUS      current
   DESCRIPTION
      "Path: ethernet2.status.vlan.name"
   ::= {sr1645v2Lan2MCVlanEntry 16777216}

sr1645v2Lan2MCVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet2.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan2MCVlanEntry 335544320}

sr1645v2Lan2MCVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.vlan.ifOperStatus

       Possibilities:
               up   (1)
               down   (2)
               testing   (3)
               unknown   (4)
               dormant   (5)
               notPresent   (6)
               lowerLayerDown   (7)"
   ::= {sr1645v2Lan2MCVlanEntry 1795162112}

sr1645v2Lan2MCVlanIfLastChange OBJECT-TYPE
   SYNTAX      TimeTicks
   MAX-ACCESS  read-only
   STATUS      current
   DESCRIPTION
      "Path: ethernet2.status.vlan.ifLastChange

       Time in centi-second."
   ::= {sr1645v2Lan2MCVlanEntry 1811939328}

sr1645v2Lan2MCVlanIfLastChangeDate OBJECT-TYPE
   SYNTAX      DisplayString
   MAX-ACCESS  read-only
   STATUS      current
   DESCRIPTION
      "Path: ethernet2.status.vlan.ifLastChangeDate"
   ::= {sr1645v2Lan2MCVlanEntry 3070230528}

sr1645v2Lan2MCVlanIpAddress OBJECT-TYPE
   SYNTAX      IpAddress
   MAX-ACCESS  read-only
   STATUS      current
   DESCRIPTION
      "Path: ethernet2.status.vlan.ip.address"
   ::= {sr1645v2Lan2MCVlanEntry 51380224}

sr1645v2Lan2MCVlanIpNetMask OBJECT-TYPE
   SYNTAX      IpAddress
   MAX-ACCESS  read-only
   STATUS      current
   DESCRIPTION
      "Path: ethernet2.status.vlan.ip.netMask"
   ::= {sr1645v2Lan2MCVlanEntry 51445760}

sr1645v2Lan2MCVlanIpRemote OBJECT-TYPE
   SYNTAX      IpAddress
   MAX-ACCESS  read-only
   STATUS      current
   DESCRIPTION
      "Path: ethernet2.status.vlan.ip.remote"
   ::= {sr1645v2Lan2MCVlanEntry 51511296}

sr1645v2Lan2MCVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: ethernet2.status.vlan.ip.dhcp.status

       Possibilities:
               none   (0)
               selecting   (1)
               requesting   (2)
               rebinding   (3)
               bound   (4)
               renewing   (5)
               rebooting   (6)
               initreboot   (7)"
   ::= {sr1645v2Lan2MCVlanEntry 51904768}

sr1645v2Lan2MCVlanIpDhcpLeaseTime OBJECT-TYPE
   SYNTAX      TimeTicks
   MAX-ACCESS  read-only
   STATUS      current
   DESCRIPTION
      "Path: ethernet2.status.vlan.ip.dhcp.leaseTime

       Time in centi-second."
   ::= {sr1645v2Lan2MCVlanEntry 51905024}

sr1645v2Lan2MCVlanIpV6State OBJECT-TYPE
   SYNTAX      INTEGER
               {
               disabled (0),
               enabled (1)
               }
   MAX-ACCESS  read-only
   STATUS      current
   DESCRIPTION
      "Path: ethernet2.status.vlan.ipV6.state

       Possibilities:
               disabled   (0)
               enabled   (1)"
   ::= {sr1645v2Lan2MCVlanEntry 100728832}

sr1645v2Lan2MCVlanIpV6InterfaceId OBJECT-TYPE
   SYNTAX      OCTET STRING
   MAX-ACCESS  read-only
   STATUS      current
   DESCRIPTION
      "Path: ethernet2.status.vlan.ipV6.interfaceId"
   ::= {sr1645v2Lan2MCVlanEntry 100794368}

sr1645v2Lan2MCVlanIpV6LinkMtu OBJECT-TYPE
   SYNTAX      Integer32
   MAX-ACCESS  read-only
   STATUS      current
   DESCRIPTION
      "Path: ethernet2.status.vlan.ipV6.linkMtu"
   ::= {sr1645v2Lan2MCVlanEntry 100925440}

sr1645v2Lan2MCVlanIpV6HopLimit OBJECT-TYPE
   SYNTAX      Integer32
   MAX-ACCESS  read-only
   STATUS      current
   DESCRIPTION
      "Path: ethernet2.status.vlan.ipV6.hopLimit"
   ::= {sr1645v2Lan2MCVlanEntry 100990976}

sr1645v2Lan2MCVlanIpV6DhcpIaid OBJECT-TYPE
   SYNTAX      Counter32
   MAX-ACCESS  read-only
   STATUS      current
   DESCRIPTION
      "Path: ethernet2.status.vlan.ipV6.dhcp.iaid

       32 bit unsigned wrappable counter."
   ::= {sr1645v2Lan2MCVlanEntry 101056768}

sr1645v2Lan2MCVlanIpV6RaRcvOption OBJECT-TYPE
   SYNTAX      Integer32
   MAX-ACCESS  read-only
   STATUS      current
   DESCRIPTION
      "Path: ethernet2.status.vlan.ipV6.raRcvOption

       Bit meanings:
               bit 0 = linkMtu,
               bit 1 = srcLinkLayer,
               bit 2 = prefixInfo,
               bit 3 = rdnss,
               bit 4 = dnssl"
   ::= {sr1645v2Lan2MCVlanEntry 101122048}

sr1645v2Lan2MCVlanBridgingStatus OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: ethernet2.status.vlan.bridging.status

       Possibilities:
               disabled   (0)
               discarding   (1)
               learning   (2)
               forwarding   (3)
               backupBlockedIntfDown   (256)
               backupBlockedIntfUp   (259)
               shutdown   (255)"
   ::= {sr1645v2Lan2MCVlanEntry 453050368}

sr1645v2Lan2MCVlanBridgingSpanningTreePortRole OBJECT-TYPE
   SYNTAX      INTEGER
               {
               none (0),
               root (1),
               designated (2),
               alternate (3),
               backup (4),
               disabled (5),
               master (6)
               }
   MAX-ACCESS  read-only
   STATUS      current
   DESCRIPTION
      "Path: ethernet2.status.vlan.bridging.spanningTree.portRole

       Possibilities:
               none   (0)
               root   (1)
               designated   (2)
               alternate   (3)
               backup   (4)
               disabled   (5)
               master   (6)"
   ::= {sr1645v2Lan2MCVlanEntry 453116160}

sr1645v2Lan2MCVlanBridgingSpanningTreePortId OBJECT-TYPE
   SYNTAX      Integer32
   MAX-ACCESS  read-only
   STATUS      current
   DESCRIPTION
      "Path: ethernet2.status.vlan.bridging.spanningTree.portId"
   ::= {sr1645v2Lan2MCVlanEntry 453116416}

sr1645v2Lan2MCVlanBridgingSpanningTreePpCostExtPathCost OBJECT-TYPE
   SYNTAX      Integer32
   MAX-ACCESS  read-only
   STATUS      current
   DESCRIPTION
      "Path: ethernet2.status.vlan.bridging.spanningTree.portPathCosts.extPathCost"
   ::= {sr1645v2Lan2MCVlanEntry 453116673}

sr1645v2Lan2MCVlanBridgingSpanningTreePpCostIntPathCost OBJECT-TYPE
   SYNTAX      Integer32
   MAX-ACCESS  read-only
   STATUS      current
   DESCRIPTION
      "Path: ethernet2.status.vlan.bridging.spanningTree.portPathCosts.intPathCost"
   ::= {sr1645v2Lan2MCVlanEntry 453116674}

sr1645v2Lan2MCVlanBridgingSpanningTreeExtRpCost OBJECT-TYPE
   SYNTAX      Integer32
   MAX-ACCESS  read-only
   STATUS      current
   DESCRIPTION
      "Path: ethernet2.status.vlan.bridging.spanningTree.extRootPathCost"
   ::= {sr1645v2Lan2MCVlanEntry 453116928}

sr1645v2Lan2MCVlanBridgingSpanningTreeIntRpCost OBJECT-TYPE
   SYNTAX      Integer32
   MAX-ACCESS  read-only
   STATUS      current
   DESCRIPTION
      "Path: ethernet2.status.vlan.bridging.spanningTree.intRootPathCost"
   ::= {sr1645v2Lan2MCVlanEntry 453117184}

sr1645v2Lan2MCVlanBridgingSpanningTreeDesBrIdPriority OBJECT-TYPE
   SYNTAX      Integer32
   MAX-ACCESS  read-only
   STATUS      current
   DESCRIPTION
      "Path: ethernet2.status.vlan.bridging.spanningTree.designatedBridgeId.priority"
   ::= {sr1645v2Lan2MCVlanEntry 453117441}

sr1645v2Lan2MCVlanBridgingSpanningTreeDesBrIdMacAddress OBJECT-TYPE
   SYNTAX      OCTET STRING
   MAX-ACCESS  read-only
   STATUS      current
   DESCRIPTION
      "Path: ethernet2.status.vlan.bridging.spanningTree.designatedBridgeId.macAddress

       MAC address."
   ::= {sr1645v2Lan2MCVlanEntry 453117442}

sr1645v2Lan2MCVlanBridgingSpanningTreeDesPrtId OBJECT-TYPE
   SYNTAX      Integer32
   MAX-ACCESS  read-only
   STATUS      current
   DESCRIPTION
      "Path: ethernet2.status.vlan.bridging.spanningTree.designatedPortId"
   ::= {sr1645v2Lan2MCVlanEntry 453117696}

sr1645v2Lan2MCVlanBridgingSpanningTreeDesInt OBJECT-TYPE
   SYNTAX      INTEGER
               {
               no (0),
               yes (1)
               }
   MAX-ACCESS  read-only
   STATUS      current
   DESCRIPTION
      "Path: ethernet2.status.vlan.bridging.spanningTree.designatedOrInternal

       Possibilities:
               no   (0)
               yes   (1)"
   ::= {sr1645v2Lan2MCVlanEntry 453117952}

sr1645v2Lan2MCVlanBridgingSpanningTreeEdgeDetection OBJECT-TYPE
   SYNTAX      INTEGER
               {
               none (0),
               edge (1),
               notEdge (2)
               }
   MAX-ACCESS  read-only
   STATUS      current
   DESCRIPTION
      "Path: ethernet2.status.vlan.bridging.spanningTree.edgeDetection

       Possibilities:
               none   (0)
               edge   (1)
               notEdge   (2)"
   ::= {sr1645v2Lan2MCVlanEntry 453118208}

sr1645v2Lan2MCVlanVlanVid OBJECT-TYPE
   SYNTAX      Integer32
   MAX-ACCESS  read-only
   STATUS      current
   DESCRIPTION
      "Path: ethernet2.status.vlan.vlan.vid"
   ::= {sr1645v2Lan2MCVlanEntry 234946560}

sr1645v2Lan2MCVlanPppOEthDiscState OBJECT-TYPE
   SYNTAX      INTEGER
               {
               idle (0),
               waitForPADO (1),
               waitForPADS (2),
               established (3)
               }
   MAX-ACCESS  read-only
   STATUS      current
   DESCRIPTION
      "Path: ethernet2.status.vlan.pppOverEth.discState

       Possibilities:
               idle   (0)
               waitForPADO   (1)
               waitForPADS   (2)
               established   (3)"
   ::= {sr1645v2Lan2MCVlanEntry 67174400}

sr1645v2Lan2MCVlanPppOEthPeerMac OBJECT-TYPE
   SYNTAX      OCTET STRING
   MAX-ACCESS  read-only
   STATUS      current
   DESCRIPTION
      "Path: ethernet2.status.vlan.pppOverEth.remoteMacAddress

       MAC address."
   ::= {sr1645v2Lan2MCVlanEntry 67239936}

sr1645v2Lan2MCVlanPppOEthServiceName OBJECT-TYPE
   SYNTAX      DisplayString
   MAX-ACCESS  read-only
   STATUS      current
   DESCRIPTION
      "Path: ethernet2.status.vlan.pppOverEth.serviceName"
   ::= {sr1645v2Lan2MCVlanEntry 67305472}

sr1645v2Lan2MCVlanPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2MCVlanEntry 83951616}

sr1645v2Lan2MCVlanPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2MCVlanEntry 84017152}

sr1645v2Lan2MCVlanPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.vlan.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2MCVlanEntry 84869120}

sr1645v2Lan2MCVlanPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet2.status.vlan.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan2MCVlanEntry 84541440}

sr1645v2Lan2MCVlanPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet2.status.vlan.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan2MCVlanEntry 84606976}

sr1645v2Lan2MCVlanPppMru OBJECT-TYPE
   SYNTAX      Integer32
   MAX-ACCESS  read-only
   STATUS      current
   DESCRIPTION
      "Path: ethernet2.status.vlan.ppp.mru"
   ::= {sr1645v2Lan2MCVlanEntry 84934656}

sr1645v2Lan2MCVlanIpSecondaryIp OBJECT-TYPE
   SYNTAX      SEQUENCE OF Sr1645v2Lan2MCVlanIpSecondaryIpEntry
   MAX-ACCESS  not-accessible
   STATUS      current
   DESCRIPTION
      ""
   ::= {sr1645v2Lan2MCVlan 51838976}

sr1645v2Lan2MCVlanIpSecondaryIpEntry OBJECT-TYPE
   SYNTAX      Sr1645v2Lan2MCVlanIpSecondaryIpEntry
   MAX-ACCESS  not-accessible
   STATUS      current
   DESCRIPTION
      ""
   INDEX      { sr1645v2Lan2MCVlanTableIx,
                sr1645v2Lan2MCVlanIpSecondaryIpTableIx }
   ::= {sr1645v2Lan2MCVlanIpSecondaryIp 1}

Sr1645v2Lan2MCVlanIpSecondaryIpEntry ::=
   SEQUENCE
      {
      sr1645v2Lan2MCVlanIpSecondaryIpTableIx
         TableIndex,
      sr1645v2Lan2MCVlanIpSecondaryIpAddress
         IpAddress,
      sr1645v2Lan2MCVlanIpSecondaryIpNetMask
         IpAddress
      }

sr1645v2Lan2MCVlanIpSecondaryIpTableIx OBJECT-TYPE
   SYNTAX      TableIndex
   MAX-ACCESS  not-accessible
   STATUS      current
   DESCRIPTION
      ""
   ::= {sr1645v2Lan2MCVlanIpSecondaryIpEntry 11}

sr1645v2Lan2MCVlanIpSecondaryIpAddress OBJECT-TYPE
   SYNTAX      IpAddress
   MAX-ACCESS  read-only
   STATUS      current
   DESCRIPTION
      "Path: ethernet2.status.vlan.ip.secondaryIp.address"
   ::= {sr1645v2Lan2MCVlanIpSecondaryIpEntry 2030043136}

sr1645v2Lan2MCVlanIpSecondaryIpNetMask OBJECT-TYPE
   SYNTAX      IpAddress
   MAX-ACCESS  read-only
   STATUS      current
   DESCRIPTION
      "Path: ethernet2.status.vlan.ip.secondaryIp.netMask"
   ::= {sr1645v2Lan2MCVlanIpSecondaryIpEntry 2063597568}

sr1645v2Lan2MCVlanIpV6Addresses OBJECT-TYPE
   SYNTAX      SEQUENCE OF Sr1645v2Lan2MCVlanIpV6AddressesEntry
   MAX-ACCESS  not-accessible
   STATUS      current
   DESCRIPTION
      ""
   ::= {sr1645v2Lan2MCVlan 100859904}

sr1645v2Lan2MCVlanIpV6AddressesEntry OBJECT-TYPE
   SYNTAX      Sr1645v2Lan2MCVlanIpV6AddressesEntry
   MAX-ACCESS  not-accessible
   STATUS      current
   DESCRIPTION
      ""
   INDEX      { sr1645v2Lan2MCVlanTableIx,
                sr1645v2Lan2MCVlanIpV6AddressesTableIx }
   ::= {sr1645v2Lan2MCVlanIpV6Addresses 1}

Sr1645v2Lan2MCVlanIpV6AddressesEntry ::=
   SEQUENCE
      {
      sr1645v2Lan2MCVlanIpV6AddressesTableIx
         TableIndex,
      sr1645v2Lan2MCVlanIpV6AddressesAddress
         Ipv6Address,
      sr1645v2Lan2MCVlanIpV6AddressesPrefixLength
         Integer32,
      sr1645v2Lan2MCVlanIpV6AddressesStatus
         INTEGER,
      sr1645v2Lan2MCVlanIpV6AddressesOrigin
         INTEGER,
      sr1645v2Lan2MCVlanIpV6AddressesFlagsInterfaceId
         INTEGER,
      sr1645v2Lan2MCVlanIpV6AddressesFlagsAnycast
         INTEGER,
      sr1645v2Lan2MCVlanIpV6AddressesTimersValidLifeTime
         TimeTicks,
      sr1645v2Lan2MCVlanIpV6AddressesTimersPrefLifeTime
         TimeTicks
      }

sr1645v2Lan2MCVlanIpV6AddressesTableIx OBJECT-TYPE
   SYNTAX      TableIndex
   MAX-ACCESS  not-accessible
   STATUS      current
   DESCRIPTION
      ""
   ::= {sr1645v2Lan2MCVlanIpV6AddressesEntry 11}

sr1645v2Lan2MCVlanIpV6AddressesAddress OBJECT-TYPE
   SYNTAX      Ipv6Address
   MAX-ACCESS  read-only
   STATUS      current
   DESCRIPTION
      "Path: ethernet2.status.vlan.ipV6.addresses.address

       ipv6 address"
   ::= {sr1645v2Lan2MCVlanIpV6AddressesEntry 16777216}

sr1645v2Lan2MCVlanIpV6AddressesPrefixLength OBJECT-TYPE
   SYNTAX      Integer32
   MAX-ACCESS  read-only
   STATUS      current
   DESCRIPTION
      "Path: ethernet2.status.vlan.ipV6.addresses.prefixLength"
   ::= {sr1645v2Lan2MCVlanIpV6AddressesEntry 33554432}

sr1645v2Lan2MCVlanIpV6AddressesStatus OBJECT-TYPE
   SYNTAX      INTEGER
               {
               invalid (0),
               tentative (1),
               deprecated (2),
               preferred (3)
               }
   MAX-ACCESS  read-only
   STATUS      current
   DESCRIPTION
      "Path: ethernet2.status.vlan.ipV6.addresses.status

       Possibilities:
               invalid   (0)
               tentative   (1)
               deprecated   (2)
               preferred   (3)"
   ::= {sr1645v2Lan2MCVlanIpV6AddressesEntry 50331648}

sr1645v2Lan2MCVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.vlan.ipV6.addresses.origin

       Possibilities:
               unknown   (0)
               manual   (1)
               generalPrefix   (2)
               statelessAuto   (3)
               statefullAuto   (4)"
   ::= {sr1645v2Lan2MCVlanIpV6AddressesEntry 67108864}

sr1645v2Lan2MCVlanIpV6AddressesFlagsInterfaceId OBJECT-TYPE
   SYNTAX      INTEGER
               {
               no (0),
               yes (1)
               }
   MAX-ACCESS  read-only
   STATUS      current
   DESCRIPTION
      "Path: ethernet2.status.vlan.ipV6.addresses.flags.interfaceId

       Possibilities:
               no   (0)
               yes   (1)"
   ::= {sr1645v2Lan2MCVlanIpV6AddressesEntry 83951616}

sr1645v2Lan2MCVlanIpV6AddressesFlagsAnycast OBJECT-TYPE
   SYNTAX      INTEGER
               {
               no (0),
               yes (1)
               }
   MAX-ACCESS  read-only
   STATUS      current
   DESCRIPTION
      "Path: ethernet2.status.vlan.ipV6.addresses.flags.anycast

       Possibilities:
               no   (0)
               yes   (1)"
   ::= {sr1645v2Lan2MCVlanIpV6AddressesEntry 84017152}

sr1645v2Lan2MCVlanIpV6AddressesTimersValidLifeTime OBJECT-TYPE
   SYNTAX      TimeTicks
   MAX-ACCESS  read-only
   STATUS      current
   DESCRIPTION
      "Path: ethernet2.status.vlan.ipV6.addresses.timers.validLifeTime

       Time in centi-second."
   ::= {sr1645v2Lan2MCVlanIpV6AddressesEntry 100794368}

sr1645v2Lan2MCVlanIpV6AddressesTimersPrefLifeTime OBJECT-TYPE
   SYNTAX      TimeTicks
   MAX-ACCESS  read-only
   STATUS      current
   DESCRIPTION
      "Path: ethernet2.status.vlan.ipV6.addresses.timers.prefLifeTime

       Time in centi-second."
   ::= {sr1645v2Lan2MCVlanIpV6AddressesEntry 100728832}

sr1645v2Lan2MCVlanVlanArpCache OBJECT-TYPE
   SYNTAX      SEQUENCE OF Sr1645v2Lan2MCVlanVlanArpCacheEntry
   MAX-ACCESS  not-accessible
   STATUS      current
   DESCRIPTION
      ""
   ::= {sr1645v2Lan2MCVlan 235601920}

sr1645v2Lan2MCVlanVlanArpCacheEntry OBJECT-TYPE
   SYNTAX      Sr1645v2Lan2MCVlanVlanArpCacheEntry
   MAX-ACCESS  not-accessible
   STATUS      current
   DESCRIPTION
      ""
   INDEX      { sr1645v2Lan2MCVlanTableIx,
                sr1645v2Lan2MCVlanVlanArpCacheTableIx }
   ::= {sr1645v2Lan2MCVlanVlanArpCache 1}

Sr1645v2Lan2MCVlanVlanArpCacheEntry ::=
   SEQUENCE
      {
      sr1645v2Lan2MCVlanVlanArpCacheTableIx
         TableIndex,
      sr1645v2Lan2MCVlanVlanArpCacheMacAddress
         OCTET STRING,
      sr1645v2Lan2MCVlanVlanArpCacheIpAddress
         IpAddress,
      sr1645v2Lan2MCVlanVlanArpCacheType
         INTEGER,
      sr1645v2Lan2MCVlanVlanArpCacheTimeOut
         TimeTicks
      }

sr1645v2Lan2MCVlanVlanArpCacheTableIx OBJECT-TYPE
   SYNTAX      TableIndex
   MAX-ACCESS  not-accessible
   STATUS      current
   DESCRIPTION
      ""
   ::= {sr1645v2Lan2MCVlanVlanArpCacheEntry 11}

sr1645v2Lan2MCVlanVlanArpCacheMacAddress OBJECT-TYPE
   SYNTAX      OCTET STRING
   MAX-ACCESS  read-only
   STATUS      current
   DESCRIPTION
      "Path: ethernet2.status.vlan.vlan.arpCache.macAddress

       MAC address."
   ::= {sr1645v2Lan2MCVlanVlanArpCacheEntry 16777216}

sr1645v2Lan2MCVlanVlanArpCacheIpAddress OBJECT-TYPE
   SYNTAX      IpAddress
   MAX-ACCESS  read-only
   STATUS      current
   DESCRIPTION
      "Path: ethernet2.status.vlan.vlan.arpCache.ipAddress"
   ::= {sr1645v2Lan2MCVlanVlanArpCacheEntry 33554432}

sr1645v2Lan2MCVlanVlanArpCacheType OBJECT-TYPE
   SYNTAX      INTEGER
               {
               static (0),
               dynamic (1)
               }
   MAX-ACCESS  read-only
   STATUS      current
   DESCRIPTION
      "Path: ethernet2.status.vlan.vlan.arpCache.type

       Possibilities:
               static   (0)
               dynamic   (1)"
   ::= {sr1645v2Lan2MCVlanVlanArpCacheEntry 50331648}

sr1645v2Lan2MCVlanVlanArpCacheTimeOut OBJECT-TYPE
   SYNTAX      TimeTicks
   MAX-ACCESS  read-only
   STATUS      current
   DESCRIPTION
      "Path: ethernet2.status.vlan.vlan.arpCache.timeOut

       Time in centi-second."
   ::= {sr1645v2Lan2MCVlanVlanArpCacheEntry 67108864}


sr1645v2Lan2MCPppOE OBJECT IDENTIFIER ::= {sr1645v2Lan2MC 36}

sr1645v2Lan2MCPppOESSCTable OBJECT-TYPE
   SYNTAX      SEQUENCE OF Sr1645v2Lan2MCPppOEEntry
   MAX-ACCESS  not-accessible
   STATUS      current
   DESCRIPTION
      ""
   ::= {sr1645v2Lan2MCPppOE 1}

sr1645v2Lan2MCPppOEEntry OBJECT-TYPE
   SYNTAX      Sr1645v2Lan2MCPppOEEntry
   MAX-ACCESS  not-accessible
   STATUS      current
   DESCRIPTION
      ""
   INDEX      { sr1645v2Lan2MCPppOETableIx }
   ::= {sr1645v2Lan2MCPppOESSCTable 1}

Sr1645v2Lan2MCPppOEEntry ::=
   SEQUENCE
      {
      sr1645v2Lan2MCPppOETableIx
         TableIndex,
      sr1645v2Lan2MCPppOEName
         DisplayString,
      sr1645v2Lan2MCPppOEMode
         INTEGER,
      sr1645v2Lan2MCPppOEIfOperStatus
         INTEGER,
      sr1645v2Lan2MCPppOEIfLastChange
         TimeTicks,
      sr1645v2Lan2MCPppOEIfLastChangeDate
         DisplayString,
      sr1645v2Lan2MCPppOEIpAddress
         IpAddress,
      sr1645v2Lan2MCPppOEIpNetMask
         IpAddress,
      sr1645v2Lan2MCPppOEIpRemote
         IpAddress,
      sr1645v2Lan2MCPppOEPppOEthDiscState
         INTEGER,
      sr1645v2Lan2MCPppOEPppOEthPeerMac
         OCTET STRING,
      sr1645v2Lan2MCPppOEPppOEthServiceName
         DisplayString,
      sr1645v2Lan2MCPppOEPppLcpState
         INTEGER,
      sr1645v2Lan2MCPppOEPppIpcpState
         INTEGER,
      sr1645v2Lan2MCPppOEPppIp6cpState
         INTEGER,
      sr1645v2Lan2MCPppOEPppMyAutSt
         INTEGER,
      sr1645v2Lan2MCPppOEPppHisAutSt
         INTEGER,
      sr1645v2Lan2MCPppOEPppMru
         Integer32,
      sr1645v2Lan2MCPppOEIpV6State
         INTEGER,
      sr1645v2Lan2MCPppOEIpV6InterfaceId
         OCTET STRING,
      sr1645v2Lan2MCPppOEIpV6LinkMtu
         Integer32,
      sr1645v2Lan2MCPppOEIpV6HopLimit
         Integer32,
      sr1645v2Lan2MCPppOEIpV6DhcpIaid
         Counter32,
      sr1645v2Lan2MCPppOEIpV6RaRcvOption
         Integer32
      }

sr1645v2Lan2MCPppOETableIx OBJECT-TYPE
   SYNTAX      TableIndex
   MAX-ACCESS  not-accessible
   STATUS      current
   DESCRIPTION
      ""
   ::= {sr1645v2Lan2MCPppOEEntry 11}

sr1645v2Lan2MCPppOEName OBJECT-TYPE
   SYNTAX      DisplayString
   MAX-ACCESS  read-only
   STATUS      current
   DESCRIPTION
      "Path: ethernet2.status.pppoEClient.name"
   ::= {sr1645v2Lan2MCPppOEEntry 16777216}

sr1645v2Lan2MCPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: ethernet2.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2Lan2MCPppOEEntry 335544320}

sr1645v2Lan2MCPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: ethernet2.status.pppoEClient.ifOperStatus

       Possibilities:
               up   (1)
               down   (2)
               testing   (3)
               unknown   (4)
               dormant   (5)
               notPresent   (6)
               lowerLayerDown   (7)"
   ::= {sr1645v2Lan2MCPppOEEntry 1795162112}

sr1645v2Lan2MCPppOEIfLastChange OBJECT-TYPE
   SYNTAX      TimeTicks
   MAX-ACCESS  read-only
   STATUS      current
   DESCRIPTION
      "Path: ethernet2.status.pppoEClient.ifLastChange

       Time in centi-second."
   ::= {sr1645v2Lan2MCPppOEEntry 1811939328}

sr1645v2Lan2MCPppOEIfLastChangeDate OBJECT-TYPE
   SYNTAX      DisplayString
   MAX-ACCESS  read-only
   STATUS      current
   DESCRIPTION
      "Path: ethernet2.status.pppoEClient.ifLastChangeDate"
   ::= {sr1645v2Lan2MCPppOEEntry 3070230528}

sr1645v2Lan2MCPppOEIpAddress OBJECT-TYPE
   SYNTAX      IpAddress
   MAX-ACCESS  read-only
   STATUS      current
   DESCRIPTION
      "Path: ethernet2.status.pppoEClient.ip.address"
   ::= {sr1645v2Lan2MCPppOEEntry 51380224}

sr1645v2Lan2MCPppOEIpNetMask OBJECT-TYPE
   SYNTAX      IpAddress
   MAX-ACCESS  read-only
   STATUS      current
   DESCRIPTION
      "Path: ethernet2.status.pppoEClient.ip.netMask"
   ::= {sr1645v2Lan2MCPppOEEntry 51445760}

sr1645v2Lan2MCPppOEIpRemote OBJECT-TYPE
   SYNTAX      IpAddress
   MAX-ACCESS  read-only
   STATUS      current
   DESCRIPTION
      "Path: ethernet2.status.pppoEClient.ip.remote"
   ::= {sr1645v2Lan2MCPppOEEntry 51511296}

sr1645v2Lan2MCPppOEPppOEthDiscState OBJECT-TYPE
   SYNTAX      INTEGER
               {
               idle (0),
               waitForPADO (1),
               waitForPADS (2),
               established (3)
               }
   MAX-ACCESS  read-only
   STATUS      current
   DESCRIPTION
      "Path: ethernet2.status.pppoEClient.pppOverEth.discState

       Possibilities:
               idle   (0)
               waitForPADO   (1)
               waitForPADS   (2)
               established   (3)"
   ::= {sr1645v2Lan2MCPppOEEntry 67174400}

sr1645v2Lan2MCPppOEPppOEthPeerMac OBJECT-TYPE
   SYNTAX      OCTET STRING
   MAX-ACCESS  read-only
   STATUS      current
   DESCRIPTION
      "Path: ethernet2.status.pppoEClient.pppOverEth.remoteMacAddress

       MAC address."
   ::= {sr1645v2Lan2MCPppOEEntry 67239936}

sr1645v2Lan2MCPppOEPppOEthServiceName OBJECT-TYPE
   SYNTAX      DisplayString
   MAX-ACCESS  read-only
   STATUS      current
   DESCRIPTION
      "Path: ethernet2.status.pppoEClient.pppOverEth.serviceName"
   ::= {sr1645v2Lan2MCPppOEEntry 67305472}

sr1645v2Lan2MCPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2MCPppOEEntry 83951616}

sr1645v2Lan2MCPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2MCPppOEEntry 84017152}

sr1645v2Lan2MCPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: ethernet2.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2Lan2MCPppOEEntry 84869120}

sr1645v2Lan2MCPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: ethernet2.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2Lan2MCPppOEEntry 84541440}

sr1645v2Lan2MCPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: ethernet2.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2Lan2MCPppOEEntry 84606976}

sr1645v2Lan2MCPppOEPppMru OBJECT-TYPE
   SYNTAX      Integer32
   MAX-ACCESS  read-only
   STATUS      current
   DESCRIPTION
      "Path: ethernet2.status.pppoEClient.ppp.mru"
   ::= {sr1645v2Lan2MCPppOEEntry 84934656}

sr1645v2Lan2MCPppOEIpV6State OBJECT-TYPE
   SYNTAX      INTEGER
               {
               disabled (0),
               enabled (1)
               }
   MAX-ACCESS  read-only
   STATUS      current
   DESCRIPTION
      "Path: ethernet2.status.pppoEClient.ipV6.state

       Possibilities:
               disabled   (0)
               enabled   (1)"
   ::= {sr1645v2Lan2MCPppOEEntry 100728832}

sr1645v2Lan2MCPppOEIpV6InterfaceId OBJECT-TYPE
   SYNTAX      OCTET STRING
   MAX-ACCESS  read-only
   STATUS      current
   DESCRIPTION
      "Path: ethernet2.status.pppoEClient.ipV6.interfaceId"
   ::= {sr1645v2Lan2MCPppOEEntry 100794368}

sr1645v2Lan2MCPppOEIpV6LinkMtu OBJECT-TYPE
   SYNTAX      Integer32
   MAX-ACCESS  read-only
   STATUS      current
   DESCRIPTION
      "Path: ethernet2.status.pppoEClient.ipV6.linkMtu"
   ::= {sr1645v2Lan2MCPppOEEntry 100925440}

sr1645v2Lan2MCPppOEIpV6HopLimit OBJECT-TYPE
   SYNTAX      Integer32
   MAX-ACCESS  read-only
   STATUS      current
   DESCRIPTION
      "Path: ethernet2.status.pppoEClient.ipV6.hopLimit"
   ::= {sr1645v2Lan2MCPppOEEntry 100990976}

sr1645v2Lan2MCPppOEIpV6DhcpIaid OBJECT-TYPE
   SYNTAX      Counter32
   MAX-ACCESS  read-only
   STATUS      current
   DESCRIPTION
      "Path: ethernet2.status.pppoEClient.ipV6.dhcp.iaid

       32 bit unsigned wrappable counter."
   ::= {sr1645v2Lan2MCPppOEEntry 101056768}

sr1645v2Lan2MCPppOEIpV6RaRcvOption OBJECT-TYPE
   SYNTAX      Integer32
   MAX-ACCESS  read-only
   STATUS      current
   DESCRIPTION
      "Path: ethernet2.status.pppoEClient.ipV6.raRcvOption

       Bit meanings:
               bit 0 = linkMtu,
               bit 1 = srcLinkLayer,
               bit 2 = prefixInfo,
               bit 3 = rdnss,
               bit 4 = dnssl"
   ::= {sr1645v2Lan2MCPppOEEntry 101122048}

sr1645v2Lan2MCPppOEIpV6Addresses OBJECT-TYPE
   SYNTAX      SEQUENCE OF Sr1645v2Lan2MCPppOEIpV6AddressesEntry
   MAX-ACCESS  not-accessible
   STATUS      current
   DESCRIPTION
      ""
   ::= {sr1645v2Lan2MCPppOE 100859904}

sr1645v2Lan2MCPppOEIpV6AddressesEntry OBJECT-TYPE
   SYNTAX      Sr1645v2Lan2MCPppOEIpV6AddressesEntry
   MAX-ACCESS  not-accessible
   STATUS      current
   DESCRIPTION
      ""
   INDEX      { sr1645v2Lan2MCPppOETableIx,
                sr1645v2Lan2MCPppOEIpV6AddressesTableIx }
   ::= {sr1645v2Lan2MCPppOEIpV6Addresses 1}

Sr1645v2Lan2MCPppOEIpV6AddressesEntry ::=
   SEQUENCE
      {
      sr1645v2Lan2MCPppOEIpV6AddressesTableIx
         TableIndex,
      sr1645v2Lan2MCPppOEIpV6AddressesAddress
         Ipv6Address,
      sr1645v2Lan2MCPppOEIpV6AddressesPrefixLength
         Integer32,
      sr1645v2Lan2MCPppOEIpV6AddressesStatus
         INTEGER,
      sr1645v2Lan2MCPppOEIpV6AddressesOrigin
         INTEGER,
      sr1645v2Lan2MCPppOEIpV6AddressesFlagsInterfaceId
         INTEGER,
      sr1645v2Lan2MCPppOEIpV6AddressesFlagsAnycast
         INTEGER,
      sr1645v2Lan2MCPppOEIpV6AddressesTimersValidLifeTime
         TimeTicks,
      sr1645v2Lan2MCPppOEIpV6AddressesTimersPrefLifeTime
         TimeTicks
      }

sr1645v2Lan2MCPppOEIpV6AddressesTableIx OBJECT-TYPE
   SYNTAX      TableIndex
   MAX-ACCESS  not-accessible
   STATUS      current
   DESCRIPTION
      ""
   ::= {sr1645v2Lan2MCPppOEIpV6AddressesEntry 11}

sr1645v2Lan2MCPppOEIpV6AddressesAddress OBJECT-TYPE
   SYNTAX      Ipv6Address
   MAX-ACCESS  read-only
   STATUS      current
   DESCRIPTION
      "Path: ethernet2.status.pppoEClient.ipV6.addresses.address

       ipv6 address"
   ::= {sr1645v2Lan2MCPppOEIpV6AddressesEntry 16777216}

sr1645v2Lan2MCPppOEIpV6AddressesPrefixLength OBJECT-TYPE
   SYNTAX      Integer32
   MAX-ACCESS  read-only
   STATUS      current
   DESCRIPTION
      "Path: ethernet2.status.pppoEClient.ipV6.addresses.prefixLength"
   ::= {sr1645v2Lan2MCPppOEIpV6AddressesEntry 33554432}

sr1645v2Lan2MCPppOEIpV6AddressesStatus OBJECT-TYPE
   SYNTAX      INTEGER
               {
               invalid (0),
               tentative (1),
               deprecated (2),
               preferred (3)
               }
   MAX-ACCESS  read-only
   STATUS      current
   DESCRIPTION
      "Path: ethernet2.status.pppoEClient.ipV6.addresses.status

       Possibilities:
               invalid   (0)
               tentative   (1)
               deprecated   (2)
               preferred   (3)"
   ::= {sr1645v2Lan2MCPppOEIpV6AddressesEntry 50331648}

sr1645v2Lan2MCPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.pppoEClient.ipV6.addresses.origin

       Possibilities:
               unknown   (0)
               manual   (1)
               generalPrefix   (2)
               statelessAuto   (3)
               statefullAuto   (4)"
   ::= {sr1645v2Lan2MCPppOEIpV6AddressesEntry 67108864}

sr1645v2Lan2MCPppOEIpV6AddressesFlagsInterfaceId OBJECT-TYPE
   SYNTAX      INTEGER
               {
               no (0),
               yes (1)
               }
   MAX-ACCESS  read-only
   STATUS      current
   DESCRIPTION
      "Path: ethernet2.status.pppoEClient.ipV6.addresses.flags.interfaceId

       Possibilities:
               no   (0)
               yes   (1)"
   ::= {sr1645v2Lan2MCPppOEIpV6AddressesEntry 83951616}

sr1645v2Lan2MCPppOEIpV6AddressesFlagsAnycast OBJECT-TYPE
   SYNTAX      INTEGER
               {
               no (0),
               yes (1)
               }
   MAX-ACCESS  read-only
   STATUS      current
   DESCRIPTION
      "Path: ethernet2.status.pppoEClient.ipV6.addresses.flags.anycast

       Possibilities:
               no   (0)
               yes   (1)"
   ::= {sr1645v2Lan2MCPppOEIpV6AddressesEntry 84017152}

sr1645v2Lan2MCPppOEIpV6AddressesTimersValidLifeTime OBJECT-TYPE
   SYNTAX      TimeTicks
   MAX-ACCESS  read-only
   STATUS      current
   DESCRIPTION
      "Path: ethernet2.status.pppoEClient.ipV6.addresses.timers.validLifeTime

       Time in centi-second."
   ::= {sr1645v2Lan2MCPppOEIpV6AddressesEntry 100794368}

sr1645v2Lan2MCPppOEIpV6AddressesTimersPrefLifeTime OBJECT-TYPE
   SYNTAX      TimeTicks
   MAX-ACCESS  read-only
   STATUS      current
   DESCRIPTION
      "Path: ethernet2.status.pppoEClient.ipV6.addresses.timers.prefLifeTime

       Time in centi-second."
   ::= {sr1645v2Lan2MCPppOEIpV6AddressesEntry 100728832}


sr1645v2Lan2MCDot1x OBJECT IDENTIFIER ::= {sr1645v2Lan2MC 190}

sr1645v2Lan2MCDot1xSSCTable OBJECT-TYPE
   SYNTAX      SEQUENCE OF Sr1645v2Lan2MCDot1xEntry
   MAX-ACCESS  not-accessible
   STATUS      current
   DESCRIPTION
      "Ethernet Switch VLAN Table"
   ::= {sr1645v2Lan2MCDot1x 1}

sr1645v2Lan2MCDot1xEntry OBJECT-TYPE
   SYNTAX      Sr1645v2Lan2MCDot1xEntry
   MAX-ACCESS  not-accessible
   STATUS      current
   DESCRIPTION
      ""
   INDEX      { sr1645v2Lan2MCDot1xTableIx }
   ::= {sr1645v2Lan2MCDot1xSSCTable 1}

Sr1645v2Lan2MCDot1xEntry ::=
   SEQUENCE
      {
      sr1645v2Lan2MCDot1xTableIx
         TableIndex,
      sr1645v2Lan2MCDot1xRemote
         OCTET STRING,
      sr1645v2Lan2MCDot1xAuthorized
         INTEGER,
      sr1645v2Lan2MCDot1xAuthenticator
         INTEGER,
      sr1645v2Lan2MCDot1xBackEnd
         INTEGER,
      sr1645v2Lan2MCDot1xRetries
         Integer32,
      sr1645v2Lan2MCDot1xReAuthTime
         TimeTicks,
      sr1645v2Lan2MCDot1xHoldTime
         TimeTicks
      }

sr1645v2Lan2MCDot1xTableIx OBJECT-TYPE
   SYNTAX      TableIndex
   MAX-ACCESS  not-accessible
   STATUS      current
   DESCRIPTION
      ""
   ::= {sr1645v2Lan2MCDot1xEntry 11}

sr1645v2Lan2MCDot1xRemote OBJECT-TYPE
   SYNTAX      OCTET STRING
   MAX-ACCESS  read-only
   STATUS      current
   DESCRIPTION
      "Path: ethernet2.status.dot1x.remote

       MAC address."
   ::= {sr1645v2Lan2MCDot1xEntry 16777216}

sr1645v2Lan2MCDot1xAuthorized OBJECT-TYPE
   SYNTAX      INTEGER
               {
               no (0),
               yes (1)
               }
   MAX-ACCESS  read-only
   STATUS      current
   DESCRIPTION
      "Path: ethernet2.status.dot1x.authorized

       Possibilities:
               no   (0)
               yes   (1)"
   ::= {sr1645v2Lan2MCDot1xEntry 33554432}

sr1645v2Lan2MCDot1xAuthenticator OBJECT-TYPE
   SYNTAX      INTEGER
               {
               preInit (0),
               initialize (1),
               disconnected (2),
               restart (3),
               connecting (4),
               authenticating (5),
               authenticated (6),
               aborting (7),
               held (8),
               forceAuth (9),
               forceUnauth (10)
               }
   MAX-ACCESS  read-only
   STATUS      current
   DESCRIPTION
      "Path: ethernet2.status.dot1x.authenticator

       Possibilities:
               preInit   (0)
               initialize   (1)
               disconnected   (2)
               restart   (3)
               connecting   (4)
               authenticating   (5)
               authenticated   (6)
               aborting   (7)
               held   (8)
               forceAuth   (9)
               forceUnauth   (10)"
   ::= {sr1645v2Lan2MCDot1xEntry 50331648}

sr1645v2Lan2MCDot1xBackEnd OBJECT-TYPE
   SYNTAX      INTEGER
               {
               preInit (0),
               initialize (1),
               idle (2),
               request (3),
               response (4),
               success (5),
               failure (6),
               radiusTimeout (7),
               timeout (8)
               }
   MAX-ACCESS  read-only
   STATUS      current
   DESCRIPTION
      "Path: ethernet2.status.dot1x.backEnd

       Possibilities:
               preInit   (0)
               initialize   (1)
               idle   (2)
               request   (3)
               response   (4)
               success   (5)
               failure   (6)
               radiusTimeout   (7)
               timeout   (8)"
   ::= {sr1645v2Lan2MCDot1xEntry 67108864}

sr1645v2Lan2MCDot1xRetries OBJECT-TYPE
   SYNTAX      Integer32
   MAX-ACCESS  read-only
   STATUS      current
   DESCRIPTION
      "Path: ethernet2.status.dot1x.retries"
   ::= {sr1645v2Lan2MCDot1xEntry 83886080}

sr1645v2Lan2MCDot1xReAuthTime OBJECT-TYPE
   SYNTAX      TimeTicks
   MAX-ACCESS  read-only
   STATUS      current
   DESCRIPTION
      "Path: ethernet2.status.dot1x.reAuthTime

       Time in centi-second."
   ::= {sr1645v2Lan2MCDot1xEntry 100663296}

sr1645v2Lan2MCDot1xHoldTime OBJECT-TYPE
   SYNTAX      TimeTicks
   MAX-ACCESS  read-only
   STATUS      current
   DESCRIPTION
      "Path: ethernet2.status.dot1x.holdTime

       Time in centi-second."
   ::= {sr1645v2Lan2MCDot1xEntry 117440512}


sr1645v2Lan2MCIpV6 OBJECT IDENTIFIER ::= {sr1645v2Lan2MC 17}

sr1645v2Lan2MCIpV6SSC OBJECT IDENTIFIER ::= {sr1645v2Lan2MCIpV6 1}

sr1645v2Lan2MCIpV6Entry OBJECT IDENTIFIER ::= {sr1645v2Lan2MCIpV6SSC 1}

sr1645v2Lan2MCIpV6State OBJECT-TYPE
   SYNTAX      INTEGER
               {
               disabled (0),
               enabled (1)
               }
   MAX-ACCESS  read-only
   STATUS      current
   DESCRIPTION
      "Path: ethernet2.status.ipV6.state

       Possibilities:
               disabled   (0)
               enabled   (1)"
   ::= {sr1645v2Lan2MCIpV6Entry 16777216}

sr1645v2Lan2MCIpV6InterfaceId OBJECT-TYPE
   SYNTAX      OCTET STRING
   MAX-ACCESS  read-only
   STATUS      current
   DESCRIPTION
      "Path: ethernet2.status.ipV6.interfaceId"
   ::= {sr1645v2Lan2MCIpV6Entry 33554432}

sr1645v2Lan2MCIpV6LinkMtu OBJECT-TYPE
   SYNTAX      Integer32
   MAX-ACCESS  read-only
   STATUS      current
   DESCRIPTION
      "Path: ethernet2.status.ipV6.linkMtu"
   ::= {sr1645v2Lan2MCIpV6Entry 67108864}

sr1645v2Lan2MCIpV6HopLimit OBJECT-TYPE
   SYNTAX      Integer32
   MAX-ACCESS  read-only
   STATUS      current
   DESCRIPTION
      "Path: ethernet2.status.ipV6.hopLimit"
   ::= {sr1645v2Lan2MCIpV6Entry 83886080}

sr1645v2Lan2MCIpV6DhcpIaid OBJECT-TYPE
   SYNTAX      Counter32
   MAX-ACCESS  read-only
   STATUS      current
   DESCRIPTION
      "Path: ethernet2.status.ipV6.dhcp.iaid

       32 bit unsigned wrappable counter."
   ::= {sr1645v2Lan2MCIpV6Entry 100728832}

sr1645v2Lan2MCIpV6RaRcvOption OBJECT-TYPE
   SYNTAX      Integer32
   MAX-ACCESS  read-only
   STATUS      current
   DESCRIPTION
      "Path: ethernet2.status.ipV6.raRcvOption

       Bit meanings:
               bit 0 = linkMtu,
               bit 1 = srcLinkLayer,
               bit 2 = prefixInfo,
               bit 3 = rdnss,
               bit 4 = dnssl"
   ::= {sr1645v2Lan2MCIpV6Entry 117440512}

sr1645v2Lan2MCIpV6Addresses OBJECT-TYPE
   SYNTAX      SEQUENCE OF Sr1645v2Lan2MCIpV6AddressesEntry
   MAX-ACCESS  not-accessible
   STATUS      current
   DESCRIPTION
      ""
   ::= {sr1645v2Lan2MCIpV6 50331648}

sr1645v2Lan2MCIpV6AddressesEntry OBJECT-TYPE
   SYNTAX      Sr1645v2Lan2MCIpV6AddressesEntry
   MAX-ACCESS  not-accessible
   STATUS      current
   DESCRIPTION
      ""
   INDEX      { sr1645v2Lan2MCIpV6AddressesTableIx }
   ::= {sr1645v2Lan2MCIpV6Addresses 1}

Sr1645v2Lan2MCIpV6AddressesEntry ::=
   SEQUENCE
      {
      sr1645v2Lan2MCIpV6AddressesTableIx
         TableIndex,
      sr1645v2Lan2MCIpV6AddressesAddress
         Ipv6Address,
      sr1645v2Lan2MCIpV6AddressesPrefixLength
         Integer32,
      sr1645v2Lan2MCIpV6AddressesStatus
         INTEGER,
      sr1645v2Lan2MCIpV6AddressesOrigin
         INTEGER,
      sr1645v2Lan2MCIpV6AddressesFlagsInterfaceId
         INTEGER,
      sr1645v2Lan2MCIpV6AddressesFlagsAnycast
         INTEGER,
      sr1645v2Lan2MCIpV6AddressesTimersValidLifeTime
         TimeTicks,
      sr1645v2Lan2MCIpV6AddressesTimersPrefLifeTime
         TimeTicks
      }

sr1645v2Lan2MCIpV6AddressesTableIx OBJECT-TYPE
   SYNTAX      TableIndex
   MAX-ACCESS  not-accessible
   STATUS      current
   DESCRIPTION
      ""
   ::= {sr1645v2Lan2MCIpV6AddressesEntry 11}

sr1645v2Lan2MCIpV6AddressesAddress OBJECT-TYPE
   SYNTAX      Ipv6Address
   MAX-ACCESS  read-only
   STATUS      current
   DESCRIPTION
      "Path: ethernet2.status.ipV6.addresses.address

       ipv6 address"
   ::= {sr1645v2Lan2MCIpV6AddressesEntry 16777216}

sr1645v2Lan2MCIpV6AddressesPrefixLength OBJECT-TYPE
   SYNTAX      Integer32
   MAX-ACCESS  read-only
   STATUS      current
   DESCRIPTION
      "Path: ethernet2.status.ipV6.addresses.prefixLength"
   ::= {sr1645v2Lan2MCIpV6AddressesEntry 33554432}

sr1645v2Lan2MCIpV6AddressesStatus OBJECT-TYPE
   SYNTAX      INTEGER
               {
               invalid (0),
               tentative (1),
               deprecated (2),
               preferred (3)
               }
   MAX-ACCESS  read-only
   STATUS      current
   DESCRIPTION
      "Path: ethernet2.status.ipV6.addresses.status

       Possibilities:
               invalid   (0)
               tentative   (1)
               deprecated   (2)
               preferred   (3)"
   ::= {sr1645v2Lan2MCIpV6AddressesEntry 50331648}

sr1645v2Lan2MCIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: ethernet2.status.ipV6.addresses.origin

       Possibilities:
               unknown   (0)
               manual   (1)
               generalPrefix   (2)
               statelessAuto   (3)
               statefullAuto   (4)"
   ::= {sr1645v2Lan2MCIpV6AddressesEntry 67108864}

sr1645v2Lan2MCIpV6AddressesFlagsInterfaceId OBJECT-TYPE
   SYNTAX      INTEGER
               {
               no (0),
               yes (1)
               }
   MAX-ACCESS  read-only
   STATUS      current
   DESCRIPTION
      "Path: ethernet2.status.ipV6.addresses.flags.interfaceId

       Possibilities:
               no   (0)
               yes   (1)"
   ::= {sr1645v2Lan2MCIpV6AddressesEntry 83951616}

sr1645v2Lan2MCIpV6AddressesFlagsAnycast OBJECT-TYPE
   SYNTAX      INTEGER
               {
               no (0),
               yes (1)
               }
   MAX-ACCESS  read-only
   STATUS      current
   DESCRIPTION
      "Path: ethernet2.status.ipV6.addresses.flags.anycast

       Possibilities:
               no   (0)
               yes   (1)"
   ::= {sr1645v2Lan2MCIpV6AddressesEntry 84017152}

sr1645v2Lan2MCIpV6AddressesTimersValidLifeTime OBJECT-TYPE
   SYNTAX      TimeTicks
   MAX-ACCESS  read-only
   STATUS      current
   DESCRIPTION
      "Path: ethernet2.status.ipV6.addresses.timers.validLifeTime

       Time in centi-second."
   ::= {sr1645v2Lan2MCIpV6AddressesEntry 100794368}

sr1645v2Lan2MCIpV6AddressesTimersPrefLifeTime OBJECT-TYPE
   SYNTAX      TimeTicks
   MAX-ACCESS  read-only
   STATUS      current
   DESCRIPTION
      "Path: ethernet2.status.ipV6.addresses.timers.prefLifeTime

       Time in centi-second."
   ::= {sr1645v2Lan2MCIpV6AddressesEntry 100728832}


sr1645v2Lan2MCMediaType OBJECT-TYPE
   SYNTAX      INTEGER
               {
               utp (1),
               sfp (2),
               down (255)
               }
   MAX-ACCESS  read-only
   STATUS      current
   DESCRIPTION
      "Path: ethernet2.status.mediaType

       Possibilities:
               utp   (1)
               sfp   (2)
               down   (255)"
   ::= {sr1645v2Lan2MC 500}



pr1645v2Lan2MC OBJECT IDENTIFIER ::= {r1645v2Lan2MC 12}


pr1645v2Lan2MCInOctets OBJECT-TYPE
   SYNTAX      Counter64
   MAX-ACCESS  read-only
   STATUS      current
   DESCRIPTION
      "Path: ethernet2.performance.ifInOctets
       Info: ifInOctets

       64 bit unsigned wrappable counter."
   ::= {pr1645v2Lan2MC 109}


pr1645v2Lan2MCInUcast OBJECT-TYPE
   SYNTAX      Counter64
   MAX-ACCESS  read-only
   STATUS      current
   DESCRIPTION
      "Path: ethernet2.performance.ifInUcastPkts
       Info: ifInUcastPkts

       64 bit unsigned wrappable counter."
   ::= {pr1645v2Lan2MC 110}


pr1645v2Lan2MCInNUcastPkts OBJECT-TYPE
   SYNTAX      Counter64
   MAX-ACCESS  read-only
   STATUS      current
   DESCRIPTION
      "Path: ethernet2.performance.ifInNUcastPkts
       Info: ifInNUcastPkts

       64 bit unsigned wrappable counter."
   ::= {pr1645v2Lan2MC 111}


pr1645v2Lan2MCInBcastPkts OBJECT-TYPE
   SYNTAX      Counter64
   MAX-ACCESS  read-only
   STATUS      current
   DESCRIPTION
      "Path: ethernet2.performance.ifInBcastPkts
       Info: ifInBcastPkts

       64 bit unsigned wrappable counter."
   ::= {pr1645v2Lan2MC 211}


pr1645v2Lan2MCInMcastPkts OBJECT-TYPE
   SYNTAX      Counter64
   MAX-ACCESS  read-only
   STATUS      current
   DESCRIPTION
      "Path: ethernet2.performance.ifInMcastPkts
       Info: ifInNUcastPkts

       64 bit unsigned wrappable counter."
   ::= {pr1645v2Lan2MC 221}


pr1645v2Lan2MCInDiscards OBJECT-TYPE
   SYNTAX      Counter64
   MAX-ACCESS  read-only
   STATUS      current
   DESCRIPTION
      "Path: ethernet2.performance.ifInDiscards
       Info: ifInDiscards

       64 bit unsigned wrappable counter."
   ::= {pr1645v2Lan2MC 112}


pr1645v2Lan2MCInErrors OBJECT-TYPE
   SYNTAX      Counter64
   MAX-ACCESS  read-only
   STATUS      current
   DESCRIPTION
      "Path: ethernet2.performance.ifInErrors
       Info: ifInErrors

       64 bit unsigned wrappable counter."
   ::= {pr1645v2Lan2MC 113}


pr1645v2Lan2MCInUnknownProtos OBJECT-TYPE
   SYNTAX      Counter64
   MAX-ACCESS  read-only
   STATUS      current
   DESCRIPTION
      "Path: ethernet2.performance.ifInUnknownProtos
       Info: ifInUnknownprotos

       64 bit unsigned wrappable counter."
   ::= {pr1645v2Lan2MC 114}


pr1645v2Lan2MCInQLen OBJECT-TYPE
   SYNTAX      Gauge32
   MAX-ACCESS  read-only
   STATUS      current
   DESCRIPTION
      "Path: ethernet2.performance.ifInQLen
       Info: ifInQLen

       32 bit unsigned gauge value."
   ::= {pr1645v2Lan2MC 128}


pr1645v2Lan2MCInDropEx OBJECT-TYPE
   SYNTAX      Counter64
   MAX-ACCESS  read-only
   STATUS      current
   DESCRIPTION
      "Path: ethernet2.performance.ifInDropLevelExceeded
       Info: ifInDiscards

       64 bit unsigned wrappable counter."
   ::= {pr1645v2Lan2MC 130}


pr1645v2Lan2MCInDropNoMac OBJECT-TYPE
   SYNTAX      Counter64
   MAX-ACCESS  read-only
   STATUS      current
   DESCRIPTION
      "Path: ethernet2.performance.ifInDiscardsNoMacFit
       Info: ifInDiscards

       64 bit unsigned wrappable counter."
   ::= {pr1645v2Lan2MC 133}


pr1645v2Lan2MCInDropNUCast OBJECT-TYPE
   SYNTAX      Counter64
   MAX-ACCESS  read-only
   STATUS      current
   DESCRIPTION
      "Path: ethernet2.performance.ifInDiscardsNUCast
       Info: ifInDiscards

       64 bit unsigned wrappable counter."
   ::= {pr1645v2Lan2MC 136}


pr1645v2Lan2MCInDropFilter OBJECT-TYPE
   SYNTAX      Counter64
   MAX-ACCESS  read-only
   STATUS      current
   DESCRIPTION
      "Path: ethernet2.performance.ifInDiscardsFilter
       Info: ifInDiscards

       64 bit unsigned wrappable counter."
   ::= {pr1645v2Lan2MC 137}


pr1645v2Lan2MCInQueues OBJECT IDENTIFIER ::= {pr1645v2Lan2MC 131}

pr1645v2Lan2MCInQueuesSSCTable OBJECT-TYPE
   SYNTAX      SEQUENCE OF Pr1645v2Lan2MCInQueuesEntry
   MAX-ACCESS  not-accessible
   STATUS      current
   DESCRIPTION
      "Queue Lengths"
   ::= {pr1645v2Lan2MCInQueues 1}

pr1645v2Lan2MCInQueuesEntry OBJECT-TYPE
   SYNTAX      Pr1645v2Lan2MCInQueuesEntry
   MAX-ACCESS  not-accessible
   STATUS      current
   DESCRIPTION
      ""
   INDEX      { pr1645v2Lan2MCInQueuesTableIx }
   ::= {pr1645v2Lan2MCInQueuesSSCTable 1}

Pr1645v2Lan2MCInQueuesEntry ::=
   SEQUENCE
      {
      pr1645v2Lan2MCInQueuesTableIx
         TableIndex,
      pr1645v2Lan2MCInQueuesName
         INTEGER,
      pr1645v2Lan2MCInQueuesLength
         Integer32,
      pr1645v2Lan2MCInQueuesOctetLength
         Integer32,
      pr1645v2Lan2MCInQueuesRedLength
         Integer32,
      pr1645v2Lan2MCInQueuesPacketsTotal
         Counter64,
      pr1645v2Lan2MCInQueuesPacketsDirectTx
         Counter64,
      pr1645v2Lan2MCInQueuesPacketsQueued
         Counter64,
      pr1645v2Lan2MCInQueuesPacketsDropped
         Counter64,
      pr1645v2Lan2MCInQueuesPacketsRedDropped
         Counter64,
      pr1645v2Lan2MCInQueuesPacketsCirTx
         Counter64,
      pr1645v2Lan2MCInQueuesPacketsEirTx
         Counter64,
      pr1645v2Lan2MCInQueuesPacketsViolateTx
         Counter64,
      pr1645v2Lan2MCInQueuesOctetsTotal
         Counter64,
      pr1645v2Lan2MCInQueuesOctetsDirectTx
         Counter64,
      pr1645v2Lan2MCInQueuesOctetsQueued
         Counter64,
      pr1645v2Lan2MCInQueuesOctetsDropped
         Counter64,
      pr1645v2Lan2MCInQueuesOctetsRedDropped
         Counter64,
      pr1645v2Lan2MCInQueuesOctetsCirTx
         Counter64,
      pr1645v2Lan2MCInQueuesOctetsEirTx
         Counter64,
      pr1645v2Lan2MCInQueuesOctetsViolateTx
         Counter64,
      pr1645v2Lan2MCInQueuesOctetsBandwidth15sec
         Integer32,
      pr1645v2Lan2MCInQueuesOctetsBandwidth30sec
         Integer32,
      pr1645v2Lan2MCInQueuesOctetsBandwidth1min
         Integer32,
      pr1645v2Lan2MCInQueuesOctetsBandwidth2min
         Integer32,
      pr1645v2Lan2MCInQueuesOctetsBandwidth5min
         Integer32
      }

pr1645v2Lan2MCInQueuesTableIx OBJECT-TYPE
   SYNTAX      TableIndex
   MAX-ACCESS  not-accessible
   STATUS      current
   DESCRIPTION
      ""
   ::= {pr1645v2Lan2MCInQueuesEntry 11}

pr1645v2Lan2MCInQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifInPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2MCInQueuesEntry 16777216}

pr1645v2Lan2MCInQueuesLength OBJECT-TYPE
   SYNTAX      Integer32
   MAX-ACCESS  read-only
   STATUS      current
   DESCRIPTION
      "Path: ethernet2.performance.ifInPriorityQueues.length"
   ::= {pr1645v2Lan2MCInQueuesEntry 33554432}

pr1645v2Lan2MCInQueuesOctetLength OBJECT-TYPE
   SYNTAX      Integer32
   MAX-ACCESS  read-only
   STATUS      current
   DESCRIPTION
      "Path: ethernet2.performance.ifInPriorityQueues.octetLength"
   ::= {pr1645v2Lan2MCInQueuesEntry 150994944}

pr1645v2Lan2MCInQueuesRedLength OBJECT-TYPE
   SYNTAX      Integer32
   MAX-ACCESS  read-only
   STATUS      current
   DESCRIPTION
      "Path: ethernet2.performance.ifInPriorityQueues.redLength"
   ::= {pr1645v2Lan2MCInQueuesEntry 134217728}

pr1645v2Lan2MCInQueuesPacketsTotal OBJECT-TYPE
   SYNTAX      Counter64
   MAX-ACCESS  read-only
   STATUS      current
   DESCRIPTION
      "Path: ethernet2.performance.ifInPriorityQueues.packets.total

       64 bit unsigned wrappable counter."
   ::= {pr1645v2Lan2MCInQueuesEntry 50790400}

pr1645v2Lan2MCInQueuesPacketsDirectTx OBJECT-TYPE
   SYNTAX      Counter64
   MAX-ACCESS  read-only
   STATUS      current
   DESCRIPTION
      "Path: ethernet2.performance.ifInPriorityQueues.packets.directTx

       64 bit unsigned wrappable counter."
   ::= {pr1645v2Lan2MCInQueuesEntry 50397184}

pr1645v2Lan2MCInQueuesPacketsQueued OBJECT-TYPE
   SYNTAX      Counter64
   MAX-ACCESS  read-only
   STATUS      current
   DESCRIPTION
      "Path: ethernet2.performance.ifInPriorityQueues.packets.queued

       64 bit unsigned wrappable counter."
   ::= {pr1645v2Lan2MCInQueuesEntry 50462720}

pr1645v2Lan2MCInQueuesPacketsDropped OBJECT-TYPE
   SYNTAX      Counter64
   MAX-ACCESS  read-only
   STATUS      current
   DESCRIPTION
      "Path: ethernet2.performance.ifInPriorityQueues.packets.dropped

       64 bit unsigned wrappable counter."
   ::= {pr1645v2Lan2MCInQueuesEntry 50528256}

pr1645v2Lan2MCInQueuesPacketsRedDropped OBJECT-TYPE
   SYNTAX      Counter64
   MAX-ACCESS  read-only
   STATUS      current
   DESCRIPTION
      "Path: ethernet2.performance.ifInPriorityQueues.packets.redDropped

       64 bit unsigned wrappable counter."
   ::= {pr1645v2Lan2MCInQueuesEntry 50724864}

pr1645v2Lan2MCInQueuesPacketsCirTx OBJECT-TYPE
   SYNTAX      Counter64
   MAX-ACCESS  read-only
   STATUS      current
   DESCRIPTION
      "Path: ethernet2.performance.ifInPriorityQueues.packets.cirTx

       64 bit unsigned wrappable counter."
   ::= {pr1645v2Lan2MCInQueuesEntry 50593792}

pr1645v2Lan2MCInQueuesPacketsEirTx OBJECT-TYPE
   SYNTAX      Counter64
   MAX-ACCESS  read-only
   STATUS      current
   DESCRIPTION
      "Path: ethernet2.performance.ifInPriorityQueues.packets.eirTx

       64 bit unsigned wrappable counter."
   ::= {pr1645v2Lan2MCInQueuesEntry 50659328}

pr1645v2Lan2MCInQueuesPacketsViolateTx OBJECT-TYPE
   SYNTAX      Counter64
   MAX-ACCESS  read-only
   STATUS      current
   DESCRIPTION
      "Path: ethernet2.performance.ifInPriorityQueues.packets.violateTx

       64 bit unsigned wrappable counter."
   ::= {pr1645v2Lan2MCInQueuesEntry 50855936}

pr1645v2Lan2MCInQueuesOctetsTotal OBJECT-TYPE
   SYNTAX      Counter64
   MAX-ACCESS  read-only
   STATUS      current
   DESCRIPTION
      "Path: ethernet2.performance.ifInPriorityQueues.octets.total

       64 bit unsigned wrappable counter."
   ::= {pr1645v2Lan2MCInQueuesEntry 67567616}

pr1645v2Lan2MCInQueuesOctetsDirectTx OBJECT-TYPE
   SYNTAX      Counter64
   MAX-ACCESS  read-only
   STATUS      current
   DESCRIPTION
      "Path: ethernet2.performance.ifInPriorityQueues.octets.directTx

       64 bit unsigned wrappable counter."
   ::= {pr1645v2Lan2MCInQueuesEntry 67174400}

pr1645v2Lan2MCInQueuesOctetsQueued OBJECT-TYPE
   SYNTAX      Counter64
   MAX-ACCESS  read-only
   STATUS      current
   DESCRIPTION
      "Path: ethernet2.performance.ifInPriorityQueues.octets.queued

       64 bit unsigned wrappable counter."
   ::= {pr1645v2Lan2MCInQueuesEntry 67239936}

pr1645v2Lan2MCInQueuesOctetsDropped OBJECT-TYPE
   SYNTAX      Counter64
   MAX-ACCESS  read-only
   STATUS      current
   DESCRIPTION
      "Path: ethernet2.performance.ifInPriorityQueues.octets.dropped

       64 bit unsigned wrappable counter."
   ::= {pr1645v2Lan2MCInQueuesEntry 67305472}

pr1645v2Lan2MCInQueuesOctetsRedDropped OBJECT-TYPE
   SYNTAX      Counter64
   MAX-ACCESS  read-only
   STATUS      current
   DESCRIPTION
      "Path: ethernet2.performance.ifInPriorityQueues.octets.redDropped

       64 bit unsigned wrappable counter."
   ::= {pr1645v2Lan2MCInQueuesEntry 67502080}

pr1645v2Lan2MCInQueuesOctetsCirTx OBJECT-TYPE
   SYNTAX      Counter64
   MAX-ACCESS  read-only
   STATUS      current
   DESCRIPTION
      "Path: ethernet2.performance.ifInPriorityQueues.octets.cirTx

       64 bit unsigned wrappable counter."
   ::= {pr1645v2Lan2MCInQueuesEntry 67371008}

pr1645v2Lan2MCInQueuesOctetsEirTx OBJECT-TYPE
   SYNTAX      Counter64
   MAX-ACCESS  read-only
   STATUS      current
   DESCRIPTION
      "Path: ethernet2.performance.ifInPriorityQueues.octets.eirTx

       64 bit unsigned wrappable counter."
   ::= {pr1645v2Lan2MCInQueuesEntry 67436544}

pr1645v2Lan2MCInQueuesOctetsViolateTx OBJECT-TYPE
   SYNTAX      Counter64
   MAX-ACCESS  read-only
   STATUS      current
   DESCRIPTION
      "Path: ethernet2.performance.ifInPriorityQueues.octets.violateTx

       64 bit unsigned wrappable counter."
   ::= {pr1645v2Lan2MCInQueuesEntry 67633152}

pr1645v2Lan2MCInQueuesOctetsBandwidth15sec OBJECT-TYPE
   SYNTAX      Integer32
   MAX-ACCESS  read-only
   STATUS      current
   DESCRIPTION
      "Path: ethernet2.performance.ifInPriorityQueues.octets.bandwidth.15sec

       unit name = bps
       formula = 8 * ; 8 /"
   ::= {pr1645v2Lan2MCInQueuesEntry 70386944}

pr1645v2Lan2MCInQueuesOctetsBandwidth30sec OBJECT-TYPE
   SYNTAX      Integer32
   MAX-ACCESS  read-only
   STATUS      current
   DESCRIPTION
      "Path: ethernet2.performance.ifInPriorityQueues.octets.bandwidth.30sec

       unit name = bps
       formula = 8 * ; 8 /"
   ::= {pr1645v2Lan2MCInQueuesEntry 70388224}

pr1645v2Lan2MCInQueuesOctetsBandwidth1min OBJECT-TYPE
   SYNTAX      Integer32
   MAX-ACCESS  read-only
   STATUS      current
   DESCRIPTION
      "Path: ethernet2.performance.ifInPriorityQueues.octets.bandwidth.1min

       unit name = bps
       formula = 8 * ; 8 /"
   ::= {pr1645v2Lan2MCInQueuesEntry 70390784}

pr1645v2Lan2MCInQueuesOctetsBandwidth2min OBJECT-TYPE
   SYNTAX      Integer32
   MAX-ACCESS  read-only
   STATUS      current
   DESCRIPTION
      "Path: ethernet2.performance.ifInPriorityQueues.octets.bandwidth.2min

       unit name = bps
       formula = 8 * ; 8 /"
   ::= {pr1645v2Lan2MCInQueuesEntry 70395904}

pr1645v2Lan2MCInQueuesOctetsBandwidth5min OBJECT-TYPE
   SYNTAX      Integer32
   MAX-ACCESS  read-only
   STATUS      current
   DESCRIPTION
      "Path: ethernet2.performance.ifInPriorityQueues.octets.bandwidth.5min

       unit name = bps
       formula = 8 * ; 8 /"
   ::= {pr1645v2Lan2MCInQueuesEntry 70411264}

pr1645v2Lan2MCInQueuesH2Performance OBJECT-TYPE
   SYNTAX      SEQUENCE OF Pr1645v2Lan2MCInQueuesH2PerformanceEntry
   MAX-ACCESS  not-accessible
   STATUS      current
   DESCRIPTION
      ""
   ::= {pr1645v2Lan2MCInQueues 83886080}

pr1645v2Lan2MCInQueuesH2PerformanceEntry OBJECT-TYPE
   SYNTAX      Pr1645v2Lan2MCInQueuesH2PerformanceEntry
   MAX-ACCESS  not-accessible
   STATUS      current
   DESCRIPTION
      ""
   INDEX      { pr1645v2Lan2MCInQueuesTableIx,
                pr1645v2Lan2MCInQueuesH2PerformanceTableIx }
   ::= {pr1645v2Lan2MCInQueuesH2Performance 1}

Pr1645v2Lan2MCInQueuesH2PerformanceEntry ::=
   SEQUENCE
      {
      pr1645v2Lan2MCInQueuesH2PerformanceTableIx
         TableIndex,
      pr1645v2Lan2MCInQueuesH2PerformanceSysUpTime
         TimeTicks,
      pr1645v2Lan2MCInQueuesH2PerformanceTotPkts
         Counter64,
      pr1645v2Lan2MCInQueuesH2PerformanceDirTxPkts
         Counter64,
      pr1645v2Lan2MCInQueuesH2PerformanceQdPkts
         Counter64,
      pr1645v2Lan2MCInQueuesH2PerformanceDropPkts
         Counter64,
      pr1645v2Lan2MCInQueuesH2PerformanceRDropPkts
         Counter64,
      pr1645v2Lan2MCInQueuesH2PerformanceCirTxPkts
         Counter64,
      pr1645v2Lan2MCInQueuesH2PerformanceEirTxPkts
         Counter64,
      pr1645v2Lan2MCInQueuesH2PerformanceViolTxPkts
         Counter64,
      pr1645v2Lan2MCInQueuesH2PerformanceTotOcts
         Counter64,
      pr1645v2Lan2MCInQueuesH2PerformanceDirTxOcts
         Counter64,
      pr1645v2Lan2MCInQueuesH2PerformanceQdOcts
         Counter64,
      pr1645v2Lan2MCInQueuesH2PerformanceDropOcts
         Counter64,
      pr1645v2Lan2MCInQueuesH2PerformanceRDropOcts
         Counter64,
      pr1645v2Lan2MCInQueuesH2PerformanceCirTxOcts
         Counter64,
      pr1645v2Lan2MCInQueuesH2PerformanceEirTxOcts
         Counter64,
      pr1645v2Lan2MCInQueuesH2PerformanceViolTxOcts
         Counter64,
      pr1645v2Lan2MCInQueuesH2PerformanceBandwidth
         Integer32
      }

pr1645v2Lan2MCInQueuesH2PerformanceTableIx OBJECT-TYPE
   SYNTAX      TableIndex
   MAX-ACCESS  not-accessible
   STATUS      current
   DESCRIPTION
      ""
   ::= {pr1645v2Lan2MCInQueuesH2PerformanceEntry 11}

pr1645v2Lan2MCInQueuesH2PerformanceSysUpTime OBJECT-TYPE
   SYNTAX      TimeTicks
   MAX-ACCESS  read-only
   STATUS      current
   DESCRIPTION
      "Path: ethernet2.performance.ifInPriorityQueues.h2Performance.sysUpTime

       Time in centi-second."
   ::= {pr1645v2Lan2MCInQueuesH2PerformanceEntry 16777216}

pr1645v2Lan2MCInQueuesH2PerformanceTotPkts OBJECT-TYPE
   SYNTAX      Counter64
   MAX-ACCESS  read-only
   STATUS      current
   DESCRIPTION
      "Path: ethernet2.performance.ifInPriorityQueues.h2Performance.totalPkts

       64 bit unsigned wrappable counter."
   ::= {pr1645v2Lan2MCInQueuesH2PerformanceEntry 234881024}

pr1645v2Lan2MCInQueuesH2PerformanceDirTxPkts OBJECT-TYPE
   SYNTAX      Counter64
   MAX-ACCESS  read-only
   STATUS      current
   DESCRIPTION
      "Path: ethernet2.performance.ifInPriorityQueues.h2Performance.directTxPkts

       64 bit unsigned wrappable counter."
   ::= {pr1645v2Lan2MCInQueuesH2PerformanceEntry 33554432}

pr1645v2Lan2MCInQueuesH2PerformanceQdPkts OBJECT-TYPE
   SYNTAX      Counter64
   MAX-ACCESS  read-only
   STATUS      current
   DESCRIPTION
      "Path: ethernet2.performance.ifInPriorityQueues.h2Performance.queuedPkts

       64 bit unsigned wrappable counter."
   ::= {pr1645v2Lan2MCInQueuesH2PerformanceEntry 50331648}

pr1645v2Lan2MCInQueuesH2PerformanceDropPkts OBJECT-TYPE
   SYNTAX      Counter64
   MAX-ACCESS  read-only
   STATUS      current
   DESCRIPTION
      "Path: ethernet2.performance.ifInPriorityQueues.h2Performance.droppedPkts

       64 bit unsigned wrappable counter."
   ::= {pr1645v2Lan2MCInQueuesH2PerformanceEntry 67108864}

pr1645v2Lan2MCInQueuesH2PerformanceRDropPkts OBJECT-TYPE
   SYNTAX      Counter64
   MAX-ACCESS  read-only
   STATUS      current
   DESCRIPTION
      "Path: ethernet2.performance.ifInPriorityQueues.h2Performance.redDroppedPkts

       64 bit unsigned wrappable counter."
   ::= {pr1645v2Lan2MCInQueuesH2PerformanceEntry 201326592}

pr1645v2Lan2MCInQueuesH2PerformanceCirTxPkts OBJECT-TYPE
   SYNTAX      Counter64
   MAX-ACCESS  read-only
   STATUS      current
   DESCRIPTION
      "Path: ethernet2.performance.ifInPriorityQueues.h2Performance.cirTxPkts

       64 bit unsigned wrappable counter."
   ::= {pr1645v2Lan2MCInQueuesH2PerformanceEntry 83886080}

pr1645v2Lan2MCInQueuesH2PerformanceEirTxPkts OBJECT-TYPE
   SYNTAX      Counter64
   MAX-ACCESS  read-only
   STATUS      current
   DESCRIPTION
      "Path: ethernet2.performance.ifInPriorityQueues.h2Performance.eirTxPkts

       64 bit unsigned wrappable counter."
   ::= {pr1645v2Lan2MCInQueuesH2PerformanceEntry 100663296}

pr1645v2Lan2MCInQueuesH2PerformanceViolTxPkts OBJECT-TYPE
   SYNTAX      Counter64
   MAX-ACCESS  read-only
   STATUS      current
   DESCRIPTION
      "Path: ethernet2.performance.ifInPriorityQueues.h2Performance.violateTxPkts

       64 bit unsigned wrappable counter."
   ::= {pr1645v2Lan2MCInQueuesH2PerformanceEntry 301989888}

pr1645v2Lan2MCInQueuesH2PerformanceTotOcts OBJECT-TYPE
   SYNTAX      Counter64
   MAX-ACCESS  read-only
   STATUS      current
   DESCRIPTION
      "Path: ethernet2.performance.ifInPriorityQueues.h2Performance.totalOctets

       64 bit unsigned wrappable counter."
   ::= {pr1645v2Lan2MCInQueuesH2PerformanceEntry 251658240}

pr1645v2Lan2MCInQueuesH2PerformanceDirTxOcts OBJECT-TYPE
   SYNTAX      Counter64
   MAX-ACCESS  read-only
   STATUS      current
   DESCRIPTION
      "Path: ethernet2.performance.ifInPriorityQueues.h2Performance.directTxOctets

       64 bit unsigned wrappable counter."
   ::= {pr1645v2Lan2MCInQueuesH2PerformanceEntry 117440512}

pr1645v2Lan2MCInQueuesH2PerformanceQdOcts OBJECT-TYPE
   SYNTAX      Counter64
   MAX-ACCESS  read-only
   STATUS      current
   DESCRIPTION
      "Path: ethernet2.performance.ifInPriorityQueues.h2Performance.queuedOctets

       64 bit unsigned wrappable counter."
   ::= {pr1645v2Lan2MCInQueuesH2PerformanceEntry 134217728}

pr1645v2Lan2MCInQueuesH2PerformanceDropOcts OBJECT-TYPE
   SYNTAX      Counter64
   MAX-ACCESS  read-only
   STATUS      current
   DESCRIPTION
      "Path: ethernet2.performance.ifInPriorityQueues.h2Performance.droppedOctets

       64 bit unsigned wrappable counter."
   ::= {pr1645v2Lan2MCInQueuesH2PerformanceEntry 150994944}

pr1645v2Lan2MCInQueuesH2PerformanceRDropOcts OBJECT-TYPE
   SYNTAX      Counter64
   MAX-ACCESS  read-only
   STATUS      current
   DESCRIPTION
      "Path: ethernet2.performance.ifInPriorityQueues.h2Performance.redDroppedOctets

       64 bit unsigned wrappable counter."
   ::= {pr1645v2Lan2MCInQueuesH2PerformanceEntry 218103808}

pr1645v2Lan2MCInQueuesH2PerformanceCirTxOcts OBJECT-TYPE
   SYNTAX      Counter64
   MAX-ACCESS  read-only
   STATUS      current
   DESCRIPTION
      "Path: ethernet2.performance.ifInPriorityQueues.h2Performance.cirTxOctets

       64 bit unsigned wrappable counter."
   ::= {pr1645v2Lan2MCInQueuesH2PerformanceEntry 167772160}

pr1645v2Lan2MCInQueuesH2PerformanceEirTxOcts OBJECT-TYPE
   SYNTAX      Counter64
   MAX-ACCESS  read-only
   STATUS      current
   DESCRIPTION
      "Path: ethernet2.performance.ifInPriorityQueues.h2Performance.eirTxOctets

       64 bit unsigned wrappable counter."
   ::= {pr1645v2Lan2MCInQueuesH2PerformanceEntry 184549376}

pr1645v2Lan2MCInQueuesH2PerformanceViolTxOcts OBJECT-TYPE
   SYNTAX      Counter64
   MAX-ACCESS  read-only
   STATUS      current
   DESCRIPTION
      "Path: ethernet2.performance.ifInPriorityQueues.h2Performance.violateTxOctets

       64 bit unsigned wrappable counter."
   ::= {pr1645v2Lan2MCInQueuesH2PerformanceEntry 318767104}

pr1645v2Lan2MCInQueuesH2PerformanceBandwidth OBJECT-TYPE
   SYNTAX      Integer32
   MAX-ACCESS  read-only
   STATUS      current
   DESCRIPTION
      "Path: ethernet2.performance.ifInPriorityQueues.h2Performance.bandwidth

       unit name = bps
       formula = 8 * ; 8 /"
   ::= {pr1645v2Lan2MCInQueuesH2PerformanceEntry 268435456}

pr1645v2Lan2MCInQueuesH24Performance OBJECT-TYPE
   SYNTAX      SEQUENCE OF Pr1645v2Lan2MCInQueuesH24PerformanceEntry
   MAX-ACCESS  not-accessible
   STATUS      current
   DESCRIPTION
      ""
   ::= {pr1645v2Lan2MCInQueues 100663296}

pr1645v2Lan2MCInQueuesH24PerformanceEntry OBJECT-TYPE
   SYNTAX      Pr1645v2Lan2MCInQueuesH24PerformanceEntry
   MAX-ACCESS  not-accessible
   STATUS      current
   DESCRIPTION
      ""
   INDEX      { pr1645v2Lan2MCInQueuesTableIx,
                pr1645v2Lan2MCInQueuesH24PerformanceTableIx }
   ::= {pr1645v2Lan2MCInQueuesH24Performance 1}

Pr1645v2Lan2MCInQueuesH24PerformanceEntry ::=
   SEQUENCE
      {
      pr1645v2Lan2MCInQueuesH24PerformanceTableIx
         TableIndex,
      pr1645v2Lan2MCInQueuesH24PerformanceSysUpTime
         TimeTicks,
      pr1645v2Lan2MCInQueuesH24PerformanceTotPkts
         Counter64,
      pr1645v2Lan2MCInQueuesH24PerformanceDirTxPkts
         Counter64,
      pr1645v2Lan2MCInQueuesH24PerformanceQdPkts
         Counter64,
      pr1645v2Lan2MCInQueuesH24PerformanceDropPkts
         Counter64,
      pr1645v2Lan2MCInQueuesH24PerformanceRDropPkts
         Counter64,
      pr1645v2Lan2MCInQueuesH24PerformanceCirTxPkts
         Counter64,
      pr1645v2Lan2MCInQueuesH24PerformanceEirTxPkts
         Counter64,
      pr1645v2Lan2MCInQueuesH24PerformanceViolTxPkts
         Counter64,
      pr1645v2Lan2MCInQueuesH24PerformanceTotOcts
         Counter64,
      pr1645v2Lan2MCInQueuesH24PerformanceDirTxOcts
         Counter64,
      pr1645v2Lan2MCInQueuesH24PerformanceQdOcts
         Counter64,
      pr1645v2Lan2MCInQueuesH24PerformanceDropOcts
         Counter64,
      pr1645v2Lan2MCInQueuesH24PerformanceRDropOcts
         Counter64,
      pr1645v2Lan2MCInQueuesH24PerformanceCirTxOcts
         Counter64,
      pr1645v2Lan2MCInQueuesH24PerformanceEirTxOcts
         Counter64,
      pr1645v2Lan2MCInQueuesH24PerformanceViolTxOcts
         Counter64,
      pr1645v2Lan2MCInQueuesH24PerformanceBandwidth
         Integer32
      }

pr1645v2Lan2MCInQueuesH24PerformanceTableIx OBJECT-TYPE
   SYNTAX      TableIndex
   MAX-ACCESS  not-accessible
   STATUS      current
   DESCRIPTION
      ""
   ::= {pr1645v2Lan2MCInQueuesH24PerformanceEntry 11}

pr1645v2Lan2MCInQueuesH24PerformanceSysUpTime OBJECT-TYPE
   SYNTAX      TimeTicks
   MAX-ACCESS  read-only
   STATUS      current
   DESCRIPTION
      "Path: ethernet2.performance.ifInPriorityQueues.h24Performance.sysUpTime

       Time in centi-second."
   ::= {pr1645v2Lan2MCInQueuesH24PerformanceEntry 16777216}

pr1645v2Lan2MCInQueuesH24PerformanceTotPkts OBJECT-TYPE
   SYNTAX      Counter64
   MAX-ACCESS  read-only
   STATUS      current
   DESCRIPTION
      "Path: ethernet2.performance.ifInPriorityQueues.h24Performance.totalPkts

       64 bit unsigned wrappable counter."
   ::= {pr1645v2Lan2MCInQueuesH24PerformanceEntry 234881024}

pr1645v2Lan2MCInQueuesH24PerformanceDirTxPkts OBJECT-TYPE
   SYNTAX      Counter64
   MAX-ACCESS  read-only
   STATUS      current
   DESCRIPTION
      "Path: ethernet2.performance.ifInPriorityQueues.h24Performance.directTxPkts

       64 bit unsigned wrappable counter."
   ::= {pr1645v2Lan2MCInQueuesH24PerformanceEntry 33554432}

pr1645v2Lan2MCInQueuesH24PerformanceQdPkts OBJECT-TYPE
   SYNTAX      Counter64
   MAX-ACCESS  read-only
   STATUS      current
   DESCRIPTION
      "Path: ethernet2.performance.ifInPriorityQueues.h24Performance.queuedPkts

       64 bit unsigned wrappable counter."
   ::= {pr1645v2Lan2MCInQueuesH24PerformanceEntry 50331648}

pr1645v2Lan2MCInQueuesH24PerformanceDropPkts OBJECT-TYPE
   SYNTAX      Counter64
   MAX-ACCESS  read-only
   STATUS      current
   DESCRIPTION
      "Path: ethernet2.performance.ifInPriorityQueues.h24Performance.droppedPkts

       64 bit unsigned wrappable counter."
   ::= {pr1645v2Lan2MCInQueuesH24PerformanceEntry 67108864}

pr1645v2Lan2MCInQueuesH24PerformanceRDropPkts OBJECT-TYPE
   SYNTAX      Counter64
   MAX-ACCESS  read-only
   STATUS      current
   DESCRIPTION
      "Path: ethernet2.performance.ifInPriorityQueues.h24Performance.redDroppedPkts

       64 bit unsigned wrappable counter."
   ::= {pr1645v2Lan2MCInQueuesH24PerformanceEntry 201326592}

pr1645v2Lan2MCInQueuesH24PerformanceCirTxPkts OBJECT-TYPE
   SYNTAX      Counter64
   MAX-ACCESS  read-only
   STATUS      current
   DESCRIPTION
      "Path: ethernet2.performance.ifInPriorityQueues.h24Performance.cirTxPkts

       64 bit unsigned wrappable counter."
   ::= {pr1645v2Lan2MCInQueuesH24PerformanceEntry 83886080}

pr1645v2Lan2MCInQueuesH24PerformanceEirTxPkts OBJECT-TYPE
   SYNTAX      Counter64
   MAX-ACCESS  read-only
   STATUS      current
   DESCRIPTION
      "Path: ethernet2.performance.ifInPriorityQueues.h24Performance.eirTxPkts

       64 bit unsigned wrappable counter."
   ::= {pr1645v2Lan2MCInQueuesH24PerformanceEntry 100663296}

pr1645v2Lan2MCInQueuesH24PerformanceViolTxPkts OBJECT-TYPE
   SYNTAX      Counter64
   MAX-ACCESS  read-only
   STATUS      current
   DESCRIPTION
      "Path: ethernet2.performance.ifInPriorityQueues.h24Performance.violateTxPkts

       64 bit unsigned wrappable counter."
   ::= {pr1645v2Lan2MCInQueuesH24PerformanceEntry 301989888}

pr1645v2Lan2MCInQueuesH24PerformanceTotOcts OBJECT-TYPE
   SYNTAX      Counter64
   MAX-ACCESS  read-only
   STATUS      current
   DESCRIPTION
      "Path: ethernet2.performance.ifInPriorityQueues.h24Performance.totalOctets

       64 bit unsigned wrappable counter."
   ::= {pr1645v2Lan2MCInQueuesH24PerformanceEntry 251658240}

pr1645v2Lan2MCInQueuesH24PerformanceDirTxOcts OBJECT-TYPE
   SYNTAX      Counter64
   MAX-ACCESS  read-only
   STATUS      current
   DESCRIPTION
      "Path: ethernet2.performance.ifInPriorityQueues.h24Performance.directTxOctets

       64 bit unsigned wrappable counter."
   ::= {pr1645v2Lan2MCInQueuesH24PerformanceEntry 117440512}

pr1645v2Lan2MCInQueuesH24PerformanceQdOcts OBJECT-TYPE
   SYNTAX      Counter64
   MAX-ACCESS  read-only
   STATUS      current
   DESCRIPTION
      "Path: ethernet2.performance.ifInPriorityQueues.h24Performance.queuedOctets

       64 bit unsigned wrappable counter."
   ::= {pr1645v2Lan2MCInQueuesH24PerformanceEntry 134217728}

pr1645v2Lan2MCInQueuesH24PerformanceDropOcts OBJECT-TYPE
   SYNTAX      Counter64
   MAX-ACCESS  read-only
   STATUS      current
   DESCRIPTION
      "Path: ethernet2.performance.ifInPriorityQueues.h24Performance.droppedOctets

       64 bit unsigned wrappable counter."
   ::= {pr1645v2Lan2MCInQueuesH24PerformanceEntry 150994944}

pr1645v2Lan2MCInQueuesH24PerformanceRDropOcts OBJECT-TYPE
   SYNTAX      Counter64
   MAX-ACCESS  read-only
   STATUS      current
   DESCRIPTION
      "Path: ethernet2.performance.ifInPriorityQueues.h24Performance.redDroppedOctets

       64 bit unsigned wrappable counter."
   ::= {pr1645v2Lan2MCInQueuesH24PerformanceEntry 218103808}

pr1645v2Lan2MCInQueuesH24PerformanceCirTxOcts OBJECT-TYPE
   SYNTAX      Counter64
   MAX-ACCESS  read-only
   STATUS      current
   DESCRIPTION
      "Path: ethernet2.performance.ifInPriorityQueues.h24Performance.cirTxOctets

       64 bit unsigned wrappable counter."
   ::= {pr1645v2Lan2MCInQueuesH24PerformanceEntry 167772160}

pr1645v2Lan2MCInQueuesH24PerformanceEirTxOcts OBJECT-TYPE
   SYNTAX      Counter64
   MAX-ACCESS  read-only
   STATUS      current
   DESCRIPTION
      "Path: ethernet2.performance.ifInPriorityQueues.h24Performance.eirTxOctets

       64 bit unsigned wrappable counter."
   ::= {pr1645v2Lan2MCInQueuesH24PerformanceEntry 184549376}

pr1645v2Lan2MCInQueuesH24PerformanceViolTxOcts OBJECT-TYPE
   SYNTAX      Counter64
   MAX-ACCESS  read-only
   STATUS      current
   DESCRIPTION
      "Path: ethernet2.performance.ifInPriorityQueues.h24Performance.violateTxOctets

       64 bit unsigned wrappable counter."
   ::= {pr1645v2Lan2MCInQueuesH24PerformanceEntry 318767104}

pr1645v2Lan2MCInQueuesH24PerformanceBandwidth OBJECT-TYPE
   SYNTAX      Integer32
   MAX-ACCESS  read-only
   STATUS      current
   DESCRIPTION
      "Path: ethernet2.performance.ifInPriorityQueues.h24Performance.bandwidth

       unit name = bps
       formula = 8 * ; 8 /"
   ::= {pr1645v2Lan2MCInQueuesH24PerformanceEntry 268435456}

pr1645v2Lan2MCInQueuesD7Performance OBJECT-TYPE
   SYNTAX      SEQUENCE OF Pr1645v2Lan2MCInQueuesD7PerformanceEntry
   MAX-ACCESS  not-accessible
   STATUS      current
   DESCRIPTION
      ""
   ::= {pr1645v2Lan2MCInQueues 117440512}

pr1645v2Lan2MCInQueuesD7PerformanceEntry OBJECT-TYPE
   SYNTAX      Pr1645v2Lan2MCInQueuesD7PerformanceEntry
   MAX-ACCESS  not-accessible
   STATUS      current
   DESCRIPTION
      ""
   INDEX      { pr1645v2Lan2MCInQueuesTableIx,
                pr1645v2Lan2MCInQueuesD7PerformanceTableIx }
   ::= {pr1645v2Lan2MCInQueuesD7Performance 1}

Pr1645v2Lan2MCInQueuesD7PerformanceEntry ::=
   SEQUENCE
      {
      pr1645v2Lan2MCInQueuesD7PerformanceTableIx
         TableIndex,
      pr1645v2Lan2MCInQueuesD7PerformanceSysUpTime
         TimeTicks,
      pr1645v2Lan2MCInQueuesD7PerformanceTotPkts
         Counter64,
      pr1645v2Lan2MCInQueuesD7PerformanceDirTxPkts
         Counter64,
      pr1645v2Lan2MCInQueuesD7PerformanceQdPkts
         Counter64,
      pr1645v2Lan2MCInQueuesD7PerformanceDropPkts
         Counter64,
      pr1645v2Lan2MCInQueuesD7PerformanceRDropPkts
         Counter64,
      pr1645v2Lan2MCInQueuesD7PerformanceCirTxPkts
         Counter64,
      pr1645v2Lan2MCInQueuesD7PerformanceEirTxPkts
         Counter64,
      pr1645v2Lan2MCInQueuesD7PerformanceViolTxPkts
         Counter64,
      pr1645v2Lan2MCInQueuesD7PerformanceTotOcts
         Counter64,
      pr1645v2Lan2MCInQueuesD7PerformanceDirTxOcts
         Counter64,
      pr1645v2Lan2MCInQueuesD7PerformanceQdOcts
         Counter64,
      pr1645v2Lan2MCInQueuesD7PerformanceDropOcts
         Counter64,
      pr1645v2Lan2MCInQueuesD7PerformanceRDropOcts
         Counter64,
      pr1645v2Lan2MCInQueuesD7PerformanceCirTxOcts
         Counter64,
      pr1645v2Lan2MCInQueuesD7PerformanceEirTxOcts
         Counter64,
      pr1645v2Lan2MCInQueuesD7PerformanceViolTxOcts
         Counter64,
      pr1645v2Lan2MCInQueuesD7PerformanceBandwidth
         Integer32
      }

pr1645v2Lan2MCInQueuesD7PerformanceTableIx OBJECT-TYPE
   SYNTAX      TableIndex
   MAX-ACCESS  not-accessible
   STATUS      current
   DESCRIPTION
      ""
   ::= {pr1645v2Lan2MCInQueuesD7PerformanceEntry 11}

pr1645v2Lan2MCInQueuesD7PerformanceSysUpTime OBJECT-TYPE
   SYNTAX      TimeTicks
   MAX-ACCESS  read-only
   STATUS      current
   DESCRIPTION
      "Path: ethernet2.performance.ifInPriorityQueues.d7Performance.sysUpTime

       Time in centi-second."
   ::= {pr1645v2Lan2MCInQueuesD7PerformanceEntry 16777216}

pr1645v2Lan2MCInQueuesD7PerformanceTotPkts OBJECT-TYPE
   SYNTAX      Counter64
   MAX-ACCESS  read-only
   STATUS      current
   DESCRIPTION
      "Path: ethernet2.performance.ifInPriorityQueues.d7Performance.totalPkts

       64 bit unsigned wrappable counter."
   ::= {pr1645v2Lan2MCInQueuesD7PerformanceEntry 234881024}

pr1645v2Lan2MCInQueuesD7PerformanceDirTxPkts OBJECT-TYPE
   SYNTAX      Counter64
   MAX-ACCESS  read-only
   STATUS      current
   DESCRIPTION
      "Path: ethernet2.performance.ifInPriorityQueues.d7Performance.directTxPkts

       64 bit unsigned wrappable counter."
   ::= {pr1645v2Lan2MCInQueuesD7PerformanceEntry 33554432}

pr1645v2Lan2MCInQueuesD7PerformanceQdPkts OBJECT-TYPE
   SYNTAX      Counter64
   MAX-ACCESS  read-only
   STATUS      current
   DESCRIPTION
      "Path: ethernet2.performance.ifInPriorityQueues.d7Performance.queuedPkts

       64 bit unsigned wrappable counter."
   ::= {pr1645v2Lan2MCInQueuesD7PerformanceEntry 50331648}

pr1645v2Lan2MCInQueuesD7PerformanceDropPkts OBJECT-TYPE
   SYNTAX      Counter64
   MAX-ACCESS  read-only
   STATUS      current
   DESCRIPTION
      "Path: ethernet2.performance.ifInPriorityQueues.d7Performance.droppedPkts

       64 bit unsigned wrappable counter."
   ::= {pr1645v2Lan2MCInQueuesD7PerformanceEntry 67108864}

pr1645v2Lan2MCInQueuesD7PerformanceRDropPkts OBJECT-TYPE
   SYNTAX      Counter64
   MAX-ACCESS  read-only
   STATUS      current
   DESCRIPTION
      "Path: ethernet2.performance.ifInPriorityQueues.d7Performance.redDroppedPkts

       64 bit unsigned wrappable counter."
   ::= {pr1645v2Lan2MCInQueuesD7PerformanceEntry 201326592}

pr1645v2Lan2MCInQueuesD7PerformanceCirTxPkts OBJECT-TYPE
   SYNTAX      Counter64
   MAX-ACCESS  read-only
   STATUS      current
   DESCRIPTION
      "Path: ethernet2.performance.ifInPriorityQueues.d7Performance.cirTxPkts

       64 bit unsigned wrappable counter."
   ::= {pr1645v2Lan2MCInQueuesD7PerformanceEntry 83886080}

pr1645v2Lan2MCInQueuesD7PerformanceEirTxPkts OBJECT-TYPE
   SYNTAX      Counter64
   MAX-ACCESS  read-only
   STATUS      current
   DESCRIPTION
      "Path: ethernet2.performance.ifInPriorityQueues.d7Performance.eirTxPkts

       64 bit unsigned wrappable counter."
   ::= {pr1645v2Lan2MCInQueuesD7PerformanceEntry 100663296}

pr1645v2Lan2MCInQueuesD7PerformanceViolTxPkts OBJECT-TYPE
   SYNTAX      Counter64
   MAX-ACCESS  read-only
   STATUS      current
   DESCRIPTION
      "Path: ethernet2.performance.ifInPriorityQueues.d7Performance.violateTxPkts

       64 bit unsigned wrappable counter."
   ::= {pr1645v2Lan2MCInQueuesD7PerformanceEntry 301989888}

pr1645v2Lan2MCInQueuesD7PerformanceTotOcts OBJECT-TYPE
   SYNTAX      Counter64
   MAX-ACCESS  read-only
   STATUS      current
   DESCRIPTION
      "Path: ethernet2.performance.ifInPriorityQueues.d7Performance.totalOctets

       64 bit unsigned wrappable counter."
   ::= {pr1645v2Lan2MCInQueuesD7PerformanceEntry 251658240}

pr1645v2Lan2MCInQueuesD7PerformanceDirTxOcts OBJECT-TYPE
   SYNTAX      Counter64
   MAX-ACCESS  read-only
   STATUS      current
   DESCRIPTION
      "Path: ethernet2.performance.ifInPriorityQueues.d7Performance.directTxOctets

       64 bit unsigned wrappable counter."
   ::= {pr1645v2Lan2MCInQueuesD7PerformanceEntry 117440512}

pr1645v2Lan2MCInQueuesD7PerformanceQdOcts OBJECT-TYPE
   SYNTAX      Counter64
   MAX-ACCESS  read-only
   STATUS      current
   DESCRIPTION
      "Path: ethernet2.performance.ifInPriorityQueues.d7Performance.queuedOctets

       64 bit unsigned wrappable counter."
   ::= {pr1645v2Lan2MCInQueuesD7PerformanceEntry 134217728}

pr1645v2Lan2MCInQueuesD7PerformanceDropOcts OBJECT-TYPE
   SYNTAX      Counter64
   MAX-ACCESS  read-only
   STATUS      current
   DESCRIPTION
      "Path: ethernet2.performance.ifInPriorityQueues.d7Performance.droppedOctets

       64 bit unsigned wrappable counter."
   ::= {pr1645v2Lan2MCInQueuesD7PerformanceEntry 150994944}

pr1645v2Lan2MCInQueuesD7PerformanceRDropOcts OBJECT-TYPE
   SYNTAX      Counter64
   MAX-ACCESS  read-only
   STATUS      current
   DESCRIPTION
      "Path: ethernet2.performance.ifInPriorityQueues.d7Performance.redDroppedOctets

       64 bit unsigned wrappable counter."
   ::= {pr1645v2Lan2MCInQueuesD7PerformanceEntry 218103808}

pr1645v2Lan2MCInQueuesD7PerformanceCirTxOcts OBJECT-TYPE
   SYNTAX      Counter64
   MAX-ACCESS  read-only
   STATUS      current
   DESCRIPTION
      "Path: ethernet2.performance.ifInPriorityQueues.d7Performance.cirTxOctets

       64 bit unsigned wrappable counter."
   ::= {pr1645v2Lan2MCInQueuesD7PerformanceEntry 167772160}

pr1645v2Lan2MCInQueuesD7PerformanceEirTxOcts OBJECT-TYPE
   SYNTAX      Counter64
   MAX-ACCESS  read-only
   STATUS      current
   DESCRIPTION
      "Path: ethernet2.performance.ifInPriorityQueues.d7Performance.eirTxOctets

       64 bit unsigned wrappable counter."
   ::= {pr1645v2Lan2MCInQueuesD7PerformanceEntry 184549376}

pr1645v2Lan2MCInQueuesD7PerformanceViolTxOcts OBJECT-TYPE
   SYNTAX      Counter64
   MAX-ACCESS  read-only
   STATUS      current
   DESCRIPTION
      "Path: ethernet2.performance.ifInPriorityQueues.d7Performance.violateTxOctets

       64 bit unsigned wrappable counter."
   ::= {pr1645v2Lan2MCInQueuesD7PerformanceEntry 318767104}

pr1645v2Lan2MCInQueuesD7PerformanceBandwidth OBJECT-TYPE
   SYNTAX      Integer32
   MAX-ACCESS  read-only
   STATUS      current
   DESCRIPTION
      "Path: ethernet2.performance.ifInPriorityQueues.d7Performance.bandwidth

       unit name = bps
       formula = 8 * ; 8 /"
   ::= {pr1645v2Lan2MCInQueuesD7PerformanceEntry 268435456}


pr1645v2Lan2MCInBandwidth OBJECT IDENTIFIER ::= {pr1645v2Lan2MC 181}

pr1645v2Lan2MCInBandwidthSSC OBJECT IDENTIFIER ::= {pr1645v2Lan2MCInBandwidth 1}

pr1645v2Lan2MCInBandwidthEntry OBJECT IDENTIFIER ::= {pr1645v2Lan2MCInBandwidthSSC 1}

pr1645v2Lan2MCInBandwidth15sec OBJECT-TYPE
   SYNTAX      Integer32
   MAX-ACCESS  read-only
   STATUS      current
   DESCRIPTION
      "Path: ethernet2.performance.ifInBandwidth.15sec

       unit name = bps
       formula = 8 * ; 8 /"
   ::= {pr1645v2Lan2MCInBandwidthEntry 83886080}

pr1645v2Lan2MCInBandwidth30sec OBJECT-TYPE
   SYNTAX      Integer32
   MAX-ACCESS  read-only
   STATUS      current
   DESCRIPTION
      "Path: ethernet2.performance.ifInBandwidth.30sec

       unit name = bps
       formula = 8 * ; 8 /"
   ::= {pr1645v2Lan2MCInBandwidthEntry 167772160}

pr1645v2Lan2MCInBandwidth1min OBJECT-TYPE
   SYNTAX      Integer32
   MAX-ACCESS  read-only
   STATUS      current
   DESCRIPTION
      "Path: ethernet2.performance.ifInBandwidth.1min

       unit name = bps
       formula = 8 * ; 8 /"
   ::= {pr1645v2Lan2MCInBandwidthEntry 335544320}

pr1645v2Lan2MCInBandwidth2min OBJECT-TYPE
   SYNTAX      Integer32
   MAX-ACCESS  read-only
   STATUS      current
   DESCRIPTION
      "Path: ethernet2.performance.ifInBandwidth.2min

       unit name = bps
       formula = 8 * ; 8 /"
   ::= {pr1645v2Lan2MCInBandwidthEntry 671088640}

pr1645v2Lan2MCInBandwidth5min OBJECT-TYPE
   SYNTAX      Integer32
   MAX-ACCESS  read-only
   STATUS      current
   DESCRIPTION
      "Path: ethernet2.performance.ifInBandwidth.5min

       unit name = bps
       formula = 8 * ; 8 /"
   ::= {pr1645v2Lan2MCInBandwidthEntry 1677721600}


pr1645v2Lan2MCOutOctets OBJECT-TYPE
   SYNTAX      Counter64
   MAX-ACCESS  read-only
   STATUS      current
   DESCRIPTION
      "Path: ethernet2.performance.ifOutOctets
       Info: ifOutOctets

       64 bit unsigned wrappable counter."
   ::= {pr1645v2Lan2MC 115}


pr1645v2Lan2MCOutUcastPkts OBJECT-TYPE
   SYNTAX      Counter64
   MAX-ACCESS  read-only
   STATUS      current
   DESCRIPTION
      "Path: ethernet2.performance.ifOutUcastPkts
       Info: ifOutUcastPkts

       64 bit unsigned wrappable counter."
   ::= {pr1645v2Lan2MC 116}


pr1645v2Lan2MCOutNUcastPkts OBJECT-TYPE
   SYNTAX      Counter64
   MAX-ACCESS  read-only
   STATUS      current
   DESCRIPTION
      "Path: ethernet2.performance.ifOutNUcastPkts
       Info: ifOutNUcastPkts

       64 bit unsigned wrappable counter."
   ::= {pr1645v2Lan2MC 117}


pr1645v2Lan2MCOutBcastPkts OBJECT-TYPE
   SYNTAX      Counter64
   MAX-ACCESS  read-only
   STATUS      current
   DESCRIPTION
      "Path: ethernet2.performance.ifOutBcastPkts
       Info: ifOutBcastPkts

       64 bit unsigned wrappable counter."
   ::= {pr1645v2Lan2MC 217}


pr1645v2Lan2MCOutMcastPkts OBJECT-TYPE
   SYNTAX      Counter64
   MAX-ACCESS  read-only
   STATUS      current
   DESCRIPTION
      "Path: ethernet2.performance.ifOutMcastPkts
       Info: ifOutMcastPkts

       64 bit unsigned wrappable counter."
   ::= {pr1645v2Lan2MC 227}


pr1645v2Lan2MCOutDiscards OBJECT-TYPE
   SYNTAX      Counter64
   MAX-ACCESS  read-only
   STATUS      current
   DESCRIPTION
      "Path: ethernet2.performance.ifOutDiscards
       Info: ifOutDiscards

       64 bit unsigned wrappable counter."
   ::= {pr1645v2Lan2MC 118}


pr1645v2Lan2MCOutErrors OBJECT-TYPE
   SYNTAX      Counter64
   MAX-ACCESS  read-only
   STATUS      current
   DESCRIPTION
      "Path: ethernet2.performance.ifOutErrors
       Info: ifOutErrors

       64 bit unsigned wrappable counter."
   ::= {pr1645v2Lan2MC 119}


pr1645v2Lan2MCOutQLen OBJECT-TYPE
   SYNTAX      Gauge32
   MAX-ACCESS  read-only
   STATUS      current
   DESCRIPTION
      "Path: ethernet2.performance.ifOutQLen
       Info: ifOutQLen

       32 bit unsigned gauge value."
   ::= {pr1645v2Lan2MC 120}


pr1645v2Lan2MCOutDropEx OBJECT-TYPE
   SYNTAX      Counter64
   MAX-ACCESS  read-only
   STATUS      current
   DESCRIPTION
      "Path: ethernet2.performance.ifOutDropLevelExceeded
       Info: ifOutDiscards

       64 bit unsigned wrappable counter."
   ::= {pr1645v2Lan2MC 127}


pr1645v2Lan2MCOutDropNoArp OBJECT-TYPE
   SYNTAX      Counter64
   MAX-ACCESS  read-only
   STATUS      current
   DESCRIPTION
      "Path: ethernet2.performance.ifOutDiscardsNoArp
       Info: ifOutDiscards

       64 bit unsigned wrappable counter."
   ::= {pr1645v2Lan2MC 134}


pr1645v2Lan2MCOutDropFilter OBJECT-TYPE
   SYNTAX      Counter64
   MAX-ACCESS  read-only
   STATUS      current
   DESCRIPTION
      "Path: ethernet2.performance.ifOutDiscardsFilter
       Info: ifOutDiscards

       64 bit unsigned wrappable counter."
   ::= {pr1645v2Lan2MC 138}


pr1645v2Lan2MCOutQueues OBJECT IDENTIFIER ::= {pr1645v2Lan2MC 129}

pr1645v2Lan2MCOutQueuesSSCTable OBJECT-TYPE
   SYNTAX      SEQUENCE OF Pr1645v2Lan2MCOutQueuesEntry
   MAX-ACCESS  not-accessible
   STATUS      current
   DESCRIPTION
      "Queue Lengths"
   ::= {pr1645v2Lan2MCOutQueues 1}

pr1645v2Lan2MCOutQueuesEntry OBJECT-TYPE
   SYNTAX      Pr1645v2Lan2MCOutQueuesEntry
   MAX-ACCESS  not-accessible
   STATUS      current
   DESCRIPTION
      ""
   INDEX      { pr1645v2Lan2MCOutQueuesTableIx }
   ::= {pr1645v2Lan2MCOutQueuesSSCTable 1}

Pr1645v2Lan2MCOutQueuesEntry ::=
   SEQUENCE
      {
      pr1645v2Lan2MCOutQueuesTableIx
         TableIndex,
      pr1645v2Lan2MCOutQueuesName
         INTEGER,
      pr1645v2Lan2MCOutQueuesLength
         Integer32,
      pr1645v2Lan2MCOutQueuesOctetLength
         Integer32,
      pr1645v2Lan2MCOutQueuesRedLength
         Integer32,
      pr1645v2Lan2MCOutQueuesPacketsTotal
         Counter64,
      pr1645v2Lan2MCOutQueuesPacketsDirectTx
         Counter64,
      pr1645v2Lan2MCOutQueuesPacketsQueued
         Counter64,
      pr1645v2Lan2MCOutQueuesPacketsDropped
         Counter64,
      pr1645v2Lan2MCOutQueuesPacketsRedDropped
         Counter64,
      pr1645v2Lan2MCOutQueuesPacketsCirTx
         Counter64,
      pr1645v2Lan2MCOutQueuesPacketsEirTx
         Counter64,
      pr1645v2Lan2MCOutQueuesPacketsViolateTx
         Counter64,
      pr1645v2Lan2MCOutQueuesOctetsTotal
         Counter64,
      pr1645v2Lan2MCOutQueuesOctetsDirectTx
         Counter64,
      pr1645v2Lan2MCOutQueuesOctetsQueued
         Counter64,
      pr1645v2Lan2MCOutQueuesOctetsDropped
         Counter64,
      pr1645v2Lan2MCOutQueuesOctetsRedDropped
         Counter64,
      pr1645v2Lan2MCOutQueuesOctetsCirTx
         Counter64,
      pr1645v2Lan2MCOutQueuesOctetsEirTx
         Counter64,
      pr1645v2Lan2MCOutQueuesOctetsViolateTx
         Counter64,
      pr1645v2Lan2MCOutQueuesOctetsBandwidth15sec
         Integer32,
      pr1645v2Lan2MCOutQueuesOctetsBandwidth30sec
         Integer32,
      pr1645v2Lan2MCOutQueuesOctetsBandwidth1min
         Integer32,
      pr1645v2Lan2MCOutQueuesOctetsBandwidth2min
         Integer32,
      pr1645v2Lan2MCOutQueuesOctetsBandwidth5min
         Integer32
      }

pr1645v2Lan2MCOutQueuesTableIx OBJECT-TYPE
   SYNTAX      TableIndex
   MAX-ACCESS  not-accessible
   STATUS      current
   DESCRIPTION
      ""
   ::= {pr1645v2Lan2MCOutQueuesEntry 11}

pr1645v2Lan2MCOutQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifOutPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2MCOutQueuesEntry 16777216}

pr1645v2Lan2MCOutQueuesLength OBJECT-TYPE
   SYNTAX      Integer32
   MAX-ACCESS  read-only
   STATUS      current
   DESCRIPTION
      "Path: ethernet2.performance.ifOutPriorityQueues.length"
   ::= {pr1645v2Lan2MCOutQueuesEntry 33554432}

pr1645v2Lan2MCOutQueuesOctetLength OBJECT-TYPE
   SYNTAX      Integer32
   MAX-ACCESS  read-only
   STATUS      current
   DESCRIPTION
      "Path: ethernet2.performance.ifOutPriorityQueues.octetLength"
   ::= {pr1645v2Lan2MCOutQueuesEntry 150994944}

pr1645v2Lan2MCOutQueuesRedLength OBJECT-TYPE
   SYNTAX      Integer32
   MAX-ACCESS  read-only
   STATUS      current
   DESCRIPTION
      "Path: ethernet2.performance.ifOutPriorityQueues.redLength"
   ::= {pr1645v2Lan2MCOutQueuesEntry 134217728}

pr1645v2Lan2MCOutQueuesPacketsTotal OBJECT-TYPE
   SYNTAX      Counter64
   MAX-ACCESS  read-only
   STATUS      current
   DESCRIPTION
      "Path: ethernet2.performance.ifOutPriorityQueues.packets.total

       64 bit unsigned wrappable counter."
   ::= {pr1645v2Lan2MCOutQueuesEntry 50790400}

pr1645v2Lan2MCOutQueuesPacketsDirectTx OBJECT-TYPE
   SYNTAX      Counter64
   MAX-ACCESS  read-only
   STATUS      current
   DESCRIPTION
      "Path: ethernet2.performance.ifOutPriorityQueues.packets.directTx

       64 bit unsigned wrappable counter."
   ::= {pr1645v2Lan2MCOutQueuesEntry 50397184}

pr1645v2Lan2MCOutQueuesPacketsQueued OBJECT-TYPE
   SYNTAX      Counter64
   MAX-ACCESS  read-only
   STATUS      current
   DESCRIPTION
      "Path: ethernet2.performance.ifOutPriorityQueues.packets.queued

       64 bit unsigned wrappable counter."
   ::= {pr1645v2Lan2MCOutQueuesEntry 50462720}

pr1645v2Lan2MCOutQueuesPacketsDropped OBJECT-TYPE
   SYNTAX      Counter64
   MAX-ACCESS  read-only
   STATUS      current
   DESCRIPTION
      "Path: ethernet2.performance.ifOutPriorityQueues.packets.dropped

       64 bit unsigned wrappable counter."
   ::= {pr1645v2Lan2MCOutQueuesEntry 50528256}

pr1645v2Lan2MCOutQueuesPacketsRedDropped OBJECT-TYPE
   SYNTAX      Counter64
   MAX-ACCESS  read-only
   STATUS      current
   DESCRIPTION
      "Path: ethernet2.performance.ifOutPriorityQueues.packets.redDropped

       64 bit unsigned wrappable counter."
   ::= {pr1645v2Lan2MCOutQueuesEntry 50724864}

pr1645v2Lan2MCOutQueuesPacketsCirTx OBJECT-TYPE
   SYNTAX      Counter64
   MAX-ACCESS  read-only
   STATUS      current
   DESCRIPTION
      "Path: ethernet2.performance.ifOutPriorityQueues.packets.cirTx

       64 bit unsigned wrappable counter."
   ::= {pr1645v2Lan2MCOutQueuesEntry 50593792}

pr1645v2Lan2MCOutQueuesPacketsEirTx OBJECT-TYPE
   SYNTAX      Counter64
   MAX-ACCESS  read-only
   STATUS      current
   DESCRIPTION
      "Path: ethernet2.performance.ifOutPriorityQueues.packets.eirTx

       64 bit unsigned wrappable counter."
   ::= {pr1645v2Lan2MCOutQueuesEntry 50659328}

pr1645v2Lan2MCOutQueuesPacketsViolateTx OBJECT-TYPE
   SYNTAX      Counter64
   MAX-ACCESS  read-only
   STATUS      current
   DESCRIPTION
      "Path: ethernet2.performance.ifOutPriorityQueues.packets.violateTx

       64 bit unsigned wrappable counter."
   ::= {pr1645v2Lan2MCOutQueuesEntry 50855936}

pr1645v2Lan2MCOutQueuesOctetsTotal OBJECT-TYPE
   SYNTAX      Counter64
   MAX-ACCESS  read-only
   STATUS      current
   DESCRIPTION
      "Path: ethernet2.performance.ifOutPriorityQueues.octets.total

       64 bit unsigned wrappable counter."
   ::= {pr1645v2Lan2MCOutQueuesEntry 67567616}

pr1645v2Lan2MCOutQueuesOctetsDirectTx OBJECT-TYPE
   SYNTAX      Counter64
   MAX-ACCESS  read-only
   STATUS      current
   DESCRIPTION
      "Path: ethernet2.performance.ifOutPriorityQueues.octets.directTx

       64 bit unsigned wrappable counter."
   ::= {pr1645v2Lan2MCOutQueuesEntry 67174400}

pr1645v2Lan2MCOutQueuesOctetsQueued OBJECT-TYPE
   SYNTAX      Counter64
   MAX-ACCESS  read-only
   STATUS      current
   DESCRIPTION
      "Path: ethernet2.performance.ifOutPriorityQueues.octets.queued

       64 bit unsigned wrappable counter."
   ::= {pr1645v2Lan2MCOutQueuesEntry 67239936}

pr1645v2Lan2MCOutQueuesOctetsDropped OBJECT-TYPE
   SYNTAX      Counter64
   MAX-ACCESS  read-only
   STATUS      current
   DESCRIPTION
      "Path: ethernet2.performance.ifOutPriorityQueues.octets.dropped

       64 bit unsigned wrappable counter."
   ::= {pr1645v2Lan2MCOutQueuesEntry 67305472}

pr1645v2Lan2MCOutQueuesOctetsRedDropped OBJECT-TYPE
   SYNTAX      Counter64
   MAX-ACCESS  read-only
   STATUS      current
   DESCRIPTION
      "Path: ethernet2.performance.ifOutPriorityQueues.octets.redDropped

       64 bit unsigned wrappable counter."
   ::= {pr1645v2Lan2MCOutQueuesEntry 67502080}

pr1645v2Lan2MCOutQueuesOctetsCirTx OBJECT-TYPE
   SYNTAX      Counter64
   MAX-ACCESS  read-only
   STATUS      current
   DESCRIPTION
      "Path: ethernet2.performance.ifOutPriorityQueues.octets.cirTx

       64 bit unsigned wrappable counter."
   ::= {pr1645v2Lan2MCOutQueuesEntry 67371008}

pr1645v2Lan2MCOutQueuesOctetsEirTx OBJECT-TYPE
   SYNTAX      Counter64
   MAX-ACCESS  read-only
   STATUS      current
   DESCRIPTION
      "Path: ethernet2.performance.ifOutPriorityQueues.octets.eirTx

       64 bit unsigned wrappable counter."
   ::= {pr1645v2Lan2MCOutQueuesEntry 67436544}

pr1645v2Lan2MCOutQueuesOctetsViolateTx OBJECT-TYPE
   SYNTAX      Counter64
   MAX-ACCESS  read-only
   STATUS      current
   DESCRIPTION
      "Path: ethernet2.performance.ifOutPriorityQueues.octets.violateTx

       64 bit unsigned wrappable counter."
   ::= {pr1645v2Lan2MCOutQueuesEntry 67633152}

pr1645v2Lan2MCOutQueuesOctetsBandwidth15sec OBJECT-TYPE
   SYNTAX      Integer32
   MAX-ACCESS  read-only
   STATUS      current
   DESCRIPTION
      "Path: ethernet2.performance.ifOutPriorityQueues.octets.bandwidth.15sec

       unit name = bps
       formula = 8 * ; 8 /"
   ::= {pr1645v2Lan2MCOutQueuesEntry 70386944}

pr1645v2Lan2MCOutQueuesOctetsBandwidth30sec OBJECT-TYPE
   SYNTAX      Integer32
   MAX-ACCESS  read-only
   STATUS      current
   DESCRIPTION
      "Path: ethernet2.performance.ifOutPriorityQueues.octets.bandwidth.30sec

       unit name = bps
       formula = 8 * ; 8 /"
   ::= {pr1645v2Lan2MCOutQueuesEntry 70388224}

pr1645v2Lan2MCOutQueuesOctetsBandwidth1min OBJECT-TYPE
   SYNTAX      Integer32
   MAX-ACCESS  read-only
   STATUS      current
   DESCRIPTION
      "Path: ethernet2.performance.ifOutPriorityQueues.octets.bandwidth.1min

       unit name = bps
       formula = 8 * ; 8 /"
   ::= {pr1645v2Lan2MCOutQueuesEntry 70390784}

pr1645v2Lan2MCOutQueuesOctetsBandwidth2min OBJECT-TYPE
   SYNTAX      Integer32
   MAX-ACCESS  read-only
   STATUS      current
   DESCRIPTION
      "Path: ethernet2.performance.ifOutPriorityQueues.octets.bandwidth.2min

       unit name = bps
       formula = 8 * ; 8 /"
   ::= {pr1645v2Lan2MCOutQueuesEntry 70395904}

pr1645v2Lan2MCOutQueuesOctetsBandwidth5min OBJECT-TYPE
   SYNTAX      Integer32
   MAX-ACCESS  read-only
   STATUS      current
   DESCRIPTION
      "Path: ethernet2.performance.ifOutPriorityQueues.octets.bandwidth.5min

       unit name = bps
       formula = 8 * ; 8 /"
   ::= {pr1645v2Lan2MCOutQueuesEntry 70411264}

pr1645v2Lan2MCOutQueuesH2Performance OBJECT-TYPE
   SYNTAX      SEQUENCE OF Pr1645v2Lan2MCOutQueuesH2PerformanceEntry
   MAX-ACCESS  not-accessible
   STATUS      current
   DESCRIPTION
      ""
   ::= {pr1645v2Lan2MCOutQueues 83886080}

pr1645v2Lan2MCOutQueuesH2PerformanceEntry OBJECT-TYPE
   SYNTAX      Pr1645v2Lan2MCOutQueuesH2PerformanceEntry
   MAX-ACCESS  not-accessible
   STATUS      current
   DESCRIPTION
      ""
   INDEX      { pr1645v2Lan2MCOutQueuesTableIx,
                pr1645v2Lan2MCOutQueuesH2PerformanceTableIx }
   ::= {pr1645v2Lan2MCOutQueuesH2Performance 1}

Pr1645v2Lan2MCOutQueuesH2PerformanceEntry ::=
   SEQUENCE
      {
      pr1645v2Lan2MCOutQueuesH2PerformanceTableIx
         TableIndex,
      pr1645v2Lan2MCOutQueuesH2PerformanceSysUpTime
         TimeTicks,
      pr1645v2Lan2MCOutQueuesH2PerformanceTotPkts
         Counter64,
      pr1645v2Lan2MCOutQueuesH2PerformanceDirTxPkts
         Counter64,
      pr1645v2Lan2MCOutQueuesH2PerformanceQdPkts
         Counter64,
      pr1645v2Lan2MCOutQueuesH2PerformanceDropPkts
         Counter64,
      pr1645v2Lan2MCOutQueuesH2PerformanceRDropPkts
         Counter64,
      pr1645v2Lan2MCOutQueuesH2PerformanceCirTxPkts
         Counter64,
      pr1645v2Lan2MCOutQueuesH2PerformanceEirTxPkts
         Counter64,
      pr1645v2Lan2MCOutQueuesH2PerformanceViolTxPkts
         Counter64,
      pr1645v2Lan2MCOutQueuesH2PerformanceTotOcts
         Counter64,
      pr1645v2Lan2MCOutQueuesH2PerformanceDirTxOcts
         Counter64,
      pr1645v2Lan2MCOutQueuesH2PerformanceQdOcts
         Counter64,
      pr1645v2Lan2MCOutQueuesH2PerformanceDropOcts
         Counter64,
      pr1645v2Lan2MCOutQueuesH2PerformanceRDropOcts
         Counter64,
      pr1645v2Lan2MCOutQueuesH2PerformanceCirTxOcts
         Counter64,
      pr1645v2Lan2MCOutQueuesH2PerformanceEirTxOcts
         Counter64,
      pr1645v2Lan2MCOutQueuesH2PerformanceViolTxOcts
         Counter64,
      pr1645v2Lan2MCOutQueuesH2PerformanceBandwidth
         Integer32
      }

pr1645v2Lan2MCOutQueuesH2PerformanceTableIx OBJECT-TYPE
   SYNTAX      TableIndex
   MAX-ACCESS  not-accessible
   STATUS      current
   DESCRIPTION
      ""
   ::= {pr1645v2Lan2MCOutQueuesH2PerformanceEntry 11}

pr1645v2Lan2MCOutQueuesH2PerformanceSysUpTime OBJECT-TYPE
   SYNTAX      TimeTicks
   MAX-ACCESS  read-only
   STATUS      current
   DESCRIPTION
      "Path: ethernet2.performance.ifOutPriorityQueues.h2Performance.sysUpTime

       Time in centi-second."
   ::= {pr1645v2Lan2MCOutQueuesH2PerformanceEntry 16777216}

pr1645v2Lan2MCOutQueuesH2PerformanceTotPkts OBJECT-TYPE
   SYNTAX      Counter64
   MAX-ACCESS  read-only
   STATUS      current
   DESCRIPTION
      "Path: ethernet2.performance.ifOutPriorityQueues.h2Performance.totalPkts

       64 bit unsigned wrappable counter."
   ::= {pr1645v2Lan2MCOutQueuesH2PerformanceEntry 234881024}

pr1645v2Lan2MCOutQueuesH2PerformanceDirTxPkts OBJECT-TYPE
   SYNTAX      Counter64
   MAX-ACCESS  read-only
   STATUS      current
   DESCRIPTION
      "Path: ethernet2.performance.ifOutPriorityQueues.h2Performance.directTxPkts

       64 bit unsigned wrappable counter."
   ::= {pr1645v2Lan2MCOutQueuesH2PerformanceEntry 33554432}

pr1645v2Lan2MCOutQueuesH2PerformanceQdPkts OBJECT-TYPE
   SYNTAX      Counter64
   MAX-ACCESS  read-only
   STATUS      current
   DESCRIPTION
      "Path: ethernet2.performance.ifOutPriorityQueues.h2Performance.queuedPkts

       64 bit unsigned wrappable counter."
   ::= {pr1645v2Lan2MCOutQueuesH2PerformanceEntry 50331648}

pr1645v2Lan2MCOutQueuesH2PerformanceDropPkts OBJECT-TYPE
   SYNTAX      Counter64
   MAX-ACCESS  read-only
   STATUS      current
   DESCRIPTION
      "Path: ethernet2.performance.ifOutPriorityQueues.h2Performance.droppedPkts

       64 bit unsigned wrappable counter."
   ::= {pr1645v2Lan2MCOutQueuesH2PerformanceEntry 67108864}

pr1645v2Lan2MCOutQueuesH2PerformanceRDropPkts OBJECT-TYPE
   SYNTAX      Counter64
   MAX-ACCESS  read-only
   STATUS      current
   DESCRIPTION
      "Path: ethernet2.performance.ifOutPriorityQueues.h2Performance.redDroppedPkts

       64 bit unsigned wrappable counter."
   ::= {pr1645v2Lan2MCOutQueuesH2PerformanceEntry 201326592}

pr1645v2Lan2MCOutQueuesH2PerformanceCirTxPkts OBJECT-TYPE
   SYNTAX      Counter64
   MAX-ACCESS  read-only
   STATUS      current
   DESCRIPTION
      "Path: ethernet2.performance.ifOutPriorityQueues.h2Performance.cirTxPkts

       64 bit unsigned wrappable counter."
   ::= {pr1645v2Lan2MCOutQueuesH2PerformanceEntry 83886080}

pr1645v2Lan2MCOutQueuesH2PerformanceEirTxPkts OBJECT-TYPE
   SYNTAX      Counter64
   MAX-ACCESS  read-only
   STATUS      current
   DESCRIPTION
      "Path: ethernet2.performance.ifOutPriorityQueues.h2Performance.eirTxPkts

       64 bit unsigned wrappable counter."
   ::= {pr1645v2Lan2MCOutQueuesH2PerformanceEntry 100663296}

pr1645v2Lan2MCOutQueuesH2PerformanceViolTxPkts OBJECT-TYPE
   SYNTAX      Counter64
   MAX-ACCESS  read-only
   STATUS      current
   DESCRIPTION
      "Path: ethernet2.performance.ifOutPriorityQueues.h2Performance.violateTxPkts

       64 bit unsigned wrappable counter."
   ::= {pr1645v2Lan2MCOutQueuesH2PerformanceEntry 301989888}

pr1645v2Lan2MCOutQueuesH2PerformanceTotOcts OBJECT-TYPE
   SYNTAX      Counter64
   MAX-ACCESS  read-only
   STATUS      current
   DESCRIPTION
      "Path: ethernet2.performance.ifOutPriorityQueues.h2Performance.totalOctets

       64 bit unsigned wrappable counter."
   ::= {pr1645v2Lan2MCOutQueuesH2PerformanceEntry 251658240}

pr1645v2Lan2MCOutQueuesH2PerformanceDirTxOcts OBJECT-TYPE
   SYNTAX      Counter64
   MAX-ACCESS  read-only
   STATUS      current
   DESCRIPTION
      "Path: ethernet2.performance.ifOutPriorityQueues.h2Performance.directTxOctets

       64 bit unsigned wrappable counter."
   ::= {pr1645v2Lan2MCOutQueuesH2PerformanceEntry 117440512}

pr1645v2Lan2MCOutQueuesH2PerformanceQdOcts OBJECT-TYPE
   SYNTAX      Counter64
   MAX-ACCESS  read-only
   STATUS      current
   DESCRIPTION
      "Path: ethernet2.performance.ifOutPriorityQueues.h2Performance.queuedOctets

       64 bit unsigned wrappable counter."
   ::= {pr1645v2Lan2MCOutQueuesH2PerformanceEntry 134217728}

pr1645v2Lan2MCOutQueuesH2PerformanceDropOcts OBJECT-TYPE
   SYNTAX      Counter64
   MAX-ACCESS  read-only
   STATUS      current
   DESCRIPTION
      "Path: ethernet2.performance.ifOutPriorityQueues.h2Performance.droppedOctets

       64 bit unsigned wrappable counter."
   ::= {pr1645v2Lan2MCOutQueuesH2PerformanceEntry 150994944}

pr1645v2Lan2MCOutQueuesH2PerformanceRDropOcts OBJECT-TYPE
   SYNTAX      Counter64
   MAX-ACCESS  read-only
   STATUS      current
   DESCRIPTION
      "Path: ethernet2.performance.ifOutPriorityQueues.h2Performance.redDroppedOctets

       64 bit unsigned wrappable counter."
   ::= {pr1645v2Lan2MCOutQueuesH2PerformanceEntry 218103808}

pr1645v2Lan2MCOutQueuesH2PerformanceCirTxOcts OBJECT-TYPE
   SYNTAX      Counter64
   MAX-ACCESS  read-only
   STATUS      current
   DESCRIPTION
      "Path: ethernet2.performance.ifOutPriorityQueues.h2Performance.cirTxOctets

       64 bit unsigned wrappable counter."
   ::= {pr1645v2Lan2MCOutQueuesH2PerformanceEntry 167772160}

pr1645v2Lan2MCOutQueuesH2PerformanceEirTxOcts OBJECT-TYPE
   SYNTAX      Counter64
   MAX-ACCESS  read-only
   STATUS      current
   DESCRIPTION
      "Path: ethernet2.performance.ifOutPriorityQueues.h2Performance.eirTxOctets

       64 bit unsigned wrappable counter."
   ::= {pr1645v2Lan2MCOutQueuesH2PerformanceEntry 184549376}

pr1645v2Lan2MCOutQueuesH2PerformanceViolTxOcts OBJECT-TYPE
   SYNTAX      Counter64
   MAX-ACCESS  read-only
   STATUS      current
   DESCRIPTION
      "Path: ethernet2.performance.ifOutPriorityQueues.h2Performance.violateTxOctets

       64 bit unsigned wrappable counter."
   ::= {pr1645v2Lan2MCOutQueuesH2PerformanceEntry 318767104}

pr1645v2Lan2MCOutQueuesH2PerformanceBandwidth OBJECT-TYPE
   SYNTAX      Integer32
   MAX-ACCESS  read-only
   STATUS      current
   DESCRIPTION
      "Path: ethernet2.performance.ifOutPriorityQueues.h2Performance.bandwidth

       unit name = bps
       formula = 8 * ; 8 /"
   ::= {pr1645v2Lan2MCOutQueuesH2PerformanceEntry 268435456}

pr1645v2Lan2MCOutQueuesH24Performance OBJECT-TYPE
   SYNTAX      SEQUENCE OF Pr1645v2Lan2MCOutQueuesH24PerformanceEntry
   MAX-ACCESS  not-accessible
   STATUS      current
   DESCRIPTION
      ""
   ::= {pr1645v2Lan2MCOutQueues 100663296}

pr1645v2Lan2MCOutQueuesH24PerformanceEntry OBJECT-TYPE
   SYNTAX      Pr1645v2Lan2MCOutQueuesH24PerformanceEntry
   MAX-ACCESS  not-accessible
   STATUS      current
   DESCRIPTION
      ""
   INDEX      { pr1645v2Lan2MCOutQueuesTableIx,
                pr1645v2Lan2MCOutQueuesH24PerformanceTableIx }
   ::= {pr1645v2Lan2MCOutQueuesH24Performance 1}

Pr1645v2Lan2MCOutQueuesH24PerformanceEntry ::=
   SEQUENCE
      {
      pr1645v2Lan2MCOutQueuesH24PerformanceTableIx
         TableIndex,
      pr1645v2Lan2MCOutQueuesH24PerformanceSysUpTime
         TimeTicks,
      pr1645v2Lan2MCOutQueuesH24PerformanceTotPkts
         Counter64,
      pr1645v2Lan2MCOutQueuesH24PerformanceDirTxPkts
         Counter64,
      pr1645v2Lan2MCOutQueuesH24PerformanceQdPkts
         Counter64,
      pr1645v2Lan2MCOutQueuesH24PerformanceDropPkts
         Counter64,
      pr1645v2Lan2MCOutQueuesH24PerformanceRDropPkts
         Counter64,
      pr1645v2Lan2MCOutQueuesH24PerformanceCirTxPkts
         Counter64,
      pr1645v2Lan2MCOutQueuesH24PerformanceEirTxPkts
         Counter64,
      pr1645v2Lan2MCOutQueuesH24PerformanceViolTxPkts
         Counter64,
      pr1645v2Lan2MCOutQueuesH24PerformanceTotOcts
         Counter64,
      pr1645v2Lan2MCOutQueuesH24PerformanceDirTxOcts
         Counter64,
      pr1645v2Lan2MCOutQueuesH24PerformanceQdOcts
         Counter64,
      pr1645v2Lan2MCOutQueuesH24PerformanceDropOcts
         Counter64,
      pr1645v2Lan2MCOutQueuesH24PerformanceRDropOcts
         Counter64,
      pr1645v2Lan2MCOutQueuesH24PerformanceCirTxOcts
         Counter64,
      pr1645v2Lan2MCOutQueuesH24PerformanceEirTxOcts
         Counter64,
      pr1645v2Lan2MCOutQueuesH24PerformanceViolTxOcts
         Counter64,
      pr1645v2Lan2MCOutQueuesH24PerformanceBandwidth
         Integer32
      }

pr1645v2Lan2MCOutQueuesH24PerformanceTableIx OBJECT-TYPE
   SYNTAX      TableIndex
   MAX-ACCESS  not-accessible
   STATUS      current
   DESCRIPTION
      ""
   ::= {pr1645v2Lan2MCOutQueuesH24PerformanceEntry 11}

pr1645v2Lan2MCOutQueuesH24PerformanceSysUpTime OBJECT-TYPE
   SYNTAX      TimeTicks
   MAX-ACCESS  read-only
   STATUS      current
   DESCRIPTION
      "Path: ethernet2.performance.ifOutPriorityQueues.h24Performance.sysUpTime

       Time in centi-second."
   ::= {pr1645v2Lan2MCOutQueuesH24PerformanceEntry 16777216}

pr1645v2Lan2MCOutQueuesH24PerformanceTotPkts OBJECT-TYPE
   SYNTAX      Counter64
   MAX-ACCESS  read-only
   STATUS      current
   DESCRIPTION
      "Path: ethernet2.performance.ifOutPriorityQueues.h24Performance.totalPkts

       64 bit unsigned wrappable counter."
   ::= {pr1645v2Lan2MCOutQueuesH24PerformanceEntry 234881024}

pr1645v2Lan2MCOutQueuesH24PerformanceDirTxPkts OBJECT-TYPE
   SYNTAX      Counter64
   MAX-ACCESS  read-only
   STATUS      current
   DESCRIPTION
      "Path: ethernet2.performance.ifOutPriorityQueues.h24Performance.directTxPkts

       64 bit unsigned wrappable counter."
   ::= {pr1645v2Lan2MCOutQueuesH24PerformanceEntry 33554432}

pr1645v2Lan2MCOutQueuesH24PerformanceQdPkts OBJECT-TYPE
   SYNTAX      Counter64
   MAX-ACCESS  read-only
   STATUS      current
   DESCRIPTION
      "Path: ethernet2.performance.ifOutPriorityQueues.h24Performance.queuedPkts

       64 bit unsigned wrappable counter."
   ::= {pr1645v2Lan2MCOutQueuesH24PerformanceEntry 50331648}

pr1645v2Lan2MCOutQueuesH24PerformanceDropPkts OBJECT-TYPE
   SYNTAX      Counter64
   MAX-ACCESS  read-only
   STATUS      current
   DESCRIPTION
      "Path: ethernet2.performance.ifOutPriorityQueues.h24Performance.droppedPkts

       64 bit unsigned wrappable counter."
   ::= {pr1645v2Lan2MCOutQueuesH24PerformanceEntry 67108864}

pr1645v2Lan2MCOutQueuesH24PerformanceRDropPkts OBJECT-TYPE
   SYNTAX      Counter64
   MAX-ACCESS  read-only
   STATUS      current
   DESCRIPTION
      "Path: ethernet2.performance.ifOutPriorityQueues.h24Performance.redDroppedPkts

       64 bit unsigned wrappable counter."
   ::= {pr1645v2Lan2MCOutQueuesH24PerformanceEntry 201326592}

pr1645v2Lan2MCOutQueuesH24PerformanceCirTxPkts OBJECT-TYPE
   SYNTAX      Counter64
   MAX-ACCESS  read-only
   STATUS      current
   DESCRIPTION
      "Path: ethernet2.performance.ifOutPriorityQueues.h24Performance.cirTxPkts

       64 bit unsigned wrappable counter."
   ::= {pr1645v2Lan2MCOutQueuesH24PerformanceEntry 83886080}

pr1645v2Lan2MCOutQueuesH24PerformanceEirTxPkts OBJECT-TYPE
   SYNTAX      Counter64
   MAX-ACCESS  read-only
   STATUS      current
   DESCRIPTION
      "Path: ethernet2.performance.ifOutPriorityQueues.h24Performance.eirTxPkts

       64 bit unsigned wrappable counter."
   ::= {pr1645v2Lan2MCOutQueuesH24PerformanceEntry 100663296}

pr1645v2Lan2MCOutQueuesH24PerformanceViolTxPkts OBJECT-TYPE
   SYNTAX      Counter64
   MAX-ACCESS  read-only
   STATUS      current
   DESCRIPTION
      "Path: ethernet2.performance.ifOutPriorityQueues.h24Performance.violateTxPkts

       64 bit unsigned wrappable counter."
   ::= {pr1645v2Lan2MCOutQueuesH24PerformanceEntry 301989888}

pr1645v2Lan2MCOutQueuesH24PerformanceTotOcts OBJECT-TYPE
   SYNTAX      Counter64
   MAX-ACCESS  read-only
   STATUS      current
   DESCRIPTION
      "Path: ethernet2.performance.ifOutPriorityQueues.h24Performance.totalOctets

       64 bit unsigned wrappable counter."
   ::= {pr1645v2Lan2MCOutQueuesH24PerformanceEntry 251658240}

pr1645v2Lan2MCOutQueuesH24PerformanceDirTxOcts OBJECT-TYPE
   SYNTAX      Counter64
   MAX-ACCESS  read-only
   STATUS      current
   DESCRIPTION
      "Path: ethernet2.performance.ifOutPriorityQueues.h24Performance.directTxOctets

       64 bit unsigned wrappable counter."
   ::= {pr1645v2Lan2MCOutQueuesH24PerformanceEntry 117440512}

pr1645v2Lan2MCOutQueuesH24PerformanceQdOcts OBJECT-TYPE
   SYNTAX      Counter64
   MAX-ACCESS  read-only
   STATUS      current
   DESCRIPTION
      "Path: ethernet2.performance.ifOutPriorityQueues.h24Performance.queuedOctets

       64 bit unsigned wrappable counter."
   ::= {pr1645v2Lan2MCOutQueuesH24PerformanceEntry 134217728}

pr1645v2Lan2MCOutQueuesH24PerformanceDropOcts OBJECT-TYPE
   SYNTAX      Counter64
   MAX-ACCESS  read-only
   STATUS      current
   DESCRIPTION
      "Path: ethernet2.performance.ifOutPriorityQueues.h24Performance.droppedOctets

       64 bit unsigned wrappable counter."
   ::= {pr1645v2Lan2MCOutQueuesH24PerformanceEntry 150994944}

pr1645v2Lan2MCOutQueuesH24PerformanceRDropOcts OBJECT-TYPE
   SYNTAX      Counter64
   MAX-ACCESS  read-only
   STATUS      current
   DESCRIPTION
      "Path: ethernet2.performance.ifOutPriorityQueues.h24Performance.redDroppedOctets

       64 bit unsigned wrappable counter."
   ::= {pr1645v2Lan2MCOutQueuesH24PerformanceEntry 218103808}

pr1645v2Lan2MCOutQueuesH24PerformanceCirTxOcts OBJECT-TYPE
   SYNTAX      Counter64
   MAX-ACCESS  read-only
   STATUS      current
   DESCRIPTION
      "Path: ethernet2.performance.ifOutPriorityQueues.h24Performance.cirTxOctets

       64 bit unsigned wrappable counter."
   ::= {pr1645v2Lan2MCOutQueuesH24PerformanceEntry 167772160}

pr1645v2Lan2MCOutQueuesH24PerformanceEirTxOcts OBJECT-TYPE
   SYNTAX      Counter64
   MAX-ACCESS  read-only
   STATUS      current
   DESCRIPTION
      "Path: ethernet2.performance.ifOutPriorityQueues.h24Performance.eirTxOctets

       64 bit unsigned wrappable counter."
   ::= {pr1645v2Lan2MCOutQueuesH24PerformanceEntry 184549376}

pr1645v2Lan2MCOutQueuesH24PerformanceViolTxOcts OBJECT-TYPE
   SYNTAX      Counter64
   MAX-ACCESS  read-only
   STATUS      current
   DESCRIPTION
      "Path: ethernet2.performance.ifOutPriorityQueues.h24Performance.violateTxOctets

       64 bit unsigned wrappable counter."
   ::= {pr1645v2Lan2MCOutQueuesH24PerformanceEntry 318767104}

pr1645v2Lan2MCOutQueuesH24PerformanceBandwidth OBJECT-TYPE
   SYNTAX      Integer32
   MAX-ACCESS  read-only
   STATUS      current
   DESCRIPTION
      "Path: ethernet2.performance.ifOutPriorityQueues.h24Performance.bandwidth

       unit name = bps
       formula = 8 * ; 8 /"
   ::= {pr1645v2Lan2MCOutQueuesH24PerformanceEntry 268435456}

pr1645v2Lan2MCOutQueuesD7Performance OBJECT-TYPE
   SYNTAX      SEQUENCE OF Pr1645v2Lan2MCOutQueuesD7PerformanceEntry
   MAX-ACCESS  not-accessible
   STATUS      current
   DESCRIPTION
      ""
   ::= {pr1645v2Lan2MCOutQueues 117440512}

pr1645v2Lan2MCOutQueuesD7PerformanceEntry OBJECT-TYPE
   SYNTAX      Pr1645v2Lan2MCOutQueuesD7PerformanceEntry
   MAX-ACCESS  not-accessible
   STATUS      current
   DESCRIPTION
      ""
   INDEX      { pr1645v2Lan2MCOutQueuesTableIx,
                pr1645v2Lan2MCOutQueuesD7PerformanceTableIx }
   ::= {pr1645v2Lan2MCOutQueuesD7Performance 1}

Pr1645v2Lan2MCOutQueuesD7PerformanceEntry ::=
   SEQUENCE
      {
      pr1645v2Lan2MCOutQueuesD7PerformanceTableIx
         TableIndex,
      pr1645v2Lan2MCOutQueuesD7PerformanceSysUpTime
         TimeTicks,
      pr1645v2Lan2MCOutQueuesD7PerformanceTotPkts
         Counter64,
      pr1645v2Lan2MCOutQueuesD7PerformanceDirTxPkts
         Counter64,
      pr1645v2Lan2MCOutQueuesD7PerformanceQdPkts
         Counter64,
      pr1645v2Lan2MCOutQueuesD7PerformanceDropPkts
         Counter64,
      pr1645v2Lan2MCOutQueuesD7PerformanceRDropPkts
         Counter64,
      pr1645v2Lan2MCOutQueuesD7PerformanceCirTxPkts
         Counter64,
      pr1645v2Lan2MCOutQueuesD7PerformanceEirTxPkts
         Counter64,
      pr1645v2Lan2MCOutQueuesD7PerformanceViolTxPkts
         Counter64,
      pr1645v2Lan2MCOutQueuesD7PerformanceTotOcts
         Counter64,
      pr1645v2Lan2MCOutQueuesD7PerformanceDirTxOcts
         Counter64,
      pr1645v2Lan2MCOutQueuesD7PerformanceQdOcts
         Counter64,
      pr1645v2Lan2MCOutQueuesD7PerformanceDropOcts
         Counter64,
      pr1645v2Lan2MCOutQueuesD7PerformanceRDropOcts
         Counter64,
      pr1645v2Lan2MCOutQueuesD7PerformanceCirTxOcts
         Counter64,
      pr1645v2Lan2MCOutQueuesD7PerformanceEirTxOcts
         Counter64,
      pr1645v2Lan2MCOutQueuesD7PerformanceViolTxOcts
         Counter64,
      pr1645v2Lan2MCOutQueuesD7PerformanceBandwidth
         Integer32
      }

pr1645v2Lan2MCOutQueuesD7PerformanceTableIx OBJECT-TYPE
   SYNTAX      TableIndex
   MAX-ACCESS  not-accessible
   STATUS      current
   DESCRIPTION
      ""
   ::= {pr1645v2Lan2MCOutQueuesD7PerformanceEntry 11}

pr1645v2Lan2MCOutQueuesD7PerformanceSysUpTime OBJECT-TYPE
   SYNTAX      TimeTicks
   MAX-ACCESS  read-only
   STATUS      current
   DESCRIPTION
      "Path: ethernet2.performance.ifOutPriorityQueues.d7Performance.sysUpTime

       Time in centi-second."
   ::= {pr1645v2Lan2MCOutQueuesD7PerformanceEntry 16777216}

pr1645v2Lan2MCOutQueuesD7PerformanceTotPkts OBJECT-TYPE
   SYNTAX      Counter64
   MAX-ACCESS  read-only
   STATUS      current
   DESCRIPTION
      "Path: ethernet2.performance.ifOutPriorityQueues.d7Performance.totalPkts

       64 bit unsigned wrappable counter."
   ::= {pr1645v2Lan2MCOutQueuesD7PerformanceEntry 234881024}

pr1645v2Lan2MCOutQueuesD7PerformanceDirTxPkts OBJECT-TYPE
   SYNTAX      Counter64
   MAX-ACCESS  read-only
   STATUS      current
   DESCRIPTION
      "Path: ethernet2.performance.ifOutPriorityQueues.d7Performance.directTxPkts

       64 bit unsigned wrappable counter."
   ::= {pr1645v2Lan2MCOutQueuesD7PerformanceEntry 33554432}

pr1645v2Lan2MCOutQueuesD7PerformanceQdPkts OBJECT-TYPE
   SYNTAX      Counter64
   MAX-ACCESS  read-only
   STATUS      current
   DESCRIPTION
      "Path: ethernet2.performance.ifOutPriorityQueues.d7Performance.queuedPkts

       64 bit unsigned wrappable counter."
   ::= {pr1645v2Lan2MCOutQueuesD7PerformanceEntry 50331648}

pr1645v2Lan2MCOutQueuesD7PerformanceDropPkts OBJECT-TYPE
   SYNTAX      Counter64
   MAX-ACCESS  read-only
   STATUS      current
   DESCRIPTION
      "Path: ethernet2.performance.ifOutPriorityQueues.d7Performance.droppedPkts

       64 bit unsigned wrappable counter."
   ::= {pr1645v2Lan2MCOutQueuesD7PerformanceEntry 67108864}

pr1645v2Lan2MCOutQueuesD7PerformanceRDropPkts OBJECT-TYPE
   SYNTAX      Counter64
   MAX-ACCESS  read-only
   STATUS      current
   DESCRIPTION
      "Path: ethernet2.performance.ifOutPriorityQueues.d7Performance.redDroppedPkts

       64 bit unsigned wrappable counter."
   ::= {pr1645v2Lan2MCOutQueuesD7PerformanceEntry 201326592}

pr1645v2Lan2MCOutQueuesD7PerformanceCirTxPkts OBJECT-TYPE
   SYNTAX      Counter64
   MAX-ACCESS  read-only
   STATUS      current
   DESCRIPTION
      "Path: ethernet2.performance.ifOutPriorityQueues.d7Performance.cirTxPkts

       64 bit unsigned wrappable counter."
   ::= {pr1645v2Lan2MCOutQueuesD7PerformanceEntry 83886080}

pr1645v2Lan2MCOutQueuesD7PerformanceEirTxPkts OBJECT-TYPE
   SYNTAX      Counter64
   MAX-ACCESS  read-only
   STATUS      current
   DESCRIPTION
      "Path: ethernet2.performance.ifOutPriorityQueues.d7Performance.eirTxPkts

       64 bit unsigned wrappable counter."
   ::= {pr1645v2Lan2MCOutQueuesD7PerformanceEntry 100663296}

pr1645v2Lan2MCOutQueuesD7PerformanceViolTxPkts OBJECT-TYPE
   SYNTAX      Counter64
   MAX-ACCESS  read-only
   STATUS      current
   DESCRIPTION
      "Path: ethernet2.performance.ifOutPriorityQueues.d7Performance.violateTxPkts

       64 bit unsigned wrappable counter."
   ::= {pr1645v2Lan2MCOutQueuesD7PerformanceEntry 301989888}

pr1645v2Lan2MCOutQueuesD7PerformanceTotOcts OBJECT-TYPE
   SYNTAX      Counter64
   MAX-ACCESS  read-only
   STATUS      current
   DESCRIPTION
      "Path: ethernet2.performance.ifOutPriorityQueues.d7Performance.totalOctets

       64 bit unsigned wrappable counter."
   ::= {pr1645v2Lan2MCOutQueuesD7PerformanceEntry 251658240}

pr1645v2Lan2MCOutQueuesD7PerformanceDirTxOcts OBJECT-TYPE
   SYNTAX      Counter64
   MAX-ACCESS  read-only
   STATUS      current
   DESCRIPTION
      "Path: ethernet2.performance.ifOutPriorityQueues.d7Performance.directTxOctets

       64 bit unsigned wrappable counter."
   ::= {pr1645v2Lan2MCOutQueuesD7PerformanceEntry 117440512}

pr1645v2Lan2MCOutQueuesD7PerformanceQdOcts OBJECT-TYPE
   SYNTAX      Counter64
   MAX-ACCESS  read-only
   STATUS      current
   DESCRIPTION
      "Path: ethernet2.performance.ifOutPriorityQueues.d7Performance.queuedOctets

       64 bit unsigned wrappable counter."
   ::= {pr1645v2Lan2MCOutQueuesD7PerformanceEntry 134217728}

pr1645v2Lan2MCOutQueuesD7PerformanceDropOcts OBJECT-TYPE
   SYNTAX      Counter64
   MAX-ACCESS  read-only
   STATUS      current
   DESCRIPTION
      "Path: ethernet2.performance.ifOutPriorityQueues.d7Performance.droppedOctets

       64 bit unsigned wrappable counter."
   ::= {pr1645v2Lan2MCOutQueuesD7PerformanceEntry 150994944}

pr1645v2Lan2MCOutQueuesD7PerformanceRDropOcts OBJECT-TYPE
   SYNTAX      Counter64
   MAX-ACCESS  read-only
   STATUS      current
   DESCRIPTION
      "Path: ethernet2.performance.ifOutPriorityQueues.d7Performance.redDroppedOctets

       64 bit unsigned wrappable counter."
   ::= {pr1645v2Lan2MCOutQueuesD7PerformanceEntry 218103808}

pr1645v2Lan2MCOutQueuesD7PerformanceCirTxOcts OBJECT-TYPE
   SYNTAX      Counter64
   MAX-ACCESS  read-only
   STATUS      current
   DESCRIPTION
      "Path: ethernet2.performance.ifOutPriorityQueues.d7Performance.cirTxOctets

       64 bit unsigned wrappable counter."
   ::= {pr1645v2Lan2MCOutQueuesD7PerformanceEntry 167772160}

pr1645v2Lan2MCOutQueuesD7PerformanceEirTxOcts OBJECT-TYPE
   SYNTAX      Counter64
   MAX-ACCESS  read-only
   STATUS      current
   DESCRIPTION
      "Path: ethernet2.performance.ifOutPriorityQueues.d7Performance.eirTxOctets

       64 bit unsigned wrappable counter."
   ::= {pr1645v2Lan2MCOutQueuesD7PerformanceEntry 184549376}

pr1645v2Lan2MCOutQueuesD7PerformanceViolTxOcts OBJECT-TYPE
   SYNTAX      Counter64
   MAX-ACCESS  read-only
   STATUS      current
   DESCRIPTION
      "Path: ethernet2.performance.ifOutPriorityQueues.d7Performance.violateTxOctets

       64 bit unsigned wrappable counter."
   ::= {pr1645v2Lan2MCOutQueuesD7PerformanceEntry 318767104}

pr1645v2Lan2MCOutQueuesD7PerformanceBandwidth OBJECT-TYPE
   SYNTAX      Integer32
   MAX-ACCESS  read-only
   STATUS      current
   DESCRIPTION
      "Path: ethernet2.performance.ifOutPriorityQueues.d7Performance.bandwidth

       unit name = bps
       formula = 8 * ; 8 /"
   ::= {pr1645v2Lan2MCOutQueuesD7PerformanceEntry 268435456}


pr1645v2Lan2MCOutBandwidth OBJECT IDENTIFIER ::= {pr1645v2Lan2MC 182}

pr1645v2Lan2MCOutBandwidthSSC OBJECT IDENTIFIER ::= {pr1645v2Lan2MCOutBandwidth 1}

pr1645v2Lan2MCOutBandwidthEntry OBJECT IDENTIFIER ::= {pr1645v2Lan2MCOutBandwidthSSC 1}

pr1645v2Lan2MCOutBandwidth15sec OBJECT-TYPE
   SYNTAX      Integer32
   MAX-ACCESS  read-only
   STATUS      current
   DESCRIPTION
      "Path: ethernet2.performance.ifOutBandwidth.15sec

       unit name = bps
       formula = 8 * ; 8 /"
   ::= {pr1645v2Lan2MCOutBandwidthEntry 83886080}

pr1645v2Lan2MCOutBandwidth30sec OBJECT-TYPE
   SYNTAX      Integer32
   MAX-ACCESS  read-only
   STATUS      current
   DESCRIPTION
      "Path: ethernet2.performance.ifOutBandwidth.30sec

       unit name = bps
       formula = 8 * ; 8 /"
   ::= {pr1645v2Lan2MCOutBandwidthEntry 167772160}

pr1645v2Lan2MCOutBandwidth1min OBJECT-TYPE
   SYNTAX      Integer32
   MAX-ACCESS  read-only
   STATUS      current
   DESCRIPTION
      "Path: ethernet2.performance.ifOutBandwidth.1min

       unit name = bps
       formula = 8 * ; 8 /"
   ::= {pr1645v2Lan2MCOutBandwidthEntry 335544320}

pr1645v2Lan2MCOutBandwidth2min OBJECT-TYPE
   SYNTAX      Integer32
   MAX-ACCESS  read-only
   STATUS      current
   DESCRIPTION
      "Path: ethernet2.performance.ifOutBandwidth.2min

       unit name = bps
       formula = 8 * ; 8 /"
   ::= {pr1645v2Lan2MCOutBandwidthEntry 671088640}

pr1645v2Lan2MCOutBandwidth5min OBJECT-TYPE
   SYNTAX      Integer32
   MAX-ACCESS  read-only
   STATUS      current
   DESCRIPTION
      "Path: ethernet2.performance.ifOutBandwidth.5min

       unit name = bps
       formula = 8 * ; 8 /"
   ::= {pr1645v2Lan2MCOutBandwidthEntry 1677721600}


pr1645v2Lan2MCInP OBJECT IDENTIFIER ::= {pr1645v2Lan2MC 307}

pr1645v2Lan2MCInPSSCTable OBJECT-TYPE
   SYNTAX      SEQUENCE OF Pr1645v2Lan2MCInPEntry
   MAX-ACCESS  not-accessible
   STATUS      current
   DESCRIPTION
      "h2IfInPerformance"
   ::= {pr1645v2Lan2MCInP 1}

pr1645v2Lan2MCInPEntry OBJECT-TYPE
   SYNTAX      Pr1645v2Lan2MCInPEntry
   MAX-ACCESS  not-accessible
   STATUS      current
   DESCRIPTION
      ""
   INDEX      { pr1645v2Lan2MCInPTableIx }
   ::= {pr1645v2Lan2MCInPSSCTable 1}

Pr1645v2Lan2MCInPEntry ::=
   SEQUENCE
      {
      pr1645v2Lan2MCInPTableIx
         TableIndex,
      pr1645v2Lan2MCInPSysUpTime
         TimeTicks,
      pr1645v2Lan2MCInPIfUpTime
         TimeTicks,
      pr1645v2Lan2MCInPIfStatChanges
         Counter32,
      pr1645v2Lan2MCInPIfInOctets
         Counter64,
      pr1645v2Lan2MCInPIfInUCPkts
         Counter64,
      pr1645v2Lan2MCInPIfInNUCPkts
         Counter64,
      pr1645v2Lan2MCInPIfInBCPkts
         Counter64,
      pr1645v2Lan2MCInPIfInMCPkts
         Counter64,
      pr1645v2Lan2MCInPIfInDiscards
         Counter64,
      pr1645v2Lan2MCInPIfInErrors
         Counter64,
      pr1645v2Lan2MCInPIfInUnkwn
         Counter64,
      pr1645v2Lan2MCInPInDropEx
         Counter64,
      pr1645v2Lan2MCInPInDropNoMac
         Counter64,
      pr1645v2Lan2MCInPInDropNUCast
         Counter64,
      pr1645v2Lan2MCInPInDropFilter
         Counter64,
      pr1645v2Lan2MCInPIfInBandwidth
         Integer32,
      pr1645v2Lan2MCInPIfOutOctets
         Counter64,
      pr1645v2Lan2MCInPIfOutUCPkts
         Counter64,
      pr1645v2Lan2MCInPIfOutNUCPkts
         Counter64,
      pr1645v2Lan2MCInPIfOutBCPkts
         Counter64,
      pr1645v2Lan2MCInPIfOutMCPkts
         Counter64,
      pr1645v2Lan2MCInPIfOutDiscards
         Counter64,
      pr1645v2Lan2MCInPIfOutErrors
         Counter64,
      pr1645v2Lan2MCInPOutDropEx
         Counter64,
      pr1645v2Lan2MCInPOutDropNoArp
         Counter64,
      pr1645v2Lan2MCInPOutDropFilter
         Counter64,
      pr1645v2Lan2MCInPIfOutBandwidth
         Integer32,
      pr1645v2Lan2MCInPIfErrSec
         Counter32
      }

pr1645v2Lan2MCInPTableIx OBJECT-TYPE
   SYNTAX      TableIndex
   MAX-ACCESS  not-accessible
   STATUS      current
   DESCRIPTION
      ""
   ::= {pr1645v2Lan2MCInPEntry 11}

pr1645v2Lan2MCInPSysUpTime OBJECT-TYPE
   SYNTAX      TimeTicks
   MAX-ACCESS  read-only
   STATUS      current
   DESCRIPTION
      "Path: ethernet2.performance.h2Performance.sysUpTime

       Time in centi-second."
   ::= {pr1645v2Lan2MCInPEntry 16777216}

pr1645v2Lan2MCInPIfUpTime OBJECT-TYPE
   SYNTAX      TimeTicks
   MAX-ACCESS  read-only
   STATUS      current
   DESCRIPTION
      "Path: ethernet2.performance.h2Performance.ifUpTime

       Time in centi-second."
   ::= {pr1645v2Lan2MCInPEntry 33554432}

pr1645v2Lan2MCInPIfStatChanges OBJECT-TYPE
   SYNTAX      Counter32
   MAX-ACCESS  read-only
   STATUS      current
   DESCRIPTION
      "Path: ethernet2.performance.h2Performance.ifStatusChanges

       32 bit unsigned wrappable counter."
   ::= {pr1645v2Lan2MCInPEntry 50331648}

pr1645v2Lan2MCInPIfInOctets OBJECT-TYPE
   SYNTAX      Counter64
   MAX-ACCESS  read-only
   STATUS      current
   DESCRIPTION
      "Path: ethernet2.performance.h2Performance.ifInOctets

       64 bit unsigned wrappable counter."
   ::= {pr1645v2Lan2MCInPEntry 67108864}

pr1645v2Lan2MCInPIfInUCPkts OBJECT-TYPE
   SYNTAX      Counter64
   MAX-ACCESS  read-only
   STATUS      current
   DESCRIPTION
      "Path: ethernet2.performance.h2Performance.ifInUcastPkts

       64 bit unsigned wrappable counter."
   ::= {pr1645v2Lan2MCInPEntry 83886080}

pr1645v2Lan2MCInPIfInNUCPkts OBJECT-TYPE
   SYNTAX      Counter64
   MAX-ACCESS  read-only
   STATUS      current
   DESCRIPTION
      "Path: ethernet2.performance.h2Performance.ifInNUcastPkts

       64 bit unsigned wrappable counter."
   ::= {pr1645v2Lan2MCInPEntry 100663296}

pr1645v2Lan2MCInPIfInBCPkts OBJECT-TYPE
   SYNTAX      Counter64
   MAX-ACCESS  read-only
   STATUS      current
   DESCRIPTION
      "Path: ethernet2.performance.h2Performance.ifInBcastPkts

       64 bit unsigned wrappable counter."
   ::= {pr1645v2Lan2MCInPEntry 419430400}

pr1645v2Lan2MCInPIfInMCPkts OBJECT-TYPE
   SYNTAX      Counter64
   MAX-ACCESS  read-only
   STATUS      current
   DESCRIPTION
      "Path: ethernet2.performance.h2Performance.ifInMcastPkts

       64 bit unsigned wrappable counter."
   ::= {pr1645v2Lan2MCInPEntry 436207616}

pr1645v2Lan2MCInPIfInDiscards OBJECT-TYPE
   SYNTAX      Counter64
   MAX-ACCESS  read-only
   STATUS      current
   DESCRIPTION
      "Path: ethernet2.performance.h2Performance.ifInDiscards

       64 bit unsigned wrappable counter."
   ::= {pr1645v2Lan2MCInPEntry 117440512}

pr1645v2Lan2MCInPIfInErrors OBJECT-TYPE
   SYNTAX      Counter64
   MAX-ACCESS  read-only
   STATUS      current
   DESCRIPTION
      "Path: ethernet2.performance.h2Performance.ifInErrors

       64 bit unsigned wrappable counter."
   ::= {pr1645v2Lan2MCInPEntry 134217728}

pr1645v2Lan2MCInPIfInUnkwn OBJECT-TYPE
   SYNTAX      Counter64
   MAX-ACCESS  read-only
   STATUS      current
   DESCRIPTION
      "Path: ethernet2.performance.h2Performance.ifInUnknownProtos

       64 bit unsigned wrappable counter."
   ::= {pr1645v2Lan2MCInPEntry 150994944}

pr1645v2Lan2MCInPInDropEx OBJECT-TYPE
   SYNTAX      Counter64
   MAX-ACCESS  read-only
   STATUS      current
   DESCRIPTION
      "Path: ethernet2.performance.h2Performance.ifInDropLevelExceeded

       64 bit unsigned wrappable counter."
   ::= {pr1645v2Lan2MCInPEntry 335544320}

pr1645v2Lan2MCInPInDropNoMac OBJECT-TYPE
   SYNTAX      Counter64
   MAX-ACCESS  read-only
   STATUS      current
   DESCRIPTION
      "Path: ethernet2.performance.h2Performance.fInDiscardsNoMacFit

       64 bit unsigned wrappable counter."
   ::= {pr1645v2Lan2MCInPEntry 301989888}

pr1645v2Lan2MCInPInDropNUCast OBJECT-TYPE
   SYNTAX      Counter64
   MAX-ACCESS  read-only
   STATUS      current
   DESCRIPTION
      "Path: ethernet2.performance.h2Performance.fInDiscardsNUCast

       64 bit unsigned wrappable counter."
   ::= {pr1645v2Lan2MCInPEntry 318767104}

pr1645v2Lan2MCInPInDropFilter OBJECT-TYPE
   SYNTAX      Counter64
   MAX-ACCESS  read-only
   STATUS      current
   DESCRIPTION
      "Path: ethernet2.performance.h2Performance.fInDiscardsFilter

       64 bit unsigned wrappable counter."
   ::= {pr1645v2Lan2MCInPEntry 385875968}

pr1645v2Lan2MCInPIfInBandwidth OBJECT-TYPE
   SYNTAX      Integer32
   MAX-ACCESS  read-only
   STATUS      current
   DESCRIPTION
      "Path: ethernet2.performance.h2Performance.ifInBandwidth

       unit name = bps
       formula = 8 * ; 8 /"
   ::= {pr1645v2Lan2MCInPEntry 268435456}

pr1645v2Lan2MCInPIfOutOctets OBJECT-TYPE
   SYNTAX      Counter64
   MAX-ACCESS  read-only
   STATUS      current
   DESCRIPTION
      "Path: ethernet2.performance.h2Performance.ifOutOctets

       64 bit unsigned wrappable counter."
   ::= {pr1645v2Lan2MCInPEntry 167772160}

pr1645v2Lan2MCInPIfOutUCPkts OBJECT-TYPE
   SYNTAX      Counter64
   MAX-ACCESS  read-only
   STATUS      current
   DESCRIPTION
      "Path: ethernet2.performance.h2Performance.ifOutUcastPkts

       64 bit unsigned wrappable counter."
   ::= {pr1645v2Lan2MCInPEntry 184549376}

pr1645v2Lan2MCInPIfOutNUCPkts OBJECT-TYPE
   SYNTAX      Counter64
   MAX-ACCESS  read-only
   STATUS      current
   DESCRIPTION
      "Path: ethernet2.performance.h2Performance.ifOutNUcastPkts

       64 bit unsigned wrappable counter."
   ::= {pr1645v2Lan2MCInPEntry 201326592}

pr1645v2Lan2MCInPIfOutBCPkts OBJECT-TYPE
   SYNTAX      Counter64
   MAX-ACCESS  read-only
   STATUS      current
   DESCRIPTION
      "Path: ethernet2.performance.h2Performance.ifOutBcastPkts

       64 bit unsigned wrappable counter."
   ::= {pr1645v2Lan2MCInPEntry 452984832}

pr1645v2Lan2MCInPIfOutMCPkts OBJECT-TYPE
   SYNTAX      Counter64
   MAX-ACCESS  read-only
   STATUS      current
   DESCRIPTION
      "Path: ethernet2.performance.h2Performance.ifOutMcastPkts

       64 bit unsigned wrappable counter."
   ::= {pr1645v2Lan2MCInPEntry 469762048}

pr1645v2Lan2MCInPIfOutDiscards OBJECT-TYPE
   SYNTAX      Counter64
   MAX-ACCESS  read-only
   STATUS      current
   DESCRIPTION
      "Path: ethernet2.performance.h2Performance.ifOutDiscards

       64 bit unsigned wrappable counter."
   ::= {pr1645v2Lan2MCInPEntry 218103808}

pr1645v2Lan2MCInPIfOutErrors OBJECT-TYPE
   SYNTAX      Counter64
   MAX-ACCESS  read-only
   STATUS      current
   DESCRIPTION
      "Path: ethernet2.performance.h2Performance.ifOutErrors

       64 bit unsigned wrappable counter."
   ::= {pr1645v2Lan2MCInPEntry 234881024}

pr1645v2Lan2MCInPOutDropEx OBJECT-TYPE
   SYNTAX      Counter64
   MAX-ACCESS  read-only
   STATUS      current
   DESCRIPTION
      "Path: ethernet2.performance.h2Performance.ifOutDropLevelExceeded

       64 bit unsigned wrappable counter."
   ::= {pr1645v2Lan2MCInPEntry 352321536}

pr1645v2Lan2MCInPOutDropNoArp OBJECT-TYPE
   SYNTAX      Counter64
   MAX-ACCESS  read-only
   STATUS      current
   DESCRIPTION
      "Path: ethernet2.performance.h2Performance.ifOutDiscardsNoArp

       64 bit unsigned wrappable counter."
   ::= {pr1645v2Lan2MCInPEntry 369098752}

pr1645v2Lan2MCInPOutDropFilter OBJECT-TYPE
   SYNTAX      Counter64
   MAX-ACCESS  read-only
   STATUS      current
   DESCRIPTION
      "Path: ethernet2.performance.h2Performance.ifOutDiscardsFilter

       64 bit unsigned wrappable counter."
   ::= {pr1645v2Lan2MCInPEntry 402653184}

pr1645v2Lan2MCInPIfOutBandwidth OBJECT-TYPE
   SYNTAX      Integer32
   MAX-ACCESS  read-only
   STATUS      current
   DESCRIPTION
      "Path: ethernet2.performance.h2Performance.ifOutBandwidth

       unit name = bps
       formula = 8 * ; 8 /"
   ::= {pr1645v2Lan2MCInPEntry 285212672}

pr1645v2Lan2MCInPIfErrSec OBJECT-TYPE
   SYNTAX      Counter32
   MAX-ACCESS  read-only
   STATUS      current
   DESCRIPTION
      "Path: ethernet2.performance.h2Performance.ifErrSec

       32 bit unsigned wrappable counter."
   ::= {pr1645v2Lan2MCInPEntry 251658240}


pr1645v2Lan2MCH24InP OBJECT IDENTIFIER ::= {pr1645v2Lan2MC 308}

pr1645v2Lan2MCH24InPSSCTable OBJECT-TYPE
   SYNTAX      SEQUENCE OF Pr1645v2Lan2MCH24InPEntry
   MAX-ACCESS  not-accessible
   STATUS      current
   DESCRIPTION
      "h24IfInPerformance"
   ::= {pr1645v2Lan2MCH24InP 1}

pr1645v2Lan2MCH24InPEntry OBJECT-TYPE
   SYNTAX      Pr1645v2Lan2MCH24InPEntry
   MAX-ACCESS  not-accessible
   STATUS      current
   DESCRIPTION
      ""
   INDEX      { pr1645v2Lan2MCH24InPTableIx }
   ::= {pr1645v2Lan2MCH24InPSSCTable 1}

Pr1645v2Lan2MCH24InPEntry ::=
   SEQUENCE
      {
      pr1645v2Lan2MCH24InPTableIx
         TableIndex,
      pr1645v2Lan2MCH24InPSysUpTime
         TimeTicks,
      pr1645v2Lan2MCH24InPIfUpTime
         TimeTicks,
      pr1645v2Lan2MCH24InPIfStatChanges
         Counter32,
      pr1645v2Lan2MCH24InPIfInOctets
         Counter64,
      pr1645v2Lan2MCH24InPIfInUCPkts
         Counter64,
      pr1645v2Lan2MCH24InPIfInNUCPkts
         Counter64,
      pr1645v2Lan2MCH24InPIfInBCPkts
         Counter64,
      pr1645v2Lan2MCH24InPIfInMCPkts
         Counter64,
      pr1645v2Lan2MCH24InPIfInDiscards
         Counter64,
      pr1645v2Lan2MCH24InPIfInErrors
         Counter64,
      pr1645v2Lan2MCH24InPIfInUnkwn
         Counter64,
      pr1645v2Lan2MCH24InPInDropEx
         Counter64,
      pr1645v2Lan2MCH24InPInDropNoMac
         Counter64,
      pr1645v2Lan2MCH24InPInDropNUCast
         Counter64,
      pr1645v2Lan2MCH24InPInDropFilter
         Counter64,
      pr1645v2Lan2MCH24InPIfInBandwidth
         Integer32,
      pr1645v2Lan2MCH24InPIfOutOctets
         Counter64,
      pr1645v2Lan2MCH24InPIfOutUCPkts
         Counter64,
      pr1645v2Lan2MCH24InPIfOutNUCPkts
         Counter64,
      pr1645v2Lan2MCH24InPIfOutBCPkts
         Counter64,
      pr1645v2Lan2MCH24InPIfOutMCPkts
         Counter64,
      pr1645v2Lan2MCH24InPIfOutDiscards
         Counter64,
      pr1645v2Lan2MCH24InPIfOutErrors
         Counter64,
      pr1645v2Lan2MCH24InPOutDropEx
         Counter64,
      pr1645v2Lan2MCH24InPOutDropNoArp
         Counter64,
      pr1645v2Lan2MCH24InPOutDropFilter
         Counter64,
      pr1645v2Lan2MCH24InPIfOutBandwidth
         Integer32,
      pr1645v2Lan2MCH24InPIfErrSec
         Counter32
      }

pr1645v2Lan2MCH24InPTableIx OBJECT-TYPE
   SYNTAX      TableIndex
   MAX-ACCESS  not-accessible
   STATUS      current
   DESCRIPTION
      ""
   ::= {pr1645v2Lan2MCH24InPEntry 11}

pr1645v2Lan2MCH24InPSysUpTime OBJECT-TYPE
   SYNTAX      TimeTicks
   MAX-ACCESS  read-only
   STATUS      current
   DESCRIPTION
      "Path: ethernet2.performance.h24Performance.sysUpTime

       Time in centi-second."
   ::= {pr1645v2Lan2MCH24InPEntry 16777216}

pr1645v2Lan2MCH24InPIfUpTime OBJECT-TYPE
   SYNTAX      TimeTicks
   MAX-ACCESS  read-only
   STATUS      current
   DESCRIPTION
      "Path: ethernet2.performance.h24Performance.ifUpTime

       Time in centi-second."
   ::= {pr1645v2Lan2MCH24InPEntry 33554432}

pr1645v2Lan2MCH24InPIfStatChanges OBJECT-TYPE
   SYNTAX      Counter32
   MAX-ACCESS  read-only
   STATUS      current
   DESCRIPTION
      "Path: ethernet2.performance.h24Performance.ifStatusChanges

       32 bit unsigned wrappable counter."
   ::= {pr1645v2Lan2MCH24InPEntry 50331648}

pr1645v2Lan2MCH24InPIfInOctets OBJECT-TYPE
   SYNTAX      Counter64
   MAX-ACCESS  read-only
   STATUS      current
   DESCRIPTION
      "Path: ethernet2.performance.h24Performance.ifInOctets

       64 bit unsigned wrappable counter."
   ::= {pr1645v2Lan2MCH24InPEntry 67108864}

pr1645v2Lan2MCH24InPIfInUCPkts OBJECT-TYPE
   SYNTAX      Counter64
   MAX-ACCESS  read-only
   STATUS      current
   DESCRIPTION
      "Path: ethernet2.performance.h24Performance.ifInUcastPkts

       64 bit unsigned wrappable counter."
   ::= {pr1645v2Lan2MCH24InPEntry 83886080}

pr1645v2Lan2MCH24InPIfInNUCPkts OBJECT-TYPE
   SYNTAX      Counter64
   MAX-ACCESS  read-only
   STATUS      current
   DESCRIPTION
      "Path: ethernet2.performance.h24Performance.ifInNUcastPkts

       64 bit unsigned wrappable counter."
   ::= {pr1645v2Lan2MCH24InPEntry 100663296}

pr1645v2Lan2MCH24InPIfInBCPkts OBJECT-TYPE
   SYNTAX      Counter64
   MAX-ACCESS  read-only
   STATUS      current
   DESCRIPTION
      "Path: ethernet2.performance.h24Performance.ifInBcastPkts

       64 bit unsigned wrappable counter."
   ::= {pr1645v2Lan2MCH24InPEntry 419430400}

pr1645v2Lan2MCH24InPIfInMCPkts OBJECT-TYPE
   SYNTAX      Counter64
   MAX-ACCESS  read-only
   STATUS      current
   DESCRIPTION
      "Path: ethernet2.performance.h24Performance.ifInMcastPkts

       64 bit unsigned wrappable counter."
   ::= {pr1645v2Lan2MCH24InPEntry 436207616}

pr1645v2Lan2MCH24InPIfInDiscards OBJECT-TYPE
   SYNTAX      Counter64
   MAX-ACCESS  read-only
   STATUS      current
   DESCRIPTION
      "Path: ethernet2.performance.h24Performance.ifInDiscards

       64 bit unsigned wrappable counter."
   ::= {pr1645v2Lan2MCH24InPEntry 117440512}

pr1645v2Lan2MCH24InPIfInErrors OBJECT-TYPE
   SYNTAX      Counter64
   MAX-ACCESS  read-only
   STATUS      current
   DESCRIPTION
      "Path: ethernet2.performance.h24Performance.ifInErrors

       64 bit unsigned wrappable counter."
   ::= {pr1645v2Lan2MCH24InPEntry 134217728}

pr1645v2Lan2MCH24InPIfInUnkwn OBJECT-TYPE
   SYNTAX      Counter64
   MAX-ACCESS  read-only
   STATUS      current
   DESCRIPTION
      "Path: ethernet2.performance.h24Performance.ifInUnknownProtos

       64 bit unsigned wrappable counter."
   ::= {pr1645v2Lan2MCH24InPEntry 150994944}

pr1645v2Lan2MCH24InPInDropEx OBJECT-TYPE
   SYNTAX      Counter64
   MAX-ACCESS  read-only
   STATUS      current
   DESCRIPTION
      "Path: ethernet2.performance.h24Performance.ifInDropLevelExceeded

       64 bit unsigned wrappable counter."
   ::= {pr1645v2Lan2MCH24InPEntry 335544320}

pr1645v2Lan2MCH24InPInDropNoMac OBJECT-TYPE
   SYNTAX      Counter64
   MAX-ACCESS  read-only
   STATUS      current
   DESCRIPTION
      "Path: ethernet2.performance.h24Performance.fInDiscardsNoMacFit

       64 bit unsigned wrappable counter."
   ::= {pr1645v2Lan2MCH24InPEntry 301989888}

pr1645v2Lan2MCH24InPInDropNUCast OBJECT-TYPE
   SYNTAX      Counter64
   MAX-ACCESS  read-only
   STATUS      current
   DESCRIPTION
      "Path: ethernet2.performance.h24Performance.fInDiscardsNUCast

       64 bit unsigned wrappable counter."
   ::= {pr1645v2Lan2MCH24InPEntry 318767104}

pr1645v2Lan2MCH24InPInDropFilter OBJECT-TYPE
   SYNTAX      Counter64
   MAX-ACCESS  read-only
   STATUS      current
   DESCRIPTION
      "Path: ethernet2.performance.h24Performance.fInDiscardsFilter

       64 bit unsigned wrappable counter."
   ::= {pr1645v2Lan2MCH24InPEntry 385875968}

pr1645v2Lan2MCH24InPIfInBandwidth OBJECT-TYPE
   SYNTAX      Integer32
   MAX-ACCESS  read-only
   STATUS      current
   DESCRIPTION
      "Path: ethernet2.performance.h24Performance.ifInBandwidth

       unit name = bps
       formula = 8 * ; 8 /"
   ::= {pr1645v2Lan2MCH24InPEntry 268435456}

pr1645v2Lan2MCH24InPIfOutOctets OBJECT-TYPE
   SYNTAX      Counter64
   MAX-ACCESS  read-only
   STATUS      current
   DESCRIPTION
      "Path: ethernet2.performance.h24Performance.ifOutOctets

       64 bit unsigned wrappable counter."
   ::= {pr1645v2Lan2MCH24InPEntry 167772160}

pr1645v2Lan2MCH24InPIfOutUCPkts OBJECT-TYPE
   SYNTAX      Counter64
   MAX-ACCESS  read-only
   STATUS      current
   DESCRIPTION
      "Path: ethernet2.performance.h24Performance.ifOutUcastPkts

       64 bit unsigned wrappable counter."
   ::= {pr1645v2Lan2MCH24InPEntry 184549376}

pr1645v2Lan2MCH24InPIfOutNUCPkts OBJECT-TYPE
   SYNTAX      Counter64
   MAX-ACCESS  read-only
   STATUS      current
   DESCRIPTION
      "Path: ethernet2.performance.h24Performance.ifOutNUcastPkts

       64 bit unsigned wrappable counter."
   ::= {pr1645v2Lan2MCH24InPEntry 201326592}

pr1645v2Lan2MCH24InPIfOutBCPkts OBJECT-TYPE
   SYNTAX      Counter64
   MAX-ACCESS  read-only
   STATUS      current
   DESCRIPTION
      "Path: ethernet2.performance.h24Performance.ifOutBcastPkts

       64 bit unsigned wrappable counter."
   ::= {pr1645v2Lan2MCH24InPEntry 452984832}

pr1645v2Lan2MCH24InPIfOutMCPkts OBJECT-TYPE
   SYNTAX      Counter64
   MAX-ACCESS  read-only
   STATUS      current
   DESCRIPTION
      "Path: ethernet2.performance.h24Performance.ifOutMcastPkts

       64 bit unsigned wrappable counter."
   ::= {pr1645v2Lan2MCH24InPEntry 469762048}

pr1645v2Lan2MCH24InPIfOutDiscards OBJECT-TYPE
   SYNTAX      Counter64
   MAX-ACCESS  read-only
   STATUS      current
   DESCRIPTION
      "Path: ethernet2.performance.h24Performance.ifOutDiscards

       64 bit unsigned wrappable counter."
   ::= {pr1645v2Lan2MCH24InPEntry 218103808}

pr1645v2Lan2MCH24InPIfOutErrors OBJECT-TYPE
   SYNTAX      Counter64
   MAX-ACCESS  read-only
   STATUS      current
   DESCRIPTION
      "Path: ethernet2.performance.h24Performance.ifOutErrors

       64 bit unsigned wrappable counter."
   ::= {pr1645v2Lan2MCH24InPEntry 234881024}

pr1645v2Lan2MCH24InPOutDropEx OBJECT-TYPE
   SYNTAX      Counter64
   MAX-ACCESS  read-only
   STATUS      current
   DESCRIPTION
      "Path: ethernet2.performance.h24Performance.ifOutDropLevelExceeded

       64 bit unsigned wrappable counter."
   ::= {pr1645v2Lan2MCH24InPEntry 352321536}

pr1645v2Lan2MCH24InPOutDropNoArp OBJECT-TYPE
   SYNTAX      Counter64
   MAX-ACCESS  read-only
   STATUS      current
   DESCRIPTION
      "Path: ethernet2.performance.h24Performance.ifOutDiscardsNoArp

       64 bit unsigned wrappable counter."
   ::= {pr1645v2Lan2MCH24InPEntry 369098752}

pr1645v2Lan2MCH24InPOutDropFilter OBJECT-TYPE
   SYNTAX      Counter64
   MAX-ACCESS  read-only
   STATUS      current
   DESCRIPTION
      "Path: ethernet2.performance.h24Performance.ifOutDiscardsFilter

       64 bit unsigned wrappable counter."
   ::= {pr1645v2Lan2MCH24InPEntry 402653184}

pr1645v2Lan2MCH24InPIfOutBandwidth OBJECT-TYPE
   SYNTAX      Integer32
   MAX-ACCESS  read-only
   STATUS      current
   DESCRIPTION
      "Path: ethernet2.performance.h24Performance.ifOutBandwidth

       unit name = bps
       formula = 8 * ; 8 /"
   ::= {pr1645v2Lan2MCH24InPEntry 285212672}

pr1645v2Lan2MCH24InPIfErrSec OBJECT-TYPE
   SYNTAX      Counter32
   MAX-ACCESS  read-only
   STATUS      current
   DESCRIPTION
      "Path: ethernet2.performance.h24Performance.ifErrSec

       32 bit unsigned wrappable counter."
   ::= {pr1645v2Lan2MCH24InPEntry 251658240}


pr1645v2Lan2MCD7InP OBJECT IDENTIFIER ::= {pr1645v2Lan2MC 309}

pr1645v2Lan2MCD7InPSSCTable OBJECT-TYPE
   SYNTAX      SEQUENCE OF Pr1645v2Lan2MCD7InPEntry
   MAX-ACCESS  not-accessible
   STATUS      current
   DESCRIPTION
      "d7IfInPerformance"
   ::= {pr1645v2Lan2MCD7InP 1}

pr1645v2Lan2MCD7InPEntry OBJECT-TYPE
   SYNTAX      Pr1645v2Lan2MCD7InPEntry
   MAX-ACCESS  not-accessible
   STATUS      current
   DESCRIPTION
      ""
   INDEX      { pr1645v2Lan2MCD7InPTableIx }
   ::= {pr1645v2Lan2MCD7InPSSCTable 1}

Pr1645v2Lan2MCD7InPEntry ::=
   SEQUENCE
      {
      pr1645v2Lan2MCD7InPTableIx
         TableIndex,
      pr1645v2Lan2MCD7InPSysUpTime
         TimeTicks,
      pr1645v2Lan2MCD7InPIfUpTime
         TimeTicks,
      pr1645v2Lan2MCD7InPIfStatChanges
         Counter32,
      pr1645v2Lan2MCD7InPIfInOctets
         Counter64,
      pr1645v2Lan2MCD7InPIfInUCPkts
         Counter64,
      pr1645v2Lan2MCD7InPIfInNUCPkts
         Counter64,
      pr1645v2Lan2MCD7InPIfInBCPkts
         Counter64,
      pr1645v2Lan2MCD7InPIfInMCPkts
         Counter64,
      pr1645v2Lan2MCD7InPIfInDiscards
         Counter64,
      pr1645v2Lan2MCD7InPIfInErrors
         Counter64,
      pr1645v2Lan2MCD7InPIfInUnkwn
         Counter64,
      pr1645v2Lan2MCD7InPInDropEx
         Counter64,
      pr1645v2Lan2MCD7InPInDropNoMac
         Counter64,
      pr1645v2Lan2MCD7InPInDropNUCast
         Counter64,
      pr1645v2Lan2MCD7InPInDropFilter
         Counter64,
      pr1645v2Lan2MCD7InPIfInBandwidth
         Integer32,
      pr1645v2Lan2MCD7InPIfOutOctets
         Counter64,
      pr1645v2Lan2MCD7InPIfOutUCPkts
         Counter64,
      pr1645v2Lan2MCD7InPIfOutNUCPkts
         Counter64,
      pr1645v2Lan2MCD7InPIfOutBCPkts
         Counter64,
      pr1645v2Lan2MCD7InPIfOutMCPkts
         Counter64,
      pr1645v2Lan2MCD7InPIfOutDiscards
         Counter64,
      pr1645v2Lan2MCD7InPIfOutErrors
         Counter64,
      pr1645v2Lan2MCD7InPOutDropEx
         Counter64,
      pr1645v2Lan2MCD7InPOutDropNoArp
         Counter64,
      pr1645v2Lan2MCD7InPOutDropFilter
         Counter64,
      pr1645v2Lan2MCD7InPIfOutBandwidth
         Integer32,
      pr1645v2Lan2MCD7InPIfErrSec
         Counter32
      }

pr1645v2Lan2MCD7InPTableIx OBJECT-TYPE
   SYNTAX      TableIndex
   MAX-ACCESS  not-accessible
   STATUS      current
   DESCRIPTION
      ""
   ::= {pr1645v2Lan2MCD7InPEntry 11}

pr1645v2Lan2MCD7InPSysUpTime OBJECT-TYPE
   SYNTAX      TimeTicks
   MAX-ACCESS  read-only
   STATUS      current
   DESCRIPTION
      "Path: ethernet2.performance.d7Performance.sysUpTime

       Time in centi-second."
   ::= {pr1645v2Lan2MCD7InPEntry 16777216}

pr1645v2Lan2MCD7InPIfUpTime OBJECT-TYPE
   SYNTAX      TimeTicks
   MAX-ACCESS  read-only
   STATUS      current
   DESCRIPTION
      "Path: ethernet2.performance.d7Performance.ifUpTime

       Time in centi-second."
   ::= {pr1645v2Lan2MCD7InPEntry 33554432}

pr1645v2Lan2MCD7InPIfStatChanges OBJECT-TYPE
   SYNTAX      Counter32
   MAX-ACCESS  read-only
   STATUS      current
   DESCRIPTION
      "Path: ethernet2.performance.d7Performance.ifStatusChanges

       32 bit unsigned wrappable counter."
   ::= {pr1645v2Lan2MCD7InPEntry 50331648}

pr1645v2Lan2MCD7InPIfInOctets OBJECT-TYPE
   SYNTAX      Counter64
   MAX-ACCESS  read-only
   STATUS      current
   DESCRIPTION
      "Path: ethernet2.performance.d7Performance.ifInOctets

       64 bit unsigned wrappable counter."
   ::= {pr1645v2Lan2MCD7InPEntry 67108864}

pr1645v2Lan2MCD7InPIfInUCPkts OBJECT-TYPE
   SYNTAX      Counter64
   MAX-ACCESS  read-only
   STATUS      current
   DESCRIPTION
      "Path: ethernet2.performance.d7Performance.ifInUcastPkts

       64 bit unsigned wrappable counter."
   ::= {pr1645v2Lan2MCD7InPEntry 83886080}

pr1645v2Lan2MCD7InPIfInNUCPkts OBJECT-TYPE
   SYNTAX      Counter64
   MAX-ACCESS  read-only
   STATUS      current
   DESCRIPTION
      "Path: ethernet2.performance.d7Performance.ifInNUcastPkts

       64 bit unsigned wrappable counter."
   ::= {pr1645v2Lan2MCD7InPEntry 100663296}

pr1645v2Lan2MCD7InPIfInBCPkts OBJECT-TYPE
   SYNTAX      Counter64
   MAX-ACCESS  read-only
   STATUS      current
   DESCRIPTION
      "Path: ethernet2.performance.d7Performance.ifInBcastPkts

       64 bit unsigned wrappable counter."
   ::= {pr1645v2Lan2MCD7InPEntry 419430400}

pr1645v2Lan2MCD7InPIfInMCPkts OBJECT-TYPE
   SYNTAX      Counter64
   MAX-ACCESS  read-only
   STATUS      current
   DESCRIPTION
      "Path: ethernet2.performance.d7Performance.ifInMcastPkts

       64 bit unsigned wrappable counter."
   ::= {pr1645v2Lan2MCD7InPEntry 436207616}

pr1645v2Lan2MCD7InPIfInDiscards OBJECT-TYPE
   SYNTAX      Counter64
   MAX-ACCESS  read-only
   STATUS      current
   DESCRIPTION
      "Path: ethernet2.performance.d7Performance.ifInDiscards

       64 bit unsigned wrappable counter."
   ::= {pr1645v2Lan2MCD7InPEntry 117440512}

pr1645v2Lan2MCD7InPIfInErrors OBJECT-TYPE
   SYNTAX      Counter64
   MAX-ACCESS  read-only
   STATUS      current
   DESCRIPTION
      "Path: ethernet2.performance.d7Performance.ifInErrors

       64 bit unsigned wrappable counter."
   ::= {pr1645v2Lan2MCD7InPEntry 134217728}

pr1645v2Lan2MCD7InPIfInUnkwn OBJECT-TYPE
   SYNTAX      Counter64
   MAX-ACCESS  read-only
   STATUS      current
   DESCRIPTION
      "Path: ethernet2.performance.d7Performance.ifInUnknownProtos

       64 bit unsigned wrappable counter."
   ::= {pr1645v2Lan2MCD7InPEntry 150994944}

pr1645v2Lan2MCD7InPInDropEx OBJECT-TYPE
   SYNTAX      Counter64
   MAX-ACCESS  read-only
   STATUS      current
   DESCRIPTION
      "Path: ethernet2.performance.d7Performance.ifInDropLevelExceeded

       64 bit unsigned wrappable counter."
   ::= {pr1645v2Lan2MCD7InPEntry 335544320}

pr1645v2Lan2MCD7InPInDropNoMac OBJECT-TYPE
   SYNTAX      Counter64
   MAX-ACCESS  read-only
   STATUS      current
   DESCRIPTION
      "Path: ethernet2.performance.d7Performance.fInDiscardsNoMacFit

       64 bit unsigned wrappable counter."
   ::= {pr1645v2Lan2MCD7InPEntry 301989888}

pr1645v2Lan2MCD7InPInDropNUCast OBJECT-TYPE
   SYNTAX      Counter64
   MAX-ACCESS  read-only
   STATUS      current
   DESCRIPTION
      "Path: ethernet2.performance.d7Performance.fInDiscardsNUCast

       64 bit unsigned wrappable counter."
   ::= {pr1645v2Lan2MCD7InPEntry 318767104}

pr1645v2Lan2MCD7InPInDropFilter OBJECT-TYPE
   SYNTAX      Counter64
   MAX-ACCESS  read-only
   STATUS      current
   DESCRIPTION
      "Path: ethernet2.performance.d7Performance.fInDiscardsFilter

       64 bit unsigned wrappable counter."
   ::= {pr1645v2Lan2MCD7InPEntry 385875968}

pr1645v2Lan2MCD7InPIfInBandwidth OBJECT-TYPE
   SYNTAX      Integer32
   MAX-ACCESS  read-only
   STATUS      current
   DESCRIPTION
      "Path: ethernet2.performance.d7Performance.ifInBandwidth

       unit name = bps
       formula = 8 * ; 8 /"
   ::= {pr1645v2Lan2MCD7InPEntry 268435456}

pr1645v2Lan2MCD7InPIfOutOctets OBJECT-TYPE
   SYNTAX      Counter64
   MAX-ACCESS  read-only
   STATUS      current
   DESCRIPTION
      "Path: ethernet2.performance.d7Performance.ifOutOctets

       64 bit unsigned wrappable counter."
   ::= {pr1645v2Lan2MCD7InPEntry 167772160}

pr1645v2Lan2MCD7InPIfOutUCPkts OBJECT-TYPE
   SYNTAX      Counter64
   MAX-ACCESS  read-only
   STATUS      current
   DESCRIPTION
      "Path: ethernet2.performance.d7Performance.ifOutUcastPkts

       64 bit unsigned wrappable counter."
   ::= {pr1645v2Lan2MCD7InPEntry 184549376}

pr1645v2Lan2MCD7InPIfOutNUCPkts OBJECT-TYPE
   SYNTAX      Counter64
   MAX-ACCESS  read-only
   STATUS      current
   DESCRIPTION
      "Path: ethernet2.performance.d7Performance.ifOutNUcastPkts

       64 bit unsigned wrappable counter."
   ::= {pr1645v2Lan2MCD7InPEntry 201326592}

pr1645v2Lan2MCD7InPIfOutBCPkts OBJECT-TYPE
   SYNTAX      Counter64
   MAX-ACCESS  read-only
   STATUS      current
   DESCRIPTION
      "Path: ethernet2.performance.d7Performance.ifOutBcastPkts

       64 bit unsigned wrappable counter."
   ::= {pr1645v2Lan2MCD7InPEntry 452984832}

pr1645v2Lan2MCD7InPIfOutMCPkts OBJECT-TYPE
   SYNTAX      Counter64
   MAX-ACCESS  read-only
   STATUS      current
   DESCRIPTION
      "Path: ethernet2.performance.d7Performance.ifOutMcastPkts

       64 bit unsigned wrappable counter."
   ::= {pr1645v2Lan2MCD7InPEntry 469762048}

pr1645v2Lan2MCD7InPIfOutDiscards OBJECT-TYPE
   SYNTAX      Counter64
   MAX-ACCESS  read-only
   STATUS      current
   DESCRIPTION
      "Path: ethernet2.performance.d7Performance.ifOutDiscards

       64 bit unsigned wrappable counter."
   ::= {pr1645v2Lan2MCD7InPEntry 218103808}

pr1645v2Lan2MCD7InPIfOutErrors OBJECT-TYPE
   SYNTAX      Counter64
   MAX-ACCESS  read-only
   STATUS      current
   DESCRIPTION
      "Path: ethernet2.performance.d7Performance.ifOutErrors

       64 bit unsigned wrappable counter."
   ::= {pr1645v2Lan2MCD7InPEntry 234881024}

pr1645v2Lan2MCD7InPOutDropEx OBJECT-TYPE
   SYNTAX      Counter64
   MAX-ACCESS  read-only
   STATUS      current
   DESCRIPTION
      "Path: ethernet2.performance.d7Performance.ifOutDropLevelExceeded

       64 bit unsigned wrappable counter."
   ::= {pr1645v2Lan2MCD7InPEntry 352321536}

pr1645v2Lan2MCD7InPOutDropNoArp OBJECT-TYPE
   SYNTAX      Counter64
   MAX-ACCESS  read-only
   STATUS      current
   DESCRIPTION
      "Path: ethernet2.performance.d7Performance.ifOutDiscardsNoArp

       64 bit unsigned wrappable counter."
   ::= {pr1645v2Lan2MCD7InPEntry 369098752}

pr1645v2Lan2MCD7InPOutDropFilter OBJECT-TYPE
   SYNTAX      Counter64
   MAX-ACCESS  read-only
   STATUS      current
   DESCRIPTION
      "Path: ethernet2.performance.d7Performance.ifOutDiscardsFilter

       64 bit unsigned wrappable counter."
   ::= {pr1645v2Lan2MCD7InPEntry 402653184}

pr1645v2Lan2MCD7InPIfOutBandwidth OBJECT-TYPE
   SYNTAX      Integer32
   MAX-ACCESS  read-only
   STATUS      current
   DESCRIPTION
      "Path: ethernet2.performance.d7Performance.ifOutBandwidth

       unit name = bps
       formula = 8 * ; 8 /"
   ::= {pr1645v2Lan2MCD7InPEntry 285212672}

pr1645v2Lan2MCD7InPIfErrSec OBJECT-TYPE
   SYNTAX      Counter32
   MAX-ACCESS  read-only
   STATUS      current
   DESCRIPTION
      "Path: ethernet2.performance.d7Performance.ifErrSec

       32 bit unsigned wrappable counter."
   ::= {pr1645v2Lan2MCD7InPEntry 251658240}


pr1645v2Lan2MCOam OBJECT IDENTIFIER ::= {pr1645v2Lan2MC 910}

pr1645v2Lan2MCOamSSC OBJECT IDENTIFIER ::= {pr1645v2Lan2MCOam 1}

pr1645v2Lan2MCOamEntry OBJECT IDENTIFIER ::= {pr1645v2Lan2MCOamSSC 1}

pr1645v2Lan2MCOamInformationTx OBJECT-TYPE
   SYNTAX      Counter32
   MAX-ACCESS  read-only
   STATUS      current
   DESCRIPTION
      "Path: ethernet2.performance.oam.informationTx

       32 bit unsigned wrappable counter."
   ::= {pr1645v2Lan2MCOamEntry 16777216}

pr1645v2Lan2MCOamInformationRx OBJECT-TYPE
   SYNTAX      Counter32
   MAX-ACCESS  read-only
   STATUS      current
   DESCRIPTION
      "Path: ethernet2.performance.oam.informationRx

       32 bit unsigned wrappable counter."
   ::= {pr1645v2Lan2MCOamEntry 33554432}

pr1645v2Lan2MCOamUniqueEventNotifTx OBJECT-TYPE
   SYNTAX      Counter32
   MAX-ACCESS  read-only
   STATUS      current
   DESCRIPTION
      "Path: ethernet2.performance.oam.uniqueEventNotifTx

       32 bit unsigned wrappable counter."
   ::= {pr1645v2Lan2MCOamEntry 50331648}

pr1645v2Lan2MCOamUniqueEventNotifRx OBJECT-TYPE
   SYNTAX      Counter32
   MAX-ACCESS  read-only
   STATUS      current
   DESCRIPTION
      "Path: ethernet2.performance.oam.uniqueEventNotifRx

       32 bit unsigned wrappable counter."
   ::= {pr1645v2Lan2MCOamEntry 67108864}

pr1645v2Lan2MCOamLoopbackCtrlTx OBJECT-TYPE
   SYNTAX      Counter32
   MAX-ACCESS  read-only
   STATUS      current
   DESCRIPTION
      "Path: ethernet2.performance.oam.loopbackCtrlTx

       32 bit unsigned wrappable counter."
   ::= {pr1645v2Lan2MCOamEntry 117440512}

pr1645v2Lan2MCOamLoopbackCtrlRx OBJECT-TYPE
   SYNTAX      Counter32
   MAX-ACCESS  read-only
   STATUS      current
   DESCRIPTION
      "Path: ethernet2.performance.oam.loopbackCtrlRx

       32 bit unsigned wrappable counter."
   ::= {pr1645v2Lan2MCOamEntry 134217728}

pr1645v2Lan2MCOamVarReqTx OBJECT-TYPE
   SYNTAX      Counter32
   MAX-ACCESS  read-only
   STATUS      current
   DESCRIPTION
      "Path: ethernet2.performance.oam.varReqTx

       32 bit unsigned wrappable counter."
   ::= {pr1645v2Lan2MCOamEntry 150994944}

pr1645v2Lan2MCOamVarReqRx OBJECT-TYPE
   SYNTAX      Counter32
   MAX-ACCESS  read-only
   STATUS      current
   DESCRIPTION
      "Path: ethernet2.performance.oam.varReqRx

       32 bit unsigned wrappable counter."
   ::= {pr1645v2Lan2MCOamEntry 167772160}

pr1645v2Lan2MCOamVarRespTx OBJECT-TYPE
   SYNTAX      Counter32
   MAX-ACCESS  read-only
   STATUS      current
   DESCRIPTION
      "Path: ethernet2.performance.oam.varRespTx

       32 bit unsigned wrappable counter."
   ::= {pr1645v2Lan2MCOamEntry 184549376}

pr1645v2Lan2MCOamVarRespRx OBJECT-TYPE
   SYNTAX      Counter32
   MAX-ACCESS  read-only
   STATUS      current
   DESCRIPTION
      "Path: ethernet2.performance.oam.varRespRx

       32 bit unsigned wrappable counter."
   ::= {pr1645v2Lan2MCOamEntry 201326592}

pr1645v2Lan2MCOamOrgSpecificTx OBJECT-TYPE
   SYNTAX      Counter32
   MAX-ACCESS  read-only
   STATUS      current
   DESCRIPTION
      "Path: ethernet2.performance.oam.orgSpecificTx

       32 bit unsigned wrappable counter."
   ::= {pr1645v2Lan2MCOamEntry 218103808}

pr1645v2Lan2MCOamOrgSpecificRx OBJECT-TYPE
   SYNTAX      Counter32
   MAX-ACCESS  read-only
   STATUS      current
   DESCRIPTION
      "Path: ethernet2.performance.oam.orgSpecificRx

       32 bit unsigned wrappable counter."
   ::= {pr1645v2Lan2MCOamEntry 234881024}

pr1645v2Lan2MCOamUnsupportedCodesTx OBJECT-TYPE
   SYNTAX      Counter32
   MAX-ACCESS  read-only
   STATUS      current
   DESCRIPTION
      "Path: ethernet2.performance.oam.unsupportedCodesTx

       32 bit unsigned wrappable counter."
   ::= {pr1645v2Lan2MCOamEntry 251658240}

pr1645v2Lan2MCOamUnsupportedCodesRx OBJECT-TYPE
   SYNTAX      Counter32
   MAX-ACCESS  read-only
   STATUS      current
   DESCRIPTION
      "Path: ethernet2.performance.oam.unsupportedCodesRx

       32 bit unsigned wrappable counter."
   ::= {pr1645v2Lan2MCOamEntry 268435456}

pr1645v2Lan2MCOamPduDiscardRx OBJECT-TYPE
   SYNTAX      Counter32
   MAX-ACCESS  read-only
   STATUS      current
   DESCRIPTION
      "Path: ethernet2.performance.oam.pduDiscardRx

       32 bit unsigned wrappable counter."
   ::= {pr1645v2Lan2MCOamEntry 1694498816}

pr1645v2Lan2MCOamDataDiscardTx OBJECT-TYPE
   SYNTAX      Counter32
   MAX-ACCESS  read-only
   STATUS      current
   DESCRIPTION
      "Path: ethernet2.performance.oam.dataDiscardTx

       32 bit unsigned wrappable counter."
   ::= {pr1645v2Lan2MCOamEntry 1711276032}

pr1645v2Lan2MCOamDataDiscardRx OBJECT-TYPE
   SYNTAX      Counter32
   MAX-ACCESS  read-only
   STATUS      current
   DESCRIPTION
      "Path: ethernet2.performance.oam.dataDiscardRx

       32 bit unsigned wrappable counter."
   ::= {pr1645v2Lan2MCOamEntry 1728053248}


pr1645v2Lan2MCVlan OBJECT IDENTIFIER ::= {pr1645v2Lan2MC 310}

pr1645v2Lan2MCVlanSSCTable OBJECT-TYPE
   SYNTAX      SEQUENCE OF Pr1645v2Lan2MCVlanEntry
   MAX-ACCESS  not-accessible
   STATUS      current
   DESCRIPTION
      ""
   ::= {pr1645v2Lan2MCVlan 1}

pr1645v2Lan2MCVlanEntry OBJECT-TYPE
   SYNTAX      Pr1645v2Lan2MCVlanEntry
   MAX-ACCESS  not-accessible
   STATUS      current
   DESCRIPTION
      ""
   INDEX      { pr1645v2Lan2MCVlanTableIx }
   ::= {pr1645v2Lan2MCVlanSSCTable 1}

Pr1645v2Lan2MCVlanEntry ::=
   SEQUENCE
      {
      pr1645v2Lan2MCVlanTableIx
         TableIndex,
      pr1645v2Lan2MCVlanName
         DisplayString,
      pr1645v2Lan2MCVlanMCInOctets
         Counter64,
      pr1645v2Lan2MCVlanMCInUcast
         Counter64,
      pr1645v2Lan2MCVlanMCInNUcastPkts
         Counter64,
      pr1645v2Lan2MCVlanMCInBcastPkts
         Counter64,
      pr1645v2Lan2MCVlanMCInMcastPkts
         Counter64,
      pr1645v2Lan2MCVlanMCInDiscards
         Counter64,
      pr1645v2Lan2MCVlanMCInErrors
         Counter64,
      pr1645v2Lan2MCVlanMCInUnknownProtos
         Counter64,
      pr1645v2Lan2MCVlanMCInDropEx
         Counter64,
      pr1645v2Lan2MCVlanMCInDropNoMac
         Counter64,
      pr1645v2Lan2MCVlanMCInDropNUCast
         Counter64,
      pr1645v2Lan2MCVlanMCInDropFilter
         Counter64,
      pr1645v2Lan2MCVlanMCInBandwidth15sec
         Integer32,
      pr1645v2Lan2MCVlanMCInBandwidth30sec
         Integer32,
      pr1645v2Lan2MCVlanMCInBandwidth1min
         Integer32,
      pr1645v2Lan2MCVlanMCInBandwidth2min
         Integer32,
      pr1645v2Lan2MCVlanMCInBandwidth5min
         Integer32,
      pr1645v2Lan2MCVlanMCOutOctets
         Counter64,
      pr1645v2Lan2MCVlanMCOutUcastPkts
         Counter64,
      pr1645v2Lan2MCVlanMCOutNUcastPkts
         Counter64,
      pr1645v2Lan2MCVlanMCOutBcastPkts
         Counter64,
      pr1645v2Lan2MCVlanMCOutMcastPkts
         Counter64,
      pr1645v2Lan2MCVlanMCOutDiscards
         Counter64,
      pr1645v2Lan2MCVlanMCOutErrors
         Counter64,
      pr1645v2Lan2MCVlanMCOutQLen
         Counter32,
      pr1645v2Lan2MCVlanMCOutDropEx
         Counter64,
      pr1645v2Lan2MCVlanMCOutDropNoArp
         Counter64,
      pr1645v2Lan2MCVlanMCOutDropFilter
         Counter64,
      pr1645v2Lan2MCVlanMCOutBandwidth15sec
         Integer32,
      pr1645v2Lan2MCVlanMCOutBandwidth30sec
         Integer32,
      pr1645v2Lan2MCVlanMCOutBandwidth1min
         Integer32,
      pr1645v2Lan2MCVlanMCOutBandwidth2min
         Integer32,
      pr1645v2Lan2MCVlanMCOutBandwidth5min
         Integer32,
      pr1645v2Lan2MCVlanVlanVid
         Integer32,
      pr1645v2Lan2MCVlanPppLinkMonitoringRequestsSent
         Gauge32,
      pr1645v2Lan2MCVlanPppLinkMonitoringRepliesRcvd
         Gauge32,
      pr1645v2Lan2MCVlanPppLinkMonitoringRequestsRcvd
         Gauge32,
      pr1645v2Lan2MCVlanPppLinkMonitoringRepliesSent
         Gauge32
      }

pr1645v2Lan2MCVlanTableIx OBJECT-TYPE
   SYNTAX      TableIndex
   MAX-ACCESS  not-accessible
   STATUS      current
   DESCRIPTION
      ""
   ::= {pr1645v2Lan2MCVlanEntry 11}

pr1645v2Lan2MCVlanName OBJECT-TYPE
   SYNTAX      DisplayString
   MAX-ACCESS  read-only
   STATUS      current
   DESCRIPTION
      "Path: ethernet2.performance.vlan.name"
   ::= {pr1645v2Lan2MCVlanEntry 16777216}

pr1645v2Lan2MCVlanMCInOctets OBJECT-TYPE
   SYNTAX      Counter64
   MAX-ACCESS  read-only
   STATUS      current
   DESCRIPTION
      "Path: ethernet2.performance.vlan.mibCounters.ifInOctets

       64 bit unsigned wrappable counter."
   ::= {pr1645v2Lan2MCVlanEntry 40697856}

pr1645v2Lan2MCVlanMCInUcast OBJECT-TYPE
   SYNTAX      Counter64
   MAX-ACCESS  read-only
   STATUS      current
   DESCRIPTION
      "Path: ethernet2.performance.vlan.mibCounters.ifInUcastPkts

       64 bit unsigned wrappable counter."
   ::= {pr1645v2Lan2MCVlanEntry 40763392}

pr1645v2Lan2MCVlanMCInNUcastPkts OBJECT-TYPE
   SYNTAX      Counter64
   MAX-ACCESS  read-only
   STATUS      current
   DESCRIPTION
      "Path: ethernet2.performance.vlan.mibCounters.ifInNUcastPkts

       64 bit unsigned wrappable counter."
   ::= {pr1645v2Lan2MCVlanEntry 40828928}

pr1645v2Lan2MCVlanMCInBcastPkts OBJECT-TYPE
   SYNTAX      Counter64
   MAX-ACCESS  read-only
   STATUS      current
   DESCRIPTION
      "Path: ethernet2.performance.vlan.mibCounters.ifInBcastPkts

       64 bit unsigned wrappable counter."
   ::= {pr1645v2Lan2MCVlanEntry 47382528}

pr1645v2Lan2MCVlanMCInMcastPkts OBJECT-TYPE
   SYNTAX      Counter64
   MAX-ACCESS  read-only
   STATUS      current
   DESCRIPTION
      "Path: ethernet2.performance.vlan.mibCounters.ifInMcastPkts

       64 bit unsigned wrappable counter."
   ::= {pr1645v2Lan2MCVlanEntry 48037888}

pr1645v2Lan2MCVlanMCInDiscards OBJECT-TYPE
   SYNTAX      Counter64
   MAX-ACCESS  read-only
   STATUS      current
   DESCRIPTION
      "Path: ethernet2.performance.vlan.mibCounters.ifInDiscards

       64 bit unsigned wrappable counter."
   ::= {pr1645v2Lan2MCVlanEntry 40894464}

pr1645v2Lan2MCVlanMCInErrors OBJECT-TYPE
   SYNTAX      Counter64
   MAX-ACCESS  read-only
   STATUS      current
   DESCRIPTION
      "Path: ethernet2.performance.vlan.mibCounters.ifInErrors

       64 bit unsigned wrappable counter."
   ::= {pr1645v2Lan2MCVlanEntry 40960000}

pr1645v2Lan2MCVlanMCInUnknownProtos OBJECT-TYPE
   SYNTAX      Counter64
   MAX-ACCESS  read-only
   STATUS      current
   DESCRIPTION
      "Path: ethernet2.performance.vlan.mibCounters.ifInUnknownProtos

       64 bit unsigned wrappable counter."
   ::= {pr1645v2Lan2MCVlanEntry 41025536}

pr1645v2Lan2MCVlanMCInDropEx OBJECT-TYPE
   SYNTAX      Counter64
   MAX-ACCESS  read-only
   STATUS      current
   DESCRIPTION
      "Path: ethernet2.performance.vlan.mibCounters.ifInDropLevelExceeded

       64 bit unsigned wrappable counter."
   ::= {pr1645v2Lan2MCVlanEntry 42074112}

pr1645v2Lan2MCVlanMCInDropNoMac OBJECT-TYPE
   SYNTAX      Counter64
   MAX-ACCESS  read-only
   STATUS      current
   DESCRIPTION
      "Path: ethernet2.performance.vlan.mibCounters.ifInDiscardsNoMacFit

       64 bit unsigned wrappable counter."
   ::= {pr1645v2Lan2MCVlanEntry 42270720}

pr1645v2Lan2MCVlanMCInDropNUCast OBJECT-TYPE
   SYNTAX      Counter64
   MAX-ACCESS  read-only
   STATUS      current
   DESCRIPTION
      "Path: ethernet2.performance.vlan.mibCounters.ifInDiscardsNUCast

       64 bit unsigned wrappable counter."
   ::= {pr1645v2Lan2MCVlanEntry 42467328}

pr1645v2Lan2MCVlanMCInDropFilter OBJECT-TYPE
   SYNTAX      Counter64
   MAX-ACCESS  read-only
   STATUS      current
   DESCRIPTION
      "Path: ethernet2.performance.vlan.mibCounters.ifInDiscardsFilter

       64 bit unsigned wrappable counter."
   ::= {pr1645v2Lan2MCVlanEntry 42532864}

pr1645v2Lan2MCVlanMCInBandwidth15sec OBJECT-TYPE
   SYNTAX      Integer32
   MAX-ACCESS  read-only
   STATUS      current
   DESCRIPTION
      "Path: ethernet2.performance.vlan.mibCounters.ifInBandwidth.15sec

       unit name = bps
       formula = 8 * ; 8 /"
   ::= {pr1645v2Lan2MCVlanEntry 45417728}

pr1645v2Lan2MCVlanMCInBandwidth30sec OBJECT-TYPE
   SYNTAX      Integer32
   MAX-ACCESS  read-only
   STATUS      current
   DESCRIPTION
      "Path: ethernet2.performance.vlan.mibCounters.ifInBandwidth.30sec

       unit name = bps
       formula = 8 * ; 8 /"
   ::= {pr1645v2Lan2MCVlanEntry 45419008}

pr1645v2Lan2MCVlanMCInBandwidth1min OBJECT-TYPE
   SYNTAX      Integer32
   MAX-ACCESS  read-only
   STATUS      current
   DESCRIPTION
      "Path: ethernet2.performance.vlan.mibCounters.ifInBandwidth.1min

       unit name = bps
       formula = 8 * ; 8 /"
   ::= {pr1645v2Lan2MCVlanEntry 45421568}

pr1645v2Lan2MCVlanMCInBandwidth2min OBJECT-TYPE
   SYNTAX      Integer32
   MAX-ACCESS  read-only
   STATUS      current
   DESCRIPTION
      "Path: ethernet2.performance.vlan.mibCounters.ifInBandwidth.2min

       unit name = bps
       formula = 8 * ; 8 /"
   ::= {pr1645v2Lan2MCVlanEntry 45426688}

pr1645v2Lan2MCVlanMCInBandwidth5min OBJECT-TYPE
   SYNTAX      Integer32
   MAX-ACCESS  read-only
   STATUS      current
   DESCRIPTION
      "Path: ethernet2.performance.vlan.mibCounters.ifInBandwidth.5min

       unit name = bps
       formula = 8 * ; 8 /"
   ::= {pr1645v2Lan2MCVlanEntry 45442048}

pr1645v2Lan2MCVlanMCOutOctets OBJECT-TYPE
   SYNTAX      Counter64
   MAX-ACCESS  read-only
   STATUS      current
   DESCRIPTION
      "Path: ethernet2.performance.vlan.mibCounters.ifOutOctets

       64 bit unsigned wrappable counter."
   ::= {pr1645v2Lan2MCVlanEntry 41091072}

pr1645v2Lan2MCVlanMCOutUcastPkts OBJECT-TYPE
   SYNTAX      Counter64
   MAX-ACCESS  read-only
   STATUS      current
   DESCRIPTION
      "Path: ethernet2.performance.vlan.mibCounters.ifOutUcastPkts

       64 bit unsigned wrappable counter."
   ::= {pr1645v2Lan2MCVlanEntry 41156608}

pr1645v2Lan2MCVlanMCOutNUcastPkts OBJECT-TYPE
   SYNTAX      Counter64
   MAX-ACCESS  read-only
   STATUS      current
   DESCRIPTION
      "Path: ethernet2.performance.vlan.mibCounters.ifOutNUcastPkts

       64 bit unsigned wrappable counter."
   ::= {pr1645v2Lan2MCVlanEntry 41222144}

pr1645v2Lan2MCVlanMCOutBcastPkts OBJECT-TYPE
   SYNTAX      Counter64
   MAX-ACCESS  read-only
   STATUS      current
   DESCRIPTION
      "Path: ethernet2.performance.vlan.mibCounters.ifOutBcastPkts

       64 bit unsigned wrappable counter."
   ::= {pr1645v2Lan2MCVlanEntry 47775744}

pr1645v2Lan2MCVlanMCOutMcastPkts OBJECT-TYPE
   SYNTAX      Counter64
   MAX-ACCESS  read-only
   STATUS      current
   DESCRIPTION
      "Path: ethernet2.performance.vlan.mibCounters.ifOutMcastPkts

       64 bit unsigned wrappable counter."
   ::= {pr1645v2Lan2MCVlanEntry 48431104}

pr1645v2Lan2MCVlanMCOutDiscards OBJECT-TYPE
   SYNTAX      Counter64
   MAX-ACCESS  read-only
   STATUS      current
   DESCRIPTION
      "Path: ethernet2.performance.vlan.mibCounters.ifOutDiscards

       64 bit unsigned wrappable counter."
   ::= {pr1645v2Lan2MCVlanEntry 41287680}

pr1645v2Lan2MCVlanMCOutErrors OBJECT-TYPE
   SYNTAX      Counter64
   MAX-ACCESS  read-only
   STATUS      current
   DESCRIPTION
      "Path: ethernet2.performance.vlan.mibCounters.ifOutErrors

       64 bit unsigned wrappable counter."
   ::= {pr1645v2Lan2MCVlanEntry 41353216}

pr1645v2Lan2MCVlanMCOutQLen OBJECT-TYPE
   SYNTAX      Counter32
   MAX-ACCESS  read-only
   STATUS      current
   DESCRIPTION
      "Path: ethernet2.performance.vlan.mibCounters.ifOutQLen

       32 bit unsigned wrappable counter."
   ::= {pr1645v2Lan2MCVlanEntry 41418752}

pr1645v2Lan2MCVlanMCOutDropEx OBJECT-TYPE
   SYNTAX      Counter64
   MAX-ACCESS  read-only
   STATUS      current
   DESCRIPTION
      "Path: ethernet2.performance.vlan.mibCounters.ifOutDropLevelExceeded

       64 bit unsigned wrappable counter."
   ::= {pr1645v2Lan2MCVlanEntry 41484288}

pr1645v2Lan2MCVlanMCOutDropNoArp OBJECT-TYPE
   SYNTAX      Counter64
   MAX-ACCESS  read-only
   STATUS      current
   DESCRIPTION
      "Path: ethernet2.performance.vlan.mibCounters.ifOutDiscardsNoArp

       64 bit unsigned wrappable counter."
   ::= {pr1645v2Lan2MCVlanEntry 42336256}

pr1645v2Lan2MCVlanMCOutDropFilter OBJECT-TYPE
   SYNTAX      Counter64
   MAX-ACCESS  read-only
   STATUS      current
   DESCRIPTION
      "Path: ethernet2.performance.vlan.mibCounters.ifOutDiscardsFilter

       64 bit unsigned wrappable counter."
   ::= {pr1645v2Lan2MCVlanEntry 42598400}

pr1645v2Lan2MCVlanMCOutBandwidth15sec OBJECT-TYPE
   SYNTAX      Integer32
   MAX-ACCESS  read-only
   STATUS      current
   DESCRIPTION
      "Path: ethernet2.performance.vlan.mibCounters.ifOutBandwidth.15sec

       unit name = bps
       formula = 8 * ; 8 /"
   ::= {pr1645v2Lan2MCVlanEntry 45483264}

pr1645v2Lan2MCVlanMCOutBandwidth30sec OBJECT-TYPE
   SYNTAX      Integer32
   MAX-ACCESS  read-only
   STATUS      current
   DESCRIPTION
      "Path: ethernet2.performance.vlan.mibCounters.ifOutBandwidth.30sec

       unit name = bps
       formula = 8 * ; 8 /"
   ::= {pr1645v2Lan2MCVlanEntry 45484544}

pr1645v2Lan2MCVlanMCOutBandwidth1min OBJECT-TYPE
   SYNTAX      Integer32
   MAX-ACCESS  read-only
   STATUS      current
   DESCRIPTION
      "Path: ethernet2.performance.vlan.mibCounters.ifOutBandwidth.1min

       unit name = bps
       formula = 8 * ; 8 /"
   ::= {pr1645v2Lan2MCVlanEntry 45487104}

pr1645v2Lan2MCVlanMCOutBandwidth2min OBJECT-TYPE
   SYNTAX      Integer32
   MAX-ACCESS  read-only
   STATUS      current
   DESCRIPTION
      "Path: ethernet2.performance.vlan.mibCounters.ifOutBandwidth.2min

       unit name = bps
       formula = 8 * ; 8 /"
   ::= {pr1645v2Lan2MCVlanEntry 45492224}

pr1645v2Lan2MCVlanMCOutBandwidth5min OBJECT-TYPE
   SYNTAX      Integer32
   MAX-ACCESS  read-only
   STATUS      current
   DESCRIPTION
      "Path: ethernet2.performance.vlan.mibCounters.ifOutBandwidth.5min

       unit name = bps
       formula = 8 * ; 8 /"
   ::= {pr1645v2Lan2MCVlanEntry 45507584}

pr1645v2Lan2MCVlanVlanVid OBJECT-TYPE
   SYNTAX      Integer32
   MAX-ACCESS  read-only
   STATUS      current
   DESCRIPTION
      "Path: ethernet2.performance.vlan.vlan.vid"
   ::= {pr1645v2Lan2MCVlanEntry 234946560}

pr1645v2Lan2MCVlanPppLinkMonitoringRequestsSent OBJECT-TYPE
   SYNTAX      Gauge32
   MAX-ACCESS  read-only
   STATUS      current
   DESCRIPTION
      "Path: ethernet2.performance.vlan.ppp.linkMonitoring.requestsSent

       32 bit unsigned gauge value."
   ::= {pr1645v2Lan2MCVlanEntry 50397440}

pr1645v2Lan2MCVlanPppLinkMonitoringRepliesRcvd OBJECT-TYPE
   SYNTAX      Gauge32
   MAX-ACCESS  read-only
   STATUS      current
   DESCRIPTION
      "Path: ethernet2.performance.vlan.ppp.linkMonitoring.repliesRcvd

       32 bit unsigned gauge value."
   ::= {pr1645v2Lan2MCVlanEntry 50397696}

pr1645v2Lan2MCVlanPppLinkMonitoringRequestsRcvd OBJECT-TYPE
   SYNTAX      Gauge32
   MAX-ACCESS  read-only
   STATUS      current
   DESCRIPTION
      "Path: ethernet2.performance.vlan.ppp.linkMonitoring.requestsRcvd

       32 bit unsigned gauge value."
   ::= {pr1645v2Lan2MCVlanEntry 50397952}

pr1645v2Lan2MCVlanPppLinkMonitoringRepliesSent OBJECT-TYPE
   SYNTAX      Gauge32
   MAX-ACCESS  read-only
   STATUS      current
   DESCRIPTION
      "Path: ethernet2.performance.vlan.ppp.linkMonitoring.repliesSent

       32 bit unsigned gauge value."
   ::= {pr1645v2Lan2MCVlanEntry 50398208}

pr1645v2Lan2MCVlanMCH2P OBJECT-TYPE
   SYNTAX      SEQUENCE OF Pr1645v2Lan2MCVlanMCH2PEntry
   MAX-ACCESS  not-accessible
   STATUS      current
   DESCRIPTION
      ""
   ::= {pr1645v2Lan2MCVlan 41549824}

pr1645v2Lan2MCVlanMCH2PEntry OBJECT-TYPE
   SYNTAX      Pr1645v2Lan2MCVlanMCH2PEntry
   MAX-ACCESS  not-accessible
   STATUS      current
   DESCRIPTION
      ""
   INDEX      { pr1645v2Lan2MCVlanTableIx,
                pr1645v2Lan2MCVlanMCH2PTableIx }
   ::= {pr1645v2Lan2MCVlanMCH2P 1}

Pr1645v2Lan2MCVlanMCH2PEntry ::=
   SEQUENCE
      {
      pr1645v2Lan2MCVlanMCH2PTableIx
         TableIndex,
      pr1645v2Lan2MCVlanMCH2PSysUpTime
         TimeTicks,
      pr1645v2Lan2MCVlanMCH2PIfUpTime
         TimeTicks,
      pr1645v2Lan2MCVlanMCH2PIfStatChanges
         Counter32,
      pr1645v2Lan2MCVlanMCH2PIfInOctets
         Counter64,
      pr1645v2Lan2MCVlanMCH2PIfInUCPkts
         Counter64,
      pr1645v2Lan2MCVlanMCH2PIfInNUCPkts
         Counter64,
      pr1645v2Lan2MCVlanMCH2PIfInBCPkts
         Counter64,
      pr1645v2Lan2MCVlanMCH2PIfInMCPkts
         Counter64,
      pr1645v2Lan2MCVlanMCH2PIfInDiscards
         Counter64,
      pr1645v2Lan2MCVlanMCH2PIfInErrors
         Counter64,
      pr1645v2Lan2MCVlanMCH2PIfInUnkwn
         Counter64,
      pr1645v2Lan2MCVlanMCH2PInDropEx
         Counter64,
      pr1645v2Lan2MCVlanMCH2PInDropNoMac
         Counter64,
      pr1645v2Lan2MCVlanMCH2PInDropNUCast
         Counter64,
      pr1645v2Lan2MCVlanMCH2PInDropFilter
         Counter64,
      pr1645v2Lan2MCVlanMCH2PIfInBandwidth
         Integer32,
      pr1645v2Lan2MCVlanMCH2PIfOutOctets
         Counter64,
      pr1645v2Lan2MCVlanMCH2PIfOutUCPkts
         Counter64,
      pr1645v2Lan2MCVlanMCH2PIfOutNUCPkts
         Counter64,
      pr1645v2Lan2MCVlanMCH2PIfOutBCPkts
         Counter64,
      pr1645v2Lan2MCVlanMCH2PIfOutMCPkts
         Counter64,
      pr1645v2Lan2MCVlanMCH2PIfOutDiscards
         Counter64,
      pr1645v2Lan2MCVlanMCH2PIfOutErrors
         Counter64,
      pr1645v2Lan2MCVlanMCH2POutDropEx
         Counter64,
      pr1645v2Lan2MCVlanMCH2POutDropNoArp
         Counter64,
      pr1645v2Lan2MCVlanMCH2POutDropFilter
         Counter64,
      pr1645v2Lan2MCVlanMCH2PIfOutBandwidth
         Integer32,
      pr1645v2Lan2MCVlanMCH2PIfErrSec
         Counter32
      }

pr1645v2Lan2MCVlanMCH2PTableIx OBJECT-TYPE
   SYNTAX      TableIndex
   MAX-ACCESS  not-accessible
   STATUS      current
   DESCRIPTION
      ""
   ::= {pr1645v2Lan2MCVlanMCH2PEntry 11}

pr1645v2Lan2MCVlanMCH2PSysUpTime OBJECT-TYPE
   SYNTAX      TimeTicks
   MAX-ACCESS  read-only
   STATUS      current
   DESCRIPTION
      "Path: ethernet2.performance.vlan.mibCounters.h2Performance.sysUpTime

       Time in centi-second."
   ::= {pr1645v2Lan2MCVlanMCH2PEntry 16777216}

pr1645v2Lan2MCVlanMCH2PIfUpTime OBJECT-TYPE
   SYNTAX      TimeTicks
   MAX-ACCESS  read-only
   STATUS      current
   DESCRIPTION
      "Path: ethernet2.performance.vlan.mibCounters.h2Performance.ifUpTime

       Time in centi-second."
   ::= {pr1645v2Lan2MCVlanMCH2PEntry 33554432}

pr1645v2Lan2MCVlanMCH2PIfStatChanges OBJECT-TYPE
   SYNTAX      Counter32
   MAX-ACCESS  read-only
   STATUS      current
   DESCRIPTION
      "Path: ethernet2.performance.vlan.mibCounters.h2Performance.ifStatusChanges

       32 bit unsigned wrappable counter."
   ::= {pr1645v2Lan2MCVlanMCH2PEntry 50331648}

pr1645v2Lan2MCVlanMCH2PIfInOctets OBJECT-TYPE
   SYNTAX      Counter64
   MAX-ACCESS  read-only
   STATUS      current
   DESCRIPTION
      "Path: ethernet2.performance.vlan.mibCounters.h2Performance.ifInOctets

       64 bit unsigned wrappable counter."
   ::= {pr1645v2Lan2MCVlanMCH2PEntry 67108864}

pr1645v2Lan2MCVlanMCH2PIfInUCPkts OBJECT-TYPE
   SYNTAX      Counter64
   MAX-ACCESS  read-only
   STATUS      current
   DESCRIPTION
      "Path: ethernet2.performance.vlan.mibCounters.h2Performance.ifInUcastPkts

       64 bit unsigned wrappable counter."
   ::= {pr1645v2Lan2MCVlanMCH2PEntry 83886080}

pr1645v2Lan2MCVlanMCH2PIfInNUCPkts OBJECT-TYPE
   SYNTAX      Counter64
   MAX-ACCESS  read-only
   STATUS      current
   DESCRIPTION
      "Path: ethernet2.performance.vlan.mibCounters.h2Performance.ifInNUcastPkts

       64 bit unsigned wrappable counter."
   ::= {pr1645v2Lan2MCVlanMCH2PEntry 100663296}

pr1645v2Lan2MCVlanMCH2PIfInBCPkts OBJECT-TYPE
   SYNTAX      Counter64
   MAX-ACCESS  read-only
   STATUS      current
   DESCRIPTION
      "Path: ethernet2.performance.vlan.mibCounters.h2Performance.ifInBcastPkts

       64 bit unsigned wrappable counter."
   ::= {pr1645v2Lan2MCVlanMCH2PEntry 419430400}

pr1645v2Lan2MCVlanMCH2PIfInMCPkts OBJECT-TYPE
   SYNTAX      Counter64
   MAX-ACCESS  read-only
   STATUS      current
   DESCRIPTION
      "Path: ethernet2.performance.vlan.mibCounters.h2Performance.ifInMcastPkts

       64 bit unsigned wrappable counter."
   ::= {pr1645v2Lan2MCVlanMCH2PEntry 436207616}

pr1645v2Lan2MCVlanMCH2PIfInDiscards OBJECT-TYPE
   SYNTAX      Counter64
   MAX-ACCESS  read-only
   STATUS      current
   DESCRIPTION
      "Path: ethernet2.performance.vlan.mibCounters.h2Performance.ifInDiscards

       64 bit unsigned wrappable counter."
   ::= {pr1645v2Lan2MCVlanMCH2PEntry 117440512}

pr1645v2Lan2MCVlanMCH2PIfInErrors OBJECT-TYPE
   SYNTAX      Counter64
   MAX-ACCESS  read-only
   STATUS      current
   DESCRIPTION
      "Path: ethernet2.performance.vlan.mibCounters.h2Performance.ifInErrors

       64 bit unsigned wrappable counter."
   ::= {pr1645v2Lan2MCVlanMCH2PEntry 134217728}

pr1645v2Lan2MCVlanMCH2PIfInUnkwn OBJECT-TYPE
   SYNTAX      Counter64
   MAX-ACCESS  read-only
   STATUS      current
   DESCRIPTION
      "Path: ethernet2.performance.vlan.mibCounters.h2Performance.ifInUnknownProtos

       64 bit unsigned wrappable counter."
   ::= {pr1645v2Lan2MCVlanMCH2PEntry 150994944}

pr1645v2Lan2MCVlanMCH2PInDropEx OBJECT-TYPE
   SYNTAX      Counter64
   MAX-ACCESS  read-only
   STATUS      current
   DESCRIPTION
      "Path: ethernet2.performance.vlan.mibCounters.h2Performance.ifInDropLevelExceeded

       64 bit unsigned wrappable counter."
   ::= {pr1645v2Lan2MCVlanMCH2PEntry 335544320}

pr1645v2Lan2MCVlanMCH2PInDropNoMac OBJECT-TYPE
   SYNTAX      Counter64
   MAX-ACCESS  read-only
   STATUS      current
   DESCRIPTION
      "Path: ethernet2.performance.vlan.mibCounters.h2Performance.fInDiscardsNoMacFit

       64 bit unsigned wrappable counter."
   ::= {pr1645v2Lan2MCVlanMCH2PEntry 301989888}

pr1645v2Lan2MCVlanMCH2PInDropNUCast OBJECT-TYPE
   SYNTAX      Counter64
   MAX-ACCESS  read-only
   STATUS      current
   DESCRIPTION
      "Path: ethernet2.performance.vlan.mibCounters.h2Performance.fInDiscardsNUCast

       64 bit unsigned wrappable counter."
   ::= {pr1645v2Lan2MCVlanMCH2PEntry 318767104}

pr1645v2Lan2MCVlanMCH2PInDropFilter OBJECT-TYPE
   SYNTAX      Counter64
   MAX-ACCESS  read-only
   STATUS      current
   DESCRIPTION
      "Path: ethernet2.performance.vlan.mibCounters.h2Performance.fInDiscardsFilter

       64 bit unsigned wrappable counter."
   ::= {pr1645v2Lan2MCVlanMCH2PEntry 385875968}

pr1645v2Lan2MCVlanMCH2PIfInBandwidth OBJECT-TYPE
   SYNTAX      Integer32
   MAX-ACCESS  read-only
   STATUS      current
   DESCRIPTION
      "Path: ethernet2.performance.vlan.mibCounters.h2Performance.ifInBandwidth

       unit name = bps
       formula = 8 * ; 8 /"
   ::= {pr1645v2Lan2MCVlanMCH2PEntry 268435456}

pr1645v2Lan2MCVlanMCH2PIfOutOctets OBJECT-TYPE
   SYNTAX      Counter64
   MAX-ACCESS  read-only
   STATUS      current
   DESCRIPTION
      "Path: ethernet2.performance.vlan.mibCounters.h2Performance.ifOutOctets

       64 bit unsigned wrappable counter."
   ::= {pr1645v2Lan2MCVlanMCH2PEntry 167772160}

pr1645v2Lan2MCVlanMCH2PIfOutUCPkts OBJECT-TYPE
   SYNTAX      Counter64
   MAX-ACCESS  read-only
   STATUS      current
   DESCRIPTION
      "Path: ethernet2.performance.vlan.mibCounters.h2Performance.ifOutUcastPkts

       64 bit unsigned wrappable counter."
   ::= {pr1645v2Lan2MCVlanMCH2PEntry 184549376}

pr1645v2Lan2MCVlanMCH2PIfOutNUCPkts OBJECT-TYPE
   SYNTAX      Counter64
   MAX-ACCESS  read-only
   STATUS      current
   DESCRIPTION
      "Path: ethernet2.performance.vlan.mibCounters.h2Performance.ifOutNUcastPkts

       64 bit unsigned wrappable counter."
   ::= {pr1645v2Lan2MCVlanMCH2PEntry 201326592}

pr1645v2Lan2MCVlanMCH2PIfOutBCPkts OBJECT-TYPE
   SYNTAX      Counter64
   MAX-ACCESS  read-only
   STATUS      current
   DESCRIPTION
      "Path: ethernet2.performance.vlan.mibCounters.h2Performance.ifOutBcastPkts

       64 bit unsigned wrappable counter."
   ::= {pr1645v2Lan2MCVlanMCH2PEntry 452984832}

pr1645v2Lan2MCVlanMCH2PIfOutMCPkts OBJECT-TYPE
   SYNTAX      Counter64
   MAX-ACCESS  read-only
   STATUS      current
   DESCRIPTION
      "Path: ethernet2.performance.vlan.mibCounters.h2Performance.ifOutMcastPkts

       64 bit unsigned wrappable counter."
   ::= {pr1645v2Lan2MCVlanMCH2PEntry 469762048}

pr1645v2Lan2MCVlanMCH2PIfOutDiscards OBJECT-TYPE
   SYNTAX      Counter64
   MAX-ACCESS  read-only
   STATUS      current
   DESCRIPTION
      "Path: ethernet2.performance.vlan.mibCounters.h2Performance.ifOutDiscards

       64 bit unsigned wrappable counter."
   ::= {pr1645v2Lan2MCVlanMCH2PEntry 218103808}

pr1645v2Lan2MCVlanMCH2PIfOutErrors OBJECT-TYPE
   SYNTAX      Counter64
   MAX-ACCESS  read-only
   STATUS      current
   DESCRIPTION
      "Path: ethernet2.performance.vlan.mibCounters.h2Performance.ifOutErrors

       64 bit unsigned wrappable counter."
   ::= {pr1645v2Lan2MCVlanMCH2PEntry 234881024}

pr1645v2Lan2MCVlanMCH2POutDropEx OBJECT-TYPE
   SYNTAX      Counter64
   MAX-ACCESS  read-only
   STATUS      current
   DESCRIPTION
      "Path: ethernet2.performance.vlan.mibCounters.h2Performance.ifOutDropLevelExceeded

       64 bit unsigned wrappable counter."
   ::= {pr1645v2Lan2MCVlanMCH2PEntry 352321536}

pr1645v2Lan2MCVlanMCH2POutDropNoArp OBJECT-TYPE
   SYNTAX      Counter64
   MAX-ACCESS  read-only
   STATUS      current
   DESCRIPTION
      "Path: ethernet2.performance.vlan.mibCounters.h2Performance.ifOutDiscardsNoArp

       64 bit unsigned wrappable counter."
   ::= {pr1645v2Lan2MCVlanMCH2PEntry 369098752}

pr1645v2Lan2MCVlanMCH2POutDropFilter OBJECT-TYPE
   SYNTAX      Counter64
   MAX-ACCESS  read-only
   STATUS      current
   DESCRIPTION
      "Path: ethernet2.performance.vlan.mibCounters.h2Performance.ifOutDiscardsFilter

       64 bit unsigned wrappable counter."
   ::= {pr1645v2Lan2MCVlanMCH2PEntry 402653184}

pr1645v2Lan2MCVlanMCH2PIfOutBandwidth OBJECT-TYPE
   SYNTAX      Integer32
   MAX-ACCESS  read-only
   STATUS      current
   DESCRIPTION
      "Path: ethernet2.performance.vlan.mibCounters.h2Performance.ifOutBandwidth

       unit name = bps
       formula = 8 * ; 8 /"
   ::= {pr1645v2Lan2MCVlanMCH2PEntry 285212672}

pr1645v2Lan2MCVlanMCH2PIfErrSec OBJECT-TYPE
   SYNTAX      Counter32
   MAX-ACCESS  read-only
   STATUS      current
   DESCRIPTION
      "Path: ethernet2.performance.vlan.mibCounters.h2Performance.ifErrSec

       32 bit unsigned wrappable counter."
   ::= {pr1645v2Lan2MCVlanMCH2PEntry 251658240}

pr1645v2Lan2MCVlanMCH24P OBJECT-TYPE
   SYNTAX      SEQUENCE OF Pr1645v2Lan2MCVlanMCH24PEntry
   MAX-ACCESS  not-accessible
   STATUS      current
   DESCRIPTION
      ""
   ::= {pr1645v2Lan2MCVlan 41615360}

pr1645v2Lan2MCVlanMCH24PEntry OBJECT-TYPE
   SYNTAX      Pr1645v2Lan2MCVlanMCH24PEntry
   MAX-ACCESS  not-accessible
   STATUS      current
   DESCRIPTION
      ""
   INDEX      { pr1645v2Lan2MCVlanTableIx,
                pr1645v2Lan2MCVlanMCH24PTableIx }
   ::= {pr1645v2Lan2MCVlanMCH24P 1}

Pr1645v2Lan2MCVlanMCH24PEntry ::=
   SEQUENCE
      {
      pr1645v2Lan2MCVlanMCH24PTableIx
         TableIndex,
      pr1645v2Lan2MCVlanMCH24PSysUpTime
         TimeTicks,
      pr1645v2Lan2MCVlanMCH24PIfUpTime
         TimeTicks,
      pr1645v2Lan2MCVlanMCH24PIfStatChanges
         Counter32,
      pr1645v2Lan2MCVlanMCH24PIfInOctets
         Counter64,
      pr1645v2Lan2MCVlanMCH24PIfInUCPkts
         Counter64,
      pr1645v2Lan2MCVlanMCH24PIfInNUCPkts
         Counter64,
      pr1645v2Lan2MCVlanMCH24PIfInBCPkts
         Counter64,
      pr1645v2Lan2MCVlanMCH24PIfInMCPkts
         Counter64,
      pr1645v2Lan2MCVlanMCH24PIfInDiscards
         Counter64,
      pr1645v2Lan2MCVlanMCH24PIfInErrors
         Counter64,
      pr1645v2Lan2MCVlanMCH24PIfInUnkwn
         Counter64,
      pr1645v2Lan2MCVlanMCH24PInDropEx
         Counter64,
      pr1645v2Lan2MCVlanMCH24PInDropNoMac
         Counter64,
      pr1645v2Lan2MCVlanMCH24PInDropNUCast
         Counter64,
      pr1645v2Lan2MCVlanMCH24PInDropFilter
         Counter64,
      pr1645v2Lan2MCVlanMCH24PIfInBandwidth
         Integer32,
      pr1645v2Lan2MCVlanMCH24PIfOutOctets
         Counter64,
      pr1645v2Lan2MCVlanMCH24PIfOutUCPkts
         Counter64,
      pr1645v2Lan2MCVlanMCH24PIfOutNUCPkts
         Counter64,
      pr1645v2Lan2MCVlanMCH24PIfOutBCPkts
         Counter64,
      pr1645v2Lan2MCVlanMCH24PIfOutMCPkts
         Counter64,
      pr1645v2Lan2MCVlanMCH24PIfOutDiscards
         Counter64,
      pr1645v2Lan2MCVlanMCH24PIfOutErrors
         Counter64,
      pr1645v2Lan2MCVlanMCH24POutDropEx
         Counter64,
      pr1645v2Lan2MCVlanMCH24POutDropNoArp
         Counter64,
      pr1645v2Lan2MCVlanMCH24POutDropFilter
         Counter64,
      pr1645v2Lan2MCVlanMCH24PIfOutBandwidth
         Integer32,
      pr1645v2Lan2MCVlanMCH24PIfErrSec
         Counter32
      }

pr1645v2Lan2MCVlanMCH24PTableIx OBJECT-TYPE
   SYNTAX      TableIndex
   MAX-ACCESS  not-accessible
   STATUS      current
   DESCRIPTION
      ""
   ::= {pr1645v2Lan2MCVlanMCH24PEntry 11}

pr1645v2Lan2MCVlanMCH24PSysUpTime OBJECT-TYPE
   SYNTAX      TimeTicks
   MAX-ACCESS  read-only
   STATUS      current
   DESCRIPTION
      "Path: ethernet2.performance.vlan.mibCounters.h24Performance.sysUpTime

       Time in centi-second."
   ::= {pr1645v2Lan2MCVlanMCH24PEntry 16777216}

pr1645v2Lan2MCVlanMCH24PIfUpTime OBJECT-TYPE
   SYNTAX      TimeTicks
   MAX-ACCESS  read-only
   STATUS      current
   DESCRIPTION
      "Path: ethernet2.performance.vlan.mibCounters.h24Performance.ifUpTime

       Time in centi-second."
   ::= {pr1645v2Lan2MCVlanMCH24PEntry 33554432}

pr1645v2Lan2MCVlanMCH24PIfStatChanges OBJECT-TYPE
   SYNTAX      Counter32
   MAX-ACCESS  read-only
   STATUS      current
   DESCRIPTION
      "Path: ethernet2.performance.vlan.mibCounters.h24Performance.ifStatusChanges

       32 bit unsigned wrappable counter."
   ::= {pr1645v2Lan2MCVlanMCH24PEntry 50331648}

pr1645v2Lan2MCVlanMCH24PIfInOctets OBJECT-TYPE
   SYNTAX      Counter64
   MAX-ACCESS  read-only
   STATUS      current
   DESCRIPTION
      "Path: ethernet2.performance.vlan.mibCounters.h24Performance.ifInOctets

       64 bit unsigned wrappable counter."
   ::= {pr1645v2Lan2MCVlanMCH24PEntry 67108864}

pr1645v2Lan2MCVlanMCH24PIfInUCPkts OBJECT-TYPE
   SYNTAX      Counter64
   MAX-ACCESS  read-only
   STATUS      current
   DESCRIPTION
      "Path: ethernet2.performance.vlan.mibCounters.h24Performance.ifInUcastPkts

       64 bit unsigned wrappable counter."
   ::= {pr1645v2Lan2MCVlanMCH24PEntry 83886080}

pr1645v2Lan2MCVlanMCH24PIfInNUCPkts OBJECT-TYPE
   SYNTAX      Counter64
   MAX-ACCESS  read-only
   STATUS      current
   DESCRIPTION
      "Path: ethernet2.performance.vlan.mibCounters.h24Performance.ifInNUcastPkts

       64 bit unsigned wrappable counter."
   ::= {pr1645v2Lan2MCVlanMCH24PEntry 100663296}

pr1645v2Lan2MCVlanMCH24PIfInBCPkts OBJECT-TYPE
   SYNTAX      Counter64
   MAX-ACCESS  read-only
   STATUS      current
   DESCRIPTION
      "Path: ethernet2.performance.vlan.mibCounters.h24Performance.ifInBcastPkts

       64 bit unsigned wrappable counter."
   ::= {pr1645v2Lan2MCVlanMCH24PEntry 419430400}

pr1645v2Lan2MCVlanMCH24PIfInMCPkts OBJECT-TYPE
   SYNTAX      Counter64
   MAX-ACCESS  read-only
   STATUS      current
   DESCRIPTION
      "Path: ethernet2.performance.vlan.mibCounters.h24Performance.ifInMcastPkts

       64 bit unsigned wrappable counter."
   ::= {pr1645v2Lan2MCVlanMCH24PEntry 436207616}

pr1645v2Lan2MCVlanMCH24PIfInDiscards OBJECT-TYPE
   SYNTAX      Counter64
   MAX-ACCESS  read-only
   STATUS      current
   DESCRIPTION
      "Path: ethernet2.performance.vlan.mibCounters.h24Performance.ifInDiscards

       64 bit unsigned wrappable counter."
   ::= {pr1645v2Lan2MCVlanMCH24PEntry 117440512}

pr1645v2Lan2MCVlanMCH24PIfInErrors OBJECT-TYPE
   SYNTAX      Counter64
   MAX-ACCESS  read-only
   STATUS      current
   DESCRIPTION
      "Path: ethernet2.performance.vlan.mibCounters.h24Performance.ifInErrors

       64 bit unsigned wrappable counter."
   ::= {pr1645v2Lan2MCVlanMCH24PEntry 134217728}

pr1645v2Lan2MCVlanMCH24PIfInUnkwn OBJECT-TYPE
   SYNTAX      Counter64
   MAX-ACCESS  read-only
   STATUS      current
   DESCRIPTION
      "Path: ethernet2.performance.vlan.mibCounters.h24Performance.ifInUnknownProtos

       64 bit unsigned wrappable counter."
   ::= {pr1645v2Lan2MCVlanMCH24PEntry 150994944}

pr1645v2Lan2MCVlanMCH24PInDropEx OBJECT-TYPE
   SYNTAX      Counter64
   MAX-ACCESS  read-only
   STATUS      current
   DESCRIPTION
      "Path: ethernet2.performance.vlan.mibCounters.h24Performance.ifInDropLevelExceeded

       64 bit unsigned wrappable counter."
   ::= {pr1645v2Lan2MCVlanMCH24PEntry 335544320}

pr1645v2Lan2MCVlanMCH24PInDropNoMac OBJECT-TYPE
   SYNTAX      Counter64
   MAX-ACCESS  read-only
   STATUS      current
   DESCRIPTION
      "Path: ethernet2.performance.vlan.mibCounters.h24Performance.fInDiscardsNoMacFit

       64 bit unsigned wrappable counter."
   ::= {pr1645v2Lan2MCVlanMCH24PEntry 301989888}

pr1645v2Lan2MCVlanMCH24PInDropNUCast OBJECT-TYPE
   SYNTAX      Counter64
   MAX-ACCESS  read-only
   STATUS      current
   DESCRIPTION
      "Path: ethernet2.performance.vlan.mibCounters.h24Performance.fInDiscardsNUCast

       64 bit unsigned wrappable counter."
   ::= {pr1645v2Lan2MCVlanMCH24PEntry 318767104}

pr1645v2Lan2MCVlanMCH24PInDropFilter OBJECT-TYPE
   SYNTAX      Counter64
   MAX-ACCESS  read-only
   STATUS      current
   DESCRIPTION
      "Path: ethernet2.performance.vlan.mibCounters.h24Performance.fInDiscardsFilter

       64 bit unsigned wrappable counter."
   ::= {pr1645v2Lan2MCVlanMCH24PEntry 385875968}

pr1645v2Lan2MCVlanMCH24PIfInBandwidth OBJECT-TYPE
   SYNTAX      Integer32
   MAX-ACCESS  read-only
   STATUS      current
   DESCRIPTION
      "Path: ethernet2.performance.vlan.mibCounters.h24Performance.ifInBandwidth

       unit name = bps
       formula = 8 * ; 8 /"
   ::= {pr1645v2Lan2MCVlanMCH24PEntry 268435456}

pr1645v2Lan2MCVlanMCH24PIfOutOctets OBJECT-TYPE
   SYNTAX      Counter64
   MAX-ACCESS  read-only
   STATUS      current
   DESCRIPTION
      "Path: ethernet2.performance.vlan.mibCounters.h24Performance.ifOutOctets

       64 bit unsigned wrappable counter."
   ::= {pr1645v2Lan2MCVlanMCH24PEntry 167772160}

pr1645v2Lan2MCVlanMCH24PIfOutUCPkts OBJECT-TYPE
   SYNTAX      Counter64
   MAX-ACCESS  read-only
   STATUS      current
   DESCRIPTION
      "Path: ethernet2.performance.vlan.mibCounters.h24Performance.ifOutUcastPkts

       64 bit unsigned wrappable counter."
   ::= {pr1645v2Lan2MCVlanMCH24PEntry 184549376}

pr1645v2Lan2MCVlanMCH24PIfOutNUCPkts OBJECT-TYPE
   SYNTAX      Counter64
   MAX-ACCESS  read-only
   STATUS      current
   DESCRIPTION
      "Path: ethernet2.performance.vlan.mibCounters.h24Performance.ifOutNUcastPkts

       64 bit unsigned wrappable counter."
   ::= {pr1645v2Lan2MCVlanMCH24PEntry 201326592}

pr1645v2Lan2MCVlanMCH24PIfOutBCPkts OBJECT-TYPE
   SYNTAX      Counter64
   MAX-ACCESS  read-only
   STATUS      current
   DESCRIPTION
      "Path: ethernet2.performance.vlan.mibCounters.h24Performance.ifOutBcastPkts

       64 bit unsigned wrappable counter."
   ::= {pr1645v2Lan2MCVlanMCH24PEntry 452984832}

pr1645v2Lan2MCVlanMCH24PIfOutMCPkts OBJECT-TYPE
   SYNTAX      Counter64
   MAX-ACCESS  read-only
   STATUS      current
   DESCRIPTION
      "Path: ethernet2.performance.vlan.mibCounters.h24Performance.ifOutMcastPkts

       64 bit unsigned wrappable counter."
   ::= {pr1645v2Lan2MCVlanMCH24PEntry 469762048}

pr1645v2Lan2MCVlanMCH24PIfOutDiscards OBJECT-TYPE
   SYNTAX      Counter64
   MAX-ACCESS  read-only
   STATUS      current
   DESCRIPTION
      "Path: ethernet2.performance.vlan.mibCounters.h24Performance.ifOutDiscards

       64 bit unsigned wrappable counter."
   ::= {pr1645v2Lan2MCVlanMCH24PEntry 218103808}

pr1645v2Lan2MCVlanMCH24PIfOutErrors OBJECT-TYPE
   SYNTAX      Counter64
   MAX-ACCESS  read-only
   STATUS      current
   DESCRIPTION
      "Path: ethernet2.performance.vlan.mibCounters.h24Performance.ifOutErrors

       64 bit unsigned wrappable counter."
   ::= {pr1645v2Lan2MCVlanMCH24PEntry 234881024}

pr1645v2Lan2MCVlanMCH24POutDropEx OBJECT-TYPE
   SYNTAX      Counter64
   MAX-ACCESS  read-only
   STATUS      current
   DESCRIPTION
      "Path: ethernet2.performance.vlan.mibCounters.h24Performance.ifOutDropLevelExceeded

       64 bit unsigned wrappable counter."
   ::= {pr1645v2Lan2MCVlanMCH24PEntry 352321536}

pr1645v2Lan2MCVlanMCH24POutDropNoArp OBJECT-TYPE
   SYNTAX      Counter64
   MAX-ACCESS  read-only
   STATUS      current
   DESCRIPTION
      "Path: ethernet2.performance.vlan.mibCounters.h24Performance.ifOutDiscardsNoArp

       64 bit unsigned wrappable counter."
   ::= {pr1645v2Lan2MCVlanMCH24PEntry 369098752}

pr1645v2Lan2MCVlanMCH24POutDropFilter OBJECT-TYPE
   SYNTAX      Counter64
   MAX-ACCESS  read-only
   STATUS      current
   DESCRIPTION
      "Path: ethernet2.performance.vlan.mibCounters.h24Performance.ifOutDiscardsFilter

       64 bit unsigned wrappable counter."
   ::= {pr1645v2Lan2MCVlanMCH24PEntry 402653184}

pr1645v2Lan2MCVlanMCH24PIfOutBandwidth OBJECT-TYPE
   SYNTAX      Integer32
   MAX-ACCESS  read-only
   STATUS      current
   DESCRIPTION
      "Path: ethernet2.performance.vlan.mibCounters.h24Performance.ifOutBandwidth

       unit name = bps
       formula = 8 * ; 8 /"
   ::= {pr1645v2Lan2MCVlanMCH24PEntry 285212672}

pr1645v2Lan2MCVlanMCH24PIfErrSec OBJECT-TYPE
   SYNTAX      Counter32
   MAX-ACCESS  read-only
   STATUS      current
   DESCRIPTION
      "Path: ethernet2.performance.vlan.mibCounters.h24Performance.ifErrSec

       32 bit unsigned wrappable counter."
   ::= {pr1645v2Lan2MCVlanMCH24PEntry 251658240}

pr1645v2Lan2MCVlanMCD7P OBJECT-TYPE
   SYNTAX      SEQUENCE OF Pr1645v2Lan2MCVlanMCD7PEntry
   MAX-ACCESS  not-accessible
   STATUS      current
   DESCRIPTION
      ""
   ::= {pr1645v2Lan2MCVlan 41680896}

pr1645v2Lan2MCVlanMCD7PEntry OBJECT-TYPE
   SYNTAX      Pr1645v2Lan2MCVlanMCD7PEntry
   MAX-ACCESS  not-accessible
   STATUS      current
   DESCRIPTION
      ""
   INDEX      { pr1645v2Lan2MCVlanTableIx,
                pr1645v2Lan2MCVlanMCD7PTableIx }
   ::= {pr1645v2Lan2MCVlanMCD7P 1}

Pr1645v2Lan2MCVlanMCD7PEntry ::=
   SEQUENCE
      {
      pr1645v2Lan2MCVlanMCD7PTableIx
         TableIndex,
      pr1645v2Lan2MCVlanMCD7PSysUpTime
         TimeTicks,
      pr1645v2Lan2MCVlanMCD7PIfUpTime
         TimeTicks,
      pr1645v2Lan2MCVlanMCD7PIfStatChanges
         Counter32,
      pr1645v2Lan2MCVlanMCD7PIfInOctets
         Counter64,
      pr1645v2Lan2MCVlanMCD7PIfInUCPkts
         Counter64,
      pr1645v2Lan2MCVlanMCD7PIfInNUCPkts
         Counter64,
      pr1645v2Lan2MCVlanMCD7PIfInBCPkts
         Counter64,
      pr1645v2Lan2MCVlanMCD7PIfInMCPkts
         Counter64,
      pr1645v2Lan2MCVlanMCD7PIfInDiscards
         Counter64,
      pr1645v2Lan2MCVlanMCD7PIfInErrors
         Counter64,
      pr1645v2Lan2MCVlanMCD7PIfInUnkwn
         Counter64,
      pr1645v2Lan2MCVlanMCD7PInDropEx
         Counter64,
      pr1645v2Lan2MCVlanMCD7PInDropNoMac
         Counter64,
      pr1645v2Lan2MCVlanMCD7PInDropNUCast
         Counter64,
      pr1645v2Lan2MCVlanMCD7PInDropFilter
         Counter64,
      pr1645v2Lan2MCVlanMCD7PIfInBandwidth
         Integer32,
      pr1645v2Lan2MCVlanMCD7PIfOutOctets
         Counter64,
      pr1645v2Lan2MCVlanMCD7PIfOutUCPkts
         Counter64,
      pr1645v2Lan2MCVlanMCD7PIfOutNUCPkts
         Counter64,
      pr1645v2Lan2MCVlanMCD7PIfOutBCPkts
         Counter64,
      pr1645v2Lan2MCVlanMCD7PIfOutMCPkts
         Counter64,
      pr1645v2Lan2MCVlanMCD7PIfOutDiscards
         Counter64,
      pr1645v2Lan2MCVlanMCD7PIfOutErrors
         Counter64,
      pr1645v2Lan2MCVlanMCD7POutDropEx
         Counter64,
      pr1645v2Lan2MCVlanMCD7POutDropNoArp
         Counter64,
      pr1645v2Lan2MCVlanMCD7POutDropFilter
         Counter64,
      pr1645v2Lan2MCVlanMCD7PIfOutBandwidth
         Integer32,
      pr1645v2Lan2MCVlanMCD7PIfErrSec
         Counter32
      }

pr1645v2Lan2MCVlanMCD7PTableIx OBJECT-TYPE
   SYNTAX      TableIndex
   MAX-ACCESS  not-accessible
   STATUS      current
   DESCRIPTION
      ""
   ::= {pr1645v2Lan2MCVlanMCD7PEntry 11}

pr1645v2Lan2MCVlanMCD7PSysUpTime OBJECT-TYPE
   SYNTAX      TimeTicks
   MAX-ACCESS  read-only
   STATUS      current
   DESCRIPTION
      "Path: ethernet2.performance.vlan.mibCounters.d7Performance.sysUpTime

       Time in centi-second."
   ::= {pr1645v2Lan2MCVlanMCD7PEntry 16777216}

pr1645v2Lan2MCVlanMCD7PIfUpTime OBJECT-TYPE
   SYNTAX      TimeTicks
   MAX-ACCESS  read-only
   STATUS      current
   DESCRIPTION
      "Path: ethernet2.performance.vlan.mibCounters.d7Performance.ifUpTime

       Time in centi-second."
   ::= {pr1645v2Lan2MCVlanMCD7PEntry 33554432}

pr1645v2Lan2MCVlanMCD7PIfStatChanges OBJECT-TYPE
   SYNTAX      Counter32
   MAX-ACCESS  read-only
   STATUS      current
   DESCRIPTION
      "Path: ethernet2.performance.vlan.mibCounters.d7Performance.ifStatusChanges

       32 bit unsigned wrappable counter."
   ::= {pr1645v2Lan2MCVlanMCD7PEntry 50331648}

pr1645v2Lan2MCVlanMCD7PIfInOctets OBJECT-TYPE
   SYNTAX      Counter64
   MAX-ACCESS  read-only
   STATUS      current
   DESCRIPTION
      "Path: ethernet2.performance.vlan.mibCounters.d7Performance.ifInOctets

       64 bit unsigned wrappable counter."
   ::= {pr1645v2Lan2MCVlanMCD7PEntry 67108864}

pr1645v2Lan2MCVlanMCD7PIfInUCPkts OBJECT-TYPE
   SYNTAX      Counter64
   MAX-ACCESS  read-only
   STATUS      current
   DESCRIPTION
      "Path: ethernet2.performance.vlan.mibCounters.d7Performance.ifInUcastPkts

       64 bit unsigned wrappable counter."
   ::= {pr1645v2Lan2MCVlanMCD7PEntry 83886080}

pr1645v2Lan2MCVlanMCD7PIfInNUCPkts OBJECT-TYPE
   SYNTAX      Counter64
   MAX-ACCESS  read-only
   STATUS      current
   DESCRIPTION
      "Path: ethernet2.performance.vlan.mibCounters.d7Performance.ifInNUcastPkts

       64 bit unsigned wrappable counter."
   ::= {pr1645v2Lan2MCVlanMCD7PEntry 100663296}

pr1645v2Lan2MCVlanMCD7PIfInBCPkts OBJECT-TYPE
   SYNTAX      Counter64
   MAX-ACCESS  read-only
   STATUS      current
   DESCRIPTION
      "Path: ethernet2.performance.vlan.mibCounters.d7Performance.ifInBcastPkts

       64 bit unsigned wrappable counter."
   ::= {pr1645v2Lan2MCVlanMCD7PEntry 419430400}

pr1645v2Lan2MCVlanMCD7PIfInMCPkts OBJECT-TYPE
   SYNTAX      Counter64
   MAX-ACCESS  read-only
   STATUS      current
   DESCRIPTION
      "Path: ethernet2.performance.vlan.mibCounters.d7Performance.ifInMcastPkts

       64 bit unsigned wrappable counter."
   ::= {pr1645v2Lan2MCVlanMCD7PEntry 436207616}

pr1645v2Lan2MCVlanMCD7PIfInDiscards OBJECT-TYPE
   SYNTAX      Counter64
   MAX-ACCESS  read-only
   STATUS      current
   DESCRIPTION
      "Path: ethernet2.performance.vlan.mibCounters.d7Performance.ifInDiscards

       64 bit unsigned wrappable counter."
   ::= {pr1645v2Lan2MCVlanMCD7PEntry 117440512}

pr1645v2Lan2MCVlanMCD7PIfInErrors OBJECT-TYPE
   SYNTAX      Counter64
   MAX-ACCESS  read-only
   STATUS      current
   DESCRIPTION
      "Path: ethernet2.performance.vlan.mibCounters.d7Performance.ifInErrors

       64 bit unsigned wrappable counter."
   ::= {pr1645v2Lan2MCVlanMCD7PEntry 134217728}

pr1645v2Lan2MCVlanMCD7PIfInUnkwn OBJECT-TYPE
   SYNTAX      Counter64
   MAX-ACCESS  read-only
   STATUS      current
   DESCRIPTION
      "Path: ethernet2.performance.vlan.mibCounters.d7Performance.ifInUnknownProtos

       64 bit unsigned wrappable counter."
   ::= {pr1645v2Lan2MCVlanMCD7PEntry 150994944}

pr1645v2Lan2MCVlanMCD7PInDropEx OBJECT-TYPE
   SYNTAX      Counter64
   MAX-ACCESS  read-only
   STATUS      current
   DESCRIPTION
      "Path: ethernet2.performance.vlan.mibCounters.d7Performance.ifInDropLevelExceeded

       64 bit unsigned wrappable counter."
   ::= {pr1645v2Lan2MCVlanMCD7PEntry 335544320}

pr1645v2Lan2MCVlanMCD7PInDropNoMac OBJECT-TYPE
   SYNTAX      Counter64
   MAX-ACCESS  read-only
   STATUS      current
   DESCRIPTION
      "Path: ethernet2.performance.vlan.mibCounters.d7Performance.fInDiscardsNoMacFit

       64 bit unsigned wrappable counter."
   ::= {pr1645v2Lan2MCVlanMCD7PEntry 301989888}

pr1645v2Lan2MCVlanMCD7PInDropNUCast OBJECT-TYPE
   SYNTAX      Counter64
   MAX-ACCESS  read-only
   STATUS      current
   DESCRIPTION
      "Path: ethernet2.performance.vlan.mibCounters.d7Performance.fInDiscardsNUCast

       64 bit unsigned wrappable counter."
   ::= {pr1645v2Lan2MCVlanMCD7PEntry 318767104}

pr1645v2Lan2MCVlanMCD7PInDropFilter OBJECT-TYPE
   SYNTAX      Counter64
   MAX-ACCESS  read-only
   STATUS      current
   DESCRIPTION
      "Path: ethernet2.performance.vlan.mibCounters.d7Performance.fInDiscardsFilter

       64 bit unsigned wrappable counter."
   ::= {pr1645v2Lan2MCVlanMCD7PEntry 385875968}

pr1645v2Lan2MCVlanMCD7PIfInBandwidth OBJECT-TYPE
   SYNTAX      Integer32
   MAX-ACCESS  read-only
   STATUS      current
   DESCRIPTION
      "Path: ethernet2.performance.vlan.mibCounters.d7Performance.ifInBandwidth

       unit name = bps
       formula = 8 * ; 8 /"
   ::= {pr1645v2Lan2MCVlanMCD7PEntry 268435456}

pr1645v2Lan2MCVlanMCD7PIfOutOctets OBJECT-TYPE
   SYNTAX      Counter64
   MAX-ACCESS  read-only
   STATUS      current
   DESCRIPTION
      "Path: ethernet2.performance.vlan.mibCounters.d7Performance.ifOutOctets

       64 bit unsigned wrappable counter."
   ::= {pr1645v2Lan2MCVlanMCD7PEntry 167772160}

pr1645v2Lan2MCVlanMCD7PIfOutUCPkts OBJECT-TYPE
   SYNTAX      Counter64
   MAX-ACCESS  read-only
   STATUS      current
   DESCRIPTION
      "Path: ethernet2.performance.vlan.mibCounters.d7Performance.ifOutUcastPkts

       64 bit unsigned wrappable counter."
   ::= {pr1645v2Lan2MCVlanMCD7PEntry 184549376}

pr1645v2Lan2MCVlanMCD7PIfOutNUCPkts OBJECT-TYPE
   SYNTAX      Counter64
   MAX-ACCESS  read-only
   STATUS      current
   DESCRIPTION
      "Path: ethernet2.performance.vlan.mibCounters.d7Performance.ifOutNUcastPkts

       64 bit unsigned wrappable counter."
   ::= {pr1645v2Lan2MCVlanMCD7PEntry 201326592}

pr1645v2Lan2MCVlanMCD7PIfOutBCPkts OBJECT-TYPE
   SYNTAX      Counter64
   MAX-ACCESS  read-only
   STATUS      current
   DESCRIPTION
      "Path: ethernet2.performance.vlan.mibCounters.d7Performance.ifOutBcastPkts

       64 bit unsigned wrappable counter."
   ::= {pr1645v2Lan2MCVlanMCD7PEntry 452984832}

pr1645v2Lan2MCVlanMCD7PIfOutMCPkts OBJECT-TYPE
   SYNTAX      Counter64
   MAX-ACCESS  read-only
   STATUS      current
   DESCRIPTION
      "Path: ethernet2.performance.vlan.mibCounters.d7Performance.ifOutMcastPkts

       64 bit unsigned wrappable counter."
   ::= {pr1645v2Lan2MCVlanMCD7PEntry 469762048}

pr1645v2Lan2MCVlanMCD7PIfOutDiscards OBJECT-TYPE
   SYNTAX      Counter64
   MAX-ACCESS  read-only
   STATUS      current
   DESCRIPTION
      "Path: ethernet2.performance.vlan.mibCounters.d7Performance.ifOutDiscards

       64 bit unsigned wrappable counter."
   ::= {pr1645v2Lan2MCVlanMCD7PEntry 218103808}

pr1645v2Lan2MCVlanMCD7PIfOutErrors OBJECT-TYPE
   SYNTAX      Counter64
   MAX-ACCESS  read-only
   STATUS      current
   DESCRIPTION
      "Path: ethernet2.performance.vlan.mibCounters.d7Performance.ifOutErrors

       64 bit unsigned wrappable counter."
   ::= {pr1645v2Lan2MCVlanMCD7PEntry 234881024}

pr1645v2Lan2MCVlanMCD7POutDropEx OBJECT-TYPE
   SYNTAX      Counter64
   MAX-ACCESS  read-only
   STATUS      current
   DESCRIPTION
      "Path: ethernet2.performance.vlan.mibCounters.d7Performance.ifOutDropLevelExceeded

       64 bit unsigned wrappable counter."
   ::= {pr1645v2Lan2MCVlanMCD7PEntry 352321536}

pr1645v2Lan2MCVlanMCD7POutDropNoArp OBJECT-TYPE
   SYNTAX      Counter64
   MAX-ACCESS  read-only
   STATUS      current
   DESCRIPTION
      "Path: ethernet2.performance.vlan.mibCounters.d7Performance.ifOutDiscardsNoArp

       64 bit unsigned wrappable counter."
   ::= {pr1645v2Lan2MCVlanMCD7PEntry 369098752}

pr1645v2Lan2MCVlanMCD7POutDropFilter OBJECT-TYPE
   SYNTAX      Counter64
   MAX-ACCESS  read-only
   STATUS      current
   DESCRIPTION
      "Path: ethernet2.performance.vlan.mibCounters.d7Performance.ifOutDiscardsFilter

       64 bit unsigned wrappable counter."
   ::= {pr1645v2Lan2MCVlanMCD7PEntry 402653184}

pr1645v2Lan2MCVlanMCD7PIfOutBandwidth OBJECT-TYPE
   SYNTAX      Integer32
   MAX-ACCESS  read-only
   STATUS      current
   DESCRIPTION
      "Path: ethernet2.performance.vlan.mibCounters.d7Performance.ifOutBandwidth

       unit name = bps
       formula = 8 * ; 8 /"
   ::= {pr1645v2Lan2MCVlanMCD7PEntry 285212672}

pr1645v2Lan2MCVlanMCD7PIfErrSec OBJECT-TYPE
   SYNTAX      Counter32
   MAX-ACCESS  read-only
   STATUS      current
   DESCRIPTION
      "Path: ethernet2.performance.vlan.mibCounters.d7Performance.ifErrSec

       32 bit unsigned wrappable counter."
   ::= {pr1645v2Lan2MCVlanMCD7PEntry 251658240}

pr1645v2Lan2MCVlanInPQs OBJECT-TYPE
   SYNTAX      SEQUENCE OF Pr1645v2Lan2MCVlanInPQsEntry
   MAX-ACCESS  not-accessible
   STATUS      current
   DESCRIPTION
      ""
   ::= {pr1645v2Lan2MCVlan 100663296}

pr1645v2Lan2MCVlanInPQsEntry OBJECT-TYPE
   SYNTAX      Pr1645v2Lan2MCVlanInPQsEntry
   MAX-ACCESS  not-accessible
   STATUS      current
   DESCRIPTION
      ""
   INDEX      { pr1645v2Lan2MCVlanTableIx,
                pr1645v2Lan2MCVlanInPQsTableIx }
   ::= {pr1645v2Lan2MCVlanInPQs 1}

Pr1645v2Lan2MCVlanInPQsEntry ::=
   SEQUENCE
      {
      pr1645v2Lan2MCVlanInPQsTableIx
         TableIndex,
      pr1645v2Lan2MCVlanInPQsName
         INTEGER,
      pr1645v2Lan2MCVlanInPQsLength
         Integer32,
      pr1645v2Lan2MCVlanInPQsOctetLength
         Integer32,
      pr1645v2Lan2MCVlanInPQsRedLength
         Integer32,
      pr1645v2Lan2MCVlanInPQsPacketsTotal
         Counter64,
      pr1645v2Lan2MCVlanInPQsPacketsDirectTx
         Counter64,
      pr1645v2Lan2MCVlanInPQsPacketsQueued
         Counter64,
      pr1645v2Lan2MCVlanInPQsPacketsDropped
         Counter64,
      pr1645v2Lan2MCVlanInPQsPacketsRedDropped
         Counter64,
      pr1645v2Lan2MCVlanInPQsPacketsCirTx
         Counter64,
      pr1645v2Lan2MCVlanInPQsPacketsEirTx
         Counter64,
      pr1645v2Lan2MCVlanInPQsPacketsViolateTx
         Counter64,
      pr1645v2Lan2MCVlanInPQsOctetsTotal
         Counter64,
      pr1645v2Lan2MCVlanInPQsOctetsDirectTx
         Counter64,
      pr1645v2Lan2MCVlanInPQsOctetsQueued
         Counter64,
      pr1645v2Lan2MCVlanInPQsOctetsDropped
         Counter64,
      pr1645v2Lan2MCVlanInPQsOctetsRedDropped
         Counter64,
      pr1645v2Lan2MCVlanInPQsOctetsCirTx
         Counter64,
      pr1645v2Lan2MCVlanInPQsOctetsEirTx
         Counter64,
      pr1645v2Lan2MCVlanInPQsOctetsViolateTx
         Counter64,
      pr1645v2Lan2MCVlanInPQsOctetsBandwidth15sec
         Integer32,
      pr1645v2Lan2MCVlanInPQsOctetsBandwidth30sec
         Integer32,
      pr1645v2Lan2MCVlanInPQsOctetsBandwidth1min
         Integer32,
      pr1645v2Lan2MCVlanInPQsOctetsBandwidth2min
         Integer32,
      pr1645v2Lan2MCVlanInPQsOctetsBandwidth5min
         Integer32
      }

pr1645v2Lan2MCVlanInPQsTableIx OBJECT-TYPE
   SYNTAX      TableIndex
   MAX-ACCESS  not-accessible
   STATUS      current
   DESCRIPTION
      ""
   ::= {pr1645v2Lan2MCVlanInPQsEntry 11}

pr1645v2Lan2MCVlanInPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.vlan.inPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2MCVlanInPQsEntry 16777216}

pr1645v2Lan2MCVlanInPQsLength OBJECT-TYPE
   SYNTAX      Integer32
   MAX-ACCESS  read-only
   STATUS      current
   DESCRIPTION
      "Path: ethernet2.performance.vlan.inPriorityQueues.length"
   ::= {pr1645v2Lan2MCVlanInPQsEntry 33554432}

pr1645v2Lan2MCVlanInPQsOctetLength OBJECT-TYPE
   SYNTAX      Integer32
   MAX-ACCESS  read-only
   STATUS      current
   DESCRIPTION
      "Path: ethernet2.performance.vlan.inPriorityQueues.octetLength"
   ::= {pr1645v2Lan2MCVlanInPQsEntry 150994944}

pr1645v2Lan2MCVlanInPQsRedLength OBJECT-TYPE
   SYNTAX      Integer32
   MAX-ACCESS  read-only
   STATUS      current
   DESCRIPTION
      "Path: ethernet2.performance.vlan.inPriorityQueues.redLength"
   ::= {pr1645v2Lan2MCVlanInPQsEntry 134217728}

pr1645v2Lan2MCVlanInPQsPacketsTotal OBJECT-TYPE
   SYNTAX      Counter64
   MAX-ACCESS  read-only
   STATUS      current
   DESCRIPTION
      "Path: ethernet2.performance.vlan.inPriorityQueues.packets.total

       64 bit unsigned wrappable counter."
   ::= {pr1645v2Lan2MCVlanInPQsEntry 50790400}

pr1645v2Lan2MCVlanInPQsPacketsDirectTx OBJECT-TYPE
   SYNTAX      Counter64
   MAX-ACCESS  read-only
   STATUS      current
   DESCRIPTION
      "Path: ethernet2.performance.vlan.inPriorityQueues.packets.directTx

       64 bit unsigned wrappable counter."
   ::= {pr1645v2Lan2MCVlanInPQsEntry 50397184}

pr1645v2Lan2MCVlanInPQsPacketsQueued OBJECT-TYPE
   SYNTAX      Counter64
   MAX-ACCESS  read-only
   STATUS      current
   DESCRIPTION
      "Path: ethernet2.performance.vlan.inPriorityQueues.packets.queued

       64 bit unsigned wrappable counter."
   ::= {pr1645v2Lan2MCVlanInPQsEntry 50462720}

pr1645v2Lan2MCVlanInPQsPacketsDropped OBJECT-TYPE
   SYNTAX      Counter64
   MAX-ACCESS  read-only
   STATUS      current
   DESCRIPTION
      "Path: ethernet2.performance.vlan.inPriorityQueues.packets.dropped

       64 bit unsigned wrappable counter."
   ::= {pr1645v2Lan2MCVlanInPQsEntry 50528256}

pr1645v2Lan2MCVlanInPQsPacketsRedDropped OBJECT-TYPE
   SYNTAX      Counter64
   MAX-ACCESS  read-only
   STATUS      current
   DESCRIPTION
      "Path: ethernet2.performance.vlan.inPriorityQueues.packets.redDropped

       64 bit unsigned wrappable counter."
   ::= {pr1645v2Lan2MCVlanInPQsEntry 50724864}

pr1645v2Lan2MCVlanInPQsPacketsCirTx OBJECT-TYPE
   SYNTAX      Counter64
   MAX-ACCESS  read-only
   STATUS      current
   DESCRIPTION
      "Path: ethernet2.performance.vlan.inPriorityQueues.packets.cirTx

       64 bit unsigned wrappable counter."
   ::= {pr1645v2Lan2MCVlanInPQsEntry 50593792}

pr1645v2Lan2MCVlanInPQsPacketsEirTx OBJECT-TYPE
   SYNTAX      Counter64
   MAX-ACCESS  read-only
   STATUS      current
   DESCRIPTION
      "Path: ethernet2.performance.vlan.inPriorityQueues.packets.eirTx

       64 bit unsigned wrappable counter."
   ::= {pr1645v2Lan2MCVlanInPQsEntry 50659328}

pr1645v2Lan2MCVlanInPQsPacketsViolateTx OBJECT-TYPE
   SYNTAX      Counter64
   MAX-ACCESS  read-only
   STATUS      current
   DESCRIPTION
      "Path: ethernet2.performance.vlan.inPriorityQueues.packets.violateTx

       64 bit unsigned wrappable counter."
   ::= {pr1645v2Lan2MCVlanInPQsEntry 50855936}

pr1645v2Lan2MCVlanInPQsOctetsTotal OBJECT-TYPE
   SYNTAX      Counter64
   MAX-ACCESS  read-only
   STATUS      current
   DESCRIPTION
      "Path: ethernet2.performance.vlan.inPriorityQueues.octets.total

       64 bit unsigned wrappable counter."
   ::= {pr1645v2Lan2MCVlanInPQsEntry 67567616}

pr1645v2Lan2MCVlanInPQsOctetsDirectTx OBJECT-TYPE
   SYNTAX      Counter64
   MAX-ACCESS  read-only
   STATUS      current
   DESCRIPTION
      "Path: ethernet2.performance.vlan.inPriorityQueues.octets.directTx

       64 bit unsigned wrappable counter."
   ::= {pr1645v2Lan2MCVlanInPQsEntry 67174400}

pr1645v2Lan2MCVlanInPQsOctetsQueued OBJECT-TYPE
   SYNTAX      Counter64
   MAX-ACCESS  read-only
   STATUS      current
   DESCRIPTION
      "Path: ethernet2.performance.vlan.inPriorityQueues.octets.queued

       64 bit unsigned wrappable counter."
   ::= {pr1645v2Lan2MCVlanInPQsEntry 67239936}

pr1645v2Lan2MCVlanInPQsOctetsDropped OBJECT-TYPE
   SYNTAX      Counter64
   MAX-ACCESS  read-only
   STATUS      current
   DESCRIPTION
      "Path: ethernet2.performance.vlan.inPriorityQueues.octets.dropped

       64 bit unsigned wrappable counter."
   ::= {pr1645v2Lan2MCVlanInPQsEntry 67305472}

pr1645v2Lan2MCVlanInPQsOctetsRedDropped OBJECT-TYPE
   SYNTAX      Counter64
   MAX-ACCESS  read-only
   STATUS      current
   DESCRIPTION
      "Path: ethernet2.performance.vlan.inPriorityQueues.octets.redDropped

       64 bit unsigned wrappable counter."
   ::= {pr1645v2Lan2MCVlanInPQsEntry 67502080}

pr1645v2Lan2MCVlanInPQsOctetsCirTx OBJECT-TYPE
   SYNTAX      Counter64
   MAX-ACCESS  read-only
   STATUS      current
   DESCRIPTION
      "Path: ethernet2.performance.vlan.inPriorityQueues.octets.cirTx

       64 bit unsigned wrappable counter."
   ::= {pr1645v2Lan2MCVlanInPQsEntry 67371008}

pr1645v2Lan2MCVlanInPQsOctetsEirTx OBJECT-TYPE
   SYNTAX      Counter64
   MAX-ACCESS  read-only
   STATUS      current
   DESCRIPTION
      "Path: ethernet2.performance.vlan.inPriorityQueues.octets.eirTx

       64 bit unsigned wrappable counter."
   ::= {pr1645v2Lan2MCVlanInPQsEntry 67436544}

pr1645v2Lan2MCVlanInPQsOctetsViolateTx OBJECT-TYPE
   SYNTAX      Counter64
   MAX-ACCESS  read-only
   STATUS      current
   DESCRIPTION
      "Path: ethernet2.performance.vlan.inPriorityQueues.octets.violateTx

       64 bit unsigned wrappable counter."
   ::= {pr1645v2Lan2MCVlanInPQsEntry 67633152}

pr1645v2Lan2MCVlanInPQsOctetsBandwidth15sec OBJECT-TYPE
   SYNTAX      Integer32
   MAX-ACCESS  read-only
   STATUS      current
   DESCRIPTION
      "Path: ethernet2.performance.vlan.inPriorityQueues.octets.bandwidth.15sec

       unit name = bps
       formula = 8 * ; 8 /"
   ::= {pr1645v2Lan2MCVlanInPQsEntry 70386944}

pr1645v2Lan2MCVlanInPQsOctetsBandwidth30sec OBJECT-TYPE
   SYNTAX      Integer32
   MAX-ACCESS  read-only
   STATUS      current
   DESCRIPTION
      "Path: ethernet2.performance.vlan.inPriorityQueues.octets.bandwidth.30sec

       unit name = bps
       formula = 8 * ; 8 /"
   ::= {pr1645v2Lan2MCVlanInPQsEntry 70388224}

pr1645v2Lan2MCVlanInPQsOctetsBandwidth1min OBJECT-TYPE
   SYNTAX      Integer32
   MAX-ACCESS  read-only
   STATUS      current
   DESCRIPTION
      "Path: ethernet2.performance.vlan.inPriorityQueues.octets.bandwidth.1min

       unit name = bps
       formula = 8 * ; 8 /"
   ::= {pr1645v2Lan2MCVlanInPQsEntry 70390784}

pr1645v2Lan2MCVlanInPQsOctetsBandwidth2min OBJECT-TYPE
   SYNTAX      Integer32
   MAX-ACCESS  read-only
   STATUS      current
   DESCRIPTION
      "Path: ethernet2.performance.vlan.inPriorityQueues.octets.bandwidth.2min

       unit name = bps
       formula = 8 * ; 8 /"
   ::= {pr1645v2Lan2MCVlanInPQsEntry 70395904}

pr1645v2Lan2MCVlanInPQsOctetsBandwidth5min OBJECT-TYPE
   SYNTAX      Integer32
   MAX-ACCESS  read-only
   STATUS      current
   DESCRIPTION
      "Path: ethernet2.performance.vlan.inPriorityQueues.octets.bandwidth.5min

       unit name = bps
       formula = 8 * ; 8 /"
   ::= {pr1645v2Lan2MCVlanInPQsEntry 70411264}

pr1645v2Lan2MCVlanInPQsH2Performance OBJECT-TYPE
   SYNTAX      SEQUENCE OF Pr1645v2Lan2MCVlanInPQsH2PerformanceEntry
   MAX-ACCESS  not-accessible
   STATUS      current
   DESCRIPTION
      ""
   ::= {pr1645v2Lan2MCVlan 100990976}

pr1645v2Lan2MCVlanInPQsH2PerformanceEntry OBJECT-TYPE
   SYNTAX      Pr1645v2Lan2MCVlanInPQsH2PerformanceEntry
   MAX-ACCESS  not-accessible
   STATUS      current
   DESCRIPTION
      ""
   INDEX      { pr1645v2Lan2MCVlanTableIx,
                pr1645v2Lan2MCVlanInPQsTableIx,
                pr1645v2Lan2MCVlanInPQsH2PerformanceTableIx }
   ::= {pr1645v2Lan2MCVlanInPQsH2Performance 1}

Pr1645v2Lan2MCVlanInPQsH2PerformanceEntry ::=
   SEQUENCE
      {
      pr1645v2Lan2MCVlanInPQsH2PerformanceTableIx
         TableIndex,
      pr1645v2Lan2MCVlanInPQsH2PerformanceSysUpTime
         TimeTicks,
      pr1645v2Lan2MCVlanInPQsH2PerformanceTotPkts
         Counter64,
      pr1645v2Lan2MCVlanInPQsH2PerformanceDirTxPkts
         Counter64,
      pr1645v2Lan2MCVlanInPQsH2PerformanceQdPkts
         Counter64,
      pr1645v2Lan2MCVlanInPQsH2PerformanceDropPkts
         Counter64,
      pr1645v2Lan2MCVlanInPQsH2PerformanceRDropPkts
         Counter64,
      pr1645v2Lan2MCVlanInPQsH2PerformanceCirTxPkts
         Counter64,
      pr1645v2Lan2MCVlanInPQsH2PerformanceEirTxPkts
         Counter64,
      pr1645v2Lan2MCVlanInPQsH2PerformanceViolTxPkts
         Counter64,
      pr1645v2Lan2MCVlanInPQsH2PerformanceTotOcts
         Counter64,
      pr1645v2Lan2MCVlanInPQsH2PerformanceDirTxOcts
         Counter64,
      pr1645v2Lan2MCVlanInPQsH2PerformanceQdOcts
         Counter64,
      pr1645v2Lan2MCVlanInPQsH2PerformanceDropOcts
         Counter64,
      pr1645v2Lan2MCVlanInPQsH2PerformanceRDropOcts
         Counter64,
      pr1645v2Lan2MCVlanInPQsH2PerformanceCirTxOcts
         Counter64,
      pr1645v2Lan2MCVlanInPQsH2PerformanceEirTxOcts
         Counter64,
      pr1645v2Lan2MCVlanInPQsH2PerformanceViolTxOcts
         Counter64,
      pr1645v2Lan2MCVlanInPQsH2PerformanceBandwidth
         Integer32
      }

pr1645v2Lan2MCVlanInPQsH2PerformanceTableIx OBJECT-TYPE
   SYNTAX      TableIndex
   MAX-ACCESS  not-accessible
   STATUS      current
   DESCRIPTION
      ""
   ::= {pr1645v2Lan2MCVlanInPQsH2PerformanceEntry 11}

pr1645v2Lan2MCVlanInPQsH2PerformanceSysUpTime OBJECT-TYPE
   SYNTAX      TimeTicks
   MAX-ACCESS  read-only
   STATUS      current
   DESCRIPTION
      "Path: ethernet2.performance.vlan.inPriorityQueues.h2Performance.sysUpTime

       Time in centi-second."
   ::= {pr1645v2Lan2MCVlanInPQsH2PerformanceEntry 16777216}

pr1645v2Lan2MCVlanInPQsH2PerformanceTotPkts OBJECT-TYPE
   SYNTAX      Counter64
   MAX-ACCESS  read-only
   STATUS      current
   DESCRIPTION
      "Path: ethernet2.performance.vlan.inPriorityQueues.h2Performance.totalPkts

       64 bit unsigned wrappable counter."
   ::= {pr1645v2Lan2MCVlanInPQsH2PerformanceEntry 234881024}

pr1645v2Lan2MCVlanInPQsH2PerformanceDirTxPkts OBJECT-TYPE
   SYNTAX      Counter64
   MAX-ACCESS  read-only
   STATUS      current
   DESCRIPTION
      "Path: ethernet2.performance.vlan.inPriorityQueues.h2Performance.directTxPkts

       64 bit unsigned wrappable counter."
   ::= {pr1645v2Lan2MCVlanInPQsH2PerformanceEntry 33554432}

pr1645v2Lan2MCVlanInPQsH2PerformanceQdPkts OBJECT-TYPE
   SYNTAX      Counter64
   MAX-ACCESS  read-only
   STATUS      current
   DESCRIPTION
      "Path: ethernet2.performance.vlan.inPriorityQueues.h2Performance.queuedPkts

       64 bit unsigned wrappable counter."
   ::= {pr1645v2Lan2MCVlanInPQsH2PerformanceEntry 50331648}

pr1645v2Lan2MCVlanInPQsH2PerformanceDropPkts OBJECT-TYPE
   SYNTAX      Counter64
   MAX-ACCESS  read-only
   STATUS      current
   DESCRIPTION
      "Path: ethernet2.performance.vlan.inPriorityQueues.h2Performance.droppedPkts

       64 bit unsigned wrappable counter."
   ::= {pr1645v2Lan2MCVlanInPQsH2PerformanceEntry 67108864}

pr1645v2Lan2MCVlanInPQsH2PerformanceRDropPkts OBJECT-TYPE
   SYNTAX      Counter64
   MAX-ACCESS  read-only
   STATUS      current
   DESCRIPTION
      "Path: ethernet2.performance.vlan.inPriorityQueues.h2Performance.redDroppedPkts

       64 bit unsigned wrappable counter."
   ::= {pr1645v2Lan2MCVlanInPQsH2PerformanceEntry 201326592}

pr1645v2Lan2MCVlanInPQsH2PerformanceCirTxPkts OBJECT-TYPE
   SYNTAX      Counter64
   MAX-ACCESS  read-only
   STATUS      current
   DESCRIPTION
      "Path: ethernet2.performance.vlan.inPriorityQueues.h2Performance.cirTxPkts

       64 bit unsigned wrappable counter."
   ::= {pr1645v2Lan2MCVlanInPQsH2PerformanceEntry 83886080}

pr1645v2Lan2MCVlanInPQsH2PerformanceEirTxPkts OBJECT-TYPE
   SYNTAX      Counter64
   MAX-ACCESS  read-only
   STATUS      current
   DESCRIPTION
      "Path: ethernet2.performance.vlan.inPriorityQueues.h2Performance.eirTxPkts

       64 bit unsigned wrappable counter."
   ::= {pr1645v2Lan2MCVlanInPQsH2PerformanceEntry 100663296}

pr1645v2Lan2MCVlanInPQsH2PerformanceViolTxPkts OBJECT-TYPE
   SYNTAX      Counter64
   MAX-ACCESS  read-only
   STATUS      current
   DESCRIPTION
      "Path: ethernet2.performance.vlan.inPriorityQueues.h2Performance.violateTxPkts

       64 bit unsigned wrappable counter."
   ::= {pr1645v2Lan2MCVlanInPQsH2PerformanceEntry 301989888}

pr1645v2Lan2MCVlanInPQsH2PerformanceTotOcts OBJECT-TYPE
   SYNTAX      Counter64
   MAX-ACCESS  read-only
   STATUS      current
   DESCRIPTION
      "Path: ethernet2.performance.vlan.inPriorityQueues.h2Performance.totalOctets

       64 bit unsigned wrappable counter."
   ::= {pr1645v2Lan2MCVlanInPQsH2PerformanceEntry 251658240}

pr1645v2Lan2MCVlanInPQsH2PerformanceDirTxOcts OBJECT-TYPE
   SYNTAX      Counter64
   MAX-ACCESS  read-only
   STATUS      current
   DESCRIPTION
      "Path: ethernet2.performance.vlan.inPriorityQueues.h2Performance.directTxOctets

       64 bit unsigned wrappable counter."
   ::= {pr1645v2Lan2MCVlanInPQsH2PerformanceEntry 117440512}

pr1645v2Lan2MCVlanInPQsH2PerformanceQdOcts OBJECT-TYPE
   SYNTAX      Counter64
   MAX-ACCESS  read-only
   STATUS      current
   DESCRIPTION
      "Path: ethernet2.performance.vlan.inPriorityQueues.h2Performance.queuedOctets

       64 bit unsigned wrappable counter."
   ::= {pr1645v2Lan2MCVlanInPQsH2PerformanceEntry 134217728}

pr1645v2Lan2MCVlanInPQsH2PerformanceDropOcts OBJECT-TYPE
   SYNTAX      Counter64
   MAX-ACCESS  read-only
   STATUS      current
   DESCRIPTION
      "Path: ethernet2.performance.vlan.inPriorityQueues.h2Performance.droppedOctets

       64 bit unsigned wrappable counter."
   ::= {pr1645v2Lan2MCVlanInPQsH2PerformanceEntry 150994944}

pr1645v2Lan2MCVlanInPQsH2PerformanceRDropOcts OBJECT-TYPE
   SYNTAX      Counter64
   MAX-ACCESS  read-only
   STATUS      current
   DESCRIPTION
      "Path: ethernet2.performance.vlan.inPriorityQueues.h2Performance.redDroppedOctets

       64 bit unsigned wrappable counter."
   ::= {pr1645v2Lan2MCVlanInPQsH2PerformanceEntry 218103808}

pr1645v2Lan2MCVlanInPQsH2PerformanceCirTxOcts OBJECT-TYPE
   SYNTAX      Counter64
   MAX-ACCESS  read-only
   STATUS      current
   DESCRIPTION
      "Path: ethernet2.performance.vlan.inPriorityQueues.h2Performance.cirTxOctets

       64 bit unsigned wrappable counter."
   ::= {pr1645v2Lan2MCVlanInPQsH2PerformanceEntry 167772160}

pr1645v2Lan2MCVlanInPQsH2PerformanceEirTxOcts OBJECT-TYPE
   SYNTAX      Counter64
   MAX-ACCESS  read-only
   STATUS      current
   DESCRIPTION
      "Path: ethernet2.performance.vlan.inPriorityQueues.h2Performance.eirTxOctets

       64 bit unsigned wrappable counter."
   ::= {pr1645v2Lan2MCVlanInPQsH2PerformanceEntry 184549376}

pr1645v2Lan2MCVlanInPQsH2PerformanceViolTxOcts OBJECT-TYPE
   SYNTAX      Counter64
   MAX-ACCESS  read-only
   STATUS      current
   DESCRIPTION
      "Path: ethernet2.performance.vlan.inPriorityQueues.h2Performance.violateTxOctets

       64 bit unsigned wrappable counter."
   ::= {pr1645v2Lan2MCVlanInPQsH2PerformanceEntry 318767104}

pr1645v2Lan2MCVlanInPQsH2PerformanceBandwidth OBJECT-TYPE
   SYNTAX      Integer32
   MAX-ACCESS  read-only
   STATUS      current
   DESCRIPTION
      "Path: ethernet2.performance.vlan.inPriorityQueues.h2Performance.bandwidth

       unit name = bps
       formula = 8 * ; 8 /"
   ::= {pr1645v2Lan2MCVlanInPQsH2PerformanceEntry 268435456}

pr1645v2Lan2MCVlanInPQsH24Performance OBJECT-TYPE
   SYNTAX      SEQUENCE OF Pr1645v2Lan2MCVlanInPQsH24PerformanceEntry
   MAX-ACCESS  not-accessible
   STATUS      current
   DESCRIPTION
      ""
   ::= {pr1645v2Lan2MCVlan 101056512}

pr1645v2Lan2MCVlanInPQsH24PerformanceEntry OBJECT-TYPE
   SYNTAX      Pr1645v2Lan2MCVlanInPQsH24PerformanceEntry
   MAX-ACCESS  not-accessible
   STATUS      current
   DESCRIPTION
      ""
   INDEX      { pr1645v2Lan2MCVlanTableIx,
                pr1645v2Lan2MCVlanInPQsTableIx,
                pr1645v2Lan2MCVlanInPQsH24PerformanceTableIx }
   ::= {pr1645v2Lan2MCVlanInPQsH24Performance 1}

Pr1645v2Lan2MCVlanInPQsH24PerformanceEntry ::=
   SEQUENCE
      {
      pr1645v2Lan2MCVlanInPQsH24PerformanceTableIx
         TableIndex,
      pr1645v2Lan2MCVlanInPQsH24PerformanceSysUpTime
         TimeTicks,
      pr1645v2Lan2MCVlanInPQsH24PerformanceTotPkts
         Counter64,
      pr1645v2Lan2MCVlanInPQsH24PerformanceDirTxPkts
         Counter64,
      pr1645v2Lan2MCVlanInPQsH24PerformanceQdPkts
         Counter64,
      pr1645v2Lan2MCVlanInPQsH24PerformanceDropPkts
         Counter64,
      pr1645v2Lan2MCVlanInPQsH24PerformanceRDropPkts
         Counter64,
      pr1645v2Lan2MCVlanInPQsH24PerformanceCirTxPkts
         Counter64,
      pr1645v2Lan2MCVlanInPQsH24PerformanceEirTxPkts
         Counter64,
      pr1645v2Lan2MCVlanInPQsH24PerformanceViolTxPkts
         Counter64,
      pr1645v2Lan2MCVlanInPQsH24PerformanceTotOcts
         Counter64,
      pr1645v2Lan2MCVlanInPQsH24PerformanceDirTxOcts
         Counter64,
      pr1645v2Lan2MCVlanInPQsH24PerformanceQdOcts
         Counter64,
      pr1645v2Lan2MCVlanInPQsH24PerformanceDropOcts
         Counter64,
      pr1645v2Lan2MCVlanInPQsH24PerformanceRDropOcts
         Counter64,
      pr1645v2Lan2MCVlanInPQsH24PerformanceCirTxOcts
         Counter64,
      pr1645v2Lan2MCVlanInPQsH24PerformanceEirTxOcts
         Counter64,
      pr1645v2Lan2MCVlanInPQsH24PerformanceViolTxOcts
         Counter64,
      pr1645v2Lan2MCVlanInPQsH24PerformanceBandwidth
         Integer32
      }

pr1645v2Lan2MCVlanInPQsH24PerformanceTableIx OBJECT-TYPE
   SYNTAX      TableIndex
   MAX-ACCESS  not-accessible
   STATUS      current
   DESCRIPTION
      ""
   ::= {pr1645v2Lan2MCVlanInPQsH24PerformanceEntry 11}

pr1645v2Lan2MCVlanInPQsH24PerformanceSysUpTime OBJECT-TYPE
   SYNTAX      TimeTicks
   MAX-ACCESS  read-only
   STATUS      current
   DESCRIPTION
      "Path: ethernet2.performance.vlan.inPriorityQueues.h24Performance.sysUpTime

       Time in centi-second."
   ::= {pr1645v2Lan2MCVlanInPQsH24PerformanceEntry 16777216}

pr1645v2Lan2MCVlanInPQsH24PerformanceTotPkts OBJECT-TYPE
   SYNTAX      Counter64
   MAX-ACCESS  read-only
   STATUS      current
   DESCRIPTION
      "Path: ethernet2.performance.vlan.inPriorityQueues.h24Performance.totalPkts

       64 bit unsigned wrappable counter."
   ::= {pr1645v2Lan2MCVlanInPQsH24PerformanceEntry 234881024}

pr1645v2Lan2MCVlanInPQsH24PerformanceDirTxPkts OBJECT-TYPE
   SYNTAX      Counter64
   MAX-ACCESS  read-only
   STATUS      current
   DESCRIPTION
      "Path: ethernet2.performance.vlan.inPriorityQueues.h24Performance.directTxPkts

       64 bit unsigned wrappable counter."
   ::= {pr1645v2Lan2MCVlanInPQsH24PerformanceEntry 33554432}

pr1645v2Lan2MCVlanInPQsH24PerformanceQdPkts OBJECT-TYPE
   SYNTAX      Counter64
   MAX-ACCESS  read-only
   STATUS      current
   DESCRIPTION
      "Path: ethernet2.performance.vlan.inPriorityQueues.h24Performance.queuedPkts

       64 bit unsigned wrappable counter."
   ::= {pr1645v2Lan2MCVlanInPQsH24PerformanceEntry 50331648}

pr1645v2Lan2MCVlanInPQsH24PerformanceDropPkts OBJECT-TYPE
   SYNTAX      Counter64
   MAX-ACCESS  read-only
   STATUS      current
   DESCRIPTION
      "Path: ethernet2.performance.vlan.inPriorityQueues.h24Performance.droppedPkts

       64 bit unsigned wrappable counter."
   ::= {pr1645v2Lan2MCVlanInPQsH24PerformanceEntry 67108864}

pr1645v2Lan2MCVlanInPQsH24PerformanceRDropPkts OBJECT-TYPE
   SYNTAX      Counter64
   MAX-ACCESS  read-only
   STATUS      current
   DESCRIPTION
      "Path: ethernet2.performance.vlan.inPriorityQueues.h24Performance.redDroppedPkts

       64 bit unsigned wrappable counter."
   ::= {pr1645v2Lan2MCVlanInPQsH24PerformanceEntry 201326592}

pr1645v2Lan2MCVlanInPQsH24PerformanceCirTxPkts OBJECT-TYPE
   SYNTAX      Counter64
   MAX-ACCESS  read-only
   STATUS      current
   DESCRIPTION
      "Path: ethernet2.performance.vlan.inPriorityQueues.h24Performance.cirTxPkts

       64 bit unsigned wrappable counter."
   ::= {pr1645v2Lan2MCVlanInPQsH24PerformanceEntry 83886080}

pr1645v2Lan2MCVlanInPQsH24PerformanceEirTxPkts OBJECT-TYPE
   SYNTAX      Counter64
   MAX-ACCESS  read-only
   STATUS      current
   DESCRIPTION
      "Path: ethernet2.performance.vlan.inPriorityQueues.h24Performance.eirTxPkts

       64 bit unsigned wrappable counter."
   ::= {pr1645v2Lan2MCVlanInPQsH24PerformanceEntry 100663296}

pr1645v2Lan2MCVlanInPQsH24PerformanceViolTxPkts OBJECT-TYPE
   SYNTAX      Counter64
   MAX-ACCESS  read-only
   STATUS      current
   DESCRIPTION
      "Path: ethernet2.performance.vlan.inPriorityQueues.h24Performance.violateTxPkts

       64 bit unsigned wrappable counter."
   ::= {pr1645v2Lan2MCVlanInPQsH24PerformanceEntry 301989888}

pr1645v2Lan2MCVlanInPQsH24PerformanceTotOcts OBJECT-TYPE
   SYNTAX      Counter64
   MAX-ACCESS  read-only
   STATUS      current
   DESCRIPTION
      "Path: ethernet2.performance.vlan.inPriorityQueues.h24Performance.totalOctets

       64 bit unsigned wrappable counter."
   ::= {pr1645v2Lan2MCVlanInPQsH24PerformanceEntry 251658240}

pr1645v2Lan2MCVlanInPQsH24PerformanceDirTxOcts OBJECT-TYPE
   SYNTAX      Counter64
   MAX-ACCESS  read-only
   STATUS      current
   DESCRIPTION
      "Path: ethernet2.performance.vlan.inPriorityQueues.h24Performance.directTxOctets

       64 bit unsigned wrappable counter."
   ::= {pr1645v2Lan2MCVlanInPQsH24PerformanceEntry 117440512}

pr1645v2Lan2MCVlanInPQsH24PerformanceQdOcts OBJECT-TYPE
   SYNTAX      Counter64
   MAX-ACCESS  read-only
   STATUS      current
   DESCRIPTION
      "Path: ethernet2.performance.vlan.inPriorityQueues.h24Performance.queuedOctets

       64 bit unsigned wrappable counter."
   ::= {pr1645v2Lan2MCVlanInPQsH24PerformanceEntry 134217728}

pr1645v2Lan2MCVlanInPQsH24PerformanceDropOcts OBJECT-TYPE
   SYNTAX      Counter64
   MAX-ACCESS  read-only
   STATUS      current
   DESCRIPTION
      "Path: ethernet2.performance.vlan.inPriorityQueues.h24Performance.droppedOctets

       64 bit unsigned wrappable counter."
   ::= {pr1645v2Lan2MCVlanInPQsH24PerformanceEntry 150994944}

pr1645v2Lan2MCVlanInPQsH24PerformanceRDropOcts OBJECT-TYPE
   SYNTAX      Counter64
   MAX-ACCESS  read-only
   STATUS      current
   DESCRIPTION
      "Path: ethernet2.performance.vlan.inPriorityQueues.h24Performance.redDroppedOctets

       64 bit unsigned wrappable counter."
   ::= {pr1645v2Lan2MCVlanInPQsH24PerformanceEntry 218103808}

pr1645v2Lan2MCVlanInPQsH24PerformanceCirTxOcts OBJECT-TYPE
   SYNTAX      Counter64
   MAX-ACCESS  read-only
   STATUS      current
   DESCRIPTION
      "Path: ethernet2.performance.vlan.inPriorityQueues.h24Performance.cirTxOctets

       64 bit unsigned wrappable counter."
   ::= {pr1645v2Lan2MCVlanInPQsH24PerformanceEntry 167772160}

pr1645v2Lan2MCVlanInPQsH24PerformanceEirTxOcts OBJECT-TYPE
   SYNTAX      Counter64
   MAX-ACCESS  read-only
   STATUS      current
   DESCRIPTION
      "Path: ethernet2.performance.vlan.inPriorityQueues.h24Performance.eirTxOctets

       64 bit unsigned wrappable counter."
   ::= {pr1645v2Lan2MCVlanInPQsH24PerformanceEntry 184549376}

pr1645v2Lan2MCVlanInPQsH24PerformanceViolTxOcts OBJECT-TYPE
   SYNTAX      Counter64
   MAX-ACCESS  read-only
   STATUS      current
   DESCRIPTION
      "Path: ethernet2.performance.vlan.inPriorityQueues.h24Performance.violateTxOctets

       64 bit unsigned wrappable counter."
   ::= {pr1645v2Lan2MCVlanInPQsH24PerformanceEntry 318767104}

pr1645v2Lan2MCVlanInPQsH24PerformanceBandwidth OBJECT-TYPE
   SYNTAX      Integer32
   MAX-ACCESS  read-only
   STATUS      current
   DESCRIPTION
      "Path: ethernet2.performance.vlan.inPriorityQueues.h24Performance.bandwidth

       unit name = bps
       formula = 8 * ; 8 /"
   ::= {pr1645v2Lan2MCVlanInPQsH24PerformanceEntry 268435456}

pr1645v2Lan2MCVlanInPQsD7Performance OBJECT-TYPE
   SYNTAX      SEQUENCE OF Pr1645v2Lan2MCVlanInPQsD7PerformanceEntry
   MAX-ACCESS  not-accessible
   STATUS      current
   DESCRIPTION
      ""
   ::= {pr1645v2Lan2MCVlan 101122048}

pr1645v2Lan2MCVlanInPQsD7PerformanceEntry OBJECT-TYPE
   SYNTAX      Pr1645v2Lan2MCVlanInPQsD7PerformanceEntry
   MAX-ACCESS  not-accessible
   STATUS      current
   DESCRIPTION
      ""
   INDEX      { pr1645v2Lan2MCVlanTableIx,
                pr1645v2Lan2MCVlanInPQsTableIx,
                pr1645v2Lan2MCVlanInPQsD7PerformanceTableIx }
   ::= {pr1645v2Lan2MCVlanInPQsD7Performance 1}

Pr1645v2Lan2MCVlanInPQsD7PerformanceEntry ::=
   SEQUENCE
      {
      pr1645v2Lan2MCVlanInPQsD7PerformanceTableIx
         TableIndex,
      pr1645v2Lan2MCVlanInPQsD7PerformanceSysUpTime
         TimeTicks,
      pr1645v2Lan2MCVlanInPQsD7PerformanceTotPkts
         Counter64,
      pr1645v2Lan2MCVlanInPQsD7PerformanceDirTxPkts
         Counter64,
      pr1645v2Lan2MCVlanInPQsD7PerformanceQdPkts
         Counter64,
      pr1645v2Lan2MCVlanInPQsD7PerformanceDropPkts
         Counter64,
      pr1645v2Lan2MCVlanInPQsD7PerformanceRDropPkts
         Counter64,
      pr1645v2Lan2MCVlanInPQsD7PerformanceCirTxPkts
         Counter64,
      pr1645v2Lan2MCVlanInPQsD7PerformanceEirTxPkts
         Counter64,
      pr1645v2Lan2MCVlanInPQsD7PerformanceViolTxPkts
         Counter64,
      pr1645v2Lan2MCVlanInPQsD7PerformanceTotOcts
         Counter64,
      pr1645v2Lan2MCVlanInPQsD7PerformanceDirTxOcts
         Counter64,
      pr1645v2Lan2MCVlanInPQsD7PerformanceQdOcts
         Counter64,
      pr1645v2Lan2MCVlanInPQsD7PerformanceDropOcts
         Counter64,
      pr1645v2Lan2MCVlanInPQsD7PerformanceRDropOcts
         Counter64,
      pr1645v2Lan2MCVlanInPQsD7PerformanceCirTxOcts
         Counter64,
      pr1645v2Lan2MCVlanInPQsD7PerformanceEirTxOcts
         Counter64,
      pr1645v2Lan2MCVlanInPQsD7PerformanceViolTxOcts
         Counter64,
      pr1645v2Lan2MCVlanInPQsD7PerformanceBandwidth
         Integer32
      }

pr1645v2Lan2MCVlanInPQsD7PerformanceTableIx OBJECT-TYPE
   SYNTAX      TableIndex
   MAX-ACCESS  not-accessible
   STATUS      current
   DESCRIPTION
      ""
   ::= {pr1645v2Lan2MCVlanInPQsD7PerformanceEntry 11}

pr1645v2Lan2MCVlanInPQsD7PerformanceSysUpTime OBJECT-TYPE
   SYNTAX      TimeTicks
   MAX-ACCESS  read-only
   STATUS      current
   DESCRIPTION
      "Path: ethernet2.performance.vlan.inPriorityQueues.d7Performance.sysUpTime

       Time in centi-second."
   ::= {pr1645v2Lan2MCVlanInPQsD7PerformanceEntry 16777216}

pr1645v2Lan2MCVlanInPQsD7PerformanceTotPkts OBJECT-TYPE
   SYNTAX      Counter64
   MAX-ACCESS  read-only
   STATUS      current
   DESCRIPTION
      "Path: ethernet2.performance.vlan.inPriorityQueues.d7Performance.totalPkts

       64 bit unsigned wrappable counter."
   ::= {pr1645v2Lan2MCVlanInPQsD7PerformanceEntry 234881024}

pr1645v2Lan2MCVlanInPQsD7PerformanceDirTxPkts OBJECT-TYPE
   SYNTAX      Counter64
   MAX-ACCESS  read-only
   STATUS      current
   DESCRIPTION
      "Path: ethernet2.performance.vlan.inPriorityQueues.d7Performance.directTxPkts

       64 bit unsigned wrappable counter."
   ::= {pr1645v2Lan2MCVlanInPQsD7PerformanceEntry 33554432}

pr1645v2Lan2MCVlanInPQsD7PerformanceQdPkts OBJECT-TYPE
   SYNTAX      Counter64
   MAX-ACCESS  read-only
   STATUS      current
   DESCRIPTION
      "Path: ethernet2.performance.vlan.inPriorityQueues.d7Performance.queuedPkts

       64 bit unsigned wrappable counter."
   ::= {pr1645v2Lan2MCVlanInPQsD7PerformanceEntry 50331648}

pr1645v2Lan2MCVlanInPQsD7PerformanceDropPkts OBJECT-TYPE
   SYNTAX      Counter64
   MAX-ACCESS  read-only
   STATUS      current
   DESCRIPTION
      "Path: ethernet2.performance.vlan.inPriorityQueues.d7Performance.droppedPkts

       64 bit unsigned wrappable counter."
   ::= {pr1645v2Lan2MCVlanInPQsD7PerformanceEntry 67108864}

pr1645v2Lan2MCVlanInPQsD7PerformanceRDropPkts OBJECT-TYPE
   SYNTAX      Counter64
   MAX-ACCESS  read-only
   STATUS      current
   DESCRIPTION
      "Path: ethernet2.performance.vlan.inPriorityQueues.d7Performance.redDroppedPkts

       64 bit unsigned wrappable counter."
   ::= {pr1645v2Lan2MCVlanInPQsD7PerformanceEntry 201326592}

pr1645v2Lan2MCVlanInPQsD7PerformanceCirTxPkts OBJECT-TYPE
   SYNTAX      Counter64
   MAX-ACCESS  read-only
   STATUS      current
   DESCRIPTION
      "Path: ethernet2.performance.vlan.inPriorityQueues.d7Performance.cirTxPkts

       64 bit unsigned wrappable counter."
   ::= {pr1645v2Lan2MCVlanInPQsD7PerformanceEntry 83886080}

pr1645v2Lan2MCVlanInPQsD7PerformanceEirTxPkts OBJECT-TYPE
   SYNTAX      Counter64
   MAX-ACCESS  read-only
   STATUS      current
   DESCRIPTION
      "Path: ethernet2.performance.vlan.inPriorityQueues.d7Performance.eirTxPkts

       64 bit unsigned wrappable counter."
   ::= {pr1645v2Lan2MCVlanInPQsD7PerformanceEntry 100663296}

pr1645v2Lan2MCVlanInPQsD7PerformanceViolTxPkts OBJECT-TYPE
   SYNTAX      Counter64
   MAX-ACCESS  read-only
   STATUS      current
   DESCRIPTION
      "Path: ethernet2.performance.vlan.inPriorityQueues.d7Performance.violateTxPkts

       64 bit unsigned wrappable counter."
   ::= {pr1645v2Lan2MCVlanInPQsD7PerformanceEntry 301989888}

pr1645v2Lan2MCVlanInPQsD7PerformanceTotOcts OBJECT-TYPE
   SYNTAX      Counter64
   MAX-ACCESS  read-only
   STATUS      current
   DESCRIPTION
      "Path: ethernet2.performance.vlan.inPriorityQueues.d7Performance.totalOctets

       64 bit unsigned wrappable counter."
   ::= {pr1645v2Lan2MCVlanInPQsD7PerformanceEntry 251658240}

pr1645v2Lan2MCVlanInPQsD7PerformanceDirTxOcts OBJECT-TYPE
   SYNTAX      Counter64
   MAX-ACCESS  read-only
   STATUS      current
   DESCRIPTION
      "Path: ethernet2.performance.vlan.inPriorityQueues.d7Performance.directTxOctets

       64 bit unsigned wrappable counter."
   ::= {pr1645v2Lan2MCVlanInPQsD7PerformanceEntry 117440512}

pr1645v2Lan2MCVlanInPQsD7PerformanceQdOcts OBJECT-TYPE
   SYNTAX      Counter64
   MAX-ACCESS  read-only
   STATUS      current
   DESCRIPTION
      "Path: ethernet2.performance.vlan.inPriorityQueues.d7Performance.queuedOctets

       64 bit unsigned wrappable counter."
   ::= {pr1645v2Lan2MCVlanInPQsD7PerformanceEntry 134217728}

pr1645v2Lan2MCVlanInPQsD7PerformanceDropOcts OBJECT-TYPE
   SYNTAX      Counter64
   MAX-ACCESS  read-only
   STATUS      current
   DESCRIPTION
      "Path: ethernet2.performance.vlan.inPriorityQueues.d7Performance.droppedOctets

       64 bit unsigned wrappable counter."
   ::= {pr1645v2Lan2MCVlanInPQsD7PerformanceEntry 150994944}

pr1645v2Lan2MCVlanInPQsD7PerformanceRDropOcts OBJECT-TYPE
   SYNTAX      Counter64
   MAX-ACCESS  read-only
   STATUS      current
   DESCRIPTION
      "Path: ethernet2.performance.vlan.inPriorityQueues.d7Performance.redDroppedOctets

       64 bit unsigned wrappable counter."
   ::= {pr1645v2Lan2MCVlanInPQsD7PerformanceEntry 218103808}

pr1645v2Lan2MCVlanInPQsD7PerformanceCirTxOcts OBJECT-TYPE
   SYNTAX      Counter64
   MAX-ACCESS  read-only
   STATUS      current
   DESCRIPTION
      "Path: ethernet2.performance.vlan.inPriorityQueues.d7Performance.cirTxOctets

       64 bit unsigned wrappable counter."
   ::= {pr1645v2Lan2MCVlanInPQsD7PerformanceEntry 167772160}

pr1645v2Lan2MCVlanInPQsD7PerformanceEirTxOcts OBJECT-TYPE
   SYNTAX      Counter64
   MAX-ACCESS  read-only
   STATUS      current
   DESCRIPTION
      "Path: ethernet2.performance.vlan.inPriorityQueues.d7Performance.eirTxOctets

       64 bit unsigned wrappable counter."
   ::= {pr1645v2Lan2MCVlanInPQsD7PerformanceEntry 184549376}

pr1645v2Lan2MCVlanInPQsD7PerformanceViolTxOcts OBJECT-TYPE
   SYNTAX      Counter64
   MAX-ACCESS  read-only
   STATUS      current
   DESCRIPTION
      "Path: ethernet2.performance.vlan.inPriorityQueues.d7Performance.violateTxOctets

       64 bit unsigned wrappable counter."
   ::= {pr1645v2Lan2MCVlanInPQsD7PerformanceEntry 318767104}

pr1645v2Lan2MCVlanInPQsD7PerformanceBandwidth OBJECT-TYPE
   SYNTAX      Integer32
   MAX-ACCESS  read-only
   STATUS      current
   DESCRIPTION
      "Path: ethernet2.performance.vlan.inPriorityQueues.d7Performance.bandwidth

       unit name = bps
       formula = 8 * ; 8 /"
   ::= {pr1645v2Lan2MCVlanInPQsD7PerformanceEntry 268435456}

pr1645v2Lan2MCVlanOutPQs OBJECT-TYPE
   SYNTAX      SEQUENCE OF Pr1645v2Lan2MCVlanOutPQsEntry
   MAX-ACCESS  not-accessible
   STATUS      current
   DESCRIPTION
      ""
   ::= {pr1645v2Lan2MCVlan 83886080}

pr1645v2Lan2MCVlanOutPQsEntry OBJECT-TYPE
   SYNTAX      Pr1645v2Lan2MCVlanOutPQsEntry
   MAX-ACCESS  not-accessible
   STATUS      current
   DESCRIPTION
      ""
   INDEX      { pr1645v2Lan2MCVlanTableIx,
                pr1645v2Lan2MCVlanOutPQsTableIx }
   ::= {pr1645v2Lan2MCVlanOutPQs 1}

Pr1645v2Lan2MCVlanOutPQsEntry ::=
   SEQUENCE
      {
      pr1645v2Lan2MCVlanOutPQsTableIx
         TableIndex,
      pr1645v2Lan2MCVlanOutPQsName
         INTEGER,
      pr1645v2Lan2MCVlanOutPQsLength
         Integer32,
      pr1645v2Lan2MCVlanOutPQsOctetLength
         Integer32,
      pr1645v2Lan2MCVlanOutPQsRedLength
         Integer32,
      pr1645v2Lan2MCVlanOutPQsPacketsTotal
         Counter64,
      pr1645v2Lan2MCVlanOutPQsPacketsDirectTx
         Counter64,
      pr1645v2Lan2MCVlanOutPQsPacketsQueued
         Counter64,
      pr1645v2Lan2MCVlanOutPQsPacketsDropped
         Counter64,
      pr1645v2Lan2MCVlanOutPQsPacketsRedDropped
         Counter64,
      pr1645v2Lan2MCVlanOutPQsPacketsCirTx
         Counter64,
      pr1645v2Lan2MCVlanOutPQsPacketsEirTx
         Counter64,
      pr1645v2Lan2MCVlanOutPQsPacketsViolateTx
         Counter64,
      pr1645v2Lan2MCVlanOutPQsOctetsTotal
         Counter64,
      pr1645v2Lan2MCVlanOutPQsOctetsDirectTx
         Counter64,
      pr1645v2Lan2MCVlanOutPQsOctetsQueued
         Counter64,
      pr1645v2Lan2MCVlanOutPQsOctetsDropped
         Counter64,
      pr1645v2Lan2MCVlanOutPQsOctetsRedDropped
         Counter64,
      pr1645v2Lan2MCVlanOutPQsOctetsCirTx
         Counter64,
      pr1645v2Lan2MCVlanOutPQsOctetsEirTx
         Counter64,
      pr1645v2Lan2MCVlanOutPQsOctetsViolateTx
         Counter64,
      pr1645v2Lan2MCVlanOutPQsOctetsBandwidth15sec
         Integer32,
      pr1645v2Lan2MCVlanOutPQsOctetsBandwidth30sec
         Integer32,
      pr1645v2Lan2MCVlanOutPQsOctetsBandwidth1min
         Integer32,
      pr1645v2Lan2MCVlanOutPQsOctetsBandwidth2min
         Integer32,
      pr1645v2Lan2MCVlanOutPQsOctetsBandwidth5min
         Integer32
      }

pr1645v2Lan2MCVlanOutPQsTableIx OBJECT-TYPE
   SYNTAX      TableIndex
   MAX-ACCESS  not-accessible
   STATUS      current
   DESCRIPTION
      ""
   ::= {pr1645v2Lan2MCVlanOutPQsEntry 11}

pr1645v2Lan2MCVlanOutPQsName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.vlan.outPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2MCVlanOutPQsEntry 16777216}

pr1645v2Lan2MCVlanOutPQsLength OBJECT-TYPE
   SYNTAX      Integer32
   MAX-ACCESS  read-only
   STATUS      current
   DESCRIPTION
      "Path: ethernet2.performance.vlan.outPriorityQueues.length"
   ::= {pr1645v2Lan2MCVlanOutPQsEntry 33554432}

pr1645v2Lan2MCVlanOutPQsOctetLength OBJECT-TYPE
   SYNTAX      Integer32
   MAX-ACCESS  read-only
   STATUS      current
   DESCRIPTION
      "Path: ethernet2.performance.vlan.outPriorityQueues.octetLength"
   ::= {pr1645v2Lan2MCVlanOutPQsEntry 150994944}

pr1645v2Lan2MCVlanOutPQsRedLength OBJECT-TYPE
   SYNTAX      Integer32
   MAX-ACCESS  read-only
   STATUS      current
   DESCRIPTION
      "Path: ethernet2.performance.vlan.outPriorityQueues.redLength"
   ::= {pr1645v2Lan2MCVlanOutPQsEntry 134217728}

pr1645v2Lan2MCVlanOutPQsPacketsTotal OBJECT-TYPE
   SYNTAX      Counter64
   MAX-ACCESS  read-only
   STATUS      current
   DESCRIPTION
      "Path: ethernet2.performance.vlan.outPriorityQueues.packets.total

       64 bit unsigned wrappable counter."
   ::= {pr1645v2Lan2MCVlanOutPQsEntry 50790400}

pr1645v2Lan2MCVlanOutPQsPacketsDirectTx OBJECT-TYPE
   SYNTAX      Counter64
   MAX-ACCESS  read-only
   STATUS      current
   DESCRIPTION
      "Path: ethernet2.performance.vlan.outPriorityQueues.packets.directTx

       64 bit unsigned wrappable counter."
   ::= {pr1645v2Lan2MCVlanOutPQsEntry 50397184}

pr1645v2Lan2MCVlanOutPQsPacketsQueued OBJECT-TYPE
   SYNTAX      Counter64
   MAX-ACCESS  read-only
   STATUS      current
   DESCRIPTION
      "Path: ethernet2.performance.vlan.outPriorityQueues.packets.queued

       64 bit unsigned wrappable counter."
   ::= {pr1645v2Lan2MCVlanOutPQsEntry 50462720}

pr1645v2Lan2MCVlanOutPQsPacketsDropped OBJECT-TYPE
   SYNTAX      Counter64
   MAX-ACCESS  read-only
   STATUS      current
   DESCRIPTION
      "Path: ethernet2.performance.vlan.outPriorityQueues.packets.dropped

       64 bit unsigned wrappable counter."
   ::= {pr1645v2Lan2MCVlanOutPQsEntry 50528256}

pr1645v2Lan2MCVlanOutPQsPacketsRedDropped OBJECT-TYPE
   SYNTAX      Counter64
   MAX-ACCESS  read-only
   STATUS      current
   DESCRIPTION
      "Path: ethernet2.performance.vlan.outPriorityQueues.packets.redDropped

       64 bit unsigned wrappable counter."
   ::= {pr1645v2Lan2MCVlanOutPQsEntry 50724864}

pr1645v2Lan2MCVlanOutPQsPacketsCirTx OBJECT-TYPE
   SYNTAX      Counter64
   MAX-ACCESS  read-only
   STATUS      current
   DESCRIPTION
      "Path: ethernet2.performance.vlan.outPriorityQueues.packets.cirTx

       64 bit unsigned wrappable counter."
   ::= {pr1645v2Lan2MCVlanOutPQsEntry 50593792}

pr1645v2Lan2MCVlanOutPQsPacketsEirTx OBJECT-TYPE
   SYNTAX      Counter64
   MAX-ACCESS  read-only
   STATUS      current
   DESCRIPTION
      "Path: ethernet2.performance.vlan.outPriorityQueues.packets.eirTx

       64 bit unsigned wrappable counter."
   ::= {pr1645v2Lan2MCVlanOutPQsEntry 50659328}

pr1645v2Lan2MCVlanOutPQsPacketsViolateTx OBJECT-TYPE
   SYNTAX      Counter64
   MAX-ACCESS  read-only
   STATUS      current
   DESCRIPTION
      "Path: ethernet2.performance.vlan.outPriorityQueues.packets.violateTx

       64 bit unsigned wrappable counter."
   ::= {pr1645v2Lan2MCVlanOutPQsEntry 50855936}

pr1645v2Lan2MCVlanOutPQsOctetsTotal OBJECT-TYPE
   SYNTAX      Counter64
   MAX-ACCESS  read-only
   STATUS      current
   DESCRIPTION
      "Path: ethernet2.performance.vlan.outPriorityQueues.octets.total

       64 bit unsigned wrappable counter."
   ::= {pr1645v2Lan2MCVlanOutPQsEntry 67567616}

pr1645v2Lan2MCVlanOutPQsOctetsDirectTx OBJECT-TYPE
   SYNTAX      Counter64
   MAX-ACCESS  read-only
   STATUS      current
   DESCRIPTION
      "Path: ethernet2.performance.vlan.outPriorityQueues.octets.directTx

       64 bit unsigned wrappable counter."
   ::= {pr1645v2Lan2MCVlanOutPQsEntry 67174400}

pr1645v2Lan2MCVlanOutPQsOctetsQueued OBJECT-TYPE
   SYNTAX      Counter64
   MAX-ACCESS  read-only
   STATUS      current
   DESCRIPTION
      "Path: ethernet2.performance.vlan.outPriorityQueues.octets.queued

       64 bit unsigned wrappable counter."
   ::= {pr1645v2Lan2MCVlanOutPQsEntry 67239936}

pr1645v2Lan2MCVlanOutPQsOctetsDropped OBJECT-TYPE
   SYNTAX      Counter64
   MAX-ACCESS  read-only
   STATUS      current
   DESCRIPTION
      "Path: ethernet2.performance.vlan.outPriorityQueues.octets.dropped

       64 bit unsigned wrappable counter."
   ::= {pr1645v2Lan2MCVlanOutPQsEntry 67305472}

pr1645v2Lan2MCVlanOutPQsOctetsRedDropped OBJECT-TYPE
   SYNTAX      Counter64
   MAX-ACCESS  read-only
   STATUS      current
   DESCRIPTION
      "Path: ethernet2.performance.vlan.outPriorityQueues.octets.redDropped

       64 bit unsigned wrappable counter."
   ::= {pr1645v2Lan2MCVlanOutPQsEntry 67502080}

pr1645v2Lan2MCVlanOutPQsOctetsCirTx OBJECT-TYPE
   SYNTAX      Counter64
   MAX-ACCESS  read-only
   STATUS      current
   DESCRIPTION
      "Path: ethernet2.performance.vlan.outPriorityQueues.octets.cirTx

       64 bit unsigned wrappable counter."
   ::= {pr1645v2Lan2MCVlanOutPQsEntry 67371008}

pr1645v2Lan2MCVlanOutPQsOctetsEirTx OBJECT-TYPE
   SYNTAX      Counter64
   MAX-ACCESS  read-only
   STATUS      current
   DESCRIPTION
      "Path: ethernet2.performance.vlan.outPriorityQueues.octets.eirTx

       64 bit unsigned wrappable counter."
   ::= {pr1645v2Lan2MCVlanOutPQsEntry 67436544}

pr1645v2Lan2MCVlanOutPQsOctetsViolateTx OBJECT-TYPE
   SYNTAX      Counter64
   MAX-ACCESS  read-only
   STATUS      current
   DESCRIPTION
      "Path: ethernet2.performance.vlan.outPriorityQueues.octets.violateTx

       64 bit unsigned wrappable counter."
   ::= {pr1645v2Lan2MCVlanOutPQsEntry 67633152}

pr1645v2Lan2MCVlanOutPQsOctetsBandwidth15sec OBJECT-TYPE
   SYNTAX      Integer32
   MAX-ACCESS  read-only
   STATUS      current
   DESCRIPTION
      "Path: ethernet2.performance.vlan.outPriorityQueues.octets.bandwidth.15sec

       unit name = bps
       formula = 8 * ; 8 /"
   ::= {pr1645v2Lan2MCVlanOutPQsEntry 70386944}

pr1645v2Lan2MCVlanOutPQsOctetsBandwidth30sec OBJECT-TYPE
   SYNTAX      Integer32
   MAX-ACCESS  read-only
   STATUS      current
   DESCRIPTION
      "Path: ethernet2.performance.vlan.outPriorityQueues.octets.bandwidth.30sec

       unit name = bps
       formula = 8 * ; 8 /"
   ::= {pr1645v2Lan2MCVlanOutPQsEntry 70388224}

pr1645v2Lan2MCVlanOutPQsOctetsBandwidth1min OBJECT-TYPE
   SYNTAX      Integer32
   MAX-ACCESS  read-only
   STATUS      current
   DESCRIPTION
      "Path: ethernet2.performance.vlan.outPriorityQueues.octets.bandwidth.1min

       unit name = bps
       formula = 8 * ; 8 /"
   ::= {pr1645v2Lan2MCVlanOutPQsEntry 70390784}

pr1645v2Lan2MCVlanOutPQsOctetsBandwidth2min OBJECT-TYPE
   SYNTAX      Integer32
   MAX-ACCESS  read-only
   STATUS      current
   DESCRIPTION
      "Path: ethernet2.performance.vlan.outPriorityQueues.octets.bandwidth.2min

       unit name = bps
       formula = 8 * ; 8 /"
   ::= {pr1645v2Lan2MCVlanOutPQsEntry 70395904}

pr1645v2Lan2MCVlanOutPQsOctetsBandwidth5min OBJECT-TYPE
   SYNTAX      Integer32
   MAX-ACCESS  read-only
   STATUS      current
   DESCRIPTION
      "Path: ethernet2.performance.vlan.outPriorityQueues.octets.bandwidth.5min

       unit name = bps
       formula = 8 * ; 8 /"
   ::= {pr1645v2Lan2MCVlanOutPQsEntry 70411264}

pr1645v2Lan2MCVlanOutPQsH2Performance OBJECT-TYPE
   SYNTAX      SEQUENCE OF Pr1645v2Lan2MCVlanOutPQsH2PerformanceEntry
   MAX-ACCESS  not-accessible
   STATUS      current
   DESCRIPTION
      ""
   ::= {pr1645v2Lan2MCVlan 84213760}

pr1645v2Lan2MCVlanOutPQsH2PerformanceEntry OBJECT-TYPE
   SYNTAX      Pr1645v2Lan2MCVlanOutPQsH2PerformanceEntry
   MAX-ACCESS  not-accessible
   STATUS      current
   DESCRIPTION
      ""
   INDEX      { pr1645v2Lan2MCVlanTableIx,
                pr1645v2Lan2MCVlanOutPQsTableIx,
                pr1645v2Lan2MCVlanOutPQsH2PerformanceTableIx }
   ::= {pr1645v2Lan2MCVlanOutPQsH2Performance 1}

Pr1645v2Lan2MCVlanOutPQsH2PerformanceEntry ::=
   SEQUENCE
      {
      pr1645v2Lan2MCVlanOutPQsH2PerformanceTableIx
         TableIndex,
      pr1645v2Lan2MCVlanOutPQsH2PerformanceSysUpTime
         TimeTicks,
      pr1645v2Lan2MCVlanOutPQsH2PerformanceTotPkts
         Counter64,
      pr1645v2Lan2MCVlanOutPQsH2PerformanceDirTxPkts
         Counter64,
      pr1645v2Lan2MCVlanOutPQsH2PerformanceQdPkts
         Counter64,
      pr1645v2Lan2MCVlanOutPQsH2PerformanceDropPkts
         Counter64,
      pr1645v2Lan2MCVlanOutPQsH2PerformanceRDropPkts
         Counter64,
      pr1645v2Lan2MCVlanOutPQsH2PerformanceCirTxPkts
         Counter64,
      pr1645v2Lan2MCVlanOutPQsH2PerformanceEirTxPkts
         Counter64,
      pr1645v2Lan2MCVlanOutPQsH2PerformanceViolTxPkts
         Counter64,
      pr1645v2Lan2MCVlanOutPQsH2PerformanceTotOcts
         Counter64,
      pr1645v2Lan2MCVlanOutPQsH2PerformanceDirTxOcts
         Counter64,
      pr1645v2Lan2MCVlanOutPQsH2PerformanceQdOcts
         Counter64,
      pr1645v2Lan2MCVlanOutPQsH2PerformanceDropOcts
         Counter64,
      pr1645v2Lan2MCVlanOutPQsH2PerformanceRDropOcts
         Counter64,
      pr1645v2Lan2MCVlanOutPQsH2PerformanceCirTxOcts
         Counter64,
      pr1645v2Lan2MCVlanOutPQsH2PerformanceEirTxOcts
         Counter64,
      pr1645v2Lan2MCVlanOutPQsH2PerformanceViolTxOcts
         Counter64,
      pr1645v2Lan2MCVlanOutPQsH2PerformanceBandwidth
         Integer32
      }

pr1645v2Lan2MCVlanOutPQsH2PerformanceTableIx OBJECT-TYPE
   SYNTAX      TableIndex
   MAX-ACCESS  not-accessible
   STATUS      current
   DESCRIPTION
      ""
   ::= {pr1645v2Lan2MCVlanOutPQsH2PerformanceEntry 11}

pr1645v2Lan2MCVlanOutPQsH2PerformanceSysUpTime OBJECT-TYPE
   SYNTAX      TimeTicks
   MAX-ACCESS  read-only
   STATUS      current
   DESCRIPTION
      "Path: ethernet2.performance.vlan.outPriorityQueues.h2Performance.sysUpTime

       Time in centi-second."
   ::= {pr1645v2Lan2MCVlanOutPQsH2PerformanceEntry 16777216}

pr1645v2Lan2MCVlanOutPQsH2PerformanceTotPkts OBJECT-TYPE
   SYNTAX      Counter64
   MAX-ACCESS  read-only
   STATUS      current
   DESCRIPTION
      "Path: ethernet2.performance.vlan.outPriorityQueues.h2Performance.totalPkts

       64 bit unsigned wrappable counter."
   ::= {pr1645v2Lan2MCVlanOutPQsH2PerformanceEntry 234881024}

pr1645v2Lan2MCVlanOutPQsH2PerformanceDirTxPkts OBJECT-TYPE
   SYNTAX      Counter64
   MAX-ACCESS  read-only
   STATUS      current
   DESCRIPTION
      "Path: ethernet2.performance.vlan.outPriorityQueues.h2Performance.directTxPkts

       64 bit unsigned wrappable counter."
   ::= {pr1645v2Lan2MCVlanOutPQsH2PerformanceEntry 33554432}

pr1645v2Lan2MCVlanOutPQsH2PerformanceQdPkts OBJECT-TYPE
   SYNTAX      Counter64
   MAX-ACCESS  read-only
   STATUS      current
   DESCRIPTION
      "Path: ethernet2.performance.vlan.outPriorityQueues.h2Performance.queuedPkts

       64 bit unsigned wrappable counter."
   ::= {pr1645v2Lan2MCVlanOutPQsH2PerformanceEntry 50331648}

pr1645v2Lan2MCVlanOutPQsH2PerformanceDropPkts OBJECT-TYPE
   SYNTAX      Counter64
   MAX-ACCESS  read-only
   STATUS      current
   DESCRIPTION
      "Path: ethernet2.performance.vlan.outPriorityQueues.h2Performance.droppedPkts

       64 bit unsigned wrappable counter."
   ::= {pr1645v2Lan2MCVlanOutPQsH2PerformanceEntry 67108864}

pr1645v2Lan2MCVlanOutPQsH2PerformanceRDropPkts OBJECT-TYPE
   SYNTAX      Counter64
   MAX-ACCESS  read-only
   STATUS      current
   DESCRIPTION
      "Path: ethernet2.performance.vlan.outPriorityQueues.h2Performance.redDroppedPkts

       64 bit unsigned wrappable counter."
   ::= {pr1645v2Lan2MCVlanOutPQsH2PerformanceEntry 201326592}

pr1645v2Lan2MCVlanOutPQsH2PerformanceCirTxPkts OBJECT-TYPE
   SYNTAX      Counter64
   MAX-ACCESS  read-only
   STATUS      current
   DESCRIPTION
      "Path: ethernet2.performance.vlan.outPriorityQueues.h2Performance.cirTxPkts

       64 bit unsigned wrappable counter."
   ::= {pr1645v2Lan2MCVlanOutPQsH2PerformanceEntry 83886080}

pr1645v2Lan2MCVlanOutPQsH2PerformanceEirTxPkts OBJECT-TYPE
   SYNTAX      Counter64
   MAX-ACCESS  read-only
   STATUS      current
   DESCRIPTION
      "Path: ethernet2.performance.vlan.outPriorityQueues.h2Performance.eirTxPkts

       64 bit unsigned wrappable counter."
   ::= {pr1645v2Lan2MCVlanOutPQsH2PerformanceEntry 100663296}

pr1645v2Lan2MCVlanOutPQsH2PerformanceViolTxPkts OBJECT-TYPE
   SYNTAX      Counter64
   MAX-ACCESS  read-only
   STATUS      current
   DESCRIPTION
      "Path: ethernet2.performance.vlan.outPriorityQueues.h2Performance.violateTxPkts

       64 bit unsigned wrappable counter."
   ::= {pr1645v2Lan2MCVlanOutPQsH2PerformanceEntry 301989888}

pr1645v2Lan2MCVlanOutPQsH2PerformanceTotOcts OBJECT-TYPE
   SYNTAX      Counter64
   MAX-ACCESS  read-only
   STATUS      current
   DESCRIPTION
      "Path: ethernet2.performance.vlan.outPriorityQueues.h2Performance.totalOctets

       64 bit unsigned wrappable counter."
   ::= {pr1645v2Lan2MCVlanOutPQsH2PerformanceEntry 251658240}

pr1645v2Lan2MCVlanOutPQsH2PerformanceDirTxOcts OBJECT-TYPE
   SYNTAX      Counter64
   MAX-ACCESS  read-only
   STATUS      current
   DESCRIPTION
      "Path: ethernet2.performance.vlan.outPriorityQueues.h2Performance.directTxOctets

       64 bit unsigned wrappable counter."
   ::= {pr1645v2Lan2MCVlanOutPQsH2PerformanceEntry 117440512}

pr1645v2Lan2MCVlanOutPQsH2PerformanceQdOcts OBJECT-TYPE
   SYNTAX      Counter64
   MAX-ACCESS  read-only
   STATUS      current
   DESCRIPTION
      "Path: ethernet2.performance.vlan.outPriorityQueues.h2Performance.queuedOctets

       64 bit unsigned wrappable counter."
   ::= {pr1645v2Lan2MCVlanOutPQsH2PerformanceEntry 134217728}

pr1645v2Lan2MCVlanOutPQsH2PerformanceDropOcts OBJECT-TYPE
   SYNTAX      Counter64
   MAX-ACCESS  read-only
   STATUS      current
   DESCRIPTION
      "Path: ethernet2.performance.vlan.outPriorityQueues.h2Performance.droppedOctets

       64 bit unsigned wrappable counter."
   ::= {pr1645v2Lan2MCVlanOutPQsH2PerformanceEntry 150994944}

pr1645v2Lan2MCVlanOutPQsH2PerformanceRDropOcts OBJECT-TYPE
   SYNTAX      Counter64
   MAX-ACCESS  read-only
   STATUS      current
   DESCRIPTION
      "Path: ethernet2.performance.vlan.outPriorityQueues.h2Performance.redDroppedOctets

       64 bit unsigned wrappable counter."
   ::= {pr1645v2Lan2MCVlanOutPQsH2PerformanceEntry 218103808}

pr1645v2Lan2MCVlanOutPQsH2PerformanceCirTxOcts OBJECT-TYPE
   SYNTAX      Counter64
   MAX-ACCESS  read-only
   STATUS      current
   DESCRIPTION
      "Path: ethernet2.performance.vlan.outPriorityQueues.h2Performance.cirTxOctets

       64 bit unsigned wrappable counter."
   ::= {pr1645v2Lan2MCVlanOutPQsH2PerformanceEntry 167772160}

pr1645v2Lan2MCVlanOutPQsH2PerformanceEirTxOcts OBJECT-TYPE
   SYNTAX      Counter64
   MAX-ACCESS  read-only
   STATUS      current
   DESCRIPTION
      "Path: ethernet2.performance.vlan.outPriorityQueues.h2Performance.eirTxOctets

       64 bit unsigned wrappable counter."
   ::= {pr1645v2Lan2MCVlanOutPQsH2PerformanceEntry 184549376}

pr1645v2Lan2MCVlanOutPQsH2PerformanceViolTxOcts OBJECT-TYPE
   SYNTAX      Counter64
   MAX-ACCESS  read-only
   STATUS      current
   DESCRIPTION
      "Path: ethernet2.performance.vlan.outPriorityQueues.h2Performance.violateTxOctets

       64 bit unsigned wrappable counter."
   ::= {pr1645v2Lan2MCVlanOutPQsH2PerformanceEntry 318767104}

pr1645v2Lan2MCVlanOutPQsH2PerformanceBandwidth OBJECT-TYPE
   SYNTAX      Integer32
   MAX-ACCESS  read-only
   STATUS      current
   DESCRIPTION
      "Path: ethernet2.performance.vlan.outPriorityQueues.h2Performance.bandwidth

       unit name = bps
       formula = 8 * ; 8 /"
   ::= {pr1645v2Lan2MCVlanOutPQsH2PerformanceEntry 268435456}

pr1645v2Lan2MCVlanOutPQsH24Performance OBJECT-TYPE
   SYNTAX      SEQUENCE OF Pr1645v2Lan2MCVlanOutPQsH24PerformanceEntry
   MAX-ACCESS  not-accessible
   STATUS      current
   DESCRIPTION
      ""
   ::= {pr1645v2Lan2MCVlan 84279296}

pr1645v2Lan2MCVlanOutPQsH24PerformanceEntry OBJECT-TYPE
   SYNTAX      Pr1645v2Lan2MCVlanOutPQsH24PerformanceEntry
   MAX-ACCESS  not-accessible
   STATUS      current
   DESCRIPTION
      ""
   INDEX      { pr1645v2Lan2MCVlanTableIx,
                pr1645v2Lan2MCVlanOutPQsTableIx,
                pr1645v2Lan2MCVlanOutPQsH24PerformanceTableIx }
   ::= {pr1645v2Lan2MCVlanOutPQsH24Performance 1}

Pr1645v2Lan2MCVlanOutPQsH24PerformanceEntry ::=
   SEQUENCE
      {
      pr1645v2Lan2MCVlanOutPQsH24PerformanceTableIx
         TableIndex,
      pr1645v2Lan2MCVlanOutPQsH24PerformanceSysUpTime
         TimeTicks,
      pr1645v2Lan2MCVlanOutPQsH24PerformanceTotPkts
         Counter64,
      pr1645v2Lan2MCVlanOutPQsH24PerformanceDirTxPkts
         Counter64,
      pr1645v2Lan2MCVlanOutPQsH24PerformanceQdPkts
         Counter64,
      pr1645v2Lan2MCVlanOutPQsH24PerformanceDropPkts
         Counter64,
      pr1645v2Lan2MCVlanOutPQsH24PerformanceRDropPkts
         Counter64,
      pr1645v2Lan2MCVlanOutPQsH24PerformanceCirTxPkts
         Counter64,
      pr1645v2Lan2MCVlanOutPQsH24PerformanceEirTxPkts
         Counter64,
      pr1645v2Lan2MCVlanOutPQsH24PerformanceViolTxPkts
         Counter64,
      pr1645v2Lan2MCVlanOutPQsH24PerformanceTotOcts
         Counter64,
      pr1645v2Lan2MCVlanOutPQsH24PerformanceDirTxOcts
         Counter64,
      pr1645v2Lan2MCVlanOutPQsH24PerformanceQdOcts
         Counter64,
      pr1645v2Lan2MCVlanOutPQsH24PerformanceDropOcts
         Counter64,
      pr1645v2Lan2MCVlanOutPQsH24PerformanceRDropOcts
         Counter64,
      pr1645v2Lan2MCVlanOutPQsH24PerformanceCirTxOcts
         Counter64,
      pr1645v2Lan2MCVlanOutPQsH24PerformanceEirTxOcts
         Counter64,
      pr1645v2Lan2MCVlanOutPQsH24PerformanceViolTxOcts
         Counter64,
      pr1645v2Lan2MCVlanOutPQsH24PerformanceBandwidth
         Integer32
      }

pr1645v2Lan2MCVlanOutPQsH24PerformanceTableIx OBJECT-TYPE
   SYNTAX      TableIndex
   MAX-ACCESS  not-accessible
   STATUS      current
   DESCRIPTION
      ""
   ::= {pr1645v2Lan2MCVlanOutPQsH24PerformanceEntry 11}

pr1645v2Lan2MCVlanOutPQsH24PerformanceSysUpTime OBJECT-TYPE
   SYNTAX      TimeTicks
   MAX-ACCESS  read-only
   STATUS      current
   DESCRIPTION
      "Path: ethernet2.performance.vlan.outPriorityQueues.h24Performance.sysUpTime

       Time in centi-second."
   ::= {pr1645v2Lan2MCVlanOutPQsH24PerformanceEntry 16777216}

pr1645v2Lan2MCVlanOutPQsH24PerformanceTotPkts OBJECT-TYPE
   SYNTAX      Counter64
   MAX-ACCESS  read-only
   STATUS      current
   DESCRIPTION
      "Path: ethernet2.performance.vlan.outPriorityQueues.h24Performance.totalPkts

       64 bit unsigned wrappable counter."
   ::= {pr1645v2Lan2MCVlanOutPQsH24PerformanceEntry 234881024}

pr1645v2Lan2MCVlanOutPQsH24PerformanceDirTxPkts OBJECT-TYPE
   SYNTAX      Counter64
   MAX-ACCESS  read-only
   STATUS      current
   DESCRIPTION
      "Path: ethernet2.performance.vlan.outPriorityQueues.h24Performance.directTxPkts

       64 bit unsigned wrappable counter."
   ::= {pr1645v2Lan2MCVlanOutPQsH24PerformanceEntry 33554432}

pr1645v2Lan2MCVlanOutPQsH24PerformanceQdPkts OBJECT-TYPE
   SYNTAX      Counter64
   MAX-ACCESS  read-only
   STATUS      current
   DESCRIPTION
      "Path: ethernet2.performance.vlan.outPriorityQueues.h24Performance.queuedPkts

       64 bit unsigned wrappable counter."
   ::= {pr1645v2Lan2MCVlanOutPQsH24PerformanceEntry 50331648}

pr1645v2Lan2MCVlanOutPQsH24PerformanceDropPkts OBJECT-TYPE
   SYNTAX      Counter64
   MAX-ACCESS  read-only
   STATUS      current
   DESCRIPTION
      "Path: ethernet2.performance.vlan.outPriorityQueues.h24Performance.droppedPkts

       64 bit unsigned wrappable counter."
   ::= {pr1645v2Lan2MCVlanOutPQsH24PerformanceEntry 67108864}

pr1645v2Lan2MCVlanOutPQsH24PerformanceRDropPkts OBJECT-TYPE
   SYNTAX      Counter64
   MAX-ACCESS  read-only
   STATUS      current
   DESCRIPTION
      "Path: ethernet2.performance.vlan.outPriorityQueues.h24Performance.redDroppedPkts

       64 bit unsigned wrappable counter."
   ::= {pr1645v2Lan2MCVlanOutPQsH24PerformanceEntry 201326592}

pr1645v2Lan2MCVlanOutPQsH24PerformanceCirTxPkts OBJECT-TYPE
   SYNTAX      Counter64
   MAX-ACCESS  read-only
   STATUS      current
   DESCRIPTION
      "Path: ethernet2.performance.vlan.outPriorityQueues.h24Performance.cirTxPkts

       64 bit unsigned wrappable counter."
   ::= {pr1645v2Lan2MCVlanOutPQsH24PerformanceEntry 83886080}

pr1645v2Lan2MCVlanOutPQsH24PerformanceEirTxPkts OBJECT-TYPE
   SYNTAX      Counter64
   MAX-ACCESS  read-only
   STATUS      current
   DESCRIPTION
      "Path: ethernet2.performance.vlan.outPriorityQueues.h24Performance.eirTxPkts

       64 bit unsigned wrappable counter."
   ::= {pr1645v2Lan2MCVlanOutPQsH24PerformanceEntry 100663296}

pr1645v2Lan2MCVlanOutPQsH24PerformanceViolTxPkts OBJECT-TYPE
   SYNTAX      Counter64
   MAX-ACCESS  read-only
   STATUS      current
   DESCRIPTION
      "Path: ethernet2.performance.vlan.outPriorityQueues.h24Performance.violateTxPkts

       64 bit unsigned wrappable counter."
   ::= {pr1645v2Lan2MCVlanOutPQsH24PerformanceEntry 301989888}

pr1645v2Lan2MCVlanOutPQsH24PerformanceTotOcts OBJECT-TYPE
   SYNTAX      Counter64
   MAX-ACCESS  read-only
   STATUS      current
   DESCRIPTION
      "Path: ethernet2.performance.vlan.outPriorityQueues.h24Performance.totalOctets

       64 bit unsigned wrappable counter."
   ::= {pr1645v2Lan2MCVlanOutPQsH24PerformanceEntry 251658240}

pr1645v2Lan2MCVlanOutPQsH24PerformanceDirTxOcts OBJECT-TYPE
   SYNTAX      Counter64
   MAX-ACCESS  read-only
   STATUS      current
   DESCRIPTION
      "Path: ethernet2.performance.vlan.outPriorityQueues.h24Performance.directTxOctets

       64 bit unsigned wrappable counter."
   ::= {pr1645v2Lan2MCVlanOutPQsH24PerformanceEntry 117440512}

pr1645v2Lan2MCVlanOutPQsH24PerformanceQdOcts OBJECT-TYPE
   SYNTAX      Counter64
   MAX-ACCESS  read-only
   STATUS      current
   DESCRIPTION
      "Path: ethernet2.performance.vlan.outPriorityQueues.h24Performance.queuedOctets

       64 bit unsigned wrappable counter."
   ::= {pr1645v2Lan2MCVlanOutPQsH24PerformanceEntry 134217728}

pr1645v2Lan2MCVlanOutPQsH24PerformanceDropOcts OBJECT-TYPE
   SYNTAX      Counter64
   MAX-ACCESS  read-only
   STATUS      current
   DESCRIPTION
      "Path: ethernet2.performance.vlan.outPriorityQueues.h24Performance.droppedOctets

       64 bit unsigned wrappable counter."
   ::= {pr1645v2Lan2MCVlanOutPQsH24PerformanceEntry 150994944}

pr1645v2Lan2MCVlanOutPQsH24PerformanceRDropOcts OBJECT-TYPE
   SYNTAX      Counter64
   MAX-ACCESS  read-only
   STATUS      current
   DESCRIPTION
      "Path: ethernet2.performance.vlan.outPriorityQueues.h24Performance.redDroppedOctets

       64 bit unsigned wrappable counter."
   ::= {pr1645v2Lan2MCVlanOutPQsH24PerformanceEntry 218103808}

pr1645v2Lan2MCVlanOutPQsH24PerformanceCirTxOcts OBJECT-TYPE
   SYNTAX      Counter64
   MAX-ACCESS  read-only
   STATUS      current
   DESCRIPTION
      "Path: ethernet2.performance.vlan.outPriorityQueues.h24Performance.cirTxOctets

       64 bit unsigned wrappable counter."
   ::= {pr1645v2Lan2MCVlanOutPQsH24PerformanceEntry 167772160}

pr1645v2Lan2MCVlanOutPQsH24PerformanceEirTxOcts OBJECT-TYPE
   SYNTAX      Counter64
   MAX-ACCESS  read-only
   STATUS      current
   DESCRIPTION
      "Path: ethernet2.performance.vlan.outPriorityQueues.h24Performance.eirTxOctets

       64 bit unsigned wrappable counter."
   ::= {pr1645v2Lan2MCVlanOutPQsH24PerformanceEntry 184549376}

pr1645v2Lan2MCVlanOutPQsH24PerformanceViolTxOcts OBJECT-TYPE
   SYNTAX      Counter64
   MAX-ACCESS  read-only
   STATUS      current
   DESCRIPTION
      "Path: ethernet2.performance.vlan.outPriorityQueues.h24Performance.violateTxOctets

       64 bit unsigned wrappable counter."
   ::= {pr1645v2Lan2MCVlanOutPQsH24PerformanceEntry 318767104}

pr1645v2Lan2MCVlanOutPQsH24PerformanceBandwidth OBJECT-TYPE
   SYNTAX      Integer32
   MAX-ACCESS  read-only
   STATUS      current
   DESCRIPTION
      "Path: ethernet2.performance.vlan.outPriorityQueues.h24Performance.bandwidth

       unit name = bps
       formula = 8 * ; 8 /"
   ::= {pr1645v2Lan2MCVlanOutPQsH24PerformanceEntry 268435456}

pr1645v2Lan2MCVlanOutPQsD7Performance OBJECT-TYPE
   SYNTAX      SEQUENCE OF Pr1645v2Lan2MCVlanOutPQsD7PerformanceEntry
   MAX-ACCESS  not-accessible
   STATUS      current
   DESCRIPTION
      ""
   ::= {pr1645v2Lan2MCVlan 84344832}

pr1645v2Lan2MCVlanOutPQsD7PerformanceEntry OBJECT-TYPE
   SYNTAX      Pr1645v2Lan2MCVlanOutPQsD7PerformanceEntry
   MAX-ACCESS  not-accessible
   STATUS      current
   DESCRIPTION
      ""
   INDEX      { pr1645v2Lan2MCVlanTableIx,
                pr1645v2Lan2MCVlanOutPQsTableIx,
                pr1645v2Lan2MCVlanOutPQsD7PerformanceTableIx }
   ::= {pr1645v2Lan2MCVlanOutPQsD7Performance 1}

Pr1645v2Lan2MCVlanOutPQsD7PerformanceEntry ::=
   SEQUENCE
      {
      pr1645v2Lan2MCVlanOutPQsD7PerformanceTableIx
         TableIndex,
      pr1645v2Lan2MCVlanOutPQsD7PerformanceSysUpTime
         TimeTicks,
      pr1645v2Lan2MCVlanOutPQsD7PerformanceTotPkts
         Counter64,
      pr1645v2Lan2MCVlanOutPQsD7PerformanceDirTxPkts
         Counter64,
      pr1645v2Lan2MCVlanOutPQsD7PerformanceQdPkts
         Counter64,
      pr1645v2Lan2MCVlanOutPQsD7PerformanceDropPkts
         Counter64,
      pr1645v2Lan2MCVlanOutPQsD7PerformanceRDropPkts
         Counter64,
      pr1645v2Lan2MCVlanOutPQsD7PerformanceCirTxPkts
         Counter64,
      pr1645v2Lan2MCVlanOutPQsD7PerformanceEirTxPkts
         Counter64,
      pr1645v2Lan2MCVlanOutPQsD7PerformanceViolTxPkts
         Counter64,
      pr1645v2Lan2MCVlanOutPQsD7PerformanceTotOcts
         Counter64,
      pr1645v2Lan2MCVlanOutPQsD7PerformanceDirTxOcts
         Counter64,
      pr1645v2Lan2MCVlanOutPQsD7PerformanceQdOcts
         Counter64,
      pr1645v2Lan2MCVlanOutPQsD7PerformanceDropOcts
         Counter64,
      pr1645v2Lan2MCVlanOutPQsD7PerformanceRDropOcts
         Counter64,
      pr1645v2Lan2MCVlanOutPQsD7PerformanceCirTxOcts
         Counter64,
      pr1645v2Lan2MCVlanOutPQsD7PerformanceEirTxOcts
         Counter64,
      pr1645v2Lan2MCVlanOutPQsD7PerformanceViolTxOcts
         Counter64,
      pr1645v2Lan2MCVlanOutPQsD7PerformanceBandwidth
         Integer32
      }

pr1645v2Lan2MCVlanOutPQsD7PerformanceTableIx OBJECT-TYPE
   SYNTAX      TableIndex
   MAX-ACCESS  not-accessible
   STATUS      current
   DESCRIPTION
      ""
   ::= {pr1645v2Lan2MCVlanOutPQsD7PerformanceEntry 11}

pr1645v2Lan2MCVlanOutPQsD7PerformanceSysUpTime OBJECT-TYPE
   SYNTAX      TimeTicks
   MAX-ACCESS  read-only
   STATUS      current
   DESCRIPTION
      "Path: ethernet2.performance.vlan.outPriorityQueues.d7Performance.sysUpTime

       Time in centi-second."
   ::= {pr1645v2Lan2MCVlanOutPQsD7PerformanceEntry 16777216}

pr1645v2Lan2MCVlanOutPQsD7PerformanceTotPkts OBJECT-TYPE
   SYNTAX      Counter64
   MAX-ACCESS  read-only
   STATUS      current
   DESCRIPTION
      "Path: ethernet2.performance.vlan.outPriorityQueues.d7Performance.totalPkts

       64 bit unsigned wrappable counter."
   ::= {pr1645v2Lan2MCVlanOutPQsD7PerformanceEntry 234881024}

pr1645v2Lan2MCVlanOutPQsD7PerformanceDirTxPkts OBJECT-TYPE
   SYNTAX      Counter64
   MAX-ACCESS  read-only
   STATUS      current
   DESCRIPTION
      "Path: ethernet2.performance.vlan.outPriorityQueues.d7Performance.directTxPkts

       64 bit unsigned wrappable counter."
   ::= {pr1645v2Lan2MCVlanOutPQsD7PerformanceEntry 33554432}

pr1645v2Lan2MCVlanOutPQsD7PerformanceQdPkts OBJECT-TYPE
   SYNTAX      Counter64
   MAX-ACCESS  read-only
   STATUS      current
   DESCRIPTION
      "Path: ethernet2.performance.vlan.outPriorityQueues.d7Performance.queuedPkts

       64 bit unsigned wrappable counter."
   ::= {pr1645v2Lan2MCVlanOutPQsD7PerformanceEntry 50331648}

pr1645v2Lan2MCVlanOutPQsD7PerformanceDropPkts OBJECT-TYPE
   SYNTAX      Counter64
   MAX-ACCESS  read-only
   STATUS      current
   DESCRIPTION
      "Path: ethernet2.performance.vlan.outPriorityQueues.d7Performance.droppedPkts

       64 bit unsigned wrappable counter."
   ::= {pr1645v2Lan2MCVlanOutPQsD7PerformanceEntry 67108864}

pr1645v2Lan2MCVlanOutPQsD7PerformanceRDropPkts OBJECT-TYPE
   SYNTAX      Counter64
   MAX-ACCESS  read-only
   STATUS      current
   DESCRIPTION
      "Path: ethernet2.performance.vlan.outPriorityQueues.d7Performance.redDroppedPkts

       64 bit unsigned wrappable counter."
   ::= {pr1645v2Lan2MCVlanOutPQsD7PerformanceEntry 201326592}

pr1645v2Lan2MCVlanOutPQsD7PerformanceCirTxPkts OBJECT-TYPE
   SYNTAX      Counter64
   MAX-ACCESS  read-only
   STATUS      current
   DESCRIPTION
      "Path: ethernet2.performance.vlan.outPriorityQueues.d7Performance.cirTxPkts

       64 bit unsigned wrappable counter."
   ::= {pr1645v2Lan2MCVlanOutPQsD7PerformanceEntry 83886080}

pr1645v2Lan2MCVlanOutPQsD7PerformanceEirTxPkts OBJECT-TYPE
   SYNTAX      Counter64
   MAX-ACCESS  read-only
   STATUS      current
   DESCRIPTION
      "Path: ethernet2.performance.vlan.outPriorityQueues.d7Performance.eirTxPkts

       64 bit unsigned wrappable counter."
   ::= {pr1645v2Lan2MCVlanOutPQsD7PerformanceEntry 100663296}

pr1645v2Lan2MCVlanOutPQsD7PerformanceViolTxPkts OBJECT-TYPE
   SYNTAX      Counter64
   MAX-ACCESS  read-only
   STATUS      current
   DESCRIPTION
      "Path: ethernet2.performance.vlan.outPriorityQueues.d7Performance.violateTxPkts

       64 bit unsigned wrappable counter."
   ::= {pr1645v2Lan2MCVlanOutPQsD7PerformanceEntry 301989888}

pr1645v2Lan2MCVlanOutPQsD7PerformanceTotOcts OBJECT-TYPE
   SYNTAX      Counter64
   MAX-ACCESS  read-only
   STATUS      current
   DESCRIPTION
      "Path: ethernet2.performance.vlan.outPriorityQueues.d7Performance.totalOctets

       64 bit unsigned wrappable counter."
   ::= {pr1645v2Lan2MCVlanOutPQsD7PerformanceEntry 251658240}

pr1645v2Lan2MCVlanOutPQsD7PerformanceDirTxOcts OBJECT-TYPE
   SYNTAX      Counter64
   MAX-ACCESS  read-only
   STATUS      current
   DESCRIPTION
      "Path: ethernet2.performance.vlan.outPriorityQueues.d7Performance.directTxOctets

       64 bit unsigned wrappable counter."
   ::= {pr1645v2Lan2MCVlanOutPQsD7PerformanceEntry 117440512}

pr1645v2Lan2MCVlanOutPQsD7PerformanceQdOcts OBJECT-TYPE
   SYNTAX      Counter64
   MAX-ACCESS  read-only
   STATUS      current
   DESCRIPTION
      "Path: ethernet2.performance.vlan.outPriorityQueues.d7Performance.queuedOctets

       64 bit unsigned wrappable counter."
   ::= {pr1645v2Lan2MCVlanOutPQsD7PerformanceEntry 134217728}

pr1645v2Lan2MCVlanOutPQsD7PerformanceDropOcts OBJECT-TYPE
   SYNTAX      Counter64
   MAX-ACCESS  read-only
   STATUS      current
   DESCRIPTION
      "Path: ethernet2.performance.vlan.outPriorityQueues.d7Performance.droppedOctets

       64 bit unsigned wrappable counter."
   ::= {pr1645v2Lan2MCVlanOutPQsD7PerformanceEntry 150994944}

pr1645v2Lan2MCVlanOutPQsD7PerformanceRDropOcts OBJECT-TYPE
   SYNTAX      Counter64
   MAX-ACCESS  read-only
   STATUS      current
   DESCRIPTION
      "Path: ethernet2.performance.vlan.outPriorityQueues.d7Performance.redDroppedOctets

       64 bit unsigned wrappable counter."
   ::= {pr1645v2Lan2MCVlanOutPQsD7PerformanceEntry 218103808}

pr1645v2Lan2MCVlanOutPQsD7PerformanceCirTxOcts OBJECT-TYPE
   SYNTAX      Counter64
   MAX-ACCESS  read-only
   STATUS      current
   DESCRIPTION
      "Path: ethernet2.performance.vlan.outPriorityQueues.d7Performance.cirTxOctets

       64 bit unsigned wrappable counter."
   ::= {pr1645v2Lan2MCVlanOutPQsD7PerformanceEntry 167772160}

pr1645v2Lan2MCVlanOutPQsD7PerformanceEirTxOcts OBJECT-TYPE
   SYNTAX      Counter64
   MAX-ACCESS  read-only
   STATUS      current
   DESCRIPTION
      "Path: ethernet2.performance.vlan.outPriorityQueues.d7Performance.eirTxOctets

       64 bit unsigned wrappable counter."
   ::= {pr1645v2Lan2MCVlanOutPQsD7PerformanceEntry 184549376}

pr1645v2Lan2MCVlanOutPQsD7PerformanceViolTxOcts OBJECT-TYPE
   SYNTAX      Counter64
   MAX-ACCESS  read-only
   STATUS      current
   DESCRIPTION
      "Path: ethernet2.performance.vlan.outPriorityQueues.d7Performance.violateTxOctets

       64 bit unsigned wrappable counter."
   ::= {pr1645v2Lan2MCVlanOutPQsD7PerformanceEntry 318767104}

pr1645v2Lan2MCVlanOutPQsD7PerformanceBandwidth OBJECT-TYPE
   SYNTAX      Integer32
   MAX-ACCESS  read-only
   STATUS      current
   DESCRIPTION
      "Path: ethernet2.performance.vlan.outPriorityQueues.d7Performance.bandwidth

       unit name = bps
       formula = 8 * ; 8 /"
   ::= {pr1645v2Lan2MCVlanOutPQsD7PerformanceEntry 268435456}


pr1645v2Lan2MCPPPoE OBJECT IDENTIFIER ::= {pr1645v2Lan2MC 53}

pr1645v2Lan2MCPPPoESSCTable OBJECT-TYPE
   SYNTAX      SEQUENCE OF Pr1645v2Lan2MCPPPoEEntry
   MAX-ACCESS  not-accessible
   STATUS      current
   DESCRIPTION
      ""
   ::= {pr1645v2Lan2MCPPPoE 1}

pr1645v2Lan2MCPPPoEEntry OBJECT-TYPE
   SYNTAX      Pr1645v2Lan2MCPPPoEEntry
   MAX-ACCESS  not-accessible
   STATUS      current
   DESCRIPTION
      ""
   INDEX      { pr1645v2Lan2MCPPPoETableIx }
   ::= {pr1645v2Lan2MCPPPoESSCTable 1}

Pr1645v2Lan2MCPPPoEEntry ::=
   SEQUENCE
      {
      pr1645v2Lan2MCPPPoETableIx
         TableIndex,
      pr1645v2Lan2MCPPPoEName
         DisplayString,
      pr1645v2Lan2MCPPPoEMCInOctets
         Counter64,
      pr1645v2Lan2MCPPPoEMCInUcast
         Counter64,
      pr1645v2Lan2MCPPPoEMCInNUcastPkts
         Counter64,
      pr1645v2Lan2MCPPPoEMCInBcastPkts
         Counter64,
      pr1645v2Lan2MCPPPoEMCInMcastPkts
         Counter64,
      pr1645v2Lan2MCPPPoEMCInDiscards
         Counter64,
      pr1645v2Lan2MCPPPoEMCInErrors
         Counter64,
      pr1645v2Lan2MCPPPoEMCInUnknownProtos
         Counter64,
      pr1645v2Lan2MCPPPoEMCInDropEx
         Counter64,
      pr1645v2Lan2MCPPPoEMCInDropNoMac
         Counter64,
      pr1645v2Lan2MCPPPoEMCInDropNUCast
         Counter64,
      pr1645v2Lan2MCPPPoEMCInDropFilter
         Counter64,
      pr1645v2Lan2MCPPPoEMCInBandwidth15sec
         Integer32,
      pr1645v2Lan2MCPPPoEMCInBandwidth30sec
         Integer32,
      pr1645v2Lan2MCPPPoEMCInBandwidth1min
         Integer32,
      pr1645v2Lan2MCPPPoEMCInBandwidth2min
         Integer32,
      pr1645v2Lan2MCPPPoEMCInBandwidth5min
         Integer32,
      pr1645v2Lan2MCPPPoEMCOutOctets
         Counter64,
      pr1645v2Lan2MCPPPoEMCOutUcastPkts
         Counter64,
      pr1645v2Lan2MCPPPoEMCOutNUcastPkts
         Counter64,
      pr1645v2Lan2MCPPPoEMCOutBcastPkts
         Counter64,
      pr1645v2Lan2MCPPPoEMCOutMcastPkts
         Counter64,
      pr1645v2Lan2MCPPPoEMCOutDiscards
         Counter64,
      pr1645v2Lan2MCPPPoEMCOutErrors
         Counter64,
      pr1645v2Lan2MCPPPoEMCOutQLen
         Counter32,
      pr1645v2Lan2MCPPPoEMCOutDropEx
         Counter64,
      pr1645v2Lan2MCPPPoEMCOutDropNoArp
         Counter64,
      pr1645v2Lan2MCPPPoEMCOutDropFilter
         Counter64,
      pr1645v2Lan2MCPPPoEMCOutBandwidth15sec
         Integer32,
      pr1645v2Lan2MCPPPoEMCOutBandwidth30sec
         Integer32,
      pr1645v2Lan2MCPPPoEMCOutBandwidth1min
         Integer32,
      pr1645v2Lan2MCPPPoEMCOutBandwidth2min
         Integer32,
      pr1645v2Lan2MCPPPoEMCOutBandwidth5min
         Integer32,
      pr1645v2Lan2MCPPPoEPppLinkMonitoringRequestsSent
         Gauge32,
      pr1645v2Lan2MCPPPoEPppLinkMonitoringRepliesRcvd
         Gauge32,
      pr1645v2Lan2MCPPPoEPppLinkMonitoringRequestsRcvd
         Gauge32,
      pr1645v2Lan2MCPPPoEPppLinkMonitoringRepliesSent
         Gauge32
      }

pr1645v2Lan2MCPPPoETableIx OBJECT-TYPE
   SYNTAX      TableIndex
   MAX-ACCESS  not-accessible
   STATUS      current
   DESCRIPTION
      ""
   ::= {pr1645v2Lan2MCPPPoEEntry 11}

pr1645v2Lan2MCPPPoEName OBJECT-TYPE
   SYNTAX      DisplayString
   MAX-ACCESS  read-only
   STATUS      current
   DESCRIPTION
      "Path: ethernet2.performance.pppoEClient.name"
   ::= {pr1645v2Lan2MCPPPoEEntry 16777216}

pr1645v2Lan2MCPPPoEMCInOctets OBJECT-TYPE
   SYNTAX      Counter64
   MAX-ACCESS  read-only
   STATUS      current
   DESCRIPTION
      "Path: ethernet2.performance.pppoEClient.mibCounters.ifInOctets

       64 bit unsigned wrappable counter."
   ::= {pr1645v2Lan2MCPPPoEEntry 40697856}

pr1645v2Lan2MCPPPoEMCInUcast OBJECT-TYPE
   SYNTAX      Counter64
   MAX-ACCESS  read-only
   STATUS      current
   DESCRIPTION
      "Path: ethernet2.performance.pppoEClient.mibCounters.ifInUcastPkts

       64 bit unsigned wrappable counter."
   ::= {pr1645v2Lan2MCPPPoEEntry 40763392}

pr1645v2Lan2MCPPPoEMCInNUcastPkts OBJECT-TYPE
   SYNTAX      Counter64
   MAX-ACCESS  read-only
   STATUS      current
   DESCRIPTION
      "Path: ethernet2.performance.pppoEClient.mibCounters.ifInNUcastPkts

       64 bit unsigned wrappable counter."
   ::= {pr1645v2Lan2MCPPPoEEntry 40828928}

pr1645v2Lan2MCPPPoEMCInBcastPkts OBJECT-TYPE
   SYNTAX      Counter64
   MAX-ACCESS  read-only
   STATUS      current
   DESCRIPTION
      "Path: ethernet2.performance.pppoEClient.mibCounters.ifInBcastPkts

       64 bit unsigned wrappable counter."
   ::= {pr1645v2Lan2MCPPPoEEntry 47382528}

pr1645v2Lan2MCPPPoEMCInMcastPkts OBJECT-TYPE
   SYNTAX      Counter64
   MAX-ACCESS  read-only
   STATUS      current
   DESCRIPTION
      "Path: ethernet2.performance.pppoEClient.mibCounters.ifInMcastPkts

       64 bit unsigned wrappable counter."
   ::= {pr1645v2Lan2MCPPPoEEntry 48037888}

pr1645v2Lan2MCPPPoEMCInDiscards OBJECT-TYPE
   SYNTAX      Counter64
   MAX-ACCESS  read-only
   STATUS      current
   DESCRIPTION
      "Path: ethernet2.performance.pppoEClient.mibCounters.ifInDiscards

       64 bit unsigned wrappable counter."
   ::= {pr1645v2Lan2MCPPPoEEntry 40894464}

pr1645v2Lan2MCPPPoEMCInErrors OBJECT-TYPE
   SYNTAX      Counter64
   MAX-ACCESS  read-only
   STATUS      current
   DESCRIPTION
      "Path: ethernet2.performance.pppoEClient.mibCounters.ifInErrors

       64 bit unsigned wrappable counter."
   ::= {pr1645v2Lan2MCPPPoEEntry 40960000}

pr1645v2Lan2MCPPPoEMCInUnknownProtos OBJECT-TYPE
   SYNTAX      Counter64
   MAX-ACCESS  read-only
   STATUS      current
   DESCRIPTION
      "Path: ethernet2.performance.pppoEClient.mibCounters.ifInUnknownProtos

       64 bit unsigned wrappable counter."
   ::= {pr1645v2Lan2MCPPPoEEntry 41025536}

pr1645v2Lan2MCPPPoEMCInDropEx OBJECT-TYPE
   SYNTAX      Counter64
   MAX-ACCESS  read-only
   STATUS      current
   DESCRIPTION
      "Path: ethernet2.performance.pppoEClient.mibCounters.ifInDropLevelExceeded

       64 bit unsigned wrappable counter."
   ::= {pr1645v2Lan2MCPPPoEEntry 42074112}

pr1645v2Lan2MCPPPoEMCInDropNoMac OBJECT-TYPE
   SYNTAX      Counter64
   MAX-ACCESS  read-only
   STATUS      current
   DESCRIPTION
      "Path: ethernet2.performance.pppoEClient.mibCounters.ifInDiscardsNoMacFit

       64 bit unsigned wrappable counter."
   ::= {pr1645v2Lan2MCPPPoEEntry 42270720}

pr1645v2Lan2MCPPPoEMCInDropNUCast OBJECT-TYPE
   SYNTAX      Counter64
   MAX-ACCESS  read-only
   STATUS      current
   DESCRIPTION
      "Path: ethernet2.performance.pppoEClient.mibCounters.ifInDiscardsNUCast

       64 bit unsigned wrappable counter."
   ::= {pr1645v2Lan2MCPPPoEEntry 42467328}

pr1645v2Lan2MCPPPoEMCInDropFilter OBJECT-TYPE
   SYNTAX      Counter64
   MAX-ACCESS  read-only
   STATUS      current
   DESCRIPTION
      "Path: ethernet2.performance.pppoEClient.mibCounters.ifInDiscardsFilter

       64 bit unsigned wrappable counter."
   ::= {pr1645v2Lan2MCPPPoEEntry 42532864}

pr1645v2Lan2MCPPPoEMCInBandwidth15sec OBJECT-TYPE
   SYNTAX      Integer32
   MAX-ACCESS  read-only
   STATUS      current
   DESCRIPTION
      "Path: ethernet2.performance.pppoEClient.mibCounters.ifInBandwidth.15sec

       unit name = bps
       formula = 8 * ; 8 /"
   ::= {pr1645v2Lan2MCPPPoEEntry 45417728}

pr1645v2Lan2MCPPPoEMCInBandwidth30sec OBJECT-TYPE
   SYNTAX      Integer32
   MAX-ACCESS  read-only
   STATUS      current
   DESCRIPTION
      "Path: ethernet2.performance.pppoEClient.mibCounters.ifInBandwidth.30sec

       unit name = bps
       formula = 8 * ; 8 /"
   ::= {pr1645v2Lan2MCPPPoEEntry 45419008}

pr1645v2Lan2MCPPPoEMCInBandwidth1min OBJECT-TYPE
   SYNTAX      Integer32
   MAX-ACCESS  read-only
   STATUS      current
   DESCRIPTION
      "Path: ethernet2.performance.pppoEClient.mibCounters.ifInBandwidth.1min

       unit name = bps
       formula = 8 * ; 8 /"
   ::= {pr1645v2Lan2MCPPPoEEntry 45421568}

pr1645v2Lan2MCPPPoEMCInBandwidth2min OBJECT-TYPE
   SYNTAX      Integer32
   MAX-ACCESS  read-only
   STATUS      current
   DESCRIPTION
      "Path: ethernet2.performance.pppoEClient.mibCounters.ifInBandwidth.2min

       unit name = bps
       formula = 8 * ; 8 /"
   ::= {pr1645v2Lan2MCPPPoEEntry 45426688}

pr1645v2Lan2MCPPPoEMCInBandwidth5min OBJECT-TYPE
   SYNTAX      Integer32
   MAX-ACCESS  read-only
   STATUS      current
   DESCRIPTION
      "Path: ethernet2.performance.pppoEClient.mibCounters.ifInBandwidth.5min

       unit name = bps
       formula = 8 * ; 8 /"
   ::= {pr1645v2Lan2MCPPPoEEntry 45442048}

pr1645v2Lan2MCPPPoEMCOutOctets OBJECT-TYPE
   SYNTAX      Counter64
   MAX-ACCESS  read-only
   STATUS      current
   DESCRIPTION
      "Path: ethernet2.performance.pppoEClient.mibCounters.ifOutOctets

       64 bit unsigned wrappable counter."
   ::= {pr1645v2Lan2MCPPPoEEntry 41091072}

pr1645v2Lan2MCPPPoEMCOutUcastPkts OBJECT-TYPE
   SYNTAX      Counter64
   MAX-ACCESS  read-only
   STATUS      current
   DESCRIPTION
      "Path: ethernet2.performance.pppoEClient.mibCounters.ifOutUcastPkts

       64 bit unsigned wrappable counter."
   ::= {pr1645v2Lan2MCPPPoEEntry 41156608}

pr1645v2Lan2MCPPPoEMCOutNUcastPkts OBJECT-TYPE
   SYNTAX      Counter64
   MAX-ACCESS  read-only
   STATUS      current
   DESCRIPTION
      "Path: ethernet2.performance.pppoEClient.mibCounters.ifOutNUcastPkts

       64 bit unsigned wrappable counter."
   ::= {pr1645v2Lan2MCPPPoEEntry 41222144}

pr1645v2Lan2MCPPPoEMCOutBcastPkts OBJECT-TYPE
   SYNTAX      Counter64
   MAX-ACCESS  read-only
   STATUS      current
   DESCRIPTION
      "Path: ethernet2.performance.pppoEClient.mibCounters.ifOutBcastPkts

       64 bit unsigned wrappable counter."
   ::= {pr1645v2Lan2MCPPPoEEntry 47775744}

pr1645v2Lan2MCPPPoEMCOutMcastPkts OBJECT-TYPE
   SYNTAX      Counter64
   MAX-ACCESS  read-only
   STATUS      current
   DESCRIPTION
      "Path: ethernet2.performance.pppoEClient.mibCounters.ifOutMcastPkts

       64 bit unsigned wrappable counter."
   ::= {pr1645v2Lan2MCPPPoEEntry 48431104}

pr1645v2Lan2MCPPPoEMCOutDiscards OBJECT-TYPE
   SYNTAX      Counter64
   MAX-ACCESS  read-only
   STATUS      current
   DESCRIPTION
      "Path: ethernet2.performance.pppoEClient.mibCounters.ifOutDiscards

       64 bit unsigned wrappable counter."
   ::= {pr1645v2Lan2MCPPPoEEntry 41287680}

pr1645v2Lan2MCPPPoEMCOutErrors OBJECT-TYPE
   SYNTAX      Counter64
   MAX-ACCESS  read-only
   STATUS      current
   DESCRIPTION
      "Path: ethernet2.performance.pppoEClient.mibCounters.ifOutErrors

       64 bit unsigned wrappable counter."
   ::= {pr1645v2Lan2MCPPPoEEntry 41353216}

pr1645v2Lan2MCPPPoEMCOutQLen OBJECT-TYPE
   SYNTAX      Counter32
   MAX-ACCESS  read-only
   STATUS      current
   DESCRIPTION
      "Path: ethernet2.performance.pppoEClient.mibCounters.ifOutQLen

       32 bit unsigned wrappable counter."
   ::= {pr1645v2Lan2MCPPPoEEntry 41418752}

pr1645v2Lan2MCPPPoEMCOutDropEx OBJECT-TYPE
   SYNTAX      Counter64
   MAX-ACCESS  read-only
   STATUS      current
   DESCRIPTION
      "Path: ethernet2.performance.pppoEClient.mibCounters.ifOutDropLevelExceeded

       64 bit unsigned wrappable counter."
   ::= {pr1645v2Lan2MCPPPoEEntry 41484288}

pr1645v2Lan2MCPPPoEMCOutDropNoArp OBJECT-TYPE
   SYNTAX      Counter64
   MAX-ACCESS  read-only
   STATUS      current
   DESCRIPTION
      "Path: ethernet2.performance.pppoEClient.mibCounters.ifOutDiscardsNoArp

       64 bit unsigned wrappable counter."
   ::= {pr1645v2Lan2MCPPPoEEntry 42336256}

pr1645v2Lan2MCPPPoEMCOutDropFilter OBJECT-TYPE
   SYNTAX      Counter64
   MAX-ACCESS  read-only
   STATUS      current
   DESCRIPTION
      "Path: ethernet2.performance.pppoEClient.mibCounters.ifOutDiscardsFilter

       64 bit unsigned wrappable counter."
   ::= {pr1645v2Lan2MCPPPoEEntry 42598400}

pr1645v2Lan2MCPPPoEMCOutBandwidth15sec OBJECT-TYPE
   SYNTAX      Integer32
   MAX-ACCESS  read-only
   STATUS      current
   DESCRIPTION
      "Path: ethernet2.performance.pppoEClient.mibCounters.ifOutBandwidth.15sec

       unit name = bps
       formula = 8 * ; 8 /"
   ::= {pr1645v2Lan2MCPPPoEEntry 45483264}

pr1645v2Lan2MCPPPoEMCOutBandwidth30sec OBJECT-TYPE
   SYNTAX      Integer32
   MAX-ACCESS  read-only
   STATUS      current
   DESCRIPTION
      "Path: ethernet2.performance.pppoEClient.mibCounters.ifOutBandwidth.30sec

       unit name = bps
       formula = 8 * ; 8 /"
   ::= {pr1645v2Lan2MCPPPoEEntry 45484544}

pr1645v2Lan2MCPPPoEMCOutBandwidth1min OBJECT-TYPE
   SYNTAX      Integer32
   MAX-ACCESS  read-only
   STATUS      current
   DESCRIPTION
      "Path: ethernet2.performance.pppoEClient.mibCounters.ifOutBandwidth.1min

       unit name = bps
       formula = 8 * ; 8 /"
   ::= {pr1645v2Lan2MCPPPoEEntry 45487104}

pr1645v2Lan2MCPPPoEMCOutBandwidth2min OBJECT-TYPE
   SYNTAX      Integer32
   MAX-ACCESS  read-only
   STATUS      current
   DESCRIPTION
      "Path: ethernet2.performance.pppoEClient.mibCounters.ifOutBandwidth.2min

       unit name = bps
       formula = 8 * ; 8 /"
   ::= {pr1645v2Lan2MCPPPoEEntry 45492224}

pr1645v2Lan2MCPPPoEMCOutBandwidth5min OBJECT-TYPE
   SYNTAX      Integer32
   MAX-ACCESS  read-only
   STATUS      current
   DESCRIPTION
      "Path: ethernet2.performance.pppoEClient.mibCounters.ifOutBandwidth.5min

       unit name = bps
       formula = 8 * ; 8 /"
   ::= {pr1645v2Lan2MCPPPoEEntry 45507584}

pr1645v2Lan2MCPPPoEPppLinkMonitoringRequestsSent OBJECT-TYPE
   SYNTAX      Gauge32
   MAX-ACCESS  read-only
   STATUS      current
   DESCRIPTION
      "Path: ethernet2.performance.pppoEClient.ppp.linkMonitoring.requestsSent

       32 bit unsigned gauge value."
   ::= {pr1645v2Lan2MCPPPoEEntry 50397440}

pr1645v2Lan2MCPPPoEPppLinkMonitoringRepliesRcvd OBJECT-TYPE
   SYNTAX      Gauge32
   MAX-ACCESS  read-only
   STATUS      current
   DESCRIPTION
      "Path: ethernet2.performance.pppoEClient.ppp.linkMonitoring.repliesRcvd

       32 bit unsigned gauge value."
   ::= {pr1645v2Lan2MCPPPoEEntry 50397696}

pr1645v2Lan2MCPPPoEPppLinkMonitoringRequestsRcvd OBJECT-TYPE
   SYNTAX      Gauge32
   MAX-ACCESS  read-only
   STATUS      current
   DESCRIPTION
      "Path: ethernet2.performance.pppoEClient.ppp.linkMonitoring.requestsRcvd

       32 bit unsigned gauge value."
   ::= {pr1645v2Lan2MCPPPoEEntry 50397952}

pr1645v2Lan2MCPPPoEPppLinkMonitoringRepliesSent OBJECT-TYPE
   SYNTAX      Gauge32
   MAX-ACCESS  read-only
   STATUS      current
   DESCRIPTION
      "Path: ethernet2.performance.pppoEClient.ppp.linkMonitoring.repliesSent

       32 bit unsigned gauge value."
   ::= {pr1645v2Lan2MCPPPoEEntry 50398208}

pr1645v2Lan2MCPPPoEMCH2P OBJECT-TYPE
   SYNTAX      SEQUENCE OF Pr1645v2Lan2MCPPPoEMCH2PEntry
   MAX-ACCESS  not-accessible
   STATUS      current
   DESCRIPTION
      ""
   ::= {pr1645v2Lan2MCPPPoE 41549824}

pr1645v2Lan2MCPPPoEMCH2PEntry OBJECT-TYPE
   SYNTAX      Pr1645v2Lan2MCPPPoEMCH2PEntry
   MAX-ACCESS  not-accessible
   STATUS      current
   DESCRIPTION
      ""
   INDEX      { pr1645v2Lan2MCPPPoETableIx,
                pr1645v2Lan2MCPPPoEMCH2PTableIx }
   ::= {pr1645v2Lan2MCPPPoEMCH2P 1}

Pr1645v2Lan2MCPPPoEMCH2PEntry ::=
   SEQUENCE
      {
      pr1645v2Lan2MCPPPoEMCH2PTableIx
         TableIndex,
      pr1645v2Lan2MCPPPoEMCH2PSysUpTime
         TimeTicks,
      pr1645v2Lan2MCPPPoEMCH2PIfUpTime
         TimeTicks,
      pr1645v2Lan2MCPPPoEMCH2PIfStatChanges
         Counter32,
      pr1645v2Lan2MCPPPoEMCH2PIfInOctets
         Counter64,
      pr1645v2Lan2MCPPPoEMCH2PIfInUCPkts
         Counter64,
      pr1645v2Lan2MCPPPoEMCH2PIfInNUCPkts
         Counter64,
      pr1645v2Lan2MCPPPoEMCH2PIfInBCPkts
         Counter64,
      pr1645v2Lan2MCPPPoEMCH2PIfInMCPkts
         Counter64,
      pr1645v2Lan2MCPPPoEMCH2PIfInDiscards
         Counter64,
      pr1645v2Lan2MCPPPoEMCH2PIfInErrors
         Counter64,
      pr1645v2Lan2MCPPPoEMCH2PIfInUnkwn
         Counter64,
      pr1645v2Lan2MCPPPoEMCH2PInDropEx
         Counter64,
      pr1645v2Lan2MCPPPoEMCH2PInDropNoMac
         Counter64,
      pr1645v2Lan2MCPPPoEMCH2PInDropNUCast
         Counter64,
      pr1645v2Lan2MCPPPoEMCH2PInDropFilter
         Counter64,
      pr1645v2Lan2MCPPPoEMCH2PIfInBandwidth
         Integer32,
      pr1645v2Lan2MCPPPoEMCH2PIfOutOctets
         Counter64,
      pr1645v2Lan2MCPPPoEMCH2PIfOutUCPkts
         Counter64,
      pr1645v2Lan2MCPPPoEMCH2PIfOutNUCPkts
         Counter64,
      pr1645v2Lan2MCPPPoEMCH2PIfOutBCPkts
         Counter64,
      pr1645v2Lan2MCPPPoEMCH2PIfOutMCPkts
         Counter64,
      pr1645v2Lan2MCPPPoEMCH2PIfOutDiscards
         Counter64,
      pr1645v2Lan2MCPPPoEMCH2PIfOutErrors
         Counter64,
      pr1645v2Lan2MCPPPoEMCH2POutDropEx
         Counter64,
      pr1645v2Lan2MCPPPoEMCH2POutDropNoArp
         Counter64,
      pr1645v2Lan2MCPPPoEMCH2POutDropFilter
         Counter64,
      pr1645v2Lan2MCPPPoEMCH2PIfOutBandwidth
         Integer32,
      pr1645v2Lan2MCPPPoEMCH2PIfErrSec
         Counter32
      }

pr1645v2Lan2MCPPPoEMCH2PTableIx OBJECT-TYPE
   SYNTAX      TableIndex
   MAX-ACCESS  not-accessible
   STATUS      current
   DESCRIPTION
      ""
   ::= {pr1645v2Lan2MCPPPoEMCH2PEntry 11}

pr1645v2Lan2MCPPPoEMCH2PSysUpTime OBJECT-TYPE
   SYNTAX      TimeTicks
   MAX-ACCESS  read-only
   STATUS      current
   DESCRIPTION
      "Path: ethernet2.performance.pppoEClient.mibCounters.h2Performance.sysUpTime

       Time in centi-second."
   ::= {pr1645v2Lan2MCPPPoEMCH2PEntry 16777216}

pr1645v2Lan2MCPPPoEMCH2PIfUpTime OBJECT-TYPE
   SYNTAX      TimeTicks
   MAX-ACCESS  read-only
   STATUS      current
   DESCRIPTION
      "Path: ethernet2.performance.pppoEClient.mibCounters.h2Performance.ifUpTime

       Time in centi-second."
   ::= {pr1645v2Lan2MCPPPoEMCH2PEntry 33554432}

pr1645v2Lan2MCPPPoEMCH2PIfStatChanges OBJECT-TYPE
   SYNTAX      Counter32
   MAX-ACCESS  read-only
   STATUS      current
   DESCRIPTION
      "Path: ethernet2.performance.pppoEClient.mibCounters.h2Performance.ifStatusChanges

       32 bit unsigned wrappable counter."
   ::= {pr1645v2Lan2MCPPPoEMCH2PEntry 50331648}

pr1645v2Lan2MCPPPoEMCH2PIfInOctets OBJECT-TYPE
   SYNTAX      Counter64
   MAX-ACCESS  read-only
   STATUS      current
   DESCRIPTION
      "Path: ethernet2.performance.pppoEClient.mibCounters.h2Performance.ifInOctets

       64 bit unsigned wrappable counter."
   ::= {pr1645v2Lan2MCPPPoEMCH2PEntry 67108864}

pr1645v2Lan2MCPPPoEMCH2PIfInUCPkts OBJECT-TYPE
   SYNTAX      Counter64
   MAX-ACCESS  read-only
   STATUS      current
   DESCRIPTION
      "Path: ethernet2.performance.pppoEClient.mibCounters.h2Performance.ifInUcastPkts

       64 bit unsigned wrappable counter."
   ::= {pr1645v2Lan2MCPPPoEMCH2PEntry 83886080}

pr1645v2Lan2MCPPPoEMCH2PIfInNUCPkts OBJECT-TYPE
   SYNTAX      Counter64
   MAX-ACCESS  read-only
   STATUS      current
   DESCRIPTION
      "Path: ethernet2.performance.pppoEClient.mibCounters.h2Performance.ifInNUcastPkts

       64 bit unsigned wrappable counter."
   ::= {pr1645v2Lan2MCPPPoEMCH2PEntry 100663296}

pr1645v2Lan2MCPPPoEMCH2PIfInBCPkts OBJECT-TYPE
   SYNTAX      Counter64
   MAX-ACCESS  read-only
   STATUS      current
   DESCRIPTION
      "Path: ethernet2.performance.pppoEClient.mibCounters.h2Performance.ifInBcastPkts

       64 bit unsigned wrappable counter."
   ::= {pr1645v2Lan2MCPPPoEMCH2PEntry 419430400}

pr1645v2Lan2MCPPPoEMCH2PIfInMCPkts OBJECT-TYPE
   SYNTAX      Counter64
   MAX-ACCESS  read-only
   STATUS      current
   DESCRIPTION
      "Path: ethernet2.performance.pppoEClient.mibCounters.h2Performance.ifInMcastPkts

       64 bit unsigned wrappable counter."
   ::= {pr1645v2Lan2MCPPPoEMCH2PEntry 436207616}

pr1645v2Lan2MCPPPoEMCH2PIfInDiscards OBJECT-TYPE
   SYNTAX      Counter64
   MAX-ACCESS  read-only
   STATUS      current
   DESCRIPTION
      "Path: ethernet2.performance.pppoEClient.mibCounters.h2Performance.ifInDiscards

       64 bit unsigned wrappable counter."
   ::= {pr1645v2Lan2MCPPPoEMCH2PEntry 117440512}

pr1645v2Lan2MCPPPoEMCH2PIfInErrors OBJECT-TYPE
   SYNTAX      Counter64
   MAX-ACCESS  read-only
   STATUS      current
   DESCRIPTION
      "Path: ethernet2.performance.pppoEClient.mibCounters.h2Performance.ifInErrors

       64 bit unsigned wrappable counter."
   ::= {pr1645v2Lan2MCPPPoEMCH2PEntry 134217728}

pr1645v2Lan2MCPPPoEMCH2PIfInUnkwn OBJECT-TYPE
   SYNTAX      Counter64
   MAX-ACCESS  read-only
   STATUS      current
   DESCRIPTION
      "Path: ethernet2.performance.pppoEClient.mibCounters.h2Performance.ifInUnknownProtos

       64 bit unsigned wrappable counter."
   ::= {pr1645v2Lan2MCPPPoEMCH2PEntry 150994944}

pr1645v2Lan2MCPPPoEMCH2PInDropEx OBJECT-TYPE
   SYNTAX      Counter64
   MAX-ACCESS  read-only
   STATUS      current
   DESCRIPTION
      "Path: ethernet2.performance.pppoEClient.mibCounters.h2Performance.ifInDropLevelExceeded

       64 bit unsigned wrappable counter."
   ::= {pr1645v2Lan2MCPPPoEMCH2PEntry 335544320}

pr1645v2Lan2MCPPPoEMCH2PInDropNoMac OBJECT-TYPE
   SYNTAX      Counter64
   MAX-ACCESS  read-only
   STATUS      current
   DESCRIPTION
      "Path: ethernet2.performance.pppoEClient.mibCounters.h2Performance.fInDiscardsNoMacFit

       64 bit unsigned wrappable counter."
   ::= {pr1645v2Lan2MCPPPoEMCH2PEntry 301989888}

pr1645v2Lan2MCPPPoEMCH2PInDropNUCast OBJECT-TYPE
   SYNTAX      Counter64
   MAX-ACCESS  read-only
   STATUS      current
   DESCRIPTION
      "Path: ethernet2.performance.pppoEClient.mibCounters.h2Performance.fInDiscardsNUCast

       64 bit unsigned wrappable counter."
   ::= {pr1645v2Lan2MCPPPoEMCH2PEntry 318767104}

pr1645v2Lan2MCPPPoEMCH2PInDropFilter OBJECT-TYPE
   SYNTAX      Counter64
   MAX-ACCESS  read-only
   STATUS      current
   DESCRIPTION
      "Path: ethernet2.performance.pppoEClient.mibCounters.h2Performance.fInDiscardsFilter

       64 bit unsigned wrappable counter."
   ::= {pr1645v2Lan2MCPPPoEMCH2PEntry 385875968}

pr1645v2Lan2MCPPPoEMCH2PIfInBandwidth OBJECT-TYPE
   SYNTAX      Integer32
   MAX-ACCESS  read-only
   STATUS      current
   DESCRIPTION
      "Path: ethernet2.performance.pppoEClient.mibCounters.h2Performance.ifInBandwidth

       unit name = bps
       formula = 8 * ; 8 /"
   ::= {pr1645v2Lan2MCPPPoEMCH2PEntry 268435456}

pr1645v2Lan2MCPPPoEMCH2PIfOutOctets OBJECT-TYPE
   SYNTAX      Counter64
   MAX-ACCESS  read-only
   STATUS      current
   DESCRIPTION
      "Path: ethernet2.performance.pppoEClient.mibCounters.h2Performance.ifOutOctets

       64 bit unsigned wrappable counter."
   ::= {pr1645v2Lan2MCPPPoEMCH2PEntry 167772160}

pr1645v2Lan2MCPPPoEMCH2PIfOutUCPkts OBJECT-TYPE
   SYNTAX      Counter64
   MAX-ACCESS  read-only
   STATUS      current
   DESCRIPTION
      "Path: ethernet2.performance.pppoEClient.mibCounters.h2Performance.ifOutUcastPkts

       64 bit unsigned wrappable counter."
   ::= {pr1645v2Lan2MCPPPoEMCH2PEntry 184549376}

pr1645v2Lan2MCPPPoEMCH2PIfOutNUCPkts OBJECT-TYPE
   SYNTAX      Counter64
   MAX-ACCESS  read-only
   STATUS      current
   DESCRIPTION
      "Path: ethernet2.performance.pppoEClient.mibCounters.h2Performance.ifOutNUcastPkts

       64 bit unsigned wrappable counter."
   ::= {pr1645v2Lan2MCPPPoEMCH2PEntry 201326592}

pr1645v2Lan2MCPPPoEMCH2PIfOutBCPkts OBJECT-TYPE
   SYNTAX      Counter64
   MAX-ACCESS  read-only
   STATUS      current
   DESCRIPTION
      "Path: ethernet2.performance.pppoEClient.mibCounters.h2Performance.ifOutBcastPkts

       64 bit unsigned wrappable counter."
   ::= {pr1645v2Lan2MCPPPoEMCH2PEntry 452984832}

pr1645v2Lan2MCPPPoEMCH2PIfOutMCPkts OBJECT-TYPE
   SYNTAX      Counter64
   MAX-ACCESS  read-only
   STATUS      current
   DESCRIPTION
      "Path: ethernet2.performance.pppoEClient.mibCounters.h2Performance.ifOutMcastPkts

       64 bit unsigned wrappable counter."
   ::= {pr1645v2Lan2MCPPPoEMCH2PEntry 469762048}

pr1645v2Lan2MCPPPoEMCH2PIfOutDiscards OBJECT-TYPE
   SYNTAX      Counter64
   MAX-ACCESS  read-only
   STATUS      current
   DESCRIPTION
      "Path: ethernet2.performance.pppoEClient.mibCounters.h2Performance.ifOutDiscards

       64 bit unsigned wrappable counter."
   ::= {pr1645v2Lan2MCPPPoEMCH2PEntry 218103808}

pr1645v2Lan2MCPPPoEMCH2PIfOutErrors OBJECT-TYPE
   SYNTAX      Counter64
   MAX-ACCESS  read-only
   STATUS      current
   DESCRIPTION
      "Path: ethernet2.performance.pppoEClient.mibCounters.h2Performance.ifOutErrors

       64 bit unsigned wrappable counter."
   ::= {pr1645v2Lan2MCPPPoEMCH2PEntry 234881024}

pr1645v2Lan2MCPPPoEMCH2POutDropEx OBJECT-TYPE
   SYNTAX      Counter64
   MAX-ACCESS  read-only
   STATUS      current
   DESCRIPTION
      "Path: ethernet2.performance.pppoEClient.mibCounters.h2Performance.ifOutDropLevelExceeded

       64 bit unsigned wrappable counter."
   ::= {pr1645v2Lan2MCPPPoEMCH2PEntry 352321536}

pr1645v2Lan2MCPPPoEMCH2POutDropNoArp OBJECT-TYPE
   SYNTAX      Counter64
   MAX-ACCESS  read-only
   STATUS      current
   DESCRIPTION
      "Path: ethernet2.performance.pppoEClient.mibCounters.h2Performance.ifOutDiscardsNoArp

       64 bit unsigned wrappable counter."
   ::= {pr1645v2Lan2MCPPPoEMCH2PEntry 369098752}

pr1645v2Lan2MCPPPoEMCH2POutDropFilter OBJECT-TYPE
   SYNTAX      Counter64
   MAX-ACCESS  read-only
   STATUS      current
   DESCRIPTION
      "Path: ethernet2.performance.pppoEClient.mibCounters.h2Performance.ifOutDiscardsFilter

       64 bit unsigned wrappable counter."
   ::= {pr1645v2Lan2MCPPPoEMCH2PEntry 402653184}

pr1645v2Lan2MCPPPoEMCH2PIfOutBandwidth OBJECT-TYPE
   SYNTAX      Integer32
   MAX-ACCESS  read-only
   STATUS      current
   DESCRIPTION
      "Path: ethernet2.performance.pppoEClient.mibCounters.h2Performance.ifOutBandwidth

       unit name = bps
       formula = 8 * ; 8 /"
   ::= {pr1645v2Lan2MCPPPoEMCH2PEntry 285212672}

pr1645v2Lan2MCPPPoEMCH2PIfErrSec OBJECT-TYPE
   SYNTAX      Counter32
   MAX-ACCESS  read-only
   STATUS      current
   DESCRIPTION
      "Path: ethernet2.performance.pppoEClient.mibCounters.h2Performance.ifErrSec

       32 bit unsigned wrappable counter."
   ::= {pr1645v2Lan2MCPPPoEMCH2PEntry 251658240}

pr1645v2Lan2MCPPPoEMCH24P OBJECT-TYPE
   SYNTAX      SEQUENCE OF Pr1645v2Lan2MCPPPoEMCH24PEntry
   MAX-ACCESS  not-accessible
   STATUS      current
   DESCRIPTION
      ""
   ::= {pr1645v2Lan2MCPPPoE 41615360}

pr1645v2Lan2MCPPPoEMCH24PEntry OBJECT-TYPE
   SYNTAX      Pr1645v2Lan2MCPPPoEMCH24PEntry
   MAX-ACCESS  not-accessible
   STATUS      current
   DESCRIPTION
      ""
   INDEX      { pr1645v2Lan2MCPPPoETableIx,
                pr1645v2Lan2MCPPPoEMCH24PTableIx }
   ::= {pr1645v2Lan2MCPPPoEMCH24P 1}

Pr1645v2Lan2MCPPPoEMCH24PEntry ::=
   SEQUENCE
      {
      pr1645v2Lan2MCPPPoEMCH24PTableIx
         TableIndex,
      pr1645v2Lan2MCPPPoEMCH24PSysUpTime
         TimeTicks,
      pr1645v2Lan2MCPPPoEMCH24PIfUpTime
         TimeTicks,
      pr1645v2Lan2MCPPPoEMCH24PIfStatChanges
         Counter32,
      pr1645v2Lan2MCPPPoEMCH24PIfInOctets
         Counter64,
      pr1645v2Lan2MCPPPoEMCH24PIfInUCPkts
         Counter64,
      pr1645v2Lan2MCPPPoEMCH24PIfInNUCPkts
         Counter64,
      pr1645v2Lan2MCPPPoEMCH24PIfInBCPkts
         Counter64,
      pr1645v2Lan2MCPPPoEMCH24PIfInMCPkts
         Counter64,
      pr1645v2Lan2MCPPPoEMCH24PIfInDiscards
         Counter64,
      pr1645v2Lan2MCPPPoEMCH24PIfInErrors
         Counter64,
      pr1645v2Lan2MCPPPoEMCH24PIfInUnkwn
         Counter64,
      pr1645v2Lan2MCPPPoEMCH24PInDropEx
         Counter64,
      pr1645v2Lan2MCPPPoEMCH24PInDropNoMac
         Counter64,
      pr1645v2Lan2MCPPPoEMCH24PInDropNUCast
         Counter64,
      pr1645v2Lan2MCPPPoEMCH24PInDropFilter
         Counter64,
      pr1645v2Lan2MCPPPoEMCH24PIfInBandwidth
         Integer32,
      pr1645v2Lan2MCPPPoEMCH24PIfOutOctets
         Counter64,
      pr1645v2Lan2MCPPPoEMCH24PIfOutUCPkts
         Counter64,
      pr1645v2Lan2MCPPPoEMCH24PIfOutNUCPkts
         Counter64,
      pr1645v2Lan2MCPPPoEMCH24PIfOutBCPkts
         Counter64,
      pr1645v2Lan2MCPPPoEMCH24PIfOutMCPkts
         Counter64,
      pr1645v2Lan2MCPPPoEMCH24PIfOutDiscards
         Counter64,
      pr1645v2Lan2MCPPPoEMCH24PIfOutErrors
         Counter64,
      pr1645v2Lan2MCPPPoEMCH24POutDropEx
         Counter64,
      pr1645v2Lan2MCPPPoEMCH24POutDropNoArp
         Counter64,
      pr1645v2Lan2MCPPPoEMCH24POutDropFilter
         Counter64,
      pr1645v2Lan2MCPPPoEMCH24PIfOutBandwidth
         Integer32,
      pr1645v2Lan2MCPPPoEMCH24PIfErrSec
         Counter32
      }

pr1645v2Lan2MCPPPoEMCH24PTableIx OBJECT-TYPE
   SYNTAX      TableIndex
   MAX-ACCESS  not-accessible
   STATUS      current
   DESCRIPTION
      ""
   ::= {pr1645v2Lan2MCPPPoEMCH24PEntry 11}

pr1645v2Lan2MCPPPoEMCH24PSysUpTime OBJECT-TYPE
   SYNTAX      TimeTicks
   MAX-ACCESS  read-only
   STATUS      current
   DESCRIPTION
      "Path: ethernet2.performance.pppoEClient.mibCounters.h24Performance.sysUpTime

       Time in centi-second."
   ::= {pr1645v2Lan2MCPPPoEMCH24PEntry 16777216}

pr1645v2Lan2MCPPPoEMCH24PIfUpTime OBJECT-TYPE
   SYNTAX      TimeTicks
   MAX-ACCESS  read-only
   STATUS      current
   DESCRIPTION
      "Path: ethernet2.performance.pppoEClient.mibCounters.h24Performance.ifUpTime

       Time in centi-second."
   ::= {pr1645v2Lan2MCPPPoEMCH24PEntry 33554432}

pr1645v2Lan2MCPPPoEMCH24PIfStatChanges OBJECT-TYPE
   SYNTAX      Counter32
   MAX-ACCESS  read-only
   STATUS      current
   DESCRIPTION
      "Path: ethernet2.performance.pppoEClient.mibCounters.h24Performance.ifStatusChanges

       32 bit unsigned wrappable counter."
   ::= {pr1645v2Lan2MCPPPoEMCH24PEntry 50331648}

pr1645v2Lan2MCPPPoEMCH24PIfInOctets OBJECT-TYPE
   SYNTAX      Counter64
   MAX-ACCESS  read-only
   STATUS      current
   DESCRIPTION
      "Path: ethernet2.performance.pppoEClient.mibCounters.h24Performance.ifInOctets

       64 bit unsigned wrappable counter."
   ::= {pr1645v2Lan2MCPPPoEMCH24PEntry 67108864}

pr1645v2Lan2MCPPPoEMCH24PIfInUCPkts OBJECT-TYPE
   SYNTAX      Counter64
   MAX-ACCESS  read-only
   STATUS      current
   DESCRIPTION
      "Path: ethernet2.performance.pppoEClient.mibCounters.h24Performance.ifInUcastPkts

       64 bit unsigned wrappable counter."
   ::= {pr1645v2Lan2MCPPPoEMCH24PEntry 83886080}

pr1645v2Lan2MCPPPoEMCH24PIfInNUCPkts OBJECT-TYPE
   SYNTAX      Counter64
   MAX-ACCESS  read-only
   STATUS      current
   DESCRIPTION
      "Path: ethernet2.performance.pppoEClient.mibCounters.h24Performance.ifInNUcastPkts

       64 bit unsigned wrappable counter."
   ::= {pr1645v2Lan2MCPPPoEMCH24PEntry 100663296}

pr1645v2Lan2MCPPPoEMCH24PIfInBCPkts OBJECT-TYPE
   SYNTAX      Counter64
   MAX-ACCESS  read-only
   STATUS      current
   DESCRIPTION
      "Path: ethernet2.performance.pppoEClient.mibCounters.h24Performance.ifInBcastPkts

       64 bit unsigned wrappable counter."
   ::= {pr1645v2Lan2MCPPPoEMCH24PEntry 419430400}

pr1645v2Lan2MCPPPoEMCH24PIfInMCPkts OBJECT-TYPE
   SYNTAX      Counter64
   MAX-ACCESS  read-only
   STATUS      current
   DESCRIPTION
      "Path: ethernet2.performance.pppoEClient.mibCounters.h24Performance.ifInMcastPkts

       64 bit unsigned wrappable counter."
   ::= {pr1645v2Lan2MCPPPoEMCH24PEntry 436207616}

pr1645v2Lan2MCPPPoEMCH24PIfInDiscards OBJECT-TYPE
   SYNTAX      Counter64
   MAX-ACCESS  read-only
   STATUS      current
   DESCRIPTION
      "Path: ethernet2.performance.pppoEClient.mibCounters.h24Performance.ifInDiscards

       64 bit unsigned wrappable counter."
   ::= {pr1645v2Lan2MCPPPoEMCH24PEntry 117440512}

pr1645v2Lan2MCPPPoEMCH24PIfInErrors OBJECT-TYPE
   SYNTAX      Counter64
   MAX-ACCESS  read-only
   STATUS      current
   DESCRIPTION
      "Path: ethernet2.performance.pppoEClient.mibCounters.h24Performance.ifInErrors

       64 bit unsigned wrappable counter."
   ::= {pr1645v2Lan2MCPPPoEMCH24PEntry 134217728}

pr1645v2Lan2MCPPPoEMCH24PIfInUnkwn OBJECT-TYPE
   SYNTAX      Counter64
   MAX-ACCESS  read-only
   STATUS      current
   DESCRIPTION
      "Path: ethernet2.performance.pppoEClient.mibCounters.h24Performance.ifInUnknownProtos

       64 bit unsigned wrappable counter."
   ::= {pr1645v2Lan2MCPPPoEMCH24PEntry 150994944}

pr1645v2Lan2MCPPPoEMCH24PInDropEx OBJECT-TYPE
   SYNTAX      Counter64
   MAX-ACCESS  read-only
   STATUS      current
   DESCRIPTION
      "Path: ethernet2.performance.pppoEClient.mibCounters.h24Performance.ifInDropLevelExceeded

       64 bit unsigned wrappable counter."
   ::= {pr1645v2Lan2MCPPPoEMCH24PEntry 335544320}

pr1645v2Lan2MCPPPoEMCH24PInDropNoMac OBJECT-TYPE
   SYNTAX      Counter64
   MAX-ACCESS  read-only
   STATUS      current
   DESCRIPTION
      "Path: ethernet2.performance.pppoEClient.mibCounters.h24Performance.fInDiscardsNoMacFit

       64 bit unsigned wrappable counter."
   ::= {pr1645v2Lan2MCPPPoEMCH24PEntry 301989888}

pr1645v2Lan2MCPPPoEMCH24PInDropNUCast OBJECT-TYPE
   SYNTAX      Counter64
   MAX-ACCESS  read-only
   STATUS      current
   DESCRIPTION
      "Path: ethernet2.performance.pppoEClient.mibCounters.h24Performance.fInDiscardsNUCast

       64 bit unsigned wrappable counter."
   ::= {pr1645v2Lan2MCPPPoEMCH24PEntry 318767104}

pr1645v2Lan2MCPPPoEMCH24PInDropFilter OBJECT-TYPE
   SYNTAX      Counter64
   MAX-ACCESS  read-only
   STATUS      current
   DESCRIPTION
      "Path: ethernet2.performance.pppoEClient.mibCounters.h24Performance.fInDiscardsFilter

       64 bit unsigned wrappable counter."
   ::= {pr1645v2Lan2MCPPPoEMCH24PEntry 385875968}

pr1645v2Lan2MCPPPoEMCH24PIfInBandwidth OBJECT-TYPE
   SYNTAX      Integer32
   MAX-ACCESS  read-only
   STATUS      current
   DESCRIPTION
      "Path: ethernet2.performance.pppoEClient.mibCounters.h24Performance.ifInBandwidth

       unit name = bps
       formula = 8 * ; 8 /"
   ::= {pr1645v2Lan2MCPPPoEMCH24PEntry 268435456}

pr1645v2Lan2MCPPPoEMCH24PIfOutOctets OBJECT-TYPE
   SYNTAX      Counter64
   MAX-ACCESS  read-only
   STATUS      current
   DESCRIPTION
      "Path: ethernet2.performance.pppoEClient.mibCounters.h24Performance.ifOutOctets

       64 bit unsigned wrappable counter."
   ::= {pr1645v2Lan2MCPPPoEMCH24PEntry 167772160}

pr1645v2Lan2MCPPPoEMCH24PIfOutUCPkts OBJECT-TYPE
   SYNTAX      Counter64
   MAX-ACCESS  read-only
   STATUS      current
   DESCRIPTION
      "Path: ethernet2.performance.pppoEClient.mibCounters.h24Performance.ifOutUcastPkts

       64 bit unsigned wrappable counter."
   ::= {pr1645v2Lan2MCPPPoEMCH24PEntry 184549376}

pr1645v2Lan2MCPPPoEMCH24PIfOutNUCPkts OBJECT-TYPE
   SYNTAX      Counter64
   MAX-ACCESS  read-only
   STATUS      current
   DESCRIPTION
      "Path: ethernet2.performance.pppoEClient.mibCounters.h24Performance.ifOutNUcastPkts

       64 bit unsigned wrappable counter."
   ::= {pr1645v2Lan2MCPPPoEMCH24PEntry 201326592}

pr1645v2Lan2MCPPPoEMCH24PIfOutBCPkts OBJECT-TYPE
   SYNTAX      Counter64
   MAX-ACCESS  read-only
   STATUS      current
   DESCRIPTION
      "Path: ethernet2.performance.pppoEClient.mibCounters.h24Performance.ifOutBcastPkts

       64 bit unsigned wrappable counter."
   ::= {pr1645v2Lan2MCPPPoEMCH24PEntry 452984832}

pr1645v2Lan2MCPPPoEMCH24PIfOutMCPkts OBJECT-TYPE
   SYNTAX      Counter64
   MAX-ACCESS  read-only
   STATUS      current
   DESCRIPTION
      "Path: ethernet2.performance.pppoEClient.mibCounters.h24Performance.ifOutMcastPkts

       64 bit unsigned wrappable counter."
   ::= {pr1645v2Lan2MCPPPoEMCH24PEntry 469762048}

pr1645v2Lan2MCPPPoEMCH24PIfOutDiscards OBJECT-TYPE
   SYNTAX      Counter64
   MAX-ACCESS  read-only
   STATUS      current
   DESCRIPTION
      "Path: ethernet2.performance.pppoEClient.mibCounters.h24Performance.ifOutDiscards

       64 bit unsigned wrappable counter."
   ::= {pr1645v2Lan2MCPPPoEMCH24PEntry 218103808}

pr1645v2Lan2MCPPPoEMCH24PIfOutErrors OBJECT-TYPE
   SYNTAX      Counter64
   MAX-ACCESS  read-only
   STATUS      current
   DESCRIPTION
      "Path: ethernet2.performance.pppoEClient.mibCounters.h24Performance.ifOutErrors

       64 bit unsigned wrappable counter."
   ::= {pr1645v2Lan2MCPPPoEMCH24PEntry 234881024}

pr1645v2Lan2MCPPPoEMCH24POutDropEx OBJECT-TYPE
   SYNTAX      Counter64
   MAX-ACCESS  read-only
   STATUS      current
   DESCRIPTION
      "Path: ethernet2.performance.pppoEClient.mibCounters.h24Performance.ifOutDropLevelExceeded

       64 bit unsigned wrappable counter."
   ::= {pr1645v2Lan2MCPPPoEMCH24PEntry 352321536}

pr1645v2Lan2MCPPPoEMCH24POutDropNoArp OBJECT-TYPE
   SYNTAX      Counter64
   MAX-ACCESS  read-only
   STATUS      current
   DESCRIPTION
      "Path: ethernet2.performance.pppoEClient.mibCounters.h24Performance.ifOutDiscardsNoArp

       64 bit unsigned wrappable counter."
   ::= {pr1645v2Lan2MCPPPoEMCH24PEntry 369098752}

pr1645v2Lan2MCPPPoEMCH24POutDropFilter OBJECT-TYPE
   SYNTAX      Counter64
   MAX-ACCESS  read-only
   STATUS      current
   DESCRIPTION
      "Path: ethernet2.performance.pppoEClient.mibCounters.h24Performance.ifOutDiscardsFilter

       64 bit unsigned wrappable counter."
   ::= {pr1645v2Lan2MCPPPoEMCH24PEntry 402653184}

pr1645v2Lan2MCPPPoEMCH24PIfOutBandwidth OBJECT-TYPE
   SYNTAX      Integer32
   MAX-ACCESS  read-only
   STATUS      current
   DESCRIPTION
      "Path: ethernet2.performance.pppoEClient.mibCounters.h24Performance.ifOutBandwidth

       unit name = bps
       formula = 8 * ; 8 /"
   ::= {pr1645v2Lan2MCPPPoEMCH24PEntry 285212672}

pr1645v2Lan2MCPPPoEMCH24PIfErrSec OBJECT-TYPE
   SYNTAX      Counter32
   MAX-ACCESS  read-only
   STATUS      current
   DESCRIPTION
      "Path: ethernet2.performance.pppoEClient.mibCounters.h24Performance.ifErrSec

       32 bit unsigned wrappable counter."
   ::= {pr1645v2Lan2MCPPPoEMCH24PEntry 251658240}

pr1645v2Lan2MCPPPoEMCD7P OBJECT-TYPE
   SYNTAX      SEQUENCE OF Pr1645v2Lan2MCPPPoEMCD7PEntry
   MAX-ACCESS  not-accessible
   STATUS      current
   DESCRIPTION
      ""
   ::= {pr1645v2Lan2MCPPPoE 41680896}

pr1645v2Lan2MCPPPoEMCD7PEntry OBJECT-TYPE
   SYNTAX      Pr1645v2Lan2MCPPPoEMCD7PEntry
   MAX-ACCESS  not-accessible
   STATUS      current
   DESCRIPTION
      ""
   INDEX      { pr1645v2Lan2MCPPPoETableIx,
                pr1645v2Lan2MCPPPoEMCD7PTableIx }
   ::= {pr1645v2Lan2MCPPPoEMCD7P 1}

Pr1645v2Lan2MCPPPoEMCD7PEntry ::=
   SEQUENCE
      {
      pr1645v2Lan2MCPPPoEMCD7PTableIx
         TableIndex,
      pr1645v2Lan2MCPPPoEMCD7PSysUpTime
         TimeTicks,
      pr1645v2Lan2MCPPPoEMCD7PIfUpTime
         TimeTicks,
      pr1645v2Lan2MCPPPoEMCD7PIfStatChanges
         Counter32,
      pr1645v2Lan2MCPPPoEMCD7PIfInOctets
         Counter64,
      pr1645v2Lan2MCPPPoEMCD7PIfInUCPkts
         Counter64,
      pr1645v2Lan2MCPPPoEMCD7PIfInNUCPkts
         Counter64,
      pr1645v2Lan2MCPPPoEMCD7PIfInBCPkts
         Counter64,
      pr1645v2Lan2MCPPPoEMCD7PIfInMCPkts
         Counter64,
      pr1645v2Lan2MCPPPoEMCD7PIfInDiscards
         Counter64,
      pr1645v2Lan2MCPPPoEMCD7PIfInErrors
         Counter64,
      pr1645v2Lan2MCPPPoEMCD7PIfInUnkwn
         Counter64,
      pr1645v2Lan2MCPPPoEMCD7PInDropEx
         Counter64,
      pr1645v2Lan2MCPPPoEMCD7PInDropNoMac
         Counter64,
      pr1645v2Lan2MCPPPoEMCD7PInDropNUCast
         Counter64,
      pr1645v2Lan2MCPPPoEMCD7PInDropFilter
         Counter64,
      pr1645v2Lan2MCPPPoEMCD7PIfInBandwidth
         Integer32,
      pr1645v2Lan2MCPPPoEMCD7PIfOutOctets
         Counter64,
      pr1645v2Lan2MCPPPoEMCD7PIfOutUCPkts
         Counter64,
      pr1645v2Lan2MCPPPoEMCD7PIfOutNUCPkts
         Counter64,
      pr1645v2Lan2MCPPPoEMCD7PIfOutBCPkts
         Counter64,
      pr1645v2Lan2MCPPPoEMCD7PIfOutMCPkts
         Counter64,
      pr1645v2Lan2MCPPPoEMCD7PIfOutDiscards
         Counter64,
      pr1645v2Lan2MCPPPoEMCD7PIfOutErrors
         Counter64,
      pr1645v2Lan2MCPPPoEMCD7POutDropEx
         Counter64,
      pr1645v2Lan2MCPPPoEMCD7POutDropNoArp
         Counter64,
      pr1645v2Lan2MCPPPoEMCD7POutDropFilter
         Counter64,
      pr1645v2Lan2MCPPPoEMCD7PIfOutBandwidth
         Integer32,
      pr1645v2Lan2MCPPPoEMCD7PIfErrSec
         Counter32
      }

pr1645v2Lan2MCPPPoEMCD7PTableIx OBJECT-TYPE
   SYNTAX      TableIndex
   MAX-ACCESS  not-accessible
   STATUS      current
   DESCRIPTION
      ""
   ::= {pr1645v2Lan2MCPPPoEMCD7PEntry 11}

pr1645v2Lan2MCPPPoEMCD7PSysUpTime OBJECT-TYPE
   SYNTAX      TimeTicks
   MAX-ACCESS  read-only
   STATUS      current
   DESCRIPTION
      "Path: ethernet2.performance.pppoEClient.mibCounters.d7Performance.sysUpTime

       Time in centi-second."
   ::= {pr1645v2Lan2MCPPPoEMCD7PEntry 16777216}

pr1645v2Lan2MCPPPoEMCD7PIfUpTime OBJECT-TYPE
   SYNTAX      TimeTicks
   MAX-ACCESS  read-only
   STATUS      current
   DESCRIPTION
      "Path: ethernet2.performance.pppoEClient.mibCounters.d7Performance.ifUpTime

       Time in centi-second."
   ::= {pr1645v2Lan2MCPPPoEMCD7PEntry 33554432}

pr1645v2Lan2MCPPPoEMCD7PIfStatChanges OBJECT-TYPE
   SYNTAX      Counter32
   MAX-ACCESS  read-only
   STATUS      current
   DESCRIPTION
      "Path: ethernet2.performance.pppoEClient.mibCounters.d7Performance.ifStatusChanges

       32 bit unsigned wrappable counter."
   ::= {pr1645v2Lan2MCPPPoEMCD7PEntry 50331648}

pr1645v2Lan2MCPPPoEMCD7PIfInOctets OBJECT-TYPE
   SYNTAX      Counter64
   MAX-ACCESS  read-only
   STATUS      current
   DESCRIPTION
      "Path: ethernet2.performance.pppoEClient.mibCounters.d7Performance.ifInOctets

       64 bit unsigned wrappable counter."
   ::= {pr1645v2Lan2MCPPPoEMCD7PEntry 67108864}

pr1645v2Lan2MCPPPoEMCD7PIfInUCPkts OBJECT-TYPE
   SYNTAX      Counter64
   MAX-ACCESS  read-only
   STATUS      current
   DESCRIPTION
      "Path: ethernet2.performance.pppoEClient.mibCounters.d7Performance.ifInUcastPkts

       64 bit unsigned wrappable counter."
   ::= {pr1645v2Lan2MCPPPoEMCD7PEntry 83886080}

pr1645v2Lan2MCPPPoEMCD7PIfInNUCPkts OBJECT-TYPE
   SYNTAX      Counter64
   MAX-ACCESS  read-only
   STATUS      current
   DESCRIPTION
      "Path: ethernet2.performance.pppoEClient.mibCounters.d7Performance.ifInNUcastPkts

       64 bit unsigned wrappable counter."
   ::= {pr1645v2Lan2MCPPPoEMCD7PEntry 100663296}

pr1645v2Lan2MCPPPoEMCD7PIfInBCPkts OBJECT-TYPE
   SYNTAX      Counter64
   MAX-ACCESS  read-only
   STATUS      current
   DESCRIPTION
      "Path: ethernet2.performance.pppoEClient.mibCounters.d7Performance.ifInBcastPkts

       64 bit unsigned wrappable counter."
   ::= {pr1645v2Lan2MCPPPoEMCD7PEntry 419430400}

pr1645v2Lan2MCPPPoEMCD7PIfInMCPkts OBJECT-TYPE
   SYNTAX      Counter64
   MAX-ACCESS  read-only
   STATUS      current
   DESCRIPTION
      "Path: ethernet2.performance.pppoEClient.mibCounters.d7Performance.ifInMcastPkts

       64 bit unsigned wrappable counter."
   ::= {pr1645v2Lan2MCPPPoEMCD7PEntry 436207616}

pr1645v2Lan2MCPPPoEMCD7PIfInDiscards OBJECT-TYPE
   SYNTAX      Counter64
   MAX-ACCESS  read-only
   STATUS      current
   DESCRIPTION
      "Path: ethernet2.performance.pppoEClient.mibCounters.d7Performance.ifInDiscards

       64 bit unsigned wrappable counter."
   ::= {pr1645v2Lan2MCPPPoEMCD7PEntry 117440512}

pr1645v2Lan2MCPPPoEMCD7PIfInErrors OBJECT-TYPE
   SYNTAX      Counter64
   MAX-ACCESS  read-only
   STATUS      current
   DESCRIPTION
      "Path: ethernet2.performance.pppoEClient.mibCounters.d7Performance.ifInErrors

       64 bit unsigned wrappable counter."
   ::= {pr1645v2Lan2MCPPPoEMCD7PEntry 134217728}

pr1645v2Lan2MCPPPoEMCD7PIfInUnkwn OBJECT-TYPE
   SYNTAX      Counter64
   MAX-ACCESS  read-only
   STATUS      current
   DESCRIPTION
      "Path: ethernet2.performance.pppoEClient.mibCounters.d7Performance.ifInUnknownProtos

       64 bit unsigned wrappable counter."
   ::= {pr1645v2Lan2MCPPPoEMCD7PEntry 150994944}

pr1645v2Lan2MCPPPoEMCD7PInDropEx OBJECT-TYPE
   SYNTAX      Counter64
   MAX-ACCESS  read-only
   STATUS      current
   DESCRIPTION
      "Path: ethernet2.performance.pppoEClient.mibCounters.d7Performance.ifInDropLevelExceeded

       64 bit unsigned wrappable counter."
   ::= {pr1645v2Lan2MCPPPoEMCD7PEntry 335544320}

pr1645v2Lan2MCPPPoEMCD7PInDropNoMac OBJECT-TYPE
   SYNTAX      Counter64
   MAX-ACCESS  read-only
   STATUS      current
   DESCRIPTION
      "Path: ethernet2.performance.pppoEClient.mibCounters.d7Performance.fInDiscardsNoMacFit

       64 bit unsigned wrappable counter."
   ::= {pr1645v2Lan2MCPPPoEMCD7PEntry 301989888}

pr1645v2Lan2MCPPPoEMCD7PInDropNUCast OBJECT-TYPE
   SYNTAX      Counter64
   MAX-ACCESS  read-only
   STATUS      current
   DESCRIPTION
      "Path: ethernet2.performance.pppoEClient.mibCounters.d7Performance.fInDiscardsNUCast

       64 bit unsigned wrappable counter."
   ::= {pr1645v2Lan2MCPPPoEMCD7PEntry 318767104}

pr1645v2Lan2MCPPPoEMCD7PInDropFilter OBJECT-TYPE
   SYNTAX      Counter64
   MAX-ACCESS  read-only
   STATUS      current
   DESCRIPTION
      "Path: ethernet2.performance.pppoEClient.mibCounters.d7Performance.fInDiscardsFilter

       64 bit unsigned wrappable counter."
   ::= {pr1645v2Lan2MCPPPoEMCD7PEntry 385875968}

pr1645v2Lan2MCPPPoEMCD7PIfInBandwidth OBJECT-TYPE
   SYNTAX      Integer32
   MAX-ACCESS  read-only
   STATUS      current
   DESCRIPTION
      "Path: ethernet2.performance.pppoEClient.mibCounters.d7Performance.ifInBandwidth

       unit name = bps
       formula = 8 * ; 8 /"
   ::= {pr1645v2Lan2MCPPPoEMCD7PEntry 268435456}

pr1645v2Lan2MCPPPoEMCD7PIfOutOctets OBJECT-TYPE
   SYNTAX      Counter64
   MAX-ACCESS  read-only
   STATUS      current
   DESCRIPTION
      "Path: ethernet2.performance.pppoEClient.mibCounters.d7Performance.ifOutOctets

       64 bit unsigned wrappable counter."
   ::= {pr1645v2Lan2MCPPPoEMCD7PEntry 167772160}

pr1645v2Lan2MCPPPoEMCD7PIfOutUCPkts OBJECT-TYPE
   SYNTAX      Counter64
   MAX-ACCESS  read-only
   STATUS      current
   DESCRIPTION
      "Path: ethernet2.performance.pppoEClient.mibCounters.d7Performance.ifOutUcastPkts

       64 bit unsigned wrappable counter."
   ::= {pr1645v2Lan2MCPPPoEMCD7PEntry 184549376}

pr1645v2Lan2MCPPPoEMCD7PIfOutNUCPkts OBJECT-TYPE
   SYNTAX      Counter64
   MAX-ACCESS  read-only
   STATUS      current
   DESCRIPTION
      "Path: ethernet2.performance.pppoEClient.mibCounters.d7Performance.ifOutNUcastPkts

       64 bit unsigned wrappable counter."
   ::= {pr1645v2Lan2MCPPPoEMCD7PEntry 201326592}

pr1645v2Lan2MCPPPoEMCD7PIfOutBCPkts OBJECT-TYPE
   SYNTAX      Counter64
   MAX-ACCESS  read-only
   STATUS      current
   DESCRIPTION
      "Path: ethernet2.performance.pppoEClient.mibCounters.d7Performance.ifOutBcastPkts

       64 bit unsigned wrappable counter."
   ::= {pr1645v2Lan2MCPPPoEMCD7PEntry 452984832}

pr1645v2Lan2MCPPPoEMCD7PIfOutMCPkts OBJECT-TYPE
   SYNTAX      Counter64
   MAX-ACCESS  read-only
   STATUS      current
   DESCRIPTION
      "Path: ethernet2.performance.pppoEClient.mibCounters.d7Performance.ifOutMcastPkts

       64 bit unsigned wrappable counter."
   ::= {pr1645v2Lan2MCPPPoEMCD7PEntry 469762048}

pr1645v2Lan2MCPPPoEMCD7PIfOutDiscards OBJECT-TYPE
   SYNTAX      Counter64
   MAX-ACCESS  read-only
   STATUS      current
   DESCRIPTION
      "Path: ethernet2.performance.pppoEClient.mibCounters.d7Performance.ifOutDiscards

       64 bit unsigned wrappable counter."
   ::= {pr1645v2Lan2MCPPPoEMCD7PEntry 218103808}

pr1645v2Lan2MCPPPoEMCD7PIfOutErrors OBJECT-TYPE
   SYNTAX      Counter64
   MAX-ACCESS  read-only
   STATUS      current
   DESCRIPTION
      "Path: ethernet2.performance.pppoEClient.mibCounters.d7Performance.ifOutErrors

       64 bit unsigned wrappable counter."
   ::= {pr1645v2Lan2MCPPPoEMCD7PEntry 234881024}

pr1645v2Lan2MCPPPoEMCD7POutDropEx OBJECT-TYPE
   SYNTAX      Counter64
   MAX-ACCESS  read-only
   STATUS      current
   DESCRIPTION
      "Path: ethernet2.performance.pppoEClient.mibCounters.d7Performance.ifOutDropLevelExceeded

       64 bit unsigned wrappable counter."
   ::= {pr1645v2Lan2MCPPPoEMCD7PEntry 352321536}

pr1645v2Lan2MCPPPoEMCD7POutDropNoArp OBJECT-TYPE
   SYNTAX      Counter64
   MAX-ACCESS  read-only
   STATUS      current
   DESCRIPTION
      "Path: ethernet2.performance.pppoEClient.mibCounters.d7Performance.ifOutDiscardsNoArp

       64 bit unsigned wrappable counter."
   ::= {pr1645v2Lan2MCPPPoEMCD7PEntry 369098752}

pr1645v2Lan2MCPPPoEMCD7POutDropFilter OBJECT-TYPE
   SYNTAX      Counter64
   MAX-ACCESS  read-only
   STATUS      current
   DESCRIPTION
      "Path: ethernet2.performance.pppoEClient.mibCounters.d7Performance.ifOutDiscardsFilter

       64 bit unsigned wrappable counter."
   ::= {pr1645v2Lan2MCPPPoEMCD7PEntry 402653184}

pr1645v2Lan2MCPPPoEMCD7PIfOutBandwidth OBJECT-TYPE
   SYNTAX      Integer32
   MAX-ACCESS  read-only
   STATUS      current
   DESCRIPTION
      "Path: ethernet2.performance.pppoEClient.mibCounters.d7Performance.ifOutBandwidth

       unit name = bps
       formula = 8 * ; 8 /"
   ::= {pr1645v2Lan2MCPPPoEMCD7PEntry 285212672}

pr1645v2Lan2MCPPPoEMCD7PIfErrSec OBJECT-TYPE
   SYNTAX      Counter32
   MAX-ACCESS  read-only
   STATUS      current
   DESCRIPTION
      "Path: ethernet2.performance.pppoEClient.mibCounters.d7Performance.ifErrSec

       32 bit unsigned wrappable counter."
   ::= {pr1645v2Lan2MCPPPoEMCD7PEntry 251658240}


pr1645v2Lan2MCIfInHwPriorityQueues OBJECT IDENTIFIER ::= {pr1645v2Lan2MC 132}

pr1645v2Lan2MCIfInHwPriorityQueuesSSCTable OBJECT-TYPE
   SYNTAX      SEQUENCE OF Pr1645v2Lan2MCIfInHwPriorityQueuesEntry
   MAX-ACCESS  not-accessible
   STATUS      current
   DESCRIPTION
      "hwPriorityQueues"
   ::= {pr1645v2Lan2MCIfInHwPriorityQueues 1}

pr1645v2Lan2MCIfInHwPriorityQueuesEntry OBJECT-TYPE
   SYNTAX      Pr1645v2Lan2MCIfInHwPriorityQueuesEntry
   MAX-ACCESS  not-accessible
   STATUS      current
   DESCRIPTION
      ""
   INDEX      { pr1645v2Lan2MCIfInHwPriorityQueuesTableIx }
   ::= {pr1645v2Lan2MCIfInHwPriorityQueuesSSCTable 1}

Pr1645v2Lan2MCIfInHwPriorityQueuesEntry ::=
   SEQUENCE
      {
      pr1645v2Lan2MCIfInHwPriorityQueuesTableIx
         TableIndex,
      pr1645v2Lan2MCIfInHwPriorityQueuesName
         INTEGER,
      pr1645v2Lan2MCIfInHwPriorityQueuesLength
         Integer32,
      pr1645v2Lan2MCIfInHwPriorityQueuesPacketsTotal
         Counter64,
      pr1645v2Lan2MCIfInHwPriorityQueuesOctetsTotal
         Counter64,
      pr1645v2Lan2MCIfInHwPriorityQueuesOctetsBandwidth15sec
         Integer32,
      pr1645v2Lan2MCIfInHwPriorityQueuesOctetsBandwidth30sec
         Integer32,
      pr1645v2Lan2MCIfInHwPriorityQueuesOctetsBandwidth1min
         Integer32,
      pr1645v2Lan2MCIfInHwPriorityQueuesOctetsBandwidth2min
         Integer32,
      pr1645v2Lan2MCIfInHwPriorityQueuesOctetsBandwidth5min
         Integer32
      }

pr1645v2Lan2MCIfInHwPriorityQueuesTableIx OBJECT-TYPE
   SYNTAX      TableIndex
   MAX-ACCESS  not-accessible
   STATUS      current
   DESCRIPTION
      ""
   ::= {pr1645v2Lan2MCIfInHwPriorityQueuesEntry 11}

pr1645v2Lan2MCIfInHwPriorityQueuesName OBJECT-TYPE
   SYNTAX      INTEGER
               {
               queue1 (0),
               queue2 (1),
               queue3 (2),
               queue4 (3),
               queue5 (4),
               lowDelayQueue (5),
               lowDelay2Queue (6),
               systemQueue (7),
               queue (8),
               queue1Sum (9),
               queue2Sum (10),
               queue3Sum (11),
               queue4Sum (12),
               queue5Sum (13),
               lowDelayQueueSum (14),
               lowDelay2QueueSum (15),
               systemQueueSum (16),
               queueSum (17),
               queue1Driver (18),
               queue2Driver (19),
               queue3Driver (20),
               queue4Driver (21),
               queue5Driver (22),
               lowDelayQueueDriver (23),
               lowDelay2QueueDriver (24),
               systemQueueDriver (25)
               }
   MAX-ACCESS  read-only
   STATUS      current
   DESCRIPTION
      "Path: ethernet2.performance.ifInHwPriorityQueues.name

       Possibilities:
               queue1   (0)
               queue2   (1)
               queue3   (2)
               queue4   (3)
               queue5   (4)
               lowDelayQueue   (5)
               lowDelay2Queue   (6)
               systemQueue   (7)
               queue   (8)
               queue1Sum   (9)
               queue2Sum   (10)
               queue3Sum   (11)
               queue4Sum   (12)
               queue5Sum   (13)
               lowDelayQueueSum   (14)
               lowDelay2QueueSum   (15)
               systemQueueSum   (16)
               queueSum   (17)
               queue1Driver   (18)
               queue2Driver   (19)
               queue3Driver   (20)
               queue4Driver   (21)
               queue5Driver   (22)
               lowDelayQueueDriver   (23)
               lowDelay2QueueDriver   (24)
               systemQueueDriver   (25)"
   ::= {pr1645v2Lan2MCIfInHwPriorityQueuesEntry 16777216}

pr1645v2Lan2MCIfInHwPriorityQueuesLength OBJECT-TYPE
   SYNTAX      Integer32
   MAX-ACCESS  read-only
   STATUS      current
   DESCRIPTION
      "Path: ethernet2.performance.ifInHwPriorityQueues.length"
   ::= {pr1645v2Lan2MCIfInHwPriorityQueuesEntry 33554432}

pr1645v2Lan2MCIfInHwPriorityQueuesPacketsTotal OBJECT-TYPE
   SYNTAX      Counter64
   MAX-ACCESS  read-only
   STATUS      current
   DESCRIPTION
      "Path: ethernet2.performance.ifInHwPriorityQueues.packets.total

       64 bit unsigned wrappable counter."
   ::= {pr1645v2Lan2MCIfInHwPriorityQueuesEntry 50790400}

pr1645v2Lan2MCIfInHwPriorityQueuesOctetsTotal OBJECT-TYPE
   SYNTAX      Counter64
   MAX-ACCESS  read-only
   STATUS      current
   DESCRIPTION
      "Path: ethernet2.performance.ifInHwPriorityQueues.octets.total

       64 bit unsigned wrappable counter."
   ::= {pr1645v2Lan2MCIfInHwPriorityQueuesEntry 67567616}

pr1645v2Lan2MCIfInHwPriorityQueuesOctetsBandwidth15sec OBJECT-TYPE
   SYNTAX      Integer32
   MAX-ACCESS  read-only
   STATUS      current
   DESCRIPTION
      "Path: ethernet2.performance.ifInHwPriorityQueues.octets.bandwidth.15sec

       unit name = bps
       formula = 8 * ; 8 /"
   ::= {pr1645v2Lan2MCIfInHwPriorityQueuesEntry 70386944}

pr1645v2Lan2MCIfInHwPriorityQueuesOctetsBandwidth30sec OBJECT-TYPE
   SYNTAX      Integer32
   MAX-ACCESS  read-only
   STATUS      current
   DESCRIPTION
      "Path: ethernet2.performance.ifInHwPriorityQueues.octets.bandwidth.30sec

       unit name = bps
       formula = 8 * ; 8 /"
   ::= {pr1645v2Lan2MCIfInHwPriorityQueuesEntry 70388224}

pr1645v2Lan2MCIfInHwPriorityQueuesOctetsBandwidth1min OBJECT-TYPE
   SYNTAX      Integer32
   MAX-ACCESS  read-only
   STATUS      current
   DESCRIPTION
      "Path: ethernet2.performance.ifInHwPriorityQueues.octets.bandwidth.1min

       unit name = bps
       formula = 8 * ; 8 /"
   ::= {pr1645v2Lan2MCIfInHwPriorityQueuesEntry 70390784}

pr1645v2Lan2MCIfInHwPriorityQueuesOctetsBandwidth2min OBJECT-TYPE
   SYNTAX      Integer32
   MAX-ACCESS  read-only
   STATUS      current
   DESCRIPTION
      "Path: ethernet2.performance.ifInHwPriorityQueues.octets.bandwidth.2min

       unit name = bps
       formula = 8 * ; 8 /"
   ::= {pr1645v2Lan2MCIfInHwPriorityQueuesEntry 70395904}

pr1645v2Lan2MCIfInHwPriorityQueuesOctetsBandwidth5min OBJECT-TYPE
   SYNTAX      Integer32
   MAX-ACCESS  read-only
   STATUS      current
   DESCRIPTION
      "Path: ethernet2.performance.ifInHwPriorityQueues.octets.bandwidth.5min

       unit name = bps
       formula = 8 * ; 8 /"
   ::= {pr1645v2Lan2MCIfInHwPriorityQueuesEntry 70411264}

pr1645v2Lan2MCIfInHwPriorityQueuesH2Performance OBJECT-TYPE
   SYNTAX      SEQUENCE OF Pr1645v2Lan2MCIfInHwPriorityQueuesH2PerformanceEntry
   MAX-ACCESS  not-accessible
   STATUS      current
   DESCRIPTION
      ""
   ::= {pr1645v2Lan2MCIfInHwPriorityQueues 83886080}

pr1645v2Lan2MCIfInHwPriorityQueuesH2PerformanceEntry OBJECT-TYPE
   SYNTAX      Pr1645v2Lan2MCIfInHwPriorityQueuesH2PerformanceEntry
   MAX-ACCESS  not-accessible
   STATUS      current
   DESCRIPTION
      ""
   INDEX      { pr1645v2Lan2MCIfInHwPriorityQueuesTableIx,
                pr1645v2Lan2MCIfInHwPriorityQueuesH2PerformanceTableIx }
   ::= {pr1645v2Lan2MCIfInHwPriorityQueuesH2Performance 1}

Pr1645v2Lan2MCIfInHwPriorityQueuesH2PerformanceEntry ::=
   SEQUENCE
      {
      pr1645v2Lan2MCIfInHwPriorityQueuesH2PerformanceTableIx
         TableIndex,
      pr1645v2Lan2MCIfInHwPriorityQueuesH2PerformanceSysUpTime
         TimeTicks,
      pr1645v2Lan2MCIfInHwPriorityQueuesH2PerformanceTotPkts
         Counter64,
      pr1645v2Lan2MCIfInHwPriorityQueuesH2PerformanceTotOcts
         Counter64,
      pr1645v2Lan2MCIfInHwPriorityQueuesH2PerformanceBandwidth
         Integer32
      }

pr1645v2Lan2MCIfInHwPriorityQueuesH2PerformanceTableIx OBJECT-TYPE
   SYNTAX      TableIndex
   MAX-ACCESS  not-accessible
   STATUS      current
   DESCRIPTION
      ""
   ::= {pr1645v2Lan2MCIfInHwPriorityQueuesH2PerformanceEntry 11}

pr1645v2Lan2MCIfInHwPriorityQueuesH2PerformanceSysUpTime OBJECT-TYPE
   SYNTAX      TimeTicks
   MAX-ACCESS  read-only
   STATUS      current
   DESCRIPTION
      "Path: ethernet2.performance.ifInHwPriorityQueues.h2Performance.sysUpTime

       Time in centi-second."
   ::= {pr1645v2Lan2MCIfInHwPriorityQueuesH2PerformanceEntry 16777216}

pr1645v2Lan2MCIfInHwPriorityQueuesH2PerformanceTotPkts OBJECT-TYPE
   SYNTAX      Counter64
   MAX-ACCESS  read-only
   STATUS      current
   DESCRIPTION
      "Path: ethernet2.performance.ifInHwPriorityQueues.h2Performance.totalPkts

       64 bit unsigned wrappable counter."
   ::= {pr1645v2Lan2MCIfInHwPriorityQueuesH2PerformanceEntry 234881024}

pr1645v2Lan2MCIfInHwPriorityQueuesH2PerformanceTotOcts OBJECT-TYPE
   SYNTAX      Counter64
   MAX-ACCESS  read-only
   STATUS      current
   DESCRIPTION
      "Path: ethernet2.performance.ifInHwPriorityQueues.h2Performance.totalOctets

       64 bit unsigned wrappable counter."
   ::= {pr1645v2Lan2MCIfInHwPriorityQueuesH2PerformanceEntry 251658240}

pr1645v2Lan2MCIfInHwPriorityQueuesH2PerformanceBandwidth OBJECT-TYPE
   SYNTAX      Integer32
   MAX-ACCESS  read-only
   STATUS      current
   DESCRIPTION
      "Path: ethernet2.performance.ifInHwPriorityQueues.h2Performance.bandwidth

       unit name = bps
       formula = 8 * ; 8 /"
   ::= {pr1645v2Lan2MCIfInHwPriorityQueuesH2PerformanceEntry 268435456}

pr1645v2Lan2MCIfInHwPriorityQueuesH24Performance OBJECT-TYPE
   SYNTAX      SEQUENCE OF Pr1645v2Lan2MCIfInHwPriorityQueuesH24PerformanceEntry
   MAX-ACCESS  not-accessible
   STATUS      current
   DESCRIPTION
      ""
   ::= {pr1645v2Lan2MCIfInHwPriorityQueues 100663296}

pr1645v2Lan2MCIfInHwPriorityQueuesH24PerformanceEntry OBJECT-TYPE
   SYNTAX      Pr1645v2Lan2MCIfInHwPriorityQueuesH24PerformanceEntry
   MAX-ACCESS  not-accessible
   STATUS      current
   DESCRIPTION
      ""
   INDEX      { pr1645v2Lan2MCIfInHwPriorityQueuesTableIx,
                pr1645v2Lan2MCIfInHwPriorityQueuesH24PerformanceTableIx }
   ::= {pr1645v2Lan2MCIfInHwPriorityQueuesH24Performance 1}

Pr1645v2Lan2MCIfInHwPriorityQueuesH24PerformanceEntry ::=
   SEQUENCE
      {
      pr1645v2Lan2MCIfInHwPriorityQueuesH24PerformanceTableIx
         TableIndex,
      pr1645v2Lan2MCIfInHwPriorityQueuesH24PerformanceSysUpTime
         TimeTicks,
      pr1645v2Lan2MCIfInHwPriorityQueuesH24PerformanceTotPkts
         Counter64,
      pr1645v2Lan2MCIfInHwPriorityQueuesH24PerformanceTotOcts
         Counter64,
      pr1645v2Lan2MCIfInHwPriorityQueuesH24PerformanceBandwidth
         Integer32
      }

pr1645v2Lan2MCIfInHwPriorityQueuesH24PerformanceTableIx OBJECT-TYPE
   SYNTAX      TableIndex
   MAX-ACCESS  not-accessible
   STATUS      current
   DESCRIPTION
      ""
   ::= {pr1645v2Lan2MCIfInHwPriorityQueuesH24PerformanceEntry 11}

pr1645v2Lan2MCIfInHwPriorityQueuesH24PerformanceSysUpTime OBJECT-TYPE
   SYNTAX      TimeTicks
   MAX-ACCESS  read-only
   STATUS      current
   DESCRIPTION
      "Path: ethernet2.performance.ifInHwPriorityQueues.h24Performance.sysUpTime

       Time in centi-second."
   ::= {pr1645v2Lan2MCIfInHwPriorityQueuesH24PerformanceEntry 16777216}

pr1645v2Lan2MCIfInHwPriorityQueuesH24PerformanceTotPkts OBJECT-TYPE
   SYNTAX      Counter64
   MAX-ACCESS  read-only
   STATUS      current
   DESCRIPTION
      "Path: ethernet2.performance.ifInHwPriorityQueues.h24Performance.totalPkts

       64 bit unsigned wrappable counter."
   ::= {pr1645v2Lan2MCIfInHwPriorityQueuesH24PerformanceEntry 234881024}

pr1645v2Lan2MCIfInHwPriorityQueuesH24PerformanceTotOcts OBJECT-TYPE
   SYNTAX      Counter64
   MAX-ACCESS  read-only
   STATUS      current
   DESCRIPTION
      "Path: ethernet2.performance.ifInHwPriorityQueues.h24Performance.totalOctets

       64 bit unsigned wrappable counter."
   ::= {pr1645v2Lan2MCIfInHwPriorityQueuesH24PerformanceEntry 251658240}

pr1645v2Lan2MCIfInHwPriorityQueuesH24PerformanceBandwidth OBJECT-TYPE
   SYNTAX      Integer32
   MAX-ACCESS  read-only
   STATUS      current
   DESCRIPTION
      "Path: ethernet2.performance.ifInHwPriorityQueues.h24Performance.bandwidth

       unit name = bps
       formula = 8 * ; 8 /"
   ::= {pr1645v2Lan2MCIfInHwPriorityQueuesH24PerformanceEntry 268435456}

pr1645v2Lan2MCIfInHwPriorityQueuesD7Performance OBJECT-TYPE
   SYNTAX      SEQUENCE OF Pr1645v2Lan2MCIfInHwPriorityQueuesD7PerformanceEntry
   MAX-ACCESS  not-accessible
   STATUS      current
   DESCRIPTION
      ""
   ::= {pr1645v2Lan2MCIfInHwPriorityQueues 117440512}

pr1645v2Lan2MCIfInHwPriorityQueuesD7PerformanceEntry OBJECT-TYPE
   SYNTAX      Pr1645v2Lan2MCIfInHwPriorityQueuesD7PerformanceEntry
   MAX-ACCESS  not-accessible
   STATUS      current
   DESCRIPTION
      ""
   INDEX      { pr1645v2Lan2MCIfInHwPriorityQueuesTableIx,
                pr1645v2Lan2MCIfInHwPriorityQueuesD7PerformanceTableIx }
   ::= {pr1645v2Lan2MCIfInHwPriorityQueuesD7Performance 1}

Pr1645v2Lan2MCIfInHwPriorityQueuesD7PerformanceEntry ::=
   SEQUENCE
      {
      pr1645v2Lan2MCIfInHwPriorityQueuesD7PerformanceTableIx
         TableIndex,
      pr1645v2Lan2MCIfInHwPriorityQueuesD7PerformanceSysUpTime
         TimeTicks,
      pr1645v2Lan2MCIfInHwPriorityQueuesD7PerformanceTotPkts
         Counter64,
      pr1645v2Lan2MCIfInHwPriorityQueuesD7PerformanceTotOcts
         Counter64,
      pr1645v2Lan2MCIfInHwPriorityQueuesD7PerformanceBandwidth
         Integer32
      }

pr1645v2Lan2MCIfInHwPriorityQueuesD7PerformanceTableIx OBJECT-TYPE
   SYNTAX      TableIndex
   MAX-ACCESS  not-accessible
   STATUS      current
   DESCRIPTION
      ""
   ::= {pr1645v2Lan2MCIfInHwPriorityQueuesD7PerformanceEntry 11}

pr1645v2Lan2MCIfInHwPriorityQueuesD7PerformanceSysUpTime OBJECT-TYPE
   SYNTAX      TimeTicks
   MAX-ACCESS  read-only
   STATUS      current
   DESCRIPTION
      "Path: ethernet2.performance.ifInHwPriorityQueues.d7Performance.sysUpTime

       Time in centi-second."
   ::= {pr1645v2Lan2MCIfInHwPriorityQueuesD7PerformanceEntry 16777216}

pr1645v2Lan2MCIfInHwPriorityQueuesD7PerformanceTotPkts OBJECT-TYPE
   SYNTAX      Counter64
   MAX-ACCESS  read-only
   STATUS      current
   DESCRIPTION
      "Path: ethernet2.performance.ifInHwPriorityQueues.d7Performance.totalPkts

       64 bit unsigned wrappable counter."
   ::= {pr1645v2Lan2MCIfInHwPriorityQueuesD7PerformanceEntry 234881024}

pr1645v2Lan2MCIfInHwPriorityQueuesD7PerformanceTotOcts OBJECT-TYPE
   SYNTAX      Counter64
   MAX-ACCESS  read-only
   STATUS      current
   DESCRIPTION
      "Path: ethernet2.performance.ifInHwPriorityQueues.d7Performance.totalOctets

       64 bit unsigned wrappable counter."
   ::= {pr1645v2Lan2MCIfInHwPriorityQueuesD7PerformanceEntry 251658240}

pr1645v2Lan2MCIfInHwPriorityQueuesD7PerformanceBandwidth OBJECT-TYPE
   SYNTAX      Integer32
   MAX-ACCESS  read-only
   STATUS      current
   DESCRIPTION
      "Path: ethernet2.performance.ifInHwPriorityQueues.d7Performance.bandwidth

       unit name = bps
       formula = 8 * ; 8 /"
   ::= {pr1645v2Lan2MCIfInHwPriorityQueuesD7PerformanceEntry 268435456}



ar1645v2Lan2MC OBJECT IDENTIFIER ::= {r1645v2Lan2MC 16}


ar1645v2Lan2MCClearCounters OBJECT-TYPE
   SYNTAX      Integer32
   MAX-ACCESS  read-write
   STATUS      current
   DESCRIPTION
      "Path: ethernet2.actions.clearCounters
       Info: reset counters"
   ::= {ar1645v2Lan2MC 263}


ar1645v2Lan2MCPowerToggle OBJECT-TYPE
   SYNTAX      Integer32
   MAX-ACCESS  read-write
   STATUS      current
   DESCRIPTION
      "Path: ethernet2.actions.powerToggle
       Info: action in the debug group"
   ::= {ar1645v2Lan2MC 68}


ar1645v2Lan2MCRestartIntf OBJECT-TYPE
   SYNTAX      Integer32
   MAX-ACCESS  read-write
   STATUS      current
   DESCRIPTION
      "Path: ethernet2.actions.restartIntf
       Info: action in the debug group"
   ::= {ar1645v2Lan2MC 67}


ar1645v2Lan2MCClearOamEventLog OBJECT-TYPE
   SYNTAX      Integer32
   MAX-ACCESS  read-write
   STATUS      current
   DESCRIPTION
      "Path: ethernet2.actions.clearOamEventLog
       Info: clear the OAM event log"
   ::= {ar1645v2Lan2MC 916}


ar1645v2Lan2MCLoopback OBJECT-TYPE
   SYNTAX      Integer32
   MAX-ACCESS  read-write
   STATUS      current
   DESCRIPTION
      "Path: ethernet2.actions.loopback
       Info: ethernet loopback"
   ::= {ar1645v2Lan2MC 914}


ar1645v2Lan2MCLoop OBJECT IDENTIFIER ::= {ar1645v2Lan2MC 915}

ar1645v2Lan2MCLoopSSC OBJECT IDENTIFIER ::= {ar1645v2Lan2MCLoop 1}

ar1645v2Lan2MCLoopEntry OBJECT IDENTIFIER ::= {ar1645v2Lan2MCLoopSSC 1}

ar1645v2Lan2MCLoopAction OBJECT-TYPE
   SYNTAX      INTEGER
               {
               start (1),
               stop (2)
               }
   MAX-ACCESS  read-write
   STATUS      current
   DESCRIPTION
      "Path: ethernet2.actions.loop.action

       Possibilities:
               start   (1)
               stop   (2)"
   ::= {ar1645v2Lan2MCLoopEntry 16777216}

ar1645v2Lan2MCLoopTime OBJECT-TYPE
   SYNTAX      TimeTicks
   MAX-ACCESS  read-write
   STATUS      current
   DESCRIPTION
      "Path: ethernet2.actions.loop.time

       Time in centi-second."
   ::= {ar1645v2Lan2MCLoopEntry 50331648}

ar1645v2Lan2MCLoopIntfName OBJECT-TYPE
   SYNTAX      DisplayString
   MAX-ACCESS  read-write
   STATUS      current
   DESCRIPTION
      "Path: ethernet2.actions.loop.intfName"
   ::= {ar1645v2Lan2MCLoopEntry 67108864}


ar1645v2Lan2MCOamRemLoopback OBJECT-TYPE
   SYNTAX      Integer32
   MAX-ACCESS  read-write
   STATUS      current
   DESCRIPTION
      "Path: ethernet2.actions.oamRemLoopback
       Info: OAM Remote Loopback"
   ::= {ar1645v2Lan2MC 912}


ar1645v2Lan2MCType OBJECT-TYPE
   SYNTAX      INTEGER
               {
               start (0),
               stop (1)
               }
   MAX-ACCESS  read-write
   STATUS      current
   DESCRIPTION
      "Path: ethernet2.actions.type
       Info: OAM Remote Loopback type

       Possibilities:
               start   (0)
               stop   (1)"
   ::= {ar1645v2Lan2MC 913}


ar1645v2Lan2MCSendWOL OBJECT-TYPE
   SYNTAX      Integer32
   MAX-ACCESS  read-write
   STATUS      current
   DESCRIPTION
      "Path: ethernet2.actions.sendWOL
       Info: send a WakeOnLan message on this interface"
   ::= {ar1645v2Lan2MC 333}


ar1645v2Lan2MCWolInfo OBJECT IDENTIFIER ::= {ar1645v2Lan2MC 332}

ar1645v2Lan2MCWolInfoSSC OBJECT IDENTIFIER ::= {ar1645v2Lan2MCWolInfo 1}

ar1645v2Lan2MCWolInfoEntry OBJECT IDENTIFIER ::= {ar1645v2Lan2MCWolInfoSSC 1}

ar1645v2Lan2MCWolInfoTargetMAC OBJECT-TYPE
   SYNTAX      OCTET STRING
   MAX-ACCESS  read-write
   STATUS      current
   DESCRIPTION
      "Path: ethernet2.actions.wolInfo.targetMAC

       MAC address."
   ::= {ar1645v2Lan2MCWolInfoEntry 16777216}

ar1645v2Lan2MCWolInfoPassword OBJECT-TYPE
   SYNTAX      OCTET STRING
   MAX-ACCESS  read-write
   STATUS      current
   DESCRIPTION
      "Path: ethernet2.actions.wolInfo.password"
   ::= {ar1645v2Lan2MCWolInfoEntry 33554432}


ar1645v2Lan2MCClearArpCache OBJECT-TYPE
   SYNTAX      Integer32
   MAX-ACCESS  read-write
   STATUS      current
   DESCRIPTION
      "Path: ethernet2.actions.clearArpCache
       Info: clear all dynamic enties in ARP cache table"
   ::= {ar1645v2Lan2MC 25}


ar1645v2Lan2MCClearDebugCounters OBJECT-TYPE
   SYNTAX      Integer32
   MAX-ACCESS  read-write
   STATUS      current
   DESCRIPTION
      "Path: ethernet2.actions.clearDebugCounters
       Info: action in the debug group"
   ::= {ar1645v2Lan2MC 76}


ar1645v2Lan2MCEnableRds OBJECT-TYPE
   SYNTAX      Integer32
   MAX-ACCESS  read-write
   STATUS      current
   DESCRIPTION
      "Path: ethernet2.actions.enableRds
       Info: action in the debug group"
   ::= {ar1645v2Lan2MC 367}


ar1645v2Lan2MCDisableRds OBJECT-TYPE
   SYNTAX      Integer32
   MAX-ACCESS  read-write
   STATUS      current
   DESCRIPTION
      "Path: ethernet2.actions.disableRds
       Info: action in the debug group"
   ::= {ar1645v2Lan2MC 366}


ar1645v2Lan2MCEnableTds OBJECT-TYPE
   SYNTAX      Integer32
   MAX-ACCESS  read-write
   STATUS      current
   DESCRIPTION
      "Path: ethernet2.actions.enableTds
       Info: action in the debug group"
   ::= {ar1645v2Lan2MC 365}


ar1645v2Lan2MCDisableTds OBJECT-TYPE
   SYNTAX      Integer32
   MAX-ACCESS  read-write
   STATUS      current
   DESCRIPTION
      "Path: ethernet2.actions.disableTds
       Info: action in the debug group"
   ::= {ar1645v2Lan2MC 364}


ar1645v2Lan2MCClearTsecStats OBJECT-TYPE
   SYNTAX      Integer32
   MAX-ACCESS  read-write
   STATUS      current
   DESCRIPTION
      "Path: ethernet2.actions.clearTsecStats
       Info: action in the debug group"
   ::= {ar1645v2Lan2MC 363}


ar1645v2Lan2MCStopTsecStats OBJECT-TYPE
   SYNTAX      Integer32
   MAX-ACCESS  read-write
   STATUS      current
   DESCRIPTION
      "Path: ethernet2.actions.stopTsecStats
       Info: action in the debug group"
   ::= {ar1645v2Lan2MC 362}


ar1645v2Lan2MCStartTsecStats OBJECT-TYPE
   SYNTAX      Integer32
   MAX-ACCESS  read-write
   STATUS      current
   DESCRIPTION
      "Path: ethernet2.actions.startTsecStats
       Info: action in the debug group"
   ::= {ar1645v2Lan2MC 361}


ar1645v2Lan2MCPhyAction OBJECT-TYPE
   SYNTAX      Integer32
   MAX-ACCESS  read-write
   STATUS      current
   DESCRIPTION
      "Path: ethernet2.actions.phyAction
       Info: action in the debug group"
   ::= {ar1645v2Lan2MC 90}



fr1645v2Lan2MC OBJECT IDENTIFIER ::= {r1645v2Lan2MC 13}


fr1645v2Lan2MCAlarm OBJECT IDENTIFIER ::= {fr1645v2Lan2MC 207}

fr1645v2Lan2MCAlarmSSC OBJECT IDENTIFIER ::= {fr1645v2Lan2MCAlarm 1}

fr1645v2Lan2MCAlarmEntry OBJECT IDENTIFIER ::= {fr1645v2Lan2MCAlarmSSC 1}

fr1645v2Lan2MCAlarmDiscriminator OBJECT-TYPE
   SYNTAX      Integer32
   MAX-ACCESS  read-only
   STATUS      current
   DESCRIPTION
      "Path: ethernet2.alarms.alarmInfo.discriminator"
   ::= {fr1645v2Lan2MCAlarmEntry 16777216}

fr1645v2Lan2MCAlarmCurrent OBJECT-TYPE
   SYNTAX      Integer32
   MAX-ACCESS  read-only
   STATUS      current
   DESCRIPTION
      "Path: ethernet2.alarms.alarmInfo.currentAlarms

       Bit meanings:
               bit 0 = linkDown,
               bit 9 = pppoEDown"
   ::= {fr1645v2Lan2MCAlarmEntry 33554432}

fr1645v2Lan2MCAlarmPrevious OBJECT-TYPE
   SYNTAX      Integer32
   MAX-ACCESS  read-only
   STATUS      current
   DESCRIPTION
      "Path: ethernet2.alarms.alarmInfo.previousAlarms

       Bit meanings:
               bit 0 = linkDown,
               bit 9 = pppoEDown"
   ::= {fr1645v2Lan2MCAlarmEntry 50331648}

fr1645v2Lan2MCAlarmMask OBJECT-TYPE
   SYNTAX      Integer32
   MAX-ACCESS  read-only
   STATUS      current
   DESCRIPTION
      "Path: ethernet2.alarms.alarmInfo.alarmMask

       Bit meanings:
               bit 0 = linkDown,
               bit 9 = pppoEDown"
   ::= {fr1645v2Lan2MCAlarmEntry 67108864}

fr1645v2Lan2MCAlarmLevLinkDown OBJECT-TYPE
   SYNTAX      Integer32
   MAX-ACCESS  read-only
   STATUS      current
   DESCRIPTION
      "Path: ethernet2.alarms.alarmInfo.alarmLevel.linkDown"
   ::= {fr1645v2Lan2MCAlarmEntry 83951616}

fr1645v2Lan2MCAlarmLevPppoEDown OBJECT-TYPE
   SYNTAX      Integer32
   MAX-ACCESS  read-only
   STATUS      current
   DESCRIPTION
      "Path: ethernet2.alarms.alarmInfo.alarmLevel.pppoEDown"
   ::= {fr1645v2Lan2MCAlarmEntry 84541440}


fr1645v2Lan2MCAlarmE2 OBJECT IDENTIFIER ::= {fr1645v2Lan2MCAlarm 2}

fr1645v2Lan2MCAlarmE2Entry OBJECT IDENTIFIER ::= {fr1645v2Lan2MCAlarmE2 1}

fr1645v2Lan2MCAlarmE2LinkDown OBJECT IDENTIFIER ::= {fr1645v2Lan2MCAlarmE2Entry 10}

fr1645v2Lan2MCAlarmE2LinkDownPfx OBJECT IDENTIFIER ::= {fr1645v2Lan2MCAlarmE2LinkDown 0}

fr1645v2Lan2MCAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg2MC'
                (root='router1645') has changed from the ON to the OFF state."
   ::= {fr1645v2Lan2MCAlarmE2LinkDownPfx 1}

fr1645v2Lan2MCAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'lanCfg2MC'
                (root='router1645') has changed from the OFF to the ON state."
   ::= {fr1645v2Lan2MCAlarmE2LinkDownPfx 2}

fr1645v2Lan2MCAlarmE2PppoEDown OBJECT IDENTIFIER ::= {fr1645v2Lan2MCAlarmE2Entry 19}

fr1645v2Lan2MCAlarmE2PppoEDownPfx OBJECT IDENTIFIER ::= {fr1645v2Lan2MCAlarmE2PppoEDown 0}

fr1645v2Lan2MCAlarmE2PppoEDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg2MC'
                (root='router1645') has changed from the ON to the OFF state."
   ::= {fr1645v2Lan2MCAlarmE2PppoEDownPfx 1}

fr1645v2Lan2MCAlarmE2PppoEDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'pppoEDown'
                representing an alarm condition in the alarm word
                of attribute 'alarmInfo' of managed object 'lanCfg2MC'
                (root='router1645') has changed from the OFF to the ON state."
   ::= {fr1645v2Lan2MCAlarmE2PppoEDownPfx 2}



END
