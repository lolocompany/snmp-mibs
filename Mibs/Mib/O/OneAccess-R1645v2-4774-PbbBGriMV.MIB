OneAccess-R1645v2-4774-PbbBGriMV DEFINITIONS ::= BEGIN



IMPORTS                                                                     
        MODULE-IDENTITY, OBJECT-IDENTITY, NOTIFICATION-TYPE, Integer32,     
        Unsigned32, IpAddress, Counter32, Counter64, Gauge32, TimeTicks,    
        OBJECT-TYPE                                                         
            FROM SNMPv2-SMI                                                 
        DisplayString                                                       
            FROM SNMPv2-TC                                                  
        ifIndex                                                             
            FROM IF-MIB                                                     
        Ipv6Address, Ipv6AddressPrefix                                      
            FROM IPV6-TC                                                    
        telindus, GlobalIndex, LocalIndex, ContainmentPath, ObjectRevision, 
        TableIndex, FixedLengthTableActions, VariableLengthTableActions,    
        tlsCntTreeGlobalIndex, tlsTrapDescription, tlsSeverityLevel,        
        tlsTrapSeverityLevel                                                
            FROM TELINDUS-SMI;                                              



r1645Rootv2 MODULE-IDENTITY
   LAST-UPDATED "202107151728Z"
   ORGANIZATION "OneAccess"
   CONTACT-INFO "http://www.oneaccess-net.com/telindus/"
   DESCRIPTION
      "..."
   ::= {telindus 1126}




r1645v2PbbBGriMV OBJECT IDENTIFIER ::= {r1645Rootv2 4774}

r1645v2PbbBGriMVMOProp OBJECT-TYPE
   SYNTAX      SEQUENCE OF R1645v2PbbBGriMVMOPropEntry
   MAX-ACCESS  not-accessible
   STATUS      current
   DESCRIPTION
      ""
   ::= {r1645v2PbbBGriMV 1}

r1645v2PbbBGriMVMOPropEntry OBJECT-TYPE
   SYNTAX      R1645v2PbbBGriMVMOPropEntry
   MAX-ACCESS  not-accessible
   STATUS      current
   DESCRIPTION
      ""
   INDEX      { r1645v2PbbBGriMVMOPropGlobalIx }
   ::= {r1645v2PbbBGriMVMOProp 1}

R1645v2PbbBGriMVMOPropEntry ::=
   SEQUENCE
      {
      r1645v2PbbBGriMVMOPropPath
         ContainmentPath,
      r1645v2PbbBGriMVMOPropRev
         ObjectRevision,
      r1645v2PbbBGriMVMOPropGlobalIx
         GlobalIndex
      }

r1645v2PbbBGriMVMOPropPath OBJECT-TYPE
   SYNTAX      ContainmentPath
   MAX-ACCESS  read-only
   STATUS      current
   DESCRIPTION
      "Textual description of the containment tree from the instance of
       the root object down to the instance of the current object."
   ::= {r1645v2PbbBGriMVMOPropEntry 3}

r1645v2PbbBGriMVMOPropRev OBJECT-TYPE
   SYNTAX      ObjectRevision
   MAX-ACCESS  read-only
   STATUS      current
   DESCRIPTION
      "This value corresponds with the revision of the MANAGED OBJECT."
   ::= {r1645v2PbbBGriMVMOPropEntry 4}

r1645v2PbbBGriMVMOPropGlobalIx OBJECT-TYPE
   SYNTAX      GlobalIndex
   MAX-ACCESS  read-only
   STATUS      current
   DESCRIPTION
      "The value of the tlsCntTreeGlobalIndex of the MANAGED OBJECT."
   ::= {r1645v2PbbBGriMVMOPropEntry 10}



er1645v2PbbBGriMV OBJECT IDENTIFIER ::= {r1645v2PbbBGriMV 11}


er1645v2PbbBGriMVBridgeCache OBJECT IDENTIFIER ::= {er1645v2PbbBGriMV 10}

er1645v2PbbBGriMVBridgeCacheTable OBJECT-TYPE
   SYNTAX      SEQUENCE OF Er1645v2PbbBGriMVBridgeCacheEntry
   MAX-ACCESS  not-accessible
   STATUS      current
   DESCRIPTION
      "used for bridgeCache"
   ::= {er1645v2PbbBGriMVBridgeCache 1}

er1645v2PbbBGriMVBridgeCacheEntry OBJECT-TYPE
   SYNTAX      Er1645v2PbbBGriMVBridgeCacheEntry
   MAX-ACCESS  not-accessible
   STATUS      current
   DESCRIPTION
      ""
   INDEX      { er1645v2PbbBGriMVBridgeCacheGlobalIx }
   ::= {er1645v2PbbBGriMVBridgeCacheTable 1}

Er1645v2PbbBGriMVBridgeCacheEntry ::=
   SEQUENCE
      {
      er1645v2PbbBGriMVBridgeCacheGlobalIx
         GlobalIndex,
      er1645v2PbbBGriMVBridgeCacheValue
         INTEGER
      }

er1645v2PbbBGriMVBridgeCacheGlobalIx OBJECT-TYPE
   SYNTAX      GlobalIndex
   MAX-ACCESS  not-accessible
   STATUS      current
   DESCRIPTION
      "The value of the tlsCntTreeGlobalIndex of the MANAGED OBJECT."
   ::= {er1645v2PbbBGriMVBridgeCacheEntry 10}

er1645v2PbbBGriMVBridgeCacheValue OBJECT-TYPE
   SYNTAX      INTEGER
               {
               disabled (0),
               learning (1),
               switching (2)
               }
   MAX-ACCESS  read-write
   STATUS      current
   DESCRIPTION
      "Path: pbbBridgeGroup.editConf.bridgeCache

       Possibilities:
               disabled   (0)
               learning   (1)
               switching   (2)"
   ::= {er1645v2PbbBGriMVBridgeCacheEntry 2147483648}


er1645v2PbbBGriMVMaxCacheSize OBJECT IDENTIFIER ::= {er1645v2PbbBGriMV 38}

er1645v2PbbBGriMVMaxCacheSizeTable OBJECT-TYPE
   SYNTAX      SEQUENCE OF Er1645v2PbbBGriMVMaxCacheSizeEntry
   MAX-ACCESS  not-accessible
   STATUS      current
   DESCRIPTION
      "used for size of bridgeCache"
   ::= {er1645v2PbbBGriMVMaxCacheSize 1}

er1645v2PbbBGriMVMaxCacheSizeEntry OBJECT-TYPE
   SYNTAX      Er1645v2PbbBGriMVMaxCacheSizeEntry
   MAX-ACCESS  not-accessible
   STATUS      current
   DESCRIPTION
      ""
   INDEX      { er1645v2PbbBGriMVMaxCacheSizeGlobalIx }
   ::= {er1645v2PbbBGriMVMaxCacheSizeTable 1}

Er1645v2PbbBGriMVMaxCacheSizeEntry ::=
   SEQUENCE
      {
      er1645v2PbbBGriMVMaxCacheSizeGlobalIx
         GlobalIndex,
      er1645v2PbbBGriMVMaxCacheSizeValue
         INTEGER
      }

er1645v2PbbBGriMVMaxCacheSizeGlobalIx OBJECT-TYPE
   SYNTAX      GlobalIndex
   MAX-ACCESS  not-accessible
   STATUS      current
   DESCRIPTION
      "The value of the tlsCntTreeGlobalIndex of the MANAGED OBJECT."
   ::= {er1645v2PbbBGriMVMaxCacheSizeEntry 10}

er1645v2PbbBGriMVMaxCacheSizeValue OBJECT-TYPE
   SYNTAX      INTEGER
               {
               unlimited (0)
               }
   MAX-ACCESS  read-write
   STATUS      current
   DESCRIPTION
      "Path: pbbBridgeGroup.editConf.maxCacheSize

       Possibilities:
               unlimited   (0)"
   ::= {er1645v2PbbBGriMVMaxCacheSizeEntry 2147483648}


er1645v2PbbBGriMVStaticBridgeCache OBJECT IDENTIFIER ::= {er1645v2PbbBGriMV 36}

er1645v2PbbBGriMVStaticBridgeCacheSSCTable OBJECT-TYPE
   SYNTAX      SEQUENCE OF Er1645v2PbbBGriMVStaticBridgeCacheEntry
   MAX-ACCESS  not-accessible
   STATUS      current
   DESCRIPTION
      "bridge cache"
   ::= {er1645v2PbbBGriMVStaticBridgeCache 1}

er1645v2PbbBGriMVStaticBridgeCacheEntry OBJECT-TYPE
   SYNTAX      Er1645v2PbbBGriMVStaticBridgeCacheEntry
   MAX-ACCESS  not-accessible
   STATUS      current
   DESCRIPTION
      ""
   INDEX      { er1645v2PbbBGriMVStaticBridgeCacheGlobalIx,
                er1645v2PbbBGriMVStaticBridgeCacheTableIx }
   ::= {er1645v2PbbBGriMVStaticBridgeCacheSSCTable 1}

Er1645v2PbbBGriMVStaticBridgeCacheEntry ::=
   SEQUENCE
      {
      er1645v2PbbBGriMVStaticBridgeCacheActions
         VariableLengthTableActions,
      er1645v2PbbBGriMVStaticBridgeCacheGlobalIx
         GlobalIndex,
      er1645v2PbbBGriMVStaticBridgeCacheTableIx
         TableIndex,
      er1645v2PbbBGriMVStaticBridgeCacheIf
         DisplayString,
      er1645v2PbbBGriMVStaticBridgeCacheMacAddress
         OCTET STRING,
      er1645v2PbbBGriMVStaticBridgeCacheVlanId
         Integer32
      }

er1645v2PbbBGriMVStaticBridgeCacheActions OBJECT-TYPE
   SYNTAX      VariableLengthTableActions
   MAX-ACCESS  read-write
   STATUS      current
   DESCRIPTION
      "By way of this field, some manipulations
       on this table may be performed."
   ::= {er1645v2PbbBGriMVStaticBridgeCacheEntry 2}

er1645v2PbbBGriMVStaticBridgeCacheGlobalIx OBJECT-TYPE
   SYNTAX      GlobalIndex
   MAX-ACCESS  not-accessible
   STATUS      current
   DESCRIPTION
      "The value of the tlsCntTreeGlobalIndex of the MANAGED OBJECT."
   ::= {er1645v2PbbBGriMVStaticBridgeCacheEntry 10}

er1645v2PbbBGriMVStaticBridgeCacheTableIx OBJECT-TYPE
   SYNTAX      TableIndex
   MAX-ACCESS  not-accessible
   STATUS      current
   DESCRIPTION
      ""
   ::= {er1645v2PbbBGriMVStaticBridgeCacheEntry 11}

er1645v2PbbBGriMVStaticBridgeCacheIf OBJECT-TYPE
   SYNTAX      DisplayString
   MAX-ACCESS  read-write
   STATUS      current
   DESCRIPTION
      "Path: pbbBridgeGroup.editConf.staticBridgeCache.interface"
   ::= {er1645v2PbbBGriMVStaticBridgeCacheEntry 16777216}

er1645v2PbbBGriMVStaticBridgeCacheMacAddress OBJECT-TYPE
   SYNTAX      OCTET STRING
   MAX-ACCESS  read-write
   STATUS      current
   DESCRIPTION
      "Path: pbbBridgeGroup.editConf.staticBridgeCache.macAddress

       MAC address."
   ::= {er1645v2PbbBGriMVStaticBridgeCacheEntry 33554432}

er1645v2PbbBGriMVStaticBridgeCacheVlanId OBJECT-TYPE
   SYNTAX      Integer32
   MAX-ACCESS  read-write
   STATUS      current
   DESCRIPTION
      "Path: pbbBridgeGroup.editConf.staticBridgeCache.vlanId"
   ::= {er1645v2PbbBGriMVStaticBridgeCacheEntry 50331648}


er1645v2PbbBGriMVForwardMulticast OBJECT IDENTIFIER ::= {er1645v2PbbBGriMV 35}

er1645v2PbbBGriMVForwardMulticastTable OBJECT-TYPE
   SYNTAX      SEQUENCE OF Er1645v2PbbBGriMVForwardMulticastEntry
   MAX-ACCESS  not-accessible
   STATUS      current
   DESCRIPTION
      "used for size of bridgeCache"
   ::= {er1645v2PbbBGriMVForwardMulticast 1}

er1645v2PbbBGriMVForwardMulticastEntry OBJECT-TYPE
   SYNTAX      Er1645v2PbbBGriMVForwardMulticastEntry
   MAX-ACCESS  not-accessible
   STATUS      current
   DESCRIPTION
      ""
   INDEX      { er1645v2PbbBGriMVForwardMulticastGlobalIx }
   ::= {er1645v2PbbBGriMVForwardMulticastTable 1}

Er1645v2PbbBGriMVForwardMulticastEntry ::=
   SEQUENCE
      {
      er1645v2PbbBGriMVForwardMulticastGlobalIx
         GlobalIndex,
      er1645v2PbbBGriMVForwardMulticastValue
         INTEGER
      }

er1645v2PbbBGriMVForwardMulticastGlobalIx OBJECT-TYPE
   SYNTAX      GlobalIndex
   MAX-ACCESS  not-accessible
   STATUS      current
   DESCRIPTION
      "The value of the tlsCntTreeGlobalIndex of the MANAGED OBJECT."
   ::= {er1645v2PbbBGriMVForwardMulticastEntry 10}

er1645v2PbbBGriMVForwardMulticastValue OBJECT-TYPE
   SYNTAX      INTEGER
               {
               noSpanningTree (0),
               all (1),
               noLinkConstrainedProtos (2),
               dot1ad (3)
               }
   MAX-ACCESS  read-write
   STATUS      current
   DESCRIPTION
      "Path: pbbBridgeGroup.editConf.forwardMulticast

       Possibilities:
               noSpanningTree   (0)
               all   (1)
               noLinkConstrainedProtos   (2)
               dot1ad   (3)"
   ::= {er1645v2PbbBGriMVForwardMulticastEntry 2147483648}


er1645v2PbbBGriMVVlanLearningMode OBJECT IDENTIFIER ::= {er1645v2PbbBGriMV 17}

er1645v2PbbBGriMVVlanLearningModeTable OBJECT-TYPE
   SYNTAX      SEQUENCE OF Er1645v2PbbBGriMVVlanLearningModeEntry
   MAX-ACCESS  not-accessible
   STATUS      current
   DESCRIPTION
      ""
   ::= {er1645v2PbbBGriMVVlanLearningMode 1}

er1645v2PbbBGriMVVlanLearningModeEntry OBJECT-TYPE
   SYNTAX      Er1645v2PbbBGriMVVlanLearningModeEntry
   MAX-ACCESS  not-accessible
   STATUS      current
   DESCRIPTION
      ""
   INDEX      { er1645v2PbbBGriMVVlanLearningModeGlobalIx }
   ::= {er1645v2PbbBGriMVVlanLearningModeTable 1}

Er1645v2PbbBGriMVVlanLearningModeEntry ::=
   SEQUENCE
      {
      er1645v2PbbBGriMVVlanLearningModeGlobalIx
         GlobalIndex,
      er1645v2PbbBGriMVVlanLearningModeValue
         INTEGER
      }

er1645v2PbbBGriMVVlanLearningModeGlobalIx OBJECT-TYPE
   SYNTAX      GlobalIndex
   MAX-ACCESS  not-accessible
   STATUS      current
   DESCRIPTION
      "The value of the tlsCntTreeGlobalIndex of the MANAGED OBJECT."
   ::= {er1645v2PbbBGriMVVlanLearningModeEntry 10}

er1645v2PbbBGriMVVlanLearningModeValue OBJECT-TYPE
   SYNTAX      INTEGER
               {
               shared (0),
               independent (1),
               grouped (2)
               }
   MAX-ACCESS  read-write
   STATUS      current
   DESCRIPTION
      "Path: pbbBridgeGroup.editConf.vlanLearningMode

       Possibilities:
               shared   (0)
               independent   (1)
               grouped   (2)"
   ::= {er1645v2PbbBGriMVVlanLearningModeEntry 2147483648}


er1645v2PbbBGriMVVlanSwitching OBJECT IDENTIFIER ::= {er1645v2PbbBGriMV 15}

er1645v2PbbBGriMVVlanSwitchingSSCTable OBJECT-TYPE
   SYNTAX      SEQUENCE OF Er1645v2PbbBGriMVVlanSwitchingEntry
   MAX-ACCESS  not-accessible
   STATUS      current
   DESCRIPTION
      "used for bridgeCache"
   ::= {er1645v2PbbBGriMVVlanSwitching 1}

er1645v2PbbBGriMVVlanSwitchingEntry OBJECT-TYPE
   SYNTAX      Er1645v2PbbBGriMVVlanSwitchingEntry
   MAX-ACCESS  not-accessible
   STATUS      current
   DESCRIPTION
      ""
   INDEX      { er1645v2PbbBGriMVVlanSwitchingGlobalIx,
                er1645v2PbbBGriMVVlanSwitchingTableIx }
   ::= {er1645v2PbbBGriMVVlanSwitchingSSCTable 1}

Er1645v2PbbBGriMVVlanSwitchingEntry ::=
   SEQUENCE
      {
      er1645v2PbbBGriMVVlanSwitchingActions
         VariableLengthTableActions,
      er1645v2PbbBGriMVVlanSwitchingGlobalIx
         GlobalIndex,
      er1645v2PbbBGriMVVlanSwitchingTableIx
         TableIndex,
      er1645v2PbbBGriMVVlanSwitchingSi
         DisplayString,
      er1645v2PbbBGriMVVlanSwitchingSv
         INTEGER,
      er1645v2PbbBGriMVVlanSwitchingSp
         INTEGER,
      er1645v2PbbBGriMVVlanSwitchingSmP0
         Integer32,
      er1645v2PbbBGriMVVlanSwitchingSmP1
         Integer32,
      er1645v2PbbBGriMVVlanSwitchingSmP2
         Integer32,
      er1645v2PbbBGriMVVlanSwitchingSmP3
         Integer32,
      er1645v2PbbBGriMVVlanSwitchingSmP4
         Integer32,
      er1645v2PbbBGriMVVlanSwitchingSmP5
         Integer32,
      er1645v2PbbBGriMVVlanSwitchingSmP6
         Integer32,
      er1645v2PbbBGriMVVlanSwitchingSmP7
         Integer32,
      er1645v2PbbBGriMVVlanSwitchingDi
         DisplayString,
      er1645v2PbbBGriMVVlanSwitchingDv
         INTEGER,
      er1645v2PbbBGriMVVlanSwitchingDp
         INTEGER,
      er1645v2PbbBGriMVVlanSwitchingDmP0
         Integer32,
      er1645v2PbbBGriMVVlanSwitchingDmP1
         Integer32,
      er1645v2PbbBGriMVVlanSwitchingDmP2
         Integer32,
      er1645v2PbbBGriMVVlanSwitchingDmP3
         Integer32,
      er1645v2PbbBGriMVVlanSwitchingDmP4
         Integer32,
      er1645v2PbbBGriMVVlanSwitchingDmP5
         Integer32,
      er1645v2PbbBGriMVVlanSwitchingDmP6
         Integer32,
      er1645v2PbbBGriMVVlanSwitchingDmP7
         Integer32,
      er1645v2PbbBGriMVVlanSwitchingTunnel
         INTEGER,
      er1645v2PbbBGriMVVlanSwitchingBidir
         INTEGER
      }

er1645v2PbbBGriMVVlanSwitchingActions OBJECT-TYPE
   SYNTAX      VariableLengthTableActions
   MAX-ACCESS  read-write
   STATUS      current
   DESCRIPTION
      "By way of this field, some manipulations
       on this table may be performed."
   ::= {er1645v2PbbBGriMVVlanSwitchingEntry 2}

er1645v2PbbBGriMVVlanSwitchingGlobalIx OBJECT-TYPE
   SYNTAX      GlobalIndex
   MAX-ACCESS  not-accessible
   STATUS      current
   DESCRIPTION
      "The value of the tlsCntTreeGlobalIndex of the MANAGED OBJECT."
   ::= {er1645v2PbbBGriMVVlanSwitchingEntry 10}

er1645v2PbbBGriMVVlanSwitchingTableIx OBJECT-TYPE
   SYNTAX      TableIndex
   MAX-ACCESS  not-accessible
   STATUS      current
   DESCRIPTION
      ""
   ::= {er1645v2PbbBGriMVVlanSwitchingEntry 11}

er1645v2PbbBGriMVVlanSwitchingSi OBJECT-TYPE
   SYNTAX      DisplayString
   MAX-ACCESS  read-write
   STATUS      current
   DESCRIPTION
      "Path: pbbBridgeGroup.editConf.vlanSwitching.sourceIntf"
   ::= {er1645v2PbbBGriMVVlanSwitchingEntry 16777216}

er1645v2PbbBGriMVVlanSwitchingSv OBJECT-TYPE
   SYNTAX      INTEGER
               {
               any (-1)
               }
   MAX-ACCESS  read-write
   STATUS      current
   DESCRIPTION
      "Path: pbbBridgeGroup.editConf.vlanSwitching.sourceVlan

       Possibilities:
               any   (-1)"
   ::= {er1645v2PbbBGriMVVlanSwitchingEntry 33554432}

er1645v2PbbBGriMVVlanSwitchingSp OBJECT-TYPE
   SYNTAX      INTEGER
               {
               any (-1)
               }
   MAX-ACCESS  read-write
   STATUS      current
   DESCRIPTION
      "Path: pbbBridgeGroup.editConf.vlanSwitching.sourcePFilter

       Possibilities:
               any   (-1)"
   ::= {er1645v2PbbBGriMVVlanSwitchingEntry 134217728}

er1645v2PbbBGriMVVlanSwitchingSmP0 OBJECT-TYPE
   SYNTAX      Integer32
   MAX-ACCESS  read-write
   STATUS      current
   DESCRIPTION
      "Path: pbbBridgeGroup.editConf.vlanSwitching.sourcePMap.p0"
   ::= {er1645v2PbbBGriMVVlanSwitchingEntry 50397184}

er1645v2PbbBGriMVVlanSwitchingSmP1 OBJECT-TYPE
   SYNTAX      Integer32
   MAX-ACCESS  read-write
   STATUS      current
   DESCRIPTION
      "Path: pbbBridgeGroup.editConf.vlanSwitching.sourcePMap.p1"
   ::= {er1645v2PbbBGriMVVlanSwitchingEntry 50462720}

er1645v2PbbBGriMVVlanSwitchingSmP2 OBJECT-TYPE
   SYNTAX      Integer32
   MAX-ACCESS  read-write
   STATUS      current
   DESCRIPTION
      "Path: pbbBridgeGroup.editConf.vlanSwitching.sourcePMap.p2"
   ::= {er1645v2PbbBGriMVVlanSwitchingEntry 50528256}

er1645v2PbbBGriMVVlanSwitchingSmP3 OBJECT-TYPE
   SYNTAX      Integer32
   MAX-ACCESS  read-write
   STATUS      current
   DESCRIPTION
      "Path: pbbBridgeGroup.editConf.vlanSwitching.sourcePMap.p3"
   ::= {er1645v2PbbBGriMVVlanSwitchingEntry 50593792}

er1645v2PbbBGriMVVlanSwitchingSmP4 OBJECT-TYPE
   SYNTAX      Integer32
   MAX-ACCESS  read-write
   STATUS      current
   DESCRIPTION
      "Path: pbbBridgeGroup.editConf.vlanSwitching.sourcePMap.p4"
   ::= {er1645v2PbbBGriMVVlanSwitchingEntry 50659328}

er1645v2PbbBGriMVVlanSwitchingSmP5 OBJECT-TYPE
   SYNTAX      Integer32
   MAX-ACCESS  read-write
   STATUS      current
   DESCRIPTION
      "Path: pbbBridgeGroup.editConf.vlanSwitching.sourcePMap.p5"
   ::= {er1645v2PbbBGriMVVlanSwitchingEntry 50724864}

er1645v2PbbBGriMVVlanSwitchingSmP6 OBJECT-TYPE
   SYNTAX      Integer32
   MAX-ACCESS  read-write
   STATUS      current
   DESCRIPTION
      "Path: pbbBridgeGroup.editConf.vlanSwitching.sourcePMap.p6"
   ::= {er1645v2PbbBGriMVVlanSwitchingEntry 50790400}

er1645v2PbbBGriMVVlanSwitchingSmP7 OBJECT-TYPE
   SYNTAX      Integer32
   MAX-ACCESS  read-write
   STATUS      current
   DESCRIPTION
      "Path: pbbBridgeGroup.editConf.vlanSwitching.sourcePMap.p7"
   ::= {er1645v2PbbBGriMVVlanSwitchingEntry 50855936}

er1645v2PbbBGriMVVlanSwitchingDi OBJECT-TYPE
   SYNTAX      DisplayString
   MAX-ACCESS  read-write
   STATUS      current
   DESCRIPTION
      "Path: pbbBridgeGroup.editConf.vlanSwitching.destinationIntf"
   ::= {er1645v2PbbBGriMVVlanSwitchingEntry 67108864}

er1645v2PbbBGriMVVlanSwitchingDv OBJECT-TYPE
   SYNTAX      INTEGER
               {
               unchanged (-1)
               }
   MAX-ACCESS  read-write
   STATUS      current
   DESCRIPTION
      "Path: pbbBridgeGroup.editConf.vlanSwitching.destinationVlan

       Possibilities:
               unchanged   (-1)"
   ::= {er1645v2PbbBGriMVVlanSwitchingEntry 83886080}

er1645v2PbbBGriMVVlanSwitchingDp OBJECT-TYPE
   SYNTAX      INTEGER
               {
               any (-1)
               }
   MAX-ACCESS  read-write
   STATUS      current
   DESCRIPTION
      "Path: pbbBridgeGroup.editConf.vlanSwitching.destinationPFilter

       Possibilities:
               any   (-1)"
   ::= {er1645v2PbbBGriMVVlanSwitchingEntry 167772160}

er1645v2PbbBGriMVVlanSwitchingDmP0 OBJECT-TYPE
   SYNTAX      Integer32
   MAX-ACCESS  read-write
   STATUS      current
   DESCRIPTION
      "Path: pbbBridgeGroup.editConf.vlanSwitching.destinationPMap.p0"
   ::= {er1645v2PbbBGriMVVlanSwitchingEntry 100728832}

er1645v2PbbBGriMVVlanSwitchingDmP1 OBJECT-TYPE
   SYNTAX      Integer32
   MAX-ACCESS  read-write
   STATUS      current
   DESCRIPTION
      "Path: pbbBridgeGroup.editConf.vlanSwitching.destinationPMap.p1"
   ::= {er1645v2PbbBGriMVVlanSwitchingEntry 100794368}

er1645v2PbbBGriMVVlanSwitchingDmP2 OBJECT-TYPE
   SYNTAX      Integer32
   MAX-ACCESS  read-write
   STATUS      current
   DESCRIPTION
      "Path: pbbBridgeGroup.editConf.vlanSwitching.destinationPMap.p2"
   ::= {er1645v2PbbBGriMVVlanSwitchingEntry 100859904}

er1645v2PbbBGriMVVlanSwitchingDmP3 OBJECT-TYPE
   SYNTAX      Integer32
   MAX-ACCESS  read-write
   STATUS      current
   DESCRIPTION
      "Path: pbbBridgeGroup.editConf.vlanSwitching.destinationPMap.p3"
   ::= {er1645v2PbbBGriMVVlanSwitchingEntry 100925440}

er1645v2PbbBGriMVVlanSwitchingDmP4 OBJECT-TYPE
   SYNTAX      Integer32
   MAX-ACCESS  read-write
   STATUS      current
   DESCRIPTION
      "Path: pbbBridgeGroup.editConf.vlanSwitching.destinationPMap.p4"
   ::= {er1645v2PbbBGriMVVlanSwitchingEntry 100990976}

er1645v2PbbBGriMVVlanSwitchingDmP5 OBJECT-TYPE
   SYNTAX      Integer32
   MAX-ACCESS  read-write
   STATUS      current
   DESCRIPTION
      "Path: pbbBridgeGroup.editConf.vlanSwitching.destinationPMap.p5"
   ::= {er1645v2PbbBGriMVVlanSwitchingEntry 101056512}

er1645v2PbbBGriMVVlanSwitchingDmP6 OBJECT-TYPE
   SYNTAX      Integer32
   MAX-ACCESS  read-write
   STATUS      current
   DESCRIPTION
      "Path: pbbBridgeGroup.editConf.vlanSwitching.destinationPMap.p6"
   ::= {er1645v2PbbBGriMVVlanSwitchingEntry 101122048}

er1645v2PbbBGriMVVlanSwitchingDmP7 OBJECT-TYPE
   SYNTAX      Integer32
   MAX-ACCESS  read-write
   STATUS      current
   DESCRIPTION
      "Path: pbbBridgeGroup.editConf.vlanSwitching.destinationPMap.p7"
   ::= {er1645v2PbbBGriMVVlanSwitchingEntry 101187584}

er1645v2PbbBGriMVVlanSwitchingTunnel OBJECT-TYPE
   SYNTAX      INTEGER
               {
               disabled (0),
               enabled (1),
               sVlan (3)
               }
   MAX-ACCESS  read-write
   STATUS      current
   DESCRIPTION
      "Path: pbbBridgeGroup.editConf.vlanSwitching.tunnel

       Possibilities:
               disabled   (0)
               enabled   (1)
               sVlan   (3)"
   ::= {er1645v2PbbBGriMVVlanSwitchingEntry 117440512}

er1645v2PbbBGriMVVlanSwitchingBidir OBJECT-TYPE
   SYNTAX      INTEGER
               {
               no (0),
               yes (1)
               }
   MAX-ACCESS  read-write
   STATUS      current
   DESCRIPTION
      "Path: pbbBridgeGroup.editConf.vlanSwitching.bidirectional

       Possibilities:
               no   (0)
               yes   (1)"
   ::= {er1645v2PbbBGriMVVlanSwitchingEntry 150994944}


er1645v2PbbBGriMVPktCounters OBJECT IDENTIFIER ::= {er1645v2PbbBGriMV 31}

er1645v2PbbBGriMVPktCountersTable OBJECT-TYPE
   SYNTAX      SEQUENCE OF Er1645v2PbbBGriMVPktCountersEntry
   MAX-ACCESS  not-accessible
   STATUS      current
   DESCRIPTION
      ""
   ::= {er1645v2PbbBGriMVPktCounters 1}

er1645v2PbbBGriMVPktCountersEntry OBJECT-TYPE
   SYNTAX      Er1645v2PbbBGriMVPktCountersEntry
   MAX-ACCESS  not-accessible
   STATUS      current
   DESCRIPTION
      ""
   INDEX      { er1645v2PbbBGriMVPktCountersGlobalIx }
   ::= {er1645v2PbbBGriMVPktCountersTable 1}

Er1645v2PbbBGriMVPktCountersEntry ::=
   SEQUENCE
      {
      er1645v2PbbBGriMVPktCountersGlobalIx
         GlobalIndex,
      er1645v2PbbBGriMVPktCountersValue
         INTEGER
      }

er1645v2PbbBGriMVPktCountersGlobalIx OBJECT-TYPE
   SYNTAX      GlobalIndex
   MAX-ACCESS  not-accessible
   STATUS      current
   DESCRIPTION
      "The value of the tlsCntTreeGlobalIndex of the MANAGED OBJECT."
   ::= {er1645v2PbbBGriMVPktCountersEntry 10}

er1645v2PbbBGriMVPktCountersValue OBJECT-TYPE
   SYNTAX      INTEGER
               {
               disabled (1),
               enabled (2)
               }
   MAX-ACCESS  read-write
   STATUS      current
   DESCRIPTION
      "Path: pbbBridgeGroup.editConf.pktCounters

       Possibilities:
               disabled   (1)
               enabled   (2)"
   ::= {er1645v2PbbBGriMVPktCountersEntry 2147483648}


er1645v2PbbBGriMVBackup OBJECT IDENTIFIER ::= {er1645v2PbbBGriMV 32}

er1645v2PbbBGriMVBackupSSCTable OBJECT-TYPE
   SYNTAX      SEQUENCE OF Er1645v2PbbBGriMVBackupEntry
   MAX-ACCESS  not-accessible
   STATUS      current
   DESCRIPTION
      ""
   ::= {er1645v2PbbBGriMVBackup 1}

er1645v2PbbBGriMVBackupEntry OBJECT-TYPE
   SYNTAX      Er1645v2PbbBGriMVBackupEntry
   MAX-ACCESS  not-accessible
   STATUS      current
   DESCRIPTION
      ""
   INDEX      { er1645v2PbbBGriMVBackupGlobalIx }
   ::= {er1645v2PbbBGriMVBackupSSCTable 1}

Er1645v2PbbBGriMVBackupEntry ::=
   SEQUENCE
      {
      er1645v2PbbBGriMVBackupGlobalIx
         GlobalIndex,
      er1645v2PbbBGriMVBackupDisabled
         OCTET STRING,
      er1645v2PbbBGriMVBackupSimpleInterface1
         DisplayString,
      er1645v2PbbBGriMVBackupSimpleInterface1MepName
         DisplayString,
      er1645v2PbbBGriMVBackupSimpleInterface2
         DisplayString,
      er1645v2PbbBGriMVBackupSimpleInterface2MepName
         DisplayString,
      er1645v2PbbBGriMVBackupSimpleBackup
         DisplayString,
      er1645v2PbbBGriMVBackupSimpleBackupMepName
         DisplayString,
      er1645v2PbbBGriMVBackupSimpleType
         INTEGER
      }

er1645v2PbbBGriMVBackupGlobalIx OBJECT-TYPE
   SYNTAX      GlobalIndex
   MAX-ACCESS  not-accessible
   STATUS      current
   DESCRIPTION
      "The value of the tlsCntTreeGlobalIndex of the MANAGED OBJECT."
   ::= {er1645v2PbbBGriMVBackupEntry 10}

er1645v2PbbBGriMVBackupDisabled OBJECT-TYPE
   SYNTAX      OCTET STRING
   MAX-ACCESS  read-write
   STATUS      current
   DESCRIPTION
      "Path: pbbBridgeGroup.editConf.backup.disabled"
   ::= {er1645v2PbbBGriMVBackupEntry 16777216}

er1645v2PbbBGriMVBackupSimpleInterface1 OBJECT-TYPE
   SYNTAX      DisplayString
   MAX-ACCESS  read-write
   STATUS      current
   DESCRIPTION
      "Path: pbbBridgeGroup.editConf.backup.simple.interface1"
   ::= {er1645v2PbbBGriMVBackupEntry 33619968}

er1645v2PbbBGriMVBackupSimpleInterface1MepName OBJECT-TYPE
   SYNTAX      DisplayString
   MAX-ACCESS  read-write
   STATUS      current
   DESCRIPTION
      "Path: pbbBridgeGroup.editConf.backup.simple.interface1MepName"
   ::= {er1645v2PbbBGriMVBackupEntry 33947648}

er1645v2PbbBGriMVBackupSimpleInterface2 OBJECT-TYPE
   SYNTAX      DisplayString
   MAX-ACCESS  read-write
   STATUS      current
   DESCRIPTION
      "Path: pbbBridgeGroup.editConf.backup.simple.interface2"
   ::= {er1645v2PbbBGriMVBackupEntry 33685504}

er1645v2PbbBGriMVBackupSimpleInterface2MepName OBJECT-TYPE
   SYNTAX      DisplayString
   MAX-ACCESS  read-write
   STATUS      current
   DESCRIPTION
      "Path: pbbBridgeGroup.editConf.backup.simple.interface2MepName"
   ::= {er1645v2PbbBGriMVBackupEntry 34013184}

er1645v2PbbBGriMVBackupSimpleBackup OBJECT-TYPE
   SYNTAX      DisplayString
   MAX-ACCESS  read-write
   STATUS      current
   DESCRIPTION
      "Path: pbbBridgeGroup.editConf.backup.simple.backup"
   ::= {er1645v2PbbBGriMVBackupEntry 33751040}

er1645v2PbbBGriMVBackupSimpleBackupMepName OBJECT-TYPE
   SYNTAX      DisplayString
   MAX-ACCESS  read-write
   STATUS      current
   DESCRIPTION
      "Path: pbbBridgeGroup.editConf.backup.simple.backupMepName"
   ::= {er1645v2PbbBGriMVBackupEntry 33816576}

er1645v2PbbBGriMVBackupSimpleType OBJECT-TYPE
   SYNTAX      INTEGER
               {
               master (1),
               slave (2)
               }
   MAX-ACCESS  read-write
   STATUS      current
   DESCRIPTION
      "Path: pbbBridgeGroup.editConf.backup.simple.type

       Possibilities:
               master   (1)
               slave   (2)"
   ::= {er1645v2PbbBGriMVBackupEntry 33882112}

er1645v2PbbBGriMVBackupSimpleCacheDistribution OBJECT-TYPE
   SYNTAX      SEQUENCE OF Er1645v2PbbBGriMVBackupSimpleCacheDistributionEntry
   MAX-ACCESS  not-accessible
   STATUS      current
   DESCRIPTION
      ""
   ::= {er1645v2PbbBGriMVBackup 34078720}

er1645v2PbbBGriMVBackupSimpleCacheDistributionEntry OBJECT-TYPE
   SYNTAX      Er1645v2PbbBGriMVBackupSimpleCacheDistributionEntry
   MAX-ACCESS  not-accessible
   STATUS      current
   DESCRIPTION
      ""
   INDEX      { er1645v2PbbBGriMVBackupSimpleCacheDistributionGlobalIx,
                er1645v2PbbBGriMVBackupSimpleCacheDistributionTableIx }
   ::= {er1645v2PbbBGriMVBackupSimpleCacheDistribution 1}

Er1645v2PbbBGriMVBackupSimpleCacheDistributionEntry ::=
   SEQUENCE
      {
      er1645v2PbbBGriMVBackupSimpleCacheDistributionActions
         VariableLengthTableActions,
      er1645v2PbbBGriMVBackupSimpleCacheDistributionGlobalIx
         GlobalIndex,
      er1645v2PbbBGriMVBackupSimpleCacheDistributionTableIx
         TableIndex,
      er1645v2PbbBGriMVBackupSimpleCacheDistributionDestinationMac
         OCTET STRING,
      er1645v2PbbBGriMVBackupSimpleCacheDistributionType
         INTEGER
      }

er1645v2PbbBGriMVBackupSimpleCacheDistributionActions OBJECT-TYPE
   SYNTAX      VariableLengthTableActions
   MAX-ACCESS  read-write
   STATUS      current
   DESCRIPTION
      "By way of this field, some manipulations
       on this table may be performed."
   ::= {er1645v2PbbBGriMVBackupSimpleCacheDistributionEntry 2}

er1645v2PbbBGriMVBackupSimpleCacheDistributionGlobalIx OBJECT-TYPE
   SYNTAX      GlobalIndex
   MAX-ACCESS  not-accessible
   STATUS      current
   DESCRIPTION
      "The value of the tlsCntTreeGlobalIndex of the MANAGED OBJECT."
   ::= {er1645v2PbbBGriMVBackupSimpleCacheDistributionEntry 10}

er1645v2PbbBGriMVBackupSimpleCacheDistributionTableIx OBJECT-TYPE
   SYNTAX      TableIndex
   MAX-ACCESS  not-accessible
   STATUS      current
   DESCRIPTION
      ""
   ::= {er1645v2PbbBGriMVBackupSimpleCacheDistributionEntry 11}

er1645v2PbbBGriMVBackupSimpleCacheDistributionDestinationMac OBJECT-TYPE
   SYNTAX      OCTET STRING
   MAX-ACCESS  read-write
   STATUS      current
   DESCRIPTION
      "Path: pbbBridgeGroup.editConf.backup.simple.cacheDistribution.destinationMac

       MAC address."
   ::= {er1645v2PbbBGriMVBackupSimpleCacheDistributionEntry 16777216}

er1645v2PbbBGriMVBackupSimpleCacheDistributionType OBJECT-TYPE
   SYNTAX      INTEGER
               {
               arp (2054)
               }
   MAX-ACCESS  read-write
   STATUS      current
   DESCRIPTION
      "Path: pbbBridgeGroup.editConf.backup.simple.cacheDistribution.type

       Possibilities:
               arp   (2054)"
   ::= {er1645v2PbbBGriMVBackupSimpleCacheDistributionEntry 33554432}


er1645v2PbbBGriMVAlarmMask OBJECT IDENTIFIER ::= {er1645v2PbbBGriMV 50}

er1645v2PbbBGriMVAlarmMaskTable OBJECT-TYPE
   SYNTAX      SEQUENCE OF Er1645v2PbbBGriMVAlarmMaskEntry
   MAX-ACCESS  not-accessible
   STATUS      current
   DESCRIPTION
      "bridge group alarmMask"
   ::= {er1645v2PbbBGriMVAlarmMask 1}

er1645v2PbbBGriMVAlarmMaskEntry OBJECT-TYPE
   SYNTAX      Er1645v2PbbBGriMVAlarmMaskEntry
   MAX-ACCESS  not-accessible
   STATUS      current
   DESCRIPTION
      ""
   INDEX      { er1645v2PbbBGriMVAlarmMaskGlobalIx }
   ::= {er1645v2PbbBGriMVAlarmMaskTable 1}

Er1645v2PbbBGriMVAlarmMaskEntry ::=
   SEQUENCE
      {
      er1645v2PbbBGriMVAlarmMaskGlobalIx
         GlobalIndex,
      er1645v2PbbBGriMVAlarmMaskValue
         Integer32
      }

er1645v2PbbBGriMVAlarmMaskGlobalIx OBJECT-TYPE
   SYNTAX      GlobalIndex
   MAX-ACCESS  not-accessible
   STATUS      current
   DESCRIPTION
      "The value of the tlsCntTreeGlobalIndex of the MANAGED OBJECT."
   ::= {er1645v2PbbBGriMVAlarmMaskEntry 10}

er1645v2PbbBGriMVAlarmMaskValue OBJECT-TYPE
   SYNTAX      Integer32
   MAX-ACCESS  read-write
   STATUS      current
   DESCRIPTION
      "Path: pbbBridgeGroup.editConf.alarmMask

       Bit meanings:
               bit 0 = linkDown,
               bit 1 = linkShutdown"
   ::= {er1645v2PbbBGriMVAlarmMaskEntry 2147483648}


er1645v2PbbBGriMVAlarmLev OBJECT IDENTIFIER ::= {er1645v2PbbBGriMV 51}

er1645v2PbbBGriMVAlarmLevSSCTable OBJECT-TYPE
   SYNTAX      SEQUENCE OF Er1645v2PbbBGriMVAlarmLevEntry
   MAX-ACCESS  not-accessible
   STATUS      current
   DESCRIPTION
      "bridge group alarmLevels"
   ::= {er1645v2PbbBGriMVAlarmLev 1}

er1645v2PbbBGriMVAlarmLevEntry OBJECT-TYPE
   SYNTAX      Er1645v2PbbBGriMVAlarmLevEntry
   MAX-ACCESS  not-accessible
   STATUS      current
   DESCRIPTION
      ""
   INDEX      { er1645v2PbbBGriMVAlarmLevGlobalIx }
   ::= {er1645v2PbbBGriMVAlarmLevSSCTable 1}

Er1645v2PbbBGriMVAlarmLevEntry ::=
   SEQUENCE
      {
      er1645v2PbbBGriMVAlarmLevGlobalIx
         GlobalIndex,
      er1645v2PbbBGriMVAlarmLevLinkDown
         Integer32,
      er1645v2PbbBGriMVAlarmLevLinkShutdown
         Integer32
      }

er1645v2PbbBGriMVAlarmLevGlobalIx OBJECT-TYPE
   SYNTAX      GlobalIndex
   MAX-ACCESS  not-accessible
   STATUS      current
   DESCRIPTION
      "The value of the tlsCntTreeGlobalIndex of the MANAGED OBJECT."
   ::= {er1645v2PbbBGriMVAlarmLevEntry 10}

er1645v2PbbBGriMVAlarmLevLinkDown OBJECT-TYPE
   SYNTAX      Integer32
   MAX-ACCESS  read-write
   STATUS      current
   DESCRIPTION
      "Path: pbbBridgeGroup.editConf.alarmLevel.linkDown"
   ::= {er1645v2PbbBGriMVAlarmLevEntry 16777216}

er1645v2PbbBGriMVAlarmLevLinkShutdown OBJECT-TYPE
   SYNTAX      Integer32
   MAX-ACCESS  read-write
   STATUS      current
   DESCRIPTION
      "Path: pbbBridgeGroup.editConf.alarmLevel.linkShutdown"
   ::= {er1645v2PbbBGriMVAlarmLevEntry 33554432}


er1645v2PbbBGriMVBridgeTimeOut OBJECT IDENTIFIER ::= {er1645v2PbbBGriMV 21}

er1645v2PbbBGriMVBridgeTimeOutTable OBJECT-TYPE
   SYNTAX      SEQUENCE OF Er1645v2PbbBGriMVBridgeTimeOutEntry
   MAX-ACCESS  not-accessible
   STATUS      current
   DESCRIPTION
      "timeout of bridge cache entries"
   ::= {er1645v2PbbBGriMVBridgeTimeOut 1}

er1645v2PbbBGriMVBridgeTimeOutEntry OBJECT-TYPE
   SYNTAX      Er1645v2PbbBGriMVBridgeTimeOutEntry
   MAX-ACCESS  not-accessible
   STATUS      current
   DESCRIPTION
      ""
   INDEX      { er1645v2PbbBGriMVBridgeTimeOutGlobalIx }
   ::= {er1645v2PbbBGriMVBridgeTimeOutTable 1}

Er1645v2PbbBGriMVBridgeTimeOutEntry ::=
   SEQUENCE
      {
      er1645v2PbbBGriMVBridgeTimeOutGlobalIx
         GlobalIndex,
      er1645v2PbbBGriMVBridgeTimeOutValue
         TimeTicks
      }

er1645v2PbbBGriMVBridgeTimeOutGlobalIx OBJECT-TYPE
   SYNTAX      GlobalIndex
   MAX-ACCESS  not-accessible
   STATUS      current
   DESCRIPTION
      "The value of the tlsCntTreeGlobalIndex of the MANAGED OBJECT."
   ::= {er1645v2PbbBGriMVBridgeTimeOutEntry 10}

er1645v2PbbBGriMVBridgeTimeOutValue OBJECT-TYPE
   SYNTAX      TimeTicks
   MAX-ACCESS  read-write
   STATUS      current
   DESCRIPTION
      "Path: pbbBridgeGroup.editConf.bridgeTimeOut

       Time in centi-second."
   ::= {er1645v2PbbBGriMVBridgeTimeOutEntry 2147483648}


er1645v2PbbBGriMVRemark OBJECT IDENTIFIER ::= {er1645v2PbbBGriMV 321}

er1645v2PbbBGriMVRemarkTable OBJECT-TYPE
   SYNTAX      SEQUENCE OF Er1645v2PbbBGriMVRemarkEntry
   MAX-ACCESS  not-accessible
   STATUS      current
   DESCRIPTION
      "intfRemark"
   ::= {er1645v2PbbBGriMVRemark 1}

er1645v2PbbBGriMVRemarkEntry OBJECT-TYPE
   SYNTAX      Er1645v2PbbBGriMVRemarkEntry
   MAX-ACCESS  not-accessible
   STATUS      current
   DESCRIPTION
      ""
   INDEX      { er1645v2PbbBGriMVRemarkGlobalIx }
   ::= {er1645v2PbbBGriMVRemarkTable 1}

Er1645v2PbbBGriMVRemarkEntry ::=
   SEQUENCE
      {
      er1645v2PbbBGriMVRemarkGlobalIx
         GlobalIndex,
      er1645v2PbbBGriMVRemarkValue
         DisplayString
      }

er1645v2PbbBGriMVRemarkGlobalIx OBJECT-TYPE
   SYNTAX      GlobalIndex
   MAX-ACCESS  not-accessible
   STATUS      current
   DESCRIPTION
      "The value of the tlsCntTreeGlobalIndex of the MANAGED OBJECT."
   ::= {er1645v2PbbBGriMVRemarkEntry 10}

er1645v2PbbBGriMVRemarkValue OBJECT-TYPE
   SYNTAX      DisplayString
   MAX-ACCESS  read-write
   STATUS      current
   DESCRIPTION
      "Path: pbbBridgeGroup.editConf.remark"
   ::= {er1645v2PbbBGriMVRemarkEntry 2147483648}


er1645v2PbbBGriMVMode OBJECT IDENTIFIER ::= {er1645v2PbbBGriMV 4}

er1645v2PbbBGriMVModeTable OBJECT-TYPE
   SYNTAX      SEQUENCE OF Er1645v2PbbBGriMVModeEntry
   MAX-ACCESS  not-accessible
   STATUS      current
   DESCRIPTION
      "routing and/or ipV6 selection"
   ::= {er1645v2PbbBGriMVMode 1}

er1645v2PbbBGriMVModeEntry OBJECT-TYPE
   SYNTAX      Er1645v2PbbBGriMVModeEntry
   MAX-ACCESS  not-accessible
   STATUS      current
   DESCRIPTION
      ""
   INDEX      { er1645v2PbbBGriMVModeGlobalIx }
   ::= {er1645v2PbbBGriMVModeTable 1}

Er1645v2PbbBGriMVModeEntry ::=
   SEQUENCE
      {
      er1645v2PbbBGriMVModeGlobalIx
         GlobalIndex,
      er1645v2PbbBGriMVModeValue
         INTEGER
      }

er1645v2PbbBGriMVModeGlobalIx OBJECT-TYPE
   SYNTAX      GlobalIndex
   MAX-ACCESS  not-accessible
   STATUS      current
   DESCRIPTION
      "The value of the tlsCntTreeGlobalIndex of the MANAGED OBJECT."
   ::= {er1645v2PbbBGriMVModeEntry 10}

er1645v2PbbBGriMVModeValue OBJECT-TYPE
   SYNTAX      INTEGER
               {
               routing (1),
               ipV6 (3),
               ipV6ipV4 (4),
               disabled (100)
               }
   MAX-ACCESS  read-write
   STATUS      current
   DESCRIPTION
      "Path: pbbBridgeGroup.editConf.mode

       Possibilities:
               routing   (1)
               ipV6   (3)
               ipV6/ipV4   (4)
               disabled   (100)"
   ::= {er1645v2PbbBGriMVModeEntry 2147483648}


er1645v2PbbBGriMVIpV6 OBJECT IDENTIFIER ::= {er1645v2PbbBGriMV 16}

er1645v2PbbBGriMVIpV6SSCTable OBJECT-TYPE
   SYNTAX      SEQUENCE OF Er1645v2PbbBGriMVIpV6Entry
   MAX-ACCESS  not-accessible
   STATUS      current
   DESCRIPTION
      "IPv6 interface config parameters"
   ::= {er1645v2PbbBGriMVIpV6 1}

er1645v2PbbBGriMVIpV6Entry OBJECT-TYPE
   SYNTAX      Er1645v2PbbBGriMVIpV6Entry
   MAX-ACCESS  not-accessible
   STATUS      current
   DESCRIPTION
      ""
   INDEX      { er1645v2PbbBGriMVIpV6GlobalIx }
   ::= {er1645v2PbbBGriMVIpV6SSCTable 1}

Er1645v2PbbBGriMVIpV6Entry ::=
   SEQUENCE
      {
      er1645v2PbbBGriMVIpV6GlobalIx
         GlobalIndex,
      er1645v2PbbBGriMVIpV6VrfRouter
         DisplayString,
      er1645v2PbbBGriMVIpV6AddrAutoConfigNrDupAddrDetects
         Integer32,
      er1645v2PbbBGriMVIpV6AddrAutoConfigAcceptRa
         INTEGER,
      er1645v2PbbBGriMVIpV6AddrAutoConfigAcceptRaRdnss
         INTEGER,
      er1645v2PbbBGriMVIpV6AddrAutoConfigAcceptRaDnssl
         INTEGER,
      er1645v2PbbBGriMVIpV6DefaultRoute
         INTEGER,
      er1645v2PbbBGriMVIpV6RaSend
         INTEGER,
      er1645v2PbbBGriMVIpV6RaMinInterval
         TimeTicks,
      er1645v2PbbBGriMVIpV6RaMaxInterval
         TimeTicks,
      er1645v2PbbBGriMVIpV6RaManagedFlag
         INTEGER,
      er1645v2PbbBGriMVIpV6RaOtherConfFlag
         INTEGER,
      er1645v2PbbBGriMVIpV6RaLinkMtu
         Integer32,
      er1645v2PbbBGriMVIpV6RaReachableTime
         TimeTicks,
      er1645v2PbbBGriMVIpV6RaRetransmitTime
         TimeTicks,
      er1645v2PbbBGriMVIpV6RaHopLimit
         Integer32,
      er1645v2PbbBGriMVIpV6RaDefaultLifeTime
         TimeTicks,
      er1645v2PbbBGriMVIpV6RaDnsOptionsRdnssLifeTime
         TimeTicks,
      er1645v2PbbBGriMVIpV6RaDnsOptionsRdnssImportServers
         INTEGER,
      er1645v2PbbBGriMVIpV6RaDnsOptionsDnsslLifeTime
         TimeTicks,
      er1645v2PbbBGriMVIpV6RaDnsOptionsDnsslImportDomains
         INTEGER,
      er1645v2PbbBGriMVIpV6RsSend
         INTEGER,
      er1645v2PbbBGriMVIpV6RsMaxRandomDelay
         TimeTicks,
      er1645v2PbbBGriMVIpV6RsInterval
         TimeTicks,
      er1645v2PbbBGriMVIpV6RsMaxSolicitations
         Integer32,
      er1645v2PbbBGriMVIpV6TrafficPolicyInbound
         DisplayString,
      er1645v2PbbBGriMVIpV6TrafficPolicyOutbound
         DisplayString,
      er1645v2PbbBGriMVIpV6FirewallZone
         DisplayString,
      er1645v2PbbBGriMVIpV6DhcpClientAddrAC
         INTEGER,
      er1645v2PbbBGriMVIpV6DhcpClientPrDelMode
         INTEGER,
      er1645v2PbbBGriMVIpV6DhcpClientPrDelPool
         DisplayString,
      er1645v2PbbBGriMVIpV6DhcpClientPrDelPdExclOpt
         INTEGER,
      er1645v2PbbBGriMVIpV6DhcpClientDnsServerPref
         Integer32,
      er1645v2PbbBGriMVIpV6DhcpClientRapidCommit
         INTEGER,
      er1645v2PbbBGriMVIpV6DhcpClientTimersSolTimeOut
         TimeTicks,
      er1645v2PbbBGriMVIpV6DhcpClientTimersSolMaxRt
         TimeTicks,
      er1645v2PbbBGriMVIpV6DhcpClientTimersInfoRefresh
         TimeTicks,
      er1645v2PbbBGriMVIpV6DhcpServerMode
         INTEGER,
      er1645v2PbbBGriMVIpV6DhcpServerPreference
         Integer32,
      er1645v2PbbBGriMVIpV6DhcpServerPool
         DisplayString,
      er1645v2PbbBGriMVIpV6DhcpServerRapidCommit
         INTEGER,
      er1645v2PbbBGriMVIpV6DhcpServerTimersInfoRefresh
         TimeTicks,
      er1645v2PbbBGriMVIpV6DhcpRelayMode
         INTEGER,
      er1645v2PbbBGriMVIpV6SendRedirect
         INTEGER,
      er1645v2PbbBGriMVIpV6LinkMtu
         Integer32,
      er1645v2PbbBGriMVIpV6InterfaceId
         OCTET STRING,
      er1645v2PbbBGriMVIpV6MF
         Integer32,
      er1645v2PbbBGriMVIpV6IcmpMessagesNoRoute
         INTEGER,
      er1645v2PbbBGriMVIpV6IcmpMessagesBeyondScope
         INTEGER,
      er1645v2PbbBGriMVIpV6IcmpMessagesAddressUnreachable
         INTEGER,
      er1645v2PbbBGriMVIpV6IcmpMessagesPortUnreachable
         INTEGER,
      er1645v2PbbBGriMVIpV6IcmpMessagesPacketTooBig
         INTEGER,
      er1645v2PbbBGriMVIpV6IcmpMessagesHopLimitExceeded
         INTEGER,
      er1645v2PbbBGriMVIpV6IcmpMessagesFragTimeExceeded
         INTEGER,
      er1645v2PbbBGriMVIpV6IcmpMessagesHeaderFieldErr
         INTEGER,
      er1645v2PbbBGriMVIpV6IcmpMessagesOptionUnrecognized
         INTEGER,
      er1645v2PbbBGriMVIpV6IcmpMessagesRedirect
         INTEGER
      }

er1645v2PbbBGriMVIpV6GlobalIx OBJECT-TYPE
   SYNTAX      GlobalIndex
   MAX-ACCESS  not-accessible
   STATUS      current
   DESCRIPTION
      "The value of the tlsCntTreeGlobalIndex of the MANAGED OBJECT."
   ::= {er1645v2PbbBGriMVIpV6Entry 10}

er1645v2PbbBGriMVIpV6VrfRouter OBJECT-TYPE
   SYNTAX      DisplayString
   MAX-ACCESS  read-write
   STATUS      current
   DESCRIPTION
      "Path: pbbBridgeGroup.editConf.ipV6.vrfRouter"
   ::= {er1645v2PbbBGriMVIpV6Entry 16777216}

er1645v2PbbBGriMVIpV6AddrAutoConfigNrDupAddrDetects OBJECT-TYPE
   SYNTAX      Integer32
   MAX-ACCESS  read-write
   STATUS      current
   DESCRIPTION
      "Path: pbbBridgeGroup.editConf.ipV6.addrAutoConfig.nrDupAddrDetects"
   ::= {er1645v2PbbBGriMVIpV6Entry 67174400}

er1645v2PbbBGriMVIpV6AddrAutoConfigAcceptRa OBJECT-TYPE
   SYNTAX      INTEGER
               {
               disabled (0),
               enabled (1)
               }
   MAX-ACCESS  read-write
   STATUS      current
   DESCRIPTION
      "Path: pbbBridgeGroup.editConf.ipV6.addrAutoConfig.acceptRa

       Possibilities:
               disabled   (0)
               enabled   (1)"
   ::= {er1645v2PbbBGriMVIpV6Entry 67239936}

er1645v2PbbBGriMVIpV6AddrAutoConfigAcceptRaRdnss OBJECT-TYPE
   SYNTAX      INTEGER
               {
               disabled (0),
               enabled (1)
               }
   MAX-ACCESS  read-write
   STATUS      current
   DESCRIPTION
      "Path: pbbBridgeGroup.editConf.ipV6.addrAutoConfig.acceptRaRdnss

       Possibilities:
               disabled   (0)
               enabled   (1)"
   ::= {er1645v2PbbBGriMVIpV6Entry 67305472}

er1645v2PbbBGriMVIpV6AddrAutoConfigAcceptRaDnssl OBJECT-TYPE
   SYNTAX      INTEGER
               {
               disabled (0),
               enabled (1)
               }
   MAX-ACCESS  read-write
   STATUS      current
   DESCRIPTION
      "Path: pbbBridgeGroup.editConf.ipV6.addrAutoConfig.acceptRaDnssl

       Possibilities:
               disabled   (0)
               enabled   (1)"
   ::= {er1645v2PbbBGriMVIpV6Entry 67371008}

er1645v2PbbBGriMVIpV6DefaultRoute OBJECT-TYPE
   SYNTAX      INTEGER
               {
               disabled (0),
               enabled (1)
               }
   MAX-ACCESS  read-write
   STATUS      current
   DESCRIPTION
      "Path: pbbBridgeGroup.editConf.ipV6.defaultRoute

       Possibilities:
               disabled   (0)
               enabled   (1)"
   ::= {er1645v2PbbBGriMVIpV6Entry 83886080}

er1645v2PbbBGriMVIpV6RaSend OBJECT-TYPE
   SYNTAX      INTEGER
               {
               disabled (0),
               enabled (1)
               }
   MAX-ACCESS  read-write
   STATUS      current
   DESCRIPTION
      "Path: pbbBridgeGroup.editConf.ipV6.ra.send

       Possibilities:
               disabled   (0)
               enabled   (1)"
   ::= {er1645v2PbbBGriMVIpV6Entry 100728832}

er1645v2PbbBGriMVIpV6RaMinInterval OBJECT-TYPE
   SYNTAX      TimeTicks
   MAX-ACCESS  read-write
   STATUS      current
   DESCRIPTION
      "Path: pbbBridgeGroup.editConf.ipV6.ra.minInterval

       Time in centi-second."
   ::= {er1645v2PbbBGriMVIpV6Entry 100794368}

er1645v2PbbBGriMVIpV6RaMaxInterval OBJECT-TYPE
   SYNTAX      TimeTicks
   MAX-ACCESS  read-write
   STATUS      current
   DESCRIPTION
      "Path: pbbBridgeGroup.editConf.ipV6.ra.maxInterval

       Time in centi-second."
   ::= {er1645v2PbbBGriMVIpV6Entry 100859904}

er1645v2PbbBGriMVIpV6RaManagedFlag OBJECT-TYPE
   SYNTAX      INTEGER
               {
               disabled (0),
               enabled (1)
               }
   MAX-ACCESS  read-write
   STATUS      current
   DESCRIPTION
      "Path: pbbBridgeGroup.editConf.ipV6.ra.managedFlag

       Possibilities:
               disabled   (0)
               enabled   (1)"
   ::= {er1645v2PbbBGriMVIpV6Entry 100925440}

er1645v2PbbBGriMVIpV6RaOtherConfFlag OBJECT-TYPE
   SYNTAX      INTEGER
               {
               disabled (0),
               enabled (1)
               }
   MAX-ACCESS  read-write
   STATUS      current
   DESCRIPTION
      "Path: pbbBridgeGroup.editConf.ipV6.ra.otherConfFlag

       Possibilities:
               disabled   (0)
               enabled   (1)"
   ::= {er1645v2PbbBGriMVIpV6Entry 100990976}

er1645v2PbbBGriMVIpV6RaLinkMtu OBJECT-TYPE
   SYNTAX      Integer32
   MAX-ACCESS  read-write
   STATUS      current
   DESCRIPTION
      "Path: pbbBridgeGroup.editConf.ipV6.ra.linkMtu"
   ::= {er1645v2PbbBGriMVIpV6Entry 101056512}

er1645v2PbbBGriMVIpV6RaReachableTime OBJECT-TYPE
   SYNTAX      TimeTicks
   MAX-ACCESS  read-write
   STATUS      current
   DESCRIPTION
      "Path: pbbBridgeGroup.editConf.ipV6.ra.reachableTime

       Time in centi-second."
   ::= {er1645v2PbbBGriMVIpV6Entry 101122048}

er1645v2PbbBGriMVIpV6RaRetransmitTime OBJECT-TYPE
   SYNTAX      TimeTicks
   MAX-ACCESS  read-write
   STATUS      current
   DESCRIPTION
      "Path: pbbBridgeGroup.editConf.ipV6.ra.retransmitTime

       Time in centi-second."
   ::= {er1645v2PbbBGriMVIpV6Entry 101187584}

er1645v2PbbBGriMVIpV6RaHopLimit OBJECT-TYPE
   SYNTAX      Integer32
   MAX-ACCESS  read-write
   STATUS      current
   DESCRIPTION
      "Path: pbbBridgeGroup.editConf.ipV6.ra.hopLimit"
   ::= {er1645v2PbbBGriMVIpV6Entry 101253120}

er1645v2PbbBGriMVIpV6RaDefaultLifeTime OBJECT-TYPE
   SYNTAX      TimeTicks
   MAX-ACCESS  read-write
   STATUS      current
   DESCRIPTION
      "Path: pbbBridgeGroup.editConf.ipV6.ra.defaultLifeTime

       Time in centi-second."
   ::= {er1645v2PbbBGriMVIpV6Entry 101318656}

er1645v2PbbBGriMVIpV6RaDnsOptionsRdnssLifeTime OBJECT-TYPE
   SYNTAX      TimeTicks
   MAX-ACCESS  read-write
   STATUS      current
   DESCRIPTION
      "Path: pbbBridgeGroup.editConf.ipV6.ra.dnsOptions.rdnss.lifeTime

       Time in centi-second."
   ::= {er1645v2PbbBGriMVIpV6Entry 101393408}

er1645v2PbbBGriMVIpV6RaDnsOptionsRdnssImportServers OBJECT-TYPE
   SYNTAX      INTEGER
               {
               disabled (0),
               enabled (1)
               }
   MAX-ACCESS  read-write
   STATUS      current
   DESCRIPTION
      "Path: pbbBridgeGroup.editConf.ipV6.ra.dnsOptions.rdnss.importServers

       Possibilities:
               disabled   (0)
               enabled   (1)"
   ::= {er1645v2PbbBGriMVIpV6Entry 101395456}

er1645v2PbbBGriMVIpV6RaDnsOptionsDnsslLifeTime OBJECT-TYPE
   SYNTAX      TimeTicks
   MAX-ACCESS  read-write
   STATUS      current
   DESCRIPTION
      "Path: pbbBridgeGroup.editConf.ipV6.ra.dnsOptions.dnssl.lifeTime

       Time in centi-second."
   ::= {er1645v2PbbBGriMVIpV6Entry 101401600}

er1645v2PbbBGriMVIpV6RaDnsOptionsDnsslImportDomains OBJECT-TYPE
   SYNTAX      INTEGER
               {
               disabled (0),
               enabled (1)
               }
   MAX-ACCESS  read-write
   STATUS      current
   DESCRIPTION
      "Path: pbbBridgeGroup.editConf.ipV6.ra.dnsOptions.dnssl.importDomains

       Possibilities:
               disabled   (0)
               enabled   (1)"
   ::= {er1645v2PbbBGriMVIpV6Entry 101403648}

er1645v2PbbBGriMVIpV6RsSend OBJECT-TYPE
   SYNTAX      INTEGER
               {
               disabled (0),
               enabled (1)
               }
   MAX-ACCESS  read-write
   STATUS      current
   DESCRIPTION
      "Path: pbbBridgeGroup.editConf.ipV6.rs.send

       Possibilities:
               disabled   (0)
               enabled   (1)"
   ::= {er1645v2PbbBGriMVIpV6Entry 335609856}

er1645v2PbbBGriMVIpV6RsMaxRandomDelay OBJECT-TYPE
   SYNTAX      TimeTicks
   MAX-ACCESS  read-write
   STATUS      current
   DESCRIPTION
      "Path: pbbBridgeGroup.editConf.ipV6.rs.maxRandomDelay

       Time in centi-second."
   ::= {er1645v2PbbBGriMVIpV6Entry 335675392}

er1645v2PbbBGriMVIpV6RsInterval OBJECT-TYPE
   SYNTAX      TimeTicks
   MAX-ACCESS  read-write
   STATUS      current
   DESCRIPTION
      "Path: pbbBridgeGroup.editConf.ipV6.rs.interval

       Time in centi-second."
   ::= {er1645v2PbbBGriMVIpV6Entry 335740928}

er1645v2PbbBGriMVIpV6RsMaxSolicitations OBJECT-TYPE
   SYNTAX      Integer32
   MAX-ACCESS  read-write
   STATUS      current
   DESCRIPTION
      "Path: pbbBridgeGroup.editConf.ipV6.rs.maxSolicitations"
   ::= {er1645v2PbbBGriMVIpV6Entry 335806464}

er1645v2PbbBGriMVIpV6TrafficPolicyInbound OBJECT-TYPE
   SYNTAX      DisplayString
   MAX-ACCESS  read-write
   STATUS      current
   DESCRIPTION
      "Path: pbbBridgeGroup.editConf.ipV6.trafficPolicy.inbound"
   ::= {er1645v2PbbBGriMVIpV6Entry 184614912}

er1645v2PbbBGriMVIpV6TrafficPolicyOutbound OBJECT-TYPE
   SYNTAX      DisplayString
   MAX-ACCESS  read-write
   STATUS      current
   DESCRIPTION
      "Path: pbbBridgeGroup.editConf.ipV6.trafficPolicy.outbound"
   ::= {er1645v2PbbBGriMVIpV6Entry 184680448}

er1645v2PbbBGriMVIpV6FirewallZone OBJECT-TYPE
   SYNTAX      DisplayString
   MAX-ACCESS  read-write
   STATUS      current
   DESCRIPTION
      "Path: pbbBridgeGroup.editConf.ipV6.firewall.zone"
   ::= {er1645v2PbbBGriMVIpV6Entry 201392128}

er1645v2PbbBGriMVIpV6DhcpClientAddrAC OBJECT-TYPE
   SYNTAX      INTEGER
               {
               disabled (0),
               enabled (1)
               }
   MAX-ACCESS  read-write
   STATUS      current
   DESCRIPTION
      "Path: pbbBridgeGroup.editConf.ipV6.dhcp.client.addrAutoConfig

       Possibilities:
               disabled   (0)
               enabled   (1)"
   ::= {er1645v2PbbBGriMVIpV6Entry 170131456}

er1645v2PbbBGriMVIpV6DhcpClientPrDelMode OBJECT-TYPE
   SYNTAX      INTEGER
               {
               disabled (0),
               enabled (1)
               }
   MAX-ACCESS  read-write
   STATUS      current
   DESCRIPTION
      "Path: pbbBridgeGroup.editConf.ipV6.dhcp.client.pd.mode

       Possibilities:
               disabled   (0)
               enabled   (1)"
   ::= {er1645v2PbbBGriMVIpV6Entry 170394624}

er1645v2PbbBGriMVIpV6DhcpClientPrDelPool OBJECT-TYPE
   SYNTAX      DisplayString
   MAX-ACCESS  read-write
   STATUS      current
   DESCRIPTION
      "Path: pbbBridgeGroup.editConf.ipV6.dhcp.client.pd.pool"
   ::= {er1645v2PbbBGriMVIpV6Entry 170395648}

er1645v2PbbBGriMVIpV6DhcpClientPrDelPdExclOpt OBJECT-TYPE
   SYNTAX      INTEGER
               {
               disabled (0),
               enabled (1)
               }
   MAX-ACCESS  read-write
   STATUS      current
   DESCRIPTION
      "Path: pbbBridgeGroup.editConf.ipV6.dhcp.client.pd.pdExclOpt

       Possibilities:
               disabled   (0)
               enabled   (1)"
   ::= {er1645v2PbbBGriMVIpV6Entry 170396672}

er1645v2PbbBGriMVIpV6DhcpClientDnsServerPref OBJECT-TYPE
   SYNTAX      Integer32
   MAX-ACCESS  read-write
   STATUS      current
   DESCRIPTION
      "Path: pbbBridgeGroup.editConf.ipV6.dhcp.client.dns.serverPref"
   ::= {er1645v2PbbBGriMVIpV6Entry 170918912}

er1645v2PbbBGriMVIpV6DhcpClientRapidCommit OBJECT-TYPE
   SYNTAX      INTEGER
               {
               disabled (0),
               enabled (1)
               }
   MAX-ACCESS  read-write
   STATUS      current
   DESCRIPTION
      "Path: pbbBridgeGroup.editConf.ipV6.dhcp.client.rapidCommit

       Possibilities:
               disabled   (0)
               enabled   (1)"
   ::= {er1645v2PbbBGriMVIpV6Entry 170655744}

er1645v2PbbBGriMVIpV6DhcpClientTimersSolTimeOut OBJECT-TYPE
   SYNTAX      TimeTicks
   MAX-ACCESS  read-write
   STATUS      current
   DESCRIPTION
      "Path: pbbBridgeGroup.editConf.ipV6.dhcp.client.timers.solTimeOut

       Time in centi-second."
   ::= {er1645v2PbbBGriMVIpV6Entry 171181056}

er1645v2PbbBGriMVIpV6DhcpClientTimersSolMaxRt OBJECT-TYPE
   SYNTAX      TimeTicks
   MAX-ACCESS  read-write
   STATUS      current
   DESCRIPTION
      "Path: pbbBridgeGroup.editConf.ipV6.dhcp.client.timers.solMaxRt

       Time in centi-second."
   ::= {er1645v2PbbBGriMVIpV6Entry 171182080}

er1645v2PbbBGriMVIpV6DhcpClientTimersInfoRefresh OBJECT-TYPE
   SYNTAX      TimeTicks
   MAX-ACCESS  read-write
   STATUS      current
   DESCRIPTION
      "Path: pbbBridgeGroup.editConf.ipV6.dhcp.client.timers.infoRefresh

       Time in centi-second."
   ::= {er1645v2PbbBGriMVIpV6Entry 171183104}

er1645v2PbbBGriMVIpV6DhcpServerMode OBJECT-TYPE
   SYNTAX      INTEGER
               {
               disabled (0),
               enabled (1)
               }
   MAX-ACCESS  read-write
   STATUS      current
   DESCRIPTION
      "Path: pbbBridgeGroup.editConf.ipV6.dhcp.server.mode

       Possibilities:
               disabled   (0)
               enabled   (1)"
   ::= {er1645v2PbbBGriMVIpV6Entry 172228608}

er1645v2PbbBGriMVIpV6DhcpServerPreference OBJECT-TYPE
   SYNTAX      Integer32
   MAX-ACCESS  read-write
   STATUS      current
   DESCRIPTION
      "Path: pbbBridgeGroup.editConf.ipV6.dhcp.server.preference"
   ::= {er1645v2PbbBGriMVIpV6Entry 172490752}

er1645v2PbbBGriMVIpV6DhcpServerPool OBJECT-TYPE
   SYNTAX      DisplayString
   MAX-ACCESS  read-write
   STATUS      current
   DESCRIPTION
      "Path: pbbBridgeGroup.editConf.ipV6.dhcp.server.pool"
   ::= {er1645v2PbbBGriMVIpV6Entry 172752896}

er1645v2PbbBGriMVIpV6DhcpServerRapidCommit OBJECT-TYPE
   SYNTAX      INTEGER
               {
               disabled (0),
               enabled (1)
               }
   MAX-ACCESS  read-write
   STATUS      current
   DESCRIPTION
      "Path: pbbBridgeGroup.editConf.ipV6.dhcp.server.rapidCommit

       Possibilities:
               disabled   (0)
               enabled   (1)"
   ::= {er1645v2PbbBGriMVIpV6Entry 173015040}

er1645v2PbbBGriMVIpV6DhcpServerTimersInfoRefresh OBJECT-TYPE
   SYNTAX      TimeTicks
   MAX-ACCESS  read-write
   STATUS      current
   DESCRIPTION
      "Path: pbbBridgeGroup.editConf.ipV6.dhcp.server.timers.infoRefresh

       Time in centi-second."
   ::= {er1645v2PbbBGriMVIpV6Entry 173278208}

er1645v2PbbBGriMVIpV6DhcpRelayMode OBJECT-TYPE
   SYNTAX      INTEGER
               {
               disabled (0),
               enabled (1)
               }
   MAX-ACCESS  read-write
   STATUS      current
   DESCRIPTION
      "Path: pbbBridgeGroup.editConf.ipV6.dhcp.relay.mode

       Possibilities:
               disabled   (0)
               enabled   (1)"
   ::= {er1645v2PbbBGriMVIpV6Entry 174071808}

er1645v2PbbBGriMVIpV6SendRedirect OBJECT-TYPE
   SYNTAX      INTEGER
               {
               disabled (0),
               enabled (1)
               }
   MAX-ACCESS  read-write
   STATUS      current
   DESCRIPTION
      "Path: pbbBridgeGroup.editConf.ipV6.sendRedirect

       Possibilities:
               disabled   (0)
               enabled   (1)"
   ::= {er1645v2PbbBGriMVIpV6Entry 117440512}

er1645v2PbbBGriMVIpV6LinkMtu OBJECT-TYPE
   SYNTAX      Integer32
   MAX-ACCESS  read-write
   STATUS      current
   DESCRIPTION
      "Path: pbbBridgeGroup.editConf.ipV6.linkMtu"
   ::= {er1645v2PbbBGriMVIpV6Entry 134217728}

er1645v2PbbBGriMVIpV6InterfaceId OBJECT-TYPE
   SYNTAX      OCTET STRING
   MAX-ACCESS  read-write
   STATUS      current
   DESCRIPTION
      "Path: pbbBridgeGroup.editConf.ipV6.interfaceId"
   ::= {er1645v2PbbBGriMVIpV6Entry 150994944}

er1645v2PbbBGriMVIpV6MF OBJECT-TYPE
   SYNTAX      Integer32
   MAX-ACCESS  read-write
   STATUS      current
   DESCRIPTION
      "Path: pbbBridgeGroup.editConf.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2PbbBGriMVIpV6Entry 285212672}

er1645v2PbbBGriMVIpV6IcmpMessagesNoRoute OBJECT-TYPE
   SYNTAX      INTEGER
               {
               disabled (0),
               enabled (1)
               }
   MAX-ACCESS  read-write
   STATUS      current
   DESCRIPTION
      "Path: pbbBridgeGroup.editConf.ipV6.icmpMessages.noRoute

       Possibilities:
               disabled   (0)
               enabled   (1)"
   ::= {er1645v2PbbBGriMVIpV6Entry 302055424}

er1645v2PbbBGriMVIpV6IcmpMessagesBeyondScope OBJECT-TYPE
   SYNTAX      INTEGER
               {
               disabled (0),
               enabled (1)
               }
   MAX-ACCESS  read-write
   STATUS      current
   DESCRIPTION
      "Path: pbbBridgeGroup.editConf.ipV6.icmpMessages.beyondScope

       Possibilities:
               disabled   (0)
               enabled   (1)"
   ::= {er1645v2PbbBGriMVIpV6Entry 302186496}

er1645v2PbbBGriMVIpV6IcmpMessagesAddressUnreachable OBJECT-TYPE
   SYNTAX      INTEGER
               {
               disabled (0),
               enabled (1)
               }
   MAX-ACCESS  read-write
   STATUS      current
   DESCRIPTION
      "Path: pbbBridgeGroup.editConf.ipV6.icmpMessages.addressUnreachable

       Possibilities:
               disabled   (0)
               enabled   (1)"
   ::= {er1645v2PbbBGriMVIpV6Entry 302252032}

er1645v2PbbBGriMVIpV6IcmpMessagesPortUnreachable OBJECT-TYPE
   SYNTAX      INTEGER
               {
               disabled (0),
               enabled (1)
               }
   MAX-ACCESS  read-write
   STATUS      current
   DESCRIPTION
      "Path: pbbBridgeGroup.editConf.ipV6.icmpMessages.portUnreachable

       Possibilities:
               disabled   (0)
               enabled   (1)"
   ::= {er1645v2PbbBGriMVIpV6Entry 302317568}

er1645v2PbbBGriMVIpV6IcmpMessagesPacketTooBig OBJECT-TYPE
   SYNTAX      INTEGER
               {
               disabled (0),
               enabled (1)
               }
   MAX-ACCESS  read-write
   STATUS      current
   DESCRIPTION
      "Path: pbbBridgeGroup.editConf.ipV6.icmpMessages.packetTooBig

       Possibilities:
               disabled   (0)
               enabled   (1)"
   ::= {er1645v2PbbBGriMVIpV6Entry 302645248}

er1645v2PbbBGriMVIpV6IcmpMessagesHopLimitExceeded OBJECT-TYPE
   SYNTAX      INTEGER
               {
               disabled (0),
               enabled (1)
               }
   MAX-ACCESS  read-write
   STATUS      current
   DESCRIPTION
      "Path: pbbBridgeGroup.editConf.ipV6.icmpMessages.hopLimitExceeded

       Possibilities:
               disabled   (0)
               enabled   (1)"
   ::= {er1645v2PbbBGriMVIpV6Entry 303300608}

er1645v2PbbBGriMVIpV6IcmpMessagesFragTimeExceeded OBJECT-TYPE
   SYNTAX      INTEGER
               {
               disabled (0),
               enabled (1)
               }
   MAX-ACCESS  read-write
   STATUS      current
   DESCRIPTION
      "Path: pbbBridgeGroup.editConf.ipV6.icmpMessages.fragTimeExceeded

       Possibilities:
               disabled   (0)
               enabled   (1)"
   ::= {er1645v2PbbBGriMVIpV6Entry 303366144}

er1645v2PbbBGriMVIpV6IcmpMessagesHeaderFieldErr OBJECT-TYPE
   SYNTAX      INTEGER
               {
               disabled (0),
               enabled (1)
               }
   MAX-ACCESS  read-write
   STATUS      current
   DESCRIPTION
      "Path: pbbBridgeGroup.editConf.ipV6.icmpMessages.headerFieldErr

       Possibilities:
               disabled   (0)
               enabled   (1)"
   ::= {er1645v2PbbBGriMVIpV6Entry 303955968}

er1645v2PbbBGriMVIpV6IcmpMessagesOptionUnrecognized OBJECT-TYPE
   SYNTAX      INTEGER
               {
               disabled (0),
               enabled (1)
               }
   MAX-ACCESS  read-write
   STATUS      current
   DESCRIPTION
      "Path: pbbBridgeGroup.editConf.ipV6.icmpMessages.optionUnrecognized

       Possibilities:
               disabled   (0)
               enabled   (1)"
   ::= {er1645v2PbbBGriMVIpV6Entry 304087040}

er1645v2PbbBGriMVIpV6IcmpMessagesRedirect OBJECT-TYPE
   SYNTAX      INTEGER
               {
               disabled (0),
               enabled (1)
               }
   MAX-ACCESS  read-write
   STATUS      current
   DESCRIPTION
      "Path: pbbBridgeGroup.editConf.ipV6.icmpMessages.redirect

       Possibilities:
               disabled   (0)
               enabled   (1)"
   ::= {er1645v2PbbBGriMVIpV6Entry 304611328}

er1645v2PbbBGriMVIpV6Addresses OBJECT-TYPE
   SYNTAX      SEQUENCE OF Er1645v2PbbBGriMVIpV6AddressesEntry
   MAX-ACCESS  not-accessible
   STATUS      current
   DESCRIPTION
      ""
   ::= {er1645v2PbbBGriMVIpV6 50331648}

er1645v2PbbBGriMVIpV6AddressesEntry OBJECT-TYPE
   SYNTAX      Er1645v2PbbBGriMVIpV6AddressesEntry
   MAX-ACCESS  not-accessible
   STATUS      current
   DESCRIPTION
      ""
   INDEX      { er1645v2PbbBGriMVIpV6AddressesGlobalIx,
                er1645v2PbbBGriMVIpV6AddressesTableIx }
   ::= {er1645v2PbbBGriMVIpV6Addresses 1}

Er1645v2PbbBGriMVIpV6AddressesEntry ::=
   SEQUENCE
      {
      er1645v2PbbBGriMVIpV6AddressesActions
         VariableLengthTableActions,
      er1645v2PbbBGriMVIpV6AddressesGlobalIx
         GlobalIndex,
      er1645v2PbbBGriMVIpV6AddressesTableIx
         TableIndex,
      er1645v2PbbBGriMVIpV6AddressesType
         INTEGER,
      er1645v2PbbBGriMVIpV6AddressesAddress
         Ipv6Address,
      er1645v2PbbBGriMVIpV6AddressesPrefixLength
         Integer32,
      er1645v2PbbBGriMVIpV6AddressesGeneralPrefix
         DisplayString,
      er1645v2PbbBGriMVIpV6AddressesRaSend
         INTEGER,
      er1645v2PbbBGriMVIpV6AddressesRaOnLinkFlag
         INTEGER,
      er1645v2PbbBGriMVIpV6AddressesRaAutoFlag
         INTEGER,
      er1645v2PbbBGriMVIpV6AddressesRaValidLifeTime
         TimeTicks,
      er1645v2PbbBGriMVIpV6AddressesRaValidLTMode
         INTEGER,
      er1645v2PbbBGriMVIpV6AddressesRaPrefLifeTime
         TimeTicks,
      er1645v2PbbBGriMVIpV6AddressesRaPrefLTMode
         INTEGER
      }

er1645v2PbbBGriMVIpV6AddressesActions OBJECT-TYPE
   SYNTAX      VariableLengthTableActions
   MAX-ACCESS  read-write
   STATUS      current
   DESCRIPTION
      "By way of this field, some manipulations
       on this table may be performed."
   ::= {er1645v2PbbBGriMVIpV6AddressesEntry 2}

er1645v2PbbBGriMVIpV6AddressesGlobalIx OBJECT-TYPE
   SYNTAX      GlobalIndex
   MAX-ACCESS  not-accessible
   STATUS      current
   DESCRIPTION
      "The value of the tlsCntTreeGlobalIndex of the MANAGED OBJECT."
   ::= {er1645v2PbbBGriMVIpV6AddressesEntry 10}

er1645v2PbbBGriMVIpV6AddressesTableIx OBJECT-TYPE
   SYNTAX      TableIndex
   MAX-ACCESS  not-accessible
   STATUS      current
   DESCRIPTION
      ""
   ::= {er1645v2PbbBGriMVIpV6AddressesEntry 11}

er1645v2PbbBGriMVIpV6AddressesType OBJECT-TYPE
   SYNTAX      INTEGER
               {
               unicast (0),
               eui64 (1),
               anycast (2),
               linkLocal (3),
               generalPrefix (4)
               }
   MAX-ACCESS  read-write
   STATUS      current
   DESCRIPTION
      "Path: pbbBridgeGroup.editConf.ipV6.addresses.type

       Possibilities:
               unicast   (0)
               eui64   (1)
               anycast   (2)
               linkLocal   (3)
               generalPrefix   (4)"
   ::= {er1645v2PbbBGriMVIpV6AddressesEntry 50331648}

er1645v2PbbBGriMVIpV6AddressesAddress OBJECT-TYPE
   SYNTAX      Ipv6Address
   MAX-ACCESS  read-write
   STATUS      current
   DESCRIPTION
      "Path: pbbBridgeGroup.editConf.ipV6.addresses.address

       ipv6 address"
   ::= {er1645v2PbbBGriMVIpV6AddressesEntry 16777216}

er1645v2PbbBGriMVIpV6AddressesPrefixLength OBJECT-TYPE
   SYNTAX      Integer32
   MAX-ACCESS  read-write
   STATUS      current
   DESCRIPTION
      "Path: pbbBridgeGroup.editConf.ipV6.addresses.prefixLength"
   ::= {er1645v2PbbBGriMVIpV6AddressesEntry 33554432}

er1645v2PbbBGriMVIpV6AddressesGeneralPrefix OBJECT-TYPE
   SYNTAX      DisplayString
   MAX-ACCESS  read-write
   STATUS      current
   DESCRIPTION
      "Path: pbbBridgeGroup.editConf.ipV6.addresses.generalPrefix"
   ::= {er1645v2PbbBGriMVIpV6AddressesEntry 83886080}

er1645v2PbbBGriMVIpV6AddressesRaSend OBJECT-TYPE
   SYNTAX      INTEGER
               {
               disabled (0),
               enabled (1)
               }
   MAX-ACCESS  read-write
   STATUS      current
   DESCRIPTION
      "Path: pbbBridgeGroup.editConf.ipV6.addresses.ra.send

       Possibilities:
               disabled   (0)
               enabled   (1)"
   ::= {er1645v2PbbBGriMVIpV6AddressesEntry 67174400}

er1645v2PbbBGriMVIpV6AddressesRaOnLinkFlag OBJECT-TYPE
   SYNTAX      INTEGER
               {
               disabled (0),
               enabled (1)
               }
   MAX-ACCESS  read-write
   STATUS      current
   DESCRIPTION
      "Path: pbbBridgeGroup.editConf.ipV6.addresses.ra.onLinkFlag

       Possibilities:
               disabled   (0)
               enabled   (1)"
   ::= {er1645v2PbbBGriMVIpV6AddressesEntry 67371008}

er1645v2PbbBGriMVIpV6AddressesRaAutoFlag OBJECT-TYPE
   SYNTAX      INTEGER
               {
               disabled (0),
               enabled (1)
               }
   MAX-ACCESS  read-write
   STATUS      current
   DESCRIPTION
      "Path: pbbBridgeGroup.editConf.ipV6.addresses.ra.autonomousFlag

       Possibilities:
               disabled   (0)
               enabled   (1)"
   ::= {er1645v2PbbBGriMVIpV6AddressesEntry 67567616}

er1645v2PbbBGriMVIpV6AddressesRaValidLifeTime OBJECT-TYPE
   SYNTAX      TimeTicks
   MAX-ACCESS  read-write
   STATUS      current
   DESCRIPTION
      "Path: pbbBridgeGroup.editConf.ipV6.addresses.ra.validLifeTime

       Time in centi-second."
   ::= {er1645v2PbbBGriMVIpV6AddressesEntry 67239936}

er1645v2PbbBGriMVIpV6AddressesRaValidLTMode OBJECT-TYPE
   SYNTAX      INTEGER
               {
               fixed (0),
               infinite (2)
               }
   MAX-ACCESS  read-write
   STATUS      current
   DESCRIPTION
      "Path: pbbBridgeGroup.editConf.ipV6.addresses.ra.validLifeTimeMode

       Possibilities:
               fixed   (0)
               infinite   (2)"
   ::= {er1645v2PbbBGriMVIpV6AddressesEntry 67305472}

er1645v2PbbBGriMVIpV6AddressesRaPrefLifeTime OBJECT-TYPE
   SYNTAX      TimeTicks
   MAX-ACCESS  read-write
   STATUS      current
   DESCRIPTION
      "Path: pbbBridgeGroup.editConf.ipV6.addresses.ra.prefLifeTime

       Time in centi-second."
   ::= {er1645v2PbbBGriMVIpV6AddressesEntry 67436544}

er1645v2PbbBGriMVIpV6AddressesRaPrefLTMode OBJECT-TYPE
   SYNTAX      INTEGER
               {
               fixed (0),
               infinite (2)
               }
   MAX-ACCESS  read-write
   STATUS      current
   DESCRIPTION
      "Path: pbbBridgeGroup.editConf.ipV6.addresses.ra.prefLifeTimeMode

       Possibilities:
               fixed   (0)
               infinite   (2)"
   ::= {er1645v2PbbBGriMVIpV6AddressesEntry 67502080}

er1645v2PbbBGriMVIpV6RaDnsOptionsRdnssServers OBJECT-TYPE
   SYNTAX      SEQUENCE OF Er1645v2PbbBGriMVIpV6RaDnsOptionsRdnssServersEntry
   MAX-ACCESS  not-accessible
   STATUS      current
   DESCRIPTION
      ""
   ::= {er1645v2PbbBGriMVIpV6 101394432}

er1645v2PbbBGriMVIpV6RaDnsOptionsRdnssServersEntry OBJECT-TYPE
   SYNTAX      Er1645v2PbbBGriMVIpV6RaDnsOptionsRdnssServersEntry
   MAX-ACCESS  not-accessible
   STATUS      current
   DESCRIPTION
      ""
   INDEX      { er1645v2PbbBGriMVIpV6RaDnsOptionsRdnssServersGlobalIx,
                er1645v2PbbBGriMVIpV6RaDnsOptionsRdnssServersTableIx }
   ::= {er1645v2PbbBGriMVIpV6RaDnsOptionsRdnssServers 1}

Er1645v2PbbBGriMVIpV6RaDnsOptionsRdnssServersEntry ::=
   SEQUENCE
      {
      er1645v2PbbBGriMVIpV6RaDnsOptionsRdnssServersActions
         VariableLengthTableActions,
      er1645v2PbbBGriMVIpV6RaDnsOptionsRdnssServersGlobalIx
         GlobalIndex,
      er1645v2PbbBGriMVIpV6RaDnsOptionsRdnssServersTableIx
         TableIndex,
      er1645v2PbbBGriMVIpV6RaDnsOptionsRdnssServersAddress
         Ipv6Address
      }

er1645v2PbbBGriMVIpV6RaDnsOptionsRdnssServersActions OBJECT-TYPE
   SYNTAX      VariableLengthTableActions
   MAX-ACCESS  read-write
   STATUS      current
   DESCRIPTION
      "By way of this field, some manipulations
       on this table may be performed."
   ::= {er1645v2PbbBGriMVIpV6RaDnsOptionsRdnssServersEntry 2}

er1645v2PbbBGriMVIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2PbbBGriMVIpV6RaDnsOptionsRdnssServersEntry 10}

er1645v2PbbBGriMVIpV6RaDnsOptionsRdnssServersTableIx OBJECT-TYPE
   SYNTAX      TableIndex
   MAX-ACCESS  not-accessible
   STATUS      current
   DESCRIPTION
      ""
   ::= {er1645v2PbbBGriMVIpV6RaDnsOptionsRdnssServersEntry 11}

er1645v2PbbBGriMVIpV6RaDnsOptionsRdnssServersAddress OBJECT-TYPE
   SYNTAX      Ipv6Address
   MAX-ACCESS  read-write
   STATUS      current
   DESCRIPTION
      "Path: pbbBridgeGroup.editConf.ipV6.ra.dnsOptions.rdnss.servers.address

       ipv6 address"
   ::= {er1645v2PbbBGriMVIpV6RaDnsOptionsRdnssServersEntry 16777216}

er1645v2PbbBGriMVIpV6RaDnsOptionsDnsslDomains OBJECT-TYPE
   SYNTAX      SEQUENCE OF Er1645v2PbbBGriMVIpV6RaDnsOptionsDnsslDomainsEntry
   MAX-ACCESS  not-accessible
   STATUS      current
   DESCRIPTION
      ""
   ::= {er1645v2PbbBGriMVIpV6 101402624}

er1645v2PbbBGriMVIpV6RaDnsOptionsDnsslDomainsEntry OBJECT-TYPE
   SYNTAX      Er1645v2PbbBGriMVIpV6RaDnsOptionsDnsslDomainsEntry
   MAX-ACCESS  not-accessible
   STATUS      current
   DESCRIPTION
      ""
   INDEX      { er1645v2PbbBGriMVIpV6RaDnsOptionsDnsslDomainsGlobalIx,
                er1645v2PbbBGriMVIpV6RaDnsOptionsDnsslDomainsTableIx }
   ::= {er1645v2PbbBGriMVIpV6RaDnsOptionsDnsslDomains 1}

Er1645v2PbbBGriMVIpV6RaDnsOptionsDnsslDomainsEntry ::=
   SEQUENCE
      {
      er1645v2PbbBGriMVIpV6RaDnsOptionsDnsslDomainsActions
         VariableLengthTableActions,
      er1645v2PbbBGriMVIpV6RaDnsOptionsDnsslDomainsGlobalIx
         GlobalIndex,
      er1645v2PbbBGriMVIpV6RaDnsOptionsDnsslDomainsTableIx
         TableIndex,
      er1645v2PbbBGriMVIpV6RaDnsOptionsDnsslDomainsName
         DisplayString
      }

er1645v2PbbBGriMVIpV6RaDnsOptionsDnsslDomainsActions OBJECT-TYPE
   SYNTAX      VariableLengthTableActions
   MAX-ACCESS  read-write
   STATUS      current
   DESCRIPTION
      "By way of this field, some manipulations
       on this table may be performed."
   ::= {er1645v2PbbBGriMVIpV6RaDnsOptionsDnsslDomainsEntry 2}

er1645v2PbbBGriMVIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2PbbBGriMVIpV6RaDnsOptionsDnsslDomainsEntry 10}

er1645v2PbbBGriMVIpV6RaDnsOptionsDnsslDomainsTableIx OBJECT-TYPE
   SYNTAX      TableIndex
   MAX-ACCESS  not-accessible
   STATUS      current
   DESCRIPTION
      ""
   ::= {er1645v2PbbBGriMVIpV6RaDnsOptionsDnsslDomainsEntry 11}

er1645v2PbbBGriMVIpV6RaDnsOptionsDnsslDomainsName OBJECT-TYPE
   SYNTAX      DisplayString
   MAX-ACCESS  read-write
   STATUS      current
   DESCRIPTION
      "Path: pbbBridgeGroup.editConf.ipV6.ra.dnsOptions.dnssl.domains.name"
   ::= {er1645v2PbbBGriMVIpV6RaDnsOptionsDnsslDomainsEntry 16777216}

er1645v2PbbBGriMVIpV6DhcpClientUserClassOpt OBJECT-TYPE
   SYNTAX      SEQUENCE OF Er1645v2PbbBGriMVIpV6DhcpClientUserClassOptEntry
   MAX-ACCESS  not-accessible
   STATUS      current
   DESCRIPTION
      ""
   ::= {er1645v2PbbBGriMVIpV6 171442176}

er1645v2PbbBGriMVIpV6DhcpClientUserClassOptEntry OBJECT-TYPE
   SYNTAX      Er1645v2PbbBGriMVIpV6DhcpClientUserClassOptEntry
   MAX-ACCESS  not-accessible
   STATUS      current
   DESCRIPTION
      ""
   INDEX      { er1645v2PbbBGriMVIpV6DhcpClientUserClassOptGlobalIx,
                er1645v2PbbBGriMVIpV6DhcpClientUserClassOptTableIx }
   ::= {er1645v2PbbBGriMVIpV6DhcpClientUserClassOpt 1}

Er1645v2PbbBGriMVIpV6DhcpClientUserClassOptEntry ::=
   SEQUENCE
      {
      er1645v2PbbBGriMVIpV6DhcpClientUserClassOptActions
         VariableLengthTableActions,
      er1645v2PbbBGriMVIpV6DhcpClientUserClassOptGlobalIx
         GlobalIndex,
      er1645v2PbbBGriMVIpV6DhcpClientUserClassOptTableIx
         TableIndex,
      er1645v2PbbBGriMVIpV6DhcpClientUserClassOptValueAscii
         DisplayString,
      er1645v2PbbBGriMVIpV6DhcpClientUserClassOptValueDecimal
         Integer32,
      er1645v2PbbBGriMVIpV6DhcpClientUserClassOptValueHexData
         OCTET STRING
      }

er1645v2PbbBGriMVIpV6DhcpClientUserClassOptActions OBJECT-TYPE
   SYNTAX      VariableLengthTableActions
   MAX-ACCESS  read-write
   STATUS      current
   DESCRIPTION
      "By way of this field, some manipulations
       on this table may be performed."
   ::= {er1645v2PbbBGriMVIpV6DhcpClientUserClassOptEntry 2}

er1645v2PbbBGriMVIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2PbbBGriMVIpV6DhcpClientUserClassOptEntry 10}

er1645v2PbbBGriMVIpV6DhcpClientUserClassOptTableIx OBJECT-TYPE
   SYNTAX      TableIndex
   MAX-ACCESS  not-accessible
   STATUS      current
   DESCRIPTION
      ""
   ::= {er1645v2PbbBGriMVIpV6DhcpClientUserClassOptEntry 11}

er1645v2PbbBGriMVIpV6DhcpClientUserClassOptValueAscii OBJECT-TYPE
   SYNTAX      DisplayString
   MAX-ACCESS  read-write
   STATUS      current
   DESCRIPTION
      "Path: pbbBridgeGroup.editConf.ipV6.dhcp.client.userClassOpt.value.ascii"
   ::= {er1645v2PbbBGriMVIpV6DhcpClientUserClassOptEntry 16842752}

er1645v2PbbBGriMVIpV6DhcpClientUserClassOptValueDecimal OBJECT-TYPE
   SYNTAX      Integer32
   MAX-ACCESS  read-write
   STATUS      current
   DESCRIPTION
      "Path: pbbBridgeGroup.editConf.ipV6.dhcp.client.userClassOpt.value.decimal"
   ::= {er1645v2PbbBGriMVIpV6DhcpClientUserClassOptEntry 16908288}

er1645v2PbbBGriMVIpV6DhcpClientUserClassOptValueHexData OBJECT-TYPE
   SYNTAX      OCTET STRING
   MAX-ACCESS  read-write
   STATUS      current
   DESCRIPTION
      "Path: pbbBridgeGroup.editConf.ipV6.dhcp.client.userClassOpt.value.hexData"
   ::= {er1645v2PbbBGriMVIpV6DhcpClientUserClassOptEntry 16973824}

er1645v2PbbBGriMVIpV6DhcpClientVendorCl OBJECT-TYPE
   SYNTAX      SEQUENCE OF Er1645v2PbbBGriMVIpV6DhcpClientVendorClEntry
   MAX-ACCESS  not-accessible
   STATUS      current
   DESCRIPTION
      ""
   ::= {er1645v2PbbBGriMVIpV6 171704320}

er1645v2PbbBGriMVIpV6DhcpClientVendorClEntry OBJECT-TYPE
   SYNTAX      Er1645v2PbbBGriMVIpV6DhcpClientVendorClEntry
   MAX-ACCESS  not-accessible
   STATUS      current
   DESCRIPTION
      ""
   INDEX      { er1645v2PbbBGriMVIpV6DhcpClientVendorClGlobalIx,
                er1645v2PbbBGriMVIpV6DhcpClientVendorClTableIx }
   ::= {er1645v2PbbBGriMVIpV6DhcpClientVendorCl 1}

Er1645v2PbbBGriMVIpV6DhcpClientVendorClEntry ::=
   SEQUENCE
      {
      er1645v2PbbBGriMVIpV6DhcpClientVendorClActions
         VariableLengthTableActions,
      er1645v2PbbBGriMVIpV6DhcpClientVendorClGlobalIx
         GlobalIndex,
      er1645v2PbbBGriMVIpV6DhcpClientVendorClTableIx
         TableIndex,
      er1645v2PbbBGriMVIpV6DhcpClientVendorClValueAscii
         DisplayString,
      er1645v2PbbBGriMVIpV6DhcpClientVendorClValueDecimal
         Integer32,
      er1645v2PbbBGriMVIpV6DhcpClientVendorClValueHexData
         OCTET STRING
      }

er1645v2PbbBGriMVIpV6DhcpClientVendorClActions OBJECT-TYPE
   SYNTAX      VariableLengthTableActions
   MAX-ACCESS  read-write
   STATUS      current
   DESCRIPTION
      "By way of this field, some manipulations
       on this table may be performed."
   ::= {er1645v2PbbBGriMVIpV6DhcpClientVendorClEntry 2}

er1645v2PbbBGriMVIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2PbbBGriMVIpV6DhcpClientVendorClEntry 10}

er1645v2PbbBGriMVIpV6DhcpClientVendorClTableIx OBJECT-TYPE
   SYNTAX      TableIndex
   MAX-ACCESS  not-accessible
   STATUS      current
   DESCRIPTION
      ""
   ::= {er1645v2PbbBGriMVIpV6DhcpClientVendorClEntry 11}

er1645v2PbbBGriMVIpV6DhcpClientVendorClValueAscii OBJECT-TYPE
   SYNTAX      DisplayString
   MAX-ACCESS  read-write
   STATUS      current
   DESCRIPTION
      "Path: pbbBridgeGroup.editConf.ipV6.dhcp.client.vendorClassOpt.value.ascii"
   ::= {er1645v2PbbBGriMVIpV6DhcpClientVendorClEntry 16842752}

er1645v2PbbBGriMVIpV6DhcpClientVendorClValueDecimal OBJECT-TYPE
   SYNTAX      Integer32
   MAX-ACCESS  read-write
   STATUS      current
   DESCRIPTION
      "Path: pbbBridgeGroup.editConf.ipV6.dhcp.client.vendorClassOpt.value.decimal"
   ::= {er1645v2PbbBGriMVIpV6DhcpClientVendorClEntry 16908288}

er1645v2PbbBGriMVIpV6DhcpClientVendorClValueHexData OBJECT-TYPE
   SYNTAX      OCTET STRING
   MAX-ACCESS  read-write
   STATUS      current
   DESCRIPTION
      "Path: pbbBridgeGroup.editConf.ipV6.dhcp.client.vendorClassOpt.value.hexData"
   ::= {er1645v2PbbBGriMVIpV6DhcpClientVendorClEntry 16973824}

er1645v2PbbBGriMVIpV6DhcpRelayDestinations OBJECT-TYPE
   SYNTAX      SEQUENCE OF Er1645v2PbbBGriMVIpV6DhcpRelayDestinationsEntry
   MAX-ACCESS  not-accessible
   STATUS      current
   DESCRIPTION
      ""
   ::= {er1645v2PbbBGriMVIpV6 174080000}

er1645v2PbbBGriMVIpV6DhcpRelayDestinationsEntry OBJECT-TYPE
   SYNTAX      Er1645v2PbbBGriMVIpV6DhcpRelayDestinationsEntry
   MAX-ACCESS  not-accessible
   STATUS      current
   DESCRIPTION
      ""
   INDEX      { er1645v2PbbBGriMVIpV6DhcpRelayDestinationsGlobalIx,
                er1645v2PbbBGriMVIpV6DhcpRelayDestinationsTableIx }
   ::= {er1645v2PbbBGriMVIpV6DhcpRelayDestinations 1}

Er1645v2PbbBGriMVIpV6DhcpRelayDestinationsEntry ::=
   SEQUENCE
      {
      er1645v2PbbBGriMVIpV6DhcpRelayDestinationsActions
         VariableLengthTableActions,
      er1645v2PbbBGriMVIpV6DhcpRelayDestinationsGlobalIx
         GlobalIndex,
      er1645v2PbbBGriMVIpV6DhcpRelayDestinationsTableIx
         TableIndex,
      er1645v2PbbBGriMVIpV6DhcpRelayDestinationsAddress
         Ipv6Address,
      er1645v2PbbBGriMVIpV6DhcpRelayDestinationsInterface
         DisplayString
      }

er1645v2PbbBGriMVIpV6DhcpRelayDestinationsActions OBJECT-TYPE
   SYNTAX      VariableLengthTableActions
   MAX-ACCESS  read-write
   STATUS      current
   DESCRIPTION
      "By way of this field, some manipulations
       on this table may be performed."
   ::= {er1645v2PbbBGriMVIpV6DhcpRelayDestinationsEntry 2}

er1645v2PbbBGriMVIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2PbbBGriMVIpV6DhcpRelayDestinationsEntry 10}

er1645v2PbbBGriMVIpV6DhcpRelayDestinationsTableIx OBJECT-TYPE
   SYNTAX      TableIndex
   MAX-ACCESS  not-accessible
   STATUS      current
   DESCRIPTION
      ""
   ::= {er1645v2PbbBGriMVIpV6DhcpRelayDestinationsEntry 11}

er1645v2PbbBGriMVIpV6DhcpRelayDestinationsAddress OBJECT-TYPE
   SYNTAX      Ipv6Address
   MAX-ACCESS  read-write
   STATUS      current
   DESCRIPTION
      "Path: pbbBridgeGroup.editConf.ipV6.dhcp.relay.destinations.address

       ipv6 address"
   ::= {er1645v2PbbBGriMVIpV6DhcpRelayDestinationsEntry 16777216}

er1645v2PbbBGriMVIpV6DhcpRelayDestinationsInterface OBJECT-TYPE
   SYNTAX      DisplayString
   MAX-ACCESS  read-write
   STATUS      current
   DESCRIPTION
      "Path: pbbBridgeGroup.editConf.ipV6.dhcp.relay.destinations.interface"
   ::= {er1645v2PbbBGriMVIpV6DhcpRelayDestinationsEntry 33554432}


er1645v2PbbBGriMVArp OBJECT IDENTIFIER ::= {er1645v2PbbBGriMV 19}

er1645v2PbbBGriMVArpSSCTable OBJECT-TYPE
   SYNTAX      SEQUENCE OF Er1645v2PbbBGriMVArpEntry
   MAX-ACCESS  not-accessible
   STATUS      current
   DESCRIPTION
      "ethernet related config parameters"
   ::= {er1645v2PbbBGriMVArp 1}

er1645v2PbbBGriMVArpEntry OBJECT-TYPE
   SYNTAX      Er1645v2PbbBGriMVArpEntry
   MAX-ACCESS  not-accessible
   STATUS      current
   DESCRIPTION
      ""
   INDEX      { er1645v2PbbBGriMVArpGlobalIx }
   ::= {er1645v2PbbBGriMVArpSSCTable 1}

Er1645v2PbbBGriMVArpEntry ::=
   SEQUENCE
      {
      er1645v2PbbBGriMVArpGlobalIx
         GlobalIndex,
      er1645v2PbbBGriMVArpTimeOut
         TimeTicks,
      er1645v2PbbBGriMVArpProxyArp
         INTEGER
      }

er1645v2PbbBGriMVArpGlobalIx OBJECT-TYPE
   SYNTAX      GlobalIndex
   MAX-ACCESS  not-accessible
   STATUS      current
   DESCRIPTION
      "The value of the tlsCntTreeGlobalIndex of the MANAGED OBJECT."
   ::= {er1645v2PbbBGriMVArpEntry 10}

er1645v2PbbBGriMVArpTimeOut OBJECT-TYPE
   SYNTAX      TimeTicks
   MAX-ACCESS  read-write
   STATUS      current
   DESCRIPTION
      "Path: pbbBridgeGroup.editConf.arp.timeOut

       Time in centi-second."
   ::= {er1645v2PbbBGriMVArpEntry 201326592}

er1645v2PbbBGriMVArpProxyArp OBJECT-TYPE
   SYNTAX      INTEGER
               {
               disabled (0),
               enabled (1)
               }
   MAX-ACCESS  read-write
   STATUS      current
   DESCRIPTION
      "Path: pbbBridgeGroup.editConf.arp.proxyArp

       Possibilities:
               disabled   (0)
               enabled   (1)"
   ::= {er1645v2PbbBGriMVArpEntry 838860800}

er1645v2PbbBGriMVArpStaticArp OBJECT-TYPE
   SYNTAX      SEQUENCE OF Er1645v2PbbBGriMVArpStaticArpEntry
   MAX-ACCESS  not-accessible
   STATUS      current
   DESCRIPTION
      ""
   ::= {er1645v2PbbBGriMVArp 50331648}

er1645v2PbbBGriMVArpStaticArpEntry OBJECT-TYPE
   SYNTAX      Er1645v2PbbBGriMVArpStaticArpEntry
   MAX-ACCESS  not-accessible
   STATUS      current
   DESCRIPTION
      ""
   INDEX      { er1645v2PbbBGriMVArpStaticArpGlobalIx,
                er1645v2PbbBGriMVArpStaticArpTableIx }
   ::= {er1645v2PbbBGriMVArpStaticArp 1}

Er1645v2PbbBGriMVArpStaticArpEntry ::=
   SEQUENCE
      {
      er1645v2PbbBGriMVArpStaticArpActions
         VariableLengthTableActions,
      er1645v2PbbBGriMVArpStaticArpGlobalIx
         GlobalIndex,
      er1645v2PbbBGriMVArpStaticArpTableIx
         TableIndex,
      er1645v2PbbBGriMVArpStaticArpMacAddress
         OCTET STRING,
      er1645v2PbbBGriMVArpStaticArpIpAddress
         IpAddress
      }

er1645v2PbbBGriMVArpStaticArpActions OBJECT-TYPE
   SYNTAX      VariableLengthTableActions
   MAX-ACCESS  read-write
   STATUS      current
   DESCRIPTION
      "By way of this field, some manipulations
       on this table may be performed."
   ::= {er1645v2PbbBGriMVArpStaticArpEntry 2}

er1645v2PbbBGriMVArpStaticArpGlobalIx OBJECT-TYPE
   SYNTAX      GlobalIndex
   MAX-ACCESS  not-accessible
   STATUS      current
   DESCRIPTION
      "The value of the tlsCntTreeGlobalIndex of the MANAGED OBJECT."
   ::= {er1645v2PbbBGriMVArpStaticArpEntry 10}

er1645v2PbbBGriMVArpStaticArpTableIx OBJECT-TYPE
   SYNTAX      TableIndex
   MAX-ACCESS  not-accessible
   STATUS      current
   DESCRIPTION
      ""
   ::= {er1645v2PbbBGriMVArpStaticArpEntry 11}

er1645v2PbbBGriMVArpStaticArpMacAddress OBJECT-TYPE
   SYNTAX      OCTET STRING
   MAX-ACCESS  read-write
   STATUS      current
   DESCRIPTION
      "Path: pbbBridgeGroup.editConf.arp.staticArp.macAddress

       MAC address."
   ::= {er1645v2PbbBGriMVArpStaticArpEntry 16777216}

er1645v2PbbBGriMVArpStaticArpIpAddress OBJECT-TYPE
   SYNTAX      IpAddress
   MAX-ACCESS  read-write
   STATUS      current
   DESCRIPTION
      "Path: pbbBridgeGroup.editConf.arp.staticArp.ipAddress"
   ::= {er1645v2PbbBGriMVArpStaticArpEntry 33554432}


er1645v2PbbBGriMVSpanningTree OBJECT IDENTIFIER ::= {er1645v2PbbBGriMV 5}

er1645v2PbbBGriMVSpanningTreeSSCTable OBJECT-TYPE
   SYNTAX      SEQUENCE OF Er1645v2PbbBGriMVSpanningTreeEntry
   MAX-ACCESS  not-accessible
   STATUS      current
   DESCRIPTION
      "Enable spanning tree algorithm"
   ::= {er1645v2PbbBGriMVSpanningTree 1}

er1645v2PbbBGriMVSpanningTreeEntry OBJECT-TYPE
   SYNTAX      Er1645v2PbbBGriMVSpanningTreeEntry
   MAX-ACCESS  not-accessible
   STATUS      current
   DESCRIPTION
      ""
   INDEX      { er1645v2PbbBGriMVSpanningTreeGlobalIx }
   ::= {er1645v2PbbBGriMVSpanningTreeSSCTable 1}

Er1645v2PbbBGriMVSpanningTreeEntry ::=
   SEQUENCE
      {
      er1645v2PbbBGriMVSpanningTreeGlobalIx
         GlobalIndex,
      er1645v2PbbBGriMVSpanningTreeSpTProt
         INTEGER,
      er1645v2PbbBGriMVSpanningTreeBrPrio
         Integer32,
      er1645v2PbbBGriMVSpanningTreeBrMAge
         TimeTicks,
      er1645v2PbbBGriMVSpanningTreeBrHTim
         TimeTicks,
      er1645v2PbbBGriMVSpanningTreeBrFDel
         TimeTicks,
      er1645v2PbbBGriMVSpanningTreeTxHoldCnt
         Integer32,
      er1645v2PbbBGriMVSpanningTreeMstConfigIdName
         DisplayString,
      er1645v2PbbBGriMVSpanningTreeMstConfigIdRevisionLevel
         Integer32,
      er1645v2PbbBGriMVSpanningTreeMaxHops
         Integer32
      }

er1645v2PbbBGriMVSpanningTreeGlobalIx OBJECT-TYPE
   SYNTAX      GlobalIndex
   MAX-ACCESS  not-accessible
   STATUS      current
   DESCRIPTION
      "The value of the tlsCntTreeGlobalIndex of the MANAGED OBJECT."
   ::= {er1645v2PbbBGriMVSpanningTreeEntry 10}

er1645v2PbbBGriMVSpanningTreeSpTProt OBJECT-TYPE
   SYNTAX      INTEGER
               {
               none (0),
               p802d1DsmsSTPsCompatibility (2),
               p802d1D (1),
               p802d1Q (3)
               }
   MAX-ACCESS  read-write
   STATUS      current
   DESCRIPTION
      "Path: pbbBridgeGroup.editConf.spanningTree.protocol

       Possibilities:
               none   (0)
               p802.1D - STP Compatibility   (2)
               p802.1D   (1)
               p802.1Q   (3)"
   ::= {er1645v2PbbBGriMVSpanningTreeEntry 16777216}

er1645v2PbbBGriMVSpanningTreeBrPrio OBJECT-TYPE
   SYNTAX      Integer32
   MAX-ACCESS  read-write
   STATUS      current
   DESCRIPTION
      "Path: pbbBridgeGroup.editConf.spanningTree.bridgePriority"
   ::= {er1645v2PbbBGriMVSpanningTreeEntry 33554432}

er1645v2PbbBGriMVSpanningTreeBrMAge OBJECT-TYPE
   SYNTAX      TimeTicks
   MAX-ACCESS  read-write
   STATUS      current
   DESCRIPTION
      "Path: pbbBridgeGroup.editConf.spanningTree.bridgeMaxAge

       Time in centi-second."
   ::= {er1645v2PbbBGriMVSpanningTreeEntry 50331648}

er1645v2PbbBGriMVSpanningTreeBrHTim OBJECT-TYPE
   SYNTAX      TimeTicks
   MAX-ACCESS  read-write
   STATUS      current
   DESCRIPTION
      "Path: pbbBridgeGroup.editConf.spanningTree.bridgeHelloTime

       Time in centi-second."
   ::= {er1645v2PbbBGriMVSpanningTreeEntry 67108864}

er1645v2PbbBGriMVSpanningTreeBrFDel OBJECT-TYPE
   SYNTAX      TimeTicks
   MAX-ACCESS  read-write
   STATUS      current
   DESCRIPTION
      "Path: pbbBridgeGroup.editConf.spanningTree.bridgeForwardDelay

       Time in centi-second."
   ::= {er1645v2PbbBGriMVSpanningTreeEntry 83886080}

er1645v2PbbBGriMVSpanningTreeTxHoldCnt OBJECT-TYPE
   SYNTAX      Integer32
   MAX-ACCESS  read-write
   STATUS      current
   DESCRIPTION
      "Path: pbbBridgeGroup.editConf.spanningTree.transmitHoldCount"
   ::= {er1645v2PbbBGriMVSpanningTreeEntry 100663296}

er1645v2PbbBGriMVSpanningTreeMstConfigIdName OBJECT-TYPE
   SYNTAX      DisplayString
   MAX-ACCESS  read-write
   STATUS      current
   DESCRIPTION
      "Path: pbbBridgeGroup.editConf.spanningTree.mstConfigId.name"
   ::= {er1645v2PbbBGriMVSpanningTreeEntry 117506048}

er1645v2PbbBGriMVSpanningTreeMstConfigIdRevisionLevel OBJECT-TYPE
   SYNTAX      Integer32
   MAX-ACCESS  read-write
   STATUS      current
   DESCRIPTION
      "Path: pbbBridgeGroup.editConf.spanningTree.mstConfigId.revisionLevel"
   ::= {er1645v2PbbBGriMVSpanningTreeEntry 117571584}

er1645v2PbbBGriMVSpanningTreeMaxHops OBJECT-TYPE
   SYNTAX      Integer32
   MAX-ACCESS  read-write
   STATUS      current
   DESCRIPTION
      "Path: pbbBridgeGroup.editConf.spanningTree.maxHops"
   ::= {er1645v2PbbBGriMVSpanningTreeEntry 134217728}


er1645v2PbbBGriMVLocalAccess OBJECT IDENTIFIER ::= {er1645v2PbbBGriMV 28}

er1645v2PbbBGriMVLocalAccessTable OBJECT-TYPE
   SYNTAX      SEQUENCE OF Er1645v2PbbBGriMVLocalAccessEntry
   MAX-ACCESS  not-accessible
   STATUS      current
   DESCRIPTION
      "restricts access to protocolstack via bridgegroup"
   ::= {er1645v2PbbBGriMVLocalAccess 1}

er1645v2PbbBGriMVLocalAccessEntry OBJECT-TYPE
   SYNTAX      Er1645v2PbbBGriMVLocalAccessEntry
   MAX-ACCESS  not-accessible
   STATUS      current
   DESCRIPTION
      ""
   INDEX      { er1645v2PbbBGriMVLocalAccessGlobalIx }
   ::= {er1645v2PbbBGriMVLocalAccessTable 1}

Er1645v2PbbBGriMVLocalAccessEntry ::=
   SEQUENCE
      {
      er1645v2PbbBGriMVLocalAccessGlobalIx
         GlobalIndex,
      er1645v2PbbBGriMVLocalAccessValue
         INTEGER
      }

er1645v2PbbBGriMVLocalAccessGlobalIx OBJECT-TYPE
   SYNTAX      GlobalIndex
   MAX-ACCESS  not-accessible
   STATUS      current
   DESCRIPTION
      "The value of the tlsCntTreeGlobalIndex of the MANAGED OBJECT."
   ::= {er1645v2PbbBGriMVLocalAccessEntry 10}

er1645v2PbbBGriMVLocalAccessValue OBJECT-TYPE
   SYNTAX      INTEGER
               {
               permitted (0),
               restricted (1)
               }
   MAX-ACCESS  read-write
   STATUS      current
   DESCRIPTION
      "Path: pbbBridgeGroup.editConf.localAccess

       Possibilities:
               permitted   (0)
               restricted   (1)"
   ::= {er1645v2PbbBGriMVLocalAccessEntry 2147483648}


er1645v2PbbBGriMVAccessControl OBJECT IDENTIFIER ::= {er1645v2PbbBGriMV 29}

er1645v2PbbBGriMVAccessControlSSCTable OBJECT-TYPE
   SYNTAX      SEQUENCE OF Er1645v2PbbBGriMVAccessControlEntry
   MAX-ACCESS  not-accessible
   STATUS      current
   DESCRIPTION
      "access control on bridgegroups"
   ::= {er1645v2PbbBGriMVAccessControl 1}

er1645v2PbbBGriMVAccessControlEntry OBJECT-TYPE
   SYNTAX      Er1645v2PbbBGriMVAccessControlEntry
   MAX-ACCESS  not-accessible
   STATUS      current
   DESCRIPTION
      ""
   INDEX      { er1645v2PbbBGriMVAccessControlGlobalIx }
   ::= {er1645v2PbbBGriMVAccessControlSSCTable 1}

Er1645v2PbbBGriMVAccessControlEntry ::=
   SEQUENCE
      {
      er1645v2PbbBGriMVAccessControlGlobalIx
         GlobalIndex,
      er1645v2PbbBGriMVAccessControlInAccessList
         DisplayString,
      er1645v2PbbBGriMVAccessControlLimBC
         INTEGER
      }

er1645v2PbbBGriMVAccessControlGlobalIx OBJECT-TYPE
   SYNTAX      GlobalIndex
   MAX-ACCESS  not-accessible
   STATUS      current
   DESCRIPTION
      "The value of the tlsCntTreeGlobalIndex of the MANAGED OBJECT."
   ::= {er1645v2PbbBGriMVAccessControlEntry 10}

er1645v2PbbBGriMVAccessControlInAccessList OBJECT-TYPE
   SYNTAX      DisplayString
   MAX-ACCESS  read-write
   STATUS      current
   DESCRIPTION
      "Path: pbbBridgeGroup.editConf.accessControl.inAccessList"
   ::= {er1645v2PbbBGriMVAccessControlEntry 83886080}

er1645v2PbbBGriMVAccessControlLimBC OBJECT-TYPE
   SYNTAX      INTEGER
               {
               disabled (0),
               enabled (1)
               }
   MAX-ACCESS  read-write
   STATUS      current
   DESCRIPTION
      "Path: pbbBridgeGroup.editConf.accessControl.limitBroadcasts

       Possibilities:
               disabled   (0)
               enabled   (1)"
   ::= {er1645v2PbbBGriMVAccessControlEntry 134217728}


er1645v2PbbBGriMVIp OBJECT IDENTIFIER ::= {er1645v2PbbBGriMV 18}

er1645v2PbbBGriMVIpSSCTable OBJECT-TYPE
   SYNTAX      SEQUENCE OF Er1645v2PbbBGriMVIpEntry
   MAX-ACCESS  not-accessible
   STATUS      current
   DESCRIPTION
      "ip interface config parameters"
   ::= {er1645v2PbbBGriMVIp 1}

er1645v2PbbBGriMVIpEntry OBJECT-TYPE
   SYNTAX      Er1645v2PbbBGriMVIpEntry
   MAX-ACCESS  not-accessible
   STATUS      current
   DESCRIPTION
      ""
   INDEX      { er1645v2PbbBGriMVIpGlobalIx }
   ::= {er1645v2PbbBGriMVIpSSCTable 1}

Er1645v2PbbBGriMVIpEntry ::=
   SEQUENCE
      {
      er1645v2PbbBGriMVIpGlobalIx
         GlobalIndex,
      er1645v2PbbBGriMVIpVrfRouter
         DisplayString,
      er1645v2PbbBGriMVIpAdr
         IpAddress,
      er1645v2PbbBGriMVIpNetm
         IpAddress,
      er1645v2PbbBGriMVIpSNetName
         INTEGER,
      er1645v2PbbBGriMVIpSNetCust
         DisplayString,
      er1645v2PbbBGriMVIpDhcpC
         INTEGER,
      er1645v2PbbBGriMVIpDhcpGatewayPreference
         Integer32,
      er1645v2PbbBGriMVIpDhcpRoutePreference
         Integer32,
      er1645v2PbbBGriMVIpDhcpDnsPreference
         Integer32,
      er1645v2PbbBGriMVIpMtu
         Integer32,
      er1645v2PbbBGriMVIpMssAdjust
         INTEGER,
      er1645v2PbbBGriMVIpRipMetric
         Integer32,
      er1645v2PbbBGriMVIpRipMetricOut
         Integer32,
      er1645v2PbbBGriMVIpRipMode
         INTEGER,
      er1645v2PbbBGriMVIpRipTxVer
         INTEGER,
      er1645v2PbbBGriMVIpRipRxVer
         INTEGER,
      er1645v2PbbBGriMVIpRipSplitH
         INTEGER,
      er1645v2PbbBGriMVIpRipAuth
         INTEGER,
      er1645v2PbbBGriMVIpRipFilter
         DisplayString,
      er1645v2PbbBGriMVIpRipFilterIn
         DisplayString,
      er1645v2PbbBGriMVIpRipClearNextHop
         INTEGER,
      er1645v2PbbBGriMVIpAccPol
         DisplayString,
      er1645v2PbbBGriMVIpAB
         DisplayString,
      er1645v2PbbBGriMVIpMA
         INTEGER,
      er1645v2PbbBGriMVIpMF
         Integer32,
      er1645v2PbbBGriMVIpDB
         INTEGER,
      er1645v2PbbBGriMVIpIR
         INTEGER,
      er1645v2PbbBGriMVIpIgmp
         INTEGER,
      er1645v2PbbBGriMVIpNN
         DisplayString,
      er1645v2PbbBGriMVIpVrrp
         INTEGER,
      er1645v2PbbBGriMVIpPimMode
         INTEGER,
      er1645v2PbbBGriMVIpPimDrPriority
         Counter32,
      er1645v2PbbBGriMVIpPimHelloTime
         TimeTicks,
      er1645v2PbbBGriMVIpPimPropagationDelay
         TimeTicks,
      er1645v2PbbBGriMVIpPimOverrideInterval
         TimeTicks,
      er1645v2PbbBGriMVIpPimBsrBorder
         INTEGER,
      er1645v2PbbBGriMVIpPimTtlThreshold
         Integer32,
      er1645v2PbbBGriMVIpIMNetworkUnreachable
         INTEGER,
      er1645v2PbbBGriMVIpIMHostUnreachable
         INTEGER,
      er1645v2PbbBGriMVIpIMProtocolUnreachable
         INTEGER,
      er1645v2PbbBGriMVIpIMPortUnreachable
         INTEGER,
      er1645v2PbbBGriMVIpIMMtuExceeded
         INTEGER,
      er1645v2PbbBGriMVIpIMAdminProhibited
         INTEGER,
      er1645v2PbbBGriMVIpIMTtlExceeded
         INTEGER,
      er1645v2PbbBGriMVIpIMRedirect
         INTEGER
      }

er1645v2PbbBGriMVIpGlobalIx OBJECT-TYPE
   SYNTAX      GlobalIndex
   MAX-ACCESS  not-accessible
   STATUS      current
   DESCRIPTION
      "The value of the tlsCntTreeGlobalIndex of the MANAGED OBJECT."
   ::= {er1645v2PbbBGriMVIpEntry 10}

er1645v2PbbBGriMVIpVrfRouter OBJECT-TYPE
   SYNTAX      DisplayString
   MAX-ACCESS  read-write
   STATUS      current
   DESCRIPTION
      "Path: pbbBridgeGroup.editConf.ip.vrfRouter"
   ::= {er1645v2PbbBGriMVIpEntry 738197504}

er1645v2PbbBGriMVIpAdr OBJECT-TYPE
   SYNTAX      IpAddress
   MAX-ACCESS  read-write
   STATUS      current
   DESCRIPTION
      "Path: pbbBridgeGroup.editConf.ip.address"
   ::= {er1645v2PbbBGriMVIpEntry 2030043136}

er1645v2PbbBGriMVIpNetm OBJECT-TYPE
   SYNTAX      IpAddress
   MAX-ACCESS  read-write
   STATUS      current
   DESCRIPTION
      "Path: pbbBridgeGroup.editConf.ip.netMask"
   ::= {er1645v2PbbBGriMVIpEntry 2063597568}

er1645v2PbbBGriMVIpSNetName OBJECT-TYPE
   SYNTAX      INTEGER
               {
               slOPTg (0),
               corp (2),
               dmz (3),
               internet (1)
               }
   MAX-ACCESS  read-write
   STATUS      current
   DESCRIPTION
      "Path: pbbBridgeGroup.editConf.ip.sNet.name

       Possibilities:
               <OPT>   (0)
               corp   (2)
               dmz   (3)
               internet   (1)"
   ::= {er1645v2PbbBGriMVIpEntry 855703552}

er1645v2PbbBGriMVIpSNetCust OBJECT-TYPE
   SYNTAX      DisplayString
   MAX-ACCESS  read-write
   STATUS      current
   DESCRIPTION
      "Path: pbbBridgeGroup.editConf.ip.sNet.custom"
   ::= {er1645v2PbbBGriMVIpEntry 855769088}

er1645v2PbbBGriMVIpDhcpC OBJECT-TYPE
   SYNTAX      INTEGER
               {
               disabled (0),
               enabled (1)
               }
   MAX-ACCESS  read-write
   STATUS      current
   DESCRIPTION
      "Path: pbbBridgeGroup.editConf.ip.dhcpClient

       Possibilities:
               disabled   (0)
               enabled   (1)"
   ::= {er1645v2PbbBGriMVIpEntry 838860800}

er1645v2PbbBGriMVIpDhcpGatewayPreference OBJECT-TYPE
   SYNTAX      Integer32
   MAX-ACCESS  read-write
   STATUS      current
   DESCRIPTION
      "Path: pbbBridgeGroup.editConf.ip.dhcp.gatewayPreference"
   ::= {er1645v2PbbBGriMVIpEntry 872480768}

er1645v2PbbBGriMVIpDhcpRoutePreference OBJECT-TYPE
   SYNTAX      Integer32
   MAX-ACCESS  read-write
   STATUS      current
   DESCRIPTION
      "Path: pbbBridgeGroup.editConf.ip.dhcp.routePreference"
   ::= {er1645v2PbbBGriMVIpEntry 872546304}

er1645v2PbbBGriMVIpDhcpDnsPreference OBJECT-TYPE
   SYNTAX      Integer32
   MAX-ACCESS  read-write
   STATUS      current
   DESCRIPTION
      "Path: pbbBridgeGroup.editConf.ip.dhcp.dnsPreference"
   ::= {er1645v2PbbBGriMVIpEntry 872611840}

er1645v2PbbBGriMVIpMtu OBJECT-TYPE
   SYNTAX      Integer32
   MAX-ACCESS  read-write
   STATUS      current
   DESCRIPTION
      "Path: pbbBridgeGroup.editConf.ip.mtu"
   ::= {er1645v2PbbBGriMVIpEntry 671088640}

er1645v2PbbBGriMVIpMssAdjust OBJECT-TYPE
   SYNTAX      INTEGER
               {
               disabled (0),
               auto (65536)
               }
   MAX-ACCESS  read-write
   STATUS      current
   DESCRIPTION
      "Path: pbbBridgeGroup.editConf.ip.mssAdjust

       Possibilities:
               disabled   (0)
               auto   (65536)"
   ::= {er1645v2PbbBGriMVIpEntry 754974720}

er1645v2PbbBGriMVIpRipMetric OBJECT-TYPE
   SYNTAX      Integer32
   MAX-ACCESS  read-write
   STATUS      current
   DESCRIPTION
      "Path: pbbBridgeGroup.editConf.ip.rip.metric"
   ::= {er1645v2PbbBGriMVIpEntry 353566720}

er1645v2PbbBGriMVIpRipMetricOut OBJECT-TYPE
   SYNTAX      Integer32
   MAX-ACCESS  read-write
   STATUS      current
   DESCRIPTION
      "Path: pbbBridgeGroup.editConf.ip.rip.metricOut"
   ::= {er1645v2PbbBGriMVIpEntry 353632256}

er1645v2PbbBGriMVIpRipMode OBJECT-TYPE
   SYNTAX      INTEGER
               {
               disabled (0),
               passive (1),
               active (2)
               }
   MAX-ACCESS  read-write
   STATUS      current
   DESCRIPTION
      "Path: pbbBridgeGroup.editConf.ip.rip.mode

       Possibilities:
               disabled   (0)
               passive   (1)
               active   (2)"
   ::= {er1645v2PbbBGriMVIpEntry 353697792}

er1645v2PbbBGriMVIpRipTxVer OBJECT-TYPE
   SYNTAX      INTEGER
               {
               rip1 (0),
               rip2 (1),
               rip1mcompatible (2)
               }
   MAX-ACCESS  read-write
   STATUS      current
   DESCRIPTION
      "Path: pbbBridgeGroup.editConf.ip.rip.txVersion

       Possibilities:
               rip1   (0)
               rip2   (1)
               rip1-compatible   (2)"
   ::= {er1645v2PbbBGriMVIpEntry 354615296}

er1645v2PbbBGriMVIpRipRxVer OBJECT-TYPE
   SYNTAX      INTEGER
               {
               rip1only (0),
               rip2only (1),
               rip12 (2)
               }
   MAX-ACCESS  read-write
   STATUS      current
   DESCRIPTION
      "Path: pbbBridgeGroup.editConf.ip.rip.rxVersion

       Possibilities:
               rip1only   (0)
               rip2only   (1)
               rip1&2   (2)"
   ::= {er1645v2PbbBGriMVIpEntry 354680832}

er1645v2PbbBGriMVIpRipSplitH OBJECT-TYPE
   SYNTAX      INTEGER
               {
               disabled (0),
               enabled (1),
               poisonedReverse (2)
               }
   MAX-ACCESS  read-write
   STATUS      current
   DESCRIPTION
      "Path: pbbBridgeGroup.editConf.ip.rip.splitHorizon

       Possibilities:
               disabled   (0)
               enabled   (1)
               poisonedReverse   (2)"
   ::= {er1645v2PbbBGriMVIpEntry 353828864}

er1645v2PbbBGriMVIpRipAuth OBJECT-TYPE
   SYNTAX      INTEGER
               {
               disabled (0),
               texts (1),
               md5 (2)
               }
   MAX-ACCESS  read-write
   STATUS      current
   DESCRIPTION
      "Path: pbbBridgeGroup.editConf.ip.rip.authentication

       Possibilities:
               disabled   (0)
               text    (1)
               md5   (2)"
   ::= {er1645v2PbbBGriMVIpEntry 353501184}

er1645v2PbbBGriMVIpRipFilter OBJECT-TYPE
   SYNTAX      DisplayString
   MAX-ACCESS  read-write
   STATUS      current
   DESCRIPTION
      "Path: pbbBridgeGroup.editConf.ip.rip.filter"
   ::= {er1645v2PbbBGriMVIpEntry 354418688}

er1645v2PbbBGriMVIpRipFilterIn OBJECT-TYPE
   SYNTAX      DisplayString
   MAX-ACCESS  read-write
   STATUS      current
   DESCRIPTION
      "Path: pbbBridgeGroup.editConf.ip.rip.filterIn"
   ::= {er1645v2PbbBGriMVIpEntry 354484224}

er1645v2PbbBGriMVIpRipClearNextHop OBJECT-TYPE
   SYNTAX      INTEGER
               {
               disabled (0),
               enabled (1)
               }
   MAX-ACCESS  read-write
   STATUS      current
   DESCRIPTION
      "Path: pbbBridgeGroup.editConf.ip.rip.clearNextHop

       Possibilities:
               disabled   (0)
               enabled   (1)"
   ::= {er1645v2PbbBGriMVIpEntry 352452608}

er1645v2PbbBGriMVIpAccPol OBJECT-TYPE
   SYNTAX      DisplayString
   MAX-ACCESS  read-write
   STATUS      current
   DESCRIPTION
      "Path: pbbBridgeGroup.editConf.ip.accessPolicy"
   ::= {er1645v2PbbBGriMVIpEntry 704643072}

er1645v2PbbBGriMVIpAB OBJECT-TYPE
   SYNTAX      DisplayString
   MAX-ACCESS  read-write
   STATUS      current
   DESCRIPTION
      "Path: pbbBridgeGroup.editConf.ip.trafficPolicy"
   ::= {er1645v2PbbBGriMVIpEntry 234881024}

er1645v2PbbBGriMVIpMA OBJECT-TYPE
   SYNTAX      INTEGER
               {
               disabled (0),
               enabled (1)
               }
   MAX-ACCESS  read-write
   STATUS      current
   DESCRIPTION
      "Path: pbbBridgeGroup.editConf.ip.mgmtAccess

       Possibilities:
               disabled   (0)
               enabled   (1)"
   ::= {er1645v2PbbBGriMVIpEntry 268435456}

er1645v2PbbBGriMVIpMF OBJECT-TYPE
   SYNTAX      Integer32
   MAX-ACCESS  read-write
   STATUS      current
   DESCRIPTION
      "Path: pbbBridgeGroup.editConf.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2PbbBGriMVIpEntry 285212672}

er1645v2PbbBGriMVIpDB OBJECT-TYPE
   SYNTAX      INTEGER
               {
               disabled (0),
               enabled (1)
               }
   MAX-ACCESS  read-write
   STATUS      current
   DESCRIPTION
      "Path: pbbBridgeGroup.editConf.ip.directedBroadcasts

       Possibilities:
               disabled   (0)
               enabled   (1)"
   ::= {er1645v2PbbBGriMVIpEntry 369098752}

er1645v2PbbBGriMVIpIR OBJECT-TYPE
   SYNTAX      INTEGER
               {
               disabled (0),
               enabled (1)
               }
   MAX-ACCESS  read-write
   STATUS      current
   DESCRIPTION
      "Path: pbbBridgeGroup.editConf.ip.icmpRedirects

       Possibilities:
               disabled   (0)
               enabled   (1)"
   ::= {er1645v2PbbBGriMVIpEntry 436207616}

er1645v2PbbBGriMVIpIgmp OBJECT-TYPE
   SYNTAX      INTEGER
               {
               disabled (0),
               proxy (1),
               router (2),
               v3Router (5)
               }
   MAX-ACCESS  read-write
   STATUS      current
   DESCRIPTION
      "Path: pbbBridgeGroup.editConf.ip.igmp

       Possibilities:
               disabled   (0)
               proxy   (1)
               router   (2)
               v3Router   (5)"
   ::= {er1645v2PbbBGriMVIpEntry 536870912}

er1645v2PbbBGriMVIpNN OBJECT-TYPE
   SYNTAX      DisplayString
   MAX-ACCESS  read-write
   STATUS      current
   DESCRIPTION
      "Path: pbbBridgeGroup.editConf.ip.nat"
   ::= {er1645v2PbbBGriMVIpEntry 452984832}

er1645v2PbbBGriMVIpVrrp OBJECT-TYPE
   SYNTAX      INTEGER
               {
               disabled (0),
               enabled (1)
               }
   MAX-ACCESS  read-write
   STATUS      current
   DESCRIPTION
      "Path: pbbBridgeGroup.editConf.ip.vrrp

       Possibilities:
               disabled   (0)
               enabled   (1)"
   ::= {er1645v2PbbBGriMVIpEntry 721420288}

er1645v2PbbBGriMVIpPimMode OBJECT-TYPE
   SYNTAX      INTEGER
               {
               disabled (0),
               sparse (1),
               passive (2)
               }
   MAX-ACCESS  read-write
   STATUS      current
   DESCRIPTION
      "Path: pbbBridgeGroup.editConf.ip.pim.mode

       Possibilities:
               disabled   (0)
               sparse   (1)
               passive   (2)"
   ::= {er1645v2PbbBGriMVIpEntry 771817472}

er1645v2PbbBGriMVIpPimDrPriority OBJECT-TYPE
   SYNTAX      Counter32
   MAX-ACCESS  read-write
   STATUS      current
   DESCRIPTION
      "Path: pbbBridgeGroup.editConf.ip.pim.drPriority

       32 bit unsigned wrappable counter."
   ::= {er1645v2PbbBGriMVIpEntry 771883008}

er1645v2PbbBGriMVIpPimHelloTime OBJECT-TYPE
   SYNTAX      TimeTicks
   MAX-ACCESS  read-write
   STATUS      current
   DESCRIPTION
      "Path: pbbBridgeGroup.editConf.ip.pim.helloTime

       Time in centi-second."
   ::= {er1645v2PbbBGriMVIpEntry 771948544}

er1645v2PbbBGriMVIpPimPropagationDelay OBJECT-TYPE
   SYNTAX      TimeTicks
   MAX-ACCESS  read-write
   STATUS      current
   DESCRIPTION
      "Path: pbbBridgeGroup.editConf.ip.pim.propagationDelay

       Time in centi-second."
   ::= {er1645v2PbbBGriMVIpEntry 772014080}

er1645v2PbbBGriMVIpPimOverrideInterval OBJECT-TYPE
   SYNTAX      TimeTicks
   MAX-ACCESS  read-write
   STATUS      current
   DESCRIPTION
      "Path: pbbBridgeGroup.editConf.ip.pim.overrideInterval

       Time in centi-second."
   ::= {er1645v2PbbBGriMVIpEntry 772079616}

er1645v2PbbBGriMVIpPimBsrBorder OBJECT-TYPE
   SYNTAX      INTEGER
               {
               disabled (0),
               enabled (1)
               }
   MAX-ACCESS  read-write
   STATUS      current
   DESCRIPTION
      "Path: pbbBridgeGroup.editConf.ip.pim.bsrBorder

       Possibilities:
               disabled   (0)
               enabled   (1)"
   ::= {er1645v2PbbBGriMVIpEntry 772145152}

er1645v2PbbBGriMVIpPimTtlThreshold OBJECT-TYPE
   SYNTAX      Integer32
   MAX-ACCESS  read-write
   STATUS      current
   DESCRIPTION
      "Path: pbbBridgeGroup.editConf.ip.pim.ttlThreshold"
   ::= {er1645v2PbbBGriMVIpEntry 772210688}

er1645v2PbbBGriMVIpIMNetworkUnreachable OBJECT-TYPE
   SYNTAX      INTEGER
               {
               disabled (0),
               enabled (1)
               }
   MAX-ACCESS  read-write
   STATUS      current
   DESCRIPTION
      "Path: pbbBridgeGroup.editConf.ip.icmpMessages.networkUnreachable

       Possibilities:
               disabled   (0)
               enabled   (1)"
   ::= {er1645v2PbbBGriMVIpEntry 788594688}

er1645v2PbbBGriMVIpIMHostUnreachable OBJECT-TYPE
   SYNTAX      INTEGER
               {
               disabled (0),
               enabled (1)
               }
   MAX-ACCESS  read-write
   STATUS      current
   DESCRIPTION
      "Path: pbbBridgeGroup.editConf.ip.icmpMessages.hostUnreachable

       Possibilities:
               disabled   (0)
               enabled   (1)"
   ::= {er1645v2PbbBGriMVIpEntry 788660224}

er1645v2PbbBGriMVIpIMProtocolUnreachable OBJECT-TYPE
   SYNTAX      INTEGER
               {
               disabled (0),
               enabled (1)
               }
   MAX-ACCESS  read-write
   STATUS      current
   DESCRIPTION
      "Path: pbbBridgeGroup.editConf.ip.icmpMessages.protocolUnreachable

       Possibilities:
               disabled   (0)
               enabled   (1)"
   ::= {er1645v2PbbBGriMVIpEntry 788725760}

er1645v2PbbBGriMVIpIMPortUnreachable OBJECT-TYPE
   SYNTAX      INTEGER
               {
               disabled (0),
               enabled (1)
               }
   MAX-ACCESS  read-write
   STATUS      current
   DESCRIPTION
      "Path: pbbBridgeGroup.editConf.ip.icmpMessages.portUnreachable

       Possibilities:
               disabled   (0)
               enabled   (1)"
   ::= {er1645v2PbbBGriMVIpEntry 788791296}

er1645v2PbbBGriMVIpIMMtuExceeded OBJECT-TYPE
   SYNTAX      INTEGER
               {
               disabled (0),
               enabled (1)
               }
   MAX-ACCESS  read-write
   STATUS      current
   DESCRIPTION
      "Path: pbbBridgeGroup.editConf.ip.icmpMessages.mtuExceeded

       Possibilities:
               disabled   (0)
               enabled   (1)"
   ::= {er1645v2PbbBGriMVIpEntry 788856832}

er1645v2PbbBGriMVIpIMAdminProhibited OBJECT-TYPE
   SYNTAX      INTEGER
               {
               disabled (0),
               enabled (1)
               }
   MAX-ACCESS  read-write
   STATUS      current
   DESCRIPTION
      "Path: pbbBridgeGroup.editConf.ip.icmpMessages.adminProhibited

       Possibilities:
               disabled   (0)
               enabled   (1)"
   ::= {er1645v2PbbBGriMVIpEntry 788922368}

er1645v2PbbBGriMVIpIMTtlExceeded OBJECT-TYPE
   SYNTAX      INTEGER
               {
               disabled (0),
               enabled (1)
               }
   MAX-ACCESS  read-write
   STATUS      current
   DESCRIPTION
      "Path: pbbBridgeGroup.editConf.ip.icmpMessages.ttlExceeded

       Possibilities:
               disabled   (0)
               enabled   (1)"
   ::= {er1645v2PbbBGriMVIpEntry 788987904}

er1645v2PbbBGriMVIpIMRedirect OBJECT-TYPE
   SYNTAX      INTEGER
               {
               disabled (0),
               enabled (1)
               }
   MAX-ACCESS  read-write
   STATUS      current
   DESCRIPTION
      "Path: pbbBridgeGroup.editConf.ip.icmpMessages.redirect

       Possibilities:
               disabled   (0)
               enabled   (1)"
   ::= {er1645v2PbbBGriMVIpEntry 789053440}

er1645v2PbbBGriMVIpSaddr OBJECT-TYPE
   SYNTAX      SEQUENCE OF Er1645v2PbbBGriMVIpSaddrEntry
   MAX-ACCESS  not-accessible
   STATUS      current
   DESCRIPTION
      ""
   ::= {er1645v2PbbBGriMVIp 385875968}

er1645v2PbbBGriMVIpSaddrEntry OBJECT-TYPE
   SYNTAX      Er1645v2PbbBGriMVIpSaddrEntry
   MAX-ACCESS  not-accessible
   STATUS      current
   DESCRIPTION
      ""
   INDEX      { er1645v2PbbBGriMVIpSaddrGlobalIx,
                er1645v2PbbBGriMVIpSaddrTableIx }
   ::= {er1645v2PbbBGriMVIpSaddr 1}

Er1645v2PbbBGriMVIpSaddrEntry ::=
   SEQUENCE
      {
      er1645v2PbbBGriMVIpSaddrActions
         VariableLengthTableActions,
      er1645v2PbbBGriMVIpSaddrGlobalIx
         GlobalIndex,
      er1645v2PbbBGriMVIpSaddrTableIx
         TableIndex,
      er1645v2PbbBGriMVIpSaddrAddress
         IpAddress,
      er1645v2PbbBGriMVIpSaddrNetMask
         IpAddress
      }

er1645v2PbbBGriMVIpSaddrActions OBJECT-TYPE
   SYNTAX      VariableLengthTableActions
   MAX-ACCESS  read-write
   STATUS      current
   DESCRIPTION
      "By way of this field, some manipulations
       on this table may be performed."
   ::= {er1645v2PbbBGriMVIpSaddrEntry 2}

er1645v2PbbBGriMVIpSaddrGlobalIx OBJECT-TYPE
   SYNTAX      GlobalIndex
   MAX-ACCESS  not-accessible
   STATUS      current
   DESCRIPTION
      "The value of the tlsCntTreeGlobalIndex of the MANAGED OBJECT."
   ::= {er1645v2PbbBGriMVIpSaddrEntry 10}

er1645v2PbbBGriMVIpSaddrTableIx OBJECT-TYPE
   SYNTAX      TableIndex
   MAX-ACCESS  not-accessible
   STATUS      current
   DESCRIPTION
      ""
   ::= {er1645v2PbbBGriMVIpSaddrEntry 11}

er1645v2PbbBGriMVIpSaddrAddress OBJECT-TYPE
   SYNTAX      IpAddress
   MAX-ACCESS  read-write
   STATUS      current
   DESCRIPTION
      "Path: pbbBridgeGroup.editConf.ip.secondaryIp.address"
   ::= {er1645v2PbbBGriMVIpSaddrEntry 2030043136}

er1645v2PbbBGriMVIpSaddrNetMask OBJECT-TYPE
   SYNTAX      IpAddress
   MAX-ACCESS  read-write
   STATUS      current
   DESCRIPTION
      "Path: pbbBridgeGroup.editConf.ip.secondaryIp.netMask"
   ::= {er1645v2PbbBGriMVIpSaddrEntry 2063597568}

er1645v2PbbBGriMVIpH OBJECT-TYPE
   SYNTAX      SEQUENCE OF Er1645v2PbbBGriMVIpHEntry
   MAX-ACCESS  not-accessible
   STATUS      current
   DESCRIPTION
      ""
   ::= {er1645v2PbbBGriMVIp 251658240}

er1645v2PbbBGriMVIpHEntry OBJECT-TYPE
   SYNTAX      Er1645v2PbbBGriMVIpHEntry
   MAX-ACCESS  not-accessible
   STATUS      current
   DESCRIPTION
      ""
   INDEX      { er1645v2PbbBGriMVIpHGlobalIx,
                er1645v2PbbBGriMVIpHTableIx }
   ::= {er1645v2PbbBGriMVIpH 1}

Er1645v2PbbBGriMVIpHEntry ::=
   SEQUENCE
      {
      er1645v2PbbBGriMVIpHActions
         VariableLengthTableActions,
      er1645v2PbbBGriMVIpHGlobalIx
         GlobalIndex,
      er1645v2PbbBGriMVIpHTableIx
         TableIndex,
      er1645v2PbbBGriMVIpHAddress
         IpAddress,
      er1645v2PbbBGriMVIpHDhcpRelayOptionSubscriberId
         DisplayString
      }

er1645v2PbbBGriMVIpHActions OBJECT-TYPE
   SYNTAX      VariableLengthTableActions
   MAX-ACCESS  read-write
   STATUS      current
   DESCRIPTION
      "By way of this field, some manipulations
       on this table may be performed."
   ::= {er1645v2PbbBGriMVIpHEntry 2}

er1645v2PbbBGriMVIpHGlobalIx OBJECT-TYPE
   SYNTAX      GlobalIndex
   MAX-ACCESS  not-accessible
   STATUS      current
   DESCRIPTION
      "The value of the tlsCntTreeGlobalIndex of the MANAGED OBJECT."
   ::= {er1645v2PbbBGriMVIpHEntry 10}

er1645v2PbbBGriMVIpHTableIx OBJECT-TYPE
   SYNTAX      TableIndex
   MAX-ACCESS  not-accessible
   STATUS      current
   DESCRIPTION
      ""
   ::= {er1645v2PbbBGriMVIpHEntry 11}

er1645v2PbbBGriMVIpHAddress OBJECT-TYPE
   SYNTAX      IpAddress
   MAX-ACCESS  read-write
   STATUS      current
   DESCRIPTION
      "Path: pbbBridgeGroup.editConf.ip.helpers.address"
   ::= {er1645v2PbbBGriMVIpHEntry 16777216}

er1645v2PbbBGriMVIpHDhcpRelayOptionSubscriberId OBJECT-TYPE
   SYNTAX      DisplayString
   MAX-ACCESS  read-write
   STATUS      current
   DESCRIPTION
      "Path: pbbBridgeGroup.editConf.ip.helpers.dhcpRelayOption.subscriberId"
   ::= {er1645v2PbbBGriMVIpHEntry 33947648}


er1645v2PbbBGriMVVlan OBJECT IDENTIFIER ::= {er1645v2PbbBGriMV 33}

er1645v2PbbBGriMVVlanSSCTable OBJECT-TYPE
   SYNTAX      SEQUENCE OF Er1645v2PbbBGriMVVlanEntry
   MAX-ACCESS  not-accessible
   STATUS      current
   DESCRIPTION
      ""
   ::= {er1645v2PbbBGriMVVlan 1}

er1645v2PbbBGriMVVlanEntry OBJECT-TYPE
   SYNTAX      Er1645v2PbbBGriMVVlanEntry
   MAX-ACCESS  not-accessible
   STATUS      current
   DESCRIPTION
      ""
   INDEX      { er1645v2PbbBGriMVVlanGlobalIx,
                er1645v2PbbBGriMVVlanTableIx }
   ::= {er1645v2PbbBGriMVVlanSSCTable 1}

Er1645v2PbbBGriMVVlanEntry ::=
   SEQUENCE
      {
      er1645v2PbbBGriMVVlanActions
         VariableLengthTableActions,
      er1645v2PbbBGriMVVlanGlobalIx
         GlobalIndex,
      er1645v2PbbBGriMVVlanTableIx
         TableIndex,
      er1645v2PbbBGriMVVlanName
         DisplayString,
      er1645v2PbbBGriMVVlanRemark
         DisplayString,
      er1645v2PbbBGriMVVlanAdminStatus
         INTEGER,
      er1645v2PbbBGriMVVlanMode
         INTEGER,
      er1645v2PbbBGriMVVlanIpVrfRouter
         DisplayString,
      er1645v2PbbBGriMVVlanIpAdr
         IpAddress,
      er1645v2PbbBGriMVVlanIpNetm
         IpAddress,
      er1645v2PbbBGriMVVlanIpSNetName
         INTEGER,
      er1645v2PbbBGriMVVlanIpSNetCust
         DisplayString,
      er1645v2PbbBGriMVVlanIpDhcpC
         INTEGER,
      er1645v2PbbBGriMVVlanIpDhcpGatewayPreference
         Integer32,
      er1645v2PbbBGriMVVlanIpDhcpRoutePreference
         Integer32,
      er1645v2PbbBGriMVVlanIpDhcpDnsPreference
         Integer32,
      er1645v2PbbBGriMVVlanIpMtu
         Integer32,
      er1645v2PbbBGriMVVlanIpMssAdjust
         INTEGER,
      er1645v2PbbBGriMVVlanIpRipMetric
         Integer32,
      er1645v2PbbBGriMVVlanIpRipMetricOut
         Integer32,
      er1645v2PbbBGriMVVlanIpRipMode
         INTEGER,
      er1645v2PbbBGriMVVlanIpRipTxVer
         INTEGER,
      er1645v2PbbBGriMVVlanIpRipRxVer
         INTEGER,
      er1645v2PbbBGriMVVlanIpRipSplitH
         INTEGER,
      er1645v2PbbBGriMVVlanIpRipAuth
         INTEGER,
      er1645v2PbbBGriMVVlanIpRipFilter
         DisplayString,
      er1645v2PbbBGriMVVlanIpRipFilterIn
         DisplayString,
      er1645v2PbbBGriMVVlanIpRipClearNextHop
         INTEGER,
      er1645v2PbbBGriMVVlanIpAccPol
         DisplayString,
      er1645v2PbbBGriMVVlanIpAB
         DisplayString,
      er1645v2PbbBGriMVVlanIpMA
         INTEGER,
      er1645v2PbbBGriMVVlanIpMF
         Integer32,
      er1645v2PbbBGriMVVlanIpDB
         INTEGER,
      er1645v2PbbBGriMVVlanIpIR
         INTEGER,
      er1645v2PbbBGriMVVlanIpIgmp
         INTEGER,
      er1645v2PbbBGriMVVlanIpNN
         DisplayString,
      er1645v2PbbBGriMVVlanIpVrrp
         INTEGER,
      er1645v2PbbBGriMVVlanIpPimMode
         INTEGER,
      er1645v2PbbBGriMVVlanIpPimDrPriority
         Counter32,
      er1645v2PbbBGriMVVlanIpPimHelloTime
         TimeTicks,
      er1645v2PbbBGriMVVlanIpPimPropagationDelay
         TimeTicks,
      er1645v2PbbBGriMVVlanIpPimOverrideInterval
         TimeTicks,
      er1645v2PbbBGriMVVlanIpPimBsrBorder
         INTEGER,
      er1645v2PbbBGriMVVlanIpPimTtlThreshold
         Integer32,
      er1645v2PbbBGriMVVlanIpIMNetworkUnreachable
         INTEGER,
      er1645v2PbbBGriMVVlanIpIMHostUnreachable
         INTEGER,
      er1645v2PbbBGriMVVlanIpIMProtocolUnreachable
         INTEGER,
      er1645v2PbbBGriMVVlanIpIMPortUnreachable
         INTEGER,
      er1645v2PbbBGriMVVlanIpIMMtuExceeded
         INTEGER,
      er1645v2PbbBGriMVVlanIpIMAdminProhibited
         INTEGER,
      er1645v2PbbBGriMVVlanIpIMTtlExceeded
         INTEGER,
      er1645v2PbbBGriMVVlanIpIMRedirect
         INTEGER,
      er1645v2PbbBGriMVVlanIpV6VrfRouter
         DisplayString,
      er1645v2PbbBGriMVVlanIpV6AddrAutoConfigNrDupAddrDetects
         Integer32,
      er1645v2PbbBGriMVVlanIpV6AddrAutoConfigAcceptRa
         INTEGER,
      er1645v2PbbBGriMVVlanIpV6AddrAutoConfigAcceptRaRdnss
         INTEGER,
      er1645v2PbbBGriMVVlanIpV6AddrAutoConfigAcceptRaDnssl
         INTEGER,
      er1645v2PbbBGriMVVlanIpV6DefaultRoute
         INTEGER,
      er1645v2PbbBGriMVVlanIpV6RaSend
         INTEGER,
      er1645v2PbbBGriMVVlanIpV6RaMinInterval
         TimeTicks,
      er1645v2PbbBGriMVVlanIpV6RaMaxInterval
         TimeTicks,
      er1645v2PbbBGriMVVlanIpV6RaManagedFlag
         INTEGER,
      er1645v2PbbBGriMVVlanIpV6RaOtherConfFlag
         INTEGER,
      er1645v2PbbBGriMVVlanIpV6RaLinkMtu
         Integer32,
      er1645v2PbbBGriMVVlanIpV6RaReachableTime
         TimeTicks,
      er1645v2PbbBGriMVVlanIpV6RaRetransmitTime
         TimeTicks,
      er1645v2PbbBGriMVVlanIpV6RaHopLimit
         Integer32,
      er1645v2PbbBGriMVVlanIpV6RaDefaultLifeTime
         TimeTicks,
      er1645v2PbbBGriMVVlanIpV6RaDnsOptionsRdnssLifeTime
         TimeTicks,
      er1645v2PbbBGriMVVlanIpV6RaDnsOptionsRdnssImportServers
         INTEGER,
      er1645v2PbbBGriMVVlanIpV6RaDnsOptionsDnsslLifeTime
         TimeTicks,
      er1645v2PbbBGriMVVlanIpV6RaDnsOptionsDnsslImportDomains
         INTEGER,
      er1645v2PbbBGriMVVlanIpV6RsSend
         INTEGER,
      er1645v2PbbBGriMVVlanIpV6RsMaxRandomDelay
         TimeTicks,
      er1645v2PbbBGriMVVlanIpV6RsInterval
         TimeTicks,
      er1645v2PbbBGriMVVlanIpV6RsMaxSolicitations
         Integer32,
      er1645v2PbbBGriMVVlanIpV6TrafficPolicyInbound
         DisplayString,
      er1645v2PbbBGriMVVlanIpV6TrafficPolicyOutbound
         DisplayString,
      er1645v2PbbBGriMVVlanIpV6FirewallZone
         DisplayString,
      er1645v2PbbBGriMVVlanIpV6DhcpClientAddrAC
         INTEGER,
      er1645v2PbbBGriMVVlanIpV6DhcpClientPrDelMode
         INTEGER,
      er1645v2PbbBGriMVVlanIpV6DhcpClientPrDelPool
         DisplayString,
      er1645v2PbbBGriMVVlanIpV6DhcpClientPrDelPdExclOpt
         INTEGER,
      er1645v2PbbBGriMVVlanIpV6DhcpClientDnsServerPref
         Integer32,
      er1645v2PbbBGriMVVlanIpV6DhcpClientRapidCommit
         INTEGER,
      er1645v2PbbBGriMVVlanIpV6DhcpClientTimersSolTimeOut
         TimeTicks,
      er1645v2PbbBGriMVVlanIpV6DhcpClientTimersSolMaxRt
         TimeTicks,
      er1645v2PbbBGriMVVlanIpV6DhcpClientTimersInfoRefresh
         TimeTicks,
      er1645v2PbbBGriMVVlanIpV6DhcpServerMode
         INTEGER,
      er1645v2PbbBGriMVVlanIpV6DhcpServerPreference
         Integer32,
      er1645v2PbbBGriMVVlanIpV6DhcpServerPool
         DisplayString,
      er1645v2PbbBGriMVVlanIpV6DhcpServerRapidCommit
         INTEGER,
      er1645v2PbbBGriMVVlanIpV6DhcpServerTimersInfoRefresh
         TimeTicks,
      er1645v2PbbBGriMVVlanIpV6DhcpRelayMode
         INTEGER,
      er1645v2PbbBGriMVVlanIpV6SendRedirect
         INTEGER,
      er1645v2PbbBGriMVVlanIpV6LinkMtu
         Integer32,
      er1645v2PbbBGriMVVlanIpV6InterfaceId
         OCTET STRING,
      er1645v2PbbBGriMVVlanIpV6MF
         Integer32,
      er1645v2PbbBGriMVVlanIpV6IcmpMessagesNoRoute
         INTEGER,
      er1645v2PbbBGriMVVlanIpV6IcmpMessagesBeyondScope
         INTEGER,
      er1645v2PbbBGriMVVlanIpV6IcmpMessagesAddressUnreachable
         INTEGER,
      er1645v2PbbBGriMVVlanIpV6IcmpMessagesPortUnreachable
         INTEGER,
      er1645v2PbbBGriMVVlanIpV6IcmpMessagesPacketTooBig
         INTEGER,
      er1645v2PbbBGriMVVlanIpV6IcmpMessagesHopLimitExceeded
         INTEGER,
      er1645v2PbbBGriMVVlanIpV6IcmpMessagesFragTimeExceeded
         INTEGER,
      er1645v2PbbBGriMVVlanIpV6IcmpMessagesHeaderFieldErr
         INTEGER,
      er1645v2PbbBGriMVVlanIpV6IcmpMessagesOptionUnrecognized
         INTEGER,
      er1645v2PbbBGriMVVlanIpV6IcmpMessagesRedirect
         INTEGER,
      er1645v2PbbBGriMVVlanVlanVid
         INTEGER,
      er1645v2PbbBGriMVVlanVlanTpid
         INTEGER,
      er1645v2PbbBGriMVVlanVlanTxCos
         INTEGER,
      er1645v2PbbBGriMVVlanVlanChTos
         INTEGER,
      er1645v2PbbBGriMVVlanVlanCTMapP0
         INTEGER,
      er1645v2PbbBGriMVVlanVlanCTMapP1
         INTEGER,
      er1645v2PbbBGriMVVlanVlanCTMapP2
         INTEGER,
      er1645v2PbbBGriMVVlanVlanCTMapP3
         INTEGER,
      er1645v2PbbBGriMVVlanVlanCTMapP4
         INTEGER,
      er1645v2PbbBGriMVVlanVlanCTMapP5
         INTEGER,
      er1645v2PbbBGriMVVlanVlanCTMapP6
         INTEGER,
      er1645v2PbbBGriMVVlanVlanCTMapP7
         INTEGER,
      er1645v2PbbBGriMVVlanVlanQCMapQueue1
         Integer32,
      er1645v2PbbBGriMVVlanVlanQCMapQueue2
         Integer32,
      er1645v2PbbBGriMVVlanVlanQCMapQueue3
         Integer32,
      er1645v2PbbBGriMVVlanVlanQCMapQueue4
         Integer32,
      er1645v2PbbBGriMVVlanVlanQCMapQueue5
         Integer32,
      er1645v2PbbBGriMVVlanVlanQCMapLowDelayQueue
         Integer32,
      er1645v2PbbBGriMVVlanVlanQCMapLowDelay2Queue
         Integer32,
      er1645v2PbbBGriMVVlanVlanQCMapSystemQueue
         Integer32,
      er1645v2PbbBGriMVVlanVlanArpTimeOut
         TimeTicks,
      er1645v2PbbBGriMVVlanVlanArpProxyArp
         INTEGER
      }

er1645v2PbbBGriMVVlanActions OBJECT-TYPE
   SYNTAX      VariableLengthTableActions
   MAX-ACCESS  read-write
   STATUS      current
   DESCRIPTION
      "By way of this field, some manipulations
       on this table may be performed."
   ::= {er1645v2PbbBGriMVVlanEntry 2}

er1645v2PbbBGriMVVlanGlobalIx OBJECT-TYPE
   SYNTAX      GlobalIndex
   MAX-ACCESS  not-accessible
   STATUS      current
   DESCRIPTION
      "The value of the tlsCntTreeGlobalIndex of the MANAGED OBJECT."
   ::= {er1645v2PbbBGriMVVlanEntry 10}

er1645v2PbbBGriMVVlanTableIx OBJECT-TYPE
   SYNTAX      TableIndex
   MAX-ACCESS  not-accessible
   STATUS      current
   DESCRIPTION
      ""
   ::= {er1645v2PbbBGriMVVlanEntry 11}

er1645v2PbbBGriMVVlanName OBJECT-TYPE
   SYNTAX      DisplayString
   MAX-ACCESS  read-write
   STATUS      current
   DESCRIPTION
      "Path: pbbBridgeGroup.editConf.vlan.name"
   ::= {er1645v2PbbBGriMVVlanEntry 16777216}

er1645v2PbbBGriMVVlanRemark OBJECT-TYPE
   SYNTAX      DisplayString
   MAX-ACCESS  read-write
   STATUS      current
   DESCRIPTION
      "Path: pbbBridgeGroup.editConf.vlan.remark"
   ::= {er1645v2PbbBGriMVVlanEntry 1157627904}

er1645v2PbbBGriMVVlanAdminStatus OBJECT-TYPE
   SYNTAX      INTEGER
               {
               up (1),
               down (2)
               }
   MAX-ACCESS  read-write
   STATUS      current
   DESCRIPTION
      "Path: pbbBridgeGroup.editConf.vlan.adminStatus

       Possibilities:
               up   (1)
               down   (2)"
   ::= {er1645v2PbbBGriMVVlanEntry 33554432}

er1645v2PbbBGriMVVlanMode OBJECT-TYPE
   SYNTAX      INTEGER
               {
               routing (1),
               ipV6 (16),
               ipV6ipV4 (17)
               }
   MAX-ACCESS  read-write
   STATUS      current
   DESCRIPTION
      "Path: pbbBridgeGroup.editConf.vlan.mode

       Possibilities:
               routing   (1)
               ipV6   (16)
               ipV6/ipV4   (17)"
   ::= {er1645v2PbbBGriMVVlanEntry 67108864}

er1645v2PbbBGriMVVlanIpVrfRouter OBJECT-TYPE
   SYNTAX      DisplayString
   MAX-ACCESS  read-write
   STATUS      current
   DESCRIPTION
      "Path: pbbBridgeGroup.editConf.vlan.ip.vrfRouter"
   ::= {er1645v2PbbBGriMVVlanEntry 53215232}

er1645v2PbbBGriMVVlanIpAdr OBJECT-TYPE
   SYNTAX      IpAddress
   MAX-ACCESS  read-write
   STATUS      current
   DESCRIPTION
      "Path: pbbBridgeGroup.editConf.vlan.ip.address"
   ::= {er1645v2PbbBGriMVVlanEntry 58261504}

er1645v2PbbBGriMVVlanIpNetm OBJECT-TYPE
   SYNTAX      IpAddress
   MAX-ACCESS  read-write
   STATUS      current
   DESCRIPTION
      "Path: pbbBridgeGroup.editConf.vlan.ip.netMask"
   ::= {er1645v2PbbBGriMVVlanEntry 58392576}

er1645v2PbbBGriMVVlanIpSNetName OBJECT-TYPE
   SYNTAX      INTEGER
               {
               slOPTg (0),
               corp (2),
               dmz (3),
               internet (1)
               }
   MAX-ACCESS  read-write
   STATUS      current
   DESCRIPTION
      "Path: pbbBridgeGroup.editConf.vlan.ip.sNet.name

       Possibilities:
               <OPT>   (0)
               corp   (2)
               dmz   (3)
               internet   (1)"
   ::= {er1645v2PbbBGriMVVlanEntry 53674240}

er1645v2PbbBGriMVVlanIpSNetCust OBJECT-TYPE
   SYNTAX      DisplayString
   MAX-ACCESS  read-write
   STATUS      current
   DESCRIPTION
      "Path: pbbBridgeGroup.editConf.vlan.ip.sNet.custom"
   ::= {er1645v2PbbBGriMVVlanEntry 53674496}

er1645v2PbbBGriMVVlanIpDhcpC OBJECT-TYPE
   SYNTAX      INTEGER
               {
               disabled (0),
               enabled (1)
               }
   MAX-ACCESS  read-write
   STATUS      current
   DESCRIPTION
      "Path: pbbBridgeGroup.editConf.vlan.ip.dhcpClient

       Possibilities:
               disabled   (0)
               enabled   (1)"
   ::= {er1645v2PbbBGriMVVlanEntry 53608448}

er1645v2PbbBGriMVVlanIpDhcpGatewayPreference OBJECT-TYPE
   SYNTAX      Integer32
   MAX-ACCESS  read-write
   STATUS      current
   DESCRIPTION
      "Path: pbbBridgeGroup.editConf.vlan.ip.dhcp.gatewayPreference"
   ::= {er1645v2PbbBGriMVVlanEntry 53739776}

er1645v2PbbBGriMVVlanIpDhcpRoutePreference OBJECT-TYPE
   SYNTAX      Integer32
   MAX-ACCESS  read-write
   STATUS      current
   DESCRIPTION
      "Path: pbbBridgeGroup.editConf.vlan.ip.dhcp.routePreference"
   ::= {er1645v2PbbBGriMVVlanEntry 53740032}

er1645v2PbbBGriMVVlanIpDhcpDnsPreference OBJECT-TYPE
   SYNTAX      Integer32
   MAX-ACCESS  read-write
   STATUS      current
   DESCRIPTION
      "Path: pbbBridgeGroup.editConf.vlan.ip.dhcp.dnsPreference"
   ::= {er1645v2PbbBGriMVVlanEntry 53740288}

er1645v2PbbBGriMVVlanIpMtu OBJECT-TYPE
   SYNTAX      Integer32
   MAX-ACCESS  read-write
   STATUS      current
   DESCRIPTION
      "Path: pbbBridgeGroup.editConf.vlan.ip.mtu"
   ::= {er1645v2PbbBGriMVVlanEntry 52953088}

er1645v2PbbBGriMVVlanIpMssAdjust OBJECT-TYPE
   SYNTAX      INTEGER
               {
               disabled (0),
               auto (65536)
               }
   MAX-ACCESS  read-write
   STATUS      current
   DESCRIPTION
      "Path: pbbBridgeGroup.editConf.vlan.ip.mssAdjust

       Possibilities:
               disabled   (0)
               auto   (65536)"
   ::= {er1645v2PbbBGriMVVlanEntry 53280768}

er1645v2PbbBGriMVVlanIpRipMetric OBJECT-TYPE
   SYNTAX      Integer32
   MAX-ACCESS  read-write
   STATUS      current
   DESCRIPTION
      "Path: pbbBridgeGroup.editConf.vlan.ip.rip.metric"
   ::= {er1645v2PbbBGriMVVlanEntry 51712768}

er1645v2PbbBGriMVVlanIpRipMetricOut OBJECT-TYPE
   SYNTAX      Integer32
   MAX-ACCESS  read-write
   STATUS      current
   DESCRIPTION
      "Path: pbbBridgeGroup.editConf.vlan.ip.rip.metricOut"
   ::= {er1645v2PbbBGriMVVlanEntry 51713024}

er1645v2PbbBGriMVVlanIpRipMode OBJECT-TYPE
   SYNTAX      INTEGER
               {
               disabled (0),
               passive (1),
               active (2)
               }
   MAX-ACCESS  read-write
   STATUS      current
   DESCRIPTION
      "Path: pbbBridgeGroup.editConf.vlan.ip.rip.mode

       Possibilities:
               disabled   (0)
               passive   (1)
               active   (2)"
   ::= {er1645v2PbbBGriMVVlanEntry 51713280}

er1645v2PbbBGriMVVlanIpRipTxVer OBJECT-TYPE
   SYNTAX      INTEGER
               {
               rip1 (0),
               rip2 (1),
               rip1mcompatible (2)
               }
   MAX-ACCESS  read-write
   STATUS      current
   DESCRIPTION
      "Path: pbbBridgeGroup.editConf.vlan.ip.rip.txVersion

       Possibilities:
               rip1   (0)
               rip2   (1)
               rip1-compatible   (2)"
   ::= {er1645v2PbbBGriMVVlanEntry 51716864}

er1645v2PbbBGriMVVlanIpRipRxVer OBJECT-TYPE
   SYNTAX      INTEGER
               {
               rip1only (0),
               rip2only (1),
               rip12 (2)
               }
   MAX-ACCESS  read-write
   STATUS      current
   DESCRIPTION
      "Path: pbbBridgeGroup.editConf.vlan.ip.rip.rxVersion

       Possibilities:
               rip1only   (0)
               rip2only   (1)
               rip1&2   (2)"
   ::= {er1645v2PbbBGriMVVlanEntry 51717120}

er1645v2PbbBGriMVVlanIpRipSplitH OBJECT-TYPE
   SYNTAX      INTEGER
               {
               disabled (0),
               enabled (1),
               poisonedReverse (2)
               }
   MAX-ACCESS  read-write
   STATUS      current
   DESCRIPTION
      "Path: pbbBridgeGroup.editConf.vlan.ip.rip.splitHorizon

       Possibilities:
               disabled   (0)
               enabled   (1)
               poisonedReverse   (2)"
   ::= {er1645v2PbbBGriMVVlanEntry 51713792}

er1645v2PbbBGriMVVlanIpRipAuth OBJECT-TYPE
   SYNTAX      INTEGER
               {
               disabled (0),
               texts (1),
               md5 (2)
               }
   MAX-ACCESS  read-write
   STATUS      current
   DESCRIPTION
      "Path: pbbBridgeGroup.editConf.vlan.ip.rip.authentication

       Possibilities:
               disabled   (0)
               text    (1)
               md5   (2)"
   ::= {er1645v2PbbBGriMVVlanEntry 51712512}

er1645v2PbbBGriMVVlanIpRipFilter OBJECT-TYPE
   SYNTAX      DisplayString
   MAX-ACCESS  read-write
   STATUS      current
   DESCRIPTION
      "Path: pbbBridgeGroup.editConf.vlan.ip.rip.filter"
   ::= {er1645v2PbbBGriMVVlanEntry 51716096}

er1645v2PbbBGriMVVlanIpRipFilterIn OBJECT-TYPE
   SYNTAX      DisplayString
   MAX-ACCESS  read-write
   STATUS      current
   DESCRIPTION
      "Path: pbbBridgeGroup.editConf.vlan.ip.rip.filterIn"
   ::= {er1645v2PbbBGriMVVlanEntry 51716352}

er1645v2PbbBGriMVVlanIpRipClearNextHop OBJECT-TYPE
   SYNTAX      INTEGER
               {
               disabled (0),
               enabled (1)
               }
   MAX-ACCESS  read-write
   STATUS      current
   DESCRIPTION
      "Path: pbbBridgeGroup.editConf.vlan.ip.rip.clearNextHop

       Possibilities:
               disabled   (0)
               enabled   (1)"
   ::= {er1645v2PbbBGriMVVlanEntry 51708416}

er1645v2PbbBGriMVVlanIpAccPol OBJECT-TYPE
   SYNTAX      DisplayString
   MAX-ACCESS  read-write
   STATUS      current
   DESCRIPTION
      "Path: pbbBridgeGroup.editConf.vlan.ip.accessPolicy"
   ::= {er1645v2PbbBGriMVVlanEntry 53084160}

er1645v2PbbBGriMVVlanIpAB OBJECT-TYPE
   SYNTAX      DisplayString
   MAX-ACCESS  read-write
   STATUS      current
   DESCRIPTION
      "Path: pbbBridgeGroup.editConf.vlan.ip.trafficPolicy"
   ::= {er1645v2PbbBGriMVVlanEntry 51249152}

er1645v2PbbBGriMVVlanIpMA OBJECT-TYPE
   SYNTAX      INTEGER
               {
               disabled (0),
               enabled (1)
               }
   MAX-ACCESS  read-write
   STATUS      current
   DESCRIPTION
      "Path: pbbBridgeGroup.editConf.vlan.ip.mgmtAccess

       Possibilities:
               disabled   (0)
               enabled   (1)"
   ::= {er1645v2PbbBGriMVVlanEntry 51380224}

er1645v2PbbBGriMVVlanIpMF OBJECT-TYPE
   SYNTAX      Integer32
   MAX-ACCESS  read-write
   STATUS      current
   DESCRIPTION
      "Path: pbbBridgeGroup.editConf.vlan.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2PbbBGriMVVlanEntry 51445760}

er1645v2PbbBGriMVVlanIpDB OBJECT-TYPE
   SYNTAX      INTEGER
               {
               disabled (0),
               enabled (1)
               }
   MAX-ACCESS  read-write
   STATUS      current
   DESCRIPTION
      "Path: pbbBridgeGroup.editConf.vlan.ip.directedBroadcasts

       Possibilities:
               disabled   (0)
               enabled   (1)"
   ::= {er1645v2PbbBGriMVVlanEntry 51773440}

er1645v2PbbBGriMVVlanIpIR OBJECT-TYPE
   SYNTAX      INTEGER
               {
               disabled (0),
               enabled (1)
               }
   MAX-ACCESS  read-write
   STATUS      current
   DESCRIPTION
      "Path: pbbBridgeGroup.editConf.vlan.ip.icmpRedirects

       Possibilities:
               disabled   (0)
               enabled   (1)"
   ::= {er1645v2PbbBGriMVVlanEntry 52035584}

er1645v2PbbBGriMVVlanIpIgmp OBJECT-TYPE
   SYNTAX      INTEGER
               {
               disabled (0),
               proxy (1),
               router (2),
               v3Router (5)
               }
   MAX-ACCESS  read-write
   STATUS      current
   DESCRIPTION
      "Path: pbbBridgeGroup.editConf.vlan.ip.igmp

       Possibilities:
               disabled   (0)
               proxy   (1)
               router   (2)
               v3Router   (5)"
   ::= {er1645v2PbbBGriMVVlanEntry 52428800}

er1645v2PbbBGriMVVlanIpNN OBJECT-TYPE
   SYNTAX      DisplayString
   MAX-ACCESS  read-write
   STATUS      current
   DESCRIPTION
      "Path: pbbBridgeGroup.editConf.vlan.ip.nat"
   ::= {er1645v2PbbBGriMVVlanEntry 52101120}

er1645v2PbbBGriMVVlanIpVrrp OBJECT-TYPE
   SYNTAX      INTEGER
               {
               disabled (0),
               enabled (1)
               }
   MAX-ACCESS  read-write
   STATUS      current
   DESCRIPTION
      "Path: pbbBridgeGroup.editConf.vlan.ip.vrrp

       Possibilities:
               disabled   (0)
               enabled   (1)"
   ::= {er1645v2PbbBGriMVVlanEntry 53149696}

er1645v2PbbBGriMVVlanIpPimMode OBJECT-TYPE
   SYNTAX      INTEGER
               {
               disabled (0),
               sparse (1),
               passive (2)
               }
   MAX-ACCESS  read-write
   STATUS      current
   DESCRIPTION
      "Path: pbbBridgeGroup.editConf.vlan.ip.pim.mode

       Possibilities:
               disabled   (0)
               sparse   (1)
               passive   (2)"
   ::= {er1645v2PbbBGriMVVlanEntry 53346560}

er1645v2PbbBGriMVVlanIpPimDrPriority OBJECT-TYPE
   SYNTAX      Counter32
   MAX-ACCESS  read-write
   STATUS      current
   DESCRIPTION
      "Path: pbbBridgeGroup.editConf.vlan.ip.pim.drPriority

       32 bit unsigned wrappable counter."
   ::= {er1645v2PbbBGriMVVlanEntry 53346816}

er1645v2PbbBGriMVVlanIpPimHelloTime OBJECT-TYPE
   SYNTAX      TimeTicks
   MAX-ACCESS  read-write
   STATUS      current
   DESCRIPTION
      "Path: pbbBridgeGroup.editConf.vlan.ip.pim.helloTime

       Time in centi-second."
   ::= {er1645v2PbbBGriMVVlanEntry 53347072}

er1645v2PbbBGriMVVlanIpPimPropagationDelay OBJECT-TYPE
   SYNTAX      TimeTicks
   MAX-ACCESS  read-write
   STATUS      current
   DESCRIPTION
      "Path: pbbBridgeGroup.editConf.vlan.ip.pim.propagationDelay

       Time in centi-second."
   ::= {er1645v2PbbBGriMVVlanEntry 53347328}

er1645v2PbbBGriMVVlanIpPimOverrideInterval OBJECT-TYPE
   SYNTAX      TimeTicks
   MAX-ACCESS  read-write
   STATUS      current
   DESCRIPTION
      "Path: pbbBridgeGroup.editConf.vlan.ip.pim.overrideInterval

       Time in centi-second."
   ::= {er1645v2PbbBGriMVVlanEntry 53347584}

er1645v2PbbBGriMVVlanIpPimBsrBorder OBJECT-TYPE
   SYNTAX      INTEGER
               {
               disabled (0),
               enabled (1)
               }
   MAX-ACCESS  read-write
   STATUS      current
   DESCRIPTION
      "Path: pbbBridgeGroup.editConf.vlan.ip.pim.bsrBorder

       Possibilities:
               disabled   (0)
               enabled   (1)"
   ::= {er1645v2PbbBGriMVVlanEntry 53347840}

er1645v2PbbBGriMVVlanIpPimTtlThreshold OBJECT-TYPE
   SYNTAX      Integer32
   MAX-ACCESS  read-write
   STATUS      current
   DESCRIPTION
      "Path: pbbBridgeGroup.editConf.vlan.ip.pim.ttlThreshold"
   ::= {er1645v2PbbBGriMVVlanEntry 53348096}

er1645v2PbbBGriMVVlanIpIMNetworkUnreachable OBJECT-TYPE
   SYNTAX      INTEGER
               {
               disabled (0),
               enabled (1)
               }
   MAX-ACCESS  read-write
   STATUS      current
   DESCRIPTION
      "Path: pbbBridgeGroup.editConf.vlan.ip.icmpMessages.networkUnreachable

       Possibilities:
               disabled   (0)
               enabled   (1)"
   ::= {er1645v2PbbBGriMVVlanEntry 53412096}

er1645v2PbbBGriMVVlanIpIMHostUnreachable OBJECT-TYPE
   SYNTAX      INTEGER
               {
               disabled (0),
               enabled (1)
               }
   MAX-ACCESS  read-write
   STATUS      current
   DESCRIPTION
      "Path: pbbBridgeGroup.editConf.vlan.ip.icmpMessages.hostUnreachable

       Possibilities:
               disabled   (0)
               enabled   (1)"
   ::= {er1645v2PbbBGriMVVlanEntry 53412352}

er1645v2PbbBGriMVVlanIpIMProtocolUnreachable OBJECT-TYPE
   SYNTAX      INTEGER
               {
               disabled (0),
               enabled (1)
               }
   MAX-ACCESS  read-write
   STATUS      current
   DESCRIPTION
      "Path: pbbBridgeGroup.editConf.vlan.ip.icmpMessages.protocolUnreachable

       Possibilities:
               disabled   (0)
               enabled   (1)"
   ::= {er1645v2PbbBGriMVVlanEntry 53412608}

er1645v2PbbBGriMVVlanIpIMPortUnreachable OBJECT-TYPE
   SYNTAX      INTEGER
               {
               disabled (0),
               enabled (1)
               }
   MAX-ACCESS  read-write
   STATUS      current
   DESCRIPTION
      "Path: pbbBridgeGroup.editConf.vlan.ip.icmpMessages.portUnreachable

       Possibilities:
               disabled   (0)
               enabled   (1)"
   ::= {er1645v2PbbBGriMVVlanEntry 53412864}

er1645v2PbbBGriMVVlanIpIMMtuExceeded OBJECT-TYPE
   SYNTAX      INTEGER
               {
               disabled (0),
               enabled (1)
               }
   MAX-ACCESS  read-write
   STATUS      current
   DESCRIPTION
      "Path: pbbBridgeGroup.editConf.vlan.ip.icmpMessages.mtuExceeded

       Possibilities:
               disabled   (0)
               enabled   (1)"
   ::= {er1645v2PbbBGriMVVlanEntry 53413120}

er1645v2PbbBGriMVVlanIpIMAdminProhibited OBJECT-TYPE
   SYNTAX      INTEGER
               {
               disabled (0),
               enabled (1)
               }
   MAX-ACCESS  read-write
   STATUS      current
   DESCRIPTION
      "Path: pbbBridgeGroup.editConf.vlan.ip.icmpMessages.adminProhibited

       Possibilities:
               disabled   (0)
               enabled   (1)"
   ::= {er1645v2PbbBGriMVVlanEntry 53413376}

er1645v2PbbBGriMVVlanIpIMTtlExceeded OBJECT-TYPE
   SYNTAX      INTEGER
               {
               disabled (0),
               enabled (1)
               }
   MAX-ACCESS  read-write
   STATUS      current
   DESCRIPTION
      "Path: pbbBridgeGroup.editConf.vlan.ip.icmpMessages.ttlExceeded

       Possibilities:
               disabled   (0)
               enabled   (1)"
   ::= {er1645v2PbbBGriMVVlanEntry 53413632}

er1645v2PbbBGriMVVlanIpIMRedirect OBJECT-TYPE
   SYNTAX      INTEGER
               {
               disabled (0),
               enabled (1)
               }
   MAX-ACCESS  read-write
   STATUS      current
   DESCRIPTION
      "Path: pbbBridgeGroup.editConf.vlan.ip.icmpMessages.redirect

       Possibilities:
               disabled   (0)
               enabled   (1)"
   ::= {er1645v2PbbBGriMVVlanEntry 53413888}

er1645v2PbbBGriMVVlanIpV6VrfRouter OBJECT-TYPE
   SYNTAX      DisplayString
   MAX-ACCESS  read-write
   STATUS      current
   DESCRIPTION
      "Path: pbbBridgeGroup.editConf.vlan.ipV6.vrfRouter"
   ::= {er1645v2PbbBGriMVVlanEntry 704708608}

er1645v2PbbBGriMVVlanIpV6AddrAutoConfigNrDupAddrDetects OBJECT-TYPE
   SYNTAX      Integer32
   MAX-ACCESS  read-write
   STATUS      current
   DESCRIPTION
      "Path: pbbBridgeGroup.editConf.vlan.ipV6.addrAutoConfig.nrDupAddrDetects"
   ::= {er1645v2PbbBGriMVVlanEntry 704905472}

er1645v2PbbBGriMVVlanIpV6AddrAutoConfigAcceptRa OBJECT-TYPE
   SYNTAX      INTEGER
               {
               disabled (0),
               enabled (1)
               }
   MAX-ACCESS  read-write
   STATUS      current
   DESCRIPTION
      "Path: pbbBridgeGroup.editConf.vlan.ipV6.addrAutoConfig.acceptRa

       Possibilities:
               disabled   (0)
               enabled   (1)"
   ::= {er1645v2PbbBGriMVVlanEntry 704905728}

er1645v2PbbBGriMVVlanIpV6AddrAutoConfigAcceptRaRdnss OBJECT-TYPE
   SYNTAX      INTEGER
               {
               disabled (0),
               enabled (1)
               }
   MAX-ACCESS  read-write
   STATUS      current
   DESCRIPTION
      "Path: pbbBridgeGroup.editConf.vlan.ipV6.addrAutoConfig.acceptRaRdnss

       Possibilities:
               disabled   (0)
               enabled   (1)"
   ::= {er1645v2PbbBGriMVVlanEntry 704905984}

er1645v2PbbBGriMVVlanIpV6AddrAutoConfigAcceptRaDnssl OBJECT-TYPE
   SYNTAX      INTEGER
               {
               disabled (0),
               enabled (1)
               }
   MAX-ACCESS  read-write
   STATUS      current
   DESCRIPTION
      "Path: pbbBridgeGroup.editConf.vlan.ipV6.addrAutoConfig.acceptRaDnssl

       Possibilities:
               disabled   (0)
               enabled   (1)"
   ::= {er1645v2PbbBGriMVVlanEntry 704906240}

er1645v2PbbBGriMVVlanIpV6DefaultRoute OBJECT-TYPE
   SYNTAX      INTEGER
               {
               disabled (0),
               enabled (1)
               }
   MAX-ACCESS  read-write
   STATUS      current
   DESCRIPTION
      "Path: pbbBridgeGroup.editConf.vlan.ipV6.defaultRoute

       Possibilities:
               disabled   (0)
               enabled   (1)"
   ::= {er1645v2PbbBGriMVVlanEntry 704970752}

er1645v2PbbBGriMVVlanIpV6RaSend OBJECT-TYPE
   SYNTAX      INTEGER
               {
               disabled (0),
               enabled (1)
               }
   MAX-ACCESS  read-write
   STATUS      current
   DESCRIPTION
      "Path: pbbBridgeGroup.editConf.vlan.ipV6.ra.send

       Possibilities:
               disabled   (0)
               enabled   (1)"
   ::= {er1645v2PbbBGriMVVlanEntry 705036544}

er1645v2PbbBGriMVVlanIpV6RaMinInterval OBJECT-TYPE
   SYNTAX      TimeTicks
   MAX-ACCESS  read-write
   STATUS      current
   DESCRIPTION
      "Path: pbbBridgeGroup.editConf.vlan.ipV6.ra.minInterval

       Time in centi-second."
   ::= {er1645v2PbbBGriMVVlanEntry 705036800}

er1645v2PbbBGriMVVlanIpV6RaMaxInterval OBJECT-TYPE
   SYNTAX      TimeTicks
   MAX-ACCESS  read-write
   STATUS      current
   DESCRIPTION
      "Path: pbbBridgeGroup.editConf.vlan.ipV6.ra.maxInterval

       Time in centi-second."
   ::= {er1645v2PbbBGriMVVlanEntry 705037056}

er1645v2PbbBGriMVVlanIpV6RaManagedFlag OBJECT-TYPE
   SYNTAX      INTEGER
               {
               disabled (0),
               enabled (1)
               }
   MAX-ACCESS  read-write
   STATUS      current
   DESCRIPTION
      "Path: pbbBridgeGroup.editConf.vlan.ipV6.ra.managedFlag

       Possibilities:
               disabled   (0)
               enabled   (1)"
   ::= {er1645v2PbbBGriMVVlanEntry 705037312}

er1645v2PbbBGriMVVlanIpV6RaOtherConfFlag OBJECT-TYPE
   SYNTAX      INTEGER
               {
               disabled (0),
               enabled (1)
               }
   MAX-ACCESS  read-write
   STATUS      current
   DESCRIPTION
      "Path: pbbBridgeGroup.editConf.vlan.ipV6.ra.otherConfFlag

       Possibilities:
               disabled   (0)
               enabled   (1)"
   ::= {er1645v2PbbBGriMVVlanEntry 705037568}

er1645v2PbbBGriMVVlanIpV6RaLinkMtu OBJECT-TYPE
   SYNTAX      Integer32
   MAX-ACCESS  read-write
   STATUS      current
   DESCRIPTION
      "Path: pbbBridgeGroup.editConf.vlan.ipV6.ra.linkMtu"
   ::= {er1645v2PbbBGriMVVlanEntry 705037824}

er1645v2PbbBGriMVVlanIpV6RaReachableTime OBJECT-TYPE
   SYNTAX      TimeTicks
   MAX-ACCESS  read-write
   STATUS      current
   DESCRIPTION
      "Path: pbbBridgeGroup.editConf.vlan.ipV6.ra.reachableTime

       Time in centi-second."
   ::= {er1645v2PbbBGriMVVlanEntry 705038080}

er1645v2PbbBGriMVVlanIpV6RaRetransmitTime OBJECT-TYPE
   SYNTAX      TimeTicks
   MAX-ACCESS  read-write
   STATUS      current
   DESCRIPTION
      "Path: pbbBridgeGroup.editConf.vlan.ipV6.ra.retransmitTime

       Time in centi-second."
   ::= {er1645v2PbbBGriMVVlanEntry 705038336}

er1645v2PbbBGriMVVlanIpV6RaHopLimit OBJECT-TYPE
   SYNTAX      Integer32
   MAX-ACCESS  read-write
   STATUS      current
   DESCRIPTION
      "Path: pbbBridgeGroup.editConf.vlan.ipV6.ra.hopLimit"
   ::= {er1645v2PbbBGriMVVlanEntry 705038592}

er1645v2PbbBGriMVVlanIpV6RaDefaultLifeTime OBJECT-TYPE
   SYNTAX      TimeTicks
   MAX-ACCESS  read-write
   STATUS      current
   DESCRIPTION
      "Path: pbbBridgeGroup.editConf.vlan.ipV6.ra.defaultLifeTime

       Time in centi-second."
   ::= {er1645v2PbbBGriMVVlanEntry 705038848}

er1645v2PbbBGriMVVlanIpV6RaDnsOptionsRdnssLifeTime OBJECT-TYPE
   SYNTAX      TimeTicks
   MAX-ACCESS  read-write
   STATUS      current
   DESCRIPTION
      "Path: pbbBridgeGroup.editConf.vlan.ipV6.ra.dnsOptions.rdnss.lifeTime

       Time in centi-second."
   ::= {er1645v2PbbBGriMVVlanEntry 705039140}

er1645v2PbbBGriMVVlanIpV6RaDnsOptionsRdnssImportServers OBJECT-TYPE
   SYNTAX      INTEGER
               {
               disabled (0),
               enabled (1)
               }
   MAX-ACCESS  read-write
   STATUS      current
   DESCRIPTION
      "Path: pbbBridgeGroup.editConf.vlan.ipV6.ra.dnsOptions.rdnss.importServers

       Possibilities:
               disabled   (0)
               enabled   (1)"
   ::= {er1645v2PbbBGriMVVlanEntry 705039148}

er1645v2PbbBGriMVVlanIpV6RaDnsOptionsDnsslLifeTime OBJECT-TYPE
   SYNTAX      TimeTicks
   MAX-ACCESS  read-write
   STATUS      current
   DESCRIPTION
      "Path: pbbBridgeGroup.editConf.vlan.ipV6.ra.dnsOptions.dnssl.lifeTime

       Time in centi-second."
   ::= {er1645v2PbbBGriMVVlanEntry 705039172}

er1645v2PbbBGriMVVlanIpV6RaDnsOptionsDnsslImportDomains OBJECT-TYPE
   SYNTAX      INTEGER
               {
               disabled (0),
               enabled (1)
               }
   MAX-ACCESS  read-write
   STATUS      current
   DESCRIPTION
      "Path: pbbBridgeGroup.editConf.vlan.ipV6.ra.dnsOptions.dnssl.importDomains

       Possibilities:
               disabled   (0)
               enabled   (1)"
   ::= {er1645v2PbbBGriMVVlanEntry 705039180}

er1645v2PbbBGriMVVlanIpV6RsSend OBJECT-TYPE
   SYNTAX      INTEGER
               {
               disabled (0),
               enabled (1)
               }
   MAX-ACCESS  read-write
   STATUS      current
   DESCRIPTION
      "Path: pbbBridgeGroup.editConf.vlan.ipV6.rs.send

       Possibilities:
               disabled   (0)
               enabled   (1)"
   ::= {er1645v2PbbBGriMVVlanEntry 705954048}

er1645v2PbbBGriMVVlanIpV6RsMaxRandomDelay OBJECT-TYPE
   SYNTAX      TimeTicks
   MAX-ACCESS  read-write
   STATUS      current
   DESCRIPTION
      "Path: pbbBridgeGroup.editConf.vlan.ipV6.rs.maxRandomDelay

       Time in centi-second."
   ::= {er1645v2PbbBGriMVVlanEntry 705954304}

er1645v2PbbBGriMVVlanIpV6RsInterval OBJECT-TYPE
   SYNTAX      TimeTicks
   MAX-ACCESS  read-write
   STATUS      current
   DESCRIPTION
      "Path: pbbBridgeGroup.editConf.vlan.ipV6.rs.interval

       Time in centi-second."
   ::= {er1645v2PbbBGriMVVlanEntry 705954560}

er1645v2PbbBGriMVVlanIpV6RsMaxSolicitations OBJECT-TYPE
   SYNTAX      Integer32
   MAX-ACCESS  read-write
   STATUS      current
   DESCRIPTION
      "Path: pbbBridgeGroup.editConf.vlan.ipV6.rs.maxSolicitations"
   ::= {er1645v2PbbBGriMVVlanEntry 705954816}

er1645v2PbbBGriMVVlanIpV6TrafficPolicyInbound OBJECT-TYPE
   SYNTAX      DisplayString
   MAX-ACCESS  read-write
   STATUS      current
   DESCRIPTION
      "Path: pbbBridgeGroup.editConf.vlan.ipV6.trafficPolicy.inbound"
   ::= {er1645v2PbbBGriMVVlanEntry 705364224}

er1645v2PbbBGriMVVlanIpV6TrafficPolicyOutbound OBJECT-TYPE
   SYNTAX      DisplayString
   MAX-ACCESS  read-write
   STATUS      current
   DESCRIPTION
      "Path: pbbBridgeGroup.editConf.vlan.ipV6.trafficPolicy.outbound"
   ::= {er1645v2PbbBGriMVVlanEntry 705364480}

er1645v2PbbBGriMVVlanIpV6FirewallZone OBJECT-TYPE
   SYNTAX      DisplayString
   MAX-ACCESS  read-write
   STATUS      current
   DESCRIPTION
      "Path: pbbBridgeGroup.editConf.vlan.ipV6.firewall.zone"
   ::= {er1645v2PbbBGriMVVlanEntry 705429760}

er1645v2PbbBGriMVVlanIpV6DhcpClientAddrAC OBJECT-TYPE
   SYNTAX      INTEGER
               {
               disabled (0),
               enabled (1)
               }
   MAX-ACCESS  read-write
   STATUS      current
   DESCRIPTION
      "Path: pbbBridgeGroup.editConf.vlan.ipV6.dhcp.client.addrAutoConfig

       Possibilities:
               disabled   (0)
               enabled   (1)"
   ::= {er1645v2PbbBGriMVVlanEntry 705307648}

er1645v2PbbBGriMVVlanIpV6DhcpClientPrDelMode OBJECT-TYPE
   SYNTAX      INTEGER
               {
               disabled (0),
               enabled (1)
               }
   MAX-ACCESS  read-write
   STATUS      current
   DESCRIPTION
      "Path: pbbBridgeGroup.editConf.vlan.ipV6.dhcp.client.pd.mode

       Possibilities:
               disabled   (0)
               enabled   (1)"
   ::= {er1645v2PbbBGriMVVlanEntry 705308676}

er1645v2PbbBGriMVVlanIpV6DhcpClientPrDelPool OBJECT-TYPE
   SYNTAX      DisplayString
   MAX-ACCESS  read-write
   STATUS      current
   DESCRIPTION
      "Path: pbbBridgeGroup.editConf.vlan.ipV6.dhcp.client.pd.pool"
   ::= {er1645v2PbbBGriMVVlanEntry 705308680}

er1645v2PbbBGriMVVlanIpV6DhcpClientPrDelPdExclOpt OBJECT-TYPE
   SYNTAX      INTEGER
               {
               disabled (0),
               enabled (1)
               }
   MAX-ACCESS  read-write
   STATUS      current
   DESCRIPTION
      "Path: pbbBridgeGroup.editConf.vlan.ipV6.dhcp.client.pd.pdExclOpt

       Possibilities:
               disabled   (0)
               enabled   (1)"
   ::= {er1645v2PbbBGriMVVlanEntry 705308684}

er1645v2PbbBGriMVVlanIpV6DhcpClientDnsServerPref OBJECT-TYPE
   SYNTAX      Integer32
   MAX-ACCESS  read-write
   STATUS      current
   DESCRIPTION
      "Path: pbbBridgeGroup.editConf.vlan.ipV6.dhcp.client.dns.serverPref"
   ::= {er1645v2PbbBGriMVVlanEntry 705310724}

er1645v2PbbBGriMVVlanIpV6DhcpClientRapidCommit OBJECT-TYPE
   SYNTAX      INTEGER
               {
               disabled (0),
               enabled (1)
               }
   MAX-ACCESS  read-write
   STATUS      current
   DESCRIPTION
      "Path: pbbBridgeGroup.editConf.vlan.ipV6.dhcp.client.rapidCommit

       Possibilities:
               disabled   (0)
               enabled   (1)"
   ::= {er1645v2PbbBGriMVVlanEntry 705309696}

er1645v2PbbBGriMVVlanIpV6DhcpClientTimersSolTimeOut OBJECT-TYPE
   SYNTAX      TimeTicks
   MAX-ACCESS  read-write
   STATUS      current
   DESCRIPTION
      "Path: pbbBridgeGroup.editConf.vlan.ipV6.dhcp.client.timers.solTimeOut

       Time in centi-second."
   ::= {er1645v2PbbBGriMVVlanEntry 705311748}

er1645v2PbbBGriMVVlanIpV6DhcpClientTimersSolMaxRt OBJECT-TYPE
   SYNTAX      TimeTicks
   MAX-ACCESS  read-write
   STATUS      current
   DESCRIPTION
      "Path: pbbBridgeGroup.editConf.vlan.ipV6.dhcp.client.timers.solMaxRt

       Time in centi-second."
   ::= {er1645v2PbbBGriMVVlanEntry 705311752}

er1645v2PbbBGriMVVlanIpV6DhcpClientTimersInfoRefresh OBJECT-TYPE
   SYNTAX      TimeTicks
   MAX-ACCESS  read-write
   STATUS      current
   DESCRIPTION
      "Path: pbbBridgeGroup.editConf.vlan.ipV6.dhcp.client.timers.infoRefresh

       Time in centi-second."
   ::= {er1645v2PbbBGriMVVlanEntry 705311756}

er1645v2PbbBGriMVVlanIpV6DhcpServerMode OBJECT-TYPE
   SYNTAX      INTEGER
               {
               disabled (0),
               enabled (1)
               }
   MAX-ACCESS  read-write
   STATUS      current
   DESCRIPTION
      "Path: pbbBridgeGroup.editConf.vlan.ipV6.dhcp.server.mode

       Possibilities:
               disabled   (0)
               enabled   (1)"
   ::= {er1645v2PbbBGriMVVlanEntry 705315840}

er1645v2PbbBGriMVVlanIpV6DhcpServerPreference OBJECT-TYPE
   SYNTAX      Integer32
   MAX-ACCESS  read-write
   STATUS      current
   DESCRIPTION
      "Path: pbbBridgeGroup.editConf.vlan.ipV6.dhcp.server.preference"
   ::= {er1645v2PbbBGriMVVlanEntry 705316864}

er1645v2PbbBGriMVVlanIpV6DhcpServerPool OBJECT-TYPE
   SYNTAX      DisplayString
   MAX-ACCESS  read-write
   STATUS      current
   DESCRIPTION
      "Path: pbbBridgeGroup.editConf.vlan.ipV6.dhcp.server.pool"
   ::= {er1645v2PbbBGriMVVlanEntry 705317888}

er1645v2PbbBGriMVVlanIpV6DhcpServerRapidCommit OBJECT-TYPE
   SYNTAX      INTEGER
               {
               disabled (0),
               enabled (1)
               }
   MAX-ACCESS  read-write
   STATUS      current
   DESCRIPTION
      "Path: pbbBridgeGroup.editConf.vlan.ipV6.dhcp.server.rapidCommit

       Possibilities:
               disabled   (0)
               enabled   (1)"
   ::= {er1645v2PbbBGriMVVlanEntry 705318912}

er1645v2PbbBGriMVVlanIpV6DhcpServerTimersInfoRefresh OBJECT-TYPE
   SYNTAX      TimeTicks
   MAX-ACCESS  read-write
   STATUS      current
   DESCRIPTION
      "Path: pbbBridgeGroup.editConf.vlan.ipV6.dhcp.server.timers.infoRefresh

       Time in centi-second."
   ::= {er1645v2PbbBGriMVVlanEntry 705319940}

er1645v2PbbBGriMVVlanIpV6DhcpRelayMode OBJECT-TYPE
   SYNTAX      INTEGER
               {
               disabled (0),
               enabled (1)
               }
   MAX-ACCESS  read-write
   STATUS      current
   DESCRIPTION
      "Path: pbbBridgeGroup.editConf.vlan.ipV6.dhcp.relay.mode

       Possibilities:
               disabled   (0)
               enabled   (1)"
   ::= {er1645v2PbbBGriMVVlanEntry 705323040}

er1645v2PbbBGriMVVlanIpV6SendRedirect OBJECT-TYPE
   SYNTAX      INTEGER
               {
               disabled (0),
               enabled (1)
               }
   MAX-ACCESS  read-write
   STATUS      current
   DESCRIPTION
      "Path: pbbBridgeGroup.editConf.vlan.ipV6.sendRedirect

       Possibilities:
               disabled   (0)
               enabled   (1)"
   ::= {er1645v2PbbBGriMVVlanEntry 705101824}

er1645v2PbbBGriMVVlanIpV6LinkMtu OBJECT-TYPE
   SYNTAX      Integer32
   MAX-ACCESS  read-write
   STATUS      current
   DESCRIPTION
      "Path: pbbBridgeGroup.editConf.vlan.ipV6.linkMtu"
   ::= {er1645v2PbbBGriMVVlanEntry 705167360}

er1645v2PbbBGriMVVlanIpV6InterfaceId OBJECT-TYPE
   SYNTAX      OCTET STRING
   MAX-ACCESS  read-write
   STATUS      current
   DESCRIPTION
      "Path: pbbBridgeGroup.editConf.vlan.ipV6.interfaceId"
   ::= {er1645v2PbbBGriMVVlanEntry 705232896}

er1645v2PbbBGriMVVlanIpV6MF OBJECT-TYPE
   SYNTAX      Integer32
   MAX-ACCESS  read-write
   STATUS      current
   DESCRIPTION
      "Path: pbbBridgeGroup.editConf.vlan.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2PbbBGriMVVlanEntry 705757184}

er1645v2PbbBGriMVVlanIpV6IcmpMessagesNoRoute OBJECT-TYPE
   SYNTAX      INTEGER
               {
               disabled (0),
               enabled (1)
               }
   MAX-ACCESS  read-write
   STATUS      current
   DESCRIPTION
      "Path: pbbBridgeGroup.editConf.vlan.ipV6.icmpMessages.noRoute

       Possibilities:
               disabled   (0)
               enabled   (1)"
   ::= {er1645v2PbbBGriMVVlanEntry 705822976}

er1645v2PbbBGriMVVlanIpV6IcmpMessagesBeyondScope OBJECT-TYPE
   SYNTAX      INTEGER
               {
               disabled (0),
               enabled (1)
               }
   MAX-ACCESS  read-write
   STATUS      current
   DESCRIPTION
      "Path: pbbBridgeGroup.editConf.vlan.ipV6.icmpMessages.beyondScope

       Possibilities:
               disabled   (0)
               enabled   (1)"
   ::= {er1645v2PbbBGriMVVlanEntry 705823488}

er1645v2PbbBGriMVVlanIpV6IcmpMessagesAddressUnreachable OBJECT-TYPE
   SYNTAX      INTEGER
               {
               disabled (0),
               enabled (1)
               }
   MAX-ACCESS  read-write
   STATUS      current
   DESCRIPTION
      "Path: pbbBridgeGroup.editConf.vlan.ipV6.icmpMessages.addressUnreachable

       Possibilities:
               disabled   (0)
               enabled   (1)"
   ::= {er1645v2PbbBGriMVVlanEntry 705823744}

er1645v2PbbBGriMVVlanIpV6IcmpMessagesPortUnreachable OBJECT-TYPE
   SYNTAX      INTEGER
               {
               disabled (0),
               enabled (1)
               }
   MAX-ACCESS  read-write
   STATUS      current
   DESCRIPTION
      "Path: pbbBridgeGroup.editConf.vlan.ipV6.icmpMessages.portUnreachable

       Possibilities:
               disabled   (0)
               enabled   (1)"
   ::= {er1645v2PbbBGriMVVlanEntry 705824000}

er1645v2PbbBGriMVVlanIpV6IcmpMessagesPacketTooBig OBJECT-TYPE
   SYNTAX      INTEGER
               {
               disabled (0),
               enabled (1)
               }
   MAX-ACCESS  read-write
   STATUS      current
   DESCRIPTION
      "Path: pbbBridgeGroup.editConf.vlan.ipV6.icmpMessages.packetTooBig

       Possibilities:
               disabled   (0)
               enabled   (1)"
   ::= {er1645v2PbbBGriMVVlanEntry 705825280}

er1645v2PbbBGriMVVlanIpV6IcmpMessagesHopLimitExceeded OBJECT-TYPE
   SYNTAX      INTEGER
               {
               disabled (0),
               enabled (1)
               }
   MAX-ACCESS  read-write
   STATUS      current
   DESCRIPTION
      "Path: pbbBridgeGroup.editConf.vlan.ipV6.icmpMessages.hopLimitExceeded

       Possibilities:
               disabled   (0)
               enabled   (1)"
   ::= {er1645v2PbbBGriMVVlanEntry 705827840}

er1645v2PbbBGriMVVlanIpV6IcmpMessagesFragTimeExceeded OBJECT-TYPE
   SYNTAX      INTEGER
               {
               disabled (0),
               enabled (1)
               }
   MAX-ACCESS  read-write
   STATUS      current
   DESCRIPTION
      "Path: pbbBridgeGroup.editConf.vlan.ipV6.icmpMessages.fragTimeExceeded

       Possibilities:
               disabled   (0)
               enabled   (1)"
   ::= {er1645v2PbbBGriMVVlanEntry 705828096}

er1645v2PbbBGriMVVlanIpV6IcmpMessagesHeaderFieldErr OBJECT-TYPE
   SYNTAX      INTEGER
               {
               disabled (0),
               enabled (1)
               }
   MAX-ACCESS  read-write
   STATUS      current
   DESCRIPTION
      "Path: pbbBridgeGroup.editConf.vlan.ipV6.icmpMessages.headerFieldErr

       Possibilities:
               disabled   (0)
               enabled   (1)"
   ::= {er1645v2PbbBGriMVVlanEntry 705830400}

er1645v2PbbBGriMVVlanIpV6IcmpMessagesOptionUnrecognized OBJECT-TYPE
   SYNTAX      INTEGER
               {
               disabled (0),
               enabled (1)
               }
   MAX-ACCESS  read-write
   STATUS      current
   DESCRIPTION
      "Path: pbbBridgeGroup.editConf.vlan.ipV6.icmpMessages.optionUnrecognized

       Possibilities:
               disabled   (0)
               enabled   (1)"
   ::= {er1645v2PbbBGriMVVlanEntry 705830912}

er1645v2PbbBGriMVVlanIpV6IcmpMessagesRedirect OBJECT-TYPE
   SYNTAX      INTEGER
               {
               disabled (0),
               enabled (1)
               }
   MAX-ACCESS  read-write
   STATUS      current
   DESCRIPTION
      "Path: pbbBridgeGroup.editConf.vlan.ipV6.icmpMessages.redirect

       Possibilities:
               disabled   (0)
               enabled   (1)"
   ::= {er1645v2PbbBGriMVVlanEntry 705832960}

er1645v2PbbBGriMVVlanVlanVid OBJECT-TYPE
   SYNTAX      INTEGER
               {
               prioTagged (4096)
               }
   MAX-ACCESS  read-write
   STATUS      current
   DESCRIPTION
      "Path: pbbBridgeGroup.editConf.vlan.vlan.vid

       Possibilities:
               prioTagged   (4096)"
   ::= {er1645v2PbbBGriMVVlanEntry 234946560}

er1645v2PbbBGriMVVlanVlanTpid OBJECT-TYPE
   SYNTAX      INTEGER
               {
               dot1Q (33024),
               dot1ad (34984),
               s0x9100 (37120),
               s0x9200 (37376),
               s0x9300 (37632)
               }
   MAX-ACCESS  read-write
   STATUS      current
   DESCRIPTION
      "Path: pbbBridgeGroup.editConf.vlan.vlan.tpid

       Possibilities:
               dot1Q   (33024)
               dot1ad   (34984)
               0x9100   (37120)
               0x9200   (37376)
               0x9300   (37632)"
   ::= {er1645v2PbbBGriMVVlanEntry 241238016}

er1645v2PbbBGriMVVlanVlanTxCos OBJECT-TYPE
   SYNTAX      INTEGER
               {
               tosCosMap (8),
               queueCosMap (16)
               }
   MAX-ACCESS  read-write
   STATUS      current
   DESCRIPTION
      "Path: pbbBridgeGroup.editConf.vlan.vlan.txCos

       Possibilities:
               tosCosMap   (8)
               queueCosMap   (16)"
   ::= {er1645v2PbbBGriMVVlanEntry 235077632}

er1645v2PbbBGriMVVlanVlanChTos OBJECT-TYPE
   SYNTAX      INTEGER
               {
               disabled (0),
               enabled (1)
               }
   MAX-ACCESS  read-write
   STATUS      current
   DESCRIPTION
      "Path: pbbBridgeGroup.editConf.vlan.vlan.changeTos

       Possibilities:
               disabled   (0)
               enabled   (1)"
   ::= {er1645v2PbbBGriMVVlanEntry 235208704}

er1645v2PbbBGriMVVlanVlanCTMapP0 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p0

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235143424}

er1645v2PbbBGriMVVlanVlanCTMapP1 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p1

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235143680}

er1645v2PbbBGriMVVlanVlanCTMapP2 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p2

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235143936}

er1645v2PbbBGriMVVlanVlanCTMapP3 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p3

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235144192}

er1645v2PbbBGriMVVlanVlanCTMapP4 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p4

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235144448}

er1645v2PbbBGriMVVlanVlanCTMapP5 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p5

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235144704}

er1645v2PbbBGriMVVlanVlanCTMapP6 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p6

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235144960}

er1645v2PbbBGriMVVlanVlanCTMapP7 OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184)
               }
   MAX-ACCESS  read-write
   STATUS      current
   DESCRIPTION
      "Path: pbbBridgeGroup.editConf.vlan.vlan.cosTosMap.p7

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)"
   ::= {er1645v2PbbBGriMVVlanEntry 235145216}

er1645v2PbbBGriMVVlanVlanQCMapQueue1 OBJECT-TYPE
   SYNTAX      Integer32
   MAX-ACCESS  read-write
   STATUS      current
   DESCRIPTION
      "Path: pbbBridgeGroup.editConf.vlan.vlan.queueCosMap.queue1"
   ::= {er1645v2PbbBGriMVVlanEntry 241434880}

er1645v2PbbBGriMVVlanVlanQCMapQueue2 OBJECT-TYPE
   SYNTAX      Integer32
   MAX-ACCESS  read-write
   STATUS      current
   DESCRIPTION
      "Path: pbbBridgeGroup.editConf.vlan.vlan.queueCosMap.queue2"
   ::= {er1645v2PbbBGriMVVlanEntry 241435136}

er1645v2PbbBGriMVVlanVlanQCMapQueue3 OBJECT-TYPE
   SYNTAX      Integer32
   MAX-ACCESS  read-write
   STATUS      current
   DESCRIPTION
      "Path: pbbBridgeGroup.editConf.vlan.vlan.queueCosMap.queue3"
   ::= {er1645v2PbbBGriMVVlanEntry 241435392}

er1645v2PbbBGriMVVlanVlanQCMapQueue4 OBJECT-TYPE
   SYNTAX      Integer32
   MAX-ACCESS  read-write
   STATUS      current
   DESCRIPTION
      "Path: pbbBridgeGroup.editConf.vlan.vlan.queueCosMap.queue4"
   ::= {er1645v2PbbBGriMVVlanEntry 241435648}

er1645v2PbbBGriMVVlanVlanQCMapQueue5 OBJECT-TYPE
   SYNTAX      Integer32
   MAX-ACCESS  read-write
   STATUS      current
   DESCRIPTION
      "Path: pbbBridgeGroup.editConf.vlan.vlan.queueCosMap.queue5"
   ::= {er1645v2PbbBGriMVVlanEntry 241435904}

er1645v2PbbBGriMVVlanVlanQCMapLowDelayQueue OBJECT-TYPE
   SYNTAX      Integer32
   MAX-ACCESS  read-write
   STATUS      current
   DESCRIPTION
      "Path: pbbBridgeGroup.editConf.vlan.vlan.queueCosMap.lowDelayQueue"
   ::= {er1645v2PbbBGriMVVlanEntry 241436160}

er1645v2PbbBGriMVVlanVlanQCMapLowDelay2Queue OBJECT-TYPE
   SYNTAX      Integer32
   MAX-ACCESS  read-write
   STATUS      current
   DESCRIPTION
      "Path: pbbBridgeGroup.editConf.vlan.vlan.queueCosMap.lowDelay2Queue"
   ::= {er1645v2PbbBGriMVVlanEntry 241436416}

er1645v2PbbBGriMVVlanVlanQCMapSystemQueue OBJECT-TYPE
   SYNTAX      Integer32
   MAX-ACCESS  read-write
   STATUS      current
   DESCRIPTION
      "Path: pbbBridgeGroup.editConf.vlan.vlan.queueCosMap.systemQueue"
   ::= {er1645v2PbbBGriMVVlanEntry 241436672}

er1645v2PbbBGriMVVlanVlanArpTimeOut OBJECT-TYPE
   SYNTAX      TimeTicks
   MAX-ACCESS  read-write
   STATUS      current
   DESCRIPTION
      "Path: pbbBridgeGroup.editConf.vlan.vlan.arp.timeOut

       Time in centi-second."
   ::= {er1645v2PbbBGriMVVlanEntry 235277312}

er1645v2PbbBGriMVVlanVlanArpProxyArp OBJECT-TYPE
   SYNTAX      INTEGER
               {
               disabled (0),
               enabled (1)
               }
   MAX-ACCESS  read-write
   STATUS      current
   DESCRIPTION
      "Path: pbbBridgeGroup.editConf.vlan.vlan.arp.proxyArp

       Possibilities:
               disabled   (0)
               enabled   (1)"
   ::= {er1645v2PbbBGriMVVlanEntry 235287040}

er1645v2PbbBGriMVVlanIpSaddr OBJECT-TYPE
   SYNTAX      SEQUENCE OF Er1645v2PbbBGriMVVlanIpSaddrEntry
   MAX-ACCESS  not-accessible
   STATUS      current
   DESCRIPTION
      ""
   ::= {er1645v2PbbBGriMVVlan 51838976}

er1645v2PbbBGriMVVlanIpSaddrEntry OBJECT-TYPE
   SYNTAX      Er1645v2PbbBGriMVVlanIpSaddrEntry
   MAX-ACCESS  not-accessible
   STATUS      current
   DESCRIPTION
      ""
   INDEX      { er1645v2PbbBGriMVVlanIpSaddrGlobalIx,
                er1645v2PbbBGriMVVlanTableIx,
                er1645v2PbbBGriMVVlanIpSaddrTableIx }
   ::= {er1645v2PbbBGriMVVlanIpSaddr 1}

Er1645v2PbbBGriMVVlanIpSaddrEntry ::=
   SEQUENCE
      {
      er1645v2PbbBGriMVVlanIpSaddrActions
         VariableLengthTableActions,
      er1645v2PbbBGriMVVlanIpSaddrGlobalIx
         GlobalIndex,
      er1645v2PbbBGriMVVlanIpSaddrTableIx
         TableIndex,
      er1645v2PbbBGriMVVlanIpSaddrAddress
         IpAddress,
      er1645v2PbbBGriMVVlanIpSaddrNetMask
         IpAddress
      }

er1645v2PbbBGriMVVlanIpSaddrActions OBJECT-TYPE
   SYNTAX      VariableLengthTableActions
   MAX-ACCESS  read-write
   STATUS      current
   DESCRIPTION
      "By way of this field, some manipulations
       on this table may be performed."
   ::= {er1645v2PbbBGriMVVlanIpSaddrEntry 2}

er1645v2PbbBGriMVVlanIpSaddrGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpSaddrEntry 10}

er1645v2PbbBGriMVVlanIpSaddrTableIx OBJECT-TYPE
   SYNTAX      TableIndex
   MAX-ACCESS  not-accessible
   STATUS      current
   DESCRIPTION
      ""
   ::= {er1645v2PbbBGriMVVlanIpSaddrEntry 11}

er1645v2PbbBGriMVVlanIpSaddrAddress OBJECT-TYPE
   SYNTAX      IpAddress
   MAX-ACCESS  read-write
   STATUS      current
   DESCRIPTION
      "Path: pbbBridgeGroup.editConf.vlan.ip.secondaryIp.address"
   ::= {er1645v2PbbBGriMVVlanIpSaddrEntry 2030043136}

er1645v2PbbBGriMVVlanIpSaddrNetMask OBJECT-TYPE
   SYNTAX      IpAddress
   MAX-ACCESS  read-write
   STATUS      current
   DESCRIPTION
      "Path: pbbBridgeGroup.editConf.vlan.ip.secondaryIp.netMask"
   ::= {er1645v2PbbBGriMVVlanIpSaddrEntry 2063597568}

er1645v2PbbBGriMVVlanIpH OBJECT-TYPE
   SYNTAX      SEQUENCE OF Er1645v2PbbBGriMVVlanIpHEntry
   MAX-ACCESS  not-accessible
   STATUS      current
   DESCRIPTION
      ""
   ::= {er1645v2PbbBGriMVVlan 51314688}

er1645v2PbbBGriMVVlanIpHEntry OBJECT-TYPE
   SYNTAX      Er1645v2PbbBGriMVVlanIpHEntry
   MAX-ACCESS  not-accessible
   STATUS      current
   DESCRIPTION
      ""
   INDEX      { er1645v2PbbBGriMVVlanIpHGlobalIx,
                er1645v2PbbBGriMVVlanTableIx,
                er1645v2PbbBGriMVVlanIpHTableIx }
   ::= {er1645v2PbbBGriMVVlanIpH 1}

Er1645v2PbbBGriMVVlanIpHEntry ::=
   SEQUENCE
      {
      er1645v2PbbBGriMVVlanIpHActions
         VariableLengthTableActions,
      er1645v2PbbBGriMVVlanIpHGlobalIx
         GlobalIndex,
      er1645v2PbbBGriMVVlanIpHTableIx
         TableIndex,
      er1645v2PbbBGriMVVlanIpHAddress
         IpAddress,
      er1645v2PbbBGriMVVlanIpHDhcpRelayOptionSubscriberId
         DisplayString
      }

er1645v2PbbBGriMVVlanIpHActions OBJECT-TYPE
   SYNTAX      VariableLengthTableActions
   MAX-ACCESS  read-write
   STATUS      current
   DESCRIPTION
      "By way of this field, some manipulations
       on this table may be performed."
   ::= {er1645v2PbbBGriMVVlanIpHEntry 2}

er1645v2PbbBGriMVVlanIpHGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpHEntry 10}

er1645v2PbbBGriMVVlanIpHTableIx OBJECT-TYPE
   SYNTAX      TableIndex
   MAX-ACCESS  not-accessible
   STATUS      current
   DESCRIPTION
      ""
   ::= {er1645v2PbbBGriMVVlanIpHEntry 11}

er1645v2PbbBGriMVVlanIpHAddress OBJECT-TYPE
   SYNTAX      IpAddress
   MAX-ACCESS  read-write
   STATUS      current
   DESCRIPTION
      "Path: pbbBridgeGroup.editConf.vlan.ip.helpers.address"
   ::= {er1645v2PbbBGriMVVlanIpHEntry 16777216}

er1645v2PbbBGriMVVlanIpHDhcpRelayOptionSubscriberId OBJECT-TYPE
   SYNTAX      DisplayString
   MAX-ACCESS  read-write
   STATUS      current
   DESCRIPTION
      "Path: pbbBridgeGroup.editConf.vlan.ip.helpers.dhcpRelayOption.subscriberId"
   ::= {er1645v2PbbBGriMVVlanIpHEntry 33947648}

er1645v2PbbBGriMVVlanIpV6Addresses OBJECT-TYPE
   SYNTAX      SEQUENCE OF Er1645v2PbbBGriMVVlanIpV6AddressesEntry
   MAX-ACCESS  not-accessible
   STATUS      current
   DESCRIPTION
      ""
   ::= {er1645v2PbbBGriMVVlan 704839680}

er1645v2PbbBGriMVVlanIpV6AddressesEntry OBJECT-TYPE
   SYNTAX      Er1645v2PbbBGriMVVlanIpV6AddressesEntry
   MAX-ACCESS  not-accessible
   STATUS      current
   DESCRIPTION
      ""
   INDEX      { er1645v2PbbBGriMVVlanIpV6AddressesGlobalIx,
                er1645v2PbbBGriMVVlanTableIx,
                er1645v2PbbBGriMVVlanIpV6AddressesTableIx }
   ::= {er1645v2PbbBGriMVVlanIpV6Addresses 1}

Er1645v2PbbBGriMVVlanIpV6AddressesEntry ::=
   SEQUENCE
      {
      er1645v2PbbBGriMVVlanIpV6AddressesActions
         VariableLengthTableActions,
      er1645v2PbbBGriMVVlanIpV6AddressesGlobalIx
         GlobalIndex,
      er1645v2PbbBGriMVVlanIpV6AddressesTableIx
         TableIndex,
      er1645v2PbbBGriMVVlanIpV6AddressesType
         INTEGER,
      er1645v2PbbBGriMVVlanIpV6AddressesAddress
         Ipv6Address,
      er1645v2PbbBGriMVVlanIpV6AddressesPrefixLength
         Integer32,
      er1645v2PbbBGriMVVlanIpV6AddressesGeneralPrefix
         DisplayString,
      er1645v2PbbBGriMVVlanIpV6AddressesRaSend
         INTEGER,
      er1645v2PbbBGriMVVlanIpV6AddressesRaOnLinkFlag
         INTEGER,
      er1645v2PbbBGriMVVlanIpV6AddressesRaAutoFlag
         INTEGER,
      er1645v2PbbBGriMVVlanIpV6AddressesRaValidLifeTime
         TimeTicks,
      er1645v2PbbBGriMVVlanIpV6AddressesRaValidLTMode
         INTEGER,
      er1645v2PbbBGriMVVlanIpV6AddressesRaPrefLifeTime
         TimeTicks,
      er1645v2PbbBGriMVVlanIpV6AddressesRaPrefLTMode
         INTEGER
      }

er1645v2PbbBGriMVVlanIpV6AddressesActions OBJECT-TYPE
   SYNTAX      VariableLengthTableActions
   MAX-ACCESS  read-write
   STATUS      current
   DESCRIPTION
      "By way of this field, some manipulations
       on this table may be performed."
   ::= {er1645v2PbbBGriMVVlanIpV6AddressesEntry 2}

er1645v2PbbBGriMVVlanIpV6AddressesGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpV6AddressesEntry 10}

er1645v2PbbBGriMVVlanIpV6AddressesTableIx OBJECT-TYPE
   SYNTAX      TableIndex
   MAX-ACCESS  not-accessible
   STATUS      current
   DESCRIPTION
      ""
   ::= {er1645v2PbbBGriMVVlanIpV6AddressesEntry 11}

er1645v2PbbBGriMVVlanIpV6AddressesType OBJECT-TYPE
   SYNTAX      INTEGER
               {
               unicast (0),
               eui64 (1),
               anycast (2),
               linkLocal (3),
               generalPrefix (4)
               }
   MAX-ACCESS  read-write
   STATUS      current
   DESCRIPTION
      "Path: pbbBridgeGroup.editConf.vlan.ipV6.addresses.type

       Possibilities:
               unicast   (0)
               eui64   (1)
               anycast   (2)
               linkLocal   (3)
               generalPrefix   (4)"
   ::= {er1645v2PbbBGriMVVlanIpV6AddressesEntry 50331648}

er1645v2PbbBGriMVVlanIpV6AddressesAddress OBJECT-TYPE
   SYNTAX      Ipv6Address
   MAX-ACCESS  read-write
   STATUS      current
   DESCRIPTION
      "Path: pbbBridgeGroup.editConf.vlan.ipV6.addresses.address

       ipv6 address"
   ::= {er1645v2PbbBGriMVVlanIpV6AddressesEntry 16777216}

er1645v2PbbBGriMVVlanIpV6AddressesPrefixLength OBJECT-TYPE
   SYNTAX      Integer32
   MAX-ACCESS  read-write
   STATUS      current
   DESCRIPTION
      "Path: pbbBridgeGroup.editConf.vlan.ipV6.addresses.prefixLength"
   ::= {er1645v2PbbBGriMVVlanIpV6AddressesEntry 33554432}

er1645v2PbbBGriMVVlanIpV6AddressesGeneralPrefix OBJECT-TYPE
   SYNTAX      DisplayString
   MAX-ACCESS  read-write
   STATUS      current
   DESCRIPTION
      "Path: pbbBridgeGroup.editConf.vlan.ipV6.addresses.generalPrefix"
   ::= {er1645v2PbbBGriMVVlanIpV6AddressesEntry 83886080}

er1645v2PbbBGriMVVlanIpV6AddressesRaSend OBJECT-TYPE
   SYNTAX      INTEGER
               {
               disabled (0),
               enabled (1)
               }
   MAX-ACCESS  read-write
   STATUS      current
   DESCRIPTION
      "Path: pbbBridgeGroup.editConf.vlan.ipV6.addresses.ra.send

       Possibilities:
               disabled   (0)
               enabled   (1)"
   ::= {er1645v2PbbBGriMVVlanIpV6AddressesEntry 67174400}

er1645v2PbbBGriMVVlanIpV6AddressesRaOnLinkFlag OBJECT-TYPE
   SYNTAX      INTEGER
               {
               disabled (0),
               enabled (1)
               }
   MAX-ACCESS  read-write
   STATUS      current
   DESCRIPTION
      "Path: pbbBridgeGroup.editConf.vlan.ipV6.addresses.ra.onLinkFlag

       Possibilities:
               disabled   (0)
               enabled   (1)"
   ::= {er1645v2PbbBGriMVVlanIpV6AddressesEntry 67371008}

er1645v2PbbBGriMVVlanIpV6AddressesRaAutoFlag OBJECT-TYPE
   SYNTAX      INTEGER
               {
               disabled (0),
               enabled (1)
               }
   MAX-ACCESS  read-write
   STATUS      current
   DESCRIPTION
      "Path: pbbBridgeGroup.editConf.vlan.ipV6.addresses.ra.autonomousFlag

       Possibilities:
               disabled   (0)
               enabled   (1)"
   ::= {er1645v2PbbBGriMVVlanIpV6AddressesEntry 67567616}

er1645v2PbbBGriMVVlanIpV6AddressesRaValidLifeTime OBJECT-TYPE
   SYNTAX      TimeTicks
   MAX-ACCESS  read-write
   STATUS      current
   DESCRIPTION
      "Path: pbbBridgeGroup.editConf.vlan.ipV6.addresses.ra.validLifeTime

       Time in centi-second."
   ::= {er1645v2PbbBGriMVVlanIpV6AddressesEntry 67239936}

er1645v2PbbBGriMVVlanIpV6AddressesRaValidLTMode OBJECT-TYPE
   SYNTAX      INTEGER
               {
               fixed (0),
               infinite (2)
               }
   MAX-ACCESS  read-write
   STATUS      current
   DESCRIPTION
      "Path: pbbBridgeGroup.editConf.vlan.ipV6.addresses.ra.validLifeTimeMode

       Possibilities:
               fixed   (0)
               infinite   (2)"
   ::= {er1645v2PbbBGriMVVlanIpV6AddressesEntry 67305472}

er1645v2PbbBGriMVVlanIpV6AddressesRaPrefLifeTime OBJECT-TYPE
   SYNTAX      TimeTicks
   MAX-ACCESS  read-write
   STATUS      current
   DESCRIPTION
      "Path: pbbBridgeGroup.editConf.vlan.ipV6.addresses.ra.prefLifeTime

       Time in centi-second."
   ::= {er1645v2PbbBGriMVVlanIpV6AddressesEntry 67436544}

er1645v2PbbBGriMVVlanIpV6AddressesRaPrefLTMode OBJECT-TYPE
   SYNTAX      INTEGER
               {
               fixed (0),
               infinite (2)
               }
   MAX-ACCESS  read-write
   STATUS      current
   DESCRIPTION
      "Path: pbbBridgeGroup.editConf.vlan.ipV6.addresses.ra.prefLifeTimeMode

       Possibilities:
               fixed   (0)
               infinite   (2)"
   ::= {er1645v2PbbBGriMVVlanIpV6AddressesEntry 67502080}

er1645v2PbbBGriMVVlanIpV6RaDnsOptionsRdnssServers OBJECT-TYPE
   SYNTAX      SEQUENCE OF Er1645v2PbbBGriMVVlanIpV6RaDnsOptionsRdnssServersEntry
   MAX-ACCESS  not-accessible
   STATUS      current
   DESCRIPTION
      ""
   ::= {er1645v2PbbBGriMVVlan 705039144}

er1645v2PbbBGriMVVlanIpV6RaDnsOptionsRdnssServersEntry OBJECT-TYPE
   SYNTAX      Er1645v2PbbBGriMVVlanIpV6RaDnsOptionsRdnssServersEntry
   MAX-ACCESS  not-accessible
   STATUS      current
   DESCRIPTION
      ""
   INDEX      { er1645v2PbbBGriMVVlanIpV6RaDnsOptionsRdnssServersGlobalIx,
                er1645v2PbbBGriMVVlanTableIx,
                er1645v2PbbBGriMVVlanIpV6RaDnsOptionsRdnssServersTableIx }
   ::= {er1645v2PbbBGriMVVlanIpV6RaDnsOptionsRdnssServers 1}

Er1645v2PbbBGriMVVlanIpV6RaDnsOptionsRdnssServersEntry ::=
   SEQUENCE
      {
      er1645v2PbbBGriMVVlanIpV6RaDnsOptionsRdnssServersActions
         VariableLengthTableActions,
      er1645v2PbbBGriMVVlanIpV6RaDnsOptionsRdnssServersGlobalIx
         GlobalIndex,
      er1645v2PbbBGriMVVlanIpV6RaDnsOptionsRdnssServersTableIx
         TableIndex,
      er1645v2PbbBGriMVVlanIpV6RaDnsOptionsRdnssServersAddress
         Ipv6Address
      }

er1645v2PbbBGriMVVlanIpV6RaDnsOptionsRdnssServersActions OBJECT-TYPE
   SYNTAX      VariableLengthTableActions
   MAX-ACCESS  read-write
   STATUS      current
   DESCRIPTION
      "By way of this field, some manipulations
       on this table may be performed."
   ::= {er1645v2PbbBGriMVVlanIpV6RaDnsOptionsRdnssServersEntry 2}

er1645v2PbbBGriMVVlanIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpV6RaDnsOptionsRdnssServersEntry 10}

er1645v2PbbBGriMVVlanIpV6RaDnsOptionsRdnssServersTableIx OBJECT-TYPE
   SYNTAX      TableIndex
   MAX-ACCESS  not-accessible
   STATUS      current
   DESCRIPTION
      ""
   ::= {er1645v2PbbBGriMVVlanIpV6RaDnsOptionsRdnssServersEntry 11}

er1645v2PbbBGriMVVlanIpV6RaDnsOptionsRdnssServersAddress OBJECT-TYPE
   SYNTAX      Ipv6Address
   MAX-ACCESS  read-write
   STATUS      current
   DESCRIPTION
      "Path: pbbBridgeGroup.editConf.vlan.ipV6.ra.dnsOptions.rdnss.servers.address

       ipv6 address"
   ::= {er1645v2PbbBGriMVVlanIpV6RaDnsOptionsRdnssServersEntry 16777216}

er1645v2PbbBGriMVVlanIpV6RaDnsOptionsDnsslDomains OBJECT-TYPE
   SYNTAX      SEQUENCE OF Er1645v2PbbBGriMVVlanIpV6RaDnsOptionsDnsslDomainsEntry
   MAX-ACCESS  not-accessible
   STATUS      current
   DESCRIPTION
      ""
   ::= {er1645v2PbbBGriMVVlan 705039176}

er1645v2PbbBGriMVVlanIpV6RaDnsOptionsDnsslDomainsEntry OBJECT-TYPE
   SYNTAX      Er1645v2PbbBGriMVVlanIpV6RaDnsOptionsDnsslDomainsEntry
   MAX-ACCESS  not-accessible
   STATUS      current
   DESCRIPTION
      ""
   INDEX      { er1645v2PbbBGriMVVlanIpV6RaDnsOptionsDnsslDomainsGlobalIx,
                er1645v2PbbBGriMVVlanTableIx,
                er1645v2PbbBGriMVVlanIpV6RaDnsOptionsDnsslDomainsTableIx }
   ::= {er1645v2PbbBGriMVVlanIpV6RaDnsOptionsDnsslDomains 1}

Er1645v2PbbBGriMVVlanIpV6RaDnsOptionsDnsslDomainsEntry ::=
   SEQUENCE
      {
      er1645v2PbbBGriMVVlanIpV6RaDnsOptionsDnsslDomainsActions
         VariableLengthTableActions,
      er1645v2PbbBGriMVVlanIpV6RaDnsOptionsDnsslDomainsGlobalIx
         GlobalIndex,
      er1645v2PbbBGriMVVlanIpV6RaDnsOptionsDnsslDomainsTableIx
         TableIndex,
      er1645v2PbbBGriMVVlanIpV6RaDnsOptionsDnsslDomainsName
         DisplayString
      }

er1645v2PbbBGriMVVlanIpV6RaDnsOptionsDnsslDomainsActions OBJECT-TYPE
   SYNTAX      VariableLengthTableActions
   MAX-ACCESS  read-write
   STATUS      current
   DESCRIPTION
      "By way of this field, some manipulations
       on this table may be performed."
   ::= {er1645v2PbbBGriMVVlanIpV6RaDnsOptionsDnsslDomainsEntry 2}

er1645v2PbbBGriMVVlanIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpV6RaDnsOptionsDnsslDomainsEntry 10}

er1645v2PbbBGriMVVlanIpV6RaDnsOptionsDnsslDomainsTableIx OBJECT-TYPE
   SYNTAX      TableIndex
   MAX-ACCESS  not-accessible
   STATUS      current
   DESCRIPTION
      ""
   ::= {er1645v2PbbBGriMVVlanIpV6RaDnsOptionsDnsslDomainsEntry 11}

er1645v2PbbBGriMVVlanIpV6RaDnsOptionsDnsslDomainsName OBJECT-TYPE
   SYNTAX      DisplayString
   MAX-ACCESS  read-write
   STATUS      current
   DESCRIPTION
      "Path: pbbBridgeGroup.editConf.vlan.ipV6.ra.dnsOptions.dnssl.domains.name"
   ::= {er1645v2PbbBGriMVVlanIpV6RaDnsOptionsDnsslDomainsEntry 16777216}

er1645v2PbbBGriMVVlanIpV6DhcpClientUserClassOpt OBJECT-TYPE
   SYNTAX      SEQUENCE OF Er1645v2PbbBGriMVVlanIpV6DhcpClientUserClassOptEntry
   MAX-ACCESS  not-accessible
   STATUS      current
   DESCRIPTION
      ""
   ::= {er1645v2PbbBGriMVVlan 705312768}

er1645v2PbbBGriMVVlanIpV6DhcpClientUserClassOptEntry OBJECT-TYPE
   SYNTAX      Er1645v2PbbBGriMVVlanIpV6DhcpClientUserClassOptEntry
   MAX-ACCESS  not-accessible
   STATUS      current
   DESCRIPTION
      ""
   INDEX      { er1645v2PbbBGriMVVlanIpV6DhcpClientUserClassOptGlobalIx,
                er1645v2PbbBGriMVVlanTableIx,
                er1645v2PbbBGriMVVlanIpV6DhcpClientUserClassOptTableIx }
   ::= {er1645v2PbbBGriMVVlanIpV6DhcpClientUserClassOpt 1}

Er1645v2PbbBGriMVVlanIpV6DhcpClientUserClassOptEntry ::=
   SEQUENCE
      {
      er1645v2PbbBGriMVVlanIpV6DhcpClientUserClassOptActions
         VariableLengthTableActions,
      er1645v2PbbBGriMVVlanIpV6DhcpClientUserClassOptGlobalIx
         GlobalIndex,
      er1645v2PbbBGriMVVlanIpV6DhcpClientUserClassOptTableIx
         TableIndex,
      er1645v2PbbBGriMVVlanIpV6DhcpClientUserClassOptValueAscii
         DisplayString,
      er1645v2PbbBGriMVVlanIpV6DhcpClientUserClassOptValueDecimal
         Integer32,
      er1645v2PbbBGriMVVlanIpV6DhcpClientUserClassOptValueHexData
         OCTET STRING
      }

er1645v2PbbBGriMVVlanIpV6DhcpClientUserClassOptActions OBJECT-TYPE
   SYNTAX      VariableLengthTableActions
   MAX-ACCESS  read-write
   STATUS      current
   DESCRIPTION
      "By way of this field, some manipulations
       on this table may be performed."
   ::= {er1645v2PbbBGriMVVlanIpV6DhcpClientUserClassOptEntry 2}

er1645v2PbbBGriMVVlanIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpV6DhcpClientUserClassOptEntry 10}

er1645v2PbbBGriMVVlanIpV6DhcpClientUserClassOptTableIx OBJECT-TYPE
   SYNTAX      TableIndex
   MAX-ACCESS  not-accessible
   STATUS      current
   DESCRIPTION
      ""
   ::= {er1645v2PbbBGriMVVlanIpV6DhcpClientUserClassOptEntry 11}

er1645v2PbbBGriMVVlanIpV6DhcpClientUserClassOptValueAscii OBJECT-TYPE
   SYNTAX      DisplayString
   MAX-ACCESS  read-write
   STATUS      current
   DESCRIPTION
      "Path: pbbBridgeGroup.editConf.vlan.ipV6.dhcp.client.userClassOpt.value.ascii"
   ::= {er1645v2PbbBGriMVVlanIpV6DhcpClientUserClassOptEntry 16842752}

er1645v2PbbBGriMVVlanIpV6DhcpClientUserClassOptValueDecimal OBJECT-TYPE
   SYNTAX      Integer32
   MAX-ACCESS  read-write
   STATUS      current
   DESCRIPTION
      "Path: pbbBridgeGroup.editConf.vlan.ipV6.dhcp.client.userClassOpt.value.decimal"
   ::= {er1645v2PbbBGriMVVlanIpV6DhcpClientUserClassOptEntry 16908288}

er1645v2PbbBGriMVVlanIpV6DhcpClientUserClassOptValueHexData OBJECT-TYPE
   SYNTAX      OCTET STRING
   MAX-ACCESS  read-write
   STATUS      current
   DESCRIPTION
      "Path: pbbBridgeGroup.editConf.vlan.ipV6.dhcp.client.userClassOpt.value.hexData"
   ::= {er1645v2PbbBGriMVVlanIpV6DhcpClientUserClassOptEntry 16973824}

er1645v2PbbBGriMVVlanIpV6DhcpClientVendorCl OBJECT-TYPE
   SYNTAX      SEQUENCE OF Er1645v2PbbBGriMVVlanIpV6DhcpClientVendorClEntry
   MAX-ACCESS  not-accessible
   STATUS      current
   DESCRIPTION
      ""
   ::= {er1645v2PbbBGriMVVlan 705313792}

er1645v2PbbBGriMVVlanIpV6DhcpClientVendorClEntry OBJECT-TYPE
   SYNTAX      Er1645v2PbbBGriMVVlanIpV6DhcpClientVendorClEntry
   MAX-ACCESS  not-accessible
   STATUS      current
   DESCRIPTION
      ""
   INDEX      { er1645v2PbbBGriMVVlanIpV6DhcpClientVendorClGlobalIx,
                er1645v2PbbBGriMVVlanTableIx,
                er1645v2PbbBGriMVVlanIpV6DhcpClientVendorClTableIx }
   ::= {er1645v2PbbBGriMVVlanIpV6DhcpClientVendorCl 1}

Er1645v2PbbBGriMVVlanIpV6DhcpClientVendorClEntry ::=
   SEQUENCE
      {
      er1645v2PbbBGriMVVlanIpV6DhcpClientVendorClActions
         VariableLengthTableActions,
      er1645v2PbbBGriMVVlanIpV6DhcpClientVendorClGlobalIx
         GlobalIndex,
      er1645v2PbbBGriMVVlanIpV6DhcpClientVendorClTableIx
         TableIndex,
      er1645v2PbbBGriMVVlanIpV6DhcpClientVendorClValueAscii
         DisplayString,
      er1645v2PbbBGriMVVlanIpV6DhcpClientVendorClValueDecimal
         Integer32,
      er1645v2PbbBGriMVVlanIpV6DhcpClientVendorClValueHexData
         OCTET STRING
      }

er1645v2PbbBGriMVVlanIpV6DhcpClientVendorClActions OBJECT-TYPE
   SYNTAX      VariableLengthTableActions
   MAX-ACCESS  read-write
   STATUS      current
   DESCRIPTION
      "By way of this field, some manipulations
       on this table may be performed."
   ::= {er1645v2PbbBGriMVVlanIpV6DhcpClientVendorClEntry 2}

er1645v2PbbBGriMVVlanIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpV6DhcpClientVendorClEntry 10}

er1645v2PbbBGriMVVlanIpV6DhcpClientVendorClTableIx OBJECT-TYPE
   SYNTAX      TableIndex
   MAX-ACCESS  not-accessible
   STATUS      current
   DESCRIPTION
      ""
   ::= {er1645v2PbbBGriMVVlanIpV6DhcpClientVendorClEntry 11}

er1645v2PbbBGriMVVlanIpV6DhcpClientVendorClValueAscii OBJECT-TYPE
   SYNTAX      DisplayString
   MAX-ACCESS  read-write
   STATUS      current
   DESCRIPTION
      "Path: pbbBridgeGroup.editConf.vlan.ipV6.dhcp.client.vendorClassOpt.value.ascii"
   ::= {er1645v2PbbBGriMVVlanIpV6DhcpClientVendorClEntry 16842752}

er1645v2PbbBGriMVVlanIpV6DhcpClientVendorClValueDecimal OBJECT-TYPE
   SYNTAX      Integer32
   MAX-ACCESS  read-write
   STATUS      current
   DESCRIPTION
      "Path: pbbBridgeGroup.editConf.vlan.ipV6.dhcp.client.vendorClassOpt.value.decimal"
   ::= {er1645v2PbbBGriMVVlanIpV6DhcpClientVendorClEntry 16908288}

er1645v2PbbBGriMVVlanIpV6DhcpClientVendorClValueHexData OBJECT-TYPE
   SYNTAX      OCTET STRING
   MAX-ACCESS  read-write
   STATUS      current
   DESCRIPTION
      "Path: pbbBridgeGroup.editConf.vlan.ipV6.dhcp.client.vendorClassOpt.value.hexData"
   ::= {er1645v2PbbBGriMVVlanIpV6DhcpClientVendorClEntry 16973824}

er1645v2PbbBGriMVVlanIpV6DhcpRelayDestinations OBJECT-TYPE
   SYNTAX      SEQUENCE OF Er1645v2PbbBGriMVVlanIpV6DhcpRelayDestinationsEntry
   MAX-ACCESS  not-accessible
   STATUS      current
   DESCRIPTION
      ""
   ::= {er1645v2PbbBGriMVVlan 705323072}

er1645v2PbbBGriMVVlanIpV6DhcpRelayDestinationsEntry OBJECT-TYPE
   SYNTAX      Er1645v2PbbBGriMVVlanIpV6DhcpRelayDestinationsEntry
   MAX-ACCESS  not-accessible
   STATUS      current
   DESCRIPTION
      ""
   INDEX      { er1645v2PbbBGriMVVlanIpV6DhcpRelayDestinationsGlobalIx,
                er1645v2PbbBGriMVVlanTableIx,
                er1645v2PbbBGriMVVlanIpV6DhcpRelayDestinationsTableIx }
   ::= {er1645v2PbbBGriMVVlanIpV6DhcpRelayDestinations 1}

Er1645v2PbbBGriMVVlanIpV6DhcpRelayDestinationsEntry ::=
   SEQUENCE
      {
      er1645v2PbbBGriMVVlanIpV6DhcpRelayDestinationsActions
         VariableLengthTableActions,
      er1645v2PbbBGriMVVlanIpV6DhcpRelayDestinationsGlobalIx
         GlobalIndex,
      er1645v2PbbBGriMVVlanIpV6DhcpRelayDestinationsTableIx
         TableIndex,
      er1645v2PbbBGriMVVlanIpV6DhcpRelayDestinationsAddress
         Ipv6Address,
      er1645v2PbbBGriMVVlanIpV6DhcpRelayDestinationsInterface
         DisplayString
      }

er1645v2PbbBGriMVVlanIpV6DhcpRelayDestinationsActions OBJECT-TYPE
   SYNTAX      VariableLengthTableActions
   MAX-ACCESS  read-write
   STATUS      current
   DESCRIPTION
      "By way of this field, some manipulations
       on this table may be performed."
   ::= {er1645v2PbbBGriMVVlanIpV6DhcpRelayDestinationsEntry 2}

er1645v2PbbBGriMVVlanIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2PbbBGriMVVlanIpV6DhcpRelayDestinationsEntry 10}

er1645v2PbbBGriMVVlanIpV6DhcpRelayDestinationsTableIx OBJECT-TYPE
   SYNTAX      TableIndex
   MAX-ACCESS  not-accessible
   STATUS      current
   DESCRIPTION
      ""
   ::= {er1645v2PbbBGriMVVlanIpV6DhcpRelayDestinationsEntry 11}

er1645v2PbbBGriMVVlanIpV6DhcpRelayDestinationsAddress OBJECT-TYPE
   SYNTAX      Ipv6Address
   MAX-ACCESS  read-write
   STATUS      current
   DESCRIPTION
      "Path: pbbBridgeGroup.editConf.vlan.ipV6.dhcp.relay.destinations.address

       ipv6 address"
   ::= {er1645v2PbbBGriMVVlanIpV6DhcpRelayDestinationsEntry 16777216}

er1645v2PbbBGriMVVlanIpV6DhcpRelayDestinationsInterface OBJECT-TYPE
   SYNTAX      DisplayString
   MAX-ACCESS  read-write
   STATUS      current
   DESCRIPTION
      "Path: pbbBridgeGroup.editConf.vlan.ipV6.dhcp.relay.destinations.interface"
   ::= {er1645v2PbbBGriMVVlanIpV6DhcpRelayDestinationsEntry 33554432}

er1645v2PbbBGriMVVlanVlanTCMap OBJECT-TYPE
   SYNTAX      SEQUENCE OF Er1645v2PbbBGriMVVlanVlanTCMapEntry
   MAX-ACCESS  not-accessible
   STATUS      current
   DESCRIPTION
      ""
   ::= {er1645v2PbbBGriMVVlan 241369088}

er1645v2PbbBGriMVVlanVlanTCMapEntry OBJECT-TYPE
   SYNTAX      Er1645v2PbbBGriMVVlanVlanTCMapEntry
   MAX-ACCESS  not-accessible
   STATUS      current
   DESCRIPTION
      ""
   INDEX      { er1645v2PbbBGriMVVlanVlanTCMapGlobalIx,
                er1645v2PbbBGriMVVlanTableIx,
                er1645v2PbbBGriMVVlanVlanTCMapTableIx }
   ::= {er1645v2PbbBGriMVVlanVlanTCMap 1}

Er1645v2PbbBGriMVVlanVlanTCMapEntry ::=
   SEQUENCE
      {
      er1645v2PbbBGriMVVlanVlanTCMapActions
         VariableLengthTableActions,
      er1645v2PbbBGriMVVlanVlanTCMapGlobalIx
         GlobalIndex,
      er1645v2PbbBGriMVVlanVlanTCMapTableIx
         TableIndex,
      er1645v2PbbBGriMVVlanVlanTCMapStartTos
         INTEGER,
      er1645v2PbbBGriMVVlanVlanTCMapEndTos
         INTEGER,
      er1645v2PbbBGriMVVlanVlanTCMapCos
         INTEGER
      }

er1645v2PbbBGriMVVlanVlanTCMapActions OBJECT-TYPE
   SYNTAX      VariableLengthTableActions
   MAX-ACCESS  read-write
   STATUS      current
   DESCRIPTION
      "By way of this field, some manipulations
       on this table may be performed."
   ::= {er1645v2PbbBGriMVVlanVlanTCMapEntry 2}

er1645v2PbbBGriMVVlanVlanTCMapGlobalIx OBJECT-TYPE
   SYNTAX      GlobalIndex
   MAX-ACCESS  not-accessible
   STATUS      current
   DESCRIPTION
      "The value of the tlsCntTreeGlobalIndex of the MANAGED OBJECT."
   ::= {er1645v2PbbBGriMVVlanVlanTCMapEntry 10}

er1645v2PbbBGriMVVlanVlanTCMapTableIx OBJECT-TYPE
   SYNTAX      TableIndex
   MAX-ACCESS  not-accessible
   STATUS      current
   DESCRIPTION
      ""
   ::= {er1645v2PbbBGriMVVlanVlanTCMapEntry 11}

er1645v2PbbBGriMVVlanVlanTCMapStartTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: pbbBridgeGroup.editConf.vlan.vlan.tosCosMap.startTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2PbbBGriMVVlanVlanTCMapEntry 16777216}

er1645v2PbbBGriMVVlanVlanTCMapEndTos OBJECT-TYPE
   SYNTAX      INTEGER
               {
               cs1 (32),
               cs2 (64),
               cs3 (96),
               cs4 (128),
               cs5 (160),
               cs6 (192),
               cs7 (224),
               af11 (40),
               af12 (48),
               af13 (56),
               af21 (72),
               af22 (80),
               af23 (88),
               af31 (104),
               af32 (112),
               af33 (120),
               af41 (136),
               af42 (144),
               af43 (152),
               ef (184),
               nonIp (256)
               }
   MAX-ACCESS  read-write
   STATUS      current
   DESCRIPTION
      "Path: pbbBridgeGroup.editConf.vlan.vlan.tosCosMap.endTos

       Possibilities:
               cs1   (32)
               cs2   (64)
               cs3   (96)
               cs4   (128)
               cs5   (160)
               cs6   (192)
               cs7   (224)
               af11   (40)
               af12   (48)
               af13   (56)
               af21   (72)
               af22   (80)
               af23   (88)
               af31   (104)
               af32   (112)
               af33   (120)
               af41   (136)
               af42   (144)
               af43   (152)
               ef   (184)
               nonIp   (256)"
   ::= {er1645v2PbbBGriMVVlanVlanTCMapEntry 33554432}

er1645v2PbbBGriMVVlanVlanTCMapCos OBJECT-TYPE
   SYNTAX      INTEGER
               {
               queueCosMap (8)
               }
   MAX-ACCESS  read-write
   STATUS      current
   DESCRIPTION
      "Path: pbbBridgeGroup.editConf.vlan.vlan.tosCosMap.cos

       Possibilities:
               queueCosMap   (8)"
   ::= {er1645v2PbbBGriMVVlanVlanTCMapEntry 50331648}

er1645v2PbbBGriMVVlanVlanArpStaticArp OBJECT-TYPE
   SYNTAX      SEQUENCE OF Er1645v2PbbBGriMVVlanVlanArpStaticArpEntry
   MAX-ACCESS  not-accessible
   STATUS      current
   DESCRIPTION
      ""
   ::= {er1645v2PbbBGriMVVlan 235275008}

er1645v2PbbBGriMVVlanVlanArpStaticArpEntry OBJECT-TYPE
   SYNTAX      Er1645v2PbbBGriMVVlanVlanArpStaticArpEntry
   MAX-ACCESS  not-accessible
   STATUS      current
   DESCRIPTION
      ""
   INDEX      { er1645v2PbbBGriMVVlanVlanArpStaticArpGlobalIx,
                er1645v2PbbBGriMVVlanTableIx,
                er1645v2PbbBGriMVVlanVlanArpStaticArpTableIx }
   ::= {er1645v2PbbBGriMVVlanVlanArpStaticArp 1}

Er1645v2PbbBGriMVVlanVlanArpStaticArpEntry ::=
   SEQUENCE
      {
      er1645v2PbbBGriMVVlanVlanArpStaticArpActions
         VariableLengthTableActions,
      er1645v2PbbBGriMVVlanVlanArpStaticArpGlobalIx
         GlobalIndex,
      er1645v2PbbBGriMVVlanVlanArpStaticArpTableIx
         TableIndex,
      er1645v2PbbBGriMVVlanVlanArpStaticArpMacAddress
         OCTET STRING,
      er1645v2PbbBGriMVVlanVlanArpStaticArpIpAddress
         IpAddress
      }

er1645v2PbbBGriMVVlanVlanArpStaticArpActions OBJECT-TYPE
   SYNTAX      VariableLengthTableActions
   MAX-ACCESS  read-write
   STATUS      current
   DESCRIPTION
      "By way of this field, some manipulations
       on this table may be performed."
   ::= {er1645v2PbbBGriMVVlanVlanArpStaticArpEntry 2}

er1645v2PbbBGriMVVlanVlanArpStaticArpGlobalIx OBJECT-TYPE
   SYNTAX      GlobalIndex
   MAX-ACCESS  not-accessible
   STATUS      current
   DESCRIPTION
      "The value of the tlsCntTreeGlobalIndex of the MANAGED OBJECT."
   ::= {er1645v2PbbBGriMVVlanVlanArpStaticArpEntry 10}

er1645v2PbbBGriMVVlanVlanArpStaticArpTableIx OBJECT-TYPE
   SYNTAX      TableIndex
   MAX-ACCESS  not-accessible
   STATUS      current
   DESCRIPTION
      ""
   ::= {er1645v2PbbBGriMVVlanVlanArpStaticArpEntry 11}

er1645v2PbbBGriMVVlanVlanArpStaticArpMacAddress OBJECT-TYPE
   SYNTAX      OCTET STRING
   MAX-ACCESS  read-write
   STATUS      current
   DESCRIPTION
      "Path: pbbBridgeGroup.editConf.vlan.vlan.arp.staticArp.macAddress

       MAC address."
   ::= {er1645v2PbbBGriMVVlanVlanArpStaticArpEntry 16777216}

er1645v2PbbBGriMVVlanVlanArpStaticArpIpAddress OBJECT-TYPE
   SYNTAX      IpAddress
   MAX-ACCESS  read-write
   STATUS      current
   DESCRIPTION
      "Path: pbbBridgeGroup.editConf.vlan.vlan.arp.staticArp.ipAddress"
   ::= {er1645v2PbbBGriMVVlanVlanArpStaticArpEntry 33554432}


er1645v2PbbBGriMVPppOE OBJECT IDENTIFIER ::= {er1645v2PbbBGriMV 80}

er1645v2PbbBGriMVPppOESSCTable OBJECT-TYPE
   SYNTAX      SEQUENCE OF Er1645v2PbbBGriMVPppOEEntry
   MAX-ACCESS  not-accessible
   STATUS      current
   DESCRIPTION
      ""
   ::= {er1645v2PbbBGriMVPppOE 1}

er1645v2PbbBGriMVPppOEEntry OBJECT-TYPE
   SYNTAX      Er1645v2PbbBGriMVPppOEEntry
   MAX-ACCESS  not-accessible
   STATUS      current
   DESCRIPTION
      ""
   INDEX      { er1645v2PbbBGriMVPppOEGlobalIx,
                er1645v2PbbBGriMVPppOETableIx }
   ::= {er1645v2PbbBGriMVPppOESSCTable 1}

Er1645v2PbbBGriMVPppOEEntry ::=
   SEQUENCE
      {
      er1645v2PbbBGriMVPppOEActions
         VariableLengthTableActions,
      er1645v2PbbBGriMVPppOEGlobalIx
         GlobalIndex,
      er1645v2PbbBGriMVPppOETableIx
         TableIndex,
      er1645v2PbbBGriMVPppOEName
         DisplayString,
      er1645v2PbbBGriMVPppOERemark
         DisplayString,
      er1645v2PbbBGriMVPppOEAdminStatus
         INTEGER,
      er1645v2PbbBGriMVPppOEMode
         INTEGER,
      er1645v2PbbBGriMVPppOEIpVrfRouter
         DisplayString,
      er1645v2PbbBGriMVPppOEIpAdr
         IpAddress,
      er1645v2PbbBGriMVPppOEIpNetm
         IpAddress,
      er1645v2PbbBGriMVPppOEIpSNetName
         INTEGER,
      er1645v2PbbBGriMVPppOEIpSNetCust
         DisplayString,
      er1645v2PbbBGriMVPppOEIpRem
         IpAddress,
      er1645v2PbbBGriMVPppOEIpUnnumbered
         DisplayString,
      er1645v2PbbBGriMVPppOEIpGwPref
         Integer32,
      er1645v2PbbBGriMVPppOEIpRsn
         INTEGER,
      er1645v2PbbBGriMVPppOEIpMtu
         Integer32,
      er1645v2PbbBGriMVPppOEIpMssAdjust
         INTEGER,
      er1645v2PbbBGriMVPppOEIpRipMetric
         Integer32,
      er1645v2PbbBGriMVPppOEIpRipMetricOut
         Integer32,
      er1645v2PbbBGriMVPppOEIpRipMode
         INTEGER,
      er1645v2PbbBGriMVPppOEIpRipTxVer
         INTEGER,
      er1645v2PbbBGriMVPppOEIpRipRxVer
         INTEGER,
      er1645v2PbbBGriMVPppOEIpRipSplitH
         INTEGER,
      er1645v2PbbBGriMVPppOEIpRipAuth
         INTEGER,
      er1645v2PbbBGriMVPppOEIpRipFilter
         DisplayString,
      er1645v2PbbBGriMVPppOEIpRipFilterIn
         DisplayString,
      er1645v2PbbBGriMVPppOEIpRipClearNextHop
         INTEGER,
      er1645v2PbbBGriMVPppOEIpAccPol
         DisplayString,
      er1645v2PbbBGriMVPppOEIpAB
         DisplayString,
      er1645v2PbbBGriMVPppOEIpMA
         INTEGER,
      er1645v2PbbBGriMVPppOEIpMF
         Integer32,
      er1645v2PbbBGriMVPppOEIpDB
         INTEGER,
      er1645v2PbbBGriMVPppOEIpIR
         INTEGER,
      er1645v2PbbBGriMVPppOEIpIgmp
         INTEGER,
      er1645v2PbbBGriMVPppOEIpNN
         DisplayString,
      er1645v2PbbBGriMVPppOEIpPimMode
         INTEGER,
      er1645v2PbbBGriMVPppOEIpPimDrPriority
         Counter32,
      er1645v2PbbBGriMVPppOEIpPimHelloTime
         TimeTicks,
      er1645v2PbbBGriMVPppOEIpPimPropagationDelay
         TimeTicks,
      er1645v2PbbBGriMVPppOEIpPimOverrideInterval
         TimeTicks,
      er1645v2PbbBGriMVPppOEIpPimBsrBorder
         INTEGER,
      er1645v2PbbBGriMVPppOEIpPimTtlThreshold
         Integer32,
      er1645v2PbbBGriMVPppOEIpIMNetworkUnreachable
         INTEGER,
      er1645v2PbbBGriMVPppOEIpIMHostUnreachable
         INTEGER,
      er1645v2PbbBGriMVPppOEIpIMProtocolUnreachable
         INTEGER,
      er1645v2PbbBGriMVPppOEIpIMPortUnreachable
         INTEGER,
      er1645v2PbbBGriMVPppOEIpIMMtuExceeded
         INTEGER,
      er1645v2PbbBGriMVPppOEIpIMAdminProhibited
         INTEGER,
      er1645v2PbbBGriMVPppOEIpIMTtlExceeded
         INTEGER,
      er1645v2PbbBGriMVPppOEIpIMRedirect
         INTEGER,
      er1645v2PbbBGriMVPppOEIpV6VrfRouter
         DisplayString,
      er1645v2PbbBGriMVPppOEIpV6AddrAutoConfigNrDupAddrDetects
         Integer32,
      er1645v2PbbBGriMVPppOEIpV6AddrAutoConfigAcceptRa
         INTEGER,
      er1645v2PbbBGriMVPppOEIpV6AddrAutoConfigAcceptRaRdnss
         INTEGER,
      er1645v2PbbBGriMVPppOEIpV6AddrAutoConfigAcceptRaDnssl
         INTEGER,
      er1645v2PbbBGriMVPppOEIpV6DefaultRoute
         INTEGER,
      er1645v2PbbBGriMVPppOEIpV6RaSend
         INTEGER,
      er1645v2PbbBGriMVPppOEIpV6RaMinInterval
         TimeTicks,
      er1645v2PbbBGriMVPppOEIpV6RaMaxInterval
         TimeTicks,
      er1645v2PbbBGriMVPppOEIpV6RaManagedFlag
         INTEGER,
      er1645v2PbbBGriMVPppOEIpV6RaOtherConfFlag
         INTEGER,
      er1645v2PbbBGriMVPppOEIpV6RaLinkMtu
         Integer32,
      er1645v2PbbBGriMVPppOEIpV6RaReachableTime
         TimeTicks,
      er1645v2PbbBGriMVPppOEIpV6RaRetransmitTime
         TimeTicks,
      er1645v2PbbBGriMVPppOEIpV6RaHopLimit
         Integer32,
      er1645v2PbbBGriMVPppOEIpV6RaDefaultLifeTime
         TimeTicks,
      er1645v2PbbBGriMVPppOEIpV6RaDnsOptionsRdnssLifeTime
         TimeTicks,
      er1645v2PbbBGriMVPppOEIpV6RaDnsOptionsRdnssImportServers
         INTEGER,
      er1645v2PbbBGriMVPppOEIpV6RaDnsOptionsDnsslLifeTime
         TimeTicks,
      er1645v2PbbBGriMVPppOEIpV6RaDnsOptionsDnsslImportDomains
         INTEGER,
      er1645v2PbbBGriMVPppOEIpV6RsSend
         INTEGER,
      er1645v2PbbBGriMVPppOEIpV6RsMaxRandomDelay
         TimeTicks,
      er1645v2PbbBGriMVPppOEIpV6RsInterval
         TimeTicks,
      er1645v2PbbBGriMVPppOEIpV6RsMaxSolicitations
         Integer32,
      er1645v2PbbBGriMVPppOEIpV6TrafficPolicyInbound
         DisplayString,
      er1645v2PbbBGriMVPppOEIpV6TrafficPolicyOutbound
         DisplayString,
      er1645v2PbbBGriMVPppOEIpV6FirewallZone
         DisplayString,
      er1645v2PbbBGriMVPppOEIpV6DhcpClientAddrAC
         INTEGER,
      er1645v2PbbBGriMVPppOEIpV6DhcpClientPrDelMode
         INTEGER,
      er1645v2PbbBGriMVPppOEIpV6DhcpClientPrDelPool
         DisplayString,
      er1645v2PbbBGriMVPppOEIpV6DhcpClientPrDelPdExclOpt
         INTEGER,
      er1645v2PbbBGriMVPppOEIpV6DhcpClientDnsServerPref
         Integer32,
      er1645v2PbbBGriMVPppOEIpV6DhcpClientRapidCommit
         INTEGER,
      er1645v2PbbBGriMVPppOEIpV6DhcpClientTimersSolTimeOut
         TimeTicks,
      er1645v2PbbBGriMVPppOEIpV6DhcpClientTimersSolMaxRt
         TimeTicks,
      er1645v2PbbBGriMVPppOEIpV6DhcpClientTimersInfoRefresh
         TimeTicks,
      er1645v2PbbBGriMVPppOEIpV6DhcpServerMode
         INTEGER,
      er1645v2PbbBGriMVPppOEIpV6DhcpServerPreference
         Integer32,
      er1645v2PbbBGriMVPppOEIpV6DhcpServerPool
         DisplayString,
      er1645v2PbbBGriMVPppOEIpV6DhcpServerRapidCommit
         INTEGER,
      er1645v2PbbBGriMVPppOEIpV6DhcpServerTimersInfoRefresh
         TimeTicks,
      er1645v2PbbBGriMVPppOEIpV6DhcpRelayMode
         INTEGER,
      er1645v2PbbBGriMVPppOEIpV6SendRedirect
         INTEGER,
      er1645v2PbbBGriMVPppOEIpV6LinkMtu
         Integer32,
      er1645v2PbbBGriMVPppOEIpV6InterfaceId
         OCTET STRING,
      er1645v2PbbBGriMVPppOEIpV6MF
         Integer32,
      er1645v2PbbBGriMVPppOEIpV6IcmpMessagesNoRoute
         INTEGER,
      er1645v2PbbBGriMVPppOEIpV6IcmpMessagesBeyondScope
         INTEGER,
      er1645v2PbbBGriMVPppOEIpV6IcmpMessagesAddressUnreachable
         INTEGER,
      er1645v2PbbBGriMVPppOEIpV6IcmpMessagesPortUnreachable
         INTEGER,
      er1645v2PbbBGriMVPppOEIpV6IcmpMessagesPacketTooBig
         INTEGER,
      er1645v2PbbBGriMVPppOEIpV6IcmpMessagesHopLimitExceeded
         INTEGER,
      er1645v2PbbBGriMVPppOEIpV6IcmpMessagesFragTimeExceeded
         INTEGER,
      er1645v2PbbBGriMVPppOEIpV6IcmpMessagesHeaderFieldErr
         INTEGER,
      er1645v2PbbBGriMVPppOEIpV6IcmpMessagesOptionUnrecognized
         INTEGER,
      er1645v2PbbBGriMVPppOEIpV6IcmpMessagesRedirect
         INTEGER,
      er1645v2PbbBGriMVPppOEPppLnkMOperation
         INTEGER,
      er1645v2PbbBGriMVPppOEPppLnkMInterval
         TimeTicks,
      er1645v2PbbBGriMVPppOEPppLnkMRepTimeOut
         TimeTicks,
      er1645v2PbbBGriMVPppOEPppLnkMFailsPrmt
         Integer32,
      er1645v2PbbBGriMVPppOEPppAuthentication
         INTEGER,
      er1645v2PbbBGriMVPppOEPppAuthenPeriod
         TimeTicks,
      er1645v2PbbBGriMVPppOEPppSessionName
         DisplayString,
      er1645v2PbbBGriMVPppOEPppSessionSecret
         DisplayString,
      er1645v2PbbBGriMVPppOEPppEncModeSessionSecret
         INTEGER,
      er1645v2PbbBGriMVPppOEPppEncSessionSecret
         DisplayString,
      er1645v2PbbBGriMVPppOEPppServiceName
         DisplayString
      }

er1645v2PbbBGriMVPppOEActions OBJECT-TYPE
   SYNTAX      VariableLengthTableActions
   MAX-ACCESS  read-write
   STATUS      current
   DESCRIPTION
      "By way of this field, some manipulations
       on this table may be performed."
   ::= {er1645v2PbbBGriMVPppOEEntry 2}

er1645v2PbbBGriMVPppOEGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEEntry 10}

er1645v2PbbBGriMVPppOETableIx OBJECT-TYPE
   SYNTAX      TableIndex
   MAX-ACCESS  not-accessible
   STATUS      current
   DESCRIPTION
      ""
   ::= {er1645v2PbbBGriMVPppOEEntry 11}

er1645v2PbbBGriMVPppOEName OBJECT-TYPE
   SYNTAX      DisplayString
   MAX-ACCESS  read-write
   STATUS      current
   DESCRIPTION
      "Path: pbbBridgeGroup.editConf.pppoEClient.name"
   ::= {er1645v2PbbBGriMVPppOEEntry 16777216}

er1645v2PbbBGriMVPppOERemark OBJECT-TYPE
   SYNTAX      DisplayString
   MAX-ACCESS  read-write
   STATUS      current
   DESCRIPTION
      "Path: pbbBridgeGroup.editConf.pppoEClient.remark"
   ::= {er1645v2PbbBGriMVPppOEEntry 1157627904}

er1645v2PbbBGriMVPppOEAdminStatus OBJECT-TYPE
   SYNTAX      INTEGER
               {
               up (1),
               down (2)
               }
   MAX-ACCESS  read-write
   STATUS      current
   DESCRIPTION
      "Path: pbbBridgeGroup.editConf.pppoEClient.adminStatus

       Possibilities:
               up   (1)
               down   (2)"
   ::= {er1645v2PbbBGriMVPppOEEntry 33554432}

er1645v2PbbBGriMVPppOEMode OBJECT-TYPE
   SYNTAX      INTEGER
               {
               routing (1),
               multilink (8),
               ipV6 (16),
               ipV6ipV4 (17)
               }
   MAX-ACCESS  read-write
   STATUS      current
   DESCRIPTION
      "Path: pbbBridgeGroup.editConf.pppoEClient.mode

       Possibilities:
               routing   (1)
               multilink   (8)
               ipV6   (16)
               ipV6/ipV4   (17)"
   ::= {er1645v2PbbBGriMVPppOEEntry 67108864}

er1645v2PbbBGriMVPppOEIpVrfRouter OBJECT-TYPE
   SYNTAX      DisplayString
   MAX-ACCESS  read-write
   STATUS      current
   DESCRIPTION
      "Path: pbbBridgeGroup.editConf.pppoEClient.ip.vrfRouter"
   ::= {er1645v2PbbBGriMVPppOEEntry 53215232}

er1645v2PbbBGriMVPppOEIpAdr OBJECT-TYPE
   SYNTAX      IpAddress
   MAX-ACCESS  read-write
   STATUS      current
   DESCRIPTION
      "Path: pbbBridgeGroup.editConf.pppoEClient.ip.address"
   ::= {er1645v2PbbBGriMVPppOEEntry 58261504}

er1645v2PbbBGriMVPppOEIpNetm OBJECT-TYPE
   SYNTAX      IpAddress
   MAX-ACCESS  read-write
   STATUS      current
   DESCRIPTION
      "Path: pbbBridgeGroup.editConf.pppoEClient.ip.netMask"
   ::= {er1645v2PbbBGriMVPppOEEntry 58392576}

er1645v2PbbBGriMVPppOEIpSNetName OBJECT-TYPE
   SYNTAX      INTEGER
               {
               slOPTg (0),
               corp (2),
               dmz (3),
               internet (1)
               }
   MAX-ACCESS  read-write
   STATUS      current
   DESCRIPTION
      "Path: pbbBridgeGroup.editConf.pppoEClient.ip.sNet.name

       Possibilities:
               <OPT>   (0)
               corp   (2)
               dmz   (3)
               internet   (1)"
   ::= {er1645v2PbbBGriMVPppOEEntry 53674240}

er1645v2PbbBGriMVPppOEIpSNetCust OBJECT-TYPE
   SYNTAX      DisplayString
   MAX-ACCESS  read-write
   STATUS      current
   DESCRIPTION
      "Path: pbbBridgeGroup.editConf.pppoEClient.ip.sNet.custom"
   ::= {er1645v2PbbBGriMVPppOEEntry 53674496}

er1645v2PbbBGriMVPppOEIpRem OBJECT-TYPE
   SYNTAX      IpAddress
   MAX-ACCESS  read-write
   STATUS      current
   DESCRIPTION
      "Path: pbbBridgeGroup.editConf.pppoEClient.ip.remote"
   ::= {er1645v2PbbBGriMVPppOEEntry 58458112}

er1645v2PbbBGriMVPppOEIpUnnumbered OBJECT-TYPE
   SYNTAX      DisplayString
   MAX-ACCESS  read-write
   STATUS      current
   DESCRIPTION
      "Path: pbbBridgeGroup.editConf.pppoEClient.ip.unnumbered"
   ::= {er1645v2PbbBGriMVPppOEEntry 52625408}

er1645v2PbbBGriMVPppOEIpGwPref OBJECT-TYPE
   SYNTAX      Integer32
   MAX-ACCESS  read-write
   STATUS      current
   DESCRIPTION
      "Path: pbbBridgeGroup.editConf.pppoEClient.ip.gatewayPreference"
   ::= {er1645v2PbbBGriMVPppOEEntry 52690944}

er1645v2PbbBGriMVPppOEIpRsn OBJECT-TYPE
   SYNTAX      INTEGER
               {
               disabled (0),
               enabled (1)
               }
   MAX-ACCESS  read-write
   STATUS      current
   DESCRIPTION
      "Path: pbbBridgeGroup.editConf.pppoEClient.ip.requestSubnet

       Possibilities:
               disabled   (0)
               enabled   (1)"
   ::= {er1645v2PbbBGriMVPppOEEntry 56688640}

er1645v2PbbBGriMVPppOEIpMtu OBJECT-TYPE
   SYNTAX      Integer32
   MAX-ACCESS  read-write
   STATUS      current
   DESCRIPTION
      "Path: pbbBridgeGroup.editConf.pppoEClient.ip.mtu"
   ::= {er1645v2PbbBGriMVPppOEEntry 52953088}

er1645v2PbbBGriMVPppOEIpMssAdjust OBJECT-TYPE
   SYNTAX      INTEGER
               {
               disabled (0),
               auto (65536)
               }
   MAX-ACCESS  read-write
   STATUS      current
   DESCRIPTION
      "Path: pbbBridgeGroup.editConf.pppoEClient.ip.mssAdjust

       Possibilities:
               disabled   (0)
               auto   (65536)"
   ::= {er1645v2PbbBGriMVPppOEEntry 53280768}

er1645v2PbbBGriMVPppOEIpRipMetric OBJECT-TYPE
   SYNTAX      Integer32
   MAX-ACCESS  read-write
   STATUS      current
   DESCRIPTION
      "Path: pbbBridgeGroup.editConf.pppoEClient.ip.rip.metric"
   ::= {er1645v2PbbBGriMVPppOEEntry 51712768}

er1645v2PbbBGriMVPppOEIpRipMetricOut OBJECT-TYPE
   SYNTAX      Integer32
   MAX-ACCESS  read-write
   STATUS      current
   DESCRIPTION
      "Path: pbbBridgeGroup.editConf.pppoEClient.ip.rip.metricOut"
   ::= {er1645v2PbbBGriMVPppOEEntry 51713024}

er1645v2PbbBGriMVPppOEIpRipMode OBJECT-TYPE
   SYNTAX      INTEGER
               {
               disabled (0),
               passive (1),
               active (2)
               }
   MAX-ACCESS  read-write
   STATUS      current
   DESCRIPTION
      "Path: pbbBridgeGroup.editConf.pppoEClient.ip.rip.mode

       Possibilities:
               disabled   (0)
               passive   (1)
               active   (2)"
   ::= {er1645v2PbbBGriMVPppOEEntry 51713280}

er1645v2PbbBGriMVPppOEIpRipTxVer OBJECT-TYPE
   SYNTAX      INTEGER
               {
               rip1 (0),
               rip2 (1),
               rip1mcompatible (2)
               }
   MAX-ACCESS  read-write
   STATUS      current
   DESCRIPTION
      "Path: pbbBridgeGroup.editConf.pppoEClient.ip.rip.txVersion

       Possibilities:
               rip1   (0)
               rip2   (1)
               rip1-compatible   (2)"
   ::= {er1645v2PbbBGriMVPppOEEntry 51716864}

er1645v2PbbBGriMVPppOEIpRipRxVer OBJECT-TYPE
   SYNTAX      INTEGER
               {
               rip1only (0),
               rip2only (1),
               rip12 (2)
               }
   MAX-ACCESS  read-write
   STATUS      current
   DESCRIPTION
      "Path: pbbBridgeGroup.editConf.pppoEClient.ip.rip.rxVersion

       Possibilities:
               rip1only   (0)
               rip2only   (1)
               rip1&2   (2)"
   ::= {er1645v2PbbBGriMVPppOEEntry 51717120}

er1645v2PbbBGriMVPppOEIpRipSplitH OBJECT-TYPE
   SYNTAX      INTEGER
               {
               disabled (0),
               enabled (1),
               poisonedReverse (2)
               }
   MAX-ACCESS  read-write
   STATUS      current
   DESCRIPTION
      "Path: pbbBridgeGroup.editConf.pppoEClient.ip.rip.splitHorizon

       Possibilities:
               disabled   (0)
               enabled   (1)
               poisonedReverse   (2)"
   ::= {er1645v2PbbBGriMVPppOEEntry 51713792}

er1645v2PbbBGriMVPppOEIpRipAuth OBJECT-TYPE
   SYNTAX      INTEGER
               {
               disabled (0),
               texts (1),
               md5 (2)
               }
   MAX-ACCESS  read-write
   STATUS      current
   DESCRIPTION
      "Path: pbbBridgeGroup.editConf.pppoEClient.ip.rip.authentication

       Possibilities:
               disabled   (0)
               text    (1)
               md5   (2)"
   ::= {er1645v2PbbBGriMVPppOEEntry 51712512}

er1645v2PbbBGriMVPppOEIpRipFilter OBJECT-TYPE
   SYNTAX      DisplayString
   MAX-ACCESS  read-write
   STATUS      current
   DESCRIPTION
      "Path: pbbBridgeGroup.editConf.pppoEClient.ip.rip.filter"
   ::= {er1645v2PbbBGriMVPppOEEntry 51716096}

er1645v2PbbBGriMVPppOEIpRipFilterIn OBJECT-TYPE
   SYNTAX      DisplayString
   MAX-ACCESS  read-write
   STATUS      current
   DESCRIPTION
      "Path: pbbBridgeGroup.editConf.pppoEClient.ip.rip.filterIn"
   ::= {er1645v2PbbBGriMVPppOEEntry 51716352}

er1645v2PbbBGriMVPppOEIpRipClearNextHop OBJECT-TYPE
   SYNTAX      INTEGER
               {
               disabled (0),
               enabled (1)
               }
   MAX-ACCESS  read-write
   STATUS      current
   DESCRIPTION
      "Path: pbbBridgeGroup.editConf.pppoEClient.ip.rip.clearNextHop

       Possibilities:
               disabled   (0)
               enabled   (1)"
   ::= {er1645v2PbbBGriMVPppOEEntry 51708416}

er1645v2PbbBGriMVPppOEIpAccPol OBJECT-TYPE
   SYNTAX      DisplayString
   MAX-ACCESS  read-write
   STATUS      current
   DESCRIPTION
      "Path: pbbBridgeGroup.editConf.pppoEClient.ip.accessPolicy"
   ::= {er1645v2PbbBGriMVPppOEEntry 53084160}

er1645v2PbbBGriMVPppOEIpAB OBJECT-TYPE
   SYNTAX      DisplayString
   MAX-ACCESS  read-write
   STATUS      current
   DESCRIPTION
      "Path: pbbBridgeGroup.editConf.pppoEClient.ip.trafficPolicy"
   ::= {er1645v2PbbBGriMVPppOEEntry 51249152}

er1645v2PbbBGriMVPppOEIpMA OBJECT-TYPE
   SYNTAX      INTEGER
               {
               disabled (0),
               enabled (1)
               }
   MAX-ACCESS  read-write
   STATUS      current
   DESCRIPTION
      "Path: pbbBridgeGroup.editConf.pppoEClient.ip.mgmtAccess

       Possibilities:
               disabled   (0)
               enabled   (1)"
   ::= {er1645v2PbbBGriMVPppOEEntry 51380224}

er1645v2PbbBGriMVPppOEIpMF OBJECT-TYPE
   SYNTAX      Integer32
   MAX-ACCESS  read-write
   STATUS      current
   DESCRIPTION
      "Path: pbbBridgeGroup.editConf.pppoEClient.ip.mgmtFilter

       Bit meanings:
               bit 0 = cms2,
               bit 4 = snmp,
               bit 5 = tftp,
               bit 6 = ftp,
               bit 7 = telnet,
               bit 8 = ssh,
               bit 9 = snmpv3,
               bit 11 = http,
               bit 19 = https,
               bit 25 = dns"
   ::= {er1645v2PbbBGriMVPppOEEntry 51445760}

er1645v2PbbBGriMVPppOEIpDB OBJECT-TYPE
   SYNTAX      INTEGER
               {
               disabled (0),
               enabled (1)
               }
   MAX-ACCESS  read-write
   STATUS      current
   DESCRIPTION
      "Path: pbbBridgeGroup.editConf.pppoEClient.ip.directedBroadcasts

       Possibilities:
               disabled   (0)
               enabled   (1)"
   ::= {er1645v2PbbBGriMVPppOEEntry 51773440}

er1645v2PbbBGriMVPppOEIpIR OBJECT-TYPE
   SYNTAX      INTEGER
               {
               disabled (0),
               enabled (1)
               }
   MAX-ACCESS  read-write
   STATUS      current
   DESCRIPTION
      "Path: pbbBridgeGroup.editConf.pppoEClient.ip.icmpRedirects

       Possibilities:
               disabled   (0)
               enabled   (1)"
   ::= {er1645v2PbbBGriMVPppOEEntry 52035584}

er1645v2PbbBGriMVPppOEIpIgmp OBJECT-TYPE
   SYNTAX      INTEGER
               {
               disabled (0),
               proxy (1),
               router (2),
               v3Router (5)
               }
   MAX-ACCESS  read-write
   STATUS      current
   DESCRIPTION
      "Path: pbbBridgeGroup.editConf.pppoEClient.ip.igmp

       Possibilities:
               disabled   (0)
               proxy   (1)
               router   (2)
               v3Router   (5)"
   ::= {er1645v2PbbBGriMVPppOEEntry 52428800}

er1645v2PbbBGriMVPppOEIpNN OBJECT-TYPE
   SYNTAX      DisplayString
   MAX-ACCESS  read-write
   STATUS      current
   DESCRIPTION
      "Path: pbbBridgeGroup.editConf.pppoEClient.ip.nat"
   ::= {er1645v2PbbBGriMVPppOEEntry 52101120}

er1645v2PbbBGriMVPppOEIpPimMode OBJECT-TYPE
   SYNTAX      INTEGER
               {
               disabled (0),
               sparse (1),
               passive (2)
               }
   MAX-ACCESS  read-write
   STATUS      current
   DESCRIPTION
      "Path: pbbBridgeGroup.editConf.pppoEClient.ip.pim.mode

       Possibilities:
               disabled   (0)
               sparse   (1)
               passive   (2)"
   ::= {er1645v2PbbBGriMVPppOEEntry 53346560}

er1645v2PbbBGriMVPppOEIpPimDrPriority OBJECT-TYPE
   SYNTAX      Counter32
   MAX-ACCESS  read-write
   STATUS      current
   DESCRIPTION
      "Path: pbbBridgeGroup.editConf.pppoEClient.ip.pim.drPriority

       32 bit unsigned wrappable counter."
   ::= {er1645v2PbbBGriMVPppOEEntry 53346816}

er1645v2PbbBGriMVPppOEIpPimHelloTime OBJECT-TYPE
   SYNTAX      TimeTicks
   MAX-ACCESS  read-write
   STATUS      current
   DESCRIPTION
      "Path: pbbBridgeGroup.editConf.pppoEClient.ip.pim.helloTime

       Time in centi-second."
   ::= {er1645v2PbbBGriMVPppOEEntry 53347072}

er1645v2PbbBGriMVPppOEIpPimPropagationDelay OBJECT-TYPE
   SYNTAX      TimeTicks
   MAX-ACCESS  read-write
   STATUS      current
   DESCRIPTION
      "Path: pbbBridgeGroup.editConf.pppoEClient.ip.pim.propagationDelay

       Time in centi-second."
   ::= {er1645v2PbbBGriMVPppOEEntry 53347328}

er1645v2PbbBGriMVPppOEIpPimOverrideInterval OBJECT-TYPE
   SYNTAX      TimeTicks
   MAX-ACCESS  read-write
   STATUS      current
   DESCRIPTION
      "Path: pbbBridgeGroup.editConf.pppoEClient.ip.pim.overrideInterval

       Time in centi-second."
   ::= {er1645v2PbbBGriMVPppOEEntry 53347584}

er1645v2PbbBGriMVPppOEIpPimBsrBorder OBJECT-TYPE
   SYNTAX      INTEGER
               {
               disabled (0),
               enabled (1)
               }
   MAX-ACCESS  read-write
   STATUS      current
   DESCRIPTION
      "Path: pbbBridgeGroup.editConf.pppoEClient.ip.pim.bsrBorder

       Possibilities:
               disabled   (0)
               enabled   (1)"
   ::= {er1645v2PbbBGriMVPppOEEntry 53347840}

er1645v2PbbBGriMVPppOEIpPimTtlThreshold OBJECT-TYPE
   SYNTAX      Integer32
   MAX-ACCESS  read-write
   STATUS      current
   DESCRIPTION
      "Path: pbbBridgeGroup.editConf.pppoEClient.ip.pim.ttlThreshold"
   ::= {er1645v2PbbBGriMVPppOEEntry 53348096}

er1645v2PbbBGriMVPppOEIpIMNetworkUnreachable OBJECT-TYPE
   SYNTAX      INTEGER
               {
               disabled (0),
               enabled (1)
               }
   MAX-ACCESS  read-write
   STATUS      current
   DESCRIPTION
      "Path: pbbBridgeGroup.editConf.pppoEClient.ip.icmpMessages.networkUnreachable

       Possibilities:
               disabled   (0)
               enabled   (1)"
   ::= {er1645v2PbbBGriMVPppOEEntry 53412096}

er1645v2PbbBGriMVPppOEIpIMHostUnreachable OBJECT-TYPE
   SYNTAX      INTEGER
               {
               disabled (0),
               enabled (1)
               }
   MAX-ACCESS  read-write
   STATUS      current
   DESCRIPTION
      "Path: pbbBridgeGroup.editConf.pppoEClient.ip.icmpMessages.hostUnreachable

       Possibilities:
               disabled   (0)
               enabled   (1)"
   ::= {er1645v2PbbBGriMVPppOEEntry 53412352}

er1645v2PbbBGriMVPppOEIpIMProtocolUnreachable OBJECT-TYPE
   SYNTAX      INTEGER
               {
               disabled (0),
               enabled (1)
               }
   MAX-ACCESS  read-write
   STATUS      current
   DESCRIPTION
      "Path: pbbBridgeGroup.editConf.pppoEClient.ip.icmpMessages.protocolUnreachable

       Possibilities:
               disabled   (0)
               enabled   (1)"
   ::= {er1645v2PbbBGriMVPppOEEntry 53412608}

er1645v2PbbBGriMVPppOEIpIMPortUnreachable OBJECT-TYPE
   SYNTAX      INTEGER
               {
               disabled (0),
               enabled (1)
               }
   MAX-ACCESS  read-write
   STATUS      current
   DESCRIPTION
      "Path: pbbBridgeGroup.editConf.pppoEClient.ip.icmpMessages.portUnreachable

       Possibilities:
               disabled   (0)
               enabled   (1)"
   ::= {er1645v2PbbBGriMVPppOEEntry 53412864}

er1645v2PbbBGriMVPppOEIpIMMtuExceeded OBJECT-TYPE
   SYNTAX      INTEGER
               {
               disabled (0),
               enabled (1)
               }
   MAX-ACCESS  read-write
   STATUS      current
   DESCRIPTION
      "Path: pbbBridgeGroup.editConf.pppoEClient.ip.icmpMessages.mtuExceeded

       Possibilities:
               disabled   (0)
               enabled   (1)"
   ::= {er1645v2PbbBGriMVPppOEEntry 53413120}

er1645v2PbbBGriMVPppOEIpIMAdminProhibited OBJECT-TYPE
   SYNTAX      INTEGER
               {
               disabled (0),
               enabled (1)
               }
   MAX-ACCESS  read-write
   STATUS      current
   DESCRIPTION
      "Path: pbbBridgeGroup.editConf.pppoEClient.ip.icmpMessages.adminProhibited

       Possibilities:
               disabled   (0)
               enabled   (1)"
   ::= {er1645v2PbbBGriMVPppOEEntry 53413376}

er1645v2PbbBGriMVPppOEIpIMTtlExceeded OBJECT-TYPE
   SYNTAX      INTEGER
               {
               disabled (0),
               enabled (1)
               }
   MAX-ACCESS  read-write
   STATUS      current
   DESCRIPTION
      "Path: pbbBridgeGroup.editConf.pppoEClient.ip.icmpMessages.ttlExceeded

       Possibilities:
               disabled   (0)
               enabled   (1)"
   ::= {er1645v2PbbBGriMVPppOEEntry 53413632}

er1645v2PbbBGriMVPppOEIpIMRedirect OBJECT-TYPE
   SYNTAX      INTEGER
               {
               disabled (0),
               enabled (1)
               }
   MAX-ACCESS  read-write
   STATUS      current
   DESCRIPTION
      "Path: pbbBridgeGroup.editConf.pppoEClient.ip.icmpMessages.redirect

       Possibilities:
               disabled   (0)
               enabled   (1)"
   ::= {er1645v2PbbBGriMVPppOEEntry 53413888}

er1645v2PbbBGriMVPppOEIpV6VrfRouter OBJECT-TYPE
   SYNTAX      DisplayString
   MAX-ACCESS  read-write
   STATUS      current
   DESCRIPTION
      "Path: pbbBridgeGroup.editConf.pppoEClient.ipV6.vrfRouter"
   ::= {er1645v2PbbBGriMVPppOEEntry 704708608}

er1645v2PbbBGriMVPppOEIpV6AddrAutoConfigNrDupAddrDetects OBJECT-TYPE
   SYNTAX      Integer32
   MAX-ACCESS  read-write
   STATUS      current
   DESCRIPTION
      "Path: pbbBridgeGroup.editConf.pppoEClient.ipV6.addrAutoConfig.nrDupAddrDetects"
   ::= {er1645v2PbbBGriMVPppOEEntry 704905472}

er1645v2PbbBGriMVPppOEIpV6AddrAutoConfigAcceptRa OBJECT-TYPE
   SYNTAX      INTEGER
               {
               disabled (0),
               enabled (1)
               }
   MAX-ACCESS  read-write
   STATUS      current
   DESCRIPTION
      "Path: pbbBridgeGroup.editConf.pppoEClient.ipV6.addrAutoConfig.acceptRa

       Possibilities:
               disabled   (0)
               enabled   (1)"
   ::= {er1645v2PbbBGriMVPppOEEntry 704905728}

er1645v2PbbBGriMVPppOEIpV6AddrAutoConfigAcceptRaRdnss OBJECT-TYPE
   SYNTAX      INTEGER
               {
               disabled (0),
               enabled (1)
               }
   MAX-ACCESS  read-write
   STATUS      current
   DESCRIPTION
      "Path: pbbBridgeGroup.editConf.pppoEClient.ipV6.addrAutoConfig.acceptRaRdnss

       Possibilities:
               disabled   (0)
               enabled   (1)"
   ::= {er1645v2PbbBGriMVPppOEEntry 704905984}

er1645v2PbbBGriMVPppOEIpV6AddrAutoConfigAcceptRaDnssl OBJECT-TYPE
   SYNTAX      INTEGER
               {
               disabled (0),
               enabled (1)
               }
   MAX-ACCESS  read-write
   STATUS      current
   DESCRIPTION
      "Path: pbbBridgeGroup.editConf.pppoEClient.ipV6.addrAutoConfig.acceptRaDnssl

       Possibilities:
               disabled   (0)
               enabled   (1)"
   ::= {er1645v2PbbBGriMVPppOEEntry 704906240}

er1645v2PbbBGriMVPppOEIpV6DefaultRoute OBJECT-TYPE
   SYNTAX      INTEGER
               {
               disabled (0),
               enabled (1)
               }
   MAX-ACCESS  read-write
   STATUS      current
   DESCRIPTION
      "Path: pbbBridgeGroup.editConf.pppoEClient.ipV6.defaultRoute

       Possibilities:
               disabled   (0)
               enabled   (1)"
   ::= {er1645v2PbbBGriMVPppOEEntry 704970752}

er1645v2PbbBGriMVPppOEIpV6RaSend OBJECT-TYPE
   SYNTAX      INTEGER
               {
               disabled (0),
               enabled (1)
               }
   MAX-ACCESS  read-write
   STATUS      current
   DESCRIPTION
      "Path: pbbBridgeGroup.editConf.pppoEClient.ipV6.ra.send

       Possibilities:
               disabled   (0)
               enabled   (1)"
   ::= {er1645v2PbbBGriMVPppOEEntry 705036544}

er1645v2PbbBGriMVPppOEIpV6RaMinInterval OBJECT-TYPE
   SYNTAX      TimeTicks
   MAX-ACCESS  read-write
   STATUS      current
   DESCRIPTION
      "Path: pbbBridgeGroup.editConf.pppoEClient.ipV6.ra.minInterval

       Time in centi-second."
   ::= {er1645v2PbbBGriMVPppOEEntry 705036800}

er1645v2PbbBGriMVPppOEIpV6RaMaxInterval OBJECT-TYPE
   SYNTAX      TimeTicks
   MAX-ACCESS  read-write
   STATUS      current
   DESCRIPTION
      "Path: pbbBridgeGroup.editConf.pppoEClient.ipV6.ra.maxInterval

       Time in centi-second."
   ::= {er1645v2PbbBGriMVPppOEEntry 705037056}

er1645v2PbbBGriMVPppOEIpV6RaManagedFlag OBJECT-TYPE
   SYNTAX      INTEGER
               {
               disabled (0),
               enabled (1)
               }
   MAX-ACCESS  read-write
   STATUS      current
   DESCRIPTION
      "Path: pbbBridgeGroup.editConf.pppoEClient.ipV6.ra.managedFlag

       Possibilities:
               disabled   (0)
               enabled   (1)"
   ::= {er1645v2PbbBGriMVPppOEEntry 705037312}

er1645v2PbbBGriMVPppOEIpV6RaOtherConfFlag OBJECT-TYPE
   SYNTAX      INTEGER
               {
               disabled (0),
               enabled (1)
               }
   MAX-ACCESS  read-write
   STATUS      current
   DESCRIPTION
      "Path: pbbBridgeGroup.editConf.pppoEClient.ipV6.ra.otherConfFlag

       Possibilities:
               disabled   (0)
               enabled   (1)"
   ::= {er1645v2PbbBGriMVPppOEEntry 705037568}

er1645v2PbbBGriMVPppOEIpV6RaLinkMtu OBJECT-TYPE
   SYNTAX      Integer32
   MAX-ACCESS  read-write
   STATUS      current
   DESCRIPTION
      "Path: pbbBridgeGroup.editConf.pppoEClient.ipV6.ra.linkMtu"
   ::= {er1645v2PbbBGriMVPppOEEntry 705037824}

er1645v2PbbBGriMVPppOEIpV6RaReachableTime OBJECT-TYPE
   SYNTAX      TimeTicks
   MAX-ACCESS  read-write
   STATUS      current
   DESCRIPTION
      "Path: pbbBridgeGroup.editConf.pppoEClient.ipV6.ra.reachableTime

       Time in centi-second."
   ::= {er1645v2PbbBGriMVPppOEEntry 705038080}

er1645v2PbbBGriMVPppOEIpV6RaRetransmitTime OBJECT-TYPE
   SYNTAX      TimeTicks
   MAX-ACCESS  read-write
   STATUS      current
   DESCRIPTION
      "Path: pbbBridgeGroup.editConf.pppoEClient.ipV6.ra.retransmitTime

       Time in centi-second."
   ::= {er1645v2PbbBGriMVPppOEEntry 705038336}

er1645v2PbbBGriMVPppOEIpV6RaHopLimit OBJECT-TYPE
   SYNTAX      Integer32
   MAX-ACCESS  read-write
   STATUS      current
   DESCRIPTION
      "Path: pbbBridgeGroup.editConf.pppoEClient.ipV6.ra.hopLimit"
   ::= {er1645v2PbbBGriMVPppOEEntry 705038592}

er1645v2PbbBGriMVPppOEIpV6RaDefaultLifeTime OBJECT-TYPE
   SYNTAX      TimeTicks
   MAX-ACCESS  read-write
   STATUS      current
   DESCRIPTION
      "Path: pbbBridgeGroup.editConf.pppoEClient.ipV6.ra.defaultLifeTime

       Time in centi-second."
   ::= {er1645v2PbbBGriMVPppOEEntry 705038848}

er1645v2PbbBGriMVPppOEIpV6RaDnsOptionsRdnssLifeTime OBJECT-TYPE
   SYNTAX      TimeTicks
   MAX-ACCESS  read-write
   STATUS      current
   DESCRIPTION
      "Path: pbbBridgeGroup.editConf.pppoEClient.ipV6.ra.dnsOptions.rdnss.lifeTime

       Time in centi-second."
   ::= {er1645v2PbbBGriMVPppOEEntry 705039140}

er1645v2PbbBGriMVPppOEIpV6RaDnsOptionsRdnssImportServers OBJECT-TYPE
   SYNTAX      INTEGER
               {
               disabled (0),
               enabled (1)
               }
   MAX-ACCESS  read-write
   STATUS      current
   DESCRIPTION
      "Path: pbbBridgeGroup.editConf.pppoEClient.ipV6.ra.dnsOptions.rdnss.importServers

       Possibilities:
               disabled   (0)
               enabled   (1)"
   ::= {er1645v2PbbBGriMVPppOEEntry 705039148}

er1645v2PbbBGriMVPppOEIpV6RaDnsOptionsDnsslLifeTime OBJECT-TYPE
   SYNTAX      TimeTicks
   MAX-ACCESS  read-write
   STATUS      current
   DESCRIPTION
      "Path: pbbBridgeGroup.editConf.pppoEClient.ipV6.ra.dnsOptions.dnssl.lifeTime

       Time in centi-second."
   ::= {er1645v2PbbBGriMVPppOEEntry 705039172}

er1645v2PbbBGriMVPppOEIpV6RaDnsOptionsDnsslImportDomains OBJECT-TYPE
   SYNTAX      INTEGER
               {
               disabled (0),
               enabled (1)
               }
   MAX-ACCESS  read-write
   STATUS      current
   DESCRIPTION
      "Path: pbbBridgeGroup.editConf.pppoEClient.ipV6.ra.dnsOptions.dnssl.importDomains

       Possibilities:
               disabled   (0)
               enabled   (1)"
   ::= {er1645v2PbbBGriMVPppOEEntry 705039180}

er1645v2PbbBGriMVPppOEIpV6RsSend OBJECT-TYPE
   SYNTAX      INTEGER
               {
               disabled (0),
               enabled (1)
               }
   MAX-ACCESS  read-write
   STATUS      current
   DESCRIPTION
      "Path: pbbBridgeGroup.editConf.pppoEClient.ipV6.rs.send

       Possibilities:
               disabled   (0)
               enabled   (1)"
   ::= {er1645v2PbbBGriMVPppOEEntry 705954048}

er1645v2PbbBGriMVPppOEIpV6RsMaxRandomDelay OBJECT-TYPE
   SYNTAX      TimeTicks
   MAX-ACCESS  read-write
   STATUS      current
   DESCRIPTION
      "Path: pbbBridgeGroup.editConf.pppoEClient.ipV6.rs.maxRandomDelay

       Time in centi-second."
   ::= {er1645v2PbbBGriMVPppOEEntry 705954304}

er1645v2PbbBGriMVPppOEIpV6RsInterval OBJECT-TYPE
   SYNTAX      TimeTicks
   MAX-ACCESS  read-write
   STATUS      current
   DESCRIPTION
      "Path: pbbBridgeGroup.editConf.pppoEClient.ipV6.rs.interval

       Time in centi-second."
   ::= {er1645v2PbbBGriMVPppOEEntry 705954560}

er1645v2PbbBGriMVPppOEIpV6RsMaxSolicitations OBJECT-TYPE
   SYNTAX      Integer32
   MAX-ACCESS  read-write
   STATUS      current
   DESCRIPTION
      "Path: pbbBridgeGroup.editConf.pppoEClient.ipV6.rs.maxSolicitations"
   ::= {er1645v2PbbBGriMVPppOEEntry 705954816}

er1645v2PbbBGriMVPppOEIpV6TrafficPolicyInbound OBJECT-TYPE
   SYNTAX      DisplayString
   MAX-ACCESS  read-write
   STATUS      current
   DESCRIPTION
      "Path: pbbBridgeGroup.editConf.pppoEClient.ipV6.trafficPolicy.inbound"
   ::= {er1645v2PbbBGriMVPppOEEntry 705364224}

er1645v2PbbBGriMVPppOEIpV6TrafficPolicyOutbound OBJECT-TYPE
   SYNTAX      DisplayString
   MAX-ACCESS  read-write
   STATUS      current
   DESCRIPTION
      "Path: pbbBridgeGroup.editConf.pppoEClient.ipV6.trafficPolicy.outbound"
   ::= {er1645v2PbbBGriMVPppOEEntry 705364480}

er1645v2PbbBGriMVPppOEIpV6FirewallZone OBJECT-TYPE
   SYNTAX      DisplayString
   MAX-ACCESS  read-write
   STATUS      current
   DESCRIPTION
      "Path: pbbBridgeGroup.editConf.pppoEClient.ipV6.firewall.zone"
   ::= {er1645v2PbbBGriMVPppOEEntry 705429760}

er1645v2PbbBGriMVPppOEIpV6DhcpClientAddrAC OBJECT-TYPE
   SYNTAX      INTEGER
               {
               disabled (0),
               enabled (1)
               }
   MAX-ACCESS  read-write
   STATUS      current
   DESCRIPTION
      "Path: pbbBridgeGroup.editConf.pppoEClient.ipV6.dhcp.client.addrAutoConfig

       Possibilities:
               disabled   (0)
               enabled   (1)"
   ::= {er1645v2PbbBGriMVPppOEEntry 705307648}

er1645v2PbbBGriMVPppOEIpV6DhcpClientPrDelMode OBJECT-TYPE
   SYNTAX      INTEGER
               {
               disabled (0),
               enabled (1)
               }
   MAX-ACCESS  read-write
   STATUS      current
   DESCRIPTION
      "Path: pbbBridgeGroup.editConf.pppoEClient.ipV6.dhcp.client.pd.mode

       Possibilities:
               disabled   (0)
               enabled   (1)"
   ::= {er1645v2PbbBGriMVPppOEEntry 705308676}

er1645v2PbbBGriMVPppOEIpV6DhcpClientPrDelPool OBJECT-TYPE
   SYNTAX      DisplayString
   MAX-ACCESS  read-write
   STATUS      current
   DESCRIPTION
      "Path: pbbBridgeGroup.editConf.pppoEClient.ipV6.dhcp.client.pd.pool"
   ::= {er1645v2PbbBGriMVPppOEEntry 705308680}

er1645v2PbbBGriMVPppOEIpV6DhcpClientPrDelPdExclOpt OBJECT-TYPE
   SYNTAX      INTEGER
               {
               disabled (0),
               enabled (1)
               }
   MAX-ACCESS  read-write
   STATUS      current
   DESCRIPTION
      "Path: pbbBridgeGroup.editConf.pppoEClient.ipV6.dhcp.client.pd.pdExclOpt

       Possibilities:
               disabled   (0)
               enabled   (1)"
   ::= {er1645v2PbbBGriMVPppOEEntry 705308684}

er1645v2PbbBGriMVPppOEIpV6DhcpClientDnsServerPref OBJECT-TYPE
   SYNTAX      Integer32
   MAX-ACCESS  read-write
   STATUS      current
   DESCRIPTION
      "Path: pbbBridgeGroup.editConf.pppoEClient.ipV6.dhcp.client.dns.serverPref"
   ::= {er1645v2PbbBGriMVPppOEEntry 705310724}

er1645v2PbbBGriMVPppOEIpV6DhcpClientRapidCommit OBJECT-TYPE
   SYNTAX      INTEGER
               {
               disabled (0),
               enabled (1)
               }
   MAX-ACCESS  read-write
   STATUS      current
   DESCRIPTION
      "Path: pbbBridgeGroup.editConf.pppoEClient.ipV6.dhcp.client.rapidCommit

       Possibilities:
               disabled   (0)
               enabled   (1)"
   ::= {er1645v2PbbBGriMVPppOEEntry 705309696}

er1645v2PbbBGriMVPppOEIpV6DhcpClientTimersSolTimeOut OBJECT-TYPE
   SYNTAX      TimeTicks
   MAX-ACCESS  read-write
   STATUS      current
   DESCRIPTION
      "Path: pbbBridgeGroup.editConf.pppoEClient.ipV6.dhcp.client.timers.solTimeOut

       Time in centi-second."
   ::= {er1645v2PbbBGriMVPppOEEntry 705311748}

er1645v2PbbBGriMVPppOEIpV6DhcpClientTimersSolMaxRt OBJECT-TYPE
   SYNTAX      TimeTicks
   MAX-ACCESS  read-write
   STATUS      current
   DESCRIPTION
      "Path: pbbBridgeGroup.editConf.pppoEClient.ipV6.dhcp.client.timers.solMaxRt

       Time in centi-second."
   ::= {er1645v2PbbBGriMVPppOEEntry 705311752}

er1645v2PbbBGriMVPppOEIpV6DhcpClientTimersInfoRefresh OBJECT-TYPE
   SYNTAX      TimeTicks
   MAX-ACCESS  read-write
   STATUS      current
   DESCRIPTION
      "Path: pbbBridgeGroup.editConf.pppoEClient.ipV6.dhcp.client.timers.infoRefresh

       Time in centi-second."
   ::= {er1645v2PbbBGriMVPppOEEntry 705311756}

er1645v2PbbBGriMVPppOEIpV6DhcpServerMode OBJECT-TYPE
   SYNTAX      INTEGER
               {
               disabled (0),
               enabled (1)
               }
   MAX-ACCESS  read-write
   STATUS      current
   DESCRIPTION
      "Path: pbbBridgeGroup.editConf.pppoEClient.ipV6.dhcp.server.mode

       Possibilities:
               disabled   (0)
               enabled   (1)"
   ::= {er1645v2PbbBGriMVPppOEEntry 705315840}

er1645v2PbbBGriMVPppOEIpV6DhcpServerPreference OBJECT-TYPE
   SYNTAX      Integer32
   MAX-ACCESS  read-write
   STATUS      current
   DESCRIPTION
      "Path: pbbBridgeGroup.editConf.pppoEClient.ipV6.dhcp.server.preference"
   ::= {er1645v2PbbBGriMVPppOEEntry 705316864}

er1645v2PbbBGriMVPppOEIpV6DhcpServerPool OBJECT-TYPE
   SYNTAX      DisplayString
   MAX-ACCESS  read-write
   STATUS      current
   DESCRIPTION
      "Path: pbbBridgeGroup.editConf.pppoEClient.ipV6.dhcp.server.pool"
   ::= {er1645v2PbbBGriMVPppOEEntry 705317888}

er1645v2PbbBGriMVPppOEIpV6DhcpServerRapidCommit OBJECT-TYPE
   SYNTAX      INTEGER
               {
               disabled (0),
               enabled (1)
               }
   MAX-ACCESS  read-write
   STATUS      current
   DESCRIPTION
      "Path: pbbBridgeGroup.editConf.pppoEClient.ipV6.dhcp.server.rapidCommit

       Possibilities:
               disabled   (0)
               enabled   (1)"
   ::= {er1645v2PbbBGriMVPppOEEntry 705318912}

er1645v2PbbBGriMVPppOEIpV6DhcpServerTimersInfoRefresh OBJECT-TYPE
   SYNTAX      TimeTicks
   MAX-ACCESS  read-write
   STATUS      current
   DESCRIPTION
      "Path: pbbBridgeGroup.editConf.pppoEClient.ipV6.dhcp.server.timers.infoRefresh

       Time in centi-second."
   ::= {er1645v2PbbBGriMVPppOEEntry 705319940}

er1645v2PbbBGriMVPppOEIpV6DhcpRelayMode OBJECT-TYPE
   SYNTAX      INTEGER
               {
               disabled (0),
               enabled (1)
               }
   MAX-ACCESS  read-write
   STATUS      current
   DESCRIPTION
      "Path: pbbBridgeGroup.editConf.pppoEClient.ipV6.dhcp.relay.mode

       Possibilities:
               disabled   (0)
               enabled   (1)"
   ::= {er1645v2PbbBGriMVPppOEEntry 705323040}

er1645v2PbbBGriMVPppOEIpV6SendRedirect OBJECT-TYPE
   SYNTAX      INTEGER
               {
               disabled (0),
               enabled (1)
               }
   MAX-ACCESS  read-write
   STATUS      current
   DESCRIPTION
      "Path: pbbBridgeGroup.editConf.pppoEClient.ipV6.sendRedirect

       Possibilities:
               disabled   (0)
               enabled   (1)"
   ::= {er1645v2PbbBGriMVPppOEEntry 705101824}

er1645v2PbbBGriMVPppOEIpV6LinkMtu OBJECT-TYPE
   SYNTAX      Integer32
   MAX-ACCESS  read-write
   STATUS      current
   DESCRIPTION
      "Path: pbbBridgeGroup.editConf.pppoEClient.ipV6.linkMtu"
   ::= {er1645v2PbbBGriMVPppOEEntry 705167360}

er1645v2PbbBGriMVPppOEIpV6InterfaceId OBJECT-TYPE
   SYNTAX      OCTET STRING
   MAX-ACCESS  read-write
   STATUS      current
   DESCRIPTION
      "Path: pbbBridgeGroup.editConf.pppoEClient.ipV6.interfaceId"
   ::= {er1645v2PbbBGriMVPppOEEntry 705232896}

er1645v2PbbBGriMVPppOEIpV6MF OBJECT-TYPE
   SYNTAX      Integer32
   MAX-ACCESS  read-write
   STATUS      current
   DESCRIPTION
      "Path: pbbBridgeGroup.editConf.pppoEClient.ipV6.mgmtFilter

       Bit meanings:
               bit 0 = cms2,
               bit 4 = snmp,
               bit 6 = ftp,
               bit 7 = telnet,
               bit 8 = ssh,
               bit 9 = snmpv3,
               bit 11 = http,
               bit 19 = https,
               bit 25 = dns"
   ::= {er1645v2PbbBGriMVPppOEEntry 705757184}

er1645v2PbbBGriMVPppOEIpV6IcmpMessagesNoRoute OBJECT-TYPE
   SYNTAX      INTEGER
               {
               disabled (0),
               enabled (1)
               }
   MAX-ACCESS  read-write
   STATUS      current
   DESCRIPTION
      "Path: pbbBridgeGroup.editConf.pppoEClient.ipV6.icmpMessages.noRoute

       Possibilities:
               disabled   (0)
               enabled   (1)"
   ::= {er1645v2PbbBGriMVPppOEEntry 705822976}

er1645v2PbbBGriMVPppOEIpV6IcmpMessagesBeyondScope OBJECT-TYPE
   SYNTAX      INTEGER
               {
               disabled (0),
               enabled (1)
               }
   MAX-ACCESS  read-write
   STATUS      current
   DESCRIPTION
      "Path: pbbBridgeGroup.editConf.pppoEClient.ipV6.icmpMessages.beyondScope

       Possibilities:
               disabled   (0)
               enabled   (1)"
   ::= {er1645v2PbbBGriMVPppOEEntry 705823488}

er1645v2PbbBGriMVPppOEIpV6IcmpMessagesAddressUnreachable OBJECT-TYPE
   SYNTAX      INTEGER
               {
               disabled (0),
               enabled (1)
               }
   MAX-ACCESS  read-write
   STATUS      current
   DESCRIPTION
      "Path: pbbBridgeGroup.editConf.pppoEClient.ipV6.icmpMessages.addressUnreachable

       Possibilities:
               disabled   (0)
               enabled   (1)"
   ::= {er1645v2PbbBGriMVPppOEEntry 705823744}

er1645v2PbbBGriMVPppOEIpV6IcmpMessagesPortUnreachable OBJECT-TYPE
   SYNTAX      INTEGER
               {
               disabled (0),
               enabled (1)
               }
   MAX-ACCESS  read-write
   STATUS      current
   DESCRIPTION
      "Path: pbbBridgeGroup.editConf.pppoEClient.ipV6.icmpMessages.portUnreachable

       Possibilities:
               disabled   (0)
               enabled   (1)"
   ::= {er1645v2PbbBGriMVPppOEEntry 705824000}

er1645v2PbbBGriMVPppOEIpV6IcmpMessagesPacketTooBig OBJECT-TYPE
   SYNTAX      INTEGER
               {
               disabled (0),
               enabled (1)
               }
   MAX-ACCESS  read-write
   STATUS      current
   DESCRIPTION
      "Path: pbbBridgeGroup.editConf.pppoEClient.ipV6.icmpMessages.packetTooBig

       Possibilities:
               disabled   (0)
               enabled   (1)"
   ::= {er1645v2PbbBGriMVPppOEEntry 705825280}

er1645v2PbbBGriMVPppOEIpV6IcmpMessagesHopLimitExceeded OBJECT-TYPE
   SYNTAX      INTEGER
               {
               disabled (0),
               enabled (1)
               }
   MAX-ACCESS  read-write
   STATUS      current
   DESCRIPTION
      "Path: pbbBridgeGroup.editConf.pppoEClient.ipV6.icmpMessages.hopLimitExceeded

       Possibilities:
               disabled   (0)
               enabled   (1)"
   ::= {er1645v2PbbBGriMVPppOEEntry 705827840}

er1645v2PbbBGriMVPppOEIpV6IcmpMessagesFragTimeExceeded OBJECT-TYPE
   SYNTAX      INTEGER
               {
               disabled (0),
               enabled (1)
               }
   MAX-ACCESS  read-write
   STATUS      current
   DESCRIPTION
      "Path: pbbBridgeGroup.editConf.pppoEClient.ipV6.icmpMessages.fragTimeExceeded

       Possibilities:
               disabled   (0)
               enabled   (1)"
   ::= {er1645v2PbbBGriMVPppOEEntry 705828096}

er1645v2PbbBGriMVPppOEIpV6IcmpMessagesHeaderFieldErr OBJECT-TYPE
   SYNTAX      INTEGER
               {
               disabled (0),
               enabled (1)
               }
   MAX-ACCESS  read-write
   STATUS      current
   DESCRIPTION
      "Path: pbbBridgeGroup.editConf.pppoEClient.ipV6.icmpMessages.headerFieldErr

       Possibilities:
               disabled   (0)
               enabled   (1)"
   ::= {er1645v2PbbBGriMVPppOEEntry 705830400}

er1645v2PbbBGriMVPppOEIpV6IcmpMessagesOptionUnrecognized OBJECT-TYPE
   SYNTAX      INTEGER
               {
               disabled (0),
               enabled (1)
               }
   MAX-ACCESS  read-write
   STATUS      current
   DESCRIPTION
      "Path: pbbBridgeGroup.editConf.pppoEClient.ipV6.icmpMessages.optionUnrecognized

       Possibilities:
               disabled   (0)
               enabled   (1)"
   ::= {er1645v2PbbBGriMVPppOEEntry 705830912}

er1645v2PbbBGriMVPppOEIpV6IcmpMessagesRedirect OBJECT-TYPE
   SYNTAX      INTEGER
               {
               disabled (0),
               enabled (1)
               }
   MAX-ACCESS  read-write
   STATUS      current
   DESCRIPTION
      "Path: pbbBridgeGroup.editConf.pppoEClient.ipV6.icmpMessages.redirect

       Possibilities:
               disabled   (0)
               enabled   (1)"
   ::= {er1645v2PbbBGriMVPppOEEntry 705832960}

er1645v2PbbBGriMVPppOEPppLnkMOperation OBJECT-TYPE
   SYNTAX      INTEGER
               {
               disabled (0),
               enabled (1)
               }
   MAX-ACCESS  read-write
   STATUS      current
   DESCRIPTION
      "Path: pbbBridgeGroup.editConf.pppoEClient.ppp.linkMonitoring.operation

       Possibilities:
               disabled   (0)
               enabled   (1)"
   ::= {er1645v2PbbBGriMVPppOEEntry 251724032}

er1645v2PbbBGriMVPppOEPppLnkMInterval OBJECT-TYPE
   SYNTAX      TimeTicks
   MAX-ACCESS  read-write
   STATUS      current
   DESCRIPTION
      "Path: pbbBridgeGroup.editConf.pppoEClient.ppp.linkMonitoring.interval

       Time in centi-second."
   ::= {er1645v2PbbBGriMVPppOEEntry 251724288}

er1645v2PbbBGriMVPppOEPppLnkMRepTimeOut OBJECT-TYPE
   SYNTAX      TimeTicks
   MAX-ACCESS  read-write
   STATUS      current
   DESCRIPTION
      "Path: pbbBridgeGroup.editConf.pppoEClient.ppp.linkMonitoring.replyTimeOut

       Time in centi-second."
   ::= {er1645v2PbbBGriMVPppOEEntry 251724544}

er1645v2PbbBGriMVPppOEPppLnkMFailsPrmt OBJECT-TYPE
   SYNTAX      Integer32
   MAX-ACCESS  read-write
   STATUS      current
   DESCRIPTION
      "Path: pbbBridgeGroup.editConf.pppoEClient.ppp.linkMonitoring.failsPermitted"
   ::= {er1645v2PbbBGriMVPppOEEntry 251724800}

er1645v2PbbBGriMVPppOEPppAuthentication OBJECT-TYPE
   SYNTAX      INTEGER
               {
               disabled (0),
               chap (1),
               pap (2),
               chapOrPap (3),
               msChap (4),
               msChapV2 (5)
               }
   MAX-ACCESS  read-write
   STATUS      current
   DESCRIPTION
      "Path: pbbBridgeGroup.editConf.pppoEClient.ppp.authentication

       Possibilities:
               disabled   (0)
               chap   (1)
               pap   (2)
               chapOrPap   (3)
               msChap   (4)
               msChapV2   (5)"
   ::= {er1645v2PbbBGriMVPppOEEntry 251789312}

er1645v2PbbBGriMVPppOEPppAuthenPeriod OBJECT-TYPE
   SYNTAX      TimeTicks
   MAX-ACCESS  read-write
   STATUS      current
   DESCRIPTION
      "Path: pbbBridgeGroup.editConf.pppoEClient.ppp.authenPeriod

       Time in centi-second."
   ::= {er1645v2PbbBGriMVPppOEEntry 251854848}

er1645v2PbbBGriMVPppOEPppSessionName OBJECT-TYPE
   SYNTAX      DisplayString
   MAX-ACCESS  read-write
   STATUS      current
   DESCRIPTION
      "Path: pbbBridgeGroup.editConf.pppoEClient.ppp.sessionName"
   ::= {er1645v2PbbBGriMVPppOEEntry 251985920}

er1645v2PbbBGriMVPppOEPppSessionSecret OBJECT-TYPE
   SYNTAX      DisplayString
   MAX-ACCESS  read-write
   STATUS      current
   DESCRIPTION
      "Path: pbbBridgeGroup.editConf.pppoEClient.ppp.sessionSecret"
   ::= {er1645v2PbbBGriMVPppOEEntry 252051456}

er1645v2PbbBGriMVPppOEPppEncModeSessionSecret OBJECT-TYPE
   SYNTAX      INTEGER
               {
               none (1),
               encrypt (2),
               encType1 (3),
               invalid (128)
               }
   MAX-ACCESS  read-write
   STATUS      current
   DESCRIPTION
      "Path: pbbBridgeGroup.editConf.pppoEClient.ppp.encModeSessionSecret

       Possibilities:
               none   (1)
               encrypt   (2)
               encType1   (3)
               invalid   (128)"
   ::= {er1645v2PbbBGriMVPppOEEntry 252182528}

er1645v2PbbBGriMVPppOEPppEncSessionSecret OBJECT-TYPE
   SYNTAX      DisplayString
   MAX-ACCESS  read-write
   STATUS      current
   DESCRIPTION
      "Path: pbbBridgeGroup.editConf.pppoEClient.ppp.encSessionSecret"
   ::= {er1645v2PbbBGriMVPppOEEntry 252248064}

er1645v2PbbBGriMVPppOEPppServiceName OBJECT-TYPE
   SYNTAX      DisplayString
   MAX-ACCESS  read-write
   STATUS      current
   DESCRIPTION
      "Path: pbbBridgeGroup.editConf.pppoEClient.ppp.serviceName"
   ::= {er1645v2PbbBGriMVPppOEEntry 252116992}

er1645v2PbbBGriMVPppOEIpH OBJECT-TYPE
   SYNTAX      SEQUENCE OF Er1645v2PbbBGriMVPppOEIpHEntry
   MAX-ACCESS  not-accessible
   STATUS      current
   DESCRIPTION
      ""
   ::= {er1645v2PbbBGriMVPppOE 51314688}

er1645v2PbbBGriMVPppOEIpHEntry OBJECT-TYPE
   SYNTAX      Er1645v2PbbBGriMVPppOEIpHEntry
   MAX-ACCESS  not-accessible
   STATUS      current
   DESCRIPTION
      ""
   INDEX      { er1645v2PbbBGriMVPppOEIpHGlobalIx,
                er1645v2PbbBGriMVPppOETableIx,
                er1645v2PbbBGriMVPppOEIpHTableIx }
   ::= {er1645v2PbbBGriMVPppOEIpH 1}

Er1645v2PbbBGriMVPppOEIpHEntry ::=
   SEQUENCE
      {
      er1645v2PbbBGriMVPppOEIpHActions
         VariableLengthTableActions,
      er1645v2PbbBGriMVPppOEIpHGlobalIx
         GlobalIndex,
      er1645v2PbbBGriMVPppOEIpHTableIx
         TableIndex,
      er1645v2PbbBGriMVPppOEIpHAddress
         IpAddress,
      er1645v2PbbBGriMVPppOEIpHDhcpRelayOptionSubscriberId
         DisplayString
      }

er1645v2PbbBGriMVPppOEIpHActions OBJECT-TYPE
   SYNTAX      VariableLengthTableActions
   MAX-ACCESS  read-write
   STATUS      current
   DESCRIPTION
      "By way of this field, some manipulations
       on this table may be performed."
   ::= {er1645v2PbbBGriMVPppOEIpHEntry 2}

er1645v2PbbBGriMVPppOEIpHGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEIpHEntry 10}

er1645v2PbbBGriMVPppOEIpHTableIx OBJECT-TYPE
   SYNTAX      TableIndex
   MAX-ACCESS  not-accessible
   STATUS      current
   DESCRIPTION
      ""
   ::= {er1645v2PbbBGriMVPppOEIpHEntry 11}

er1645v2PbbBGriMVPppOEIpHAddress OBJECT-TYPE
   SYNTAX      IpAddress
   MAX-ACCESS  read-write
   STATUS      current
   DESCRIPTION
      "Path: pbbBridgeGroup.editConf.pppoEClient.ip.helpers.address"
   ::= {er1645v2PbbBGriMVPppOEIpHEntry 16777216}

er1645v2PbbBGriMVPppOEIpHDhcpRelayOptionSubscriberId OBJECT-TYPE
   SYNTAX      DisplayString
   MAX-ACCESS  read-write
   STATUS      current
   DESCRIPTION
      "Path: pbbBridgeGroup.editConf.pppoEClient.ip.helpers.dhcpRelayOption.subscriberId"
   ::= {er1645v2PbbBGriMVPppOEIpHEntry 33947648}

er1645v2PbbBGriMVPppOEIpV6Addresses OBJECT-TYPE
   SYNTAX      SEQUENCE OF Er1645v2PbbBGriMVPppOEIpV6AddressesEntry
   MAX-ACCESS  not-accessible
   STATUS      current
   DESCRIPTION
      ""
   ::= {er1645v2PbbBGriMVPppOE 704839680}

er1645v2PbbBGriMVPppOEIpV6AddressesEntry OBJECT-TYPE
   SYNTAX      Er1645v2PbbBGriMVPppOEIpV6AddressesEntry
   MAX-ACCESS  not-accessible
   STATUS      current
   DESCRIPTION
      ""
   INDEX      { er1645v2PbbBGriMVPppOEIpV6AddressesGlobalIx,
                er1645v2PbbBGriMVPppOETableIx,
                er1645v2PbbBGriMVPppOEIpV6AddressesTableIx }
   ::= {er1645v2PbbBGriMVPppOEIpV6Addresses 1}

Er1645v2PbbBGriMVPppOEIpV6AddressesEntry ::=
   SEQUENCE
      {
      er1645v2PbbBGriMVPppOEIpV6AddressesActions
         VariableLengthTableActions,
      er1645v2PbbBGriMVPppOEIpV6AddressesGlobalIx
         GlobalIndex,
      er1645v2PbbBGriMVPppOEIpV6AddressesTableIx
         TableIndex,
      er1645v2PbbBGriMVPppOEIpV6AddressesType
         INTEGER,
      er1645v2PbbBGriMVPppOEIpV6AddressesAddress
         Ipv6Address,
      er1645v2PbbBGriMVPppOEIpV6AddressesPrefixLength
         Integer32,
      er1645v2PbbBGriMVPppOEIpV6AddressesGeneralPrefix
         DisplayString,
      er1645v2PbbBGriMVPppOEIpV6AddressesRaSend
         INTEGER,
      er1645v2PbbBGriMVPppOEIpV6AddressesRaOnLinkFlag
         INTEGER,
      er1645v2PbbBGriMVPppOEIpV6AddressesRaAutoFlag
         INTEGER,
      er1645v2PbbBGriMVPppOEIpV6AddressesRaValidLifeTime
         TimeTicks,
      er1645v2PbbBGriMVPppOEIpV6AddressesRaValidLTMode
         INTEGER,
      er1645v2PbbBGriMVPppOEIpV6AddressesRaPrefLifeTime
         TimeTicks,
      er1645v2PbbBGriMVPppOEIpV6AddressesRaPrefLTMode
         INTEGER
      }

er1645v2PbbBGriMVPppOEIpV6AddressesActions OBJECT-TYPE
   SYNTAX      VariableLengthTableActions
   MAX-ACCESS  read-write
   STATUS      current
   DESCRIPTION
      "By way of this field, some manipulations
       on this table may be performed."
   ::= {er1645v2PbbBGriMVPppOEIpV6AddressesEntry 2}

er1645v2PbbBGriMVPppOEIpV6AddressesGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEIpV6AddressesEntry 10}

er1645v2PbbBGriMVPppOEIpV6AddressesTableIx OBJECT-TYPE
   SYNTAX      TableIndex
   MAX-ACCESS  not-accessible
   STATUS      current
   DESCRIPTION
      ""
   ::= {er1645v2PbbBGriMVPppOEIpV6AddressesEntry 11}

er1645v2PbbBGriMVPppOEIpV6AddressesType OBJECT-TYPE
   SYNTAX      INTEGER
               {
               unicast (0),
               eui64 (1),
               anycast (2),
               linkLocal (3),
               generalPrefix (4)
               }
   MAX-ACCESS  read-write
   STATUS      current
   DESCRIPTION
      "Path: pbbBridgeGroup.editConf.pppoEClient.ipV6.addresses.type

       Possibilities:
               unicast   (0)
               eui64   (1)
               anycast   (2)
               linkLocal   (3)
               generalPrefix   (4)"
   ::= {er1645v2PbbBGriMVPppOEIpV6AddressesEntry 50331648}

er1645v2PbbBGriMVPppOEIpV6AddressesAddress OBJECT-TYPE
   SYNTAX      Ipv6Address
   MAX-ACCESS  read-write
   STATUS      current
   DESCRIPTION
      "Path: pbbBridgeGroup.editConf.pppoEClient.ipV6.addresses.address

       ipv6 address"
   ::= {er1645v2PbbBGriMVPppOEIpV6AddressesEntry 16777216}

er1645v2PbbBGriMVPppOEIpV6AddressesPrefixLength OBJECT-TYPE
   SYNTAX      Integer32
   MAX-ACCESS  read-write
   STATUS      current
   DESCRIPTION
      "Path: pbbBridgeGroup.editConf.pppoEClient.ipV6.addresses.prefixLength"
   ::= {er1645v2PbbBGriMVPppOEIpV6AddressesEntry 33554432}

er1645v2PbbBGriMVPppOEIpV6AddressesGeneralPrefix OBJECT-TYPE
   SYNTAX      DisplayString
   MAX-ACCESS  read-write
   STATUS      current
   DESCRIPTION
      "Path: pbbBridgeGroup.editConf.pppoEClient.ipV6.addresses.generalPrefix"
   ::= {er1645v2PbbBGriMVPppOEIpV6AddressesEntry 83886080}

er1645v2PbbBGriMVPppOEIpV6AddressesRaSend OBJECT-TYPE
   SYNTAX      INTEGER
               {
               disabled (0),
               enabled (1)
               }
   MAX-ACCESS  read-write
   STATUS      current
   DESCRIPTION
      "Path: pbbBridgeGroup.editConf.pppoEClient.ipV6.addresses.ra.send

       Possibilities:
               disabled   (0)
               enabled   (1)"
   ::= {er1645v2PbbBGriMVPppOEIpV6AddressesEntry 67174400}

er1645v2PbbBGriMVPppOEIpV6AddressesRaOnLinkFlag OBJECT-TYPE
   SYNTAX      INTEGER
               {
               disabled (0),
               enabled (1)
               }
   MAX-ACCESS  read-write
   STATUS      current
   DESCRIPTION
      "Path: pbbBridgeGroup.editConf.pppoEClient.ipV6.addresses.ra.onLinkFlag

       Possibilities:
               disabled   (0)
               enabled   (1)"
   ::= {er1645v2PbbBGriMVPppOEIpV6AddressesEntry 67371008}

er1645v2PbbBGriMVPppOEIpV6AddressesRaAutoFlag OBJECT-TYPE
   SYNTAX      INTEGER
               {
               disabled (0),
               enabled (1)
               }
   MAX-ACCESS  read-write
   STATUS      current
   DESCRIPTION
      "Path: pbbBridgeGroup.editConf.pppoEClient.ipV6.addresses.ra.autonomousFlag

       Possibilities:
               disabled   (0)
               enabled   (1)"
   ::= {er1645v2PbbBGriMVPppOEIpV6AddressesEntry 67567616}

er1645v2PbbBGriMVPppOEIpV6AddressesRaValidLifeTime OBJECT-TYPE
   SYNTAX      TimeTicks
   MAX-ACCESS  read-write
   STATUS      current
   DESCRIPTION
      "Path: pbbBridgeGroup.editConf.pppoEClient.ipV6.addresses.ra.validLifeTime

       Time in centi-second."
   ::= {er1645v2PbbBGriMVPppOEIpV6AddressesEntry 67239936}

er1645v2PbbBGriMVPppOEIpV6AddressesRaValidLTMode OBJECT-TYPE
   SYNTAX      INTEGER
               {
               fixed (0),
               infinite (2)
               }
   MAX-ACCESS  read-write
   STATUS      current
   DESCRIPTION
      "Path: pbbBridgeGroup.editConf.pppoEClient.ipV6.addresses.ra.validLifeTimeMode

       Possibilities:
               fixed   (0)
               infinite   (2)"
   ::= {er1645v2PbbBGriMVPppOEIpV6AddressesEntry 67305472}

er1645v2PbbBGriMVPppOEIpV6AddressesRaPrefLifeTime OBJECT-TYPE
   SYNTAX      TimeTicks
   MAX-ACCESS  read-write
   STATUS      current
   DESCRIPTION
      "Path: pbbBridgeGroup.editConf.pppoEClient.ipV6.addresses.ra.prefLifeTime

       Time in centi-second."
   ::= {er1645v2PbbBGriMVPppOEIpV6AddressesEntry 67436544}

er1645v2PbbBGriMVPppOEIpV6AddressesRaPrefLTMode OBJECT-TYPE
   SYNTAX      INTEGER
               {
               fixed (0),
               infinite (2)
               }
   MAX-ACCESS  read-write
   STATUS      current
   DESCRIPTION
      "Path: pbbBridgeGroup.editConf.pppoEClient.ipV6.addresses.ra.prefLifeTimeMode

       Possibilities:
               fixed   (0)
               infinite   (2)"
   ::= {er1645v2PbbBGriMVPppOEIpV6AddressesEntry 67502080}

er1645v2PbbBGriMVPppOEIpV6RaDnsOptionsRdnssServers OBJECT-TYPE
   SYNTAX      SEQUENCE OF Er1645v2PbbBGriMVPppOEIpV6RaDnsOptionsRdnssServersEntry
   MAX-ACCESS  not-accessible
   STATUS      current
   DESCRIPTION
      ""
   ::= {er1645v2PbbBGriMVPppOE 705039144}

er1645v2PbbBGriMVPppOEIpV6RaDnsOptionsRdnssServersEntry OBJECT-TYPE
   SYNTAX      Er1645v2PbbBGriMVPppOEIpV6RaDnsOptionsRdnssServersEntry
   MAX-ACCESS  not-accessible
   STATUS      current
   DESCRIPTION
      ""
   INDEX      { er1645v2PbbBGriMVPppOEIpV6RaDnsOptionsRdnssServersGlobalIx,
                er1645v2PbbBGriMVPppOETableIx,
                er1645v2PbbBGriMVPppOEIpV6RaDnsOptionsRdnssServersTableIx }
   ::= {er1645v2PbbBGriMVPppOEIpV6RaDnsOptionsRdnssServers 1}

Er1645v2PbbBGriMVPppOEIpV6RaDnsOptionsRdnssServersEntry ::=
   SEQUENCE
      {
      er1645v2PbbBGriMVPppOEIpV6RaDnsOptionsRdnssServersActions
         VariableLengthTableActions,
      er1645v2PbbBGriMVPppOEIpV6RaDnsOptionsRdnssServersGlobalIx
         GlobalIndex,
      er1645v2PbbBGriMVPppOEIpV6RaDnsOptionsRdnssServersTableIx
         TableIndex,
      er1645v2PbbBGriMVPppOEIpV6RaDnsOptionsRdnssServersAddress
         Ipv6Address
      }

er1645v2PbbBGriMVPppOEIpV6RaDnsOptionsRdnssServersActions OBJECT-TYPE
   SYNTAX      VariableLengthTableActions
   MAX-ACCESS  read-write
   STATUS      current
   DESCRIPTION
      "By way of this field, some manipulations
       on this table may be performed."
   ::= {er1645v2PbbBGriMVPppOEIpV6RaDnsOptionsRdnssServersEntry 2}

er1645v2PbbBGriMVPppOEIpV6RaDnsOptionsRdnssServersGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEIpV6RaDnsOptionsRdnssServersEntry 10}

er1645v2PbbBGriMVPppOEIpV6RaDnsOptionsRdnssServersTableIx OBJECT-TYPE
   SYNTAX      TableIndex
   MAX-ACCESS  not-accessible
   STATUS      current
   DESCRIPTION
      ""
   ::= {er1645v2PbbBGriMVPppOEIpV6RaDnsOptionsRdnssServersEntry 11}

er1645v2PbbBGriMVPppOEIpV6RaDnsOptionsRdnssServersAddress OBJECT-TYPE
   SYNTAX      Ipv6Address
   MAX-ACCESS  read-write
   STATUS      current
   DESCRIPTION
      "Path: pbbBridgeGroup.editConf.pppoEClient.ipV6.ra.dnsOptions.rdnss.servers.address

       ipv6 address"
   ::= {er1645v2PbbBGriMVPppOEIpV6RaDnsOptionsRdnssServersEntry 16777216}

er1645v2PbbBGriMVPppOEIpV6RaDnsOptionsDnsslDomains OBJECT-TYPE
   SYNTAX      SEQUENCE OF Er1645v2PbbBGriMVPppOEIpV6RaDnsOptionsDnsslDomainsEntry
   MAX-ACCESS  not-accessible
   STATUS      current
   DESCRIPTION
      ""
   ::= {er1645v2PbbBGriMVPppOE 705039176}

er1645v2PbbBGriMVPppOEIpV6RaDnsOptionsDnsslDomainsEntry OBJECT-TYPE
   SYNTAX      Er1645v2PbbBGriMVPppOEIpV6RaDnsOptionsDnsslDomainsEntry
   MAX-ACCESS  not-accessible
   STATUS      current
   DESCRIPTION
      ""
   INDEX      { er1645v2PbbBGriMVPppOEIpV6RaDnsOptionsDnsslDomainsGlobalIx,
                er1645v2PbbBGriMVPppOETableIx,
                er1645v2PbbBGriMVPppOEIpV6RaDnsOptionsDnsslDomainsTableIx }
   ::= {er1645v2PbbBGriMVPppOEIpV6RaDnsOptionsDnsslDomains 1}

Er1645v2PbbBGriMVPppOEIpV6RaDnsOptionsDnsslDomainsEntry ::=
   SEQUENCE
      {
      er1645v2PbbBGriMVPppOEIpV6RaDnsOptionsDnsslDomainsActions
         VariableLengthTableActions,
      er1645v2PbbBGriMVPppOEIpV6RaDnsOptionsDnsslDomainsGlobalIx
         GlobalIndex,
      er1645v2PbbBGriMVPppOEIpV6RaDnsOptionsDnsslDomainsTableIx
         TableIndex,
      er1645v2PbbBGriMVPppOEIpV6RaDnsOptionsDnsslDomainsName
         DisplayString
      }

er1645v2PbbBGriMVPppOEIpV6RaDnsOptionsDnsslDomainsActions OBJECT-TYPE
   SYNTAX      VariableLengthTableActions
   MAX-ACCESS  read-write
   STATUS      current
   DESCRIPTION
      "By way of this field, some manipulations
       on this table may be performed."
   ::= {er1645v2PbbBGriMVPppOEIpV6RaDnsOptionsDnsslDomainsEntry 2}

er1645v2PbbBGriMVPppOEIpV6RaDnsOptionsDnsslDomainsGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEIpV6RaDnsOptionsDnsslDomainsEntry 10}

er1645v2PbbBGriMVPppOEIpV6RaDnsOptionsDnsslDomainsTableIx OBJECT-TYPE
   SYNTAX      TableIndex
   MAX-ACCESS  not-accessible
   STATUS      current
   DESCRIPTION
      ""
   ::= {er1645v2PbbBGriMVPppOEIpV6RaDnsOptionsDnsslDomainsEntry 11}

er1645v2PbbBGriMVPppOEIpV6RaDnsOptionsDnsslDomainsName OBJECT-TYPE
   SYNTAX      DisplayString
   MAX-ACCESS  read-write
   STATUS      current
   DESCRIPTION
      "Path: pbbBridgeGroup.editConf.pppoEClient.ipV6.ra.dnsOptions.dnssl.domains.name"
   ::= {er1645v2PbbBGriMVPppOEIpV6RaDnsOptionsDnsslDomainsEntry 16777216}

er1645v2PbbBGriMVPppOEIpV6DhcpClientUserClassOpt OBJECT-TYPE
   SYNTAX      SEQUENCE OF Er1645v2PbbBGriMVPppOEIpV6DhcpClientUserClassOptEntry
   MAX-ACCESS  not-accessible
   STATUS      current
   DESCRIPTION
      ""
   ::= {er1645v2PbbBGriMVPppOE 705312768}

er1645v2PbbBGriMVPppOEIpV6DhcpClientUserClassOptEntry OBJECT-TYPE
   SYNTAX      Er1645v2PbbBGriMVPppOEIpV6DhcpClientUserClassOptEntry
   MAX-ACCESS  not-accessible
   STATUS      current
   DESCRIPTION
      ""
   INDEX      { er1645v2PbbBGriMVPppOEIpV6DhcpClientUserClassOptGlobalIx,
                er1645v2PbbBGriMVPppOETableIx,
                er1645v2PbbBGriMVPppOEIpV6DhcpClientUserClassOptTableIx }
   ::= {er1645v2PbbBGriMVPppOEIpV6DhcpClientUserClassOpt 1}

Er1645v2PbbBGriMVPppOEIpV6DhcpClientUserClassOptEntry ::=
   SEQUENCE
      {
      er1645v2PbbBGriMVPppOEIpV6DhcpClientUserClassOptActions
         VariableLengthTableActions,
      er1645v2PbbBGriMVPppOEIpV6DhcpClientUserClassOptGlobalIx
         GlobalIndex,
      er1645v2PbbBGriMVPppOEIpV6DhcpClientUserClassOptTableIx
         TableIndex,
      er1645v2PbbBGriMVPppOEIpV6DhcpClientUserClassOptValueAscii
         DisplayString,
      er1645v2PbbBGriMVPppOEIpV6DhcpClientUserClassOptValueDecimal
         Integer32,
      er1645v2PbbBGriMVPppOEIpV6DhcpClientUserClassOptValueHexData
         OCTET STRING
      }

er1645v2PbbBGriMVPppOEIpV6DhcpClientUserClassOptActions OBJECT-TYPE
   SYNTAX      VariableLengthTableActions
   MAX-ACCESS  read-write
   STATUS      current
   DESCRIPTION
      "By way of this field, some manipulations
       on this table may be performed."
   ::= {er1645v2PbbBGriMVPppOEIpV6DhcpClientUserClassOptEntry 2}

er1645v2PbbBGriMVPppOEIpV6DhcpClientUserClassOptGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEIpV6DhcpClientUserClassOptEntry 10}

er1645v2PbbBGriMVPppOEIpV6DhcpClientUserClassOptTableIx OBJECT-TYPE
   SYNTAX      TableIndex
   MAX-ACCESS  not-accessible
   STATUS      current
   DESCRIPTION
      ""
   ::= {er1645v2PbbBGriMVPppOEIpV6DhcpClientUserClassOptEntry 11}

er1645v2PbbBGriMVPppOEIpV6DhcpClientUserClassOptValueAscii OBJECT-TYPE
   SYNTAX      DisplayString
   MAX-ACCESS  read-write
   STATUS      current
   DESCRIPTION
      "Path: pbbBridgeGroup.editConf.pppoEClient.ipV6.dhcp.client.userClassOpt.value.ascii"
   ::= {er1645v2PbbBGriMVPppOEIpV6DhcpClientUserClassOptEntry 16842752}

er1645v2PbbBGriMVPppOEIpV6DhcpClientUserClassOptValueDecimal OBJECT-TYPE
   SYNTAX      Integer32
   MAX-ACCESS  read-write
   STATUS      current
   DESCRIPTION
      "Path: pbbBridgeGroup.editConf.pppoEClient.ipV6.dhcp.client.userClassOpt.value.decimal"
   ::= {er1645v2PbbBGriMVPppOEIpV6DhcpClientUserClassOptEntry 16908288}

er1645v2PbbBGriMVPppOEIpV6DhcpClientUserClassOptValueHexData OBJECT-TYPE
   SYNTAX      OCTET STRING
   MAX-ACCESS  read-write
   STATUS      current
   DESCRIPTION
      "Path: pbbBridgeGroup.editConf.pppoEClient.ipV6.dhcp.client.userClassOpt.value.hexData"
   ::= {er1645v2PbbBGriMVPppOEIpV6DhcpClientUserClassOptEntry 16973824}

er1645v2PbbBGriMVPppOEIpV6DhcpClientVendorCl OBJECT-TYPE
   SYNTAX      SEQUENCE OF Er1645v2PbbBGriMVPppOEIpV6DhcpClientVendorClEntry
   MAX-ACCESS  not-accessible
   STATUS      current
   DESCRIPTION
      ""
   ::= {er1645v2PbbBGriMVPppOE 705313792}

er1645v2PbbBGriMVPppOEIpV6DhcpClientVendorClEntry OBJECT-TYPE
   SYNTAX      Er1645v2PbbBGriMVPppOEIpV6DhcpClientVendorClEntry
   MAX-ACCESS  not-accessible
   STATUS      current
   DESCRIPTION
      ""
   INDEX      { er1645v2PbbBGriMVPppOEIpV6DhcpClientVendorClGlobalIx,
                er1645v2PbbBGriMVPppOETableIx,
                er1645v2PbbBGriMVPppOEIpV6DhcpClientVendorClTableIx }
   ::= {er1645v2PbbBGriMVPppOEIpV6DhcpClientVendorCl 1}

Er1645v2PbbBGriMVPppOEIpV6DhcpClientVendorClEntry ::=
   SEQUENCE
      {
      er1645v2PbbBGriMVPppOEIpV6DhcpClientVendorClActions
         VariableLengthTableActions,
      er1645v2PbbBGriMVPppOEIpV6DhcpClientVendorClGlobalIx
         GlobalIndex,
      er1645v2PbbBGriMVPppOEIpV6DhcpClientVendorClTableIx
         TableIndex,
      er1645v2PbbBGriMVPppOEIpV6DhcpClientVendorClValueAscii
         DisplayString,
      er1645v2PbbBGriMVPppOEIpV6DhcpClientVendorClValueDecimal
         Integer32,
      er1645v2PbbBGriMVPppOEIpV6DhcpClientVendorClValueHexData
         OCTET STRING
      }

er1645v2PbbBGriMVPppOEIpV6DhcpClientVendorClActions OBJECT-TYPE
   SYNTAX      VariableLengthTableActions
   MAX-ACCESS  read-write
   STATUS      current
   DESCRIPTION
      "By way of this field, some manipulations
       on this table may be performed."
   ::= {er1645v2PbbBGriMVPppOEIpV6DhcpClientVendorClEntry 2}

er1645v2PbbBGriMVPppOEIpV6DhcpClientVendorClGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEIpV6DhcpClientVendorClEntry 10}

er1645v2PbbBGriMVPppOEIpV6DhcpClientVendorClTableIx OBJECT-TYPE
   SYNTAX      TableIndex
   MAX-ACCESS  not-accessible
   STATUS      current
   DESCRIPTION
      ""
   ::= {er1645v2PbbBGriMVPppOEIpV6DhcpClientVendorClEntry 11}

er1645v2PbbBGriMVPppOEIpV6DhcpClientVendorClValueAscii OBJECT-TYPE
   SYNTAX      DisplayString
   MAX-ACCESS  read-write
   STATUS      current
   DESCRIPTION
      "Path: pbbBridgeGroup.editConf.pppoEClient.ipV6.dhcp.client.vendorClassOpt.value.ascii"
   ::= {er1645v2PbbBGriMVPppOEIpV6DhcpClientVendorClEntry 16842752}

er1645v2PbbBGriMVPppOEIpV6DhcpClientVendorClValueDecimal OBJECT-TYPE
   SYNTAX      Integer32
   MAX-ACCESS  read-write
   STATUS      current
   DESCRIPTION
      "Path: pbbBridgeGroup.editConf.pppoEClient.ipV6.dhcp.client.vendorClassOpt.value.decimal"
   ::= {er1645v2PbbBGriMVPppOEIpV6DhcpClientVendorClEntry 16908288}

er1645v2PbbBGriMVPppOEIpV6DhcpClientVendorClValueHexData OBJECT-TYPE
   SYNTAX      OCTET STRING
   MAX-ACCESS  read-write
   STATUS      current
   DESCRIPTION
      "Path: pbbBridgeGroup.editConf.pppoEClient.ipV6.dhcp.client.vendorClassOpt.value.hexData"
   ::= {er1645v2PbbBGriMVPppOEIpV6DhcpClientVendorClEntry 16973824}

er1645v2PbbBGriMVPppOEIpV6DhcpRelayDestinations OBJECT-TYPE
   SYNTAX      SEQUENCE OF Er1645v2PbbBGriMVPppOEIpV6DhcpRelayDestinationsEntry
   MAX-ACCESS  not-accessible
   STATUS      current
   DESCRIPTION
      ""
   ::= {er1645v2PbbBGriMVPppOE 705323072}

er1645v2PbbBGriMVPppOEIpV6DhcpRelayDestinationsEntry OBJECT-TYPE
   SYNTAX      Er1645v2PbbBGriMVPppOEIpV6DhcpRelayDestinationsEntry
   MAX-ACCESS  not-accessible
   STATUS      current
   DESCRIPTION
      ""
   INDEX      { er1645v2PbbBGriMVPppOEIpV6DhcpRelayDestinationsGlobalIx,
                er1645v2PbbBGriMVPppOETableIx,
                er1645v2PbbBGriMVPppOEIpV6DhcpRelayDestinationsTableIx }
   ::= {er1645v2PbbBGriMVPppOEIpV6DhcpRelayDestinations 1}

Er1645v2PbbBGriMVPppOEIpV6DhcpRelayDestinationsEntry ::=
   SEQUENCE
      {
      er1645v2PbbBGriMVPppOEIpV6DhcpRelayDestinationsActions
         VariableLengthTableActions,
      er1645v2PbbBGriMVPppOEIpV6DhcpRelayDestinationsGlobalIx
         GlobalIndex,
      er1645v2PbbBGriMVPppOEIpV6DhcpRelayDestinationsTableIx
         TableIndex,
      er1645v2PbbBGriMVPppOEIpV6DhcpRelayDestinationsAddress
         Ipv6Address,
      er1645v2PbbBGriMVPppOEIpV6DhcpRelayDestinationsInterface
         DisplayString
      }

er1645v2PbbBGriMVPppOEIpV6DhcpRelayDestinationsActions OBJECT-TYPE
   SYNTAX      VariableLengthTableActions
   MAX-ACCESS  read-write
   STATUS      current
   DESCRIPTION
      "By way of this field, some manipulations
       on this table may be performed."
   ::= {er1645v2PbbBGriMVPppOEIpV6DhcpRelayDestinationsEntry 2}

er1645v2PbbBGriMVPppOEIpV6DhcpRelayDestinationsGlobalIx OBJECT-TYPE
   SYNTAX      GlobalIndex
   MAX-ACCESS  not-accessible
   STATUS      current
   DESCRIPTION
      "The value of the tlsCntTreeGlobalIndex of the MANAGED OBJECT."
   ::= {er1645v2PbbBGriMVPppOEIpV6DhcpRelayDestinationsEntry 10}

er1645v2PbbBGriMVPppOEIpV6DhcpRelayDestinationsTableIx OBJECT-TYPE
   SYNTAX      TableIndex
   MAX-ACCESS  not-accessible
   STATUS      current
   DESCRIPTION
      ""
   ::= {er1645v2PbbBGriMVPppOEIpV6DhcpRelayDestinationsEntry 11}

er1645v2PbbBGriMVPppOEIpV6DhcpRelayDestinationsAddress OBJECT-TYPE
   SYNTAX      Ipv6Address
   MAX-ACCESS  read-write
   STATUS      current
   DESCRIPTION
      "Path: pbbBridgeGroup.editConf.pppoEClient.ipV6.dhcp.relay.destinations.address

       ipv6 address"
   ::= {er1645v2PbbBGriMVPppOEIpV6DhcpRelayDestinationsEntry 16777216}

er1645v2PbbBGriMVPppOEIpV6DhcpRelayDestinationsInterface OBJECT-TYPE
   SYNTAX      DisplayString
   MAX-ACCESS  read-write
   STATUS      current
   DESCRIPTION
      "Path: pbbBridgeGroup.editConf.pppoEClient.ipV6.dhcp.relay.destinations.interface"
   ::= {er1645v2PbbBGriMVPppOEIpV6DhcpRelayDestinationsEntry 33554432}


er1645v2PbbBGriMVSnmpIndexOffset OBJECT IDENTIFIER ::= {er1645v2PbbBGriMV 268}

er1645v2PbbBGriMVSnmpIndexOffsetTable OBJECT-TYPE
   SYNTAX      SEQUENCE OF Er1645v2PbbBGriMVSnmpIndexOffsetEntry
   MAX-ACCESS  not-accessible
   STATUS      current
   DESCRIPTION
      "Preferred offset in the range of SNMP indices for this SWinst, 0 means automatic"
   ::= {er1645v2PbbBGriMVSnmpIndexOffset 1}

er1645v2PbbBGriMVSnmpIndexOffsetEntry OBJECT-TYPE
   SYNTAX      Er1645v2PbbBGriMVSnmpIndexOffsetEntry
   MAX-ACCESS  not-accessible
   STATUS      current
   DESCRIPTION
      ""
   INDEX      { er1645v2PbbBGriMVSnmpIndexOffsetGlobalIx }
   ::= {er1645v2PbbBGriMVSnmpIndexOffsetTable 1}

Er1645v2PbbBGriMVSnmpIndexOffsetEntry ::=
   SEQUENCE
      {
      er1645v2PbbBGriMVSnmpIndexOffsetGlobalIx
         GlobalIndex,
      er1645v2PbbBGriMVSnmpIndexOffsetValue
         Integer32
      }

er1645v2PbbBGriMVSnmpIndexOffsetGlobalIx OBJECT-TYPE
   SYNTAX      GlobalIndex
   MAX-ACCESS  not-accessible
   STATUS      current
   DESCRIPTION
      "The value of the tlsCntTreeGlobalIndex of the MANAGED OBJECT."
   ::= {er1645v2PbbBGriMVSnmpIndexOffsetEntry 10}

er1645v2PbbBGriMVSnmpIndexOffsetValue OBJECT-TYPE
   SYNTAX      Integer32
   MAX-ACCESS  read-write
   STATUS      current
   DESCRIPTION
      "Path: pbbBridgeGroup.editConf.snmpIndexOffset"
   ::= {er1645v2PbbBGriMVSnmpIndexOffsetEntry 2147483648}


er1645v2PbbBGriMVMacAddress OBJECT IDENTIFIER ::= {er1645v2PbbBGriMV 27}

er1645v2PbbBGriMVMacAddressSSCTable OBJECT-TYPE
   SYNTAX      SEQUENCE OF Er1645v2PbbBGriMVMacAddressEntry
   MAX-ACCESS  not-accessible
   STATUS      current
   DESCRIPTION
      "Configurable MAC address of Bridge group"
   ::= {er1645v2PbbBGriMVMacAddress 1}

er1645v2PbbBGriMVMacAddressEntry OBJECT-TYPE
   SYNTAX      Er1645v2PbbBGriMVMacAddressEntry
   MAX-ACCESS  not-accessible
   STATUS      current
   DESCRIPTION
      ""
   INDEX      { er1645v2PbbBGriMVMacAddressGlobalIx }
   ::= {er1645v2PbbBGriMVMacAddressSSCTable 1}

Er1645v2PbbBGriMVMacAddressEntry ::=
   SEQUENCE
      {
      er1645v2PbbBGriMVMacAddressGlobalIx
         GlobalIndex,
      er1645v2PbbBGriMVMacAddressDeviceMac
         DisplayString,
      er1645v2PbbBGriMVMacAddressUserMac
         OCTET STRING,
      er1645v2PbbBGriMVMacAddressRandomMac
         Integer32
      }

er1645v2PbbBGriMVMacAddressGlobalIx OBJECT-TYPE
   SYNTAX      GlobalIndex
   MAX-ACCESS  not-accessible
   STATUS      current
   DESCRIPTION
      "The value of the tlsCntTreeGlobalIndex of the MANAGED OBJECT."
   ::= {er1645v2PbbBGriMVMacAddressEntry 10}

er1645v2PbbBGriMVMacAddressDeviceMac OBJECT-TYPE
   SYNTAX      DisplayString
   MAX-ACCESS  read-write
   STATUS      current
   DESCRIPTION
      "Path: pbbBridgeGroup.editConf.macAddress.deviceMac"
   ::= {er1645v2PbbBGriMVMacAddressEntry 50331648}

er1645v2PbbBGriMVMacAddressUserMac OBJECT-TYPE
   SYNTAX      OCTET STRING
   MAX-ACCESS  read-write
   STATUS      current
   DESCRIPTION
      "Path: pbbBridgeGroup.editConf.macAddress.userMac

       MAC address."
   ::= {er1645v2PbbBGriMVMacAddressEntry 33554432}

er1645v2PbbBGriMVMacAddressRandomMac OBJECT-TYPE
   SYNTAX      Integer32
   MAX-ACCESS  read-write
   STATUS      current
   DESCRIPTION
      "Path: pbbBridgeGroup.editConf.macAddress.randomMac"
   ::= {er1645v2PbbBGriMVMacAddressEntry 67108864}


er1645v2PbbBGriMVPppoEServer OBJECT IDENTIFIER ::= {er1645v2PbbBGriMV 37}

er1645v2PbbBGriMVPppoEServerTable OBJECT-TYPE
   SYNTAX      SEQUENCE OF Er1645v2PbbBGriMVPppoEServerEntry
   MAX-ACCESS  not-accessible
   STATUS      current
   DESCRIPTION
      "ppp server name on interface"
   ::= {er1645v2PbbBGriMVPppoEServer 1}

er1645v2PbbBGriMVPppoEServerEntry OBJECT-TYPE
   SYNTAX      Er1645v2PbbBGriMVPppoEServerEntry
   MAX-ACCESS  not-accessible
   STATUS      current
   DESCRIPTION
      ""
   INDEX      { er1645v2PbbBGriMVPppoEServerGlobalIx }
   ::= {er1645v2PbbBGriMVPppoEServerTable 1}

Er1645v2PbbBGriMVPppoEServerEntry ::=
   SEQUENCE
      {
      er1645v2PbbBGriMVPppoEServerGlobalIx
         GlobalIndex,
      er1645v2PbbBGriMVPppoEServerValue
         DisplayString
      }

er1645v2PbbBGriMVPppoEServerGlobalIx OBJECT-TYPE
   SYNTAX      GlobalIndex
   MAX-ACCESS  not-accessible
   STATUS      current
   DESCRIPTION
      "The value of the tlsCntTreeGlobalIndex of the MANAGED OBJECT."
   ::= {er1645v2PbbBGriMVPppoEServerEntry 10}

er1645v2PbbBGriMVPppoEServerValue OBJECT-TYPE
   SYNTAX      DisplayString
   MAX-ACCESS  read-write
   STATUS      current
   DESCRIPTION
      "Path: pbbBridgeGroup.editConf.pppoEServer"
   ::= {er1645v2PbbBGriMVPppoEServerEntry 2147483648}



sr1645v2PbbBGriMV OBJECT IDENTIFIER ::= {r1645v2PbbBGriMV 14}


sr1645v2PbbBGriMVBridgeCacheSize OBJECT IDENTIFIER ::= {sr1645v2PbbBGriMV 39}

sr1645v2PbbBGriMVBridgeCacheSizeSSCTable OBJECT-TYPE
   SYNTAX      SEQUENCE OF Sr1645v2PbbBGriMVBridgeCacheSizeEntry
   MAX-ACCESS  not-accessible
   STATUS      current
   DESCRIPTION
      "bridge cache size info"
   ::= {sr1645v2PbbBGriMVBridgeCacheSize 1}

sr1645v2PbbBGriMVBridgeCacheSizeEntry OBJECT-TYPE
   SYNTAX      Sr1645v2PbbBGriMVBridgeCacheSizeEntry
   MAX-ACCESS  not-accessible
   STATUS      current
   DESCRIPTION
      ""
   INDEX      { sr1645v2PbbBGriMVBridgeCacheSizeGlobalIx }
   ::= {sr1645v2PbbBGriMVBridgeCacheSizeSSCTable 1}

Sr1645v2PbbBGriMVBridgeCacheSizeEntry ::=
   SEQUENCE
      {
      sr1645v2PbbBGriMVBridgeCacheSizeGlobalIx
         GlobalIndex,
      sr1645v2PbbBGriMVBridgeCacheSizeSize
         Counter32,
      sr1645v2PbbBGriMVBridgeCacheSizeMaxSize
         INTEGER
      }

sr1645v2PbbBGriMVBridgeCacheSizeGlobalIx OBJECT-TYPE
   SYNTAX      GlobalIndex
   MAX-ACCESS  not-accessible
   STATUS      current
   DESCRIPTION
      "The value of the tlsCntTreeGlobalIndex of the MANAGED OBJECT."
   ::= {sr1645v2PbbBGriMVBridgeCacheSizeEntry 10}

sr1645v2PbbBGriMVBridgeCacheSizeSize OBJECT-TYPE
   SYNTAX      Counter32
   MAX-ACCESS  read-only
   STATUS      current
   DESCRIPTION
      "Path: pbbBridgeGroup.status.bridgeCacheSize.size

       32 bit unsigned wrappable counter."
   ::= {sr1645v2PbbBGriMVBridgeCacheSizeEntry 16777216}

sr1645v2PbbBGriMVBridgeCacheSizeMaxSize OBJECT-TYPE
   SYNTAX      INTEGER
               {
               unlimited (0)
               }
   MAX-ACCESS  read-only
   STATUS      current
   DESCRIPTION
      "Path: pbbBridgeGroup.status.bridgeCacheSize.maxSize

       Possibilities:
               unlimited   (0)"
   ::= {sr1645v2PbbBGriMVBridgeCacheSizeEntry 33554432}


sr1645v2PbbBGriMVMacAddress OBJECT IDENTIFIER ::= {sr1645v2PbbBGriMV 105}

sr1645v2PbbBGriMVMacAddressTable OBJECT-TYPE
   SYNTAX      SEQUENCE OF Sr1645v2PbbBGriMVMacAddressEntry
   MAX-ACCESS  not-accessible
   STATUS      current
   DESCRIPTION
      "ifPhysAddress"
   ::= {sr1645v2PbbBGriMVMacAddress 1}

sr1645v2PbbBGriMVMacAddressEntry OBJECT-TYPE
   SYNTAX      Sr1645v2PbbBGriMVMacAddressEntry
   MAX-ACCESS  not-accessible
   STATUS      current
   DESCRIPTION
      ""
   INDEX      { sr1645v2PbbBGriMVMacAddressGlobalIx }
   ::= {sr1645v2PbbBGriMVMacAddressTable 1}

Sr1645v2PbbBGriMVMacAddressEntry ::=
   SEQUENCE
      {
      sr1645v2PbbBGriMVMacAddressGlobalIx
         GlobalIndex,
      sr1645v2PbbBGriMVMacAddressValue
         OCTET STRING
      }

sr1645v2PbbBGriMVMacAddressGlobalIx OBJECT-TYPE
   SYNTAX      GlobalIndex
   MAX-ACCESS  not-accessible
   STATUS      current
   DESCRIPTION
      "The value of the tlsCntTreeGlobalIndex of the MANAGED OBJECT."
   ::= {sr1645v2PbbBGriMVMacAddressEntry 10}

sr1645v2PbbBGriMVMacAddressValue OBJECT-TYPE
   SYNTAX      OCTET STRING
   MAX-ACCESS  read-only
   STATUS      current
   DESCRIPTION
      "Path: pbbBridgeGroup.status.macAddress

       MAC address."
   ::= {sr1645v2PbbBGriMVMacAddressEntry 2147483648}


sr1645v2PbbBGriMVDescr OBJECT IDENTIFIER ::= {sr1645v2PbbBGriMV 101}

sr1645v2PbbBGriMVDescrTable OBJECT-TYPE
   SYNTAX      SEQUENCE OF Sr1645v2PbbBGriMVDescrEntry
   MAX-ACCESS  not-accessible
   STATUS      current
   DESCRIPTION
      "ifDescr"
   ::= {sr1645v2PbbBGriMVDescr 1}

sr1645v2PbbBGriMVDescrEntry OBJECT-TYPE
   SYNTAX      Sr1645v2PbbBGriMVDescrEntry
   MAX-ACCESS  not-accessible
   STATUS      current
   DESCRIPTION
      ""
   INDEX      { sr1645v2PbbBGriMVDescrGlobalIx }
   ::= {sr1645v2PbbBGriMVDescrTable 1}

Sr1645v2PbbBGriMVDescrEntry ::=
   SEQUENCE
      {
      sr1645v2PbbBGriMVDescrGlobalIx
         GlobalIndex,
      sr1645v2PbbBGriMVDescrValue
         DisplayString
      }

sr1645v2PbbBGriMVDescrGlobalIx OBJECT-TYPE
   SYNTAX      GlobalIndex
   MAX-ACCESS  not-accessible
   STATUS      current
   DESCRIPTION
      "The value of the tlsCntTreeGlobalIndex of the MANAGED OBJECT."
   ::= {sr1645v2PbbBGriMVDescrEntry 10}

sr1645v2PbbBGriMVDescrValue OBJECT-TYPE
   SYNTAX      DisplayString
   MAX-ACCESS  read-only
   STATUS      current
   DESCRIPTION
      "Path: pbbBridgeGroup.status.ifDescr"
   ::= {sr1645v2PbbBGriMVDescrEntry 2147483648}


sr1645v2PbbBGriMVType OBJECT IDENTIFIER ::= {sr1645v2PbbBGriMV 102}

sr1645v2PbbBGriMVTypeTable OBJECT-TYPE
   SYNTAX      SEQUENCE OF Sr1645v2PbbBGriMVTypeEntry
   MAX-ACCESS  not-accessible
   STATUS      current
   DESCRIPTION
      "ifType"
   ::= {sr1645v2PbbBGriMVType 1}

sr1645v2PbbBGriMVTypeEntry OBJECT-TYPE
   SYNTAX      Sr1645v2PbbBGriMVTypeEntry
   MAX-ACCESS  not-accessible
   STATUS      current
   DESCRIPTION
      ""
   INDEX      { sr1645v2PbbBGriMVTypeGlobalIx }
   ::= {sr1645v2PbbBGriMVTypeTable 1}

Sr1645v2PbbBGriMVTypeEntry ::=
   SEQUENCE
      {
      sr1645v2PbbBGriMVTypeGlobalIx
         GlobalIndex,
      sr1645v2PbbBGriMVTypeValue
         INTEGER
      }

sr1645v2PbbBGriMVTypeGlobalIx OBJECT-TYPE
   SYNTAX      GlobalIndex
   MAX-ACCESS  not-accessible
   STATUS      current
   DESCRIPTION
      "The value of the tlsCntTreeGlobalIndex of the MANAGED OBJECT."
   ::= {sr1645v2PbbBGriMVTypeEntry 10}

sr1645v2PbbBGriMVTypeValue OBJECT-TYPE
   SYNTAX      INTEGER
               {
               other (1),
               regular1822 (2),
               hdh1822 (3),
               ddnmx25 (4),
               rfc877mx25 (5),
               ethernetmcsmacd (6),
               iso88023mcsmacd (7),
               iso88024mtokenBus (8),
               iso88025mtokenRing (9),
               is088026mman (10),
               starlan (11),
               proteonm10Mbit (12),
               proteonm80Mbit (13),
               hyperChannel (14),
               fddi (15),
               lapb (16),
               sdlc (17),
               ds1 (18),
               e1 (19),
               basicISDN (20),
               primaryISDN (21),
               propPointToPointSerial (22),
               ppp (23),
               softwareLoopback (24),
               eon (25),
               ethernetm3Mbit (26),
               nsip (27),
               slip (28),
               ultra (29),
               ds3 (30),
               sip (31),
               framemrelay (32),
               rs232 (33),
               para (34),
               arcnet (35),
               arcnetPlus (36),
               atm (37),
               miox25 (38),
               sonet (39),
               x25ple (40),
               iso88022llc (41),
               localTalk (42),
               smdsDxi (43),
               frameRelayService (44),
               v35 (45),
               hssi (46),
               hippi (47),
               modem (48),
               aal5 (49),
               sonetPath (50),
               sonetVT (51),
               smdsIcip (52),
               propVirtual (53),
               propMultiplexor (54),
               ieee80212 (55),
               fibreChannel (56),
               hippiInterface (57),
               frameRelayInterconnect (58),
               aflane8023 (59),
               aflane8025 (60),
               cctEmul (61),
               fastEther (62),
               isdn (63),
               v11 (64),
               v36 (65),
               g703at64k (66),
               g703at2mb (67),
               qllc (68),
               fastEtherFX (69),
               channel (70),
               ieee80211 (71),
               ibm370parChan (72),
               escon (73),
               dlsw (74),
               isdns (75),
               isdnu (76),
               lapd (77),
               ipSwitch (78),
               rsrb (79),
               atmmlogical (80),
               ds0 (81),
               ds0Bundle (82),
               bsc (83),
               async (84),
               cnr (85),
               iso88025Dtr (86),
               eplrs (87),
               arap (88),
               propCnls (89),
               hostPad (90),
               termPad (91),
               frameRelayMPI (92),
               x213 (93),
               adsl (94),
               radsl (95),
               sdsl (96),
               vdsl (97),
               iso88025CRFPInt (98),
               myrinet (99),
               voiceEM (100),
               voiceFXO (101),
               voiceFXS (102),
               voiceEncap (103),
               voiceOverIp (104),
               atmDxi (105),
               atmFuni (106),
               atmIma (107),
               pppMultilinkBundle (108),
               ipOverCdlc (109),
               ipOverClaw (110),
               stackToStack (111),
               virtualIpAddress (112),
               mpc (113),
               ipOverAtm (114),
               iso88025Fiber (115),
               tdlc (116),
               gigabitEthernet (117),
               hdlc (118),
               lapf (119),
               v37 (120),
               x25mlp (121),
               x25huntGroup (122),
               trasnpHdlc (123),
               interleave (124),
               fast (125),
               ip (126),
               docsCableMaclayer (127),
               docsCableDownstream (128),
               docsCableUpstream (129),
               a12MppSwitch (130),
               tunnel (131),
               coffee (132),
               ces (133),
               atmSubInterface (134),
               l2vlan (135),
               l3ipvlan (136),
               l3ipxvlan (137),
               digitalPowerline (138),
               mediaMailOverIp (139),
               dtm (140),
               dcn (141),
               ipForward (142),
               msdsl (143),
               ieee1394 (144),
               ifmgsn (145),
               dvbRccMacLayer (146),
               dvbRccDownstream (147),
               dvbRccUpstream (148),
               atmVirtual (149),
               mplsTunnel (150),
               srp (151),
               voiceOverAtm (152),
               voiceOverFrameRelay (153),
               idsl (154),
               compositeLink (155),
               ss7SigLink (156),
               propWirelessP2P (157),
               frForward (158),
               rfc1483 (159),
               usb (160),
               ieee8023adLag (161),
               bgppolicyaccounting (162),
               frf16MfrBundle (163),
               h323Gatekeeper (164),
               h323Proxy (165),
               mpls (166),
               mfSigLink (167),
               hdsl2 (168),
               shdsl (169),
               ds1FDL (170),
               pos (171),
               dvbAsiIn (172),
               dvbAsiOut (173),
               plc (174),
               nfas (175),
               tr008 (176),
               gr303RDT (177),
               gr303IDT (178),
               isup (179),
               propDocsWirelessMaclayer (180),
               propDocsWirelessDownstream (181),
               propDocsWirelessUpstream (182),
               hiperlan2 (183),
               propBWAp2Mp (184),
               sonetOverheadChannel (185),
               digitalWrapperOverheadChannel (186),
               aal2 (187),
               radioMAC (188),
               atmRadio (189),
               imt (190),
               mvl (191),
               reachDSL (192),
               frDlciEndPt (193),
               atmVciEndPt (194),
               opticalChannel (195),
               opticalTransport (196),
               propAtm (197),
               voiceOverCable (198),
               infiniband (199),
               teLink (200),
               q2931 (201),
               virtualTg (202),
               sipTg (203),
               sipSig (204),
               docsCableUpstreamChannel (205),
               econet (206),
               pon155 (207),
               pon622 (208),
               bridge (209),
               linegroup (210),
               voiceEMFGD (211),
               voiceFGDEANA (212),
               voiceDID (213),
               mpegTransport (214),
               sixToFour (215),
               gtp (216),
               pdnEtherLoop1 (217),
               pdnEtherLoop2 (218),
               opticalChannelGroup (219),
               homepna (220),
               gfp (221),
               ciscoISLvlan (222),
               actelisMetaLOOP (223),
               fcipLink (224),
               rpr (225),
               qam (226),
               lmp (227),
               cblVectaStar (228),
               docsCableMCmtsDownstream (229),
               adsl2 (230),
               macSecControlledIF (231),
               macSecUncontrolledIF (232),
               aviciOpticalEther (233),
               atmbond (234),
               voiceFGDOS (235),
               mocaVersion1 (236),
               ieee80216WMAN (237),
               adsl2plus (238),
               dvbRcsMacLayer (239),
               dvbTdm (240),
               dvbRcsTdma (241),
               x86Laps (242),
               wwanPP (243),
               wwanPP2 (244),
               voiceEBS (245),
               ifPwType (246),
               ilan (247),
               pip (248),
               aluELP (249),
               gpon (250),
               vdsl2 (251),
               capwapDot11Profile (252),
               capwapDot11Bss (253),
               capwapWtpVirtualRadio (254),
               bits (255),
               docsCableUpstreamRfPort (256),
               cableDownstreamRfPort (257),
               gfast (279)
               }
   MAX-ACCESS  read-only
   STATUS      current
   DESCRIPTION
      "Path: pbbBridgeGroup.status.ifType

       Possibilities:
               other   (1)
               regular1822   (2)
               hdh1822   (3)
               ddn-x25   (4)
               rfc877-x25   (5)
               ethernet-csmacd   (6)
               iso88023-csmacd   (7)
               iso88024-tokenBus   (8)
               iso88025-tokenRing   (9)
               is088026-man   (10)
               starlan   (11)
               proteon-10Mbit   (12)
               proteon-80Mbit   (13)
               hyperChannel   (14)
               fddi   (15)
               lapb   (16)
               sdlc   (17)
               ds1   (18)
               e1   (19)
               basicISDN   (20)
               primaryISDN   (21)
               propPointToPointSerial   (22)
               ppp   (23)
               softwareLoopback   (24)
               eon   (25)
               ethernet-3Mbit   (26)
               nsip   (27)
               slip   (28)
               ultra   (29)
               ds3   (30)
               sip   (31)
               frame-relay   (32)
               rs232   (33)
               para   (34)
               arcnet   (35)
               arcnetPlus   (36)
               atm   (37)
               miox25   (38)
               sonet   (39)
               x25ple   (40)
               iso88022llc   (41)
               localTalk   (42)
               smdsDxi   (43)
               frameRelayService   (44)
               v35   (45)
               hssi   (46)
               hippi   (47)
               modem   (48)
               aal5   (49)
               sonetPath   (50)
               sonetVT   (51)
               smdsIcip   (52)
               propVirtual   (53)
               propMultiplexor   (54)
               ieee80212   (55)
               fibreChannel   (56)
               hippiInterface   (57)
               frameRelayInterconnect   (58)
               aflane8023   (59)
               aflane8025   (60)
               cctEmul   (61)
               fastEther   (62)
               isdn   (63)
               v11   (64)
               v36   (65)
               g703at64k   (66)
               g703at2mb   (67)
               qllc   (68)
               fastEtherFX   (69)
               channel   (70)
               ieee80211   (71)
               ibm370parChan   (72)
               escon   (73)
               dlsw   (74)
               isdns   (75)
               isdnu   (76)
               lapd   (77)
               ipSwitch   (78)
               rsrb   (79)
               atm-logical   (80)
               ds0   (81)
               ds0Bundle   (82)
               bsc   (83)
               async   (84)
               cnr   (85)
               iso88025Dtr   (86)
               eplrs   (87)
               arap   (88)
               propCnls   (89)
               hostPad   (90)
               termPad   (91)
               frameRelayMPI   (92)
               x213   (93)
               adsl   (94)
               radsl   (95)
               sdsl   (96)
               vdsl   (97)
               iso88025CRFPInt   (98)
               myrinet   (99)
               voiceEM   (100)
               voiceFXO   (101)
               voiceFXS   (102)
               voiceEncap   (103)
               voiceOverIp   (104)
               atmDxi   (105)
               atmFuni   (106)
               atmIma   (107)
               pppMultilinkBundle   (108)
               ipOverCdlc   (109)
               ipOverClaw   (110)
               stackToStack   (111)
               virtualIpAddress   (112)
               mpc   (113)
               ipOverAtm   (114)
               iso88025Fiber   (115)
               tdlc   (116)
               gigabitEthernet   (117)
               hdlc   (118)
               lapf   (119)
               v37   (120)
               x25mlp   (121)
               x25huntGroup   (122)
               trasnpHdlc   (123)
               interleave   (124)
               fast   (125)
               ip   (126)
               docsCableMaclayer   (127)
               docsCableDownstream   (128)
               docsCableUpstream   (129)
               a12MppSwitch   (130)
               tunnel   (131)
               coffee   (132)
               ces   (133)
               atmSubInterface   (134)
               l2vlan   (135)
               l3ipvlan   (136)
               l3ipxvlan   (137)
               digitalPowerline   (138)
               mediaMailOverIp   (139)
               dtm   (140)
               dcn   (141)
               ipForward   (142)
               msdsl   (143)
               ieee1394   (144)
               if-gsn   (145)
               dvbRccMacLayer   (146)
               dvbRccDownstream   (147)
               dvbRccUpstream   (148)
               atmVirtual   (149)
               mplsTunnel   (150)
               srp   (151)
               voiceOverAtm   (152)
               voiceOverFrameRelay   (153)
               idsl   (154)
               compositeLink   (155)
               ss7SigLink   (156)
               propWirelessP2P   (157)
               frForward   (158)
               rfc1483   (159)
               usb   (160)
               ieee8023adLag   (161)
               bgppolicyaccounting   (162)
               frf16MfrBundle   (163)
               h323Gatekeeper   (164)
               h323Proxy   (165)
               mpls   (166)
               mfSigLink   (167)
               hdsl2   (168)
               shdsl   (169)
               ds1FDL   (170)
               pos   (171)
               dvbAsiIn   (172)
               dvbAsiOut   (173)
               plc   (174)
               nfas   (175)
               tr008   (176)
               gr303RDT   (177)
               gr303IDT   (178)
               isup   (179)
               propDocsWirelessMaclayer   (180)
               propDocsWirelessDownstream   (181)
               propDocsWirelessUpstream   (182)
               hiperlan2   (183)
               propBWAp2Mp   (184)
               sonetOverheadChannel   (185)
               digitalWrapperOverheadChannel   (186)
               aal2   (187)
               radioMAC   (188)
               atmRadio   (189)
               imt   (190)
               mvl   (191)
               reachDSL   (192)
               frDlciEndPt   (193)
               atmVciEndPt   (194)
               opticalChannel   (195)
               opticalTransport   (196)
               propAtm   (197)
               voiceOverCable   (198)
               infiniband   (199)
               teLink   (200)
               q2931   (201)
               virtualTg   (202)
               sipTg   (203)
               sipSig   (204)
               docsCableUpstreamChannel   (205)
               econet   (206)
               pon155   (207)
               pon622   (208)
               bridge   (209)
               linegroup   (210)
               voiceEMFGD   (211)
               voiceFGDEANA   (212)
               voiceDID   (213)
               mpegTransport   (214)
               sixToFour   (215)
               gtp   (216)
               pdnEtherLoop1   (217)
               pdnEtherLoop2   (218)
               opticalChannelGroup   (219)
               homepna   (220)
               gfp   (221)
               ciscoISLvlan   (222)
               actelisMetaLOOP   (223)
               fcipLink   (224)
               rpr   (225)
               qam   (226)
               lmp   (227)
               cblVectaStar   (228)
               docsCableMCmtsDownstream   (229)
               adsl2   (230)
               macSecControlledIF   (231)
               macSecUncontrolledIF   (232)
               aviciOpticalEther   (233)
               atmbond   (234)
               voiceFGDOS   (235)
               mocaVersion1   (236)
               ieee80216WMAN   (237)
               adsl2plus   (238)
               dvbRcsMacLayer   (239)
               dvbTdm   (240)
               dvbRcsTdma   (241)
               x86Laps   (242)
               wwanPP   (243)
               wwanPP2   (244)
               voiceEBS   (245)
               ifPwType   (246)
               ilan   (247)
               pip   (248)
               aluELP   (249)
               gpon   (250)
               vdsl2   (251)
               capwapDot11Profile   (252)
               capwapDot11Bss   (253)
               capwapWtpVirtualRadio   (254)
               bits   (255)
               docsCableUpstreamRfPort   (256)
               cableDownstreamRfPort   (257)
               gfast   (279)"
   ::= {sr1645v2PbbBGriMVTypeEntry 2147483648}


sr1645v2PbbBGriMVMtu OBJECT IDENTIFIER ::= {sr1645v2PbbBGriMV 103}

sr1645v2PbbBGriMVMtuTable OBJECT-TYPE
   SYNTAX      SEQUENCE OF Sr1645v2PbbBGriMVMtuEntry
   MAX-ACCESS  not-accessible
   STATUS      current
   DESCRIPTION
      "ifMtu"
   ::= {sr1645v2PbbBGriMVMtu 1}

sr1645v2PbbBGriMVMtuEntry OBJECT-TYPE
   SYNTAX      Sr1645v2PbbBGriMVMtuEntry
   MAX-ACCESS  not-accessible
   STATUS      current
   DESCRIPTION
      ""
   INDEX      { sr1645v2PbbBGriMVMtuGlobalIx }
   ::= {sr1645v2PbbBGriMVMtuTable 1}

Sr1645v2PbbBGriMVMtuEntry ::=
   SEQUENCE
      {
      sr1645v2PbbBGriMVMtuGlobalIx
         GlobalIndex,
      sr1645v2PbbBGriMVMtuValue
         Integer32
      }

sr1645v2PbbBGriMVMtuGlobalIx OBJECT-TYPE
   SYNTAX      GlobalIndex
   MAX-ACCESS  not-accessible
   STATUS      current
   DESCRIPTION
      "The value of the tlsCntTreeGlobalIndex of the MANAGED OBJECT."
   ::= {sr1645v2PbbBGriMVMtuEntry 10}

sr1645v2PbbBGriMVMtuValue OBJECT-TYPE
   SYNTAX      Integer32
   MAX-ACCESS  read-only
   STATUS      current
   DESCRIPTION
      "Path: pbbBridgeGroup.status.ifMtu"
   ::= {sr1645v2PbbBGriMVMtuEntry 2147483648}


sr1645v2PbbBGriMVOperStatus OBJECT IDENTIFIER ::= {sr1645v2PbbBGriMV 107}

sr1645v2PbbBGriMVOperStatusTable OBJECT-TYPE
   SYNTAX      SEQUENCE OF Sr1645v2PbbBGriMVOperStatusEntry
   MAX-ACCESS  not-accessible
   STATUS      current
   DESCRIPTION
      "ifOperStatus"
   ::= {sr1645v2PbbBGriMVOperStatus 1}

sr1645v2PbbBGriMVOperStatusEntry OBJECT-TYPE
   SYNTAX      Sr1645v2PbbBGriMVOperStatusEntry
   MAX-ACCESS  not-accessible
   STATUS      current
   DESCRIPTION
      ""
   INDEX      { sr1645v2PbbBGriMVOperStatusGlobalIx }
   ::= {sr1645v2PbbBGriMVOperStatusTable 1}

Sr1645v2PbbBGriMVOperStatusEntry ::=
   SEQUENCE
      {
      sr1645v2PbbBGriMVOperStatusGlobalIx
         GlobalIndex,
      sr1645v2PbbBGriMVOperStatusValue
         INTEGER
      }

sr1645v2PbbBGriMVOperStatusGlobalIx OBJECT-TYPE
   SYNTAX      GlobalIndex
   MAX-ACCESS  not-accessible
   STATUS      current
   DESCRIPTION
      "The value of the tlsCntTreeGlobalIndex of the MANAGED OBJECT."
   ::= {sr1645v2PbbBGriMVOperStatusEntry 10}

sr1645v2PbbBGriMVOperStatusValue OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: pbbBridgeGroup.status.ifOperStatus

       Possibilities:
               up   (1)
               down   (2)
               testing   (3)
               unknown   (4)
               dormant   (5)
               notPresent   (6)
               lowerLayerDown   (7)"
   ::= {sr1645v2PbbBGriMVOperStatusEntry 2147483648}


sr1645v2PbbBGriMVIp OBJECT IDENTIFIER ::= {sr1645v2PbbBGriMV 11}

sr1645v2PbbBGriMVIpSSCTable OBJECT-TYPE
   SYNTAX      SEQUENCE OF Sr1645v2PbbBGriMVIpEntry
   MAX-ACCESS  not-accessible
   STATUS      current
   DESCRIPTION
      "Ip status parameters of a bridge gateway"
   ::= {sr1645v2PbbBGriMVIp 1}

sr1645v2PbbBGriMVIpEntry OBJECT-TYPE
   SYNTAX      Sr1645v2PbbBGriMVIpEntry
   MAX-ACCESS  not-accessible
   STATUS      current
   DESCRIPTION
      ""
   INDEX      { sr1645v2PbbBGriMVIpGlobalIx }
   ::= {sr1645v2PbbBGriMVIpSSCTable 1}

Sr1645v2PbbBGriMVIpEntry ::=
   SEQUENCE
      {
      sr1645v2PbbBGriMVIpGlobalIx
         GlobalIndex,
      sr1645v2PbbBGriMVIpAddress
         IpAddress,
      sr1645v2PbbBGriMVIpNetMask
         IpAddress,
      sr1645v2PbbBGriMVIpDhcpStatus
         INTEGER,
      sr1645v2PbbBGriMVIpDhcpLeaseTime
         TimeTicks
      }

sr1645v2PbbBGriMVIpGlobalIx OBJECT-TYPE
   SYNTAX      GlobalIndex
   MAX-ACCESS  not-accessible
   STATUS      current
   DESCRIPTION
      "The value of the tlsCntTreeGlobalIndex of the MANAGED OBJECT."
   ::= {sr1645v2PbbBGriMVIpEntry 10}

sr1645v2PbbBGriMVIpAddress OBJECT-TYPE
   SYNTAX      IpAddress
   MAX-ACCESS  read-only
   STATUS      current
   DESCRIPTION
      "Path: pbbBridgeGroup.status.ip.address"
   ::= {sr1645v2PbbBGriMVIpEntry 268435456}

sr1645v2PbbBGriMVIpNetMask OBJECT-TYPE
   SYNTAX      IpAddress
   MAX-ACCESS  read-only
   STATUS      current
   DESCRIPTION
      "Path: pbbBridgeGroup.status.ip.netMask"
   ::= {sr1645v2PbbBGriMVIpEntry 285212672}

sr1645v2PbbBGriMVIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: pbbBridgeGroup.status.ip.dhcp.status

       Possibilities:
               none   (0)
               selecting   (1)
               requesting   (2)
               rebinding   (3)
               bound   (4)
               renewing   (5)
               rebooting   (6)
               initreboot   (7)"
   ::= {sr1645v2PbbBGriMVIpEntry 402718720}

sr1645v2PbbBGriMVIpDhcpLeaseTime OBJECT-TYPE
   SYNTAX      TimeTicks
   MAX-ACCESS  read-only
   STATUS      current
   DESCRIPTION
      "Path: pbbBridgeGroup.status.ip.dhcp.leaseTime

       Time in centi-second."
   ::= {sr1645v2PbbBGriMVIpEntry 402784256}

sr1645v2PbbBGriMVIpSecondaryIp OBJECT-TYPE
   SYNTAX      SEQUENCE OF Sr1645v2PbbBGriMVIpSecondaryIpEntry
   MAX-ACCESS  not-accessible
   STATUS      current
   DESCRIPTION
      ""
   ::= {sr1645v2PbbBGriMVIp 385875968}

sr1645v2PbbBGriMVIpSecondaryIpEntry OBJECT-TYPE
   SYNTAX      Sr1645v2PbbBGriMVIpSecondaryIpEntry
   MAX-ACCESS  not-accessible
   STATUS      current
   DESCRIPTION
      ""
   INDEX      { sr1645v2PbbBGriMVIpSecondaryIpGlobalIx,
                sr1645v2PbbBGriMVIpSecondaryIpTableIx }
   ::= {sr1645v2PbbBGriMVIpSecondaryIp 1}

Sr1645v2PbbBGriMVIpSecondaryIpEntry ::=
   SEQUENCE
      {
      sr1645v2PbbBGriMVIpSecondaryIpGlobalIx
         GlobalIndex,
      sr1645v2PbbBGriMVIpSecondaryIpTableIx
         TableIndex,
      sr1645v2PbbBGriMVIpSecondaryIpAddress
         IpAddress,
      sr1645v2PbbBGriMVIpSecondaryIpNetMask
         IpAddress
      }

sr1645v2PbbBGriMVIpSecondaryIpGlobalIx OBJECT-TYPE
   SYNTAX      GlobalIndex
   MAX-ACCESS  not-accessible
   STATUS      current
   DESCRIPTION
      "The value of the tlsCntTreeGlobalIndex of the MANAGED OBJECT."
   ::= {sr1645v2PbbBGriMVIpSecondaryIpEntry 10}

sr1645v2PbbBGriMVIpSecondaryIpTableIx OBJECT-TYPE
   SYNTAX      TableIndex
   MAX-ACCESS  not-accessible
   STATUS      current
   DESCRIPTION
      ""
   ::= {sr1645v2PbbBGriMVIpSecondaryIpEntry 11}

sr1645v2PbbBGriMVIpSecondaryIpAddress OBJECT-TYPE
   SYNTAX      IpAddress
   MAX-ACCESS  read-only
   STATUS      current
   DESCRIPTION
      "Path: pbbBridgeGroup.status.ip.secondaryIp.address"
   ::= {sr1645v2PbbBGriMVIpSecondaryIpEntry 2030043136}

sr1645v2PbbBGriMVIpSecondaryIpNetMask OBJECT-TYPE
   SYNTAX      IpAddress
   MAX-ACCESS  read-only
   STATUS      current
   DESCRIPTION
      "Path: pbbBridgeGroup.status.ip.secondaryIp.netMask"
   ::= {sr1645v2PbbBGriMVIpSecondaryIpEntry 2063597568}


sr1645v2PbbBGriMVIpV6 OBJECT IDENTIFIER ::= {sr1645v2PbbBGriMV 22}

sr1645v2PbbBGriMVIpV6SSCTable OBJECT-TYPE
   SYNTAX      SEQUENCE OF Sr1645v2PbbBGriMVIpV6Entry
   MAX-ACCESS  not-accessible
   STATUS      current
   DESCRIPTION
      "IPv6 interface config parameters"
   ::= {sr1645v2PbbBGriMVIpV6 1}

sr1645v2PbbBGriMVIpV6Entry OBJECT-TYPE
   SYNTAX      Sr1645v2PbbBGriMVIpV6Entry
   MAX-ACCESS  not-accessible
   STATUS      current
   DESCRIPTION
      ""
   INDEX      { sr1645v2PbbBGriMVIpV6GlobalIx }
   ::= {sr1645v2PbbBGriMVIpV6SSCTable 1}

Sr1645v2PbbBGriMVIpV6Entry ::=
   SEQUENCE
      {
      sr1645v2PbbBGriMVIpV6GlobalIx
         GlobalIndex,
      sr1645v2PbbBGriMVIpV6State
         INTEGER,
      sr1645v2PbbBGriMVIpV6InterfaceId
         OCTET STRING,
      sr1645v2PbbBGriMVIpV6LinkMtu
         Integer32,
      sr1645v2PbbBGriMVIpV6HopLimit
         Integer32,
      sr1645v2PbbBGriMVIpV6DhcpIaid
         Counter32,
      sr1645v2PbbBGriMVIpV6RaRcvOption
         Integer32
      }

sr1645v2PbbBGriMVIpV6GlobalIx OBJECT-TYPE
   SYNTAX      GlobalIndex
   MAX-ACCESS  not-accessible
   STATUS      current
   DESCRIPTION
      "The value of the tlsCntTreeGlobalIndex of the MANAGED OBJECT."
   ::= {sr1645v2PbbBGriMVIpV6Entry 10}

sr1645v2PbbBGriMVIpV6State OBJECT-TYPE
   SYNTAX      INTEGER
               {
               disabled (0),
               enabled (1)
               }
   MAX-ACCESS  read-only
   STATUS      current
   DESCRIPTION
      "Path: pbbBridgeGroup.status.ipV6.state

       Possibilities:
               disabled   (0)
               enabled   (1)"
   ::= {sr1645v2PbbBGriMVIpV6Entry 16777216}

sr1645v2PbbBGriMVIpV6InterfaceId OBJECT-TYPE
   SYNTAX      OCTET STRING
   MAX-ACCESS  read-only
   STATUS      current
   DESCRIPTION
      "Path: pbbBridgeGroup.status.ipV6.interfaceId"
   ::= {sr1645v2PbbBGriMVIpV6Entry 33554432}

sr1645v2PbbBGriMVIpV6LinkMtu OBJECT-TYPE
   SYNTAX      Integer32
   MAX-ACCESS  read-only
   STATUS      current
   DESCRIPTION
      "Path: pbbBridgeGroup.status.ipV6.linkMtu"
   ::= {sr1645v2PbbBGriMVIpV6Entry 67108864}

sr1645v2PbbBGriMVIpV6HopLimit OBJECT-TYPE
   SYNTAX      Integer32
   MAX-ACCESS  read-only
   STATUS      current
   DESCRIPTION
      "Path: pbbBridgeGroup.status.ipV6.hopLimit"
   ::= {sr1645v2PbbBGriMVIpV6Entry 83886080}

sr1645v2PbbBGriMVIpV6DhcpIaid OBJECT-TYPE
   SYNTAX      Counter32
   MAX-ACCESS  read-only
   STATUS      current
   DESCRIPTION
      "Path: pbbBridgeGroup.status.ipV6.dhcp.iaid

       32 bit unsigned wrappable counter."
   ::= {sr1645v2PbbBGriMVIpV6Entry 100728832}

sr1645v2PbbBGriMVIpV6RaRcvOption OBJECT-TYPE
   SYNTAX      Integer32
   MAX-ACCESS  read-only
   STATUS      current
   DESCRIPTION
      "Path: pbbBridgeGroup.status.ipV6.raRcvOption

       Bit meanings:
               bit 0 = linkMtu,
               bit 1 = srcLinkLayer,
               bit 2 = prefixInfo,
               bit 3 = rdnss,
               bit 4 = dnssl"
   ::= {sr1645v2PbbBGriMVIpV6Entry 117440512}

sr1645v2PbbBGriMVIpV6Addresses OBJECT-TYPE
   SYNTAX      SEQUENCE OF Sr1645v2PbbBGriMVIpV6AddressesEntry
   MAX-ACCESS  not-accessible
   STATUS      current
   DESCRIPTION
      ""
   ::= {sr1645v2PbbBGriMVIpV6 50331648}

sr1645v2PbbBGriMVIpV6AddressesEntry OBJECT-TYPE
   SYNTAX      Sr1645v2PbbBGriMVIpV6AddressesEntry
   MAX-ACCESS  not-accessible
   STATUS      current
   DESCRIPTION
      ""
   INDEX      { sr1645v2PbbBGriMVIpV6AddressesGlobalIx,
                sr1645v2PbbBGriMVIpV6AddressesTableIx }
   ::= {sr1645v2PbbBGriMVIpV6Addresses 1}

Sr1645v2PbbBGriMVIpV6AddressesEntry ::=
   SEQUENCE
      {
      sr1645v2PbbBGriMVIpV6AddressesGlobalIx
         GlobalIndex,
      sr1645v2PbbBGriMVIpV6AddressesTableIx
         TableIndex,
      sr1645v2PbbBGriMVIpV6AddressesAddress
         Ipv6Address,
      sr1645v2PbbBGriMVIpV6AddressesPrefixLength
         Integer32,
      sr1645v2PbbBGriMVIpV6AddressesStatus
         INTEGER,
      sr1645v2PbbBGriMVIpV6AddressesOrigin
         INTEGER,
      sr1645v2PbbBGriMVIpV6AddressesFlagsInterfaceId
         INTEGER,
      sr1645v2PbbBGriMVIpV6AddressesFlagsAnycast
         INTEGER,
      sr1645v2PbbBGriMVIpV6AddressesTimersValidLifeTime
         TimeTicks,
      sr1645v2PbbBGriMVIpV6AddressesTimersPrefLifeTime
         TimeTicks
      }

sr1645v2PbbBGriMVIpV6AddressesGlobalIx OBJECT-TYPE
   SYNTAX      GlobalIndex
   MAX-ACCESS  not-accessible
   STATUS      current
   DESCRIPTION
      "The value of the tlsCntTreeGlobalIndex of the MANAGED OBJECT."
   ::= {sr1645v2PbbBGriMVIpV6AddressesEntry 10}

sr1645v2PbbBGriMVIpV6AddressesTableIx OBJECT-TYPE
   SYNTAX      TableIndex
   MAX-ACCESS  not-accessible
   STATUS      current
   DESCRIPTION
      ""
   ::= {sr1645v2PbbBGriMVIpV6AddressesEntry 11}

sr1645v2PbbBGriMVIpV6AddressesAddress OBJECT-TYPE
   SYNTAX      Ipv6Address
   MAX-ACCESS  read-only
   STATUS      current
   DESCRIPTION
      "Path: pbbBridgeGroup.status.ipV6.addresses.address

       ipv6 address"
   ::= {sr1645v2PbbBGriMVIpV6AddressesEntry 16777216}

sr1645v2PbbBGriMVIpV6AddressesPrefixLength OBJECT-TYPE
   SYNTAX      Integer32
   MAX-ACCESS  read-only
   STATUS      current
   DESCRIPTION
      "Path: pbbBridgeGroup.status.ipV6.addresses.prefixLength"
   ::= {sr1645v2PbbBGriMVIpV6AddressesEntry 33554432}

sr1645v2PbbBGriMVIpV6AddressesStatus OBJECT-TYPE
   SYNTAX      INTEGER
               {
               invalid (0),
               tentative (1),
               deprecated (2),
               preferred (3)
               }
   MAX-ACCESS  read-only
   STATUS      current
   DESCRIPTION
      "Path: pbbBridgeGroup.status.ipV6.addresses.status

       Possibilities:
               invalid   (0)
               tentative   (1)
               deprecated   (2)
               preferred   (3)"
   ::= {sr1645v2PbbBGriMVIpV6AddressesEntry 50331648}

sr1645v2PbbBGriMVIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: pbbBridgeGroup.status.ipV6.addresses.origin

       Possibilities:
               unknown   (0)
               manual   (1)
               generalPrefix   (2)
               statelessAuto   (3)
               statefullAuto   (4)"
   ::= {sr1645v2PbbBGriMVIpV6AddressesEntry 67108864}

sr1645v2PbbBGriMVIpV6AddressesFlagsInterfaceId OBJECT-TYPE
   SYNTAX      INTEGER
               {
               no (0),
               yes (1)
               }
   MAX-ACCESS  read-only
   STATUS      current
   DESCRIPTION
      "Path: pbbBridgeGroup.status.ipV6.addresses.flags.interfaceId

       Possibilities:
               no   (0)
               yes   (1)"
   ::= {sr1645v2PbbBGriMVIpV6AddressesEntry 83951616}

sr1645v2PbbBGriMVIpV6AddressesFlagsAnycast OBJECT-TYPE
   SYNTAX      INTEGER
               {
               no (0),
               yes (1)
               }
   MAX-ACCESS  read-only
   STATUS      current
   DESCRIPTION
      "Path: pbbBridgeGroup.status.ipV6.addresses.flags.anycast

       Possibilities:
               no   (0)
               yes   (1)"
   ::= {sr1645v2PbbBGriMVIpV6AddressesEntry 84017152}

sr1645v2PbbBGriMVIpV6AddressesTimersValidLifeTime OBJECT-TYPE
   SYNTAX      TimeTicks
   MAX-ACCESS  read-only
   STATUS      current
   DESCRIPTION
      "Path: pbbBridgeGroup.status.ipV6.addresses.timers.validLifeTime

       Time in centi-second."
   ::= {sr1645v2PbbBGriMVIpV6AddressesEntry 100794368}

sr1645v2PbbBGriMVIpV6AddressesTimersPrefLifeTime OBJECT-TYPE
   SYNTAX      TimeTicks
   MAX-ACCESS  read-only
   STATUS      current
   DESCRIPTION
      "Path: pbbBridgeGroup.status.ipV6.addresses.timers.prefLifeTime

       Time in centi-second."
   ::= {sr1645v2PbbBGriMVIpV6AddressesEntry 100728832}


sr1645v2PbbBGriMVStp OBJECT IDENTIFIER ::= {sr1645v2PbbBGriMV 9}

sr1645v2PbbBGriMVStpSSCTable OBJECT-TYPE
   SYNTAX      SEQUENCE OF Sr1645v2PbbBGriMVStpEntry
   MAX-ACCESS  not-accessible
   STATUS      current
   DESCRIPTION
      "spanning tree info on bridge group"
   ::= {sr1645v2PbbBGriMVStp 1}

sr1645v2PbbBGriMVStpEntry OBJECT-TYPE
   SYNTAX      Sr1645v2PbbBGriMVStpEntry
   MAX-ACCESS  not-accessible
   STATUS      current
   DESCRIPTION
      ""
   INDEX      { sr1645v2PbbBGriMVStpGlobalIx }
   ::= {sr1645v2PbbBGriMVStpSSCTable 1}

Sr1645v2PbbBGriMVStpEntry ::=
   SEQUENCE
      {
      sr1645v2PbbBGriMVStpGlobalIx
         GlobalIndex,
      sr1645v2PbbBGriMVStpBridgePriority
         Integer32,
      sr1645v2PbbBGriMVStpBridgeMacAddress
         OCTET STRING,
      sr1645v2PbbBGriMVStpBridgeTimesMessageAge
         TimeTicks,
      sr1645v2PbbBGriMVStpBridgeTimesMaxAge
         TimeTicks,
      sr1645v2PbbBGriMVStpBridgeTimesForwardDelay
         TimeTicks,
      sr1645v2PbbBGriMVStpBridgeTimesNrHops
         Integer32,
      sr1645v2PbbBGriMVStpRootBridgeIdPriority
         Integer32,
      sr1645v2PbbBGriMVStpRootBridgeIdMacAddress
         OCTET STRING,
      sr1645v2PbbBGriMVStpRootPortId
         Integer32,
      sr1645v2PbbBGriMVStpExtRootPathCost
         Integer32,
      sr1645v2PbbBGriMVStpIntRootPathCost
         Integer32,
      sr1645v2PbbBGriMVStpMstConfigIdFormatSelector
         Integer32,
      sr1645v2PbbBGriMVStpMstConfigIdName
         DisplayString,
      sr1645v2PbbBGriMVStpMstConfigIdRevisionLevel
         Integer32,
      sr1645v2PbbBGriMVStpMstConfigIdDigest
         OCTET STRING
      }

sr1645v2PbbBGriMVStpGlobalIx OBJECT-TYPE
   SYNTAX      GlobalIndex
   MAX-ACCESS  not-accessible
   STATUS      current
   DESCRIPTION
      "The value of the tlsCntTreeGlobalIndex of the MANAGED OBJECT."
   ::= {sr1645v2PbbBGriMVStpEntry 10}

sr1645v2PbbBGriMVStpBridgePriority OBJECT-TYPE
   SYNTAX      Integer32
   MAX-ACCESS  read-only
   STATUS      current
   DESCRIPTION
      "Path: pbbBridgeGroup.status.spanningTree.bridgePriority"
   ::= {sr1645v2PbbBGriMVStpEntry 16777216}

sr1645v2PbbBGriMVStpBridgeMacAddress OBJECT-TYPE
   SYNTAX      OCTET STRING
   MAX-ACCESS  read-only
   STATUS      current
   DESCRIPTION
      "Path: pbbBridgeGroup.status.spanningTree.bridgeMacAddress

       MAC address."
   ::= {sr1645v2PbbBGriMVStpEntry 33554432}

sr1645v2PbbBGriMVStpBridgeTimesMessageAge OBJECT-TYPE
   SYNTAX      TimeTicks
   MAX-ACCESS  read-only
   STATUS      current
   DESCRIPTION
      "Path: pbbBridgeGroup.status.spanningTree.bridgeTimes.messageAge

       Time in centi-second."
   ::= {sr1645v2PbbBGriMVStpEntry 50397184}

sr1645v2PbbBGriMVStpBridgeTimesMaxAge OBJECT-TYPE
   SYNTAX      TimeTicks
   MAX-ACCESS  read-only
   STATUS      current
   DESCRIPTION
      "Path: pbbBridgeGroup.status.spanningTree.bridgeTimes.maxAge

       Time in centi-second."
   ::= {sr1645v2PbbBGriMVStpEntry 50462720}

sr1645v2PbbBGriMVStpBridgeTimesForwardDelay OBJECT-TYPE
   SYNTAX      TimeTicks
   MAX-ACCESS  read-only
   STATUS      current
   DESCRIPTION
      "Path: pbbBridgeGroup.status.spanningTree.bridgeTimes.forwardDelay

       Time in centi-second."
   ::= {sr1645v2PbbBGriMVStpEntry 50528256}

sr1645v2PbbBGriMVStpBridgeTimesNrHops OBJECT-TYPE
   SYNTAX      Integer32
   MAX-ACCESS  read-only
   STATUS      current
   DESCRIPTION
      "Path: pbbBridgeGroup.status.spanningTree.bridgeTimes.nrHops"
   ::= {sr1645v2PbbBGriMVStpEntry 50593792}

sr1645v2PbbBGriMVStpRootBridgeIdPriority OBJECT-TYPE
   SYNTAX      Integer32
   MAX-ACCESS  read-only
   STATUS      current
   DESCRIPTION
      "Path: pbbBridgeGroup.status.spanningTree.rootBridgeId.priority"
   ::= {sr1645v2PbbBGriMVStpEntry 67174400}

sr1645v2PbbBGriMVStpRootBridgeIdMacAddress OBJECT-TYPE
   SYNTAX      OCTET STRING
   MAX-ACCESS  read-only
   STATUS      current
   DESCRIPTION
      "Path: pbbBridgeGroup.status.spanningTree.rootBridgeId.macAddress

       MAC address."
   ::= {sr1645v2PbbBGriMVStpEntry 67239936}

sr1645v2PbbBGriMVStpRootPortId OBJECT-TYPE
   SYNTAX      Integer32
   MAX-ACCESS  read-only
   STATUS      current
   DESCRIPTION
      "Path: pbbBridgeGroup.status.spanningTree.rootPortId"
   ::= {sr1645v2PbbBGriMVStpEntry 83886080}

sr1645v2PbbBGriMVStpExtRootPathCost OBJECT-TYPE
   SYNTAX      Integer32
   MAX-ACCESS  read-only
   STATUS      current
   DESCRIPTION
      "Path: pbbBridgeGroup.status.spanningTree.extRootPathCost"
   ::= {sr1645v2PbbBGriMVStpEntry 100663296}

sr1645v2PbbBGriMVStpIntRootPathCost OBJECT-TYPE
   SYNTAX      Integer32
   MAX-ACCESS  read-only
   STATUS      current
   DESCRIPTION
      "Path: pbbBridgeGroup.status.spanningTree.intRootPathCost"
   ::= {sr1645v2PbbBGriMVStpEntry 117440512}

sr1645v2PbbBGriMVStpMstConfigIdFormatSelector OBJECT-TYPE
   SYNTAX      Integer32
   MAX-ACCESS  read-only
   STATUS      current
   DESCRIPTION
      "Path: pbbBridgeGroup.status.spanningTree.mstConfigId.formatSelector"
   ::= {sr1645v2PbbBGriMVStpEntry 134283264}

sr1645v2PbbBGriMVStpMstConfigIdName OBJECT-TYPE
   SYNTAX      DisplayString
   MAX-ACCESS  read-only
   STATUS      current
   DESCRIPTION
      "Path: pbbBridgeGroup.status.spanningTree.mstConfigId.name"
   ::= {sr1645v2PbbBGriMVStpEntry 134348800}

sr1645v2PbbBGriMVStpMstConfigIdRevisionLevel OBJECT-TYPE
   SYNTAX      Integer32
   MAX-ACCESS  read-only
   STATUS      current
   DESCRIPTION
      "Path: pbbBridgeGroup.status.spanningTree.mstConfigId.revisionLevel"
   ::= {sr1645v2PbbBGriMVStpEntry 134414336}

sr1645v2PbbBGriMVStpMstConfigIdDigest OBJECT-TYPE
   SYNTAX      OCTET STRING
   MAX-ACCESS  read-only
   STATUS      current
   DESCRIPTION
      "Path: pbbBridgeGroup.status.spanningTree.mstConfigId.digest"
   ::= {sr1645v2PbbBGriMVStpEntry 134479872}


sr1645v2PbbBGriMVArpCache OBJECT IDENTIFIER ::= {sr1645v2PbbBGriMV 13}

sr1645v2PbbBGriMVArpCacheSSCTable OBJECT-TYPE
   SYNTAX      SEQUENCE OF Sr1645v2PbbBGriMVArpCacheEntry
   MAX-ACCESS  not-accessible
   STATUS      current
   DESCRIPTION
      "arp cache of ethernet interface"
   ::= {sr1645v2PbbBGriMVArpCache 1}

sr1645v2PbbBGriMVArpCacheEntry OBJECT-TYPE
   SYNTAX      Sr1645v2PbbBGriMVArpCacheEntry
   MAX-ACCESS  not-accessible
   STATUS      current
   DESCRIPTION
      ""
   INDEX      { sr1645v2PbbBGriMVArpCacheGlobalIx,
                sr1645v2PbbBGriMVArpCacheTableIx }
   ::= {sr1645v2PbbBGriMVArpCacheSSCTable 1}

Sr1645v2PbbBGriMVArpCacheEntry ::=
   SEQUENCE
      {
      sr1645v2PbbBGriMVArpCacheGlobalIx
         GlobalIndex,
      sr1645v2PbbBGriMVArpCacheTableIx
         TableIndex,
      sr1645v2PbbBGriMVArpCacheMacAddress
         OCTET STRING,
      sr1645v2PbbBGriMVArpCacheIpAddress
         IpAddress,
      sr1645v2PbbBGriMVArpCacheType
         INTEGER,
      sr1645v2PbbBGriMVArpCacheTimeOut
         TimeTicks
      }

sr1645v2PbbBGriMVArpCacheGlobalIx OBJECT-TYPE
   SYNTAX      GlobalIndex
   MAX-ACCESS  not-accessible
   STATUS      current
   DESCRIPTION
      "The value of the tlsCntTreeGlobalIndex of the MANAGED OBJECT."
   ::= {sr1645v2PbbBGriMVArpCacheEntry 10}

sr1645v2PbbBGriMVArpCacheTableIx OBJECT-TYPE
   SYNTAX      TableIndex
   MAX-ACCESS  not-accessible
   STATUS      current
   DESCRIPTION
      ""
   ::= {sr1645v2PbbBGriMVArpCacheEntry 11}

sr1645v2PbbBGriMVArpCacheMacAddress OBJECT-TYPE
   SYNTAX      OCTET STRING
   MAX-ACCESS  read-only
   STATUS      current
   DESCRIPTION
      "Path: pbbBridgeGroup.status.arpCache.macAddress

       MAC address."
   ::= {sr1645v2PbbBGriMVArpCacheEntry 16777216}

sr1645v2PbbBGriMVArpCacheIpAddress OBJECT-TYPE
   SYNTAX      IpAddress
   MAX-ACCESS  read-only
   STATUS      current
   DESCRIPTION
      "Path: pbbBridgeGroup.status.arpCache.ipAddress"
   ::= {sr1645v2PbbBGriMVArpCacheEntry 33554432}

sr1645v2PbbBGriMVArpCacheType OBJECT-TYPE
   SYNTAX      INTEGER
               {
               static (0),
               dynamic (1)
               }
   MAX-ACCESS  read-only
   STATUS      current
   DESCRIPTION
      "Path: pbbBridgeGroup.status.arpCache.type

       Possibilities:
               static   (0)
               dynamic   (1)"
   ::= {sr1645v2PbbBGriMVArpCacheEntry 50331648}

sr1645v2PbbBGriMVArpCacheTimeOut OBJECT-TYPE
   SYNTAX      TimeTicks
   MAX-ACCESS  read-only
   STATUS      current
   DESCRIPTION
      "Path: pbbBridgeGroup.status.arpCache.timeOut

       Time in centi-second."
   ::= {sr1645v2PbbBGriMVArpCacheEntry 67108864}


sr1645v2PbbBGriMVVlan OBJECT IDENTIFIER ::= {sr1645v2PbbBGriMV 34}

sr1645v2PbbBGriMVVlanSSCTable OBJECT-TYPE
   SYNTAX      SEQUENCE OF Sr1645v2PbbBGriMVVlanEntry
   MAX-ACCESS  not-accessible
   STATUS      current
   DESCRIPTION
      ""
   ::= {sr1645v2PbbBGriMVVlan 1}

sr1645v2PbbBGriMVVlanEntry OBJECT-TYPE
   SYNTAX      Sr1645v2PbbBGriMVVlanEntry
   MAX-ACCESS  not-accessible
   STATUS      current
   DESCRIPTION
      ""
   INDEX      { sr1645v2PbbBGriMVVlanGlobalIx,
                sr1645v2PbbBGriMVVlanTableIx }
   ::= {sr1645v2PbbBGriMVVlanSSCTable 1}

Sr1645v2PbbBGriMVVlanEntry ::=
   SEQUENCE
      {
      sr1645v2PbbBGriMVVlanGlobalIx
         GlobalIndex,
      sr1645v2PbbBGriMVVlanTableIx
         TableIndex,
      sr1645v2PbbBGriMVVlanName
         DisplayString,
      sr1645v2PbbBGriMVVlanMode
         INTEGER,
      sr1645v2PbbBGriMVVlanIfOperStatus
         INTEGER,
      sr1645v2PbbBGriMVVlanIfLastChange
         TimeTicks,
      sr1645v2PbbBGriMVVlanIfLastChangeDate
         DisplayString,
      sr1645v2PbbBGriMVVlanIpAddress
         IpAddress,
      sr1645v2PbbBGriMVVlanIpNetMask
         IpAddress,
      sr1645v2PbbBGriMVVlanIpDhcpStatus
         INTEGER,
      sr1645v2PbbBGriMVVlanIpDhcpLeaseTime
         TimeTicks,
      sr1645v2PbbBGriMVVlanIpV6State
         INTEGER,
      sr1645v2PbbBGriMVVlanIpV6InterfaceId
         OCTET STRING,
      sr1645v2PbbBGriMVVlanIpV6LinkMtu
         Integer32,
      sr1645v2PbbBGriMVVlanIpV6HopLimit
         Integer32,
      sr1645v2PbbBGriMVVlanIpV6DhcpIaid
         Counter32,
      sr1645v2PbbBGriMVVlanIpV6RaRcvOption
         Integer32,
      sr1645v2PbbBGriMVVlanVlanVid
         Integer32
      }

sr1645v2PbbBGriMVVlanGlobalIx OBJECT-TYPE
   SYNTAX      GlobalIndex
   MAX-ACCESS  not-accessible
   STATUS      current
   DESCRIPTION
      "The value of the tlsCntTreeGlobalIndex of the MANAGED OBJECT."
   ::= {sr1645v2PbbBGriMVVlanEntry 10}

sr1645v2PbbBGriMVVlanTableIx OBJECT-TYPE
   SYNTAX      TableIndex
   MAX-ACCESS  not-accessible
   STATUS      current
   DESCRIPTION
      ""
   ::= {sr1645v2PbbBGriMVVlanEntry 11}

sr1645v2PbbBGriMVVlanName OBJECT-TYPE
   SYNTAX      DisplayString
   MAX-ACCESS  read-only
   STATUS      current
   DESCRIPTION
      "Path: pbbBridgeGroup.status.vlan.name"
   ::= {sr1645v2PbbBGriMVVlanEntry 16777216}

sr1645v2PbbBGriMVVlanMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: pbbBridgeGroup.status.vlan.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2PbbBGriMVVlanEntry 335544320}

sr1645v2PbbBGriMVVlanIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: pbbBridgeGroup.status.vlan.ifOperStatus

       Possibilities:
               up   (1)
               down   (2)
               testing   (3)
               unknown   (4)
               dormant   (5)
               notPresent   (6)
               lowerLayerDown   (7)"
   ::= {sr1645v2PbbBGriMVVlanEntry 1795162112}

sr1645v2PbbBGriMVVlanIfLastChange OBJECT-TYPE
   SYNTAX      TimeTicks
   MAX-ACCESS  read-only
   STATUS      current
   DESCRIPTION
      "Path: pbbBridgeGroup.status.vlan.ifLastChange

       Time in centi-second."
   ::= {sr1645v2PbbBGriMVVlanEntry 1811939328}

sr1645v2PbbBGriMVVlanIfLastChangeDate OBJECT-TYPE
   SYNTAX      DisplayString
   MAX-ACCESS  read-only
   STATUS      current
   DESCRIPTION
      "Path: pbbBridgeGroup.status.vlan.ifLastChangeDate"
   ::= {sr1645v2PbbBGriMVVlanEntry 3070230528}

sr1645v2PbbBGriMVVlanIpAddress OBJECT-TYPE
   SYNTAX      IpAddress
   MAX-ACCESS  read-only
   STATUS      current
   DESCRIPTION
      "Path: pbbBridgeGroup.status.vlan.ip.address"
   ::= {sr1645v2PbbBGriMVVlanEntry 51380224}

sr1645v2PbbBGriMVVlanIpNetMask OBJECT-TYPE
   SYNTAX      IpAddress
   MAX-ACCESS  read-only
   STATUS      current
   DESCRIPTION
      "Path: pbbBridgeGroup.status.vlan.ip.netMask"
   ::= {sr1645v2PbbBGriMVVlanEntry 51445760}

sr1645v2PbbBGriMVVlanIpDhcpStatus OBJECT-TYPE
   SYNTAX      INTEGER
               {
               none (0),
               selecting (1),
               requesting (2),
               rebinding (3),
               bound (4),
               renewing (5),
               rebooting (6),
               initreboot (7)
               }
   MAX-ACCESS  read-only
   STATUS      current
   DESCRIPTION
      "Path: pbbBridgeGroup.status.vlan.ip.dhcp.status

       Possibilities:
               none   (0)
               selecting   (1)
               requesting   (2)
               rebinding   (3)
               bound   (4)
               renewing   (5)
               rebooting   (6)
               initreboot   (7)"
   ::= {sr1645v2PbbBGriMVVlanEntry 51904768}

sr1645v2PbbBGriMVVlanIpDhcpLeaseTime OBJECT-TYPE
   SYNTAX      TimeTicks
   MAX-ACCESS  read-only
   STATUS      current
   DESCRIPTION
      "Path: pbbBridgeGroup.status.vlan.ip.dhcp.leaseTime

       Time in centi-second."
   ::= {sr1645v2PbbBGriMVVlanEntry 51905024}

sr1645v2PbbBGriMVVlanIpV6State OBJECT-TYPE
   SYNTAX      INTEGER
               {
               disabled (0),
               enabled (1)
               }
   MAX-ACCESS  read-only
   STATUS      current
   DESCRIPTION
      "Path: pbbBridgeGroup.status.vlan.ipV6.state

       Possibilities:
               disabled   (0)
               enabled   (1)"
   ::= {sr1645v2PbbBGriMVVlanEntry 100728832}

sr1645v2PbbBGriMVVlanIpV6InterfaceId OBJECT-TYPE
   SYNTAX      OCTET STRING
   MAX-ACCESS  read-only
   STATUS      current
   DESCRIPTION
      "Path: pbbBridgeGroup.status.vlan.ipV6.interfaceId"
   ::= {sr1645v2PbbBGriMVVlanEntry 100794368}

sr1645v2PbbBGriMVVlanIpV6LinkMtu OBJECT-TYPE
   SYNTAX      Integer32
   MAX-ACCESS  read-only
   STATUS      current
   DESCRIPTION
      "Path: pbbBridgeGroup.status.vlan.ipV6.linkMtu"
   ::= {sr1645v2PbbBGriMVVlanEntry 100925440}

sr1645v2PbbBGriMVVlanIpV6HopLimit OBJECT-TYPE
   SYNTAX      Integer32
   MAX-ACCESS  read-only
   STATUS      current
   DESCRIPTION
      "Path: pbbBridgeGroup.status.vlan.ipV6.hopLimit"
   ::= {sr1645v2PbbBGriMVVlanEntry 100990976}

sr1645v2PbbBGriMVVlanIpV6DhcpIaid OBJECT-TYPE
   SYNTAX      Counter32
   MAX-ACCESS  read-only
   STATUS      current
   DESCRIPTION
      "Path: pbbBridgeGroup.status.vlan.ipV6.dhcp.iaid

       32 bit unsigned wrappable counter."
   ::= {sr1645v2PbbBGriMVVlanEntry 101056768}

sr1645v2PbbBGriMVVlanIpV6RaRcvOption OBJECT-TYPE
   SYNTAX      Integer32
   MAX-ACCESS  read-only
   STATUS      current
   DESCRIPTION
      "Path: pbbBridgeGroup.status.vlan.ipV6.raRcvOption

       Bit meanings:
               bit 0 = linkMtu,
               bit 1 = srcLinkLayer,
               bit 2 = prefixInfo,
               bit 3 = rdnss,
               bit 4 = dnssl"
   ::= {sr1645v2PbbBGriMVVlanEntry 101122048}

sr1645v2PbbBGriMVVlanVlanVid OBJECT-TYPE
   SYNTAX      Integer32
   MAX-ACCESS  read-only
   STATUS      current
   DESCRIPTION
      "Path: pbbBridgeGroup.status.vlan.vlan.vid"
   ::= {sr1645v2PbbBGriMVVlanEntry 234946560}

sr1645v2PbbBGriMVVlanIpSecondaryIp OBJECT-TYPE
   SYNTAX      SEQUENCE OF Sr1645v2PbbBGriMVVlanIpSecondaryIpEntry
   MAX-ACCESS  not-accessible
   STATUS      current
   DESCRIPTION
      ""
   ::= {sr1645v2PbbBGriMVVlan 51838976}

sr1645v2PbbBGriMVVlanIpSecondaryIpEntry OBJECT-TYPE
   SYNTAX      Sr1645v2PbbBGriMVVlanIpSecondaryIpEntry
   MAX-ACCESS  not-accessible
   STATUS      current
   DESCRIPTION
      ""
   INDEX      { sr1645v2PbbBGriMVVlanIpSecondaryIpGlobalIx,
                sr1645v2PbbBGriMVVlanTableIx,
                sr1645v2PbbBGriMVVlanIpSecondaryIpTableIx }
   ::= {sr1645v2PbbBGriMVVlanIpSecondaryIp 1}

Sr1645v2PbbBGriMVVlanIpSecondaryIpEntry ::=
   SEQUENCE
      {
      sr1645v2PbbBGriMVVlanIpSecondaryIpGlobalIx
         GlobalIndex,
      sr1645v2PbbBGriMVVlanIpSecondaryIpTableIx
         TableIndex,
      sr1645v2PbbBGriMVVlanIpSecondaryIpAddress
         IpAddress,
      sr1645v2PbbBGriMVVlanIpSecondaryIpNetMask
         IpAddress
      }

sr1645v2PbbBGriMVVlanIpSecondaryIpGlobalIx OBJECT-TYPE
   SYNTAX      GlobalIndex
   MAX-ACCESS  not-accessible
   STATUS      current
   DESCRIPTION
      "The value of the tlsCntTreeGlobalIndex of the MANAGED OBJECT."
   ::= {sr1645v2PbbBGriMVVlanIpSecondaryIpEntry 10}

sr1645v2PbbBGriMVVlanIpSecondaryIpTableIx OBJECT-TYPE
   SYNTAX      TableIndex
   MAX-ACCESS  not-accessible
   STATUS      current
   DESCRIPTION
      ""
   ::= {sr1645v2PbbBGriMVVlanIpSecondaryIpEntry 11}

sr1645v2PbbBGriMVVlanIpSecondaryIpAddress OBJECT-TYPE
   SYNTAX      IpAddress
   MAX-ACCESS  read-only
   STATUS      current
   DESCRIPTION
      "Path: pbbBridgeGroup.status.vlan.ip.secondaryIp.address"
   ::= {sr1645v2PbbBGriMVVlanIpSecondaryIpEntry 2030043136}

sr1645v2PbbBGriMVVlanIpSecondaryIpNetMask OBJECT-TYPE
   SYNTAX      IpAddress
   MAX-ACCESS  read-only
   STATUS      current
   DESCRIPTION
      "Path: pbbBridgeGroup.status.vlan.ip.secondaryIp.netMask"
   ::= {sr1645v2PbbBGriMVVlanIpSecondaryIpEntry 2063597568}

sr1645v2PbbBGriMVVlanIpV6Addresses OBJECT-TYPE
   SYNTAX      SEQUENCE OF Sr1645v2PbbBGriMVVlanIpV6AddressesEntry
   MAX-ACCESS  not-accessible
   STATUS      current
   DESCRIPTION
      ""
   ::= {sr1645v2PbbBGriMVVlan 100859904}

sr1645v2PbbBGriMVVlanIpV6AddressesEntry OBJECT-TYPE
   SYNTAX      Sr1645v2PbbBGriMVVlanIpV6AddressesEntry
   MAX-ACCESS  not-accessible
   STATUS      current
   DESCRIPTION
      ""
   INDEX      { sr1645v2PbbBGriMVVlanIpV6AddressesGlobalIx,
                sr1645v2PbbBGriMVVlanTableIx,
                sr1645v2PbbBGriMVVlanIpV6AddressesTableIx }
   ::= {sr1645v2PbbBGriMVVlanIpV6Addresses 1}

Sr1645v2PbbBGriMVVlanIpV6AddressesEntry ::=
   SEQUENCE
      {
      sr1645v2PbbBGriMVVlanIpV6AddressesGlobalIx
         GlobalIndex,
      sr1645v2PbbBGriMVVlanIpV6AddressesTableIx
         TableIndex,
      sr1645v2PbbBGriMVVlanIpV6AddressesAddress
         Ipv6Address,
      sr1645v2PbbBGriMVVlanIpV6AddressesPrefixLength
         Integer32,
      sr1645v2PbbBGriMVVlanIpV6AddressesStatus
         INTEGER,
      sr1645v2PbbBGriMVVlanIpV6AddressesOrigin
         INTEGER,
      sr1645v2PbbBGriMVVlanIpV6AddressesFlagsInterfaceId
         INTEGER,
      sr1645v2PbbBGriMVVlanIpV6AddressesFlagsAnycast
         INTEGER,
      sr1645v2PbbBGriMVVlanIpV6AddressesTimersValidLifeTime
         TimeTicks,
      sr1645v2PbbBGriMVVlanIpV6AddressesTimersPrefLifeTime
         TimeTicks
      }

sr1645v2PbbBGriMVVlanIpV6AddressesGlobalIx OBJECT-TYPE
   SYNTAX      GlobalIndex
   MAX-ACCESS  not-accessible
   STATUS      current
   DESCRIPTION
      "The value of the tlsCntTreeGlobalIndex of the MANAGED OBJECT."
   ::= {sr1645v2PbbBGriMVVlanIpV6AddressesEntry 10}

sr1645v2PbbBGriMVVlanIpV6AddressesTableIx OBJECT-TYPE
   SYNTAX      TableIndex
   MAX-ACCESS  not-accessible
   STATUS      current
   DESCRIPTION
      ""
   ::= {sr1645v2PbbBGriMVVlanIpV6AddressesEntry 11}

sr1645v2PbbBGriMVVlanIpV6AddressesAddress OBJECT-TYPE
   SYNTAX      Ipv6Address
   MAX-ACCESS  read-only
   STATUS      current
   DESCRIPTION
      "Path: pbbBridgeGroup.status.vlan.ipV6.addresses.address

       ipv6 address"
   ::= {sr1645v2PbbBGriMVVlanIpV6AddressesEntry 16777216}

sr1645v2PbbBGriMVVlanIpV6AddressesPrefixLength OBJECT-TYPE
   SYNTAX      Integer32
   MAX-ACCESS  read-only
   STATUS      current
   DESCRIPTION
      "Path: pbbBridgeGroup.status.vlan.ipV6.addresses.prefixLength"
   ::= {sr1645v2PbbBGriMVVlanIpV6AddressesEntry 33554432}

sr1645v2PbbBGriMVVlanIpV6AddressesStatus OBJECT-TYPE
   SYNTAX      INTEGER
               {
               invalid (0),
               tentative (1),
               deprecated (2),
               preferred (3)
               }
   MAX-ACCESS  read-only
   STATUS      current
   DESCRIPTION
      "Path: pbbBridgeGroup.status.vlan.ipV6.addresses.status

       Possibilities:
               invalid   (0)
               tentative   (1)
               deprecated   (2)
               preferred   (3)"
   ::= {sr1645v2PbbBGriMVVlanIpV6AddressesEntry 50331648}

sr1645v2PbbBGriMVVlanIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: pbbBridgeGroup.status.vlan.ipV6.addresses.origin

       Possibilities:
               unknown   (0)
               manual   (1)
               generalPrefix   (2)
               statelessAuto   (3)
               statefullAuto   (4)"
   ::= {sr1645v2PbbBGriMVVlanIpV6AddressesEntry 67108864}

sr1645v2PbbBGriMVVlanIpV6AddressesFlagsInterfaceId OBJECT-TYPE
   SYNTAX      INTEGER
               {
               no (0),
               yes (1)
               }
   MAX-ACCESS  read-only
   STATUS      current
   DESCRIPTION
      "Path: pbbBridgeGroup.status.vlan.ipV6.addresses.flags.interfaceId

       Possibilities:
               no   (0)
               yes   (1)"
   ::= {sr1645v2PbbBGriMVVlanIpV6AddressesEntry 83951616}

sr1645v2PbbBGriMVVlanIpV6AddressesFlagsAnycast OBJECT-TYPE
   SYNTAX      INTEGER
               {
               no (0),
               yes (1)
               }
   MAX-ACCESS  read-only
   STATUS      current
   DESCRIPTION
      "Path: pbbBridgeGroup.status.vlan.ipV6.addresses.flags.anycast

       Possibilities:
               no   (0)
               yes   (1)"
   ::= {sr1645v2PbbBGriMVVlanIpV6AddressesEntry 84017152}

sr1645v2PbbBGriMVVlanIpV6AddressesTimersValidLifeTime OBJECT-TYPE
   SYNTAX      TimeTicks
   MAX-ACCESS  read-only
   STATUS      current
   DESCRIPTION
      "Path: pbbBridgeGroup.status.vlan.ipV6.addresses.timers.validLifeTime

       Time in centi-second."
   ::= {sr1645v2PbbBGriMVVlanIpV6AddressesEntry 100794368}

sr1645v2PbbBGriMVVlanIpV6AddressesTimersPrefLifeTime OBJECT-TYPE
   SYNTAX      TimeTicks
   MAX-ACCESS  read-only
   STATUS      current
   DESCRIPTION
      "Path: pbbBridgeGroup.status.vlan.ipV6.addresses.timers.prefLifeTime

       Time in centi-second."
   ::= {sr1645v2PbbBGriMVVlanIpV6AddressesEntry 100728832}

sr1645v2PbbBGriMVVlanVlanArpCache OBJECT-TYPE
   SYNTAX      SEQUENCE OF Sr1645v2PbbBGriMVVlanVlanArpCacheEntry
   MAX-ACCESS  not-accessible
   STATUS      current
   DESCRIPTION
      ""
   ::= {sr1645v2PbbBGriMVVlan 235601920}

sr1645v2PbbBGriMVVlanVlanArpCacheEntry OBJECT-TYPE
   SYNTAX      Sr1645v2PbbBGriMVVlanVlanArpCacheEntry
   MAX-ACCESS  not-accessible
   STATUS      current
   DESCRIPTION
      ""
   INDEX      { sr1645v2PbbBGriMVVlanVlanArpCacheGlobalIx,
                sr1645v2PbbBGriMVVlanTableIx,
                sr1645v2PbbBGriMVVlanVlanArpCacheTableIx }
   ::= {sr1645v2PbbBGriMVVlanVlanArpCache 1}

Sr1645v2PbbBGriMVVlanVlanArpCacheEntry ::=
   SEQUENCE
      {
      sr1645v2PbbBGriMVVlanVlanArpCacheGlobalIx
         GlobalIndex,
      sr1645v2PbbBGriMVVlanVlanArpCacheTableIx
         TableIndex,
      sr1645v2PbbBGriMVVlanVlanArpCacheMacAddress
         OCTET STRING,
      sr1645v2PbbBGriMVVlanVlanArpCacheIpAddress
         IpAddress,
      sr1645v2PbbBGriMVVlanVlanArpCacheType
         INTEGER,
      sr1645v2PbbBGriMVVlanVlanArpCacheTimeOut
         TimeTicks
      }

sr1645v2PbbBGriMVVlanVlanArpCacheGlobalIx OBJECT-TYPE
   SYNTAX      GlobalIndex
   MAX-ACCESS  not-accessible
   STATUS      current
   DESCRIPTION
      "The value of the tlsCntTreeGlobalIndex of the MANAGED OBJECT."
   ::= {sr1645v2PbbBGriMVVlanVlanArpCacheEntry 10}

sr1645v2PbbBGriMVVlanVlanArpCacheTableIx OBJECT-TYPE
   SYNTAX      TableIndex
   MAX-ACCESS  not-accessible
   STATUS      current
   DESCRIPTION
      ""
   ::= {sr1645v2PbbBGriMVVlanVlanArpCacheEntry 11}

sr1645v2PbbBGriMVVlanVlanArpCacheMacAddress OBJECT-TYPE
   SYNTAX      OCTET STRING
   MAX-ACCESS  read-only
   STATUS      current
   DESCRIPTION
      "Path: pbbBridgeGroup.status.vlan.vlan.arpCache.macAddress

       MAC address."
   ::= {sr1645v2PbbBGriMVVlanVlanArpCacheEntry 16777216}

sr1645v2PbbBGriMVVlanVlanArpCacheIpAddress OBJECT-TYPE
   SYNTAX      IpAddress
   MAX-ACCESS  read-only
   STATUS      current
   DESCRIPTION
      "Path: pbbBridgeGroup.status.vlan.vlan.arpCache.ipAddress"
   ::= {sr1645v2PbbBGriMVVlanVlanArpCacheEntry 33554432}

sr1645v2PbbBGriMVVlanVlanArpCacheType OBJECT-TYPE
   SYNTAX      INTEGER
               {
               static (0),
               dynamic (1)
               }
   MAX-ACCESS  read-only
   STATUS      current
   DESCRIPTION
      "Path: pbbBridgeGroup.status.vlan.vlan.arpCache.type

       Possibilities:
               static   (0)
               dynamic   (1)"
   ::= {sr1645v2PbbBGriMVVlanVlanArpCacheEntry 50331648}

sr1645v2PbbBGriMVVlanVlanArpCacheTimeOut OBJECT-TYPE
   SYNTAX      TimeTicks
   MAX-ACCESS  read-only
   STATUS      current
   DESCRIPTION
      "Path: pbbBridgeGroup.status.vlan.vlan.arpCache.timeOut

       Time in centi-second."
   ::= {sr1645v2PbbBGriMVVlanVlanArpCacheEntry 67108864}


sr1645v2PbbBGriMVPppOE OBJECT IDENTIFIER ::= {sr1645v2PbbBGriMV 81}

sr1645v2PbbBGriMVPppOESSCTable OBJECT-TYPE
   SYNTAX      SEQUENCE OF Sr1645v2PbbBGriMVPppOEEntry
   MAX-ACCESS  not-accessible
   STATUS      current
   DESCRIPTION
      ""
   ::= {sr1645v2PbbBGriMVPppOE 1}

sr1645v2PbbBGriMVPppOEEntry OBJECT-TYPE
   SYNTAX      Sr1645v2PbbBGriMVPppOEEntry
   MAX-ACCESS  not-accessible
   STATUS      current
   DESCRIPTION
      ""
   INDEX      { sr1645v2PbbBGriMVPppOEGlobalIx,
                sr1645v2PbbBGriMVPppOETableIx }
   ::= {sr1645v2PbbBGriMVPppOESSCTable 1}

Sr1645v2PbbBGriMVPppOEEntry ::=
   SEQUENCE
      {
      sr1645v2PbbBGriMVPppOEGlobalIx
         GlobalIndex,
      sr1645v2PbbBGriMVPppOETableIx
         TableIndex,
      sr1645v2PbbBGriMVPppOEName
         DisplayString,
      sr1645v2PbbBGriMVPppOEMode
         INTEGER,
      sr1645v2PbbBGriMVPppOEIfOperStatus
         INTEGER,
      sr1645v2PbbBGriMVPppOEIfLastChange
         TimeTicks,
      sr1645v2PbbBGriMVPppOEIfLastChangeDate
         DisplayString,
      sr1645v2PbbBGriMVPppOEIpAddress
         IpAddress,
      sr1645v2PbbBGriMVPppOEIpNetMask
         IpAddress,
      sr1645v2PbbBGriMVPppOEIpRemote
         IpAddress,
      sr1645v2PbbBGriMVPppOEPppOEthDiscState
         INTEGER,
      sr1645v2PbbBGriMVPppOEPppOEthPeerMac
         OCTET STRING,
      sr1645v2PbbBGriMVPppOEPppOEthServiceName
         DisplayString,
      sr1645v2PbbBGriMVPppOEPppLcpState
         INTEGER,
      sr1645v2PbbBGriMVPppOEPppIpcpState
         INTEGER,
      sr1645v2PbbBGriMVPppOEPppIp6cpState
         INTEGER,
      sr1645v2PbbBGriMVPppOEPppMyAutSt
         INTEGER,
      sr1645v2PbbBGriMVPppOEPppHisAutSt
         INTEGER,
      sr1645v2PbbBGriMVPppOEPppMru
         Integer32,
      sr1645v2PbbBGriMVPppOEIpV6State
         INTEGER,
      sr1645v2PbbBGriMVPppOEIpV6InterfaceId
         OCTET STRING,
      sr1645v2PbbBGriMVPppOEIpV6LinkMtu
         Integer32,
      sr1645v2PbbBGriMVPppOEIpV6HopLimit
         Integer32,
      sr1645v2PbbBGriMVPppOEIpV6DhcpIaid
         Counter32,
      sr1645v2PbbBGriMVPppOEIpV6RaRcvOption
         Integer32
      }

sr1645v2PbbBGriMVPppOEGlobalIx OBJECT-TYPE
   SYNTAX      GlobalIndex
   MAX-ACCESS  not-accessible
   STATUS      current
   DESCRIPTION
      "The value of the tlsCntTreeGlobalIndex of the MANAGED OBJECT."
   ::= {sr1645v2PbbBGriMVPppOEEntry 10}

sr1645v2PbbBGriMVPppOETableIx OBJECT-TYPE
   SYNTAX      TableIndex
   MAX-ACCESS  not-accessible
   STATUS      current
   DESCRIPTION
      ""
   ::= {sr1645v2PbbBGriMVPppOEEntry 11}

sr1645v2PbbBGriMVPppOEName OBJECT-TYPE
   SYNTAX      DisplayString
   MAX-ACCESS  read-only
   STATUS      current
   DESCRIPTION
      "Path: pbbBridgeGroup.status.pppoEClient.name"
   ::= {sr1645v2PbbBGriMVPppOEEntry 16777216}

sr1645v2PbbBGriMVPppOEMode OBJECT-TYPE
   SYNTAX      INTEGER
               {
               ces (0),
               routing (1),
               bridging (2),
               routingAndBridging (3),
               switching (4),
               frf5 (5),
               frf8 (6),
               multilink (8),
               ipV6 (16),
               ipV6ipV4 (17),
               virtEthernet (32)
               }
   MAX-ACCESS  read-only
   STATUS      current
   DESCRIPTION
      "Path: pbbBridgeGroup.status.pppoEClient.mode

       Possibilities:
               ces   (0)
               routing   (1)
               bridging   (2)
               routingAndBridging   (3)
               switching   (4)
               frf5   (5)
               frf8   (6)
               multilink   (8)
               ipV6   (16)
               ipV6/ipV4   (17)
               virtEthernet   (32)"
   ::= {sr1645v2PbbBGriMVPppOEEntry 335544320}

sr1645v2PbbBGriMVPppOEIfOperStatus OBJECT-TYPE
   SYNTAX      INTEGER
               {
               up (1),
               down (2),
               testing (3),
               unknown (4),
               dormant (5),
               notPresent (6),
               lowerLayerDown (7)
               }
   MAX-ACCESS  read-only
   STATUS      current
   DESCRIPTION
      "Path: pbbBridgeGroup.status.pppoEClient.ifOperStatus

       Possibilities:
               up   (1)
               down   (2)
               testing   (3)
               unknown   (4)
               dormant   (5)
               notPresent   (6)
               lowerLayerDown   (7)"
   ::= {sr1645v2PbbBGriMVPppOEEntry 1795162112}

sr1645v2PbbBGriMVPppOEIfLastChange OBJECT-TYPE
   SYNTAX      TimeTicks
   MAX-ACCESS  read-only
   STATUS      current
   DESCRIPTION
      "Path: pbbBridgeGroup.status.pppoEClient.ifLastChange

       Time in centi-second."
   ::= {sr1645v2PbbBGriMVPppOEEntry 1811939328}

sr1645v2PbbBGriMVPppOEIfLastChangeDate OBJECT-TYPE
   SYNTAX      DisplayString
   MAX-ACCESS  read-only
   STATUS      current
   DESCRIPTION
      "Path: pbbBridgeGroup.status.pppoEClient.ifLastChangeDate"
   ::= {sr1645v2PbbBGriMVPppOEEntry 3070230528}

sr1645v2PbbBGriMVPppOEIpAddress OBJECT-TYPE
   SYNTAX      IpAddress
   MAX-ACCESS  read-only
   STATUS      current
   DESCRIPTION
      "Path: pbbBridgeGroup.status.pppoEClient.ip.address"
   ::= {sr1645v2PbbBGriMVPppOEEntry 51380224}

sr1645v2PbbBGriMVPppOEIpNetMask OBJECT-TYPE
   SYNTAX      IpAddress
   MAX-ACCESS  read-only
   STATUS      current
   DESCRIPTION
      "Path: pbbBridgeGroup.status.pppoEClient.ip.netMask"
   ::= {sr1645v2PbbBGriMVPppOEEntry 51445760}

sr1645v2PbbBGriMVPppOEIpRemote OBJECT-TYPE
   SYNTAX      IpAddress
   MAX-ACCESS  read-only
   STATUS      current
   DESCRIPTION
      "Path: pbbBridgeGroup.status.pppoEClient.ip.remote"
   ::= {sr1645v2PbbBGriMVPppOEEntry 51511296}

sr1645v2PbbBGriMVPppOEPppOEthDiscState OBJECT-TYPE
   SYNTAX      INTEGER
               {
               idle (0),
               waitForPADO (1),
               waitForPADS (2),
               established (3)
               }
   MAX-ACCESS  read-only
   STATUS      current
   DESCRIPTION
      "Path: pbbBridgeGroup.status.pppoEClient.pppOverEth.discState

       Possibilities:
               idle   (0)
               waitForPADO   (1)
               waitForPADS   (2)
               established   (3)"
   ::= {sr1645v2PbbBGriMVPppOEEntry 67174400}

sr1645v2PbbBGriMVPppOEPppOEthPeerMac OBJECT-TYPE
   SYNTAX      OCTET STRING
   MAX-ACCESS  read-only
   STATUS      current
   DESCRIPTION
      "Path: pbbBridgeGroup.status.pppoEClient.pppOverEth.remoteMacAddress

       MAC address."
   ::= {sr1645v2PbbBGriMVPppOEEntry 67239936}

sr1645v2PbbBGriMVPppOEPppOEthServiceName OBJECT-TYPE
   SYNTAX      DisplayString
   MAX-ACCESS  read-only
   STATUS      current
   DESCRIPTION
      "Path: pbbBridgeGroup.status.pppoEClient.pppOverEth.serviceName"
   ::= {sr1645v2PbbBGriMVPppOEEntry 67305472}

sr1645v2PbbBGriMVPppOEPppLcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pbbBridgeGroup.status.pppoEClient.ppp.lcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PbbBGriMVPppOEEntry 83951616}

sr1645v2PbbBGriMVPppOEPppIpcpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pbbBridgeGroup.status.pppoEClient.ppp.ipcpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PbbBGriMVPppOEEntry 84017152}

sr1645v2PbbBGriMVPppOEPppIp6cpState OBJECT-TYPE
   SYNTAX      INTEGER
               {
               initial (0),
               starting (1),
               closed (2),
               stopped (3),
               closing (4),
               stopping (5),
               reqmSent (6),
               ackmRcvd (7),
               ackmSent (8),
               opened (9)
               }
   MAX-ACCESS  read-only
   STATUS      current
   DESCRIPTION
      "Path: pbbBridgeGroup.status.pppoEClient.ppp.ip6cpState

       Possibilities:
               Initial   (0)
               Starting   (1)
               Closed   (2)
               Stopped   (3)
               Closing   (4)
               Stopping   (5)
               Req-Sent   (6)
               Ack-Rcvd   (7)
               Ack-Sent   (8)
               Opened   (9)"
   ::= {sr1645v2PbbBGriMVPppOEEntry 84869120}

sr1645v2PbbBGriMVPppOEPppMyAutSt OBJECT-TYPE
   SYNTAX      INTEGER
               {
               nomAuthentication (0),
               waitmOnmResponse (1),
               authenmPapmSuccessful (2),
               authenmChapmSuccessful (3),
               authenmFailure (4),
               waitmOnmResponsemRadius (5),
               authenmNotmAllowed (6),
               waitmOnmRequest (7)
               }
   MAX-ACCESS  read-only
   STATUS      current
   DESCRIPTION
      "Path: pbbBridgeGroup.status.pppoEClient.ppp.myAuthenState

       Possibilities:
               No-Authentication   (0)
               Wait-On-Response   (1)
               Authen-Pap-Successful   (2)
               Authen-Chap-Successful   (3)
               Authen-Failure   (4)
               Wait-On-Response-Radius   (5)
               Authen-Not-Allowed   (6)
               Wait-On-Request   (7)"
   ::= {sr1645v2PbbBGriMVPppOEEntry 84541440}

sr1645v2PbbBGriMVPppOEPppHisAutSt OBJECT-TYPE
   SYNTAX      INTEGER
               {
               nomAuthentication (0),
               waitmOnmChallenge (1),
               waitmOnmSuccess (2),
               authenmPapmSuccessful (3),
               authenmChapmSuccessful (4),
               authenmFailure (5),
               authenmNotmAllowed (6),
               waitmOnmRequest (7)
               }
   MAX-ACCESS  read-only
   STATUS      current
   DESCRIPTION
      "Path: pbbBridgeGroup.status.pppoEClient.ppp.hisAuthenState

       Possibilities:
               No-Authentication   (0)
               Wait-On-Challenge   (1)
               Wait-On-Success   (2)
               Authen-Pap-Successful   (3)
               Authen-Chap-Successful   (4)
               Authen-Failure   (5)
               Authen-Not-Allowed   (6)
               Wait-On-Request   (7)"
   ::= {sr1645v2PbbBGriMVPppOEEntry 84606976}

sr1645v2PbbBGriMVPppOEPppMru OBJECT-TYPE
   SYNTAX      Integer32
   MAX-ACCESS  read-only
   STATUS      current
   DESCRIPTION
      "Path: pbbBridgeGroup.status.pppoEClient.ppp.mru"
   ::= {sr1645v2PbbBGriMVPppOEEntry 84934656}

sr1645v2PbbBGriMVPppOEIpV6State OBJECT-TYPE
   SYNTAX      INTEGER
               {
               disabled (0),
               enabled (1)
               }
   MAX-ACCESS  read-only
   STATUS      current
   DESCRIPTION
      "Path: pbbBridgeGroup.status.pppoEClient.ipV6.state

       Possibilities:
               disabled   (0)
               enabled   (1)"
   ::= {sr1645v2PbbBGriMVPppOEEntry 100728832}

sr1645v2PbbBGriMVPppOEIpV6InterfaceId OBJECT-TYPE
   SYNTAX      OCTET STRING
   MAX-ACCESS  read-only
   STATUS      current
   DESCRIPTION
      "Path: pbbBridgeGroup.status.pppoEClient.ipV6.interfaceId"
   ::= {sr1645v2PbbBGriMVPppOEEntry 100794368}

sr1645v2PbbBGriMVPppOEIpV6LinkMtu OBJECT-TYPE
   SYNTAX      Integer32
   MAX-ACCESS  read-only
   STATUS      current
   DESCRIPTION
      "Path: pbbBridgeGroup.status.pppoEClient.ipV6.linkMtu"
   ::= {sr1645v2PbbBGriMVPppOEEntry 100925440}

sr1645v2PbbBGriMVPppOEIpV6HopLimit OBJECT-TYPE
   SYNTAX      Integer32
   MAX-ACCESS  read-only
   STATUS      current
   DESCRIPTION
      "Path: pbbBridgeGroup.status.pppoEClient.ipV6.hopLimit"
   ::= {sr1645v2PbbBGriMVPppOEEntry 100990976}

sr1645v2PbbBGriMVPppOEIpV6DhcpIaid OBJECT-TYPE
   SYNTAX      Counter32
   MAX-ACCESS  read-only
   STATUS      current
   DESCRIPTION
      "Path: pbbBridgeGroup.status.pppoEClient.ipV6.dhcp.iaid

       32 bit unsigned wrappable counter."
   ::= {sr1645v2PbbBGriMVPppOEEntry 101056768}

sr1645v2PbbBGriMVPppOEIpV6RaRcvOption OBJECT-TYPE
   SYNTAX      Integer32
   MAX-ACCESS  read-only
   STATUS      current
   DESCRIPTION
      "Path: pbbBridgeGroup.status.pppoEClient.ipV6.raRcvOption

       Bit meanings:
               bit 0 = linkMtu,
               bit 1 = srcLinkLayer,
               bit 2 = prefixInfo,
               bit 3 = rdnss,
               bit 4 = dnssl"
   ::= {sr1645v2PbbBGriMVPppOEEntry 101122048}

sr1645v2PbbBGriMVPppOEIpV6Addresses OBJECT-TYPE
   SYNTAX      SEQUENCE OF Sr1645v2PbbBGriMVPppOEIpV6AddressesEntry
   MAX-ACCESS  not-accessible
   STATUS      current
   DESCRIPTION
      ""
   ::= {sr1645v2PbbBGriMVPppOE 100859904}

sr1645v2PbbBGriMVPppOEIpV6AddressesEntry OBJECT-TYPE
   SYNTAX      Sr1645v2PbbBGriMVPppOEIpV6AddressesEntry
   MAX-ACCESS  not-accessible
   STATUS      current
   DESCRIPTION
      ""
   INDEX      { sr1645v2PbbBGriMVPppOEIpV6AddressesGlobalIx,
                sr1645v2PbbBGriMVPppOETableIx,
                sr1645v2PbbBGriMVPppOEIpV6AddressesTableIx }
   ::= {sr1645v2PbbBGriMVPppOEIpV6Addresses 1}

Sr1645v2PbbBGriMVPppOEIpV6AddressesEntry ::=
   SEQUENCE
      {
      sr1645v2PbbBGriMVPppOEIpV6AddressesGlobalIx
         GlobalIndex,
      sr1645v2PbbBGriMVPppOEIpV6AddressesTableIx
         TableIndex,
      sr1645v2PbbBGriMVPppOEIpV6AddressesAddress
         Ipv6Address,
      sr1645v2PbbBGriMVPppOEIpV6AddressesPrefixLength
         Integer32,
      sr1645v2PbbBGriMVPppOEIpV6AddressesStatus
         INTEGER,
      sr1645v2PbbBGriMVPppOEIpV6AddressesOrigin
         INTEGER,
      sr1645v2PbbBGriMVPppOEIpV6AddressesFlagsInterfaceId
         INTEGER,
      sr1645v2PbbBGriMVPppOEIpV6AddressesFlagsAnycast
         INTEGER,
      sr1645v2PbbBGriMVPppOEIpV6AddressesTimersValidLifeTime
         TimeTicks,
      sr1645v2PbbBGriMVPppOEIpV6AddressesTimersPrefLifeTime
         TimeTicks
      }

sr1645v2PbbBGriMVPppOEIpV6AddressesGlobalIx OBJECT-TYPE
   SYNTAX      GlobalIndex
   MAX-ACCESS  not-accessible
   STATUS      current
   DESCRIPTION
      "The value of the tlsCntTreeGlobalIndex of the MANAGED OBJECT."
   ::= {sr1645v2PbbBGriMVPppOEIpV6AddressesEntry 10}

sr1645v2PbbBGriMVPppOEIpV6AddressesTableIx OBJECT-TYPE
   SYNTAX      TableIndex
   MAX-ACCESS  not-accessible
   STATUS      current
   DESCRIPTION
      ""
   ::= {sr1645v2PbbBGriMVPppOEIpV6AddressesEntry 11}

sr1645v2PbbBGriMVPppOEIpV6AddressesAddress OBJECT-TYPE
   SYNTAX      Ipv6Address
   MAX-ACCESS  read-only
   STATUS      current
   DESCRIPTION
      "Path: pbbBridgeGroup.status.pppoEClient.ipV6.addresses.address

       ipv6 address"
   ::= {sr1645v2PbbBGriMVPppOEIpV6AddressesEntry 16777216}

sr1645v2PbbBGriMVPppOEIpV6AddressesPrefixLength OBJECT-TYPE
   SYNTAX      Integer32
   MAX-ACCESS  read-only
   STATUS      current
   DESCRIPTION
      "Path: pbbBridgeGroup.status.pppoEClient.ipV6.addresses.prefixLength"
   ::= {sr1645v2PbbBGriMVPppOEIpV6AddressesEntry 33554432}

sr1645v2PbbBGriMVPppOEIpV6AddressesStatus OBJECT-TYPE
   SYNTAX      INTEGER
               {
               invalid (0),
               tentative (1),
               deprecated (2),
               preferred (3)
               }
   MAX-ACCESS  read-only
   STATUS      current
   DESCRIPTION
      "Path: pbbBridgeGroup.status.pppoEClient.ipV6.addresses.status

       Possibilities:
               invalid   (0)
               tentative   (1)
               deprecated   (2)
               preferred   (3)"
   ::= {sr1645v2PbbBGriMVPppOEIpV6AddressesEntry 50331648}

sr1645v2PbbBGriMVPppOEIpV6AddressesOrigin OBJECT-TYPE
   SYNTAX      INTEGER
               {
               unknown (0),
               manual (1),
               generalPrefix (2),
               statelessAuto (3),
               statefullAuto (4)
               }
   MAX-ACCESS  read-only
   STATUS      current
   DESCRIPTION
      "Path: pbbBridgeGroup.status.pppoEClient.ipV6.addresses.origin

       Possibilities:
               unknown   (0)
               manual   (1)
               generalPrefix   (2)
               statelessAuto   (3)
               statefullAuto   (4)"
   ::= {sr1645v2PbbBGriMVPppOEIpV6AddressesEntry 67108864}

sr1645v2PbbBGriMVPppOEIpV6AddressesFlagsInterfaceId OBJECT-TYPE
   SYNTAX      INTEGER
               {
               no (0),
               yes (1)
               }
   MAX-ACCESS  read-only
   STATUS      current
   DESCRIPTION
      "Path: pbbBridgeGroup.status.pppoEClient.ipV6.addresses.flags.interfaceId

       Possibilities:
               no   (0)
               yes   (1)"
   ::= {sr1645v2PbbBGriMVPppOEIpV6AddressesEntry 83951616}

sr1645v2PbbBGriMVPppOEIpV6AddressesFlagsAnycast OBJECT-TYPE
   SYNTAX      INTEGER
               {
               no (0),
               yes (1)
               }
   MAX-ACCESS  read-only
   STATUS      current
   DESCRIPTION
      "Path: pbbBridgeGroup.status.pppoEClient.ipV6.addresses.flags.anycast

       Possibilities:
               no   (0)
               yes   (1)"
   ::= {sr1645v2PbbBGriMVPppOEIpV6AddressesEntry 84017152}

sr1645v2PbbBGriMVPppOEIpV6AddressesTimersValidLifeTime OBJECT-TYPE
   SYNTAX      TimeTicks
   MAX-ACCESS  read-only
   STATUS      current
   DESCRIPTION
      "Path: pbbBridgeGroup.status.pppoEClient.ipV6.addresses.timers.validLifeTime

       Time in centi-second."
   ::= {sr1645v2PbbBGriMVPppOEIpV6AddressesEntry 100794368}

sr1645v2PbbBGriMVPppOEIpV6AddressesTimersPrefLifeTime OBJECT-TYPE
   SYNTAX      TimeTicks
   MAX-ACCESS  read-only
   STATUS      current
   DESCRIPTION
      "Path: pbbBridgeGroup.status.pppoEClient.ipV6.addresses.timers.prefLifeTime

       Time in centi-second."
   ::= {sr1645v2PbbBGriMVPppOEIpV6AddressesEntry 100728832}


sr1645v2PbbBGriMVSnmpIndex OBJECT IDENTIFIER ::= {sr1645v2PbbBGriMV 269}

sr1645v2PbbBGriMVSnmpIndexTable OBJECT-TYPE
   SYNTAX      SEQUENCE OF Sr1645v2PbbBGriMVSnmpIndexEntry
   MAX-ACCESS  not-accessible
   STATUS      current
   DESCRIPTION
      "SNMP index assigned to this object"
   ::= {sr1645v2PbbBGriMVSnmpIndex 1}

sr1645v2PbbBGriMVSnmpIndexEntry OBJECT-TYPE
   SYNTAX      Sr1645v2PbbBGriMVSnmpIndexEntry
   MAX-ACCESS  not-accessible
   STATUS      current
   DESCRIPTION
      ""
   INDEX      { sr1645v2PbbBGriMVSnmpIndexGlobalIx }
   ::= {sr1645v2PbbBGriMVSnmpIndexTable 1}

Sr1645v2PbbBGriMVSnmpIndexEntry ::=
   SEQUENCE
      {
      sr1645v2PbbBGriMVSnmpIndexGlobalIx
         GlobalIndex,
      sr1645v2PbbBGriMVSnmpIndexValue
         Integer32
      }

sr1645v2PbbBGriMVSnmpIndexGlobalIx OBJECT-TYPE
   SYNTAX      GlobalIndex
   MAX-ACCESS  not-accessible
   STATUS      current
   DESCRIPTION
      "The value of the tlsCntTreeGlobalIndex of the MANAGED OBJECT."
   ::= {sr1645v2PbbBGriMVSnmpIndexEntry 10}

sr1645v2PbbBGriMVSnmpIndexValue OBJECT-TYPE
   SYNTAX      Integer32
   MAX-ACCESS  read-only
   STATUS      current
   DESCRIPTION
      "Path: pbbBridgeGroup.status.snmpIndex"
   ::= {sr1645v2PbbBGriMVSnmpIndexEntry 2147483648}


sr1645v2PbbBGriMVBridgeCache OBJECT IDENTIFIER ::= {sr1645v2PbbBGriMV 3}

sr1645v2PbbBGriMVBridgeCacheSSCTable OBJECT-TYPE
   SYNTAX      SEQUENCE OF Sr1645v2PbbBGriMVBridgeCacheEntry
   MAX-ACCESS  not-accessible
   STATUS      current
   DESCRIPTION
      "bridge cache"
   ::= {sr1645v2PbbBGriMVBridgeCache 1}

sr1645v2PbbBGriMVBridgeCacheEntry OBJECT-TYPE
   SYNTAX      Sr1645v2PbbBGriMVBridgeCacheEntry
   MAX-ACCESS  not-accessible
   STATUS      current
   DESCRIPTION
      ""
   INDEX      { sr1645v2PbbBGriMVBridgeCacheGlobalIx,
                sr1645v2PbbBGriMVBridgeCacheTableIx }
   ::= {sr1645v2PbbBGriMVBridgeCacheSSCTable 1}

Sr1645v2PbbBGriMVBridgeCacheEntry ::=
   SEQUENCE
      {
      sr1645v2PbbBGriMVBridgeCacheGlobalIx
         GlobalIndex,
      sr1645v2PbbBGriMVBridgeCacheTableIx
         TableIndex,
      sr1645v2PbbBGriMVBridgeCacheIf
         DisplayString,
      sr1645v2PbbBGriMVBridgeCacheMacAddress
         OCTET STRING,
      sr1645v2PbbBGriMVBridgeCacheBMacAddress
         OCTET STRING,
      sr1645v2PbbBGriMVBridgeCacheIsid
         Integer32,
      sr1645v2PbbBGriMVBridgeCacheTpid
         INTEGER,
      sr1645v2PbbBGriMVBridgeCacheVlanId
         INTEGER,
      sr1645v2PbbBGriMVBridgeCacheTpid2
         INTEGER,
      sr1645v2PbbBGriMVBridgeCacheVlanId2
         INTEGER,
      sr1645v2PbbBGriMVBridgeCacheType
         INTEGER,
      sr1645v2PbbBGriMVBridgeCacheAge
         TimeTicks
      }

sr1645v2PbbBGriMVBridgeCacheGlobalIx OBJECT-TYPE
   SYNTAX      GlobalIndex
   MAX-ACCESS  not-accessible
   STATUS      current
   DESCRIPTION
      "The value of the tlsCntTreeGlobalIndex of the MANAGED OBJECT."
   ::= {sr1645v2PbbBGriMVBridgeCacheEntry 10}

sr1645v2PbbBGriMVBridgeCacheTableIx OBJECT-TYPE
   SYNTAX      TableIndex
   MAX-ACCESS  not-accessible
   STATUS      current
   DESCRIPTION
      ""
   ::= {sr1645v2PbbBGriMVBridgeCacheEntry 11}

sr1645v2PbbBGriMVBridgeCacheIf OBJECT-TYPE
   SYNTAX      DisplayString
   MAX-ACCESS  read-only
   STATUS      current
   DESCRIPTION
      "Path: pbbBridgeGroup.status.bridgeCache.interface"
   ::= {sr1645v2PbbBGriMVBridgeCacheEntry 16777216}

sr1645v2PbbBGriMVBridgeCacheMacAddress OBJECT-TYPE
   SYNTAX      OCTET STRING
   MAX-ACCESS  read-only
   STATUS      current
   DESCRIPTION
      "Path: pbbBridgeGroup.status.bridgeCache.macAddress

       MAC address."
   ::= {sr1645v2PbbBGriMVBridgeCacheEntry 33554432}

sr1645v2PbbBGriMVBridgeCacheBMacAddress OBJECT-TYPE
   SYNTAX      OCTET STRING
   MAX-ACCESS  read-only
   STATUS      current
   DESCRIPTION
      "Path: pbbBridgeGroup.status.bridgeCache.bMacAddress

       MAC address."
   ::= {sr1645v2PbbBGriMVBridgeCacheEntry 117440512}

sr1645v2PbbBGriMVBridgeCacheIsid OBJECT-TYPE
   SYNTAX      Integer32
   MAX-ACCESS  read-only
   STATUS      current
   DESCRIPTION
      "Path: pbbBridgeGroup.status.bridgeCache.isid"
   ::= {sr1645v2PbbBGriMVBridgeCacheEntry 134217728}

sr1645v2PbbBGriMVBridgeCacheTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: pbbBridgeGroup.status.bridgeCache.tpid

       Possibilities:
               untagged   (0)
               dot1q   (33024)
               dot1ad   (34984)
               group   (65534)
               notUsed   (65535)
               dot1qOrDot1ad   (65536)"
   ::= {sr1645v2PbbBGriMVBridgeCacheEntry 150994944}

sr1645v2PbbBGriMVBridgeCacheVlanId OBJECT-TYPE
   SYNTAX      INTEGER
               {
               undefined (-1)
               }
   MAX-ACCESS  read-only
   STATUS      current
   DESCRIPTION
      "Path: pbbBridgeGroup.status.bridgeCache.vlanId

       Possibilities:
               undefined   (-1)"
   ::= {sr1645v2PbbBGriMVBridgeCacheEntry 83886080}

sr1645v2PbbBGriMVBridgeCacheTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: pbbBridgeGroup.status.bridgeCache.tpid2

       Possibilities:
               untagged   (0)
               dot1q   (33024)
               dot1ad   (34984)
               group   (65534)
               notUsed   (65535)
               dot1qOrDot1ad   (65536)"
   ::= {sr1645v2PbbBGriMVBridgeCacheEntry 369098752}

sr1645v2PbbBGriMVBridgeCacheVlanId2 OBJECT-TYPE
   SYNTAX      INTEGER
               {
               undefined (-1)
               }
   MAX-ACCESS  read-only
   STATUS      current
   DESCRIPTION
      "Path: pbbBridgeGroup.status.bridgeCache.vlanId2

       Possibilities:
               undefined   (-1)"
   ::= {sr1645v2PbbBGriMVBridgeCacheEntry 385875968}

sr1645v2PbbBGriMVBridgeCacheType OBJECT-TYPE
   SYNTAX      INTEGER
               {
               static (0),
               dynamic (1),
               tester (2),
               fastFlood (3)
               }
   MAX-ACCESS  read-only
   STATUS      current
   DESCRIPTION
      "Path: pbbBridgeGroup.status.bridgeCache.type

       Possibilities:
               static   (0)
               dynamic   (1)
               tester   (2)
               fastFlood   (3)"
   ::= {sr1645v2PbbBGriMVBridgeCacheEntry 50331648}

sr1645v2PbbBGriMVBridgeCacheAge OBJECT-TYPE
   SYNTAX      TimeTicks
   MAX-ACCESS  read-only
   STATUS      current
   DESCRIPTION
      "Path: pbbBridgeGroup.status.bridgeCache.age

       Time in centi-second."
   ::= {sr1645v2PbbBGriMVBridgeCacheEntry 67108864}


sr1645v2PbbBGriMVBridging OBJECT IDENTIFIER ::= {sr1645v2PbbBGriMV 12}

sr1645v2PbbBGriMVBridgingSSCTable OBJECT-TYPE
   SYNTAX      SEQUENCE OF Sr1645v2PbbBGriMVBridgingEntry
   MAX-ACCESS  not-accessible
   STATUS      current
   DESCRIPTION
      " bridge-port status"
   ::= {sr1645v2PbbBGriMVBridging 1}

sr1645v2PbbBGriMVBridgingEntry OBJECT-TYPE
   SYNTAX      Sr1645v2PbbBGriMVBridgingEntry
   MAX-ACCESS  not-accessible
   STATUS      current
   DESCRIPTION
      ""
   INDEX      { sr1645v2PbbBGriMVBridgingGlobalIx,
                sr1645v2PbbBGriMVBridgingTableIx }
   ::= {sr1645v2PbbBGriMVBridgingSSCTable 1}

Sr1645v2PbbBGriMVBridgingEntry ::=
   SEQUENCE
      {
      sr1645v2PbbBGriMVBridgingGlobalIx
         GlobalIndex,
      sr1645v2PbbBGriMVBridgingTableIx
         TableIndex,
      sr1645v2PbbBGriMVBridgingName
         DisplayString,
      sr1645v2PbbBGriMVBridgingState
         INTEGER,
      sr1645v2PbbBGriMVBridgingCacheSize
         Counter32,
      sr1645v2PbbBGriMVBridgingMaxCacheSize
         INTEGER,
      sr1645v2PbbBGriMVBridgingVlMmbAll
         DisplayString,
      sr1645v2PbbBGriMVBridgingVlMmbNone
         DisplayString,
      sr1645v2PbbBGriMVBridgingStPortRole
         INTEGER,
      sr1645v2PbbBGriMVBridgingStPortId
         Integer32,
      sr1645v2PbbBGriMVBridgingStPpCostExtPathCost
         Integer32,
      sr1645v2PbbBGriMVBridgingStPpCostIntPathCost
         Integer32,
      sr1645v2PbbBGriMVBridgingStExtRpCost
         Integer32,
      sr1645v2PbbBGriMVBridgingStIntRpCost
         Integer32,
      sr1645v2PbbBGriMVBridgingStDesBrIdPriority
         Integer32,
      sr1645v2PbbBGriMVBridgingStDesBrIdMacAddress
         OCTET STRING,
      sr1645v2PbbBGriMVBridgingStDesPrtId
         Integer32,
      sr1645v2PbbBGriMVBridgingStDesInt
         INTEGER,
      sr1645v2PbbBGriMVBridgingStEdgeDetection
         INTEGER,
      sr1645v2PbbBGriMVBridgingBMacAddress
         OCTET STRING
      }

sr1645v2PbbBGriMVBridgingGlobalIx OBJECT-TYPE
   SYNTAX      GlobalIndex
   MAX-ACCESS  not-accessible
   STATUS      current
   DESCRIPTION
      "The value of the tlsCntTreeGlobalIndex of the MANAGED OBJECT."
   ::= {sr1645v2PbbBGriMVBridgingEntry 10}

sr1645v2PbbBGriMVBridgingTableIx OBJECT-TYPE
   SYNTAX      TableIndex
   MAX-ACCESS  not-accessible
   STATUS      current
   DESCRIPTION
      ""
   ::= {sr1645v2PbbBGriMVBridgingEntry 11}

sr1645v2PbbBGriMVBridgingName OBJECT-TYPE
   SYNTAX      DisplayString
   MAX-ACCESS  read-only
   STATUS      current
   DESCRIPTION
      "Path: pbbBridgeGroup.status.bridging.name"
   ::= {sr1645v2PbbBGriMVBridgingEntry 16777216}

sr1645v2PbbBGriMVBridgingState OBJECT-TYPE
   SYNTAX      INTEGER
               {
               disabled (0),
               discarding (1),
               learning (2),
               forwarding (3),
               backupBlockedIntfDown (256),
               backupBlockedIntfUp (259),
               shutdown (255)
               }
   MAX-ACCESS  read-only
   STATUS      current
   DESCRIPTION
      "Path: pbbBridgeGroup.status.bridging.state

       Possibilities:
               disabled   (0)
               discarding   (1)
               learning   (2)
               forwarding   (3)
               backupBlockedIntfDown   (256)
               backupBlockedIntfUp   (259)
               shutdown   (255)"
   ::= {sr1645v2PbbBGriMVBridgingEntry 33554432}

sr1645v2PbbBGriMVBridgingCacheSize OBJECT-TYPE
   SYNTAX      Counter32
   MAX-ACCESS  read-only
   STATUS      current
   DESCRIPTION
      "Path: pbbBridgeGroup.status.bridging.cacheSize

       32 bit unsigned wrappable counter."
   ::= {sr1645v2PbbBGriMVBridgingEntry 50331648}

sr1645v2PbbBGriMVBridgingMaxCacheSize OBJECT-TYPE
   SYNTAX      INTEGER
               {
               unlimited (0)
               }
   MAX-ACCESS  read-only
   STATUS      current
   DESCRIPTION
      "Path: pbbBridgeGroup.status.bridging.maxCacheSize

       Possibilities:
               unlimited   (0)"
   ::= {sr1645v2PbbBGriMVBridgingEntry 67108864}

sr1645v2PbbBGriMVBridgingVlMmbAll OBJECT-TYPE
   SYNTAX      DisplayString
   MAX-ACCESS  read-only
   STATUS      current
   DESCRIPTION
      "Path: pbbBridgeGroup.status.bridging.vlanMemberShip.all"
   ::= {sr1645v2PbbBGriMVBridgingEntry 100728832}

sr1645v2PbbBGriMVBridgingVlMmbNone OBJECT-TYPE
   SYNTAX      DisplayString
   MAX-ACCESS  read-only
   STATUS      current
   DESCRIPTION
      "Path: pbbBridgeGroup.status.bridging.vlanMemberShip.none"
   ::= {sr1645v2PbbBGriMVBridgingEntry 100794368}

sr1645v2PbbBGriMVBridgingStPortRole OBJECT-TYPE
   SYNTAX      INTEGER
               {
               none (0),
               root (1),
               designated (2),
               alternate (3),
               backup (4),
               disabled (5),
               master (6)
               }
   MAX-ACCESS  read-only
   STATUS      current
   DESCRIPTION
      "Path: pbbBridgeGroup.status.bridging.spanningTree.portRole

       Possibilities:
               none   (0)
               root   (1)
               designated   (2)
               alternate   (3)
               backup   (4)
               disabled   (5)
               master   (6)"
   ::= {sr1645v2PbbBGriMVBridgingEntry 83951616}

sr1645v2PbbBGriMVBridgingStPortId OBJECT-TYPE
   SYNTAX      Integer32
   MAX-ACCESS  read-only
   STATUS      current
   DESCRIPTION
      "Path: pbbBridgeGroup.status.bridging.spanningTree.portId"
   ::= {sr1645v2PbbBGriMVBridgingEntry 84017152}

sr1645v2PbbBGriMVBridgingStPpCostExtPathCost OBJECT-TYPE
   SYNTAX      Integer32
   MAX-ACCESS  read-only
   STATUS      current
   DESCRIPTION
      "Path: pbbBridgeGroup.status.bridging.spanningTree.portPathCosts.extPathCost"
   ::= {sr1645v2PbbBGriMVBridgingEntry 84082944}

sr1645v2PbbBGriMVBridgingStPpCostIntPathCost OBJECT-TYPE
   SYNTAX      Integer32
   MAX-ACCESS  read-only
   STATUS      current
   DESCRIPTION
      "Path: pbbBridgeGroup.status.bridging.spanningTree.portPathCosts.intPathCost"
   ::= {sr1645v2PbbBGriMVBridgingEntry 84083200}

sr1645v2PbbBGriMVBridgingStExtRpCost OBJECT-TYPE
   SYNTAX      Integer32
   MAX-ACCESS  read-only
   STATUS      current
   DESCRIPTION
      "Path: pbbBridgeGroup.status.bridging.spanningTree.extRootPathCost"
   ::= {sr1645v2PbbBGriMVBridgingEntry 84148224}

sr1645v2PbbBGriMVBridgingStIntRpCost OBJECT-TYPE
   SYNTAX      Integer32
   MAX-ACCESS  read-only
   STATUS      current
   DESCRIPTION
      "Path: pbbBridgeGroup.status.bridging.spanningTree.intRootPathCost"
   ::= {sr1645v2PbbBGriMVBridgingEntry 84213760}

sr1645v2PbbBGriMVBridgingStDesBrIdPriority OBJECT-TYPE
   SYNTAX      Integer32
   MAX-ACCESS  read-only
   STATUS      current
   DESCRIPTION
      "Path: pbbBridgeGroup.status.bridging.spanningTree.designatedBridgeId.priority"
   ::= {sr1645v2PbbBGriMVBridgingEntry 84279552}

sr1645v2PbbBGriMVBridgingStDesBrIdMacAddress OBJECT-TYPE
   SYNTAX      OCTET STRING
   MAX-ACCESS  read-only
   STATUS      current
   DESCRIPTION
      "Path: pbbBridgeGroup.status.bridging.spanningTree.designatedBridgeId.macAddress

       MAC address."
   ::= {sr1645v2PbbBGriMVBridgingEntry 84279808}

sr1645v2PbbBGriMVBridgingStDesPrtId OBJECT-TYPE
   SYNTAX      Integer32
   MAX-ACCESS  read-only
   STATUS      current
   DESCRIPTION
      "Path: pbbBridgeGroup.status.bridging.spanningTree.designatedPortId"
   ::= {sr1645v2PbbBGriMVBridgingEntry 84344832}

sr1645v2PbbBGriMVBridgingStDesInt OBJECT-TYPE
   SYNTAX      INTEGER
               {
               no (0),
               yes (1)
               }
   MAX-ACCESS  read-only
   STATUS      current
   DESCRIPTION
      "Path: pbbBridgeGroup.status.bridging.spanningTree.designatedOrInternal

       Possibilities:
               no   (0)
               yes   (1)"
   ::= {sr1645v2PbbBGriMVBridgingEntry 84410368}

sr1645v2PbbBGriMVBridgingStEdgeDetection OBJECT-TYPE
   SYNTAX      INTEGER
               {
               none (0),
               edge (1),
               notEdge (2)
               }
   MAX-ACCESS  read-only
   STATUS      current
   DESCRIPTION
      "Path: pbbBridgeGroup.status.bridging.spanningTree.edgeDetection

       Possibilities:
               none   (0)
               edge   (1)
               notEdge   (2)"
   ::= {sr1645v2PbbBGriMVBridgingEntry 84475904}

sr1645v2PbbBGriMVBridgingBMacAddress OBJECT-TYPE
   SYNTAX      OCTET STRING
   MAX-ACCESS  read-only
   STATUS      current
   DESCRIPTION
      "Path: pbbBridgeGroup.status.bridging.bMacAddress

       MAC address."
   ::= {sr1645v2PbbBGriMVBridgingEntry 117440512}

sr1645v2PbbBGriMVBridgingVlMmbGrouped OBJECT-TYPE
   SYNTAX      SEQUENCE OF Sr1645v2PbbBGriMVBridgingVlMmbGroupedEntry
   MAX-ACCESS  not-accessible
   STATUS      current
   DESCRIPTION
      ""
   ::= {sr1645v2PbbBGriMVBridging 100859904}

sr1645v2PbbBGriMVBridgingVlMmbGroupedEntry OBJECT-TYPE
   SYNTAX      Sr1645v2PbbBGriMVBridgingVlMmbGroupedEntry
   MAX-ACCESS  not-accessible
   STATUS      current
   DESCRIPTION
      ""
   INDEX      { sr1645v2PbbBGriMVBridgingVlMmbGroupedGlobalIx,
                sr1645v2PbbBGriMVBridgingTableIx,
                sr1645v2PbbBGriMVBridgingVlMmbGroupedTableIx }
   ::= {sr1645v2PbbBGriMVBridgingVlMmbGrouped 1}

Sr1645v2PbbBGriMVBridgingVlMmbGroupedEntry ::=
   SEQUENCE
      {
      sr1645v2PbbBGriMVBridgingVlMmbGroupedGlobalIx
         GlobalIndex,
      sr1645v2PbbBGriMVBridgingVlMmbGroupedTableIx
         TableIndex,
      sr1645v2PbbBGriMVBridgingVlMmbGroupedVlanId
         Integer32
      }

sr1645v2PbbBGriMVBridgingVlMmbGroupedGlobalIx OBJECT-TYPE
   SYNTAX      GlobalIndex
   MAX-ACCESS  not-accessible
   STATUS      current
   DESCRIPTION
      "The value of the tlsCntTreeGlobalIndex of the MANAGED OBJECT."
   ::= {sr1645v2PbbBGriMVBridgingVlMmbGroupedEntry 10}

sr1645v2PbbBGriMVBridgingVlMmbGroupedTableIx OBJECT-TYPE
   SYNTAX      TableIndex
   MAX-ACCESS  not-accessible
   STATUS      current
   DESCRIPTION
      ""
   ::= {sr1645v2PbbBGriMVBridgingVlMmbGroupedEntry 11}

sr1645v2PbbBGriMVBridgingVlMmbGroupedVlanId OBJECT-TYPE
   SYNTAX      Integer32
   MAX-ACCESS  read-only
   STATUS      current
   DESCRIPTION
      "Path: pbbBridgeGroup.status.bridging.vlanMemberShip.grouped.vlanId"
   ::= {sr1645v2PbbBGriMVBridgingVlMmbGroupedEntry 16777216}



pr1645v2PbbBGriMV OBJECT IDENTIFIER ::= {r1645v2PbbBGriMV 12}


pr1645v2PbbBGriMVResCachePerf OBJECT IDENTIFIER ::= {pr1645v2PbbBGriMV 45}

pr1645v2PbbBGriMVResCachePerfSSCTable OBJECT-TYPE
   SYNTAX      SEQUENCE OF Pr1645v2PbbBGriMVResCachePerfEntry
   MAX-ACCESS  not-accessible
   STATUS      current
   DESCRIPTION
      "cache of reserved Ethernet addresses"
   ::= {pr1645v2PbbBGriMVResCachePerf 1}

pr1645v2PbbBGriMVResCachePerfEntry OBJECT-TYPE
   SYNTAX      Pr1645v2PbbBGriMVResCachePerfEntry
   MAX-ACCESS  not-accessible
   STATUS      current
   DESCRIPTION
      ""
   INDEX      { pr1645v2PbbBGriMVResCachePerfGlobalIx,
                pr1645v2PbbBGriMVResCachePerfTableIx }
   ::= {pr1645v2PbbBGriMVResCachePerfSSCTable 1}

Pr1645v2PbbBGriMVResCachePerfEntry ::=
   SEQUENCE
      {
      pr1645v2PbbBGriMVResCachePerfGlobalIx
         GlobalIndex,
      pr1645v2PbbBGriMVResCachePerfTableIx
         TableIndex,
      pr1645v2PbbBGriMVResCachePerfMacAddress
         OCTET STRING,
      pr1645v2PbbBGriMVResCachePerfRxPkts
         Counter32
      }

pr1645v2PbbBGriMVResCachePerfGlobalIx OBJECT-TYPE
   SYNTAX      GlobalIndex
   MAX-ACCESS  not-accessible
   STATUS      current
   DESCRIPTION
      "The value of the tlsCntTreeGlobalIndex of the MANAGED OBJECT."
   ::= {pr1645v2PbbBGriMVResCachePerfEntry 10}

pr1645v2PbbBGriMVResCachePerfTableIx OBJECT-TYPE
   SYNTAX      TableIndex
   MAX-ACCESS  not-accessible
   STATUS      current
   DESCRIPTION
      ""
   ::= {pr1645v2PbbBGriMVResCachePerfEntry 11}

pr1645v2PbbBGriMVResCachePerfMacAddress OBJECT-TYPE
   SYNTAX      OCTET STRING
   MAX-ACCESS  read-only
   STATUS      current
   DESCRIPTION
      "Path: pbbBridgeGroup.performance.reservedAddressCache.macAddress

       MAC address."
   ::= {pr1645v2PbbBGriMVResCachePerfEntry 16777216}

pr1645v2PbbBGriMVResCachePerfRxPkts OBJECT-TYPE
   SYNTAX      Counter32
   MAX-ACCESS  read-only
   STATUS      current
   DESCRIPTION
      "Path: pbbBridgeGroup.performance.reservedAddressCache.rxPkts

       32 bit unsigned wrappable counter."
   ::= {pr1645v2PbbBGriMVResCachePerfEntry 33554432}


pr1645v2PbbBGriMVBridgeRxPkts OBJECT IDENTIFIER ::= {pr1645v2PbbBGriMV 42}

pr1645v2PbbBGriMVBridgeRxPktsTable OBJECT-TYPE
   SYNTAX      SEQUENCE OF Pr1645v2PbbBGriMVBridgeRxPktsEntry
   MAX-ACCESS  not-accessible
   STATUS      current
   DESCRIPTION
      "counter (floods or discards) of bridge"
   ::= {pr1645v2PbbBGriMVBridgeRxPkts 1}

pr1645v2PbbBGriMVBridgeRxPktsEntry OBJECT-TYPE
   SYNTAX      Pr1645v2PbbBGriMVBridgeRxPktsEntry
   MAX-ACCESS  not-accessible
   STATUS      current
   DESCRIPTION
      ""
   INDEX      { pr1645v2PbbBGriMVBridgeRxPktsGlobalIx }
   ::= {pr1645v2PbbBGriMVBridgeRxPktsTable 1}

Pr1645v2PbbBGriMVBridgeRxPktsEntry ::=
   SEQUENCE
      {
      pr1645v2PbbBGriMVBridgeRxPktsGlobalIx
         GlobalIndex,
      pr1645v2PbbBGriMVBridgeRxPktsValue
         Counter32
      }

pr1645v2PbbBGriMVBridgeRxPktsGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgeRxPktsEntry 10}

pr1645v2PbbBGriMVBridgeRxPktsValue OBJECT-TYPE
   SYNTAX      Counter32
   MAX-ACCESS  read-only
   STATUS      current
   DESCRIPTION
      "Path: pbbBridgeGroup.performance.bridgeRxPkts

       32 bit unsigned wrappable counter."
   ::= {pr1645v2PbbBGriMVBridgeRxPktsEntry 2147483648}


pr1645v2PbbBGriMVBridgeTxPkts OBJECT IDENTIFIER ::= {pr1645v2PbbBGriMV 43}

pr1645v2PbbBGriMVBridgeTxPktsTable OBJECT-TYPE
   SYNTAX      SEQUENCE OF Pr1645v2PbbBGriMVBridgeTxPktsEntry
   MAX-ACCESS  not-accessible
   STATUS      current
   DESCRIPTION
      "counter (floods or discards) of bridge"
   ::= {pr1645v2PbbBGriMVBridgeTxPkts 1}

pr1645v2PbbBGriMVBridgeTxPktsEntry OBJECT-TYPE
   SYNTAX      Pr1645v2PbbBGriMVBridgeTxPktsEntry
   MAX-ACCESS  not-accessible
   STATUS      current
   DESCRIPTION
      ""
   INDEX      { pr1645v2PbbBGriMVBridgeTxPktsGlobalIx }
   ::= {pr1645v2PbbBGriMVBridgeTxPktsTable 1}

Pr1645v2PbbBGriMVBridgeTxPktsEntry ::=
   SEQUENCE
      {
      pr1645v2PbbBGriMVBridgeTxPktsGlobalIx
         GlobalIndex,
      pr1645v2PbbBGriMVBridgeTxPktsValue
         Counter32
      }

pr1645v2PbbBGriMVBridgeTxPktsGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgeTxPktsEntry 10}

pr1645v2PbbBGriMVBridgeTxPktsValue OBJECT-TYPE
   SYNTAX      Counter32
   MAX-ACCESS  read-only
   STATUS      current
   DESCRIPTION
      "Path: pbbBridgeGroup.performance.bridgeTxPkts

       32 bit unsigned wrappable counter."
   ::= {pr1645v2PbbBGriMVBridgeTxPktsEntry 2147483648}


pr1645v2PbbBGriMVBridgeDiscards OBJECT IDENTIFIER ::= {pr1645v2PbbBGriMV 7}

pr1645v2PbbBGriMVBridgeDiscardsTable OBJECT-TYPE
   SYNTAX      SEQUENCE OF Pr1645v2PbbBGriMVBridgeDiscardsEntry
   MAX-ACCESS  not-accessible
   STATUS      current
   DESCRIPTION
      "counter (floods or discards) of bridge"
   ::= {pr1645v2PbbBGriMVBridgeDiscards 1}

pr1645v2PbbBGriMVBridgeDiscardsEntry OBJECT-TYPE
   SYNTAX      Pr1645v2PbbBGriMVBridgeDiscardsEntry
   MAX-ACCESS  not-accessible
   STATUS      current
   DESCRIPTION
      ""
   INDEX      { pr1645v2PbbBGriMVBridgeDiscardsGlobalIx }
   ::= {pr1645v2PbbBGriMVBridgeDiscardsTable 1}

Pr1645v2PbbBGriMVBridgeDiscardsEntry ::=
   SEQUENCE
      {
      pr1645v2PbbBGriMVBridgeDiscardsGlobalIx
         GlobalIndex,
      pr1645v2PbbBGriMVBridgeDiscardsValue
         Counter32
      }

pr1645v2PbbBGriMVBridgeDiscardsGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgeDiscardsEntry 10}

pr1645v2PbbBGriMVBridgeDiscardsValue OBJECT-TYPE
   SYNTAX      Counter32
   MAX-ACCESS  read-only
   STATUS      current
   DESCRIPTION
      "Path: pbbBridgeGroup.performance.bridgeDiscards

       32 bit unsigned wrappable counter."
   ::= {pr1645v2PbbBGriMVBridgeDiscardsEntry 2147483648}


pr1645v2PbbBGriMVBridgeFloods OBJECT IDENTIFIER ::= {pr1645v2PbbBGriMV 8}

pr1645v2PbbBGriMVBridgeFloodsTable OBJECT-TYPE
   SYNTAX      SEQUENCE OF Pr1645v2PbbBGriMVBridgeFloodsEntry
   MAX-ACCESS  not-accessible
   STATUS      current
   DESCRIPTION
      "counter (floods or discards) of bridge"
   ::= {pr1645v2PbbBGriMVBridgeFloods 1}

pr1645v2PbbBGriMVBridgeFloodsEntry OBJECT-TYPE
   SYNTAX      Pr1645v2PbbBGriMVBridgeFloodsEntry
   MAX-ACCESS  not-accessible
   STATUS      current
   DESCRIPTION
      ""
   INDEX      { pr1645v2PbbBGriMVBridgeFloodsGlobalIx }
   ::= {pr1645v2PbbBGriMVBridgeFloodsTable 1}

Pr1645v2PbbBGriMVBridgeFloodsEntry ::=
   SEQUENCE
      {
      pr1645v2PbbBGriMVBridgeFloodsGlobalIx
         GlobalIndex,
      pr1645v2PbbBGriMVBridgeFloodsValue
         Counter32
      }

pr1645v2PbbBGriMVBridgeFloodsGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgeFloodsEntry 10}

pr1645v2PbbBGriMVBridgeFloodsValue OBJECT-TYPE
   SYNTAX      Counter32
   MAX-ACCESS  read-only
   STATUS      current
   DESCRIPTION
      "Path: pbbBridgeGroup.performance.bridgeFloods

       32 bit unsigned wrappable counter."
   ::= {pr1645v2PbbBGriMVBridgeFloodsEntry 2147483648}


pr1645v2PbbBGriMVBridgeBroadcasts OBJECT IDENTIFIER ::= {pr1645v2PbbBGriMV 40}

pr1645v2PbbBGriMVBridgeBroadcastsTable OBJECT-TYPE
   SYNTAX      SEQUENCE OF Pr1645v2PbbBGriMVBridgeBroadcastsEntry
   MAX-ACCESS  not-accessible
   STATUS      current
   DESCRIPTION
      "counter (floods or discards) of bridge"
   ::= {pr1645v2PbbBGriMVBridgeBroadcasts 1}

pr1645v2PbbBGriMVBridgeBroadcastsEntry OBJECT-TYPE
   SYNTAX      Pr1645v2PbbBGriMVBridgeBroadcastsEntry
   MAX-ACCESS  not-accessible
   STATUS      current
   DESCRIPTION
      ""
   INDEX      { pr1645v2PbbBGriMVBridgeBroadcastsGlobalIx }
   ::= {pr1645v2PbbBGriMVBridgeBroadcastsTable 1}

Pr1645v2PbbBGriMVBridgeBroadcastsEntry ::=
   SEQUENCE
      {
      pr1645v2PbbBGriMVBridgeBroadcastsGlobalIx
         GlobalIndex,
      pr1645v2PbbBGriMVBridgeBroadcastsValue
         Counter32
      }

pr1645v2PbbBGriMVBridgeBroadcastsGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgeBroadcastsEntry 10}

pr1645v2PbbBGriMVBridgeBroadcastsValue OBJECT-TYPE
   SYNTAX      Counter32
   MAX-ACCESS  read-only
   STATUS      current
   DESCRIPTION
      "Path: pbbBridgeGroup.performance.bridgeBroadcasts

       32 bit unsigned wrappable counter."
   ::= {pr1645v2PbbBGriMVBridgeBroadcastsEntry 2147483648}


pr1645v2PbbBGriMVBridgeMulticasts OBJECT IDENTIFIER ::= {pr1645v2PbbBGriMV 41}

pr1645v2PbbBGriMVBridgeMulticastsTable OBJECT-TYPE
   SYNTAX      SEQUENCE OF Pr1645v2PbbBGriMVBridgeMulticastsEntry
   MAX-ACCESS  not-accessible
   STATUS      current
   DESCRIPTION
      "counter (floods or discards) of bridge"
   ::= {pr1645v2PbbBGriMVBridgeMulticasts 1}

pr1645v2PbbBGriMVBridgeMulticastsEntry OBJECT-TYPE
   SYNTAX      Pr1645v2PbbBGriMVBridgeMulticastsEntry
   MAX-ACCESS  not-accessible
   STATUS      current
   DESCRIPTION
      ""
   INDEX      { pr1645v2PbbBGriMVBridgeMulticastsGlobalIx }
   ::= {pr1645v2PbbBGriMVBridgeMulticastsTable 1}

Pr1645v2PbbBGriMVBridgeMulticastsEntry ::=
   SEQUENCE
      {
      pr1645v2PbbBGriMVBridgeMulticastsGlobalIx
         GlobalIndex,
      pr1645v2PbbBGriMVBridgeMulticastsValue
         Counter32
      }

pr1645v2PbbBGriMVBridgeMulticastsGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgeMulticastsEntry 10}

pr1645v2PbbBGriMVBridgeMulticastsValue OBJECT-TYPE
   SYNTAX      Counter32
   MAX-ACCESS  read-only
   STATUS      current
   DESCRIPTION
      "Path: pbbBridgeGroup.performance.bridgeMulticasts

       32 bit unsigned wrappable counter."
   ::= {pr1645v2PbbBGriMVBridgeMulticastsEntry 2147483648}


pr1645v2PbbBGriMVVlanSwitching OBJECT IDENTIFIER ::= {pr1645v2PbbBGriMV 30}

pr1645v2PbbBGriMVVlanSwitchingSSCTable OBJECT-TYPE
   SYNTAX      SEQUENCE OF Pr1645v2PbbBGriMVVlanSwitchingEntry
   MAX-ACCESS  not-accessible
   STATUS      current
   DESCRIPTION
      "ospf area summary lsa overview"
   ::= {pr1645v2PbbBGriMVVlanSwitching 1}

pr1645v2PbbBGriMVVlanSwitchingEntry OBJECT-TYPE
   SYNTAX      Pr1645v2PbbBGriMVVlanSwitchingEntry
   MAX-ACCESS  not-accessible
   STATUS      current
   DESCRIPTION
      ""
   INDEX      { pr1645v2PbbBGriMVVlanSwitchingGlobalIx,
                pr1645v2PbbBGriMVVlanSwitchingTableIx }
   ::= {pr1645v2PbbBGriMVVlanSwitchingSSCTable 1}

Pr1645v2PbbBGriMVVlanSwitchingEntry ::=
   SEQUENCE
      {
      pr1645v2PbbBGriMVVlanSwitchingGlobalIx
         GlobalIndex,
      pr1645v2PbbBGriMVVlanSwitchingTableIx
         TableIndex,
      pr1645v2PbbBGriMVVlanSwitchingSrcIntf
         DisplayString,
      pr1645v2PbbBGriMVVlanSwitchingSrcVlan
         INTEGER,
      pr1645v2PbbBGriMVVlanSwitchingSrcPFlt
         INTEGER,
      pr1645v2PbbBGriMVVlanSwitchingDestIntf
         DisplayString,
      pr1645v2PbbBGriMVVlanSwitchingDestVlan
         INTEGER,
      pr1645v2PbbBGriMVVlanSwitchingTunnelMode
         INTEGER,
      pr1645v2PbbBGriMVVlanSwitchingUses
         Counter32
      }

pr1645v2PbbBGriMVVlanSwitchingGlobalIx OBJECT-TYPE
   SYNTAX      GlobalIndex
   MAX-ACCESS  not-accessible
   STATUS      current
   DESCRIPTION
      "The value of the tlsCntTreeGlobalIndex of the MANAGED OBJECT."
   ::= {pr1645v2PbbBGriMVVlanSwitchingEntry 10}

pr1645v2PbbBGriMVVlanSwitchingTableIx OBJECT-TYPE
   SYNTAX      TableIndex
   MAX-ACCESS  not-accessible
   STATUS      current
   DESCRIPTION
      ""
   ::= {pr1645v2PbbBGriMVVlanSwitchingEntry 11}

pr1645v2PbbBGriMVVlanSwitchingSrcIntf OBJECT-TYPE
   SYNTAX      DisplayString
   MAX-ACCESS  read-only
   STATUS      current
   DESCRIPTION
      "Path: pbbBridgeGroup.performance.vlanSwitching.sourceIntf"
   ::= {pr1645v2PbbBGriMVVlanSwitchingEntry 16777216}

pr1645v2PbbBGriMVVlanSwitchingSrcVlan OBJECT-TYPE
   SYNTAX      INTEGER
               {
               any (-1)
               }
   MAX-ACCESS  read-only
   STATUS      current
   DESCRIPTION
      "Path: pbbBridgeGroup.performance.vlanSwitching.sourceVlan

       Possibilities:
               any   (-1)"
   ::= {pr1645v2PbbBGriMVVlanSwitchingEntry 33554432}

pr1645v2PbbBGriMVVlanSwitchingSrcPFlt OBJECT-TYPE
   SYNTAX      INTEGER
               {
               any (-1)
               }
   MAX-ACCESS  read-only
   STATUS      current
   DESCRIPTION
      "Path: pbbBridgeGroup.performance.vlanSwitching.sourcePFilter

       Possibilities:
               any   (-1)"
   ::= {pr1645v2PbbBGriMVVlanSwitchingEntry 100663296}

pr1645v2PbbBGriMVVlanSwitchingDestIntf OBJECT-TYPE
   SYNTAX      DisplayString
   MAX-ACCESS  read-only
   STATUS      current
   DESCRIPTION
      "Path: pbbBridgeGroup.performance.vlanSwitching.destinationIntf"
   ::= {pr1645v2PbbBGriMVVlanSwitchingEntry 50331648}

pr1645v2PbbBGriMVVlanSwitchingDestVlan OBJECT-TYPE
   SYNTAX      INTEGER
               {
               unchanged (-1)
               }
   MAX-ACCESS  read-only
   STATUS      current
   DESCRIPTION
      "Path: pbbBridgeGroup.performance.vlanSwitching.destinationVlan

       Possibilities:
               unchanged   (-1)"
   ::= {pr1645v2PbbBGriMVVlanSwitchingEntry 67108864}

pr1645v2PbbBGriMVVlanSwitchingTunnelMode OBJECT-TYPE
   SYNTAX      INTEGER
               {
               none (0),
               toTunnel (1),
               fromTunnel (2),
               toSVlanTunnel (3),
               fromSVlanTunnel (4)
               }
   MAX-ACCESS  read-only
   STATUS      current
   DESCRIPTION
      "Path: pbbBridgeGroup.performance.vlanSwitching.tunnelMode

       Possibilities:
               none   (0)
               toTunnel   (1)
               fromTunnel   (2)
               toSVlanTunnel   (3)
               fromSVlanTunnel   (4)"
   ::= {pr1645v2PbbBGriMVVlanSwitchingEntry 117440512}

pr1645v2PbbBGriMVVlanSwitchingUses OBJECT-TYPE
   SYNTAX      Counter32
   MAX-ACCESS  read-only
   STATUS      current
   DESCRIPTION
      "Path: pbbBridgeGroup.performance.vlanSwitching.uses

       32 bit unsigned wrappable counter."
   ::= {pr1645v2PbbBGriMVVlanSwitchingEntry 83886080}


pr1645v2PbbBGriMVMibCounters OBJECT IDENTIFIER ::= {pr1645v2PbbBGriMV 100}

pr1645v2PbbBGriMVMibCountersSSCTable OBJECT-TYPE
   SYNTAX      SEQUENCE OF Pr1645v2PbbBGriMVMibCountersEntry
   MAX-ACCESS  not-accessible
   STATUS      current
   DESCRIPTION
      "mibCounter"
   ::= {pr1645v2PbbBGriMVMibCounters 1}

pr1645v2PbbBGriMVMibCountersEntry OBJECT-TYPE
   SYNTAX      Pr1645v2PbbBGriMVMibCountersEntry
   MAX-ACCESS  not-accessible
   STATUS      current
   DESCRIPTION
      ""
   INDEX      { pr1645v2PbbBGriMVMibCountersGlobalIx }
   ::= {pr1645v2PbbBGriMVMibCountersSSCTable 1}

Pr1645v2PbbBGriMVMibCountersEntry ::=
   SEQUENCE
      {
      pr1645v2PbbBGriMVMibCountersGlobalIx
         GlobalIndex,
      pr1645v2PbbBGriMVMibCountersInOctets
         Counter64,
      pr1645v2PbbBGriMVMibCountersInUcast
         Counter64,
      pr1645v2PbbBGriMVMibCountersInNUcastPkts
         Counter64,
      pr1645v2PbbBGriMVMibCountersInBcastPkts
         Counter64,
      pr1645v2PbbBGriMVMibCountersInMcastPkts
         Counter64,
      pr1645v2PbbBGriMVMibCountersInDiscards
         Counter64,
      pr1645v2PbbBGriMVMibCountersInErrors
         Counter64,
      pr1645v2PbbBGriMVMibCountersInUnknownProtos
         Counter64,
      pr1645v2PbbBGriMVMibCountersInDropEx
         Counter64,
      pr1645v2PbbBGriMVMibCountersInDropNoMac
         Counter64,
      pr1645v2PbbBGriMVMibCountersInDropNUCast
         Counter64,
      pr1645v2PbbBGriMVMibCountersInDropFilter
         Counter64,
      pr1645v2PbbBGriMVMibCountersInBandwidth15sec
         Integer32,
      pr1645v2PbbBGriMVMibCountersInBandwidth30sec
         Integer32,
      pr1645v2PbbBGriMVMibCountersInBandwidth1min
         Integer32,
      pr1645v2PbbBGriMVMibCountersInBandwidth2min
         Integer32,
      pr1645v2PbbBGriMVMibCountersInBandwidth5min
         Integer32,
      pr1645v2PbbBGriMVMibCountersOutOctets
         Counter64,
      pr1645v2PbbBGriMVMibCountersOutUcastPkts
         Counter64,
      pr1645v2PbbBGriMVMibCountersOutNUcastPkts
         Counter64,
      pr1645v2PbbBGriMVMibCountersOutBcastPkts
         Counter64,
      pr1645v2PbbBGriMVMibCountersOutMcastPkts
         Counter64,
      pr1645v2PbbBGriMVMibCountersOutDiscards
         Counter64,
      pr1645v2PbbBGriMVMibCountersOutErrors
         Counter64,
      pr1645v2PbbBGriMVMibCountersOutQLen
         Counter32,
      pr1645v2PbbBGriMVMibCountersOutDropEx
         Counter64,
      pr1645v2PbbBGriMVMibCountersOutDropNoArp
         Counter64,
      pr1645v2PbbBGriMVMibCountersOutDropFilter
         Counter64,
      pr1645v2PbbBGriMVMibCountersOutBandwidth15sec
         Integer32,
      pr1645v2PbbBGriMVMibCountersOutBandwidth30sec
         Integer32,
      pr1645v2PbbBGriMVMibCountersOutBandwidth1min
         Integer32,
      pr1645v2PbbBGriMVMibCountersOutBandwidth2min
         Integer32,
      pr1645v2PbbBGriMVMibCountersOutBandwidth5min
         Integer32
      }

pr1645v2PbbBGriMVMibCountersGlobalIx OBJECT-TYPE
   SYNTAX      GlobalIndex
   MAX-ACCESS  not-accessible
   STATUS      current
   DESCRIPTION
      "The value of the tlsCntTreeGlobalIndex of the MANAGED OBJECT."
   ::= {pr1645v2PbbBGriMVMibCountersEntry 10}

pr1645v2PbbBGriMVMibCountersInOctets OBJECT-TYPE
   SYNTAX      Counter64
   MAX-ACCESS  read-only
   STATUS      current
   DESCRIPTION
      "Path: pbbBridgeGroup.performance.mibCounters.ifInOctets

       64 bit unsigned wrappable counter."
   ::= {pr1645v2PbbBGriMVMibCountersEntry 1828716544}

pr1645v2PbbBGriMVMibCountersInUcast OBJECT-TYPE
   SYNTAX      Counter64
   MAX-ACCESS  read-only
   STATUS      current
   DESCRIPTION
      "Path: pbbBridgeGroup.performance.mibCounters.ifInUcastPkts

       64 bit unsigned wrappable counter."
   ::= {pr1645v2PbbBGriMVMibCountersEntry 1845493760}

pr1645v2PbbBGriMVMibCountersInNUcastPkts OBJECT-TYPE
   SYNTAX      Counter64
   MAX-ACCESS  read-only
   STATUS      current
   DESCRIPTION
      "Path: pbbBridgeGroup.performance.mibCounters.ifInNUcastPkts

       64 bit unsigned wrappable counter."
   ::= {pr1645v2PbbBGriMVMibCountersEntry 1862270976}

pr1645v2PbbBGriMVMibCountersInBcastPkts OBJECT-TYPE
   SYNTAX      Counter64
   MAX-ACCESS  read-only
   STATUS      current
   DESCRIPTION
      "Path: pbbBridgeGroup.performance.mibCounters.ifInBcastPkts

       64 bit unsigned wrappable counter."
   ::= {pr1645v2PbbBGriMVMibCountersEntry 3539992576}

pr1645v2PbbBGriMVMibCountersInMcastPkts OBJECT-TYPE
   SYNTAX      Counter64
   MAX-ACCESS  read-only
   STATUS      current
   DESCRIPTION
      "Path: pbbBridgeGroup.performance.mibCounters.ifInMcastPkts

       64 bit unsigned wrappable counter."
   ::= {pr1645v2PbbBGriMVMibCountersEntry 3707764736}

pr1645v2PbbBGriMVMibCountersInDiscards OBJECT-TYPE
   SYNTAX      Counter64
   MAX-ACCESS  read-only
   STATUS      current
   DESCRIPTION
      "Path: pbbBridgeGroup.performance.mibCounters.ifInDiscards

       64 bit unsigned wrappable counter."
   ::= {pr1645v2PbbBGriMVMibCountersEntry 1879048192}

pr1645v2PbbBGriMVMibCountersInErrors OBJECT-TYPE
   SYNTAX      Counter64
   MAX-ACCESS  read-only
   STATUS      current
   DESCRIPTION
      "Path: pbbBridgeGroup.performance.mibCounters.ifInErrors

       64 bit unsigned wrappable counter."
   ::= {pr1645v2PbbBGriMVMibCountersEntry 1895825408}

pr1645v2PbbBGriMVMibCountersInUnknownProtos OBJECT-TYPE
   SYNTAX      Counter64
   MAX-ACCESS  read-only
   STATUS      current
   DESCRIPTION
      "Path: pbbBridgeGroup.performance.mibCounters.ifInUnknownProtos

       64 bit unsigned wrappable counter."
   ::= {pr1645v2PbbBGriMVMibCountersEntry 1912602624}

pr1645v2PbbBGriMVMibCountersInDropEx OBJECT-TYPE
   SYNTAX      Counter64
   MAX-ACCESS  read-only
   STATUS      current
   DESCRIPTION
      "Path: pbbBridgeGroup.performance.mibCounters.ifInDropLevelExceeded

       64 bit unsigned wrappable counter."
   ::= {pr1645v2PbbBGriMVMibCountersEntry 2181038080}

pr1645v2PbbBGriMVMibCountersInDropNoMac OBJECT-TYPE
   SYNTAX      Counter64
   MAX-ACCESS  read-only
   STATUS      current
   DESCRIPTION
      "Path: pbbBridgeGroup.performance.mibCounters.ifInDiscardsNoMacFit

       64 bit unsigned wrappable counter."
   ::= {pr1645v2PbbBGriMVMibCountersEntry 2231369728}

pr1645v2PbbBGriMVMibCountersInDropNUCast OBJECT-TYPE
   SYNTAX      Counter64
   MAX-ACCESS  read-only
   STATUS      current
   DESCRIPTION
      "Path: pbbBridgeGroup.performance.mibCounters.ifInDiscardsNUCast

       64 bit unsigned wrappable counter."
   ::= {pr1645v2PbbBGriMVMibCountersEntry 2281701376}

pr1645v2PbbBGriMVMibCountersInDropFilter OBJECT-TYPE
   SYNTAX      Counter64
   MAX-ACCESS  read-only
   STATUS      current
   DESCRIPTION
      "Path: pbbBridgeGroup.performance.mibCounters.ifInDiscardsFilter

       64 bit unsigned wrappable counter."
   ::= {pr1645v2PbbBGriMVMibCountersEntry 2298478592}

pr1645v2PbbBGriMVMibCountersInBandwidth15sec OBJECT-TYPE
   SYNTAX      Integer32
   MAX-ACCESS  read-only
   STATUS      current
   DESCRIPTION
      "Path: pbbBridgeGroup.performance.mibCounters.ifInBandwidth.15sec

       unit name = bps
       formula = 8 * ; 8 /"
   ::= {pr1645v2PbbBGriMVMibCountersEntry 3037003776}

pr1645v2PbbBGriMVMibCountersInBandwidth30sec OBJECT-TYPE
   SYNTAX      Integer32
   MAX-ACCESS  read-only
   STATUS      current
   DESCRIPTION
      "Path: pbbBridgeGroup.performance.mibCounters.ifInBandwidth.30sec

       unit name = bps
       formula = 8 * ; 8 /"
   ::= {pr1645v2PbbBGriMVMibCountersEntry 3037331456}

pr1645v2PbbBGriMVMibCountersInBandwidth1min OBJECT-TYPE
   SYNTAX      Integer32
   MAX-ACCESS  read-only
   STATUS      current
   DESCRIPTION
      "Path: pbbBridgeGroup.performance.mibCounters.ifInBandwidth.1min

       unit name = bps
       formula = 8 * ; 8 /"
   ::= {pr1645v2PbbBGriMVMibCountersEntry 3037986816}

pr1645v2PbbBGriMVMibCountersInBandwidth2min OBJECT-TYPE
   SYNTAX      Integer32
   MAX-ACCESS  read-only
   STATUS      current
   DESCRIPTION
      "Path: pbbBridgeGroup.performance.mibCounters.ifInBandwidth.2min

       unit name = bps
       formula = 8 * ; 8 /"
   ::= {pr1645v2PbbBGriMVMibCountersEntry 3039297536}

pr1645v2PbbBGriMVMibCountersInBandwidth5min OBJECT-TYPE
   SYNTAX      Integer32
   MAX-ACCESS  read-only
   STATUS      current
   DESCRIPTION
      "Path: pbbBridgeGroup.performance.mibCounters.ifInBandwidth.5min

       unit name = bps
       formula = 8 * ; 8 /"
   ::= {pr1645v2PbbBGriMVMibCountersEntry 3043229696}

pr1645v2PbbBGriMVMibCountersOutOctets OBJECT-TYPE
   SYNTAX      Counter64
   MAX-ACCESS  read-only
   STATUS      current
   DESCRIPTION
      "Path: pbbBridgeGroup.performance.mibCounters.ifOutOctets

       64 bit unsigned wrappable counter."
   ::= {pr1645v2PbbBGriMVMibCountersEntry 1929379840}

pr1645v2PbbBGriMVMibCountersOutUcastPkts OBJECT-TYPE
   SYNTAX      Counter64
   MAX-ACCESS  read-only
   STATUS      current
   DESCRIPTION
      "Path: pbbBridgeGroup.performance.mibCounters.ifOutUcastPkts

       64 bit unsigned wrappable counter."
   ::= {pr1645v2PbbBGriMVMibCountersEntry 1946157056}

pr1645v2PbbBGriMVMibCountersOutNUcastPkts OBJECT-TYPE
   SYNTAX      Counter64
   MAX-ACCESS  read-only
   STATUS      current
   DESCRIPTION
      "Path: pbbBridgeGroup.performance.mibCounters.ifOutNUcastPkts

       64 bit unsigned wrappable counter."
   ::= {pr1645v2PbbBGriMVMibCountersEntry 1962934272}

pr1645v2PbbBGriMVMibCountersOutBcastPkts OBJECT-TYPE
   SYNTAX      Counter64
   MAX-ACCESS  read-only
   STATUS      current
   DESCRIPTION
      "Path: pbbBridgeGroup.performance.mibCounters.ifOutBcastPkts

       64 bit unsigned wrappable counter."
   ::= {pr1645v2PbbBGriMVMibCountersEntry 3640655872}

pr1645v2PbbBGriMVMibCountersOutMcastPkts OBJECT-TYPE
   SYNTAX      Counter64
   MAX-ACCESS  read-only
   STATUS      current
   DESCRIPTION
      "Path: pbbBridgeGroup.performance.mibCounters.ifOutMcastPkts

       64 bit unsigned wrappable counter."
   ::= {pr1645v2PbbBGriMVMibCountersEntry 3808428032}

pr1645v2PbbBGriMVMibCountersOutDiscards OBJECT-TYPE
   SYNTAX      Counter64
   MAX-ACCESS  read-only
   STATUS      current
   DESCRIPTION
      "Path: pbbBridgeGroup.performance.mibCounters.ifOutDiscards

       64 bit unsigned wrappable counter."
   ::= {pr1645v2PbbBGriMVMibCountersEntry 1979711488}

pr1645v2PbbBGriMVMibCountersOutErrors OBJECT-TYPE
   SYNTAX      Counter64
   MAX-ACCESS  read-only
   STATUS      current
   DESCRIPTION
      "Path: pbbBridgeGroup.performance.mibCounters.ifOutErrors

       64 bit unsigned wrappable counter."
   ::= {pr1645v2PbbBGriMVMibCountersEntry 1996488704}

pr1645v2PbbBGriMVMibCountersOutQLen OBJECT-TYPE
   SYNTAX      Counter32
   MAX-ACCESS  read-only
   STATUS      current
   DESCRIPTION
      "Path: pbbBridgeGroup.performance.mibCounters.ifOutQLen

       32 bit unsigned wrappable counter."
   ::= {pr1645v2PbbBGriMVMibCountersEntry 2013265920}

pr1645v2PbbBGriMVMibCountersOutDropEx OBJECT-TYPE
   SYNTAX      Counter64
   MAX-ACCESS  read-only
   STATUS      current
   DESCRIPTION
      "Path: pbbBridgeGroup.performance.mibCounters.ifOutDropLevelExceeded

       64 bit unsigned wrappable counter."
   ::= {pr1645v2PbbBGriMVMibCountersEntry 2030043136}

pr1645v2PbbBGriMVMibCountersOutDropNoArp OBJECT-TYPE
   SYNTAX      Counter64
   MAX-ACCESS  read-only
   STATUS      current
   DESCRIPTION
      "Path: pbbBridgeGroup.performance.mibCounters.ifOutDiscardsNoArp

       64 bit unsigned wrappable counter."
   ::= {pr1645v2PbbBGriMVMibCountersEntry 2248146944}

pr1645v2PbbBGriMVMibCountersOutDropFilter OBJECT-TYPE
   SYNTAX      Counter64
   MAX-ACCESS  read-only
   STATUS      current
   DESCRIPTION
      "Path: pbbBridgeGroup.performance.mibCounters.ifOutDiscardsFilter

       64 bit unsigned wrappable counter."
   ::= {pr1645v2PbbBGriMVMibCountersEntry 2315255808}

pr1645v2PbbBGriMVMibCountersOutBandwidth15sec OBJECT-TYPE
   SYNTAX      Integer32
   MAX-ACCESS  read-only
   STATUS      current
   DESCRIPTION
      "Path: pbbBridgeGroup.performance.mibCounters.ifOutBandwidth.15sec

       unit name = bps
       formula = 8 * ; 8 /"
   ::= {pr1645v2PbbBGriMVMibCountersEntry 3053780992}

pr1645v2PbbBGriMVMibCountersOutBandwidth30sec OBJECT-TYPE
   SYNTAX      Integer32
   MAX-ACCESS  read-only
   STATUS      current
   DESCRIPTION
      "Path: pbbBridgeGroup.performance.mibCounters.ifOutBandwidth.30sec

       unit name = bps
       formula = 8 * ; 8 /"
   ::= {pr1645v2PbbBGriMVMibCountersEntry 3054108672}

pr1645v2PbbBGriMVMibCountersOutBandwidth1min OBJECT-TYPE
   SYNTAX      Integer32
   MAX-ACCESS  read-only
   STATUS      current
   DESCRIPTION
      "Path: pbbBridgeGroup.performance.mibCounters.ifOutBandwidth.1min

       unit name = bps
       formula = 8 * ; 8 /"
   ::= {pr1645v2PbbBGriMVMibCountersEntry 3054764032}

pr1645v2PbbBGriMVMibCountersOutBandwidth2min OBJECT-TYPE
   SYNTAX      Integer32
   MAX-ACCESS  read-only
   STATUS      current
   DESCRIPTION
      "Path: pbbBridgeGroup.performance.mibCounters.ifOutBandwidth.2min

       unit name = bps
       formula = 8 * ; 8 /"
   ::= {pr1645v2PbbBGriMVMibCountersEntry 3056074752}

pr1645v2PbbBGriMVMibCountersOutBandwidth5min OBJECT-TYPE
   SYNTAX      Integer32
   MAX-ACCESS  read-only
   STATUS      current
   DESCRIPTION
      "Path: pbbBridgeGroup.performance.mibCounters.ifOutBandwidth.5min

       unit name = bps
       formula = 8 * ; 8 /"
   ::= {pr1645v2PbbBGriMVMibCountersEntry 3060006912}

pr1645v2PbbBGriMVMibCountersH2P OBJECT-TYPE
   SYNTAX      SEQUENCE OF Pr1645v2PbbBGriMVMibCountersH2PEntry
   MAX-ACCESS  not-accessible
   STATUS      current
   DESCRIPTION
      ""
   ::= {pr1645v2PbbBGriMVMibCounters 2046820352}

pr1645v2PbbBGriMVMibCountersH2PEntry OBJECT-TYPE
   SYNTAX      Pr1645v2PbbBGriMVMibCountersH2PEntry
   MAX-ACCESS  not-accessible
   STATUS      current
   DESCRIPTION
      ""
   INDEX      { pr1645v2PbbBGriMVMibCountersH2PGlobalIx,
                pr1645v2PbbBGriMVMibCountersH2PTableIx }
   ::= {pr1645v2PbbBGriMVMibCountersH2P 1}

Pr1645v2PbbBGriMVMibCountersH2PEntry ::=
   SEQUENCE
      {
      pr1645v2PbbBGriMVMibCountersH2PGlobalIx
         GlobalIndex,
      pr1645v2PbbBGriMVMibCountersH2PTableIx
         TableIndex,
      pr1645v2PbbBGriMVMibCountersH2PSysUpTime
         TimeTicks,
      pr1645v2PbbBGriMVMibCountersH2PIfUpTime
         TimeTicks,
      pr1645v2PbbBGriMVMibCountersH2PIfStatChanges
         Counter32,
      pr1645v2PbbBGriMVMibCountersH2PIfInOctets
         Counter64,
      pr1645v2PbbBGriMVMibCountersH2PIfInUCPkts
         Counter64,
      pr1645v2PbbBGriMVMibCountersH2PIfInNUCPkts
         Counter64,
      pr1645v2PbbBGriMVMibCountersH2PIfInBCPkts
         Counter64,
      pr1645v2PbbBGriMVMibCountersH2PIfInMCPkts
         Counter64,
      pr1645v2PbbBGriMVMibCountersH2PIfInDiscards
         Counter64,
      pr1645v2PbbBGriMVMibCountersH2PIfInErrors
         Counter64,
      pr1645v2PbbBGriMVMibCountersH2PIfInUnkwn
         Counter64,
      pr1645v2PbbBGriMVMibCountersH2PInDropEx
         Counter64,
      pr1645v2PbbBGriMVMibCountersH2PInDropNoMac
         Counter64,
      pr1645v2PbbBGriMVMibCountersH2PInDropNUCast
         Counter64,
      pr1645v2PbbBGriMVMibCountersH2PInDropFilter
         Counter64,
      pr1645v2PbbBGriMVMibCountersH2PIfInBandwidth
         Integer32,
      pr1645v2PbbBGriMVMibCountersH2PIfOutOctets
         Counter64,
      pr1645v2PbbBGriMVMibCountersH2PIfOutUCPkts
         Counter64,
      pr1645v2PbbBGriMVMibCountersH2PIfOutNUCPkts
         Counter64,
      pr1645v2PbbBGriMVMibCountersH2PIfOutBCPkts
         Counter64,
      pr1645v2PbbBGriMVMibCountersH2PIfOutMCPkts
         Counter64,
      pr1645v2PbbBGriMVMibCountersH2PIfOutDiscards
         Counter64,
      pr1645v2PbbBGriMVMibCountersH2PIfOutErrors
         Counter64,
      pr1645v2PbbBGriMVMibCountersH2POutDropEx
         Counter64,
      pr1645v2PbbBGriMVMibCountersH2POutDropNoArp
         Counter64,
      pr1645v2PbbBGriMVMibCountersH2POutDropFilter
         Counter64,
      pr1645v2PbbBGriMVMibCountersH2PIfOutBandwidth
         Integer32,
      pr1645v2PbbBGriMVMibCountersH2PIfErrSec
         Counter32
      }

pr1645v2PbbBGriMVMibCountersH2PGlobalIx OBJECT-TYPE
   SYNTAX      GlobalIndex
   MAX-ACCESS  not-accessible
   STATUS      current
   DESCRIPTION
      "The value of the tlsCntTreeGlobalIndex of the MANAGED OBJECT."
   ::= {pr1645v2PbbBGriMVMibCountersH2PEntry 10}

pr1645v2PbbBGriMVMibCountersH2PTableIx OBJECT-TYPE
   SYNTAX      TableIndex
   MAX-ACCESS  not-accessible
   STATUS      current
   DESCRIPTION
      ""
   ::= {pr1645v2PbbBGriMVMibCountersH2PEntry 11}

pr1645v2PbbBGriMVMibCountersH2PSysUpTime OBJECT-TYPE
   SYNTAX      TimeTicks
   MAX-ACCESS  read-only
   STATUS      current
   DESCRIPTION
      "Path: pbbBridgeGroup.performance.mibCounters.h2Performance.sysUpTime

       Time in centi-second."
   ::= {pr1645v2PbbBGriMVMibCountersH2PEntry 16777216}

pr1645v2PbbBGriMVMibCountersH2PIfUpTime OBJECT-TYPE
   SYNTAX      TimeTicks
   MAX-ACCESS  read-only
   STATUS      current
   DESCRIPTION
      "Path: pbbBridgeGroup.performance.mibCounters.h2Performance.ifUpTime

       Time in centi-second."
   ::= {pr1645v2PbbBGriMVMibCountersH2PEntry 33554432}

pr1645v2PbbBGriMVMibCountersH2PIfStatChanges OBJECT-TYPE
   SYNTAX      Counter32
   MAX-ACCESS  read-only
   STATUS      current
   DESCRIPTION
      "Path: pbbBridgeGroup.performance.mibCounters.h2Performance.ifStatusChanges

       32 bit unsigned wrappable counter."
   ::= {pr1645v2PbbBGriMVMibCountersH2PEntry 50331648}

pr1645v2PbbBGriMVMibCountersH2PIfInOctets OBJECT-TYPE
   SYNTAX      Counter64
   MAX-ACCESS  read-only
   STATUS      current
   DESCRIPTION
      "Path: pbbBridgeGroup.performance.mibCounters.h2Performance.ifInOctets

       64 bit unsigned wrappable counter."
   ::= {pr1645v2PbbBGriMVMibCountersH2PEntry 67108864}

pr1645v2PbbBGriMVMibCountersH2PIfInUCPkts OBJECT-TYPE
   SYNTAX      Counter64
   MAX-ACCESS  read-only
   STATUS      current
   DESCRIPTION
      "Path: pbbBridgeGroup.performance.mibCounters.h2Performance.ifInUcastPkts

       64 bit unsigned wrappable counter."
   ::= {pr1645v2PbbBGriMVMibCountersH2PEntry 83886080}

pr1645v2PbbBGriMVMibCountersH2PIfInNUCPkts OBJECT-TYPE
   SYNTAX      Counter64
   MAX-ACCESS  read-only
   STATUS      current
   DESCRIPTION
      "Path: pbbBridgeGroup.performance.mibCounters.h2Performance.ifInNUcastPkts

       64 bit unsigned wrappable counter."
   ::= {pr1645v2PbbBGriMVMibCountersH2PEntry 100663296}

pr1645v2PbbBGriMVMibCountersH2PIfInBCPkts OBJECT-TYPE
   SYNTAX      Counter64
   MAX-ACCESS  read-only
   STATUS      current
   DESCRIPTION
      "Path: pbbBridgeGroup.performance.mibCounters.h2Performance.ifInBcastPkts

       64 bit unsigned wrappable counter."
   ::= {pr1645v2PbbBGriMVMibCountersH2PEntry 419430400}

pr1645v2PbbBGriMVMibCountersH2PIfInMCPkts OBJECT-TYPE
   SYNTAX      Counter64
   MAX-ACCESS  read-only
   STATUS      current
   DESCRIPTION
      "Path: pbbBridgeGroup.performance.mibCounters.h2Performance.ifInMcastPkts

       64 bit unsigned wrappable counter."
   ::= {pr1645v2PbbBGriMVMibCountersH2PEntry 436207616}

pr1645v2PbbBGriMVMibCountersH2PIfInDiscards OBJECT-TYPE
   SYNTAX      Counter64
   MAX-ACCESS  read-only
   STATUS      current
   DESCRIPTION
      "Path: pbbBridgeGroup.performance.mibCounters.h2Performance.ifInDiscards

       64 bit unsigned wrappable counter."
   ::= {pr1645v2PbbBGriMVMibCountersH2PEntry 117440512}

pr1645v2PbbBGriMVMibCountersH2PIfInErrors OBJECT-TYPE
   SYNTAX      Counter64
   MAX-ACCESS  read-only
   STATUS      current
   DESCRIPTION
      "Path: pbbBridgeGroup.performance.mibCounters.h2Performance.ifInErrors

       64 bit unsigned wrappable counter."
   ::= {pr1645v2PbbBGriMVMibCountersH2PEntry 134217728}

pr1645v2PbbBGriMVMibCountersH2PIfInUnkwn OBJECT-TYPE
   SYNTAX      Counter64
   MAX-ACCESS  read-only
   STATUS      current
   DESCRIPTION
      "Path: pbbBridgeGroup.performance.mibCounters.h2Performance.ifInUnknownProtos

       64 bit unsigned wrappable counter."
   ::= {pr1645v2PbbBGriMVMibCountersH2PEntry 150994944}

pr1645v2PbbBGriMVMibCountersH2PInDropEx OBJECT-TYPE
   SYNTAX      Counter64
   MAX-ACCESS  read-only
   STATUS      current
   DESCRIPTION
      "Path: pbbBridgeGroup.performance.mibCounters.h2Performance.ifInDropLevelExceeded

       64 bit unsigned wrappable counter."
   ::= {pr1645v2PbbBGriMVMibCountersH2PEntry 335544320}

pr1645v2PbbBGriMVMibCountersH2PInDropNoMac OBJECT-TYPE
   SYNTAX      Counter64
   MAX-ACCESS  read-only
   STATUS      current
   DESCRIPTION
      "Path: pbbBridgeGroup.performance.mibCounters.h2Performance.fInDiscardsNoMacFit

       64 bit unsigned wrappable counter."
   ::= {pr1645v2PbbBGriMVMibCountersH2PEntry 301989888}

pr1645v2PbbBGriMVMibCountersH2PInDropNUCast OBJECT-TYPE
   SYNTAX      Counter64
   MAX-ACCESS  read-only
   STATUS      current
   DESCRIPTION
      "Path: pbbBridgeGroup.performance.mibCounters.h2Performance.fInDiscardsNUCast

       64 bit unsigned wrappable counter."
   ::= {pr1645v2PbbBGriMVMibCountersH2PEntry 318767104}

pr1645v2PbbBGriMVMibCountersH2PInDropFilter OBJECT-TYPE
   SYNTAX      Counter64
   MAX-ACCESS  read-only
   STATUS      current
   DESCRIPTION
      "Path: pbbBridgeGroup.performance.mibCounters.h2Performance.fInDiscardsFilter

       64 bit unsigned wrappable counter."
   ::= {pr1645v2PbbBGriMVMibCountersH2PEntry 385875968}

pr1645v2PbbBGriMVMibCountersH2PIfInBandwidth OBJECT-TYPE
   SYNTAX      Integer32
   MAX-ACCESS  read-only
   STATUS      current
   DESCRIPTION
      "Path: pbbBridgeGroup.performance.mibCounters.h2Performance.ifInBandwidth

       unit name = bps
       formula = 8 * ; 8 /"
   ::= {pr1645v2PbbBGriMVMibCountersH2PEntry 268435456}

pr1645v2PbbBGriMVMibCountersH2PIfOutOctets OBJECT-TYPE
   SYNTAX      Counter64
   MAX-ACCESS  read-only
   STATUS      current
   DESCRIPTION
      "Path: pbbBridgeGroup.performance.mibCounters.h2Performance.ifOutOctets

       64 bit unsigned wrappable counter."
   ::= {pr1645v2PbbBGriMVMibCountersH2PEntry 167772160}

pr1645v2PbbBGriMVMibCountersH2PIfOutUCPkts OBJECT-TYPE
   SYNTAX      Counter64
   MAX-ACCESS  read-only
   STATUS      current
   DESCRIPTION
      "Path: pbbBridgeGroup.performance.mibCounters.h2Performance.ifOutUcastPkts

       64 bit unsigned wrappable counter."
   ::= {pr1645v2PbbBGriMVMibCountersH2PEntry 184549376}

pr1645v2PbbBGriMVMibCountersH2PIfOutNUCPkts OBJECT-TYPE
   SYNTAX      Counter64
   MAX-ACCESS  read-only
   STATUS      current
   DESCRIPTION
      "Path: pbbBridgeGroup.performance.mibCounters.h2Performance.ifOutNUcastPkts

       64 bit unsigned wrappable counter."
   ::= {pr1645v2PbbBGriMVMibCountersH2PEntry 201326592}

pr1645v2PbbBGriMVMibCountersH2PIfOutBCPkts OBJECT-TYPE
   SYNTAX      Counter64
   MAX-ACCESS  read-only
   STATUS      current
   DESCRIPTION
      "Path: pbbBridgeGroup.performance.mibCounters.h2Performance.ifOutBcastPkts

       64 bit unsigned wrappable counter."
   ::= {pr1645v2PbbBGriMVMibCountersH2PEntry 452984832}

pr1645v2PbbBGriMVMibCountersH2PIfOutMCPkts OBJECT-TYPE
   SYNTAX      Counter64
   MAX-ACCESS  read-only
   STATUS      current
   DESCRIPTION
      "Path: pbbBridgeGroup.performance.mibCounters.h2Performance.ifOutMcastPkts

       64 bit unsigned wrappable counter."
   ::= {pr1645v2PbbBGriMVMibCountersH2PEntry 469762048}

pr1645v2PbbBGriMVMibCountersH2PIfOutDiscards OBJECT-TYPE
   SYNTAX      Counter64
   MAX-ACCESS  read-only
   STATUS      current
   DESCRIPTION
      "Path: pbbBridgeGroup.performance.mibCounters.h2Performance.ifOutDiscards

       64 bit unsigned wrappable counter."
   ::= {pr1645v2PbbBGriMVMibCountersH2PEntry 218103808}

pr1645v2PbbBGriMVMibCountersH2PIfOutErrors OBJECT-TYPE
   SYNTAX      Counter64
   MAX-ACCESS  read-only
   STATUS      current
   DESCRIPTION
      "Path: pbbBridgeGroup.performance.mibCounters.h2Performance.ifOutErrors

       64 bit unsigned wrappable counter."
   ::= {pr1645v2PbbBGriMVMibCountersH2PEntry 234881024}

pr1645v2PbbBGriMVMibCountersH2POutDropEx OBJECT-TYPE
   SYNTAX      Counter64
   MAX-ACCESS  read-only
   STATUS      current
   DESCRIPTION
      "Path: pbbBridgeGroup.performance.mibCounters.h2Performance.ifOutDropLevelExceeded

       64 bit unsigned wrappable counter."
   ::= {pr1645v2PbbBGriMVMibCountersH2PEntry 352321536}

pr1645v2PbbBGriMVMibCountersH2POutDropNoArp OBJECT-TYPE
   SYNTAX      Counter64
   MAX-ACCESS  read-only
   STATUS      current
   DESCRIPTION
      "Path: pbbBridgeGroup.performance.mibCounters.h2Performance.ifOutDiscardsNoArp

       64 bit unsigned wrappable counter."
   ::= {pr1645v2PbbBGriMVMibCountersH2PEntry 369098752}

pr1645v2PbbBGriMVMibCountersH2POutDropFilter OBJECT-TYPE
   SYNTAX      Counter64
   MAX-ACCESS  read-only
   STATUS      current
   DESCRIPTION
      "Path: pbbBridgeGroup.performance.mibCounters.h2Performance.ifOutDiscardsFilter

       64 bit unsigned wrappable counter."
   ::= {pr1645v2PbbBGriMVMibCountersH2PEntry 402653184}

pr1645v2PbbBGriMVMibCountersH2PIfOutBandwidth OBJECT-TYPE
   SYNTAX      Integer32
   MAX-ACCESS  read-only
   STATUS      current
   DESCRIPTION
      "Path: pbbBridgeGroup.performance.mibCounters.h2Performance.ifOutBandwidth

       unit name = bps
       formula = 8 * ; 8 /"
   ::= {pr1645v2PbbBGriMVMibCountersH2PEntry 285212672}

pr1645v2PbbBGriMVMibCountersH2PIfErrSec OBJECT-TYPE
   SYNTAX      Counter32
   MAX-ACCESS  read-only
   STATUS      current
   DESCRIPTION
      "Path: pbbBridgeGroup.performance.mibCounters.h2Performance.ifErrSec

       32 bit unsigned wrappable counter."
   ::= {pr1645v2PbbBGriMVMibCountersH2PEntry 251658240}

pr1645v2PbbBGriMVMibCountersH24P OBJECT-TYPE
   SYNTAX      SEQUENCE OF Pr1645v2PbbBGriMVMibCountersH24PEntry
   MAX-ACCESS  not-accessible
   STATUS      current
   DESCRIPTION
      ""
   ::= {pr1645v2PbbBGriMVMibCounters 2063597568}

pr1645v2PbbBGriMVMibCountersH24PEntry OBJECT-TYPE
   SYNTAX      Pr1645v2PbbBGriMVMibCountersH24PEntry
   MAX-ACCESS  not-accessible
   STATUS      current
   DESCRIPTION
      ""
   INDEX      { pr1645v2PbbBGriMVMibCountersH24PGlobalIx,
                pr1645v2PbbBGriMVMibCountersH24PTableIx }
   ::= {pr1645v2PbbBGriMVMibCountersH24P 1}

Pr1645v2PbbBGriMVMibCountersH24PEntry ::=
   SEQUENCE
      {
      pr1645v2PbbBGriMVMibCountersH24PGlobalIx
         GlobalIndex,
      pr1645v2PbbBGriMVMibCountersH24PTableIx
         TableIndex,
      pr1645v2PbbBGriMVMibCountersH24PSysUpTime
         TimeTicks,
      pr1645v2PbbBGriMVMibCountersH24PIfUpTime
         TimeTicks,
      pr1645v2PbbBGriMVMibCountersH24PIfStatChanges
         Counter32,
      pr1645v2PbbBGriMVMibCountersH24PIfInOctets
         Counter64,
      pr1645v2PbbBGriMVMibCountersH24PIfInUCPkts
         Counter64,
      pr1645v2PbbBGriMVMibCountersH24PIfInNUCPkts
         Counter64,
      pr1645v2PbbBGriMVMibCountersH24PIfInBCPkts
         Counter64,
      pr1645v2PbbBGriMVMibCountersH24PIfInMCPkts
         Counter64,
      pr1645v2PbbBGriMVMibCountersH24PIfInDiscards
         Counter64,
      pr1645v2PbbBGriMVMibCountersH24PIfInErrors
         Counter64,
      pr1645v2PbbBGriMVMibCountersH24PIfInUnkwn
         Counter64,
      pr1645v2PbbBGriMVMibCountersH24PInDropEx
         Counter64,
      pr1645v2PbbBGriMVMibCountersH24PInDropNoMac
         Counter64,
      pr1645v2PbbBGriMVMibCountersH24PInDropNUCast
         Counter64,
      pr1645v2PbbBGriMVMibCountersH24PInDropFilter
         Counter64,
      pr1645v2PbbBGriMVMibCountersH24PIfInBandwidth
         Integer32,
      pr1645v2PbbBGriMVMibCountersH24PIfOutOctets
         Counter64,
      pr1645v2PbbBGriMVMibCountersH24PIfOutUCPkts
         Counter64,
      pr1645v2PbbBGriMVMibCountersH24PIfOutNUCPkts
         Counter64,
      pr1645v2PbbBGriMVMibCountersH24PIfOutBCPkts
         Counter64,
      pr1645v2PbbBGriMVMibCountersH24PIfOutMCPkts
         Counter64,
      pr1645v2PbbBGriMVMibCountersH24PIfOutDiscards
         Counter64,
      pr1645v2PbbBGriMVMibCountersH24PIfOutErrors
         Counter64,
      pr1645v2PbbBGriMVMibCountersH24POutDropEx
         Counter64,
      pr1645v2PbbBGriMVMibCountersH24POutDropNoArp
         Counter64,
      pr1645v2PbbBGriMVMibCountersH24POutDropFilter
         Counter64,
      pr1645v2PbbBGriMVMibCountersH24PIfOutBandwidth
         Integer32,
      pr1645v2PbbBGriMVMibCountersH24PIfErrSec
         Counter32
      }

pr1645v2PbbBGriMVMibCountersH24PGlobalIx OBJECT-TYPE
   SYNTAX      GlobalIndex
   MAX-ACCESS  not-accessible
   STATUS      current
   DESCRIPTION
      "The value of the tlsCntTreeGlobalIndex of the MANAGED OBJECT."
   ::= {pr1645v2PbbBGriMVMibCountersH24PEntry 10}

pr1645v2PbbBGriMVMibCountersH24PTableIx OBJECT-TYPE
   SYNTAX      TableIndex
   MAX-ACCESS  not-accessible
   STATUS      current
   DESCRIPTION
      ""
   ::= {pr1645v2PbbBGriMVMibCountersH24PEntry 11}

pr1645v2PbbBGriMVMibCountersH24PSysUpTime OBJECT-TYPE
   SYNTAX      TimeTicks
   MAX-ACCESS  read-only
   STATUS      current
   DESCRIPTION
      "Path: pbbBridgeGroup.performance.mibCounters.h24Performance.sysUpTime

       Time in centi-second."
   ::= {pr1645v2PbbBGriMVMibCountersH24PEntry 16777216}

pr1645v2PbbBGriMVMibCountersH24PIfUpTime OBJECT-TYPE
   SYNTAX      TimeTicks
   MAX-ACCESS  read-only
   STATUS      current
   DESCRIPTION
      "Path: pbbBridgeGroup.performance.mibCounters.h24Performance.ifUpTime

       Time in centi-second."
   ::= {pr1645v2PbbBGriMVMibCountersH24PEntry 33554432}

pr1645v2PbbBGriMVMibCountersH24PIfStatChanges OBJECT-TYPE
   SYNTAX      Counter32
   MAX-ACCESS  read-only
   STATUS      current
   DESCRIPTION
      "Path: pbbBridgeGroup.performance.mibCounters.h24Performance.ifStatusChanges

       32 bit unsigned wrappable counter."
   ::= {pr1645v2PbbBGriMVMibCountersH24PEntry 50331648}

pr1645v2PbbBGriMVMibCountersH24PIfInOctets OBJECT-TYPE
   SYNTAX      Counter64
   MAX-ACCESS  read-only
   STATUS      current
   DESCRIPTION
      "Path: pbbBridgeGroup.performance.mibCounters.h24Performance.ifInOctets

       64 bit unsigned wrappable counter."
   ::= {pr1645v2PbbBGriMVMibCountersH24PEntry 67108864}

pr1645v2PbbBGriMVMibCountersH24PIfInUCPkts OBJECT-TYPE
   SYNTAX      Counter64
   MAX-ACCESS  read-only
   STATUS      current
   DESCRIPTION
      "Path: pbbBridgeGroup.performance.mibCounters.h24Performance.ifInUcastPkts

       64 bit unsigned wrappable counter."
   ::= {pr1645v2PbbBGriMVMibCountersH24PEntry 83886080}

pr1645v2PbbBGriMVMibCountersH24PIfInNUCPkts OBJECT-TYPE
   SYNTAX      Counter64
   MAX-ACCESS  read-only
   STATUS      current
   DESCRIPTION
      "Path: pbbBridgeGroup.performance.mibCounters.h24Performance.ifInNUcastPkts

       64 bit unsigned wrappable counter."
   ::= {pr1645v2PbbBGriMVMibCountersH24PEntry 100663296}

pr1645v2PbbBGriMVMibCountersH24PIfInBCPkts OBJECT-TYPE
   SYNTAX      Counter64
   MAX-ACCESS  read-only
   STATUS      current
   DESCRIPTION
      "Path: pbbBridgeGroup.performance.mibCounters.h24Performance.ifInBcastPkts

       64 bit unsigned wrappable counter."
   ::= {pr1645v2PbbBGriMVMibCountersH24PEntry 419430400}

pr1645v2PbbBGriMVMibCountersH24PIfInMCPkts OBJECT-TYPE
   SYNTAX      Counter64
   MAX-ACCESS  read-only
   STATUS      current
   DESCRIPTION
      "Path: pbbBridgeGroup.performance.mibCounters.h24Performance.ifInMcastPkts

       64 bit unsigned wrappable counter."
   ::= {pr1645v2PbbBGriMVMibCountersH24PEntry 436207616}

pr1645v2PbbBGriMVMibCountersH24PIfInDiscards OBJECT-TYPE
   SYNTAX      Counter64
   MAX-ACCESS  read-only
   STATUS      current
   DESCRIPTION
      "Path: pbbBridgeGroup.performance.mibCounters.h24Performance.ifInDiscards

       64 bit unsigned wrappable counter."
   ::= {pr1645v2PbbBGriMVMibCountersH24PEntry 117440512}

pr1645v2PbbBGriMVMibCountersH24PIfInErrors OBJECT-TYPE
   SYNTAX      Counter64
   MAX-ACCESS  read-only
   STATUS      current
   DESCRIPTION
      "Path: pbbBridgeGroup.performance.mibCounters.h24Performance.ifInErrors

       64 bit unsigned wrappable counter."
   ::= {pr1645v2PbbBGriMVMibCountersH24PEntry 134217728}

pr1645v2PbbBGriMVMibCountersH24PIfInUnkwn OBJECT-TYPE
   SYNTAX      Counter64
   MAX-ACCESS  read-only
   STATUS      current
   DESCRIPTION
      "Path: pbbBridgeGroup.performance.mibCounters.h24Performance.ifInUnknownProtos

       64 bit unsigned wrappable counter."
   ::= {pr1645v2PbbBGriMVMibCountersH24PEntry 150994944}

pr1645v2PbbBGriMVMibCountersH24PInDropEx OBJECT-TYPE
   SYNTAX      Counter64
   MAX-ACCESS  read-only
   STATUS      current
   DESCRIPTION
      "Path: pbbBridgeGroup.performance.mibCounters.h24Performance.ifInDropLevelExceeded

       64 bit unsigned wrappable counter."
   ::= {pr1645v2PbbBGriMVMibCountersH24PEntry 335544320}

pr1645v2PbbBGriMVMibCountersH24PInDropNoMac OBJECT-TYPE
   SYNTAX      Counter64
   MAX-ACCESS  read-only
   STATUS      current
   DESCRIPTION
      "Path: pbbBridgeGroup.performance.mibCounters.h24Performance.fInDiscardsNoMacFit

       64 bit unsigned wrappable counter."
   ::= {pr1645v2PbbBGriMVMibCountersH24PEntry 301989888}

pr1645v2PbbBGriMVMibCountersH24PInDropNUCast OBJECT-TYPE
   SYNTAX      Counter64
   MAX-ACCESS  read-only
   STATUS      current
   DESCRIPTION
      "Path: pbbBridgeGroup.performance.mibCounters.h24Performance.fInDiscardsNUCast

       64 bit unsigned wrappable counter."
   ::= {pr1645v2PbbBGriMVMibCountersH24PEntry 318767104}

pr1645v2PbbBGriMVMibCountersH24PInDropFilter OBJECT-TYPE
   SYNTAX      Counter64
   MAX-ACCESS  read-only
   STATUS      current
   DESCRIPTION
      "Path: pbbBridgeGroup.performance.mibCounters.h24Performance.fInDiscardsFilter

       64 bit unsigned wrappable counter."
   ::= {pr1645v2PbbBGriMVMibCountersH24PEntry 385875968}

pr1645v2PbbBGriMVMibCountersH24PIfInBandwidth OBJECT-TYPE
   SYNTAX      Integer32
   MAX-ACCESS  read-only
   STATUS      current
   DESCRIPTION
      "Path: pbbBridgeGroup.performance.mibCounters.h24Performance.ifInBandwidth

       unit name = bps
       formula = 8 * ; 8 /"
   ::= {pr1645v2PbbBGriMVMibCountersH24PEntry 268435456}

pr1645v2PbbBGriMVMibCountersH24PIfOutOctets OBJECT-TYPE
   SYNTAX      Counter64
   MAX-ACCESS  read-only
   STATUS      current
   DESCRIPTION
      "Path: pbbBridgeGroup.performance.mibCounters.h24Performance.ifOutOctets

       64 bit unsigned wrappable counter."
   ::= {pr1645v2PbbBGriMVMibCountersH24PEntry 167772160}

pr1645v2PbbBGriMVMibCountersH24PIfOutUCPkts OBJECT-TYPE
   SYNTAX      Counter64
   MAX-ACCESS  read-only
   STATUS      current
   DESCRIPTION
      "Path: pbbBridgeGroup.performance.mibCounters.h24Performance.ifOutUcastPkts

       64 bit unsigned wrappable counter."
   ::= {pr1645v2PbbBGriMVMibCountersH24PEntry 184549376}

pr1645v2PbbBGriMVMibCountersH24PIfOutNUCPkts OBJECT-TYPE
   SYNTAX      Counter64
   MAX-ACCESS  read-only
   STATUS      current
   DESCRIPTION
      "Path: pbbBridgeGroup.performance.mibCounters.h24Performance.ifOutNUcastPkts

       64 bit unsigned wrappable counter."
   ::= {pr1645v2PbbBGriMVMibCountersH24PEntry 201326592}

pr1645v2PbbBGriMVMibCountersH24PIfOutBCPkts OBJECT-TYPE
   SYNTAX      Counter64
   MAX-ACCESS  read-only
   STATUS      current
   DESCRIPTION
      "Path: pbbBridgeGroup.performance.mibCounters.h24Performance.ifOutBcastPkts

       64 bit unsigned wrappable counter."
   ::= {pr1645v2PbbBGriMVMibCountersH24PEntry 452984832}

pr1645v2PbbBGriMVMibCountersH24PIfOutMCPkts OBJECT-TYPE
   SYNTAX      Counter64
   MAX-ACCESS  read-only
   STATUS      current
   DESCRIPTION
      "Path: pbbBridgeGroup.performance.mibCounters.h24Performance.ifOutMcastPkts

       64 bit unsigned wrappable counter."
   ::= {pr1645v2PbbBGriMVMibCountersH24PEntry 469762048}

pr1645v2PbbBGriMVMibCountersH24PIfOutDiscards OBJECT-TYPE
   SYNTAX      Counter64
   MAX-ACCESS  read-only
   STATUS      current
   DESCRIPTION
      "Path: pbbBridgeGroup.performance.mibCounters.h24Performance.ifOutDiscards

       64 bit unsigned wrappable counter."
   ::= {pr1645v2PbbBGriMVMibCountersH24PEntry 218103808}

pr1645v2PbbBGriMVMibCountersH24PIfOutErrors OBJECT-TYPE
   SYNTAX      Counter64
   MAX-ACCESS  read-only
   STATUS      current
   DESCRIPTION
      "Path: pbbBridgeGroup.performance.mibCounters.h24Performance.ifOutErrors

       64 bit unsigned wrappable counter."
   ::= {pr1645v2PbbBGriMVMibCountersH24PEntry 234881024}

pr1645v2PbbBGriMVMibCountersH24POutDropEx OBJECT-TYPE
   SYNTAX      Counter64
   MAX-ACCESS  read-only
   STATUS      current
   DESCRIPTION
      "Path: pbbBridgeGroup.performance.mibCounters.h24Performance.ifOutDropLevelExceeded

       64 bit unsigned wrappable counter."
   ::= {pr1645v2PbbBGriMVMibCountersH24PEntry 352321536}

pr1645v2PbbBGriMVMibCountersH24POutDropNoArp OBJECT-TYPE
   SYNTAX      Counter64
   MAX-ACCESS  read-only
   STATUS      current
   DESCRIPTION
      "Path: pbbBridgeGroup.performance.mibCounters.h24Performance.ifOutDiscardsNoArp

       64 bit unsigned wrappable counter."
   ::= {pr1645v2PbbBGriMVMibCountersH24PEntry 369098752}

pr1645v2PbbBGriMVMibCountersH24POutDropFilter OBJECT-TYPE
   SYNTAX      Counter64
   MAX-ACCESS  read-only
   STATUS      current
   DESCRIPTION
      "Path: pbbBridgeGroup.performance.mibCounters.h24Performance.ifOutDiscardsFilter

       64 bit unsigned wrappable counter."
   ::= {pr1645v2PbbBGriMVMibCountersH24PEntry 402653184}

pr1645v2PbbBGriMVMibCountersH24PIfOutBandwidth OBJECT-TYPE
   SYNTAX      Integer32
   MAX-ACCESS  read-only
   STATUS      current
   DESCRIPTION
      "Path: pbbBridgeGroup.performance.mibCounters.h24Performance.ifOutBandwidth

       unit name = bps
       formula = 8 * ; 8 /"
   ::= {pr1645v2PbbBGriMVMibCountersH24PEntry 285212672}

pr1645v2PbbBGriMVMibCountersH24PIfErrSec OBJECT-TYPE
   SYNTAX      Counter32
   MAX-ACCESS  read-only
   STATUS      current
   DESCRIPTION
      "Path: pbbBridgeGroup.performance.mibCounters.h24Performance.ifErrSec

       32 bit unsigned wrappable counter."
   ::= {pr1645v2PbbBGriMVMibCountersH24PEntry 251658240}

pr1645v2PbbBGriMVMibCountersD7P OBJECT-TYPE
   SYNTAX      SEQUENCE OF Pr1645v2PbbBGriMVMibCountersD7PEntry
   MAX-ACCESS  not-accessible
   STATUS      current
   DESCRIPTION
      ""
   ::= {pr1645v2PbbBGriMVMibCounters 2080374784}

pr1645v2PbbBGriMVMibCountersD7PEntry OBJECT-TYPE
   SYNTAX      Pr1645v2PbbBGriMVMibCountersD7PEntry
   MAX-ACCESS  not-accessible
   STATUS      current
   DESCRIPTION
      ""
   INDEX      { pr1645v2PbbBGriMVMibCountersD7PGlobalIx,
                pr1645v2PbbBGriMVMibCountersD7PTableIx }
   ::= {pr1645v2PbbBGriMVMibCountersD7P 1}

Pr1645v2PbbBGriMVMibCountersD7PEntry ::=
   SEQUENCE
      {
      pr1645v2PbbBGriMVMibCountersD7PGlobalIx
         GlobalIndex,
      pr1645v2PbbBGriMVMibCountersD7PTableIx
         TableIndex,
      pr1645v2PbbBGriMVMibCountersD7PSysUpTime
         TimeTicks,
      pr1645v2PbbBGriMVMibCountersD7PIfUpTime
         TimeTicks,
      pr1645v2PbbBGriMVMibCountersD7PIfStatChanges
         Counter32,
      pr1645v2PbbBGriMVMibCountersD7PIfInOctets
         Counter64,
      pr1645v2PbbBGriMVMibCountersD7PIfInUCPkts
         Counter64,
      pr1645v2PbbBGriMVMibCountersD7PIfInNUCPkts
         Counter64,
      pr1645v2PbbBGriMVMibCountersD7PIfInBCPkts
         Counter64,
      pr1645v2PbbBGriMVMibCountersD7PIfInMCPkts
         Counter64,
      pr1645v2PbbBGriMVMibCountersD7PIfInDiscards
         Counter64,
      pr1645v2PbbBGriMVMibCountersD7PIfInErrors
         Counter64,
      pr1645v2PbbBGriMVMibCountersD7PIfInUnkwn
         Counter64,
      pr1645v2PbbBGriMVMibCountersD7PInDropEx
         Counter64,
      pr1645v2PbbBGriMVMibCountersD7PInDropNoMac
         Counter64,
      pr1645v2PbbBGriMVMibCountersD7PInDropNUCast
         Counter64,
      pr1645v2PbbBGriMVMibCountersD7PInDropFilter
         Counter64,
      pr1645v2PbbBGriMVMibCountersD7PIfInBandwidth
         Integer32,
      pr1645v2PbbBGriMVMibCountersD7PIfOutOctets
         Counter64,
      pr1645v2PbbBGriMVMibCountersD7PIfOutUCPkts
         Counter64,
      pr1645v2PbbBGriMVMibCountersD7PIfOutNUCPkts
         Counter64,
      pr1645v2PbbBGriMVMibCountersD7PIfOutBCPkts
         Counter64,
      pr1645v2PbbBGriMVMibCountersD7PIfOutMCPkts
         Counter64,
      pr1645v2PbbBGriMVMibCountersD7PIfOutDiscards
         Counter64,
      pr1645v2PbbBGriMVMibCountersD7PIfOutErrors
         Counter64,
      pr1645v2PbbBGriMVMibCountersD7POutDropEx
         Counter64,
      pr1645v2PbbBGriMVMibCountersD7POutDropNoArp
         Counter64,
      pr1645v2PbbBGriMVMibCountersD7POutDropFilter
         Counter64,
      pr1645v2PbbBGriMVMibCountersD7PIfOutBandwidth
         Integer32,
      pr1645v2PbbBGriMVMibCountersD7PIfErrSec
         Counter32
      }

pr1645v2PbbBGriMVMibCountersD7PGlobalIx OBJECT-TYPE
   SYNTAX      GlobalIndex
   MAX-ACCESS  not-accessible
   STATUS      current
   DESCRIPTION
      "The value of the tlsCntTreeGlobalIndex of the MANAGED OBJECT."
   ::= {pr1645v2PbbBGriMVMibCountersD7PEntry 10}

pr1645v2PbbBGriMVMibCountersD7PTableIx OBJECT-TYPE
   SYNTAX      TableIndex
   MAX-ACCESS  not-accessible
   STATUS      current
   DESCRIPTION
      ""
   ::= {pr1645v2PbbBGriMVMibCountersD7PEntry 11}

pr1645v2PbbBGriMVMibCountersD7PSysUpTime OBJECT-TYPE
   SYNTAX      TimeTicks
   MAX-ACCESS  read-only
   STATUS      current
   DESCRIPTION
      "Path: pbbBridgeGroup.performance.mibCounters.d7Performance.sysUpTime

       Time in centi-second."
   ::= {pr1645v2PbbBGriMVMibCountersD7PEntry 16777216}

pr1645v2PbbBGriMVMibCountersD7PIfUpTime OBJECT-TYPE
   SYNTAX      TimeTicks
   MAX-ACCESS  read-only
   STATUS      current
   DESCRIPTION
      "Path: pbbBridgeGroup.performance.mibCounters.d7Performance.ifUpTime

       Time in centi-second."
   ::= {pr1645v2PbbBGriMVMibCountersD7PEntry 33554432}

pr1645v2PbbBGriMVMibCountersD7PIfStatChanges OBJECT-TYPE
   SYNTAX      Counter32
   MAX-ACCESS  read-only
   STATUS      current
   DESCRIPTION
      "Path: pbbBridgeGroup.performance.mibCounters.d7Performance.ifStatusChanges

       32 bit unsigned wrappable counter."
   ::= {pr1645v2PbbBGriMVMibCountersD7PEntry 50331648}

pr1645v2PbbBGriMVMibCountersD7PIfInOctets OBJECT-TYPE
   SYNTAX      Counter64
   MAX-ACCESS  read-only
   STATUS      current
   DESCRIPTION
      "Path: pbbBridgeGroup.performance.mibCounters.d7Performance.ifInOctets

       64 bit unsigned wrappable counter."
   ::= {pr1645v2PbbBGriMVMibCountersD7PEntry 67108864}

pr1645v2PbbBGriMVMibCountersD7PIfInUCPkts OBJECT-TYPE
   SYNTAX      Counter64
   MAX-ACCESS  read-only
   STATUS      current
   DESCRIPTION
      "Path: pbbBridgeGroup.performance.mibCounters.d7Performance.ifInUcastPkts

       64 bit unsigned wrappable counter."
   ::= {pr1645v2PbbBGriMVMibCountersD7PEntry 83886080}

pr1645v2PbbBGriMVMibCountersD7PIfInNUCPkts OBJECT-TYPE
   SYNTAX      Counter64
   MAX-ACCESS  read-only
   STATUS      current
   DESCRIPTION
      "Path: pbbBridgeGroup.performance.mibCounters.d7Performance.ifInNUcastPkts

       64 bit unsigned wrappable counter."
   ::= {pr1645v2PbbBGriMVMibCountersD7PEntry 100663296}

pr1645v2PbbBGriMVMibCountersD7PIfInBCPkts OBJECT-TYPE
   SYNTAX      Counter64
   MAX-ACCESS  read-only
   STATUS      current
   DESCRIPTION
      "Path: pbbBridgeGroup.performance.mibCounters.d7Performance.ifInBcastPkts

       64 bit unsigned wrappable counter."
   ::= {pr1645v2PbbBGriMVMibCountersD7PEntry 419430400}

pr1645v2PbbBGriMVMibCountersD7PIfInMCPkts OBJECT-TYPE
   SYNTAX      Counter64
   MAX-ACCESS  read-only
   STATUS      current
   DESCRIPTION
      "Path: pbbBridgeGroup.performance.mibCounters.d7Performance.ifInMcastPkts

       64 bit unsigned wrappable counter."
   ::= {pr1645v2PbbBGriMVMibCountersD7PEntry 436207616}

pr1645v2PbbBGriMVMibCountersD7PIfInDiscards OBJECT-TYPE
   SYNTAX      Counter64
   MAX-ACCESS  read-only
   STATUS      current
   DESCRIPTION
      "Path: pbbBridgeGroup.performance.mibCounters.d7Performance.ifInDiscards

       64 bit unsigned wrappable counter."
   ::= {pr1645v2PbbBGriMVMibCountersD7PEntry 117440512}

pr1645v2PbbBGriMVMibCountersD7PIfInErrors OBJECT-TYPE
   SYNTAX      Counter64
   MAX-ACCESS  read-only
   STATUS      current
   DESCRIPTION
      "Path: pbbBridgeGroup.performance.mibCounters.d7Performance.ifInErrors

       64 bit unsigned wrappable counter."
   ::= {pr1645v2PbbBGriMVMibCountersD7PEntry 134217728}

pr1645v2PbbBGriMVMibCountersD7PIfInUnkwn OBJECT-TYPE
   SYNTAX      Counter64
   MAX-ACCESS  read-only
   STATUS      current
   DESCRIPTION
      "Path: pbbBridgeGroup.performance.mibCounters.d7Performance.ifInUnknownProtos

       64 bit unsigned wrappable counter."
   ::= {pr1645v2PbbBGriMVMibCountersD7PEntry 150994944}

pr1645v2PbbBGriMVMibCountersD7PInDropEx OBJECT-TYPE
   SYNTAX      Counter64
   MAX-ACCESS  read-only
   STATUS      current
   DESCRIPTION
      "Path: pbbBridgeGroup.performance.mibCounters.d7Performance.ifInDropLevelExceeded

       64 bit unsigned wrappable counter."
   ::= {pr1645v2PbbBGriMVMibCountersD7PEntry 335544320}

pr1645v2PbbBGriMVMibCountersD7PInDropNoMac OBJECT-TYPE
   SYNTAX      Counter64
   MAX-ACCESS  read-only
   STATUS      current
   DESCRIPTION
      "Path: pbbBridgeGroup.performance.mibCounters.d7Performance.fInDiscardsNoMacFit

       64 bit unsigned wrappable counter."
   ::= {pr1645v2PbbBGriMVMibCountersD7PEntry 301989888}

pr1645v2PbbBGriMVMibCountersD7PInDropNUCast OBJECT-TYPE
   SYNTAX      Counter64
   MAX-ACCESS  read-only
   STATUS      current
   DESCRIPTION
      "Path: pbbBridgeGroup.performance.mibCounters.d7Performance.fInDiscardsNUCast

       64 bit unsigned wrappable counter."
   ::= {pr1645v2PbbBGriMVMibCountersD7PEntry 318767104}

pr1645v2PbbBGriMVMibCountersD7PInDropFilter OBJECT-TYPE
   SYNTAX      Counter64
   MAX-ACCESS  read-only
   STATUS      current
   DESCRIPTION
      "Path: pbbBridgeGroup.performance.mibCounters.d7Performance.fInDiscardsFilter

       64 bit unsigned wrappable counter."
   ::= {pr1645v2PbbBGriMVMibCountersD7PEntry 385875968}

pr1645v2PbbBGriMVMibCountersD7PIfInBandwidth OBJECT-TYPE
   SYNTAX      Integer32
   MAX-ACCESS  read-only
   STATUS      current
   DESCRIPTION
      "Path: pbbBridgeGroup.performance.mibCounters.d7Performance.ifInBandwidth

       unit name = bps
       formula = 8 * ; 8 /"
   ::= {pr1645v2PbbBGriMVMibCountersD7PEntry 268435456}

pr1645v2PbbBGriMVMibCountersD7PIfOutOctets OBJECT-TYPE
   SYNTAX      Counter64
   MAX-ACCESS  read-only
   STATUS      current
   DESCRIPTION
      "Path: pbbBridgeGroup.performance.mibCounters.d7Performance.ifOutOctets

       64 bit unsigned wrappable counter."
   ::= {pr1645v2PbbBGriMVMibCountersD7PEntry 167772160}

pr1645v2PbbBGriMVMibCountersD7PIfOutUCPkts OBJECT-TYPE
   SYNTAX      Counter64
   MAX-ACCESS  read-only
   STATUS      current
   DESCRIPTION
      "Path: pbbBridgeGroup.performance.mibCounters.d7Performance.ifOutUcastPkts

       64 bit unsigned wrappable counter."
   ::= {pr1645v2PbbBGriMVMibCountersD7PEntry 184549376}

pr1645v2PbbBGriMVMibCountersD7PIfOutNUCPkts OBJECT-TYPE
   SYNTAX      Counter64
   MAX-ACCESS  read-only
   STATUS      current
   DESCRIPTION
      "Path: pbbBridgeGroup.performance.mibCounters.d7Performance.ifOutNUcastPkts

       64 bit unsigned wrappable counter."
   ::= {pr1645v2PbbBGriMVMibCountersD7PEntry 201326592}

pr1645v2PbbBGriMVMibCountersD7PIfOutBCPkts OBJECT-TYPE
   SYNTAX      Counter64
   MAX-ACCESS  read-only
   STATUS      current
   DESCRIPTION
      "Path: pbbBridgeGroup.performance.mibCounters.d7Performance.ifOutBcastPkts

       64 bit unsigned wrappable counter."
   ::= {pr1645v2PbbBGriMVMibCountersD7PEntry 452984832}

pr1645v2PbbBGriMVMibCountersD7PIfOutMCPkts OBJECT-TYPE
   SYNTAX      Counter64
   MAX-ACCESS  read-only
   STATUS      current
   DESCRIPTION
      "Path: pbbBridgeGroup.performance.mibCounters.d7Performance.ifOutMcastPkts

       64 bit unsigned wrappable counter."
   ::= {pr1645v2PbbBGriMVMibCountersD7PEntry 469762048}

pr1645v2PbbBGriMVMibCountersD7PIfOutDiscards OBJECT-TYPE
   SYNTAX      Counter64
   MAX-ACCESS  read-only
   STATUS      current
   DESCRIPTION
      "Path: pbbBridgeGroup.performance.mibCounters.d7Performance.ifOutDiscards

       64 bit unsigned wrappable counter."
   ::= {pr1645v2PbbBGriMVMibCountersD7PEntry 218103808}

pr1645v2PbbBGriMVMibCountersD7PIfOutErrors OBJECT-TYPE
   SYNTAX      Counter64
   MAX-ACCESS  read-only
   STATUS      current
   DESCRIPTION
      "Path: pbbBridgeGroup.performance.mibCounters.d7Performance.ifOutErrors

       64 bit unsigned wrappable counter."
   ::= {pr1645v2PbbBGriMVMibCountersD7PEntry 234881024}

pr1645v2PbbBGriMVMibCountersD7POutDropEx OBJECT-TYPE
   SYNTAX      Counter64
   MAX-ACCESS  read-only
   STATUS      current
   DESCRIPTION
      "Path: pbbBridgeGroup.performance.mibCounters.d7Performance.ifOutDropLevelExceeded

       64 bit unsigned wrappable counter."
   ::= {pr1645v2PbbBGriMVMibCountersD7PEntry 352321536}

pr1645v2PbbBGriMVMibCountersD7POutDropNoArp OBJECT-TYPE
   SYNTAX      Counter64
   MAX-ACCESS  read-only
   STATUS      current
   DESCRIPTION
      "Path: pbbBridgeGroup.performance.mibCounters.d7Performance.ifOutDiscardsNoArp

       64 bit unsigned wrappable counter."
   ::= {pr1645v2PbbBGriMVMibCountersD7PEntry 369098752}

pr1645v2PbbBGriMVMibCountersD7POutDropFilter OBJECT-TYPE
   SYNTAX      Counter64
   MAX-ACCESS  read-only
   STATUS      current
   DESCRIPTION
      "Path: pbbBridgeGroup.performance.mibCounters.d7Performance.ifOutDiscardsFilter

       64 bit unsigned wrappable counter."
   ::= {pr1645v2PbbBGriMVMibCountersD7PEntry 402653184}

pr1645v2PbbBGriMVMibCountersD7PIfOutBandwidth OBJECT-TYPE
   SYNTAX      Integer32
   MAX-ACCESS  read-only
   STATUS      current
   DESCRIPTION
      "Path: pbbBridgeGroup.performance.mibCounters.d7Performance.ifOutBandwidth

       unit name = bps
       formula = 8 * ; 8 /"
   ::= {pr1645v2PbbBGriMVMibCountersD7PEntry 285212672}

pr1645v2PbbBGriMVMibCountersD7PIfErrSec OBJECT-TYPE
   SYNTAX      Counter32
   MAX-ACCESS  read-only
   STATUS      current
   DESCRIPTION
      "Path: pbbBridgeGroup.performance.mibCounters.d7Performance.ifErrSec

       32 bit unsigned wrappable counter."
   ::= {pr1645v2PbbBGriMVMibCountersD7PEntry 251658240}


pr1645v2PbbBGriMVL2ProtTunnel OBJECT IDENTIFIER ::= {pr1645v2PbbBGriMV 46}

pr1645v2PbbBGriMVL2ProtTunnelSSCTable OBJECT-TYPE
   SYNTAX      SEQUENCE OF Pr1645v2PbbBGriMVL2ProtTunnelEntry
   MAX-ACCESS  not-accessible
   STATUS      current
   DESCRIPTION
      "l2 protocol tunnel performance"
   ::= {pr1645v2PbbBGriMVL2ProtTunnel 1}

pr1645v2PbbBGriMVL2ProtTunnelEntry OBJECT-TYPE
   SYNTAX      Pr1645v2PbbBGriMVL2ProtTunnelEntry
   MAX-ACCESS  not-accessible
   STATUS      current
   DESCRIPTION
      ""
   INDEX      { pr1645v2PbbBGriMVL2ProtTunnelGlobalIx,
                pr1645v2PbbBGriMVL2ProtTunnelTableIx }
   ::= {pr1645v2PbbBGriMVL2ProtTunnelSSCTable 1}

Pr1645v2PbbBGriMVL2ProtTunnelEntry ::=
   SEQUENCE
      {
      pr1645v2PbbBGriMVL2ProtTunnelGlobalIx
         GlobalIndex,
      pr1645v2PbbBGriMVL2ProtTunnelTableIx
         TableIndex,
      pr1645v2PbbBGriMVL2ProtTunnelName
         DisplayString,
      pr1645v2PbbBGriMVL2ProtTunnelEncapsPktsStp
         Counter32,
      pr1645v2PbbBGriMVL2ProtTunnelEncapsPktsLldp
         Counter32,
      pr1645v2PbbBGriMVL2ProtTunnelEncapsPktsOam
         Counter32,
      pr1645v2PbbBGriMVL2ProtTunnelEncapsPktsCdp
         Counter32,
      pr1645v2PbbBGriMVL2ProtTunnelEncapsPktsVtp
         Counter32,
      pr1645v2PbbBGriMVL2ProtTunnelEncapsPktsLacp
         Counter32,
      pr1645v2PbbBGriMVL2ProtTunnelEncapsPktsEfmOam
         Counter32,
      pr1645v2PbbBGriMVL2ProtTunnelEncapsPktsPvst
         Counter32,
      pr1645v2PbbBGriMVL2ProtTunnelEncapsPktsMmrp
         Counter32,
      pr1645v2PbbBGriMVL2ProtTunnelEncapsPktsMvrp
         Counter32,
      pr1645v2PbbBGriMVL2ProtTunnelEncapsPktsGvrp
         Counter32,
      pr1645v2PbbBGriMVL2ProtTunnelEncapsPktsGmrp
         Counter32,
      pr1645v2PbbBGriMVL2ProtTunnelEncapsPktsDtp
         Counter32,
      pr1645v2PbbBGriMVL2ProtTunnelEncapsPktsPagp
         Counter32,
      pr1645v2PbbBGriMVL2ProtTunnelEncapsPktsUdld
         Counter32,
      pr1645v2PbbBGriMVL2ProtTunnelDecapsPktsStp
         Counter32,
      pr1645v2PbbBGriMVL2ProtTunnelDecapsPktsLldp
         Counter32,
      pr1645v2PbbBGriMVL2ProtTunnelDecapsPktsOam
         Counter32,
      pr1645v2PbbBGriMVL2ProtTunnelDecapsPktsCdp
         Counter32,
      pr1645v2PbbBGriMVL2ProtTunnelDecapsPktsVtp
         Counter32,
      pr1645v2PbbBGriMVL2ProtTunnelDecapsPktsLacp
         Counter32,
      pr1645v2PbbBGriMVL2ProtTunnelDecapsPktsEfmOam
         Counter32,
      pr1645v2PbbBGriMVL2ProtTunnelDecapsPktsPvst
         Counter32,
      pr1645v2PbbBGriMVL2ProtTunnelDecapsPktsMmrp
         Counter32,
      pr1645v2PbbBGriMVL2ProtTunnelDecapsPktsMvrp
         Counter32,
      pr1645v2PbbBGriMVL2ProtTunnelDecapsPktsGvrp
         Counter32,
      pr1645v2PbbBGriMVL2ProtTunnelDecapsPktsGmrp
         Counter32,
      pr1645v2PbbBGriMVL2ProtTunnelDecapsPktsDtp
         Counter32,
      pr1645v2PbbBGriMVL2ProtTunnelDecapsPktsPagp
         Counter32,
      pr1645v2PbbBGriMVL2ProtTunnelDecapsPktsUdld
         Counter32,
      pr1645v2PbbBGriMVL2ProtTunnelDroppedStp
         Counter32,
      pr1645v2PbbBGriMVL2ProtTunnelDroppedLldp
         Counter32,
      pr1645v2PbbBGriMVL2ProtTunnelDroppedOam
         Counter32,
      pr1645v2PbbBGriMVL2ProtTunnelDroppedCdp
         Counter32,
      pr1645v2PbbBGriMVL2ProtTunnelDroppedVtp
         Counter32,
      pr1645v2PbbBGriMVL2ProtTunnelDroppedLacp
         Counter32,
      pr1645v2PbbBGriMVL2ProtTunnelDroppedEfmOam
         Counter32,
      pr1645v2PbbBGriMVL2ProtTunnelDroppedPvst
         Counter32,
      pr1645v2PbbBGriMVL2ProtTunnelDroppedMmrp
         Counter32,
      pr1645v2PbbBGriMVL2ProtTunnelDroppedMvrp
         Counter32,
      pr1645v2PbbBGriMVL2ProtTunnelDroppedGvrp
         Counter32,
      pr1645v2PbbBGriMVL2ProtTunnelDroppedGmrp
         Counter32,
      pr1645v2PbbBGriMVL2ProtTunnelDroppedDtp
         Counter32,
      pr1645v2PbbBGriMVL2ProtTunnelDroppedPagp
         Counter32,
      pr1645v2PbbBGriMVL2ProtTunnelDroppedUdld
         Counter32
      }

pr1645v2PbbBGriMVL2ProtTunnelGlobalIx OBJECT-TYPE
   SYNTAX      GlobalIndex
   MAX-ACCESS  not-accessible
   STATUS      current
   DESCRIPTION
      "The value of the tlsCntTreeGlobalIndex of the MANAGED OBJECT."
   ::= {pr1645v2PbbBGriMVL2ProtTunnelEntry 10}

pr1645v2PbbBGriMVL2ProtTunnelTableIx OBJECT-TYPE
   SYNTAX      TableIndex
   MAX-ACCESS  not-accessible
   STATUS      current
   DESCRIPTION
      ""
   ::= {pr1645v2PbbBGriMVL2ProtTunnelEntry 11}

pr1645v2PbbBGriMVL2ProtTunnelName OBJECT-TYPE
   SYNTAX      DisplayString
   MAX-ACCESS  read-only
   STATUS      current
   DESCRIPTION
      "Path: pbbBridgeGroup.performance.l2ProtTunnel.name"
   ::= {pr1645v2PbbBGriMVL2ProtTunnelEntry 16777216}

pr1645v2PbbBGriMVL2ProtTunnelEncapsPktsStp OBJECT-TYPE
   SYNTAX      Counter32
   MAX-ACCESS  read-only
   STATUS      current
   DESCRIPTION
      "Path: pbbBridgeGroup.performance.l2ProtTunnel.encapsPkts.stp

       32 bit unsigned wrappable counter."
   ::= {pr1645v2PbbBGriMVL2ProtTunnelEntry 33619968}

pr1645v2PbbBGriMVL2ProtTunnelEncapsPktsLldp OBJECT-TYPE
   SYNTAX      Counter32
   MAX-ACCESS  read-only
   STATUS      current
   DESCRIPTION
      "Path: pbbBridgeGroup.performance.l2ProtTunnel.encapsPkts.lldp

       32 bit unsigned wrappable counter."
   ::= {pr1645v2PbbBGriMVL2ProtTunnelEntry 33685504}

pr1645v2PbbBGriMVL2ProtTunnelEncapsPktsOam OBJECT-TYPE
   SYNTAX      Counter32
   MAX-ACCESS  read-only
   STATUS      current
   DESCRIPTION
      "Path: pbbBridgeGroup.performance.l2ProtTunnel.encapsPkts.oam

       32 bit unsigned wrappable counter."
   ::= {pr1645v2PbbBGriMVL2ProtTunnelEntry 33751040}

pr1645v2PbbBGriMVL2ProtTunnelEncapsPktsCdp OBJECT-TYPE
   SYNTAX      Counter32
   MAX-ACCESS  read-only
   STATUS      current
   DESCRIPTION
      "Path: pbbBridgeGroup.performance.l2ProtTunnel.encapsPkts.cdp

       32 bit unsigned wrappable counter."
   ::= {pr1645v2PbbBGriMVL2ProtTunnelEntry 33816576}

pr1645v2PbbBGriMVL2ProtTunnelEncapsPktsVtp OBJECT-TYPE
   SYNTAX      Counter32
   MAX-ACCESS  read-only
   STATUS      current
   DESCRIPTION
      "Path: pbbBridgeGroup.performance.l2ProtTunnel.encapsPkts.vtp

       32 bit unsigned wrappable counter."
   ::= {pr1645v2PbbBGriMVL2ProtTunnelEntry 33882112}

pr1645v2PbbBGriMVL2ProtTunnelEncapsPktsLacp OBJECT-TYPE
   SYNTAX      Counter32
   MAX-ACCESS  read-only
   STATUS      current
   DESCRIPTION
      "Path: pbbBridgeGroup.performance.l2ProtTunnel.encapsPkts.lacp

       32 bit unsigned wrappable counter."
   ::= {pr1645v2PbbBGriMVL2ProtTunnelEntry 33947648}

pr1645v2PbbBGriMVL2ProtTunnelEncapsPktsEfmOam OBJECT-TYPE
   SYNTAX      Counter32
   MAX-ACCESS  read-only
   STATUS      current
   DESCRIPTION
      "Path: pbbBridgeGroup.performance.l2ProtTunnel.encapsPkts.efmOam

       32 bit unsigned wrappable counter."
   ::= {pr1645v2PbbBGriMVL2ProtTunnelEntry 34013184}

pr1645v2PbbBGriMVL2ProtTunnelEncapsPktsPvst OBJECT-TYPE
   SYNTAX      Counter32
   MAX-ACCESS  read-only
   STATUS      current
   DESCRIPTION
      "Path: pbbBridgeGroup.performance.l2ProtTunnel.encapsPkts.pvst

       32 bit unsigned wrappable counter."
   ::= {pr1645v2PbbBGriMVL2ProtTunnelEntry 34078720}

pr1645v2PbbBGriMVL2ProtTunnelEncapsPktsMmrp OBJECT-TYPE
   SYNTAX      Counter32
   MAX-ACCESS  read-only
   STATUS      current
   DESCRIPTION
      "Path: pbbBridgeGroup.performance.l2ProtTunnel.encapsPkts.mmrp

       32 bit unsigned wrappable counter."
   ::= {pr1645v2PbbBGriMVL2ProtTunnelEntry 34144256}

pr1645v2PbbBGriMVL2ProtTunnelEncapsPktsMvrp OBJECT-TYPE
   SYNTAX      Counter32
   MAX-ACCESS  read-only
   STATUS      current
   DESCRIPTION
      "Path: pbbBridgeGroup.performance.l2ProtTunnel.encapsPkts.mvrp

       32 bit unsigned wrappable counter."
   ::= {pr1645v2PbbBGriMVL2ProtTunnelEntry 34209792}

pr1645v2PbbBGriMVL2ProtTunnelEncapsPktsGvrp OBJECT-TYPE
   SYNTAX      Counter32
   MAX-ACCESS  read-only
   STATUS      current
   DESCRIPTION
      "Path: pbbBridgeGroup.performance.l2ProtTunnel.encapsPkts.gvrp

       32 bit unsigned wrappable counter."
   ::= {pr1645v2PbbBGriMVL2ProtTunnelEntry 34275328}

pr1645v2PbbBGriMVL2ProtTunnelEncapsPktsGmrp OBJECT-TYPE
   SYNTAX      Counter32
   MAX-ACCESS  read-only
   STATUS      current
   DESCRIPTION
      "Path: pbbBridgeGroup.performance.l2ProtTunnel.encapsPkts.gmrp

       32 bit unsigned wrappable counter."
   ::= {pr1645v2PbbBGriMVL2ProtTunnelEntry 34340864}

pr1645v2PbbBGriMVL2ProtTunnelEncapsPktsDtp OBJECT-TYPE
   SYNTAX      Counter32
   MAX-ACCESS  read-only
   STATUS      current
   DESCRIPTION
      "Path: pbbBridgeGroup.performance.l2ProtTunnel.encapsPkts.dtp

       32 bit unsigned wrappable counter."
   ::= {pr1645v2PbbBGriMVL2ProtTunnelEntry 34406400}

pr1645v2PbbBGriMVL2ProtTunnelEncapsPktsPagp OBJECT-TYPE
   SYNTAX      Counter32
   MAX-ACCESS  read-only
   STATUS      current
   DESCRIPTION
      "Path: pbbBridgeGroup.performance.l2ProtTunnel.encapsPkts.pagp

       32 bit unsigned wrappable counter."
   ::= {pr1645v2PbbBGriMVL2ProtTunnelEntry 34471936}

pr1645v2PbbBGriMVL2ProtTunnelEncapsPktsUdld OBJECT-TYPE
   SYNTAX      Counter32
   MAX-ACCESS  read-only
   STATUS      current
   DESCRIPTION
      "Path: pbbBridgeGroup.performance.l2ProtTunnel.encapsPkts.udld

       32 bit unsigned wrappable counter."
   ::= {pr1645v2PbbBGriMVL2ProtTunnelEntry 34537472}

pr1645v2PbbBGriMVL2ProtTunnelDecapsPktsStp OBJECT-TYPE
   SYNTAX      Counter32
   MAX-ACCESS  read-only
   STATUS      current
   DESCRIPTION
      "Path: pbbBridgeGroup.performance.l2ProtTunnel.decapsPkts.stp

       32 bit unsigned wrappable counter."
   ::= {pr1645v2PbbBGriMVL2ProtTunnelEntry 50397184}

pr1645v2PbbBGriMVL2ProtTunnelDecapsPktsLldp OBJECT-TYPE
   SYNTAX      Counter32
   MAX-ACCESS  read-only
   STATUS      current
   DESCRIPTION
      "Path: pbbBridgeGroup.performance.l2ProtTunnel.decapsPkts.lldp

       32 bit unsigned wrappable counter."
   ::= {pr1645v2PbbBGriMVL2ProtTunnelEntry 50462720}

pr1645v2PbbBGriMVL2ProtTunnelDecapsPktsOam OBJECT-TYPE
   SYNTAX      Counter32
   MAX-ACCESS  read-only
   STATUS      current
   DESCRIPTION
      "Path: pbbBridgeGroup.performance.l2ProtTunnel.decapsPkts.oam

       32 bit unsigned wrappable counter."
   ::= {pr1645v2PbbBGriMVL2ProtTunnelEntry 50528256}

pr1645v2PbbBGriMVL2ProtTunnelDecapsPktsCdp OBJECT-TYPE
   SYNTAX      Counter32
   MAX-ACCESS  read-only
   STATUS      current
   DESCRIPTION
      "Path: pbbBridgeGroup.performance.l2ProtTunnel.decapsPkts.cdp

       32 bit unsigned wrappable counter."
   ::= {pr1645v2PbbBGriMVL2ProtTunnelEntry 50593792}

pr1645v2PbbBGriMVL2ProtTunnelDecapsPktsVtp OBJECT-TYPE
   SYNTAX      Counter32
   MAX-ACCESS  read-only
   STATUS      current
   DESCRIPTION
      "Path: pbbBridgeGroup.performance.l2ProtTunnel.decapsPkts.vtp

       32 bit unsigned wrappable counter."
   ::= {pr1645v2PbbBGriMVL2ProtTunnelEntry 50659328}

pr1645v2PbbBGriMVL2ProtTunnelDecapsPktsLacp OBJECT-TYPE
   SYNTAX      Counter32
   MAX-ACCESS  read-only
   STATUS      current
   DESCRIPTION
      "Path: pbbBridgeGroup.performance.l2ProtTunnel.decapsPkts.lacp

       32 bit unsigned wrappable counter."
   ::= {pr1645v2PbbBGriMVL2ProtTunnelEntry 50724864}

pr1645v2PbbBGriMVL2ProtTunnelDecapsPktsEfmOam OBJECT-TYPE
   SYNTAX      Counter32
   MAX-ACCESS  read-only
   STATUS      current
   DESCRIPTION
      "Path: pbbBridgeGroup.performance.l2ProtTunnel.decapsPkts.efmOam

       32 bit unsigned wrappable counter."
   ::= {pr1645v2PbbBGriMVL2ProtTunnelEntry 50790400}

pr1645v2PbbBGriMVL2ProtTunnelDecapsPktsPvst OBJECT-TYPE
   SYNTAX      Counter32
   MAX-ACCESS  read-only
   STATUS      current
   DESCRIPTION
      "Path: pbbBridgeGroup.performance.l2ProtTunnel.decapsPkts.pvst

       32 bit unsigned wrappable counter."
   ::= {pr1645v2PbbBGriMVL2ProtTunnelEntry 50855936}

pr1645v2PbbBGriMVL2ProtTunnelDecapsPktsMmrp OBJECT-TYPE
   SYNTAX      Counter32
   MAX-ACCESS  read-only
   STATUS      current
   DESCRIPTION
      "Path: pbbBridgeGroup.performance.l2ProtTunnel.decapsPkts.mmrp

       32 bit unsigned wrappable counter."
   ::= {pr1645v2PbbBGriMVL2ProtTunnelEntry 50921472}

pr1645v2PbbBGriMVL2ProtTunnelDecapsPktsMvrp OBJECT-TYPE
   SYNTAX      Counter32
   MAX-ACCESS  read-only
   STATUS      current
   DESCRIPTION
      "Path: pbbBridgeGroup.performance.l2ProtTunnel.decapsPkts.mvrp

       32 bit unsigned wrappable counter."
   ::= {pr1645v2PbbBGriMVL2ProtTunnelEntry 50987008}

pr1645v2PbbBGriMVL2ProtTunnelDecapsPktsGvrp OBJECT-TYPE
   SYNTAX      Counter32
   MAX-ACCESS  read-only
   STATUS      current
   DESCRIPTION
      "Path: pbbBridgeGroup.performance.l2ProtTunnel.decapsPkts.gvrp

       32 bit unsigned wrappable counter."
   ::= {pr1645v2PbbBGriMVL2ProtTunnelEntry 51052544}

pr1645v2PbbBGriMVL2ProtTunnelDecapsPktsGmrp OBJECT-TYPE
   SYNTAX      Counter32
   MAX-ACCESS  read-only
   STATUS      current
   DESCRIPTION
      "Path: pbbBridgeGroup.performance.l2ProtTunnel.decapsPkts.gmrp

       32 bit unsigned wrappable counter."
   ::= {pr1645v2PbbBGriMVL2ProtTunnelEntry 51118080}

pr1645v2PbbBGriMVL2ProtTunnelDecapsPktsDtp OBJECT-TYPE
   SYNTAX      Counter32
   MAX-ACCESS  read-only
   STATUS      current
   DESCRIPTION
      "Path: pbbBridgeGroup.performance.l2ProtTunnel.decapsPkts.dtp

       32 bit unsigned wrappable counter."
   ::= {pr1645v2PbbBGriMVL2ProtTunnelEntry 51183616}

pr1645v2PbbBGriMVL2ProtTunnelDecapsPktsPagp OBJECT-TYPE
   SYNTAX      Counter32
   MAX-ACCESS  read-only
   STATUS      current
   DESCRIPTION
      "Path: pbbBridgeGroup.performance.l2ProtTunnel.decapsPkts.pagp

       32 bit unsigned wrappable counter."
   ::= {pr1645v2PbbBGriMVL2ProtTunnelEntry 51249152}

pr1645v2PbbBGriMVL2ProtTunnelDecapsPktsUdld OBJECT-TYPE
   SYNTAX      Counter32
   MAX-ACCESS  read-only
   STATUS      current
   DESCRIPTION
      "Path: pbbBridgeGroup.performance.l2ProtTunnel.decapsPkts.udld

       32 bit unsigned wrappable counter."
   ::= {pr1645v2PbbBGriMVL2ProtTunnelEntry 51314688}

pr1645v2PbbBGriMVL2ProtTunnelDroppedStp OBJECT-TYPE
   SYNTAX      Counter32
   MAX-ACCESS  read-only
   STATUS      current
   DESCRIPTION
      "Path: pbbBridgeGroup.performance.l2ProtTunnel.dropped.stp

       32 bit unsigned wrappable counter."
   ::= {pr1645v2PbbBGriMVL2ProtTunnelEntry 67174400}

pr1645v2PbbBGriMVL2ProtTunnelDroppedLldp OBJECT-TYPE
   SYNTAX      Counter32
   MAX-ACCESS  read-only
   STATUS      current
   DESCRIPTION
      "Path: pbbBridgeGroup.performance.l2ProtTunnel.dropped.lldp

       32 bit unsigned wrappable counter."
   ::= {pr1645v2PbbBGriMVL2ProtTunnelEntry 67239936}

pr1645v2PbbBGriMVL2ProtTunnelDroppedOam OBJECT-TYPE
   SYNTAX      Counter32
   MAX-ACCESS  read-only
   STATUS      current
   DESCRIPTION
      "Path: pbbBridgeGroup.performance.l2ProtTunnel.dropped.oam

       32 bit unsigned wrappable counter."
   ::= {pr1645v2PbbBGriMVL2ProtTunnelEntry 67305472}

pr1645v2PbbBGriMVL2ProtTunnelDroppedCdp OBJECT-TYPE
   SYNTAX      Counter32
   MAX-ACCESS  read-only
   STATUS      current
   DESCRIPTION
      "Path: pbbBridgeGroup.performance.l2ProtTunnel.dropped.cdp

       32 bit unsigned wrappable counter."
   ::= {pr1645v2PbbBGriMVL2ProtTunnelEntry 67371008}

pr1645v2PbbBGriMVL2ProtTunnelDroppedVtp OBJECT-TYPE
   SYNTAX      Counter32
   MAX-ACCESS  read-only
   STATUS      current
   DESCRIPTION
      "Path: pbbBridgeGroup.performance.l2ProtTunnel.dropped.vtp

       32 bit unsigned wrappable counter."
   ::= {pr1645v2PbbBGriMVL2ProtTunnelEntry 67436544}

pr1645v2PbbBGriMVL2ProtTunnelDroppedLacp OBJECT-TYPE
   SYNTAX      Counter32
   MAX-ACCESS  read-only
   STATUS      current
   DESCRIPTION
      "Path: pbbBridgeGroup.performance.l2ProtTunnel.dropped.lacp

       32 bit unsigned wrappable counter."
   ::= {pr1645v2PbbBGriMVL2ProtTunnelEntry 67502080}

pr1645v2PbbBGriMVL2ProtTunnelDroppedEfmOam OBJECT-TYPE
   SYNTAX      Counter32
   MAX-ACCESS  read-only
   STATUS      current
   DESCRIPTION
      "Path: pbbBridgeGroup.performance.l2ProtTunnel.dropped.efmOam

       32 bit unsigned wrappable counter."
   ::= {pr1645v2PbbBGriMVL2ProtTunnelEntry 67567616}

pr1645v2PbbBGriMVL2ProtTunnelDroppedPvst OBJECT-TYPE
   SYNTAX      Counter32
   MAX-ACCESS  read-only
   STATUS      current
   DESCRIPTION
      "Path: pbbBridgeGroup.performance.l2ProtTunnel.dropped.pvst

       32 bit unsigned wrappable counter."
   ::= {pr1645v2PbbBGriMVL2ProtTunnelEntry 67633152}

pr1645v2PbbBGriMVL2ProtTunnelDroppedMmrp OBJECT-TYPE
   SYNTAX      Counter32
   MAX-ACCESS  read-only
   STATUS      current
   DESCRIPTION
      "Path: pbbBridgeGroup.performance.l2ProtTunnel.dropped.mmrp

       32 bit unsigned wrappable counter."
   ::= {pr1645v2PbbBGriMVL2ProtTunnelEntry 67698688}

pr1645v2PbbBGriMVL2ProtTunnelDroppedMvrp OBJECT-TYPE
   SYNTAX      Counter32
   MAX-ACCESS  read-only
   STATUS      current
   DESCRIPTION
      "Path: pbbBridgeGroup.performance.l2ProtTunnel.dropped.mvrp

       32 bit unsigned wrappable counter."
   ::= {pr1645v2PbbBGriMVL2ProtTunnelEntry 67764224}

pr1645v2PbbBGriMVL2ProtTunnelDroppedGvrp OBJECT-TYPE
   SYNTAX      Counter32
   MAX-ACCESS  read-only
   STATUS      current
   DESCRIPTION
      "Path: pbbBridgeGroup.performance.l2ProtTunnel.dropped.gvrp

       32 bit unsigned wrappable counter."
   ::= {pr1645v2PbbBGriMVL2ProtTunnelEntry 67829760}

pr1645v2PbbBGriMVL2ProtTunnelDroppedGmrp OBJECT-TYPE
   SYNTAX      Counter32
   MAX-ACCESS  read-only
   STATUS      current
   DESCRIPTION
      "Path: pbbBridgeGroup.performance.l2ProtTunnel.dropped.gmrp

       32 bit unsigned wrappable counter."
   ::= {pr1645v2PbbBGriMVL2ProtTunnelEntry 67895296}

pr1645v2PbbBGriMVL2ProtTunnelDroppedDtp OBJECT-TYPE
   SYNTAX      Counter32
   MAX-ACCESS  read-only
   STATUS      current
   DESCRIPTION
      "Path: pbbBridgeGroup.performance.l2ProtTunnel.dropped.dtp

       32 bit unsigned wrappable counter."
   ::= {pr1645v2PbbBGriMVL2ProtTunnelEntry 67960832}

pr1645v2PbbBGriMVL2ProtTunnelDroppedPagp OBJECT-TYPE
   SYNTAX      Counter32
   MAX-ACCESS  read-only
   STATUS      current
   DESCRIPTION
      "Path: pbbBridgeGroup.performance.l2ProtTunnel.dropped.pagp

       32 bit unsigned wrappable counter."
   ::= {pr1645v2PbbBGriMVL2ProtTunnelEntry 68026368}

pr1645v2PbbBGriMVL2ProtTunnelDroppedUdld OBJECT-TYPE
   SYNTAX      Counter32
   MAX-ACCESS  read-only
   STATUS      current
   DESCRIPTION
      "Path: pbbBridgeGroup.performance.l2ProtTunnel.dropped.udld

       32 bit unsigned wrappable counter."
   ::= {pr1645v2PbbBGriMVL2ProtTunnelEntry 68091904}


pr1645v2PbbBGriMVVlan OBJECT IDENTIFIER ::= {pr1645v2PbbBGriMV 310}

pr1645v2PbbBGriMVVlanSSCTable OBJECT-TYPE
   SYNTAX      SEQUENCE OF Pr1645v2PbbBGriMVVlanEntry
   MAX-ACCESS  not-accessible
   STATUS      current
   DESCRIPTION
      ""
   ::= {pr1645v2PbbBGriMVVlan 1}

pr1645v2PbbBGriMVVlanEntry OBJECT-TYPE
   SYNTAX      Pr1645v2PbbBGriMVVlanEntry
   MAX-ACCESS  not-accessible
   STATUS      current
   DESCRIPTION
      ""
   INDEX      { pr1645v2PbbBGriMVVlanGlobalIx,
                pr1645v2PbbBGriMVVlanTableIx }
   ::= {pr1645v2PbbBGriMVVlanSSCTable 1}

Pr1645v2PbbBGriMVVlanEntry ::=
   SEQUENCE
      {
      pr1645v2PbbBGriMVVlanGlobalIx
         GlobalIndex,
      pr1645v2PbbBGriMVVlanTableIx
         TableIndex,
      pr1645v2PbbBGriMVVlanName
         DisplayString,
      pr1645v2PbbBGriMVVlanMCInOctets
         Counter64,
      pr1645v2PbbBGriMVVlanMCInUcast
         Counter64,
      pr1645v2PbbBGriMVVlanMCInNUcastPkts
         Counter64,
      pr1645v2PbbBGriMVVlanMCInBcastPkts
         Counter64,
      pr1645v2PbbBGriMVVlanMCInMcastPkts
         Counter64,
      pr1645v2PbbBGriMVVlanMCInDiscards
         Counter64,
      pr1645v2PbbBGriMVVlanMCInErrors
         Counter64,
      pr1645v2PbbBGriMVVlanMCInUnknownProtos
         Counter64,
      pr1645v2PbbBGriMVVlanMCInDropEx
         Counter64,
      pr1645v2PbbBGriMVVlanMCInDropNoMac
         Counter64,
      pr1645v2PbbBGriMVVlanMCInDropNUCast
         Counter64,
      pr1645v2PbbBGriMVVlanMCInDropFilter
         Counter64,
      pr1645v2PbbBGriMVVlanMCInBandwidth15sec
         Integer32,
      pr1645v2PbbBGriMVVlanMCInBandwidth30sec
         Integer32,
      pr1645v2PbbBGriMVVlanMCInBandwidth1min
         Integer32,
      pr1645v2PbbBGriMVVlanMCInBandwidth2min
         Integer32,
      pr1645v2PbbBGriMVVlanMCInBandwidth5min
         Integer32,
      pr1645v2PbbBGriMVVlanMCOutOctets
         Counter64,
      pr1645v2PbbBGriMVVlanMCOutUcastPkts
         Counter64,
      pr1645v2PbbBGriMVVlanMCOutNUcastPkts
         Counter64,
      pr1645v2PbbBGriMVVlanMCOutBcastPkts
         Counter64,
      pr1645v2PbbBGriMVVlanMCOutMcastPkts
         Counter64,
      pr1645v2PbbBGriMVVlanMCOutDiscards
         Counter64,
      pr1645v2PbbBGriMVVlanMCOutErrors
         Counter64,
      pr1645v2PbbBGriMVVlanMCOutQLen
         Counter32,
      pr1645v2PbbBGriMVVlanMCOutDropEx
         Counter64,
      pr1645v2PbbBGriMVVlanMCOutDropNoArp
         Counter64,
      pr1645v2PbbBGriMVVlanMCOutDropFilter
         Counter64,
      pr1645v2PbbBGriMVVlanMCOutBandwidth15sec
         Integer32,
      pr1645v2PbbBGriMVVlanMCOutBandwidth30sec
         Integer32,
      pr1645v2PbbBGriMVVlanMCOutBandwidth1min
         Integer32,
      pr1645v2PbbBGriMVVlanMCOutBandwidth2min
         Integer32,
      pr1645v2PbbBGriMVVlanMCOutBandwidth5min
         Integer32,
      pr1645v2PbbBGriMVVlanVlanVid
         Integer32
      }

pr1645v2PbbBGriMVVlanGlobalIx OBJECT-TYPE
   SYNTAX      GlobalIndex
   MAX-ACCESS  not-accessible
   STATUS      current
   DESCRIPTION
      "The value of the tlsCntTreeGlobalIndex of the MANAGED OBJECT."
   ::= {pr1645v2PbbBGriMVVlanEntry 10}

pr1645v2PbbBGriMVVlanTableIx OBJECT-TYPE
   SYNTAX      TableIndex
   MAX-ACCESS  not-accessible
   STATUS      current
   DESCRIPTION
      ""
   ::= {pr1645v2PbbBGriMVVlanEntry 11}

pr1645v2PbbBGriMVVlanName OBJECT-TYPE
   SYNTAX      DisplayString
   MAX-ACCESS  read-only
   STATUS      current
   DESCRIPTION
      "Path: pbbBridgeGroup.performance.vlan.name"
   ::= {pr1645v2PbbBGriMVVlanEntry 16777216}

pr1645v2PbbBGriMVVlanMCInOctets OBJECT-TYPE
   SYNTAX      Counter64
   MAX-ACCESS  read-only
   STATUS      current
   DESCRIPTION
      "Path: pbbBridgeGroup.performance.vlan.mibCounters.ifInOctets

       64 bit unsigned wrappable counter."
   ::= {pr1645v2PbbBGriMVVlanEntry 40697856}

pr1645v2PbbBGriMVVlanMCInUcast OBJECT-TYPE
   SYNTAX      Counter64
   MAX-ACCESS  read-only
   STATUS      current
   DESCRIPTION
      "Path: pbbBridgeGroup.performance.vlan.mibCounters.ifInUcastPkts

       64 bit unsigned wrappable counter."
   ::= {pr1645v2PbbBGriMVVlanEntry 40763392}

pr1645v2PbbBGriMVVlanMCInNUcastPkts OBJECT-TYPE
   SYNTAX      Counter64
   MAX-ACCESS  read-only
   STATUS      current
   DESCRIPTION
      "Path: pbbBridgeGroup.performance.vlan.mibCounters.ifInNUcastPkts

       64 bit unsigned wrappable counter."
   ::= {pr1645v2PbbBGriMVVlanEntry 40828928}

pr1645v2PbbBGriMVVlanMCInBcastPkts OBJECT-TYPE
   SYNTAX      Counter64
   MAX-ACCESS  read-only
   STATUS      current
   DESCRIPTION
      "Path: pbbBridgeGroup.performance.vlan.mibCounters.ifInBcastPkts

       64 bit unsigned wrappable counter."
   ::= {pr1645v2PbbBGriMVVlanEntry 47382528}

pr1645v2PbbBGriMVVlanMCInMcastPkts OBJECT-TYPE
   SYNTAX      Counter64
   MAX-ACCESS  read-only
   STATUS      current
   DESCRIPTION
      "Path: pbbBridgeGroup.performance.vlan.mibCounters.ifInMcastPkts

       64 bit unsigned wrappable counter."
   ::= {pr1645v2PbbBGriMVVlanEntry 48037888}

pr1645v2PbbBGriMVVlanMCInDiscards OBJECT-TYPE
   SYNTAX      Counter64
   MAX-ACCESS  read-only
   STATUS      current
   DESCRIPTION
      "Path: pbbBridgeGroup.performance.vlan.mibCounters.ifInDiscards

       64 bit unsigned wrappable counter."
   ::= {pr1645v2PbbBGriMVVlanEntry 40894464}

pr1645v2PbbBGriMVVlanMCInErrors OBJECT-TYPE
   SYNTAX      Counter64
   MAX-ACCESS  read-only
   STATUS      current
   DESCRIPTION
      "Path: pbbBridgeGroup.performance.vlan.mibCounters.ifInErrors

       64 bit unsigned wrappable counter."
   ::= {pr1645v2PbbBGriMVVlanEntry 40960000}

pr1645v2PbbBGriMVVlanMCInUnknownProtos OBJECT-TYPE
   SYNTAX      Counter64
   MAX-ACCESS  read-only
   STATUS      current
   DESCRIPTION
      "Path: pbbBridgeGroup.performance.vlan.mibCounters.ifInUnknownProtos

       64 bit unsigned wrappable counter."
   ::= {pr1645v2PbbBGriMVVlanEntry 41025536}

pr1645v2PbbBGriMVVlanMCInDropEx OBJECT-TYPE
   SYNTAX      Counter64
   MAX-ACCESS  read-only
   STATUS      current
   DESCRIPTION
      "Path: pbbBridgeGroup.performance.vlan.mibCounters.ifInDropLevelExceeded

       64 bit unsigned wrappable counter."
   ::= {pr1645v2PbbBGriMVVlanEntry 42074112}

pr1645v2PbbBGriMVVlanMCInDropNoMac OBJECT-TYPE
   SYNTAX      Counter64
   MAX-ACCESS  read-only
   STATUS      current
   DESCRIPTION
      "Path: pbbBridgeGroup.performance.vlan.mibCounters.ifInDiscardsNoMacFit

       64 bit unsigned wrappable counter."
   ::= {pr1645v2PbbBGriMVVlanEntry 42270720}

pr1645v2PbbBGriMVVlanMCInDropNUCast OBJECT-TYPE
   SYNTAX      Counter64
   MAX-ACCESS  read-only
   STATUS      current
   DESCRIPTION
      "Path: pbbBridgeGroup.performance.vlan.mibCounters.ifInDiscardsNUCast

       64 bit unsigned wrappable counter."
   ::= {pr1645v2PbbBGriMVVlanEntry 42467328}

pr1645v2PbbBGriMVVlanMCInDropFilter OBJECT-TYPE
   SYNTAX      Counter64
   MAX-ACCESS  read-only
   STATUS      current
   DESCRIPTION
      "Path: pbbBridgeGroup.performance.vlan.mibCounters.ifInDiscardsFilter

       64 bit unsigned wrappable counter."
   ::= {pr1645v2PbbBGriMVVlanEntry 42532864}

pr1645v2PbbBGriMVVlanMCInBandwidth15sec OBJECT-TYPE
   SYNTAX      Integer32
   MAX-ACCESS  read-only
   STATUS      current
   DESCRIPTION
      "Path: pbbBridgeGroup.performance.vlan.mibCounters.ifInBandwidth.15sec

       unit name = bps
       formula = 8 * ; 8 /"
   ::= {pr1645v2PbbBGriMVVlanEntry 45417728}

pr1645v2PbbBGriMVVlanMCInBandwidth30sec OBJECT-TYPE
   SYNTAX      Integer32
   MAX-ACCESS  read-only
   STATUS      current
   DESCRIPTION
      "Path: pbbBridgeGroup.performance.vlan.mibCounters.ifInBandwidth.30sec

       unit name = bps
       formula = 8 * ; 8 /"
   ::= {pr1645v2PbbBGriMVVlanEntry 45419008}

pr1645v2PbbBGriMVVlanMCInBandwidth1min OBJECT-TYPE
   SYNTAX      Integer32
   MAX-ACCESS  read-only
   STATUS      current
   DESCRIPTION
      "Path: pbbBridgeGroup.performance.vlan.mibCounters.ifInBandwidth.1min

       unit name = bps
       formula = 8 * ; 8 /"
   ::= {pr1645v2PbbBGriMVVlanEntry 45421568}

pr1645v2PbbBGriMVVlanMCInBandwidth2min OBJECT-TYPE
   SYNTAX      Integer32
   MAX-ACCESS  read-only
   STATUS      current
   DESCRIPTION
      "Path: pbbBridgeGroup.performance.vlan.mibCounters.ifInBandwidth.2min

       unit name = bps
       formula = 8 * ; 8 /"
   ::= {pr1645v2PbbBGriMVVlanEntry 45426688}

pr1645v2PbbBGriMVVlanMCInBandwidth5min OBJECT-TYPE
   SYNTAX      Integer32
   MAX-ACCESS  read-only
   STATUS      current
   DESCRIPTION
      "Path: pbbBridgeGroup.performance.vlan.mibCounters.ifInBandwidth.5min

       unit name = bps
       formula = 8 * ; 8 /"
   ::= {pr1645v2PbbBGriMVVlanEntry 45442048}

pr1645v2PbbBGriMVVlanMCOutOctets OBJECT-TYPE
   SYNTAX      Counter64
   MAX-ACCESS  read-only
   STATUS      current
   DESCRIPTION
      "Path: pbbBridgeGroup.performance.vlan.mibCounters.ifOutOctets

       64 bit unsigned wrappable counter."
   ::= {pr1645v2PbbBGriMVVlanEntry 41091072}

pr1645v2PbbBGriMVVlanMCOutUcastPkts OBJECT-TYPE
   SYNTAX      Counter64
   MAX-ACCESS  read-only
   STATUS      current
   DESCRIPTION
      "Path: pbbBridgeGroup.performance.vlan.mibCounters.ifOutUcastPkts

       64 bit unsigned wrappable counter."
   ::= {pr1645v2PbbBGriMVVlanEntry 41156608}

pr1645v2PbbBGriMVVlanMCOutNUcastPkts OBJECT-TYPE
   SYNTAX      Counter64
   MAX-ACCESS  read-only
   STATUS      current
   DESCRIPTION
      "Path: pbbBridgeGroup.performance.vlan.mibCounters.ifOutNUcastPkts

       64 bit unsigned wrappable counter."
   ::= {pr1645v2PbbBGriMVVlanEntry 41222144}

pr1645v2PbbBGriMVVlanMCOutBcastPkts OBJECT-TYPE
   SYNTAX      Counter64
   MAX-ACCESS  read-only
   STATUS      current
   DESCRIPTION
      "Path: pbbBridgeGroup.performance.vlan.mibCounters.ifOutBcastPkts

       64 bit unsigned wrappable counter."
   ::= {pr1645v2PbbBGriMVVlanEntry 47775744}

pr1645v2PbbBGriMVVlanMCOutMcastPkts OBJECT-TYPE
   SYNTAX      Counter64
   MAX-ACCESS  read-only
   STATUS      current
   DESCRIPTION
      "Path: pbbBridgeGroup.performance.vlan.mibCounters.ifOutMcastPkts

       64 bit unsigned wrappable counter."
   ::= {pr1645v2PbbBGriMVVlanEntry 48431104}

pr1645v2PbbBGriMVVlanMCOutDiscards OBJECT-TYPE
   SYNTAX      Counter64
   MAX-ACCESS  read-only
   STATUS      current
   DESCRIPTION
      "Path: pbbBridgeGroup.performance.vlan.mibCounters.ifOutDiscards

       64 bit unsigned wrappable counter."
   ::= {pr1645v2PbbBGriMVVlanEntry 41287680}

pr1645v2PbbBGriMVVlanMCOutErrors OBJECT-TYPE
   SYNTAX      Counter64
   MAX-ACCESS  read-only
   STATUS      current
   DESCRIPTION
      "Path: pbbBridgeGroup.performance.vlan.mibCounters.ifOutErrors

       64 bit unsigned wrappable counter."
   ::= {pr1645v2PbbBGriMVVlanEntry 41353216}

pr1645v2PbbBGriMVVlanMCOutQLen OBJECT-TYPE
   SYNTAX      Counter32
   MAX-ACCESS  read-only
   STATUS      current
   DESCRIPTION
      "Path: pbbBridgeGroup.performance.vlan.mibCounters.ifOutQLen

       32 bit unsigned wrappable counter."
   ::= {pr1645v2PbbBGriMVVlanEntry 41418752}

pr1645v2PbbBGriMVVlanMCOutDropEx OBJECT-TYPE
   SYNTAX      Counter64
   MAX-ACCESS  read-only
   STATUS      current
   DESCRIPTION
      "Path: pbbBridgeGroup.performance.vlan.mibCounters.ifOutDropLevelExceeded

       64 bit unsigned wrappable counter."
   ::= {pr1645v2PbbBGriMVVlanEntry 41484288}

pr1645v2PbbBGriMVVlanMCOutDropNoArp OBJECT-TYPE
   SYNTAX      Counter64
   MAX-ACCESS  read-only
   STATUS      current
   DESCRIPTION
      "Path: pbbBridgeGroup.performance.vlan.mibCounters.ifOutDiscardsNoArp

       64 bit unsigned wrappable counter."
   ::= {pr1645v2PbbBGriMVVlanEntry 42336256}

pr1645v2PbbBGriMVVlanMCOutDropFilter OBJECT-TYPE
   SYNTAX      Counter64
   MAX-ACCESS  read-only
   STATUS      current
   DESCRIPTION
      "Path: pbbBridgeGroup.performance.vlan.mibCounters.ifOutDiscardsFilter

       64 bit unsigned wrappable counter."
   ::= {pr1645v2PbbBGriMVVlanEntry 42598400}

pr1645v2PbbBGriMVVlanMCOutBandwidth15sec OBJECT-TYPE
   SYNTAX      Integer32
   MAX-ACCESS  read-only
   STATUS      current
   DESCRIPTION
      "Path: pbbBridgeGroup.performance.vlan.mibCounters.ifOutBandwidth.15sec

       unit name = bps
       formula = 8 * ; 8 /"
   ::= {pr1645v2PbbBGriMVVlanEntry 45483264}

pr1645v2PbbBGriMVVlanMCOutBandwidth30sec OBJECT-TYPE
   SYNTAX      Integer32
   MAX-ACCESS  read-only
   STATUS      current
   DESCRIPTION
      "Path: pbbBridgeGroup.performance.vlan.mibCounters.ifOutBandwidth.30sec

       unit name = bps
       formula = 8 * ; 8 /"
   ::= {pr1645v2PbbBGriMVVlanEntry 45484544}

pr1645v2PbbBGriMVVlanMCOutBandwidth1min OBJECT-TYPE
   SYNTAX      Integer32
   MAX-ACCESS  read-only
   STATUS      current
   DESCRIPTION
      "Path: pbbBridgeGroup.performance.vlan.mibCounters.ifOutBandwidth.1min

       unit name = bps
       formula = 8 * ; 8 /"
   ::= {pr1645v2PbbBGriMVVlanEntry 45487104}

pr1645v2PbbBGriMVVlanMCOutBandwidth2min OBJECT-TYPE
   SYNTAX      Integer32
   MAX-ACCESS  read-only
   STATUS      current
   DESCRIPTION
      "Path: pbbBridgeGroup.performance.vlan.mibCounters.ifOutBandwidth.2min

       unit name = bps
       formula = 8 * ; 8 /"
   ::= {pr1645v2PbbBGriMVVlanEntry 45492224}

pr1645v2PbbBGriMVVlanMCOutBandwidth5min OBJECT-TYPE
   SYNTAX      Integer32
   MAX-ACCESS  read-only
   STATUS      current
   DESCRIPTION
      "Path: pbbBridgeGroup.performance.vlan.mibCounters.ifOutBandwidth.5min

       unit name = bps
       formula = 8 * ; 8 /"
   ::= {pr1645v2PbbBGriMVVlanEntry 45507584}

pr1645v2PbbBGriMVVlanVlanVid OBJECT-TYPE
   SYNTAX      Integer32
   MAX-ACCESS  read-only
   STATUS      current
   DESCRIPTION
      "Path: pbbBridgeGroup.performance.vlan.vlan.vid"
   ::= {pr1645v2PbbBGriMVVlanEntry 234946560}

pr1645v2PbbBGriMVVlanMCH2P OBJECT-TYPE
   SYNTAX      SEQUENCE OF Pr1645v2PbbBGriMVVlanMCH2PEntry
   MAX-ACCESS  not-accessible
   STATUS      current
   DESCRIPTION
      ""
   ::= {pr1645v2PbbBGriMVVlan 41549824}

pr1645v2PbbBGriMVVlanMCH2PEntry OBJECT-TYPE
   SYNTAX      Pr1645v2PbbBGriMVVlanMCH2PEntry
   MAX-ACCESS  not-accessible
   STATUS      current
   DESCRIPTION
      ""
   INDEX      { pr1645v2PbbBGriMVVlanMCH2PGlobalIx,
                pr1645v2PbbBGriMVVlanTableIx,
                pr1645v2PbbBGriMVVlanMCH2PTableIx }
   ::= {pr1645v2PbbBGriMVVlanMCH2P 1}

Pr1645v2PbbBGriMVVlanMCH2PEntry ::=
   SEQUENCE
      {
      pr1645v2PbbBGriMVVlanMCH2PGlobalIx
         GlobalIndex,
      pr1645v2PbbBGriMVVlanMCH2PTableIx
         TableIndex,
      pr1645v2PbbBGriMVVlanMCH2PSysUpTime
         TimeTicks,
      pr1645v2PbbBGriMVVlanMCH2PIfUpTime
         TimeTicks,
      pr1645v2PbbBGriMVVlanMCH2PIfStatChanges
         Counter32,
      pr1645v2PbbBGriMVVlanMCH2PIfInOctets
         Counter64,
      pr1645v2PbbBGriMVVlanMCH2PIfInUCPkts
         Counter64,
      pr1645v2PbbBGriMVVlanMCH2PIfInNUCPkts
         Counter64,
      pr1645v2PbbBGriMVVlanMCH2PIfInBCPkts
         Counter64,
      pr1645v2PbbBGriMVVlanMCH2PIfInMCPkts
         Counter64,
      pr1645v2PbbBGriMVVlanMCH2PIfInDiscards
         Counter64,
      pr1645v2PbbBGriMVVlanMCH2PIfInErrors
         Counter64,
      pr1645v2PbbBGriMVVlanMCH2PIfInUnkwn
         Counter64,
      pr1645v2PbbBGriMVVlanMCH2PInDropEx
         Counter64,
      pr1645v2PbbBGriMVVlanMCH2PInDropNoMac
         Counter64,
      pr1645v2PbbBGriMVVlanMCH2PInDropNUCast
         Counter64,
      pr1645v2PbbBGriMVVlanMCH2PInDropFilter
         Counter64,
      pr1645v2PbbBGriMVVlanMCH2PIfInBandwidth
         Integer32,
      pr1645v2PbbBGriMVVlanMCH2PIfOutOctets
         Counter64,
      pr1645v2PbbBGriMVVlanMCH2PIfOutUCPkts
         Counter64,
      pr1645v2PbbBGriMVVlanMCH2PIfOutNUCPkts
         Counter64,
      pr1645v2PbbBGriMVVlanMCH2PIfOutBCPkts
         Counter64,
      pr1645v2PbbBGriMVVlanMCH2PIfOutMCPkts
         Counter64,
      pr1645v2PbbBGriMVVlanMCH2PIfOutDiscards
         Counter64,
      pr1645v2PbbBGriMVVlanMCH2PIfOutErrors
         Counter64,
      pr1645v2PbbBGriMVVlanMCH2POutDropEx
         Counter64,
      pr1645v2PbbBGriMVVlanMCH2POutDropNoArp
         Counter64,
      pr1645v2PbbBGriMVVlanMCH2POutDropFilter
         Counter64,
      pr1645v2PbbBGriMVVlanMCH2PIfOutBandwidth
         Integer32,
      pr1645v2PbbBGriMVVlanMCH2PIfErrSec
         Counter32
      }

pr1645v2PbbBGriMVVlanMCH2PGlobalIx OBJECT-TYPE
   SYNTAX      GlobalIndex
   MAX-ACCESS  not-accessible
   STATUS      current
   DESCRIPTION
      "The value of the tlsCntTreeGlobalIndex of the MANAGED OBJECT."
   ::= {pr1645v2PbbBGriMVVlanMCH2PEntry 10}

pr1645v2PbbBGriMVVlanMCH2PTableIx OBJECT-TYPE
   SYNTAX      TableIndex
   MAX-ACCESS  not-accessible
   STATUS      current
   DESCRIPTION
      ""
   ::= {pr1645v2PbbBGriMVVlanMCH2PEntry 11}

pr1645v2PbbBGriMVVlanMCH2PSysUpTime OBJECT-TYPE
   SYNTAX      TimeTicks
   MAX-ACCESS  read-only
   STATUS      current
   DESCRIPTION
      "Path: pbbBridgeGroup.performance.vlan.mibCounters.h2Performance.sysUpTime

       Time in centi-second."
   ::= {pr1645v2PbbBGriMVVlanMCH2PEntry 16777216}

pr1645v2PbbBGriMVVlanMCH2PIfUpTime OBJECT-TYPE
   SYNTAX      TimeTicks
   MAX-ACCESS  read-only
   STATUS      current
   DESCRIPTION
      "Path: pbbBridgeGroup.performance.vlan.mibCounters.h2Performance.ifUpTime

       Time in centi-second."
   ::= {pr1645v2PbbBGriMVVlanMCH2PEntry 33554432}

pr1645v2PbbBGriMVVlanMCH2PIfStatChanges OBJECT-TYPE
   SYNTAX      Counter32
   MAX-ACCESS  read-only
   STATUS      current
   DESCRIPTION
      "Path: pbbBridgeGroup.performance.vlan.mibCounters.h2Performance.ifStatusChanges

       32 bit unsigned wrappable counter."
   ::= {pr1645v2PbbBGriMVVlanMCH2PEntry 50331648}

pr1645v2PbbBGriMVVlanMCH2PIfInOctets OBJECT-TYPE
   SYNTAX      Counter64
   MAX-ACCESS  read-only
   STATUS      current
   DESCRIPTION
      "Path: pbbBridgeGroup.performance.vlan.mibCounters.h2Performance.ifInOctets

       64 bit unsigned wrappable counter."
   ::= {pr1645v2PbbBGriMVVlanMCH2PEntry 67108864}

pr1645v2PbbBGriMVVlanMCH2PIfInUCPkts OBJECT-TYPE
   SYNTAX      Counter64
   MAX-ACCESS  read-only
   STATUS      current
   DESCRIPTION
      "Path: pbbBridgeGroup.performance.vlan.mibCounters.h2Performance.ifInUcastPkts

       64 bit unsigned wrappable counter."
   ::= {pr1645v2PbbBGriMVVlanMCH2PEntry 83886080}

pr1645v2PbbBGriMVVlanMCH2PIfInNUCPkts OBJECT-TYPE
   SYNTAX      Counter64
   MAX-ACCESS  read-only
   STATUS      current
   DESCRIPTION
      "Path: pbbBridgeGroup.performance.vlan.mibCounters.h2Performance.ifInNUcastPkts

       64 bit unsigned wrappable counter."
   ::= {pr1645v2PbbBGriMVVlanMCH2PEntry 100663296}

pr1645v2PbbBGriMVVlanMCH2PIfInBCPkts OBJECT-TYPE
   SYNTAX      Counter64
   MAX-ACCESS  read-only
   STATUS      current
   DESCRIPTION
      "Path: pbbBridgeGroup.performance.vlan.mibCounters.h2Performance.ifInBcastPkts

       64 bit unsigned wrappable counter."
   ::= {pr1645v2PbbBGriMVVlanMCH2PEntry 419430400}

pr1645v2PbbBGriMVVlanMCH2PIfInMCPkts OBJECT-TYPE
   SYNTAX      Counter64
   MAX-ACCESS  read-only
   STATUS      current
   DESCRIPTION
      "Path: pbbBridgeGroup.performance.vlan.mibCounters.h2Performance.ifInMcastPkts

       64 bit unsigned wrappable counter."
   ::= {pr1645v2PbbBGriMVVlanMCH2PEntry 436207616}

pr1645v2PbbBGriMVVlanMCH2PIfInDiscards OBJECT-TYPE
   SYNTAX      Counter64
   MAX-ACCESS  read-only
   STATUS      current
   DESCRIPTION
      "Path: pbbBridgeGroup.performance.vlan.mibCounters.h2Performance.ifInDiscards

       64 bit unsigned wrappable counter."
   ::= {pr1645v2PbbBGriMVVlanMCH2PEntry 117440512}

pr1645v2PbbBGriMVVlanMCH2PIfInErrors OBJECT-TYPE
   SYNTAX      Counter64
   MAX-ACCESS  read-only
   STATUS      current
   DESCRIPTION
      "Path: pbbBridgeGroup.performance.vlan.mibCounters.h2Performance.ifInErrors

       64 bit unsigned wrappable counter."
   ::= {pr1645v2PbbBGriMVVlanMCH2PEntry 134217728}

pr1645v2PbbBGriMVVlanMCH2PIfInUnkwn OBJECT-TYPE
   SYNTAX      Counter64
   MAX-ACCESS  read-only
   STATUS      current
   DESCRIPTION
      "Path: pbbBridgeGroup.performance.vlan.mibCounters.h2Performance.ifInUnknownProtos

       64 bit unsigned wrappable counter."
   ::= {pr1645v2PbbBGriMVVlanMCH2PEntry 150994944}

pr1645v2PbbBGriMVVlanMCH2PInDropEx OBJECT-TYPE
   SYNTAX      Counter64
   MAX-ACCESS  read-only
   STATUS      current
   DESCRIPTION
      "Path: pbbBridgeGroup.performance.vlan.mibCounters.h2Performance.ifInDropLevelExceeded

       64 bit unsigned wrappable counter."
   ::= {pr1645v2PbbBGriMVVlanMCH2PEntry 335544320}

pr1645v2PbbBGriMVVlanMCH2PInDropNoMac OBJECT-TYPE
   SYNTAX      Counter64
   MAX-ACCESS  read-only
   STATUS      current
   DESCRIPTION
      "Path: pbbBridgeGroup.performance.vlan.mibCounters.h2Performance.fInDiscardsNoMacFit

       64 bit unsigned wrappable counter."
   ::= {pr1645v2PbbBGriMVVlanMCH2PEntry 301989888}

pr1645v2PbbBGriMVVlanMCH2PInDropNUCast OBJECT-TYPE
   SYNTAX      Counter64
   MAX-ACCESS  read-only
   STATUS      current
   DESCRIPTION
      "Path: pbbBridgeGroup.performance.vlan.mibCounters.h2Performance.fInDiscardsNUCast

       64 bit unsigned wrappable counter."
   ::= {pr1645v2PbbBGriMVVlanMCH2PEntry 318767104}

pr1645v2PbbBGriMVVlanMCH2PInDropFilter OBJECT-TYPE
   SYNTAX      Counter64
   MAX-ACCESS  read-only
   STATUS      current
   DESCRIPTION
      "Path: pbbBridgeGroup.performance.vlan.mibCounters.h2Performance.fInDiscardsFilter

       64 bit unsigned wrappable counter."
   ::= {pr1645v2PbbBGriMVVlanMCH2PEntry 385875968}

pr1645v2PbbBGriMVVlanMCH2PIfInBandwidth OBJECT-TYPE
   SYNTAX      Integer32
   MAX-ACCESS  read-only
   STATUS      current
   DESCRIPTION
      "Path: pbbBridgeGroup.performance.vlan.mibCounters.h2Performance.ifInBandwidth

       unit name = bps
       formula = 8 * ; 8 /"
   ::= {pr1645v2PbbBGriMVVlanMCH2PEntry 268435456}

pr1645v2PbbBGriMVVlanMCH2PIfOutOctets OBJECT-TYPE
   SYNTAX      Counter64
   MAX-ACCESS  read-only
   STATUS      current
   DESCRIPTION
      "Path: pbbBridgeGroup.performance.vlan.mibCounters.h2Performance.ifOutOctets

       64 bit unsigned wrappable counter."
   ::= {pr1645v2PbbBGriMVVlanMCH2PEntry 167772160}

pr1645v2PbbBGriMVVlanMCH2PIfOutUCPkts OBJECT-TYPE
   SYNTAX      Counter64
   MAX-ACCESS  read-only
   STATUS      current
   DESCRIPTION
      "Path: pbbBridgeGroup.performance.vlan.mibCounters.h2Performance.ifOutUcastPkts

       64 bit unsigned wrappable counter."
   ::= {pr1645v2PbbBGriMVVlanMCH2PEntry 184549376}

pr1645v2PbbBGriMVVlanMCH2PIfOutNUCPkts OBJECT-TYPE
   SYNTAX      Counter64
   MAX-ACCESS  read-only
   STATUS      current
   DESCRIPTION
      "Path: pbbBridgeGroup.performance.vlan.mibCounters.h2Performance.ifOutNUcastPkts

       64 bit unsigned wrappable counter."
   ::= {pr1645v2PbbBGriMVVlanMCH2PEntry 201326592}

pr1645v2PbbBGriMVVlanMCH2PIfOutBCPkts OBJECT-TYPE
   SYNTAX      Counter64
   MAX-ACCESS  read-only
   STATUS      current
   DESCRIPTION
      "Path: pbbBridgeGroup.performance.vlan.mibCounters.h2Performance.ifOutBcastPkts

       64 bit unsigned wrappable counter."
   ::= {pr1645v2PbbBGriMVVlanMCH2PEntry 452984832}

pr1645v2PbbBGriMVVlanMCH2PIfOutMCPkts OBJECT-TYPE
   SYNTAX      Counter64
   MAX-ACCESS  read-only
   STATUS      current
   DESCRIPTION
      "Path: pbbBridgeGroup.performance.vlan.mibCounters.h2Performance.ifOutMcastPkts

       64 bit unsigned wrappable counter."
   ::= {pr1645v2PbbBGriMVVlanMCH2PEntry 469762048}

pr1645v2PbbBGriMVVlanMCH2PIfOutDiscards OBJECT-TYPE
   SYNTAX      Counter64
   MAX-ACCESS  read-only
   STATUS      current
   DESCRIPTION
      "Path: pbbBridgeGroup.performance.vlan.mibCounters.h2Performance.ifOutDiscards

       64 bit unsigned wrappable counter."
   ::= {pr1645v2PbbBGriMVVlanMCH2PEntry 218103808}

pr1645v2PbbBGriMVVlanMCH2PIfOutErrors OBJECT-TYPE
   SYNTAX      Counter64
   MAX-ACCESS  read-only
   STATUS      current
   DESCRIPTION
      "Path: pbbBridgeGroup.performance.vlan.mibCounters.h2Performance.ifOutErrors

       64 bit unsigned wrappable counter."
   ::= {pr1645v2PbbBGriMVVlanMCH2PEntry 234881024}

pr1645v2PbbBGriMVVlanMCH2POutDropEx OBJECT-TYPE
   SYNTAX      Counter64
   MAX-ACCESS  read-only
   STATUS      current
   DESCRIPTION
      "Path: pbbBridgeGroup.performance.vlan.mibCounters.h2Performance.ifOutDropLevelExceeded

       64 bit unsigned wrappable counter."
   ::= {pr1645v2PbbBGriMVVlanMCH2PEntry 352321536}

pr1645v2PbbBGriMVVlanMCH2POutDropNoArp OBJECT-TYPE
   SYNTAX      Counter64
   MAX-ACCESS  read-only
   STATUS      current
   DESCRIPTION
      "Path: pbbBridgeGroup.performance.vlan.mibCounters.h2Performance.ifOutDiscardsNoArp

       64 bit unsigned wrappable counter."
   ::= {pr1645v2PbbBGriMVVlanMCH2PEntry 369098752}

pr1645v2PbbBGriMVVlanMCH2POutDropFilter OBJECT-TYPE
   SYNTAX      Counter64
   MAX-ACCESS  read-only
   STATUS      current
   DESCRIPTION
      "Path: pbbBridgeGroup.performance.vlan.mibCounters.h2Performance.ifOutDiscardsFilter

       64 bit unsigned wrappable counter."
   ::= {pr1645v2PbbBGriMVVlanMCH2PEntry 402653184}

pr1645v2PbbBGriMVVlanMCH2PIfOutBandwidth OBJECT-TYPE
   SYNTAX      Integer32
   MAX-ACCESS  read-only
   STATUS      current
   DESCRIPTION
      "Path: pbbBridgeGroup.performance.vlan.mibCounters.h2Performance.ifOutBandwidth

       unit name = bps
       formula = 8 * ; 8 /"
   ::= {pr1645v2PbbBGriMVVlanMCH2PEntry 285212672}

pr1645v2PbbBGriMVVlanMCH2PIfErrSec OBJECT-TYPE
   SYNTAX      Counter32
   MAX-ACCESS  read-only
   STATUS      current
   DESCRIPTION
      "Path: pbbBridgeGroup.performance.vlan.mibCounters.h2Performance.ifErrSec

       32 bit unsigned wrappable counter."
   ::= {pr1645v2PbbBGriMVVlanMCH2PEntry 251658240}

pr1645v2PbbBGriMVVlanMCH24P OBJECT-TYPE
   SYNTAX      SEQUENCE OF Pr1645v2PbbBGriMVVlanMCH24PEntry
   MAX-ACCESS  not-accessible
   STATUS      current
   DESCRIPTION
      ""
   ::= {pr1645v2PbbBGriMVVlan 41615360}

pr1645v2PbbBGriMVVlanMCH24PEntry OBJECT-TYPE
   SYNTAX      Pr1645v2PbbBGriMVVlanMCH24PEntry
   MAX-ACCESS  not-accessible
   STATUS      current
   DESCRIPTION
      ""
   INDEX      { pr1645v2PbbBGriMVVlanMCH24PGlobalIx,
                pr1645v2PbbBGriMVVlanTableIx,
                pr1645v2PbbBGriMVVlanMCH24PTableIx }
   ::= {pr1645v2PbbBGriMVVlanMCH24P 1}

Pr1645v2PbbBGriMVVlanMCH24PEntry ::=
   SEQUENCE
      {
      pr1645v2PbbBGriMVVlanMCH24PGlobalIx
         GlobalIndex,
      pr1645v2PbbBGriMVVlanMCH24PTableIx
         TableIndex,
      pr1645v2PbbBGriMVVlanMCH24PSysUpTime
         TimeTicks,
      pr1645v2PbbBGriMVVlanMCH24PIfUpTime
         TimeTicks,
      pr1645v2PbbBGriMVVlanMCH24PIfStatChanges
         Counter32,
      pr1645v2PbbBGriMVVlanMCH24PIfInOctets
         Counter64,
      pr1645v2PbbBGriMVVlanMCH24PIfInUCPkts
         Counter64,
      pr1645v2PbbBGriMVVlanMCH24PIfInNUCPkts
         Counter64,
      pr1645v2PbbBGriMVVlanMCH24PIfInBCPkts
         Counter64,
      pr1645v2PbbBGriMVVlanMCH24PIfInMCPkts
         Counter64,
      pr1645v2PbbBGriMVVlanMCH24PIfInDiscards
         Counter64,
      pr1645v2PbbBGriMVVlanMCH24PIfInErrors
         Counter64,
      pr1645v2PbbBGriMVVlanMCH24PIfInUnkwn
         Counter64,
      pr1645v2PbbBGriMVVlanMCH24PInDropEx
         Counter64,
      pr1645v2PbbBGriMVVlanMCH24PInDropNoMac
         Counter64,
      pr1645v2PbbBGriMVVlanMCH24PInDropNUCast
         Counter64,
      pr1645v2PbbBGriMVVlanMCH24PInDropFilter
         Counter64,
      pr1645v2PbbBGriMVVlanMCH24PIfInBandwidth
         Integer32,
      pr1645v2PbbBGriMVVlanMCH24PIfOutOctets
         Counter64,
      pr1645v2PbbBGriMVVlanMCH24PIfOutUCPkts
         Counter64,
      pr1645v2PbbBGriMVVlanMCH24PIfOutNUCPkts
         Counter64,
      pr1645v2PbbBGriMVVlanMCH24PIfOutBCPkts
         Counter64,
      pr1645v2PbbBGriMVVlanMCH24PIfOutMCPkts
         Counter64,
      pr1645v2PbbBGriMVVlanMCH24PIfOutDiscards
         Counter64,
      pr1645v2PbbBGriMVVlanMCH24PIfOutErrors
         Counter64,
      pr1645v2PbbBGriMVVlanMCH24POutDropEx
         Counter64,
      pr1645v2PbbBGriMVVlanMCH24POutDropNoArp
         Counter64,
      pr1645v2PbbBGriMVVlanMCH24POutDropFilter
         Counter64,
      pr1645v2PbbBGriMVVlanMCH24PIfOutBandwidth
         Integer32,
      pr1645v2PbbBGriMVVlanMCH24PIfErrSec
         Counter32
      }

pr1645v2PbbBGriMVVlanMCH24PGlobalIx OBJECT-TYPE
   SYNTAX      GlobalIndex
   MAX-ACCESS  not-accessible
   STATUS      current
   DESCRIPTION
      "The value of the tlsCntTreeGlobalIndex of the MANAGED OBJECT."
   ::= {pr1645v2PbbBGriMVVlanMCH24PEntry 10}

pr1645v2PbbBGriMVVlanMCH24PTableIx OBJECT-TYPE
   SYNTAX      TableIndex
   MAX-ACCESS  not-accessible
   STATUS      current
   DESCRIPTION
      ""
   ::= {pr1645v2PbbBGriMVVlanMCH24PEntry 11}

pr1645v2PbbBGriMVVlanMCH24PSysUpTime OBJECT-TYPE
   SYNTAX      TimeTicks
   MAX-ACCESS  read-only
   STATUS      current
   DESCRIPTION
      "Path: pbbBridgeGroup.performance.vlan.mibCounters.h24Performance.sysUpTime

       Time in centi-second."
   ::= {pr1645v2PbbBGriMVVlanMCH24PEntry 16777216}

pr1645v2PbbBGriMVVlanMCH24PIfUpTime OBJECT-TYPE
   SYNTAX      TimeTicks
   MAX-ACCESS  read-only
   STATUS      current
   DESCRIPTION
      "Path: pbbBridgeGroup.performance.vlan.mibCounters.h24Performance.ifUpTime

       Time in centi-second."
   ::= {pr1645v2PbbBGriMVVlanMCH24PEntry 33554432}

pr1645v2PbbBGriMVVlanMCH24PIfStatChanges OBJECT-TYPE
   SYNTAX      Counter32
   MAX-ACCESS  read-only
   STATUS      current
   DESCRIPTION
      "Path: pbbBridgeGroup.performance.vlan.mibCounters.h24Performance.ifStatusChanges

       32 bit unsigned wrappable counter."
   ::= {pr1645v2PbbBGriMVVlanMCH24PEntry 50331648}

pr1645v2PbbBGriMVVlanMCH24PIfInOctets OBJECT-TYPE
   SYNTAX      Counter64
   MAX-ACCESS  read-only
   STATUS      current
   DESCRIPTION
      "Path: pbbBridgeGroup.performance.vlan.mibCounters.h24Performance.ifInOctets

       64 bit unsigned wrappable counter."
   ::= {pr1645v2PbbBGriMVVlanMCH24PEntry 67108864}

pr1645v2PbbBGriMVVlanMCH24PIfInUCPkts OBJECT-TYPE
   SYNTAX      Counter64
   MAX-ACCESS  read-only
   STATUS      current
   DESCRIPTION
      "Path: pbbBridgeGroup.performance.vlan.mibCounters.h24Performance.ifInUcastPkts

       64 bit unsigned wrappable counter."
   ::= {pr1645v2PbbBGriMVVlanMCH24PEntry 83886080}

pr1645v2PbbBGriMVVlanMCH24PIfInNUCPkts OBJECT-TYPE
   SYNTAX      Counter64
   MAX-ACCESS  read-only
   STATUS      current
   DESCRIPTION
      "Path: pbbBridgeGroup.performance.vlan.mibCounters.h24Performance.ifInNUcastPkts

       64 bit unsigned wrappable counter."
   ::= {pr1645v2PbbBGriMVVlanMCH24PEntry 100663296}

pr1645v2PbbBGriMVVlanMCH24PIfInBCPkts OBJECT-TYPE
   SYNTAX      Counter64
   MAX-ACCESS  read-only
   STATUS      current
   DESCRIPTION
      "Path: pbbBridgeGroup.performance.vlan.mibCounters.h24Performance.ifInBcastPkts

       64 bit unsigned wrappable counter."
   ::= {pr1645v2PbbBGriMVVlanMCH24PEntry 419430400}

pr1645v2PbbBGriMVVlanMCH24PIfInMCPkts OBJECT-TYPE
   SYNTAX      Counter64
   MAX-ACCESS  read-only
   STATUS      current
   DESCRIPTION
      "Path: pbbBridgeGroup.performance.vlan.mibCounters.h24Performance.ifInMcastPkts

       64 bit unsigned wrappable counter."
   ::= {pr1645v2PbbBGriMVVlanMCH24PEntry 436207616}

pr1645v2PbbBGriMVVlanMCH24PIfInDiscards OBJECT-TYPE
   SYNTAX      Counter64
   MAX-ACCESS  read-only
   STATUS      current
   DESCRIPTION
      "Path: pbbBridgeGroup.performance.vlan.mibCounters.h24Performance.ifInDiscards

       64 bit unsigned wrappable counter."
   ::= {pr1645v2PbbBGriMVVlanMCH24PEntry 117440512}

pr1645v2PbbBGriMVVlanMCH24PIfInErrors OBJECT-TYPE
   SYNTAX      Counter64
   MAX-ACCESS  read-only
   STATUS      current
   DESCRIPTION
      "Path: pbbBridgeGroup.performance.vlan.mibCounters.h24Performance.ifInErrors

       64 bit unsigned wrappable counter."
   ::= {pr1645v2PbbBGriMVVlanMCH24PEntry 134217728}

pr1645v2PbbBGriMVVlanMCH24PIfInUnkwn OBJECT-TYPE
   SYNTAX      Counter64
   MAX-ACCESS  read-only
   STATUS      current
   DESCRIPTION
      "Path: pbbBridgeGroup.performance.vlan.mibCounters.h24Performance.ifInUnknownProtos

       64 bit unsigned wrappable counter."
   ::= {pr1645v2PbbBGriMVVlanMCH24PEntry 150994944}

pr1645v2PbbBGriMVVlanMCH24PInDropEx OBJECT-TYPE
   SYNTAX      Counter64
   MAX-ACCESS  read-only
   STATUS      current
   DESCRIPTION
      "Path: pbbBridgeGroup.performance.vlan.mibCounters.h24Performance.ifInDropLevelExceeded

       64 bit unsigned wrappable counter."
   ::= {pr1645v2PbbBGriMVVlanMCH24PEntry 335544320}

pr1645v2PbbBGriMVVlanMCH24PInDropNoMac OBJECT-TYPE
   SYNTAX      Counter64
   MAX-ACCESS  read-only
   STATUS      current
   DESCRIPTION
      "Path: pbbBridgeGroup.performance.vlan.mibCounters.h24Performance.fInDiscardsNoMacFit

       64 bit unsigned wrappable counter."
   ::= {pr1645v2PbbBGriMVVlanMCH24PEntry 301989888}

pr1645v2PbbBGriMVVlanMCH24PInDropNUCast OBJECT-TYPE
   SYNTAX      Counter64
   MAX-ACCESS  read-only
   STATUS      current
   DESCRIPTION
      "Path: pbbBridgeGroup.performance.vlan.mibCounters.h24Performance.fInDiscardsNUCast

       64 bit unsigned wrappable counter."
   ::= {pr1645v2PbbBGriMVVlanMCH24PEntry 318767104}

pr1645v2PbbBGriMVVlanMCH24PInDropFilter OBJECT-TYPE
   SYNTAX      Counter64
   MAX-ACCESS  read-only
   STATUS      current
   DESCRIPTION
      "Path: pbbBridgeGroup.performance.vlan.mibCounters.h24Performance.fInDiscardsFilter

       64 bit unsigned wrappable counter."
   ::= {pr1645v2PbbBGriMVVlanMCH24PEntry 385875968}

pr1645v2PbbBGriMVVlanMCH24PIfInBandwidth OBJECT-TYPE
   SYNTAX      Integer32
   MAX-ACCESS  read-only
   STATUS      current
   DESCRIPTION
      "Path: pbbBridgeGroup.performance.vlan.mibCounters.h24Performance.ifInBandwidth

       unit name = bps
       formula = 8 * ; 8 /"
   ::= {pr1645v2PbbBGriMVVlanMCH24PEntry 268435456}

pr1645v2PbbBGriMVVlanMCH24PIfOutOctets OBJECT-TYPE
   SYNTAX      Counter64
   MAX-ACCESS  read-only
   STATUS      current
   DESCRIPTION
      "Path: pbbBridgeGroup.performance.vlan.mibCounters.h24Performance.ifOutOctets

       64 bit unsigned wrappable counter."
   ::= {pr1645v2PbbBGriMVVlanMCH24PEntry 167772160}

pr1645v2PbbBGriMVVlanMCH24PIfOutUCPkts OBJECT-TYPE
   SYNTAX      Counter64
   MAX-ACCESS  read-only
   STATUS      current
   DESCRIPTION
      "Path: pbbBridgeGroup.performance.vlan.mibCounters.h24Performance.ifOutUcastPkts

       64 bit unsigned wrappable counter."
   ::= {pr1645v2PbbBGriMVVlanMCH24PEntry 184549376}

pr1645v2PbbBGriMVVlanMCH24PIfOutNUCPkts OBJECT-TYPE
   SYNTAX      Counter64
   MAX-ACCESS  read-only
   STATUS      current
   DESCRIPTION
      "Path: pbbBridgeGroup.performance.vlan.mibCounters.h24Performance.ifOutNUcastPkts

       64 bit unsigned wrappable counter."
   ::= {pr1645v2PbbBGriMVVlanMCH24PEntry 201326592}

pr1645v2PbbBGriMVVlanMCH24PIfOutBCPkts OBJECT-TYPE
   SYNTAX      Counter64
   MAX-ACCESS  read-only
   STATUS      current
   DESCRIPTION
      "Path: pbbBridgeGroup.performance.vlan.mibCounters.h24Performance.ifOutBcastPkts

       64 bit unsigned wrappable counter."
   ::= {pr1645v2PbbBGriMVVlanMCH24PEntry 452984832}

pr1645v2PbbBGriMVVlanMCH24PIfOutMCPkts OBJECT-TYPE
   SYNTAX      Counter64
   MAX-ACCESS  read-only
   STATUS      current
   DESCRIPTION
      "Path: pbbBridgeGroup.performance.vlan.mibCounters.h24Performance.ifOutMcastPkts

       64 bit unsigned wrappable counter."
   ::= {pr1645v2PbbBGriMVVlanMCH24PEntry 469762048}

pr1645v2PbbBGriMVVlanMCH24PIfOutDiscards OBJECT-TYPE
   SYNTAX      Counter64
   MAX-ACCESS  read-only
   STATUS      current
   DESCRIPTION
      "Path: pbbBridgeGroup.performance.vlan.mibCounters.h24Performance.ifOutDiscards

       64 bit unsigned wrappable counter."
   ::= {pr1645v2PbbBGriMVVlanMCH24PEntry 218103808}

pr1645v2PbbBGriMVVlanMCH24PIfOutErrors OBJECT-TYPE
   SYNTAX      Counter64
   MAX-ACCESS  read-only
   STATUS      current
   DESCRIPTION
      "Path: pbbBridgeGroup.performance.vlan.mibCounters.h24Performance.ifOutErrors

       64 bit unsigned wrappable counter."
   ::= {pr1645v2PbbBGriMVVlanMCH24PEntry 234881024}

pr1645v2PbbBGriMVVlanMCH24POutDropEx OBJECT-TYPE
   SYNTAX      Counter64
   MAX-ACCESS  read-only
   STATUS      current
   DESCRIPTION
      "Path: pbbBridgeGroup.performance.vlan.mibCounters.h24Performance.ifOutDropLevelExceeded

       64 bit unsigned wrappable counter."
   ::= {pr1645v2PbbBGriMVVlanMCH24PEntry 352321536}

pr1645v2PbbBGriMVVlanMCH24POutDropNoArp OBJECT-TYPE
   SYNTAX      Counter64
   MAX-ACCESS  read-only
   STATUS      current
   DESCRIPTION
      "Path: pbbBridgeGroup.performance.vlan.mibCounters.h24Performance.ifOutDiscardsNoArp

       64 bit unsigned wrappable counter."
   ::= {pr1645v2PbbBGriMVVlanMCH24PEntry 369098752}

pr1645v2PbbBGriMVVlanMCH24POutDropFilter OBJECT-TYPE
   SYNTAX      Counter64
   MAX-ACCESS  read-only
   STATUS      current
   DESCRIPTION
      "Path: pbbBridgeGroup.performance.vlan.mibCounters.h24Performance.ifOutDiscardsFilter

       64 bit unsigned wrappable counter."
   ::= {pr1645v2PbbBGriMVVlanMCH24PEntry 402653184}

pr1645v2PbbBGriMVVlanMCH24PIfOutBandwidth OBJECT-TYPE
   SYNTAX      Integer32
   MAX-ACCESS  read-only
   STATUS      current
   DESCRIPTION
      "Path: pbbBridgeGroup.performance.vlan.mibCounters.h24Performance.ifOutBandwidth

       unit name = bps
       formula = 8 * ; 8 /"
   ::= {pr1645v2PbbBGriMVVlanMCH24PEntry 285212672}

pr1645v2PbbBGriMVVlanMCH24PIfErrSec OBJECT-TYPE
   SYNTAX      Counter32
   MAX-ACCESS  read-only
   STATUS      current
   DESCRIPTION
      "Path: pbbBridgeGroup.performance.vlan.mibCounters.h24Performance.ifErrSec

       32 bit unsigned wrappable counter."
   ::= {pr1645v2PbbBGriMVVlanMCH24PEntry 251658240}

pr1645v2PbbBGriMVVlanMCD7P OBJECT-TYPE
   SYNTAX      SEQUENCE OF Pr1645v2PbbBGriMVVlanMCD7PEntry
   MAX-ACCESS  not-accessible
   STATUS      current
   DESCRIPTION
      ""
   ::= {pr1645v2PbbBGriMVVlan 41680896}

pr1645v2PbbBGriMVVlanMCD7PEntry OBJECT-TYPE
   SYNTAX      Pr1645v2PbbBGriMVVlanMCD7PEntry
   MAX-ACCESS  not-accessible
   STATUS      current
   DESCRIPTION
      ""
   INDEX      { pr1645v2PbbBGriMVVlanMCD7PGlobalIx,
                pr1645v2PbbBGriMVVlanTableIx,
                pr1645v2PbbBGriMVVlanMCD7PTableIx }
   ::= {pr1645v2PbbBGriMVVlanMCD7P 1}

Pr1645v2PbbBGriMVVlanMCD7PEntry ::=
   SEQUENCE
      {
      pr1645v2PbbBGriMVVlanMCD7PGlobalIx
         GlobalIndex,
      pr1645v2PbbBGriMVVlanMCD7PTableIx
         TableIndex,
      pr1645v2PbbBGriMVVlanMCD7PSysUpTime
         TimeTicks,
      pr1645v2PbbBGriMVVlanMCD7PIfUpTime
         TimeTicks,
      pr1645v2PbbBGriMVVlanMCD7PIfStatChanges
         Counter32,
      pr1645v2PbbBGriMVVlanMCD7PIfInOctets
         Counter64,
      pr1645v2PbbBGriMVVlanMCD7PIfInUCPkts
         Counter64,
      pr1645v2PbbBGriMVVlanMCD7PIfInNUCPkts
         Counter64,
      pr1645v2PbbBGriMVVlanMCD7PIfInBCPkts
         Counter64,
      pr1645v2PbbBGriMVVlanMCD7PIfInMCPkts
         Counter64,
      pr1645v2PbbBGriMVVlanMCD7PIfInDiscards
         Counter64,
      pr1645v2PbbBGriMVVlanMCD7PIfInErrors
         Counter64,
      pr1645v2PbbBGriMVVlanMCD7PIfInUnkwn
         Counter64,
      pr1645v2PbbBGriMVVlanMCD7PInDropEx
         Counter64,
      pr1645v2PbbBGriMVVlanMCD7PInDropNoMac
         Counter64,
      pr1645v2PbbBGriMVVlanMCD7PInDropNUCast
         Counter64,
      pr1645v2PbbBGriMVVlanMCD7PInDropFilter
         Counter64,
      pr1645v2PbbBGriMVVlanMCD7PIfInBandwidth
         Integer32,
      pr1645v2PbbBGriMVVlanMCD7PIfOutOctets
         Counter64,
      pr1645v2PbbBGriMVVlanMCD7PIfOutUCPkts
         Counter64,
      pr1645v2PbbBGriMVVlanMCD7PIfOutNUCPkts
         Counter64,
      pr1645v2PbbBGriMVVlanMCD7PIfOutBCPkts
         Counter64,
      pr1645v2PbbBGriMVVlanMCD7PIfOutMCPkts
         Counter64,
      pr1645v2PbbBGriMVVlanMCD7PIfOutDiscards
         Counter64,
      pr1645v2PbbBGriMVVlanMCD7PIfOutErrors
         Counter64,
      pr1645v2PbbBGriMVVlanMCD7POutDropEx
         Counter64,
      pr1645v2PbbBGriMVVlanMCD7POutDropNoArp
         Counter64,
      pr1645v2PbbBGriMVVlanMCD7POutDropFilter
         Counter64,
      pr1645v2PbbBGriMVVlanMCD7PIfOutBandwidth
         Integer32,
      pr1645v2PbbBGriMVVlanMCD7PIfErrSec
         Counter32
      }

pr1645v2PbbBGriMVVlanMCD7PGlobalIx OBJECT-TYPE
   SYNTAX      GlobalIndex
   MAX-ACCESS  not-accessible
   STATUS      current
   DESCRIPTION
      "The value of the tlsCntTreeGlobalIndex of the MANAGED OBJECT."
   ::= {pr1645v2PbbBGriMVVlanMCD7PEntry 10}

pr1645v2PbbBGriMVVlanMCD7PTableIx OBJECT-TYPE
   SYNTAX      TableIndex
   MAX-ACCESS  not-accessible
   STATUS      current
   DESCRIPTION
      ""
   ::= {pr1645v2PbbBGriMVVlanMCD7PEntry 11}

pr1645v2PbbBGriMVVlanMCD7PSysUpTime OBJECT-TYPE
   SYNTAX      TimeTicks
   MAX-ACCESS  read-only
   STATUS      current
   DESCRIPTION
      "Path: pbbBridgeGroup.performance.vlan.mibCounters.d7Performance.sysUpTime

       Time in centi-second."
   ::= {pr1645v2PbbBGriMVVlanMCD7PEntry 16777216}

pr1645v2PbbBGriMVVlanMCD7PIfUpTime OBJECT-TYPE
   SYNTAX      TimeTicks
   MAX-ACCESS  read-only
   STATUS      current
   DESCRIPTION
      "Path: pbbBridgeGroup.performance.vlan.mibCounters.d7Performance.ifUpTime

       Time in centi-second."
   ::= {pr1645v2PbbBGriMVVlanMCD7PEntry 33554432}

pr1645v2PbbBGriMVVlanMCD7PIfStatChanges OBJECT-TYPE
   SYNTAX      Counter32
   MAX-ACCESS  read-only
   STATUS      current
   DESCRIPTION
      "Path: pbbBridgeGroup.performance.vlan.mibCounters.d7Performance.ifStatusChanges

       32 bit unsigned wrappable counter."
   ::= {pr1645v2PbbBGriMVVlanMCD7PEntry 50331648}

pr1645v2PbbBGriMVVlanMCD7PIfInOctets OBJECT-TYPE
   SYNTAX      Counter64
   MAX-ACCESS  read-only
   STATUS      current
   DESCRIPTION
      "Path: pbbBridgeGroup.performance.vlan.mibCounters.d7Performance.ifInOctets

       64 bit unsigned wrappable counter."
   ::= {pr1645v2PbbBGriMVVlanMCD7PEntry 67108864}

pr1645v2PbbBGriMVVlanMCD7PIfInUCPkts OBJECT-TYPE
   SYNTAX      Counter64
   MAX-ACCESS  read-only
   STATUS      current
   DESCRIPTION
      "Path: pbbBridgeGroup.performance.vlan.mibCounters.d7Performance.ifInUcastPkts

       64 bit unsigned wrappable counter."
   ::= {pr1645v2PbbBGriMVVlanMCD7PEntry 83886080}

pr1645v2PbbBGriMVVlanMCD7PIfInNUCPkts OBJECT-TYPE
   SYNTAX      Counter64
   MAX-ACCESS  read-only
   STATUS      current
   DESCRIPTION
      "Path: pbbBridgeGroup.performance.vlan.mibCounters.d7Performance.ifInNUcastPkts

       64 bit unsigned wrappable counter."
   ::= {pr1645v2PbbBGriMVVlanMCD7PEntry 100663296}

pr1645v2PbbBGriMVVlanMCD7PIfInBCPkts OBJECT-TYPE
   SYNTAX      Counter64
   MAX-ACCESS  read-only
   STATUS      current
   DESCRIPTION
      "Path: pbbBridgeGroup.performance.vlan.mibCounters.d7Performance.ifInBcastPkts

       64 bit unsigned wrappable counter."
   ::= {pr1645v2PbbBGriMVVlanMCD7PEntry 419430400}

pr1645v2PbbBGriMVVlanMCD7PIfInMCPkts OBJECT-TYPE
   SYNTAX      Counter64
   MAX-ACCESS  read-only
   STATUS      current
   DESCRIPTION
      "Path: pbbBridgeGroup.performance.vlan.mibCounters.d7Performance.ifInMcastPkts

       64 bit unsigned wrappable counter."
   ::= {pr1645v2PbbBGriMVVlanMCD7PEntry 436207616}

pr1645v2PbbBGriMVVlanMCD7PIfInDiscards OBJECT-TYPE
   SYNTAX      Counter64
   MAX-ACCESS  read-only
   STATUS      current
   DESCRIPTION
      "Path: pbbBridgeGroup.performance.vlan.mibCounters.d7Performance.ifInDiscards

       64 bit unsigned wrappable counter."
   ::= {pr1645v2PbbBGriMVVlanMCD7PEntry 117440512}

pr1645v2PbbBGriMVVlanMCD7PIfInErrors OBJECT-TYPE
   SYNTAX      Counter64
   MAX-ACCESS  read-only
   STATUS      current
   DESCRIPTION
      "Path: pbbBridgeGroup.performance.vlan.mibCounters.d7Performance.ifInErrors

       64 bit unsigned wrappable counter."
   ::= {pr1645v2PbbBGriMVVlanMCD7PEntry 134217728}

pr1645v2PbbBGriMVVlanMCD7PIfInUnkwn OBJECT-TYPE
   SYNTAX      Counter64
   MAX-ACCESS  read-only
   STATUS      current
   DESCRIPTION
      "Path: pbbBridgeGroup.performance.vlan.mibCounters.d7Performance.ifInUnknownProtos

       64 bit unsigned wrappable counter."
   ::= {pr1645v2PbbBGriMVVlanMCD7PEntry 150994944}

pr1645v2PbbBGriMVVlanMCD7PInDropEx OBJECT-TYPE
   SYNTAX      Counter64
   MAX-ACCESS  read-only
   STATUS      current
   DESCRIPTION
      "Path: pbbBridgeGroup.performance.vlan.mibCounters.d7Performance.ifInDropLevelExceeded

       64 bit unsigned wrappable counter."
   ::= {pr1645v2PbbBGriMVVlanMCD7PEntry 335544320}

pr1645v2PbbBGriMVVlanMCD7PInDropNoMac OBJECT-TYPE
   SYNTAX      Counter64
   MAX-ACCESS  read-only
   STATUS      current
   DESCRIPTION
      "Path: pbbBridgeGroup.performance.vlan.mibCounters.d7Performance.fInDiscardsNoMacFit

       64 bit unsigned wrappable counter."
   ::= {pr1645v2PbbBGriMVVlanMCD7PEntry 301989888}

pr1645v2PbbBGriMVVlanMCD7PInDropNUCast OBJECT-TYPE
   SYNTAX      Counter64
   MAX-ACCESS  read-only
   STATUS      current
   DESCRIPTION
      "Path: pbbBridgeGroup.performance.vlan.mibCounters.d7Performance.fInDiscardsNUCast

       64 bit unsigned wrappable counter."
   ::= {pr1645v2PbbBGriMVVlanMCD7PEntry 318767104}

pr1645v2PbbBGriMVVlanMCD7PInDropFilter OBJECT-TYPE
   SYNTAX      Counter64
   MAX-ACCESS  read-only
   STATUS      current
   DESCRIPTION
      "Path: pbbBridgeGroup.performance.vlan.mibCounters.d7Performance.fInDiscardsFilter

       64 bit unsigned wrappable counter."
   ::= {pr1645v2PbbBGriMVVlanMCD7PEntry 385875968}

pr1645v2PbbBGriMVVlanMCD7PIfInBandwidth OBJECT-TYPE
   SYNTAX      Integer32
   MAX-ACCESS  read-only
   STATUS      current
   DESCRIPTION
      "Path: pbbBridgeGroup.performance.vlan.mibCounters.d7Performance.ifInBandwidth

       unit name = bps
       formula = 8 * ; 8 /"
   ::= {pr1645v2PbbBGriMVVlanMCD7PEntry 268435456}

pr1645v2PbbBGriMVVlanMCD7PIfOutOctets OBJECT-TYPE
   SYNTAX      Counter64
   MAX-ACCESS  read-only
   STATUS      current
   DESCRIPTION
      "Path: pbbBridgeGroup.performance.vlan.mibCounters.d7Performance.ifOutOctets

       64 bit unsigned wrappable counter."
   ::= {pr1645v2PbbBGriMVVlanMCD7PEntry 167772160}

pr1645v2PbbBGriMVVlanMCD7PIfOutUCPkts OBJECT-TYPE
   SYNTAX      Counter64
   MAX-ACCESS  read-only
   STATUS      current
   DESCRIPTION
      "Path: pbbBridgeGroup.performance.vlan.mibCounters.d7Performance.ifOutUcastPkts

       64 bit unsigned wrappable counter."
   ::= {pr1645v2PbbBGriMVVlanMCD7PEntry 184549376}

pr1645v2PbbBGriMVVlanMCD7PIfOutNUCPkts OBJECT-TYPE
   SYNTAX      Counter64
   MAX-ACCESS  read-only
   STATUS      current
   DESCRIPTION
      "Path: pbbBridgeGroup.performance.vlan.mibCounters.d7Performance.ifOutNUcastPkts

       64 bit unsigned wrappable counter."
   ::= {pr1645v2PbbBGriMVVlanMCD7PEntry 201326592}

pr1645v2PbbBGriMVVlanMCD7PIfOutBCPkts OBJECT-TYPE
   SYNTAX      Counter64
   MAX-ACCESS  read-only
   STATUS      current
   DESCRIPTION
      "Path: pbbBridgeGroup.performance.vlan.mibCounters.d7Performance.ifOutBcastPkts

       64 bit unsigned wrappable counter."
   ::= {pr1645v2PbbBGriMVVlanMCD7PEntry 452984832}

pr1645v2PbbBGriMVVlanMCD7PIfOutMCPkts OBJECT-TYPE
   SYNTAX      Counter64
   MAX-ACCESS  read-only
   STATUS      current
   DESCRIPTION
      "Path: pbbBridgeGroup.performance.vlan.mibCounters.d7Performance.ifOutMcastPkts

       64 bit unsigned wrappable counter."
   ::= {pr1645v2PbbBGriMVVlanMCD7PEntry 469762048}

pr1645v2PbbBGriMVVlanMCD7PIfOutDiscards OBJECT-TYPE
   SYNTAX      Counter64
   MAX-ACCESS  read-only
   STATUS      current
   DESCRIPTION
      "Path: pbbBridgeGroup.performance.vlan.mibCounters.d7Performance.ifOutDiscards

       64 bit unsigned wrappable counter."
   ::= {pr1645v2PbbBGriMVVlanMCD7PEntry 218103808}

pr1645v2PbbBGriMVVlanMCD7PIfOutErrors OBJECT-TYPE
   SYNTAX      Counter64
   MAX-ACCESS  read-only
   STATUS      current
   DESCRIPTION
      "Path: pbbBridgeGroup.performance.vlan.mibCounters.d7Performance.ifOutErrors

       64 bit unsigned wrappable counter."
   ::= {pr1645v2PbbBGriMVVlanMCD7PEntry 234881024}

pr1645v2PbbBGriMVVlanMCD7POutDropEx OBJECT-TYPE
   SYNTAX      Counter64
   MAX-ACCESS  read-only
   STATUS      current
   DESCRIPTION
      "Path: pbbBridgeGroup.performance.vlan.mibCounters.d7Performance.ifOutDropLevelExceeded

       64 bit unsigned wrappable counter."
   ::= {pr1645v2PbbBGriMVVlanMCD7PEntry 352321536}

pr1645v2PbbBGriMVVlanMCD7POutDropNoArp OBJECT-TYPE
   SYNTAX      Counter64
   MAX-ACCESS  read-only
   STATUS      current
   DESCRIPTION
      "Path: pbbBridgeGroup.performance.vlan.mibCounters.d7Performance.ifOutDiscardsNoArp

       64 bit unsigned wrappable counter."
   ::= {pr1645v2PbbBGriMVVlanMCD7PEntry 369098752}

pr1645v2PbbBGriMVVlanMCD7POutDropFilter OBJECT-TYPE
   SYNTAX      Counter64
   MAX-ACCESS  read-only
   STATUS      current
   DESCRIPTION
      "Path: pbbBridgeGroup.performance.vlan.mibCounters.d7Performance.ifOutDiscardsFilter

       64 bit unsigned wrappable counter."
   ::= {pr1645v2PbbBGriMVVlanMCD7PEntry 402653184}

pr1645v2PbbBGriMVVlanMCD7PIfOutBandwidth OBJECT-TYPE
   SYNTAX      Integer32
   MAX-ACCESS  read-only
   STATUS      current
   DESCRIPTION
      "Path: pbbBridgeGroup.performance.vlan.mibCounters.d7Performance.ifOutBandwidth

       unit name = bps
       formula = 8 * ; 8 /"
   ::= {pr1645v2PbbBGriMVVlanMCD7PEntry 285212672}

pr1645v2PbbBGriMVVlanMCD7PIfErrSec OBJECT-TYPE
   SYNTAX      Counter32
   MAX-ACCESS  read-only
   STATUS      current
   DESCRIPTION
      "Path: pbbBridgeGroup.performance.vlan.mibCounters.d7Performance.ifErrSec

       32 bit unsigned wrappable counter."
   ::= {pr1645v2PbbBGriMVVlanMCD7PEntry 251658240}


pr1645v2PbbBGriMVPPPoE OBJECT IDENTIFIER ::= {pr1645v2PbbBGriMV 82}

pr1645v2PbbBGriMVPPPoESSCTable OBJECT-TYPE
   SYNTAX      SEQUENCE OF Pr1645v2PbbBGriMVPPPoEEntry
   MAX-ACCESS  not-accessible
   STATUS      current
   DESCRIPTION
      ""
   ::= {pr1645v2PbbBGriMVPPPoE 1}

pr1645v2PbbBGriMVPPPoEEntry OBJECT-TYPE
   SYNTAX      Pr1645v2PbbBGriMVPPPoEEntry
   MAX-ACCESS  not-accessible
   STATUS      current
   DESCRIPTION
      ""
   INDEX      { pr1645v2PbbBGriMVPPPoEGlobalIx,
                pr1645v2PbbBGriMVPPPoETableIx }
   ::= {pr1645v2PbbBGriMVPPPoESSCTable 1}

Pr1645v2PbbBGriMVPPPoEEntry ::=
   SEQUENCE
      {
      pr1645v2PbbBGriMVPPPoEGlobalIx
         GlobalIndex,
      pr1645v2PbbBGriMVPPPoETableIx
         TableIndex,
      pr1645v2PbbBGriMVPPPoEName
         DisplayString,
      pr1645v2PbbBGriMVPPPoEMCInOctets
         Counter64,
      pr1645v2PbbBGriMVPPPoEMCInUcast
         Counter64,
      pr1645v2PbbBGriMVPPPoEMCInNUcastPkts
         Counter64,
      pr1645v2PbbBGriMVPPPoEMCInBcastPkts
         Counter64,
      pr1645v2PbbBGriMVPPPoEMCInMcastPkts
         Counter64,
      pr1645v2PbbBGriMVPPPoEMCInDiscards
         Counter64,
      pr1645v2PbbBGriMVPPPoEMCInErrors
         Counter64,
      pr1645v2PbbBGriMVPPPoEMCInUnknownProtos
         Counter64,
      pr1645v2PbbBGriMVPPPoEMCInDropEx
         Counter64,
      pr1645v2PbbBGriMVPPPoEMCInDropNoMac
         Counter64,
      pr1645v2PbbBGriMVPPPoEMCInDropNUCast
         Counter64,
      pr1645v2PbbBGriMVPPPoEMCInDropFilter
         Counter64,
      pr1645v2PbbBGriMVPPPoEMCInBandwidth15sec
         Integer32,
      pr1645v2PbbBGriMVPPPoEMCInBandwidth30sec
         Integer32,
      pr1645v2PbbBGriMVPPPoEMCInBandwidth1min
         Integer32,
      pr1645v2PbbBGriMVPPPoEMCInBandwidth2min
         Integer32,
      pr1645v2PbbBGriMVPPPoEMCInBandwidth5min
         Integer32,
      pr1645v2PbbBGriMVPPPoEMCOutOctets
         Counter64,
      pr1645v2PbbBGriMVPPPoEMCOutUcastPkts
         Counter64,
      pr1645v2PbbBGriMVPPPoEMCOutNUcastPkts
         Counter64,
      pr1645v2PbbBGriMVPPPoEMCOutBcastPkts
         Counter64,
      pr1645v2PbbBGriMVPPPoEMCOutMcastPkts
         Counter64,
      pr1645v2PbbBGriMVPPPoEMCOutDiscards
         Counter64,
      pr1645v2PbbBGriMVPPPoEMCOutErrors
         Counter64,
      pr1645v2PbbBGriMVPPPoEMCOutQLen
         Counter32,
      pr1645v2PbbBGriMVPPPoEMCOutDropEx
         Counter64,
      pr1645v2PbbBGriMVPPPoEMCOutDropNoArp
         Counter64,
      pr1645v2PbbBGriMVPPPoEMCOutDropFilter
         Counter64,
      pr1645v2PbbBGriMVPPPoEMCOutBandwidth15sec
         Integer32,
      pr1645v2PbbBGriMVPPPoEMCOutBandwidth30sec
         Integer32,
      pr1645v2PbbBGriMVPPPoEMCOutBandwidth1min
         Integer32,
      pr1645v2PbbBGriMVPPPoEMCOutBandwidth2min
         Integer32,
      pr1645v2PbbBGriMVPPPoEMCOutBandwidth5min
         Integer32,
      pr1645v2PbbBGriMVPPPoEPppLinkMonitoringRequestsSent
         Gauge32,
      pr1645v2PbbBGriMVPPPoEPppLinkMonitoringRepliesRcvd
         Gauge32,
      pr1645v2PbbBGriMVPPPoEPppLinkMonitoringRequestsRcvd
         Gauge32,
      pr1645v2PbbBGriMVPPPoEPppLinkMonitoringRepliesSent
         Gauge32
      }

pr1645v2PbbBGriMVPPPoEGlobalIx OBJECT-TYPE
   SYNTAX      GlobalIndex
   MAX-ACCESS  not-accessible
   STATUS      current
   DESCRIPTION
      "The value of the tlsCntTreeGlobalIndex of the MANAGED OBJECT."
   ::= {pr1645v2PbbBGriMVPPPoEEntry 10}

pr1645v2PbbBGriMVPPPoETableIx OBJECT-TYPE
   SYNTAX      TableIndex
   MAX-ACCESS  not-accessible
   STATUS      current
   DESCRIPTION
      ""
   ::= {pr1645v2PbbBGriMVPPPoEEntry 11}

pr1645v2PbbBGriMVPPPoEName OBJECT-TYPE
   SYNTAX      DisplayString
   MAX-ACCESS  read-only
   STATUS      current
   DESCRIPTION
      "Path: pbbBridgeGroup.performance.pppoEClient.name"
   ::= {pr1645v2PbbBGriMVPPPoEEntry 16777216}

pr1645v2PbbBGriMVPPPoEMCInOctets OBJECT-TYPE
   SYNTAX      Counter64
   MAX-ACCESS  read-only
   STATUS      current
   DESCRIPTION
      "Path: pbbBridgeGroup.performance.pppoEClient.mibCounters.ifInOctets

       64 bit unsigned wrappable counter."
   ::= {pr1645v2PbbBGriMVPPPoEEntry 40697856}

pr1645v2PbbBGriMVPPPoEMCInUcast OBJECT-TYPE
   SYNTAX      Counter64
   MAX-ACCESS  read-only
   STATUS      current
   DESCRIPTION
      "Path: pbbBridgeGroup.performance.pppoEClient.mibCounters.ifInUcastPkts

       64 bit unsigned wrappable counter."
   ::= {pr1645v2PbbBGriMVPPPoEEntry 40763392}

pr1645v2PbbBGriMVPPPoEMCInNUcastPkts OBJECT-TYPE
   SYNTAX      Counter64
   MAX-ACCESS  read-only
   STATUS      current
   DESCRIPTION
      "Path: pbbBridgeGroup.performance.pppoEClient.mibCounters.ifInNUcastPkts

       64 bit unsigned wrappable counter."
   ::= {pr1645v2PbbBGriMVPPPoEEntry 40828928}

pr1645v2PbbBGriMVPPPoEMCInBcastPkts OBJECT-TYPE
   SYNTAX      Counter64
   MAX-ACCESS  read-only
   STATUS      current
   DESCRIPTION
      "Path: pbbBridgeGroup.performance.pppoEClient.mibCounters.ifInBcastPkts

       64 bit unsigned wrappable counter."
   ::= {pr1645v2PbbBGriMVPPPoEEntry 47382528}

pr1645v2PbbBGriMVPPPoEMCInMcastPkts OBJECT-TYPE
   SYNTAX      Counter64
   MAX-ACCESS  read-only
   STATUS      current
   DESCRIPTION
      "Path: pbbBridgeGroup.performance.pppoEClient.mibCounters.ifInMcastPkts

       64 bit unsigned wrappable counter."
   ::= {pr1645v2PbbBGriMVPPPoEEntry 48037888}

pr1645v2PbbBGriMVPPPoEMCInDiscards OBJECT-TYPE
   SYNTAX      Counter64
   MAX-ACCESS  read-only
   STATUS      current
   DESCRIPTION
      "Path: pbbBridgeGroup.performance.pppoEClient.mibCounters.ifInDiscards

       64 bit unsigned wrappable counter."
   ::= {pr1645v2PbbBGriMVPPPoEEntry 40894464}

pr1645v2PbbBGriMVPPPoEMCInErrors OBJECT-TYPE
   SYNTAX      Counter64
   MAX-ACCESS  read-only
   STATUS      current
   DESCRIPTION
      "Path: pbbBridgeGroup.performance.pppoEClient.mibCounters.ifInErrors

       64 bit unsigned wrappable counter."
   ::= {pr1645v2PbbBGriMVPPPoEEntry 40960000}

pr1645v2PbbBGriMVPPPoEMCInUnknownProtos OBJECT-TYPE
   SYNTAX      Counter64
   MAX-ACCESS  read-only
   STATUS      current
   DESCRIPTION
      "Path: pbbBridgeGroup.performance.pppoEClient.mibCounters.ifInUnknownProtos

       64 bit unsigned wrappable counter."
   ::= {pr1645v2PbbBGriMVPPPoEEntry 41025536}

pr1645v2PbbBGriMVPPPoEMCInDropEx OBJECT-TYPE
   SYNTAX      Counter64
   MAX-ACCESS  read-only
   STATUS      current
   DESCRIPTION
      "Path: pbbBridgeGroup.performance.pppoEClient.mibCounters.ifInDropLevelExceeded

       64 bit unsigned wrappable counter."
   ::= {pr1645v2PbbBGriMVPPPoEEntry 42074112}

pr1645v2PbbBGriMVPPPoEMCInDropNoMac OBJECT-TYPE
   SYNTAX      Counter64
   MAX-ACCESS  read-only
   STATUS      current
   DESCRIPTION
      "Path: pbbBridgeGroup.performance.pppoEClient.mibCounters.ifInDiscardsNoMacFit

       64 bit unsigned wrappable counter."
   ::= {pr1645v2PbbBGriMVPPPoEEntry 42270720}

pr1645v2PbbBGriMVPPPoEMCInDropNUCast OBJECT-TYPE
   SYNTAX      Counter64
   MAX-ACCESS  read-only
   STATUS      current
   DESCRIPTION
      "Path: pbbBridgeGroup.performance.pppoEClient.mibCounters.ifInDiscardsNUCast

       64 bit unsigned wrappable counter."
   ::= {pr1645v2PbbBGriMVPPPoEEntry 42467328}

pr1645v2PbbBGriMVPPPoEMCInDropFilter OBJECT-TYPE
   SYNTAX      Counter64
   MAX-ACCESS  read-only
   STATUS      current
   DESCRIPTION
      "Path: pbbBridgeGroup.performance.pppoEClient.mibCounters.ifInDiscardsFilter

       64 bit unsigned wrappable counter."
   ::= {pr1645v2PbbBGriMVPPPoEEntry 42532864}

pr1645v2PbbBGriMVPPPoEMCInBandwidth15sec OBJECT-TYPE
   SYNTAX      Integer32
   MAX-ACCESS  read-only
   STATUS      current
   DESCRIPTION
      "Path: pbbBridgeGroup.performance.pppoEClient.mibCounters.ifInBandwidth.15sec

       unit name = bps
       formula = 8 * ; 8 /"
   ::= {pr1645v2PbbBGriMVPPPoEEntry 45417728}

pr1645v2PbbBGriMVPPPoEMCInBandwidth30sec OBJECT-TYPE
   SYNTAX      Integer32
   MAX-ACCESS  read-only
   STATUS      current
   DESCRIPTION
      "Path: pbbBridgeGroup.performance.pppoEClient.mibCounters.ifInBandwidth.30sec

       unit name = bps
       formula = 8 * ; 8 /"
   ::= {pr1645v2PbbBGriMVPPPoEEntry 45419008}

pr1645v2PbbBGriMVPPPoEMCInBandwidth1min OBJECT-TYPE
   SYNTAX      Integer32
   MAX-ACCESS  read-only
   STATUS      current
   DESCRIPTION
      "Path: pbbBridgeGroup.performance.pppoEClient.mibCounters.ifInBandwidth.1min

       unit name = bps
       formula = 8 * ; 8 /"
   ::= {pr1645v2PbbBGriMVPPPoEEntry 45421568}

pr1645v2PbbBGriMVPPPoEMCInBandwidth2min OBJECT-TYPE
   SYNTAX      Integer32
   MAX-ACCESS  read-only
   STATUS      current
   DESCRIPTION
      "Path: pbbBridgeGroup.performance.pppoEClient.mibCounters.ifInBandwidth.2min

       unit name = bps
       formula = 8 * ; 8 /"
   ::= {pr1645v2PbbBGriMVPPPoEEntry 45426688}

pr1645v2PbbBGriMVPPPoEMCInBandwidth5min OBJECT-TYPE
   SYNTAX      Integer32
   MAX-ACCESS  read-only
   STATUS      current
   DESCRIPTION
      "Path: pbbBridgeGroup.performance.pppoEClient.mibCounters.ifInBandwidth.5min

       unit name = bps
       formula = 8 * ; 8 /"
   ::= {pr1645v2PbbBGriMVPPPoEEntry 45442048}

pr1645v2PbbBGriMVPPPoEMCOutOctets OBJECT-TYPE
   SYNTAX      Counter64
   MAX-ACCESS  read-only
   STATUS      current
   DESCRIPTION
      "Path: pbbBridgeGroup.performance.pppoEClient.mibCounters.ifOutOctets

       64 bit unsigned wrappable counter."
   ::= {pr1645v2PbbBGriMVPPPoEEntry 41091072}

pr1645v2PbbBGriMVPPPoEMCOutUcastPkts OBJECT-TYPE
   SYNTAX      Counter64
   MAX-ACCESS  read-only
   STATUS      current
   DESCRIPTION
      "Path: pbbBridgeGroup.performance.pppoEClient.mibCounters.ifOutUcastPkts

       64 bit unsigned wrappable counter."
   ::= {pr1645v2PbbBGriMVPPPoEEntry 41156608}

pr1645v2PbbBGriMVPPPoEMCOutNUcastPkts OBJECT-TYPE
   SYNTAX      Counter64
   MAX-ACCESS  read-only
   STATUS      current
   DESCRIPTION
      "Path: pbbBridgeGroup.performance.pppoEClient.mibCounters.ifOutNUcastPkts

       64 bit unsigned wrappable counter."
   ::= {pr1645v2PbbBGriMVPPPoEEntry 41222144}

pr1645v2PbbBGriMVPPPoEMCOutBcastPkts OBJECT-TYPE
   SYNTAX      Counter64
   MAX-ACCESS  read-only
   STATUS      current
   DESCRIPTION
      "Path: pbbBridgeGroup.performance.pppoEClient.mibCounters.ifOutBcastPkts

       64 bit unsigned wrappable counter."
   ::= {pr1645v2PbbBGriMVPPPoEEntry 47775744}

pr1645v2PbbBGriMVPPPoEMCOutMcastPkts OBJECT-TYPE
   SYNTAX      Counter64
   MAX-ACCESS  read-only
   STATUS      current
   DESCRIPTION
      "Path: pbbBridgeGroup.performance.pppoEClient.mibCounters.ifOutMcastPkts

       64 bit unsigned wrappable counter."
   ::= {pr1645v2PbbBGriMVPPPoEEntry 48431104}

pr1645v2PbbBGriMVPPPoEMCOutDiscards OBJECT-TYPE
   SYNTAX      Counter64
   MAX-ACCESS  read-only
   STATUS      current
   DESCRIPTION
      "Path: pbbBridgeGroup.performance.pppoEClient.mibCounters.ifOutDiscards

       64 bit unsigned wrappable counter."
   ::= {pr1645v2PbbBGriMVPPPoEEntry 41287680}

pr1645v2PbbBGriMVPPPoEMCOutErrors OBJECT-TYPE
   SYNTAX      Counter64
   MAX-ACCESS  read-only
   STATUS      current
   DESCRIPTION
      "Path: pbbBridgeGroup.performance.pppoEClient.mibCounters.ifOutErrors

       64 bit unsigned wrappable counter."
   ::= {pr1645v2PbbBGriMVPPPoEEntry 41353216}

pr1645v2PbbBGriMVPPPoEMCOutQLen OBJECT-TYPE
   SYNTAX      Counter32
   MAX-ACCESS  read-only
   STATUS      current
   DESCRIPTION
      "Path: pbbBridgeGroup.performance.pppoEClient.mibCounters.ifOutQLen

       32 bit unsigned wrappable counter."
   ::= {pr1645v2PbbBGriMVPPPoEEntry 41418752}

pr1645v2PbbBGriMVPPPoEMCOutDropEx OBJECT-TYPE
   SYNTAX      Counter64
   MAX-ACCESS  read-only
   STATUS      current
   DESCRIPTION
      "Path: pbbBridgeGroup.performance.pppoEClient.mibCounters.ifOutDropLevelExceeded

       64 bit unsigned wrappable counter."
   ::= {pr1645v2PbbBGriMVPPPoEEntry 41484288}

pr1645v2PbbBGriMVPPPoEMCOutDropNoArp OBJECT-TYPE
   SYNTAX      Counter64
   MAX-ACCESS  read-only
   STATUS      current
   DESCRIPTION
      "Path: pbbBridgeGroup.performance.pppoEClient.mibCounters.ifOutDiscardsNoArp

       64 bit unsigned wrappable counter."
   ::= {pr1645v2PbbBGriMVPPPoEEntry 42336256}

pr1645v2PbbBGriMVPPPoEMCOutDropFilter OBJECT-TYPE
   SYNTAX      Counter64
   MAX-ACCESS  read-only
   STATUS      current
   DESCRIPTION
      "Path: pbbBridgeGroup.performance.pppoEClient.mibCounters.ifOutDiscardsFilter

       64 bit unsigned wrappable counter."
   ::= {pr1645v2PbbBGriMVPPPoEEntry 42598400}

pr1645v2PbbBGriMVPPPoEMCOutBandwidth15sec OBJECT-TYPE
   SYNTAX      Integer32
   MAX-ACCESS  read-only
   STATUS      current
   DESCRIPTION
      "Path: pbbBridgeGroup.performance.pppoEClient.mibCounters.ifOutBandwidth.15sec

       unit name = bps
       formula = 8 * ; 8 /"
   ::= {pr1645v2PbbBGriMVPPPoEEntry 45483264}

pr1645v2PbbBGriMVPPPoEMCOutBandwidth30sec OBJECT-TYPE
   SYNTAX      Integer32
   MAX-ACCESS  read-only
   STATUS      current
   DESCRIPTION
      "Path: pbbBridgeGroup.performance.pppoEClient.mibCounters.ifOutBandwidth.30sec

       unit name = bps
       formula = 8 * ; 8 /"
   ::= {pr1645v2PbbBGriMVPPPoEEntry 45484544}

pr1645v2PbbBGriMVPPPoEMCOutBandwidth1min OBJECT-TYPE
   SYNTAX      Integer32
   MAX-ACCESS  read-only
   STATUS      current
   DESCRIPTION
      "Path: pbbBridgeGroup.performance.pppoEClient.mibCounters.ifOutBandwidth.1min

       unit name = bps
       formula = 8 * ; 8 /"
   ::= {pr1645v2PbbBGriMVPPPoEEntry 45487104}

pr1645v2PbbBGriMVPPPoEMCOutBandwidth2min OBJECT-TYPE
   SYNTAX      Integer32
   MAX-ACCESS  read-only
   STATUS      current
   DESCRIPTION
      "Path: pbbBridgeGroup.performance.pppoEClient.mibCounters.ifOutBandwidth.2min

       unit name = bps
       formula = 8 * ; 8 /"
   ::= {pr1645v2PbbBGriMVPPPoEEntry 45492224}

pr1645v2PbbBGriMVPPPoEMCOutBandwidth5min OBJECT-TYPE
   SYNTAX      Integer32
   MAX-ACCESS  read-only
   STATUS      current
   DESCRIPTION
      "Path: pbbBridgeGroup.performance.pppoEClient.mibCounters.ifOutBandwidth.5min

       unit name = bps
       formula = 8 * ; 8 /"
   ::= {pr1645v2PbbBGriMVPPPoEEntry 45507584}

pr1645v2PbbBGriMVPPPoEPppLinkMonitoringRequestsSent OBJECT-TYPE
   SYNTAX      Gauge32
   MAX-ACCESS  read-only
   STATUS      current
   DESCRIPTION
      "Path: pbbBridgeGroup.performance.pppoEClient.ppp.linkMonitoring.requestsSent

       32 bit unsigned gauge value."
   ::= {pr1645v2PbbBGriMVPPPoEEntry 50397440}

pr1645v2PbbBGriMVPPPoEPppLinkMonitoringRepliesRcvd OBJECT-TYPE
   SYNTAX      Gauge32
   MAX-ACCESS  read-only
   STATUS      current
   DESCRIPTION
      "Path: pbbBridgeGroup.performance.pppoEClient.ppp.linkMonitoring.repliesRcvd

       32 bit unsigned gauge value."
   ::= {pr1645v2PbbBGriMVPPPoEEntry 50397696}

pr1645v2PbbBGriMVPPPoEPppLinkMonitoringRequestsRcvd OBJECT-TYPE
   SYNTAX      Gauge32
   MAX-ACCESS  read-only
   STATUS      current
   DESCRIPTION
      "Path: pbbBridgeGroup.performance.pppoEClient.ppp.linkMonitoring.requestsRcvd

       32 bit unsigned gauge value."
   ::= {pr1645v2PbbBGriMVPPPoEEntry 50397952}

pr1645v2PbbBGriMVPPPoEPppLinkMonitoringRepliesSent OBJECT-TYPE
   SYNTAX      Gauge32
   MAX-ACCESS  read-only
   STATUS      current
   DESCRIPTION
      "Path: pbbBridgeGroup.performance.pppoEClient.ppp.linkMonitoring.repliesSent

       32 bit unsigned gauge value."
   ::= {pr1645v2PbbBGriMVPPPoEEntry 50398208}

pr1645v2PbbBGriMVPPPoEMCH2P OBJECT-TYPE
   SYNTAX      SEQUENCE OF Pr1645v2PbbBGriMVPPPoEMCH2PEntry
   MAX-ACCESS  not-accessible
   STATUS      current
   DESCRIPTION
      ""
   ::= {pr1645v2PbbBGriMVPPPoE 41549824}

pr1645v2PbbBGriMVPPPoEMCH2PEntry OBJECT-TYPE
   SYNTAX      Pr1645v2PbbBGriMVPPPoEMCH2PEntry
   MAX-ACCESS  not-accessible
   STATUS      current
   DESCRIPTION
      ""
   INDEX      { pr1645v2PbbBGriMVPPPoEMCH2PGlobalIx,
                pr1645v2PbbBGriMVPPPoETableIx,
                pr1645v2PbbBGriMVPPPoEMCH2PTableIx }
   ::= {pr1645v2PbbBGriMVPPPoEMCH2P 1}

Pr1645v2PbbBGriMVPPPoEMCH2PEntry ::=
   SEQUENCE
      {
      pr1645v2PbbBGriMVPPPoEMCH2PGlobalIx
         GlobalIndex,
      pr1645v2PbbBGriMVPPPoEMCH2PTableIx
         TableIndex,
      pr1645v2PbbBGriMVPPPoEMCH2PSysUpTime
         TimeTicks,
      pr1645v2PbbBGriMVPPPoEMCH2PIfUpTime
         TimeTicks,
      pr1645v2PbbBGriMVPPPoEMCH2PIfStatChanges
         Counter32,
      pr1645v2PbbBGriMVPPPoEMCH2PIfInOctets
         Counter64,
      pr1645v2PbbBGriMVPPPoEMCH2PIfInUCPkts
         Counter64,
      pr1645v2PbbBGriMVPPPoEMCH2PIfInNUCPkts
         Counter64,
      pr1645v2PbbBGriMVPPPoEMCH2PIfInBCPkts
         Counter64,
      pr1645v2PbbBGriMVPPPoEMCH2PIfInMCPkts
         Counter64,
      pr1645v2PbbBGriMVPPPoEMCH2PIfInDiscards
         Counter64,
      pr1645v2PbbBGriMVPPPoEMCH2PIfInErrors
         Counter64,
      pr1645v2PbbBGriMVPPPoEMCH2PIfInUnkwn
         Counter64,
      pr1645v2PbbBGriMVPPPoEMCH2PInDropEx
         Counter64,
      pr1645v2PbbBGriMVPPPoEMCH2PInDropNoMac
         Counter64,
      pr1645v2PbbBGriMVPPPoEMCH2PInDropNUCast
         Counter64,
      pr1645v2PbbBGriMVPPPoEMCH2PInDropFilter
         Counter64,
      pr1645v2PbbBGriMVPPPoEMCH2PIfInBandwidth
         Integer32,
      pr1645v2PbbBGriMVPPPoEMCH2PIfOutOctets
         Counter64,
      pr1645v2PbbBGriMVPPPoEMCH2PIfOutUCPkts
         Counter64,
      pr1645v2PbbBGriMVPPPoEMCH2PIfOutNUCPkts
         Counter64,
      pr1645v2PbbBGriMVPPPoEMCH2PIfOutBCPkts
         Counter64,
      pr1645v2PbbBGriMVPPPoEMCH2PIfOutMCPkts
         Counter64,
      pr1645v2PbbBGriMVPPPoEMCH2PIfOutDiscards
         Counter64,
      pr1645v2PbbBGriMVPPPoEMCH2PIfOutErrors
         Counter64,
      pr1645v2PbbBGriMVPPPoEMCH2POutDropEx
         Counter64,
      pr1645v2PbbBGriMVPPPoEMCH2POutDropNoArp
         Counter64,
      pr1645v2PbbBGriMVPPPoEMCH2POutDropFilter
         Counter64,
      pr1645v2PbbBGriMVPPPoEMCH2PIfOutBandwidth
         Integer32,
      pr1645v2PbbBGriMVPPPoEMCH2PIfErrSec
         Counter32
      }

pr1645v2PbbBGriMVPPPoEMCH2PGlobalIx OBJECT-TYPE
   SYNTAX      GlobalIndex
   MAX-ACCESS  not-accessible
   STATUS      current
   DESCRIPTION
      "The value of the tlsCntTreeGlobalIndex of the MANAGED OBJECT."
   ::= {pr1645v2PbbBGriMVPPPoEMCH2PEntry 10}

pr1645v2PbbBGriMVPPPoEMCH2PTableIx OBJECT-TYPE
   SYNTAX      TableIndex
   MAX-ACCESS  not-accessible
   STATUS      current
   DESCRIPTION
      ""
   ::= {pr1645v2PbbBGriMVPPPoEMCH2PEntry 11}

pr1645v2PbbBGriMVPPPoEMCH2PSysUpTime OBJECT-TYPE
   SYNTAX      TimeTicks
   MAX-ACCESS  read-only
   STATUS      current
   DESCRIPTION
      "Path: pbbBridgeGroup.performance.pppoEClient.mibCounters.h2Performance.sysUpTime

       Time in centi-second."
   ::= {pr1645v2PbbBGriMVPPPoEMCH2PEntry 16777216}

pr1645v2PbbBGriMVPPPoEMCH2PIfUpTime OBJECT-TYPE
   SYNTAX      TimeTicks
   MAX-ACCESS  read-only
   STATUS      current
   DESCRIPTION
      "Path: pbbBridgeGroup.performance.pppoEClient.mibCounters.h2Performance.ifUpTime

       Time in centi-second."
   ::= {pr1645v2PbbBGriMVPPPoEMCH2PEntry 33554432}

pr1645v2PbbBGriMVPPPoEMCH2PIfStatChanges OBJECT-TYPE
   SYNTAX      Counter32
   MAX-ACCESS  read-only
   STATUS      current
   DESCRIPTION
      "Path: pbbBridgeGroup.performance.pppoEClient.mibCounters.h2Performance.ifStatusChanges

       32 bit unsigned wrappable counter."
   ::= {pr1645v2PbbBGriMVPPPoEMCH2PEntry 50331648}

pr1645v2PbbBGriMVPPPoEMCH2PIfInOctets OBJECT-TYPE
   SYNTAX      Counter64
   MAX-ACCESS  read-only
   STATUS      current
   DESCRIPTION
      "Path: pbbBridgeGroup.performance.pppoEClient.mibCounters.h2Performance.ifInOctets

       64 bit unsigned wrappable counter."
   ::= {pr1645v2PbbBGriMVPPPoEMCH2PEntry 67108864}

pr1645v2PbbBGriMVPPPoEMCH2PIfInUCPkts OBJECT-TYPE
   SYNTAX      Counter64
   MAX-ACCESS  read-only
   STATUS      current
   DESCRIPTION
      "Path: pbbBridgeGroup.performance.pppoEClient.mibCounters.h2Performance.ifInUcastPkts

       64 bit unsigned wrappable counter."
   ::= {pr1645v2PbbBGriMVPPPoEMCH2PEntry 83886080}

pr1645v2PbbBGriMVPPPoEMCH2PIfInNUCPkts OBJECT-TYPE
   SYNTAX      Counter64
   MAX-ACCESS  read-only
   STATUS      current
   DESCRIPTION
      "Path: pbbBridgeGroup.performance.pppoEClient.mibCounters.h2Performance.ifInNUcastPkts

       64 bit unsigned wrappable counter."
   ::= {pr1645v2PbbBGriMVPPPoEMCH2PEntry 100663296}

pr1645v2PbbBGriMVPPPoEMCH2PIfInBCPkts OBJECT-TYPE
   SYNTAX      Counter64
   MAX-ACCESS  read-only
   STATUS      current
   DESCRIPTION
      "Path: pbbBridgeGroup.performance.pppoEClient.mibCounters.h2Performance.ifInBcastPkts

       64 bit unsigned wrappable counter."
   ::= {pr1645v2PbbBGriMVPPPoEMCH2PEntry 419430400}

pr1645v2PbbBGriMVPPPoEMCH2PIfInMCPkts OBJECT-TYPE
   SYNTAX      Counter64
   MAX-ACCESS  read-only
   STATUS      current
   DESCRIPTION
      "Path: pbbBridgeGroup.performance.pppoEClient.mibCounters.h2Performance.ifInMcastPkts

       64 bit unsigned wrappable counter."
   ::= {pr1645v2PbbBGriMVPPPoEMCH2PEntry 436207616}

pr1645v2PbbBGriMVPPPoEMCH2PIfInDiscards OBJECT-TYPE
   SYNTAX      Counter64
   MAX-ACCESS  read-only
   STATUS      current
   DESCRIPTION
      "Path: pbbBridgeGroup.performance.pppoEClient.mibCounters.h2Performance.ifInDiscards

       64 bit unsigned wrappable counter."
   ::= {pr1645v2PbbBGriMVPPPoEMCH2PEntry 117440512}

pr1645v2PbbBGriMVPPPoEMCH2PIfInErrors OBJECT-TYPE
   SYNTAX      Counter64
   MAX-ACCESS  read-only
   STATUS      current
   DESCRIPTION
      "Path: pbbBridgeGroup.performance.pppoEClient.mibCounters.h2Performance.ifInErrors

       64 bit unsigned wrappable counter."
   ::= {pr1645v2PbbBGriMVPPPoEMCH2PEntry 134217728}

pr1645v2PbbBGriMVPPPoEMCH2PIfInUnkwn OBJECT-TYPE
   SYNTAX      Counter64
   MAX-ACCESS  read-only
   STATUS      current
   DESCRIPTION
      "Path: pbbBridgeGroup.performance.pppoEClient.mibCounters.h2Performance.ifInUnknownProtos

       64 bit unsigned wrappable counter."
   ::= {pr1645v2PbbBGriMVPPPoEMCH2PEntry 150994944}

pr1645v2PbbBGriMVPPPoEMCH2PInDropEx OBJECT-TYPE
   SYNTAX      Counter64
   MAX-ACCESS  read-only
   STATUS      current
   DESCRIPTION
      "Path: pbbBridgeGroup.performance.pppoEClient.mibCounters.h2Performance.ifInDropLevelExceeded

       64 bit unsigned wrappable counter."
   ::= {pr1645v2PbbBGriMVPPPoEMCH2PEntry 335544320}

pr1645v2PbbBGriMVPPPoEMCH2PInDropNoMac OBJECT-TYPE
   SYNTAX      Counter64
   MAX-ACCESS  read-only
   STATUS      current
   DESCRIPTION
      "Path: pbbBridgeGroup.performance.pppoEClient.mibCounters.h2Performance.fInDiscardsNoMacFit

       64 bit unsigned wrappable counter."
   ::= {pr1645v2PbbBGriMVPPPoEMCH2PEntry 301989888}

pr1645v2PbbBGriMVPPPoEMCH2PInDropNUCast OBJECT-TYPE
   SYNTAX      Counter64
   MAX-ACCESS  read-only
   STATUS      current
   DESCRIPTION
      "Path: pbbBridgeGroup.performance.pppoEClient.mibCounters.h2Performance.fInDiscardsNUCast

       64 bit unsigned wrappable counter."
   ::= {pr1645v2PbbBGriMVPPPoEMCH2PEntry 318767104}

pr1645v2PbbBGriMVPPPoEMCH2PInDropFilter OBJECT-TYPE
   SYNTAX      Counter64
   MAX-ACCESS  read-only
   STATUS      current
   DESCRIPTION
      "Path: pbbBridgeGroup.performance.pppoEClient.mibCounters.h2Performance.fInDiscardsFilter

       64 bit unsigned wrappable counter."
   ::= {pr1645v2PbbBGriMVPPPoEMCH2PEntry 385875968}

pr1645v2PbbBGriMVPPPoEMCH2PIfInBandwidth OBJECT-TYPE
   SYNTAX      Integer32
   MAX-ACCESS  read-only
   STATUS      current
   DESCRIPTION
      "Path: pbbBridgeGroup.performance.pppoEClient.mibCounters.h2Performance.ifInBandwidth

       unit name = bps
       formula = 8 * ; 8 /"
   ::= {pr1645v2PbbBGriMVPPPoEMCH2PEntry 268435456}

pr1645v2PbbBGriMVPPPoEMCH2PIfOutOctets OBJECT-TYPE
   SYNTAX      Counter64
   MAX-ACCESS  read-only
   STATUS      current
   DESCRIPTION
      "Path: pbbBridgeGroup.performance.pppoEClient.mibCounters.h2Performance.ifOutOctets

       64 bit unsigned wrappable counter."
   ::= {pr1645v2PbbBGriMVPPPoEMCH2PEntry 167772160}

pr1645v2PbbBGriMVPPPoEMCH2PIfOutUCPkts OBJECT-TYPE
   SYNTAX      Counter64
   MAX-ACCESS  read-only
   STATUS      current
   DESCRIPTION
      "Path: pbbBridgeGroup.performance.pppoEClient.mibCounters.h2Performance.ifOutUcastPkts

       64 bit unsigned wrappable counter."
   ::= {pr1645v2PbbBGriMVPPPoEMCH2PEntry 184549376}

pr1645v2PbbBGriMVPPPoEMCH2PIfOutNUCPkts OBJECT-TYPE
   SYNTAX      Counter64
   MAX-ACCESS  read-only
   STATUS      current
   DESCRIPTION
      "Path: pbbBridgeGroup.performance.pppoEClient.mibCounters.h2Performance.ifOutNUcastPkts

       64 bit unsigned wrappable counter."
   ::= {pr1645v2PbbBGriMVPPPoEMCH2PEntry 201326592}

pr1645v2PbbBGriMVPPPoEMCH2PIfOutBCPkts OBJECT-TYPE
   SYNTAX      Counter64
   MAX-ACCESS  read-only
   STATUS      current
   DESCRIPTION
      "Path: pbbBridgeGroup.performance.pppoEClient.mibCounters.h2Performance.ifOutBcastPkts

       64 bit unsigned wrappable counter."
   ::= {pr1645v2PbbBGriMVPPPoEMCH2PEntry 452984832}

pr1645v2PbbBGriMVPPPoEMCH2PIfOutMCPkts OBJECT-TYPE
   SYNTAX      Counter64
   MAX-ACCESS  read-only
   STATUS      current
   DESCRIPTION
      "Path: pbbBridgeGroup.performance.pppoEClient.mibCounters.h2Performance.ifOutMcastPkts

       64 bit unsigned wrappable counter."
   ::= {pr1645v2PbbBGriMVPPPoEMCH2PEntry 469762048}

pr1645v2PbbBGriMVPPPoEMCH2PIfOutDiscards OBJECT-TYPE
   SYNTAX      Counter64
   MAX-ACCESS  read-only
   STATUS      current
   DESCRIPTION
      "Path: pbbBridgeGroup.performance.pppoEClient.mibCounters.h2Performance.ifOutDiscards

       64 bit unsigned wrappable counter."
   ::= {pr1645v2PbbBGriMVPPPoEMCH2PEntry 218103808}

pr1645v2PbbBGriMVPPPoEMCH2PIfOutErrors OBJECT-TYPE
   SYNTAX      Counter64
   MAX-ACCESS  read-only
   STATUS      current
   DESCRIPTION
      "Path: pbbBridgeGroup.performance.pppoEClient.mibCounters.h2Performance.ifOutErrors

       64 bit unsigned wrappable counter."
   ::= {pr1645v2PbbBGriMVPPPoEMCH2PEntry 234881024}

pr1645v2PbbBGriMVPPPoEMCH2POutDropEx OBJECT-TYPE
   SYNTAX      Counter64
   MAX-ACCESS  read-only
   STATUS      current
   DESCRIPTION
      "Path: pbbBridgeGroup.performance.pppoEClient.mibCounters.h2Performance.ifOutDropLevelExceeded

       64 bit unsigned wrappable counter."
   ::= {pr1645v2PbbBGriMVPPPoEMCH2PEntry 352321536}

pr1645v2PbbBGriMVPPPoEMCH2POutDropNoArp OBJECT-TYPE
   SYNTAX      Counter64
   MAX-ACCESS  read-only
   STATUS      current
   DESCRIPTION
      "Path: pbbBridgeGroup.performance.pppoEClient.mibCounters.h2Performance.ifOutDiscardsNoArp

       64 bit unsigned wrappable counter."
   ::= {pr1645v2PbbBGriMVPPPoEMCH2PEntry 369098752}

pr1645v2PbbBGriMVPPPoEMCH2POutDropFilter OBJECT-TYPE
   SYNTAX      Counter64
   MAX-ACCESS  read-only
   STATUS      current
   DESCRIPTION
      "Path: pbbBridgeGroup.performance.pppoEClient.mibCounters.h2Performance.ifOutDiscardsFilter

       64 bit unsigned wrappable counter."
   ::= {pr1645v2PbbBGriMVPPPoEMCH2PEntry 402653184}

pr1645v2PbbBGriMVPPPoEMCH2PIfOutBandwidth OBJECT-TYPE
   SYNTAX      Integer32
   MAX-ACCESS  read-only
   STATUS      current
   DESCRIPTION
      "Path: pbbBridgeGroup.performance.pppoEClient.mibCounters.h2Performance.ifOutBandwidth

       unit name = bps
       formula = 8 * ; 8 /"
   ::= {pr1645v2PbbBGriMVPPPoEMCH2PEntry 285212672}

pr1645v2PbbBGriMVPPPoEMCH2PIfErrSec OBJECT-TYPE
   SYNTAX      Counter32
   MAX-ACCESS  read-only
   STATUS      current
   DESCRIPTION
      "Path: pbbBridgeGroup.performance.pppoEClient.mibCounters.h2Performance.ifErrSec

       32 bit unsigned wrappable counter."
   ::= {pr1645v2PbbBGriMVPPPoEMCH2PEntry 251658240}

pr1645v2PbbBGriMVPPPoEMCH24P OBJECT-TYPE
   SYNTAX      SEQUENCE OF Pr1645v2PbbBGriMVPPPoEMCH24PEntry
   MAX-ACCESS  not-accessible
   STATUS      current
   DESCRIPTION
      ""
   ::= {pr1645v2PbbBGriMVPPPoE 41615360}

pr1645v2PbbBGriMVPPPoEMCH24PEntry OBJECT-TYPE
   SYNTAX      Pr1645v2PbbBGriMVPPPoEMCH24PEntry
   MAX-ACCESS  not-accessible
   STATUS      current
   DESCRIPTION
      ""
   INDEX      { pr1645v2PbbBGriMVPPPoEMCH24PGlobalIx,
                pr1645v2PbbBGriMVPPPoETableIx,
                pr1645v2PbbBGriMVPPPoEMCH24PTableIx }
   ::= {pr1645v2PbbBGriMVPPPoEMCH24P 1}

Pr1645v2PbbBGriMVPPPoEMCH24PEntry ::=
   SEQUENCE
      {
      pr1645v2PbbBGriMVPPPoEMCH24PGlobalIx
         GlobalIndex,
      pr1645v2PbbBGriMVPPPoEMCH24PTableIx
         TableIndex,
      pr1645v2PbbBGriMVPPPoEMCH24PSysUpTime
         TimeTicks,
      pr1645v2PbbBGriMVPPPoEMCH24PIfUpTime
         TimeTicks,
      pr1645v2PbbBGriMVPPPoEMCH24PIfStatChanges
         Counter32,
      pr1645v2PbbBGriMVPPPoEMCH24PIfInOctets
         Counter64,
      pr1645v2PbbBGriMVPPPoEMCH24PIfInUCPkts
         Counter64,
      pr1645v2PbbBGriMVPPPoEMCH24PIfInNUCPkts
         Counter64,
      pr1645v2PbbBGriMVPPPoEMCH24PIfInBCPkts
         Counter64,
      pr1645v2PbbBGriMVPPPoEMCH24PIfInMCPkts
         Counter64,
      pr1645v2PbbBGriMVPPPoEMCH24PIfInDiscards
         Counter64,
      pr1645v2PbbBGriMVPPPoEMCH24PIfInErrors
         Counter64,
      pr1645v2PbbBGriMVPPPoEMCH24PIfInUnkwn
         Counter64,
      pr1645v2PbbBGriMVPPPoEMCH24PInDropEx
         Counter64,
      pr1645v2PbbBGriMVPPPoEMCH24PInDropNoMac
         Counter64,
      pr1645v2PbbBGriMVPPPoEMCH24PInDropNUCast
         Counter64,
      pr1645v2PbbBGriMVPPPoEMCH24PInDropFilter
         Counter64,
      pr1645v2PbbBGriMVPPPoEMCH24PIfInBandwidth
         Integer32,
      pr1645v2PbbBGriMVPPPoEMCH24PIfOutOctets
         Counter64,
      pr1645v2PbbBGriMVPPPoEMCH24PIfOutUCPkts
         Counter64,
      pr1645v2PbbBGriMVPPPoEMCH24PIfOutNUCPkts
         Counter64,
      pr1645v2PbbBGriMVPPPoEMCH24PIfOutBCPkts
         Counter64,
      pr1645v2PbbBGriMVPPPoEMCH24PIfOutMCPkts
         Counter64,
      pr1645v2PbbBGriMVPPPoEMCH24PIfOutDiscards
         Counter64,
      pr1645v2PbbBGriMVPPPoEMCH24PIfOutErrors
         Counter64,
      pr1645v2PbbBGriMVPPPoEMCH24POutDropEx
         Counter64,
      pr1645v2PbbBGriMVPPPoEMCH24POutDropNoArp
         Counter64,
      pr1645v2PbbBGriMVPPPoEMCH24POutDropFilter
         Counter64,
      pr1645v2PbbBGriMVPPPoEMCH24PIfOutBandwidth
         Integer32,
      pr1645v2PbbBGriMVPPPoEMCH24PIfErrSec
         Counter32
      }

pr1645v2PbbBGriMVPPPoEMCH24PGlobalIx OBJECT-TYPE
   SYNTAX      GlobalIndex
   MAX-ACCESS  not-accessible
   STATUS      current
   DESCRIPTION
      "The value of the tlsCntTreeGlobalIndex of the MANAGED OBJECT."
   ::= {pr1645v2PbbBGriMVPPPoEMCH24PEntry 10}

pr1645v2PbbBGriMVPPPoEMCH24PTableIx OBJECT-TYPE
   SYNTAX      TableIndex
   MAX-ACCESS  not-accessible
   STATUS      current
   DESCRIPTION
      ""
   ::= {pr1645v2PbbBGriMVPPPoEMCH24PEntry 11}

pr1645v2PbbBGriMVPPPoEMCH24PSysUpTime OBJECT-TYPE
   SYNTAX      TimeTicks
   MAX-ACCESS  read-only
   STATUS      current
   DESCRIPTION
      "Path: pbbBridgeGroup.performance.pppoEClient.mibCounters.h24Performance.sysUpTime

       Time in centi-second."
   ::= {pr1645v2PbbBGriMVPPPoEMCH24PEntry 16777216}

pr1645v2PbbBGriMVPPPoEMCH24PIfUpTime OBJECT-TYPE
   SYNTAX      TimeTicks
   MAX-ACCESS  read-only
   STATUS      current
   DESCRIPTION
      "Path: pbbBridgeGroup.performance.pppoEClient.mibCounters.h24Performance.ifUpTime

       Time in centi-second."
   ::= {pr1645v2PbbBGriMVPPPoEMCH24PEntry 33554432}

pr1645v2PbbBGriMVPPPoEMCH24PIfStatChanges OBJECT-TYPE
   SYNTAX      Counter32
   MAX-ACCESS  read-only
   STATUS      current
   DESCRIPTION
      "Path: pbbBridgeGroup.performance.pppoEClient.mibCounters.h24Performance.ifStatusChanges

       32 bit unsigned wrappable counter."
   ::= {pr1645v2PbbBGriMVPPPoEMCH24PEntry 50331648}

pr1645v2PbbBGriMVPPPoEMCH24PIfInOctets OBJECT-TYPE
   SYNTAX      Counter64
   MAX-ACCESS  read-only
   STATUS      current
   DESCRIPTION
      "Path: pbbBridgeGroup.performance.pppoEClient.mibCounters.h24Performance.ifInOctets

       64 bit unsigned wrappable counter."
   ::= {pr1645v2PbbBGriMVPPPoEMCH24PEntry 67108864}

pr1645v2PbbBGriMVPPPoEMCH24PIfInUCPkts OBJECT-TYPE
   SYNTAX      Counter64
   MAX-ACCESS  read-only
   STATUS      current
   DESCRIPTION
      "Path: pbbBridgeGroup.performance.pppoEClient.mibCounters.h24Performance.ifInUcastPkts

       64 bit unsigned wrappable counter."
   ::= {pr1645v2PbbBGriMVPPPoEMCH24PEntry 83886080}

pr1645v2PbbBGriMVPPPoEMCH24PIfInNUCPkts OBJECT-TYPE
   SYNTAX      Counter64
   MAX-ACCESS  read-only
   STATUS      current
   DESCRIPTION
      "Path: pbbBridgeGroup.performance.pppoEClient.mibCounters.h24Performance.ifInNUcastPkts

       64 bit unsigned wrappable counter."
   ::= {pr1645v2PbbBGriMVPPPoEMCH24PEntry 100663296}

pr1645v2PbbBGriMVPPPoEMCH24PIfInBCPkts OBJECT-TYPE
   SYNTAX      Counter64
   MAX-ACCESS  read-only
   STATUS      current
   DESCRIPTION
      "Path: pbbBridgeGroup.performance.pppoEClient.mibCounters.h24Performance.ifInBcastPkts

       64 bit unsigned wrappable counter."
   ::= {pr1645v2PbbBGriMVPPPoEMCH24PEntry 419430400}

pr1645v2PbbBGriMVPPPoEMCH24PIfInMCPkts OBJECT-TYPE
   SYNTAX      Counter64
   MAX-ACCESS  read-only
   STATUS      current
   DESCRIPTION
      "Path: pbbBridgeGroup.performance.pppoEClient.mibCounters.h24Performance.ifInMcastPkts

       64 bit unsigned wrappable counter."
   ::= {pr1645v2PbbBGriMVPPPoEMCH24PEntry 436207616}

pr1645v2PbbBGriMVPPPoEMCH24PIfInDiscards OBJECT-TYPE
   SYNTAX      Counter64
   MAX-ACCESS  read-only
   STATUS      current
   DESCRIPTION
      "Path: pbbBridgeGroup.performance.pppoEClient.mibCounters.h24Performance.ifInDiscards

       64 bit unsigned wrappable counter."
   ::= {pr1645v2PbbBGriMVPPPoEMCH24PEntry 117440512}

pr1645v2PbbBGriMVPPPoEMCH24PIfInErrors OBJECT-TYPE
   SYNTAX      Counter64
   MAX-ACCESS  read-only
   STATUS      current
   DESCRIPTION
      "Path: pbbBridgeGroup.performance.pppoEClient.mibCounters.h24Performance.ifInErrors

       64 bit unsigned wrappable counter."
   ::= {pr1645v2PbbBGriMVPPPoEMCH24PEntry 134217728}

pr1645v2PbbBGriMVPPPoEMCH24PIfInUnkwn OBJECT-TYPE
   SYNTAX      Counter64
   MAX-ACCESS  read-only
   STATUS      current
   DESCRIPTION
      "Path: pbbBridgeGroup.performance.pppoEClient.mibCounters.h24Performance.ifInUnknownProtos

       64 bit unsigned wrappable counter."
   ::= {pr1645v2PbbBGriMVPPPoEMCH24PEntry 150994944}

pr1645v2PbbBGriMVPPPoEMCH24PInDropEx OBJECT-TYPE
   SYNTAX      Counter64
   MAX-ACCESS  read-only
   STATUS      current
   DESCRIPTION
      "Path: pbbBridgeGroup.performance.pppoEClient.mibCounters.h24Performance.ifInDropLevelExceeded

       64 bit unsigned wrappable counter."
   ::= {pr1645v2PbbBGriMVPPPoEMCH24PEntry 335544320}

pr1645v2PbbBGriMVPPPoEMCH24PInDropNoMac OBJECT-TYPE
   SYNTAX      Counter64
   MAX-ACCESS  read-only
   STATUS      current
   DESCRIPTION
      "Path: pbbBridgeGroup.performance.pppoEClient.mibCounters.h24Performance.fInDiscardsNoMacFit

       64 bit unsigned wrappable counter."
   ::= {pr1645v2PbbBGriMVPPPoEMCH24PEntry 301989888}

pr1645v2PbbBGriMVPPPoEMCH24PInDropNUCast OBJECT-TYPE
   SYNTAX      Counter64
   MAX-ACCESS  read-only
   STATUS      current
   DESCRIPTION
      "Path: pbbBridgeGroup.performance.pppoEClient.mibCounters.h24Performance.fInDiscardsNUCast

       64 bit unsigned wrappable counter."
   ::= {pr1645v2PbbBGriMVPPPoEMCH24PEntry 318767104}

pr1645v2PbbBGriMVPPPoEMCH24PInDropFilter OBJECT-TYPE
   SYNTAX      Counter64
   MAX-ACCESS  read-only
   STATUS      current
   DESCRIPTION
      "Path: pbbBridgeGroup.performance.pppoEClient.mibCounters.h24Performance.fInDiscardsFilter

       64 bit unsigned wrappable counter."
   ::= {pr1645v2PbbBGriMVPPPoEMCH24PEntry 385875968}

pr1645v2PbbBGriMVPPPoEMCH24PIfInBandwidth OBJECT-TYPE
   SYNTAX      Integer32
   MAX-ACCESS  read-only
   STATUS      current
   DESCRIPTION
      "Path: pbbBridgeGroup.performance.pppoEClient.mibCounters.h24Performance.ifInBandwidth

       unit name = bps
       formula = 8 * ; 8 /"
   ::= {pr1645v2PbbBGriMVPPPoEMCH24PEntry 268435456}

pr1645v2PbbBGriMVPPPoEMCH24PIfOutOctets OBJECT-TYPE
   SYNTAX      Counter64
   MAX-ACCESS  read-only
   STATUS      current
   DESCRIPTION
      "Path: pbbBridgeGroup.performance.pppoEClient.mibCounters.h24Performance.ifOutOctets

       64 bit unsigned wrappable counter."
   ::= {pr1645v2PbbBGriMVPPPoEMCH24PEntry 167772160}

pr1645v2PbbBGriMVPPPoEMCH24PIfOutUCPkts OBJECT-TYPE
   SYNTAX      Counter64
   MAX-ACCESS  read-only
   STATUS      current
   DESCRIPTION
      "Path: pbbBridgeGroup.performance.pppoEClient.mibCounters.h24Performance.ifOutUcastPkts

       64 bit unsigned wrappable counter."
   ::= {pr1645v2PbbBGriMVPPPoEMCH24PEntry 184549376}

pr1645v2PbbBGriMVPPPoEMCH24PIfOutNUCPkts OBJECT-TYPE
   SYNTAX      Counter64
   MAX-ACCESS  read-only
   STATUS      current
   DESCRIPTION
      "Path: pbbBridgeGroup.performance.pppoEClient.mibCounters.h24Performance.ifOutNUcastPkts

       64 bit unsigned wrappable counter."
   ::= {pr1645v2PbbBGriMVPPPoEMCH24PEntry 201326592}

pr1645v2PbbBGriMVPPPoEMCH24PIfOutBCPkts OBJECT-TYPE
   SYNTAX      Counter64
   MAX-ACCESS  read-only
   STATUS      current
   DESCRIPTION
      "Path: pbbBridgeGroup.performance.pppoEClient.mibCounters.h24Performance.ifOutBcastPkts

       64 bit unsigned wrappable counter."
   ::= {pr1645v2PbbBGriMVPPPoEMCH24PEntry 452984832}

pr1645v2PbbBGriMVPPPoEMCH24PIfOutMCPkts OBJECT-TYPE
   SYNTAX      Counter64
   MAX-ACCESS  read-only
   STATUS      current
   DESCRIPTION
      "Path: pbbBridgeGroup.performance.pppoEClient.mibCounters.h24Performance.ifOutMcastPkts

       64 bit unsigned wrappable counter."
   ::= {pr1645v2PbbBGriMVPPPoEMCH24PEntry 469762048}

pr1645v2PbbBGriMVPPPoEMCH24PIfOutDiscards OBJECT-TYPE
   SYNTAX      Counter64
   MAX-ACCESS  read-only
   STATUS      current
   DESCRIPTION
      "Path: pbbBridgeGroup.performance.pppoEClient.mibCounters.h24Performance.ifOutDiscards

       64 bit unsigned wrappable counter."
   ::= {pr1645v2PbbBGriMVPPPoEMCH24PEntry 218103808}

pr1645v2PbbBGriMVPPPoEMCH24PIfOutErrors OBJECT-TYPE
   SYNTAX      Counter64
   MAX-ACCESS  read-only
   STATUS      current
   DESCRIPTION
      "Path: pbbBridgeGroup.performance.pppoEClient.mibCounters.h24Performance.ifOutErrors

       64 bit unsigned wrappable counter."
   ::= {pr1645v2PbbBGriMVPPPoEMCH24PEntry 234881024}

pr1645v2PbbBGriMVPPPoEMCH24POutDropEx OBJECT-TYPE
   SYNTAX      Counter64
   MAX-ACCESS  read-only
   STATUS      current
   DESCRIPTION
      "Path: pbbBridgeGroup.performance.pppoEClient.mibCounters.h24Performance.ifOutDropLevelExceeded

       64 bit unsigned wrappable counter."
   ::= {pr1645v2PbbBGriMVPPPoEMCH24PEntry 352321536}

pr1645v2PbbBGriMVPPPoEMCH24POutDropNoArp OBJECT-TYPE
   SYNTAX      Counter64
   MAX-ACCESS  read-only
   STATUS      current
   DESCRIPTION
      "Path: pbbBridgeGroup.performance.pppoEClient.mibCounters.h24Performance.ifOutDiscardsNoArp

       64 bit unsigned wrappable counter."
   ::= {pr1645v2PbbBGriMVPPPoEMCH24PEntry 369098752}

pr1645v2PbbBGriMVPPPoEMCH24POutDropFilter OBJECT-TYPE
   SYNTAX      Counter64
   MAX-ACCESS  read-only
   STATUS      current
   DESCRIPTION
      "Path: pbbBridgeGroup.performance.pppoEClient.mibCounters.h24Performance.ifOutDiscardsFilter

       64 bit unsigned wrappable counter."
   ::= {pr1645v2PbbBGriMVPPPoEMCH24PEntry 402653184}

pr1645v2PbbBGriMVPPPoEMCH24PIfOutBandwidth OBJECT-TYPE
   SYNTAX      Integer32
   MAX-ACCESS  read-only
   STATUS      current
   DESCRIPTION
      "Path: pbbBridgeGroup.performance.pppoEClient.mibCounters.h24Performance.ifOutBandwidth

       unit name = bps
       formula = 8 * ; 8 /"
   ::= {pr1645v2PbbBGriMVPPPoEMCH24PEntry 285212672}

pr1645v2PbbBGriMVPPPoEMCH24PIfErrSec OBJECT-TYPE
   SYNTAX      Counter32
   MAX-ACCESS  read-only
   STATUS      current
   DESCRIPTION
      "Path: pbbBridgeGroup.performance.pppoEClient.mibCounters.h24Performance.ifErrSec

       32 bit unsigned wrappable counter."
   ::= {pr1645v2PbbBGriMVPPPoEMCH24PEntry 251658240}

pr1645v2PbbBGriMVPPPoEMCD7P OBJECT-TYPE
   SYNTAX      SEQUENCE OF Pr1645v2PbbBGriMVPPPoEMCD7PEntry
   MAX-ACCESS  not-accessible
   STATUS      current
   DESCRIPTION
      ""
   ::= {pr1645v2PbbBGriMVPPPoE 41680896}

pr1645v2PbbBGriMVPPPoEMCD7PEntry OBJECT-TYPE
   SYNTAX      Pr1645v2PbbBGriMVPPPoEMCD7PEntry
   MAX-ACCESS  not-accessible
   STATUS      current
   DESCRIPTION
      ""
   INDEX      { pr1645v2PbbBGriMVPPPoEMCD7PGlobalIx,
                pr1645v2PbbBGriMVPPPoETableIx,
                pr1645v2PbbBGriMVPPPoEMCD7PTableIx }
   ::= {pr1645v2PbbBGriMVPPPoEMCD7P 1}

Pr1645v2PbbBGriMVPPPoEMCD7PEntry ::=
   SEQUENCE
      {
      pr1645v2PbbBGriMVPPPoEMCD7PGlobalIx
         GlobalIndex,
      pr1645v2PbbBGriMVPPPoEMCD7PTableIx
         TableIndex,
      pr1645v2PbbBGriMVPPPoEMCD7PSysUpTime
         TimeTicks,
      pr1645v2PbbBGriMVPPPoEMCD7PIfUpTime
         TimeTicks,
      pr1645v2PbbBGriMVPPPoEMCD7PIfStatChanges
         Counter32,
      pr1645v2PbbBGriMVPPPoEMCD7PIfInOctets
         Counter64,
      pr1645v2PbbBGriMVPPPoEMCD7PIfInUCPkts
         Counter64,
      pr1645v2PbbBGriMVPPPoEMCD7PIfInNUCPkts
         Counter64,
      pr1645v2PbbBGriMVPPPoEMCD7PIfInBCPkts
         Counter64,
      pr1645v2PbbBGriMVPPPoEMCD7PIfInMCPkts
         Counter64,
      pr1645v2PbbBGriMVPPPoEMCD7PIfInDiscards
         Counter64,
      pr1645v2PbbBGriMVPPPoEMCD7PIfInErrors
         Counter64,
      pr1645v2PbbBGriMVPPPoEMCD7PIfInUnkwn
         Counter64,
      pr1645v2PbbBGriMVPPPoEMCD7PInDropEx
         Counter64,
      pr1645v2PbbBGriMVPPPoEMCD7PInDropNoMac
         Counter64,
      pr1645v2PbbBGriMVPPPoEMCD7PInDropNUCast
         Counter64,
      pr1645v2PbbBGriMVPPPoEMCD7PInDropFilter
         Counter64,
      pr1645v2PbbBGriMVPPPoEMCD7PIfInBandwidth
         Integer32,
      pr1645v2PbbBGriMVPPPoEMCD7PIfOutOctets
         Counter64,
      pr1645v2PbbBGriMVPPPoEMCD7PIfOutUCPkts
         Counter64,
      pr1645v2PbbBGriMVPPPoEMCD7PIfOutNUCPkts
         Counter64,
      pr1645v2PbbBGriMVPPPoEMCD7PIfOutBCPkts
         Counter64,
      pr1645v2PbbBGriMVPPPoEMCD7PIfOutMCPkts
         Counter64,
      pr1645v2PbbBGriMVPPPoEMCD7PIfOutDiscards
         Counter64,
      pr1645v2PbbBGriMVPPPoEMCD7PIfOutErrors
         Counter64,
      pr1645v2PbbBGriMVPPPoEMCD7POutDropEx
         Counter64,
      pr1645v2PbbBGriMVPPPoEMCD7POutDropNoArp
         Counter64,
      pr1645v2PbbBGriMVPPPoEMCD7POutDropFilter
         Counter64,
      pr1645v2PbbBGriMVPPPoEMCD7PIfOutBandwidth
         Integer32,
      pr1645v2PbbBGriMVPPPoEMCD7PIfErrSec
         Counter32
      }

pr1645v2PbbBGriMVPPPoEMCD7PGlobalIx OBJECT-TYPE
   SYNTAX      GlobalIndex
   MAX-ACCESS  not-accessible
   STATUS      current
   DESCRIPTION
      "The value of the tlsCntTreeGlobalIndex of the MANAGED OBJECT."
   ::= {pr1645v2PbbBGriMVPPPoEMCD7PEntry 10}

pr1645v2PbbBGriMVPPPoEMCD7PTableIx OBJECT-TYPE
   SYNTAX      TableIndex
   MAX-ACCESS  not-accessible
   STATUS      current
   DESCRIPTION
      ""
   ::= {pr1645v2PbbBGriMVPPPoEMCD7PEntry 11}

pr1645v2PbbBGriMVPPPoEMCD7PSysUpTime OBJECT-TYPE
   SYNTAX      TimeTicks
   MAX-ACCESS  read-only
   STATUS      current
   DESCRIPTION
      "Path: pbbBridgeGroup.performance.pppoEClient.mibCounters.d7Performance.sysUpTime

       Time in centi-second."
   ::= {pr1645v2PbbBGriMVPPPoEMCD7PEntry 16777216}

pr1645v2PbbBGriMVPPPoEMCD7PIfUpTime OBJECT-TYPE
   SYNTAX      TimeTicks
   MAX-ACCESS  read-only
   STATUS      current
   DESCRIPTION
      "Path: pbbBridgeGroup.performance.pppoEClient.mibCounters.d7Performance.ifUpTime

       Time in centi-second."
   ::= {pr1645v2PbbBGriMVPPPoEMCD7PEntry 33554432}

pr1645v2PbbBGriMVPPPoEMCD7PIfStatChanges OBJECT-TYPE
   SYNTAX      Counter32
   MAX-ACCESS  read-only
   STATUS      current
   DESCRIPTION
      "Path: pbbBridgeGroup.performance.pppoEClient.mibCounters.d7Performance.ifStatusChanges

       32 bit unsigned wrappable counter."
   ::= {pr1645v2PbbBGriMVPPPoEMCD7PEntry 50331648}

pr1645v2PbbBGriMVPPPoEMCD7PIfInOctets OBJECT-TYPE
   SYNTAX      Counter64
   MAX-ACCESS  read-only
   STATUS      current
   DESCRIPTION
      "Path: pbbBridgeGroup.performance.pppoEClient.mibCounters.d7Performance.ifInOctets

       64 bit unsigned wrappable counter."
   ::= {pr1645v2PbbBGriMVPPPoEMCD7PEntry 67108864}

pr1645v2PbbBGriMVPPPoEMCD7PIfInUCPkts OBJECT-TYPE
   SYNTAX      Counter64
   MAX-ACCESS  read-only
   STATUS      current
   DESCRIPTION
      "Path: pbbBridgeGroup.performance.pppoEClient.mibCounters.d7Performance.ifInUcastPkts

       64 bit unsigned wrappable counter."
   ::= {pr1645v2PbbBGriMVPPPoEMCD7PEntry 83886080}

pr1645v2PbbBGriMVPPPoEMCD7PIfInNUCPkts OBJECT-TYPE
   SYNTAX      Counter64
   MAX-ACCESS  read-only
   STATUS      current
   DESCRIPTION
      "Path: pbbBridgeGroup.performance.pppoEClient.mibCounters.d7Performance.ifInNUcastPkts

       64 bit unsigned wrappable counter."
   ::= {pr1645v2PbbBGriMVPPPoEMCD7PEntry 100663296}

pr1645v2PbbBGriMVPPPoEMCD7PIfInBCPkts OBJECT-TYPE
   SYNTAX      Counter64
   MAX-ACCESS  read-only
   STATUS      current
   DESCRIPTION
      "Path: pbbBridgeGroup.performance.pppoEClient.mibCounters.d7Performance.ifInBcastPkts

       64 bit unsigned wrappable counter."
   ::= {pr1645v2PbbBGriMVPPPoEMCD7PEntry 419430400}

pr1645v2PbbBGriMVPPPoEMCD7PIfInMCPkts OBJECT-TYPE
   SYNTAX      Counter64
   MAX-ACCESS  read-only
   STATUS      current
   DESCRIPTION
      "Path: pbbBridgeGroup.performance.pppoEClient.mibCounters.d7Performance.ifInMcastPkts

       64 bit unsigned wrappable counter."
   ::= {pr1645v2PbbBGriMVPPPoEMCD7PEntry 436207616}

pr1645v2PbbBGriMVPPPoEMCD7PIfInDiscards OBJECT-TYPE
   SYNTAX      Counter64
   MAX-ACCESS  read-only
   STATUS      current
   DESCRIPTION
      "Path: pbbBridgeGroup.performance.pppoEClient.mibCounters.d7Performance.ifInDiscards

       64 bit unsigned wrappable counter."
   ::= {pr1645v2PbbBGriMVPPPoEMCD7PEntry 117440512}

pr1645v2PbbBGriMVPPPoEMCD7PIfInErrors OBJECT-TYPE
   SYNTAX      Counter64
   MAX-ACCESS  read-only
   STATUS      current
   DESCRIPTION
      "Path: pbbBridgeGroup.performance.pppoEClient.mibCounters.d7Performance.ifInErrors

       64 bit unsigned wrappable counter."
   ::= {pr1645v2PbbBGriMVPPPoEMCD7PEntry 134217728}

pr1645v2PbbBGriMVPPPoEMCD7PIfInUnkwn OBJECT-TYPE
   SYNTAX      Counter64
   MAX-ACCESS  read-only
   STATUS      current
   DESCRIPTION
      "Path: pbbBridgeGroup.performance.pppoEClient.mibCounters.d7Performance.ifInUnknownProtos

       64 bit unsigned wrappable counter."
   ::= {pr1645v2PbbBGriMVPPPoEMCD7PEntry 150994944}

pr1645v2PbbBGriMVPPPoEMCD7PInDropEx OBJECT-TYPE
   SYNTAX      Counter64
   MAX-ACCESS  read-only
   STATUS      current
   DESCRIPTION
      "Path: pbbBridgeGroup.performance.pppoEClient.mibCounters.d7Performance.ifInDropLevelExceeded

       64 bit unsigned wrappable counter."
   ::= {pr1645v2PbbBGriMVPPPoEMCD7PEntry 335544320}

pr1645v2PbbBGriMVPPPoEMCD7PInDropNoMac OBJECT-TYPE
   SYNTAX      Counter64
   MAX-ACCESS  read-only
   STATUS      current
   DESCRIPTION
      "Path: pbbBridgeGroup.performance.pppoEClient.mibCounters.d7Performance.fInDiscardsNoMacFit

       64 bit unsigned wrappable counter."
   ::= {pr1645v2PbbBGriMVPPPoEMCD7PEntry 301989888}

pr1645v2PbbBGriMVPPPoEMCD7PInDropNUCast OBJECT-TYPE
   SYNTAX      Counter64
   MAX-ACCESS  read-only
   STATUS      current
   DESCRIPTION
      "Path: pbbBridgeGroup.performance.pppoEClient.mibCounters.d7Performance.fInDiscardsNUCast

       64 bit unsigned wrappable counter."
   ::= {pr1645v2PbbBGriMVPPPoEMCD7PEntry 318767104}

pr1645v2PbbBGriMVPPPoEMCD7PInDropFilter OBJECT-TYPE
   SYNTAX      Counter64
   MAX-ACCESS  read-only
   STATUS      current
   DESCRIPTION
      "Path: pbbBridgeGroup.performance.pppoEClient.mibCounters.d7Performance.fInDiscardsFilter

       64 bit unsigned wrappable counter."
   ::= {pr1645v2PbbBGriMVPPPoEMCD7PEntry 385875968}

pr1645v2PbbBGriMVPPPoEMCD7PIfInBandwidth OBJECT-TYPE
   SYNTAX      Integer32
   MAX-ACCESS  read-only
   STATUS      current
   DESCRIPTION
      "Path: pbbBridgeGroup.performance.pppoEClient.mibCounters.d7Performance.ifInBandwidth

       unit name = bps
       formula = 8 * ; 8 /"
   ::= {pr1645v2PbbBGriMVPPPoEMCD7PEntry 268435456}

pr1645v2PbbBGriMVPPPoEMCD7PIfOutOctets OBJECT-TYPE
   SYNTAX      Counter64
   MAX-ACCESS  read-only
   STATUS      current
   DESCRIPTION
      "Path: pbbBridgeGroup.performance.pppoEClient.mibCounters.d7Performance.ifOutOctets

       64 bit unsigned wrappable counter."
   ::= {pr1645v2PbbBGriMVPPPoEMCD7PEntry 167772160}

pr1645v2PbbBGriMVPPPoEMCD7PIfOutUCPkts OBJECT-TYPE
   SYNTAX      Counter64
   MAX-ACCESS  read-only
   STATUS      current
   DESCRIPTION
      "Path: pbbBridgeGroup.performance.pppoEClient.mibCounters.d7Performance.ifOutUcastPkts

       64 bit unsigned wrappable counter."
   ::= {pr1645v2PbbBGriMVPPPoEMCD7PEntry 184549376}

pr1645v2PbbBGriMVPPPoEMCD7PIfOutNUCPkts OBJECT-TYPE
   SYNTAX      Counter64
   MAX-ACCESS  read-only
   STATUS      current
   DESCRIPTION
      "Path: pbbBridgeGroup.performance.pppoEClient.mibCounters.d7Performance.ifOutNUcastPkts

       64 bit unsigned wrappable counter."
   ::= {pr1645v2PbbBGriMVPPPoEMCD7PEntry 201326592}

pr1645v2PbbBGriMVPPPoEMCD7PIfOutBCPkts OBJECT-TYPE
   SYNTAX      Counter64
   MAX-ACCESS  read-only
   STATUS      current
   DESCRIPTION
      "Path: pbbBridgeGroup.performance.pppoEClient.mibCounters.d7Performance.ifOutBcastPkts

       64 bit unsigned wrappable counter."
   ::= {pr1645v2PbbBGriMVPPPoEMCD7PEntry 452984832}

pr1645v2PbbBGriMVPPPoEMCD7PIfOutMCPkts OBJECT-TYPE
   SYNTAX      Counter64
   MAX-ACCESS  read-only
   STATUS      current
   DESCRIPTION
      "Path: pbbBridgeGroup.performance.pppoEClient.mibCounters.d7Performance.ifOutMcastPkts

       64 bit unsigned wrappable counter."
   ::= {pr1645v2PbbBGriMVPPPoEMCD7PEntry 469762048}

pr1645v2PbbBGriMVPPPoEMCD7PIfOutDiscards OBJECT-TYPE
   SYNTAX      Counter64
   MAX-ACCESS  read-only
   STATUS      current
   DESCRIPTION
      "Path: pbbBridgeGroup.performance.pppoEClient.mibCounters.d7Performance.ifOutDiscards

       64 bit unsigned wrappable counter."
   ::= {pr1645v2PbbBGriMVPPPoEMCD7PEntry 218103808}

pr1645v2PbbBGriMVPPPoEMCD7PIfOutErrors OBJECT-TYPE
   SYNTAX      Counter64
   MAX-ACCESS  read-only
   STATUS      current
   DESCRIPTION
      "Path: pbbBridgeGroup.performance.pppoEClient.mibCounters.d7Performance.ifOutErrors

       64 bit unsigned wrappable counter."
   ::= {pr1645v2PbbBGriMVPPPoEMCD7PEntry 234881024}

pr1645v2PbbBGriMVPPPoEMCD7POutDropEx OBJECT-TYPE
   SYNTAX      Counter64
   MAX-ACCESS  read-only
   STATUS      current
   DESCRIPTION
      "Path: pbbBridgeGroup.performance.pppoEClient.mibCounters.d7Performance.ifOutDropLevelExceeded

       64 bit unsigned wrappable counter."
   ::= {pr1645v2PbbBGriMVPPPoEMCD7PEntry 352321536}

pr1645v2PbbBGriMVPPPoEMCD7POutDropNoArp OBJECT-TYPE
   SYNTAX      Counter64
   MAX-ACCESS  read-only
   STATUS      current
   DESCRIPTION
      "Path: pbbBridgeGroup.performance.pppoEClient.mibCounters.d7Performance.ifOutDiscardsNoArp

       64 bit unsigned wrappable counter."
   ::= {pr1645v2PbbBGriMVPPPoEMCD7PEntry 369098752}

pr1645v2PbbBGriMVPPPoEMCD7POutDropFilter OBJECT-TYPE
   SYNTAX      Counter64
   MAX-ACCESS  read-only
   STATUS      current
   DESCRIPTION
      "Path: pbbBridgeGroup.performance.pppoEClient.mibCounters.d7Performance.ifOutDiscardsFilter

       64 bit unsigned wrappable counter."
   ::= {pr1645v2PbbBGriMVPPPoEMCD7PEntry 402653184}

pr1645v2PbbBGriMVPPPoEMCD7PIfOutBandwidth OBJECT-TYPE
   SYNTAX      Integer32
   MAX-ACCESS  read-only
   STATUS      current
   DESCRIPTION
      "Path: pbbBridgeGroup.performance.pppoEClient.mibCounters.d7Performance.ifOutBandwidth

       unit name = bps
       formula = 8 * ; 8 /"
   ::= {pr1645v2PbbBGriMVPPPoEMCD7PEntry 285212672}

pr1645v2PbbBGriMVPPPoEMCD7PIfErrSec OBJECT-TYPE
   SYNTAX      Counter32
   MAX-ACCESS  read-only
   STATUS      current
   DESCRIPTION
      "Path: pbbBridgeGroup.performance.pppoEClient.mibCounters.d7Performance.ifErrSec

       32 bit unsigned wrappable counter."
   ::= {pr1645v2PbbBGriMVPPPoEMCD7PEntry 251658240}


pr1645v2PbbBGriMVBridgeCache OBJECT IDENTIFIER ::= {pr1645v2PbbBGriMV 6}

pr1645v2PbbBGriMVBridgeCacheSSCTable OBJECT-TYPE
   SYNTAX      SEQUENCE OF Pr1645v2PbbBGriMVBridgeCacheEntry
   MAX-ACCESS  not-accessible
   STATUS      current
   DESCRIPTION
      "cache entry performance"
   ::= {pr1645v2PbbBGriMVBridgeCache 1}

pr1645v2PbbBGriMVBridgeCacheEntry OBJECT-TYPE
   SYNTAX      Pr1645v2PbbBGriMVBridgeCacheEntry
   MAX-ACCESS  not-accessible
   STATUS      current
   DESCRIPTION
      ""
   INDEX      { pr1645v2PbbBGriMVBridgeCacheGlobalIx,
                pr1645v2PbbBGriMVBridgeCacheTableIx }
   ::= {pr1645v2PbbBGriMVBridgeCacheSSCTable 1}

Pr1645v2PbbBGriMVBridgeCacheEntry ::=
   SEQUENCE
      {
      pr1645v2PbbBGriMVBridgeCacheGlobalIx
         GlobalIndex,
      pr1645v2PbbBGriMVBridgeCacheTableIx
         TableIndex,
      pr1645v2PbbBGriMVBridgeCacheIf
         DisplayString,
      pr1645v2PbbBGriMVBridgeCacheMacAddress
         OCTET STRING,
      pr1645v2PbbBGriMVBridgeCacheBMacAddress
         OCTET STRING,
      pr1645v2PbbBGriMVBridgeCacheIsid
         Integer32,
      pr1645v2PbbBGriMVBridgeCacheTpid
         INTEGER,
      pr1645v2PbbBGriMVBridgeCacheVlanId
         INTEGER,
      pr1645v2PbbBGriMVBridgeCacheTpid2
         INTEGER,
      pr1645v2PbbBGriMVBridgeCacheVlanId2
         INTEGER,
      pr1645v2PbbBGriMVBridgeCacheType
         INTEGER,
      pr1645v2PbbBGriMVBridgeCacheRxPkts
         Counter32,
      pr1645v2PbbBGriMVBridgeCacheTxPkts
         Counter32,
      pr1645v2PbbBGriMVBridgeCacheStatViols
         Counter32,
      pr1645v2PbbBGriMVBridgeCacheRelearns
         Counter32,
      pr1645v2PbbBGriMVBridgeCacheRelearnDrops
         Counter32,
      pr1645v2PbbBGriMVBridgeCacheBMacRelearns
         Counter32
      }

pr1645v2PbbBGriMVBridgeCacheGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgeCacheEntry 10}

pr1645v2PbbBGriMVBridgeCacheTableIx OBJECT-TYPE
   SYNTAX      TableIndex
   MAX-ACCESS  not-accessible
   STATUS      current
   DESCRIPTION
      ""
   ::= {pr1645v2PbbBGriMVBridgeCacheEntry 11}

pr1645v2PbbBGriMVBridgeCacheIf OBJECT-TYPE
   SYNTAX      DisplayString
   MAX-ACCESS  read-only
   STATUS      current
   DESCRIPTION
      "Path: pbbBridgeGroup.performance.bridgeCache.interface"
   ::= {pr1645v2PbbBGriMVBridgeCacheEntry 16777216}

pr1645v2PbbBGriMVBridgeCacheMacAddress OBJECT-TYPE
   SYNTAX      OCTET STRING
   MAX-ACCESS  read-only
   STATUS      current
   DESCRIPTION
      "Path: pbbBridgeGroup.performance.bridgeCache.macAddress

       MAC address."
   ::= {pr1645v2PbbBGriMVBridgeCacheEntry 33554432}

pr1645v2PbbBGriMVBridgeCacheBMacAddress OBJECT-TYPE
   SYNTAX      OCTET STRING
   MAX-ACCESS  read-only
   STATUS      current
   DESCRIPTION
      "Path: pbbBridgeGroup.performance.bridgeCache.bMacAddress

       MAC address."
   ::= {pr1645v2PbbBGriMVBridgeCacheEntry 167772160}

pr1645v2PbbBGriMVBridgeCacheIsid OBJECT-TYPE
   SYNTAX      Integer32
   MAX-ACCESS  read-only
   STATUS      current
   DESCRIPTION
      "Path: pbbBridgeGroup.performance.bridgeCache.isid"
   ::= {pr1645v2PbbBGriMVBridgeCacheEntry 201326592}

pr1645v2PbbBGriMVBridgeCacheTpid OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: pbbBridgeGroup.performance.bridgeCache.tpid

       Possibilities:
               untagged   (0)
               dot1q   (33024)
               dot1ad   (34984)
               group   (65534)
               notUsed   (65535)
               dot1qOrDot1ad   (65536)"
   ::= {pr1645v2PbbBGriMVBridgeCacheEntry 335544320}

pr1645v2PbbBGriMVBridgeCacheVlanId OBJECT-TYPE
   SYNTAX      INTEGER
               {
               undefined (-1)
               }
   MAX-ACCESS  read-only
   STATUS      current
   DESCRIPTION
      "Path: pbbBridgeGroup.performance.bridgeCache.vlanId

       Possibilities:
               undefined   (-1)"
   ::= {pr1645v2PbbBGriMVBridgeCacheEntry 50331648}

pr1645v2PbbBGriMVBridgeCacheTpid2 OBJECT-TYPE
   SYNTAX      INTEGER
               {
               untagged (0),
               dot1q (33024),
               dot1ad (34984),
               group (65534),
               notUsed (65535),
               dot1qOrDot1ad (65536)
               }
   MAX-ACCESS  read-only
   STATUS      current
   DESCRIPTION
      "Path: pbbBridgeGroup.performance.bridgeCache.tpid2

       Possibilities:
               untagged   (0)
               dot1q   (33024)
               dot1ad   (34984)
               group   (65534)
               notUsed   (65535)
               dot1qOrDot1ad   (65536)"
   ::= {pr1645v2PbbBGriMVBridgeCacheEntry 369098752}

pr1645v2PbbBGriMVBridgeCacheVlanId2 OBJECT-TYPE
   SYNTAX      INTEGER
               {
               undefined (-1)
               }
   MAX-ACCESS  read-only
   STATUS      current
   DESCRIPTION
      "Path: pbbBridgeGroup.performance.bridgeCache.vlanId2

       Possibilities:
               undefined   (-1)"
   ::= {pr1645v2PbbBGriMVBridgeCacheEntry 385875968}

pr1645v2PbbBGriMVBridgeCacheType OBJECT-TYPE
   SYNTAX      INTEGER
               {
               static (0),
               dynamic (1),
               tester (2),
               fastFlood (3)
               }
   MAX-ACCESS  read-only
   STATUS      current
   DESCRIPTION
      "Path: pbbBridgeGroup.performance.bridgeCache.type

       Possibilities:
               static   (0)
               dynamic   (1)
               tester   (2)
               fastFlood   (3)"
   ::= {pr1645v2PbbBGriMVBridgeCacheEntry 352321536}

pr1645v2PbbBGriMVBridgeCacheRxPkts OBJECT-TYPE
   SYNTAX      Counter32
   MAX-ACCESS  read-only
   STATUS      current
   DESCRIPTION
      "Path: pbbBridgeGroup.performance.bridgeCache.rxPkts

       32 bit unsigned wrappable counter."
   ::= {pr1645v2PbbBGriMVBridgeCacheEntry 83886080}

pr1645v2PbbBGriMVBridgeCacheTxPkts OBJECT-TYPE
   SYNTAX      Counter32
   MAX-ACCESS  read-only
   STATUS      current
   DESCRIPTION
      "Path: pbbBridgeGroup.performance.bridgeCache.txPkts

       32 bit unsigned wrappable counter."
   ::= {pr1645v2PbbBGriMVBridgeCacheEntry 100663296}

pr1645v2PbbBGriMVBridgeCacheStatViols OBJECT-TYPE
   SYNTAX      Counter32
   MAX-ACCESS  read-only
   STATUS      current
   DESCRIPTION
      "Path: pbbBridgeGroup.performance.bridgeCache.staticViolations

       32 bit unsigned wrappable counter."
   ::= {pr1645v2PbbBGriMVBridgeCacheEntry 117440512}

pr1645v2PbbBGriMVBridgeCacheRelearns OBJECT-TYPE
   SYNTAX      Counter32
   MAX-ACCESS  read-only
   STATUS      current
   DESCRIPTION
      "Path: pbbBridgeGroup.performance.bridgeCache.relearns

       32 bit unsigned wrappable counter."
   ::= {pr1645v2PbbBGriMVBridgeCacheEntry 134217728}

pr1645v2PbbBGriMVBridgeCacheRelearnDrops OBJECT-TYPE
   SYNTAX      Counter32
   MAX-ACCESS  read-only
   STATUS      current
   DESCRIPTION
      "Path: pbbBridgeGroup.performance.bridgeCache.relearnDrops

       32 bit unsigned wrappable counter."
   ::= {pr1645v2PbbBGriMVBridgeCacheEntry 150994944}

pr1645v2PbbBGriMVBridgeCacheBMacRelearns OBJECT-TYPE
   SYNTAX      Counter32
   MAX-ACCESS  read-only
   STATUS      current
   DESCRIPTION
      "Path: pbbBridgeGroup.performance.bridgeCache.bMacRelearns

       32 bit unsigned wrappable counter."
   ::= {pr1645v2PbbBGriMVBridgeCacheEntry 184549376}


pr1645v2PbbBGriMVCacheEvents OBJECT IDENTIFIER ::= {pr1645v2PbbBGriMV 44}

pr1645v2PbbBGriMVCacheEventsSSCTable OBJECT-TYPE
   SYNTAX      SEQUENCE OF Pr1645v2PbbBGriMVCacheEventsEntry
   MAX-ACCESS  not-accessible
   STATUS      current
   DESCRIPTION
      "bridge performances"
   ::= {pr1645v2PbbBGriMVCacheEvents 1}

pr1645v2PbbBGriMVCacheEventsEntry OBJECT-TYPE
   SYNTAX      Pr1645v2PbbBGriMVCacheEventsEntry
   MAX-ACCESS  not-accessible
   STATUS      current
   DESCRIPTION
      ""
   INDEX      { pr1645v2PbbBGriMVCacheEventsGlobalIx }
   ::= {pr1645v2PbbBGriMVCacheEventsSSCTable 1}

Pr1645v2PbbBGriMVCacheEventsEntry ::=
   SEQUENCE
      {
      pr1645v2PbbBGriMVCacheEventsGlobalIx
         GlobalIndex,
      pr1645v2PbbBGriMVCacheEventsSizeOverflows
         Counter32,
      pr1645v2PbbBGriMVCacheEventsStaticViolations
         Counter32,
      pr1645v2PbbBGriMVCacheEventsRelearns
         Counter32,
      pr1645v2PbbBGriMVCacheEventsRelearnDrops
         Counter32,
      pr1645v2PbbBGriMVCacheEventsBMacRelearns
         Counter32,
      pr1645v2PbbBGriMVCacheEventsIsidMismatch
         Counter32,
      pr1645v2PbbBGriMVCacheEventsLoopsDetected
         Counter32
      }

pr1645v2PbbBGriMVCacheEventsGlobalIx OBJECT-TYPE
   SYNTAX      GlobalIndex
   MAX-ACCESS  not-accessible
   STATUS      current
   DESCRIPTION
      "The value of the tlsCntTreeGlobalIndex of the MANAGED OBJECT."
   ::= {pr1645v2PbbBGriMVCacheEventsEntry 10}

pr1645v2PbbBGriMVCacheEventsSizeOverflows OBJECT-TYPE
   SYNTAX      Counter32
   MAX-ACCESS  read-only
   STATUS      current
   DESCRIPTION
      "Path: pbbBridgeGroup.performance.cacheEvents.sizeOverflows

       32 bit unsigned wrappable counter."
   ::= {pr1645v2PbbBGriMVCacheEventsEntry 16777216}

pr1645v2PbbBGriMVCacheEventsStaticViolations OBJECT-TYPE
   SYNTAX      Counter32
   MAX-ACCESS  read-only
   STATUS      current
   DESCRIPTION
      "Path: pbbBridgeGroup.performance.cacheEvents.staticViolations

       32 bit unsigned wrappable counter."
   ::= {pr1645v2PbbBGriMVCacheEventsEntry 33554432}

pr1645v2PbbBGriMVCacheEventsRelearns OBJECT-TYPE
   SYNTAX      Counter32
   MAX-ACCESS  read-only
   STATUS      current
   DESCRIPTION
      "Path: pbbBridgeGroup.performance.cacheEvents.relearns

       32 bit unsigned wrappable counter."
   ::= {pr1645v2PbbBGriMVCacheEventsEntry 50331648}

pr1645v2PbbBGriMVCacheEventsRelearnDrops OBJECT-TYPE
   SYNTAX      Counter32
   MAX-ACCESS  read-only
   STATUS      current
   DESCRIPTION
      "Path: pbbBridgeGroup.performance.cacheEvents.relearnDrops

       32 bit unsigned wrappable counter."
   ::= {pr1645v2PbbBGriMVCacheEventsEntry 67108864}

pr1645v2PbbBGriMVCacheEventsBMacRelearns OBJECT-TYPE
   SYNTAX      Counter32
   MAX-ACCESS  read-only
   STATUS      current
   DESCRIPTION
      "Path: pbbBridgeGroup.performance.cacheEvents.bMacRelearns

       32 bit unsigned wrappable counter."
   ::= {pr1645v2PbbBGriMVCacheEventsEntry 83886080}

pr1645v2PbbBGriMVCacheEventsIsidMismatch OBJECT-TYPE
   SYNTAX      Counter32
   MAX-ACCESS  read-only
   STATUS      current
   DESCRIPTION
      "Path: pbbBridgeGroup.performance.cacheEvents.isidMismatch

       32 bit unsigned wrappable counter."
   ::= {pr1645v2PbbBGriMVCacheEventsEntry 100663296}

pr1645v2PbbBGriMVCacheEventsLoopsDetected OBJECT-TYPE
   SYNTAX      Counter32
   MAX-ACCESS  read-only
   STATUS      current
   DESCRIPTION
      "Path: pbbBridgeGroup.performance.cacheEvents.loopsDetected

       32 bit unsigned wrappable counter."
   ::= {pr1645v2PbbBGriMVCacheEventsEntry 117440512}


pr1645v2PbbBGriMVBridging OBJECT IDENTIFIER ::= {pr1645v2PbbBGriMV 90}

pr1645v2PbbBGriMVBridgingSSCTable OBJECT-TYPE
   SYNTAX      SEQUENCE OF Pr1645v2PbbBGriMVBridgingEntry
   MAX-ACCESS  not-accessible
   STATUS      current
   DESCRIPTION
      " bridge-port performance"
   ::= {pr1645v2PbbBGriMVBridging 1}

pr1645v2PbbBGriMVBridgingEntry OBJECT-TYPE
   SYNTAX      Pr1645v2PbbBGriMVBridgingEntry
   MAX-ACCESS  not-accessible
   STATUS      current
   DESCRIPTION
      ""
   INDEX      { pr1645v2PbbBGriMVBridgingGlobalIx,
                pr1645v2PbbBGriMVBridgingTableIx }
   ::= {pr1645v2PbbBGriMVBridgingSSCTable 1}

Pr1645v2PbbBGriMVBridgingEntry ::=
   SEQUENCE
      {
      pr1645v2PbbBGriMVBridgingGlobalIx
         GlobalIndex,
      pr1645v2PbbBGriMVBridgingTableIx
         TableIndex,
      pr1645v2PbbBGriMVBridgingName
         DisplayString,
      pr1645v2PbbBGriMVBridgingRxPkts
         Counter32,
      pr1645v2PbbBGriMVBridgingTxPkts
         Counter32,
      pr1645v2PbbBGriMVBridgingRxDiscards
         Counter32,
      pr1645v2PbbBGriMVBridgingRxFloods
         Counter32,
      pr1645v2PbbBGriMVBridgingRxBroadcasts
         Counter32,
      pr1645v2PbbBGriMVBridgingRxMulticasts
         Counter32,
      pr1645v2PbbBGriMVBridgingCacheSizeOverflows
         Counter32,
      pr1645v2PbbBGriMVBridgingCacheStaticViolations
         Counter32,
      pr1645v2PbbBGriMVBridgingCacheRelearns
         Counter32,
      pr1645v2PbbBGriMVBridgingCacheRelearnDrops
         Counter32,
      pr1645v2PbbBGriMVBridgingCacheBMacRelearns
         Counter32,
      pr1645v2PbbBGriMVBridgingCacheIsidMismatch
         Counter32,
      pr1645v2PbbBGriMVBridgingCacheLoopsDetected
         Counter32,
      pr1645v2PbbBGriMVBridgingVlanMemberShipRxDiscards
         Counter32,
      pr1645v2PbbBGriMVBridgingVlanMemberShipTxDiscards
         Counter32,
      pr1645v2PbbBGriMVBridgingSpanningTreeRxMstp
         Integer32,
      pr1645v2PbbBGriMVBridgingSpanningTreeRxRstp
         Integer32,
      pr1645v2PbbBGriMVBridgingSpanningTreeRxConfig
         Integer32,
      pr1645v2PbbBGriMVBridgingSpanningTreeRxTcn
         Integer32,
      pr1645v2PbbBGriMVBridgingSpanningTreeRxDiscards
         Integer32,
      pr1645v2PbbBGriMVBridgingSpanningTreeTxMstp
         Integer32,
      pr1645v2PbbBGriMVBridgingSpanningTreeTxRstp
         Integer32,
      pr1645v2PbbBGriMVBridgingSpanningTreeTxConfig
         Integer32,
      pr1645v2PbbBGriMVBridgingSpanningTreeTxTcn
         Integer32
      }

pr1645v2PbbBGriMVBridgingGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgingEntry 10}

pr1645v2PbbBGriMVBridgingTableIx OBJECT-TYPE
   SYNTAX      TableIndex
   MAX-ACCESS  not-accessible
   STATUS      current
   DESCRIPTION
      ""
   ::= {pr1645v2PbbBGriMVBridgingEntry 11}

pr1645v2PbbBGriMVBridgingName OBJECT-TYPE
   SYNTAX      DisplayString
   MAX-ACCESS  read-only
   STATUS      current
   DESCRIPTION
      "Path: pbbBridgeGroup.performance.bridging.name"
   ::= {pr1645v2PbbBGriMVBridgingEntry 16777216}

pr1645v2PbbBGriMVBridgingRxPkts OBJECT-TYPE
   SYNTAX      Counter32
   MAX-ACCESS  read-only
   STATUS      current
   DESCRIPTION
      "Path: pbbBridgeGroup.performance.bridging.rxPkts

       32 bit unsigned wrappable counter."
   ::= {pr1645v2PbbBGriMVBridgingEntry 33554432}

pr1645v2PbbBGriMVBridgingTxPkts OBJECT-TYPE
   SYNTAX      Counter32
   MAX-ACCESS  read-only
   STATUS      current
   DESCRIPTION
      "Path: pbbBridgeGroup.performance.bridging.txPkts

       32 bit unsigned wrappable counter."
   ::= {pr1645v2PbbBGriMVBridgingEntry 50331648}

pr1645v2PbbBGriMVBridgingRxDiscards OBJECT-TYPE
   SYNTAX      Counter32
   MAX-ACCESS  read-only
   STATUS      current
   DESCRIPTION
      "Path: pbbBridgeGroup.performance.bridging.rxDiscards

       32 bit unsigned wrappable counter."
   ::= {pr1645v2PbbBGriMVBridgingEntry 67108864}

pr1645v2PbbBGriMVBridgingRxFloods OBJECT-TYPE
   SYNTAX      Counter32
   MAX-ACCESS  read-only
   STATUS      current
   DESCRIPTION
      "Path: pbbBridgeGroup.performance.bridging.rxFloods

       32 bit unsigned wrappable counter."
   ::= {pr1645v2PbbBGriMVBridgingEntry 83886080}

pr1645v2PbbBGriMVBridgingRxBroadcasts OBJECT-TYPE
   SYNTAX      Counter32
   MAX-ACCESS  read-only
   STATUS      current
   DESCRIPTION
      "Path: pbbBridgeGroup.performance.bridging.rxBroadcasts

       32 bit unsigned wrappable counter."
   ::= {pr1645v2PbbBGriMVBridgingEntry 100663296}

pr1645v2PbbBGriMVBridgingRxMulticasts OBJECT-TYPE
   SYNTAX      Counter32
   MAX-ACCESS  read-only
   STATUS      current
   DESCRIPTION
      "Path: pbbBridgeGroup.performance.bridging.rxMulticasts

       32 bit unsigned wrappable counter."
   ::= {pr1645v2PbbBGriMVBridgingEntry 117440512}

pr1645v2PbbBGriMVBridgingCacheSizeOverflows OBJECT-TYPE
   SYNTAX      Counter32
   MAX-ACCESS  read-only
   STATUS      current
   DESCRIPTION
      "Path: pbbBridgeGroup.performance.bridging.cache.sizeOverflows

       32 bit unsigned wrappable counter."
   ::= {pr1645v2PbbBGriMVBridgingEntry 134283264}

pr1645v2PbbBGriMVBridgingCacheStaticViolations OBJECT-TYPE
   SYNTAX      Counter32
   MAX-ACCESS  read-only
   STATUS      current
   DESCRIPTION
      "Path: pbbBridgeGroup.performance.bridging.cache.staticViolations

       32 bit unsigned wrappable counter."
   ::= {pr1645v2PbbBGriMVBridgingEntry 134348800}

pr1645v2PbbBGriMVBridgingCacheRelearns OBJECT-TYPE
   SYNTAX      Counter32
   MAX-ACCESS  read-only
   STATUS      current
   DESCRIPTION
      "Path: pbbBridgeGroup.performance.bridging.cache.relearns

       32 bit unsigned wrappable counter."
   ::= {pr1645v2PbbBGriMVBridgingEntry 134414336}

pr1645v2PbbBGriMVBridgingCacheRelearnDrops OBJECT-TYPE
   SYNTAX      Counter32
   MAX-ACCESS  read-only
   STATUS      current
   DESCRIPTION
      "Path: pbbBridgeGroup.performance.bridging.cache.relearnDrops

       32 bit unsigned wrappable counter."
   ::= {pr1645v2PbbBGriMVBridgingEntry 134479872}

pr1645v2PbbBGriMVBridgingCacheBMacRelearns OBJECT-TYPE
   SYNTAX      Counter32
   MAX-ACCESS  read-only
   STATUS      current
   DESCRIPTION
      "Path: pbbBridgeGroup.performance.bridging.cache.bMacRelearns

       32 bit unsigned wrappable counter."
   ::= {pr1645v2PbbBGriMVBridgingEntry 134545408}

pr1645v2PbbBGriMVBridgingCacheIsidMismatch OBJECT-TYPE
   SYNTAX      Counter32
   MAX-ACCESS  read-only
   STATUS      current
   DESCRIPTION
      "Path: pbbBridgeGroup.performance.bridging.cache.isidMismatch

       32 bit unsigned wrappable counter."
   ::= {pr1645v2PbbBGriMVBridgingEntry 134610944}

pr1645v2PbbBGriMVBridgingCacheLoopsDetected OBJECT-TYPE
   SYNTAX      Counter32
   MAX-ACCESS  read-only
   STATUS      current
   DESCRIPTION
      "Path: pbbBridgeGroup.performance.bridging.cache.loopsDetected

       32 bit unsigned wrappable counter."
   ::= {pr1645v2PbbBGriMVBridgingEntry 134676480}

pr1645v2PbbBGriMVBridgingVlanMemberShipRxDiscards OBJECT-TYPE
   SYNTAX      Counter32
   MAX-ACCESS  read-only
   STATUS      current
   DESCRIPTION
      "Path: pbbBridgeGroup.performance.bridging.vlanMemberShip.rxDiscards

       32 bit unsigned wrappable counter."
   ::= {pr1645v2PbbBGriMVBridgingEntry 218169344}

pr1645v2PbbBGriMVBridgingVlanMemberShipTxDiscards OBJECT-TYPE
   SYNTAX      Counter32
   MAX-ACCESS  read-only
   STATUS      current
   DESCRIPTION
      "Path: pbbBridgeGroup.performance.bridging.vlanMemberShip.txDiscards

       32 bit unsigned wrappable counter."
   ::= {pr1645v2PbbBGriMVBridgingEntry 218234880}

pr1645v2PbbBGriMVBridgingSpanningTreeRxMstp OBJECT-TYPE
   SYNTAX      Integer32
   MAX-ACCESS  read-only
   STATUS      current
   DESCRIPTION
      "Path: pbbBridgeGroup.performance.bridging.spanningTree.rxMstp"
   ::= {pr1645v2PbbBGriMVBridgingEntry 201392128}

pr1645v2PbbBGriMVBridgingSpanningTreeRxRstp OBJECT-TYPE
   SYNTAX      Integer32
   MAX-ACCESS  read-only
   STATUS      current
   DESCRIPTION
      "Path: pbbBridgeGroup.performance.bridging.spanningTree.rxRstp"
   ::= {pr1645v2PbbBGriMVBridgingEntry 201457664}

pr1645v2PbbBGriMVBridgingSpanningTreeRxConfig OBJECT-TYPE
   SYNTAX      Integer32
   MAX-ACCESS  read-only
   STATUS      current
   DESCRIPTION
      "Path: pbbBridgeGroup.performance.bridging.spanningTree.rxConfig"
   ::= {pr1645v2PbbBGriMVBridgingEntry 201523200}

pr1645v2PbbBGriMVBridgingSpanningTreeRxTcn OBJECT-TYPE
   SYNTAX      Integer32
   MAX-ACCESS  read-only
   STATUS      current
   DESCRIPTION
      "Path: pbbBridgeGroup.performance.bridging.spanningTree.rxTcn"
   ::= {pr1645v2PbbBGriMVBridgingEntry 201588736}

pr1645v2PbbBGriMVBridgingSpanningTreeRxDiscards OBJECT-TYPE
   SYNTAX      Integer32
   MAX-ACCESS  read-only
   STATUS      current
   DESCRIPTION
      "Path: pbbBridgeGroup.performance.bridging.spanningTree.rxDiscards"
   ::= {pr1645v2PbbBGriMVBridgingEntry 201654272}

pr1645v2PbbBGriMVBridgingSpanningTreeTxMstp OBJECT-TYPE
   SYNTAX      Integer32
   MAX-ACCESS  read-only
   STATUS      current
   DESCRIPTION
      "Path: pbbBridgeGroup.performance.bridging.spanningTree.txMstp"
   ::= {pr1645v2PbbBGriMVBridgingEntry 201719808}

pr1645v2PbbBGriMVBridgingSpanningTreeTxRstp OBJECT-TYPE
   SYNTAX      Integer32
   MAX-ACCESS  read-only
   STATUS      current
   DESCRIPTION
      "Path: pbbBridgeGroup.performance.bridging.spanningTree.txRstp"
   ::= {pr1645v2PbbBGriMVBridgingEntry 201785344}

pr1645v2PbbBGriMVBridgingSpanningTreeTxConfig OBJECT-TYPE
   SYNTAX      Integer32
   MAX-ACCESS  read-only
   STATUS      current
   DESCRIPTION
      "Path: pbbBridgeGroup.performance.bridging.spanningTree.txConfig"
   ::= {pr1645v2PbbBGriMVBridgingEntry 201850880}

pr1645v2PbbBGriMVBridgingSpanningTreeTxTcn OBJECT-TYPE
   SYNTAX      Integer32
   MAX-ACCESS  read-only
   STATUS      current
   DESCRIPTION
      "Path: pbbBridgeGroup.performance.bridging.spanningTree.txTcn"
   ::= {pr1645v2PbbBGriMVBridgingEntry 201916416}

pr1645v2PbbBGriMVBridgingH2Performance OBJECT-TYPE
   SYNTAX      SEQUENCE OF Pr1645v2PbbBGriMVBridgingH2PerformanceEntry
   MAX-ACCESS  not-accessible
   STATUS      current
   DESCRIPTION
      ""
   ::= {pr1645v2PbbBGriMVBridging 150994944}

pr1645v2PbbBGriMVBridgingH2PerformanceEntry OBJECT-TYPE
   SYNTAX      Pr1645v2PbbBGriMVBridgingH2PerformanceEntry
   MAX-ACCESS  not-accessible
   STATUS      current
   DESCRIPTION
      ""
   INDEX      { pr1645v2PbbBGriMVBridgingH2PerformanceGlobalIx,
                pr1645v2PbbBGriMVBridgingTableIx,
                pr1645v2PbbBGriMVBridgingH2PerformanceTableIx }
   ::= {pr1645v2PbbBGriMVBridgingH2Performance 1}

Pr1645v2PbbBGriMVBridgingH2PerformanceEntry ::=
   SEQUENCE
      {
      pr1645v2PbbBGriMVBridgingH2PerformanceGlobalIx
         GlobalIndex,
      pr1645v2PbbBGriMVBridgingH2PerformanceTableIx
         TableIndex,
      pr1645v2PbbBGriMVBridgingH2PerformanceSysUpTime
         TimeTicks,
      pr1645v2PbbBGriMVBridgingH2PerformanceRxPkts
         Counter32,
      pr1645v2PbbBGriMVBridgingH2PerformanceTxPkts
         Counter32,
      pr1645v2PbbBGriMVBridgingH2PerformanceRxDiscards
         Counter32,
      pr1645v2PbbBGriMVBridgingH2PerformanceRxFloods
         Counter32,
      pr1645v2PbbBGriMVBridgingH2PerformanceRxBroadcasts
         Counter32,
      pr1645v2PbbBGriMVBridgingH2PerformanceRxMulticasts
         Counter32,
      pr1645v2PbbBGriMVBridgingH2PerformanceCacheSizeOverflows
         Counter32,
      pr1645v2PbbBGriMVBridgingH2PerformanceStaticCacheViolations
         Counter32,
      pr1645v2PbbBGriMVBridgingH2PerformanceCacheRelearns
         Counter32,
      pr1645v2PbbBGriMVBridgingH2PerformanceCacheRelearnDrops
         Counter32,
      pr1645v2PbbBGriMVBridgingH2PerformanceCacheBMacRelearns
         Counter32,
      pr1645v2PbbBGriMVBridgingH2PerformanceIsidMismatch
         Counter32,
      pr1645v2PbbBGriMVBridgingH2PerformanceLoopsDetected
         Counter32
      }

pr1645v2PbbBGriMVBridgingH2PerformanceGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgingH2PerformanceEntry 10}

pr1645v2PbbBGriMVBridgingH2PerformanceTableIx OBJECT-TYPE
   SYNTAX      TableIndex
   MAX-ACCESS  not-accessible
   STATUS      current
   DESCRIPTION
      ""
   ::= {pr1645v2PbbBGriMVBridgingH2PerformanceEntry 11}

pr1645v2PbbBGriMVBridgingH2PerformanceSysUpTime OBJECT-TYPE
   SYNTAX      TimeTicks
   MAX-ACCESS  read-only
   STATUS      current
   DESCRIPTION
      "Path: pbbBridgeGroup.performance.bridging.h2Performance.sysUpTime

       Time in centi-second."
   ::= {pr1645v2PbbBGriMVBridgingH2PerformanceEntry 16777216}

pr1645v2PbbBGriMVBridgingH2PerformanceRxPkts OBJECT-TYPE
   SYNTAX      Counter32
   MAX-ACCESS  read-only
   STATUS      current
   DESCRIPTION
      "Path: pbbBridgeGroup.performance.bridging.h2Performance.rxPkts

       32 bit unsigned wrappable counter."
   ::= {pr1645v2PbbBGriMVBridgingH2PerformanceEntry 33554432}

pr1645v2PbbBGriMVBridgingH2PerformanceTxPkts OBJECT-TYPE
   SYNTAX      Counter32
   MAX-ACCESS  read-only
   STATUS      current
   DESCRIPTION
      "Path: pbbBridgeGroup.performance.bridging.h2Performance.txPkts

       32 bit unsigned wrappable counter."
   ::= {pr1645v2PbbBGriMVBridgingH2PerformanceEntry 50331648}

pr1645v2PbbBGriMVBridgingH2PerformanceRxDiscards OBJECT-TYPE
   SYNTAX      Counter32
   MAX-ACCESS  read-only
   STATUS      current
   DESCRIPTION
      "Path: pbbBridgeGroup.performance.bridging.h2Performance.rxDiscards

       32 bit unsigned wrappable counter."
   ::= {pr1645v2PbbBGriMVBridgingH2PerformanceEntry 67108864}

pr1645v2PbbBGriMVBridgingH2PerformanceRxFloods OBJECT-TYPE
   SYNTAX      Counter32
   MAX-ACCESS  read-only
   STATUS      current
   DESCRIPTION
      "Path: pbbBridgeGroup.performance.bridging.h2Performance.rxFloods

       32 bit unsigned wrappable counter."
   ::= {pr1645v2PbbBGriMVBridgingH2PerformanceEntry 83886080}

pr1645v2PbbBGriMVBridgingH2PerformanceRxBroadcasts OBJECT-TYPE
   SYNTAX      Counter32
   MAX-ACCESS  read-only
   STATUS      current
   DESCRIPTION
      "Path: pbbBridgeGroup.performance.bridging.h2Performance.rxBroadcasts

       32 bit unsigned wrappable counter."
   ::= {pr1645v2PbbBGriMVBridgingH2PerformanceEntry 100663296}

pr1645v2PbbBGriMVBridgingH2PerformanceRxMulticasts OBJECT-TYPE
   SYNTAX      Counter32
   MAX-ACCESS  read-only
   STATUS      current
   DESCRIPTION
      "Path: pbbBridgeGroup.performance.bridging.h2Performance.rxMulticasts

       32 bit unsigned wrappable counter."
   ::= {pr1645v2PbbBGriMVBridgingH2PerformanceEntry 117440512}

pr1645v2PbbBGriMVBridgingH2PerformanceCacheSizeOverflows OBJECT-TYPE
   SYNTAX      Counter32
   MAX-ACCESS  read-only
   STATUS      current
   DESCRIPTION
      "Path: pbbBridgeGroup.performance.bridging.h2Performance.cacheSizeOverflows

       32 bit unsigned wrappable counter."
   ::= {pr1645v2PbbBGriMVBridgingH2PerformanceEntry 134217728}

pr1645v2PbbBGriMVBridgingH2PerformanceStaticCacheViolations OBJECT-TYPE
   SYNTAX      Counter32
   MAX-ACCESS  read-only
   STATUS      current
   DESCRIPTION
      "Path: pbbBridgeGroup.performance.bridging.h2Performance.staticCacheViolations

       32 bit unsigned wrappable counter."
   ::= {pr1645v2PbbBGriMVBridgingH2PerformanceEntry 150994944}

pr1645v2PbbBGriMVBridgingH2PerformanceCacheRelearns OBJECT-TYPE
   SYNTAX      Counter32
   MAX-ACCESS  read-only
   STATUS      current
   DESCRIPTION
      "Path: pbbBridgeGroup.performance.bridging.h2Performance.cacheRelearns

       32 bit unsigned wrappable counter."
   ::= {pr1645v2PbbBGriMVBridgingH2PerformanceEntry 167772160}

pr1645v2PbbBGriMVBridgingH2PerformanceCacheRelearnDrops OBJECT-TYPE
   SYNTAX      Counter32
   MAX-ACCESS  read-only
   STATUS      current
   DESCRIPTION
      "Path: pbbBridgeGroup.performance.bridging.h2Performance.cacheRelearnDrops

       32 bit unsigned wrappable counter."
   ::= {pr1645v2PbbBGriMVBridgingH2PerformanceEntry 184549376}

pr1645v2PbbBGriMVBridgingH2PerformanceCacheBMacRelearns OBJECT-TYPE
   SYNTAX      Counter32
   MAX-ACCESS  read-only
   STATUS      current
   DESCRIPTION
      "Path: pbbBridgeGroup.performance.bridging.h2Performance.cacheBMacRelearns

       32 bit unsigned wrappable counter."
   ::= {pr1645v2PbbBGriMVBridgingH2PerformanceEntry 201326592}

pr1645v2PbbBGriMVBridgingH2PerformanceIsidMismatch OBJECT-TYPE
   SYNTAX      Counter32
   MAX-ACCESS  read-only
   STATUS      current
   DESCRIPTION
      "Path: pbbBridgeGroup.performance.bridging.h2Performance.isidMismatch

       32 bit unsigned wrappable counter."
   ::= {pr1645v2PbbBGriMVBridgingH2PerformanceEntry 218103808}

pr1645v2PbbBGriMVBridgingH2PerformanceLoopsDetected OBJECT-TYPE
   SYNTAX      Counter32
   MAX-ACCESS  read-only
   STATUS      current
   DESCRIPTION
      "Path: pbbBridgeGroup.performance.bridging.h2Performance.loopsDetected

       32 bit unsigned wrappable counter."
   ::= {pr1645v2PbbBGriMVBridgingH2PerformanceEntry 234881024}

pr1645v2PbbBGriMVBridgingH24Performance OBJECT-TYPE
   SYNTAX      SEQUENCE OF Pr1645v2PbbBGriMVBridgingH24PerformanceEntry
   MAX-ACCESS  not-accessible
   STATUS      current
   DESCRIPTION
      ""
   ::= {pr1645v2PbbBGriMVBridging 167772160}

pr1645v2PbbBGriMVBridgingH24PerformanceEntry OBJECT-TYPE
   SYNTAX      Pr1645v2PbbBGriMVBridgingH24PerformanceEntry
   MAX-ACCESS  not-accessible
   STATUS      current
   DESCRIPTION
      ""
   INDEX      { pr1645v2PbbBGriMVBridgingH24PerformanceGlobalIx,
                pr1645v2PbbBGriMVBridgingTableIx,
                pr1645v2PbbBGriMVBridgingH24PerformanceTableIx }
   ::= {pr1645v2PbbBGriMVBridgingH24Performance 1}

Pr1645v2PbbBGriMVBridgingH24PerformanceEntry ::=
   SEQUENCE
      {
      pr1645v2PbbBGriMVBridgingH24PerformanceGlobalIx
         GlobalIndex,
      pr1645v2PbbBGriMVBridgingH24PerformanceTableIx
         TableIndex,
      pr1645v2PbbBGriMVBridgingH24PerformanceSysUpTime
         TimeTicks,
      pr1645v2PbbBGriMVBridgingH24PerformanceRxPkts
         Counter32,
      pr1645v2PbbBGriMVBridgingH24PerformanceTxPkts
         Counter32,
      pr1645v2PbbBGriMVBridgingH24PerformanceRxDiscards
         Counter32,
      pr1645v2PbbBGriMVBridgingH24PerformanceRxFloods
         Counter32,
      pr1645v2PbbBGriMVBridgingH24PerformanceRxBroadcasts
         Counter32,
      pr1645v2PbbBGriMVBridgingH24PerformanceRxMulticasts
         Counter32,
      pr1645v2PbbBGriMVBridgingH24PerformanceCacheSizeOverflows
         Counter32,
      pr1645v2PbbBGriMVBridgingH24PerformanceStaticCacheViolations
         Counter32,
      pr1645v2PbbBGriMVBridgingH24PerformanceCacheRelearns
         Counter32,
      pr1645v2PbbBGriMVBridgingH24PerformanceCacheRelearnDrops
         Counter32,
      pr1645v2PbbBGriMVBridgingH24PerformanceCacheBMacRelearns
         Counter32,
      pr1645v2PbbBGriMVBridgingH24PerformanceIsidMismatch
         Counter32,
      pr1645v2PbbBGriMVBridgingH24PerformanceLoopsDetected
         Counter32
      }

pr1645v2PbbBGriMVBridgingH24PerformanceGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgingH24PerformanceEntry 10}

pr1645v2PbbBGriMVBridgingH24PerformanceTableIx OBJECT-TYPE
   SYNTAX      TableIndex
   MAX-ACCESS  not-accessible
   STATUS      current
   DESCRIPTION
      ""
   ::= {pr1645v2PbbBGriMVBridgingH24PerformanceEntry 11}

pr1645v2PbbBGriMVBridgingH24PerformanceSysUpTime OBJECT-TYPE
   SYNTAX      TimeTicks
   MAX-ACCESS  read-only
   STATUS      current
   DESCRIPTION
      "Path: pbbBridgeGroup.performance.bridging.h24Performance.sysUpTime

       Time in centi-second."
   ::= {pr1645v2PbbBGriMVBridgingH24PerformanceEntry 16777216}

pr1645v2PbbBGriMVBridgingH24PerformanceRxPkts OBJECT-TYPE
   SYNTAX      Counter32
   MAX-ACCESS  read-only
   STATUS      current
   DESCRIPTION
      "Path: pbbBridgeGroup.performance.bridging.h24Performance.rxPkts

       32 bit unsigned wrappable counter."
   ::= {pr1645v2PbbBGriMVBridgingH24PerformanceEntry 33554432}

pr1645v2PbbBGriMVBridgingH24PerformanceTxPkts OBJECT-TYPE
   SYNTAX      Counter32
   MAX-ACCESS  read-only
   STATUS      current
   DESCRIPTION
      "Path: pbbBridgeGroup.performance.bridging.h24Performance.txPkts

       32 bit unsigned wrappable counter."
   ::= {pr1645v2PbbBGriMVBridgingH24PerformanceEntry 50331648}

pr1645v2PbbBGriMVBridgingH24PerformanceRxDiscards OBJECT-TYPE
   SYNTAX      Counter32
   MAX-ACCESS  read-only
   STATUS      current
   DESCRIPTION
      "Path: pbbBridgeGroup.performance.bridging.h24Performance.rxDiscards

       32 bit unsigned wrappable counter."
   ::= {pr1645v2PbbBGriMVBridgingH24PerformanceEntry 67108864}

pr1645v2PbbBGriMVBridgingH24PerformanceRxFloods OBJECT-TYPE
   SYNTAX      Counter32
   MAX-ACCESS  read-only
   STATUS      current
   DESCRIPTION
      "Path: pbbBridgeGroup.performance.bridging.h24Performance.rxFloods

       32 bit unsigned wrappable counter."
   ::= {pr1645v2PbbBGriMVBridgingH24PerformanceEntry 83886080}

pr1645v2PbbBGriMVBridgingH24PerformanceRxBroadcasts OBJECT-TYPE
   SYNTAX      Counter32
   MAX-ACCESS  read-only
   STATUS      current
   DESCRIPTION
      "Path: pbbBridgeGroup.performance.bridging.h24Performance.rxBroadcasts

       32 bit unsigned wrappable counter."
   ::= {pr1645v2PbbBGriMVBridgingH24PerformanceEntry 100663296}

pr1645v2PbbBGriMVBridgingH24PerformanceRxMulticasts OBJECT-TYPE
   SYNTAX      Counter32
   MAX-ACCESS  read-only
   STATUS      current
   DESCRIPTION
      "Path: pbbBridgeGroup.performance.bridging.h24Performance.rxMulticasts

       32 bit unsigned wrappable counter."
   ::= {pr1645v2PbbBGriMVBridgingH24PerformanceEntry 117440512}

pr1645v2PbbBGriMVBridgingH24PerformanceCacheSizeOverflows OBJECT-TYPE
   SYNTAX      Counter32
   MAX-ACCESS  read-only
   STATUS      current
   DESCRIPTION
      "Path: pbbBridgeGroup.performance.bridging.h24Performance.cacheSizeOverflows

       32 bit unsigned wrappable counter."
   ::= {pr1645v2PbbBGriMVBridgingH24PerformanceEntry 134217728}

pr1645v2PbbBGriMVBridgingH24PerformanceStaticCacheViolations OBJECT-TYPE
   SYNTAX      Counter32
   MAX-ACCESS  read-only
   STATUS      current
   DESCRIPTION
      "Path: pbbBridgeGroup.performance.bridging.h24Performance.staticCacheViolations

       32 bit unsigned wrappable counter."
   ::= {pr1645v2PbbBGriMVBridgingH24PerformanceEntry 150994944}

pr1645v2PbbBGriMVBridgingH24PerformanceCacheRelearns OBJECT-TYPE
   SYNTAX      Counter32
   MAX-ACCESS  read-only
   STATUS      current
   DESCRIPTION
      "Path: pbbBridgeGroup.performance.bridging.h24Performance.cacheRelearns

       32 bit unsigned wrappable counter."
   ::= {pr1645v2PbbBGriMVBridgingH24PerformanceEntry 167772160}

pr1645v2PbbBGriMVBridgingH24PerformanceCacheRelearnDrops OBJECT-TYPE
   SYNTAX      Counter32
   MAX-ACCESS  read-only
   STATUS      current
   DESCRIPTION
      "Path: pbbBridgeGroup.performance.bridging.h24Performance.cacheRelearnDrops

       32 bit unsigned wrappable counter."
   ::= {pr1645v2PbbBGriMVBridgingH24PerformanceEntry 184549376}

pr1645v2PbbBGriMVBridgingH24PerformanceCacheBMacRelearns OBJECT-TYPE
   SYNTAX      Counter32
   MAX-ACCESS  read-only
   STATUS      current
   DESCRIPTION
      "Path: pbbBridgeGroup.performance.bridging.h24Performance.cacheBMacRelearns

       32 bit unsigned wrappable counter."
   ::= {pr1645v2PbbBGriMVBridgingH24PerformanceEntry 201326592}

pr1645v2PbbBGriMVBridgingH24PerformanceIsidMismatch OBJECT-TYPE
   SYNTAX      Counter32
   MAX-ACCESS  read-only
   STATUS      current
   DESCRIPTION
      "Path: pbbBridgeGroup.performance.bridging.h24Performance.isidMismatch

       32 bit unsigned wrappable counter."
   ::= {pr1645v2PbbBGriMVBridgingH24PerformanceEntry 218103808}

pr1645v2PbbBGriMVBridgingH24PerformanceLoopsDetected OBJECT-TYPE
   SYNTAX      Counter32
   MAX-ACCESS  read-only
   STATUS      current
   DESCRIPTION
      "Path: pbbBridgeGroup.performance.bridging.h24Performance.loopsDetected

       32 bit unsigned wrappable counter."
   ::= {pr1645v2PbbBGriMVBridgingH24PerformanceEntry 234881024}

pr1645v2PbbBGriMVBridgingD7Performance OBJECT-TYPE
   SYNTAX      SEQUENCE OF Pr1645v2PbbBGriMVBridgingD7PerformanceEntry
   MAX-ACCESS  not-accessible
   STATUS      current
   DESCRIPTION
      ""
   ::= {pr1645v2PbbBGriMVBridging 184549376}

pr1645v2PbbBGriMVBridgingD7PerformanceEntry OBJECT-TYPE
   SYNTAX      Pr1645v2PbbBGriMVBridgingD7PerformanceEntry
   MAX-ACCESS  not-accessible
   STATUS      current
   DESCRIPTION
      ""
   INDEX      { pr1645v2PbbBGriMVBridgingD7PerformanceGlobalIx,
                pr1645v2PbbBGriMVBridgingTableIx,
                pr1645v2PbbBGriMVBridgingD7PerformanceTableIx }
   ::= {pr1645v2PbbBGriMVBridgingD7Performance 1}

Pr1645v2PbbBGriMVBridgingD7PerformanceEntry ::=
   SEQUENCE
      {
      pr1645v2PbbBGriMVBridgingD7PerformanceGlobalIx
         GlobalIndex,
      pr1645v2PbbBGriMVBridgingD7PerformanceTableIx
         TableIndex,
      pr1645v2PbbBGriMVBridgingD7PerformanceSysUpTime
         TimeTicks,
      pr1645v2PbbBGriMVBridgingD7PerformanceRxPkts
         Counter32,
      pr1645v2PbbBGriMVBridgingD7PerformanceTxPkts
         Counter32,
      pr1645v2PbbBGriMVBridgingD7PerformanceRxDiscards
         Counter32,
      pr1645v2PbbBGriMVBridgingD7PerformanceRxFloods
         Counter32,
      pr1645v2PbbBGriMVBridgingD7PerformanceRxBroadcasts
         Counter32,
      pr1645v2PbbBGriMVBridgingD7PerformanceRxMulticasts
         Counter32,
      pr1645v2PbbBGriMVBridgingD7PerformanceCacheSizeOverflows
         Counter32,
      pr1645v2PbbBGriMVBridgingD7PerformanceStaticCacheViolations
         Counter32,
      pr1645v2PbbBGriMVBridgingD7PerformanceCacheRelearns
         Counter32,
      pr1645v2PbbBGriMVBridgingD7PerformanceCacheRelearnDrops
         Counter32,
      pr1645v2PbbBGriMVBridgingD7PerformanceCacheBMacRelearns
         Counter32,
      pr1645v2PbbBGriMVBridgingD7PerformanceIsidMismatch
         Counter32,
      pr1645v2PbbBGriMVBridgingD7PerformanceLoopsDetected
         Counter32
      }

pr1645v2PbbBGriMVBridgingD7PerformanceGlobalIx OBJECT-TYPE
   SYNTAX      GlobalIndex
   MAX-ACCESS  not-accessible
   STATUS      current
   DESCRIPTION
      "The value of the tlsCntTreeGlobalIndex of the MANAGED OBJECT."
   ::= {pr1645v2PbbBGriMVBridgingD7PerformanceEntry 10}

pr1645v2PbbBGriMVBridgingD7PerformanceTableIx OBJECT-TYPE
   SYNTAX      TableIndex
   MAX-ACCESS  not-accessible
   STATUS      current
   DESCRIPTION
      ""
   ::= {pr1645v2PbbBGriMVBridgingD7PerformanceEntry 11}

pr1645v2PbbBGriMVBridgingD7PerformanceSysUpTime OBJECT-TYPE
   SYNTAX      TimeTicks
   MAX-ACCESS  read-only
   STATUS      current
   DESCRIPTION
      "Path: pbbBridgeGroup.performance.bridging.d7Performance.sysUpTime

       Time in centi-second."
   ::= {pr1645v2PbbBGriMVBridgingD7PerformanceEntry 16777216}

pr1645v2PbbBGriMVBridgingD7PerformanceRxPkts OBJECT-TYPE
   SYNTAX      Counter32
   MAX-ACCESS  read-only
   STATUS      current
   DESCRIPTION
      "Path: pbbBridgeGroup.performance.bridging.d7Performance.rxPkts

       32 bit unsigned wrappable counter."
   ::= {pr1645v2PbbBGriMVBridgingD7PerformanceEntry 33554432}

pr1645v2PbbBGriMVBridgingD7PerformanceTxPkts OBJECT-TYPE
   SYNTAX      Counter32
   MAX-ACCESS  read-only
   STATUS      current
   DESCRIPTION
      "Path: pbbBridgeGroup.performance.bridging.d7Performance.txPkts

       32 bit unsigned wrappable counter."
   ::= {pr1645v2PbbBGriMVBridgingD7PerformanceEntry 50331648}

pr1645v2PbbBGriMVBridgingD7PerformanceRxDiscards OBJECT-TYPE
   SYNTAX      Counter32
   MAX-ACCESS  read-only
   STATUS      current
   DESCRIPTION
      "Path: pbbBridgeGroup.performance.bridging.d7Performance.rxDiscards

       32 bit unsigned wrappable counter."
   ::= {pr1645v2PbbBGriMVBridgingD7PerformanceEntry 67108864}

pr1645v2PbbBGriMVBridgingD7PerformanceRxFloods OBJECT-TYPE
   SYNTAX      Counter32
   MAX-ACCESS  read-only
   STATUS      current
   DESCRIPTION
      "Path: pbbBridgeGroup.performance.bridging.d7Performance.rxFloods

       32 bit unsigned wrappable counter."
   ::= {pr1645v2PbbBGriMVBridgingD7PerformanceEntry 83886080}

pr1645v2PbbBGriMVBridgingD7PerformanceRxBroadcasts OBJECT-TYPE
   SYNTAX      Counter32
   MAX-ACCESS  read-only
   STATUS      current
   DESCRIPTION
      "Path: pbbBridgeGroup.performance.bridging.d7Performance.rxBroadcasts

       32 bit unsigned wrappable counter."
   ::= {pr1645v2PbbBGriMVBridgingD7PerformanceEntry 100663296}

pr1645v2PbbBGriMVBridgingD7PerformanceRxMulticasts OBJECT-TYPE
   SYNTAX      Counter32
   MAX-ACCESS  read-only
   STATUS      current
   DESCRIPTION
      "Path: pbbBridgeGroup.performance.bridging.d7Performance.rxMulticasts

       32 bit unsigned wrappable counter."
   ::= {pr1645v2PbbBGriMVBridgingD7PerformanceEntry 117440512}

pr1645v2PbbBGriMVBridgingD7PerformanceCacheSizeOverflows OBJECT-TYPE
   SYNTAX      Counter32
   MAX-ACCESS  read-only
   STATUS      current
   DESCRIPTION
      "Path: pbbBridgeGroup.performance.bridging.d7Performance.cacheSizeOverflows

       32 bit unsigned wrappable counter."
   ::= {pr1645v2PbbBGriMVBridgingD7PerformanceEntry 134217728}

pr1645v2PbbBGriMVBridgingD7PerformanceStaticCacheViolations OBJECT-TYPE
   SYNTAX      Counter32
   MAX-ACCESS  read-only
   STATUS      current
   DESCRIPTION
      "Path: pbbBridgeGroup.performance.bridging.d7Performance.staticCacheViolations

       32 bit unsigned wrappable counter."
   ::= {pr1645v2PbbBGriMVBridgingD7PerformanceEntry 150994944}

pr1645v2PbbBGriMVBridgingD7PerformanceCacheRelearns OBJECT-TYPE
   SYNTAX      Counter32
   MAX-ACCESS  read-only
   STATUS      current
   DESCRIPTION
      "Path: pbbBridgeGroup.performance.bridging.d7Performance.cacheRelearns

       32 bit unsigned wrappable counter."
   ::= {pr1645v2PbbBGriMVBridgingD7PerformanceEntry 167772160}

pr1645v2PbbBGriMVBridgingD7PerformanceCacheRelearnDrops OBJECT-TYPE
   SYNTAX      Counter32
   MAX-ACCESS  read-only
   STATUS      current
   DESCRIPTION
      "Path: pbbBridgeGroup.performance.bridging.d7Performance.cacheRelearnDrops

       32 bit unsigned wrappable counter."
   ::= {pr1645v2PbbBGriMVBridgingD7PerformanceEntry 184549376}

pr1645v2PbbBGriMVBridgingD7PerformanceCacheBMacRelearns OBJECT-TYPE
   SYNTAX      Counter32
   MAX-ACCESS  read-only
   STATUS      current
   DESCRIPTION
      "Path: pbbBridgeGroup.performance.bridging.d7Performance.cacheBMacRelearns

       32 bit unsigned wrappable counter."
   ::= {pr1645v2PbbBGriMVBridgingD7PerformanceEntry 201326592}

pr1645v2PbbBGriMVBridgingD7PerformanceIsidMismatch OBJECT-TYPE
   SYNTAX      Counter32
   MAX-ACCESS  read-only
   STATUS      current
   DESCRIPTION
      "Path: pbbBridgeGroup.performance.bridging.d7Performance.isidMismatch

       32 bit unsigned wrappable counter."
   ::= {pr1645v2PbbBGriMVBridgingD7PerformanceEntry 218103808}

pr1645v2PbbBGriMVBridgingD7PerformanceLoopsDetected OBJECT-TYPE
   SYNTAX      Counter32
   MAX-ACCESS  read-only
   STATUS      current
   DESCRIPTION
      "Path: pbbBridgeGroup.performance.bridging.d7Performance.loopsDetected

       32 bit unsigned wrappable counter."
   ::= {pr1645v2PbbBGriMVBridgingD7PerformanceEntry 234881024}


pr1645v2PbbBGriMVH2Perf OBJECT IDENTIFIER ::= {pr1645v2PbbBGriMV 91}

pr1645v2PbbBGriMVH2PerfSSCTable OBJECT-TYPE
   SYNTAX      SEQUENCE OF Pr1645v2PbbBGriMVH2PerfEntry
   MAX-ACCESS  not-accessible
   STATUS      current
   DESCRIPTION
      "2 hour bridge stats"
   ::= {pr1645v2PbbBGriMVH2Perf 1}

pr1645v2PbbBGriMVH2PerfEntry OBJECT-TYPE
   SYNTAX      Pr1645v2PbbBGriMVH2PerfEntry
   MAX-ACCESS  not-accessible
   STATUS      current
   DESCRIPTION
      ""
   INDEX      { pr1645v2PbbBGriMVH2PerfGlobalIx,
                pr1645v2PbbBGriMVH2PerfTableIx }
   ::= {pr1645v2PbbBGriMVH2PerfSSCTable 1}

Pr1645v2PbbBGriMVH2PerfEntry ::=
   SEQUENCE
      {
      pr1645v2PbbBGriMVH2PerfGlobalIx
         GlobalIndex,
      pr1645v2PbbBGriMVH2PerfTableIx
         TableIndex,
      pr1645v2PbbBGriMVH2PerfSysUpTime
         TimeTicks,
      pr1645v2PbbBGriMVH2PerfRxPkts
         Counter32,
      pr1645v2PbbBGriMVH2PerfTxPkts
         Counter32,
      pr1645v2PbbBGriMVH2PerfDiscards
         Counter32,
      pr1645v2PbbBGriMVH2PerfFloods
         Counter32,
      pr1645v2PbbBGriMVH2PerfBroadcasts
         Counter32,
      pr1645v2PbbBGriMVH2PerfMulticasts
         Counter32,
      pr1645v2PbbBGriMVH2PerfCacheSizeOverflows
         Counter32,
      pr1645v2PbbBGriMVH2PerfStaticCacheViolations
         Counter32,
      pr1645v2PbbBGriMVH2PerfCacheRelearns
         Counter32,
      pr1645v2PbbBGriMVH2PerfCacheRelearnDrops
         Counter32,
      pr1645v2PbbBGriMVH2PerfCacheBMacRelearns
         Counter32,
      pr1645v2PbbBGriMVH2PerfIsidMismatch
         Counter32,
      pr1645v2PbbBGriMVH2PerfLoopsDetected
         Counter32
      }

pr1645v2PbbBGriMVH2PerfGlobalIx OBJECT-TYPE
   SYNTAX      GlobalIndex
   MAX-ACCESS  not-accessible
   STATUS      current
   DESCRIPTION
      "The value of the tlsCntTreeGlobalIndex of the MANAGED OBJECT."
   ::= {pr1645v2PbbBGriMVH2PerfEntry 10}

pr1645v2PbbBGriMVH2PerfTableIx OBJECT-TYPE
   SYNTAX      TableIndex
   MAX-ACCESS  not-accessible
   STATUS      current
   DESCRIPTION
      ""
   ::= {pr1645v2PbbBGriMVH2PerfEntry 11}

pr1645v2PbbBGriMVH2PerfSysUpTime OBJECT-TYPE
   SYNTAX      TimeTicks
   MAX-ACCESS  read-only
   STATUS      current
   DESCRIPTION
      "Path: pbbBridgeGroup.performance.h2Performance.sysUpTime

       Time in centi-second."
   ::= {pr1645v2PbbBGriMVH2PerfEntry 16777216}

pr1645v2PbbBGriMVH2PerfRxPkts OBJECT-TYPE
   SYNTAX      Counter32
   MAX-ACCESS  read-only
   STATUS      current
   DESCRIPTION
      "Path: pbbBridgeGroup.performance.h2Performance.rxPkts

       32 bit unsigned wrappable counter."
   ::= {pr1645v2PbbBGriMVH2PerfEntry 33554432}

pr1645v2PbbBGriMVH2PerfTxPkts OBJECT-TYPE
   SYNTAX      Counter32
   MAX-ACCESS  read-only
   STATUS      current
   DESCRIPTION
      "Path: pbbBridgeGroup.performance.h2Performance.txPkts

       32 bit unsigned wrappable counter."
   ::= {pr1645v2PbbBGriMVH2PerfEntry 50331648}

pr1645v2PbbBGriMVH2PerfDiscards OBJECT-TYPE
   SYNTAX      Counter32
   MAX-ACCESS  read-only
   STATUS      current
   DESCRIPTION
      "Path: pbbBridgeGroup.performance.h2Performance.discards

       32 bit unsigned wrappable counter."
   ::= {pr1645v2PbbBGriMVH2PerfEntry 67108864}

pr1645v2PbbBGriMVH2PerfFloods OBJECT-TYPE
   SYNTAX      Counter32
   MAX-ACCESS  read-only
   STATUS      current
   DESCRIPTION
      "Path: pbbBridgeGroup.performance.h2Performance.floods

       32 bit unsigned wrappable counter."
   ::= {pr1645v2PbbBGriMVH2PerfEntry 83886080}

pr1645v2PbbBGriMVH2PerfBroadcasts OBJECT-TYPE
   SYNTAX      Counter32
   MAX-ACCESS  read-only
   STATUS      current
   DESCRIPTION
      "Path: pbbBridgeGroup.performance.h2Performance.broadcasts

       32 bit unsigned wrappable counter."
   ::= {pr1645v2PbbBGriMVH2PerfEntry 100663296}

pr1645v2PbbBGriMVH2PerfMulticasts OBJECT-TYPE
   SYNTAX      Counter32
   MAX-ACCESS  read-only
   STATUS      current
   DESCRIPTION
      "Path: pbbBridgeGroup.performance.h2Performance.multicasts

       32 bit unsigned wrappable counter."
   ::= {pr1645v2PbbBGriMVH2PerfEntry 117440512}

pr1645v2PbbBGriMVH2PerfCacheSizeOverflows OBJECT-TYPE
   SYNTAX      Counter32
   MAX-ACCESS  read-only
   STATUS      current
   DESCRIPTION
      "Path: pbbBridgeGroup.performance.h2Performance.cacheSizeOverflows

       32 bit unsigned wrappable counter."
   ::= {pr1645v2PbbBGriMVH2PerfEntry 134217728}

pr1645v2PbbBGriMVH2PerfStaticCacheViolations OBJECT-TYPE
   SYNTAX      Counter32
   MAX-ACCESS  read-only
   STATUS      current
   DESCRIPTION
      "Path: pbbBridgeGroup.performance.h2Performance.staticCacheViolations

       32 bit unsigned wrappable counter."
   ::= {pr1645v2PbbBGriMVH2PerfEntry 150994944}

pr1645v2PbbBGriMVH2PerfCacheRelearns OBJECT-TYPE
   SYNTAX      Counter32
   MAX-ACCESS  read-only
   STATUS      current
   DESCRIPTION
      "Path: pbbBridgeGroup.performance.h2Performance.cacheRelearns

       32 bit unsigned wrappable counter."
   ::= {pr1645v2PbbBGriMVH2PerfEntry 167772160}

pr1645v2PbbBGriMVH2PerfCacheRelearnDrops OBJECT-TYPE
   SYNTAX      Counter32
   MAX-ACCESS  read-only
   STATUS      current
   DESCRIPTION
      "Path: pbbBridgeGroup.performance.h2Performance.cacheRelearnDrops

       32 bit unsigned wrappable counter."
   ::= {pr1645v2PbbBGriMVH2PerfEntry 184549376}

pr1645v2PbbBGriMVH2PerfCacheBMacRelearns OBJECT-TYPE
   SYNTAX      Counter32
   MAX-ACCESS  read-only
   STATUS      current
   DESCRIPTION
      "Path: pbbBridgeGroup.performance.h2Performance.cacheBMacRelearns

       32 bit unsigned wrappable counter."
   ::= {pr1645v2PbbBGriMVH2PerfEntry 201326592}

pr1645v2PbbBGriMVH2PerfIsidMismatch OBJECT-TYPE
   SYNTAX      Counter32
   MAX-ACCESS  read-only
   STATUS      current
   DESCRIPTION
      "Path: pbbBridgeGroup.performance.h2Performance.isidMismatch

       32 bit unsigned wrappable counter."
   ::= {pr1645v2PbbBGriMVH2PerfEntry 218103808}

pr1645v2PbbBGriMVH2PerfLoopsDetected OBJECT-TYPE
   SYNTAX      Counter32
   MAX-ACCESS  read-only
   STATUS      current
   DESCRIPTION
      "Path: pbbBridgeGroup.performance.h2Performance.loopsDetected

       32 bit unsigned wrappable counter."
   ::= {pr1645v2PbbBGriMVH2PerfEntry 234881024}


pr1645v2PbbBGriMVH24Perf OBJECT IDENTIFIER ::= {pr1645v2PbbBGriMV 92}

pr1645v2PbbBGriMVH24PerfSSCTable OBJECT-TYPE
   SYNTAX      SEQUENCE OF Pr1645v2PbbBGriMVH24PerfEntry
   MAX-ACCESS  not-accessible
   STATUS      current
   DESCRIPTION
      "24 hour bridge stats"
   ::= {pr1645v2PbbBGriMVH24Perf 1}

pr1645v2PbbBGriMVH24PerfEntry OBJECT-TYPE
   SYNTAX      Pr1645v2PbbBGriMVH24PerfEntry
   MAX-ACCESS  not-accessible
   STATUS      current
   DESCRIPTION
      ""
   INDEX      { pr1645v2PbbBGriMVH24PerfGlobalIx,
                pr1645v2PbbBGriMVH24PerfTableIx }
   ::= {pr1645v2PbbBGriMVH24PerfSSCTable 1}

Pr1645v2PbbBGriMVH24PerfEntry ::=
   SEQUENCE
      {
      pr1645v2PbbBGriMVH24PerfGlobalIx
         GlobalIndex,
      pr1645v2PbbBGriMVH24PerfTableIx
         TableIndex,
      pr1645v2PbbBGriMVH24PerfSysUpTime
         TimeTicks,
      pr1645v2PbbBGriMVH24PerfRxPkts
         Counter32,
      pr1645v2PbbBGriMVH24PerfTxPkts
         Counter32,
      pr1645v2PbbBGriMVH24PerfDiscards
         Counter32,
      pr1645v2PbbBGriMVH24PerfFloods
         Counter32,
      pr1645v2PbbBGriMVH24PerfBroadcasts
         Counter32,
      pr1645v2PbbBGriMVH24PerfMulticasts
         Counter32,
      pr1645v2PbbBGriMVH24PerfCacheSizeOverflows
         Counter32,
      pr1645v2PbbBGriMVH24PerfStaticCacheViolations
         Counter32,
      pr1645v2PbbBGriMVH24PerfCacheRelearns
         Counter32,
      pr1645v2PbbBGriMVH24PerfCacheRelearnDrops
         Counter32,
      pr1645v2PbbBGriMVH24PerfCacheBMacRelearns
         Counter32,
      pr1645v2PbbBGriMVH24PerfIsidMismatch
         Counter32,
      pr1645v2PbbBGriMVH24PerfLoopsDetected
         Counter32
      }

pr1645v2PbbBGriMVH24PerfGlobalIx OBJECT-TYPE
   SYNTAX      GlobalIndex
   MAX-ACCESS  not-accessible
   STATUS      current
   DESCRIPTION
      "The value of the tlsCntTreeGlobalIndex of the MANAGED OBJECT."
   ::= {pr1645v2PbbBGriMVH24PerfEntry 10}

pr1645v2PbbBGriMVH24PerfTableIx OBJECT-TYPE
   SYNTAX      TableIndex
   MAX-ACCESS  not-accessible
   STATUS      current
   DESCRIPTION
      ""
   ::= {pr1645v2PbbBGriMVH24PerfEntry 11}

pr1645v2PbbBGriMVH24PerfSysUpTime OBJECT-TYPE
   SYNTAX      TimeTicks
   MAX-ACCESS  read-only
   STATUS      current
   DESCRIPTION
      "Path: pbbBridgeGroup.performance.h24Performance.sysUpTime

       Time in centi-second."
   ::= {pr1645v2PbbBGriMVH24PerfEntry 16777216}

pr1645v2PbbBGriMVH24PerfRxPkts OBJECT-TYPE
   SYNTAX      Counter32
   MAX-ACCESS  read-only
   STATUS      current
   DESCRIPTION
      "Path: pbbBridgeGroup.performance.h24Performance.rxPkts

       32 bit unsigned wrappable counter."
   ::= {pr1645v2PbbBGriMVH24PerfEntry 33554432}

pr1645v2PbbBGriMVH24PerfTxPkts OBJECT-TYPE
   SYNTAX      Counter32
   MAX-ACCESS  read-only
   STATUS      current
   DESCRIPTION
      "Path: pbbBridgeGroup.performance.h24Performance.txPkts

       32 bit unsigned wrappable counter."
   ::= {pr1645v2PbbBGriMVH24PerfEntry 50331648}

pr1645v2PbbBGriMVH24PerfDiscards OBJECT-TYPE
   SYNTAX      Counter32
   MAX-ACCESS  read-only
   STATUS      current
   DESCRIPTION
      "Path: pbbBridgeGroup.performance.h24Performance.discards

       32 bit unsigned wrappable counter."
   ::= {pr1645v2PbbBGriMVH24PerfEntry 67108864}

pr1645v2PbbBGriMVH24PerfFloods OBJECT-TYPE
   SYNTAX      Counter32
   MAX-ACCESS  read-only
   STATUS      current
   DESCRIPTION
      "Path: pbbBridgeGroup.performance.h24Performance.floods

       32 bit unsigned wrappable counter."
   ::= {pr1645v2PbbBGriMVH24PerfEntry 83886080}

pr1645v2PbbBGriMVH24PerfBroadcasts OBJECT-TYPE
   SYNTAX      Counter32
   MAX-ACCESS  read-only
   STATUS      current
   DESCRIPTION
      "Path: pbbBridgeGroup.performance.h24Performance.broadcasts

       32 bit unsigned wrappable counter."
   ::= {pr1645v2PbbBGriMVH24PerfEntry 100663296}

pr1645v2PbbBGriMVH24PerfMulticasts OBJECT-TYPE
   SYNTAX      Counter32
   MAX-ACCESS  read-only
   STATUS      current
   DESCRIPTION
      "Path: pbbBridgeGroup.performance.h24Performance.multicasts

       32 bit unsigned wrappable counter."
   ::= {pr1645v2PbbBGriMVH24PerfEntry 117440512}

pr1645v2PbbBGriMVH24PerfCacheSizeOverflows OBJECT-TYPE
   SYNTAX      Counter32
   MAX-ACCESS  read-only
   STATUS      current
   DESCRIPTION
      "Path: pbbBridgeGroup.performance.h24Performance.cacheSizeOverflows

       32 bit unsigned wrappable counter."
   ::= {pr1645v2PbbBGriMVH24PerfEntry 134217728}

pr1645v2PbbBGriMVH24PerfStaticCacheViolations OBJECT-TYPE
   SYNTAX      Counter32
   MAX-ACCESS  read-only
   STATUS      current
   DESCRIPTION
      "Path: pbbBridgeGroup.performance.h24Performance.staticCacheViolations

       32 bit unsigned wrappable counter."
   ::= {pr1645v2PbbBGriMVH24PerfEntry 150994944}

pr1645v2PbbBGriMVH24PerfCacheRelearns OBJECT-TYPE
   SYNTAX      Counter32
   MAX-ACCESS  read-only
   STATUS      current
   DESCRIPTION
      "Path: pbbBridgeGroup.performance.h24Performance.cacheRelearns

       32 bit unsigned wrappable counter."
   ::= {pr1645v2PbbBGriMVH24PerfEntry 167772160}

pr1645v2PbbBGriMVH24PerfCacheRelearnDrops OBJECT-TYPE
   SYNTAX      Counter32
   MAX-ACCESS  read-only
   STATUS      current
   DESCRIPTION
      "Path: pbbBridgeGroup.performance.h24Performance.cacheRelearnDrops

       32 bit unsigned wrappable counter."
   ::= {pr1645v2PbbBGriMVH24PerfEntry 184549376}

pr1645v2PbbBGriMVH24PerfCacheBMacRelearns OBJECT-TYPE
   SYNTAX      Counter32
   MAX-ACCESS  read-only
   STATUS      current
   DESCRIPTION
      "Path: pbbBridgeGroup.performance.h24Performance.cacheBMacRelearns

       32 bit unsigned wrappable counter."
   ::= {pr1645v2PbbBGriMVH24PerfEntry 201326592}

pr1645v2PbbBGriMVH24PerfIsidMismatch OBJECT-TYPE
   SYNTAX      Counter32
   MAX-ACCESS  read-only
   STATUS      current
   DESCRIPTION
      "Path: pbbBridgeGroup.performance.h24Performance.isidMismatch

       32 bit unsigned wrappable counter."
   ::= {pr1645v2PbbBGriMVH24PerfEntry 218103808}

pr1645v2PbbBGriMVH24PerfLoopsDetected OBJECT-TYPE
   SYNTAX      Counter32
   MAX-ACCESS  read-only
   STATUS      current
   DESCRIPTION
      "Path: pbbBridgeGroup.performance.h24Performance.loopsDetected

       32 bit unsigned wrappable counter."
   ::= {pr1645v2PbbBGriMVH24PerfEntry 234881024}


pr1645v2PbbBGriMVD7Perf OBJECT IDENTIFIER ::= {pr1645v2PbbBGriMV 93}

pr1645v2PbbBGriMVD7PerfSSCTable OBJECT-TYPE
   SYNTAX      SEQUENCE OF Pr1645v2PbbBGriMVD7PerfEntry
   MAX-ACCESS  not-accessible
   STATUS      current
   DESCRIPTION
      "7 days bridge stats"
   ::= {pr1645v2PbbBGriMVD7Perf 1}

pr1645v2PbbBGriMVD7PerfEntry OBJECT-TYPE
   SYNTAX      Pr1645v2PbbBGriMVD7PerfEntry
   MAX-ACCESS  not-accessible
   STATUS      current
   DESCRIPTION
      ""
   INDEX      { pr1645v2PbbBGriMVD7PerfGlobalIx,
                pr1645v2PbbBGriMVD7PerfTableIx }
   ::= {pr1645v2PbbBGriMVD7PerfSSCTable 1}

Pr1645v2PbbBGriMVD7PerfEntry ::=
   SEQUENCE
      {
      pr1645v2PbbBGriMVD7PerfGlobalIx
         GlobalIndex,
      pr1645v2PbbBGriMVD7PerfTableIx
         TableIndex,
      pr1645v2PbbBGriMVD7PerfSysUpTime
         TimeTicks,
      pr1645v2PbbBGriMVD7PerfRxPkts
         Counter32,
      pr1645v2PbbBGriMVD7PerfTxPkts
         Counter32,
      pr1645v2PbbBGriMVD7PerfDiscards
         Counter32,
      pr1645v2PbbBGriMVD7PerfFloods
         Counter32,
      pr1645v2PbbBGriMVD7PerfBroadcasts
         Counter32,
      pr1645v2PbbBGriMVD7PerfMulticasts
         Counter32,
      pr1645v2PbbBGriMVD7PerfCacheSizeOverflows
         Counter32,
      pr1645v2PbbBGriMVD7PerfStaticCacheViolations
         Counter32,
      pr1645v2PbbBGriMVD7PerfCacheRelearns
         Counter32,
      pr1645v2PbbBGriMVD7PerfCacheRelearnDrops
         Counter32,
      pr1645v2PbbBGriMVD7PerfCacheBMacRelearns
         Counter32,
      pr1645v2PbbBGriMVD7PerfIsidMismatch
         Counter32,
      pr1645v2PbbBGriMVD7PerfLoopsDetected
         Counter32
      }

pr1645v2PbbBGriMVD7PerfGlobalIx OBJECT-TYPE
   SYNTAX      GlobalIndex
   MAX-ACCESS  not-accessible
   STATUS      current
   DESCRIPTION
      "The value of the tlsCntTreeGlobalIndex of the MANAGED OBJECT."
   ::= {pr1645v2PbbBGriMVD7PerfEntry 10}

pr1645v2PbbBGriMVD7PerfTableIx OBJECT-TYPE
   SYNTAX      TableIndex
   MAX-ACCESS  not-accessible
   STATUS      current
   DESCRIPTION
      ""
   ::= {pr1645v2PbbBGriMVD7PerfEntry 11}

pr1645v2PbbBGriMVD7PerfSysUpTime OBJECT-TYPE
   SYNTAX      TimeTicks
   MAX-ACCESS  read-only
   STATUS      current
   DESCRIPTION
      "Path: pbbBridgeGroup.performance.d7Performance.sysUpTime

       Time in centi-second."
   ::= {pr1645v2PbbBGriMVD7PerfEntry 16777216}

pr1645v2PbbBGriMVD7PerfRxPkts OBJECT-TYPE
   SYNTAX      Counter32
   MAX-ACCESS  read-only
   STATUS      current
   DESCRIPTION
      "Path: pbbBridgeGroup.performance.d7Performance.rxPkts

       32 bit unsigned wrappable counter."
   ::= {pr1645v2PbbBGriMVD7PerfEntry 33554432}

pr1645v2PbbBGriMVD7PerfTxPkts OBJECT-TYPE
   SYNTAX      Counter32
   MAX-ACCESS  read-only
   STATUS      current
   DESCRIPTION
      "Path: pbbBridgeGroup.performance.d7Performance.txPkts

       32 bit unsigned wrappable counter."
   ::= {pr1645v2PbbBGriMVD7PerfEntry 50331648}

pr1645v2PbbBGriMVD7PerfDiscards OBJECT-TYPE
   SYNTAX      Counter32
   MAX-ACCESS  read-only
   STATUS      current
   DESCRIPTION
      "Path: pbbBridgeGroup.performance.d7Performance.discards

       32 bit unsigned wrappable counter."
   ::= {pr1645v2PbbBGriMVD7PerfEntry 67108864}

pr1645v2PbbBGriMVD7PerfFloods OBJECT-TYPE
   SYNTAX      Counter32
   MAX-ACCESS  read-only
   STATUS      current
   DESCRIPTION
      "Path: pbbBridgeGroup.performance.d7Performance.floods

       32 bit unsigned wrappable counter."
   ::= {pr1645v2PbbBGriMVD7PerfEntry 83886080}

pr1645v2PbbBGriMVD7PerfBroadcasts OBJECT-TYPE
   SYNTAX      Counter32
   MAX-ACCESS  read-only
   STATUS      current
   DESCRIPTION
      "Path: pbbBridgeGroup.performance.d7Performance.broadcasts

       32 bit unsigned wrappable counter."
   ::= {pr1645v2PbbBGriMVD7PerfEntry 100663296}

pr1645v2PbbBGriMVD7PerfMulticasts OBJECT-TYPE
   SYNTAX      Counter32
   MAX-ACCESS  read-only
   STATUS      current
   DESCRIPTION
      "Path: pbbBridgeGroup.performance.d7Performance.multicasts

       32 bit unsigned wrappable counter."
   ::= {pr1645v2PbbBGriMVD7PerfEntry 117440512}

pr1645v2PbbBGriMVD7PerfCacheSizeOverflows OBJECT-TYPE
   SYNTAX      Counter32
   MAX-ACCESS  read-only
   STATUS      current
   DESCRIPTION
      "Path: pbbBridgeGroup.performance.d7Performance.cacheSizeOverflows

       32 bit unsigned wrappable counter."
   ::= {pr1645v2PbbBGriMVD7PerfEntry 134217728}

pr1645v2PbbBGriMVD7PerfStaticCacheViolations OBJECT-TYPE
   SYNTAX      Counter32
   MAX-ACCESS  read-only
   STATUS      current
   DESCRIPTION
      "Path: pbbBridgeGroup.performance.d7Performance.staticCacheViolations

       32 bit unsigned wrappable counter."
   ::= {pr1645v2PbbBGriMVD7PerfEntry 150994944}

pr1645v2PbbBGriMVD7PerfCacheRelearns OBJECT-TYPE
   SYNTAX      Counter32
   MAX-ACCESS  read-only
   STATUS      current
   DESCRIPTION
      "Path: pbbBridgeGroup.performance.d7Performance.cacheRelearns

       32 bit unsigned wrappable counter."
   ::= {pr1645v2PbbBGriMVD7PerfEntry 167772160}

pr1645v2PbbBGriMVD7PerfCacheRelearnDrops OBJECT-TYPE
   SYNTAX      Counter32
   MAX-ACCESS  read-only
   STATUS      current
   DESCRIPTION
      "Path: pbbBridgeGroup.performance.d7Performance.cacheRelearnDrops

       32 bit unsigned wrappable counter."
   ::= {pr1645v2PbbBGriMVD7PerfEntry 184549376}

pr1645v2PbbBGriMVD7PerfCacheBMacRelearns OBJECT-TYPE
   SYNTAX      Counter32
   MAX-ACCESS  read-only
   STATUS      current
   DESCRIPTION
      "Path: pbbBridgeGroup.performance.d7Performance.cacheBMacRelearns

       32 bit unsigned wrappable counter."
   ::= {pr1645v2PbbBGriMVD7PerfEntry 201326592}

pr1645v2PbbBGriMVD7PerfIsidMismatch OBJECT-TYPE
   SYNTAX      Counter32
   MAX-ACCESS  read-only
   STATUS      current
   DESCRIPTION
      "Path: pbbBridgeGroup.performance.d7Performance.isidMismatch

       32 bit unsigned wrappable counter."
   ::= {pr1645v2PbbBGriMVD7PerfEntry 218103808}

pr1645v2PbbBGriMVD7PerfLoopsDetected OBJECT-TYPE
   SYNTAX      Counter32
   MAX-ACCESS  read-only
   STATUS      current
   DESCRIPTION
      "Path: pbbBridgeGroup.performance.d7Performance.loopsDetected

       32 bit unsigned wrappable counter."
   ::= {pr1645v2PbbBGriMVD7PerfEntry 234881024}



fr1645v2PbbBGriMV OBJECT IDENTIFIER ::= {r1645v2PbbBGriMV 13}


fr1645v2PbbBGriMVAlarm OBJECT IDENTIFIER ::= {fr1645v2PbbBGriMV 207}

fr1645v2PbbBGriMVAlarmSSCTable OBJECT-TYPE
   SYNTAX      SEQUENCE OF Fr1645v2PbbBGriMVAlarmEntry
   MAX-ACCESS  not-accessible
   STATUS      current
   DESCRIPTION
      "bridge group alarmInfo"
   ::= {fr1645v2PbbBGriMVAlarm 1}

fr1645v2PbbBGriMVAlarmEntry OBJECT-TYPE
   SYNTAX      Fr1645v2PbbBGriMVAlarmEntry
   MAX-ACCESS  not-accessible
   STATUS      current
   DESCRIPTION
      ""
   INDEX      { fr1645v2PbbBGriMVAlarmGlobalIx }
   ::= {fr1645v2PbbBGriMVAlarmSSCTable 1}

Fr1645v2PbbBGriMVAlarmEntry ::=
   SEQUENCE
      {
      fr1645v2PbbBGriMVAlarmGlobalIx
         GlobalIndex,
      fr1645v2PbbBGriMVAlarmDiscriminator
         Integer32,
      fr1645v2PbbBGriMVAlarmCurrent
         Integer32,
      fr1645v2PbbBGriMVAlarmPrevious
         Integer32,
      fr1645v2PbbBGriMVAlarmMask
         Integer32,
      fr1645v2PbbBGriMVAlarmLevelLinkDown
         Integer32,
      fr1645v2PbbBGriMVAlarmLevelLinkShutdown
         Integer32
      }

fr1645v2PbbBGriMVAlarmGlobalIx OBJECT-TYPE
   SYNTAX      GlobalIndex
   MAX-ACCESS  not-accessible
   STATUS      current
   DESCRIPTION
      "The value of the tlsCntTreeGlobalIndex of the MANAGED OBJECT."
   ::= {fr1645v2PbbBGriMVAlarmEntry 10}

fr1645v2PbbBGriMVAlarmDiscriminator OBJECT-TYPE
   SYNTAX      Integer32
   MAX-ACCESS  read-only
   STATUS      current
   DESCRIPTION
      "Path: pbbBridgeGroup.alarms.alarmInfo.discriminator"
   ::= {fr1645v2PbbBGriMVAlarmEntry 16777216}

fr1645v2PbbBGriMVAlarmCurrent OBJECT-TYPE
   SYNTAX      Integer32
   MAX-ACCESS  read-only
   STATUS      current
   DESCRIPTION
      "Path: pbbBridgeGroup.alarms.alarmInfo.currentAlarms

       Bit meanings:
               bit 0 = linkDown,
               bit 1 = linkShutdown"
   ::= {fr1645v2PbbBGriMVAlarmEntry 33554432}

fr1645v2PbbBGriMVAlarmPrevious OBJECT-TYPE
   SYNTAX      Integer32
   MAX-ACCESS  read-only
   STATUS      current
   DESCRIPTION
      "Path: pbbBridgeGroup.alarms.alarmInfo.previousAlarms

       Bit meanings:
               bit 0 = linkDown,
               bit 1 = linkShutdown"
   ::= {fr1645v2PbbBGriMVAlarmEntry 50331648}

fr1645v2PbbBGriMVAlarmMask OBJECT-TYPE
   SYNTAX      Integer32
   MAX-ACCESS  read-only
   STATUS      current
   DESCRIPTION
      "Path: pbbBridgeGroup.alarms.alarmInfo.alarmMask

       Bit meanings:
               bit 0 = linkDown,
               bit 1 = linkShutdown"
   ::= {fr1645v2PbbBGriMVAlarmEntry 67108864}

fr1645v2PbbBGriMVAlarmLevelLinkDown OBJECT-TYPE
   SYNTAX      Integer32
   MAX-ACCESS  read-only
   STATUS      current
   DESCRIPTION
      "Path: pbbBridgeGroup.alarms.alarmInfo.alarmLevel.linkDown"
   ::= {fr1645v2PbbBGriMVAlarmEntry 83951616}

fr1645v2PbbBGriMVAlarmLevelLinkShutdown OBJECT-TYPE
   SYNTAX      Integer32
   MAX-ACCESS  read-only
   STATUS      current
   DESCRIPTION
      "Path: pbbBridgeGroup.alarms.alarmInfo.alarmLevel.linkShutdown"
   ::= {fr1645v2PbbBGriMVAlarmEntry 84017152}


fr1645v2PbbBGriMVAlarmE2 OBJECT IDENTIFIER ::= {fr1645v2PbbBGriMVAlarm 2}

fr1645v2PbbBGriMVAlarmE2Entry OBJECT IDENTIFIER ::= {fr1645v2PbbBGriMVAlarmE2 1}

fr1645v2PbbBGriMVAlarmE2LinkDown OBJECT IDENTIFIER ::= {fr1645v2PbbBGriMVAlarmE2Entry 10}

fr1645v2PbbBGriMVAlarmE2LinkDownPfx OBJECT IDENTIFIER ::= {fr1645v2PbbBGriMVAlarmE2LinkDown 0}

fr1645v2PbbBGriMVAlarmE2LinkDownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'pbbBridgeGroupInstanceMultiVlansMacEth1'
                (root='router1645') has changed from the ON to the OFF state."
   ::= {fr1645v2PbbBGriMVAlarmE2LinkDownPfx 1}

fr1645v2PbbBGriMVAlarmE2LinkDownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkDown'
                representing an alarm condition in the alarm word
                of attribute 'alarmInfo' of managed object 'pbbBridgeGroupInstanceMultiVlansMacEth1'
                (root='router1645') has changed from the OFF to the ON state."
   ::= {fr1645v2PbbBGriMVAlarmE2LinkDownPfx 2}

fr1645v2PbbBGriMVAlarmE2LinkShutdown OBJECT IDENTIFIER ::= {fr1645v2PbbBGriMVAlarmE2Entry 11}

fr1645v2PbbBGriMVAlarmE2LinkShutdownPfx OBJECT IDENTIFIER ::= {fr1645v2PbbBGriMVAlarmE2LinkShutdown 0}

fr1645v2PbbBGriMVAlarmE2LinkShutdownOff NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'pbbBridgeGroupInstanceMultiVlansMacEth1'
                (root='router1645') has changed from the ON to the OFF state."
   ::= {fr1645v2PbbBGriMVAlarmE2LinkShutdownPfx 1}

fr1645v2PbbBGriMVAlarmE2LinkShutdownOn NOTIFICATION-TYPE 
   OBJECTS     { ifIndex,
                 tlsCntTreeGlobalIndex,
                 tlsTrapDescription,
                 tlsSeverityLevel,
                 tlsTrapSeverityLevel
               }
   STATUS      current
   DESCRIPTION "This trap signifies that bit 'linkShutdown'
                representing an alarm condition in the alarm word
                of attribute 'alarmInfo' of managed object 'pbbBridgeGroupInstanceMultiVlansMacEth1'
                (root='router1645') has changed from the OFF to the ON state."
   ::= {fr1645v2PbbBGriMVAlarmE2LinkShutdownPfx 2}



ar1645v2PbbBGriMV OBJECT IDENTIFIER ::= {r1645v2PbbBGriMV 16}


ar1645v2PbbBGriMVClearCounters OBJECT IDENTIFIER ::= {ar1645v2PbbBGriMV 263}

ar1645v2PbbBGriMVClearCountersTable OBJECT-TYPE
   SYNTAX      SEQUENCE OF Ar1645v2PbbBGriMVClearCountersEntry
   MAX-ACCESS  not-accessible
   STATUS      current
   DESCRIPTION
      "reset counters"
   ::= {ar1645v2PbbBGriMVClearCounters 1}

ar1645v2PbbBGriMVClearCountersEntry OBJECT-TYPE
   SYNTAX      Ar1645v2PbbBGriMVClearCountersEntry
   MAX-ACCESS  not-accessible
   STATUS      current
   DESCRIPTION
      ""
   INDEX      { ar1645v2PbbBGriMVClearCountersGlobalIx }
   ::= {ar1645v2PbbBGriMVClearCountersTable 1}

Ar1645v2PbbBGriMVClearCountersEntry ::=
   SEQUENCE
      {
      ar1645v2PbbBGriMVClearCountersGlobalIx
         GlobalIndex,
      ar1645v2PbbBGriMVClearCountersValue
         Integer32
      }

ar1645v2PbbBGriMVClearCountersGlobalIx OBJECT-TYPE
   SYNTAX      GlobalIndex
   MAX-ACCESS  not-accessible
   STATUS      current
   DESCRIPTION
      "The value of the tlsCntTreeGlobalIndex of the MANAGED OBJECT."
   ::= {ar1645v2PbbBGriMVClearCountersEntry 10}

ar1645v2PbbBGriMVClearCountersValue OBJECT-TYPE
   SYNTAX      Integer32
   MAX-ACCESS  read-write
   STATUS      current
   DESCRIPTION
      "Path: pbbBridgeGroup.actions.clearCounters"
   ::= {ar1645v2PbbBGriMVClearCountersEntry 2147483648}


ar1645v2PbbBGriMVClearBridgeCache OBJECT IDENTIFIER ::= {ar1645v2PbbBGriMV 20}

ar1645v2PbbBGriMVClearBridgeCacheTable OBJECT-TYPE
   SYNTAX      SEQUENCE OF Ar1645v2PbbBGriMVClearBridgeCacheEntry
   MAX-ACCESS  not-accessible
   STATUS      current
   DESCRIPTION
      "clear all dynamic entries in bridge cache table"
   ::= {ar1645v2PbbBGriMVClearBridgeCache 1}

ar1645v2PbbBGriMVClearBridgeCacheEntry OBJECT-TYPE
   SYNTAX      Ar1645v2PbbBGriMVClearBridgeCacheEntry
   MAX-ACCESS  not-accessible
   STATUS      current
   DESCRIPTION
      ""
   INDEX      { ar1645v2PbbBGriMVClearBridgeCacheGlobalIx }
   ::= {ar1645v2PbbBGriMVClearBridgeCacheTable 1}

Ar1645v2PbbBGriMVClearBridgeCacheEntry ::=
   SEQUENCE
      {
      ar1645v2PbbBGriMVClearBridgeCacheGlobalIx
         GlobalIndex,
      ar1645v2PbbBGriMVClearBridgeCacheValue
         Integer32
      }

ar1645v2PbbBGriMVClearBridgeCacheGlobalIx OBJECT-TYPE
   SYNTAX      GlobalIndex
   MAX-ACCESS  not-accessible
   STATUS      current
   DESCRIPTION
      "The value of the tlsCntTreeGlobalIndex of the MANAGED OBJECT."
   ::= {ar1645v2PbbBGriMVClearBridgeCacheEntry 10}

ar1645v2PbbBGriMVClearBridgeCacheValue OBJECT-TYPE
   SYNTAX      Integer32
   MAX-ACCESS  read-write
   STATUS      current
   DESCRIPTION
      "Path: pbbBridgeGroup.actions.clearBridgeCache"
   ::= {ar1645v2PbbBGriMVClearBridgeCacheEntry 2147483648}


ar1645v2PbbBGriMVBridgeShutdown OBJECT IDENTIFIER ::= {ar1645v2PbbBGriMV 72}

ar1645v2PbbBGriMVBridgeShutdownTable OBJECT-TYPE
   SYNTAX      SEQUENCE OF Ar1645v2PbbBGriMVBridgeShutdownEntry
   MAX-ACCESS  not-accessible
   STATUS      current
   DESCRIPTION
      "shutdown interface manually"
   ::= {ar1645v2PbbBGriMVBridgeShutdown 1}

ar1645v2PbbBGriMVBridgeShutdownEntry OBJECT-TYPE
   SYNTAX      Ar1645v2PbbBGriMVBridgeShutdownEntry
   MAX-ACCESS  not-accessible
   STATUS      current
   DESCRIPTION
      ""
   INDEX      { ar1645v2PbbBGriMVBridgeShutdownGlobalIx }
   ::= {ar1645v2PbbBGriMVBridgeShutdownTable 1}

Ar1645v2PbbBGriMVBridgeShutdownEntry ::=
   SEQUENCE
      {
      ar1645v2PbbBGriMVBridgeShutdownGlobalIx
         GlobalIndex,
      ar1645v2PbbBGriMVBridgeShutdownValue
         Integer32
      }

ar1645v2PbbBGriMVBridgeShutdownGlobalIx OBJECT-TYPE
   SYNTAX      GlobalIndex
   MAX-ACCESS  not-accessible
   STATUS      current
   DESCRIPTION
      "The value of the tlsCntTreeGlobalIndex of the MANAGED OBJECT."
   ::= {ar1645v2PbbBGriMVBridgeShutdownEntry 10}

ar1645v2PbbBGriMVBridgeShutdownValue OBJECT-TYPE
   SYNTAX      Integer32
   MAX-ACCESS  read-write
   STATUS      current
   DESCRIPTION
      "Path: pbbBridgeGroup.actions.bridgeShutdown"
   ::= {ar1645v2PbbBGriMVBridgeShutdownEntry 2147483648}


ar1645v2PbbBGriMVInterface OBJECT IDENTIFIER ::= {ar1645v2PbbBGriMV 73}

ar1645v2PbbBGriMVInterfaceTable OBJECT-TYPE
   SYNTAX      SEQUENCE OF Ar1645v2PbbBGriMVInterfaceEntry
   MAX-ACCESS  not-accessible
   STATUS      current
   DESCRIPTION
      "interface name for action"
   ::= {ar1645v2PbbBGriMVInterface 1}

ar1645v2PbbBGriMVInterfaceEntry OBJECT-TYPE
   SYNTAX      Ar1645v2PbbBGriMVInterfaceEntry
   MAX-ACCESS  not-accessible
   STATUS      current
   DESCRIPTION
      ""
   INDEX      { ar1645v2PbbBGriMVInterfaceGlobalIx }
   ::= {ar1645v2PbbBGriMVInterfaceTable 1}

Ar1645v2PbbBGriMVInterfaceEntry ::=
   SEQUENCE
      {
      ar1645v2PbbBGriMVInterfaceGlobalIx
         GlobalIndex,
      ar1645v2PbbBGriMVInterfaceValue
         DisplayString
      }

ar1645v2PbbBGriMVInterfaceGlobalIx OBJECT-TYPE
   SYNTAX      GlobalIndex
   MAX-ACCESS  not-accessible
   STATUS      current
   DESCRIPTION
      "The value of the tlsCntTreeGlobalIndex of the MANAGED OBJECT."
   ::= {ar1645v2PbbBGriMVInterfaceEntry 10}

ar1645v2PbbBGriMVInterfaceValue OBJECT-TYPE
   SYNTAX      DisplayString
   MAX-ACCESS  read-write
   STATUS      current
   DESCRIPTION
      "Path: pbbBridgeGroup.actions.interface"
   ::= {ar1645v2PbbBGriMVInterfaceEntry 2147483648}


ar1645v2PbbBGriMVBridgeRestart OBJECT IDENTIFIER ::= {ar1645v2PbbBGriMV 70}

ar1645v2PbbBGriMVBridgeRestartTable OBJECT-TYPE
   SYNTAX      SEQUENCE OF Ar1645v2PbbBGriMVBridgeRestartEntry
   MAX-ACCESS  not-accessible
   STATUS      current
   DESCRIPTION
      "restart interface blocked by security"
   ::= {ar1645v2PbbBGriMVBridgeRestart 1}

ar1645v2PbbBGriMVBridgeRestartEntry OBJECT-TYPE
   SYNTAX      Ar1645v2PbbBGriMVBridgeRestartEntry
   MAX-ACCESS  not-accessible
   STATUS      current
   DESCRIPTION
      ""
   INDEX      { ar1645v2PbbBGriMVBridgeRestartGlobalIx }
   ::= {ar1645v2PbbBGriMVBridgeRestartTable 1}

Ar1645v2PbbBGriMVBridgeRestartEntry ::=
   SEQUENCE
      {
      ar1645v2PbbBGriMVBridgeRestartGlobalIx
         GlobalIndex,
      ar1645v2PbbBGriMVBridgeRestartValue
         Integer32
      }

ar1645v2PbbBGriMVBridgeRestartGlobalIx OBJECT-TYPE
   SYNTAX      GlobalIndex
   MAX-ACCESS  not-accessible
   STATUS      current
   DESCRIPTION
      "The value of the tlsCntTreeGlobalIndex of the MANAGED OBJECT."
   ::= {ar1645v2PbbBGriMVBridgeRestartEntry 10}

ar1645v2PbbBGriMVBridgeRestartValue OBJECT-TYPE
   SYNTAX      Integer32
   MAX-ACCESS  read-write
   STATUS      current
   DESCRIPTION
      "Path: pbbBridgeGroup.actions.bridgeRestart"
   ::= {ar1645v2PbbBGriMVBridgeRestartEntry 2147483648}


ar1645v2PbbBGriMVBridgingInterface OBJECT IDENTIFIER ::= {ar1645v2PbbBGriMV 71}

ar1645v2PbbBGriMVBridgingInterfaceTable OBJECT-TYPE
   SYNTAX      SEQUENCE OF Ar1645v2PbbBGriMVBridgingInterfaceEntry
   MAX-ACCESS  not-accessible
   STATUS      current
   DESCRIPTION
      "interface name for action"
   ::= {ar1645v2PbbBGriMVBridgingInterface 1}

ar1645v2PbbBGriMVBridgingInterfaceEntry OBJECT-TYPE
   SYNTAX      Ar1645v2PbbBGriMVBridgingInterfaceEntry
   MAX-ACCESS  not-accessible
   STATUS      current
   DESCRIPTION
      ""
   INDEX      { ar1645v2PbbBGriMVBridgingInterfaceGlobalIx }
   ::= {ar1645v2PbbBGriMVBridgingInterfaceTable 1}

Ar1645v2PbbBGriMVBridgingInterfaceEntry ::=
   SEQUENCE
      {
      ar1645v2PbbBGriMVBridgingInterfaceGlobalIx
         GlobalIndex,
      ar1645v2PbbBGriMVBridgingInterfaceValue
         DisplayString
      }

ar1645v2PbbBGriMVBridgingInterfaceGlobalIx OBJECT-TYPE
   SYNTAX      GlobalIndex
   MAX-ACCESS  not-accessible
   STATUS      current
   DESCRIPTION
      "The value of the tlsCntTreeGlobalIndex of the MANAGED OBJECT."
   ::= {ar1645v2PbbBGriMVBridgingInterfaceEntry 10}

ar1645v2PbbBGriMVBridgingInterfaceValue OBJECT-TYPE
   SYNTAX      DisplayString
   MAX-ACCESS  read-write
   STATUS      current
   DESCRIPTION
      "Path: pbbBridgeGroup.actions.bridgingInterface"
   ::= {ar1645v2PbbBGriMVBridgingInterfaceEntry 2147483648}


ar1645v2PbbBGriMVClearArpCache OBJECT IDENTIFIER ::= {ar1645v2PbbBGriMV 25}

ar1645v2PbbBGriMVClearArpCacheTable OBJECT-TYPE
   SYNTAX      SEQUENCE OF Ar1645v2PbbBGriMVClearArpCacheEntry
   MAX-ACCESS  not-accessible
   STATUS      current
   DESCRIPTION
      "clear all dynamic enties in ARP cache table"
   ::= {ar1645v2PbbBGriMVClearArpCache 1}

ar1645v2PbbBGriMVClearArpCacheEntry OBJECT-TYPE
   SYNTAX      Ar1645v2PbbBGriMVClearArpCacheEntry
   MAX-ACCESS  not-accessible
   STATUS      current
   DESCRIPTION
      ""
   INDEX      { ar1645v2PbbBGriMVClearArpCacheGlobalIx }
   ::= {ar1645v2PbbBGriMVClearArpCacheTable 1}

Ar1645v2PbbBGriMVClearArpCacheEntry ::=
   SEQUENCE
      {
      ar1645v2PbbBGriMVClearArpCacheGlobalIx
         GlobalIndex,
      ar1645v2PbbBGriMVClearArpCacheValue
         Integer32
      }

ar1645v2PbbBGriMVClearArpCacheGlobalIx OBJECT-TYPE
   SYNTAX      GlobalIndex
   MAX-ACCESS  not-accessible
   STATUS      current
   DESCRIPTION
      "The value of the tlsCntTreeGlobalIndex of the MANAGED OBJECT."
   ::= {ar1645v2PbbBGriMVClearArpCacheEntry 10}

ar1645v2PbbBGriMVClearArpCacheValue OBJECT-TYPE
   SYNTAX      Integer32
   MAX-ACCESS  read-write
   STATUS      current
   DESCRIPTION
      "Path: pbbBridgeGroup.actions.clearArpCache"
   ::= {ar1645v2PbbBGriMVClearArpCacheEntry 2147483648}



END
